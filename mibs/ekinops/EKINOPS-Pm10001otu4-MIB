-- *****************************************************************
-- EKINOPS-Pm10001otu4.TXT:  MIB
--
--MIB Part Number:3MI00044AAAA
--MIB Version:03
--
-- Copyright (c) 2016 by Ekinops
-- All rights reserved.
--
-- *****************************************************************

EKINOPS-Pm10001otu4-MIB DEFINITIONS ::= BEGIN

IMPORTS
	ekinops,
	EkiState,
	EkiOnOff,
	EkiMode,
	EkiProtocol,
	EkiApiState,
	EkiSynchroMode,
	EkiMeasureType
			FROM EKINOPS-MIB
        MODULE-IDENTITY,
        OBJECT-TYPE,
        NOTIFICATION-TYPE,
	Unsigned32,
	Integer32,
	Counter32,
	IpAddress
        		FROM SNMPv2-SMI
 	TEXTUAL-CONVENTION,
	DisplayString
                FROM SNMPv2-TC;

modulePm10001otu4 MODULE-IDENTITY
        LAST-UPDATED "201611250000Z"
        ORGANIZATION "Ekinops"
        CONTACT-INFO
         "Ekinops

          3, rue Blaise Pascal
          F-22300 Lannion / FRANCE

          Tel : +33 (0)2 96 05 00 30
          Fax : +33 (0)2 96 48 62 39

          E-mail: support@ekinops.fr"
        DESCRIPTION
          "Creation."

	REVISION "201611250000Z"
	DESCRIPTION
	  "Creation for PM 10001 OTU4"
        ::= { ekinops 82 }



--- *****************************************************
---     LEAF LEVEL 2
--- *****************************************************


pm10001otu4alarms OBJECT IDENTIFIER ::= { modulePm10001otu4 2 }
pm10001otu4AlmOther OBJECT IDENTIFIER ::= { pm10001otu4alarms 1 }
pm10001otu4AlmOtherNurg OBJECT IDENTIFIER ::= { pm10001otu4AlmOther 1 }
pm10001otu4AlmOtherUrg OBJECT IDENTIFIER ::= { pm10001otu4AlmOther 2 }
pm10001otu4AlmOtherCrit OBJECT IDENTIFIER ::= { pm10001otu4AlmOther 3 }

pm10001otu4AlmClient OBJECT IDENTIFIER ::= { pm10001otu4alarms 2 }
pm10001otu4AlmClientNurg OBJECT IDENTIFIER ::= { pm10001otu4AlmClient 1 }
pm10001otu4AlmClientUrg OBJECT IDENTIFIER ::= { pm10001otu4AlmClient 2 }
pm10001otu4AlmClientCrit OBJECT IDENTIFIER ::= { pm10001otu4AlmClient 3 }

pm10001otu4AlmLine OBJECT IDENTIFIER ::= { pm10001otu4alarms 3 }
pm10001otu4AlmLineNurg OBJECT IDENTIFIER ::= { pm10001otu4AlmLine 1 }
pm10001otu4AlmLineUrg OBJECT IDENTIFIER ::= { pm10001otu4AlmLine 2 }
pm10001otu4AlmLineCrit OBJECT IDENTIFIER ::= { pm10001otu4AlmLine 3 }





pm10001otu4measures OBJECT IDENTIFIER ::= { modulePm10001otu4 3 }
pm10001otu4MesrOther OBJECT IDENTIFIER ::= { pm10001otu4measures 1 }
pm10001otu4MesrClient OBJECT IDENTIFIER ::= { pm10001otu4measures 2 }
pm10001otu4MesrLine OBJECT IDENTIFIER ::= { pm10001otu4measures 3 }




pm10001otu4counters OBJECT IDENTIFIER ::= { modulePm10001otu4 4 }
pm10001otu4CntOther OBJECT IDENTIFIER ::= { pm10001otu4counters 1 }
pm10001otu4CntClient OBJECT IDENTIFIER ::= { pm10001otu4counters 2 }
pm10001otu4CntLine OBJECT IDENTIFIER ::= { pm10001otu4counters 3 }


pm10001otu4controlsWrite OBJECT IDENTIFIER ::= { modulePm10001otu4 6 }
pm10001otu4CtrlOther OBJECT IDENTIFIER ::= { pm10001otu4controlsWrite 1 }
pm10001otu4CtrlClient OBJECT IDENTIFIER ::= { pm10001otu4controlsWrite 2 }
pm10001otu4CtrlLine OBJECT IDENTIFIER ::= { pm10001otu4controlsWrite 3 }

pm10001otu4ri OBJECT IDENTIFIER ::= { modulePm10001otu4 7 }
pm10001otu4riTable OBJECT IDENTIFIER ::= { pm10001otu4ri 1 }

pm10001otu4download OBJECT IDENTIFIER ::= { modulePm10001otu4 8 }
pm10001otu4DwlOther OBJECT IDENTIFIER ::= { pm10001otu4download 1 }
pm10001otu4DwlClient OBJECT IDENTIFIER ::= { pm10001otu4download 2 }
pm10001otu4DwlLine OBJECT IDENTIFIER ::= { pm10001otu4download 3 }


pm10001otu4Config OBJECT IDENTIFIER ::= { modulePm10001otu4 9 }

pm10001otu4traps OBJECT IDENTIFIER ::= { modulePm10001otu4 10 }



pm10001otu4Monitoring OBJECT IDENTIFIER ::= { modulePm10001otu4 11}

pm10001otu4MonOther OBJECT IDENTIFIER ::= { pm10001otu4Monitoring 1 }
pm10001otu4MonRmon OBJECT IDENTIFIER ::= { pm10001otu4MonOther 3 }

pm10001otu4MonClient OBJECT IDENTIFIER ::= { pm10001otu4Monitoring 2 }
pm10001otu4MonClientRmonCounter OBJECT IDENTIFIER ::= { pm10001otu4MonClient 4 }


pm10001otu4MonPerfOther OBJECT IDENTIFIER ::= { pm10001otu4Monitoring 5 }
pm10001otu4MonPerfSync OBJECT IDENTIFIER ::= { pm10001otu4MonPerfOther 1 }
pm10001otu4MonPerfTimeStamp OBJECT IDENTIFIER ::= { pm10001otu4MonPerfOther 2 }


pm10001otu4MonPerfClient OBJECT IDENTIFIER ::= { pm10001otu4Monitoring 6 }

pm10001otu4MonPerfLine OBJECT IDENTIFIER ::= { pm10001otu4Monitoring 7 }



--- *****************************************************
--- $$$$$$$$$$$$$$$$$$$$$$$$$$$$$$$$$$$$$$$$$$$$$$$$$$$$$
---     TEXTUAL-CONVENTION
--- $$$$$$$$$$$$$$$$$$$$$$$$$$$$$$$$$$$$$$$$$$$$$$$$$$$$$
--- *****************************************************

Pm10001otu4MultiRate ::= TEXTUAL-CONVENTION
    STATUS      current
    DESCRIPTION "different rate for a client port"
    SYNTAX INTEGER {
		rate100Mhz(0),
		rate250Mhz(1),
		rate500Mhz(2),
		rate1Ghz(3)
           }

Pm10001otu4OtxMode ::= TEXTUAL-CONVENTION
    STATUS      current
    DESCRIPTION "Different modes on OTX-TLH on client and line ports"
    SYNTAX INTEGER {
		otx80mode(1),
		otx60mode(2),
		otxadjustmode(4)
           }

Pm10001otu4OtxGrid ::= TEXTUAL-CONVENTION
    STATUS      current
    DESCRIPTION "Different grids on OTX-TLH on client and line ports"
    SYNTAX INTEGER {
		otxgrid200(200),
		otxgrid100(100),
		otxgrid50(50)
           }

Pm10001otu4AdjustValue ::= TEXTUAL-CONVENTION
    STATUS      current
    DESCRIPTION "Different values in Adjust mode on OTX-TLH on client and line ports"
    SYNTAX INTEGER {
		otxadjustvalue0(0),
		otxadjustvalue1(1),
		otxadjustvalue2(2),
		otxadjustvalue3(3),
		otxadjustvalue4(4),
		otxadjustvalue5(5),
		otxadjustvalue6(6),
		otxadjustvalue7(7),
		otxadjustvalue8(8),
		otxadjustvalue9(9),
		otxadjustvalue10(10)
           }

Pm10001otu4ClientProtocol ::= TEXTUAL-CONVENTION
    STATUS      current
    DESCRIPTION "Different values on the protocol on the client ports"
    SYNTAX INTEGER {
		protocolclientvalue0(0),
		protocolclientvalue1(1),
		protocolclientvalue2(2),
		protocolclientvalue3(3),
		protocolclientvalue4(4),
		protocolclientvalue5(5),
		protocolclientvalue6(6),
		protocolclientvalue7(7),
		protocolclientvalue8(8)
           }

Pm10001otu4ProtocolMode ::= TEXTUAL-CONVENTION
    STATUS      current
    DESCRIPTION "Different values on the protocol mode"
    SYNTAX INTEGER {
		protocolmodevalue0(0),
		protocolmodevalue1(1),
		protocolmodevalue2(2),
		protocolmodevalue3(3)
           }

Pm10001otu4OtxChannel ::= TEXTUAL-CONVENTION
    STATUS      current
    DESCRIPTION "Channel selection on transceiver Tx line ports"
    SYNTAX INTEGER

Pm10001otu4OrxChannel ::= TEXTUAL-CONVENTION
    STATUS      current
    DESCRIPTION "Channel selection on transceiver Rx line ports"
    SYNTAX INTEGER

Rm10010ClientIgnoreTimer ::= TEXTUAL-CONVENTION
    STATUS      current
    DESCRIPTION "Different values on the ignore timer on the client ports"
    SYNTAX INTEGER {
		ignoretimerclientvalue0(0),
		ignoretimerclientvalue1(1),
		ignoretimerclientvalue2(2),
		ignoretimerclientvalue3(3),
		ignoretimerclientvalue4(4),
		ignoretimerclientvalue5(5),
		ignoretimerclientvalue6(6),
		ignoretimerclientvalue7(7),
		ignoretimerclientvalue8(8),
		ignoretimerclientvalue9(9),
		ignoretimerclientvalue10(10)
           }

Pm10001otu4CompensationMode ::= TEXTUAL-CONVENTION
    STATUS      current
    DESCRIPTION "Different values on the compensation mode"
    SYNTAX INTEGER {
		compensationautomode(0),
		compensationmanmode(1)
           }

--- *****************************************************
--- $$$$$$$$$$$$$$$$$$$$$$$$$$$$$$$$$$$$$$$$$$$$$$$$$$$$$
---     REMOTE INVENTORY
--- $$$$$$$$$$$$$$$$$$$$$$$$$$$$$$$$$$$$$$$$$$$$$$$$$$$$$
--- *****************************************************

pm10001otu4RinvReloadInventory OBJECT-TYPE
  SYNTAX EkiOnOff
  MAX-ACCESS read-write
  STATUS current
  DESCRIPTION
        "Reload the inventory: This OID triggers an
         inventory reload."
  ::= { pm10001otu4ri 2 }

pm10001otu4RinvHwPlatform OBJECT-TYPE
  SYNTAX DisplayString
  MAX-ACCESS read-only
  STATUS current
  DESCRIPTION
        "HW platform description: This OID contains the
         description of the Hardware platform."
  ::= { pm10001otu4ri 3 }

pm10001otu4RinvModulePlatform OBJECT-TYPE
  SYNTAX DisplayString
  MAX-ACCESS read-only
  STATUS current
  DESCRIPTION
        "Module platform description: This OID contains the
         description of the Module."
  ::= { pm10001otu4ri 4 }

pm10001otu4RinvSwPlatform OBJECT-TYPE
  SYNTAX DisplayString
  MAX-ACCESS read-only
  STATUS current
  DESCRIPTION
        "SW platform description: This OID contains the
         description of the Software platform."
  ::= { pm10001otu4ri 5 }

pm10001otu4RinvGwPlatform OBJECT-TYPE
  SYNTAX DisplayString
  MAX-ACCESS read-only
  STATUS current
  DESCRIPTION
        "GW platform desciption: This OID contains the
         description of the Gateware platform."
  ::= { pm10001otu4ri 6 }


pm10001otu4RinvSfpTable OBJECT-TYPE
      SYNTAX  SEQUENCE OF Pm10001otu4RinvSfpEntry
      MAX-ACCESS  not-accessible
      STATUS  current
      DESCRIPTION
              "List of the SFPs on the selected module"
      ::= { pm10001otu4riTable 1 }

pm10001otu4RinvSfpEntry OBJECT-TYPE
        SYNTAX  Pm10001otu4RinvSfpEntry
        MAX-ACCESS  not-accessible
        STATUS  current
        DESCRIPTION
              "Row definition for the SFP table"
        INDEX   { pm10001otu4RinvSfpIndex }
        ::= { pm10001otu4RinvSfpTable 1 }



Pm10001otu4RinvSfpEntry::=
        SEQUENCE {
          pm10001otu4RinvSfpIndex
              Integer32,
          pm10001otu4Rinvsfp
              DisplayString
        }


    pm10001otu4RinvSfpIndex OBJECT-TYPE
        SYNTAX  Integer32(1..16)
        MAX-ACCESS  read-only
        STATUS  current
        DESCRIPTION
              "Index for SFP table"
        ::= { pm10001otu4RinvSfpEntry 1 }


    pm10001otu4Rinvsfp OBJECT-TYPE
        SYNTAX  DisplayString
        MAX-ACCESS  read-only
        STATUS  current
        DESCRIPTION
              "Inventory for the SFP: This OID contains the inventory for the SFP"
        ::= { pm10001otu4RinvSfpEntry 2 }




pm10001otu4RinvLineTable OBJECT-TYPE
      SYNTAX  SEQUENCE OF Pm10001otu4RinvLineEntry
      MAX-ACCESS  not-accessible
      STATUS  current
      DESCRIPTION
              "List of the XFPs on the selected module"
      ::= { pm10001otu4riTable 2 }

pm10001otu4RinvLineEntry OBJECT-TYPE
        SYNTAX  Pm10001otu4RinvLineEntry
        MAX-ACCESS  not-accessible
        STATUS  current
        DESCRIPTION
              "Row definition for the XFP table"
        INDEX   { pm10001otu4RinvLineIndex }
        ::= { pm10001otu4RinvLineTable 1 }



Pm10001otu4RinvLineEntry::=
        SEQUENCE {
          pm10001otu4RinvLineIndex
              Integer32,
          pm10001otu4RinvxfpLine
              DisplayString
        }


    pm10001otu4RinvLineIndex OBJECT-TYPE
        SYNTAX  Integer32(1..16)
        MAX-ACCESS  read-only
        STATUS  current
        DESCRIPTION
              "Index for XFP table"
        ::= { pm10001otu4RinvLineEntry 1 }


    pm10001otu4RinvxfpLine OBJECT-TYPE
        SYNTAX  DisplayString
        MAX-ACCESS  read-only
        STATUS  current
        DESCRIPTION
              "Inventory for the XFP: This OID contains the inventory for the XFP"
        ::= { pm10001otu4RinvLineEntry 2 }









--- *****************************************************
--- $$$$$$$$$$$$$$$$$$$$$$$$$$$$$$$$$$$$$$$$$$$$$$$$$$$$$
---     ALARMS
--- $$$$$$$$$$$$$$$$$$$$$$$$$$$$$$$$$$$$$$$$$$$$$$$$$$$$$
--- *****************************************************



--- *****************************************************
---     LEAF for the synthAlm0 article
--- *****************************************************
pm10001otu4AlmsynthAlm0 OBJECT IDENTIFIER ::= { pm10001otu4AlmOtherCrit 0 }




pm10001otu4AlmDefFuseB OBJECT-TYPE
	  SYNTAX EkiOnOff
	  MAX-ACCESS read-only
	  STATUS current
	  DESCRIPTION
        "
        Fuse B Fail :This OID indicates
        that the fuse of the power input
        B is in fail condition <Help> Status
        of the Fuse B <Condtype> DEF_FUSE_B
        <Probcause> powerProblem (36) <Alarmtype>
        equipmentAlarm (5) <Polarity> (2)
        "
	  ::= { pm10001otu4AlmsynthAlm0 16 }



pm10001otu4AlmDefFuseA OBJECT-TYPE
	  SYNTAX EkiOnOff
	  MAX-ACCESS read-only
	  STATUS current
	  DESCRIPTION
        "
        Fuse A Fail :This OID indicates
        that the fuse of the power input
        A is in fail condition <Help> Status
        of the Fuse A <Condtype> DEF_FUSE_A
        <Probcause> powerProblem (36) <Alarmtype>
        equipmentAlarm (5) <Polarity> (2)
        "
	  ::= { pm10001otu4AlmsynthAlm0 15 }



pm10001otu4AlmModGlobFail OBJECT-TYPE
	  SYNTAX EkiOnOff
	  MAX-ACCESS read-only
	  STATUS current
	  DESCRIPTION
        "
        Module Failure :This OID is set
        on detection of a failure originating
        from the RM <Help> This alarm is
        set on detection of a failure originating
        from the equipment <Condtype> MOD_GLOB_FAIL
        <Probcause> other (1) <Alarmtype>
        synthesisAlarm (12)  <Polarity>
        (2)
        "
	  ::= { pm10001otu4AlmsynthAlm0 9 }



pm10001otu4AlmFailFan OBJECT-TYPE
	  SYNTAX EkiOnOff
	  MAX-ACCESS read-only
	  STATUS current
	  DESCRIPTION
        "
        Fan Fail :This OID is at 1 when
        any fail occurs on the fan tray
        <Help> This alarm indicates that
        the Fan tray module is in a failure
        condition <Condtype> FAIL_FAN <Probcause>
        equipmentMalfunction (16) <Alarmtype>
        equipmentAlarm (5) <Polarity> (2)
        "
	  ::= { pm10001otu4AlmsynthAlm0 2 }



--- *****************************************************
---     LEAF for the synthAlm2 article
--- *****************************************************
pm10001otu4AlmsynthAlm2 OBJECT IDENTIFIER ::= { pm10001otu4AlmOtherNurg 2 }




pm10001otu4AlmMaintenanceOn OBJECT-TYPE
	  SYNTAX EkiOnOff
	  MAX-ACCESS read-only
	  STATUS current
	  DESCRIPTION
        "
        Maintenance Mode :This OID indicates
        that the RM is in maintenance mode.
        <Help> This alarm indicates that
        the maintenance mode is enabled
        on the PM <Condtype> MAINTENANCE_ON
        <Probcause> informationalStatus(1000)
        <Alarmtype> other (1) <Polarity>
        (2)
        "
	  ::= { pm10001otu4AlmsynthAlm2 5 }



pm10001otu4AlmCorrelatOff OBJECT-TYPE
	  SYNTAX EkiOnOff
	  MAX-ACCESS read-only
	  STATUS current
	  DESCRIPTION
        "
        Not Used :This OID, when set,
         indicates that alarm correlation
        is not being performed. <Condtype>
        CORRELAT_OFF <Probcause> informationalStatus(1000)
        <Alarmtype> other (1) <Polarity>
        (2)
        "
	  ::= { pm10001otu4AlmsynthAlm2 4 }



pm10001otu4AlmConfTableLoad OBJECT-TYPE
	  SYNTAX EkiOnOff
	  MAX-ACCESS read-only
	  STATUS current
	  DESCRIPTION
        "
        PM Configuration Load :This OID
         is at 1 during the loading of
         configuration tables in the modules
        RAM. <Condtype> CONF_TABLE_LOAD
        <Probcause> informationalStatus(1000)
        <Alarmtype> other (1) <Polarity>
        (2)
        "
	  ::= { pm10001otu4AlmsynthAlm2 3 }



pm10001otu4AlmInvUpload OBJECT-TYPE
	  SYNTAX EkiOnOff
	  MAX-ACCESS read-only
	  STATUS current
	  DESCRIPTION
        "
        Inventory Upload :This OID is
         at 1 during the uploading of PM
        inventory information. <Condtype>
        INV_UPLOAD <Probcause> informationalStatus(1000)
        <Alarmtype> other (1) <Polarity>
        (2)
        "
	  ::= { pm10001otu4AlmsynthAlm2 2 }



pm10001otu4AlmConfTableSave OBJECT-TYPE
	  SYNTAX EkiOnOff
	  MAX-ACCESS read-only
	  STATUS current
	  DESCRIPTION
        "
        PM Configuration Save :This OID
        is at 1 during the saving of a
         new configuration table in the
        module Flash memory. <Condtype>
        CONF_TABLE_SAVE <Probcause> informationalStatus(1000)
        <Alarmtype> other (1) <Polarity>
        (2)
        "
	  ::= { pm10001otu4AlmsynthAlm2 1 }



--- *********************************************************
---     TABLE for the pm10001otu4AlmsynthAlmPort articles
--- *********************************************************

pm10001otu4AlmsynthAlmPortTable OBJECT-TYPE
	SYNTAX  SEQUENCE OF Pm10001otu4AlmsynthAlmPortEntry
	MAX-ACCESS not-accessible
	STATUS current
	DESCRIPTION
        "
        List of pm10001otu4AlmsynthAlmPort
        Article
        "
	::= { pm10001otu4AlmClientCrit 8 }


pm10001otu4AlmsynthAlmPortEntry OBJECT-TYPE
	SYNTAX Pm10001otu4AlmsynthAlmPortEntry
	MAX-ACCESS not-accessible
	STATUS current
	DESCRIPTION
        "
        Row definition for the pm10001otu4AlmsynthAlmPort
        table
        "
	INDEX   { pm10001otu4AlmsynthAlmPortIndex }
	::= { pm10001otu4AlmsynthAlmPortTable 1 }


Pm10001otu4AlmsynthAlmPortEntry ::=
	SEQUENCE {
	pm10001otu4AlmsynthAlmPortIndex
		INTEGER,
	pm10001otu4AlmUpCsfPortn
		EkiOnOff,
	pm10001otu4AlmFailAccPortn
		EkiOnOff,
	pm10001otu4AlmIdleInsertedPortn
		EkiOnOff,
	pm10001otu4AlmSfpDdmAlmPortn
		EkiOnOff,
	pm10001otu4AlmSfpDdmWarningPortn
		EkiOnOff,
	pm10001otu4AlmDwCaisPortn
		EkiOnOff,
	pm10001otu4AlmClientRemoteOosPortn
		EkiOnOff,
	pm10001otu4AlmClientLocalOosPortn
		EkiOnOff,
	pm10001otu4AlmDwLsdPortn
		EkiOnOff,
	pm10001otu4AlmHwFailAccPortn
		EkiOnOff,
	pm10001otu4AlmDdmAbsentPortn
		EkiOnOff,
	pm10001otu4AlmSfpAbsentPortn
		EkiOnOff
	}


pm10001otu4AlmsynthAlmPortIndex OBJECT-TYPE
	SYNTAX  INTEGER(0..128)
	MAX-ACCESS  read-only
	STATUS current
	DESCRIPTION
        "
        Index definition for the pm10001otu4AlmsynthAlmPort
        table
        "
	::= { pm10001otu4AlmsynthAlmPortEntry 1 }


pm10001otu4AlmUpCsfPortn OBJECT-TYPE
	SYNTAX  EkiOnOff
	MAX-ACCESS read-only
	STATUS current
	DESCRIPTION
        "
        Client Signal Fail Inserted :This
        OID indicates a CSF has been inserted
        in the upstream client port. <Help>
        This status indicates if a Client
        Signal Fail is currently inserted
        on the line signal for this client
        port <Condtype> UP_CSF_1 <Probcause>
        informationalStatus(1000) <Alarmtype>
        other (1) <Polarity> (2)
        "
	::= { pm10001otu4AlmsynthAlmPortEntry 17 }


pm10001otu4AlmFailAccPortn OBJECT-TYPE
	SYNTAX  EkiOnOff
	MAX-ACCESS read-only
	STATUS current
	DESCRIPTION
        "
        Client Access Fail :This OID indicates
        a failure on the Client port <Help>
        This alarm indicates a failure
         on the Client port <Condtype>
         FAIL_ACC_1 <Probcause> equipmentMalfunction
        (16) <Alarmtype> synthesisAlarm
        (12)  <Polarity> (2)
        "
	::= { pm10001otu4AlmsynthAlmPortEntry 13 }


pm10001otu4AlmIdleInsertedPortn OBJECT-TYPE
	SYNTAX  EkiOnOff
	MAX-ACCESS read-only
	STATUS current
	DESCRIPTION
        "
        Idle Inserted :This OID indicates
        the client output stream is replaced
        by IDLE<Help> This alarm indicates
        the client output stream is replaced
        by IDLE <Condtype> IDLE_INSERTED
        <Probcause> informationalStatus(1000)
        <Alarmtype> other (1) <Polarity>
        (2)
        "
	::= { pm10001otu4AlmsynthAlmPortEntry 12 }


pm10001otu4AlmSfpDdmAlmPortn OBJECT-TYPE
	SYNTAX  EkiOnOff
	MAX-ACCESS read-only
	STATUS current
	DESCRIPTION
        "
        Alarm On Client Trscv DDM :This
        OID indicates an alarm is being
        received from the Client Transceiver
        DDM <Help> This alarm indicates
        if a DDM Alarm has been detected
        on the client transceiver <Condtype>
        SFP_DDM_ALM_1 <Probcause> inputOutputDeviceError
        (24) <Alarmtype> synthesisAlarm
        (12)  <Polarity> (2)
        "
	::= { pm10001otu4AlmsynthAlmPortEntry 11 }


pm10001otu4AlmSfpDdmWarningPortn OBJECT-TYPE
	SYNTAX  EkiOnOff
	MAX-ACCESS read-only
	STATUS current
	DESCRIPTION
        "
        Warning On Client Trscv DDM :This
        OID indicates a warning is being
        received from the Client Transceiver
        DDM <Help> This alarm indicates
        if a DDM Warning has been detected
        on the client transceiver <Condtype>
        SFP_DDM_WARNING_1 <Probcause> inputOutputDeviceError
        (24) <Alarmtype> synthesisAlarm
        (12)  <Polarity> (2)
        "
	::= { pm10001otu4AlmsynthAlmPortEntry 10 }


pm10001otu4AlmDwCaisPortn OBJECT-TYPE
	SYNTAX  EkiOnOff
	MAX-ACCESS read-only
	STATUS current
	DESCRIPTION
        "
        Client AIS Inserted :This OID
         indicates a CAIS has been inserted
        on the output client port. <Help>
        This status indicates if a Client
        Alarm Indication Signal is currently
        inserted on the client interface
        <Condtype> DW_CAIS_1 <Probcause>
        informationalStatus(1000) <Alarmtype>
        other (1) <Polarity> (2)
        "
	::= { pm10001otu4AlmsynthAlmPortEntry 9 }


pm10001otu4AlmClientRemoteOosPortn OBJECT-TYPE
	SYNTAX  EkiOnOff
	MAX-ACCESS read-only
	STATUS current
	DESCRIPTION
        "
        Remote Client Port In Service
         :This OID indicates that the remote
        Client port is In Service (1) or
        Out of Service (2) <Help> This
         status indicates if the remote
        client port is in service <Condtype>
        CLIENT_REMOTE_OOS <Probcause> informationalStatus(1000)
        <Alarmtype> other (1) <Polarity>
        (2)
        "
	::= { pm10001otu4AlmsynthAlmPortEntry 8 }


pm10001otu4AlmClientLocalOosPortn OBJECT-TYPE
	SYNTAX  EkiOnOff
	MAX-ACCESS read-only
	STATUS current
	DESCRIPTION
        "
        Local Client Port In Service :This
        OID indicates that the local Client
        port is In Service (1) or Out of
        Service (2) <Help> This status
         indicates if the local client
         port is in service <Condtype>
         CLIENT_LOCAL_OOS <Probcause> informationalStatus(1000)
        <Alarmtype> other (1) <Polarity>
        (2)
        "
	::= { pm10001otu4AlmsynthAlmPortEntry 7 }


pm10001otu4AlmDwLsdPortn OBJECT-TYPE
	SYNTAX  EkiOnOff
	MAX-ACCESS read-only
	STATUS current
	DESCRIPTION
        "
        Client Trscv Laser Shutdown :This
        OID indicates the Client transceiver
        laser is shutdown <Help> This status
        indicates if the client transceiver
        laser is shutdown <Condtype> DW_LSD_1
        <Probcause> other (1) <Alarmtype>
        equipmentAlarm (5) <Polarity> (2)
        "
	::= { pm10001otu4AlmsynthAlmPortEntry 6 }


pm10001otu4AlmHwFailAccPortn OBJECT-TYPE
	SYNTAX  EkiOnOff
	MAX-ACCESS read-only
	STATUS current
	DESCRIPTION
        "
        Client HW Fail :This OID indicates
        a failure on client port, most
         probably caused by a HW issue.
        <Help> This alarm indicates a failure
        on client port, most probably caused
        by a HW issue. <Condtype> HW_FAIL_ACC_1
        <Probcause> equipmentMalfunction
        (16) <Alarmtype> synthesisAlarm
        (12)  <Polarity> (2)
        "
	::= { pm10001otu4AlmsynthAlmPortEntry 5 }


pm10001otu4AlmDdmAbsentPortn OBJECT-TYPE
	SYNTAX  EkiOnOff
	MAX-ACCESS read-only
	STATUS current
	DESCRIPTION
        "
        DDM Supported On Client Trscv
         :This OID indicates that the Client
        transceiver supports the Digital
        Diagnostic Monitoring function
         <Help> This status indicates if
        the client transceiver includes
        the DDM feature <Condtype> DDM_ABSENT_1
        <Probcause> informationalStatus(1000)
        <Alarmtype> other (1) <Polarity>
        (2)
        "
	::= { pm10001otu4AlmsynthAlmPortEntry 3 }


pm10001otu4AlmSfpAbsentPortn OBJECT-TYPE
	SYNTAX  EkiOnOff
	MAX-ACCESS read-only
	STATUS current
	DESCRIPTION
        "
        Client Optical Module Absent :This
        OID indicates that the Transceiver
        is not present in the client port.
        <Help> This alarm indicates if
         the client transceiver is not
         plugged <Condtype> SFP_ABSENT_1
        <Probcause> inputOutputDeviceError
        (24) <Alarmtype> equipmentAlarm
        (5) <Polarity> (2) <Event> ObjectCDINV
        "
	::= { pm10001otu4AlmsynthAlmPortEntry 2 }


--- *********************************************************
---     TABLE for the pm10001otu4AlmsynthAlmLine articles
--- *********************************************************

pm10001otu4AlmsynthAlmLineTable OBJECT-TYPE
	SYNTAX  SEQUENCE OF Pm10001otu4AlmsynthAlmLineEntry
	MAX-ACCESS not-accessible
	STATUS current
	DESCRIPTION
        "
        List of pm10001otu4AlmsynthAlmLine
        Article
        "
	::= { pm10001otu4AlmLineCrit 24 }


pm10001otu4AlmsynthAlmLineEntry OBJECT-TYPE
	SYNTAX Pm10001otu4AlmsynthAlmLineEntry
	MAX-ACCESS not-accessible
	STATUS current
	DESCRIPTION
        "
        Row definition for the pm10001otu4AlmsynthAlmLine
        table
        "
	INDEX   { pm10001otu4AlmsynthAlmLineIndex }
	::= { pm10001otu4AlmsynthAlmLineTable 1 }


Pm10001otu4AlmsynthAlmLineEntry ::=
	SEQUENCE {
	pm10001otu4AlmsynthAlmLineIndex
		INTEGER,
	pm10001otu4AlmLineActivePortn
		EkiOnOff,
	pm10001otu4AlmLineFailPortn
		EkiOnOff,
	pm10001otu4AlmLineDdmAlmPortn
		EkiOnOff,
	pm10001otu4AlmLineDdmWarningPortn
		EkiOnOff,
	pm10001otu4AlmUpRdiInsPortn
		EkiOnOff,
	pm10001otu4AlmLineLocalOosPortn
		EkiOnOff,
	pm10001otu4AlmXfpTxOffPortn
		EkiOnOff,
	pm10001otu4AlmLineHwFailPortn
		EkiOnOff,
	pm10001otu4AlmXfpInitNotComplPortn
		EkiOnOff,
	pm10001otu4AlmXfpAbsentPortn
		EkiOnOff
	}


pm10001otu4AlmsynthAlmLineIndex OBJECT-TYPE
	SYNTAX  INTEGER(0..128)
	MAX-ACCESS  read-only
	STATUS current
	DESCRIPTION
        "
        Index definition for the pm10001otu4AlmsynthAlmLine
        table
        "
	::= { pm10001otu4AlmsynthAlmLineEntry 1 }


pm10001otu4AlmLineActivePortn OBJECT-TYPE
	SYNTAX  EkiOnOff
	MAX-ACCESS read-only
	STATUS current
	DESCRIPTION
        "
        Line Active :This OID indicates
        whether the line is active or standby.
        <Help> This status indicates whether
        the line is active or standby.
         <Condtype> LINE_ACTIVE <Probcause>
        informationalStatus(1000) <Alarmtype>
        other (1) <Polarity> (2)
        "
	::= { pm10001otu4AlmsynthAlmLineEntry 17 }


pm10001otu4AlmLineFailPortn OBJECT-TYPE
	SYNTAX  EkiOnOff
	MAX-ACCESS read-only
	STATUS current
	DESCRIPTION
        "
        Line Port Failure :This OID indicates
        a failure on the line port <Help>
        This alarm indicates a failure
         on the line port <Condtype> LINE_FAIL
        <Probcause> equipmentMalfunction
        (16) <Alarmtype> synthesisAlarm
        (12)  <Polarity> (2)
        "
	::= { pm10001otu4AlmsynthAlmLineEntry 13 }


pm10001otu4AlmLineDdmAlmPortn OBJECT-TYPE
	SYNTAX  EkiOnOff
	MAX-ACCESS read-only
	STATUS current
	DESCRIPTION
        "
        Alarm On Line Optical Module DDM
        :This OID indicates an alarm is
        present coming out of Line transceiver
        DDM <Help> This alarm indicates
        if a DDM Alarm has been detected
        on the line transceiver <Condtype>
        LINE_DDM_ALM <Probcause> inputOutputDeviceError
        (24) <Alarmtype> synthesisAlarm
        (12)  <Polarity> (2)
        "
	::= { pm10001otu4AlmsynthAlmLineEntry 11 }


pm10001otu4AlmLineDdmWarningPortn OBJECT-TYPE
	SYNTAX  EkiOnOff
	MAX-ACCESS read-only
	STATUS current
	DESCRIPTION
        "
        Warning On Line Optical Module
        DDM :This OID indicates a warning
        is present coming out of Line transceiver
        DDM <Help> This alarm indicates
        if a DDM Warning has been detected
        on the line transceiver <Condtype>
        LINE_DDM_WARNING <Probcause> inputOutputDeviceError
        (24) <Alarmtype> synthesisAlarm
        (12)  <Polarity> (2)
        "
	::= { pm10001otu4AlmsynthAlmLineEntry 10 }


pm10001otu4AlmUpRdiInsPortn OBJECT-TYPE
	SYNTAX  EkiOnOff
	MAX-ACCESS read-only
	STATUS current
	DESCRIPTION
        "
        MS-RDI/L-RDI Inserted On Line
         :This OID indicates an upstream
        MS-RDI/L-RDI has been inserted
         in the outgoing 10 Gb/s SDH/SONET
        signal. <Help> This status indicates
        if a MS-RDI/L-RDI is currently
         inserted on the line interface.
        <Condtype> UP_RDI_INS <Probcause>
        informationalStatus(1000) <Alarmtype>
        other (1) <Polarity> (2)
        "
	::= { pm10001otu4AlmsynthAlmLineEntry 9 }


pm10001otu4AlmLineLocalOosPortn OBJECT-TYPE
	SYNTAX  EkiOnOff
	MAX-ACCESS read-only
	STATUS current
	DESCRIPTION
        "
        Line Port In Service :This OID
        indicates that the Line port is
        In Service (1) of Out or Service
        (2) <Help> This status indicates
        if the line port is in service
         <Condtype> LINE_LOCAL_OOS <Probcause>
        informationalStatus(1000) <Alarmtype>
        other (1) <Polarity> (2)
        "
	::= { pm10001otu4AlmsynthAlmLineEntry 7 }


pm10001otu4AlmXfpTxOffPortn OBJECT-TYPE
	SYNTAX  EkiOnOff
	MAX-ACCESS read-only
	STATUS current
	DESCRIPTION
        "
        Line Trscv Laser Shutdown :This
        OID indicates the Line transceiver
        laser is shutdown <Help> This status
        indicates if the Line transceiver
        laser is shutdown <Condtype> XFP_TX_OFF
        <Probcause> other (1) <Alarmtype>
        equipmentAlarm (5) <Polarity> (2)
        "
	::= { pm10001otu4AlmsynthAlmLineEntry 6 }


pm10001otu4AlmLineHwFailPortn OBJECT-TYPE
	SYNTAX  EkiOnOff
	MAX-ACCESS read-only
	STATUS current
	DESCRIPTION
        "
        Line Port HW Failure :This OID
        indicates a failure on line port,
        most probably caused by a HW issue
        <Help> This alarm indicates a failure
        on line port, most probably caused
        by a HW issue <Condtype> LINE_HW_FAIL
        <Probcause> equipmentMalfunction
        (16) <Alarmtype> synthesisAlarm
        (12)  <Polarity> (2)
        "
	::= { pm10001otu4AlmsynthAlmLineEntry 5 }


pm10001otu4AlmXfpInitNotComplPortn OBJECT-TYPE
	SYNTAX  EkiOnOff
	MAX-ACCESS read-only
	STATUS current
	DESCRIPTION
        "
        Line Optical Module Ready :This
        OID indicates that the optical
         interface is not operational.
         <Help> This status indicates if
        the line transceiver has been correctly
        initialized <Condtype> XFP_INIT_NOT_COMPL
        <Probcause> equipmentMalfunction
        (16) <Alarmtype> equipmentAlarm
        (5) <Polarity> (2)
        "
	::= { pm10001otu4AlmsynthAlmLineEntry 3 }


pm10001otu4AlmXfpAbsentPortn OBJECT-TYPE
	SYNTAX  EkiOnOff
	MAX-ACCESS read-only
	STATUS current
	DESCRIPTION
        "
        Line Optical Module Absent :This
        OID indicates that the line optical
        interface is not present. <Help>
        This alarm indicates if the line
        transceiver is not plugged <Condtype>
        XFP_ABSENT <Probcause> inputOutputDeviceError
        (24) <Alarmtype> equipmentAlarm
        (5) <Polarity> (2)
        "
	::= { pm10001otu4AlmsynthAlmLineEntry 2 }


--- *****************************************************
---     LEAF for the clientModuleState article
--- *****************************************************
pm10001otu4AlmclientModuleState OBJECT IDENTIFIER ::= { pm10001otu4AlmOtherCrit 40 }




pm10001otu4AlmCfpHighPowerDown OBJECT-TYPE
	  SYNTAX EkiOnOff
	  MAX-ACCESS read-only
	  STATUS current
	  DESCRIPTION
        "
        Client Trscv High Power Down :This
        OID indicates the Client Trscv
         is entering Low Power state <Help>
        Status indicating the Client Trscv
        is entering Low Power state <Condtype>
        CFP_HIGH_POWER_DOWN <Probcause>
        informationalStatus(1000) <Alarmtype>
        other (1) <Polarity> (2)
        "
	  ::= { pm10001otu4AlmclientModuleState 9 }



pm10001otu4AlmCfpTxTurnOff OBJECT-TYPE
	  SYNTAX EkiOnOff
	  MAX-ACCESS read-only
	  STATUS current
	  DESCRIPTION
        "
        Client Trscv Laser Turn Off :This
        OID indicates the Client Trscv
         is turning off its laser <Help>
        Status indicating the Client Trscv
        is turning off its laser <Condtype>
        CFP_TX_TURN_OFF <Probcause> informationalStatus(1000)
        <Alarmtype> other (1) <Polarity>
        (2)
        "
	  ::= { pm10001otu4AlmclientModuleState 8 }



pm10001otu4AlmCfpFault OBJECT-TYPE
	  SYNTAX EkiOnOff
	  MAX-ACCESS read-only
	  STATUS current
	  DESCRIPTION
        "
        Client Trscv Fault :This OID indicates
        the Client Trscv is in Fault state
        <Help> Status indicating the Client
        Trscv is in Fault state <Condtype>
        CFP_FAULT <Probcause> informationalStatus(1000)
        <Alarmtype> other (1) <Polarity>
        (2)
        "
	  ::= { pm10001otu4AlmclientModuleState 7 }



pm10001otu4AlmCfpReady OBJECT-TYPE
	  SYNTAX EkiOnOff
	  MAX-ACCESS read-only
	  STATUS current
	  DESCRIPTION
        "
        Client Trscv Ready :This OID indicates
        the Client Trscv is ready to operate
        <Help> Status indicating the Client
        Trscv is ready to operate <Condtype>
        CFP_READY <Probcause> informationalStatus(1000)
        <Alarmtype> other (1) <Polarity>
        (2)
        "
	  ::= { pm10001otu4AlmclientModuleState 6 }



pm10001otu4AlmCfpTxTurnOn OBJECT-TYPE
	  SYNTAX EkiOnOff
	  MAX-ACCESS read-only
	  STATUS current
	  DESCRIPTION
        "
        Client Trscv Laser Turn On :This
        OID indicates the Client Trscv
         is turning on its laser <Help>
        Status indicating the Client Trscv
        is turning on its laser <Condtype>
        CFP_TX_TURN_ON <Probcause> informationalStatus(1000)
        <Alarmtype> other (1) <Polarity>
        (2)
        "
	  ::= { pm10001otu4AlmclientModuleState 5 }



pm10001otu4AlmCfpTxOff OBJECT-TYPE
	  SYNTAX EkiOnOff
	  MAX-ACCESS read-only
	  STATUS current
	  DESCRIPTION
        "
        Client Trscv Laser Shutdown :This
        OID indicates the Client Trscv
         Laser is OFF <Help> Status indicating
        the Client Trscv Laser is OFF <Condtype>
        CFP_TX_OFF <Probcause> informationalStatus(1000)
        <Alarmtype> other (1) <Polarity>
        (2)
        "
	  ::= { pm10001otu4AlmclientModuleState 4 }



pm10001otu4AlmCfpHighPowerUp OBJECT-TYPE
	  SYNTAX EkiOnOff
	  MAX-ACCESS read-only
	  STATUS current
	  DESCRIPTION
        "
        Client Trscv High Power Up :This
        OID indicates the Client Trscv
         is leaving Low Power state <Help>
        Status indicating the Client Trscv
        is leaving Low Power state <Condtype>
        CFP_HIGH_POWER_UP <Probcause> informationalStatus(1000)
        <Alarmtype> other (1) <Polarity>
        (2)
        "
	  ::= { pm10001otu4AlmclientModuleState 3 }



pm10001otu4AlmCfpLowPower OBJECT-TYPE
	  SYNTAX EkiOnOff
	  MAX-ACCESS read-only
	  STATUS current
	  DESCRIPTION
        "
        Client Trscv Low Power :This OID
        indicates the Client Trscv is in
        low power state <Help> Status indicating
        the Client Trscv is in low power
        state <Condtype> CFP_LOW_POWER
         <Probcause> informationalStatus(1000)
        <Alarmtype> other (1) <Polarity>
        (2)
        "
	  ::= { pm10001otu4AlmclientModuleState 2 }



pm10001otu4AlmCfpInitialize OBJECT-TYPE
	  SYNTAX EkiOnOff
	  MAX-ACCESS read-only
	  STATUS current
	  DESCRIPTION
        "
        Client Trscv Initialize :This
         OID indicates the Client Trscv
        initialization is in progress <Help>
        Status indicating the Client Trscv
        initialization is in progress <Condtype>
        CFP_INITIALIZE <Probcause> informationalStatus(1000)
        <Alarmtype> other (1) <Polarity>
        (2)
        "
	  ::= { pm10001otu4AlmclientModuleState 1 }



--- *****************************************************
---     LEAF for the clientModuleGeneralStatus article
--- *****************************************************
pm10001otu4AlmclientModuleGeneralStatus OBJECT IDENTIFIER ::= { pm10001otu4AlmOtherCrit 41 }




pm10001otu4AlmCfpHwInterlock OBJECT-TYPE
	  SYNTAX EkiOnOff
	  MAX-ACCESS read-only
	  STATUS current
	  DESCRIPTION
        "
        Client Trscv Hardware Interlock
        :This OID indicates the Client
         Trscv power is higher than the
        cooling capacity <Help> Alarm indicating
        the Client Trscv power is higher
        than the cooling capacity <Condtype>
        CFP_HW_INTERLOCK <Probcause> temperatureUnacceptable
        (51) <Alarmtype> equipmentAlarm
        (5) <Polarity> (2)
        "
	  ::= { pm10001otu4AlmclientModuleGeneralStatus 14 }



pm10001otu4AlmCfpLossOfRefclk OBJECT-TYPE
	  SYNTAX EkiOnOff
	  MAX-ACCESS read-only
	  STATUS current
	  DESCRIPTION
        "
        Client Trscv Loss Of Ref Clock
        :This OID indicates a Loss of Reference
        clock is detected on the Client
        Trscv <Help> Alarm indicating a
        Loss of Reference clock is detected
        on the Client Trscv <Condtype>
         CFP_LOSS_OF_REFCLK <Probcause>
        inputOutputDeviceError (24) <Alarmtype>
        equipmentAlarm (5) <Polarity> (2)
        "
	  ::= { pm10001otu4AlmclientModuleGeneralStatus 11 }



pm10001otu4AlmCfpTxJitterPllLol OBJECT-TYPE
	  SYNTAX EkiOnOff
	  MAX-ACCESS read-only
	  STATUS current
	  DESCRIPTION
        "
        Client Trscv Tx Jitter PLL Loss
        Of Lock :This OID indicates a Tx
        Jitter PLL Loss of Lock is dtected
        on the Client Trscv <Help> Alarm
        indicating a Tx Jitter PLL Loss
        of Lock is dtected on the Client
        Trscv <Condtype> CFP_TX_JITTER_PLL_LOL
        <Probcause> inputOutputDeviceError
        (24) <Alarmtype> equipmentAlarm
        (5) <Polarity> (2)
        "
	  ::= { pm10001otu4AlmclientModuleGeneralStatus 10 }



pm10001otu4AlmCfpTxCmuLol OBJECT-TYPE
	  SYNTAX EkiOnOff
	  MAX-ACCESS read-only
	  STATUS current
	  DESCRIPTION
        "
        Client Trscv CMU Loss Of Lock
         :This OID indicates a Clock Multiplier
        Unit Loss of Lock is detected on
        the Client Trscv <Help> Alarm indicating
        a Clock Multiplier Unit Loss of
        Lock is detected on the Client
         Trscv <Condtype> CFP_TX_CMU_LOL
        <Probcause> inputOutputDeviceError
        (24) <Alarmtype> equipmentAlarm
        (5) <Polarity> (2)
        "
	  ::= { pm10001otu4AlmclientModuleGeneralStatus 9 }



pm10001otu4AlmCfpTxLosf OBJECT-TYPE
	  SYNTAX EkiOnOff
	  MAX-ACCESS read-only
	  STATUS current
	  DESCRIPTION
        "
        Client Trscv Loss Of Signal Functionality
        :This OID indicates a Loss of Signal
        functionality is detected on the
        Client Trscv <Help> Alarm indicating
        a Loss of Signal functionality
         is detected on the Client Trscv
        <Condtype> CFP_TX_LOSF <Probcause>
        lossOfSignal (30) <Alarmtype> equipmentAlarm
        (5) <Polarity> (2)
        "
	  ::= { pm10001otu4AlmclientModuleGeneralStatus 8 }



pm10001otu4AlmCfpTxHostLol OBJECT-TYPE
	  SYNTAX EkiOnOff
	  MAX-ACCESS read-only
	  STATUS current
	  DESCRIPTION
        "
        Client Trscv Tx Host Loss Of Lock
        :This OID indicates of Loss of
         Lock is detected on the Client
        Trscv Tx Host interface <Help>
         Alarm indicating of Loss of Lock
        is detected on the Client Trscv
        Tx Host interface <Condtype> CFP_TX_HOST_LOL
        <Probcause> receiverFailure (42)
        <Alarmtype> equipmentAlarm (5)
         <Polarity> (2)
        "
	  ::= { pm10001otu4AlmclientModuleGeneralStatus 7 }



pm10001otu4AlmCfpRxLos OBJECT-TYPE
	  SYNTAX EkiOnOff
	  MAX-ACCESS read-only
	  STATUS current
	  DESCRIPTION
        "
        Client Trscv Loss Of Signal :This
        OID indicates a Loss of Signal
         is detected on the Client Trscv
        <Help> Alarm indicating a Loss
         of Signal is detected on the Client
        Trscv <Condtype> CFP_RX_LOS <Probcause>
        lossOfSignal (30) <Alarmtype> equipmentAlarm
        (5) <Polarity> (2)
        "
	  ::= { pm10001otu4AlmclientModuleGeneralStatus 6 }



pm10001otu4AlmCfpRxNetworkLol OBJECT-TYPE
	  SYNTAX EkiOnOff
	  MAX-ACCESS read-only
	  STATUS current
	  DESCRIPTION
        "
        Client Trscv Rx Network Loss Of
        Lock :This OID indicates of Loss
        of Lock is dected on the Client
        Trscv Rx Network interface <Help>
        Alarm indicating of Loss of Lock
        is dected on the Client Trscv Rx
        Network interface <Condtype> CFP_RX_NETWORK_LOL
        <Probcause> receiverFailure (42)
        <Alarmtype> equipmentAlarm (5)
         <Polarity> (2)
        "
	  ::= { pm10001otu4AlmclientModuleGeneralStatus 5 }



pm10001otu4AlmCfpOutOfAlignment OBJECT-TYPE
	  SYNTAX EkiOnOff
	  MAX-ACCESS read-only
	  STATUS current
	  DESCRIPTION
        "
        Client Trscv Out Of Alignment
         :This OID indicates an Out of
         alignment on the Client Trscv
         Host Interface <Help> Alarm indicating
        an Out of alignment on the Client
        Trscv Host Interface <Condtype>
        CFP_OUT_OF_ALIGNMENT <Probcause>
        receiverFailure (42) <Alarmtype>
        equipmentAlarm (5) <Polarity> (2)
        "
	  ::= { pm10001otu4AlmclientModuleGeneralStatus 4 }



--- *****************************************************
---     LEAF for the clientGlobalAlarmSummary article
--- *****************************************************
pm10001otu4AlmclientGlobalAlarmSummary OBJECT IDENTIFIER ::= { pm10001otu4AlmOtherCrit 42 }




pm10001otu4AlmCfpGlobAlarmAssertion  OBJECT-TYPE
	  SYNTAX EkiOnOff
	  MAX-ACCESS read-only
	  STATUS current
	  DESCRIPTION
        "
        Client Trscv Global Alarm :This
        OID indicates at least one  Fault
        or Status is detected on the Client
        Trscv module <Help> Synthesis alarm
        indicating at least one Alarm,
         Warning, Fault or Status is detected
        on the Client Trscv module <Condtype>
        CFP_GLOB_ALARM_ASSERTION  <Probcause>
        informationalStatus(1000) <Alarmtype>
        other (1) <Polarity> (2)
        "
	  ::= { pm10001otu4AlmclientGlobalAlarmSummary 16 }



pm10001otu4AlmCfpHostLaneFaultStatus  OBJECT-TYPE
	  SYNTAX EkiOnOff
	  MAX-ACCESS read-only
	  STATUS current
	  DESCRIPTION
        "
        Client Trscv Host Fault And Status
        :This OID indicates at least one
        Fault or Status is detected on
         the Client Trscv Host Interface
        <Help> Synthesis alarm indicating
        at least one Fault or Status is
        detected on the Client Trscv Host
        Interface <Condtype> CFP_HOST_LANE_FAULT_STATUS
         <Probcause> informationalStatus(1000)
        <Alarmtype> other (1) <Polarity>
        (2)
        "
	  ::= { pm10001otu4AlmclientGlobalAlarmSummary 15 }



pm10001otu4AlmCfpNetworkLaneFaultStatus  OBJECT-TYPE
	  SYNTAX EkiOnOff
	  MAX-ACCESS read-only
	  STATUS current
	  DESCRIPTION
        "
        Client Trscv Network Fault And
        Status :This OID indicates at least
        one Fault or Status is detected
        on the Client Trscv Network Interface
        <Help> Synthesis alarm indicating
        at least one Fault or Status is
        detected on the Client Trscv Network
        Interface <Condtype> CFP_NETWORK_LANE_FAULT_STATUS
         <Probcause> informationalStatus(1000)
        <Alarmtype> other (1) <Polarity>
        (2)
        "
	  ::= { pm10001otu4AlmclientGlobalAlarmSummary 14 }



pm10001otu4AlmCfpNetworkLaneAlarmWarning1 OBJECT-TYPE
	  SYNTAX EkiOnOff
	  MAX-ACCESS read-only
	  STATUS current
	  DESCRIPTION
        "
        Client Trscv Network Alarm And
        Warning 1 :This OID indicates at
        least one DDM  is detected on the
        Client Trscv Network Interface
         <Help> Synthesis alarm indicating
        at least one DDM Alarm or DDM Warning
        is detected on the Client Trscv
        Network Interface <Condtype> CFP_NETWORK_LANE_ALARM_WARNING_1
        <Probcause> informationalStatus(1000)
        <Alarmtype> other (1) <Polarity>
        (2)
        "
	  ::= { pm10001otu4AlmclientGlobalAlarmSummary 13 }



pm10001otu4AlmCfpModuleAlarmWarning2 OBJECT-TYPE
	  SYNTAX EkiOnOff
	  MAX-ACCESS read-only
	  STATUS current
	  DESCRIPTION
        "
        Client Trscv Module Alarm And
         Warning 2 :This OID indicates
         at least one DDM is detected on
        the Client Trscv module <Help>
         Synthesis alarm indicating at
         least one DDM Alarm or DDM Warning
        is detected on the Client Trscv
        module <Condtype> CFP_MODULE_ALARM_WARNING_2
        <Probcause> informationalStatus(1000)
        <Alarmtype> other (1) <Polarity>
        (2)
        "
	  ::= { pm10001otu4AlmclientGlobalAlarmSummary 12 }



pm10001otu4AlmCfpModuleAlarmWarning1  OBJECT-TYPE
	  SYNTAX EkiOnOff
	  MAX-ACCESS read-only
	  STATUS current
	  DESCRIPTION
        "
        Client Trscv Module Alarm And
         Warning 1 :This OID indicates
         at least one DDM  This OID is
         detected on the Client Trscv module
        <Help> Synthesis alarm indicating
        at least one DDM Alarm or DDM Warning
        is detected on the Client Trscv
        module <Condtype> CFP_MODULE_ALARM_WARNING_1
         <Probcause> informationalStatus(1000)
        <Alarmtype> other (1) <Polarity>
        (2)
        "
	  ::= { pm10001otu4AlmclientGlobalAlarmSummary 11 }



pm10001otu4AlmCfpModuleFault  OBJECT-TYPE
	  SYNTAX EkiOnOff
	  MAX-ACCESS read-only
	  STATUS current
	  DESCRIPTION
        "
        Client Trscv Module Fault :This
        OID indicates at least one Fault
        is detected on the Client Trscv
        module <Help> Synthesis alarm indicating
        at least one Fault is detected
         on the Client Trscv module <Condtype>
        CFP_MODULE_FAULT  <Probcause> informationalStatus(1000)
        <Alarmtype> other (1) <Polarity>
        (2)
        "
	  ::= { pm10001otu4AlmclientGlobalAlarmSummary 10 }



pm10001otu4AlmCfpModuleGeneralStatus  OBJECT-TYPE
	  SYNTAX EkiOnOff
	  MAX-ACCESS read-only
	  STATUS current
	  DESCRIPTION
        "
        Client Trscv General Status :This
        OID indicates the Client Trscv
         module general status <Help> Synthesis
        alarm indicating the Client Trscv
        module general status <Condtype>
        CFP_MODULE_GENERAL_STATUS  <Probcause>
        informationalStatus(1000) <Alarmtype>
        other (1) <Polarity> (2)
        "
	  ::= { pm10001otu4AlmclientGlobalAlarmSummary 9 }



pm10001otu4AlmCfpModuleState  OBJECT-TYPE
	  SYNTAX EkiOnOff
	  MAX-ACCESS read-only
	  STATUS current
	  DESCRIPTION
        "
        Client Trscv Module State :This
        OID indicates the Client Trscv
         module state <Help> Synthesis
         alarm indicating the Client Trscv
        module state <Condtype> CFP_MODULE_STATE
         <Probcause> informationalStatus(1000)
        <Alarmtype> other (1) <Polarity>
        (2)
        "
	  ::= { pm10001otu4AlmclientGlobalAlarmSummary 8 }



pm10001otu4AlmCfpNetworkLaneAlarmWarning2 OBJECT-TYPE
	  SYNTAX EkiOnOff
	  MAX-ACCESS read-only
	  STATUS current
	  DESCRIPTION
        "
        Client Trscv Network Alarm And
        Warning 2 :This OID indicates at
        least one DDM is detected on the
        Client Trscv Network Interface
         <Help> Synthesis alarm indicating
        at least one DDM Alarm or DDM Warning
        is detected on the Client Trscv
        Network Interface <Condtype> CFP_NETWORK_LANE_ALARM_WARNING_2
        <Probcause> informationalStatus(1000)
        <Alarmtype> other (1) <Polarity>
        (2)
        "
	  ::= { pm10001otu4AlmclientGlobalAlarmSummary 7 }



pm10001otu4AlmCfpSoftGlobAlarmTest  OBJECT-TYPE
	  SYNTAX EkiOnOff
	  MAX-ACCESS read-only
	  STATUS current
	  DESCRIPTION
        "
        Client Trscv Global Alarm SW Test
        :This OID indicates the Client
         Trscv Global Alarm This OID is
        raised by SW request for test purpose
        <Help> Status indicating the Client
        Trscv Global Alarm is raised by
        SW request for test purpose <Condtype>
        CFP_SOFT_GLOB_ALARM_TEST  <Probcause>
        informationalStatus(1000) <Alarmtype>
        other (1) <Polarity> (2)
        "
	  ::= { pm10001otu4AlmclientGlobalAlarmSummary 1 }



--- *****************************************************
---     LEAF for the msaModuleState article
--- *****************************************************
pm10001otu4AlmmsaModuleState OBJECT IDENTIFIER ::= { pm10001otu4AlmOtherCrit 46 }




pm10001otu4AlmMsaHighPowerDown OBJECT-TYPE
	  SYNTAX EkiOnOff
	  MAX-ACCESS read-only
	  STATUS current
	  DESCRIPTION
        "
        Line Trscv High Power Down :This
        OID indicates the Line Trscv is
        entering Low Power state <Help>
        Status indicating the Line Trscv
        is entering Low Power state <Condtype>
        MSA_HIGH_POWER_DOWN <Probcause>
        informationalStatus(1000) <Alarmtype>
        other (1) <Polarity> (2)
        "
	  ::= { pm10001otu4AlmmsaModuleState 9 }



pm10001otu4AlmMsaTxTurnOff OBJECT-TYPE
	  SYNTAX EkiOnOff
	  MAX-ACCESS read-only
	  STATUS current
	  DESCRIPTION
        "
        Line Trscv Laser Turn Off :This
        OID indicates the Line Trscv is
        turning off its laser <Help> Status
        indicating the Line Trscv is turning
        off its laser <Condtype> MSA_TX_TURN_OFF
        <Probcause> informationalStatus(1000)
        <Alarmtype> other (1) <Polarity>
        (2)
        "
	  ::= { pm10001otu4AlmmsaModuleState 8 }



pm10001otu4AlmMsaFault OBJECT-TYPE
	  SYNTAX EkiOnOff
	  MAX-ACCESS read-only
	  STATUS current
	  DESCRIPTION
        "
        Line Trscv Fault :This OID indicates
        the Line Trscv is in Fault state
        <Help> Status indicating the Line
        Trscv is in Fault state <Condtype>
        MSA_FAULT <Probcause> informationalStatus(1000)
        <Alarmtype> other (1) <Polarity>
        (2)
        "
	  ::= { pm10001otu4AlmmsaModuleState 7 }



pm10001otu4AlmMsaReady OBJECT-TYPE
	  SYNTAX EkiOnOff
	  MAX-ACCESS read-only
	  STATUS current
	  DESCRIPTION
        "
        Line Trscv Ready :This OID indicates
        the Line Trscv is ready to operate
        <Help> Status indicating the Line
        Trscv is ready to operate <Condtype>
        MSA_READY <Probcause> informationalStatus(1000)
        <Alarmtype> other (1) <Polarity>
        (2)
        "
	  ::= { pm10001otu4AlmmsaModuleState 6 }



pm10001otu4AlmMsaTxTurnOn OBJECT-TYPE
	  SYNTAX EkiOnOff
	  MAX-ACCESS read-only
	  STATUS current
	  DESCRIPTION
        "
        Line Trscv Laser Turn On :This
        OID indicates the Line Trscv is
        turning on its laser <Help> Status
        indicating the Line Trscv is turning
        on its laser <Condtype> MSA_TX_TURN_ON
        <Probcause> informationalStatus(1000)
        <Alarmtype> other (1) <Polarity>
        (2)
        "
	  ::= { pm10001otu4AlmmsaModuleState 5 }



pm10001otu4AlmMsaTxOff OBJECT-TYPE
	  SYNTAX EkiOnOff
	  MAX-ACCESS read-only
	  STATUS current
	  DESCRIPTION
        "
        Line Trscv Laser Shutdown :This
        OID indicates the Line Trscv Laser
        is OFF <Help> Status indicating
        the Line Trscv Laser is OFF <Condtype>
        MSA_TX_OFF <Probcause> informationalStatus(1000)
        <Alarmtype> other (1) <Polarity>
        (2)
        "
	  ::= { pm10001otu4AlmmsaModuleState 4 }



pm10001otu4AlmMsaHighPowerUp OBJECT-TYPE
	  SYNTAX EkiOnOff
	  MAX-ACCESS read-only
	  STATUS current
	  DESCRIPTION
        "
        Line Trscv High Power Up :This
        OID indicates the Line Trscv is
        leaving Low Power state <Help>
         Status indicating the Line Trscv
        is leaving Low Power state <Condtype>
        MSA_HIGH_POWER_UP <Probcause> informationalStatus(1000)
        <Alarmtype> other (1) <Polarity>
        (2)
        "
	  ::= { pm10001otu4AlmmsaModuleState 3 }



pm10001otu4AlmMsaLowPower OBJECT-TYPE
	  SYNTAX EkiOnOff
	  MAX-ACCESS read-only
	  STATUS current
	  DESCRIPTION
        "
        Line Trscv Low Power :This OID
        indicates the Line Trscv is in
         low power state <Help> Status
         indicating the Line Trscv is in
        low power state <Condtype> MSA_LOW_POWER
        <Probcause> informationalStatus(1000)
        <Alarmtype> other (1) <Polarity>
        (2)
        "
	  ::= { pm10001otu4AlmmsaModuleState 2 }



pm10001otu4AlmMsaInitialize OBJECT-TYPE
	  SYNTAX EkiOnOff
	  MAX-ACCESS read-only
	  STATUS current
	  DESCRIPTION
        "
        Line Trscv Initialize :This OID
        indicates the Line Trscv initialization
        is in progress <Help> Status indicating
        the Line Trscv initialization is
        in progress <Condtype> MSA_INITIALIZE
        <Probcause> informationalStatus(1000)
        <Alarmtype> other (1) <Polarity>
        (2)
        "
	  ::= { pm10001otu4AlmmsaModuleState 1 }



--- *****************************************************
---     LEAF for the msaModuleGeneralStatus article
--- *****************************************************
pm10001otu4AlmmsaModuleGeneralStatus OBJECT IDENTIFIER ::= { pm10001otu4AlmOtherCrit 47 }




pm10001otu4AlmMsaHwInterlock OBJECT-TYPE
	  SYNTAX EkiOnOff
	  MAX-ACCESS read-only
	  STATUS current
	  DESCRIPTION
        "
        Line Trscv Hardware Interlock
         :This OID indicates the Line Trscv
        power is higher than the cooling
        capacity <Help> Alarm indicating
        the Line Trscv power is higher
         than the cooling capacity <Condtype>
        MSA_HW_INTERLOCK <Probcause> temperatureUnacceptable
        (51) <Alarmtype> equipmentAlarm
        (5) <Polarity> (2)
        "
	  ::= { pm10001otu4AlmmsaModuleGeneralStatus 14 }



pm10001otu4AlmMsaLossOfRefclk OBJECT-TYPE
	  SYNTAX EkiOnOff
	  MAX-ACCESS read-only
	  STATUS current
	  DESCRIPTION
        "
        Line Trscv Loss Of Ref Clock :This
        OID indicates a Loss of Reference
        clock is detected on the Line Trscv
        <Help> Alarm indicating a Loss
         of Reference clock is detected
        on the Line Trscv <Condtype> MSA_LOSS_OF_REFCLK
        <Probcause> inputOutputDeviceError
        (24) <Alarmtype> equipmentAlarm
        (5) <Polarity> (2)
        "
	  ::= { pm10001otu4AlmmsaModuleGeneralStatus 11 }



pm10001otu4AlmMsaTxJitterPllLol OBJECT-TYPE
	  SYNTAX EkiOnOff
	  MAX-ACCESS read-only
	  STATUS current
	  DESCRIPTION
        "
        Line Trscv Tx Jitter PLL Loss
         Of Lock :This OID indicates a
         Tx Jitter PLL Loss of Lock is
         detected on the Line Trscv <Help>
        Alarm indicating a Tx Jitter PLL
        Loss of Lock is detected on the
        Line Trscv <Condtype> MSA_TX_JITTER_PLL_LOL
        <Probcause> inputOutputDeviceError
        (24) <Alarmtype> equipmentAlarm
        (5) <Polarity> (2)
        "
	  ::= { pm10001otu4AlmmsaModuleGeneralStatus 10 }



pm10001otu4AlmMsaTxCmuLol OBJECT-TYPE
	  SYNTAX EkiOnOff
	  MAX-ACCESS read-only
	  STATUS current
	  DESCRIPTION
        "
        Line Trscv CMU Loss Of Lock :This
        OID indicates a Clock Multiplier
        Unit Loss of Lock is detected on
        the Line Trscv <Help> Alarm indicating
        a Clock Multiplier Unit Loss of
        Lock is detected on the Line Trscv
        <Condtype> MSA_TX_CMU_LOL <Probcause>
        inputOutputDeviceError (24) <Alarmtype>
        equipmentAlarm (5) <Polarity> (2)
        "
	  ::= { pm10001otu4AlmmsaModuleGeneralStatus 9 }



pm10001otu4AlmMsaTxLosf OBJECT-TYPE
	  SYNTAX EkiOnOff
	  MAX-ACCESS read-only
	  STATUS current
	  DESCRIPTION
        "
        Line Trscv Loss Of Signal Functionality
        :This OID indicates a Loss of Signal
        functionality is detected on the
        Line Trscv <Help> Alarm indicating
        a Loss of Signal functionality
         is detected on the Line Trscv
         <Condtype> MSA_TX_LOSF <Probcause>
        lossOfSignal (30) <Alarmtype> equipmentAlarm
        (5) <Polarity> (2)
        "
	  ::= { pm10001otu4AlmmsaModuleGeneralStatus 8 }



pm10001otu4AlmMsaTxHostLol OBJECT-TYPE
	  SYNTAX EkiOnOff
	  MAX-ACCESS read-only
	  STATUS current
	  DESCRIPTION
        "
        Line Trscv Tx Host Loss Of Lock
        :This OID indicates of Loss of
         Lock is detected on the Line Trscv
        Tx Host interface <Help> Alarm
         indicating of Loss of Lock is
         detected on the Line Trscv Tx
         Host interface <Condtype> MSA_TX_HOST_LOL
        <Probcause> receiverFailure (42)
        <Alarmtype> equipmentAlarm (5)
         <Polarity> (2)
        "
	  ::= { pm10001otu4AlmmsaModuleGeneralStatus 7 }



pm10001otu4AlmMsaRxLos OBJECT-TYPE
	  SYNTAX EkiOnOff
	  MAX-ACCESS read-only
	  STATUS current
	  DESCRIPTION
        "
        Line Trscv Loss Of Signal :This
        OID indicates a Loss of Signal
         is detected on the Line Trscv
         <Help> Alarm indicating a Loss
        of Signal is detected on the Line
        Trscv <Condtype> MSA_RX_LOS <Probcause>
        lossOfSignal (30) <Alarmtype> equipmentAlarm
        (5) <Polarity> (2)
        "
	  ::= { pm10001otu4AlmmsaModuleGeneralStatus 6 }



pm10001otu4AlmMsaRxNetworkLol OBJECT-TYPE
	  SYNTAX EkiOnOff
	  MAX-ACCESS read-only
	  STATUS current
	  DESCRIPTION
        "
        Line Trscv Rx Network Loss Of
         Lock :This OID indicates of Loss
        of Lock is detected on the Line
        Trscv Rx Network interface <Help>
        Alarm indicating of Loss of Lock
        is detected on the Line Trscv Rx
        Network interface <Condtype> MSA_RX_NETWORK_LOL
        <Probcause> receiverFailure (42)
        <Alarmtype> equipmentAlarm (5)
         <Polarity> (2)
        "
	  ::= { pm10001otu4AlmmsaModuleGeneralStatus 5 }



pm10001otu4AlmMsaOutOfAlignment OBJECT-TYPE
	  SYNTAX EkiOnOff
	  MAX-ACCESS read-only
	  STATUS current
	  DESCRIPTION
        "
        Line Trscv Out Of Alignment :This
        OID indicates an Out of alignment
        on the Line Trscv Host Interface
        <Help> Alarm indicating an Out
         of alignment on the Line Trscv
        Host Interface <Condtype> MSA_OUT_OF_ALIGNMENT
        <Probcause> receiverFailure (42)
        <Alarmtype> equipmentAlarm (5)
         <Polarity> (2)
        "
	  ::= { pm10001otu4AlmmsaModuleGeneralStatus 4 }



--- *****************************************************
---     LEAF for the msaGlobalAlarmSummary article
--- *****************************************************
pm10001otu4AlmmsaGlobalAlarmSummary OBJECT IDENTIFIER ::= { pm10001otu4AlmOtherCrit 48 }




pm10001otu4AlmMsaGlobAlarmAssertion  OBJECT-TYPE
	  SYNTAX EkiOnOff
	  MAX-ACCESS read-only
	  STATUS current
	  DESCRIPTION
        "
        Line Trscv Global Alarm :This
         OID indicates at least one Fault
        or Status is detected on the Line
        Trscv module <Help> Synthesis alarm
        indicating at least one Alarm,
         Warning, Fault or Status is detected
        on the Line Trscv module <Condtype>
        MSA_GLOB_ALARM_ASSERTION  <Probcause>
        informationalStatus(1000) <Alarmtype>
        other (1) <Polarity> (2)
        "
	  ::= { pm10001otu4AlmmsaGlobalAlarmSummary 16 }



pm10001otu4AlmMsaHostLaneFaultStatus  OBJECT-TYPE
	  SYNTAX EkiOnOff
	  MAX-ACCESS read-only
	  STATUS current
	  DESCRIPTION
        "
        Line Trscv Host Fault And Status
        :This OID indicates at least one
        Fault or Status is detected on
         the Line Trscv Host Interface
         <Help> Synthesis alarm indicating
        at least one Fault or Status is
        detected on the Line Trscv Host
        Interface <Condtype> MSA_HOST_LANE_FAULT_STATUS
         <Probcause> informationalStatus(1000)
        <Alarmtype> other (1) <Polarity>
        (2)
        "
	  ::= { pm10001otu4AlmmsaGlobalAlarmSummary 15 }



pm10001otu4AlmMsaNetworkLaneFaultStatus  OBJECT-TYPE
	  SYNTAX EkiOnOff
	  MAX-ACCESS read-only
	  STATUS current
	  DESCRIPTION
        "
        Line Trscv Network Fault And Status
        :This OID indicates at least one
        Fault or Status is detected on
         the Line Trscv Network Interface
        <Help> Synthesis alarm indicating
        at least one Fault or Status is
        detected on the Line Trscv Network
        Interface <Condtype> MSA_NETWORK_LANE_FAULT_STATUS
         <Probcause> informationalStatus(1000)
        <Alarmtype> other (1) <Polarity>
        (2)
        "
	  ::= { pm10001otu4AlmmsaGlobalAlarmSummary 14 }



pm10001otu4AlmMsaNetworkLaneAlarmWarning1 OBJECT-TYPE
	  SYNTAX EkiOnOff
	  MAX-ACCESS read-only
	  STATUS current
	  DESCRIPTION
        "
        Line Trscv Network Alarm And Warning
        1 :This OID indicates at least
         one DDM is detected on the Line
        Trscv Network Interface <Help>
         Synthesis alarm indicating at
         least one DDM Alarm or DDM Warning
        is detected on the Line Trscv Network
        Interface <Condtype> MSA_NETWORK_LANE_ALARM_WARNING_1
        <Probcause> informationalStatus(1000)
        <Alarmtype> other (1) <Polarity>
        (2)
        "
	  ::= { pm10001otu4AlmmsaGlobalAlarmSummary 13 }



pm10001otu4AlmMsaModuleAlarmWarning2 OBJECT-TYPE
	  SYNTAX EkiOnOff
	  MAX-ACCESS read-only
	  STATUS current
	  DESCRIPTION
        "
        Line Trscv Module Alarm And Warning
        2 :This OID indicates at least
         one DDM is detected on the Line
        Trscv module <Help> Synthesis alarm
        indicating at least one DDM Alarm
        or DDM Warning is detected on the
        Line Trscv module <Condtype> MSA_MODULE_ALARM_WARNING_2
        <Probcause> informationalStatus(1000)
        <Alarmtype> other (1) <Polarity>
        (2)
        "
	  ::= { pm10001otu4AlmmsaGlobalAlarmSummary 12 }



pm10001otu4AlmMsaModuleAlarmWarning1  OBJECT-TYPE
	  SYNTAX EkiOnOff
	  MAX-ACCESS read-only
	  STATUS current
	  DESCRIPTION
        "
        Line Trscv Module Alarm And Warning
        1 :This OID indicates at least
         one DDM is detected on the Line
        Trscv module <Help> Synthesis alarm
        indicating at least one DDM Alarm
        or DDM Warning is detected on the
        Line Trscv module <Condtype> MSA_MODULE_ALARM_WARNING_1
         <Probcause> informationalStatus(1000)
        <Alarmtype> other (1) <Polarity>
        (2)
        "
	  ::= { pm10001otu4AlmmsaGlobalAlarmSummary 11 }



pm10001otu4AlmModuleFault  OBJECT-TYPE
	  SYNTAX EkiOnOff
	  MAX-ACCESS read-only
	  STATUS current
	  DESCRIPTION
        "
        Line Trscv Module Fault :This
         OID indicates at least one Fault
        is detected on the Line Trscv module
        <Help> Synthesis alarm indicating
        at least one Fault is detected
         on the Line Trscv module <Condtype>
        MODULE_FAULT  <Probcause> informationalStatus(1000)
        <Alarmtype> other (1) <Polarity>
        (2)
        "
	  ::= { pm10001otu4AlmmsaGlobalAlarmSummary 10 }



pm10001otu4AlmMsaModuleGeneralStatus  OBJECT-TYPE
	  SYNTAX EkiOnOff
	  MAX-ACCESS read-only
	  STATUS current
	  DESCRIPTION
        "
        Line Trscv General Status :This
        OID indicates the Line Trscv module
        general <Help> Synthesis alarm
         indicating the Line Trscv module
        general status <Condtype> MSA_MODULE_GENERAL_STATUS
         <Probcause> informationalStatus(1000)
        <Alarmtype> other (1) <Polarity>
        (2)
        "
	  ::= { pm10001otu4AlmmsaGlobalAlarmSummary 9 }



pm10001otu4AlmMsaModuleState  OBJECT-TYPE
	  SYNTAX EkiOnOff
	  MAX-ACCESS read-only
	  STATUS current
	  DESCRIPTION
        "
        Line Trscv Module State :This
         OID indicates the Line Trscv module
        state <Help> Synthesis alarm indicating
        the Line Trscv module state <Condtype>
        MSA_MODULE_STATE  <Probcause> informationalStatus(1000)
        <Alarmtype> other (1) <Polarity>
        (2)
        "
	  ::= { pm10001otu4AlmmsaGlobalAlarmSummary 8 }



pm10001otu4AlmMsaNetworkLaneAlarmWarning2 OBJECT-TYPE
	  SYNTAX EkiOnOff
	  MAX-ACCESS read-only
	  STATUS current
	  DESCRIPTION
        "
        Line Trscv Network Alarm And Warning
        2 :This OID indicates at least
         one DDM This OID is detected on
        the Line Trscv Network Interface
        <Help> Synthesis alarm indicating
        at least one DDM Alarm or DDM Warning
        is detected on the Line Trscv Network
        Interface <Condtype> MSA_NETWORK_LANE_ALARM_WARNING_2
        <Probcause> informationalStatus(1000)
        <Alarmtype> other (1) <Polarity>
        (2)
        "
	  ::= { pm10001otu4AlmmsaGlobalAlarmSummary 7 }



pm10001otu4AlmMsaNetworkHostAlarmStatus OBJECT-TYPE
	  SYNTAX EkiOnOff
	  MAX-ACCESS read-only
	  STATUS current
	  DESCRIPTION
        "
        Line Trscv Network/Host Alarm
         Status :This OID indicates the
        state of the Network and Host interface
        of the Line Trscv <Help> Synthesis
        alarm indicating the alarm state
        of the Network and Host interface
        of the Line Trscv <Condtype> MSA_NETWORK_HOST_ALARM_STATUS
        <Probcause> informationalStatus(1000)
        <Alarmtype> other (1) <Polarity>
        (2)
        "
	  ::= { pm10001otu4AlmmsaGlobalAlarmSummary 6 }



pm10001otu4AlmMsaSoftGlobAlarmTest  OBJECT-TYPE
	  SYNTAX EkiOnOff
	  MAX-ACCESS read-only
	  STATUS current
	  DESCRIPTION
        "
        Line Trscv Global Alarm SW Test
        :This OID indicates the Line Trscv
        Global alarm This OID is raised
        by SW request for test purpose
         <Help> Status indicating the Line
        Trscv Global Alarm is raised by
        SW request for test purpose <Condtype>
        MSA_SOFT_GLOB_ALARM_TEST  <Probcause>
        informationalStatus(1000) <Alarmtype>
        other (1) <Polarity> (2)
        "
	  ::= { pm10001otu4AlmmsaGlobalAlarmSummary 1 }



--- *****************************************************
---     LEAF for the msaNetworkTxAlignment article
--- *****************************************************
pm10001otu4AlmmsaNetworkTxAlignment OBJECT IDENTIFIER ::= { pm10001otu4AlmOtherCrit 49 }




pm10001otu4AlmNetTxLossOfAlignment OBJECT-TYPE
	  SYNTAX EkiOnOff
	  MAX-ACCESS read-only
	  STATUS current
	  DESCRIPTION
        "
        Line Trscv Network Tx Loss Of
         Alignment :This OID indicates
         a Tx Loss of Alignment is detected
        on the Line Trscv Network interface
        <Help> Alarm indicating a Tx Loss
        of Alignment is detected on the
        Line Trscv Network interface <Condtype>
        NET_TX_LOSS_OF_ALIGNMENT <Probcause>
        transmitterFailure (56) <Alarmtype>
        equipmentAlarm (5) <Polarity> (2)
        "
	  ::= { pm10001otu4AlmmsaNetworkTxAlignment 16 }



pm10001otu4AlmNetTxOutOfAlignment OBJECT-TYPE
	  SYNTAX EkiOnOff
	  MAX-ACCESS read-only
	  STATUS current
	  DESCRIPTION
        "
        Line Trscv Network Tx Out Of Alignment
        :This OID indicates a Tx Out of
        Alignment is detected on the Line
        Trscv Network interface <Help>
         Alarm indicating a Tx Out of Alignment
        is detected on the Line Trscv Network
        interface <Condtype> NET_TX_OUT_OF_ALIGNMENT
        <Probcause> transmitterFailure
         (56) <Alarmtype> equipmentAlarm
        (5) <Polarity> (2)
        "
	  ::= { pm10001otu4AlmmsaNetworkTxAlignment 15 }



pm10001otu4AlmNetTxCmuLockFault OBJECT-TYPE
	  SYNTAX EkiOnOff
	  MAX-ACCESS read-only
	  STATUS current
	  DESCRIPTION
        "
        Line Trscv Network Tx CMU Lock
        Fault :This OID indicates a Tx
         Clock Multiplier Unit Lock Fault
        is detected on the Line Trscv Network
        interface <Help> Alarm indicating
        a Tx Clock Multiplier Unit Lock
        Fault is detected on the Line Trscv
        Network interface <Condtype> NET_TX_CMU_LOCK_FAULT
        <Probcause> transmitterFailure
         (56) <Alarmtype> equipmentAlarm
        (5) <Polarity> (2)
        "
	  ::= { pm10001otu4AlmmsaNetworkTxAlignment 14 }



pm10001otu4AlmNetTxReferenceClockFault OBJECT-TYPE
	  SYNTAX EkiOnOff
	  MAX-ACCESS read-only
	  STATUS current
	  DESCRIPTION
        "
        Line Trscv Network Tx Ref Clock
        Fault :This OID indicates a Tx
         Reference Clock Fault is detected
        on the Line Trscv Network interface
        <Help> Alarm indicating a Tx Reference
        Clock Fault is detected on the
         Line Trscv Network interface <Condtype>
        NET_TX_REFERENCE_CLOCK_FAULT <Probcause>
        transmitterFailure (56) <Alarmtype>
        equipmentAlarm (5) <Polarity> (2)
        "
	  ::= { pm10001otu4AlmmsaNetworkTxAlignment 13 }



pm10001otu4AlmNetTxTimingFault OBJECT-TYPE
	  SYNTAX EkiOnOff
	  MAX-ACCESS read-only
	  STATUS current
	  DESCRIPTION
        "
        Line Trscv Network Tx Timing Fault
        :This OID indicates a Tx Timing
        Fault is detected on the Line Trscv
        Network interface <Help> Alarm
         indicating a Tx Timing Fault is
        detected on the Line Trscv Network
        interface <Condtype> NET_TX_TIMING_FAULT
        <Probcause> transmitterFailure
         (56) <Alarmtype> equipmentAlarm
        (5) <Polarity> (2)
        "
	  ::= { pm10001otu4AlmmsaNetworkTxAlignment 12 }



--- *****************************************************
---     LEAF for the msaNetworkRxAlignment article
--- *****************************************************
pm10001otu4AlmmsaNetworkRxAlignment OBJECT IDENTIFIER ::= { pm10001otu4AlmOtherCrit 50 }




pm10001otu4AlmNetRxModemSyncDetectFault OBJECT-TYPE
	  SYNTAX EkiOnOff
	  MAX-ACCESS read-only
	  STATUS current
	  DESCRIPTION
        "
        Line Trscv Network Rx Modem Sync
        Detect Fault :This OID indicates
        a Rx Modem Synchronisation Detection
        Fault is detected on the Line Trscv
        Network interface <Help> Alarm
         indicating a Rx Modem Synchronisation
        Detection Fault is detected on
         the Line Trscv Network interface
        <Condtype> NET_RX_MODEM_SYNC_DETECT_FAULT
        <Probcause> receiverFailure (42)
        <Alarmtype> equipmentAlarm (5)
         <Polarity> (2)
        "
	  ::= { pm10001otu4AlmmsaNetworkRxAlignment 16 }



pm10001otu4AlmNetRxModemLockFault OBJECT-TYPE
	  SYNTAX EkiOnOff
	  MAX-ACCESS read-only
	  STATUS current
	  DESCRIPTION
        "
        Line Trscv Network Rx Modem Lock
        Fault :This OID indicates a Rx
         Modem Lock Fault is detected on
        the Line Trscv Network interface
        <Help> Alarm indicating a Rx Modem
        Lock Fault is detected on the Line
        Trscv Network interface <Condtype>
        NET_RX_MODEM_LOCK_FAULT <Probcause>
        receiverFailure (42) <Alarmtype>
        equipmentAlarm (5) <Polarity> (2)
        "
	  ::= { pm10001otu4AlmmsaNetworkRxAlignment 15 }



pm10001otu4AlmNetRxLossOfAlignment OBJECT-TYPE
	  SYNTAX EkiOnOff
	  MAX-ACCESS read-only
	  STATUS current
	  DESCRIPTION
        "
        Line Trscv Network Rx Loss Of
         Alignment :This OID indicates
         a Rx Loss of Alignment is detected
        on the Line Trscv Network interface
        <Help> Alarm indicating a Rx Loss
        of Alignment is detected on the
        Line Trscv Network interface <Condtype>
        NET_RX_LOSS_OF_ALIGNMENT <Probcause>
        receiverFailure (42) <Alarmtype>
        equipmentAlarm (5) <Polarity> (2)
        "
	  ::= { pm10001otu4AlmmsaNetworkRxAlignment 14 }



pm10001otu4AlmNetRxOutOfAlignment OBJECT-TYPE
	  SYNTAX EkiOnOff
	  MAX-ACCESS read-only
	  STATUS current
	  DESCRIPTION
        "
        Line Trscv Network Rx Out Of Alignment
        :This OID indicates a Rx Out of
        Alignment is detected on the Line
        Trscv Network interface <Help>
         Alarm indicating a Rx Out of Alignment
        is detected on the Line Trscv Network
        interface <Condtype> NET_RX_OUT_OF_ALIGNMENT
        <Probcause> receiverFailure (42)
        <Alarmtype> equipmentAlarm (5)
         <Polarity> (2)
        "
	  ::= { pm10001otu4AlmmsaNetworkRxAlignment 13 }



pm10001otu4AlmNetRxTimingFault OBJECT-TYPE
	  SYNTAX EkiOnOff
	  MAX-ACCESS read-only
	  STATUS current
	  DESCRIPTION
        "
        Line Trscv Network Rx Timing Fault
        :This OID indicates a Rx Timing
        Fault is detected on the Line Trscv
        Network interface <Help> Alarm
         indicating a Rx Timing Fault is
        detected on the Line Trscv Network
        interface <Condtype> NET_RX_TIMING_FAULT
        <Probcause> receiverFailure (42)
        <Alarmtype> equipmentAlarm (5)
         <Polarity> (2)
        "
	  ::= { pm10001otu4AlmmsaNetworkRxAlignment 12 }



--- *****************************************************
---     LEAF for the msaNetworkHostNetworkAlarmSummary article
--- *****************************************************
pm10001otu4AlmmsaNetworkHostNetworkAlarmSummary OBJECT IDENTIFIER ::= { pm10001otu4AlmOtherCrit 51 }




pm10001otu4AlmHostTxOtnStatus OBJECT-TYPE
	  SYNTAX EkiOnOff
	  MAX-ACCESS read-only
	  STATUS current
	  DESCRIPTION
        "
        Line Trscv Host Tx OTN :This OID
        indicates a Tx OTN Fault is detected
        on the Line Trscv Host interface
        <Help> Synthesis Alarm indicating
        a Tx OTN Fault is detected on the
        Line Trscv Host interface <Condtype>
        HOST_TX_OTN_STATUS <Probcause>
         informationalStatus(1000) <Alarmtype>
        other (1) <Polarity> (2)
        "
	  ::= { pm10001otu4AlmmsaNetworkHostNetworkAlarmSummary 16 }



pm10001otu4AlmHostTxAlignment OBJECT-TYPE
	  SYNTAX EkiOnOff
	  MAX-ACCESS read-only
	  STATUS current
	  DESCRIPTION
        "
        Line Trscv Host Tx Alignment :This
        OID indicates a Tx Alignment Fault
        is detected on the Line Trscv Host
        interface <Help> Synthesis Alarm
        indicating a Tx Alignment Fault
        is detected on the Line Trscv Host
        interface <Condtype> HOST_TX_ALIGNMENT
        <Probcause> informationalStatus(1000)
        <Alarmtype> other (1) <Polarity>
        (2)
        "
	  ::= { pm10001otu4AlmmsaNetworkHostNetworkAlarmSummary 15 }



pm10001otu4AlmHostRxAlignment OBJECT-TYPE
	  SYNTAX EkiOnOff
	  MAX-ACCESS read-only
	  STATUS current
	  DESCRIPTION
        "
        Line Trscv Host Rx Alignment :This
        OID indicates a Rx Alignment Fault
        is detected on the Line Trscv Host
        interface <Help> Synthesis Alarm
        indicating a Rx Alignment Fault
        is detected on the Line Trscv Host
        interface <Condtype> HOST_RX_ALIGNMENT
        <Probcause> informationalStatus(1000)
        <Alarmtype> other (1) <Polarity>
        (2)
        "
	  ::= { pm10001otu4AlmmsaNetworkHostNetworkAlarmSummary 14 }



pm10001otu4AlmNetworkRxOtn OBJECT-TYPE
	  SYNTAX EkiOnOff
	  MAX-ACCESS read-only
	  STATUS current
	  DESCRIPTION
        "
        Line Trscv Network Rx OTN :This
        OID indicates a Rx OTN Fault is
        detected on the Line Trscv Network
        interface <Help> Synthesis Alarm
        indicating a Rx OTN Fault is detected
        on the Line Trscv Network interface
        <Condtype> NETWORK_RX_OTN <Probcause>
        informationalStatus(1000) <Alarmtype>
        other (1) <Polarity> (2)
        "
	  ::= { pm10001otu4AlmmsaNetworkHostNetworkAlarmSummary 13 }



pm10001otu4AlmNetworkRxAlignment OBJECT-TYPE
	  SYNTAX EkiOnOff
	  MAX-ACCESS read-only
	  STATUS current
	  DESCRIPTION
        "
        Line Trscv Network Rx Alignment
        :This OID indicates a Rx Alignment
        Fault is detected on the Line Trscv
        Network interface <Help> Synthesis
        Alarm indicating a Rx Alignment
        Fault is detected on the Line Trscv
        Network interface <Condtype> NETWORK_RX_ALIGNMENT
        <Probcause> informationalStatus(1000)
        <Alarmtype> other (1) <Polarity>
        (2)
        "
	  ::= { pm10001otu4AlmmsaNetworkHostNetworkAlarmSummary 12 }



pm10001otu4AlmNetworkTxAlignment OBJECT-TYPE
	  SYNTAX EkiOnOff
	  MAX-ACCESS read-only
	  STATUS current
	  DESCRIPTION
        "
        Line Trscv Network Tx Alignment
        :This OID indicates a Tx Alignment
        Fault is detected on the Line Trscv
        Network interface <Help> Synthesis
        Alarm indicating a Tx Alignment
        Fault is detected on the Line Trscv
        Network interface <Condtype> NETWORK_TX_ALIGNMENT
        <Probcause> informationalStatus(1000)
        <Alarmtype> other (1) <Polarity>
        (2)
        "
	  ::= { pm10001otu4AlmmsaNetworkHostNetworkAlarmSummary 11 }



--- *****************************************************
---     LEAF for the msaHostTxAlignment article
--- *****************************************************
pm10001otu4AlmmsaHostTxAlignment OBJECT IDENTIFIER ::= { pm10001otu4AlmOtherCrit 52 }




pm10001otu4AlmHostTxCdrLockFault OBJECT-TYPE
	  SYNTAX EkiOnOff
	  MAX-ACCESS read-only
	  STATUS current
	  DESCRIPTION
        "
        Line Trscv Host Tx CDR Lock Fault
        :This OID indicates a Tx Clock
         Data Recovery Lock Fault is detected
        on the Line Trscv Host interface
        <Help> Alarm indicating a Tx Clock
        Data Recovery Lock Fault is detected
        on the Line Trscv Host interface
        <Condtype> HOST_TX_CDR_LOCK_FAULT
        <Probcause> receiverFailure (42)
        <Alarmtype> equipmentAlarm (5)
         <Polarity> (2)
        "
	  ::= { pm10001otu4AlmmsaHostTxAlignment 16 }



pm10001otu4AlmHostTxLossOfAlignment OBJECT-TYPE
	  SYNTAX EkiOnOff
	  MAX-ACCESS read-only
	  STATUS current
	  DESCRIPTION
        "
        Line Trscv Host Tx Loss Of Alignment
        :This OID indicates a Tx Loss of
        Alignment is detected on the Line
        Trscv Host interface <Help> Alarm
        indicating a Tx Loss of Alignment
        is detected on the Line Trscv Host
        interface <Condtype> HOST_TX_LOSS_OF_ALIGNMENT
        <Probcause> receiverFailure (42)
        <Alarmtype> equipmentAlarm (5)
         <Polarity> (2)
        "
	  ::= { pm10001otu4AlmmsaHostTxAlignment 15 }



pm10001otu4AlmHostTxOutOfAlignment OBJECT-TYPE
	  SYNTAX EkiOnOff
	  MAX-ACCESS read-only
	  STATUS current
	  DESCRIPTION
        "
        Line Trscv Host Tx Out Of Alignment
        :This OID indicates a Tx Out of
        Alignment is detected on the Line
        Trscv Host interface <Help> Alarm
        indicating a Tx Out of Alignment
        is detected on the Line Trscv Host
        interface <Condtype> HOST_TX_OUT_OF_ALIGNMENT
        <Probcause> receiverFailure (42)
        <Alarmtype> equipmentAlarm (5)
         <Polarity> (2)
        "
	  ::= { pm10001otu4AlmmsaHostTxAlignment 14 }



pm10001otu4AlmHostTxDeskewLockFault OBJECT-TYPE
	  SYNTAX EkiOnOff
	  MAX-ACCESS read-only
	  STATUS current
	  DESCRIPTION
        "
        Line Trscv Host Tx Deskew Lock
        Fault :This OID indicates a Tx
         Deskew Lock Fault is detected
         on  the Line Trscv Host interface
        <Help> Alarm indicating a Tx Deskew
        Lock Fault is detected on  the
         Line Trscv Host interface <Condtype>
        HOST_TX_DESKEW_LOCK_FAULT <Probcause>
        receiverFailure (42) <Alarmtype>
        equipmentAlarm (5) <Polarity> (2)
        "
	  ::= { pm10001otu4AlmmsaHostTxAlignment 13 }



--- *****************************************************
---     LEAF for the msaHostRxAlignment article
--- *****************************************************
pm10001otu4AlmmsaHostRxAlignment OBJECT IDENTIFIER ::= { pm10001otu4AlmOtherCrit 53 }




pm10001otu4AlmHostRxLossOfAlignment OBJECT-TYPE
	  SYNTAX EkiOnOff
	  MAX-ACCESS read-only
	  STATUS current
	  DESCRIPTION
        "
        Line Trscv Host Rx Loss Of Alignment
        :This OID indicates a Rx Loss of
        Alignment is detected on the Line
        Trscv Host interface <Help> Alarm
        indicating a Rx Loss of Alignment
        is detected on the Line Trscv Host
        interface <Condtype> HOST_RX_LOSS_OF_ALIGNMENT
        <Probcause> transmitterFailure
         (56) <Alarmtype> equipmentAlarm
        (5) <Polarity> (2)
        "
	  ::= { pm10001otu4AlmmsaHostRxAlignment 16 }



pm10001otu4AlmHostRxOutOfAlignment OBJECT-TYPE
	  SYNTAX EkiOnOff
	  MAX-ACCESS read-only
	  STATUS current
	  DESCRIPTION
        "
        Line Trscv Host Rx Out Of Alignment
        :This OID indicates a Rx Out of
        Alignment is detected on the Line
        Trscv Host interface <Help> Alarm
        indicating a Rx Out of Alignment
        is detected on the Line Trscv Host
        interface <Condtype> HOST_RX_OUT_OF_ALIGNMENT
        <Probcause> transmitterFailure
         (56) <Alarmtype> equipmentAlarm
        (5) <Polarity> (2)
        "
	  ::= { pm10001otu4AlmmsaHostRxAlignment 15 }



pm10001otu4AlmHostRxCmuLockFault OBJECT-TYPE
	  SYNTAX EkiOnOff
	  MAX-ACCESS read-only
	  STATUS current
	  DESCRIPTION
        "
        Line Trscv Host Rx CMU Lock Fault
        :This OID indicates a Rx Clock
         Multiplier Unit Lock Fault is
         detected on the Line Trscv Host
        interface <Help> Alarm indicating
        a Rx Clock Multiplier Unit Lock
        Fault is detected on the Line Trscv
        Host interface <Condtype> HOST_RX_CMU_LOCK_FAULT
        <Probcause> transmitterFailure
         (56) <Alarmtype> equipmentAlarm
        (5) <Polarity> (2)
        "
	  ::= { pm10001otu4AlmmsaHostRxAlignment 14 }



--- *********************************************************
---     TABLE for the pm10001otu4AlmclientNetworkLaneAlarmWarning articles
--- *********************************************************

pm10001otu4AlmclientNetworkLaneAlarmWarningTable OBJECT-TYPE
	SYNTAX  SEQUENCE OF Pm10001otu4AlmclientNetworkLaneAlarmWarningEntry
	MAX-ACCESS not-accessible
	STATUS current
	DESCRIPTION
        "
        List of pm10001otu4AlmclientNetworkLaneAlarmWarning
        Article
        "
	::= { pm10001otu4AlmClientNurg 56 }


pm10001otu4AlmclientNetworkLaneAlarmWarningEntry OBJECT-TYPE
	SYNTAX Pm10001otu4AlmclientNetworkLaneAlarmWarningEntry
	MAX-ACCESS not-accessible
	STATUS current
	DESCRIPTION
        "
        Row definition for the pm10001otu4AlmclientNetworkLaneAlarmWarning
        table
        "
	INDEX   { pm10001otu4AlmclientNetworkLaneAlarmWarningIndex }
	::= { pm10001otu4AlmclientNetworkLaneAlarmWarningTable 1 }


Pm10001otu4AlmclientNetworkLaneAlarmWarningEntry ::=
	SEQUENCE {
	pm10001otu4AlmclientNetworkLaneAlarmWarningIndex
		INTEGER,
	pm10001otu4AlmClientBiasHighAlarmPortn
		EkiOnOff,
	pm10001otu4AlmClientBiasHighWarningPortn
		EkiOnOff,
	pm10001otu4AlmClientBiasLowWarningPortn
		EkiOnOff,
	pm10001otu4AlmClientBiasLowAlarmPortn
		EkiOnOff,
	pm10001otu4AlmClientTxPowerHighAlarmPortn
		EkiOnOff,
	pm10001otu4AlmClientTxPowerHighWarningPortn
		EkiOnOff,
	pm10001otu4AlmClientTxPowerLowWarningPortn
		EkiOnOff,
	pm10001otu4AlmClientTxPowerLowAlarmPortn
		EkiOnOff,
	pm10001otu4AlmClientLaserTempHighAlarmPortn
		EkiOnOff,
	pm10001otu4AlmClientLaserTempHighWarningPortn
		EkiOnOff,
	pm10001otu4AlmClientLaserTempLowWarningPortn
		EkiOnOff,
	pm10001otu4AlmLaserTempLowAlarmPortn
		EkiOnOff,
	pm10001otu4AlmClientRxPowerHighAlarmPortn
		EkiOnOff,
	pm10001otu4AlmClientRxPowerHighWarningPortn
		EkiOnOff,
	pm10001otu4AlmClientRxPowerLowWarningPortn
		EkiOnOff,
	pm10001otu4AlmClientRxPowerLowAlarmPortn
		EkiOnOff
	}


pm10001otu4AlmclientNetworkLaneAlarmWarningIndex OBJECT-TYPE
	SYNTAX  INTEGER(0..128)
	MAX-ACCESS  read-only
	STATUS current
	DESCRIPTION
        "
        Index definition for the pm10001otu4AlmclientNetworkLaneAlarmWarning
        table
        "
	::= { pm10001otu4AlmclientNetworkLaneAlarmWarningEntry 1 }


pm10001otu4AlmClientBiasHighAlarmPortn OBJECT-TYPE
	SYNTAX  EkiOnOff
	MAX-ACCESS read-only
	STATUS current
	DESCRIPTION
        "
        Client Trscv Bias High Alarm :This
        OID indicates that the Trscv laser
        bias current is higher than the
        threshold value written in the
         Trscv EEPROM <Help> Alarm indicating
        that the Trscv laser bias current
        is higher than the threshold value
        written in the Trscv EEPROM <Condtype>
        CLIENT_BIAS_HIGH_ALARM <Probcause>
        transmitterFailure (56) <Alarmtype>
        equipmentAlarm (5) <Polarity> (2)
        "
	::= { pm10001otu4AlmclientNetworkLaneAlarmWarningEntry 17 }


pm10001otu4AlmClientBiasHighWarningPortn OBJECT-TYPE
	SYNTAX  EkiOnOff
	MAX-ACCESS read-only
	STATUS current
	DESCRIPTION
        "
        Client Trscv Bias High Warning
        :This OID indicates that the Trscv
        laser bias current is higher than
        the threshold value written in
         the Trscv EEPROM <Help> Warning
        indicating that the Trscv laser
        bias current is higher than the
        threshold value written in the
         Trscv EEPROM <Condtype> CLIENT_BIAS_HIGH_WARNING
        <Probcause> transmitterFailure
         (56) <Alarmtype> equipmentAlarm
        (5) <Polarity> (2)
        "
	::= { pm10001otu4AlmclientNetworkLaneAlarmWarningEntry 16 }


pm10001otu4AlmClientBiasLowWarningPortn OBJECT-TYPE
	SYNTAX  EkiOnOff
	MAX-ACCESS read-only
	STATUS current
	DESCRIPTION
        "
        Client Trscv Bias Low Warning
         :This OID indicates that the Trscv
        laser bias current is lower than
        the threshold value written in
         the Trscv EEPROM <Help> Warning
        indicating that the Trscv laser
        bias current is lower than the
         threshold value written in the
        Trscv EEPROM <Condtype> CLIENT_BIAS_LOW_WARNING
        <Probcause> transmitterFailure
         (56) <Alarmtype> equipmentAlarm
        (5) <Polarity> (2)
        "
	::= { pm10001otu4AlmclientNetworkLaneAlarmWarningEntry 15 }


pm10001otu4AlmClientBiasLowAlarmPortn OBJECT-TYPE
	SYNTAX  EkiOnOff
	MAX-ACCESS read-only
	STATUS current
	DESCRIPTION
        "
        Client Trscv Bias Low Alarm :This
        OID indicates that the Trscv laser
        bias current is lower than the
         threshold value written in the
        Trscv EEPROM <Help> Alarm indicating
        that the Trscv laser bias current
        is lower than the threshold value
        written in the Trscv EEPROM <Condtype>
        CLIENT_BIAS_LOW_ALARM <Probcause>
        transmitterFailure (56) <Alarmtype>
        equipmentAlarm (5) <Polarity> (2)
        "
	::= { pm10001otu4AlmclientNetworkLaneAlarmWarningEntry 14 }


pm10001otu4AlmClientTxPowerHighAlarmPortn OBJECT-TYPE
	SYNTAX  EkiOnOff
	MAX-ACCESS read-only
	STATUS current
	DESCRIPTION
        "
        Client Trscv Tx Power High Alarm
        :This OID indicates that the Trscv
        output power is higher than the
        threshold value written in the
         Trscv EEPROM <Help> Alarm indicating
        that the Trscv output power is
         higher than the threshold value
        written in the Trscv EEPROM <Condtype>
        CLIENT_TX_POWER_HIGH_ALARM <Probcause>
        transmitterFailure (56) <Alarmtype>
        equipmentAlarm (5) <Polarity> (2)
        "
	::= { pm10001otu4AlmclientNetworkLaneAlarmWarningEntry 13 }


pm10001otu4AlmClientTxPowerHighWarningPortn OBJECT-TYPE
	SYNTAX  EkiOnOff
	MAX-ACCESS read-only
	STATUS current
	DESCRIPTION
        "
        Client Trscv Tx Power High Warning
        :This OID indicates that the Trscv
        output power is higher than the
        threshold value written in the
         Trscv EEPROM <Help> Warning indicating
        that the Trscv output power is
         higher than the threshold value
        written in the Trscv EEPROM <Condtype>
        CLIENT_TX_POWER_HIGH_WARNING <Probcause>
        transmitterFailure (56) <Alarmtype>
        equipmentAlarm (5) <Polarity> (2)
        "
	::= { pm10001otu4AlmclientNetworkLaneAlarmWarningEntry 12 }


pm10001otu4AlmClientTxPowerLowWarningPortn OBJECT-TYPE
	SYNTAX  EkiOnOff
	MAX-ACCESS read-only
	STATUS current
	DESCRIPTION
        "
        Client Trscv Tx Power Low Warning
        :This OID indicates that the Trscv
        output power is lower than the
         threshold value written in the
        Trscv EEPROM <Help> Warning indicating
        that the Trscv output power is
         lower than the threshold value
        written in the Trscv EEPROM <Condtype>
        CLIENT_TX_POWER_LOW_WARNING <Probcause>
        transmitterFailure (56) <Alarmtype>
        equipmentAlarm (5) <Polarity> (2)
        "
	::= { pm10001otu4AlmclientNetworkLaneAlarmWarningEntry 11 }


pm10001otu4AlmClientTxPowerLowAlarmPortn OBJECT-TYPE
	SYNTAX  EkiOnOff
	MAX-ACCESS read-only
	STATUS current
	DESCRIPTION
        "
        Client Trscv Tx Power Low Alarm
        :This OID indicates that the Trscv
        output power is lower than the
         threshold value written in the
        Trscv EEPROM <Help> Alarm indicating
        that the Trscv output power is
         lower than the threshold value
        written in the Trscv EEPROM <Condtype>
        CLIENT_TX_POWER_LOW_ALARM <Probcause>
        transmitterFailure (56) <Alarmtype>
        equipmentAlarm (5) <Polarity> (2)
        "
	::= { pm10001otu4AlmclientNetworkLaneAlarmWarningEntry 10 }


pm10001otu4AlmClientLaserTempHighAlarmPortn OBJECT-TYPE
	SYNTAX  EkiOnOff
	MAX-ACCESS read-only
	STATUS current
	DESCRIPTION
        "
        Client Trscv Laser Temp High Alarm
        :This OID indicates that the Trscv
        Laser Temperature is higher than
        the threshold value written in
         the Trscv EEPROM <Help> Alarm
         indicating that the Trscv Laser
        Temperature is higher than the
         threshold value written in the
        Trscv EEPROM <Condtype> CLIENT_LASER_TEMP_HIGH_ALARM
        <Probcause> temperatureUnacceptable
        (51) <Alarmtype> equipmentAlarm
        (5) <Polarity> (2)
        "
	::= { pm10001otu4AlmclientNetworkLaneAlarmWarningEntry 9 }


pm10001otu4AlmClientLaserTempHighWarningPortn OBJECT-TYPE
	SYNTAX  EkiOnOff
	MAX-ACCESS read-only
	STATUS current
	DESCRIPTION
        "
        Client Trscv Laser Temp High Warning
        :This OID indicates that the Trscv
        Laser Temperature is higher than
        the threshold value written in
         the Trscv EEPROM <Help> Warning
        indicating that the Trscv Laser
        Temperature is higher than the
         threshold value written in the
        Trscv EEPROM <Condtype> CLIENT_LASER_TEMP_HIGH_WARNING
        <Probcause> temperatureUnacceptable
        (51) <Alarmtype> equipmentAlarm
        (5) <Polarity> (2)
        "
	::= { pm10001otu4AlmclientNetworkLaneAlarmWarningEntry 8 }


pm10001otu4AlmClientLaserTempLowWarningPortn OBJECT-TYPE
	SYNTAX  EkiOnOff
	MAX-ACCESS read-only
	STATUS current
	DESCRIPTION
        "
        Client Trscv Laser Temp Low Warning
        :This OID indicates that the Trscv
        Laser Temperature is lower than
        the threshold value written in
         the Trscv EEPROM <Help> Warning
        indicating that the Trscv Laser
        Temperature is lower than the threshold
        value written in the Trscv EEPROM
        <Condtype> CLIENT_LASER_TEMP_LOW_WARNING
        <Probcause> temperatureUnacceptable
        (51) <Alarmtype> equipmentAlarm
        (5) <Polarity> (2)
        "
	::= { pm10001otu4AlmclientNetworkLaneAlarmWarningEntry 7 }


pm10001otu4AlmLaserTempLowAlarmPortn OBJECT-TYPE
	SYNTAX  EkiOnOff
	MAX-ACCESS read-only
	STATUS current
	DESCRIPTION
        "
        Client Trscv Laser Temp Low Alarm
        :This OID indicates that the Trscv
        Laser Temperature is lower than
        the threshold value written in
         the Trscv EEPROM <Help> Alarm
         indicating that the Trscv Laser
        Temperature is lower than the threshold
        value written in the Trscv EEPROM
        <Condtype> LASER_TEMP_LOW_ALARM
        <Probcause> temperatureUnacceptable
        (51) <Alarmtype> equipmentAlarm
        (5) <Polarity> (2)
        "
	::= { pm10001otu4AlmclientNetworkLaneAlarmWarningEntry 6 }


pm10001otu4AlmClientRxPowerHighAlarmPortn OBJECT-TYPE
	SYNTAX  EkiOnOff
	MAX-ACCESS read-only
	STATUS current
	DESCRIPTION
        "
        Client Trscv Rx Power High Alarm
        :This OID indicates that the Trscv
        input power is higher than the
         threshold value written in the
        Trscv EEPROM <Help> Alarm indicating
        that the Trscv input power is higher
        than the threshold value written
        in the Trscv EEPROM <Condtype>
         CLIENT_RX_POWER_HIGH_ALARM <Probcause>
        receiveFailure (41) <Alarmtype>
        equipmentAlarm (5) <Polarity> (2)
        "
	::= { pm10001otu4AlmclientNetworkLaneAlarmWarningEntry 5 }


pm10001otu4AlmClientRxPowerHighWarningPortn OBJECT-TYPE
	SYNTAX  EkiOnOff
	MAX-ACCESS read-only
	STATUS current
	DESCRIPTION
        "
        Client Trscv Rx Power High Warning
        :This OID indicates that the Trscv
        input power is higher than the
         threshold value written in the
        Trscv EEPROM <Help> Warning indicating
        that the Trscv input power is higher
        than the threshold value written
        in the Trscv EEPROM <Condtype>
         CLIENT_RX_POWER_HIGH_WARNING <Probcause>
        receiveFailure (41) <Alarmtype>
        equipmentAlarm (5) <Polarity> (2)
        "
	::= { pm10001otu4AlmclientNetworkLaneAlarmWarningEntry 4 }


pm10001otu4AlmClientRxPowerLowWarningPortn OBJECT-TYPE
	SYNTAX  EkiOnOff
	MAX-ACCESS read-only
	STATUS current
	DESCRIPTION
        "
        Client Trscv Rx Power Low Warning
        :This OID indicates that the Trscv
        input power is lower than the threshold
        value written in the Trscv EEPROM
        <Help> Warning indicating that
         the Trscv input power is lower
        than the threshold value written
        in the Trscv EEPROM <Condtype>
         CLIENT_RX_POWER_LOW_WARNING <Probcause>
        receiveFailure (41) <Alarmtype>
        equipmentAlarm (5) <Polarity> (2)
        "
	::= { pm10001otu4AlmclientNetworkLaneAlarmWarningEntry 3 }


pm10001otu4AlmClientRxPowerLowAlarmPortn OBJECT-TYPE
	SYNTAX  EkiOnOff
	MAX-ACCESS read-only
	STATUS current
	DESCRIPTION
        "
        Client Trscv Rx Power Low Alarm
        :This OID indicates that the Trscv
        input power is lower than the threshold
        value written in the Trscv EEPROM
        <Help> Alarm indicating that the
        Trscv input power is lower than
        the threshold value written in
         the Trscv EEPROM <Condtype> CLIENT_RX_POWER_LOW_ALARM
        <Probcause> receiveFailure (41)
        <Alarmtype> equipmentAlarm (5)
         <Polarity> (2)
        "
	::= { pm10001otu4AlmclientNetworkLaneAlarmWarningEntry 2 }


--- *********************************************************
---     TABLE for the pm10001otu4AlmclientNetworkLaneFault articles
--- *********************************************************

pm10001otu4AlmclientNetworkLaneFaultTable OBJECT-TYPE
	SYNTAX  SEQUENCE OF Pm10001otu4AlmclientNetworkLaneFaultEntry
	MAX-ACCESS not-accessible
	STATUS current
	DESCRIPTION
        "
        List of pm10001otu4AlmclientNetworkLaneFault
        Article
        "
	::= { pm10001otu4AlmClientUrg 72 }


pm10001otu4AlmclientNetworkLaneFaultEntry OBJECT-TYPE
	SYNTAX Pm10001otu4AlmclientNetworkLaneFaultEntry
	MAX-ACCESS not-accessible
	STATUS current
	DESCRIPTION
        "
        Row definition for the pm10001otu4AlmclientNetworkLaneFault
        table
        "
	INDEX   { pm10001otu4AlmclientNetworkLaneFaultIndex }
	::= { pm10001otu4AlmclientNetworkLaneFaultTable 1 }


Pm10001otu4AlmclientNetworkLaneFaultEntry ::=
	SEQUENCE {
	pm10001otu4AlmclientNetworkLaneFaultIndex
		INTEGER,
	pm10001otu4AlmClientLaneTecFaultPortn
		EkiOnOff,
	pm10001otu4AlmClientLaneWavelengthUnlockedPortn
		EkiOnOff,
	pm10001otu4AlmClientLaneApdPowerSupplyPortn
		EkiOnOff,
	pm10001otu4AlmClientLaneTxLosfPortn
		EkiOnOff,
	pm10001otu4AlmClientLaneTxLolPortn
		EkiOnOff,
	pm10001otu4AlmClientLaneRxLosPortn
		EkiOnOff,
	pm10001otu4AlmClientLaneRxLolPortn
		EkiOnOff,
	pm10001otu4AlmClientLaneRxFifoErrorPortn
		EkiOnOff
	}


pm10001otu4AlmclientNetworkLaneFaultIndex OBJECT-TYPE
	SYNTAX  INTEGER(0..128)
	MAX-ACCESS  read-only
	STATUS current
	DESCRIPTION
        "
        Index definition for the pm10001otu4AlmclientNetworkLaneFault
        table
        "
	::= { pm10001otu4AlmclientNetworkLaneFaultEntry 1 }


pm10001otu4AlmClientLaneTecFaultPortn OBJECT-TYPE
	SYNTAX  EkiOnOff
	MAX-ACCESS read-only
	STATUS current
	DESCRIPTION
        "
        Client Network Lane TEC Fault
         :This OID indicates a TEC Fault
        on the Client Trscv Network Lane
        <Help> Alarm indicating a TEC Fault
        on the Client Trscv Network Lane
        <Condtype> CLIENT_LANE_TEC_FAULT
        <Probcause> transmitterFailure
         (56) <Alarmtype> equipmentAlarm
        (5) <Polarity> (2)
        "
	::= { pm10001otu4AlmclientNetworkLaneFaultEntry 17 }


pm10001otu4AlmClientLaneWavelengthUnlockedPortn OBJECT-TYPE
	SYNTAX  EkiOnOff
	MAX-ACCESS read-only
	STATUS current
	DESCRIPTION
        "
        Client Network Lane Wavelength
        Unlock :This OID indicates a Wavelength
        unlock on the Client Trscv Network
        Lane <Help> Alarm indicating a
         Wavelength unlock on the Client
        Trscv Network Lane <Condtype> CLIENT_LANE_WAVELENGTH_UNLOCKED
        <Probcause> transmitterFailure
         (56) <Alarmtype> equipmentAlarm
        (5) <Polarity> (2)
        "
	::= { pm10001otu4AlmclientNetworkLaneFaultEntry 16 }


pm10001otu4AlmClientLaneApdPowerSupplyPortn OBJECT-TYPE
	SYNTAX  EkiOnOff
	MAX-ACCESS read-only
	STATUS current
	DESCRIPTION
        "
        Client Network Lane APD Power
         Supply :This OID indicates an
         APD Power supply failure on the
        Client Trscv Network Lane <Help>
        Alarm indicating an APD Power supply
        failure on the Client Trscv Network
        Lane <Condtype> CLIENT_LANE_APD_POWER_SUPPLY
        <Probcause> transmitterFailure
         (56) <Alarmtype> equipmentAlarm
        (5) <Polarity> (2)
        "
	::= { pm10001otu4AlmclientNetworkLaneFaultEntry 15 }


pm10001otu4AlmClientLaneTxLosfPortn OBJECT-TYPE
	SYNTAX  EkiOnOff
	MAX-ACCESS read-only
	STATUS current
	DESCRIPTION
        "
        Client Network Lane Tx Loss Of
        Signal Functionality :This OID
         indicates a Tx Loss of Signal
         Functionality on the Client Trscv
        Network Lane <Help> Alarm indicating
        a Tx Loss of Signal Functionality
        on the Client Trscv Network Lane
        <Condtype> CLIENT_LANE_TX_LOSF
         <Probcause> transmitterFailure
        (56) <Alarmtype> equipmentAlarm
        (5) <Polarity> (2)
        "
	::= { pm10001otu4AlmclientNetworkLaneFaultEntry 9 }


pm10001otu4AlmClientLaneTxLolPortn OBJECT-TYPE
	SYNTAX  EkiOnOff
	MAX-ACCESS read-only
	STATUS current
	DESCRIPTION
        "
        Client Network Lane Tx Loss Of
        Lock :This OID indicates a Tx Loss
        of Lock on the Client Trscv Network
        Lane <Help> Alarm indicating a
         Tx Loss of Lock on the Client
         Trscv Network Lane <Condtype>
         CLIENT_LANE_TX_LOL <Probcause>
        transmitterFailure (56) <Alarmtype>
        equipmentAlarm (5) <Polarity> (2)
        "
	::= { pm10001otu4AlmclientNetworkLaneFaultEntry 8 }


pm10001otu4AlmClientLaneRxLosPortn OBJECT-TYPE
	SYNTAX  EkiOnOff
	MAX-ACCESS read-only
	STATUS current
	DESCRIPTION
        "
        Client Network Lane Rx Loss Of
        Signal :This OID indicates a Rx
        Loss of Signal on the Client Trscv
        Network Lane <Help> Alarm indicating
        a Rx Loss of Signal on the Client
        Trscv Network Lane <Condtype> CLIENT_LANE_RX_LOS
        <Probcause> receiveFailure (41)
        <Alarmtype> physicalViolation (9)
        <Polarity> (2)
        "
	::= { pm10001otu4AlmclientNetworkLaneFaultEntry 6 }


pm10001otu4AlmClientLaneRxLolPortn OBJECT-TYPE
	SYNTAX  EkiOnOff
	MAX-ACCESS read-only
	STATUS current
	DESCRIPTION
        "
        Client Network Lane Rx Loss Of
        Lock :This OID indicates a Rx Loss
        of Lock on the Client Trscv Network
        Lane <Help> Alarm indicating a
         Rx Loss of Lock on the Client
         Trscv Network Lane <Condtype>
         CLIENT_LANE_RX_LOL <Probcause>
        receiverFailure (42) <Alarmtype>
        equipmentAlarm (5) <Polarity> (2)
        "
	::= { pm10001otu4AlmclientNetworkLaneFaultEntry 5 }


pm10001otu4AlmClientLaneRxFifoErrorPortn OBJECT-TYPE
	SYNTAX  EkiOnOff
	MAX-ACCESS read-only
	STATUS current
	DESCRIPTION
        "
        Client Network Lane Rx FIFO Error
        :This OID indicates a Rx FIFO Error
        on the Client Trscv Network Lane
        <Help> Alarm indicating a Rx FIFO
        Error on the Client Trscv Network
        Lane <Condtype> CLIENT_LANE_RX_FIFO_ERROR
        <Probcause> receiverFailure (42)
        <Alarmtype> equipmentAlarm (5)
         <Polarity> (2)
        "
	::= { pm10001otu4AlmclientNetworkLaneFaultEntry 4 }


--- *********************************************************
---     TABLE for the pm10001otu4AlmclientHostLaneFault articles
--- *********************************************************

pm10001otu4AlmclientHostLaneFaultTable OBJECT-TYPE
	SYNTAX  SEQUENCE OF Pm10001otu4AlmclientHostLaneFaultEntry
	MAX-ACCESS not-accessible
	STATUS current
	DESCRIPTION
        "
        List of pm10001otu4AlmclientHostLaneFault
        Article
        "
	::= { pm10001otu4AlmClientUrg 88 }


pm10001otu4AlmclientHostLaneFaultEntry OBJECT-TYPE
	SYNTAX Pm10001otu4AlmclientHostLaneFaultEntry
	MAX-ACCESS not-accessible
	STATUS current
	DESCRIPTION
        "
        Row definition for the pm10001otu4AlmclientHostLaneFault
        table
        "
	INDEX   { pm10001otu4AlmclientHostLaneFaultIndex }
	::= { pm10001otu4AlmclientHostLaneFaultTable 1 }


Pm10001otu4AlmclientHostLaneFaultEntry ::=
	SEQUENCE {
	pm10001otu4AlmclientHostLaneFaultIndex
		INTEGER,
	pm10001otu4AlmRfDetectedPortn
		EkiOnOff,
	pm10001otu4AlmLfDetectedPortn
		EkiOnOff,
	pm10001otu4AlmClientLaneTxFifoErrorPortn
		EkiOnOff,
	pm10001otu4AlmClientTxHostLolPortn
		EkiOnOff,
	pm10001otu4AlmClientCsfDetectedPortn
		EkiOnOff,
	pm10001otu4AlmClientLanesNotAlignedPortn
		EkiOnOff,
	pm10001otu4AlmClientLanes6466UnlockPortn
		EkiOnOff,
	pm10001otu4AlmClientLanesMarkerUnlockPortn
		EkiOnOff,
	pm10001otu4AlmClientInputLossOfSigPortn
		EkiOnOff,
	pm10001otu4AlmClientLossOfSyncPortn
		EkiOnOff
	}


pm10001otu4AlmclientHostLaneFaultIndex OBJECT-TYPE
	SYNTAX  INTEGER(0..128)
	MAX-ACCESS  read-only
	STATUS current
	DESCRIPTION
        "
        Index definition for the pm10001otu4AlmclientHostLaneFault
        table
        "
	::= { pm10001otu4AlmclientHostLaneFaultEntry 1 }


pm10001otu4AlmRfDetectedPortn OBJECT-TYPE
	SYNTAX  EkiOnOff
	MAX-ACCESS read-only
	STATUS current
	DESCRIPTION
        "
        Remote Fault Signal Detected :This
        OID indicates a Remote Fault Signal
        is detected on the client input
        port<Help> This alarm indicates
        a Remote Fault Signal is detected
        on the client input port <Condtype>
        RF_DETECTED <Probcause> receiverFailure
        (42) <Alarmtype> equipmentAlarm
        (5) <Polarity> (2)
        "
	::= { pm10001otu4AlmclientHostLaneFaultEntry 13 }


pm10001otu4AlmLfDetectedPortn OBJECT-TYPE
	SYNTAX  EkiOnOff
	MAX-ACCESS read-only
	STATUS current
	DESCRIPTION
        "
        Local Fault Signal Detected :This
        OID indicates a Local Fault Signal
        is detected on the client input
        port<Help> This alarm indicates
        a Local Fault Signal is detected
        on the client input port <Condtype>
        LF_DETECTED <Probcause> receiverFailure
        (42) <Alarmtype> equipmentAlarm
        (5) <Polarity> (2)
        "
	::= { pm10001otu4AlmclientHostLaneFaultEntry 12 }


pm10001otu4AlmClientLaneTxFifoErrorPortn OBJECT-TYPE
	SYNTAX  EkiOnOff
	MAX-ACCESS read-only
	STATUS current
	DESCRIPTION
        "
        Client Host Lane Tx FIFO Error
        :This OID indicates a Tx FIFO Error
        on the Client Trscv Host Lane <Help>
        Alarm indicating a Tx FIFO Error
        on the Client Trscv Host Lane <Condtype>
        CLIENT_LANE_TX_FIFO_ERROR <Probcause>
        receiverFailure (42) <Alarmtype>
        equipmentAlarm (5) <Polarity> (2)
        "
	::= { pm10001otu4AlmclientHostLaneFaultEntry 11 }


pm10001otu4AlmClientTxHostLolPortn OBJECT-TYPE
	SYNTAX  EkiOnOff
	MAX-ACCESS read-only
	STATUS current
	DESCRIPTION
        "
        Client Host Lane Tx Loss Of Lock
        :This OID indicates a Tx Loss of
        Lock on the Client Trscv Host Lane
        <Help> Alarm indicating a Tx Loss
        of Lock on the Client Trscv Host
        Lane <Condtype> CLIENT_TX_HOST_LOL
        <Probcause> receiverFailure (42)
        <Alarmtype> equipmentAlarm (5)
         <Polarity> (2)
        "
	::= { pm10001otu4AlmclientHostLaneFaultEntry 10 }


pm10001otu4AlmClientCsfDetectedPortn OBJECT-TYPE
	SYNTAX  EkiOnOff
	MAX-ACCESS read-only
	STATUS current
	DESCRIPTION
        "
        Client Signal Fail Detected :This
        OID indicates that a CSF has been
        detected on client port in the
         downstream direction   <Help>
          This alarm indicates if a Client
        Signal Fail has been detected in
        the incoming line frame for this
        client port <Condtype> CLIENT_CSF_DETECTED
        <Probcause> receiveFailure (41)
        <Alarmtype> other(1) <Polarity>
        (2)
        "
	::= { pm10001otu4AlmclientHostLaneFaultEntry 7 }


pm10001otu4AlmClientLanesNotAlignedPortn OBJECT-TYPE
	SYNTAX  EkiOnOff
	MAX-ACCESS read-only
	STATUS current
	DESCRIPTION
        "
        Client Lanes Not Aligned :This
        OID indicates the Client lanes
         are not aligned <Help> Alarm indicating
        the Client lanes are not aligned
        <Condtype> CLIENT_LANES_NOT_ALIGNED
        <Probcause> receiveFailure (41)
        <Alarmtype> integrityViolation
         (7) <Polarity> (2)
        "
	::= { pm10001otu4AlmclientHostLaneFaultEntry 6 }


pm10001otu4AlmClientLanes6466UnlockPortn OBJECT-TYPE
	SYNTAX  EkiOnOff
	MAX-ACCESS read-only
	STATUS current
	DESCRIPTION
        "
        Client Lanes 64/66b Unlock :This
        OID indicates the Client 64/66b
        decoder is not lock <Help> Alarm
        indicating the Client 64/66b decoder
        is not lock <Condtype> CLIENT_LANES_64_66_UNLOCK
        <Probcause> receiveFailure (41)
        <Alarmtype> integrityViolation
         (7) <Polarity> (2)
        "
	::= { pm10001otu4AlmclientHostLaneFaultEntry 5 }


pm10001otu4AlmClientLanesMarkerUnlockPortn OBJECT-TYPE
	SYNTAX  EkiOnOff
	MAX-ACCESS read-only
	STATUS current
	DESCRIPTION
        "
        Client Lanes Marker Unlock :This
        OID indicates the Client lanes
         marker alignment is not lock <Help>
        Alarm indicating the Client lanes
        marker alignment is not lock <Condtype>
        CLIENT_LANES_MARKER_UNLOCK <Probcause>
        receiveFailure (41) <Alarmtype>
        integrityViolation (7) <Polarity>
        (2)
        "
	::= { pm10001otu4AlmclientHostLaneFaultEntry 4 }


pm10001otu4AlmClientInputLossOfSigPortn OBJECT-TYPE
	SYNTAX  EkiOnOff
	MAX-ACCESS read-only
	STATUS current
	DESCRIPTION
        "
        Client Input Loss Of Signal :This
        OID indicates a Loss of Signal
         is detected on the Client Trscv
        <Help> Alarm indicating a Loss
         of Signal is detected on the Client
        Trscv <Condtype> CLIENT_INPUT_LOSS_OF_SIG
        <Probcause> receiveFailure (41)
        <Alarmtype> physicalViolation (9)
        <Polarity> (2)
        "
	::= { pm10001otu4AlmclientHostLaneFaultEntry 3 }


pm10001otu4AlmClientLossOfSyncPortn OBJECT-TYPE
	SYNTAX  EkiOnOff
	MAX-ACCESS read-only
	STATUS current
	DESCRIPTION
        "
        Client Frame Alignment Loss :This
        OID indicates the module is not
        aligned with the incoming Client
        signal <Help> Alarm indicating
         the module is not aligned with
        the incoming client signal <Condtype>
        CLIENT_LOSS_OF_SYNC <Probcause>
        receiveFailure (41) <Alarmtype>
        integrityViolation (7) <Polarity>
        (2)
        "
	::= { pm10001otu4AlmclientHostLaneFaultEntry 2 }


--- *********************************************************
---     TABLE for the pm10001otu4AlmlineNetworkLaneAlarmWarning1 articles
--- *********************************************************

pm10001otu4AlmlineNetworkLaneAlarmWarning1Table OBJECT-TYPE
	SYNTAX  SEQUENCE OF Pm10001otu4AlmlineNetworkLaneAlarmWarning1Entry
	MAX-ACCESS not-accessible
	STATUS current
	DESCRIPTION
        "
        List of pm10001otu4AlmlineNetworkLaneAlarmWarning1
        Article
        "
	::= { pm10001otu4AlmLineNurg 104 }


pm10001otu4AlmlineNetworkLaneAlarmWarning1Entry OBJECT-TYPE
	SYNTAX Pm10001otu4AlmlineNetworkLaneAlarmWarning1Entry
	MAX-ACCESS not-accessible
	STATUS current
	DESCRIPTION
        "
        Row definition for the pm10001otu4AlmlineNetworkLaneAlarmWarning1
        table
        "
	INDEX   { pm10001otu4AlmlineNetworkLaneAlarmWarning1Index }
	::= { pm10001otu4AlmlineNetworkLaneAlarmWarning1Table 1 }


Pm10001otu4AlmlineNetworkLaneAlarmWarning1Entry ::=
	SEQUENCE {
	pm10001otu4AlmlineNetworkLaneAlarmWarning1Index
		INTEGER,
	pm10001otu4AlmLineBiasHighAlarmPortn
		EkiOnOff,
	pm10001otu4AlmLineBiasHighWarningPortn
		EkiOnOff,
	pm10001otu4AlmLineBiasLowWarningPortn
		EkiOnOff,
	pm10001otu4AlmLineBiasLowAlarmPortn
		EkiOnOff,
	pm10001otu4AlmLineTxPowerHighAlarmPortn
		EkiOnOff,
	pm10001otu4AlmLineTxPowerHighWarningPortn
		EkiOnOff,
	pm10001otu4AlmLineTxPowerLowWarningPortn
		EkiOnOff,
	pm10001otu4AlmLineTxPowerLowAlarmPortn
		EkiOnOff,
	pm10001otu4AlmLineLaserTempHighAlarmPortn
		EkiOnOff,
	pm10001otu4AlmLineLaserTempHighWarningPortn
		EkiOnOff,
	pm10001otu4AlmLineLaserTempLowWarningPortn
		EkiOnOff,
	pm10001otu4AlmLineLaserTempLowAlarmPortn
		EkiOnOff,
	pm10001otu4AlmLineRxPowerHighAlarmPortn
		EkiOnOff,
	pm10001otu4AlmLineRxPowerHighWarningPortn
		EkiOnOff,
	pm10001otu4AlmLineRxPowerLowWarningPortn
		EkiOnOff,
	pm10001otu4AlmLineRxPowerLowAlarmPortn
		EkiOnOff
	}


pm10001otu4AlmlineNetworkLaneAlarmWarning1Index OBJECT-TYPE
	SYNTAX  INTEGER(0..128)
	MAX-ACCESS  read-only
	STATUS current
	DESCRIPTION
        "
        Index definition for the pm10001otu4AlmlineNetworkLaneAlarmWarning1
        table
        "
	::= { pm10001otu4AlmlineNetworkLaneAlarmWarning1Entry 1 }


pm10001otu4AlmLineBiasHighAlarmPortn OBJECT-TYPE
	SYNTAX  EkiOnOff
	MAX-ACCESS read-only
	STATUS current
	DESCRIPTION
        "
        Line Trscv Tx Bias High Alarm
         :This OID indicates that the Trscv
        laser bias current is higher than
        the threshold value written in
         the Trscv EEPROM <Help> Alarm
         indicating that the Trscv laser
        bias current is higher than the
        threshold value written in the
         Trscv EEPROM <Condtype> LINE_BIAS_HIGH_ALARM
        <Probcause> transmitterFailure
         (56) <Alarmtype> equipmentAlarm
        (5) <Polarity> (2)
        "
	::= { pm10001otu4AlmlineNetworkLaneAlarmWarning1Entry 17 }


pm10001otu4AlmLineBiasHighWarningPortn OBJECT-TYPE
	SYNTAX  EkiOnOff
	MAX-ACCESS read-only
	STATUS current
	DESCRIPTION
        "
        Line Trscv Tx Bias High Warning
        :This OID indicates that the Trscv
        laser bias current is higher than
        the threshold value written in
         the Trscv EEPROM <Help> Warning
        indicating that the Trscv laser
        bias current is higher than the
        threshold value written in the
         Trscv EEPROM <Condtype> LINE_BIAS_HIGH_WARNING
        <Probcause> transmitterFailure
         (56) <Alarmtype> equipmentAlarm
        (5) <Polarity> (2)
        "
	::= { pm10001otu4AlmlineNetworkLaneAlarmWarning1Entry 16 }


pm10001otu4AlmLineBiasLowWarningPortn OBJECT-TYPE
	SYNTAX  EkiOnOff
	MAX-ACCESS read-only
	STATUS current
	DESCRIPTION
        "
        Line Trscv Tx Bias Low Warning
        :This OID indicates that the Trscv
        laser bias current is lower than
        the threshold value written in
         the Trscv EEPROM <Help> Warning
        indicating that the Trscv laser
        bias current is lower than the
         threshold value written in the
        Trscv EEPROM <Condtype> LINE_BIAS_LOW_WARNING
        <Probcause> transmitterFailure
         (56) <Alarmtype> equipmentAlarm
        (5) <Polarity> (2)
        "
	::= { pm10001otu4AlmlineNetworkLaneAlarmWarning1Entry 15 }


pm10001otu4AlmLineBiasLowAlarmPortn OBJECT-TYPE
	SYNTAX  EkiOnOff
	MAX-ACCESS read-only
	STATUS current
	DESCRIPTION
        "
        Line Trscv Tx Bias Low Alarm :This
        OID indicates that the Trscv laser
        bias current is lower than the
         threshold value written in the
        Trscv EEPROM <Help> Alarm indicating
        that the Trscv laser bias current
        is lower than the threshold value
        written in the Trscv EEPROM <Condtype>
        LINE_BIAS_LOW_ALARM <Probcause>
        transmitterFailure (56) <Alarmtype>
        equipmentAlarm (5) <Polarity> (2)
        "
	::= { pm10001otu4AlmlineNetworkLaneAlarmWarning1Entry 14 }


pm10001otu4AlmLineTxPowerHighAlarmPortn OBJECT-TYPE
	SYNTAX  EkiOnOff
	MAX-ACCESS read-only
	STATUS current
	DESCRIPTION
        "
        Line Trscv Tx Power High Alarm
        :This OID indicates that the Trscv
        output power is higher than the
        threshold value written in the
         Trscv EEPROM <Help> Alarm indicating
        that the Trscv output power is
         higher than the threshold value
        written in the Trscv EEPROM <Condtype>
        LINE_TX_POWER_HIGH_ALARM <Probcause>
        transmitterFailure (56) <Alarmtype>
        equipmentAlarm (5) <Polarity> (2)
        "
	::= { pm10001otu4AlmlineNetworkLaneAlarmWarning1Entry 13 }


pm10001otu4AlmLineTxPowerHighWarningPortn OBJECT-TYPE
	SYNTAX  EkiOnOff
	MAX-ACCESS read-only
	STATUS current
	DESCRIPTION
        "
        Line Trscv Tx Power High Warning
        :This OID indicates that the Trscv
        output power is higher than the
        threshold value written in the
         Trscv EEPROM <Help> Warning indicating
        that the Trscv output power is
         higher than the threshold value
        written in the Trscv EEPROM <Condtype>
        LINE_TX_POWER_HIGH_WARNING <Probcause>
        transmitterFailure (56) <Alarmtype>
        equipmentAlarm (5) <Polarity> (2)
        "
	::= { pm10001otu4AlmlineNetworkLaneAlarmWarning1Entry 12 }


pm10001otu4AlmLineTxPowerLowWarningPortn OBJECT-TYPE
	SYNTAX  EkiOnOff
	MAX-ACCESS read-only
	STATUS current
	DESCRIPTION
        "
        Line Trscv Tx Power Low Warning
        :This OID indicates that the Trscv
        output power is lower than the
         threshold value written in the
        Trscv EEPROM <Help> Warning indicating
        that the Trscv output power is
         lower than the threshold value
        written in the Trscv EEPROM <Condtype>
        LINE_TX_POWER_LOW_WARNING <Probcause>
        transmitterFailure (56) <Alarmtype>
        equipmentAlarm (5) <Polarity> (2)
        "
	::= { pm10001otu4AlmlineNetworkLaneAlarmWarning1Entry 11 }


pm10001otu4AlmLineTxPowerLowAlarmPortn OBJECT-TYPE
	SYNTAX  EkiOnOff
	MAX-ACCESS read-only
	STATUS current
	DESCRIPTION
        "
        Line Trscv Tx Power Low Alarm
         :This OID indicates that the Trscv
        output power is lower than the
         threshold value written in the
        Trscv EEPROM <Help> Alarm indicating
        that the Trscv output power is
         lower than the threshold value
        written in the Trscv EEPROM <Condtype>
        LINE_TX_POWER_LOW_ALARM <Probcause>
        transmitterFailure (56) <Alarmtype>
        equipmentAlarm (5) <Polarity> (2)
        "
	::= { pm10001otu4AlmlineNetworkLaneAlarmWarning1Entry 10 }


pm10001otu4AlmLineLaserTempHighAlarmPortn OBJECT-TYPE
	SYNTAX  EkiOnOff
	MAX-ACCESS read-only
	STATUS current
	DESCRIPTION
        "
        Line Trscv Tx Laser Temp High
         Alarm :This OID indicates that
        the Trscv Tx Laser Temperature
         is higher than the threshold value
        written in the Trscv EEPROM <Help>
        Alarm indicating that the Trscv
        Tx Laser Temperature is higher
         than the threshold value written
        in the Trscv EEPROM <Condtype>
         LINE_LASER_TEMP_HIGH_ALARM <Probcause>
        temperatureUnacceptable (51) <Alarmtype>
        equipmentAlarm (5) <Polarity> (2)
        "
	::= { pm10001otu4AlmlineNetworkLaneAlarmWarning1Entry 9 }


pm10001otu4AlmLineLaserTempHighWarningPortn OBJECT-TYPE
	SYNTAX  EkiOnOff
	MAX-ACCESS read-only
	STATUS current
	DESCRIPTION
        "
        Line Trscv Tx Laser Temp High
         Warning :This OID indicates that
        the Trscv Tx Laser Temperature
         is higher than the threshold value
        written in the Trscv EEPROM <Help>
        Warning indicating that the Trscv
        Tx Laser Temperature is higher
         than the threshold value written
        in the Trscv EEPROM <Condtype>
         LINE_LASER_TEMP_HIGH_WARNING <Probcause>
        temperatureUnacceptable (51) <Alarmtype>
        equipmentAlarm (5) <Polarity> (2)
        "
	::= { pm10001otu4AlmlineNetworkLaneAlarmWarning1Entry 8 }


pm10001otu4AlmLineLaserTempLowWarningPortn OBJECT-TYPE
	SYNTAX  EkiOnOff
	MAX-ACCESS read-only
	STATUS current
	DESCRIPTION
        "
        Line Trscv Tx Laser Temp Low Warning
        :This OID indicates that the Trscv
        Tx Laser Temperature is lower than
        the threshold value written in
         the Trscv EEPROM <Help> Warning
        indicating that the Trscv Tx Laser
        Temperature is lower than the threshold
        value written in the Trscv EEPROM
        <Condtype> LINE_LASER_TEMP_LOW_WARNING
        <Probcause> temperatureUnacceptable
        (51) <Alarmtype> equipmentAlarm
        (5) <Polarity> (2)
        "
	::= { pm10001otu4AlmlineNetworkLaneAlarmWarning1Entry 7 }


pm10001otu4AlmLineLaserTempLowAlarmPortn OBJECT-TYPE
	SYNTAX  EkiOnOff
	MAX-ACCESS read-only
	STATUS current
	DESCRIPTION
        "
        Line Trscv Tx Laser Temp Low Alarm
        :This OID indicates that the Trscv
        Tx Laser Temperature is lower than
        the threshold value written in
         the Trscv EEPROM <Help> Alarm
         indicating that the Trscv Tx Laser
        Temperature is lower than the threshold
        value written in the Trscv EEPROM
        <Condtype> LINE_LASER_TEMP_LOW_ALARM
        <Probcause> temperatureUnacceptable
        (51) <Alarmtype> equipmentAlarm
        (5) <Polarity> (2)
        "
	::= { pm10001otu4AlmlineNetworkLaneAlarmWarning1Entry 6 }


pm10001otu4AlmLineRxPowerHighAlarmPortn OBJECT-TYPE
	SYNTAX  EkiOnOff
	MAX-ACCESS read-only
	STATUS current
	DESCRIPTION
        "
        Line Trscv Rx Power High Alarm
        :This OID indicates that the Trscv
        input power is higher than the
         threshold value written in the
        Trscv EEPROM <Help> Alarm indicating
        that the Trscv input power is higher
        than the threshold value written
        in the Trscv EEPROM <Condtype>
         LINE_RX_POWER_HIGH_ALARM <Probcause>
        receiveFailure (41) <Alarmtype>
        equipmentAlarm (5) <Polarity> (2)
        "
	::= { pm10001otu4AlmlineNetworkLaneAlarmWarning1Entry 5 }


pm10001otu4AlmLineRxPowerHighWarningPortn OBJECT-TYPE
	SYNTAX  EkiOnOff
	MAX-ACCESS read-only
	STATUS current
	DESCRIPTION
        "
        Line Trscv Rx Power High Warning
        :This OID indicates that the Trscv
        input power is higher than the
         threshold value written in the
        Trscv EEPROM <Help> Warning indicating
        that the Trscv input power is higher
        than the threshold value written
        in the Trscv EEPROM <Condtype>
         LINE_RX_POWER_HIGH_WARNING <Probcause>
        receiveFailure (41) <Alarmtype>
        equipmentAlarm (5) <Polarity> (2)
        "
	::= { pm10001otu4AlmlineNetworkLaneAlarmWarning1Entry 4 }


pm10001otu4AlmLineRxPowerLowWarningPortn OBJECT-TYPE
	SYNTAX  EkiOnOff
	MAX-ACCESS read-only
	STATUS current
	DESCRIPTION
        "
        Line Trscv Rx Power Low Warning
        :This OID indicates that the Trscv
        input power is lower than the threshold
        value written in the Trscv EEPROM
        <Help> Warning indicating that
         the Trscv input power is lower
        than the threshold value written
        in the Trscv EEPROM <Condtype>
         LINE_RX_POWER_LOW_WARNING <Probcause>
        receiveFailure (41) <Alarmtype>
        equipmentAlarm (5) <Polarity> (2)
        "
	::= { pm10001otu4AlmlineNetworkLaneAlarmWarning1Entry 3 }


pm10001otu4AlmLineRxPowerLowAlarmPortn OBJECT-TYPE
	SYNTAX  EkiOnOff
	MAX-ACCESS read-only
	STATUS current
	DESCRIPTION
        "
        Line Trscv Rx Power Low Alarm
         :This OID indicates that the Trscv
        input power is lower than the threshold
        value written in the Trscv EEPROM
        <Help> Alarm indicating that the
        Trscv input power is lower than
        the threshold value written in
         the Trscv EEPROM <Condtype> LINE_RX_POWER_LOW_ALARM
        <Probcause> receiveFailure (41)
        <Alarmtype> equipmentAlarm (5)
         <Polarity> (2)
        "
	::= { pm10001otu4AlmlineNetworkLaneAlarmWarning1Entry 2 }


--- *********************************************************
---     TABLE for the pm10001otu4AlmlineNetworkLaneAlarmWarning2 articles
--- *********************************************************

pm10001otu4AlmlineNetworkLaneAlarmWarning2Table OBJECT-TYPE
	SYNTAX  SEQUENCE OF Pm10001otu4AlmlineNetworkLaneAlarmWarning2Entry
	MAX-ACCESS not-accessible
	STATUS current
	DESCRIPTION
        "
        List of pm10001otu4AlmlineNetworkLaneAlarmWarning2
        Article
        "
	::= { pm10001otu4AlmLineNurg 120 }


pm10001otu4AlmlineNetworkLaneAlarmWarning2Entry OBJECT-TYPE
	SYNTAX Pm10001otu4AlmlineNetworkLaneAlarmWarning2Entry
	MAX-ACCESS not-accessible
	STATUS current
	DESCRIPTION
        "
        Row definition for the pm10001otu4AlmlineNetworkLaneAlarmWarning2
        table
        "
	INDEX   { pm10001otu4AlmlineNetworkLaneAlarmWarning2Index }
	::= { pm10001otu4AlmlineNetworkLaneAlarmWarning2Table 1 }


Pm10001otu4AlmlineNetworkLaneAlarmWarning2Entry ::=
	SEQUENCE {
	pm10001otu4AlmlineNetworkLaneAlarmWarning2Index
		INTEGER,
	pm10001otu4AlmRxLaserBiasHighAlarmPortn
		EkiOnOff,
	pm10001otu4AlmRxLaserBiasHighWarningPortn
		EkiOnOff,
	pm10001otu4AlmRxLaserBiasLowWarningPortn
		EkiOnOff,
	pm10001otu4AlmRxLaserBiasLowAlarmPortn
		EkiOnOff,
	pm10001otu4AlmRxLaserOutputHighAlarmPortn
		EkiOnOff,
	pm10001otu4AlmRxLaserOutputHighWarningPortn
		EkiOnOff,
	pm10001otu4AlmRxLaserOutputLowWarningPortn
		EkiOnOff,
	pm10001otu4AlmRxLaserOutputLowAlarmPortn
		EkiOnOff,
	pm10001otu4AlmRxLaserTempHighAlarmPortn
		EkiOnOff,
	pm10001otu4AlmRxLaserTempHighWarningPortn
		EkiOnOff,
	pm10001otu4AlmRxLaserTempLowWarningPortn
		EkiOnOff,
	pm10001otu4AlmRxLaserTempLowAlarmPortn
		EkiOnOff,
	pm10001otu4AlmTxModulatorBiasHighAlarmPortn
		EkiOnOff,
	pm10001otu4AlmTxModulatorBiasHighWarningPortn
		EkiOnOff,
	pm10001otu4AlmTxModulatorBiasLowWarningPortn
		EkiOnOff,
	pm10001otu4AlmTxModulatorBiasLowAlarmPortn
		EkiOnOff
	}


pm10001otu4AlmlineNetworkLaneAlarmWarning2Index OBJECT-TYPE
	SYNTAX  INTEGER(0..128)
	MAX-ACCESS  read-only
	STATUS current
	DESCRIPTION
        "
        Index definition for the pm10001otu4AlmlineNetworkLaneAlarmWarning2
        table
        "
	::= { pm10001otu4AlmlineNetworkLaneAlarmWarning2Entry 1 }


pm10001otu4AlmRxLaserBiasHighAlarmPortn OBJECT-TYPE
	SYNTAX  EkiOnOff
	MAX-ACCESS read-only
	STATUS current
	DESCRIPTION
        "
        Line Trscv Rx Bias High Alarm
         :This OID indicates that the Trscv
        Rx laser bias current is higher
        than the threshold value written
        in the Trscv EEPROM <Help> Alarm
        indicating that the Trscv Rx laser
        bias current is higher than the
        threshold value written in the
         Trscv EEPROM <Condtype> RX_LASER_BIAS_HIGH_ALARM
        <Probcause> receiveFailure (41)
        <Alarmtype> equipmentAlarm (5)
         <Polarity> (2)
        "
	::= { pm10001otu4AlmlineNetworkLaneAlarmWarning2Entry 17 }


pm10001otu4AlmRxLaserBiasHighWarningPortn OBJECT-TYPE
	SYNTAX  EkiOnOff
	MAX-ACCESS read-only
	STATUS current
	DESCRIPTION
        "
        Line Trscv Rx Bias High Warning
        :This OID indicates that the Trscv
        Rx laser bias current is higher
        than the threshold value written
        in the Trscv EEPROM <Help> Warning
        indicating that the Trscv Rx laser
        bias current is higher than the
        threshold value written in the
         Trscv EEPROM <Condtype> RX_LASER_BIAS_HIGH_WARNING
        <Probcause> receiveFailure (41)
        <Alarmtype> equipmentAlarm (5)
         <Polarity> (2)
        "
	::= { pm10001otu4AlmlineNetworkLaneAlarmWarning2Entry 16 }


pm10001otu4AlmRxLaserBiasLowWarningPortn OBJECT-TYPE
	SYNTAX  EkiOnOff
	MAX-ACCESS read-only
	STATUS current
	DESCRIPTION
        "
        Line Trscv Rx Bias Low Warning
        :This OID indicates that the Trscv
        Rx laser bias current is lower
         than the threshold value written
        in the Trscv EEPROM <Help> Warning
        indicating that the Trscv Rx laser
        bias current is lower than the
         threshold value written in the
        Trscv EEPROM <Condtype> RX_LASER_BIAS_LOW_WARNING
        <Probcause> receiveFailure (41)
        <Alarmtype> equipmentAlarm (5)
         <Polarity> (2)
        "
	::= { pm10001otu4AlmlineNetworkLaneAlarmWarning2Entry 15 }


pm10001otu4AlmRxLaserBiasLowAlarmPortn OBJECT-TYPE
	SYNTAX  EkiOnOff
	MAX-ACCESS read-only
	STATUS current
	DESCRIPTION
        "
        Line Trscv Rx Bias Low Alarm :This
        OID indicates that the Trscv Rx
        laser bias current is lower than
        the threshold value written in
         the Trscv EEPROM <Help> Alarm
         indicating that the Trscv Rx laser
        bias current is lower than the
         threshold value written in the
        Trscv EEPROM <Condtype> RX_LASER_BIAS_LOW_ALARM
        <Probcause> receiveFailure (41)
        <Alarmtype> equipmentAlarm (5)
         <Polarity> (2)
        "
	::= { pm10001otu4AlmlineNetworkLaneAlarmWarning2Entry 14 }


pm10001otu4AlmRxLaserOutputHighAlarmPortn OBJECT-TYPE
	SYNTAX  EkiOnOff
	MAX-ACCESS read-only
	STATUS current
	DESCRIPTION
        "
        Line Trscv Rx Output Power High
        Alarm :This OID indicates that
         the Trscv Rx output power is higher
        than the threshold value written
        in the Trscv EEPROM <Help> Alarm
        indicating that the Trscv Rx output
        power is higher than the threshold
        value written in the Trscv EEPROM
        <Condtype> RX_LASER_OUTPUT_HIGH_ALARM
        <Probcause> receiveFailure (41)
        <Alarmtype> equipmentAlarm (5)
         <Polarity> (2)
        "
	::= { pm10001otu4AlmlineNetworkLaneAlarmWarning2Entry 13 }


pm10001otu4AlmRxLaserOutputHighWarningPortn OBJECT-TYPE
	SYNTAX  EkiOnOff
	MAX-ACCESS read-only
	STATUS current
	DESCRIPTION
        "
        Line Trscv Rx Output Power High
        Warning :This OID indicates that
        the Trscv Rx output power is higher
        than the threshold value written
        in the Trscv EEPROM <Help> Warning
        indicating that the Trscv Rx output
        power is higher than the threshold
        value written in the Trscv EEPROM
        <Condtype> RX_LASER_OUTPUT_HIGH_WARNING
        <Probcause> receiveFailure (41)
        <Alarmtype> equipmentAlarm (5)
         <Polarity> (2)
        "
	::= { pm10001otu4AlmlineNetworkLaneAlarmWarning2Entry 12 }


pm10001otu4AlmRxLaserOutputLowWarningPortn OBJECT-TYPE
	SYNTAX  EkiOnOff
	MAX-ACCESS read-only
	STATUS current
	DESCRIPTION
        "
        Line Trscv Rx Output Power Low
        Warning :This OID indicates that
        the Trscv Rx output power is lower
        than the threshold value written
        in the Trscv EEPROM <Help> Warning
        indicating that the Trscv Rx output
        power is lower than the threshold
        value written in the Trscv EEPROM
        <Condtype> RX_LASER_OUTPUT_LOW_WARNING
        <Probcause> receiveFailure (41)
        <Alarmtype> equipmentAlarm (5)
         <Polarity> (2)
        "
	::= { pm10001otu4AlmlineNetworkLaneAlarmWarning2Entry 11 }


pm10001otu4AlmRxLaserOutputLowAlarmPortn OBJECT-TYPE
	SYNTAX  EkiOnOff
	MAX-ACCESS read-only
	STATUS current
	DESCRIPTION
        "
        Line Trscv Rx Output Power Low
        Alarm :This OID indicates that
         the Trscv Rx output power is lower
        than the threshold value written
        in the Trscv EEPROM <Help> Alarm
        indicating that the Trscv Rx output
        power is lower than the threshold
        value written in the Trscv EEPROM
        <Condtype> RX_LASER_OUTPUT_LOW_ALARM
        <Probcause> receiveFailure (41)
        <Alarmtype> equipmentAlarm (5)
         <Polarity> (2)
        "
	::= { pm10001otu4AlmlineNetworkLaneAlarmWarning2Entry 10 }


pm10001otu4AlmRxLaserTempHighAlarmPortn OBJECT-TYPE
	SYNTAX  EkiOnOff
	MAX-ACCESS read-only
	STATUS current
	DESCRIPTION
        "
        Line Trscv Rx Laser Temp High
         Alarm :This OID indicates that
        the Trscv Rx Laser Temperature
         is higher than the threshold value
        written in the Trscv EEPROM <Help>
        Alarm indicating that the Trscv
        Rx Laser Temperature is higher
         than the threshold value written
        in the Trscv EEPROM <Condtype>
         RX_LASER_TEMP_HIGH_ALARM <Probcause>
        temperatureUnacceptable (51) <Alarmtype>
        equipmentAlarm (5) <Polarity> (2)
        "
	::= { pm10001otu4AlmlineNetworkLaneAlarmWarning2Entry 9 }


pm10001otu4AlmRxLaserTempHighWarningPortn OBJECT-TYPE
	SYNTAX  EkiOnOff
	MAX-ACCESS read-only
	STATUS current
	DESCRIPTION
        "
        Line Trscv Rx Laser Temp High
         Warning :This OID indicates that
        the Trscv Rx Laser Temperature
         is higher than the threshold value
        written in the Trscv EEPROM <Help>
        Warning indicating that the Trscv
        Rx Laser Temperature is higher
         than the threshold value written
        in the Trscv EEPROM <Condtype>
         RX_LASER_TEMP_HIGH_WARNING <Probcause>
        temperatureUnacceptable (51) <Alarmtype>
        equipmentAlarm (5) <Polarity> (2)
        "
	::= { pm10001otu4AlmlineNetworkLaneAlarmWarning2Entry 8 }


pm10001otu4AlmRxLaserTempLowWarningPortn OBJECT-TYPE
	SYNTAX  EkiOnOff
	MAX-ACCESS read-only
	STATUS current
	DESCRIPTION
        "
        Line Trscv Rx Laser Temp Low Warning
        :This OID indicates that the Trscv
        Rx Laser Temperature is lower than
        the threshold value written in
         the Trscv EEPROM <Help> Warning
        indicating that the Trscv Rx Laser
        Temperature is lower than the threshold
        value written in the Trscv EEPROM
        <Condtype> RX_LASER_TEMP_LOW_WARNING
        <Probcause> temperatureUnacceptable
        (51) <Alarmtype> equipmentAlarm
        (5) <Polarity> (2)
        "
	::= { pm10001otu4AlmlineNetworkLaneAlarmWarning2Entry 7 }


pm10001otu4AlmRxLaserTempLowAlarmPortn OBJECT-TYPE
	SYNTAX  EkiOnOff
	MAX-ACCESS read-only
	STATUS current
	DESCRIPTION
        "
        Line Trscv Rx Laser Temp Low Alarm
        :This OID indicates that the Trscv
        Rx Laser Temperature is lower than
        the threshold value written in
         the Trscv EEPROM <Help> Alarm
         indicating that the Trscv Rx Laser
        Temperature is lower than the threshold
        value written in the Trscv EEPROM
        <Condtype> RX_LASER_TEMP_LOW_ALARM
        <Probcause> temperatureUnacceptable
        (51) <Alarmtype> equipmentAlarm
        (5) <Polarity> (2)
        "
	::= { pm10001otu4AlmlineNetworkLaneAlarmWarning2Entry 6 }


pm10001otu4AlmTxModulatorBiasHighAlarmPortn OBJECT-TYPE
	SYNTAX  EkiOnOff
	MAX-ACCESS read-only
	STATUS current
	DESCRIPTION
        "
        Line Trscv Tx Modulator Bias High
        Alarm :This OID indicates that
         the Trscv Tx modulator bias current
        is higher than the threshold value
        written in the Trscv EEPROM <Help>
        Alarm indicating that the Trscv
        Tx modulator bias current is higher
        than the threshold value written
        in the Trscv EEPROM <Condtype>
         TX_MODULATOR_BIAS_HIGH_ALARM <Probcause>
        transmitterFailure (56) <Alarmtype>
        equipmentAlarm (5) <Polarity> (2)
        "
	::= { pm10001otu4AlmlineNetworkLaneAlarmWarning2Entry 5 }


pm10001otu4AlmTxModulatorBiasHighWarningPortn OBJECT-TYPE
	SYNTAX  EkiOnOff
	MAX-ACCESS read-only
	STATUS current
	DESCRIPTION
        "
        Line Trscv Tx Modulator Bias High
        Warning :This OID indicates that
        the Trscv Tx modulator bias current
        is higher than the threshold value
        written in the Trscv EEPROM <Help>
        Warning indicating that the Trscv
        Tx modulator bias current is higher
        than the threshold value written
        in the Trscv EEPROM <Condtype>
         TX_MODULATOR_BIAS_HIGH_WARNING
        <Probcause> transmitterFailure
         (56) <Alarmtype> equipmentAlarm
        (5) <Polarity> (2)
        "
	::= { pm10001otu4AlmlineNetworkLaneAlarmWarning2Entry 4 }


pm10001otu4AlmTxModulatorBiasLowWarningPortn OBJECT-TYPE
	SYNTAX  EkiOnOff
	MAX-ACCESS read-only
	STATUS current
	DESCRIPTION
        "
        Line Trscv Tx Modulator Bias Low
        Warning :This OID indicates that
        the Trscv Tx modulator bias current
        is lower than the threshold value
        written in the Trscv EEPROM <Help>
        Warning indicating that the Trscv
        Tx modulator bias current is lower
        than the threshold value written
        in the Trscv EEPROM <Condtype>
         TX_MODULATOR_BIAS_LOW_WARNING
         <Probcause> transmitterFailure
        (56) <Alarmtype> equipmentAlarm
        (5) <Polarity> (2)
        "
	::= { pm10001otu4AlmlineNetworkLaneAlarmWarning2Entry 3 }


pm10001otu4AlmTxModulatorBiasLowAlarmPortn OBJECT-TYPE
	SYNTAX  EkiOnOff
	MAX-ACCESS read-only
	STATUS current
	DESCRIPTION
        "
        Line Trscv Tx Modulator Bias Low
        Alarm :This OID indicates that
         the Trscv Tx modulator bias current
        is lower than the threshold value
        written in the Trscv EEPROM <Help>
        Alarm indicating that the Trscv
        Tx modulator bias current is lower
        than the threshold value written
        in the Trscv EEPROM <Condtype>
         TX_MODULATOR_BIAS_LOW_ALARM <Probcause>
        transmitterFailure (56) <Alarmtype>
        equipmentAlarm (5) <Polarity> (2)
        "
	::= { pm10001otu4AlmlineNetworkLaneAlarmWarning2Entry 2 }


--- *********************************************************
---     TABLE for the pm10001otu4AlmlineNetworkLaneFault articles
--- *********************************************************

pm10001otu4AlmlineNetworkLaneFaultTable OBJECT-TYPE
	SYNTAX  SEQUENCE OF Pm10001otu4AlmlineNetworkLaneFaultEntry
	MAX-ACCESS not-accessible
	STATUS current
	DESCRIPTION
        "
        List of pm10001otu4AlmlineNetworkLaneFault
        Article
        "
	::= { pm10001otu4AlmLineUrg 136 }


pm10001otu4AlmlineNetworkLaneFaultEntry OBJECT-TYPE
	SYNTAX Pm10001otu4AlmlineNetworkLaneFaultEntry
	MAX-ACCESS not-accessible
	STATUS current
	DESCRIPTION
        "
        Row definition for the pm10001otu4AlmlineNetworkLaneFault
        table
        "
	INDEX   { pm10001otu4AlmlineNetworkLaneFaultIndex }
	::= { pm10001otu4AlmlineNetworkLaneFaultTable 1 }


Pm10001otu4AlmlineNetworkLaneFaultEntry ::=
	SEQUENCE {
	pm10001otu4AlmlineNetworkLaneFaultIndex
		INTEGER,
	pm10001otu4AlmLineLaneTecFaultPortn
		EkiOnOff,
	pm10001otu4AlmLineLaneWavelengthUnlockedPortn
		EkiOnOff,
	pm10001otu4AlmLineLaneApdPowerSupplyPortn
		EkiOnOff,
	pm10001otu4AlmLineLaneTxLosfPortn
		EkiOnOff,
	pm10001otu4AlmLineLaneTxLolPortn
		EkiOnOff,
	pm10001otu4AlmLineLaneRxLosPortn
		EkiOnOff,
	pm10001otu4AlmLineLaneRxLolPortn
		EkiOnOff,
	pm10001otu4AlmLineLaneRxFifoErrorPortn
		EkiOnOff,
	pm10001otu4AlmLineLaneRxTecFaultPortn
		EkiOnOff
	}


pm10001otu4AlmlineNetworkLaneFaultIndex OBJECT-TYPE
	SYNTAX  INTEGER(0..128)
	MAX-ACCESS  read-only
	STATUS current
	DESCRIPTION
        "
        Index definition for the pm10001otu4AlmlineNetworkLaneFault
        table
        "
	::= { pm10001otu4AlmlineNetworkLaneFaultEntry 1 }


pm10001otu4AlmLineLaneTecFaultPortn OBJECT-TYPE
	SYNTAX  EkiOnOff
	MAX-ACCESS read-only
	STATUS current
	DESCRIPTION
        "
        Line Network Lane TEC Fault :This
        OID indicates a Tx TEC Fault on
        the Line Trscv Network Lane <Help>
        Alarm indicating a Tx TEC Fault
        on the Line Trscv Network Lane
         <Condtype> LINE_LANE_TEC_FAULT
        <Probcause> transmitterFailure
         (56) <Alarmtype> equipmentAlarm
        (5) <Polarity> (2)
        "
	::= { pm10001otu4AlmlineNetworkLaneFaultEntry 17 }


pm10001otu4AlmLineLaneWavelengthUnlockedPortn OBJECT-TYPE
	SYNTAX  EkiOnOff
	MAX-ACCESS read-only
	STATUS current
	DESCRIPTION
        "
        Line Network Lane Wavelength Unlock
        :This OID indicates a Wavelength
        unlock on the Line Trscv Network
        Lane <Help> Alarm indicating a
         Wavelength unlock on the Line
         Trscv Network Lane <Condtype>
         LINE_LANE_WAVELENGTH_UNLOCKED
         <Probcause> transmitterFailure
        (56) <Alarmtype> equipmentAlarm
        (5) <Polarity> (2)
        "
	::= { pm10001otu4AlmlineNetworkLaneFaultEntry 16 }


pm10001otu4AlmLineLaneApdPowerSupplyPortn OBJECT-TYPE
	SYNTAX  EkiOnOff
	MAX-ACCESS read-only
	STATUS current
	DESCRIPTION
        "
        Line Network Lane APD Power Supply
        :This OID indicates an APD Power
        supply failure on the Line Trscv
        Network Lane <Help> Alarm indicating
        an APD Power supply failure on
         the Line Trscv Network Lane <Condtype>
        LINE_LANE_APD_POWER_SUPPLY <Probcause>
        transmitterFailure (56) <Alarmtype>
        equipmentAlarm (5) <Polarity> (2)
        "
	::= { pm10001otu4AlmlineNetworkLaneFaultEntry 15 }


pm10001otu4AlmLineLaneTxLosfPortn OBJECT-TYPE
	SYNTAX  EkiOnOff
	MAX-ACCESS read-only
	STATUS current
	DESCRIPTION
        "
        Line Network Lane Tx Loss Of Signal
        Functionality :This OID indicates
        a Tx Loss of Signal Functionality
        on the Line Trscv Network Lane
         <Help> Alarm indicating a Tx Loss
        of Signal Functionality on the
         Line Trscv Network Lane <Condtype>
        LINE_LANE_TX_LOSF <Probcause> transmitterFailure
        (56) <Alarmtype> equipmentAlarm
        (5) <Polarity> (2)
        "
	::= { pm10001otu4AlmlineNetworkLaneFaultEntry 9 }


pm10001otu4AlmLineLaneTxLolPortn OBJECT-TYPE
	SYNTAX  EkiOnOff
	MAX-ACCESS read-only
	STATUS current
	DESCRIPTION
        "
        Line Network Lane Tx Loss Of Lock
        :This OID indicates a Tx Loss of
        Lock on the Line Trscv Network
         Lane <Help> Alarm indicating a
        Tx Loss of Lock on the Line Trscv
        Network Lane <Condtype> LINE_LANE_TX_LOL
        <Probcause> transmitterFailure
         (56) <Alarmtype> equipmentAlarm
        (5) <Polarity> (2)
        "
	::= { pm10001otu4AlmlineNetworkLaneFaultEntry 8 }


pm10001otu4AlmLineLaneRxLosPortn OBJECT-TYPE
	SYNTAX  EkiOnOff
	MAX-ACCESS read-only
	STATUS current
	DESCRIPTION
        "
        Line Network Lane Rx Loss Of Signal
        :This OID indicates a Rx Loss of
        Signal on the Line Trscv Network
        Lane <Help> Alarm indicating a
         Rx Loss of Signal on the Line
         Trscv Network Lane <Condtype>
         LINE_LANE_RX_LOS <Probcause> receiveFailure
        (41) <Alarmtype> physicalViolation
        (9) <Polarity> (2)
        "
	::= { pm10001otu4AlmlineNetworkLaneFaultEntry 6 }


pm10001otu4AlmLineLaneRxLolPortn OBJECT-TYPE
	SYNTAX  EkiOnOff
	MAX-ACCESS read-only
	STATUS current
	DESCRIPTION
        "
        Line Network Lane Rx Loss Of Lock
        :This OID indicates a Rx Loss of
        Lock on the Line Trscv Network
         Lane <Help> Alarm indicating a
        Rx Loss of Lock on the Line Trscv
        Network Lane <Condtype> LINE_LANE_RX_LOL
        <Probcause> receiverFailure (42)
        <Alarmtype> equipmentAlarm (5)
         <Polarity> (2)
        "
	::= { pm10001otu4AlmlineNetworkLaneFaultEntry 5 }


pm10001otu4AlmLineLaneRxFifoErrorPortn OBJECT-TYPE
	SYNTAX  EkiOnOff
	MAX-ACCESS read-only
	STATUS current
	DESCRIPTION
        "
        Line Network Lane Rx FIFO Error
        :This OID indicates a Rx FIFO Error
        on the Line Trscv Network Lane
         <Help> Alarm indicating a Rx FIFO
        Error on the Line Trscv Network
        Lane <Condtype> LINE_LANE_RX_FIFO_ERROR
        <Probcause> receiverFailure (42)
        <Alarmtype> equipmentAlarm (5)
         <Polarity> (2)
        "
	::= { pm10001otu4AlmlineNetworkLaneFaultEntry 4 }


pm10001otu4AlmLineLaneRxTecFaultPortn OBJECT-TYPE
	SYNTAX  EkiOnOff
	MAX-ACCESS read-only
	STATUS current
	DESCRIPTION
        "
        Line Network Lane Rx TEC Fault
        :This OID indicates a Rx TEC Fault
        on the Line Trscv Network Lane
         <Help> Alarm indicating a Rx TEC
        Fault on the Line Trscv Network
        Lane <Condtype> LINE_LANE_RX_TEC_FAULT
        <Probcause> receiverFailure (42)
        <Alarmtype> equipmentAlarm (5)
         <Polarity> (2)
        "
	::= { pm10001otu4AlmlineNetworkLaneFaultEntry 3 }


--- *********************************************************
---     TABLE for the pm10001otu4AlmlineHostLaneFault articles
--- *********************************************************

pm10001otu4AlmlineHostLaneFaultTable OBJECT-TYPE
	SYNTAX  SEQUENCE OF Pm10001otu4AlmlineHostLaneFaultEntry
	MAX-ACCESS not-accessible
	STATUS current
	DESCRIPTION
        "
        List of pm10001otu4AlmlineHostLaneFault
        Article
        "
	::= { pm10001otu4AlmLineUrg 152 }


pm10001otu4AlmlineHostLaneFaultEntry OBJECT-TYPE
	SYNTAX Pm10001otu4AlmlineHostLaneFaultEntry
	MAX-ACCESS not-accessible
	STATUS current
	DESCRIPTION
        "
        Row definition for the pm10001otu4AlmlineHostLaneFault
        table
        "
	INDEX   { pm10001otu4AlmlineHostLaneFaultIndex }
	::= { pm10001otu4AlmlineHostLaneFaultTable 1 }


Pm10001otu4AlmlineHostLaneFaultEntry ::=
	SEQUENCE {
	pm10001otu4AlmlineHostLaneFaultIndex
		INTEGER,
	pm10001otu4AlmLineTrxOverTempPortn
		EkiOnOff,
	pm10001otu4AlmLinePowerDegradePortn
		EkiOnOff,
	pm10001otu4AlmLineLaneTxFifoErrorPortn
		EkiOnOff,
	pm10001otu4AlmLineTxHostLolPortn
		EkiOnOff,
	pm10001otu4AlmLineSmIaeDetectedPortn
		EkiOnOff,
	pm10001otu4AlmLineSmIaeInsertedPortn
		EkiOnOff,
	pm10001otu4AlmLineSmBdiDetectedPortn
		EkiOnOff,
	pm10001otu4AlmLineSmBdiInsertedPortn
		EkiOnOff,
	pm10001otu4AlmLineLossOfFramePortn
		EkiOnOff,
	pm10001otu4AlmLineInputLossOfSignalPortn
		EkiOnOff
	}


pm10001otu4AlmlineHostLaneFaultIndex OBJECT-TYPE
	SYNTAX  INTEGER(0..128)
	MAX-ACCESS  read-only
	STATUS current
	DESCRIPTION
        "
        Index definition for the pm10001otu4AlmlineHostLaneFault
        table
        "
	::= { pm10001otu4AlmlineHostLaneFaultEntry 1 }


pm10001otu4AlmLineTrxOverTempPortn OBJECT-TYPE
	SYNTAX  EkiOnOff
	MAX-ACCESS read-only
	STATUS current
	DESCRIPTION
        "
        Temperature Critical Level :This
        OID indicates the module temperature
        is too high triggering the power
        down protection mechanism <Help>
        This alarm indicates the module
        temperature is too high triggering
        the power down protection mechanism
        <Condtype> LINE_TRX_OVER_TEMP <Probcause>
        temperatureUnacceptable (51) <Alarmtype>
        equipmentAlarm (5) <Polarity> (2)
        "
	::= { pm10001otu4AlmlineHostLaneFaultEntry 17 }


pm10001otu4AlmLinePowerDegradePortn OBJECT-TYPE
	SYNTAX  EkiOnOff
	MAX-ACCESS read-only
	STATUS current
	DESCRIPTION
        "
        3V3 Power Degrade :This OID indicates
        the 3V3 power converter was in
         failure<Help> This alarm indicates
        the 3V3 power converter was in
         failure <Condtype> LINE_POWER_DEGRADE
        <Probcause> powerProblem (36) <Alarmtype>
        equipmentAlarm (5) <Polarity> (2)
        "
	::= { pm10001otu4AlmlineHostLaneFaultEntry 16 }


pm10001otu4AlmLineLaneTxFifoErrorPortn OBJECT-TYPE
	SYNTAX  EkiOnOff
	MAX-ACCESS read-only
	STATUS current
	DESCRIPTION
        "
        Line Host Lane Tx FIFO Error :This
        OID indicates a Tx FIFO Error on
        the Line Trscv Host Lane <Help>
        Alarm indicating a Tx FIFO Error
        on the Line Trscv Host Lane <Condtype>
        LINE_LANE_TX_FIFO_ERROR <Probcause>
        receiverFailure (42) <Alarmtype>
        equipmentAlarm (5) <Polarity> (2)
        "
	::= { pm10001otu4AlmlineHostLaneFaultEntry 11 }


pm10001otu4AlmLineTxHostLolPortn OBJECT-TYPE
	SYNTAX  EkiOnOff
	MAX-ACCESS read-only
	STATUS current
	DESCRIPTION
        "
        Line Host Lane Tx Loss Of Lock
        :This OID indicates a Tx Loss of
        Lock on the Line Trscv Host Lane
        <Help> Alarm indicating a Tx Loss
        of Lock on the Line Trscv Host
         Lane <Condtype> LINE_TX_HOST_LOL
        <Probcause> receiverFailure (42)
        <Alarmtype> equipmentAlarm (5)
         <Polarity> (2)
        "
	::= { pm10001otu4AlmlineHostLaneFaultEntry 10 }


pm10001otu4AlmLineSmIaeDetectedPortn OBJECT-TYPE
	SYNTAX  EkiOnOff
	MAX-ACCESS read-only
	STATUS current
	DESCRIPTION
        "
        Line SM IAE Detected :This OID
        indicates a SM Incoming Alignment
        Error is detected on the incoming
        Line signal <Help> Alarm indicating
        a SM Incoming Alignment Error is
        detected on the incoming Line signal
        <Condtype> LINE_SM_IAE_DETECTED
        <Probcause> receiveFailure (41)
        <Alarmtype> integrityViolation
         (7) <Polarity> (2)
        "
	::= { pm10001otu4AlmlineHostLaneFaultEntry 7 }


pm10001otu4AlmLineSmIaeInsertedPortn OBJECT-TYPE
	SYNTAX  EkiOnOff
	MAX-ACCESS read-only
	STATUS current
	DESCRIPTION
        "
        Line SM IAE Inserted :This OID
        indicates a SM Incoming Alignment
        Error is inserted on the outgoing
        Line signal <Help> Status indicating
        a SM Incoming Alignment Error is
        inserted on the outgoing Line signal
        <Condtype> LINE_SM_IAE_INSERTED
        <Probcause> informationalStatus(1000)
        <Alarmtype> other (1) <Polarity>
        (2)
        "
	::= { pm10001otu4AlmlineHostLaneFaultEntry 6 }


pm10001otu4AlmLineSmBdiDetectedPortn OBJECT-TYPE
	SYNTAX  EkiOnOff
	MAX-ACCESS read-only
	STATUS current
	DESCRIPTION
        "
        Line SM BDI Detected :This OID
        indicates a SM Backward Defect
         Indication is detected on the
         incoming Line signal <Help> Alarm
        indicating a SM Backward Defect
        Indication is detected on the incoming
        Line signal <Condtype> LINE_SM_BDI_DETECTED
        <Probcause> receiveFailure (41)
        <Alarmtype> integrityViolation
         (7) <Polarity> (2)
        "
	::= { pm10001otu4AlmlineHostLaneFaultEntry 5 }


pm10001otu4AlmLineSmBdiInsertedPortn OBJECT-TYPE
	SYNTAX  EkiOnOff
	MAX-ACCESS read-only
	STATUS current
	DESCRIPTION
        "
        Line SM BDI Inserted :This OID
        indicates a SM Backward Defect
         Indication is inserted on the
         outgoing Line signal <Help> Status
        indicating a SM Backward Defect
        Indication is inserted on the outgoing
        Line signal <Condtype> LINE_SM_BDI_INSERTED
        <Probcause> informationalStatus(1000)
        <Alarmtype> other (1) <Polarity>
        (2)
        "
	::= { pm10001otu4AlmlineHostLaneFaultEntry 4 }


pm10001otu4AlmLineLossOfFramePortn OBJECT-TYPE
	SYNTAX  EkiOnOff
	MAX-ACCESS read-only
	STATUS current
	DESCRIPTION
        "
        Line Loss Of Frame :This OID indicates
        the module is not aligned with
         the incoming Line signal <Help>
        Alarm indicating the module is
         not aligned with the incoming
         Line signal <Condtype> LINE_LOSS_OF_FRAME
        <Probcause> receiveFailure (41)
        <Alarmtype> integrityViolation
         (7) <Polarity> (2)
        "
	::= { pm10001otu4AlmlineHostLaneFaultEntry 3 }


pm10001otu4AlmLineInputLossOfSignalPortn OBJECT-TYPE
	SYNTAX  EkiOnOff
	MAX-ACCESS read-only
	STATUS current
	DESCRIPTION
        "
        Line Input Loss Of Signal :This
        OID indicates a Loss of Signal
         is detected on the Line Trscv
         <Help> Alarm indicating a Loss
        of Signal is detected on the Line
        Trscv <Condtype> LINE_INPUT_LOSS_OF_SIGNAL
        <Probcause> receiveFailure (41)
        <Alarmtype> physicalViolation (9)
        <Polarity> (2)
        "
	::= { pm10001otu4AlmlineHostLaneFaultEntry 2 }


--- *********************************************************
---     TABLE for the pm10001otu4AlmlineNetworkLaneRxOtn articles
--- *********************************************************

pm10001otu4AlmlineNetworkLaneRxOtnTable OBJECT-TYPE
	SYNTAX  SEQUENCE OF Pm10001otu4AlmlineNetworkLaneRxOtnEntry
	MAX-ACCESS not-accessible
	STATUS current
	DESCRIPTION
        "
        List of pm10001otu4AlmlineNetworkLaneRxOtn
        Article
        "
	::= { pm10001otu4AlmLineUrg 168 }


pm10001otu4AlmlineNetworkLaneRxOtnEntry OBJECT-TYPE
	SYNTAX Pm10001otu4AlmlineNetworkLaneRxOtnEntry
	MAX-ACCESS not-accessible
	STATUS current
	DESCRIPTION
        "
        Row definition for the pm10001otu4AlmlineNetworkLaneRxOtn
        table
        "
	INDEX   { pm10001otu4AlmlineNetworkLaneRxOtnIndex }
	::= { pm10001otu4AlmlineNetworkLaneRxOtnTable 1 }


Pm10001otu4AlmlineNetworkLaneRxOtnEntry ::=
	SEQUENCE {
	pm10001otu4AlmlineNetworkLaneRxOtnIndex
		INTEGER,
	pm10001otu4AlmLineRxOtnLofPortn
		EkiOnOff,
	pm10001otu4AlmLineRxOtnOofPortn
		EkiOnOff,
	pm10001otu4AlmLineRxOtnLomPortn
		EkiOnOff,
	pm10001otu4AlmLineRxOtnOomPortn
		EkiOnOff,
	pm10001otu4AlmLineRxOtnIaePortn
		EkiOnOff,
	pm10001otu4AlmLineRxSmBdiPortn
		EkiOnOff,
	pm10001otu4AlmLineRxOtnOtuAisPortn
		EkiOnOff,
	pm10001otu4AlmLineRxOtnOduAisPortn
		EkiOnOff
	}


pm10001otu4AlmlineNetworkLaneRxOtnIndex OBJECT-TYPE
	SYNTAX  INTEGER(0..128)
	MAX-ACCESS  read-only
	STATUS current
	DESCRIPTION
        "
        Index definition for the pm10001otu4AlmlineNetworkLaneRxOtn
        table
        "
	::= { pm10001otu4AlmlineNetworkLaneRxOtnEntry 1 }


pm10001otu4AlmLineRxOtnLofPortn OBJECT-TYPE
	SYNTAX  EkiOnOff
	MAX-ACCESS read-only
	STATUS current
	DESCRIPTION
        "
        Line Network Rx LOF :This OID
         indicates a Loss of Frame is detected
        on the Rx Network interface of
         the Line Trscv <Help> Alarm indicating
        a Loss of Frame is detected on
         the Rx Network interface of the
        Line Trscv <Condtype> LINE_RX_OTN_LOF
        <Probcause> receiveFailure (41)
        <Alarmtype> equipmentAlarm (5)
         <Polarity> (2)
        "
	::= { pm10001otu4AlmlineNetworkLaneRxOtnEntry 17 }


pm10001otu4AlmLineRxOtnOofPortn OBJECT-TYPE
	SYNTAX  EkiOnOff
	MAX-ACCESS read-only
	STATUS current
	DESCRIPTION
        "
        Line Network Rx OOF :This OID
         indicates an Out of Frame is detected
        on the Rx Network interface of
         the Line Trscv <Help> Alarm indicating
        an Out of Frame is detected on
         the Rx Network interface of the
        Line Trscv <Condtype> LINE_RX_OTN_OOF
        <Probcause> receiveFailure (41)
        <Alarmtype> equipmentAlarm (5)
         <Polarity> (2)
        "
	::= { pm10001otu4AlmlineNetworkLaneRxOtnEntry 16 }


pm10001otu4AlmLineRxOtnLomPortn OBJECT-TYPE
	SYNTAX  EkiOnOff
	MAX-ACCESS read-only
	STATUS current
	DESCRIPTION
        "
        Line Network Rx LOM :This OID
         indicates a Loss of Multiframe
        is detected on the Rx Network interface
        of the Line Trscv <Help> Alarm
         indicating a Loss of Multiframe
        is detected on the Rx Network interface
        of the Line Trscv <Condtype> LINE_RX_OTN_LOM
        <Probcause> receiveFailure (41)
        <Alarmtype> equipmentAlarm (5)
         <Polarity> (2)
        "
	::= { pm10001otu4AlmlineNetworkLaneRxOtnEntry 15 }


pm10001otu4AlmLineRxOtnOomPortn OBJECT-TYPE
	SYNTAX  EkiOnOff
	MAX-ACCESS read-only
	STATUS current
	DESCRIPTION
        "
        Line Network Rx OOM :This OID
         indicates an Out of Multiframe
        is detected on the Rx Network interface
        of the Line Trscv <Help> Alarm
         indicating an Out of Multiframe
        is detected on the Rx Network interface
        of the Line Trscv <Condtype> LINE_RX_OTN_OOM
        <Probcause> receiveFailure (41)
        <Alarmtype> equipmentAlarm (5)
         <Polarity> (2)
        "
	::= { pm10001otu4AlmlineNetworkLaneRxOtnEntry 14 }


pm10001otu4AlmLineRxOtnIaePortn OBJECT-TYPE
	SYNTAX  EkiOnOff
	MAX-ACCESS read-only
	STATUS current
	DESCRIPTION
        "
        Line Network Rx IAE :This OID
         indicates an Incoming Alignment
        Error is detected on the Rx Network
        interface of the Line Trscv <Help>
        Alarm indicating an Incoming Alignment
        Error is detected on the Rx Network
        interface of the Line Trscv <Condtype>
        LINE_RX_OTN_IAE <Probcause> receiveFailure
        (41) <Alarmtype> equipmentAlarm
        (5) <Polarity> (2)
        "
	::= { pm10001otu4AlmlineNetworkLaneRxOtnEntry 13 }


pm10001otu4AlmLineRxSmBdiPortn OBJECT-TYPE
	SYNTAX  EkiOnOff
	MAX-ACCESS read-only
	STATUS current
	DESCRIPTION
        "
        Line Network Rx SM BDI :This OID
        indicates an SM Backward Defect
        Indication is detected on the Rx
        Network interface of the Line Trscv
        <Help> Alarm indicating an SM Backward
        Defect Indication is detected on
        the Rx Network interface of the
        Line Trscv <Condtype> LINE_RX_SM_BDI
        <Probcause> informationalStatus(1000)
        <Alarmtype> other (1) <Polarity>
        (2)
        "
	::= { pm10001otu4AlmlineNetworkLaneRxOtnEntry 12 }


pm10001otu4AlmLineRxOtnOtuAisPortn OBJECT-TYPE
	SYNTAX  EkiOnOff
	MAX-ACCESS read-only
	STATUS current
	DESCRIPTION
        "
        Line Network Rx OTU AIS :This
         OID indicates an OTU This OID
         Indication Signal is detected
         on the Rx Network interface of
        the Line Trscv <Help> Alarm indicating
        an OTU Alarm Indication Signal
         is detected on the Rx Network
         interface of the Line Trscv <Condtype>
        LINE_RX_OTN_OTU_AIS <Probcause>
        receiveFailure (41) <Alarmtype>
        equipmentAlarm (5) <Polarity> (2)
        "
	::= { pm10001otu4AlmlineNetworkLaneRxOtnEntry 11 }


pm10001otu4AlmLineRxOtnOduAisPortn OBJECT-TYPE
	SYNTAX  EkiOnOff
	MAX-ACCESS read-only
	STATUS current
	DESCRIPTION
        "
        Line Network Rx ODU AIS :This
         OID indicates an ODU This OID
         Indication Signal is detected
         on the Rx Network interface of
        the Line Trscv <Help> Alarm indicating
        an ODU Alarm Indication Signal
         is detected on the Rx Network
         interface of the Line Trscv <Condtype>
        LINE_RX_OTN_ODU_AIS <Probcause>
        receiveFailure (41) <Alarmtype>
        equipmentAlarm (5) <Polarity> (2)
        "
	::= { pm10001otu4AlmlineNetworkLaneRxOtnEntry 10 }


--- *********************************************************
---     TABLE for the pm10001otu4AlmlineHostLaneTxOtn articles
--- *********************************************************

pm10001otu4AlmlineHostLaneTxOtnTable OBJECT-TYPE
	SYNTAX  SEQUENCE OF Pm10001otu4AlmlineHostLaneTxOtnEntry
	MAX-ACCESS not-accessible
	STATUS current
	DESCRIPTION
        "
        List of pm10001otu4AlmlineHostLaneTxOtn
        Article
        "
	::= { pm10001otu4AlmLineUrg 184 }


pm10001otu4AlmlineHostLaneTxOtnEntry OBJECT-TYPE
	SYNTAX Pm10001otu4AlmlineHostLaneTxOtnEntry
	MAX-ACCESS not-accessible
	STATUS current
	DESCRIPTION
        "
        Row definition for the pm10001otu4AlmlineHostLaneTxOtn
        table
        "
	INDEX   { pm10001otu4AlmlineHostLaneTxOtnIndex }
	::= { pm10001otu4AlmlineHostLaneTxOtnTable 1 }


Pm10001otu4AlmlineHostLaneTxOtnEntry ::=
	SEQUENCE {
	pm10001otu4AlmlineHostLaneTxOtnIndex
		INTEGER,
	pm10001otu4AlmLineTxOtnLofPortn
		EkiOnOff,
	pm10001otu4AlmLineTxOtnOofPortn
		EkiOnOff,
	pm10001otu4AlmLineTxOtnLomPortn
		EkiOnOff,
	pm10001otu4AlmLineTxOtnOomPortn
		EkiOnOff,
	pm10001otu4AlmLineTxOtnIaePortn
		EkiOnOff,
	pm10001otu4AlmLineTxSmBdiPortn
		EkiOnOff,
	pm10001otu4AlmLineTxOtnOtuAisPortn
		EkiOnOff,
	pm10001otu4AlmLineTxOtnOduAisPortn
		EkiOnOff
	}


pm10001otu4AlmlineHostLaneTxOtnIndex OBJECT-TYPE
	SYNTAX  INTEGER(0..128)
	MAX-ACCESS  read-only
	STATUS current
	DESCRIPTION
        "
        Index definition for the pm10001otu4AlmlineHostLaneTxOtn
        table
        "
	::= { pm10001otu4AlmlineHostLaneTxOtnEntry 1 }


pm10001otu4AlmLineTxOtnLofPortn OBJECT-TYPE
	SYNTAX  EkiOnOff
	MAX-ACCESS read-only
	STATUS current
	DESCRIPTION
        "
        Line Host Tx LOF :This OID indicates
        a Loss of Frame is detected on
         the Tx Host interface of the Line
        Trscv <Help> Alarm indicating a
        Loss of Frame is detected on the
        Tx Host interface of the Line Trscv
        <Condtype> LINE_TX_OTN_LOF <Probcause>
        receiveFailure (41) <Alarmtype>
        equipmentAlarm (5) <Polarity> (2)
        "
	::= { pm10001otu4AlmlineHostLaneTxOtnEntry 17 }


pm10001otu4AlmLineTxOtnOofPortn OBJECT-TYPE
	SYNTAX  EkiOnOff
	MAX-ACCESS read-only
	STATUS current
	DESCRIPTION
        "
        Line Host Tx OOF :This OID indicates
        an Out of Frame is detected on
         the Tx Host interface of the Line
        Trscv <Help> Alarm indicating an
        Out of Frame is detected on the
        Tx Host interface of the Line Trscv
        <Condtype> LINE_TX_OTN_OOF <Probcause>
        receiveFailure (41) <Alarmtype>
        equipmentAlarm (5) <Polarity> (2)
        "
	::= { pm10001otu4AlmlineHostLaneTxOtnEntry 16 }


pm10001otu4AlmLineTxOtnLomPortn OBJECT-TYPE
	SYNTAX  EkiOnOff
	MAX-ACCESS read-only
	STATUS current
	DESCRIPTION
        "
        Line Host Tx LOM :This OID indicates
        a Loss of Multiframe is detected
        on the Tx Host interface of the
        Line Trscv <Help> Alarm indicating
        a Loss of Multiframe is detected
        on the Tx Host interface of the
        Line Trscv <Condtype> LINE_TX_OTN_LOM
        <Probcause> receiveFailure (41)
        <Alarmtype> equipmentAlarm (5)
         <Polarity> (2)
        "
	::= { pm10001otu4AlmlineHostLaneTxOtnEntry 15 }


pm10001otu4AlmLineTxOtnOomPortn OBJECT-TYPE
	SYNTAX  EkiOnOff
	MAX-ACCESS read-only
	STATUS current
	DESCRIPTION
        "
        Line Host Tx OOM :This OID indicates
        an Out of Multiframe is detected
        on the Tx Host interface of the
        Line Trscv <Help> Alarm indicating
        an Out of Multiframe is detected
        on the Tx Host interface of the
        Line Trscv <Condtype> LINE_TX_OTN_OOM
        <Probcause> receiveFailure (41)
        <Alarmtype> equipmentAlarm (5)
         <Polarity> (2)
        "
	::= { pm10001otu4AlmlineHostLaneTxOtnEntry 14 }


pm10001otu4AlmLineTxOtnIaePortn OBJECT-TYPE
	SYNTAX  EkiOnOff
	MAX-ACCESS read-only
	STATUS current
	DESCRIPTION
        "
        Line Host Tx IAE :This OID indicates
        an Incoming Alignment Error is
         detected on the Tx Host interface
        of the Line Trscv <Help> Alarm
         indicating an Incoming Alignment
        Error is detected on the Tx Host
        interface of the Line Trscv <Condtype>
        LINE_TX_OTN_IAE <Probcause> receiveFailure
        (41) <Alarmtype> equipmentAlarm
        (5) <Polarity> (2)
        "
	::= { pm10001otu4AlmlineHostLaneTxOtnEntry 13 }


pm10001otu4AlmLineTxSmBdiPortn OBJECT-TYPE
	SYNTAX  EkiOnOff
	MAX-ACCESS read-only
	STATUS current
	DESCRIPTION
        "
        Line Host Tx SM BDI :This OID
         indicates an SM Backward Defect
        Indication is detected on the Tx
        Host interface of the Line Trscv
        <Help> Alarm indicating an SM Backward
        Defect Indication is detected on
        the Tx Host interface of the Line
        Trscv <Condtype> LINE_TX_SM_BDI
        <Probcause> informationalStatus(1000)
        <Alarmtype> other (1) <Polarity>
        (2)
        "
	::= { pm10001otu4AlmlineHostLaneTxOtnEntry 12 }


pm10001otu4AlmLineTxOtnOtuAisPortn OBJECT-TYPE
	SYNTAX  EkiOnOff
	MAX-ACCESS read-only
	STATUS current
	DESCRIPTION
        "
        Line Host Tx OTU AIS :This OID
        indicates an OTU This OID Indication
        Signal is detected on the Tx Host
        interface of the Line Trscv <Help>
        Alarm indicating an OTU Alarm Indication
        Signal is detected on the Tx Host
        interface of the Line Trscv <Condtype>
        LINE_TX_OTN_OTU_AIS <Probcause>
        receiveFailure (41) <Alarmtype>
        equipmentAlarm (5) <Polarity> (2)
        "
	::= { pm10001otu4AlmlineHostLaneTxOtnEntry 11 }


pm10001otu4AlmLineTxOtnOduAisPortn OBJECT-TYPE
	SYNTAX  EkiOnOff
	MAX-ACCESS read-only
	STATUS current
	DESCRIPTION
        "
        Line Host Tx ODU AIS :This OID
        indicates an ODU This OID Indication
        Signal is detected on the Tx Host
        interface of the Line Trscv <Help>
        Alarm indicating an ODU Alarm Indication
        Signal is detected on the Tx Host
        interface of the Line Trscv <Condtype>
        LINE_TX_OTN_ODU_AIS <Probcause>
        receiveFailure (41) <Alarmtype>
        equipmentAlarm (5) <Polarity> (2)
        "
	::= { pm10001otu4AlmlineHostLaneTxOtnEntry 10 }


--- *********************************************************
---     TABLE for the pm10001otu4AlmclientSfpAlmDdm articles
--- *********************************************************

pm10001otu4AlmclientSfpAlmDdmTable OBJECT-TYPE
	SYNTAX  SEQUENCE OF Pm10001otu4AlmclientSfpAlmDdmEntry
	MAX-ACCESS not-accessible
	STATUS current
	DESCRIPTION
        "
        List of pm10001otu4AlmclientSfpAlmDdm
        Article
        "
	::= { pm10001otu4AlmClientUrg 216 }


pm10001otu4AlmclientSfpAlmDdmEntry OBJECT-TYPE
	SYNTAX Pm10001otu4AlmclientSfpAlmDdmEntry
	MAX-ACCESS not-accessible
	STATUS current
	DESCRIPTION
        "
        Row definition for the pm10001otu4AlmclientSfpAlmDdm
        table
        "
	INDEX   { pm10001otu4AlmclientSfpAlmDdmIndex }
	::= { pm10001otu4AlmclientSfpAlmDdmTable 1 }


Pm10001otu4AlmclientSfpAlmDdmEntry ::=
	SEQUENCE {
	pm10001otu4AlmclientSfpAlmDdmIndex
		INTEGER,
	pm10001otu4AlmRxPwrHighAlaPortn
		EkiOnOff,
	pm10001otu4AlmRxPwrLowAlaPortn
		EkiOnOff,
	pm10001otu4AlmTempHighAlaPortn
		EkiOnOff,
	pm10001otu4AlmTempLowAlaPortn
		EkiOnOff,
	pm10001otu4AlmVccHighAlaPortn
		EkiOnOff,
	pm10001otu4AlmVccLowAlaPortn
		EkiOnOff,
	pm10001otu4AlmTxBiasHighAlaPortn
		EkiOnOff,
	pm10001otu4AlmTxBiasLowAlaPortn
		EkiOnOff,
	pm10001otu4AlmTxPwrHighAlaPortn
		EkiOnOff,
	pm10001otu4AlmTxPwrLowAlaPortn
		EkiOnOff
	}


pm10001otu4AlmclientSfpAlmDdmIndex OBJECT-TYPE
	SYNTAX  INTEGER(0..128)
	MAX-ACCESS  read-only
	STATUS current
	DESCRIPTION
        "
        Index definition for the pm10001otu4AlmclientSfpAlmDdm
        table
        "
	::= { pm10001otu4AlmclientSfpAlmDdmEntry 1 }


pm10001otu4AlmRxPwrHighAlaPortn OBJECT-TYPE
	SYNTAX  EkiOnOff
	MAX-ACCESS read-only
	STATUS current
	DESCRIPTION
        "
        Client Trscv Rx Power High :This
        OID indicates that the Trscv input
        power of port is higher than the
        threshold value written in the
         Trscv EEPROM <Help> Alarm indicating
        that the Trscv input power of port
        is higher than the threshold value
        written in the Trscv EEPROM <Condtype>
        RX_PWR_HIGH_ALA_1 <Probcause> receiveFailure
        (41) <Alarmtype> equipmentAlarm
        (5) <Polarity> (2)
        "
	::= { pm10001otu4AlmclientSfpAlmDdmEntry 17 }


pm10001otu4AlmRxPwrLowAlaPortn OBJECT-TYPE
	SYNTAX  EkiOnOff
	MAX-ACCESS read-only
	STATUS current
	DESCRIPTION
        "
        Client Trscv Rx Power Low :This
        OID indicates that the Trscv input
        power of port is lower than the
        threshold value written in the
         Trscv EEPROM <Help> Alarm indicating
        that the Trscv input power of port
        is lower than the threshold value
        written in the Trscv EEPROM <Condtype>
        RX_PWR_LOW_ALA_1 <Probcause> receiveFailure
        (41) <Alarmtype> equipmentAlarm
        (5) <Polarity> (2)
        "
	::= { pm10001otu4AlmclientSfpAlmDdmEntry 16 }


pm10001otu4AlmTempHighAlaPortn OBJECT-TYPE
	SYNTAX  EkiOnOff
	MAX-ACCESS read-only
	STATUS current
	DESCRIPTION
        "
        Client Trscv Temp High :This OID
        indicates that the Trscv temperature
        of port is higher than the threshold
        value written in the Trscv EEPROM
        <Help> Alarm indicating that the
        Trscv temperature of port is higher
        than the threshold value written
        in the Trscv EEPROM <Condtype>
         TEMP_HIGH_ALA_1 <Probcause> temperatureUnacceptable
        (51) <Alarmtype> equipmentAlarm
        (5) <Polarity> (2)
        "
	::= { pm10001otu4AlmclientSfpAlmDdmEntry 9 }


pm10001otu4AlmTempLowAlaPortn OBJECT-TYPE
	SYNTAX  EkiOnOff
	MAX-ACCESS read-only
	STATUS current
	DESCRIPTION
        "
        Client Trscv Temp Low :This OID
        indicates that the Trscv temperature
        of port is lower than the threshold
        value written in the Trscv EEPROM
        <Help> Alarm indicating that the
        Trscv temperature of port is lower
        than the threshold value written
        in the Trscv EEPROM <Condtype>
         TEMP_LOW_ALA_1 <Probcause> temperatureUnacceptable
        (51) <Alarmtype> equipmentAlarm
        (5) <Polarity> (2)
        "
	::= { pm10001otu4AlmclientSfpAlmDdmEntry 8 }


pm10001otu4AlmVccHighAlaPortn OBJECT-TYPE
	SYNTAX  EkiOnOff
	MAX-ACCESS read-only
	STATUS current
	DESCRIPTION
        "
        Client Trscv Power Supply High
        :This OID indicates that the Trscv
        power supply of port is higher
         than the threshold value written
        in the Trscv EEPROM <Help> Alarm
        indicating that the Trscv power
        supply of port is higher than the
        threshold value written in the
         Trscv EEPROM <Condtype> VCC_HIGH_ALA_1
        <Probcause> powerProblem (36) <Alarmtype>
        equipmentAlarm (5) <Polarity> (2)
        "
	::= { pm10001otu4AlmclientSfpAlmDdmEntry 7 }


pm10001otu4AlmVccLowAlaPortn OBJECT-TYPE
	SYNTAX  EkiOnOff
	MAX-ACCESS read-only
	STATUS current
	DESCRIPTION
        "
        Client Trscv Power Supply Low
         :This OID indicates that the Trscv
        power supply of port is lower than
        the threshold value written in
         the Trscv EEPROM <Help> Alarm
         indicating that the Trscv power
        supply of port is lower than the
        threshold value written in the
         Trscv EEPROM <Condtype> VCC_LOW_ALA_1
        <Probcause> powerProblem (36) <Alarmtype>
        equipmentAlarm (5) <Polarity> (2)
        "
	::= { pm10001otu4AlmclientSfpAlmDdmEntry 6 }


pm10001otu4AlmTxBiasHighAlaPortn OBJECT-TYPE
	SYNTAX  EkiOnOff
	MAX-ACCESS read-only
	STATUS current
	DESCRIPTION
        "
        Client Trscv Bias High :This OID
        indicates that the Trscv laser
         bias current of port is higher
        than the threshold value written
        in the Trscv EEPROM <Help> Alarm
        indicating that the Trscv laser
        bias current of port is higher
         than the threshold value written
        in the Trscv EEPROM <Condtype>
         TX_BIAS_HIGH_ALA_1 <Probcause>
        transmitterFailure (56) <Alarmtype>
        equipmentAlarm (5) <Polarity> (2)
        "
	::= { pm10001otu4AlmclientSfpAlmDdmEntry 5 }


pm10001otu4AlmTxBiasLowAlaPortn OBJECT-TYPE
	SYNTAX  EkiOnOff
	MAX-ACCESS read-only
	STATUS current
	DESCRIPTION
        "
        Client Trscv Bias Low :This OID
        indicates that the Trscv laser
         bias current of port is lower
         than the threshold value written
        in the Trscv EEPROM <Help> Alarm
        indicating that the Trscv laser
        bias current of port is lower than
        the threshold value written in
         the Trscv EEPROM <Condtype> TX_BIAS_LOW_ALA_1
        <Probcause> transmitterFailure
         (56) <Alarmtype> equipmentAlarm
        (5) <Polarity> (2)
        "
	::= { pm10001otu4AlmclientSfpAlmDdmEntry 4 }


pm10001otu4AlmTxPwrHighAlaPortn OBJECT-TYPE
	SYNTAX  EkiOnOff
	MAX-ACCESS read-only
	STATUS current
	DESCRIPTION
        "
        Client Trscv Tx Power High :This
        OID indicates that the Trscv output
        power of port is higher than the
        threshold value written in the
         Trscv EEPROM <Help> Alarm indicating
        that the Trscv output power of
         port is higher than the threshold
        value written in the Trscv EEPROM
        <Condtype> TX_PWR_HIGH_ALA_1 <Probcause>
        transmitterFailure (56) <Alarmtype>
        equipmentAlarm (5) <Polarity> (2)
        "
	::= { pm10001otu4AlmclientSfpAlmDdmEntry 3 }


pm10001otu4AlmTxPwrLowAlaPortn OBJECT-TYPE
	SYNTAX  EkiOnOff
	MAX-ACCESS read-only
	STATUS current
	DESCRIPTION
        "
        Client Trscv Tx Power Low :This
        OID indicates that the Trscv output
        power of port is lower than the
        threshold value written in the
         Trscv EEPROM <Help> Alarm indicating
        that the Trscv output power of
         port is lower than the threshold
        value written in the Trscv EEPROM
        <Condtype> TX_PWR_LOW_ALA_1 <Probcause>
        transmitterFailure (56) <Alarmtype>
        equipmentAlarm (5) <Polarity> (2)
        "
	::= { pm10001otu4AlmclientSfpAlmDdmEntry 2 }


--- *********************************************************
---     TABLE for the pm10001otu4AlmclientSfpWarnDdm articles
--- *********************************************************

pm10001otu4AlmclientSfpWarnDdmTable OBJECT-TYPE
	SYNTAX  SEQUENCE OF Pm10001otu4AlmclientSfpWarnDdmEntry
	MAX-ACCESS not-accessible
	STATUS current
	DESCRIPTION
        "
        List of pm10001otu4AlmclientSfpWarnDdm
        Article
        "
	::= { pm10001otu4AlmClientNurg 232 }


pm10001otu4AlmclientSfpWarnDdmEntry OBJECT-TYPE
	SYNTAX Pm10001otu4AlmclientSfpWarnDdmEntry
	MAX-ACCESS not-accessible
	STATUS current
	DESCRIPTION
        "
        Row definition for the pm10001otu4AlmclientSfpWarnDdm
        table
        "
	INDEX   { pm10001otu4AlmclientSfpWarnDdmIndex }
	::= { pm10001otu4AlmclientSfpWarnDdmTable 1 }


Pm10001otu4AlmclientSfpWarnDdmEntry ::=
	SEQUENCE {
	pm10001otu4AlmclientSfpWarnDdmIndex
		INTEGER,
	pm10001otu4AlmRxPwrHighWngPortn
		EkiOnOff,
	pm10001otu4AlmRxPwrLowWngPortn
		EkiOnOff,
	pm10001otu4AlmTempHighWngPortn
		EkiOnOff,
	pm10001otu4AlmTempLowWngPortn
		EkiOnOff,
	pm10001otu4AlmVccHighWngPortn
		EkiOnOff,
	pm10001otu4AlmVccLowWngPortn
		EkiOnOff,
	pm10001otu4AlmTxBiasHighWngPortn
		EkiOnOff,
	pm10001otu4AlmTxBiasLowWngPortn
		EkiOnOff,
	pm10001otu4AlmTxPwrHighWngPortn
		EkiOnOff,
	pm10001otu4AlmTxPwLowWngPortn
		EkiOnOff
	}


pm10001otu4AlmclientSfpWarnDdmIndex OBJECT-TYPE
	SYNTAX  INTEGER(0..128)
	MAX-ACCESS  read-only
	STATUS current
	DESCRIPTION
        "
        Index definition for the pm10001otu4AlmclientSfpWarnDdm
        table
        "
	::= { pm10001otu4AlmclientSfpWarnDdmEntry 1 }


pm10001otu4AlmRxPwrHighWngPortn OBJECT-TYPE
	SYNTAX  EkiOnOff
	MAX-ACCESS read-only
	STATUS current
	DESCRIPTION
        "
        Client Trscv Rx Power High Warning
        :This OID indicates that the Trscv
        input power is higher than the
         threshold value written in the
        Trscv EEPROM <Help> Warning indicating
        that the Trscv input power is higher
        than the threshold value written
        in the Trscv EEPROM <Condtype>
         RX_PWR_HIGH_WNG_1 <Probcause>
         receiveFailure (41) <Alarmtype>
        equipmentAlarm (5) <Polarity> (2)
        "
	::= { pm10001otu4AlmclientSfpWarnDdmEntry 17 }


pm10001otu4AlmRxPwrLowWngPortn OBJECT-TYPE
	SYNTAX  EkiOnOff
	MAX-ACCESS read-only
	STATUS current
	DESCRIPTION
        "
        Client Trscv Rx Power Low Warning
        :This OID indicates that the Trscv
        input power is lower than the threshold
        value written in the Trscv EEPROM
        <Help> Warning indicating that
         the Trscv input power is lower
        than the threshold value written
        in the Trscv EEPROM <Condtype>
         RX_PWR_LOW_WNG_1 <Probcause> receiveFailure
        (41) <Alarmtype> equipmentAlarm
        (5) <Polarity> (2)
        "
	::= { pm10001otu4AlmclientSfpWarnDdmEntry 16 }


pm10001otu4AlmTempHighWngPortn OBJECT-TYPE
	SYNTAX  EkiOnOff
	MAX-ACCESS read-only
	STATUS current
	DESCRIPTION
        "
        Client Trscv Temp High Warning
        :This OID indicates that the Trscv
        temperature is higher than the
         threshold value written in the
        Trscv EEPROM <Help> Warning indicating
        that the Trscv temperature is higher
        than the threshold value written
        in the Trscv EEPROM <Condtype>
         TEMP_HIGH_WNG_1 <Probcause> temperatureUnacceptable
        (51) <Alarmtype> equipmentAlarm
        (5) <Polarity> (2)
        "
	::= { pm10001otu4AlmclientSfpWarnDdmEntry 9 }


pm10001otu4AlmTempLowWngPortn OBJECT-TYPE
	SYNTAX  EkiOnOff
	MAX-ACCESS read-only
	STATUS current
	DESCRIPTION
        "
        Client Trscv Temp Low Warning
         :This OID indicates that the Trscv
        temperature is lower than the threshold
        value written in the Trscv EEPROM
        <Help> Warning indicating that
         the Trscv temperature is lower
        than the threshold value written
        in the Trscv EEPROM <Condtype>
         TEMP_LOW_WNG_1 <Probcause> temperatureUnacceptable
        (51) <Alarmtype> equipmentAlarm
        (5) <Polarity> (2)
        "
	::= { pm10001otu4AlmclientSfpWarnDdmEntry 8 }


pm10001otu4AlmVccHighWngPortn OBJECT-TYPE
	SYNTAX  EkiOnOff
	MAX-ACCESS read-only
	STATUS current
	DESCRIPTION
        "
        Client Trscv Power Supply High
        Warning :This OID indicates that
        the Trscv power supply is higher
        than the threshold value written
        in the Trscv EEPROM <Help> Warning
        indicating that the Trscv power
        supply is higher than the threshold
        value written in the Trscv EEPROM
        <Condtype> VCC_HIGH_WNG_1 <Probcause>
        powerProblem (36) <Alarmtype> equipmentAlarm
        (5) <Polarity> (2)
        "
	::= { pm10001otu4AlmclientSfpWarnDdmEntry 7 }


pm10001otu4AlmVccLowWngPortn OBJECT-TYPE
	SYNTAX  EkiOnOff
	MAX-ACCESS read-only
	STATUS current
	DESCRIPTION
        "
        Client Trscv Power Supply Low
         Warning :This OID indicates that
        the Trscv power supply is lower
        than the threshold value written
        in the Trscv EEPROM <Help> Warning
        indicating that the Trscv power
        supply is lower than the threshold
        value written in the Trscv EEPROM
        <Condtype> VCC_LOW_WNG_1 <Probcause>
        powerProblem (36) <Alarmtype> equipmentAlarm
        (5) <Polarity> (2)
        "
	::= { pm10001otu4AlmclientSfpWarnDdmEntry 6 }


pm10001otu4AlmTxBiasHighWngPortn OBJECT-TYPE
	SYNTAX  EkiOnOff
	MAX-ACCESS read-only
	STATUS current
	DESCRIPTION
        "
        Client Trscv Bias High Warning
        :This OID indicates that the Trscv
        laser bias current is higher than
        the threshold value written in
         the Trscv EEPROM <Help> Warning
        indicating that the Trscv laser
        bias current is higher than the
        threshold value written in the
         Trscv EEPROM <Condtype> TX_BIAS_HIGH_WNG_1
        <Probcause> transmitterFailure
         (56) <Alarmtype> equipmentAlarm
        (5) <Polarity> (2)
        "
	::= { pm10001otu4AlmclientSfpWarnDdmEntry 5 }


pm10001otu4AlmTxBiasLowWngPortn OBJECT-TYPE
	SYNTAX  EkiOnOff
	MAX-ACCESS read-only
	STATUS current
	DESCRIPTION
        "
        Client Trscv Bias Low Warning
         :This OID indicates that the Trscv
        laser bias current is lower than
        the threshold value written in
         the Trscv EEPROM <Help> Warning
        indicating that the Trscv laser
        bias current is lower than the
         threshold value written in the
        Trscv EEPROM <Condtype> TX_BIAS_LOW_WNG_1
        <Probcause> transmitterFailure
         (56) <Alarmtype> equipmentAlarm
        (5) <Polarity> (2)
        "
	::= { pm10001otu4AlmclientSfpWarnDdmEntry 4 }


pm10001otu4AlmTxPwrHighWngPortn OBJECT-TYPE
	SYNTAX  EkiOnOff
	MAX-ACCESS read-only
	STATUS current
	DESCRIPTION
        "
        Client Trscv Tx Power High Warning
        :This OID indicates that the Trscv
        output power is higher than the
        threshold value written in the
         Trscv EEPROM <Help> Warning indicating
        that the Trscv output power is
         higher than the threshold value
        written in the Trscv EEPROM <Condtype>
        TX_PWR_HIGH_WNG_1 <Probcause> transmitterFailure
        (56) <Alarmtype> equipmentAlarm
        (5) <Polarity> (2)
        "
	::= { pm10001otu4AlmclientSfpWarnDdmEntry 3 }


pm10001otu4AlmTxPwLowWngPortn OBJECT-TYPE
	SYNTAX  EkiOnOff
	MAX-ACCESS read-only
	STATUS current
	DESCRIPTION
        "
        Client Trscv Tx Power Low Warning
        :This OID indicates that the Trscv
        output power is lower than the
         threshold value written in the
        Trscv EEPROM <Help> Warning indicating
        that the Trscv output power is
         lower than the threshold value
        written in the Trscv EEPROM <Condtype>
        TX_PW_LOW_WNG_1 <Probcause> transmitterFailure
        (56) <Alarmtype> equipmentAlarm
        (5) <Polarity> (2)
        "
	::= { pm10001otu4AlmclientSfpWarnDdmEntry 2 }







--- *****************************************************
--- $$$$$$$$$$$$$$$$$$$$$$$$$$$$$$$$$$$$$$$$$$$$$$$$$$$$$
---     CONTROLS
--- $$$$$$$$$$$$$$$$$$$$$$$$$$$$$$$$$$$$$$$$$$$$$$$$$$$$$
--- *****************************************************



--- *****************************************************
---     LEAF for the confMgnt1 article
--- *****************************************************
pm10001otu4CtrlconfMgnt1 OBJECT IDENTIFIER ::= { pm10001otu4CtrlOther 1 }




pm10001otu4CtrlConf2Clear1 OBJECT-TYPE
	  SYNTAX EkiOnOff
	  MAX-ACCESS read-write
	  STATUS current
	  DESCRIPTION
        "
        Clear Configuration Tables :This
        OID clears the configuration tables
        from configuration2 in the flash.
         <Help>  This control restores
         the default configuration of the
        module
        "
	  ::= { pm10001otu4CtrlconfMgnt1 14 }



pm10001otu4CtrlConf2Flash1 OBJECT-TYPE
	  SYNTAX EkiOnOff
	  MAX-ACCESS read-write
	  STATUS current
	  DESCRIPTION
        "
        Write Configuration Tables :This
        OID saves the current configuration
        of the PM as configuration2 in
         the flash.  <Help>  This control
        saves the customer configuration
        on the module
        "
	  ::= { pm10001otu4CtrlconfMgnt1 10 }



pm10001otu4CtrlConf2Load1 OBJECT-TYPE
	  SYNTAX EkiOnOff
	  MAX-ACCESS read-write
	  STATUS current
	  DESCRIPTION
        "
        Load Configuration Tables Set
         Nb 2 :When set this OID enables
        loading from flash configuration2
        into the PM.
        "
	  ::= { pm10001otu4CtrlconfMgnt1 2 }



pm10001otu4CtrlConf1Load1 OBJECT-TYPE
	  SYNTAX EkiOnOff
	  MAX-ACCESS read-write
	  STATUS current
	  DESCRIPTION
        "
        Load Configuration Tables Set
         Nb 1 :When set this OID enables
        loading from flash configuration1
        into the PM.
        "
	  ::= { pm10001otu4CtrlconfMgnt1 1 }



--- *****************************************************
---     LEAF for the synth4 article
--- *****************************************************
pm10001otu4Ctrlsynth4 OBJECT IDENTIFIER ::= { pm10001otu4CtrlOther 4 }




pm10001otu4CtrlCorrelatOff OBJECT-TYPE
	  SYNTAX EkiOnOff
	  MAX-ACCESS read-write
	  STATUS current
	  DESCRIPTION
        "
        Disable Alarm Correlation :This
        OID disables the alarm correlation
        in the PM.
        "
	  ::= { pm10001otu4Ctrlsynth4 2 }



pm10001otu4CtrlCorrelatOn OBJECT-TYPE
	  SYNTAX EkiOnOff
	  MAX-ACCESS read-write
	  STATUS current
	  DESCRIPTION
        "
        Enable Alarm Correlation :This
        OID enables the alarm correlation
        in the PM.
        "
	  ::= { pm10001otu4Ctrlsynth4 1 }



--- *****************************************************
---     LEAF for the swMgnt article
--- *****************************************************
pm10001otu4CtrlswMgnt OBJECT IDENTIFIER ::= { pm10001otu4CtrlOther 5 }




pm10001otu4CtrlLoadSwBank2 OBJECT-TYPE
	  SYNTAX EkiOnOff
	  MAX-ACCESS read-write
	  STATUS current
	  DESCRIPTION
        "
        Set Software Nb 2 As Active :This
        OID, when set, loads the SW from
        bank2 into the PM. It must be followed
        by a reset.  <Help>  This controls
        selects the second SW bank as the
        active bank for the next module
        reset
        "
	  ::= { pm10001otu4CtrlswMgnt 6 }



pm10001otu4CtrlLoadSwBank1 OBJECT-TYPE
	  SYNTAX EkiOnOff
	  MAX-ACCESS read-write
	  STATUS current
	  DESCRIPTION
        "
        Set Software Nb 1 As Active :This
        OID, when set, loads the SW from
        bank1 into the PM. It must be followed
        by a reset.  <Help>  This controls
        selects the first SW bank as the
        active bank for the next module
        reset
        "
	  ::= { pm10001otu4CtrlswMgnt 5 }



pm10001otu4CtrlWarmReset OBJECT-TYPE
	  SYNTAX EkiOnOff
	  MAX-ACCESS read-write
	  STATUS current
	  DESCRIPTION
        "
        PM Warm Reset :This OID, when
         set, causes a warm reset of the
        PM. This reset is not traffic affecting,
        and the configuration of PM remains
        unchanged.  <Help>  This control
        initiates a warm reset of the module.
        "
	  ::= { pm10001otu4CtrlswMgnt 3 }



pm10001otu4CtrlColdReset OBJECT-TYPE
	  SYNTAX EkiOnOff
	  MAX-ACCESS read-write
	  STATUS current
	  DESCRIPTION
        "
        PM Cold Reset :This OID, when
         set, causes a cold reset of the
        PM. This reset is traffic affecting,
        and the configuration of PM is
         reloaded on start-up.  <Help>
          This control initiates a cold
        reset of the module.
        "
	  ::= { pm10001otu4CtrlswMgnt 2 }



--- *****************************************************
---     LEAF for the gwMgnt article
--- *****************************************************
pm10001otu4CtrlgwMgnt OBJECT IDENTIFIER ::= { pm10001otu4CtrlOther 6 }




pm10001otu4CtrlLoadGwBank4 OBJECT-TYPE
	  SYNTAX EkiOnOff
	  MAX-ACCESS read-write
	  STATUS current
	  DESCRIPTION
        "
        Set Gateware Nb 4 As Active :This
        OID, when set, loads the GW from
        bank4 (Flash) into the PM. It is
        followed by an automatic gateware
        cold reset.
        "
	  ::= { pm10001otu4CtrlgwMgnt 8 }



pm10001otu4CtrlLoadGwBank3 OBJECT-TYPE
	  SYNTAX EkiOnOff
	  MAX-ACCESS read-write
	  STATUS current
	  DESCRIPTION
        "
        Set Gateware Nb 3 As Active :This
        OID, when set, loads the GW from
        bank3 (Flash) into the PM. It is
        followed by an automatic gateware
        cold reset.  <Help>  This controls
        initiates a cold reset of the module
        and select the third GW bank as
        the active bank
        "
	  ::= { pm10001otu4CtrlgwMgnt 7 }



pm10001otu4CtrlLoadGwBank2 OBJECT-TYPE
	  SYNTAX EkiOnOff
	  MAX-ACCESS read-write
	  STATUS current
	  DESCRIPTION
        "
        Set Gateware Nb 2 As Active :This
        OID, when set, loads the GW from
        bank2 (Flash) into the PM. It is
        followed by an automatic gateware
        cold reset.
        "
	  ::= { pm10001otu4CtrlgwMgnt 6 }



pm10001otu4CtrlLoadGwBank1 OBJECT-TYPE
	  SYNTAX EkiOnOff
	  MAX-ACCESS read-write
	  STATUS current
	  DESCRIPTION
        "
        Set Gateware Nb 1 As Active :This
        OID, when set, loads the GW from
        bank1 (Flash) into the PM. It is
        followed by an automatic gateware
        cold reset.  <Help>  This controls
        initiates a cold reset of the module
        and select the first GW bank as
        the active bank
        "
	  ::= { pm10001otu4CtrlgwMgnt 5 }



pm10001otu4CtrlCurrentGwReset OBJECT-TYPE
	  SYNTAX EkiOnOff
	  MAX-ACCESS read-write
	  STATUS current
	  DESCRIPTION
        "
        Active Gateware Reset :This OID,
        when set, resets the active gateware.
        It is traffic affecting.
        "
	  ::= { pm10001otu4CtrlgwMgnt 1 }



--- *********************************************************
---     TABLE for the pm10001otu4CtrlaccessLoop articles
--- *********************************************************

pm10001otu4CtrlaccessLoopTable OBJECT-TYPE
	SYNTAX  SEQUENCE OF Pm10001otu4CtrlaccessLoopEntry
	MAX-ACCESS not-accessible
	STATUS current
	DESCRIPTION
        "
        List of pm10001otu4CtrlaccessLoop
        Article
        "
	::= { pm10001otu4CtrlClient 16 }


pm10001otu4CtrlaccessLoopEntry OBJECT-TYPE
	SYNTAX Pm10001otu4CtrlaccessLoopEntry
	MAX-ACCESS not-accessible
	STATUS current
	DESCRIPTION
        "
        Row definition for the pm10001otu4CtrlaccessLoop
        table
        "
	INDEX   { pm10001otu4CtrlaccessLoopIndex }
	::= { pm10001otu4CtrlaccessLoopTable 1 }


Pm10001otu4CtrlaccessLoopEntry ::=
	SEQUENCE {
	pm10001otu4CtrlaccessLoopIndex
		INTEGER,
	pm10001otu4CtrlaccessLoopPortn
		EkiState
	}


pm10001otu4CtrlaccessLoopIndex OBJECT-TYPE
	SYNTAX  INTEGER(0..128)
	MAX-ACCESS  read-only
	STATUS current
	DESCRIPTION
        "
        Index definition for the pm10001otu4CtrlaccessLoop
        table
        "
	::= { pm10001otu4CtrlaccessLoopEntry 1 }


pm10001otu4CtrlaccessLoopPortn OBJECT-TYPE
	SYNTAX  EkiState
	MAX-ACCESS read-write
	STATUS current
	DESCRIPTION
        "
        Client Facility Loopback :This
        OID, when set at '1' puts the client
        port in loopback, looping the received
        10 Gb/s signal on the transmit
         10 Gb/s output.  <Help> This control
        enables the Out Loopback on the
        client port, looping the client
        input signal on the client output
        "
	::= { pm10001otu4CtrlaccessLoopEntry 2 }


--- *********************************************************
---     TABLE for the pm10001otu4CtrlclientLoopToLine articles
--- *********************************************************

pm10001otu4CtrlclientLoopToLineTable OBJECT-TYPE
	SYNTAX  SEQUENCE OF Pm10001otu4CtrlclientLoopToLineEntry
	MAX-ACCESS not-accessible
	STATUS current
	DESCRIPTION
        "
        List of pm10001otu4CtrlclientLoopToLine
        Article
        "
	::= { pm10001otu4CtrlClient 17 }


pm10001otu4CtrlclientLoopToLineEntry OBJECT-TYPE
	SYNTAX Pm10001otu4CtrlclientLoopToLineEntry
	MAX-ACCESS not-accessible
	STATUS current
	DESCRIPTION
        "
        Row definition for the pm10001otu4CtrlclientLoopToLine
        table
        "
	INDEX   { pm10001otu4CtrlclientLoopToLineIndex }
	::= { pm10001otu4CtrlclientLoopToLineTable 1 }


Pm10001otu4CtrlclientLoopToLineEntry ::=
	SEQUENCE {
	pm10001otu4CtrlclientLoopToLineIndex
		INTEGER,
	pm10001otu4CtrlclientLoopToLinePortn
		EkiState
	}


pm10001otu4CtrlclientLoopToLineIndex OBJECT-TYPE
	SYNTAX  INTEGER(0..128)
	MAX-ACCESS  read-only
	STATUS current
	DESCRIPTION
        "
        Index definition for the pm10001otu4CtrlclientLoopToLine
        table
        "
	::= { pm10001otu4CtrlclientLoopToLineEntry 1 }


pm10001otu4CtrlclientLoopToLinePortn OBJECT-TYPE
	SYNTAX  EkiState
	MAX-ACCESS read-write
	STATUS current
	DESCRIPTION
        "
        Client Terminal Loopback :This
        OID, when set, puts the client
         port in loop back, looping the
        10 Gb/s output signal on the 10
        Gb/s input.<Help> This control
         enables the In Loopback on the
        client port, looping the client
        output signal on the client input
        "
	::= { pm10001otu4CtrlclientLoopToLineEntry 2 }


--- *********************************************************
---     TABLE for the pm10001otu4CtrlcsfUpIns articles
--- *********************************************************

pm10001otu4CtrlcsfUpInsTable OBJECT-TYPE
	SYNTAX  SEQUENCE OF Pm10001otu4CtrlcsfUpInsEntry
	MAX-ACCESS not-accessible
	STATUS current
	DESCRIPTION
        "
        List of pm10001otu4CtrlcsfUpIns
        Article
        "
	::= { pm10001otu4CtrlClient 21 }


pm10001otu4CtrlcsfUpInsEntry OBJECT-TYPE
	SYNTAX Pm10001otu4CtrlcsfUpInsEntry
	MAX-ACCESS not-accessible
	STATUS current
	DESCRIPTION
        "
        Row definition for the pm10001otu4CtrlcsfUpIns
        table
        "
	INDEX   { pm10001otu4CtrlcsfUpInsIndex }
	::= { pm10001otu4CtrlcsfUpInsTable 1 }


Pm10001otu4CtrlcsfUpInsEntry ::=
	SEQUENCE {
	pm10001otu4CtrlcsfUpInsIndex
		INTEGER,
	pm10001otu4CtrlcsfUpInsPortn
		EkiState
	}


pm10001otu4CtrlcsfUpInsIndex OBJECT-TYPE
	SYNTAX  INTEGER(0..128)
	MAX-ACCESS  read-only
	STATUS current
	DESCRIPTION
        "
        Index definition for the pm10001otu4CtrlcsfUpIns
        table
        "
	::= { pm10001otu4CtrlcsfUpInsEntry 1 }


pm10001otu4CtrlcsfUpInsPortn OBJECT-TYPE
	SYNTAX  EkiState
	MAX-ACCESS read-write
	STATUS current
	DESCRIPTION
        "
        Client Signal Fail Insertion :This
        OID, when set, inserts  a client
        signal fail in the upstream client
        Port.  <Help>  This control inserts
        a Client Signal Fail for the client
        port
        "
	::= { pm10001otu4CtrlcsfUpInsEntry 2 }


--- *********************************************************
---     TABLE for the pm10001otu4CtrlcaisDwIns articles
--- *********************************************************

pm10001otu4CtrlcaisDwInsTable OBJECT-TYPE
	SYNTAX  SEQUENCE OF Pm10001otu4CtrlcaisDwInsEntry
	MAX-ACCESS not-accessible
	STATUS current
	DESCRIPTION
        "
        List of pm10001otu4CtrlcaisDwIns
        Article
        "
	::= { pm10001otu4CtrlClient 22 }


pm10001otu4CtrlcaisDwInsEntry OBJECT-TYPE
	SYNTAX Pm10001otu4CtrlcaisDwInsEntry
	MAX-ACCESS not-accessible
	STATUS current
	DESCRIPTION
        "
        Row definition for the pm10001otu4CtrlcaisDwIns
        table
        "
	INDEX   { pm10001otu4CtrlcaisDwInsIndex }
	::= { pm10001otu4CtrlcaisDwInsTable 1 }


Pm10001otu4CtrlcaisDwInsEntry ::=
	SEQUENCE {
	pm10001otu4CtrlcaisDwInsIndex
		INTEGER,
	pm10001otu4CtrlcaisDwInsPortn
		EkiState
	}


pm10001otu4CtrlcaisDwInsIndex OBJECT-TYPE
	SYNTAX  INTEGER(0..128)
	MAX-ACCESS  read-only
	STATUS current
	DESCRIPTION
        "
        Index definition for the pm10001otu4CtrlcaisDwIns
        table
        "
	::= { pm10001otu4CtrlcaisDwInsEntry 1 }


pm10001otu4CtrlcaisDwInsPortn OBJECT-TYPE
	SYNTAX  EkiState
	MAX-ACCESS read-write
	STATUS current
	DESCRIPTION
        "
        Client AIS Insertion :This OID,
        when set, inserts a client AIS
         on the downstream client Port.
         <Help>  This control inserts a
        Client AIS for the client port
        "
	::= { pm10001otu4CtrlcaisDwInsEntry 2 }


--- *********************************************************
---     TABLE for the pm10001otu4CtrlcommAccessLoop articles
--- *********************************************************

pm10001otu4CtrlcommAccessLoopTable OBJECT-TYPE
	SYNTAX  SEQUENCE OF Pm10001otu4CtrlcommAccessLoopEntry
	MAX-ACCESS not-accessible
	STATUS current
	DESCRIPTION
        "
        List of pm10001otu4CtrlcommAccessLoop
        Article
        "
	::= { pm10001otu4CtrlLine 64 }


pm10001otu4CtrlcommAccessLoopEntry OBJECT-TYPE
	SYNTAX Pm10001otu4CtrlcommAccessLoopEntry
	MAX-ACCESS not-accessible
	STATUS current
	DESCRIPTION
        "
        Row definition for the pm10001otu4CtrlcommAccessLoop
        table
        "
	INDEX   { pm10001otu4CtrlcommAccessLoopIndex }
	::= { pm10001otu4CtrlcommAccessLoopTable 1 }


Pm10001otu4CtrlcommAccessLoopEntry ::=
	SEQUENCE {
	pm10001otu4CtrlcommAccessLoopIndex
		INTEGER,
	pm10001otu4CtrlcommAccessLoopPortn
		EkiState
	}


pm10001otu4CtrlcommAccessLoopIndex OBJECT-TYPE
	SYNTAX  INTEGER(0..128)
	MAX-ACCESS  read-only
	STATUS current
	DESCRIPTION
        "
        Index definition for the pm10001otu4CtrlcommAccessLoop
        table
        "
	::= { pm10001otu4CtrlcommAccessLoopEntry 1 }


pm10001otu4CtrlcommAccessLoopPortn OBJECT-TYPE
	SYNTAX  EkiState
	MAX-ACCESS read-write
	STATUS current
	DESCRIPTION
        "
        Line Terminal Loopback :This OID,
        when set, puts the module in common
        access loop back, looping the 100
        Gb/s output signal on the 100 Gb/s
        input.<Help> This control enables
        the In Loopback on the line port,
        looping the 100 Gb/s output signal
        on the 100 Gb/s input
        "
	::= { pm10001otu4CtrlcommAccessLoopEntry 2 }


--- *********************************************************
---     TABLE for the pm10001otu4CtrllineLoop articles
--- *********************************************************

pm10001otu4CtrllineLoopTable OBJECT-TYPE
	SYNTAX  SEQUENCE OF Pm10001otu4CtrllineLoopEntry
	MAX-ACCESS not-accessible
	STATUS current
	DESCRIPTION
        "
        List of pm10001otu4CtrllineLoop
        Article
        "
	::= { pm10001otu4CtrlLine 66 }


pm10001otu4CtrllineLoopEntry OBJECT-TYPE
	SYNTAX Pm10001otu4CtrllineLoopEntry
	MAX-ACCESS not-accessible
	STATUS current
	DESCRIPTION
        "
        Row definition for the pm10001otu4CtrllineLoop
        table
        "
	INDEX   { pm10001otu4CtrllineLoopIndex }
	::= { pm10001otu4CtrllineLoopTable 1 }


Pm10001otu4CtrllineLoopEntry ::=
	SEQUENCE {
	pm10001otu4CtrllineLoopIndex
		INTEGER,
	pm10001otu4CtrllineLoopPortn
		EkiState
	}


pm10001otu4CtrllineLoopIndex OBJECT-TYPE
	SYNTAX  INTEGER(0..128)
	MAX-ACCESS  read-only
	STATUS current
	DESCRIPTION
        "
        Index definition for the pm10001otu4CtrllineLoop
        table
        "
	::= { pm10001otu4CtrllineLoopEntry 1 }


pm10001otu4CtrllineLoopPortn OBJECT-TYPE
	SYNTAX  EkiState
	MAX-ACCESS read-write
	STATUS current
	DESCRIPTION
        "
        Line Facility Loopback :This OID,
        when set at '1' puts the module
        in line loopback mode, looping
         the received 100 Gb/s signal on
        the transmit 100 Gb/s output. The
        Upstream part of the module is
         timed on the 100 Gb/s recovered
        clock in that case.<Help> This
         control enables the Out Loopback
        on the line port, looping the 100
        Gb/s input signal on the 100 Gb/s
        output
        "
	::= { pm10001otu4CtrllineLoopEntry 2 }


--- *********************************************************
---     TABLE for the pm10001otu4CtrlfecDisable articles
--- *********************************************************

pm10001otu4CtrlfecDisableTable OBJECT-TYPE
	SYNTAX  SEQUENCE OF Pm10001otu4CtrlfecDisableEntry
	MAX-ACCESS not-accessible
	STATUS current
	DESCRIPTION
        "
        List of pm10001otu4CtrlfecDisable
        Article
        "
	::= { pm10001otu4CtrlLine 69 }


pm10001otu4CtrlfecDisableEntry OBJECT-TYPE
	SYNTAX Pm10001otu4CtrlfecDisableEntry
	MAX-ACCESS not-accessible
	STATUS current
	DESCRIPTION
        "
        Row definition for the pm10001otu4CtrlfecDisable
        table
        "
	INDEX   { pm10001otu4CtrlfecDisableIndex }
	::= { pm10001otu4CtrlfecDisableTable 1 }


Pm10001otu4CtrlfecDisableEntry ::=
	SEQUENCE {
	pm10001otu4CtrlfecDisableIndex
		INTEGER,
	pm10001otu4CtrlfecDisablePortn
		EkiState
	}


pm10001otu4CtrlfecDisableIndex OBJECT-TYPE
	SYNTAX  INTEGER(0..128)
	MAX-ACCESS  read-only
	STATUS current
	DESCRIPTION
        "
        Index definition for the pm10001otu4CtrlfecDisable
        table
        "
	::= { pm10001otu4CtrlfecDisableEntry 1 }


pm10001otu4CtrlfecDisablePortn OBJECT-TYPE
	SYNTAX  EkiState
	MAX-ACCESS read-write
	STATUS current
	DESCRIPTION
        "
        Forward Error Correction Inhibition
        :This OID, when set, inhibits the
        Forward Error Correction feature
        on the line input  <Help>  This
        control enables/disables the Forward
        Error Correction on the line interface
        "
	::= { pm10001otu4CtrlfecDisableEntry 2 }


--- *****************************************************
---     LEAF for the ledTest article
--- *****************************************************
pm10001otu4CtrlledTest OBJECT IDENTIFIER ::= { pm10001otu4CtrlOther 192 }




pm10001otu4CtrlLedOff OBJECT-TYPE
	  SYNTAX EkiOnOff
	  MAX-ACCESS read-write
	  STATUS current
	  DESCRIPTION
        "
        Leds Off :This OID switches off
        all the Leds as a test feature.
         <Help>  This control initiates
        a test leds turning all the LEDs
        to OFF
        "
	  ::= { pm10001otu4CtrlledTest 3 }



pm10001otu4CtrlRedLed OBJECT-TYPE
	  SYNTAX EkiOnOff
	  MAX-ACCESS read-write
	  STATUS current
	  DESCRIPTION
        "
        Red Leds Test :This OID switches
        on all the red Leds as a test feature.
         <Help>  This control initiates
        a test leds turning all the LEDs
        to red
        "
	  ::= { pm10001otu4CtrlledTest 2 }



pm10001otu4CtrlGreenLed OBJECT-TYPE
	  SYNTAX EkiOnOff
	  MAX-ACCESS read-write
	  STATUS current
	  DESCRIPTION
        "
        Green Leds Test :This OID switches
        on all the green Leds as a test
        feature.  <Help>  This control
         initiates a test leds turning
         all the LEDs to green
        "
	  ::= { pm10001otu4CtrlledTest 1 }



--- *****************************************************
---     LEAF for the initSwitchMarvell article
--- *****************************************************
pm10001otu4CtrlinitSwitchMarvell OBJECT IDENTIFIER ::= { pm10001otu4CtrlOther 201 }




pm10001otu4CtrlInitSwitchMarvell OBJECT-TYPE
	  SYNTAX EkiOnOff
	  MAX-ACCESS read-write
	  STATUS current
	  DESCRIPTION
        "
        Switch Initialization :This OID
        operates an initialization of the
        switch managed through the module
         <Help>  This control activates
        an initialization of the switch
        managed through the module
        "
	  ::= { pm10001otu4CtrlinitSwitchMarvell 1 }



--- *********************************************************
---     TABLE for the pm10001otu4CtrlmsaLineLoop articles
--- *********************************************************

pm10001otu4CtrlmsaLineLoopTable OBJECT-TYPE
	SYNTAX  SEQUENCE OF Pm10001otu4CtrlmsaLineLoopEntry
	MAX-ACCESS not-accessible
	STATUS current
	DESCRIPTION
        "
        List of pm10001otu4CtrlmsaLineLoop
        Article
        "
	::= { pm10001otu4CtrlLine 209 }


pm10001otu4CtrlmsaLineLoopEntry OBJECT-TYPE
	SYNTAX Pm10001otu4CtrlmsaLineLoopEntry
	MAX-ACCESS not-accessible
	STATUS current
	DESCRIPTION
        "
        Row definition for the pm10001otu4CtrlmsaLineLoop
        table
        "
	INDEX   { pm10001otu4CtrlmsaLineLoopIndex }
	::= { pm10001otu4CtrlmsaLineLoopTable 1 }


Pm10001otu4CtrlmsaLineLoopEntry ::=
	SEQUENCE {
	pm10001otu4CtrlmsaLineLoopIndex
		INTEGER,
	pm10001otu4CtrlmsaLineLoopPortn
		EkiState
	}


pm10001otu4CtrlmsaLineLoopIndex OBJECT-TYPE
	SYNTAX  INTEGER(0..128)
	MAX-ACCESS  read-only
	STATUS current
	DESCRIPTION
        "
        Index definition for the pm10001otu4CtrlmsaLineLoop
        table
        "
	::= { pm10001otu4CtrlmsaLineLoopEntry 1 }


pm10001otu4CtrlmsaLineLoopPortn OBJECT-TYPE
	SYNTAX  EkiState
	MAX-ACCESS read-write
	STATUS current
	DESCRIPTION
        "
        MSA Line Loop :This OID operates
        a line loopback on the MSA Line
         <Help>  This control defines the
        line loop back of the line transceiver
        "
	::= { pm10001otu4CtrlmsaLineLoopEntry 2 }


--- *********************************************************
---     TABLE for the pm10001otu4CtrlmsaTxReset articles
--- *********************************************************

pm10001otu4CtrlmsaTxResetTable OBJECT-TYPE
	SYNTAX  SEQUENCE OF Pm10001otu4CtrlmsaTxResetEntry
	MAX-ACCESS not-accessible
	STATUS current
	DESCRIPTION
        "
        List of pm10001otu4CtrlmsaTxReset
        Article
        "
	::= { pm10001otu4CtrlLine 210 }


pm10001otu4CtrlmsaTxResetEntry OBJECT-TYPE
	SYNTAX Pm10001otu4CtrlmsaTxResetEntry
	MAX-ACCESS not-accessible
	STATUS current
	DESCRIPTION
        "
        Row definition for the pm10001otu4CtrlmsaTxReset
        table
        "
	INDEX   { pm10001otu4CtrlmsaTxResetIndex }
	::= { pm10001otu4CtrlmsaTxResetTable 1 }


Pm10001otu4CtrlmsaTxResetEntry ::=
	SEQUENCE {
	pm10001otu4CtrlmsaTxResetIndex
		INTEGER,
	pm10001otu4CtrlmsaTxResetPortn
		EkiState
	}


pm10001otu4CtrlmsaTxResetIndex OBJECT-TYPE
	SYNTAX  INTEGER(0..128)
	MAX-ACCESS  read-only
	STATUS current
	DESCRIPTION
        "
        Index definition for the pm10001otu4CtrlmsaTxReset
        table
        "
	::= { pm10001otu4CtrlmsaTxResetEntry 1 }


pm10001otu4CtrlmsaTxResetPortn OBJECT-TYPE
	SYNTAX  EkiState
	MAX-ACCESS read-write
	STATUS current
	DESCRIPTION
        "
        Line MSA TX Reset :This OID resets
        the TX portion of the MSA line
         module  <Help > This control
         initiates a reset of the transmitting
        side
        "
	::= { pm10001otu4CtrlmsaTxResetEntry 2 }


--- *********************************************************
---     TABLE for the pm10001otu4CtrlmsaRxReset articles
--- *********************************************************

pm10001otu4CtrlmsaRxResetTable OBJECT-TYPE
	SYNTAX  SEQUENCE OF Pm10001otu4CtrlmsaRxResetEntry
	MAX-ACCESS not-accessible
	STATUS current
	DESCRIPTION
        "
        List of pm10001otu4CtrlmsaRxReset
        Article
        "
	::= { pm10001otu4CtrlLine 211 }


pm10001otu4CtrlmsaRxResetEntry OBJECT-TYPE
	SYNTAX Pm10001otu4CtrlmsaRxResetEntry
	MAX-ACCESS not-accessible
	STATUS current
	DESCRIPTION
        "
        Row definition for the pm10001otu4CtrlmsaRxReset
        table
        "
	INDEX   { pm10001otu4CtrlmsaRxResetIndex }
	::= { pm10001otu4CtrlmsaRxResetTable 1 }


Pm10001otu4CtrlmsaRxResetEntry ::=
	SEQUENCE {
	pm10001otu4CtrlmsaRxResetIndex
		INTEGER,
	pm10001otu4CtrlmsaRxResetPortn
		EkiState
	}


pm10001otu4CtrlmsaRxResetIndex OBJECT-TYPE
	SYNTAX  INTEGER(0..128)
	MAX-ACCESS  read-only
	STATUS current
	DESCRIPTION
        "
        Index definition for the pm10001otu4CtrlmsaRxReset
        table
        "
	::= { pm10001otu4CtrlmsaRxResetEntry 1 }


pm10001otu4CtrlmsaRxResetPortn OBJECT-TYPE
	SYNTAX  EkiState
	MAX-ACCESS read-write
	STATUS current
	DESCRIPTION
        "
        Line MSA RX Reset :This OID resets
        the RX portion of the MSA line
         module  <Help > This control
         initiates a reset of the receiving
        side
        "
	::= { pm10001otu4CtrlmsaRxResetEntry 2 }


--- *********************************************************
---     TABLE for the pm10001otu4CtrlmsaShutdown articles
--- *********************************************************

pm10001otu4CtrlmsaShutdownTable OBJECT-TYPE
	SYNTAX  SEQUENCE OF Pm10001otu4CtrlmsaShutdownEntry
	MAX-ACCESS not-accessible
	STATUS current
	DESCRIPTION
        "
        List of pm10001otu4CtrlmsaShutdown
        Article
        "
	::= { pm10001otu4CtrlLine 212 }


pm10001otu4CtrlmsaShutdownEntry OBJECT-TYPE
	SYNTAX Pm10001otu4CtrlmsaShutdownEntry
	MAX-ACCESS not-accessible
	STATUS current
	DESCRIPTION
        "
        Row definition for the pm10001otu4CtrlmsaShutdown
        table
        "
	INDEX   { pm10001otu4CtrlmsaShutdownIndex }
	::= { pm10001otu4CtrlmsaShutdownTable 1 }


Pm10001otu4CtrlmsaShutdownEntry ::=
	SEQUENCE {
	pm10001otu4CtrlmsaShutdownIndex
		INTEGER,
	pm10001otu4CtrlmsaShutdownPortn
		EkiState
	}


pm10001otu4CtrlmsaShutdownIndex OBJECT-TYPE
	SYNTAX  INTEGER(0..128)
	MAX-ACCESS  read-only
	STATUS current
	DESCRIPTION
        "
        Index definition for the pm10001otu4CtrlmsaShutdown
        table
        "
	::= { pm10001otu4CtrlmsaShutdownEntry 1 }


pm10001otu4CtrlmsaShutdownPortn OBJECT-TYPE
	SYNTAX  EkiState
	MAX-ACCESS read-write
	STATUS current
	DESCRIPTION
        "
        Line MSA Shutdown :This OID enters
        a process to shutdown the MSA line
        module  <Help > This control  initiates
        a shutdown of the module
        "
	::= { pm10001otu4CtrlmsaShutdownEntry 2 }


--- *****************************************************
---     LEAF for the resetCount article
--- *****************************************************
pm10001otu4CtrlresetCount OBJECT IDENTIFIER ::= { pm10001otu4CtrlOther 259 }




pm10001otu4CtrlResetcount OBJECT-TYPE
	  SYNTAX EkiOnOff
	  MAX-ACCESS read-write
	  STATUS current
	  DESCRIPTION
        "
        Module Count Global Reset :This
        OID resets all the errors counters
        on the module  <Help > This control
         initiates a reset of the errors
        counters on the module
        "
	  ::= { pm10001otu4CtrlresetCount 1 }



--- *****************************************************
---     LEAF for the resetRmon article
--- *****************************************************
pm10001otu4CtrlresetRmon OBJECT IDENTIFIER ::= { pm10001otu4CtrlOther 260 }




pm10001otu4CtrlResetrmon OBJECT-TYPE
	  SYNTAX EkiOnOff
	  MAX-ACCESS read-write
	  STATUS current
	  DESCRIPTION
        "
        Module Rmon Global Reset :This
        OID resets all the Rmon counters
        on the module  <Help > This control
         initiates a reset of the Rmon
         counters on the module
        "
	  ::= { pm10001otu4CtrlresetRmon 1 }



--- *****************************************************
---     LEAF for the resetMeasurements article
--- *****************************************************
pm10001otu4CtrlresetMeasurements OBJECT IDENTIFIER ::= { pm10001otu4CtrlOther 261 }




pm10001otu4CtrlResetmeasurements OBJECT-TYPE
	  SYNTAX EkiOnOff
	  MAX-ACCESS read-write
	  STATUS current
	  DESCRIPTION
        "
        Management Meas Global Reset :This
        OID resets some measurements on
        the management  <Help > This control
         initiates a reset of some measurements
        on the management
        "
	  ::= { pm10001otu4CtrlresetMeasurements 1 }



--- *********************************************************
---     TABLE for the pm10001otu4CtrlclientResetAllCount articles
--- *********************************************************

pm10001otu4CtrlclientResetAllCountTable OBJECT-TYPE
	SYNTAX  SEQUENCE OF Pm10001otu4CtrlclientResetAllCountEntry
	MAX-ACCESS not-accessible
	STATUS current
	DESCRIPTION
        "
        List of pm10001otu4CtrlclientResetAllCount
        Article
        "
	::= { pm10001otu4CtrlClient 262 }


pm10001otu4CtrlclientResetAllCountEntry OBJECT-TYPE
	SYNTAX Pm10001otu4CtrlclientResetAllCountEntry
	MAX-ACCESS not-accessible
	STATUS current
	DESCRIPTION
        "
        Row definition for the pm10001otu4CtrlclientResetAllCount
        table
        "
	INDEX   { pm10001otu4CtrlclientResetAllCountIndex }
	::= { pm10001otu4CtrlclientResetAllCountTable 1 }


Pm10001otu4CtrlclientResetAllCountEntry ::=
	SEQUENCE {
	pm10001otu4CtrlclientResetAllCountIndex
		INTEGER,
	pm10001otu4CtrlclientResetAllCountsPortn
		EkiState
	}


pm10001otu4CtrlclientResetAllCountIndex OBJECT-TYPE
	SYNTAX  INTEGER(0..128)
	MAX-ACCESS  read-only
	STATUS current
	DESCRIPTION
        "
        Index definition for the pm10001otu4CtrlclientResetAllCount
        table
        "
	::= { pm10001otu4CtrlclientResetAllCountEntry 1 }


pm10001otu4CtrlclientResetAllCountsPortn OBJECT-TYPE
	SYNTAX  EkiState
	MAX-ACCESS read-write
	STATUS current
	DESCRIPTION
        "
        Client Counters Reset :This OID
        resets every counter on the client
        port  <Help>   This control operates
        a reset on the statistics current
        ,previous and history client port
        counters
        "
	::= { pm10001otu4CtrlclientResetAllCountEntry 2 }


--- *********************************************************
---     TABLE for the pm10001otu4CtrllineResetAllCount articles
--- *********************************************************

pm10001otu4CtrllineResetAllCountTable OBJECT-TYPE
	SYNTAX  SEQUENCE OF Pm10001otu4CtrllineResetAllCountEntry
	MAX-ACCESS not-accessible
	STATUS current
	DESCRIPTION
        "
        List of pm10001otu4CtrllineResetAllCount
        Article
        "
	::= { pm10001otu4CtrlLine 263 }


pm10001otu4CtrllineResetAllCountEntry OBJECT-TYPE
	SYNTAX Pm10001otu4CtrllineResetAllCountEntry
	MAX-ACCESS not-accessible
	STATUS current
	DESCRIPTION
        "
        Row definition for the pm10001otu4CtrllineResetAllCount
        table
        "
	INDEX   { pm10001otu4CtrllineResetAllCountIndex }
	::= { pm10001otu4CtrllineResetAllCountTable 1 }


Pm10001otu4CtrllineResetAllCountEntry ::=
	SEQUENCE {
	pm10001otu4CtrllineResetAllCountIndex
		INTEGER,
	pm10001otu4CtrllineResetAllCountsPortn
		EkiState
	}


pm10001otu4CtrllineResetAllCountIndex OBJECT-TYPE
	SYNTAX  INTEGER(0..128)
	MAX-ACCESS  read-only
	STATUS current
	DESCRIPTION
        "
        Index definition for the pm10001otu4CtrllineResetAllCount
        table
        "
	::= { pm10001otu4CtrllineResetAllCountEntry 1 }


pm10001otu4CtrllineResetAllCountsPortn OBJECT-TYPE
	SYNTAX  EkiState
	MAX-ACCESS read-write
	STATUS current
	DESCRIPTION
        "
        Line Counters Reset :This OID
         resets every counter on the line
        port  <Help>   This control operates
        a reset on the statistics current
        ,previous and history line port
        counters
        "
	::= { pm10001otu4CtrllineResetAllCountEntry 2 }







--- *****************************************************
--- $$$$$$$$$$$$$$$$$$$$$$$$$$$$$$$$$$$$$$$$$$$$$$$$$$$$$
---     COUNTERS
--- $$$$$$$$$$$$$$$$$$$$$$$$$$$$$$$$$$$$$$$$$$$$$$$$$$$$$
--- *****************************************************



--- *********************************************************
---     TABLE for the pm10001otu4CntclientInputErrorCounterLaneOne articles
--- *********************************************************

pm10001otu4CntclientInputErrorCounterLaneOneTable OBJECT-TYPE
	SYNTAX  SEQUENCE OF Pm10001otu4CntclientInputErrorCounterLaneOneEntry
	MAX-ACCESS not-accessible
	STATUS current
	DESCRIPTION
        "
        List of pm10001otu4CntclientInputErrorCounterLaneOne
        Article
        "
	::= { pm10001otu4CntClient 16 }


pm10001otu4CntclientInputErrorCounterLaneOneEntry OBJECT-TYPE
	SYNTAX Pm10001otu4CntclientInputErrorCounterLaneOneEntry
	MAX-ACCESS not-accessible
	STATUS current
	DESCRIPTION
        "
        Row definition for the pm10001otu4CntclientInputErrorCounterLaneOne
        table
        "
	INDEX   { pm10001otu4CntclientInputErrorCounterLaneOneIndex }
	::= { pm10001otu4CntclientInputErrorCounterLaneOneTable 1 }


Pm10001otu4CntclientInputErrorCounterLaneOneEntry ::=
	SEQUENCE {
	pm10001otu4CntclientInputErrorCounterLaneOneIndex
		INTEGER,
	pm10001otu4CntclientInputErrorCounterLaneOneValuePortn
		Counter32,
	pm10001otu4CntclientInputErrorCounterLaneOneErrorPortn
		EkiOnOff,
	pm10001otu4CntclientInputErrorCounterLaneOneOverloadPortn
		EkiOnOff
	}


pm10001otu4CntclientInputErrorCounterLaneOneIndex OBJECT-TYPE
	SYNTAX  INTEGER(0..128)
	MAX-ACCESS  read-only
	STATUS current
	DESCRIPTION
        "
        Index definition for the pm10001otu4CntclientInputErrorCounterLaneOne
        table
        "
	::= { pm10001otu4CntclientInputErrorCounterLaneOneEntry 1 }


pm10001otu4CntclientInputErrorCounterLaneOneValuePortn OBJECT-TYPE
	SYNTAX  Counter32
	MAX-ACCESS read-only
	STATUS current
	DESCRIPTION
        "
        Client_Input_Error_Counter_Lane1
        :This counter is incremented each
        time a coding violation is detected
        on the host lane of the client
         transceiver <Help> This counter
        is incremented each time a coding
        violation is detected on the host
        lane of the client transceiver
        "
	::= { pm10001otu4CntclientInputErrorCounterLaneOneEntry 2 }


pm10001otu4CntclientInputErrorCounterLaneOneErrorPortn OBJECT-TYPE
	SYNTAX  EkiOnOff
	MAX-ACCESS read-only
	STATUS current
	DESCRIPTION
        "
        Client Input Counter Error :This
        OID when set indicates the rate
        adaptation removal counter value
        is invalid on Port
        "
	::= { pm10001otu4CntclientInputErrorCounterLaneOneEntry 3 }


pm10001otu4CntclientInputErrorCounterLaneOneOverloadPortn OBJECT-TYPE
	SYNTAX  EkiOnOff
	MAX-ACCESS read-only
	STATUS current
	DESCRIPTION
        "
        Client Input Counter Overload
         :This OID when set indicates a
        rate adaptation removal counter
        overload on Port
        "
	::= { pm10001otu4CntclientInputErrorCounterLaneOneEntry 4 }


--- *********************************************************
---     TABLE for the pm10001otu4CntclientInputErrorCounterLaneTwo articles
--- *********************************************************

pm10001otu4CntclientInputErrorCounterLaneTwoTable OBJECT-TYPE
	SYNTAX  SEQUENCE OF Pm10001otu4CntclientInputErrorCounterLaneTwoEntry
	MAX-ACCESS not-accessible
	STATUS current
	DESCRIPTION
        "
        List of pm10001otu4CntclientInputErrorCounterLaneTwo
        Article
        "
	::= { pm10001otu4CntClient 32 }


pm10001otu4CntclientInputErrorCounterLaneTwoEntry OBJECT-TYPE
	SYNTAX Pm10001otu4CntclientInputErrorCounterLaneTwoEntry
	MAX-ACCESS not-accessible
	STATUS current
	DESCRIPTION
        "
        Row definition for the pm10001otu4CntclientInputErrorCounterLaneTwo
        table
        "
	INDEX   { pm10001otu4CntclientInputErrorCounterLaneTwoIndex }
	::= { pm10001otu4CntclientInputErrorCounterLaneTwoTable 1 }


Pm10001otu4CntclientInputErrorCounterLaneTwoEntry ::=
	SEQUENCE {
	pm10001otu4CntclientInputErrorCounterLaneTwoIndex
		INTEGER,
	pm10001otu4CntclientInputErrorCounterLaneTwoValuePortn
		Counter32,
	pm10001otu4CntclientInputErrorCounterLaneTwoErrorPortn
		EkiOnOff,
	pm10001otu4CntclientInputErrorCounterLaneTwoOverloadPortn
		EkiOnOff
	}


pm10001otu4CntclientInputErrorCounterLaneTwoIndex OBJECT-TYPE
	SYNTAX  INTEGER(0..128)
	MAX-ACCESS  read-only
	STATUS current
	DESCRIPTION
        "
        Index definition for the pm10001otu4CntclientInputErrorCounterLaneTwo
        table
        "
	::= { pm10001otu4CntclientInputErrorCounterLaneTwoEntry 1 }


pm10001otu4CntclientInputErrorCounterLaneTwoValuePortn OBJECT-TYPE
	SYNTAX  Counter32
	MAX-ACCESS read-only
	STATUS current
	DESCRIPTION
        "
        Client_Input_Error_Counter_Lane2
        :This counter is incremented each
        time a coding violation is detected
        on the host lane of the client
         transceiver <Help> This counter
        is incremented each time a coding
        violation is detected on the host
        lane of the client transceiver
        "
	::= { pm10001otu4CntclientInputErrorCounterLaneTwoEntry 2 }


pm10001otu4CntclientInputErrorCounterLaneTwoErrorPortn OBJECT-TYPE
	SYNTAX  EkiOnOff
	MAX-ACCESS read-only
	STATUS current
	DESCRIPTION
        "
        Client Input Counter Error :This
        OID when set indicates the client
        error counter value is invalid
         on Port
        "
	::= { pm10001otu4CntclientInputErrorCounterLaneTwoEntry 3 }


pm10001otu4CntclientInputErrorCounterLaneTwoOverloadPortn OBJECT-TYPE
	SYNTAX  EkiOnOff
	MAX-ACCESS read-only
	STATUS current
	DESCRIPTION
        "
        Client Input Counter Overload
         :This OID when set indicates a
        client input error counter overload
        on Port
        "
	::= { pm10001otu4CntclientInputErrorCounterLaneTwoEntry 4 }


--- *********************************************************
---     TABLE for the pm10001otu4CntclientInputErrorCounter articles
--- *********************************************************

pm10001otu4CntclientInputErrorCounterTable OBJECT-TYPE
	SYNTAX  SEQUENCE OF Pm10001otu4CntclientInputErrorCounterEntry
	MAX-ACCESS not-accessible
	STATUS current
	DESCRIPTION
        "
        List of pm10001otu4CntclientInputErrorCounter
        Article
        "
	::= { pm10001otu4CntClient 80 }


pm10001otu4CntclientInputErrorCounterEntry OBJECT-TYPE
	SYNTAX Pm10001otu4CntclientInputErrorCounterEntry
	MAX-ACCESS not-accessible
	STATUS current
	DESCRIPTION
        "
        Row definition for the pm10001otu4CntclientInputErrorCounter
        table
        "
	INDEX   { pm10001otu4CntclientInputErrorCounterIndex }
	::= { pm10001otu4CntclientInputErrorCounterTable 1 }


Pm10001otu4CntclientInputErrorCounterEntry ::=
	SEQUENCE {
	pm10001otu4CntclientInputErrorCounterIndex
		INTEGER,
	pm10001otu4CntclientInputErrorCounterValuePortn
		Counter32,
	pm10001otu4CntclientInputErrorCounterErrorPortn
		EkiOnOff,
	pm10001otu4CntclientInputErrorCounterOverloadPortn
		EkiOnOff
	}


pm10001otu4CntclientInputErrorCounterIndex OBJECT-TYPE
	SYNTAX  INTEGER(0..128)
	MAX-ACCESS  read-only
	STATUS current
	DESCRIPTION
        "
        Index definition for the pm10001otu4CntclientInputErrorCounter
        table
        "
	::= { pm10001otu4CntclientInputErrorCounterEntry 1 }


pm10001otu4CntclientInputErrorCounterValuePortn OBJECT-TYPE
	SYNTAX  Counter32
	MAX-ACCESS read-only
	STATUS current
	DESCRIPTION
        "
        Client Input Errors :This counter
        is increased each time a 10b/8b
        running disparity error is detected
        on the Client input stream  <Help>
         This counter gives the number
         of 10b/8b running disparity errors
        on the client port
        "
	::= { pm10001otu4CntclientInputErrorCounterEntry 2 }


pm10001otu4CntclientInputErrorCounterErrorPortn OBJECT-TYPE
	SYNTAX  EkiOnOff
	MAX-ACCESS read-only
	STATUS current
	DESCRIPTION
        "
        Client Counter Error :This OID
        when set indicates the client error
        counter value is invalid on Port
        "
	::= { pm10001otu4CntclientInputErrorCounterEntry 3 }


pm10001otu4CntclientInputErrorCounterOverloadPortn OBJECT-TYPE
	SYNTAX  EkiOnOff
	MAX-ACCESS read-only
	STATUS current
	DESCRIPTION
        "
        Client Counter Overload :This
         OID when set indicates a client
        input error counter overload on
        Port
        "
	::= { pm10001otu4CntclientInputErrorCounterEntry 4 }


--- *********************************************************
---     TABLE for the pm10001otu4CntclientCbipCounter articles
--- *********************************************************

pm10001otu4CntclientCbipCounterTable OBJECT-TYPE
	SYNTAX  SEQUENCE OF Pm10001otu4CntclientCbipCounterEntry
	MAX-ACCESS not-accessible
	STATUS current
	DESCRIPTION
        "
        List of pm10001otu4CntclientCbipCounter
        Article
        "
	::= { pm10001otu4CntClient 96 }


pm10001otu4CntclientCbipCounterEntry OBJECT-TYPE
	SYNTAX Pm10001otu4CntclientCbipCounterEntry
	MAX-ACCESS not-accessible
	STATUS current
	DESCRIPTION
        "
        Row definition for the pm10001otu4CntclientCbipCounter
        table
        "
	INDEX   { pm10001otu4CntclientCbipCounterIndex }
	::= { pm10001otu4CntclientCbipCounterTable 1 }


Pm10001otu4CntclientCbipCounterEntry ::=
	SEQUENCE {
	pm10001otu4CntclientCbipCounterIndex
		INTEGER,
	pm10001otu4CntclientCbipCounterValuePortn
		Counter32,
	pm10001otu4CntclientCbipCounterErrorPortn
		EkiOnOff,
	pm10001otu4CntclientCbipCounterOverloadPortn
		EkiOnOff
	}


pm10001otu4CntclientCbipCounterIndex OBJECT-TYPE
	SYNTAX  INTEGER(0..128)
	MAX-ACCESS  read-only
	STATUS current
	DESCRIPTION
        "
        Index definition for the pm10001otu4CntclientCbipCounter
        table
        "
	::= { pm10001otu4CntclientCbipCounterEntry 1 }


pm10001otu4CntclientCbipCounterValuePortn OBJECT-TYPE
	SYNTAX  Counter32
	MAX-ACCESS read-only
	STATUS current
	DESCRIPTION
        "
        Client Output Errors :This counter
        is incremented each time a CBIP
        parity error is detected on the
        Client output stream  <Help>  This
        counter gives the number of CBIP
        errors on the client port
        "
	::= { pm10001otu4CntclientCbipCounterEntry 2 }


pm10001otu4CntclientCbipCounterErrorPortn OBJECT-TYPE
	SYNTAX  EkiOnOff
	MAX-ACCESS read-only
	STATUS current
	DESCRIPTION
        "
        Client Counter Error :This OID
        when set indicates the CBIP error
        counter value is invalid on Port
        "
	::= { pm10001otu4CntclientCbipCounterEntry 3 }


pm10001otu4CntclientCbipCounterOverloadPortn OBJECT-TYPE
	SYNTAX  EkiOnOff
	MAX-ACCESS read-only
	STATUS current
	DESCRIPTION
        "
        Client CBIP Counter Overload :This
        OID when set indicates a CBIP error
        counter overload on Port
        "
	::= { pm10001otu4CntclientCbipCounterEntry 4 }


--- *********************************************************
---     TABLE for the pm10001otu4CntlocalLineSmBip8ErrorCounter articles
--- *********************************************************

pm10001otu4CntlocalLineSmBip8ErrorCounterTable OBJECT-TYPE
	SYNTAX  SEQUENCE OF Pm10001otu4CntlocalLineSmBip8ErrorCounterEntry
	MAX-ACCESS not-accessible
	STATUS current
	DESCRIPTION
        "
        List of pm10001otu4CntlocalLineSmBip8ErrorCounter
        Article
        "
	::= { pm10001otu4CntLine 192 }


pm10001otu4CntlocalLineSmBip8ErrorCounterEntry OBJECT-TYPE
	SYNTAX Pm10001otu4CntlocalLineSmBip8ErrorCounterEntry
	MAX-ACCESS not-accessible
	STATUS current
	DESCRIPTION
        "
        Row definition for the pm10001otu4CntlocalLineSmBip8ErrorCounter
        table
        "
	INDEX   { pm10001otu4CntlocalLineSmBip8ErrorCounterIndex }
	::= { pm10001otu4CntlocalLineSmBip8ErrorCounterTable 1 }


Pm10001otu4CntlocalLineSmBip8ErrorCounterEntry ::=
	SEQUENCE {
	pm10001otu4CntlocalLineSmBip8ErrorCounterIndex
		INTEGER,
	pm10001otu4CntlocalLineSmBip8ErrorCounterValuePortn
		Counter64,
	pm10001otu4CntlocalLineSmBip8ErrorCounterErrorPortn
		EkiOnOff,
	pm10001otu4CntlocalLineSmBip8ErrorCounterOverloadPortn
		EkiOnOff
	}


pm10001otu4CntlocalLineSmBip8ErrorCounterIndex OBJECT-TYPE
	SYNTAX  INTEGER(0..128)
	MAX-ACCESS  read-only
	STATUS current
	DESCRIPTION
        "
        Index definition for the pm10001otu4CntlocalLineSmBip8ErrorCounter
        table
        "
	::= { pm10001otu4CntlocalLineSmBip8ErrorCounterEntry 1 }


pm10001otu4CntlocalLineSmBip8ErrorCounterValuePortn OBJECT-TYPE
	SYNTAX  Counter64
	MAX-ACCESS read-only
	STATUS current
	DESCRIPTION
        "
        Line Input SM-BIP8 Errors :This
        OID gives the current Bit Error
        Rate (residual SM-BIP8 error) after
        FEC   <Help> This counter gives
        the current Bit Error Rate (residual
        SM-BIP8 error) after FEC
        "
	::= { pm10001otu4CntlocalLineSmBip8ErrorCounterEntry 2 }


pm10001otu4CntlocalLineSmBip8ErrorCounterErrorPortn OBJECT-TYPE
	SYNTAX  EkiOnOff
	MAX-ACCESS read-only
	STATUS current
	DESCRIPTION
        "
        Line Counter Error :This OID when
        set indicates the B1 error counter
        value is invalid on Port
        "
	::= { pm10001otu4CntlocalLineSmBip8ErrorCounterEntry 3 }


pm10001otu4CntlocalLineSmBip8ErrorCounterOverloadPortn OBJECT-TYPE
	SYNTAX  EkiOnOff
	MAX-ACCESS read-only
	STATUS current
	DESCRIPTION
        "
        Line Counter Overload :This OID
        when set indicates a B1 error counter
        overload on Port
        "
	::= { pm10001otu4CntlocalLineSmBip8ErrorCounterEntry 4 }


--- *********************************************************
---     TABLE for the pm10001otu4CntlocalLineFecCorrectedErrorsCounter articles
--- *********************************************************

pm10001otu4CntlocalLineFecCorrectedErrorsCounterTable OBJECT-TYPE
	SYNTAX  SEQUENCE OF Pm10001otu4CntlocalLineFecCorrectedErrorsCounterEntry
	MAX-ACCESS not-accessible
	STATUS current
	DESCRIPTION
        "
        List of pm10001otu4CntlocalLineFecCorrectedErrorsCounter
        Article
        "
	::= { pm10001otu4CntLine 193 }


pm10001otu4CntlocalLineFecCorrectedErrorsCounterEntry OBJECT-TYPE
	SYNTAX Pm10001otu4CntlocalLineFecCorrectedErrorsCounterEntry
	MAX-ACCESS not-accessible
	STATUS current
	DESCRIPTION
        "
        Row definition for the pm10001otu4CntlocalLineFecCorrectedErrorsCounter
        table
        "
	INDEX   { pm10001otu4CntlocalLineFecCorrectedErrorsCounterIndex }
	::= { pm10001otu4CntlocalLineFecCorrectedErrorsCounterTable 1 }


Pm10001otu4CntlocalLineFecCorrectedErrorsCounterEntry ::=
	SEQUENCE {
	pm10001otu4CntlocalLineFecCorrectedErrorsCounterIndex
		INTEGER,
	pm10001otu4CntlocalLineFecCorrectedErrorsCounterValuePortn
		Counter64,
	pm10001otu4CntlocalLineFecCorrectedErrorsCounterErrorPortn
		EkiOnOff,
	pm10001otu4CntlocalLineFecCorrectedErrorsCounterOverloadPortn
		EkiOnOff
	}


pm10001otu4CntlocalLineFecCorrectedErrorsCounterIndex OBJECT-TYPE
	SYNTAX  INTEGER(0..128)
	MAX-ACCESS  read-only
	STATUS current
	DESCRIPTION
        "
        Index definition for the pm10001otu4CntlocalLineFecCorrectedErrorsCounter
        table
        "
	::= { pm10001otu4CntlocalLineFecCorrectedErrorsCounterEntry 1 }


pm10001otu4CntlocalLineFecCorrectedErrorsCounterValuePortn OBJECT-TYPE
	SYNTAX  Counter64
	MAX-ACCESS read-only
	STATUS current
	DESCRIPTION
        "
        Line Input HD FEC Corrected Errors
        :This OID gives the current Bit
        Error Rate before the Hard Decision
        FEC  <Help> This counter gives
         the current Bit Error Rate before
        the Hard Decision FEC
        "
	::= { pm10001otu4CntlocalLineFecCorrectedErrorsCounterEntry 2 }


pm10001otu4CntlocalLineFecCorrectedErrorsCounterErrorPortn OBJECT-TYPE
	SYNTAX  EkiOnOff
	MAX-ACCESS read-only
	STATUS current
	DESCRIPTION
        "
        FEC Counter Error :This bit when
        set indicates the FEC corrected
        errors counter value is invalid
        on Line
        "
	::= { pm10001otu4CntlocalLineFecCorrectedErrorsCounterEntry 3 }


pm10001otu4CntlocalLineFecCorrectedErrorsCounterOverloadPortn OBJECT-TYPE
	SYNTAX  EkiOnOff
	MAX-ACCESS read-only
	STATUS current
	DESCRIPTION
        "
        FEC Counter Overload :This bit
        when set indicates a FEC corrected
        errors counter overload on Line
        "
	::= { pm10001otu4CntlocalLineFecCorrectedErrorsCounterEntry 4 }


--- *********************************************************
---     TABLE for the pm10001otu4CntremoteLineSmBip8ErrorCounter articles
--- *********************************************************

pm10001otu4CntremoteLineSmBip8ErrorCounterTable OBJECT-TYPE
	SYNTAX  SEQUENCE OF Pm10001otu4CntremoteLineSmBip8ErrorCounterEntry
	MAX-ACCESS not-accessible
	STATUS current
	DESCRIPTION
        "
        List of pm10001otu4CntremoteLineSmBip8ErrorCounter
        Article
        "
	::= { pm10001otu4CntLine 194 }


pm10001otu4CntremoteLineSmBip8ErrorCounterEntry OBJECT-TYPE
	SYNTAX Pm10001otu4CntremoteLineSmBip8ErrorCounterEntry
	MAX-ACCESS not-accessible
	STATUS current
	DESCRIPTION
        "
        Row definition for the pm10001otu4CntremoteLineSmBip8ErrorCounter
        table
        "
	INDEX   { pm10001otu4CntremoteLineSmBip8ErrorCounterIndex }
	::= { pm10001otu4CntremoteLineSmBip8ErrorCounterTable 1 }


Pm10001otu4CntremoteLineSmBip8ErrorCounterEntry ::=
	SEQUENCE {
	pm10001otu4CntremoteLineSmBip8ErrorCounterIndex
		INTEGER,
	pm10001otu4CntremoteLineSmBip8ErrorCounterValuePortn
		Counter64,
	pm10001otu4CntremoteLineSmBip8ErrorCounterErrorPortn
		EkiOnOff,
	pm10001otu4CntremoteLineSmBip8ErrorCounterOverloadPortn
		EkiOnOff
	}


pm10001otu4CntremoteLineSmBip8ErrorCounterIndex OBJECT-TYPE
	SYNTAX  INTEGER(0..128)
	MAX-ACCESS  read-only
	STATUS current
	DESCRIPTION
        "
        Index definition for the pm10001otu4CntremoteLineSmBip8ErrorCounter
        table
        "
	::= { pm10001otu4CntremoteLineSmBip8ErrorCounterEntry 1 }


pm10001otu4CntremoteLineSmBip8ErrorCounterValuePortn OBJECT-TYPE
	SYNTAX  Counter64
	MAX-ACCESS read-only
	STATUS current
	DESCRIPTION
        "
        Remote SM BIP8 :This OID gives
        the current Bit Error Rate (residual
        SM-BIP8 error) after FEC on the
        remote side  <Help> This counter
        gives the current Bit Error Rate
        (residual SM-BIP8 error) after
         FEC on the remote side
        "
	::= { pm10001otu4CntremoteLineSmBip8ErrorCounterEntry 2 }


pm10001otu4CntremoteLineSmBip8ErrorCounterErrorPortn OBJECT-TYPE
	SYNTAX  EkiOnOff
	MAX-ACCESS read-only
	STATUS current
	DESCRIPTION
        "
        Remote Counter Error :
        "
	::= { pm10001otu4CntremoteLineSmBip8ErrorCounterEntry 3 }


pm10001otu4CntremoteLineSmBip8ErrorCounterOverloadPortn OBJECT-TYPE
	SYNTAX  EkiOnOff
	MAX-ACCESS read-only
	STATUS current
	DESCRIPTION
        "
        Remote Counter Overload :
        "
	::= { pm10001otu4CntremoteLineSmBip8ErrorCounterEntry 4 }


--- *********************************************************
---     TABLE for the pm10001otu4CntlineDfrmTimCnt articles
--- *********************************************************

pm10001otu4CntlineDfrmTimCntTable OBJECT-TYPE
	SYNTAX  SEQUENCE OF Pm10001otu4CntlineDfrmTimCntEntry
	MAX-ACCESS not-accessible
	STATUS current
	DESCRIPTION
        "
        List of pm10001otu4CntlineDfrmTimCnt
        Article
        "
	::= { pm10001otu4CntLine 195 }


pm10001otu4CntlineDfrmTimCntEntry OBJECT-TYPE
	SYNTAX Pm10001otu4CntlineDfrmTimCntEntry
	MAX-ACCESS not-accessible
	STATUS current
	DESCRIPTION
        "
        Row definition for the pm10001otu4CntlineDfrmTimCnt
        table
        "
	INDEX   { pm10001otu4CntlineDfrmTimCntIndex }
	::= { pm10001otu4CntlineDfrmTimCntTable 1 }


Pm10001otu4CntlineDfrmTimCntEntry ::=
	SEQUENCE {
	pm10001otu4CntlineDfrmTimCntIndex
		INTEGER,
	pm10001otu4CntlineDfrmTimCntValuePortn
		Counter64,
	pm10001otu4CntlineDfrmTimCntErrorPortn
		EkiOnOff,
	pm10001otu4CntlineDfrmTimCntOverloadPortn
		EkiOnOff
	}


pm10001otu4CntlineDfrmTimCntIndex OBJECT-TYPE
	SYNTAX  INTEGER(0..128)
	MAX-ACCESS  read-only
	STATUS current
	DESCRIPTION
        "
        Index definition for the pm10001otu4CntlineDfrmTimCnt
        table
        "
	::= { pm10001otu4CntlineDfrmTimCntEntry 1 }


pm10001otu4CntlineDfrmTimCntValuePortn OBJECT-TYPE
	SYNTAX  Counter64
	MAX-ACCESS read-only
	STATUS current
	DESCRIPTION
        "
        Line Timer Counter :
        "
	::= { pm10001otu4CntlineDfrmTimCntEntry 2 }


pm10001otu4CntlineDfrmTimCntErrorPortn OBJECT-TYPE
	SYNTAX  EkiOnOff
	MAX-ACCESS read-only
	STATUS current
	DESCRIPTION
        "
        Line Counter Error :This OID when
        set indicates the deframer timer
        counter value is invalid on Port
        "
	::= { pm10001otu4CntlineDfrmTimCntEntry 3 }


pm10001otu4CntlineDfrmTimCntOverloadPortn OBJECT-TYPE
	SYNTAX  EkiOnOff
	MAX-ACCESS read-only
	STATUS current
	DESCRIPTION
        "
        Line Counter Overload :This OID
        when set indicates a deframer timer
        counter overload on Port
        "
	::= { pm10001otu4CntlineDfrmTimCntEntry 4 }


--- *********************************************************
---     TABLE for the pm10001otu4CntlocalLineTrscvFecCorrectedErrorCounter articles
--- *********************************************************

pm10001otu4CntlocalLineTrscvFecCorrectedErrorCounterTable OBJECT-TYPE
	SYNTAX  SEQUENCE OF Pm10001otu4CntlocalLineTrscvFecCorrectedErrorCounterEntry
	MAX-ACCESS not-accessible
	STATUS current
	DESCRIPTION
        "
        List of pm10001otu4CntlocalLineTrscvFecCorrectedErrorCounter
        Article
        "
	::= { pm10001otu4CntLine 196 }


pm10001otu4CntlocalLineTrscvFecCorrectedErrorCounterEntry OBJECT-TYPE
	SYNTAX Pm10001otu4CntlocalLineTrscvFecCorrectedErrorCounterEntry
	MAX-ACCESS not-accessible
	STATUS current
	DESCRIPTION
        "
        Row definition for the pm10001otu4CntlocalLineTrscvFecCorrectedErrorCounter
        table
        "
	INDEX   { pm10001otu4CntlocalLineTrscvFecCorrectedErrorCounterIndex }
	::= { pm10001otu4CntlocalLineTrscvFecCorrectedErrorCounterTable 1 }


Pm10001otu4CntlocalLineTrscvFecCorrectedErrorCounterEntry ::=
	SEQUENCE {
	pm10001otu4CntlocalLineTrscvFecCorrectedErrorCounterIndex
		INTEGER,
	pm10001otu4CntlocalLineTrscvFecCorrectedErrorCounterValuePortn
		Counter64,
	pm10001otu4CntlocalLineTrscvFecCorrectedErrorCounterErrorPortn
		EkiOnOff,
	pm10001otu4CntlocalLineTrscvFecCorrectedErrorCounterOverloadPortn
		EkiOnOff
	}


pm10001otu4CntlocalLineTrscvFecCorrectedErrorCounterIndex OBJECT-TYPE
	SYNTAX  INTEGER(0..128)
	MAX-ACCESS  read-only
	STATUS current
	DESCRIPTION
        "
        Index definition for the pm10001otu4CntlocalLineTrscvFecCorrectedErrorCounter
        table
        "
	::= { pm10001otu4CntlocalLineTrscvFecCorrectedErrorCounterEntry 1 }


pm10001otu4CntlocalLineTrscvFecCorrectedErrorCounterValuePortn OBJECT-TYPE
	SYNTAX  Counter64
	MAX-ACCESS read-only
	STATUS current
	DESCRIPTION
        "
        Line Input SD FEC Corrected Errors
        :This OID gives the current Bit
        Error Rate before the Soft Decision
        FEC  <Help> This counter gives
         the current Bit Error Rate before
        the Soft Decision FEC
        "
	::= { pm10001otu4CntlocalLineTrscvFecCorrectedErrorCounterEntry 2 }


pm10001otu4CntlocalLineTrscvFecCorrectedErrorCounterErrorPortn OBJECT-TYPE
	SYNTAX  EkiOnOff
	MAX-ACCESS read-only
	STATUS current
	DESCRIPTION
        "
        Line Counter Error :This OID when
        set indicates the deframer timer
        counter value is invalid on Port
        "
	::= { pm10001otu4CntlocalLineTrscvFecCorrectedErrorCounterEntry 3 }


pm10001otu4CntlocalLineTrscvFecCorrectedErrorCounterOverloadPortn OBJECT-TYPE
	SYNTAX  EkiOnOff
	MAX-ACCESS read-only
	STATUS current
	DESCRIPTION
        "
        Line Counter Overload :This OID
        when set indicates a deframer timer
        counter overload on Port
        "
	::= { pm10001otu4CntlocalLineTrscvFecCorrectedErrorCounterEntry 4 }


--- *********************************************************
---     TABLE for the pm10001otu4CntlocalLineTrscvFecUncorrectedErrorCounter articles
--- *********************************************************

pm10001otu4CntlocalLineTrscvFecUncorrectedErrorCounterTable OBJECT-TYPE
	SYNTAX  SEQUENCE OF Pm10001otu4CntlocalLineTrscvFecUncorrectedErrorCounterEntry
	MAX-ACCESS not-accessible
	STATUS current
	DESCRIPTION
        "
        List of pm10001otu4CntlocalLineTrscvFecUncorrectedErrorCounter
        Article
        "
	::= { pm10001otu4CntLine 197 }


pm10001otu4CntlocalLineTrscvFecUncorrectedErrorCounterEntry OBJECT-TYPE
	SYNTAX Pm10001otu4CntlocalLineTrscvFecUncorrectedErrorCounterEntry
	MAX-ACCESS not-accessible
	STATUS current
	DESCRIPTION
        "
        Row definition for the pm10001otu4CntlocalLineTrscvFecUncorrectedErrorCounter
        table
        "
	INDEX   { pm10001otu4CntlocalLineTrscvFecUncorrectedErrorCounterIndex }
	::= { pm10001otu4CntlocalLineTrscvFecUncorrectedErrorCounterTable 1 }


Pm10001otu4CntlocalLineTrscvFecUncorrectedErrorCounterEntry ::=
	SEQUENCE {
	pm10001otu4CntlocalLineTrscvFecUncorrectedErrorCounterIndex
		INTEGER,
	pm10001otu4CntlocalLineTrscvFecUncorrectedErrorCounterValuePortn
		Counter64,
	pm10001otu4CntlocalLineTrscvFecUncorrectedErrorCounterErrorPortn
		EkiOnOff,
	pm10001otu4CntlocalLineTrscvFecUncorrectedErrorCounterOverloadPortn
		EkiOnOff
	}


pm10001otu4CntlocalLineTrscvFecUncorrectedErrorCounterIndex OBJECT-TYPE
	SYNTAX  INTEGER(0..128)
	MAX-ACCESS  read-only
	STATUS current
	DESCRIPTION
        "
        Index definition for the pm10001otu4CntlocalLineTrscvFecUncorrectedErrorCounter
        table
        "
	::= { pm10001otu4CntlocalLineTrscvFecUncorrectedErrorCounterEntry 1 }


pm10001otu4CntlocalLineTrscvFecUncorrectedErrorCounterValuePortn OBJECT-TYPE
	SYNTAX  Counter64
	MAX-ACCESS read-only
	STATUS current
	DESCRIPTION
        "
        SD Uncorrected :This OID gives
        the current Bit Error Rate after
        the Soft Decision FEC (residual)
         <Help> This counter gives the
         current Bit Error Rate after the
        Soft Decision FEC (residual)
        "
	::= { pm10001otu4CntlocalLineTrscvFecUncorrectedErrorCounterEntry 2 }


pm10001otu4CntlocalLineTrscvFecUncorrectedErrorCounterErrorPortn OBJECT-TYPE
	SYNTAX  EkiOnOff
	MAX-ACCESS read-only
	STATUS current
	DESCRIPTION
        "
        Line Counter Error :This OID when
        set indicates the deframer timer
        counter value is invalid on Port
        "
	::= { pm10001otu4CntlocalLineTrscvFecUncorrectedErrorCounterEntry 3 }


pm10001otu4CntlocalLineTrscvFecUncorrectedErrorCounterOverloadPortn OBJECT-TYPE
	SYNTAX  EkiOnOff
	MAX-ACCESS read-only
	STATUS current
	DESCRIPTION
        "
        Line Counter Overload :This OID
        when set indicates a deframer timer
        counter overload on Port
        "
	::= { pm10001otu4CntlocalLineTrscvFecUncorrectedErrorCounterEntry 4 }







--- *****************************************************
--- $$$$$$$$$$$$$$$$$$$$$$$$$$$$$$$$$$$$$$$$$$$$$$$$$$$$$
---     RMON - 64 bits COUNTERS
--- $$$$$$$$$$$$$$$$$$$$$$$$$$$$$$$$$$$$$$$$$$$$$$$$$$$$$
--- *****************************************************



--- *********************************************************
---     TABLE for the pm10001otu4MonupRmonBytesCounterClientInput articles
--- *********************************************************

pm10001otu4MonupRmonBytesCounterClientInputTable OBJECT-TYPE
	SYNTAX  SEQUENCE OF Pm10001otu4MonupRmonBytesCounterClientInputEntry
	MAX-ACCESS not-accessible
	STATUS current
	DESCRIPTION
        "
        List of pm10001otu4MonupRmonBytesCounterClientInput
        Article
        "
	::= { pm10001otu4MonClientRmonCounter 16 }


pm10001otu4MonupRmonBytesCounterClientInputEntry OBJECT-TYPE
	SYNTAX Pm10001otu4MonupRmonBytesCounterClientInputEntry
	MAX-ACCESS not-accessible
	STATUS current
	DESCRIPTION
        "
        Row definition for the pm10001otu4MonupRmonBytesCounterClientInput
        table
        "
	INDEX   { pm10001otu4MonupRmonBytesCounterClientInputIndex }
	::= { pm10001otu4MonupRmonBytesCounterClientInputTable 1 }


Pm10001otu4MonupRmonBytesCounterClientInputEntry ::=
	SEQUENCE {
	pm10001otu4MonupRmonBytesCounterClientInputIndex
		INTEGER,
	pm10001otu4MonupRmonBytesCounterClientInputValuePortn
		Counter64,
	pm10001otu4MonupRmonBytesCounterClientInputErrorPortn
		EkiOnOff,
	pm10001otu4MonupRmonBytesCounterClientInputOverloadPortn
		EkiOnOff
	}


pm10001otu4MonupRmonBytesCounterClientInputIndex OBJECT-TYPE
	SYNTAX  INTEGER(0..128)
	MAX-ACCESS  read-only
	STATUS current
	DESCRIPTION
        "
        Index definition for the pm10001otu4MonupRmonBytesCounterClientInput
        table
        "
	::= { pm10001otu4MonupRmonBytesCounterClientInputEntry 1 }


pm10001otu4MonupRmonBytesCounterClientInputValuePortn OBJECT-TYPE
	SYNTAX  Counter64
	MAX-ACCESS read-only
	STATUS current
	DESCRIPTION
        "
        Client Input Bytes :This counter
        is increased each time a data byte
        is received on the client port
          <Help>  This counter gives the
        number of bytes received on the
        client port
        "
	::= { pm10001otu4MonupRmonBytesCounterClientInputEntry 2 }


pm10001otu4MonupRmonBytesCounterClientInputErrorPortn OBJECT-TYPE
	SYNTAX  EkiOnOff
	MAX-ACCESS read-only
	STATUS current
	DESCRIPTION
        "
        Bytes Counter Error :This OID
         when set indicates the Bytes counter
        value is invalid on client port
        "
	::= { pm10001otu4MonupRmonBytesCounterClientInputEntry 3 }


pm10001otu4MonupRmonBytesCounterClientInputOverloadPortn OBJECT-TYPE
	SYNTAX  EkiOnOff
	MAX-ACCESS read-only
	STATUS current
	DESCRIPTION
        "
        Bytes Counter Overload :This OID
        when set indicates a Bytes counter
        overload on client port
        "
	::= { pm10001otu4MonupRmonBytesCounterClientInputEntry 4 }


--- *********************************************************
---     TABLE for the pm10001otu4MonupRmonCrcErrorsCounterClientInput articles
--- *********************************************************

pm10001otu4MonupRmonCrcErrorsCounterClientInputTable OBJECT-TYPE
	SYNTAX  SEQUENCE OF Pm10001otu4MonupRmonCrcErrorsCounterClientInputEntry
	MAX-ACCESS not-accessible
	STATUS current
	DESCRIPTION
        "
        List of pm10001otu4MonupRmonCrcErrorsCounterClientInput
        Article
        "
	::= { pm10001otu4MonClientRmonCounter 32 }


pm10001otu4MonupRmonCrcErrorsCounterClientInputEntry OBJECT-TYPE
	SYNTAX Pm10001otu4MonupRmonCrcErrorsCounterClientInputEntry
	MAX-ACCESS not-accessible
	STATUS current
	DESCRIPTION
        "
        Row definition for the pm10001otu4MonupRmonCrcErrorsCounterClientInput
        table
        "
	INDEX   { pm10001otu4MonupRmonCrcErrorsCounterClientInputIndex }
	::= { pm10001otu4MonupRmonCrcErrorsCounterClientInputTable 1 }


Pm10001otu4MonupRmonCrcErrorsCounterClientInputEntry ::=
	SEQUENCE {
	pm10001otu4MonupRmonCrcErrorsCounterClientInputIndex
		INTEGER,
	pm10001otu4MonupRmonCrcErrorsCounterClientInputValuePortn
		Counter64,
	pm10001otu4MonupRmonCrcErrorsCounterClientInputErrorPortn
		EkiOnOff,
	pm10001otu4MonupRmonCrcErrorsCounterClientInputOverloadPortn
		EkiOnOff
	}


pm10001otu4MonupRmonCrcErrorsCounterClientInputIndex OBJECT-TYPE
	SYNTAX  INTEGER(0..128)
	MAX-ACCESS  read-only
	STATUS current
	DESCRIPTION
        "
        Index definition for the pm10001otu4MonupRmonCrcErrorsCounterClientInput
        table
        "
	::= { pm10001otu4MonupRmonCrcErrorsCounterClientInputEntry 1 }


pm10001otu4MonupRmonCrcErrorsCounterClientInputValuePortn OBJECT-TYPE
	SYNTAX  Counter64
	MAX-ACCESS read-only
	STATUS current
	DESCRIPTION
        "
        Client Input B1/CRC Errors :This
        counter is increased each time
         a B1/FCS error is detected on
         the client port  <Help>  This
         counter gives the number of B1/FCS
        Errors received on the client port
        "
	::= { pm10001otu4MonupRmonCrcErrorsCounterClientInputEntry 2 }


pm10001otu4MonupRmonCrcErrorsCounterClientInputErrorPortn OBJECT-TYPE
	SYNTAX  EkiOnOff
	MAX-ACCESS read-only
	STATUS current
	DESCRIPTION
        "
        B1/FCS Errors Counter Error :This
        OID when set indicates the B1/FCS
        Errors counter value is invalid
        on client port
        "
	::= { pm10001otu4MonupRmonCrcErrorsCounterClientInputEntry 3 }


pm10001otu4MonupRmonCrcErrorsCounterClientInputOverloadPortn OBJECT-TYPE
	SYNTAX  EkiOnOff
	MAX-ACCESS read-only
	STATUS current
	DESCRIPTION
        "
        B1/FCS Errors Counter Overload
        :This OID when set indicates a
         B1/FCS Errors counter overload
        on client port
        "
	::= { pm10001otu4MonupRmonCrcErrorsCounterClientInputEntry 4 }


--- *********************************************************
---     TABLE for the pm10001otu4MonupRmonPacketsCounterClientInput articles
--- *********************************************************

pm10001otu4MonupRmonPacketsCounterClientInputTable OBJECT-TYPE
	SYNTAX  SEQUENCE OF Pm10001otu4MonupRmonPacketsCounterClientInputEntry
	MAX-ACCESS not-accessible
	STATUS current
	DESCRIPTION
        "
        List of pm10001otu4MonupRmonPacketsCounterClientInput
        Article
        "
	::= { pm10001otu4MonClientRmonCounter 48 }


pm10001otu4MonupRmonPacketsCounterClientInputEntry OBJECT-TYPE
	SYNTAX Pm10001otu4MonupRmonPacketsCounterClientInputEntry
	MAX-ACCESS not-accessible
	STATUS current
	DESCRIPTION
        "
        Row definition for the pm10001otu4MonupRmonPacketsCounterClientInput
        table
        "
	INDEX   { pm10001otu4MonupRmonPacketsCounterClientInputIndex }
	::= { pm10001otu4MonupRmonPacketsCounterClientInputTable 1 }


Pm10001otu4MonupRmonPacketsCounterClientInputEntry ::=
	SEQUENCE {
	pm10001otu4MonupRmonPacketsCounterClientInputIndex
		INTEGER,
	pm10001otu4MonupRmonPacketsCounterClientInputValuePortn
		Counter64,
	pm10001otu4MonupRmonPacketsCounterClientInputErrorPortn
		EkiOnOff,
	pm10001otu4MonupRmonPacketsCounterClientInputOverloadPortn
		EkiOnOff
	}


pm10001otu4MonupRmonPacketsCounterClientInputIndex OBJECT-TYPE
	SYNTAX  INTEGER(0..128)
	MAX-ACCESS  read-only
	STATUS current
	DESCRIPTION
        "
        Index definition for the pm10001otu4MonupRmonPacketsCounterClientInput
        table
        "
	::= { pm10001otu4MonupRmonPacketsCounterClientInputEntry 1 }


pm10001otu4MonupRmonPacketsCounterClientInputValuePortn OBJECT-TYPE
	SYNTAX  Counter64
	MAX-ACCESS read-only
	STATUS current
	DESCRIPTION
        "
        Client Input Packets :This counter
        is increased each time a packet
        is received on the client port
          <Help>  This counter gives the
        number of packets received on the
        client port
        "
	::= { pm10001otu4MonupRmonPacketsCounterClientInputEntry 2 }


pm10001otu4MonupRmonPacketsCounterClientInputErrorPortn OBJECT-TYPE
	SYNTAX  EkiOnOff
	MAX-ACCESS read-only
	STATUS current
	DESCRIPTION
        "
        Packets Counter Error :This OID
        when set indicates the Packets
         counter value is invalid on client
        port
        "
	::= { pm10001otu4MonupRmonPacketsCounterClientInputEntry 3 }


pm10001otu4MonupRmonPacketsCounterClientInputOverloadPortn OBJECT-TYPE
	SYNTAX  EkiOnOff
	MAX-ACCESS read-only
	STATUS current
	DESCRIPTION
        "
        Packets Counter Overload :This
        OID when set indicates a Packets
        counter overload on client port
        "
	::= { pm10001otu4MonupRmonPacketsCounterClientInputEntry 4 }


--- *********************************************************
---     TABLE for the pm10001otu4MonupRmonBroadcastCounterClientInput articles
--- *********************************************************

pm10001otu4MonupRmonBroadcastCounterClientInputTable OBJECT-TYPE
	SYNTAX  SEQUENCE OF Pm10001otu4MonupRmonBroadcastCounterClientInputEntry
	MAX-ACCESS not-accessible
	STATUS current
	DESCRIPTION
        "
        List of pm10001otu4MonupRmonBroadcastCounterClientInput
        Article
        "
	::= { pm10001otu4MonClientRmonCounter 64 }


pm10001otu4MonupRmonBroadcastCounterClientInputEntry OBJECT-TYPE
	SYNTAX Pm10001otu4MonupRmonBroadcastCounterClientInputEntry
	MAX-ACCESS not-accessible
	STATUS current
	DESCRIPTION
        "
        Row definition for the pm10001otu4MonupRmonBroadcastCounterClientInput
        table
        "
	INDEX   { pm10001otu4MonupRmonBroadcastCounterClientInputIndex }
	::= { pm10001otu4MonupRmonBroadcastCounterClientInputTable 1 }


Pm10001otu4MonupRmonBroadcastCounterClientInputEntry ::=
	SEQUENCE {
	pm10001otu4MonupRmonBroadcastCounterClientInputIndex
		INTEGER,
	pm10001otu4MonupRmonBroadcastCounterClientInputValuePortn
		Counter64,
	pm10001otu4MonupRmonBroadcastCounterClientInputErrorPortn
		EkiOnOff,
	pm10001otu4MonupRmonBroadcastCounterClientInputOverloadPortn
		EkiOnOff
	}


pm10001otu4MonupRmonBroadcastCounterClientInputIndex OBJECT-TYPE
	SYNTAX  INTEGER(0..128)
	MAX-ACCESS  read-only
	STATUS current
	DESCRIPTION
        "
        Index definition for the pm10001otu4MonupRmonBroadcastCounterClientInput
        table
        "
	::= { pm10001otu4MonupRmonBroadcastCounterClientInputEntry 1 }


pm10001otu4MonupRmonBroadcastCounterClientInputValuePortn OBJECT-TYPE
	SYNTAX  Counter64
	MAX-ACCESS read-only
	STATUS current
	DESCRIPTION
        "
        Client Input Broadcast Packets
        :This counter is increased each
        time a broadcast packet is received
        on the client port  <Help>  This
        counter gives the number of Broadcast
        packets received on the client
         port
        "
	::= { pm10001otu4MonupRmonBroadcastCounterClientInputEntry 2 }


pm10001otu4MonupRmonBroadcastCounterClientInputErrorPortn OBJECT-TYPE
	SYNTAX  EkiOnOff
	MAX-ACCESS read-only
	STATUS current
	DESCRIPTION
        "
        Broadcast Counter Error :This
         OID when set indicates the Broadcast
        counter value is invalid on client
        port
        "
	::= { pm10001otu4MonupRmonBroadcastCounterClientInputEntry 3 }


pm10001otu4MonupRmonBroadcastCounterClientInputOverloadPortn OBJECT-TYPE
	SYNTAX  EkiOnOff
	MAX-ACCESS read-only
	STATUS current
	DESCRIPTION
        "
        Broadcast Counter Overload :This
        OID when set indicates a Broadcast
        counter overload on client port
        "
	::= { pm10001otu4MonupRmonBroadcastCounterClientInputEntry 4 }


--- *********************************************************
---     TABLE for the pm10001otu4MonupRmonMulticastCounterClientInput articles
--- *********************************************************

pm10001otu4MonupRmonMulticastCounterClientInputTable OBJECT-TYPE
	SYNTAX  SEQUENCE OF Pm10001otu4MonupRmonMulticastCounterClientInputEntry
	MAX-ACCESS not-accessible
	STATUS current
	DESCRIPTION
        "
        List of pm10001otu4MonupRmonMulticastCounterClientInput
        Article
        "
	::= { pm10001otu4MonClientRmonCounter 80 }


pm10001otu4MonupRmonMulticastCounterClientInputEntry OBJECT-TYPE
	SYNTAX Pm10001otu4MonupRmonMulticastCounterClientInputEntry
	MAX-ACCESS not-accessible
	STATUS current
	DESCRIPTION
        "
        Row definition for the pm10001otu4MonupRmonMulticastCounterClientInput
        table
        "
	INDEX   { pm10001otu4MonupRmonMulticastCounterClientInputIndex }
	::= { pm10001otu4MonupRmonMulticastCounterClientInputTable 1 }


Pm10001otu4MonupRmonMulticastCounterClientInputEntry ::=
	SEQUENCE {
	pm10001otu4MonupRmonMulticastCounterClientInputIndex
		INTEGER,
	pm10001otu4MonupRmonMulticastCounterClientInputValuePortn
		Counter64,
	pm10001otu4MonupRmonMulticastCounterClientInputErrorPortn
		EkiOnOff,
	pm10001otu4MonupRmonMulticastCounterClientInputOverloadPortn
		EkiOnOff
	}


pm10001otu4MonupRmonMulticastCounterClientInputIndex OBJECT-TYPE
	SYNTAX  INTEGER(0..128)
	MAX-ACCESS  read-only
	STATUS current
	DESCRIPTION
        "
        Index definition for the pm10001otu4MonupRmonMulticastCounterClientInput
        table
        "
	::= { pm10001otu4MonupRmonMulticastCounterClientInputEntry 1 }


pm10001otu4MonupRmonMulticastCounterClientInputValuePortn OBJECT-TYPE
	SYNTAX  Counter64
	MAX-ACCESS read-only
	STATUS current
	DESCRIPTION
        "
        Client Input Multicast Packets
        :This counter is increased each
        time a Multicast packet is received
        on the client port  <Help>  This
        counter gives the number of Multicast
        packets received on the client
         port
        "
	::= { pm10001otu4MonupRmonMulticastCounterClientInputEntry 2 }


pm10001otu4MonupRmonMulticastCounterClientInputErrorPortn OBJECT-TYPE
	SYNTAX  EkiOnOff
	MAX-ACCESS read-only
	STATUS current
	DESCRIPTION
        "
        Multicast Counter Error :This
         OID when set indicates the Multicast
        counter value is invalid on client
        port
        "
	::= { pm10001otu4MonupRmonMulticastCounterClientInputEntry 3 }


pm10001otu4MonupRmonMulticastCounterClientInputOverloadPortn OBJECT-TYPE
	SYNTAX  EkiOnOff
	MAX-ACCESS read-only
	STATUS current
	DESCRIPTION
        "
        Multicast Counter Overload :This
        OID when set indicates a Multicast
        counter overload on client port
        "
	::= { pm10001otu4MonupRmonMulticastCounterClientInputEntry 4 }


--- *********************************************************
---     TABLE for the pm10001otu4MonupRmonPauseFrameCounterClientInput articles
--- *********************************************************

pm10001otu4MonupRmonPauseFrameCounterClientInputTable OBJECT-TYPE
	SYNTAX  SEQUENCE OF Pm10001otu4MonupRmonPauseFrameCounterClientInputEntry
	MAX-ACCESS not-accessible
	STATUS current
	DESCRIPTION
        "
        List of pm10001otu4MonupRmonPauseFrameCounterClientInput
        Article
        "
	::= { pm10001otu4MonClientRmonCounter 96 }


pm10001otu4MonupRmonPauseFrameCounterClientInputEntry OBJECT-TYPE
	SYNTAX Pm10001otu4MonupRmonPauseFrameCounterClientInputEntry
	MAX-ACCESS not-accessible
	STATUS current
	DESCRIPTION
        "
        Row definition for the pm10001otu4MonupRmonPauseFrameCounterClientInput
        table
        "
	INDEX   { pm10001otu4MonupRmonPauseFrameCounterClientInputIndex }
	::= { pm10001otu4MonupRmonPauseFrameCounterClientInputTable 1 }


Pm10001otu4MonupRmonPauseFrameCounterClientInputEntry ::=
	SEQUENCE {
	pm10001otu4MonupRmonPauseFrameCounterClientInputIndex
		INTEGER,
	pm10001otu4MonupRmonPauseFrameCounterClientInputValuePortn
		Counter64,
	pm10001otu4MonupRmonPauseFrameCounterClientInputErrorPortn
		EkiOnOff,
	pm10001otu4MonupRmonPauseFrameCounterClientInputOverloadPortn
		EkiOnOff
	}


pm10001otu4MonupRmonPauseFrameCounterClientInputIndex OBJECT-TYPE
	SYNTAX  INTEGER(0..128)
	MAX-ACCESS  read-only
	STATUS current
	DESCRIPTION
        "
        Index definition for the pm10001otu4MonupRmonPauseFrameCounterClientInput
        table
        "
	::= { pm10001otu4MonupRmonPauseFrameCounterClientInputEntry 1 }


pm10001otu4MonupRmonPauseFrameCounterClientInputValuePortn OBJECT-TYPE
	SYNTAX  Counter64
	MAX-ACCESS read-only
	STATUS current
	DESCRIPTION
        "
        Client Input Pause Frames :This
        counter is increased each time
         a Pause frame is received on the
        client port  <Help>  This counter
        gives the number of Pause frames
        received on the client port
        "
	::= { pm10001otu4MonupRmonPauseFrameCounterClientInputEntry 2 }


pm10001otu4MonupRmonPauseFrameCounterClientInputErrorPortn OBJECT-TYPE
	SYNTAX  EkiOnOff
	MAX-ACCESS read-only
	STATUS current
	DESCRIPTION
        "
        Pause Counter Error :This OID
         when set indicates the Pause counter
        value is invalid on client port
        "
	::= { pm10001otu4MonupRmonPauseFrameCounterClientInputEntry 3 }


pm10001otu4MonupRmonPauseFrameCounterClientInputOverloadPortn OBJECT-TYPE
	SYNTAX  EkiOnOff
	MAX-ACCESS read-only
	STATUS current
	DESCRIPTION
        "
        Pause Counter Overload :This OID
        when set indicates a Pause counter
        overload on client port
        "
	::= { pm10001otu4MonupRmonPauseFrameCounterClientInputEntry 4 }


--- *********************************************************
---     TABLE for the pm10001otu4MonupRmonUnicastCounterClientInput articles
--- *********************************************************

pm10001otu4MonupRmonUnicastCounterClientInputTable OBJECT-TYPE
	SYNTAX  SEQUENCE OF Pm10001otu4MonupRmonUnicastCounterClientInputEntry
	MAX-ACCESS not-accessible
	STATUS current
	DESCRIPTION
        "
        List of pm10001otu4MonupRmonUnicastCounterClientInput
        Article
        "
	::= { pm10001otu4MonClientRmonCounter 160 }


pm10001otu4MonupRmonUnicastCounterClientInputEntry OBJECT-TYPE
	SYNTAX Pm10001otu4MonupRmonUnicastCounterClientInputEntry
	MAX-ACCESS not-accessible
	STATUS current
	DESCRIPTION
        "
        Row definition for the pm10001otu4MonupRmonUnicastCounterClientInput
        table
        "
	INDEX   { pm10001otu4MonupRmonUnicastCounterClientInputIndex }
	::= { pm10001otu4MonupRmonUnicastCounterClientInputTable 1 }


Pm10001otu4MonupRmonUnicastCounterClientInputEntry ::=
	SEQUENCE {
	pm10001otu4MonupRmonUnicastCounterClientInputIndex
		INTEGER,
	pm10001otu4MonupRmonUnicastCounterClientInputValuePortn
		Counter64,
	pm10001otu4MonupRmonUnicastCounterClientInputErrorPortn
		EkiOnOff,
	pm10001otu4MonupRmonUnicastCounterClientInputOverloadPortn
		EkiOnOff
	}


pm10001otu4MonupRmonUnicastCounterClientInputIndex OBJECT-TYPE
	SYNTAX  INTEGER(0..128)
	MAX-ACCESS  read-only
	STATUS current
	DESCRIPTION
        "
        Index definition for the pm10001otu4MonupRmonUnicastCounterClientInput
        table
        "
	::= { pm10001otu4MonupRmonUnicastCounterClientInputEntry 1 }


pm10001otu4MonupRmonUnicastCounterClientInputValuePortn OBJECT-TYPE
	SYNTAX  Counter64
	MAX-ACCESS read-only
	STATUS current
	DESCRIPTION
        "
        Client Input Unicast Packets :This
        counter is increased each time
         a Unicast packet is received on
        the client port  <Help>  This counter
        gives the number of Unicast packets
        received on the client port
        "
	::= { pm10001otu4MonupRmonUnicastCounterClientInputEntry 2 }


pm10001otu4MonupRmonUnicastCounterClientInputErrorPortn OBJECT-TYPE
	SYNTAX  EkiOnOff
	MAX-ACCESS read-only
	STATUS current
	DESCRIPTION
        "
        Unicast Counter Error :This OID
        when set indicates the Unicast
         counter value is invalid on client
        port
        "
	::= { pm10001otu4MonupRmonUnicastCounterClientInputEntry 3 }


pm10001otu4MonupRmonUnicastCounterClientInputOverloadPortn OBJECT-TYPE
	SYNTAX  EkiOnOff
	MAX-ACCESS read-only
	STATUS current
	DESCRIPTION
        "
        Unicast Counter Overload :This
        OID when set indicates a Unicast
        counter overload on client port
        "
	::= { pm10001otu4MonupRmonUnicastCounterClientInputEntry 4 }


--- *********************************************************
---     TABLE for the pm10001otu4MonupRmonNonunicastCounterClientInput articles
--- *********************************************************

pm10001otu4MonupRmonNonunicastCounterClientInputTable OBJECT-TYPE
	SYNTAX  SEQUENCE OF Pm10001otu4MonupRmonNonunicastCounterClientInputEntry
	MAX-ACCESS not-accessible
	STATUS current
	DESCRIPTION
        "
        List of pm10001otu4MonupRmonNonunicastCounterClientInput
        Article
        "
	::= { pm10001otu4MonClientRmonCounter 176 }


pm10001otu4MonupRmonNonunicastCounterClientInputEntry OBJECT-TYPE
	SYNTAX Pm10001otu4MonupRmonNonunicastCounterClientInputEntry
	MAX-ACCESS not-accessible
	STATUS current
	DESCRIPTION
        "
        Row definition for the pm10001otu4MonupRmonNonunicastCounterClientInput
        table
        "
	INDEX   { pm10001otu4MonupRmonNonunicastCounterClientInputIndex }
	::= { pm10001otu4MonupRmonNonunicastCounterClientInputTable 1 }


Pm10001otu4MonupRmonNonunicastCounterClientInputEntry ::=
	SEQUENCE {
	pm10001otu4MonupRmonNonunicastCounterClientInputIndex
		INTEGER,
	pm10001otu4MonupRmonNonunicastCounterClientInputValuePortn
		Counter64,
	pm10001otu4MonupRmonNonunicastCounterClientInputErrorPortn
		EkiOnOff,
	pm10001otu4MonupRmonNonunicastCounterClientInputOverloadPortn
		EkiOnOff
	}


pm10001otu4MonupRmonNonunicastCounterClientInputIndex OBJECT-TYPE
	SYNTAX  INTEGER(0..128)
	MAX-ACCESS  read-only
	STATUS current
	DESCRIPTION
        "
        Index definition for the pm10001otu4MonupRmonNonunicastCounterClientInput
        table
        "
	::= { pm10001otu4MonupRmonNonunicastCounterClientInputEntry 1 }


pm10001otu4MonupRmonNonunicastCounterClientInputValuePortn OBJECT-TYPE
	SYNTAX  Counter64
	MAX-ACCESS read-only
	STATUS current
	DESCRIPTION
        "
        Client Input Non Unicast Packets
        :This counter is increased each
        time a Non-Unicast packet is received
        on the client port  <Help>  This
        counter gives the number of Non-Unicast
        packets received on the client
         port
        "
	::= { pm10001otu4MonupRmonNonunicastCounterClientInputEntry 2 }


pm10001otu4MonupRmonNonunicastCounterClientInputErrorPortn OBJECT-TYPE
	SYNTAX  EkiOnOff
	MAX-ACCESS read-only
	STATUS current
	DESCRIPTION
        "
        Non Unicast Counter Error :This
        OID when set indicates the Non-Unicast
        counter value is invalid on client
        port
        "
	::= { pm10001otu4MonupRmonNonunicastCounterClientInputEntry 3 }


pm10001otu4MonupRmonNonunicastCounterClientInputOverloadPortn OBJECT-TYPE
	SYNTAX  EkiOnOff
	MAX-ACCESS read-only
	STATUS current
	DESCRIPTION
        "
        Non Unicast Counter Overload :This
        OID when set indicates a Non-Unicast
        counter overload on client port
        "
	::= { pm10001otu4MonupRmonNonunicastCounterClientInputEntry 4 }


--- *********************************************************
---     TABLE for the pm10001otu4MondownRmonBytesCounterClientOutput articles
--- *********************************************************

pm10001otu4MondownRmonBytesCounterClientOutputTable OBJECT-TYPE
	SYNTAX  SEQUENCE OF Pm10001otu4MondownRmonBytesCounterClientOutputEntry
	MAX-ACCESS not-accessible
	STATUS current
	DESCRIPTION
        "
        List of pm10001otu4MondownRmonBytesCounterClientOutput
        Article
        "
	::= { pm10001otu4MonClientRmonCounter 208 }


pm10001otu4MondownRmonBytesCounterClientOutputEntry OBJECT-TYPE
	SYNTAX Pm10001otu4MondownRmonBytesCounterClientOutputEntry
	MAX-ACCESS not-accessible
	STATUS current
	DESCRIPTION
        "
        Row definition for the pm10001otu4MondownRmonBytesCounterClientOutput
        table
        "
	INDEX   { pm10001otu4MondownRmonBytesCounterClientOutputIndex }
	::= { pm10001otu4MondownRmonBytesCounterClientOutputTable 1 }


Pm10001otu4MondownRmonBytesCounterClientOutputEntry ::=
	SEQUENCE {
	pm10001otu4MondownRmonBytesCounterClientOutputIndex
		INTEGER,
	pm10001otu4MondownRmonBytesCounterClientOutputValuePortn
		Counter64,
	pm10001otu4MondownRmonBytesCounterClientOutputErrorPortn
		EkiOnOff,
	pm10001otu4MondownRmonBytesCounterClientOutputOverloadPortn
		EkiOnOff
	}


pm10001otu4MondownRmonBytesCounterClientOutputIndex OBJECT-TYPE
	SYNTAX  INTEGER(0..128)
	MAX-ACCESS  read-only
	STATUS current
	DESCRIPTION
        "
        Index definition for the pm10001otu4MondownRmonBytesCounterClientOutput
        table
        "
	::= { pm10001otu4MondownRmonBytesCounterClientOutputEntry 1 }


pm10001otu4MondownRmonBytesCounterClientOutputValuePortn OBJECT-TYPE
	SYNTAX  Counter64
	MAX-ACCESS read-only
	STATUS current
	DESCRIPTION
        "
        Client Output Bytes :This counter
        is increased each time a data byte
        is transmitted on the client port
         <Help>  This counter gives the
        number of bytes transmitted on
         the client port
        "
	::= { pm10001otu4MondownRmonBytesCounterClientOutputEntry 2 }


pm10001otu4MondownRmonBytesCounterClientOutputErrorPortn OBJECT-TYPE
	SYNTAX  EkiOnOff
	MAX-ACCESS read-only
	STATUS current
	DESCRIPTION
        "
        Bytes Counter Error :This OID
         when set indicates the Bytes counter
        value is invalid on client port
        "
	::= { pm10001otu4MondownRmonBytesCounterClientOutputEntry 3 }


pm10001otu4MondownRmonBytesCounterClientOutputOverloadPortn OBJECT-TYPE
	SYNTAX  EkiOnOff
	MAX-ACCESS read-only
	STATUS current
	DESCRIPTION
        "
        Bytes Counter Overload :This OID
        when set indicates a Bytes counter
        overload on client port
        "
	::= { pm10001otu4MondownRmonBytesCounterClientOutputEntry 4 }


--- *********************************************************
---     TABLE for the pm10001otu4MondownRmonCrcErrorsCounterClientOutput articles
--- *********************************************************

pm10001otu4MondownRmonCrcErrorsCounterClientOutputTable OBJECT-TYPE
	SYNTAX  SEQUENCE OF Pm10001otu4MondownRmonCrcErrorsCounterClientOutputEntry
	MAX-ACCESS not-accessible
	STATUS current
	DESCRIPTION
        "
        List of pm10001otu4MondownRmonCrcErrorsCounterClientOutput
        Article
        "
	::= { pm10001otu4MonClientRmonCounter 224 }


pm10001otu4MondownRmonCrcErrorsCounterClientOutputEntry OBJECT-TYPE
	SYNTAX Pm10001otu4MondownRmonCrcErrorsCounterClientOutputEntry
	MAX-ACCESS not-accessible
	STATUS current
	DESCRIPTION
        "
        Row definition for the pm10001otu4MondownRmonCrcErrorsCounterClientOutput
        table
        "
	INDEX   { pm10001otu4MondownRmonCrcErrorsCounterClientOutputIndex }
	::= { pm10001otu4MondownRmonCrcErrorsCounterClientOutputTable 1 }


Pm10001otu4MondownRmonCrcErrorsCounterClientOutputEntry ::=
	SEQUENCE {
	pm10001otu4MondownRmonCrcErrorsCounterClientOutputIndex
		INTEGER,
	pm10001otu4MondownRmonCrcErrorsCounterClientOutputValuePortn
		Counter64,
	pm10001otu4MondownRmonCrcErrorsCounterClientOutputErrorPortn
		EkiOnOff,
	pm10001otu4MondownRmonCrcErrorsCounterClientOutputOverloadPortn
		EkiOnOff
	}


pm10001otu4MondownRmonCrcErrorsCounterClientOutputIndex OBJECT-TYPE
	SYNTAX  INTEGER(0..128)
	MAX-ACCESS  read-only
	STATUS current
	DESCRIPTION
        "
        Index definition for the pm10001otu4MondownRmonCrcErrorsCounterClientOutput
        table
        "
	::= { pm10001otu4MondownRmonCrcErrorsCounterClientOutputEntry 1 }


pm10001otu4MondownRmonCrcErrorsCounterClientOutputValuePortn OBJECT-TYPE
	SYNTAX  Counter64
	MAX-ACCESS read-only
	STATUS current
	DESCRIPTION
        "
        Client Output B1/CRC Errors :This
        counter is increased each time
         a B1/FCS error is detected on
         the transmit client port  <Help>
         This counter gives the number
         of B1/CRC Errors transmitted on
        the client port
        "
	::= { pm10001otu4MondownRmonCrcErrorsCounterClientOutputEntry 2 }


pm10001otu4MondownRmonCrcErrorsCounterClientOutputErrorPortn OBJECT-TYPE
	SYNTAX  EkiOnOff
	MAX-ACCESS read-only
	STATUS current
	DESCRIPTION
        "
        Output B1/CRC Errors Counter Error
        :This OID when set indicates the
        B1/FCS Errors counter value is
         invalid on client port
        "
	::= { pm10001otu4MondownRmonCrcErrorsCounterClientOutputEntry 3 }


pm10001otu4MondownRmonCrcErrorsCounterClientOutputOverloadPortn OBJECT-TYPE
	SYNTAX  EkiOnOff
	MAX-ACCESS read-only
	STATUS current
	DESCRIPTION
        "
        Output B1/CRC Errors Counter Overload
        :This OID when set indicates a
         B1/FCS Errors counter overload
        on client port
        "
	::= { pm10001otu4MondownRmonCrcErrorsCounterClientOutputEntry 4 }


--- *********************************************************
---     TABLE for the pm10001otu4MondownRmonPacketsCounterClientOutput articles
--- *********************************************************

pm10001otu4MondownRmonPacketsCounterClientOutputTable OBJECT-TYPE
	SYNTAX  SEQUENCE OF Pm10001otu4MondownRmonPacketsCounterClientOutputEntry
	MAX-ACCESS not-accessible
	STATUS current
	DESCRIPTION
        "
        List of pm10001otu4MondownRmonPacketsCounterClientOutput
        Article
        "
	::= { pm10001otu4MonClientRmonCounter 240 }


pm10001otu4MondownRmonPacketsCounterClientOutputEntry OBJECT-TYPE
	SYNTAX Pm10001otu4MondownRmonPacketsCounterClientOutputEntry
	MAX-ACCESS not-accessible
	STATUS current
	DESCRIPTION
        "
        Row definition for the pm10001otu4MondownRmonPacketsCounterClientOutput
        table
        "
	INDEX   { pm10001otu4MondownRmonPacketsCounterClientOutputIndex }
	::= { pm10001otu4MondownRmonPacketsCounterClientOutputTable 1 }


Pm10001otu4MondownRmonPacketsCounterClientOutputEntry ::=
	SEQUENCE {
	pm10001otu4MondownRmonPacketsCounterClientOutputIndex
		INTEGER,
	pm10001otu4MondownRmonPacketsCounterClientOutputValuePortn
		Counter64,
	pm10001otu4MondownRmonPacketsCounterClientOutputErrorPortn
		EkiOnOff,
	pm10001otu4MondownRmonPacketsCounterClientOutputOverloadPortn
		EkiOnOff
	}


pm10001otu4MondownRmonPacketsCounterClientOutputIndex OBJECT-TYPE
	SYNTAX  INTEGER(0..128)
	MAX-ACCESS  read-only
	STATUS current
	DESCRIPTION
        "
        Index definition for the pm10001otu4MondownRmonPacketsCounterClientOutput
        table
        "
	::= { pm10001otu4MondownRmonPacketsCounterClientOutputEntry 1 }


pm10001otu4MondownRmonPacketsCounterClientOutputValuePortn OBJECT-TYPE
	SYNTAX  Counter64
	MAX-ACCESS read-only
	STATUS current
	DESCRIPTION
        "
        Client Output Packets :This counter
        is increased each time a packet
        is transmitted on the client port
         <Help>  This counter gives the
        number of packets transmitted on
        the client port
        "
	::= { pm10001otu4MondownRmonPacketsCounterClientOutputEntry 2 }


pm10001otu4MondownRmonPacketsCounterClientOutputErrorPortn OBJECT-TYPE
	SYNTAX  EkiOnOff
	MAX-ACCESS read-only
	STATUS current
	DESCRIPTION
        "
        Packets Counter Error :This OID
        when set indicates the Packets
         counter value is invalid on client
        port
        "
	::= { pm10001otu4MondownRmonPacketsCounterClientOutputEntry 3 }


pm10001otu4MondownRmonPacketsCounterClientOutputOverloadPortn OBJECT-TYPE
	SYNTAX  EkiOnOff
	MAX-ACCESS read-only
	STATUS current
	DESCRIPTION
        "
        Packets Counter Overload :This
        OID when set indicates a Packets
        counter overload on client port
        "
	::= { pm10001otu4MondownRmonPacketsCounterClientOutputEntry 4 }


--- *********************************************************
---     TABLE for the pm10001otu4MondownRmonBroadcastCounterClientOutput articles
--- *********************************************************

pm10001otu4MondownRmonBroadcastCounterClientOutputTable OBJECT-TYPE
	SYNTAX  SEQUENCE OF Pm10001otu4MondownRmonBroadcastCounterClientOutputEntry
	MAX-ACCESS not-accessible
	STATUS current
	DESCRIPTION
        "
        List of pm10001otu4MondownRmonBroadcastCounterClientOutput
        Article
        "
	::= { pm10001otu4MonClientRmonCounter 256 }


pm10001otu4MondownRmonBroadcastCounterClientOutputEntry OBJECT-TYPE
	SYNTAX Pm10001otu4MondownRmonBroadcastCounterClientOutputEntry
	MAX-ACCESS not-accessible
	STATUS current
	DESCRIPTION
        "
        Row definition for the pm10001otu4MondownRmonBroadcastCounterClientOutput
        table
        "
	INDEX   { pm10001otu4MondownRmonBroadcastCounterClientOutputIndex }
	::= { pm10001otu4MondownRmonBroadcastCounterClientOutputTable 1 }


Pm10001otu4MondownRmonBroadcastCounterClientOutputEntry ::=
	SEQUENCE {
	pm10001otu4MondownRmonBroadcastCounterClientOutputIndex
		INTEGER,
	pm10001otu4MondownRmonBroadcastCounterClientOutputValuePortn
		Counter64,
	pm10001otu4MondownRmonBroadcastCounterClientOutputErrorPortn
		EkiOnOff,
	pm10001otu4MondownRmonBroadcastCounterClientOutputOverloadPortn
		EkiOnOff
	}


pm10001otu4MondownRmonBroadcastCounterClientOutputIndex OBJECT-TYPE
	SYNTAX  INTEGER(0..128)
	MAX-ACCESS  read-only
	STATUS current
	DESCRIPTION
        "
        Index definition for the pm10001otu4MondownRmonBroadcastCounterClientOutput
        table
        "
	::= { pm10001otu4MondownRmonBroadcastCounterClientOutputEntry 1 }


pm10001otu4MondownRmonBroadcastCounterClientOutputValuePortn OBJECT-TYPE
	SYNTAX  Counter64
	MAX-ACCESS read-only
	STATUS current
	DESCRIPTION
        "
        Client Output Broadcast Packets
        :This counter is increased each
        time a broadcast packet is transmitted
        on the client port  <Help>  This
        counter gives the number of Broadcast
        packets transmitted on the client
        port
        "
	::= { pm10001otu4MondownRmonBroadcastCounterClientOutputEntry 2 }


pm10001otu4MondownRmonBroadcastCounterClientOutputErrorPortn OBJECT-TYPE
	SYNTAX  EkiOnOff
	MAX-ACCESS read-only
	STATUS current
	DESCRIPTION
        "
        Broadcast Counter Error :This
         OID when set indicates the Broadcast
        counter value is invalid on client
        port
        "
	::= { pm10001otu4MondownRmonBroadcastCounterClientOutputEntry 3 }


pm10001otu4MondownRmonBroadcastCounterClientOutputOverloadPortn OBJECT-TYPE
	SYNTAX  EkiOnOff
	MAX-ACCESS read-only
	STATUS current
	DESCRIPTION
        "
        Broadcast Counter Overload :This
        OID when set indicates a Broadcast
        counter overload on client port
        "
	::= { pm10001otu4MondownRmonBroadcastCounterClientOutputEntry 4 }


--- *********************************************************
---     TABLE for the pm10001otu4MondownRmonMulticastCounterClientOutput articles
--- *********************************************************

pm10001otu4MondownRmonMulticastCounterClientOutputTable OBJECT-TYPE
	SYNTAX  SEQUENCE OF Pm10001otu4MondownRmonMulticastCounterClientOutputEntry
	MAX-ACCESS not-accessible
	STATUS current
	DESCRIPTION
        "
        List of pm10001otu4MondownRmonMulticastCounterClientOutput
        Article
        "
	::= { pm10001otu4MonClientRmonCounter 272 }


pm10001otu4MondownRmonMulticastCounterClientOutputEntry OBJECT-TYPE
	SYNTAX Pm10001otu4MondownRmonMulticastCounterClientOutputEntry
	MAX-ACCESS not-accessible
	STATUS current
	DESCRIPTION
        "
        Row definition for the pm10001otu4MondownRmonMulticastCounterClientOutput
        table
        "
	INDEX   { pm10001otu4MondownRmonMulticastCounterClientOutputIndex }
	::= { pm10001otu4MondownRmonMulticastCounterClientOutputTable 1 }


Pm10001otu4MondownRmonMulticastCounterClientOutputEntry ::=
	SEQUENCE {
	pm10001otu4MondownRmonMulticastCounterClientOutputIndex
		INTEGER,
	pm10001otu4MondownRmonMulticastCounterClientOutputValuePortn
		Counter64,
	pm10001otu4MondownRmonMulticastCounterClientOutputErrorPortn
		EkiOnOff,
	pm10001otu4MondownRmonMulticastCounterClientOutputOverloadPortn
		EkiOnOff
	}


pm10001otu4MondownRmonMulticastCounterClientOutputIndex OBJECT-TYPE
	SYNTAX  INTEGER(0..128)
	MAX-ACCESS  read-only
	STATUS current
	DESCRIPTION
        "
        Index definition for the pm10001otu4MondownRmonMulticastCounterClientOutput
        table
        "
	::= { pm10001otu4MondownRmonMulticastCounterClientOutputEntry 1 }


pm10001otu4MondownRmonMulticastCounterClientOutputValuePortn OBJECT-TYPE
	SYNTAX  Counter64
	MAX-ACCESS read-only
	STATUS current
	DESCRIPTION
        "
        Client Output Multicast Packets
        :This counter is increased each
        time a Multicast packet is transmitted
        on the client port  <Help>  This
        counter gives the number of Multicast
        packets transmitted on the client
        port
        "
	::= { pm10001otu4MondownRmonMulticastCounterClientOutputEntry 2 }


pm10001otu4MondownRmonMulticastCounterClientOutputErrorPortn OBJECT-TYPE
	SYNTAX  EkiOnOff
	MAX-ACCESS read-only
	STATUS current
	DESCRIPTION
        "
        Multicast Counter Error :This
         OID when set indicates the Multicast
        counter value is invalid on client
        port
        "
	::= { pm10001otu4MondownRmonMulticastCounterClientOutputEntry 3 }


pm10001otu4MondownRmonMulticastCounterClientOutputOverloadPortn OBJECT-TYPE
	SYNTAX  EkiOnOff
	MAX-ACCESS read-only
	STATUS current
	DESCRIPTION
        "
        Multicast Counter Overload :This
        OID when set indicates a Multicast
        counter overload on client port
        "
	::= { pm10001otu4MondownRmonMulticastCounterClientOutputEntry 4 }


--- *********************************************************
---     TABLE for the pm10001otu4MondownRmonPauseFrameCounterClientOutput articles
--- *********************************************************

pm10001otu4MondownRmonPauseFrameCounterClientOutputTable OBJECT-TYPE
	SYNTAX  SEQUENCE OF Pm10001otu4MondownRmonPauseFrameCounterClientOutputEntry
	MAX-ACCESS not-accessible
	STATUS current
	DESCRIPTION
        "
        List of pm10001otu4MondownRmonPauseFrameCounterClientOutput
        Article
        "
	::= { pm10001otu4MonClientRmonCounter 288 }


pm10001otu4MondownRmonPauseFrameCounterClientOutputEntry OBJECT-TYPE
	SYNTAX Pm10001otu4MondownRmonPauseFrameCounterClientOutputEntry
	MAX-ACCESS not-accessible
	STATUS current
	DESCRIPTION
        "
        Row definition for the pm10001otu4MondownRmonPauseFrameCounterClientOutput
        table
        "
	INDEX   { pm10001otu4MondownRmonPauseFrameCounterClientOutputIndex }
	::= { pm10001otu4MondownRmonPauseFrameCounterClientOutputTable 1 }


Pm10001otu4MondownRmonPauseFrameCounterClientOutputEntry ::=
	SEQUENCE {
	pm10001otu4MondownRmonPauseFrameCounterClientOutputIndex
		INTEGER,
	pm10001otu4MondownRmonPauseFrameCounterClientOutputValuePortn
		Counter64,
	pm10001otu4MondownRmonPauseFrameCounterClientOutputErrorPortn
		EkiOnOff,
	pm10001otu4MondownRmonPauseFrameCounterClientOutputOverloadPortn
		EkiOnOff
	}


pm10001otu4MondownRmonPauseFrameCounterClientOutputIndex OBJECT-TYPE
	SYNTAX  INTEGER(0..128)
	MAX-ACCESS  read-only
	STATUS current
	DESCRIPTION
        "
        Index definition for the pm10001otu4MondownRmonPauseFrameCounterClientOutput
        table
        "
	::= { pm10001otu4MondownRmonPauseFrameCounterClientOutputEntry 1 }


pm10001otu4MondownRmonPauseFrameCounterClientOutputValuePortn OBJECT-TYPE
	SYNTAX  Counter64
	MAX-ACCESS read-only
	STATUS current
	DESCRIPTION
        "
        Client Output Pause Frames :This
        counter is increased each time
         a Pause frame is transmitted on
        the client port  <Help>  This counter
        gives the number of Pause frames
        transmitted on the client port
        "
	::= { pm10001otu4MondownRmonPauseFrameCounterClientOutputEntry 2 }


pm10001otu4MondownRmonPauseFrameCounterClientOutputErrorPortn OBJECT-TYPE
	SYNTAX  EkiOnOff
	MAX-ACCESS read-only
	STATUS current
	DESCRIPTION
        "
        Pause Counter Error :This OID
         when set indicates the Pause counter
        value is invalid on client port
        "
	::= { pm10001otu4MondownRmonPauseFrameCounterClientOutputEntry 3 }


pm10001otu4MondownRmonPauseFrameCounterClientOutputOverloadPortn OBJECT-TYPE
	SYNTAX  EkiOnOff
	MAX-ACCESS read-only
	STATUS current
	DESCRIPTION
        "
        Pause Counter Overload :This OID
        when set indicates a Pause counter
        overload on client port
        "
	::= { pm10001otu4MondownRmonPauseFrameCounterClientOutputEntry 4 }


--- *********************************************************
---     TABLE for the pm10001otu4MondownRmonUnicastCounterClientOutput articles
--- *********************************************************

pm10001otu4MondownRmonUnicastCounterClientOutputTable OBJECT-TYPE
	SYNTAX  SEQUENCE OF Pm10001otu4MondownRmonUnicastCounterClientOutputEntry
	MAX-ACCESS not-accessible
	STATUS current
	DESCRIPTION
        "
        List of pm10001otu4MondownRmonUnicastCounterClientOutput
        Article
        "
	::= { pm10001otu4MonClientRmonCounter 352 }


pm10001otu4MondownRmonUnicastCounterClientOutputEntry OBJECT-TYPE
	SYNTAX Pm10001otu4MondownRmonUnicastCounterClientOutputEntry
	MAX-ACCESS not-accessible
	STATUS current
	DESCRIPTION
        "
        Row definition for the pm10001otu4MondownRmonUnicastCounterClientOutput
        table
        "
	INDEX   { pm10001otu4MondownRmonUnicastCounterClientOutputIndex }
	::= { pm10001otu4MondownRmonUnicastCounterClientOutputTable 1 }


Pm10001otu4MondownRmonUnicastCounterClientOutputEntry ::=
	SEQUENCE {
	pm10001otu4MondownRmonUnicastCounterClientOutputIndex
		INTEGER,
	pm10001otu4MondownRmonUnicastCounterClientOutputValuePortn
		Counter64,
	pm10001otu4MondownRmonUnicastCounterClientOutputErrorPortn
		EkiOnOff,
	pm10001otu4MondownRmonUnicastCounterClientOutputOverloadPortn
		EkiOnOff
	}


pm10001otu4MondownRmonUnicastCounterClientOutputIndex OBJECT-TYPE
	SYNTAX  INTEGER(0..128)
	MAX-ACCESS  read-only
	STATUS current
	DESCRIPTION
        "
        Index definition for the pm10001otu4MondownRmonUnicastCounterClientOutput
        table
        "
	::= { pm10001otu4MondownRmonUnicastCounterClientOutputEntry 1 }


pm10001otu4MondownRmonUnicastCounterClientOutputValuePortn OBJECT-TYPE
	SYNTAX  Counter64
	MAX-ACCESS read-only
	STATUS current
	DESCRIPTION
        "
        Client Output Unicast Packets
         :This counter is increased each
        time a Unicast packet is transmitted
        on the client port  <Help>  This
        counter gives the number of Unicast
        packets transmitted on the client
        port
        "
	::= { pm10001otu4MondownRmonUnicastCounterClientOutputEntry 2 }


pm10001otu4MondownRmonUnicastCounterClientOutputErrorPortn OBJECT-TYPE
	SYNTAX  EkiOnOff
	MAX-ACCESS read-only
	STATUS current
	DESCRIPTION
        "
        Unicast Counter Error :This OID
        when set indicates the Unicast
         counter value is invalid on client
        port
        "
	::= { pm10001otu4MondownRmonUnicastCounterClientOutputEntry 3 }


pm10001otu4MondownRmonUnicastCounterClientOutputOverloadPortn OBJECT-TYPE
	SYNTAX  EkiOnOff
	MAX-ACCESS read-only
	STATUS current
	DESCRIPTION
        "
        Unicast Counter Overload :This
        OID when set indicates a Unicast
        counter overload on client port
        "
	::= { pm10001otu4MondownRmonUnicastCounterClientOutputEntry 4 }


--- *********************************************************
---     TABLE for the pm10001otu4MondownRmonNonunicastCounterClientOutput articles
--- *********************************************************

pm10001otu4MondownRmonNonunicastCounterClientOutputTable OBJECT-TYPE
	SYNTAX  SEQUENCE OF Pm10001otu4MondownRmonNonunicastCounterClientOutputEntry
	MAX-ACCESS not-accessible
	STATUS current
	DESCRIPTION
        "
        List of pm10001otu4MondownRmonNonunicastCounterClientOutput
        Article
        "
	::= { pm10001otu4MonClientRmonCounter 368 }


pm10001otu4MondownRmonNonunicastCounterClientOutputEntry OBJECT-TYPE
	SYNTAX Pm10001otu4MondownRmonNonunicastCounterClientOutputEntry
	MAX-ACCESS not-accessible
	STATUS current
	DESCRIPTION
        "
        Row definition for the pm10001otu4MondownRmonNonunicastCounterClientOutput
        table
        "
	INDEX   { pm10001otu4MondownRmonNonunicastCounterClientOutputIndex }
	::= { pm10001otu4MondownRmonNonunicastCounterClientOutputTable 1 }


Pm10001otu4MondownRmonNonunicastCounterClientOutputEntry ::=
	SEQUENCE {
	pm10001otu4MondownRmonNonunicastCounterClientOutputIndex
		INTEGER,
	pm10001otu4MondownRmonNonunicastCounterClientOutputValuePortn
		Counter64,
	pm10001otu4MondownRmonNonunicastCounterClientOutputErrorPortn
		EkiOnOff,
	pm10001otu4MondownRmonNonunicastCounterClientOutputOverloadPortn
		EkiOnOff
	}


pm10001otu4MondownRmonNonunicastCounterClientOutputIndex OBJECT-TYPE
	SYNTAX  INTEGER(0..128)
	MAX-ACCESS  read-only
	STATUS current
	DESCRIPTION
        "
        Index definition for the pm10001otu4MondownRmonNonunicastCounterClientOutput
        table
        "
	::= { pm10001otu4MondownRmonNonunicastCounterClientOutputEntry 1 }


pm10001otu4MondownRmonNonunicastCounterClientOutputValuePortn OBJECT-TYPE
	SYNTAX  Counter64
	MAX-ACCESS read-only
	STATUS current
	DESCRIPTION
        "
        Client Output Non Unicast Packets
        :This counter is increased each
        time a Non-Unicast packet is transmitted
        on the client port  <Help>  This
        counter gives the number of Non-Unicast
        packets transmitted on the client
        port
        "
	::= { pm10001otu4MondownRmonNonunicastCounterClientOutputEntry 2 }


pm10001otu4MondownRmonNonunicastCounterClientOutputErrorPortn OBJECT-TYPE
	SYNTAX  EkiOnOff
	MAX-ACCESS read-only
	STATUS current
	DESCRIPTION
        "
        Non Unicast Counter Error :This
        OID when set indicates the Non-Unicast
        counter value is invalid on client
        port
        "
	::= { pm10001otu4MondownRmonNonunicastCounterClientOutputEntry 3 }


pm10001otu4MondownRmonNonunicastCounterClientOutputOverloadPortn OBJECT-TYPE
	SYNTAX  EkiOnOff
	MAX-ACCESS read-only
	STATUS current
	DESCRIPTION
        "
        Non Unicast Counter Overload :This
        OID when set indicates a Non-Unicast
        counter overload on client port
        "
	::= { pm10001otu4MondownRmonNonunicastCounterClientOutputEntry 4 }







--- *****************************************************
--- $$$$$$$$$$$$$$$$$$$$$$$$$$$$$$$$$$$$$$$$$$$$$$$$$$$$$
---     MEASURES
--- $$$$$$$$$$$$$$$$$$$$$$$$$$$$$$$$$$$$$$$$$$$$$$$$$$$$$
--- *****************************************************



pm10001otu4Mesrsynth0 OBJECT-TYPE
	  SYNTAX EkiMeasureType
	  MAX-ACCESS read-only
	  STATUS deprecated
	  DESCRIPTION
        "
        Not Used :
        "
	  ::= { pm10001otu4MesrOther 0 }



pm10001otu4Mesrsynth1 OBJECT-TYPE
	  SYNTAX EkiMeasureType
	  MAX-ACCESS read-only
	  STATUS deprecated
	  DESCRIPTION
        "
        Not Used :
        "
	  ::= { pm10001otu4MesrOther 1 }



--- *****************************************************
---     LEAF for the pmIntervalNumber article
--- *****************************************************

pm10001otu4MesrpmIntervalNumber OBJECT-TYPE
	  SYNTAX Unsigned32 (0..65535)
	  MAX-ACCESS read-only
	  STATUS current
	  DESCRIPTION
        "
        PM Interval Counter :
        "
	  ::= { pm10001otu4MesrOther 7 }



--- *****************************************************
---     LEAF for the clientCfpTemp article
--- *****************************************************

pm10001otu4MesrclientCfpTemp OBJECT-TYPE
	  SYNTAX Unsigned32 (0..65535)
	  MAX-ACCESS read-only
	  STATUS current
	  DESCRIPTION
        "
        Client Trscv Temperature :This
        OID gives the temperature value
        of the Client Transceiver, read
        from the DDM (Digital Diagnostic
        Monitoring) (Temperature = AV_S16/256)
        (Unit = C) <Help> This Measure
         gives the temperature value of
        the Client Transceiver
        "
	  ::= { pm10001otu4MesrClient 8 }



--- *****************************************************
---     LEAF for the clientCfp3v3Voltage article
--- *****************************************************

pm10001otu4MesrclientCfp3v3Voltage OBJECT-TYPE
	  SYNTAX Unsigned32 (0..65535)
	  MAX-ACCESS read-only
	  STATUS current
	  DESCRIPTION
        "
        Client Trscv Voltage :This OID
        gives the 3V3 voltage value of
         the Client Transceiver, read from
        the DDM (Digital Diagnostic Monitoring)
         (Voltage = AV_U16/10000) (Unit
        = V) <Help> This Measure gives
         the 3V3 voltage value of the Client
        Transceiver
        "
	  ::= { pm10001otu4MesrClient 9 }



--- *****************************************************
---     LEAF for the clientSoaBiasCurrent article
--- *****************************************************

pm10001otu4MesrclientSoaBiasCurrent OBJECT-TYPE
	  SYNTAX Unsigned32 (0..65535)
	  MAX-ACCESS read-only
	  STATUS current
	  DESCRIPTION
        "
        Client Trscv SOA Bias :This OID
        gives the SOA bias value of the
        Client Transceiver, read from the
        DDM (Digital Diagnostic Monitoring)
         (Bias = AV_U16/500) (Unit = mA)
        <Help> This Measure gives the SOA
        bias value of the Client Transceiver
        "
	  ::= { pm10001otu4MesrClient 10 }



--- *****************************************************
---     LEAF for the lineMsaTemp article
--- *****************************************************

pm10001otu4MesrlineMsaTemp OBJECT-TYPE
	  SYNTAX Unsigned32 (0..65535)
	  MAX-ACCESS read-only
	  STATUS current
	  DESCRIPTION
        "
        Line Trscv Temperature :This OID
        gives the temperature value of
         the Line Transceiver, read from
        the DDM (Digital Diagnostic Monitoring)
         (Temperature = AV_S16/256) (Unit
        = C) <Help> This Measure gives
         the temperature value of the Line
        Transceiver.This temperature must
        remain below 95 C for proper operation
        "
	  ::= { pm10001otu4MesrLine 12 }



--- *****************************************************
---     LEAF for the lineMsa3v3Voltage article
--- *****************************************************

pm10001otu4MesrlineMsa3v3Voltage OBJECT-TYPE
	  SYNTAX Unsigned32 (0..65535)
	  MAX-ACCESS read-only
	  STATUS current
	  DESCRIPTION
        "
        Line Trscv Voltage :This OID gives
        the 3V3 voltage value of the Line
        Transceiver, read from the DDM
         (Digital Diagnostic Monitoring)
        (Voltage = AV_U16/10000) (Unit
         = V) <Help> This Measure gives
        the 3V3 voltage value of the Line
        Transceiver
        "
	  ::= { pm10001otu4MesrLine 13 }



--- *****************************************************
---     LEAF for the lineSoaBiasCurrent article
--- *****************************************************

pm10001otu4MesrlineSoaBiasCurrent OBJECT-TYPE
	  SYNTAX Unsigned32 (0..65535)
	  MAX-ACCESS read-only
	  STATUS current
	  DESCRIPTION
        "
        Line Trscv SOA Bias :This OID
         gives the SOA bias value of the
        Line Transceiver,read from the
         DDM (Digital Diagnostic Monitoring)
         (Bias = AV_U16/500) (Unit = mA)
        <Help> This Measure gives the SOA
        bias value of the Line Transceiver
        "
	  ::= { pm10001otu4MesrLine 14 }



--- *********************************************************
---     TABLE for the pm10001otu4MesrclientNetTxTemp articles
--- *********************************************************

pm10001otu4MesrclientNetTxTempTable OBJECT-TYPE
	SYNTAX  SEQUENCE OF Pm10001otu4MesrclientNetTxTempEntry
	MAX-ACCESS not-accessible
	STATUS current
	DESCRIPTION
        "
        List of pm10001otu4MesrclientNetTxTemp
        Article
        "
	::= { pm10001otu4MesrClient 16 }


pm10001otu4MesrclientNetTxTempEntry OBJECT-TYPE
	SYNTAX Pm10001otu4MesrclientNetTxTempEntry
	MAX-ACCESS not-accessible
	STATUS current
	DESCRIPTION
        "
        Row definition for the pm10001otu4MesrclientNetTxTemp
        table
        "
	INDEX   { pm10001otu4MesrclientNetTxTempIndex }
	::= { pm10001otu4MesrclientNetTxTempTable 1 }


Pm10001otu4MesrclientNetTxTempEntry ::=
	SEQUENCE {
	pm10001otu4MesrclientNetTxTempIndex
		INTEGER,
	pm10001otu4MesrclientNetTxTempPortn
		INTEGER
	}


pm10001otu4MesrclientNetTxTempIndex OBJECT-TYPE
	SYNTAX  INTEGER(0..128)
	MAX-ACCESS  read-only
	STATUS current
	DESCRIPTION
        "
        Index definition for the pm10001otu4MesrclientNetTxTemp
        table
        "
	::= { pm10001otu4MesrclientNetTxTempEntry 1 }


pm10001otu4MesrclientNetTxTempPortn OBJECT-TYPE
	SYNTAX  INTEGER (0..65535)
	MAX-ACCESS read-only
	STATUS current
	DESCRIPTION
        "
        Client Trscv Temperature :This
        OID gives the Laser temperature
        value of the Client Transceiver,
        read from the DDM (Digital Diagnostic
        Monitoring) (Temperature = AV_S16/256)
        (Unit = C) <Help> This Measure
         gives the Laser temperature value
        of the Client Transceiver
        "
	::= { pm10001otu4MesrclientNetTxTempEntry 2 }


--- *********************************************************
---     TABLE for the pm10001otu4MesrclientNetTxBias articles
--- *********************************************************

pm10001otu4MesrclientNetTxBiasTable OBJECT-TYPE
	SYNTAX  SEQUENCE OF Pm10001otu4MesrclientNetTxBiasEntry
	MAX-ACCESS not-accessible
	STATUS current
	DESCRIPTION
        "
        List of pm10001otu4MesrclientNetTxBias
        Article
        "
	::= { pm10001otu4MesrClient 32 }


pm10001otu4MesrclientNetTxBiasEntry OBJECT-TYPE
	SYNTAX Pm10001otu4MesrclientNetTxBiasEntry
	MAX-ACCESS not-accessible
	STATUS current
	DESCRIPTION
        "
        Row definition for the pm10001otu4MesrclientNetTxBias
        table
        "
	INDEX   { pm10001otu4MesrclientNetTxBiasIndex }
	::= { pm10001otu4MesrclientNetTxBiasTable 1 }


Pm10001otu4MesrclientNetTxBiasEntry ::=
	SEQUENCE {
	pm10001otu4MesrclientNetTxBiasIndex
		INTEGER,
	pm10001otu4MesrclientNetTxBiasPortn
		INTEGER
	}


pm10001otu4MesrclientNetTxBiasIndex OBJECT-TYPE
	SYNTAX  INTEGER(0..128)
	MAX-ACCESS  read-only
	STATUS current
	DESCRIPTION
        "
        Index definition for the pm10001otu4MesrclientNetTxBias
        table
        "
	::= { pm10001otu4MesrclientNetTxBiasEntry 1 }


pm10001otu4MesrclientNetTxBiasPortn OBJECT-TYPE
	SYNTAX  INTEGER (0..65535)
	MAX-ACCESS read-only
	STATUS current
	DESCRIPTION
        "
        Client Trscv Laser Bias :This
         OID gives the Laser bias value
        of the Client Transceiver, read
        from the DDM (Digital Diagnostic
        Monitoring) (Bias = AV_U16/500)
        (Unit = mA) <Help> This Measure
        gives the Laser bias value of the
        Client Transceiver
        "
	::= { pm10001otu4MesrclientNetTxBiasEntry 2 }


--- *********************************************************
---     TABLE for the pm10001otu4MesrclientNetTxPwr articles
--- *********************************************************

pm10001otu4MesrclientNetTxPwrTable OBJECT-TYPE
	SYNTAX  SEQUENCE OF Pm10001otu4MesrclientNetTxPwrEntry
	MAX-ACCESS not-accessible
	STATUS current
	DESCRIPTION
        "
        List of pm10001otu4MesrclientNetTxPwr
        Article
        "
	::= { pm10001otu4MesrClient 48 }


pm10001otu4MesrclientNetTxPwrEntry OBJECT-TYPE
	SYNTAX Pm10001otu4MesrclientNetTxPwrEntry
	MAX-ACCESS not-accessible
	STATUS current
	DESCRIPTION
        "
        Row definition for the pm10001otu4MesrclientNetTxPwr
        table
        "
	INDEX   { pm10001otu4MesrclientNetTxPwrIndex }
	::= { pm10001otu4MesrclientNetTxPwrTable 1 }


Pm10001otu4MesrclientNetTxPwrEntry ::=
	SEQUENCE {
	pm10001otu4MesrclientNetTxPwrIndex
		INTEGER,
	pm10001otu4MesrclientNetTxPwrPortn
		INTEGER
	}


pm10001otu4MesrclientNetTxPwrIndex OBJECT-TYPE
	SYNTAX  INTEGER(0..128)
	MAX-ACCESS  read-only
	STATUS current
	DESCRIPTION
        "
        Index definition for the pm10001otu4MesrclientNetTxPwr
        table
        "
	::= { pm10001otu4MesrclientNetTxPwrEntry 1 }


pm10001otu4MesrclientNetTxPwrPortn OBJECT-TYPE
	SYNTAX  INTEGER (0..65535)
	MAX-ACCESS read-only
	STATUS current
	DESCRIPTION
        "
        Client Trscv Tx Power :This OID
        gives the transmit power value
         of the Client Transceiver, read
        from the DDM (Digital Diagnostic
        Monitoring) (Power = 10*log(AV_U16)-40)
        (Unit = dBm) <Help> This Measure
        gives the transmit power value
         of the Client Transceiver
        "
	::= { pm10001otu4MesrclientNetTxPwrEntry 2 }


--- *********************************************************
---     TABLE for the pm10001otu4MesrclientNetRxPwr articles
--- *********************************************************

pm10001otu4MesrclientNetRxPwrTable OBJECT-TYPE
	SYNTAX  SEQUENCE OF Pm10001otu4MesrclientNetRxPwrEntry
	MAX-ACCESS not-accessible
	STATUS current
	DESCRIPTION
        "
        List of pm10001otu4MesrclientNetRxPwr
        Article
        "
	::= { pm10001otu4MesrClient 64 }


pm10001otu4MesrclientNetRxPwrEntry OBJECT-TYPE
	SYNTAX Pm10001otu4MesrclientNetRxPwrEntry
	MAX-ACCESS not-accessible
	STATUS current
	DESCRIPTION
        "
        Row definition for the pm10001otu4MesrclientNetRxPwr
        table
        "
	INDEX   { pm10001otu4MesrclientNetRxPwrIndex }
	::= { pm10001otu4MesrclientNetRxPwrTable 1 }


Pm10001otu4MesrclientNetRxPwrEntry ::=
	SEQUENCE {
	pm10001otu4MesrclientNetRxPwrIndex
		INTEGER,
	pm10001otu4MesrclientNetRxPwrPortn
		INTEGER
	}


pm10001otu4MesrclientNetRxPwrIndex OBJECT-TYPE
	SYNTAX  INTEGER(0..128)
	MAX-ACCESS  read-only
	STATUS current
	DESCRIPTION
        "
        Index definition for the pm10001otu4MesrclientNetRxPwr
        table
        "
	::= { pm10001otu4MesrclientNetRxPwrEntry 1 }


pm10001otu4MesrclientNetRxPwrPortn OBJECT-TYPE
	SYNTAX  INTEGER (0..65535)
	MAX-ACCESS read-only
	STATUS current
	DESCRIPTION
        "
        Client Trscv Rx Power :This OID
        gives the receive power value of
        the Client Transceiver, read in
        the DDM (Digital Diagnostic Monitoring)
        (Power = 10*log(AV_U16)-40) (Unit
        = dBm) <Help> This Measure gives
        the receive power value of the
         Client Transceiver
        "
	::= { pm10001otu4MesrclientNetRxPwrEntry 2 }


--- *********************************************************
---     TABLE for the pm10001otu4MesrlineNetTxLaserOutputPwr articles
--- *********************************************************

pm10001otu4MesrlineNetTxLaserOutputPwrTable OBJECT-TYPE
	SYNTAX  SEQUENCE OF Pm10001otu4MesrlineNetTxLaserOutputPwrEntry
	MAX-ACCESS not-accessible
	STATUS current
	DESCRIPTION
        "
        List of pm10001otu4MesrlineNetTxLaserOutputPwr
        Article
        "
	::= { pm10001otu4MesrLine 80 }


pm10001otu4MesrlineNetTxLaserOutputPwrEntry OBJECT-TYPE
	SYNTAX Pm10001otu4MesrlineNetTxLaserOutputPwrEntry
	MAX-ACCESS not-accessible
	STATUS current
	DESCRIPTION
        "
        Row definition for the pm10001otu4MesrlineNetTxLaserOutputPwr
        table
        "
	INDEX   { pm10001otu4MesrlineNetTxLaserOutputPwrIndex }
	::= { pm10001otu4MesrlineNetTxLaserOutputPwrTable 1 }


Pm10001otu4MesrlineNetTxLaserOutputPwrEntry ::=
	SEQUENCE {
	pm10001otu4MesrlineNetTxLaserOutputPwrIndex
		INTEGER,
	pm10001otu4MesrlineNetTxLaserOutputPwrPortn
		INTEGER
	}


pm10001otu4MesrlineNetTxLaserOutputPwrIndex OBJECT-TYPE
	SYNTAX  INTEGER(0..128)
	MAX-ACCESS  read-only
	STATUS current
	DESCRIPTION
        "
        Index definition for the pm10001otu4MesrlineNetTxLaserOutputPwr
        table
        "
	::= { pm10001otu4MesrlineNetTxLaserOutputPwrEntry 1 }


pm10001otu4MesrlineNetTxLaserOutputPwrPortn OBJECT-TYPE
	SYNTAX  INTEGER (0..65535)
	MAX-ACCESS read-only
	STATUS current
	DESCRIPTION
        "
        Current Line Trscv Tx Power :This
        OID gives the Tx Laser transmit
        power value of the Line Transceiver,
        read in the DDM (Digital Diagnostic
        Monitoring) (Power = AV_S16/100)
        (Unit = dBm) <Help> This Measure
        gives the Tx Laser transmit power
        value of the Line Transceiver
        "
	::= { pm10001otu4MesrlineNetTxLaserOutputPwrEntry 2 }


--- *********************************************************
---     TABLE for the pm10001otu4MesrlineNetTxLaserTemp articles
--- *********************************************************

pm10001otu4MesrlineNetTxLaserTempTable OBJECT-TYPE
	SYNTAX  SEQUENCE OF Pm10001otu4MesrlineNetTxLaserTempEntry
	MAX-ACCESS not-accessible
	STATUS current
	DESCRIPTION
        "
        List of pm10001otu4MesrlineNetTxLaserTemp
        Article
        "
	::= { pm10001otu4MesrLine 96 }


pm10001otu4MesrlineNetTxLaserTempEntry OBJECT-TYPE
	SYNTAX Pm10001otu4MesrlineNetTxLaserTempEntry
	MAX-ACCESS not-accessible
	STATUS current
	DESCRIPTION
        "
        Row definition for the pm10001otu4MesrlineNetTxLaserTemp
        table
        "
	INDEX   { pm10001otu4MesrlineNetTxLaserTempIndex }
	::= { pm10001otu4MesrlineNetTxLaserTempTable 1 }


Pm10001otu4MesrlineNetTxLaserTempEntry ::=
	SEQUENCE {
	pm10001otu4MesrlineNetTxLaserTempIndex
		INTEGER,
	pm10001otu4MesrlineNetTxLaserTempPortn
		INTEGER
	}


pm10001otu4MesrlineNetTxLaserTempIndex OBJECT-TYPE
	SYNTAX  INTEGER(0..128)
	MAX-ACCESS  read-only
	STATUS current
	DESCRIPTION
        "
        Index definition for the pm10001otu4MesrlineNetTxLaserTemp
        table
        "
	::= { pm10001otu4MesrlineNetTxLaserTempEntry 1 }


pm10001otu4MesrlineNetTxLaserTempPortn OBJECT-TYPE
	SYNTAX  INTEGER (0..65535)
	MAX-ACCESS read-only
	STATUS current
	DESCRIPTION
        "
        Current Line Trscv Tx Laser Temperature
        :This OID gives the Tx Laser Temperature
        value of the Line Transceiver,
         read from the DDM (Digital Diagnostic
        Monitoring) (Temperature = AV_S16/256)
        (Unit = C) <Help> This Measure
         gives the Tx Laser Temperature
        value of the Line Transceiver
        "
	::= { pm10001otu4MesrlineNetTxLaserTempEntry 2 }


--- *********************************************************
---     TABLE for the pm10001otu4MesrlineNetTxBiasCurrent articles
--- *********************************************************

pm10001otu4MesrlineNetTxBiasCurrentTable OBJECT-TYPE
	SYNTAX  SEQUENCE OF Pm10001otu4MesrlineNetTxBiasCurrentEntry
	MAX-ACCESS not-accessible
	STATUS current
	DESCRIPTION
        "
        List of pm10001otu4MesrlineNetTxBiasCurrent
        Article
        "
	::= { pm10001otu4MesrLine 112 }


pm10001otu4MesrlineNetTxBiasCurrentEntry OBJECT-TYPE
	SYNTAX Pm10001otu4MesrlineNetTxBiasCurrentEntry
	MAX-ACCESS not-accessible
	STATUS current
	DESCRIPTION
        "
        Row definition for the pm10001otu4MesrlineNetTxBiasCurrent
        table
        "
	INDEX   { pm10001otu4MesrlineNetTxBiasCurrentIndex }
	::= { pm10001otu4MesrlineNetTxBiasCurrentTable 1 }


Pm10001otu4MesrlineNetTxBiasCurrentEntry ::=
	SEQUENCE {
	pm10001otu4MesrlineNetTxBiasCurrentIndex
		INTEGER,
	pm10001otu4MesrlineNetTxBiasCurrentPortn
		INTEGER
	}


pm10001otu4MesrlineNetTxBiasCurrentIndex OBJECT-TYPE
	SYNTAX  INTEGER(0..128)
	MAX-ACCESS  read-only
	STATUS current
	DESCRIPTION
        "
        Index definition for the pm10001otu4MesrlineNetTxBiasCurrent
        table
        "
	::= { pm10001otu4MesrlineNetTxBiasCurrentEntry 1 }


pm10001otu4MesrlineNetTxBiasCurrentPortn OBJECT-TYPE
	SYNTAX  INTEGER (0..65535)
	MAX-ACCESS read-only
	STATUS current
	DESCRIPTION
        "
        Current Line Trscv Tx Laser Bias
        :This OID gives the Tx Laser Bias
        value of the Line Transceiver,
         read from the DDM (Digital Diagnostic
        Monitoring) (Bias = AV_S16/10)
         (Unit = mA) <Help> This Measure
        gives the Tx Laser Bias value of
        the Line Transceiver
        "
	::= { pm10001otu4MesrlineNetTxBiasCurrentEntry 2 }


--- *********************************************************
---     TABLE for the pm10001otu4MesrlineNetRxInputPwr articles
--- *********************************************************

pm10001otu4MesrlineNetRxInputPwrTable OBJECT-TYPE
	SYNTAX  SEQUENCE OF Pm10001otu4MesrlineNetRxInputPwrEntry
	MAX-ACCESS not-accessible
	STATUS current
	DESCRIPTION
        "
        List of pm10001otu4MesrlineNetRxInputPwr
        Article
        "
	::= { pm10001otu4MesrLine 128 }


pm10001otu4MesrlineNetRxInputPwrEntry OBJECT-TYPE
	SYNTAX Pm10001otu4MesrlineNetRxInputPwrEntry
	MAX-ACCESS not-accessible
	STATUS current
	DESCRIPTION
        "
        Row definition for the pm10001otu4MesrlineNetRxInputPwr
        table
        "
	INDEX   { pm10001otu4MesrlineNetRxInputPwrIndex }
	::= { pm10001otu4MesrlineNetRxInputPwrTable 1 }


Pm10001otu4MesrlineNetRxInputPwrEntry ::=
	SEQUENCE {
	pm10001otu4MesrlineNetRxInputPwrIndex
		INTEGER,
	pm10001otu4MesrlineNetRxInputPwrPortn
		INTEGER
	}


pm10001otu4MesrlineNetRxInputPwrIndex OBJECT-TYPE
	SYNTAX  INTEGER(0..128)
	MAX-ACCESS  read-only
	STATUS current
	DESCRIPTION
        "
        Index definition for the pm10001otu4MesrlineNetRxInputPwr
        table
        "
	::= { pm10001otu4MesrlineNetRxInputPwrEntry 1 }


pm10001otu4MesrlineNetRxInputPwrPortn OBJECT-TYPE
	SYNTAX  INTEGER (0..65535)
	MAX-ACCESS read-only
	STATUS current
	DESCRIPTION
        "
        Current Line Trscv Rx Power :This
        OID gives the Receive power value
        of the Line Transceiver, read in
        the DDM (Digital Diagnostic Monitoring)
        (Power = AV_S16/100) (Unit = dBm)
        <Help> This Measure gives the Receive
        power value of the Line Transceiver
        "
	::= { pm10001otu4MesrlineNetRxInputPwrEntry 2 }


--- *********************************************************
---     TABLE for the pm10001otu4MesrlineResidualChromaticDisp articles
--- *********************************************************

pm10001otu4MesrlineResidualChromaticDispTable OBJECT-TYPE
	SYNTAX  SEQUENCE OF Pm10001otu4MesrlineResidualChromaticDispEntry
	MAX-ACCESS not-accessible
	STATUS current
	DESCRIPTION
        "
        List of pm10001otu4MesrlineResidualChromaticDisp
        Article
        "
	::= { pm10001otu4MesrLine 144 }


pm10001otu4MesrlineResidualChromaticDispEntry OBJECT-TYPE
	SYNTAX Pm10001otu4MesrlineResidualChromaticDispEntry
	MAX-ACCESS not-accessible
	STATUS current
	DESCRIPTION
        "
        Row definition for the pm10001otu4MesrlineResidualChromaticDisp
        table
        "
	INDEX   { pm10001otu4MesrlineResidualChromaticDispIndex }
	::= { pm10001otu4MesrlineResidualChromaticDispTable 1 }


Pm10001otu4MesrlineResidualChromaticDispEntry ::=
	SEQUENCE {
	pm10001otu4MesrlineResidualChromaticDispIndex
		INTEGER,
	pm10001otu4MesrlineResidualChromaticDispPortn
		INTEGER
	}


pm10001otu4MesrlineResidualChromaticDispIndex OBJECT-TYPE
	SYNTAX  INTEGER(0..128)
	MAX-ACCESS  read-only
	STATUS current
	DESCRIPTION
        "
        Index definition for the pm10001otu4MesrlineResidualChromaticDisp
        table
        "
	::= { pm10001otu4MesrlineResidualChromaticDispEntry 1 }


pm10001otu4MesrlineResidualChromaticDispPortn OBJECT-TYPE
	SYNTAX  INTEGER (0..65535)
	MAX-ACCESS read-only
	STATUS current
	DESCRIPTION
        "
        Current Residual Chromatic Dispersion
        :This OID gives the current Residual
        Chromatic Dispersion on the Line
        interface (Dispersion = AV_S16*(-2))
          (Unit = ps/nm)<Help> This measure
        gives the current Residual Chromatic
        Dispersion on the Line interface.
        "
	::= { pm10001otu4MesrlineResidualChromaticDispEntry 2 }


--- *********************************************************
---     TABLE for the pm10001otu4MesrlineDiffGroupDelay articles
--- *********************************************************

pm10001otu4MesrlineDiffGroupDelayTable OBJECT-TYPE
	SYNTAX  SEQUENCE OF Pm10001otu4MesrlineDiffGroupDelayEntry
	MAX-ACCESS not-accessible
	STATUS current
	DESCRIPTION
        "
        List of pm10001otu4MesrlineDiffGroupDelay
        Article
        "
	::= { pm10001otu4MesrLine 148 }


pm10001otu4MesrlineDiffGroupDelayEntry OBJECT-TYPE
	SYNTAX Pm10001otu4MesrlineDiffGroupDelayEntry
	MAX-ACCESS not-accessible
	STATUS current
	DESCRIPTION
        "
        Row definition for the pm10001otu4MesrlineDiffGroupDelay
        table
        "
	INDEX   { pm10001otu4MesrlineDiffGroupDelayIndex }
	::= { pm10001otu4MesrlineDiffGroupDelayTable 1 }


Pm10001otu4MesrlineDiffGroupDelayEntry ::=
	SEQUENCE {
	pm10001otu4MesrlineDiffGroupDelayIndex
		INTEGER,
	pm10001otu4MesrlineDiffGroupDelayPortn
		INTEGER
	}


pm10001otu4MesrlineDiffGroupDelayIndex OBJECT-TYPE
	SYNTAX  INTEGER(0..128)
	MAX-ACCESS  read-only
	STATUS current
	DESCRIPTION
        "
        Index definition for the pm10001otu4MesrlineDiffGroupDelay
        table
        "
	::= { pm10001otu4MesrlineDiffGroupDelayEntry 1 }


pm10001otu4MesrlineDiffGroupDelayPortn OBJECT-TYPE
	SYNTAX  INTEGER (0..65535)
	MAX-ACCESS read-only
	STATUS current
	DESCRIPTION
        "
        Current Differential Group Delay
        :This OID gives the current Differential
        Group Delay on the Line interface
         (Delay = AV_S16)    (Unit = ps)<Help>
        This measure gives the current
         Differential Group Delay on the
        Line interface.
        "
	::= { pm10001otu4MesrlineDiffGroupDelayEntry 2 }


--- *********************************************************
---     TABLE for the pm10001otu4MesrlineQFactor articles
--- *********************************************************

pm10001otu4MesrlineQFactorTable OBJECT-TYPE
	SYNTAX  SEQUENCE OF Pm10001otu4MesrlineQFactorEntry
	MAX-ACCESS not-accessible
	STATUS current
	DESCRIPTION
        "
        List of pm10001otu4MesrlineQFactor
        Article
        "
	::= { pm10001otu4MesrLine 152 }


pm10001otu4MesrlineQFactorEntry OBJECT-TYPE
	SYNTAX Pm10001otu4MesrlineQFactorEntry
	MAX-ACCESS not-accessible
	STATUS current
	DESCRIPTION
        "
        Row definition for the pm10001otu4MesrlineQFactor
        table
        "
	INDEX   { pm10001otu4MesrlineQFactorIndex }
	::= { pm10001otu4MesrlineQFactorTable 1 }


Pm10001otu4MesrlineQFactorEntry ::=
	SEQUENCE {
	pm10001otu4MesrlineQFactorIndex
		INTEGER,
	pm10001otu4MesrlineQFactorPortn
		INTEGER
	}


pm10001otu4MesrlineQFactorIndex OBJECT-TYPE
	SYNTAX  INTEGER(0..128)
	MAX-ACCESS  read-only
	STATUS current
	DESCRIPTION
        "
        Index definition for the pm10001otu4MesrlineQFactor
        table
        "
	::= { pm10001otu4MesrlineQFactorEntry 1 }


pm10001otu4MesrlineQFactorPortn OBJECT-TYPE
	SYNTAX  INTEGER (0..65535)
	MAX-ACCESS read-only
	STATUS current
	DESCRIPTION
        "
        Current Q Factor :This OID gives
        the current Q Factor on the Line
        interface  (Q Factor = AV_U16)
           (Unit = dB) <Help> This measure
        gives the current Q Factor on the
        Line interface.
        "
	::= { pm10001otu4MesrlineQFactorEntry 2 }


--- *********************************************************
---     TABLE for the pm10001otu4MesrlineCarrierFreqOffset articles
--- *********************************************************

pm10001otu4MesrlineCarrierFreqOffsetTable OBJECT-TYPE
	SYNTAX  SEQUENCE OF Pm10001otu4MesrlineCarrierFreqOffsetEntry
	MAX-ACCESS not-accessible
	STATUS current
	DESCRIPTION
        "
        List of pm10001otu4MesrlineCarrierFreqOffset
        Article
        "
	::= { pm10001otu4MesrLine 156 }


pm10001otu4MesrlineCarrierFreqOffsetEntry OBJECT-TYPE
	SYNTAX Pm10001otu4MesrlineCarrierFreqOffsetEntry
	MAX-ACCESS not-accessible
	STATUS current
	DESCRIPTION
        "
        Row definition for the pm10001otu4MesrlineCarrierFreqOffset
        table
        "
	INDEX   { pm10001otu4MesrlineCarrierFreqOffsetIndex }
	::= { pm10001otu4MesrlineCarrierFreqOffsetTable 1 }


Pm10001otu4MesrlineCarrierFreqOffsetEntry ::=
	SEQUENCE {
	pm10001otu4MesrlineCarrierFreqOffsetIndex
		INTEGER,
	pm10001otu4MesrlineCarrierFreqOffsetPortn
		INTEGER
	}


pm10001otu4MesrlineCarrierFreqOffsetIndex OBJECT-TYPE
	SYNTAX  INTEGER(0..128)
	MAX-ACCESS  read-only
	STATUS current
	DESCRIPTION
        "
        Index definition for the pm10001otu4MesrlineCarrierFreqOffset
        table
        "
	::= { pm10001otu4MesrlineCarrierFreqOffsetEntry 1 }


pm10001otu4MesrlineCarrierFreqOffsetPortn OBJECT-TYPE
	SYNTAX  INTEGER (0..65535)
	MAX-ACCESS read-only
	STATUS current
	DESCRIPTION
        "
        Current Carrier Frequency Offset
        :This OID gives the current Carrier
        Frequency Offset on the Line interface
         (Offset = AV_S16)   (Unit = MHz)<Help>
        This measure gives the current
         Carrier Frequency Offset on the
        Line interface.
        "
	::= { pm10001otu4MesrlineCarrierFreqOffsetEntry 2 }


--- *********************************************************
---     TABLE for the pm10001otu4MesrlineOsnr articles
--- *********************************************************

pm10001otu4MesrlineOsnrTable OBJECT-TYPE
	SYNTAX  SEQUENCE OF Pm10001otu4MesrlineOsnrEntry
	MAX-ACCESS not-accessible
	STATUS current
	DESCRIPTION
        "
        List of pm10001otu4MesrlineOsnr
        Article
        "
	::= { pm10001otu4MesrLine 160 }


pm10001otu4MesrlineOsnrEntry OBJECT-TYPE
	SYNTAX Pm10001otu4MesrlineOsnrEntry
	MAX-ACCESS not-accessible
	STATUS current
	DESCRIPTION
        "
        Row definition for the pm10001otu4MesrlineOsnr
        table
        "
	INDEX   { pm10001otu4MesrlineOsnrIndex }
	::= { pm10001otu4MesrlineOsnrTable 1 }


Pm10001otu4MesrlineOsnrEntry ::=
	SEQUENCE {
	pm10001otu4MesrlineOsnrIndex
		INTEGER,
	pm10001otu4MesrlineOsnrPortn
		INTEGER
	}


pm10001otu4MesrlineOsnrIndex OBJECT-TYPE
	SYNTAX  INTEGER(0..128)
	MAX-ACCESS  read-only
	STATUS current
	DESCRIPTION
        "
        Index definition for the pm10001otu4MesrlineOsnr
        table
        "
	::= { pm10001otu4MesrlineOsnrEntry 1 }


pm10001otu4MesrlineOsnrPortn OBJECT-TYPE
	SYNTAX  INTEGER (0..65535)
	MAX-ACCESS read-only
	STATUS current
	DESCRIPTION
        "
        Current OSNR :This OID gives the
        current OSNR on the Line interface
          (OSNR = AV_S16/10) (Unit = dB)<Help>
        This measure gives the current
         OSNR on the Line interface.
        "
	::= { pm10001otu4MesrlineOsnrEntry 2 }


--- *****************************************************
---     LEAF for the lineNetTxLaserOutputPwrAverage article
--- *****************************************************

pm10001otu4MesrlineNetTxLaserOutputPwrAverage OBJECT-TYPE
	  SYNTAX Unsigned32 (0..65535)
	  MAX-ACCESS read-only
	  STATUS current
	  DESCRIPTION
        "
        Average Line Trscv Tx Power :This
        OID gives the average Tx Laser
         transmit power value among the
        network lanes of the Line Transceiver,
        read in the DDM (Digital Diagnostic
        Monitoring)  (Power = AV_S16/100)
        (Unit = dBm) <Help> This Measure
        gives the average Tx Laser transmit
        power value among the network lanes
        of the Line Transceiver
        "
	  ::= { pm10001otu4MesrOther 180 }



--- *****************************************************
---     LEAF for the lineNetTxLaserTempAverage article
--- *****************************************************

pm10001otu4MesrlineNetTxLaserTempAverage OBJECT-TYPE
	  SYNTAX Unsigned32 (0..65535)
	  MAX-ACCESS read-only
	  STATUS current
	  DESCRIPTION
        "
        Average Line Trscv Tx Laser Temperature
        :This OID gives the average Tx
         Laser Temperature value among
         the network lanes of the Line
         Transceiver, read from the DDM
        (Digital Diagnostic Monitoring)
        (Temperature = AV_S16/256) (Unit
        = C) <Help> This Measure gives
         the average Tx Laser Temperature
        value among the network lanes of
        the Line Transceiver
        "
	  ::= { pm10001otu4MesrOther 181 }



--- *****************************************************
---     LEAF for the lineNetTxBiasCurrentAverage article
--- *****************************************************

pm10001otu4MesrlineNetTxBiasCurrentAverage OBJECT-TYPE
	  SYNTAX Unsigned32 (0..65535)
	  MAX-ACCESS read-only
	  STATUS current
	  DESCRIPTION
        "
        Average Line Trscv Tx Laser Bias
        :This OID gives the average Tx
         Laser Bias value among the network
        lanes of the Line Transceiver,
         read from the DDM (Digital Diagnostic
        Monitoring) (Bias = AV_S16/10)
         (Unit = mA) <Help> This Measure
        gives the average Tx Laser Bias
        value among the network lanes of
        the Line Transceiver
        "
	  ::= { pm10001otu4MesrOther 182 }



--- *****************************************************
---     LEAF for the lineNetRxInputPwrAverage article
--- *****************************************************

pm10001otu4MesrlineNetRxInputPwrAverage OBJECT-TYPE
	  SYNTAX Unsigned32 (0..65535)
	  MAX-ACCESS read-only
	  STATUS current
	  DESCRIPTION
        "
        Average Line Trscv Rx Power :This
        OID gives the average Receive power
        value among the network lanes of
        the Line Transceiver, read in the
        DDM (Digital Diagnostic Monitoring)
        (Power = AV_S16/100) (Unit = dBm)
        <Help> This Measure gives the average
        Receive power value among the network
        lanes of the Line Transceiver
        "
	  ::= { pm10001otu4MesrOther 183 }



--- *****************************************************
---     LEAF for the lineResidualChromaticDispAverage article
--- *****************************************************

pm10001otu4MesrlineResidualChromaticDispAverage OBJECT-TYPE
	  SYNTAX Unsigned32 (0..65535)
	  MAX-ACCESS read-only
	  STATUS current
	  DESCRIPTION
        "
        Average Residual Chromatic Dispersion
        :This OID gives the average Residual
        Chromatic Dispersion on the Line
        interface since the last measure
        reset  (Dispersion = AV_S16*(-2))
         (Unit = ps/nm)<Help> This measure
        gives the average Residual Chromatic
        Dispersion on the Line interface
        since the last measure reset.
        "
	  ::= { pm10001otu4MesrOther 184 }



--- *****************************************************
---     LEAF for the lineDiffGroupDelayAverage article
--- *****************************************************

pm10001otu4MesrlineDiffGroupDelayAverage OBJECT-TYPE
	  SYNTAX Unsigned32 (0..65535)
	  MAX-ACCESS read-only
	  STATUS current
	  DESCRIPTION
        "
        Average Differential Group Delay
        :This OID gives the average Group
        Delay on the Line interface since
        the last measure reset (Delay =
        AV_S16)  (Unit = ps)<Help> This
        measure gives the average Differential
        Group Delay on the Line interface
        since the last measure reset.
        "
	  ::= { pm10001otu4MesrOther 185 }



--- *****************************************************
---     LEAF for the lineQFactorAverage article
--- *****************************************************

pm10001otu4MesrlineQFactorAverage OBJECT-TYPE
	  SYNTAX Unsigned32 (0..65535)
	  MAX-ACCESS read-only
	  STATUS current
	  DESCRIPTION
        "
        Average Q Factor :This OID gives
        the average Q Factor on the Line
        interface since the last measure
        reset (Q Factor = AV_U16)   (Unit
        = dB) <Help> This measure gives
        the average Q Factor on the Line
        interface since the last measure
        reset.
        "
	  ::= { pm10001otu4MesrOther 186 }



--- *****************************************************
---     LEAF for the lineCarrierFreqOffsetAverage article
--- *****************************************************

pm10001otu4MesrlineCarrierFreqOffsetAverage OBJECT-TYPE
	  SYNTAX Unsigned32 (0..65535)
	  MAX-ACCESS read-only
	  STATUS current
	  DESCRIPTION
        "
        Average Carrier Frequency Offset
        :This OID gives the average Carrier
        Frequency Offset on the Line interface
        since the last measure reset (Offset
        = AV_S16)  (Unit = MHz)<Help> This
        measure gives the average Carrier
        Frequency Offset on the Line interface
        since the last measure reset
        "
	  ::= { pm10001otu4MesrOther 187 }



--- *****************************************************
---     LEAF for the lineOsnrAverage article
--- *****************************************************

pm10001otu4MesrlineOsnrAverage OBJECT-TYPE
	  SYNTAX Unsigned32 (0..65535)
	  MAX-ACCESS read-only
	  STATUS current
	  DESCRIPTION
        "
        Average OSNR :This OID gives the
        average OSNR on the Line interface
        since the last measure reset (OSNR
        = AV_S16/10) (Unit = dB)<Help>
         This measure gives the average
        OSNR on the Line interface since
        the last measure reset.
        "
	  ::= { pm10001otu4MesrOther 188 }



--- *****************************************************
---     LEAF for the clientNetTxTempMin article
--- *****************************************************

pm10001otu4MesrclientNetTxTempMin OBJECT-TYPE
	  SYNTAX Unsigned32 (0..65535)
	  MAX-ACCESS read-only
	  STATUS current
	  DESCRIPTION
        "
        Min Client Trscv Laser Temperature
        :This OID gives the minimum Laser
        temperature value among the network
        lanes of the Client Transceiver,
        read from the DDM (Digital Diagnostic
        Monitoring) (Temperature = AV_S16/256)
        (Unit = C) <Help> This Measure
         gives the minimum Laser temperature
        value among the network lanes of
        the Client Transceiver
        "
	  ::= { pm10001otu4MesrOther 192 }



--- *****************************************************
---     LEAF for the clientNetTxBiasMin article
--- *****************************************************

pm10001otu4MesrclientNetTxBiasMin OBJECT-TYPE
	  SYNTAX Unsigned32 (0..65535)
	  MAX-ACCESS read-only
	  STATUS current
	  DESCRIPTION
        "
        Min Client Trscv Laser Bias :This
        OID gives the minimum Laser bias
        value among the network lanes of
        the Client Transceiver, read from
        the DDM (Digital Diagnostic Monitoring)
        (Bias = AV_U16/500) (Unit = mA)
        <Help> This Measure gives the minimum
        Laser bias value among the network
        lanes of the Client Transceiver
        "
	  ::= { pm10001otu4MesrOther 193 }



--- *****************************************************
---     LEAF for the clientNetTxPwrMin article
--- *****************************************************

pm10001otu4MesrclientNetTxPwrMin OBJECT-TYPE
	  SYNTAX Unsigned32 (0..65535)
	  MAX-ACCESS read-only
	  STATUS current
	  DESCRIPTION
        "
        Min Client Trscv Tx Power :This
        OID gives the minimum transmit
         power value among the network
         lanes of the Client Transceiver,
        read from the DDM (Digital Diagnostic
        Monitoring) (Power = 10*log(AV_U16)-40)
        (Unit = dBm) <Help> This Measure
        gives the minimum transmit power
        value among the network lanes of
        the Client Transceiver
        "
	  ::= { pm10001otu4MesrOther 194 }



--- *****************************************************
---     LEAF for the clientNetRxPwrMin article
--- *****************************************************

pm10001otu4MesrclientNetRxPwrMin OBJECT-TYPE
	  SYNTAX Unsigned32 (0..65535)
	  MAX-ACCESS read-only
	  STATUS current
	  DESCRIPTION
        "
        Min Client Trscv Rx Power :This
        OID gives the minimum receive power
        value among the network lanes of
        the Client Transceiver, read in
        the DDM (Digital Diagnostic Monitoring)
        (Power = 10*log(AV_U16)-40) (Unit
        = dBm) <Help> This Measure gives
        the minimum receive power value
        among the network lanes of the
         Client Transceiver
        "
	  ::= { pm10001otu4MesrOther 195 }



--- *****************************************************
---     LEAF for the lineNetTxLaserOutputPwrMin article
--- *****************************************************

pm10001otu4MesrlineNetTxLaserOutputPwrMin OBJECT-TYPE
	  SYNTAX Unsigned32 (0..65535)
	  MAX-ACCESS read-only
	  STATUS current
	  DESCRIPTION
        "
        Min Line Trscv Tx Power :This
         OID gives the minimum Tx Laser
        transmit power value among the
         network lanes of the Line Transceiver,
        read in the DDM (Digital Diagnostic
        Monitoring)  (Power = AV_S16/100)
        (Unit = dBm) <Help> This Measure
        gives the minimum Tx Laser transmit
        power value among the network lanes
        of the Line Transceiver
        "
	  ::= { pm10001otu4MesrOther 196 }



--- *****************************************************
---     LEAF for the lineNetTxLaserTempMin article
--- *****************************************************

pm10001otu4MesrlineNetTxLaserTempMin OBJECT-TYPE
	  SYNTAX Unsigned32 (0..65535)
	  MAX-ACCESS read-only
	  STATUS current
	  DESCRIPTION
        "
        Min Line Trscv Tx Laser Temperature
        :This OID gives the minimum Tx
         Laser Temperature value among
         the network lanes of the Line
         Transceiver, read from the DDM
        (Digital Diagnostic Monitoring)
        (Temperature = AV_S16/256) (Unit
        = C) <Help> This Measure gives
         the minimum Tx Laser Temperature
        value among the network lanes of
        the Line Transceiver
        "
	  ::= { pm10001otu4MesrOther 197 }



--- *****************************************************
---     LEAF for the lineNetTxBiasCurrentMin article
--- *****************************************************

pm10001otu4MesrlineNetTxBiasCurrentMin OBJECT-TYPE
	  SYNTAX Unsigned32 (0..65535)
	  MAX-ACCESS read-only
	  STATUS current
	  DESCRIPTION
        "
        Min Line Trscv Tx Laser Bias :This
        OID gives the minimum Tx Laser
         Bias value among the network lanes
        of the Line Transceiver, read from
        the DDM (Digital Diagnostic Monitoring)
        (Bias = AV_S16/10) (Unit = mA)
         <Help> This Measure gives the
         minimum Tx Laser Bias value among
        the network lanes of the Line Transceiver
        "
	  ::= { pm10001otu4MesrOther 198 }



--- *****************************************************
---     LEAF for the lineNetRxInputPwrMin article
--- *****************************************************

pm10001otu4MesrlineNetRxInputPwrMin OBJECT-TYPE
	  SYNTAX Unsigned32 (0..65535)
	  MAX-ACCESS read-only
	  STATUS current
	  DESCRIPTION
        "
        Min Line Trscv Rx Power :This
         OID gives the minimum Receive
         power value among the network
         lanes of the Line Transceiver,
        read in the DDM (Digital Diagnostic
        Monitoring) (Power = AV_S16/100)
        (Unit = dBm) <Help> This Measure
        gives the minimum Receive power
        value among the network lanes of
        the Line Transceiver
        "
	  ::= { pm10001otu4MesrOther 199 }



--- *****************************************************
---     LEAF for the lineResidualChromaticDispMin article
--- *****************************************************

pm10001otu4MesrlineResidualChromaticDispMin OBJECT-TYPE
	  SYNTAX Unsigned32 (0..65535)
	  MAX-ACCESS read-only
	  STATUS current
	  DESCRIPTION
        "
        Min Residual Chromatic Dispersion
        :This OID gives the minimum Residual
        Chromatic Dispersion on the Line
        interface since the last measure
        reset (Dispersion = AV_S16*(-2))
          (Unit = ps/nm)<Help> This measure
        gives the minimum Residual Chromatic
        Dispersion on the Line interface
        since the last measure reset.
        "
	  ::= { pm10001otu4MesrOther 200 }



--- *****************************************************
---     LEAF for the lineDiffGroupDelayMin article
--- *****************************************************

pm10001otu4MesrlineDiffGroupDelayMin OBJECT-TYPE
	  SYNTAX Unsigned32 (0..65535)
	  MAX-ACCESS read-only
	  STATUS current
	  DESCRIPTION
        "
        Min Differential Group Delay :This
        OID gives the minimum Differential
        Group Delay  on the Line interface
        since the last measure reset (Delay
        = AV_S16)  (Unit = ps)<Help> This
        measure gives the minimum Differential
        Group Delay on the Line interface
        since the last measure reset.
        "
	  ::= { pm10001otu4MesrOther 201 }



--- *****************************************************
---     LEAF for the lineQFactorMin article
--- *****************************************************

pm10001otu4MesrlineQFactorMin OBJECT-TYPE
	  SYNTAX Unsigned32 (0..65535)
	  MAX-ACCESS read-only
	  STATUS current
	  DESCRIPTION
        "
        Min Q Factor :This OID gives the
        minimum Q Factor on the Line interface
        since the last measure reset (Q
        Factor = AV_U16)  (Unit = dB)<Help>
        This measure gives the minimum
         Q Factor on the Line interface
        since the last measure reset.
        "
	  ::= { pm10001otu4MesrOther 202 }



--- *****************************************************
---     LEAF for the lineCarrierFreqOffsetMin article
--- *****************************************************

pm10001otu4MesrlineCarrierFreqOffsetMin OBJECT-TYPE
	  SYNTAX Unsigned32 (0..65535)
	  MAX-ACCESS read-only
	  STATUS current
	  DESCRIPTION
        "
        Min Carrier Frequency Offset :This
        OID gives the minimum Carrier Frequency
        Offset on the Line interface since
        the last measure reset  (Offset
        = AV_S16)   (Unit = MHz)<Help>
         This measure gives the minimum
        Carrier Frequency Offset on the
        Line interface since the last measure
        reset
        "
	  ::= { pm10001otu4MesrOther 203 }



--- *****************************************************
---     LEAF for the lineOsnrMin article
--- *****************************************************

pm10001otu4MesrlineOsnrMin OBJECT-TYPE
	  SYNTAX Unsigned32 (0..65535)
	  MAX-ACCESS read-only
	  STATUS current
	  DESCRIPTION
        "
        Min OSNR :This OID gives the minimum
        OSNR on the Line interface since
        the last measure reset  (OSNR =
        AV_S16/10) (Unit = dB)<Help> This
        measure gives the minimum OSNR
         on the Line interface since the
        last measure reset.
        "
	  ::= { pm10001otu4MesrOther 204 }



--- *****************************************************
---     LEAF for the clientNetTxTempMax article
--- *****************************************************

pm10001otu4MesrclientNetTxTempMax OBJECT-TYPE
	  SYNTAX Unsigned32 (0..65535)
	  MAX-ACCESS read-only
	  STATUS current
	  DESCRIPTION
        "
        Max Client Trscv Laser Temperature
        :This OID gives the maximum Laser
        temperature value among the network
        lanes of the Client Transceiver,
        read from the DDM (Digital Diagnostic
        Monitoring) (Temperature = AV_S16/256)
        (Unit = C) <Help> This Measure
         gives the maximum Laser temperature
        value among the network lanes of
        the Client Transceiver
        "
	  ::= { pm10001otu4MesrOther 208 }



--- *****************************************************
---     LEAF for the clientNetTxBiasMax article
--- *****************************************************

pm10001otu4MesrclientNetTxBiasMax OBJECT-TYPE
	  SYNTAX Unsigned32 (0..65535)
	  MAX-ACCESS read-only
	  STATUS current
	  DESCRIPTION
        "
        Max Client Trscv Laser Bias :This
        OID gives the maximum Laser bias
        value among the network lanes of
        the Client Transceiver, read from
        the DDM (Digital Diagnostic Monitoring)
        (Bias = AV_U16/500) (Unit = mA)
        <Help> This Measure gives the maximum
        Laser bias value among the network
        lanes of the Client Transceiver
        "
	  ::= { pm10001otu4MesrOther 209 }



--- *****************************************************
---     LEAF for the clientNetTxPwrMax article
--- *****************************************************

pm10001otu4MesrclientNetTxPwrMax OBJECT-TYPE
	  SYNTAX Unsigned32 (0..65535)
	  MAX-ACCESS read-only
	  STATUS current
	  DESCRIPTION
        "
        Max Client Trscv Tx Power :This
        OID gives the maximum transmit
         power value among the network
         lanes of the Client Transceiver,
        read from the DDM (Digital Diagnostic
        Monitoring) (Power = 10*log(AV_U16)-40)
        (Unit = dBm) <Help> This Measure
        gives the maximum transmit power
        value among the network lanes of
        the Client Transceiver
        "
	  ::= { pm10001otu4MesrOther 210 }



--- *****************************************************
---     LEAF for the clientNetRxPwrMax article
--- *****************************************************

pm10001otu4MesrclientNetRxPwrMax OBJECT-TYPE
	  SYNTAX Unsigned32 (0..65535)
	  MAX-ACCESS read-only
	  STATUS current
	  DESCRIPTION
        "
        Max Client Trscv Rx Power :This
        OID gives the maximum receive power
        value among the network lanes of
        the Client Transceiver, read in
        the DDM (Digital Diagnostic Monitoring)
        (Power = 10*log(AV_U16)-40) (Unit
        = dBm) <Help> This Measure gives
        the maximum receive power value
        among the network lanes of the
         Client Transceiver
        "
	  ::= { pm10001otu4MesrOther 211 }



--- *****************************************************
---     LEAF for the lineNetTxLaserOutputPwrMax article
--- *****************************************************

pm10001otu4MesrlineNetTxLaserOutputPwrMax OBJECT-TYPE
	  SYNTAX Unsigned32 (0..65535)
	  MAX-ACCESS read-only
	  STATUS current
	  DESCRIPTION
        "
        Max Line Trscv Tx Power :This
         OID gives the maximum Tx Laser
        transmit power value among the
         network lanes of the Line Transceiver,
        read in the DDM (Digital Diagnostic
        Monitoring) (Power = AV_S16/100)
        (Unit = dBm) <Help> This Measure
        gives the maximum Tx Laser transmit
        power value among the network lanes
        of the Line Transceiver
        "
	  ::= { pm10001otu4MesrOther 212 }



--- *****************************************************
---     LEAF for the lineNetTxLaserTempMax article
--- *****************************************************

pm10001otu4MesrlineNetTxLaserTempMax OBJECT-TYPE
	  SYNTAX Unsigned32 (0..65535)
	  MAX-ACCESS read-only
	  STATUS current
	  DESCRIPTION
        "
        Max Line Trscv Tx Laser Temperature
        :This OID gives the maximum Tx
         Laser Temperature value among
         the network lanes of the Line
         Transceiver, read from the DDM
        (Digital Diagnostic Monitoring)
        (Temperature = AV_S16/256) (Unit
        = C) <Help> This Measure gives
         the maximum Tx Laser Temperature
        value among the network lanes of
        the Line Transceiver
        "
	  ::= { pm10001otu4MesrOther 213 }



--- *****************************************************
---     LEAF for the lineNetTxBiasCurrentMax article
--- *****************************************************

pm10001otu4MesrlineNetTxBiasCurrentMax OBJECT-TYPE
	  SYNTAX Unsigned32 (0..65535)
	  MAX-ACCESS read-only
	  STATUS current
	  DESCRIPTION
        "
        Max Line Trscv Tx Laser Bias :This
        OID gives the maximum Tx Laser
         Bias value among the network lanes
        of the Line Transceiver, read from
        the DDM (Digital Diagnostic Monitoring)
        (Bias = AV_S16/10) (Unit = mA)
         <Help> This Measure gives the
         maximum Tx Laser Bias value among
        the network lanes of the Line Transceiver
        "
	  ::= { pm10001otu4MesrOther 214 }



--- *****************************************************
---     LEAF for the lineNetRxInputPwrMax article
--- *****************************************************

pm10001otu4MesrlineNetRxInputPwrMax OBJECT-TYPE
	  SYNTAX Unsigned32 (0..65535)
	  MAX-ACCESS read-only
	  STATUS current
	  DESCRIPTION
        "
        Max Line Trscv Rx Power :This
         OID gives the maximum Receive
         power value among the network
         lanes of the Line Transceiver,
        read in the DDM (Digital Diagnostic
        Monitoring) (Power = AV_S16/100)
        (Unit = dBm) <Help> This Measure
        gives the maximum Receive power
        value among the network lanes of
        the Line Transceiver
        "
	  ::= { pm10001otu4MesrOther 215 }



--- *****************************************************
---     LEAF for the lineResidualChromaticDispMax article
--- *****************************************************

pm10001otu4MesrlineResidualChromaticDispMax OBJECT-TYPE
	  SYNTAX Unsigned32 (0..65535)
	  MAX-ACCESS read-only
	  STATUS current
	  DESCRIPTION
        "
        Max Residual Chromatic Dispersion
        :This OID gives the maximum Residual
        Chromatic Dispersion on the Line
        interface since the last measure
        reset (Dispersion = AV_S16*(-2))
          (Unit = ps/nm)<Help> This measure
        gives the maximum Residual Chromatic
        Dispersion on the Line interface
        since the last measure reset.
        "
	  ::= { pm10001otu4MesrOther 216 }



--- *****************************************************
---     LEAF for the lineDiffGroupDelayMax article
--- *****************************************************

pm10001otu4MesrlineDiffGroupDelayMax OBJECT-TYPE
	  SYNTAX Unsigned32 (0..65535)
	  MAX-ACCESS read-only
	  STATUS current
	  DESCRIPTION
        "
        Max Differential Group Delay :This
        OID gives the maximum Differential
        Group Delay  on the Line interface
        since the last measure reset  (Delay
        = AV_S16)   (Unit = ps)<Help> This
        measure gives the maximum Differential
        Group Delay on the Line interface
        since the last measure reset.
        "
	  ::= { pm10001otu4MesrOther 217 }



--- *****************************************************
---     LEAF for the lineQFactorMax article
--- *****************************************************

pm10001otu4MesrlineQFactorMax OBJECT-TYPE
	  SYNTAX Unsigned32 (0..65535)
	  MAX-ACCESS read-only
	  STATUS current
	  DESCRIPTION
        "
        Max Q Factor :This OID gives the
        maximum Q Factor on the Line interface
        since the last measure reset (Q
        Factor = AV_U16)    (Unit = dB)<Help>
        This measure gives the maximum
         Q Factor on the Line interface
        since the last measure reset.
        "
	  ::= { pm10001otu4MesrOther 218 }



--- *****************************************************
---     LEAF for the lineCarrierFreqOffsetMax article
--- *****************************************************

pm10001otu4MesrlineCarrierFreqOffsetMax OBJECT-TYPE
	  SYNTAX Unsigned32 (0..65535)
	  MAX-ACCESS read-only
	  STATUS current
	  DESCRIPTION
        "
        Max Carrier Frequency Offset :This
        OID gives the maximum Carrier Frequency
        Offset on the Line interface since
        the last measure reset  (Offset
        = AV_S16)   (Unit = MHz)<Help>
         This measure gives the maximum
        Carrier Frequency Offset on the
        Line interface since the last measure
        reset.
        "
	  ::= { pm10001otu4MesrOther 219 }



--- *****************************************************
---     LEAF for the lineOsnrMax article
--- *****************************************************

pm10001otu4MesrlineOsnrMax OBJECT-TYPE
	  SYNTAX Unsigned32 (0..65535)
	  MAX-ACCESS read-only
	  STATUS current
	  DESCRIPTION
        "
        Max OSNR :This OID gives the maximum
        OSNR on the Line interface since
        the last measure reset   (OSNR
         = AV_S16/10) (Unit = dB)<Help>
        This measure gives the maximum
         OSNR on the Line interface since
        the last measure reset
        "
	  ::= { pm10001otu4MesrOther 220 }








--- *****************************************************
--- $$$$$$$$$$$$$$$$$$$$$$$$$$$$$$$$$$$$$$$$$$$$$$$$$$$$$
---     PERFORMANCE
--- $$$$$$$$$$$$$$$$$$$$$$$$$$$$$$$$$$$$$$$$$$$$$$$$$$$$$
--- *****************************************************



--- *****************************************************
---     Leaf of the telecomInputClientCurrent15Stat
--- *****************************************************
--- *********************************************************
---     TABLE for the pm10001otu4PerfTelecomInputClientCurrent15Stat articles
--- *********************************************************

pm10001otu4PerfTelecomInputClientCurrent15StatTable OBJECT-TYPE
	SYNTAX  SEQUENCE OF Pm10001otu4PerfTelecomInputClientCurrent15StatEntry
	MAX-ACCESS not-accessible
	STATUS current
	DESCRIPTION
        "
        List of pm10001otu4PerfTelecomInputClientCurrent15Stat
        Article
        "
	::= { pm10001otu4MonPerfClient 16 }


pm10001otu4PerfTelecomInputClientCurrent15StatEntry OBJECT-TYPE
	SYNTAX Pm10001otu4PerfTelecomInputClientCurrent15StatEntry
	MAX-ACCESS not-accessible
	STATUS current
	DESCRIPTION
        "
        Row definition for the pm10001otu4PerfTelecomInputClientCurrent15Stat
        table
        "
	INDEX   { pm10001otu4PerfTelecomInputClientCurrent15StatIndex }
	::= { pm10001otu4PerfTelecomInputClientCurrent15StatTable 1 }


Pm10001otu4PerfTelecomInputClientCurrent15StatEntry ::=
	SEQUENCE {
	pm10001otu4PerfTelecomInputClientCurrent15StatIndex
		INTEGER,
	pm10001otu4PerfTelecomInputClientCurrent15StatInvCvPortn
		EkiOnOff,
	pm10001otu4PerfTelecomInputClientCurrent15StatCvValuePortn
		Unsigned32,
	pm10001otu4PerfTelecomInputClientCurrent15StatInvEsPortn
		EkiOnOff,
	pm10001otu4PerfTelecomInputClientCurrent15StatEsValuePortn
		Unsigned32,
	pm10001otu4PerfTelecomInputClientCurrent15StatInvSesPortn
		EkiOnOff,
	pm10001otu4PerfTelecomInputClientCurrent15StatSesValuePortn
		Unsigned32,
	pm10001otu4PerfTelecomInputClientCurrent15StatInvSefsPortn
		EkiOnOff,
	pm10001otu4PerfTelecomInputClientCurrent15StatSefsValuePortn
		Unsigned32,
	pm10001otu4PerfTelecomInputClientCurrent15StatInvUasPortn
		EkiOnOff,
	pm10001otu4PerfTelecomInputClientCurrent15StatUasValuePortn
		Unsigned32
	}


pm10001otu4PerfTelecomInputClientCurrent15StatIndex OBJECT-TYPE
	SYNTAX  INTEGER(0..128)
	MAX-ACCESS  read-only
	STATUS current
	DESCRIPTION
        "
        Index definition for the pm10001otu4PerfTelecomInputClientCurrent15Stat
        table
        "
	::= { pm10001otu4PerfTelecomInputClientCurrent15StatEntry 1 }


pm10001otu4PerfTelecomInputClientCurrent15StatInvCvPortn OBJECT-TYPE
	SYNTAX  EkiOnOff
	MAX-ACCESS read-only
	STATUS current
	DESCRIPTION
        "
        Current 15-min EBC counter inv.
        :This OID indicates that the current
        15-min Coding Violation counter
        is invalid
        "
	::= { pm10001otu4PerfTelecomInputClientCurrent15StatEntry 2 }


pm10001otu4PerfTelecomInputClientCurrent15StatCvValuePortn OBJECT-TYPE
	SYNTAX  Unsigned32
	MAX-ACCESS read-only
	STATUS current
	DESCRIPTION
        "
        Current 15-min EBC counter :This
        OID gives the current 15-min Coding
        Violation counter value
        "
	::= { pm10001otu4PerfTelecomInputClientCurrent15StatEntry 3 }


pm10001otu4PerfTelecomInputClientCurrent15StatInvEsPortn OBJECT-TYPE
	SYNTAX  EkiOnOff
	MAX-ACCESS read-only
	STATUS current
	DESCRIPTION
        "
        Current 15-min ES counter inv.
        :This OID indicates that the current
        15-min Errored Second counter is
        invalid
        "
	::= { pm10001otu4PerfTelecomInputClientCurrent15StatEntry 4 }


pm10001otu4PerfTelecomInputClientCurrent15StatEsValuePortn OBJECT-TYPE
	SYNTAX  Unsigned32
	MAX-ACCESS read-only
	STATUS current
	DESCRIPTION
        "
        Current 15-min ES counter :This
        OID gives the current 15-min Errored
        Second counter value
        "
	::= { pm10001otu4PerfTelecomInputClientCurrent15StatEntry 5 }


pm10001otu4PerfTelecomInputClientCurrent15StatInvSesPortn OBJECT-TYPE
	SYNTAX  EkiOnOff
	MAX-ACCESS read-only
	STATUS current
	DESCRIPTION
        "
        Current 15-min SES counter inv.
        :This OID indicates that the current
        15-min severely Errored Second
         counter is invalid
        "
	::= { pm10001otu4PerfTelecomInputClientCurrent15StatEntry 6 }


pm10001otu4PerfTelecomInputClientCurrent15StatSesValuePortn OBJECT-TYPE
	SYNTAX  Unsigned32
	MAX-ACCESS read-only
	STATUS current
	DESCRIPTION
        "
        Current 15-min SES counter :This
        OID gives the current 15-min severely
        Errored Second counter value
        "
	::= { pm10001otu4PerfTelecomInputClientCurrent15StatEntry 7 }


pm10001otu4PerfTelecomInputClientCurrent15StatInvSefsPortn OBJECT-TYPE
	SYNTAX  EkiOnOff
	MAX-ACCESS read-only
	STATUS current
	DESCRIPTION
        "
        Current 15-min SEFS counter inv.
        :This OID indicates that the current
        15-min severely Errored Framing
        Second counter is invalid
        "
	::= { pm10001otu4PerfTelecomInputClientCurrent15StatEntry 8 }


pm10001otu4PerfTelecomInputClientCurrent15StatSefsValuePortn OBJECT-TYPE
	SYNTAX  Unsigned32
	MAX-ACCESS read-only
	STATUS current
	DESCRIPTION
        "
        Current 15-min SEFS counter :This
        OID gives the current 15-min severely
        Errored Framing Second counter
         value
        "
	::= { pm10001otu4PerfTelecomInputClientCurrent15StatEntry 9 }


pm10001otu4PerfTelecomInputClientCurrent15StatInvUasPortn OBJECT-TYPE
	SYNTAX  EkiOnOff
	MAX-ACCESS read-only
	STATUS current
	DESCRIPTION
        "
        Current 15-min UAS counter inv.
        :This OID indicates that the current
        15-min UnAvailable Second counter
        is invalid
        "
	::= { pm10001otu4PerfTelecomInputClientCurrent15StatEntry 10 }


pm10001otu4PerfTelecomInputClientCurrent15StatUasValuePortn OBJECT-TYPE
	SYNTAX  Unsigned32
	MAX-ACCESS read-only
	STATUS current
	DESCRIPTION
        "
        Current 15-min UAS counter :This
        OID gives the current 15-min UnAvailable
        Second counter value
        "
	::= { pm10001otu4PerfTelecomInputClientCurrent15StatEntry 11 }


--- *****************************************************
---     Leaf of the telecomInputClientPast15Stat
--- *****************************************************
--- *********************************************************
---     TABLE for the pm10001otu4PerfTelecomInputClientPast15StatHistory articles
--- *********************************************************

pm10001otu4PerfTelecomInputClientPast15StatHistoryPort1Table OBJECT-TYPE
	SYNTAX  SEQUENCE OF Pm10001otu4PerfTelecomInputClientPast15StatHistoryPort1Entry
	MAX-ACCESS not-accessible
	STATUS current
	DESCRIPTION
        "
        List of pm10001otu4PerfTelecomInputClientPast15StatHistory
        Article
        "
	::= { pm10001otu4MonPerfClient 32 }


pm10001otu4PerfTelecomInputClientPast15StatHistoryPort1Entry OBJECT-TYPE
	SYNTAX Pm10001otu4PerfTelecomInputClientPast15StatHistoryPort1Entry
	MAX-ACCESS not-accessible
	STATUS current
	DESCRIPTION
        "
        Row definition for the pm10001otu4PerfTelecomInputClientPast15StatHistory
        table
        "
	INDEX   { pm10001otu4PerfTelecomInputClientPast15StatHistoryPort1Index }
	::= { pm10001otu4PerfTelecomInputClientPast15StatHistoryPort1Table 1 }


Pm10001otu4PerfTelecomInputClientPast15StatHistoryPort1Entry ::=
	SEQUENCE {
	pm10001otu4PerfTelecomInputClientPast15StatHistoryPort1Index
		INTEGER,
	pm10001otu4PerfTelecomInputClientPast15StatHistoryInvCvPort1
		EkiOnOff,
	pm10001otu4PerfTelecomInputClientPast15StatHistoryCvValuePort1
		Unsigned32,
	pm10001otu4PerfTelecomInputClientPast15StatHistoryInvEsPort1
		EkiOnOff,
	pm10001otu4PerfTelecomInputClientPast15StatHistoryEsValuePort1
		Unsigned32,
	pm10001otu4PerfTelecomInputClientPast15StatHistoryInvSesPort1
		EkiOnOff,
	pm10001otu4PerfTelecomInputClientPast15StatHistorySesValuePort1
		Unsigned32,
	pm10001otu4PerfTelecomInputClientPast15StatHistoryInvSefsPort1
		EkiOnOff,
	pm10001otu4PerfTelecomInputClientPast15StatHistorySefsValuePort1
		Unsigned32,
	pm10001otu4PerfTelecomInputClientPast15StatHistoryInvUasPort1
		EkiOnOff,
	pm10001otu4PerfTelecomInputClientPast15StatHistoryUasValuePort1
		Unsigned32
	}


pm10001otu4PerfTelecomInputClientPast15StatHistoryPort1Index OBJECT-TYPE
	SYNTAX  INTEGER(0..128)
	MAX-ACCESS  read-only
	STATUS current
	DESCRIPTION
        "
        Index definition for the pm10001otu4PerfTelecomInputClientPast15StatHistory
        table
        "
	::= { pm10001otu4PerfTelecomInputClientPast15StatHistoryPort1Entry 1 }


pm10001otu4PerfTelecomInputClientPast15StatHistoryInvCvPort1 OBJECT-TYPE
	SYNTAX  EkiOnOff
	MAX-ACCESS read-only
	STATUS current
	DESCRIPTION
        "
        Previous 15-min EBC counter inv.
        :This OID indicates that the previous
        15-min Coding Violation counter
        is invalid
        "
	::= { pm10001otu4PerfTelecomInputClientPast15StatHistoryPort1Entry 2 }


pm10001otu4PerfTelecomInputClientPast15StatHistoryCvValuePort1 OBJECT-TYPE
	SYNTAX  Unsigned32
	MAX-ACCESS read-only
	STATUS current
	DESCRIPTION
        "
        Previous 15-min EBC counter :This
        OID gives the previous 15-min Coding
        Violation counter value
        "
	::= { pm10001otu4PerfTelecomInputClientPast15StatHistoryPort1Entry 3 }


pm10001otu4PerfTelecomInputClientPast15StatHistoryInvEsPort1 OBJECT-TYPE
	SYNTAX  EkiOnOff
	MAX-ACCESS read-only
	STATUS current
	DESCRIPTION
        "
        Previous 15-min ES counter inv.
        :This OID indicates that the previous
        15-min Errored Second counter is
        invalid
        "
	::= { pm10001otu4PerfTelecomInputClientPast15StatHistoryPort1Entry 4 }


pm10001otu4PerfTelecomInputClientPast15StatHistoryEsValuePort1 OBJECT-TYPE
	SYNTAX  Unsigned32
	MAX-ACCESS read-only
	STATUS current
	DESCRIPTION
        "
        Previous 15-min ES counter :This
        OID gives the previous 15-min Errored
        Second counter value
        "
	::= { pm10001otu4PerfTelecomInputClientPast15StatHistoryPort1Entry 5 }


pm10001otu4PerfTelecomInputClientPast15StatHistoryInvSesPort1 OBJECT-TYPE
	SYNTAX  EkiOnOff
	MAX-ACCESS read-only
	STATUS current
	DESCRIPTION
        "
        Previous 15-min SES counter inv.
        :This OID indicates that the previous
        15-min severely Errored Second
         counter is invalid
        "
	::= { pm10001otu4PerfTelecomInputClientPast15StatHistoryPort1Entry 6 }


pm10001otu4PerfTelecomInputClientPast15StatHistorySesValuePort1 OBJECT-TYPE
	SYNTAX  Unsigned32
	MAX-ACCESS read-only
	STATUS current
	DESCRIPTION
        "
        Previous 15-min SES counter :This
        OID gives the previous 15-min severely
        Errored Second counter value
        "
	::= { pm10001otu4PerfTelecomInputClientPast15StatHistoryPort1Entry 7 }


pm10001otu4PerfTelecomInputClientPast15StatHistoryInvSefsPort1 OBJECT-TYPE
	SYNTAX  EkiOnOff
	MAX-ACCESS read-only
	STATUS current
	DESCRIPTION
        "
        Previous 15-min SEFS counter inv.
        :This OID indicates that the previous
        15-min severely Errored Framing
        Second counter is invalid
        "
	::= { pm10001otu4PerfTelecomInputClientPast15StatHistoryPort1Entry 8 }


pm10001otu4PerfTelecomInputClientPast15StatHistorySefsValuePort1 OBJECT-TYPE
	SYNTAX  Unsigned32
	MAX-ACCESS read-only
	STATUS current
	DESCRIPTION
        "
        Previous 15-min SEFS counter :This
        OID gives the previous 15-min severely
        Errored Framing Second counter
         value
        "
	::= { pm10001otu4PerfTelecomInputClientPast15StatHistoryPort1Entry 9 }


pm10001otu4PerfTelecomInputClientPast15StatHistoryInvUasPort1 OBJECT-TYPE
	SYNTAX  EkiOnOff
	MAX-ACCESS read-only
	STATUS current
	DESCRIPTION
        "
        Previous 15-min UAS counter inv.
        :This OID indicates that the previous
        15-min UnAvailable Second counter
        is invalid
        "
	::= { pm10001otu4PerfTelecomInputClientPast15StatHistoryPort1Entry 10 }


pm10001otu4PerfTelecomInputClientPast15StatHistoryUasValuePort1 OBJECT-TYPE
	SYNTAX  Unsigned32
	MAX-ACCESS read-only
	STATUS current
	DESCRIPTION
        "
        Previous 15-min UAS counter :This
        OID gives the previous 15-min UnAvailable
        Second counter value
        "
	::= { pm10001otu4PerfTelecomInputClientPast15StatHistoryPort1Entry 11 }


--- *****************************************************
---     Leaf of the telecomInputClientCurrent24Stat
--- *****************************************************
--- *********************************************************
---     TABLE for the pm10001otu4PerfTelecomInputClientCurrent24Stat articles
--- *********************************************************

pm10001otu4PerfTelecomInputClientCurrent24StatTable OBJECT-TYPE
	SYNTAX  SEQUENCE OF Pm10001otu4PerfTelecomInputClientCurrent24StatEntry
	MAX-ACCESS not-accessible
	STATUS current
	DESCRIPTION
        "
        List of pm10001otu4PerfTelecomInputClientCurrent24Stat
        Article
        "
	::= { pm10001otu4MonPerfClient 48 }


pm10001otu4PerfTelecomInputClientCurrent24StatEntry OBJECT-TYPE
	SYNTAX Pm10001otu4PerfTelecomInputClientCurrent24StatEntry
	MAX-ACCESS not-accessible
	STATUS current
	DESCRIPTION
        "
        Row definition for the pm10001otu4PerfTelecomInputClientCurrent24Stat
        table
        "
	INDEX   { pm10001otu4PerfTelecomInputClientCurrent24StatIndex }
	::= { pm10001otu4PerfTelecomInputClientCurrent24StatTable 1 }


Pm10001otu4PerfTelecomInputClientCurrent24StatEntry ::=
	SEQUENCE {
	pm10001otu4PerfTelecomInputClientCurrent24StatIndex
		INTEGER,
	pm10001otu4PerfTelecomInputClientCurrent24StatInvCvPortn
		EkiOnOff,
	pm10001otu4PerfTelecomInputClientCurrent24StatCvValuePortn
		Unsigned32,
	pm10001otu4PerfTelecomInputClientCurrent24StatInvEsPortn
		EkiOnOff,
	pm10001otu4PerfTelecomInputClientCurrent24StatEsValuePortn
		Unsigned32,
	pm10001otu4PerfTelecomInputClientCurrent24StatInvSesPortn
		EkiOnOff,
	pm10001otu4PerfTelecomInputClientCurrent24StatSesValuePortn
		Unsigned32,
	pm10001otu4PerfTelecomInputClientCurrent24StatInvSefsPortn
		EkiOnOff,
	pm10001otu4PerfTelecomInputClientCurrent24StatSefsValuePortn
		Unsigned32,
	pm10001otu4PerfTelecomInputClientCurrent24StatInvUasPortn
		EkiOnOff,
	pm10001otu4PerfTelecomInputClientCurrent24StatUasValuePortn
		Unsigned32
	}


pm10001otu4PerfTelecomInputClientCurrent24StatIndex OBJECT-TYPE
	SYNTAX  INTEGER(0..128)
	MAX-ACCESS  read-only
	STATUS current
	DESCRIPTION
        "
        Index definition for the pm10001otu4PerfTelecomInputClientCurrent24Stat
        table
        "
	::= { pm10001otu4PerfTelecomInputClientCurrent24StatEntry 1 }


pm10001otu4PerfTelecomInputClientCurrent24StatInvCvPortn OBJECT-TYPE
	SYNTAX  EkiOnOff
	MAX-ACCESS read-only
	STATUS current
	DESCRIPTION
        "
        Current 24-hours EBC counter inv.
        :This OID indicates that the current
        24-hours Coding Violation counter
        is invalid
        "
	::= { pm10001otu4PerfTelecomInputClientCurrent24StatEntry 2 }


pm10001otu4PerfTelecomInputClientCurrent24StatCvValuePortn OBJECT-TYPE
	SYNTAX  Unsigned32
	MAX-ACCESS read-only
	STATUS current
	DESCRIPTION
        "
        Current 24-hours EBC counter :This
        OID gives the current 24-hours
         Coding Violation counter value
        "
	::= { pm10001otu4PerfTelecomInputClientCurrent24StatEntry 3 }


pm10001otu4PerfTelecomInputClientCurrent24StatInvEsPortn OBJECT-TYPE
	SYNTAX  EkiOnOff
	MAX-ACCESS read-only
	STATUS current
	DESCRIPTION
        "
        Current 24-hours ES counter inv.
        :This OID indicates that the current
        24-hours Errored Second counter
        is invalid
        "
	::= { pm10001otu4PerfTelecomInputClientCurrent24StatEntry 4 }


pm10001otu4PerfTelecomInputClientCurrent24StatEsValuePortn OBJECT-TYPE
	SYNTAX  Unsigned32
	MAX-ACCESS read-only
	STATUS current
	DESCRIPTION
        "
        Current 24-hours ES counter :This
        OID gives the current 24-hours
         Errored Second counter value
        "
	::= { pm10001otu4PerfTelecomInputClientCurrent24StatEntry 5 }


pm10001otu4PerfTelecomInputClientCurrent24StatInvSesPortn OBJECT-TYPE
	SYNTAX  EkiOnOff
	MAX-ACCESS read-only
	STATUS current
	DESCRIPTION
        "
        Current 24-hours SES counter inv.
        :This OID indicates that the current
        24-hours severely Errored Second
        counter is invalid
        "
	::= { pm10001otu4PerfTelecomInputClientCurrent24StatEntry 6 }


pm10001otu4PerfTelecomInputClientCurrent24StatSesValuePortn OBJECT-TYPE
	SYNTAX  Unsigned32
	MAX-ACCESS read-only
	STATUS current
	DESCRIPTION
        "
        Current 24-hours SES counter :This
        OID gives the current 24-hours
         severely Errored Second counter
        value
        "
	::= { pm10001otu4PerfTelecomInputClientCurrent24StatEntry 7 }


pm10001otu4PerfTelecomInputClientCurrent24StatInvSefsPortn OBJECT-TYPE
	SYNTAX  EkiOnOff
	MAX-ACCESS read-only
	STATUS current
	DESCRIPTION
        "
        Current 24-hours SEFS counter
         inv. :This OID indicates that
         the current 24-hours severely
         Errored Framing Second counter
        is invalid
        "
	::= { pm10001otu4PerfTelecomInputClientCurrent24StatEntry 8 }


pm10001otu4PerfTelecomInputClientCurrent24StatSefsValuePortn OBJECT-TYPE
	SYNTAX  Unsigned32
	MAX-ACCESS read-only
	STATUS current
	DESCRIPTION
        "
        Current 24-hours SEFS counter
         :This OID gives the current 24-hours
        severely Errored Framing Second
        counter value
        "
	::= { pm10001otu4PerfTelecomInputClientCurrent24StatEntry 9 }


pm10001otu4PerfTelecomInputClientCurrent24StatInvUasPortn OBJECT-TYPE
	SYNTAX  EkiOnOff
	MAX-ACCESS read-only
	STATUS current
	DESCRIPTION
        "
        Current 24-hours UAS counter inv.
        :This OID indicates that the current
        24-hours UnAvailable Second counter
        is invalid
        "
	::= { pm10001otu4PerfTelecomInputClientCurrent24StatEntry 10 }


pm10001otu4PerfTelecomInputClientCurrent24StatUasValuePortn OBJECT-TYPE
	SYNTAX  Unsigned32
	MAX-ACCESS read-only
	STATUS current
	DESCRIPTION
        "
        Current 24-hours UAS counter :This
        OID gives the current 24-hours
         UnAvailable Second counter value
        "
	::= { pm10001otu4PerfTelecomInputClientCurrent24StatEntry 11 }


--- *****************************************************
---     Leaf of the telecomInputClientPast24Stat
--- *****************************************************
--- *********************************************************
---     TABLE for the pm10001otu4PerfTelecomInputClientPast24StatHistory articles
--- *********************************************************

pm10001otu4PerfTelecomInputClientPast24StatHistoryPort1Table OBJECT-TYPE
	SYNTAX  SEQUENCE OF Pm10001otu4PerfTelecomInputClientPast24StatHistoryPort1Entry
	MAX-ACCESS not-accessible
	STATUS current
	DESCRIPTION
        "
        List of pm10001otu4PerfTelecomInputClientPast24StatHistory
        Article
        "
	::= { pm10001otu4MonPerfClient 64 }


pm10001otu4PerfTelecomInputClientPast24StatHistoryPort1Entry OBJECT-TYPE
	SYNTAX Pm10001otu4PerfTelecomInputClientPast24StatHistoryPort1Entry
	MAX-ACCESS not-accessible
	STATUS current
	DESCRIPTION
        "
        Row definition for the pm10001otu4PerfTelecomInputClientPast24StatHistory
        table
        "
	INDEX   { pm10001otu4PerfTelecomInputClientPast24StatHistoryPort1Index }
	::= { pm10001otu4PerfTelecomInputClientPast24StatHistoryPort1Table 1 }


Pm10001otu4PerfTelecomInputClientPast24StatHistoryPort1Entry ::=
	SEQUENCE {
	pm10001otu4PerfTelecomInputClientPast24StatHistoryPort1Index
		INTEGER,
	pm10001otu4PerfTelecomInputClientPast24StatHistoryInvCvPort1
		EkiOnOff,
	pm10001otu4PerfTelecomInputClientPast24StatHistoryCvValuePort1
		Unsigned32,
	pm10001otu4PerfTelecomInputClientPast24StatHistoryInvEsPort1
		EkiOnOff,
	pm10001otu4PerfTelecomInputClientPast24StatHistoryEsValuePort1
		Unsigned32,
	pm10001otu4PerfTelecomInputClientPast24StatHistoryInvSesPort1
		EkiOnOff,
	pm10001otu4PerfTelecomInputClientPast24StatHistorySesValuePort1
		Unsigned32,
	pm10001otu4PerfTelecomInputClientPast24StatHistoryInvSefsPort1
		EkiOnOff,
	pm10001otu4PerfTelecomInputClientPast24StatHistorySefsValuePort1
		Unsigned32,
	pm10001otu4PerfTelecomInputClientPast24StatHistoryInvUasPort1
		EkiOnOff,
	pm10001otu4PerfTelecomInputClientPast24StatHistoryUasValuePort1
		Unsigned32
	}


pm10001otu4PerfTelecomInputClientPast24StatHistoryPort1Index OBJECT-TYPE
	SYNTAX  INTEGER(0..128)
	MAX-ACCESS  read-only
	STATUS current
	DESCRIPTION
        "
        Index definition for the pm10001otu4PerfTelecomInputClientPast24StatHistory
        table
        "
	::= { pm10001otu4PerfTelecomInputClientPast24StatHistoryPort1Entry 1 }


pm10001otu4PerfTelecomInputClientPast24StatHistoryInvCvPort1 OBJECT-TYPE
	SYNTAX  EkiOnOff
	MAX-ACCESS read-only
	STATUS current
	DESCRIPTION
        "
        Previous 24-hours EBC counter
         inv. :This OID indicates that
         the previous 24-hours Coding Violation
        counter is invalid
        "
	::= { pm10001otu4PerfTelecomInputClientPast24StatHistoryPort1Entry 2 }


pm10001otu4PerfTelecomInputClientPast24StatHistoryCvValuePort1 OBJECT-TYPE
	SYNTAX  Unsigned32
	MAX-ACCESS read-only
	STATUS current
	DESCRIPTION
        "
        Previous 24-hours EBC counter
         :This OID gives the previous 24-hours
        Coding Violation counter value
        "
	::= { pm10001otu4PerfTelecomInputClientPast24StatHistoryPort1Entry 3 }


pm10001otu4PerfTelecomInputClientPast24StatHistoryInvEsPort1 OBJECT-TYPE
	SYNTAX  EkiOnOff
	MAX-ACCESS read-only
	STATUS current
	DESCRIPTION
        "
        Previous 24-hours ES counter inv.
        :This OID indicates that the previous
        24-hours Errored Second counter
        is invalid
        "
	::= { pm10001otu4PerfTelecomInputClientPast24StatHistoryPort1Entry 4 }


pm10001otu4PerfTelecomInputClientPast24StatHistoryEsValuePort1 OBJECT-TYPE
	SYNTAX  Unsigned32
	MAX-ACCESS read-only
	STATUS current
	DESCRIPTION
        "
        Previous 24-hours ES counter :This
        OID gives the previous 24-hours
        Errored Second counter value
        "
	::= { pm10001otu4PerfTelecomInputClientPast24StatHistoryPort1Entry 5 }


pm10001otu4PerfTelecomInputClientPast24StatHistoryInvSesPort1 OBJECT-TYPE
	SYNTAX  EkiOnOff
	MAX-ACCESS read-only
	STATUS current
	DESCRIPTION
        "
        Previous 24-hours SES counter
         inv. :This OID indicates that
         the previous 24-hours severely
        Errored Second counter is invalid
        "
	::= { pm10001otu4PerfTelecomInputClientPast24StatHistoryPort1Entry 6 }


pm10001otu4PerfTelecomInputClientPast24StatHistorySesValuePort1 OBJECT-TYPE
	SYNTAX  Unsigned32
	MAX-ACCESS read-only
	STATUS current
	DESCRIPTION
        "
        Previous 24-hours SES counter
         :This OID gives the previous 24-hours
        severely Errored Second counter
        value
        "
	::= { pm10001otu4PerfTelecomInputClientPast24StatHistoryPort1Entry 7 }


pm10001otu4PerfTelecomInputClientPast24StatHistoryInvSefsPort1 OBJECT-TYPE
	SYNTAX  EkiOnOff
	MAX-ACCESS read-only
	STATUS current
	DESCRIPTION
        "
        Previous 24-hours SEFS counter
        inv. :This OID indicates that the
        previous 24-hours severely Errored
        Framing Second counter is invalid
        "
	::= { pm10001otu4PerfTelecomInputClientPast24StatHistoryPort1Entry 8 }


pm10001otu4PerfTelecomInputClientPast24StatHistorySefsValuePort1 OBJECT-TYPE
	SYNTAX  Unsigned32
	MAX-ACCESS read-only
	STATUS current
	DESCRIPTION
        "
        Previous 24-hours SEFS counter
        :This OID gives the previous 24-hours
        severely Errored Framing Second
        counter value
        "
	::= { pm10001otu4PerfTelecomInputClientPast24StatHistoryPort1Entry 9 }


pm10001otu4PerfTelecomInputClientPast24StatHistoryInvUasPort1 OBJECT-TYPE
	SYNTAX  EkiOnOff
	MAX-ACCESS read-only
	STATUS current
	DESCRIPTION
        "
        Previous 24-hours UAS counter
         inv. :This OID indicates that
         the previous 24-hours UnAvailable
        Second counter is invalid
        "
	::= { pm10001otu4PerfTelecomInputClientPast24StatHistoryPort1Entry 10 }


pm10001otu4PerfTelecomInputClientPast24StatHistoryUasValuePort1 OBJECT-TYPE
	SYNTAX  Unsigned32
	MAX-ACCESS read-only
	STATUS current
	DESCRIPTION
        "
        Previous 24-hours UAS counter
         :This OID gives the previous 24-hours
        UnAvailable Second counter value
        "
	::= { pm10001otu4PerfTelecomInputClientPast24StatHistoryPort1Entry 11 }


--- *****************************************************
---     Leaf of the telecomOutputClientCurrent15Stat
--- *****************************************************
--- *********************************************************
---     TABLE for the pm10001otu4PerfTelecomOutputClientCurrent15Stat articles
--- *********************************************************

pm10001otu4PerfTelecomOutputClientCurrent15StatTable OBJECT-TYPE
	SYNTAX  SEQUENCE OF Pm10001otu4PerfTelecomOutputClientCurrent15StatEntry
	MAX-ACCESS not-accessible
	STATUS current
	DESCRIPTION
        "
        List of pm10001otu4PerfTelecomOutputClientCurrent15Stat
        Article
        "
	::= { pm10001otu4MonPerfClient 80 }


pm10001otu4PerfTelecomOutputClientCurrent15StatEntry OBJECT-TYPE
	SYNTAX Pm10001otu4PerfTelecomOutputClientCurrent15StatEntry
	MAX-ACCESS not-accessible
	STATUS current
	DESCRIPTION
        "
        Row definition for the pm10001otu4PerfTelecomOutputClientCurrent15Stat
        table
        "
	INDEX   { pm10001otu4PerfTelecomOutputClientCurrent15StatIndex }
	::= { pm10001otu4PerfTelecomOutputClientCurrent15StatTable 1 }


Pm10001otu4PerfTelecomOutputClientCurrent15StatEntry ::=
	SEQUENCE {
	pm10001otu4PerfTelecomOutputClientCurrent15StatIndex
		INTEGER,
	pm10001otu4PerfTelecomOutputClientCurrent15StatInvCvPortn
		EkiOnOff,
	pm10001otu4PerfTelecomOutputClientCurrent15StatCvValuePortn
		Unsigned32,
	pm10001otu4PerfTelecomOutputClientCurrent15StatInvEsPortn
		EkiOnOff,
	pm10001otu4PerfTelecomOutputClientCurrent15StatEsValuePortn
		Unsigned32,
	pm10001otu4PerfTelecomOutputClientCurrent15StatInvSesPortn
		EkiOnOff,
	pm10001otu4PerfTelecomOutputClientCurrent15StatSesValuePortn
		Unsigned32,
	pm10001otu4PerfTelecomOutputClientCurrent15StatInvSefsPortn
		EkiOnOff,
	pm10001otu4PerfTelecomOutputClientCurrent15StatSefsValuePortn
		Unsigned32,
	pm10001otu4PerfTelecomOutputClientCurrent15StatInvUasPortn
		EkiOnOff,
	pm10001otu4PerfTelecomOutputClientCurrent15StatUasValuePortn
		Unsigned32
	}


pm10001otu4PerfTelecomOutputClientCurrent15StatIndex OBJECT-TYPE
	SYNTAX  INTEGER(0..128)
	MAX-ACCESS  read-only
	STATUS current
	DESCRIPTION
        "
        Index definition for the pm10001otu4PerfTelecomOutputClientCurrent15Stat
        table
        "
	::= { pm10001otu4PerfTelecomOutputClientCurrent15StatEntry 1 }


pm10001otu4PerfTelecomOutputClientCurrent15StatInvCvPortn OBJECT-TYPE
	SYNTAX  EkiOnOff
	MAX-ACCESS read-only
	STATUS current
	DESCRIPTION
        "
        Current 15-min EBC counter inv.
        :This OID indicates that the current
        15-min Coding Violation counter
        is invalid
        "
	::= { pm10001otu4PerfTelecomOutputClientCurrent15StatEntry 2 }


pm10001otu4PerfTelecomOutputClientCurrent15StatCvValuePortn OBJECT-TYPE
	SYNTAX  Unsigned32
	MAX-ACCESS read-only
	STATUS current
	DESCRIPTION
        "
        Current 15-min EBC counter :This
        OID gives the current 15-min Coding
        Violation counter value
        "
	::= { pm10001otu4PerfTelecomOutputClientCurrent15StatEntry 3 }


pm10001otu4PerfTelecomOutputClientCurrent15StatInvEsPortn OBJECT-TYPE
	SYNTAX  EkiOnOff
	MAX-ACCESS read-only
	STATUS current
	DESCRIPTION
        "
        Current 15-min ES counter inv.
        :This OID indicates that the current
        15-min Errored Second counter is
        invalid
        "
	::= { pm10001otu4PerfTelecomOutputClientCurrent15StatEntry 4 }


pm10001otu4PerfTelecomOutputClientCurrent15StatEsValuePortn OBJECT-TYPE
	SYNTAX  Unsigned32
	MAX-ACCESS read-only
	STATUS current
	DESCRIPTION
        "
        Current 15-min ES counter :This
        OID gives the current 15-min Errored
        Second counter value
        "
	::= { pm10001otu4PerfTelecomOutputClientCurrent15StatEntry 5 }


pm10001otu4PerfTelecomOutputClientCurrent15StatInvSesPortn OBJECT-TYPE
	SYNTAX  EkiOnOff
	MAX-ACCESS read-only
	STATUS current
	DESCRIPTION
        "
        Current 15-min SES counter inv.
        :This OID indicates that the current
        15-min severely Errored Second
         counter is invalid
        "
	::= { pm10001otu4PerfTelecomOutputClientCurrent15StatEntry 6 }


pm10001otu4PerfTelecomOutputClientCurrent15StatSesValuePortn OBJECT-TYPE
	SYNTAX  Unsigned32
	MAX-ACCESS read-only
	STATUS current
	DESCRIPTION
        "
        Current 15-min SES counter :This
        OID gives the current 15-min severely
        Errored Second counter value
        "
	::= { pm10001otu4PerfTelecomOutputClientCurrent15StatEntry 7 }


pm10001otu4PerfTelecomOutputClientCurrent15StatInvSefsPortn OBJECT-TYPE
	SYNTAX  EkiOnOff
	MAX-ACCESS read-only
	STATUS current
	DESCRIPTION
        "
        Current 15-min SEFS counter inv.
        :This OID indicates that the current
        15-min severely Errored Framing
        Second counter is invalid
        "
	::= { pm10001otu4PerfTelecomOutputClientCurrent15StatEntry 8 }


pm10001otu4PerfTelecomOutputClientCurrent15StatSefsValuePortn OBJECT-TYPE
	SYNTAX  Unsigned32
	MAX-ACCESS read-only
	STATUS current
	DESCRIPTION
        "
        Current 15-min SEFS counter :This
        OID gives the current 15-min severely
        Errored Framing Second counter
         value
        "
	::= { pm10001otu4PerfTelecomOutputClientCurrent15StatEntry 9 }


pm10001otu4PerfTelecomOutputClientCurrent15StatInvUasPortn OBJECT-TYPE
	SYNTAX  EkiOnOff
	MAX-ACCESS read-only
	STATUS current
	DESCRIPTION
        "
        Current 15-min UAS counter inv.
        :This OID indicates that the current
        15-min UnAvailable Second counter
        is invalid
        "
	::= { pm10001otu4PerfTelecomOutputClientCurrent15StatEntry 10 }


pm10001otu4PerfTelecomOutputClientCurrent15StatUasValuePortn OBJECT-TYPE
	SYNTAX  Unsigned32
	MAX-ACCESS read-only
	STATUS current
	DESCRIPTION
        "
        Current 15-min UAS counter :This
        OID gives the current 15-min UnAvailable
        Second counter value
        "
	::= { pm10001otu4PerfTelecomOutputClientCurrent15StatEntry 11 }


--- *****************************************************
---     Leaf of the telecomOutputClientPast15Stat
--- *****************************************************
--- *********************************************************
---     TABLE for the pm10001otu4PerfTelecomOutputClientPast15StatHistory articles
--- *********************************************************

pm10001otu4PerfTelecomOutputClientPast15StatHistoryPort1Table OBJECT-TYPE
	SYNTAX  SEQUENCE OF Pm10001otu4PerfTelecomOutputClientPast15StatHistoryPort1Entry
	MAX-ACCESS not-accessible
	STATUS current
	DESCRIPTION
        "
        List of pm10001otu4PerfTelecomOutputClientPast15StatHistory
        Article
        "
	::= { pm10001otu4MonPerfClient 96 }


pm10001otu4PerfTelecomOutputClientPast15StatHistoryPort1Entry OBJECT-TYPE
	SYNTAX Pm10001otu4PerfTelecomOutputClientPast15StatHistoryPort1Entry
	MAX-ACCESS not-accessible
	STATUS current
	DESCRIPTION
        "
        Row definition for the pm10001otu4PerfTelecomOutputClientPast15StatHistory
        table
        "
	INDEX   { pm10001otu4PerfTelecomOutputClientPast15StatHistoryPort1Index }
	::= { pm10001otu4PerfTelecomOutputClientPast15StatHistoryPort1Table 1 }


Pm10001otu4PerfTelecomOutputClientPast15StatHistoryPort1Entry ::=
	SEQUENCE {
	pm10001otu4PerfTelecomOutputClientPast15StatHistoryPort1Index
		INTEGER,
	pm10001otu4PerfTelecomOutputClientPast15StatHistoryInvCvPort1
		EkiOnOff,
	pm10001otu4PerfTelecomOutputClientPast15StatHistoryCvValuePort1
		Unsigned32,
	pm10001otu4PerfTelecomOutputClientPast15StatHistoryInvEsPort1
		EkiOnOff,
	pm10001otu4PerfTelecomOutputClientPast15StatHistoryEsValuePort1
		Unsigned32,
	pm10001otu4PerfTelecomOutputClientPast15StatHistoryInvSesPort1
		EkiOnOff,
	pm10001otu4PerfTelecomOutputClientPast15StatHistorySesValuePort1
		Unsigned32,
	pm10001otu4PerfTelecomOutputClientPast15StatHistoryInvSefsPort1
		EkiOnOff,
	pm10001otu4PerfTelecomOutputClientPast15StatHistorySefsValuePort1
		Unsigned32,
	pm10001otu4PerfTelecomOutputClientPast15StatHistoryInvUasPort1
		EkiOnOff,
	pm10001otu4PerfTelecomOutputClientPast15StatHistoryUasValuePort1
		Unsigned32
	}


pm10001otu4PerfTelecomOutputClientPast15StatHistoryPort1Index OBJECT-TYPE
	SYNTAX  INTEGER(0..128)
	MAX-ACCESS  read-only
	STATUS current
	DESCRIPTION
        "
        Index definition for the pm10001otu4PerfTelecomOutputClientPast15StatHistory
        table
        "
	::= { pm10001otu4PerfTelecomOutputClientPast15StatHistoryPort1Entry 1 }


pm10001otu4PerfTelecomOutputClientPast15StatHistoryInvCvPort1 OBJECT-TYPE
	SYNTAX  EkiOnOff
	MAX-ACCESS read-only
	STATUS current
	DESCRIPTION
        "
        Previous 15-min EBC counter inv.
        :This OID indicates that the previous
        15-min Coding Violation counter
        is invalid
        "
	::= { pm10001otu4PerfTelecomOutputClientPast15StatHistoryPort1Entry 2 }


pm10001otu4PerfTelecomOutputClientPast15StatHistoryCvValuePort1 OBJECT-TYPE
	SYNTAX  Unsigned32
	MAX-ACCESS read-only
	STATUS current
	DESCRIPTION
        "
        Previous 15-min EBC counter :This
        OID gives the previous 15-min Coding
        Violation counter value
        "
	::= { pm10001otu4PerfTelecomOutputClientPast15StatHistoryPort1Entry 3 }


pm10001otu4PerfTelecomOutputClientPast15StatHistoryInvEsPort1 OBJECT-TYPE
	SYNTAX  EkiOnOff
	MAX-ACCESS read-only
	STATUS current
	DESCRIPTION
        "
        Previous 15-min ES counter inv.
        :This OID indicates that the previous
        15-min Errored Second counter is
        invalid
        "
	::= { pm10001otu4PerfTelecomOutputClientPast15StatHistoryPort1Entry 4 }


pm10001otu4PerfTelecomOutputClientPast15StatHistoryEsValuePort1 OBJECT-TYPE
	SYNTAX  Unsigned32
	MAX-ACCESS read-only
	STATUS current
	DESCRIPTION
        "
        Previous 15-min ES counter :This
        OID gives the previous 15-min Errored
        Second counter value
        "
	::= { pm10001otu4PerfTelecomOutputClientPast15StatHistoryPort1Entry 5 }


pm10001otu4PerfTelecomOutputClientPast15StatHistoryInvSesPort1 OBJECT-TYPE
	SYNTAX  EkiOnOff
	MAX-ACCESS read-only
	STATUS current
	DESCRIPTION
        "
        Previous 15-min SES counter inv.
        :This OID indicates that the previous
        15-min severely Errored Second
         counter is invalid
        "
	::= { pm10001otu4PerfTelecomOutputClientPast15StatHistoryPort1Entry 6 }


pm10001otu4PerfTelecomOutputClientPast15StatHistorySesValuePort1 OBJECT-TYPE
	SYNTAX  Unsigned32
	MAX-ACCESS read-only
	STATUS current
	DESCRIPTION
        "
        Previous 15-min SES counter :This
        OID gives the previous 15-min severely
        Errored Second counter value
        "
	::= { pm10001otu4PerfTelecomOutputClientPast15StatHistoryPort1Entry 7 }


pm10001otu4PerfTelecomOutputClientPast15StatHistoryInvSefsPort1 OBJECT-TYPE
	SYNTAX  EkiOnOff
	MAX-ACCESS read-only
	STATUS current
	DESCRIPTION
        "
        Previous 15-min SEFS counter inv.
        :This OID indicates that the previous
        15-min severely Errored Framing
        Second counter is invalid
        "
	::= { pm10001otu4PerfTelecomOutputClientPast15StatHistoryPort1Entry 8 }


pm10001otu4PerfTelecomOutputClientPast15StatHistorySefsValuePort1 OBJECT-TYPE
	SYNTAX  Unsigned32
	MAX-ACCESS read-only
	STATUS current
	DESCRIPTION
        "
        Previous 15-min SEFS counter :This
        OID gives the previous 15-min severely
        Errored Framing Second counter
         value
        "
	::= { pm10001otu4PerfTelecomOutputClientPast15StatHistoryPort1Entry 9 }


pm10001otu4PerfTelecomOutputClientPast15StatHistoryInvUasPort1 OBJECT-TYPE
	SYNTAX  EkiOnOff
	MAX-ACCESS read-only
	STATUS current
	DESCRIPTION
        "
        Previous 15-min UAS counter inv.
        :This OID indicates that the previous
        15-min UnAvailable Second counter
        is invalid
        "
	::= { pm10001otu4PerfTelecomOutputClientPast15StatHistoryPort1Entry 10 }


pm10001otu4PerfTelecomOutputClientPast15StatHistoryUasValuePort1 OBJECT-TYPE
	SYNTAX  Unsigned32
	MAX-ACCESS read-only
	STATUS current
	DESCRIPTION
        "
        Previous 15-min UAS counter :This
        OID gives the previous 15-min UnAvailable
        Second counter value
        "
	::= { pm10001otu4PerfTelecomOutputClientPast15StatHistoryPort1Entry 11 }


--- *****************************************************
---     Leaf of the telecomOutputClientCurrent24Stat
--- *****************************************************
--- *********************************************************
---     TABLE for the pm10001otu4PerfTelecomOutputClientCurrent24Stat articles
--- *********************************************************

pm10001otu4PerfTelecomOutputClientCurrent24StatTable OBJECT-TYPE
	SYNTAX  SEQUENCE OF Pm10001otu4PerfTelecomOutputClientCurrent24StatEntry
	MAX-ACCESS not-accessible
	STATUS current
	DESCRIPTION
        "
        List of pm10001otu4PerfTelecomOutputClientCurrent24Stat
        Article
        "
	::= { pm10001otu4MonPerfClient 112 }


pm10001otu4PerfTelecomOutputClientCurrent24StatEntry OBJECT-TYPE
	SYNTAX Pm10001otu4PerfTelecomOutputClientCurrent24StatEntry
	MAX-ACCESS not-accessible
	STATUS current
	DESCRIPTION
        "
        Row definition for the pm10001otu4PerfTelecomOutputClientCurrent24Stat
        table
        "
	INDEX   { pm10001otu4PerfTelecomOutputClientCurrent24StatIndex }
	::= { pm10001otu4PerfTelecomOutputClientCurrent24StatTable 1 }


Pm10001otu4PerfTelecomOutputClientCurrent24StatEntry ::=
	SEQUENCE {
	pm10001otu4PerfTelecomOutputClientCurrent24StatIndex
		INTEGER,
	pm10001otu4PerfTelecomOutputClientCurrent24StatInvCvPortn
		EkiOnOff,
	pm10001otu4PerfTelecomOutputClientCurrent24StatCvValuePortn
		Unsigned32,
	pm10001otu4PerfTelecomOutputClientCurrent24StatInvEsPortn
		EkiOnOff,
	pm10001otu4PerfTelecomOutputClientCurrent24StatEsValuePortn
		Unsigned32,
	pm10001otu4PerfTelecomOutputClientCurrent24StatInvSesPortn
		EkiOnOff,
	pm10001otu4PerfTelecomOutputClientCurrent24StatSesValuePortn
		Unsigned32,
	pm10001otu4PerfTelecomOutputClientCurrent24StatInvSefsPortn
		EkiOnOff,
	pm10001otu4PerfTelecomOutputClientCurrent24StatSefsValuePortn
		Unsigned32,
	pm10001otu4PerfTelecomOutputClientCurrent24StatInvUasPortn
		EkiOnOff,
	pm10001otu4PerfTelecomOutputClientCurrent24StatUasValuePortn
		Unsigned32
	}


pm10001otu4PerfTelecomOutputClientCurrent24StatIndex OBJECT-TYPE
	SYNTAX  INTEGER(0..128)
	MAX-ACCESS  read-only
	STATUS current
	DESCRIPTION
        "
        Index definition for the pm10001otu4PerfTelecomOutputClientCurrent24Stat
        table
        "
	::= { pm10001otu4PerfTelecomOutputClientCurrent24StatEntry 1 }


pm10001otu4PerfTelecomOutputClientCurrent24StatInvCvPortn OBJECT-TYPE
	SYNTAX  EkiOnOff
	MAX-ACCESS read-only
	STATUS current
	DESCRIPTION
        "
        Current 24-hours EBC counter inv.
        :This OID indicates that the current
        24-hours Coding Violation counter
        is invalid
        "
	::= { pm10001otu4PerfTelecomOutputClientCurrent24StatEntry 2 }


pm10001otu4PerfTelecomOutputClientCurrent24StatCvValuePortn OBJECT-TYPE
	SYNTAX  Unsigned32
	MAX-ACCESS read-only
	STATUS current
	DESCRIPTION
        "
        Current 24-hours EBC counter :This
        OID gives the current 24-hours
         Coding Violation counter value
        "
	::= { pm10001otu4PerfTelecomOutputClientCurrent24StatEntry 3 }


pm10001otu4PerfTelecomOutputClientCurrent24StatInvEsPortn OBJECT-TYPE
	SYNTAX  EkiOnOff
	MAX-ACCESS read-only
	STATUS current
	DESCRIPTION
        "
        Current 24-hours ES counter inv.
        :This OID indicates that the current
        24-hours Errored Second counter
        is invalid
        "
	::= { pm10001otu4PerfTelecomOutputClientCurrent24StatEntry 4 }


pm10001otu4PerfTelecomOutputClientCurrent24StatEsValuePortn OBJECT-TYPE
	SYNTAX  Unsigned32
	MAX-ACCESS read-only
	STATUS current
	DESCRIPTION
        "
        Current 24-hours ES counter :This
        OID gives the current 24-hours
         Errored Second counter value
        "
	::= { pm10001otu4PerfTelecomOutputClientCurrent24StatEntry 5 }


pm10001otu4PerfTelecomOutputClientCurrent24StatInvSesPortn OBJECT-TYPE
	SYNTAX  EkiOnOff
	MAX-ACCESS read-only
	STATUS current
	DESCRIPTION
        "
        Current 24-hours SES counter inv.
        :This OID indicates that the current
        24-hours severely Errored Second
        counter is invalid
        "
	::= { pm10001otu4PerfTelecomOutputClientCurrent24StatEntry 6 }


pm10001otu4PerfTelecomOutputClientCurrent24StatSesValuePortn OBJECT-TYPE
	SYNTAX  Unsigned32
	MAX-ACCESS read-only
	STATUS current
	DESCRIPTION
        "
        Current 24-hours SES counter :This
        OID gives the current 24-hours
         severely Errored Second counter
        value
        "
	::= { pm10001otu4PerfTelecomOutputClientCurrent24StatEntry 7 }


pm10001otu4PerfTelecomOutputClientCurrent24StatInvSefsPortn OBJECT-TYPE
	SYNTAX  EkiOnOff
	MAX-ACCESS read-only
	STATUS current
	DESCRIPTION
        "
        Current 24-hours SEFS counter
         inv. :This OID indicates that
         the current 24-hours severely
         Errored Framing Second counter
        is invalid
        "
	::= { pm10001otu4PerfTelecomOutputClientCurrent24StatEntry 8 }


pm10001otu4PerfTelecomOutputClientCurrent24StatSefsValuePortn OBJECT-TYPE
	SYNTAX  Unsigned32
	MAX-ACCESS read-only
	STATUS current
	DESCRIPTION
        "
        Current 24-hours SEFS counter
         :This OID gives the current 24-hours
        severely Errored Framing Second
        counter value
        "
	::= { pm10001otu4PerfTelecomOutputClientCurrent24StatEntry 9 }


pm10001otu4PerfTelecomOutputClientCurrent24StatInvUasPortn OBJECT-TYPE
	SYNTAX  EkiOnOff
	MAX-ACCESS read-only
	STATUS current
	DESCRIPTION
        "
        Current 24-hours UAS counter inv.
        :This OID indicates that the current
        24-hours UnAvailable Second counter
        is invalid
        "
	::= { pm10001otu4PerfTelecomOutputClientCurrent24StatEntry 10 }


pm10001otu4PerfTelecomOutputClientCurrent24StatUasValuePortn OBJECT-TYPE
	SYNTAX  Unsigned32
	MAX-ACCESS read-only
	STATUS current
	DESCRIPTION
        "
        Current 24-hours UAS counter :This
        OID gives the current 24-hours
         UnAvailable Second counter value
        "
	::= { pm10001otu4PerfTelecomOutputClientCurrent24StatEntry 11 }


--- *****************************************************
---     Leaf of the telecomOutputClientPast24Stat
--- *****************************************************
--- *********************************************************
---     TABLE for the pm10001otu4PerfTelecomOutputClientPast24StatHistory articles
--- *********************************************************

pm10001otu4PerfTelecomOutputClientPast24StatHistoryPort1Table OBJECT-TYPE
	SYNTAX  SEQUENCE OF Pm10001otu4PerfTelecomOutputClientPast24StatHistoryPort1Entry
	MAX-ACCESS not-accessible
	STATUS current
	DESCRIPTION
        "
        List of pm10001otu4PerfTelecomOutputClientPast24StatHistory
        Article
        "
	::= { pm10001otu4MonPerfClient 128 }


pm10001otu4PerfTelecomOutputClientPast24StatHistoryPort1Entry OBJECT-TYPE
	SYNTAX Pm10001otu4PerfTelecomOutputClientPast24StatHistoryPort1Entry
	MAX-ACCESS not-accessible
	STATUS current
	DESCRIPTION
        "
        Row definition for the pm10001otu4PerfTelecomOutputClientPast24StatHistory
        table
        "
	INDEX   { pm10001otu4PerfTelecomOutputClientPast24StatHistoryPort1Index }
	::= { pm10001otu4PerfTelecomOutputClientPast24StatHistoryPort1Table 1 }


Pm10001otu4PerfTelecomOutputClientPast24StatHistoryPort1Entry ::=
	SEQUENCE {
	pm10001otu4PerfTelecomOutputClientPast24StatHistoryPort1Index
		INTEGER,
	pm10001otu4PerfTelecomOutputClientPast24StatHistoryInvCvPort1
		EkiOnOff,
	pm10001otu4PerfTelecomOutputClientPast24StatHistoryCvValuePort1
		Unsigned32,
	pm10001otu4PerfTelecomOutputClientPast24StatHistoryInvEsPort1
		EkiOnOff,
	pm10001otu4PerfTelecomOutputClientPast24StatHistoryEsValuePort1
		Unsigned32,
	pm10001otu4PerfTelecomOutputClientPast24StatHistoryInvSesPort1
		EkiOnOff,
	pm10001otu4PerfTelecomOutputClientPast24StatHistorySesValuePort1
		Unsigned32,
	pm10001otu4PerfTelecomOutputClientPast24StatHistoryInvSefsPort1
		EkiOnOff,
	pm10001otu4PerfTelecomOutputClientPast24StatHistorySefsValuePort1
		Unsigned32,
	pm10001otu4PerfTelecomOutputClientPast24StatHistoryInvUasPort1
		EkiOnOff,
	pm10001otu4PerfTelecomOutputClientPast24StatHistoryUasValuePort1
		Unsigned32
	}


pm10001otu4PerfTelecomOutputClientPast24StatHistoryPort1Index OBJECT-TYPE
	SYNTAX  INTEGER(0..128)
	MAX-ACCESS  read-only
	STATUS current
	DESCRIPTION
        "
        Index definition for the pm10001otu4PerfTelecomOutputClientPast24StatHistory
        table
        "
	::= { pm10001otu4PerfTelecomOutputClientPast24StatHistoryPort1Entry 1 }


pm10001otu4PerfTelecomOutputClientPast24StatHistoryInvCvPort1 OBJECT-TYPE
	SYNTAX  EkiOnOff
	MAX-ACCESS read-only
	STATUS current
	DESCRIPTION
        "
        Previous 24-hours EBC counter
         inv. :This OID indicates that
         the previous 24-hours Coding Violation
        counter is invalid
        "
	::= { pm10001otu4PerfTelecomOutputClientPast24StatHistoryPort1Entry 2 }


pm10001otu4PerfTelecomOutputClientPast24StatHistoryCvValuePort1 OBJECT-TYPE
	SYNTAX  Unsigned32
	MAX-ACCESS read-only
	STATUS current
	DESCRIPTION
        "
        Previous 24-hours EBC counter
         :This OID gives the previous 24-hours
        Coding Violation counter value
        "
	::= { pm10001otu4PerfTelecomOutputClientPast24StatHistoryPort1Entry 3 }


pm10001otu4PerfTelecomOutputClientPast24StatHistoryInvEsPort1 OBJECT-TYPE
	SYNTAX  EkiOnOff
	MAX-ACCESS read-only
	STATUS current
	DESCRIPTION
        "
        Previous 24-hours ES counter inv.
        :This OID indicates that the previous
        24-hours Errored Second counter
        is invalid
        "
	::= { pm10001otu4PerfTelecomOutputClientPast24StatHistoryPort1Entry 4 }


pm10001otu4PerfTelecomOutputClientPast24StatHistoryEsValuePort1 OBJECT-TYPE
	SYNTAX  Unsigned32
	MAX-ACCESS read-only
	STATUS current
	DESCRIPTION
        "
        Previous 24-hours ES counter :This
        OID gives the previous 24-hours
        Errored Second counter value
        "
	::= { pm10001otu4PerfTelecomOutputClientPast24StatHistoryPort1Entry 5 }


pm10001otu4PerfTelecomOutputClientPast24StatHistoryInvSesPort1 OBJECT-TYPE
	SYNTAX  EkiOnOff
	MAX-ACCESS read-only
	STATUS current
	DESCRIPTION
        "
        Previous 24-hours SES counter
         inv. :This OID indicates that
         the previous 24-hours severely
        Errored Second counter is invalid
        "
	::= { pm10001otu4PerfTelecomOutputClientPast24StatHistoryPort1Entry 6 }


pm10001otu4PerfTelecomOutputClientPast24StatHistorySesValuePort1 OBJECT-TYPE
	SYNTAX  Unsigned32
	MAX-ACCESS read-only
	STATUS current
	DESCRIPTION
        "
        Previous 24-hours SES counter
         :This OID gives the previous 24-hours
        severely Errored Second counter
        value
        "
	::= { pm10001otu4PerfTelecomOutputClientPast24StatHistoryPort1Entry 7 }


pm10001otu4PerfTelecomOutputClientPast24StatHistoryInvSefsPort1 OBJECT-TYPE
	SYNTAX  EkiOnOff
	MAX-ACCESS read-only
	STATUS current
	DESCRIPTION
        "
        Previous 24-hours SEFS counter
        inv. :This OID indicates that the
        previous 24-hours severely Errored
        Framing Second counter is invalid
        "
	::= { pm10001otu4PerfTelecomOutputClientPast24StatHistoryPort1Entry 8 }


pm10001otu4PerfTelecomOutputClientPast24StatHistorySefsValuePort1 OBJECT-TYPE
	SYNTAX  Unsigned32
	MAX-ACCESS read-only
	STATUS current
	DESCRIPTION
        "
        Previous 24-hours SEFS counter
        :This OID gives the previous 24-hours
        severely Errored Framing Second
        counter value
        "
	::= { pm10001otu4PerfTelecomOutputClientPast24StatHistoryPort1Entry 9 }


pm10001otu4PerfTelecomOutputClientPast24StatHistoryInvUasPort1 OBJECT-TYPE
	SYNTAX  EkiOnOff
	MAX-ACCESS read-only
	STATUS current
	DESCRIPTION
        "
        Previous 24-hours UAS counter
         inv. :This OID indicates that
         the previous 24-hours UnAvailable
        Second counter is invalid
        "
	::= { pm10001otu4PerfTelecomOutputClientPast24StatHistoryPort1Entry 10 }


pm10001otu4PerfTelecomOutputClientPast24StatHistoryUasValuePort1 OBJECT-TYPE
	SYNTAX  Unsigned32
	MAX-ACCESS read-only
	STATUS current
	DESCRIPTION
        "
        Previous 24-hours UAS counter
         :This OID gives the previous 24-hours
        UnAvailable Second counter value
        "
	::= { pm10001otu4PerfTelecomOutputClientPast24StatHistoryPort1Entry 11 }


--- *****************************************************
---     Leaf of the telecomLinePostFecCurrent15Stat
--- *****************************************************
--- *********************************************************
---     TABLE for the pm10001otu4PerfTelecomLinePostFecCurrent15Stat articles
--- *********************************************************

pm10001otu4PerfTelecomLinePostFecCurrent15StatTable OBJECT-TYPE
	SYNTAX  SEQUENCE OF Pm10001otu4PerfTelecomLinePostFecCurrent15StatEntry
	MAX-ACCESS not-accessible
	STATUS current
	DESCRIPTION
        "
        List of pm10001otu4PerfTelecomLinePostFecCurrent15Stat
        Article
        "
	::= { pm10001otu4MonPerfLine 192 }


pm10001otu4PerfTelecomLinePostFecCurrent15StatEntry OBJECT-TYPE
	SYNTAX Pm10001otu4PerfTelecomLinePostFecCurrent15StatEntry
	MAX-ACCESS not-accessible
	STATUS current
	DESCRIPTION
        "
        Row definition for the pm10001otu4PerfTelecomLinePostFecCurrent15Stat
        table
        "
	INDEX   { pm10001otu4PerfTelecomLinePostFecCurrent15StatIndex }
	::= { pm10001otu4PerfTelecomLinePostFecCurrent15StatTable 1 }


Pm10001otu4PerfTelecomLinePostFecCurrent15StatEntry ::=
	SEQUENCE {
	pm10001otu4PerfTelecomLinePostFecCurrent15StatIndex
		INTEGER,
	pm10001otu4PerfTelecomLinePostFecCurrent15StatInvCvPortn
		EkiOnOff,
	pm10001otu4PerfTelecomLinePostFecCurrent15StatCvValuePortn
		Unsigned32,
	pm10001otu4PerfTelecomLinePostFecCurrent15StatInvEsPortn
		EkiOnOff,
	pm10001otu4PerfTelecomLinePostFecCurrent15StatEsValuePortn
		Unsigned32,
	pm10001otu4PerfTelecomLinePostFecCurrent15StatInvSesPortn
		EkiOnOff,
	pm10001otu4PerfTelecomLinePostFecCurrent15StatSesValuePortn
		Unsigned32,
	pm10001otu4PerfTelecomLinePostFecCurrent15StatInvSefsPortn
		EkiOnOff,
	pm10001otu4PerfTelecomLinePostFecCurrent15StatSefsValuePortn
		Unsigned32,
	pm10001otu4PerfTelecomLinePostFecCurrent15StatInvUasPortn
		EkiOnOff,
	pm10001otu4PerfTelecomLinePostFecCurrent15StatUasValuePortn
		Unsigned32
	}


pm10001otu4PerfTelecomLinePostFecCurrent15StatIndex OBJECT-TYPE
	SYNTAX  INTEGER(0..128)
	MAX-ACCESS  read-only
	STATUS current
	DESCRIPTION
        "
        Index definition for the pm10001otu4PerfTelecomLinePostFecCurrent15Stat
        table
        "
	::= { pm10001otu4PerfTelecomLinePostFecCurrent15StatEntry 1 }


pm10001otu4PerfTelecomLinePostFecCurrent15StatInvCvPortn OBJECT-TYPE
	SYNTAX  EkiOnOff
	MAX-ACCESS read-only
	STATUS current
	DESCRIPTION
        "
        Current 15-min EBC counter inv.
        :This OID indicates that the current
        15-min Coding Violation counter
        is invalid
        "
	::= { pm10001otu4PerfTelecomLinePostFecCurrent15StatEntry 2 }


pm10001otu4PerfTelecomLinePostFecCurrent15StatCvValuePortn OBJECT-TYPE
	SYNTAX  Unsigned32
	MAX-ACCESS read-only
	STATUS current
	DESCRIPTION
        "
        Current 15-min EBC counter :This
        OID gives the current 15-min Coding
        Violation counter value
        "
	::= { pm10001otu4PerfTelecomLinePostFecCurrent15StatEntry 3 }


pm10001otu4PerfTelecomLinePostFecCurrent15StatInvEsPortn OBJECT-TYPE
	SYNTAX  EkiOnOff
	MAX-ACCESS read-only
	STATUS current
	DESCRIPTION
        "
        Current 15-min ES counter inv.
        :This OID indicates that the current
        15-min Errored Second counter is
        invalid
        "
	::= { pm10001otu4PerfTelecomLinePostFecCurrent15StatEntry 4 }


pm10001otu4PerfTelecomLinePostFecCurrent15StatEsValuePortn OBJECT-TYPE
	SYNTAX  Unsigned32
	MAX-ACCESS read-only
	STATUS current
	DESCRIPTION
        "
        Current 15-min ES counter :This
        OID gives the current 15-min Errored
        Second counter value
        "
	::= { pm10001otu4PerfTelecomLinePostFecCurrent15StatEntry 5 }


pm10001otu4PerfTelecomLinePostFecCurrent15StatInvSesPortn OBJECT-TYPE
	SYNTAX  EkiOnOff
	MAX-ACCESS read-only
	STATUS current
	DESCRIPTION
        "
        Current 15-min SES counter inv.
        :This OID indicates that the current
        15-min severely Errored Second
         counter is invalid
        "
	::= { pm10001otu4PerfTelecomLinePostFecCurrent15StatEntry 6 }


pm10001otu4PerfTelecomLinePostFecCurrent15StatSesValuePortn OBJECT-TYPE
	SYNTAX  Unsigned32
	MAX-ACCESS read-only
	STATUS current
	DESCRIPTION
        "
        Current 15-min SES counter :This
        OID gives the current 15-min severely
        Errored Second counter value
        "
	::= { pm10001otu4PerfTelecomLinePostFecCurrent15StatEntry 7 }


pm10001otu4PerfTelecomLinePostFecCurrent15StatInvSefsPortn OBJECT-TYPE
	SYNTAX  EkiOnOff
	MAX-ACCESS read-only
	STATUS current
	DESCRIPTION
        "
        Current 15-min SEFS counter inv.
        :This OID indicates that the current
        15-min severely Errored Framing
        Second counter is invalid
        "
	::= { pm10001otu4PerfTelecomLinePostFecCurrent15StatEntry 8 }


pm10001otu4PerfTelecomLinePostFecCurrent15StatSefsValuePortn OBJECT-TYPE
	SYNTAX  Unsigned32
	MAX-ACCESS read-only
	STATUS current
	DESCRIPTION
        "
        Current 15-min SEFS counter :This
        OID gives the current 15-min severely
        Errored Framing Second counter
         value
        "
	::= { pm10001otu4PerfTelecomLinePostFecCurrent15StatEntry 9 }


pm10001otu4PerfTelecomLinePostFecCurrent15StatInvUasPortn OBJECT-TYPE
	SYNTAX  EkiOnOff
	MAX-ACCESS read-only
	STATUS current
	DESCRIPTION
        "
        Current 15-min UAS counter inv.
        :This OID indicates that the current
        15-min UnAvailable Second counter
        is invalid
        "
	::= { pm10001otu4PerfTelecomLinePostFecCurrent15StatEntry 10 }


pm10001otu4PerfTelecomLinePostFecCurrent15StatUasValuePortn OBJECT-TYPE
	SYNTAX  Unsigned32
	MAX-ACCESS read-only
	STATUS current
	DESCRIPTION
        "
        Current 15-min UAS counter :This
        OID gives the current 15-min UnAvailable
        Second counter value
        "
	::= { pm10001otu4PerfTelecomLinePostFecCurrent15StatEntry 11 }


--- *****************************************************
---     Leaf of the telecomLinePostFecPast15Stat
--- *****************************************************
--- *********************************************************
---     TABLE for the pm10001otu4PerfTelecomLinePostFecPast15StatHistory articles
--- *********************************************************

pm10001otu4PerfTelecomLinePostFecPast15StatHistoryPort1Table OBJECT-TYPE
	SYNTAX  SEQUENCE OF Pm10001otu4PerfTelecomLinePostFecPast15StatHistoryPort1Entry
	MAX-ACCESS not-accessible
	STATUS current
	DESCRIPTION
        "
        List of pm10001otu4PerfTelecomLinePostFecPast15StatHistory
        Article
        "
	::= { pm10001otu4MonPerfLine 193 }


pm10001otu4PerfTelecomLinePostFecPast15StatHistoryPort1Entry OBJECT-TYPE
	SYNTAX Pm10001otu4PerfTelecomLinePostFecPast15StatHistoryPort1Entry
	MAX-ACCESS not-accessible
	STATUS current
	DESCRIPTION
        "
        Row definition for the pm10001otu4PerfTelecomLinePostFecPast15StatHistory
        table
        "
	INDEX   { pm10001otu4PerfTelecomLinePostFecPast15StatHistoryPort1Index }
	::= { pm10001otu4PerfTelecomLinePostFecPast15StatHistoryPort1Table 1 }


Pm10001otu4PerfTelecomLinePostFecPast15StatHistoryPort1Entry ::=
	SEQUENCE {
	pm10001otu4PerfTelecomLinePostFecPast15StatHistoryPort1Index
		INTEGER,
	pm10001otu4PerfTelecomLinePostFecPast15StatHistoryInvCvPort1
		EkiOnOff,
	pm10001otu4PerfTelecomLinePostFecPast15StatHistoryCvValuePort1
		Unsigned32,
	pm10001otu4PerfTelecomLinePostFecPast15StatHistoryInvEsPort1
		EkiOnOff,
	pm10001otu4PerfTelecomLinePostFecPast15StatHistoryEsValuePort1
		Unsigned32,
	pm10001otu4PerfTelecomLinePostFecPast15StatHistoryInvSesPort1
		EkiOnOff,
	pm10001otu4PerfTelecomLinePostFecPast15StatHistorySesValuePort1
		Unsigned32,
	pm10001otu4PerfTelecomLinePostFecPast15StatHistoryInvSefsPort1
		EkiOnOff,
	pm10001otu4PerfTelecomLinePostFecPast15StatHistorySefsValuePort1
		Unsigned32,
	pm10001otu4PerfTelecomLinePostFecPast15StatHistoryInvUasPort1
		EkiOnOff,
	pm10001otu4PerfTelecomLinePostFecPast15StatHistoryUasValuePort1
		Unsigned32
	}


pm10001otu4PerfTelecomLinePostFecPast15StatHistoryPort1Index OBJECT-TYPE
	SYNTAX  INTEGER(0..128)
	MAX-ACCESS  read-only
	STATUS current
	DESCRIPTION
        "
        Index definition for the pm10001otu4PerfTelecomLinePostFecPast15StatHistory
        table
        "
	::= { pm10001otu4PerfTelecomLinePostFecPast15StatHistoryPort1Entry 1 }


pm10001otu4PerfTelecomLinePostFecPast15StatHistoryInvCvPort1 OBJECT-TYPE
	SYNTAX  EkiOnOff
	MAX-ACCESS read-only
	STATUS current
	DESCRIPTION
        "
        Previous 15-min EBC counter inv.
        :This OID indicates that the previous
        15-min Coding Violation counter
        is invalid
        "
	::= { pm10001otu4PerfTelecomLinePostFecPast15StatHistoryPort1Entry 2 }


pm10001otu4PerfTelecomLinePostFecPast15StatHistoryCvValuePort1 OBJECT-TYPE
	SYNTAX  Unsigned32
	MAX-ACCESS read-only
	STATUS current
	DESCRIPTION
        "
        Previous 15-min EBC counter :This
        OID gives the previous 15-min Coding
        Violation counter value
        "
	::= { pm10001otu4PerfTelecomLinePostFecPast15StatHistoryPort1Entry 3 }


pm10001otu4PerfTelecomLinePostFecPast15StatHistoryInvEsPort1 OBJECT-TYPE
	SYNTAX  EkiOnOff
	MAX-ACCESS read-only
	STATUS current
	DESCRIPTION
        "
        Previous 15-min ES counter inv.
        :This OID indicates that the previous
        15-min Errored Second counter is
        invalid
        "
	::= { pm10001otu4PerfTelecomLinePostFecPast15StatHistoryPort1Entry 4 }


pm10001otu4PerfTelecomLinePostFecPast15StatHistoryEsValuePort1 OBJECT-TYPE
	SYNTAX  Unsigned32
	MAX-ACCESS read-only
	STATUS current
	DESCRIPTION
        "
        Previous 15-min ES counter :This
        OID gives the previous 15-min Errored
        Second counter value
        "
	::= { pm10001otu4PerfTelecomLinePostFecPast15StatHistoryPort1Entry 5 }


pm10001otu4PerfTelecomLinePostFecPast15StatHistoryInvSesPort1 OBJECT-TYPE
	SYNTAX  EkiOnOff
	MAX-ACCESS read-only
	STATUS current
	DESCRIPTION
        "
        Previous 15-min SES counter inv.
        :This OID indicates that the previous
        15-min severely Errored Second
         counter is invalid
        "
	::= { pm10001otu4PerfTelecomLinePostFecPast15StatHistoryPort1Entry 6 }


pm10001otu4PerfTelecomLinePostFecPast15StatHistorySesValuePort1 OBJECT-TYPE
	SYNTAX  Unsigned32
	MAX-ACCESS read-only
	STATUS current
	DESCRIPTION
        "
        Previous 15-min SES counter :This
        OID gives the previous 15-min severely
        Errored Second counter value
        "
	::= { pm10001otu4PerfTelecomLinePostFecPast15StatHistoryPort1Entry 7 }


pm10001otu4PerfTelecomLinePostFecPast15StatHistoryInvSefsPort1 OBJECT-TYPE
	SYNTAX  EkiOnOff
	MAX-ACCESS read-only
	STATUS current
	DESCRIPTION
        "
        Previous 15-min SEFS counter inv.
        :This OID indicates that the previous
        15-min severely Errored Framing
        Second counter is invalid
        "
	::= { pm10001otu4PerfTelecomLinePostFecPast15StatHistoryPort1Entry 8 }


pm10001otu4PerfTelecomLinePostFecPast15StatHistorySefsValuePort1 OBJECT-TYPE
	SYNTAX  Unsigned32
	MAX-ACCESS read-only
	STATUS current
	DESCRIPTION
        "
        Previous 15-min SEFS counter :This
        OID gives the previous 15-min severely
        Errored Framing Second counter
         value
        "
	::= { pm10001otu4PerfTelecomLinePostFecPast15StatHistoryPort1Entry 9 }


pm10001otu4PerfTelecomLinePostFecPast15StatHistoryInvUasPort1 OBJECT-TYPE
	SYNTAX  EkiOnOff
	MAX-ACCESS read-only
	STATUS current
	DESCRIPTION
        "
        Previous 15-min UAS counter inv.
        :This OID indicates that the previous
        15-min UnAvailable Second counter
        is invalid
        "
	::= { pm10001otu4PerfTelecomLinePostFecPast15StatHistoryPort1Entry 10 }


pm10001otu4PerfTelecomLinePostFecPast15StatHistoryUasValuePort1 OBJECT-TYPE
	SYNTAX  Unsigned32
	MAX-ACCESS read-only
	STATUS current
	DESCRIPTION
        "
        Previous 15-min UAS counter :This
        OID gives the previous 15-min UnAvailable
        Second counter value
        "
	::= { pm10001otu4PerfTelecomLinePostFecPast15StatHistoryPort1Entry 11 }


--- *****************************************************
---     Leaf of the telecomLinePostFecCurrent24Stat
--- *****************************************************
--- *********************************************************
---     TABLE for the pm10001otu4PerfTelecomLinePostFecCurrent24Stat articles
--- *********************************************************

pm10001otu4PerfTelecomLinePostFecCurrent24StatTable OBJECT-TYPE
	SYNTAX  SEQUENCE OF Pm10001otu4PerfTelecomLinePostFecCurrent24StatEntry
	MAX-ACCESS not-accessible
	STATUS current
	DESCRIPTION
        "
        List of pm10001otu4PerfTelecomLinePostFecCurrent24Stat
        Article
        "
	::= { pm10001otu4MonPerfLine 194 }


pm10001otu4PerfTelecomLinePostFecCurrent24StatEntry OBJECT-TYPE
	SYNTAX Pm10001otu4PerfTelecomLinePostFecCurrent24StatEntry
	MAX-ACCESS not-accessible
	STATUS current
	DESCRIPTION
        "
        Row definition for the pm10001otu4PerfTelecomLinePostFecCurrent24Stat
        table
        "
	INDEX   { pm10001otu4PerfTelecomLinePostFecCurrent24StatIndex }
	::= { pm10001otu4PerfTelecomLinePostFecCurrent24StatTable 1 }


Pm10001otu4PerfTelecomLinePostFecCurrent24StatEntry ::=
	SEQUENCE {
	pm10001otu4PerfTelecomLinePostFecCurrent24StatIndex
		INTEGER,
	pm10001otu4PerfTelecomLinePostFecCurrent24StatInvCvPortn
		EkiOnOff,
	pm10001otu4PerfTelecomLinePostFecCurrent24StatCvValuePortn
		Unsigned32,
	pm10001otu4PerfTelecomLinePostFecCurrent24StatInvEsPortn
		EkiOnOff,
	pm10001otu4PerfTelecomLinePostFecCurrent24StatEsValuePortn
		Unsigned32,
	pm10001otu4PerfTelecomLinePostFecCurrent24StatInvSesPortn
		EkiOnOff,
	pm10001otu4PerfTelecomLinePostFecCurrent24StatSesValuePortn
		Unsigned32,
	pm10001otu4PerfTelecomLinePostFecCurrent24StatInvSefsPortn
		EkiOnOff,
	pm10001otu4PerfTelecomLinePostFecCurrent24StatSefsValuePortn
		Unsigned32,
	pm10001otu4PerfTelecomLinePostFecCurrent24StatInvUasPortn
		EkiOnOff,
	pm10001otu4PerfTelecomLinePostFecCurrent24StatUasValuePortn
		Unsigned32
	}


pm10001otu4PerfTelecomLinePostFecCurrent24StatIndex OBJECT-TYPE
	SYNTAX  INTEGER(0..128)
	MAX-ACCESS  read-only
	STATUS current
	DESCRIPTION
        "
        Index definition for the pm10001otu4PerfTelecomLinePostFecCurrent24Stat
        table
        "
	::= { pm10001otu4PerfTelecomLinePostFecCurrent24StatEntry 1 }


pm10001otu4PerfTelecomLinePostFecCurrent24StatInvCvPortn OBJECT-TYPE
	SYNTAX  EkiOnOff
	MAX-ACCESS read-only
	STATUS current
	DESCRIPTION
        "
        Current 24-hours EBC counter inv.
        :This OID indicates that the current
        24-hours Coding Violation counter
        is invalid
        "
	::= { pm10001otu4PerfTelecomLinePostFecCurrent24StatEntry 2 }


pm10001otu4PerfTelecomLinePostFecCurrent24StatCvValuePortn OBJECT-TYPE
	SYNTAX  Unsigned32
	MAX-ACCESS read-only
	STATUS current
	DESCRIPTION
        "
        Current 24-hours EBC counter :This
        OID gives the current 24-hours
         Coding Violation counter value
        "
	::= { pm10001otu4PerfTelecomLinePostFecCurrent24StatEntry 3 }


pm10001otu4PerfTelecomLinePostFecCurrent24StatInvEsPortn OBJECT-TYPE
	SYNTAX  EkiOnOff
	MAX-ACCESS read-only
	STATUS current
	DESCRIPTION
        "
        Current 24-hours ES counter inv.
        :This OID indicates that the current
        24-hours Errored Second counter
        is invalid
        "
	::= { pm10001otu4PerfTelecomLinePostFecCurrent24StatEntry 4 }


pm10001otu4PerfTelecomLinePostFecCurrent24StatEsValuePortn OBJECT-TYPE
	SYNTAX  Unsigned32
	MAX-ACCESS read-only
	STATUS current
	DESCRIPTION
        "
        Current 24-hours ES counter :This
        OID gives the current 24-hours
         Errored Second counter value
        "
	::= { pm10001otu4PerfTelecomLinePostFecCurrent24StatEntry 5 }


pm10001otu4PerfTelecomLinePostFecCurrent24StatInvSesPortn OBJECT-TYPE
	SYNTAX  EkiOnOff
	MAX-ACCESS read-only
	STATUS current
	DESCRIPTION
        "
        Current 24-hours SES counter inv.
        :This OID indicates that the current
        24-hours severely Errored Second
        counter is invalid
        "
	::= { pm10001otu4PerfTelecomLinePostFecCurrent24StatEntry 6 }


pm10001otu4PerfTelecomLinePostFecCurrent24StatSesValuePortn OBJECT-TYPE
	SYNTAX  Unsigned32
	MAX-ACCESS read-only
	STATUS current
	DESCRIPTION
        "
        Current 24-hours SES counter :This
        OID gives the current 24-hours
         severely Errored Second counter
        value
        "
	::= { pm10001otu4PerfTelecomLinePostFecCurrent24StatEntry 7 }


pm10001otu4PerfTelecomLinePostFecCurrent24StatInvSefsPortn OBJECT-TYPE
	SYNTAX  EkiOnOff
	MAX-ACCESS read-only
	STATUS current
	DESCRIPTION
        "
        Current 24-hours SEFS counter
         inv. :This OID indicates that
         the current 24-hours severely
         Errored Framing Second counter
        is invalid
        "
	::= { pm10001otu4PerfTelecomLinePostFecCurrent24StatEntry 8 }


pm10001otu4PerfTelecomLinePostFecCurrent24StatSefsValuePortn OBJECT-TYPE
	SYNTAX  Unsigned32
	MAX-ACCESS read-only
	STATUS current
	DESCRIPTION
        "
        Current 24-hours SEFS counter
         :This OID gives the current 24-hours
        severely Errored Framing Second
        counter value
        "
	::= { pm10001otu4PerfTelecomLinePostFecCurrent24StatEntry 9 }


pm10001otu4PerfTelecomLinePostFecCurrent24StatInvUasPortn OBJECT-TYPE
	SYNTAX  EkiOnOff
	MAX-ACCESS read-only
	STATUS current
	DESCRIPTION
        "
        Current 24-hours UAS counter inv.
        :This OID indicates that the current
        24-hours UnAvailable Second counter
        is invalid
        "
	::= { pm10001otu4PerfTelecomLinePostFecCurrent24StatEntry 10 }


pm10001otu4PerfTelecomLinePostFecCurrent24StatUasValuePortn OBJECT-TYPE
	SYNTAX  Unsigned32
	MAX-ACCESS read-only
	STATUS current
	DESCRIPTION
        "
        Current 24-hours UAS counter :This
        OID gives the current 24-hours
         UnAvailable Second counter value
        "
	::= { pm10001otu4PerfTelecomLinePostFecCurrent24StatEntry 11 }


--- *****************************************************
---     Leaf of the telecomLinePostFecPast24Stat
--- *****************************************************
--- *********************************************************
---     TABLE for the pm10001otu4PerfTelecomLinePostFecPast24StatHistory articles
--- *********************************************************

pm10001otu4PerfTelecomLinePostFecPast24StatHistoryPort1Table OBJECT-TYPE
	SYNTAX  SEQUENCE OF Pm10001otu4PerfTelecomLinePostFecPast24StatHistoryPort1Entry
	MAX-ACCESS not-accessible
	STATUS current
	DESCRIPTION
        "
        List of pm10001otu4PerfTelecomLinePostFecPast24StatHistory
        Article
        "
	::= { pm10001otu4MonPerfLine 195 }


pm10001otu4PerfTelecomLinePostFecPast24StatHistoryPort1Entry OBJECT-TYPE
	SYNTAX Pm10001otu4PerfTelecomLinePostFecPast24StatHistoryPort1Entry
	MAX-ACCESS not-accessible
	STATUS current
	DESCRIPTION
        "
        Row definition for the pm10001otu4PerfTelecomLinePostFecPast24StatHistory
        table
        "
	INDEX   { pm10001otu4PerfTelecomLinePostFecPast24StatHistoryPort1Index }
	::= { pm10001otu4PerfTelecomLinePostFecPast24StatHistoryPort1Table 1 }


Pm10001otu4PerfTelecomLinePostFecPast24StatHistoryPort1Entry ::=
	SEQUENCE {
	pm10001otu4PerfTelecomLinePostFecPast24StatHistoryPort1Index
		INTEGER,
	pm10001otu4PerfTelecomLinePostFecPast24StatHistoryInvCvPort1
		EkiOnOff,
	pm10001otu4PerfTelecomLinePostFecPast24StatHistoryCvValuePort1
		Unsigned32,
	pm10001otu4PerfTelecomLinePostFecPast24StatHistoryInvEsPort1
		EkiOnOff,
	pm10001otu4PerfTelecomLinePostFecPast24StatHistoryEsValuePort1
		Unsigned32,
	pm10001otu4PerfTelecomLinePostFecPast24StatHistoryInvSesPort1
		EkiOnOff,
	pm10001otu4PerfTelecomLinePostFecPast24StatHistorySesValuePort1
		Unsigned32,
	pm10001otu4PerfTelecomLinePostFecPast24StatHistoryInvSefsPort1
		EkiOnOff,
	pm10001otu4PerfTelecomLinePostFecPast24StatHistorySefsValuePort1
		Unsigned32,
	pm10001otu4PerfTelecomLinePostFecPast24StatHistoryInvUasPort1
		EkiOnOff,
	pm10001otu4PerfTelecomLinePostFecPast24StatHistoryUasValuePort1
		Unsigned32
	}


pm10001otu4PerfTelecomLinePostFecPast24StatHistoryPort1Index OBJECT-TYPE
	SYNTAX  INTEGER(0..128)
	MAX-ACCESS  read-only
	STATUS current
	DESCRIPTION
        "
        Index definition for the pm10001otu4PerfTelecomLinePostFecPast24StatHistory
        table
        "
	::= { pm10001otu4PerfTelecomLinePostFecPast24StatHistoryPort1Entry 1 }


pm10001otu4PerfTelecomLinePostFecPast24StatHistoryInvCvPort1 OBJECT-TYPE
	SYNTAX  EkiOnOff
	MAX-ACCESS read-only
	STATUS current
	DESCRIPTION
        "
        Previous 24-hours EBC counter
         inv. :This OID indicates that
         the previous 24-hours Coding Violation
        counter is invalid
        "
	::= { pm10001otu4PerfTelecomLinePostFecPast24StatHistoryPort1Entry 2 }


pm10001otu4PerfTelecomLinePostFecPast24StatHistoryCvValuePort1 OBJECT-TYPE
	SYNTAX  Unsigned32
	MAX-ACCESS read-only
	STATUS current
	DESCRIPTION
        "
        Previous 24-hours EBC counter
         :This OID gives the previous 24-hours
        Coding Violation counter value
        "
	::= { pm10001otu4PerfTelecomLinePostFecPast24StatHistoryPort1Entry 3 }


pm10001otu4PerfTelecomLinePostFecPast24StatHistoryInvEsPort1 OBJECT-TYPE
	SYNTAX  EkiOnOff
	MAX-ACCESS read-only
	STATUS current
	DESCRIPTION
        "
        Previous 24-hours ES counter inv.
        :This OID indicates that the previous
        24-hours Errored Second counter
        is invalid
        "
	::= { pm10001otu4PerfTelecomLinePostFecPast24StatHistoryPort1Entry 4 }


pm10001otu4PerfTelecomLinePostFecPast24StatHistoryEsValuePort1 OBJECT-TYPE
	SYNTAX  Unsigned32
	MAX-ACCESS read-only
	STATUS current
	DESCRIPTION
        "
        Previous 24-hours ES counter :This
        OID gives the previous 24-hours
        Errored Second counter value
        "
	::= { pm10001otu4PerfTelecomLinePostFecPast24StatHistoryPort1Entry 5 }


pm10001otu4PerfTelecomLinePostFecPast24StatHistoryInvSesPort1 OBJECT-TYPE
	SYNTAX  EkiOnOff
	MAX-ACCESS read-only
	STATUS current
	DESCRIPTION
        "
        Previous 24-hours SES counter
         inv. :This OID indicates that
         the previous 24-hours severely
        Errored Second counter is invalid
        "
	::= { pm10001otu4PerfTelecomLinePostFecPast24StatHistoryPort1Entry 6 }


pm10001otu4PerfTelecomLinePostFecPast24StatHistorySesValuePort1 OBJECT-TYPE
	SYNTAX  Unsigned32
	MAX-ACCESS read-only
	STATUS current
	DESCRIPTION
        "
        Previous 24-hours SES counter
         :This OID gives the previous 24-hours
        severely Errored Second counter
        value
        "
	::= { pm10001otu4PerfTelecomLinePostFecPast24StatHistoryPort1Entry 7 }


pm10001otu4PerfTelecomLinePostFecPast24StatHistoryInvSefsPort1 OBJECT-TYPE
	SYNTAX  EkiOnOff
	MAX-ACCESS read-only
	STATUS current
	DESCRIPTION
        "
        Previous 24-hours SEFS counter
        inv. :This OID indicates that the
        previous 24-hours severely Errored
        Framing Second counter is invalid
        "
	::= { pm10001otu4PerfTelecomLinePostFecPast24StatHistoryPort1Entry 8 }


pm10001otu4PerfTelecomLinePostFecPast24StatHistorySefsValuePort1 OBJECT-TYPE
	SYNTAX  Unsigned32
	MAX-ACCESS read-only
	STATUS current
	DESCRIPTION
        "
        Previous 24-hours SEFS counter
        :This OID gives the previous 24-hours
        severely Errored Framing Second
        counter value
        "
	::= { pm10001otu4PerfTelecomLinePostFecPast24StatHistoryPort1Entry 9 }


pm10001otu4PerfTelecomLinePostFecPast24StatHistoryInvUasPort1 OBJECT-TYPE
	SYNTAX  EkiOnOff
	MAX-ACCESS read-only
	STATUS current
	DESCRIPTION
        "
        Previous 24-hours UAS counter
         inv. :This OID indicates that
         the previous 24-hours UnAvailable
        Second counter is invalid
        "
	::= { pm10001otu4PerfTelecomLinePostFecPast24StatHistoryPort1Entry 10 }


pm10001otu4PerfTelecomLinePostFecPast24StatHistoryUasValuePort1 OBJECT-TYPE
	SYNTAX  Unsigned32
	MAX-ACCESS read-only
	STATUS current
	DESCRIPTION
        "
        Previous 24-hours UAS counter
         :This OID gives the previous 24-hours
        UnAvailable Second counter value
        "
	::= { pm10001otu4PerfTelecomLinePostFecPast24StatHistoryPort1Entry 11 }


--- *****************************************************
---     Leaf of the telecomBerLinePreFecCurrent15Stat
--- *****************************************************
--- *********************************************************
---     TABLE for the pm10001otu4PerfTelecomBerLinePreFecCurrent15Stat articles
--- *********************************************************

pm10001otu4PerfTelecomBerLinePreFecCurrent15StatTable OBJECT-TYPE
	SYNTAX  SEQUENCE OF Pm10001otu4PerfTelecomBerLinePreFecCurrent15StatEntry
	MAX-ACCESS not-accessible
	STATUS current
	DESCRIPTION
        "
        List of pm10001otu4PerfTelecomBerLinePreFecCurrent15Stat
        Article
        "
	::= { pm10001otu4MonPerfLine 208 }


pm10001otu4PerfTelecomBerLinePreFecCurrent15StatEntry OBJECT-TYPE
	SYNTAX Pm10001otu4PerfTelecomBerLinePreFecCurrent15StatEntry
	MAX-ACCESS not-accessible
	STATUS current
	DESCRIPTION
        "
        Row definition for the pm10001otu4PerfTelecomBerLinePreFecCurrent15Stat
        table
        "
	INDEX   { pm10001otu4PerfTelecomBerLinePreFecCurrent15StatIndex }
	::= { pm10001otu4PerfTelecomBerLinePreFecCurrent15StatTable 1 }


Pm10001otu4PerfTelecomBerLinePreFecCurrent15StatEntry ::=
	SEQUENCE {
	pm10001otu4PerfTelecomBerLinePreFecCurrent15StatIndex
		INTEGER,
	pm10001otu4PerfTelecomBerLinePreFecCurrent15StatInvBerPortn
		EkiOnOff,
	pm10001otu4PerfTelecomBerLinePreFecCurrent15StatBerValuePortn
		Unsigned32,
	pm10001otu4PerfTelecomBerLinePreFecCurrent15StatInvMinBerPortn
		EkiOnOff,
	pm10001otu4PerfTelecomBerLinePreFecCurrent15StatMinBerValuePortn
		Unsigned32,
	pm10001otu4PerfTelecomBerLinePreFecCurrent15StatInvMaxBerPortn
		EkiOnOff,
	pm10001otu4PerfTelecomBerLinePreFecCurrent15StatMaxBerValuePortn
		Unsigned32
	}


pm10001otu4PerfTelecomBerLinePreFecCurrent15StatIndex OBJECT-TYPE
	SYNTAX  INTEGER(0..128)
	MAX-ACCESS  read-only
	STATUS current
	DESCRIPTION
        "
        Index definition for the pm10001otu4PerfTelecomBerLinePreFecCurrent15Stat
        table
        "
	::= { pm10001otu4PerfTelecomBerLinePreFecCurrent15StatEntry 1 }


pm10001otu4PerfTelecomBerLinePreFecCurrent15StatInvBerPortn OBJECT-TYPE
	SYNTAX  EkiOnOff
	MAX-ACCESS read-only
	STATUS current
	DESCRIPTION
        "
        Current 15-min BER counter inv.
        :This OID indicates that the current
        15-min Coding Violation counter
        is invalid
        "
	::= { pm10001otu4PerfTelecomBerLinePreFecCurrent15StatEntry 2 }


pm10001otu4PerfTelecomBerLinePreFecCurrent15StatBerValuePortn OBJECT-TYPE
	SYNTAX  Unsigned32
	MAX-ACCESS read-only
	STATUS current
	DESCRIPTION
        "
        Current 15-min BER counter :This
        OID gives the current 15-min Coding
        Violation counter value
        "
	::= { pm10001otu4PerfTelecomBerLinePreFecCurrent15StatEntry 3 }


pm10001otu4PerfTelecomBerLinePreFecCurrent15StatInvMinBerPortn OBJECT-TYPE
	SYNTAX  EkiOnOff
	MAX-ACCESS read-only
	STATUS current
	DESCRIPTION
        "
        Current 15-min MinBER counter
         inv. :This OID indicates that
         the current 15-min Errored Second
        counter is invalid
        "
	::= { pm10001otu4PerfTelecomBerLinePreFecCurrent15StatEntry 4 }


pm10001otu4PerfTelecomBerLinePreFecCurrent15StatMinBerValuePortn OBJECT-TYPE
	SYNTAX  Unsigned32
	MAX-ACCESS read-only
	STATUS current
	DESCRIPTION
        "
        Current 15-min MinBER counter
         :This OID gives the current 15-min
        Errored Second counter value
        "
	::= { pm10001otu4PerfTelecomBerLinePreFecCurrent15StatEntry 5 }


pm10001otu4PerfTelecomBerLinePreFecCurrent15StatInvMaxBerPortn OBJECT-TYPE
	SYNTAX  EkiOnOff
	MAX-ACCESS read-only
	STATUS current
	DESCRIPTION
        "
        Current 15-min MaxBER counter
         inv. :This OID indicates that
         the current 15-min severely Errored
        Second counter is invalid
        "
	::= { pm10001otu4PerfTelecomBerLinePreFecCurrent15StatEntry 6 }


pm10001otu4PerfTelecomBerLinePreFecCurrent15StatMaxBerValuePortn OBJECT-TYPE
	SYNTAX  Unsigned32
	MAX-ACCESS read-only
	STATUS current
	DESCRIPTION
        "
        Current 15-min MaxBER counter
         :This OID gives the current 15-min
        severely Errored Second counter
        value
        "
	::= { pm10001otu4PerfTelecomBerLinePreFecCurrent15StatEntry 7 }


--- *****************************************************
---     Leaf of the telecomBerLinePreFecPast15Stat
--- *****************************************************
--- *********************************************************
---     TABLE for the pm10001otu4PerfTelecomBerLinePreFecPast15StatHistory articles
--- *********************************************************

pm10001otu4PerfTelecomBerLinePreFecPast15StatHistoryPort1Table OBJECT-TYPE
	SYNTAX  SEQUENCE OF Pm10001otu4PerfTelecomBerLinePreFecPast15StatHistoryPort1Entry
	MAX-ACCESS not-accessible
	STATUS current
	DESCRIPTION
        "
        List of pm10001otu4PerfTelecomBerLinePreFecPast15StatHistory
        Article
        "
	::= { pm10001otu4MonPerfLine 209 }


pm10001otu4PerfTelecomBerLinePreFecPast15StatHistoryPort1Entry OBJECT-TYPE
	SYNTAX Pm10001otu4PerfTelecomBerLinePreFecPast15StatHistoryPort1Entry
	MAX-ACCESS not-accessible
	STATUS current
	DESCRIPTION
        "
        Row definition for the pm10001otu4PerfTelecomBerLinePreFecPast15StatHistory
        table
        "
	INDEX   { pm10001otu4PerfTelecomBerLinePreFecPast15StatHistoryPort1Index }
	::= { pm10001otu4PerfTelecomBerLinePreFecPast15StatHistoryPort1Table 1 }


Pm10001otu4PerfTelecomBerLinePreFecPast15StatHistoryPort1Entry ::=
	SEQUENCE {
	pm10001otu4PerfTelecomBerLinePreFecPast15StatHistoryPort1Index
		INTEGER,
	pm10001otu4PerfTelecomBerLinePreFecPast15StatHistoryInvBerPort1
		EkiOnOff,
	pm10001otu4PerfTelecomBerLinePreFecPast15StatHistoryBerValuePort1
		Unsigned32,
	pm10001otu4PerfTelecomBerLinePreFecPast15StatHistoryInvMinBerPort1
		EkiOnOff,
	pm10001otu4PerfTelecomBerLinePreFecPast15StatHistoryMinBerValuePort1
		Unsigned32,
	pm10001otu4PerfTelecomBerLinePreFecPast15StatHistoryInvMaxBerPort1
		EkiOnOff,
	pm10001otu4PerfTelecomBerLinePreFecPast15StatHistoryMaxBerValuePort1
		Unsigned32
	}


pm10001otu4PerfTelecomBerLinePreFecPast15StatHistoryPort1Index OBJECT-TYPE
	SYNTAX  INTEGER(0..128)
	MAX-ACCESS  read-only
	STATUS current
	DESCRIPTION
        "
        Index definition for the pm10001otu4PerfTelecomBerLinePreFecPast15StatHistory
        table
        "
	::= { pm10001otu4PerfTelecomBerLinePreFecPast15StatHistoryPort1Entry 1 }


pm10001otu4PerfTelecomBerLinePreFecPast15StatHistoryInvBerPort1 OBJECT-TYPE
	SYNTAX  EkiOnOff
	MAX-ACCESS read-only
	STATUS current
	DESCRIPTION
        "
        Previous 15-min BER counter inv.
        :This OID indicates that the previous
        15-min Coding Violation counter
        is invalid
        "
	::= { pm10001otu4PerfTelecomBerLinePreFecPast15StatHistoryPort1Entry 2 }


pm10001otu4PerfTelecomBerLinePreFecPast15StatHistoryBerValuePort1 OBJECT-TYPE
	SYNTAX  Unsigned32
	MAX-ACCESS read-only
	STATUS current
	DESCRIPTION
        "
        Previous 15-min BER counter :This
        OID gives the previous 15-min Coding
        Violation counter value
        "
	::= { pm10001otu4PerfTelecomBerLinePreFecPast15StatHistoryPort1Entry 3 }


pm10001otu4PerfTelecomBerLinePreFecPast15StatHistoryInvMinBerPort1 OBJECT-TYPE
	SYNTAX  EkiOnOff
	MAX-ACCESS read-only
	STATUS current
	DESCRIPTION
        "
        Previous 15-min MinBER counter
        inv. :This OID indicates that the
        previous 15-min Errored Second
         counter is invalid
        "
	::= { pm10001otu4PerfTelecomBerLinePreFecPast15StatHistoryPort1Entry 4 }


pm10001otu4PerfTelecomBerLinePreFecPast15StatHistoryMinBerValuePort1 OBJECT-TYPE
	SYNTAX  Unsigned32
	MAX-ACCESS read-only
	STATUS current
	DESCRIPTION
        "
        Previous 15-min MinBER counter
        :This OID gives the previous 15-min
        Errored Second counter value
        "
	::= { pm10001otu4PerfTelecomBerLinePreFecPast15StatHistoryPort1Entry 5 }


pm10001otu4PerfTelecomBerLinePreFecPast15StatHistoryInvMaxBerPort1 OBJECT-TYPE
	SYNTAX  EkiOnOff
	MAX-ACCESS read-only
	STATUS current
	DESCRIPTION
        "
        Previous 15-min MaxBER counter
        inv. :This OID indicates that the
        previous 15-min severely Errored
        Second counter is invalid
        "
	::= { pm10001otu4PerfTelecomBerLinePreFecPast15StatHistoryPort1Entry 6 }


pm10001otu4PerfTelecomBerLinePreFecPast15StatHistoryMaxBerValuePort1 OBJECT-TYPE
	SYNTAX  Unsigned32
	MAX-ACCESS read-only
	STATUS current
	DESCRIPTION
        "
        Previous 15-min MaxBER counter
        :This OID gives the previous 15-min
        severely Errored Second counter
        value
        "
	::= { pm10001otu4PerfTelecomBerLinePreFecPast15StatHistoryPort1Entry 7 }


--- *****************************************************
---     Leaf of the telecomBerLinePreFecCurrent24Stat
--- *****************************************************
--- *********************************************************
---     TABLE for the pm10001otu4PerfTelecomBerLinePreFecCurrent24Stat articles
--- *********************************************************

pm10001otu4PerfTelecomBerLinePreFecCurrent24StatTable OBJECT-TYPE
	SYNTAX  SEQUENCE OF Pm10001otu4PerfTelecomBerLinePreFecCurrent24StatEntry
	MAX-ACCESS not-accessible
	STATUS current
	DESCRIPTION
        "
        List of pm10001otu4PerfTelecomBerLinePreFecCurrent24Stat
        Article
        "
	::= { pm10001otu4MonPerfLine 210 }


pm10001otu4PerfTelecomBerLinePreFecCurrent24StatEntry OBJECT-TYPE
	SYNTAX Pm10001otu4PerfTelecomBerLinePreFecCurrent24StatEntry
	MAX-ACCESS not-accessible
	STATUS current
	DESCRIPTION
        "
        Row definition for the pm10001otu4PerfTelecomBerLinePreFecCurrent24Stat
        table
        "
	INDEX   { pm10001otu4PerfTelecomBerLinePreFecCurrent24StatIndex }
	::= { pm10001otu4PerfTelecomBerLinePreFecCurrent24StatTable 1 }


Pm10001otu4PerfTelecomBerLinePreFecCurrent24StatEntry ::=
	SEQUENCE {
	pm10001otu4PerfTelecomBerLinePreFecCurrent24StatIndex
		INTEGER,
	pm10001otu4PerfTelecomBerLinePreFecCurrent24StatInvBerPortn
		EkiOnOff,
	pm10001otu4PerfTelecomBerLinePreFecCurrent24StatBerValuePortn
		Unsigned32,
	pm10001otu4PerfTelecomBerLinePreFecCurrent24StatInvMinBerPortn
		EkiOnOff,
	pm10001otu4PerfTelecomBerLinePreFecCurrent24StatMinBerValuePortn
		Unsigned32,
	pm10001otu4PerfTelecomBerLinePreFecCurrent24StatInvMaxBerPortn
		EkiOnOff,
	pm10001otu4PerfTelecomBerLinePreFecCurrent24StatMaxBerValuePortn
		Unsigned32
	}


pm10001otu4PerfTelecomBerLinePreFecCurrent24StatIndex OBJECT-TYPE
	SYNTAX  INTEGER(0..128)
	MAX-ACCESS  read-only
	STATUS current
	DESCRIPTION
        "
        Index definition for the pm10001otu4PerfTelecomBerLinePreFecCurrent24Stat
        table
        "
	::= { pm10001otu4PerfTelecomBerLinePreFecCurrent24StatEntry 1 }


pm10001otu4PerfTelecomBerLinePreFecCurrent24StatInvBerPortn OBJECT-TYPE
	SYNTAX  EkiOnOff
	MAX-ACCESS read-only
	STATUS current
	DESCRIPTION
        "
        Current 24-hours BER counter inv.
        :This OID indicates that the current
        24-hours Coding Violation counter
        is invalid
        "
	::= { pm10001otu4PerfTelecomBerLinePreFecCurrent24StatEntry 2 }


pm10001otu4PerfTelecomBerLinePreFecCurrent24StatBerValuePortn OBJECT-TYPE
	SYNTAX  Unsigned32
	MAX-ACCESS read-only
	STATUS current
	DESCRIPTION
        "
        Current 24-hours BER counter :This
        OID gives the current 24-hours
         Coding Violation counter value
        "
	::= { pm10001otu4PerfTelecomBerLinePreFecCurrent24StatEntry 3 }


pm10001otu4PerfTelecomBerLinePreFecCurrent24StatInvMinBerPortn OBJECT-TYPE
	SYNTAX  EkiOnOff
	MAX-ACCESS read-only
	STATUS current
	DESCRIPTION
        "
        Current 24-hoursMinBER counter
        inv. :This OID indicates that the
        current 24-hours Errored Second
        counter is invalid
        "
	::= { pm10001otu4PerfTelecomBerLinePreFecCurrent24StatEntry 4 }


pm10001otu4PerfTelecomBerLinePreFecCurrent24StatMinBerValuePortn OBJECT-TYPE
	SYNTAX  Unsigned32
	MAX-ACCESS read-only
	STATUS current
	DESCRIPTION
        "
        Current 24-hours MinBER counter
        :This OID gives the current 24-hours
        Errored Second counter value
        "
	::= { pm10001otu4PerfTelecomBerLinePreFecCurrent24StatEntry 5 }


pm10001otu4PerfTelecomBerLinePreFecCurrent24StatInvMaxBerPortn OBJECT-TYPE
	SYNTAX  EkiOnOff
	MAX-ACCESS read-only
	STATUS current
	DESCRIPTION
        "
        Current 24-hours MaxBER counter
        inv. :This OID indicates that the
        current 24-hours severely Errored
        Second counter is invalid
        "
	::= { pm10001otu4PerfTelecomBerLinePreFecCurrent24StatEntry 6 }


pm10001otu4PerfTelecomBerLinePreFecCurrent24StatMaxBerValuePortn OBJECT-TYPE
	SYNTAX  Unsigned32
	MAX-ACCESS read-only
	STATUS current
	DESCRIPTION
        "
        Current 24-hours MaxBER counter
        :This OID gives the current 24-hours
        severely Errored Second counter
        value
        "
	::= { pm10001otu4PerfTelecomBerLinePreFecCurrent24StatEntry 7 }


--- *****************************************************
---     Leaf of the telecomBerLinePreFecPast24Stat
--- *****************************************************
--- *********************************************************
---     TABLE for the pm10001otu4PerfTelecomBerLinePreFecPast24StatHistory articles
--- *********************************************************

pm10001otu4PerfTelecomBerLinePreFecPast24StatHistoryPort1Table OBJECT-TYPE
	SYNTAX  SEQUENCE OF Pm10001otu4PerfTelecomBerLinePreFecPast24StatHistoryPort1Entry
	MAX-ACCESS not-accessible
	STATUS current
	DESCRIPTION
        "
        List of pm10001otu4PerfTelecomBerLinePreFecPast24StatHistory
        Article
        "
	::= { pm10001otu4MonPerfLine 211 }


pm10001otu4PerfTelecomBerLinePreFecPast24StatHistoryPort1Entry OBJECT-TYPE
	SYNTAX Pm10001otu4PerfTelecomBerLinePreFecPast24StatHistoryPort1Entry
	MAX-ACCESS not-accessible
	STATUS current
	DESCRIPTION
        "
        Row definition for the pm10001otu4PerfTelecomBerLinePreFecPast24StatHistory
        table
        "
	INDEX   { pm10001otu4PerfTelecomBerLinePreFecPast24StatHistoryPort1Index }
	::= { pm10001otu4PerfTelecomBerLinePreFecPast24StatHistoryPort1Table 1 }


Pm10001otu4PerfTelecomBerLinePreFecPast24StatHistoryPort1Entry ::=
	SEQUENCE {
	pm10001otu4PerfTelecomBerLinePreFecPast24StatHistoryPort1Index
		INTEGER,
	pm10001otu4PerfTelecomBerLinePreFecPast24StatHistoryInvBerPort1
		EkiOnOff,
	pm10001otu4PerfTelecomBerLinePreFecPast24StatHistoryBerValuePort1
		Unsigned32,
	pm10001otu4PerfTelecomBerLinePreFecPast24StatHistoryInvMinBerPort1
		EkiOnOff,
	pm10001otu4PerfTelecomBerLinePreFecPast24StatHistoryMinBerValuePort1
		Unsigned32,
	pm10001otu4PerfTelecomBerLinePreFecPast24StatHistoryInvMaxBerPort1
		EkiOnOff,
	pm10001otu4PerfTelecomBerLinePreFecPast24StatHistoryMaxBerValuePort1
		Unsigned32
	}


pm10001otu4PerfTelecomBerLinePreFecPast24StatHistoryPort1Index OBJECT-TYPE
	SYNTAX  INTEGER(0..128)
	MAX-ACCESS  read-only
	STATUS current
	DESCRIPTION
        "
        Index definition for the pm10001otu4PerfTelecomBerLinePreFecPast24StatHistory
        table
        "
	::= { pm10001otu4PerfTelecomBerLinePreFecPast24StatHistoryPort1Entry 1 }


pm10001otu4PerfTelecomBerLinePreFecPast24StatHistoryInvBerPort1 OBJECT-TYPE
	SYNTAX  EkiOnOff
	MAX-ACCESS read-only
	STATUS current
	DESCRIPTION
        "
        Previous 24-hours BER counter
         inv. :This OID indicates that
         the previous 24-hours Coding Violation
        counter is invalid
        "
	::= { pm10001otu4PerfTelecomBerLinePreFecPast24StatHistoryPort1Entry 2 }


pm10001otu4PerfTelecomBerLinePreFecPast24StatHistoryBerValuePort1 OBJECT-TYPE
	SYNTAX  Unsigned32
	MAX-ACCESS read-only
	STATUS current
	DESCRIPTION
        "
        Previous 24-hours BER counter
         :This OID gives the previous 24-hours
        Coding Violation counter value
        "
	::= { pm10001otu4PerfTelecomBerLinePreFecPast24StatHistoryPort1Entry 3 }


pm10001otu4PerfTelecomBerLinePreFecPast24StatHistoryInvMinBerPort1 OBJECT-TYPE
	SYNTAX  EkiOnOff
	MAX-ACCESS read-only
	STATUS current
	DESCRIPTION
        "
        Previous 24-hours MinBER counter
        inv. :This OID indicates that the
        previous 24-hours Errored Second
        counter is invalid
        "
	::= { pm10001otu4PerfTelecomBerLinePreFecPast24StatHistoryPort1Entry 4 }


pm10001otu4PerfTelecomBerLinePreFecPast24StatHistoryMinBerValuePort1 OBJECT-TYPE
	SYNTAX  Unsigned32
	MAX-ACCESS read-only
	STATUS current
	DESCRIPTION
        "
        Previous 24-hours MinBER counter
        :This OID gives the previous 24-hours
        Errored Second counter value
        "
	::= { pm10001otu4PerfTelecomBerLinePreFecPast24StatHistoryPort1Entry 5 }


pm10001otu4PerfTelecomBerLinePreFecPast24StatHistoryInvMaxBerPort1 OBJECT-TYPE
	SYNTAX  EkiOnOff
	MAX-ACCESS read-only
	STATUS current
	DESCRIPTION
        "
        Previous 24-hours MaxBER counter
        inv. :This OID indicates that the
        previous 24-hours severely Errored
        Second counter is invalid
        "
	::= { pm10001otu4PerfTelecomBerLinePreFecPast24StatHistoryPort1Entry 6 }


pm10001otu4PerfTelecomBerLinePreFecPast24StatHistoryMaxBerValuePort1 OBJECT-TYPE
	SYNTAX  Unsigned32
	MAX-ACCESS read-only
	STATUS current
	DESCRIPTION
        "
        Previous 24-hours MaxBER counter
        :This OID gives the previous 24-hours
        severely Errored Second counter
        value
        "
	::= { pm10001otu4PerfTelecomBerLinePreFecPast24StatHistoryPort1Entry 7 }


--- *****************************************************
---     Leaf of the datacomClientCurrent15Stat
--- *****************************************************
--- *********************************************************
---     TABLE for the pm10001otu4PerfDatacomClientCurrent15Stat articles
--- *********************************************************

pm10001otu4PerfDatacomClientCurrent15StatTable OBJECT-TYPE
	SYNTAX  SEQUENCE OF Pm10001otu4PerfDatacomClientCurrent15StatEntry
	MAX-ACCESS not-accessible
	STATUS current
	DESCRIPTION
        "
        List of pm10001otu4PerfDatacomClientCurrent15Stat
        Article
        "
	::= { pm10001otu4MonPerfClient 432 }


pm10001otu4PerfDatacomClientCurrent15StatEntry OBJECT-TYPE
	SYNTAX Pm10001otu4PerfDatacomClientCurrent15StatEntry
	MAX-ACCESS not-accessible
	STATUS current
	DESCRIPTION
        "
        Row definition for the pm10001otu4PerfDatacomClientCurrent15Stat
        table
        "
	INDEX   { pm10001otu4PerfDatacomClientCurrent15StatIndex }
	::= { pm10001otu4PerfDatacomClientCurrent15StatTable 1 }


Pm10001otu4PerfDatacomClientCurrent15StatEntry ::=
	SEQUENCE {
	pm10001otu4PerfDatacomClientCurrent15StatIndex
		INTEGER,
	rm10010perfdatacomclientCurrent15StatOutPacketCountInvPortn
		EkiOnOff,
	rm10010perfdatacomclientCurrent15StatOutPacketCountPortn
		Counter64,
	rm10010perfdatacomclientCurrent15StatOutCrcCountInvPortn
		EkiOnOff,
	rm10010perfdatacomclientCurrent15StatOutCrcCountPortn
		Counter64,
	rm10010perfdatacomclientCurrent15StatInPacketCountInvPortn
		EkiOnOff,
	rm10010perfdatacomclientCurrent15StatInPacketCountPortn
		Counter64,
	rm10010perfdatacomclientCurrent15StatInCrcCountInvPortn
		EkiOnOff,
	rm10010perfdatacomclientCurrent15StatInCrcCountPortn
		Counter64
	}


pm10001otu4PerfDatacomClientCurrent15StatIndex OBJECT-TYPE
	SYNTAX  INTEGER(0..128)
	MAX-ACCESS  read-only
	STATUS current
	DESCRIPTION
        "
        Index definition for the pm10001otu4PerfDatacomClientCurrent15Stat
        table
        "
	::= { pm10001otu4PerfDatacomClientCurrent15StatEntry 1 }


rm10010perfdatacomclientCurrent15StatOutPacketCountInvPortn OBJECT-TYPE
	SYNTAX  EkiOnOff
	MAX-ACCESS read-only
	STATUS current
	DESCRIPTION
        "
        Client Current 15-min Output Packet
        counter inv. :This OID indicates
        that the current 15-min Output
         Packets counter is invalid
        "
	::= { pm10001otu4PerfDatacomClientCurrent15StatEntry 30 }


rm10010perfdatacomclientCurrent15StatOutPacketCountPortn OBJECT-TYPE
	SYNTAX  Counter64
	MAX-ACCESS read-only
	STATUS current
	DESCRIPTION
        "
        Client Current 15-min Output Packet
        counter :This OID gives the current
        15-min Output Packets counter value
        "
	::= { pm10001otu4PerfDatacomClientCurrent15StatEntry 31 }


rm10010perfdatacomclientCurrent15StatOutCrcCountInvPortn OBJECT-TYPE
	SYNTAX  EkiOnOff
	MAX-ACCESS read-only
	STATUS current
	DESCRIPTION
        "
        Client Current 15-min Output CRC
        counter inv. :This OID indicates
        that the current 15-min Output
         CRC counter is invalid
        "
	::= { pm10001otu4PerfDatacomClientCurrent15StatEntry 28 }


rm10010perfdatacomclientCurrent15StatOutCrcCountPortn OBJECT-TYPE
	SYNTAX  Counter64
	MAX-ACCESS read-only
	STATUS current
	DESCRIPTION
        "
        Client Current 15-min Output CRC
        counter :This OID gives the current
        15-min Output CRC counter value
        "
	::= { pm10001otu4PerfDatacomClientCurrent15StatEntry 29 }


rm10010perfdatacomclientCurrent15StatInPacketCountInvPortn OBJECT-TYPE
	SYNTAX  EkiOnOff
	MAX-ACCESS read-only
	STATUS current
	DESCRIPTION
        "
        Client Current 15-min Input Packet
        counter inv. :This OID indicates
        that the current 15-min Input Packet
        counter is invalid
        "
	::= { pm10001otu4PerfDatacomClientCurrent15StatEntry 6 }


rm10010perfdatacomclientCurrent15StatInPacketCountPortn OBJECT-TYPE
	SYNTAX  Counter64
	MAX-ACCESS read-only
	STATUS current
	DESCRIPTION
        "
        Client Current 15-min Input Packet
        counter :This OID gives the current
        15-min Input Packet counter value
        "
	::= { pm10001otu4PerfDatacomClientCurrent15StatEntry 7 }


rm10010perfdatacomclientCurrent15StatInCrcCountInvPortn OBJECT-TYPE
	SYNTAX  EkiOnOff
	MAX-ACCESS read-only
	STATUS current
	DESCRIPTION
        "
        Client Current 15-min Input CRC
        counter inv. :This OID indicates
        that the current 15-min Input CRC
        counter is invalid
        "
	::= { pm10001otu4PerfDatacomClientCurrent15StatEntry 4 }


rm10010perfdatacomclientCurrent15StatInCrcCountPortn OBJECT-TYPE
	SYNTAX  Counter64
	MAX-ACCESS read-only
	STATUS current
	DESCRIPTION
        "
        Client Current 15-min Input CRC
        counter :This OID gives the current
        15-min Input CRC counter value
        "
	::= { pm10001otu4PerfDatacomClientCurrent15StatEntry 5 }


--- *****************************************************
---     Leaf of the datacomClientPast15Stat
--- *****************************************************
--- *********************************************************
---     TABLE for the pm10001otu4PerfDatacomClientPast15StatHistory articles
--- *********************************************************

pm10001otu4PerfDatacomClientPast15StatHistoryPort1Table OBJECT-TYPE
	SYNTAX  SEQUENCE OF Pm10001otu4PerfDatacomClientPast15StatHistoryPort1Entry
	MAX-ACCESS not-accessible
	STATUS current
	DESCRIPTION
        "
        List of pm10001otu4PerfDatacomClientPast15StatHistory
        Article
        "
	::= { pm10001otu4MonPerfClient 448 }


pm10001otu4PerfDatacomClientPast15StatHistoryPort1Entry OBJECT-TYPE
	SYNTAX Pm10001otu4PerfDatacomClientPast15StatHistoryPort1Entry
	MAX-ACCESS not-accessible
	STATUS current
	DESCRIPTION
        "
        Row definition for the pm10001otu4PerfDatacomClientPast15StatHistory
        table
        "
	INDEX   { pm10001otu4PerfDatacomClientPast15StatHistoryPort1Index }
	::= { pm10001otu4PerfDatacomClientPast15StatHistoryPort1Table 1 }


Pm10001otu4PerfDatacomClientPast15StatHistoryPort1Entry ::=
	SEQUENCE {
	pm10001otu4PerfDatacomClientPast15StatHistoryPort1Index
		INTEGER,
	rm10010perfdatacomclientPast15StatOutPacketCountInvPort1
		EkiOnOff,
	rm10010perfdatacomclientPast15StatOutPacketCountPort1
		Counter64,
	rm10010perfdatacomclientPast15StatOutCrcCountInvPort1
		EkiOnOff,
	rm10010perfdatacomclientPast15StatOutCrcCountPort1
		Counter64,
	rm10010perfdatacomclientPast15StatInPacketCountInvPort1
		EkiOnOff,
	rm10010perfdatacomclientPast15StatInPacketCountPort1
		Counter64,
	rm10010perfdatacomclientPast15StatInCrcCountInvPort1
		EkiOnOff,
	rm10010perfdatacomclientPast15StatInCrcCountPort1
		Counter64
	}


pm10001otu4PerfDatacomClientPast15StatHistoryPort1Index OBJECT-TYPE
	SYNTAX  INTEGER(0..128)
	MAX-ACCESS  read-only
	STATUS current
	DESCRIPTION
        "
        Index definition for the pm10001otu4PerfDatacomClientPast15StatHistory
        table
        "
	::= { pm10001otu4PerfDatacomClientPast15StatHistoryPort1Entry 1 }


rm10010perfdatacomclientPast15StatOutPacketCountInvPort1 OBJECT-TYPE
	SYNTAX  EkiOnOff
	MAX-ACCESS read-only
	STATUS current
	DESCRIPTION
        "
        Client Past 15-min Output Packet
        counter inv. :This OID indicates
        that the past 15-min Output Packets
        counter is invalid
        "
	::= { pm10001otu4PerfDatacomClientPast15StatHistoryPort1Entry 30 }


rm10010perfdatacomclientPast15StatOutPacketCountPort1 OBJECT-TYPE
	SYNTAX  Counter64
	MAX-ACCESS read-only
	STATUS current
	DESCRIPTION
        "
        Client Past 15-min Output Packet
        counter :This OID gives the past
        15-min Output Packets counter value
        "
	::= { pm10001otu4PerfDatacomClientPast15StatHistoryPort1Entry 31 }


rm10010perfdatacomclientPast15StatOutCrcCountInvPort1 OBJECT-TYPE
	SYNTAX  EkiOnOff
	MAX-ACCESS read-only
	STATUS current
	DESCRIPTION
        "
        Client Past 15-min Output CRC
         counter inv. :This OID indicates
        that the past 15-min Output CRC
        counter is invalid
        "
	::= { pm10001otu4PerfDatacomClientPast15StatHistoryPort1Entry 28 }


rm10010perfdatacomclientPast15StatOutCrcCountPort1 OBJECT-TYPE
	SYNTAX  Counter64
	MAX-ACCESS read-only
	STATUS current
	DESCRIPTION
        "
        Client Past 15-min Output CRC
         counter :This OID gives the past
        15-min Output CRC counter value
        "
	::= { pm10001otu4PerfDatacomClientPast15StatHistoryPort1Entry 29 }


rm10010perfdatacomclientPast15StatInPacketCountInvPort1 OBJECT-TYPE
	SYNTAX  EkiOnOff
	MAX-ACCESS read-only
	STATUS current
	DESCRIPTION
        "
        Client Past 15-min Input Packet
        counter inv. :This OID indicates
        that the past 15-min Input Packet
        counter is invalid
        "
	::= { pm10001otu4PerfDatacomClientPast15StatHistoryPort1Entry 6 }


rm10010perfdatacomclientPast15StatInPacketCountPort1 OBJECT-TYPE
	SYNTAX  Counter64
	MAX-ACCESS read-only
	STATUS current
	DESCRIPTION
        "
        Client Past 15-min Input Packet
        counter :This OID gives the past
        15-min Input Packet counter value
        "
	::= { pm10001otu4PerfDatacomClientPast15StatHistoryPort1Entry 7 }


rm10010perfdatacomclientPast15StatInCrcCountInvPort1 OBJECT-TYPE
	SYNTAX  EkiOnOff
	MAX-ACCESS read-only
	STATUS current
	DESCRIPTION
        "
        Client Past 15-min Input CRC counter
        inv. :This OID indicates that the
        past 15-min Input CRC counter is
        invalid
        "
	::= { pm10001otu4PerfDatacomClientPast15StatHistoryPort1Entry 4 }


rm10010perfdatacomclientPast15StatInCrcCountPort1 OBJECT-TYPE
	SYNTAX  Counter64
	MAX-ACCESS read-only
	STATUS current
	DESCRIPTION
        "
        Client Past 15-min Input CRC counter
        :This OID gives the past 15-min
        Input CRC counter value
        "
	::= { pm10001otu4PerfDatacomClientPast15StatHistoryPort1Entry 5 }


--- *****************************************************
---     Leaf of the datacomClientCurrent24Stat
--- *****************************************************
--- *********************************************************
---     TABLE for the pm10001otu4PerfDatacomClientCurrent24Stat articles
--- *********************************************************

pm10001otu4PerfDatacomClientCurrent24StatTable OBJECT-TYPE
	SYNTAX  SEQUENCE OF Pm10001otu4PerfDatacomClientCurrent24StatEntry
	MAX-ACCESS not-accessible
	STATUS current
	DESCRIPTION
        "
        List of pm10001otu4PerfDatacomClientCurrent24Stat
        Article
        "
	::= { pm10001otu4MonPerfClient 464 }


pm10001otu4PerfDatacomClientCurrent24StatEntry OBJECT-TYPE
	SYNTAX Pm10001otu4PerfDatacomClientCurrent24StatEntry
	MAX-ACCESS not-accessible
	STATUS current
	DESCRIPTION
        "
        Row definition for the pm10001otu4PerfDatacomClientCurrent24Stat
        table
        "
	INDEX   { pm10001otu4PerfDatacomClientCurrent24StatIndex }
	::= { pm10001otu4PerfDatacomClientCurrent24StatTable 1 }


Pm10001otu4PerfDatacomClientCurrent24StatEntry ::=
	SEQUENCE {
	pm10001otu4PerfDatacomClientCurrent24StatIndex
		INTEGER,
	rm10010perfdatacomclientCurrent24StatOutPacketCountInvPortn
		EkiOnOff,
	rm10010perfdatacomclientCurrent24StatOutPacketCountPortn
		Counter64,
	rm10010perfdatacomclientCurrent24StatOutCrcCountInvPortn
		EkiOnOff,
	rm10010perfdatacomclientCurrent24StatOutCrcCountPortn
		Counter64,
	rm10010perfdatacomclientCurrent24StatInPacketCountInvPortn
		EkiOnOff,
	rm10010perfdatacomclientCurrent24StatInPacketCountPortn
		Counter64,
	rm10010perfdatacomclientCurrent24StatInCrcCountInvPortn
		EkiOnOff,
	rm10010perfdatacomclientCurrent24StatInCrcCountPortn
		Counter64
	}


pm10001otu4PerfDatacomClientCurrent24StatIndex OBJECT-TYPE
	SYNTAX  INTEGER(0..128)
	MAX-ACCESS  read-only
	STATUS current
	DESCRIPTION
        "
        Index definition for the pm10001otu4PerfDatacomClientCurrent24Stat
        table
        "
	::= { pm10001otu4PerfDatacomClientCurrent24StatEntry 1 }


rm10010perfdatacomclientCurrent24StatOutPacketCountInvPortn OBJECT-TYPE
	SYNTAX  EkiOnOff
	MAX-ACCESS read-only
	STATUS current
	DESCRIPTION
        "
        Client Current 24-hours Output
        Packet counter inv. :This OID indicates
        that the current 24-hours Output
        Packets counter is invalid
        "
	::= { pm10001otu4PerfDatacomClientCurrent24StatEntry 30 }


rm10010perfdatacomclientCurrent24StatOutPacketCountPortn OBJECT-TYPE
	SYNTAX  Counter64
	MAX-ACCESS read-only
	STATUS current
	DESCRIPTION
        "
        Client Current 24-hours Output
        Packet counter :This OID gives
         the current 24-hours Output Packets
        counter value
        "
	::= { pm10001otu4PerfDatacomClientCurrent24StatEntry 31 }


rm10010perfdatacomclientCurrent24StatOutCrcCountInvPortn OBJECT-TYPE
	SYNTAX  EkiOnOff
	MAX-ACCESS read-only
	STATUS current
	DESCRIPTION
        "
        Client Current 24-hours Output
        CRC counter inv. :This OID indicates
        that the current 24-hours Output
        CRC counter is invalid
        "
	::= { pm10001otu4PerfDatacomClientCurrent24StatEntry 28 }


rm10010perfdatacomclientCurrent24StatOutCrcCountPortn OBJECT-TYPE
	SYNTAX  Counter64
	MAX-ACCESS read-only
	STATUS current
	DESCRIPTION
        "
        Client Current 24-hours Output
        CRC counter :This OID gives the
        current 24-hours Output CRC counter
        value
        "
	::= { pm10001otu4PerfDatacomClientCurrent24StatEntry 29 }


rm10010perfdatacomclientCurrent24StatInPacketCountInvPortn OBJECT-TYPE
	SYNTAX  EkiOnOff
	MAX-ACCESS read-only
	STATUS current
	DESCRIPTION
        "
        Client Current 24-hours Input
         Packet counter inv. :This OID
         indicates that the current 24-hours
        Input Packet counter is invalid
        "
	::= { pm10001otu4PerfDatacomClientCurrent24StatEntry 6 }


rm10010perfdatacomclientCurrent24StatInPacketCountPortn OBJECT-TYPE
	SYNTAX  Counter64
	MAX-ACCESS read-only
	STATUS current
	DESCRIPTION
        "
        Client Current 24-hours Input
         Packet counter :This OID gives
        the current 24-hours Input Packet
        counter value
        "
	::= { pm10001otu4PerfDatacomClientCurrent24StatEntry 7 }


rm10010perfdatacomclientCurrent24StatInCrcCountInvPortn OBJECT-TYPE
	SYNTAX  EkiOnOff
	MAX-ACCESS read-only
	STATUS current
	DESCRIPTION
        "
        Client Current 24-hours Input
         CRC counter inv. :This OID indicates
        that the current 24-hours Input
        CRC counter is invalid
        "
	::= { pm10001otu4PerfDatacomClientCurrent24StatEntry 4 }


rm10010perfdatacomclientCurrent24StatInCrcCountPortn OBJECT-TYPE
	SYNTAX  Counter64
	MAX-ACCESS read-only
	STATUS current
	DESCRIPTION
        "
        Client Current 24-hours Input
         CRC counter :This OID gives the
        current 24-hours Input CRC counter
        value
        "
	::= { pm10001otu4PerfDatacomClientCurrent24StatEntry 5 }


--- *****************************************************
---     Leaf of the datacomClientPast24Stat
--- *****************************************************
--- *********************************************************
---     TABLE for the pm10001otu4PerfDatacomClientPast24StatHistory articles
--- *********************************************************

pm10001otu4PerfDatacomClientPast24StatHistoryPort1Table OBJECT-TYPE
	SYNTAX  SEQUENCE OF Pm10001otu4PerfDatacomClientPast24StatHistoryPort1Entry
	MAX-ACCESS not-accessible
	STATUS current
	DESCRIPTION
        "
        List of pm10001otu4PerfDatacomClientPast24StatHistory
        Article
        "
	::= { pm10001otu4MonPerfClient 480 }


pm10001otu4PerfDatacomClientPast24StatHistoryPort1Entry OBJECT-TYPE
	SYNTAX Pm10001otu4PerfDatacomClientPast24StatHistoryPort1Entry
	MAX-ACCESS not-accessible
	STATUS current
	DESCRIPTION
        "
        Row definition for the pm10001otu4PerfDatacomClientPast24StatHistory
        table
        "
	INDEX   { pm10001otu4PerfDatacomClientPast24StatHistoryPort1Index }
	::= { pm10001otu4PerfDatacomClientPast24StatHistoryPort1Table 1 }


Pm10001otu4PerfDatacomClientPast24StatHistoryPort1Entry ::=
	SEQUENCE {
	pm10001otu4PerfDatacomClientPast24StatHistoryPort1Index
		INTEGER,
	rm10010perfdatacomclientPast24StatOutPacketCountInvPort1
		EkiOnOff,
	rm10010perfdatacomclientPast24StatOutPacketCountPort1
		Counter64,
	rm10010perfdatacomclientPast24StatOutCrcCountInvPort1
		EkiOnOff,
	rm10010perfdatacomclientPast24StatOutCrcCountPort1
		Counter64,
	rm10010perfdatacomclientPast24StatInPacketCountInvPort1
		EkiOnOff,
	rm10010perfdatacomclientPast24StatInPacketCountPort1
		Counter64,
	rm10010perfdatacomclientPast24StatInCrcCountInvPort1
		EkiOnOff,
	rm10010perfdatacomclientPast24StatInCrcCountPort1
		Counter64
	}


pm10001otu4PerfDatacomClientPast24StatHistoryPort1Index OBJECT-TYPE
	SYNTAX  INTEGER(0..128)
	MAX-ACCESS  read-only
	STATUS current
	DESCRIPTION
        "
        Index definition for the pm10001otu4PerfDatacomClientPast24StatHistory
        table
        "
	::= { pm10001otu4PerfDatacomClientPast24StatHistoryPort1Entry 1 }


rm10010perfdatacomclientPast24StatOutPacketCountInvPort1 OBJECT-TYPE
	SYNTAX  EkiOnOff
	MAX-ACCESS read-only
	STATUS current
	DESCRIPTION
        "
        Client Past 24-hours Output Packet
        counter inv. :This OID indicates
        that the past 24-hours Output Packets
        counter is invalid
        "
	::= { pm10001otu4PerfDatacomClientPast24StatHistoryPort1Entry 30 }


rm10010perfdatacomclientPast24StatOutPacketCountPort1 OBJECT-TYPE
	SYNTAX  Counter64
	MAX-ACCESS read-only
	STATUS current
	DESCRIPTION
        "
        Client Past 24-hours Output Packet
        counter :This OID gives the past
        24-hours Output Packets counter
        value
        "
	::= { pm10001otu4PerfDatacomClientPast24StatHistoryPort1Entry 31 }


rm10010perfdatacomclientPast24StatOutCrcCountInvPort1 OBJECT-TYPE
	SYNTAX  EkiOnOff
	MAX-ACCESS read-only
	STATUS current
	DESCRIPTION
        "
        Client Past 24-hours Output CRC
        counter inv. :This OID indicates
        that the past 24-hours Output CRC
        counter is invalid
        "
	::= { pm10001otu4PerfDatacomClientPast24StatHistoryPort1Entry 28 }


rm10010perfdatacomclientPast24StatOutCrcCountPort1 OBJECT-TYPE
	SYNTAX  Counter64
	MAX-ACCESS read-only
	STATUS current
	DESCRIPTION
        "
        Client Past 24-hours Output CRC
        counter :This OID gives the past
        24-hours Output CRC counter value
        "
	::= { pm10001otu4PerfDatacomClientPast24StatHistoryPort1Entry 29 }


rm10010perfdatacomclientPast24StatInPacketCountInvPort1 OBJECT-TYPE
	SYNTAX  EkiOnOff
	MAX-ACCESS read-only
	STATUS current
	DESCRIPTION
        "
        Client Past 24-hours Input Packet
        counter inv. :This OID indicates
        that the past 24-hours Input Packet
        counter is invalid
        "
	::= { pm10001otu4PerfDatacomClientPast24StatHistoryPort1Entry 6 }


rm10010perfdatacomclientPast24StatInPacketCountPort1 OBJECT-TYPE
	SYNTAX  Counter64
	MAX-ACCESS read-only
	STATUS current
	DESCRIPTION
        "
        Client Past 24-hours Input Packet
        counter :This OID gives the past
        24-hours Input Packet counter value
        "
	::= { pm10001otu4PerfDatacomClientPast24StatHistoryPort1Entry 7 }


rm10010perfdatacomclientPast24StatInCrcCountInvPort1 OBJECT-TYPE
	SYNTAX  EkiOnOff
	MAX-ACCESS read-only
	STATUS current
	DESCRIPTION
        "
        Client Past 24-hours Input CRC
        counter inv. :This OID indicates
        that the past 24-hours Input CRC
        counter is invalid
        "
	::= { pm10001otu4PerfDatacomClientPast24StatHistoryPort1Entry 4 }


rm10010perfdatacomclientPast24StatInCrcCountPort1 OBJECT-TYPE
	SYNTAX  Counter64
	MAX-ACCESS read-only
	STATUS current
	DESCRIPTION
        "
        Client Past 24-hours Input CRC
        counter :This OID gives the past
        24-hours Input CRC counter value
        "
	::= { pm10001otu4PerfDatacomClientPast24StatHistoryPort1Entry 5 }



pm10001otu4PerfEnable OBJECT-TYPE
	SYNTAX EkiOnOff
	MAX-ACCESS read-write
	STATUS current
	DESCRIPTION
        "
        Perf. Mon. Enable :This OID enables
        the Performance Monitoring application
        "
	::= { pm10001otu4MonPerfSync 257 }


pm10001otu4Perf15minSync OBJECT-TYPE
	SYNTAX EkiOnOff
	MAX-ACCESS read-write
	STATUS current
	DESCRIPTION
        "
        Perf. Mon. 15-min sync. :This
         OID must be used in external synchronisation
        mode only to send a 15-min synchronisation
        command
        "
	::= { pm10001otu4MonPerfSync 259 }


pm10001otu4Perf24hSync OBJECT-TYPE
	SYNTAX EkiOnOff
	MAX-ACCESS read-write
	STATUS current
	DESCRIPTION
        "
        Perf. Mon. 24-hours sync. :This
        OID must be used in external synchronisation
        mode only to send a 24-hours synchronisation
        command
        "
	::= { pm10001otu4MonPerfSync 260 }


pm10001otu4Perf15MinShort OBJECT-TYPE
	SYNTAX EkiOnOff
	MAX-ACCESS read-write
	STATUS current
	DESCRIPTION
        "
        15-min period is short :This OID
        indicates that the 15-min period
        lasts less than 890 seconds
        "
	::= { pm10001otu4MonPerfTimeStamp 1 }


pm10001otu4Perf15MinLong OBJECT-TYPE
	SYNTAX EkiOnOff
	MAX-ACCESS read-write
	STATUS current
	DESCRIPTION
        "
        15-min period is long :This OID
        indicates that the 15-min period
        lasts more than 910 seconds
        "
	::= { pm10001otu4MonPerfTimeStamp 2 }


pm10001otu4Perf24HoursShort OBJECT-TYPE
	SYNTAX Counter32
	MAX-ACCESS read-write
	STATUS current
	DESCRIPTION
        "
        24-hours period is short :This
        OID indicates that 24-hours period
        lasts less than 86390 seconds
        "
	::= { pm10001otu4MonPerfTimeStamp 5 }


pm10001otu4Perf24HoursLong OBJECT-TYPE
	SYNTAX Counter32
	MAX-ACCESS read-write
	STATUS current
	DESCRIPTION
        "
        24-hours period is long :This
         OID indicates that 24-hours period
        lasts more than 86410 seconds
        "
	::= { pm10001otu4MonPerfTimeStamp 6 }


pm10001otu4PerfCurrent15MinElapsedTime OBJECT-TYPE
	SYNTAX Counter32
	MAX-ACCESS read-write
	STATUS current
	DESCRIPTION
        "
        Current 15min period Elapsed Time
         :This OID gives the number of
         seconds elapsed in the current
        15-minutes period
        "
	::= { pm10001otu4MonPerfTimeStamp 7 }


pm10001otu4PerfCurrent24HoursElapsedTime OBJECT-TYPE
	SYNTAX Counter32
	MAX-ACCESS read-write
	STATUS current
	DESCRIPTION
        "
        Current 24hours period Elapsed
        Time :This OID gives the number
        of seconds elapsed in the current
        24-hours period
        "
	::= { pm10001otu4MonPerfTimeStamp 8 }






--- *****************************************************
--- $$$$$$$$$$$$$$$$$$$$$$$$$$$$$$$$$$$$$$$$$$$$$$$$$$$$$
---     DOWNLOAD
--- $$$$$$$$$$$$$$$$$$$$$$$$$$$$$$$$$$$$$$$$$$$$$$$$$$$$$
--- *****************************************************



--- *****************************************************
---     LEAF for the restartProcess article
--- *****************************************************
pm10001otu4DwlrestartProcess OBJECT IDENTIFIER ::= { pm10001otu4DwlOther 0 }




pm10001otu4DwlColdRestartProcessed OBJECT-TYPE
	  SYNTAX EkiOnOff
	  MAX-ACCESS read-only
	  STATUS current
	  DESCRIPTION
        "
        Cold Restart :This OID indicates
        that the module last restart was
        a Cold RESTART
        "
	  ::= { pm10001otu4DwlrestartProcess 2 }



pm10001otu4DwlWarmRestartProcessed OBJECT-TYPE
	  SYNTAX EkiOnOff
	  MAX-ACCESS read-only
	  STATUS current
	  DESCRIPTION
        "
        Warm Restart :This OID indicates
        that the module last restart was
        a Warm RESTART
        "
	  ::= { pm10001otu4DwlrestartProcess 1 }



--- *****************************************************
---     LEAF for the swBanksUsed article
--- *****************************************************
pm10001otu4DwlswBanksUsed OBJECT IDENTIFIER ::= { pm10001otu4DwlOther 1 }




pm10001otu4DwlSwBank2Notempty OBJECT-TYPE
	  SYNTAX EkiOnOff
	  MAX-ACCESS read-only
	  STATUS current
	  DESCRIPTION
        "
        SW bank 2 loaded :This OID indicates
        a software is loaded in SW bank
        2  <Help>  This status indicates
        if the SW bank 2 contains SW package
        "
	  ::= { pm10001otu4DwlswBanksUsed 6 }



pm10001otu4DwlSwBank1Notempty OBJECT-TYPE
	  SYNTAX EkiOnOff
	  MAX-ACCESS read-only
	  STATUS current
	  DESCRIPTION
        "
        SW bank 1 loaded :This OID indicates
        a software is loaded in SW bank
        1  <Help>  This status indicates
        if the SW bank 1 contains SW package
        "
	  ::= { pm10001otu4DwlswBanksUsed 5 }



pm10001otu4DwlSwBank2Used OBJECT-TYPE
	  SYNTAX EkiOnOff
	  MAX-ACCESS read-only
	  STATUS current
	  DESCRIPTION
        "
        SW bank 2 active :This OID indicates
        the module is working on SW bank
        2  <Help>  This status indicates
        if the SW bank 2 is active or standby
        "
	  ::= { pm10001otu4DwlswBanksUsed 2 }



pm10001otu4DwlSwBank1Used OBJECT-TYPE
	  SYNTAX EkiOnOff
	  MAX-ACCESS read-only
	  STATUS current
	  DESCRIPTION
        "
        SW bank 1 active :This OID indicates
        the module is working on SW bank
        1  <Help>  This status indicates
        if the SW bank 1 is active or standby
        "
	  ::= { pm10001otu4DwlswBanksUsed 1 }



--- *****************************************************
---     LEAF for the gwBanksUsed article
--- *****************************************************
pm10001otu4DwlgwBanksUsed OBJECT IDENTIFIER ::= { pm10001otu4DwlOther 2 }




pm10001otu4DwlGwBank4Notempty OBJECT-TYPE
	  SYNTAX EkiOnOff
	  MAX-ACCESS read-only
	  STATUS current
	  DESCRIPTION
        "
        GW bank 4 loaded :This OID indicates
        a gateware is loaded in GW bank
        4
        "
	  ::= { pm10001otu4DwlgwBanksUsed 8 }



pm10001otu4DwlGwBank3Notempty OBJECT-TYPE
	  SYNTAX EkiOnOff
	  MAX-ACCESS read-only
	  STATUS current
	  DESCRIPTION
        "
        GW bank 3 loaded :This OID indicates
        a gateware is loaded in GW bank
        3  <Help>  This status indicates
        if the GW bank 3 contains GW package
        "
	  ::= { pm10001otu4DwlgwBanksUsed 7 }



pm10001otu4DwlGwBank2Notempty OBJECT-TYPE
	  SYNTAX EkiOnOff
	  MAX-ACCESS read-only
	  STATUS current
	  DESCRIPTION
        "
        GW bank 2 loaded :This OID indicates
        a gateware is loaded in GW bank
        2
        "
	  ::= { pm10001otu4DwlgwBanksUsed 6 }



pm10001otu4DwlGwBank1Notempty OBJECT-TYPE
	  SYNTAX EkiOnOff
	  MAX-ACCESS read-only
	  STATUS current
	  DESCRIPTION
        "
        GW bank 1 loaded :This OID indicates
        a gateware is loaded in GW bank
        1  <Help>  This status indicates
        if the GW bank 1 contains GW package
        "
	  ::= { pm10001otu4DwlgwBanksUsed 5 }



pm10001otu4DwlGwBank4Used OBJECT-TYPE
	  SYNTAX EkiOnOff
	  MAX-ACCESS read-only
	  STATUS current
	  DESCRIPTION
        "
        GW bank 4 active :This OID indicates
        the module is working on GW bank
        4
        "
	  ::= { pm10001otu4DwlgwBanksUsed 4 }



pm10001otu4DwlGwBank3Used OBJECT-TYPE
	  SYNTAX EkiOnOff
	  MAX-ACCESS read-only
	  STATUS current
	  DESCRIPTION
        "
        GW bank 3 active :This OID indicates
        the module is working on GW bank
        3  <Help>  This status indicates
        if the GW bank 3 is active or standby
        "
	  ::= { pm10001otu4DwlgwBanksUsed 3 }



pm10001otu4DwlGwBank2Used OBJECT-TYPE
	  SYNTAX EkiOnOff
	  MAX-ACCESS read-only
	  STATUS current
	  DESCRIPTION
        "
        GW bank 2 active :This OID indicates
        the module is working on GW bank
        2
        "
	  ::= { pm10001otu4DwlgwBanksUsed 2 }



pm10001otu4DwlGwBank1Used OBJECT-TYPE
	  SYNTAX EkiOnOff
	  MAX-ACCESS read-only
	  STATUS current
	  DESCRIPTION
        "
        GW bank 1 active :This OID indicates
        the module is working on GW bank
        1  <Help>  This status indicates
        if the GW bank 1 is active or standby
        "
	  ::= { pm10001otu4DwlgwBanksUsed 1 }








--- *****************************************************
--- $$$$$$$$$$$$$$$$$$$$$$$$$$$$$$$$$$$$$$$$$$$$$$$$$$$$$
---     CONFIG
--- $$$$$$$$$$$$$$$$$$$$$$$$$$$$$$$$$$$$$$$$$$$$$$$$$$$$$
--- *****************************************************



--- *****************************************************
---     LEAF for the table Group accessCAisCsf
--- *****************************************************

pm10001otu4CfgAccessCAisCsf OBJECT IDENTIFIER ::= { pm10001otu4Config 1 }



--- *****************************************************
---     LEAF for the table 0012
--- *****************************************************

pm10001otu4CfgClientcaiscsfTable OBJECT-TYPE
	SYNTAX  SEQUENCE OF Pm10001otu4CfgClientcaiscsfEntry
	MAX-ACCESS not-accessible
	STATUS current
	DESCRIPTION
        "
        List of  Article
        "
	::= { pm10001otu4CfgAccessCAisCsf 1 }


pm10001otu4CfgClientcaiscsfEntry OBJECT-TYPE
	SYNTAX Pm10001otu4CfgClientcaiscsfEntry
	MAX-ACCESS not-accessible
	STATUS current
	DESCRIPTION
        "
        Row definition for the accessCAisCsf
        table
        "
	INDEX   { pm10001otu4CfgClientcaiscsfIndex }
	::= { pm10001otu4CfgClientcaiscsfTable 1 }


Pm10001otu4CfgClientcaiscsfEntry ::=
	SEQUENCE {
	pm10001otu4CfgClientcaiscsfIndex
		INTEGER,
	pm10001otu4CfgReservePortn
		Unsigned32
	}


pm10001otu4CfgClientcaiscsfIndex OBJECT-TYPE
	SYNTAX  INTEGER(0..128)
	MAX-ACCESS  read-only
	STATUS current
	DESCRIPTION
        "
        Index definition for the clientcaiscsf
        table
        "
	::= { pm10001otu4CfgClientcaiscsfEntry 1 }


pm10001otu4CfgReservePortn OBJECT-TYPE
	SYNTAX  Unsigned32 (0..65536)
	MAX-ACCESS read-write
	STATUS current
	DESCRIPTION
        "
        CAIS mode  on Client Port :This
        register enables/disables port
          laser shutdown on CAIS insertion
        condition
        "
	::= { pm10001otu4CfgClientcaiscsfEntry 3 }


--- *****************************************************
---     LEAF for the table Group startup
--- *****************************************************

pm10001otu4CfgStartup OBJECT IDENTIFIER ::= { pm10001otu4Config 2 }



--- *****************************************************
---     LEAF for the table 2110
--- *****************************************************

pm10001otu4CfgClientStartupTable OBJECT-TYPE
	SYNTAX  SEQUENCE OF Pm10001otu4CfgClientStartupEntry
	MAX-ACCESS not-accessible
	STATUS current
	DESCRIPTION
        "
        List of  Article
        "
	::= { pm10001otu4CfgStartup 1 }


pm10001otu4CfgClientStartupEntry OBJECT-TYPE
	SYNTAX Pm10001otu4CfgClientStartupEntry
	MAX-ACCESS not-accessible
	STATUS current
	DESCRIPTION
        "
        Row definition for the startup
        table
        "
	INDEX   { pm10001otu4CfgClientStartupIndex }
	::= { pm10001otu4CfgClientStartupTable 1 }


Pm10001otu4CfgClientStartupEntry ::=
	SEQUENCE {
	pm10001otu4CfgClientStartupIndex
		INTEGER,
	pm10001otu4CfgSystConfPortPortn
		Unsigned32,
	pm10001otu4CfgNetConfPortPortn
		Unsigned32,
	pm10001otu4CfgIgnoreTimePortn
		Unsigned32,
	pm10001otu4CfgOptionsPortPortn
		Unsigned32
	}


pm10001otu4CfgClientStartupIndex OBJECT-TYPE
	SYNTAX  INTEGER(0..128)
	MAX-ACCESS  read-only
	STATUS current
	DESCRIPTION
        "
        Index definition for the clientStartup
        table
        "
	::= { pm10001otu4CfgClientStartupEntry 1 }


pm10001otu4CfgSystConfPortPortn OBJECT-TYPE
	SYNTAX  Unsigned32 (0..65536)
	MAX-ACCESS read-write
	STATUS current
	DESCRIPTION
        "
        Default Settings on Client Port
        :This  register configures the
         default initialisation settings
        on the port.
        "
	::= { pm10001otu4CfgClientStartupEntry 3 }


pm10001otu4CfgNetConfPortPortn OBJECT-TYPE
	SYNTAX  Unsigned32 (0..65536)
	MAX-ACCESS read-write
	STATUS current
	DESCRIPTION
        "
        Default Settings on Client Port
        :This  register configures the
         default initialisation settings
        on the port.
        "
	::= { pm10001otu4CfgClientStartupEntry 4 }


pm10001otu4CfgIgnoreTimePortn OBJECT-TYPE
	SYNTAX  Unsigned32 (0..65536)
	MAX-ACCESS read-write
	STATUS current
	DESCRIPTION
        "
        Default Settings on Client Port
        :This  register configures the
         default initialisation settings
        on the port.
        "
	::= { pm10001otu4CfgClientStartupEntry 6 }


pm10001otu4CfgOptionsPortPortn OBJECT-TYPE
	SYNTAX  Unsigned32 (0..65536)
	MAX-ACCESS read-write
	STATUS current
	DESCRIPTION
        "
        Default Options on Client Port
        :This register configures the default
        options on the port.
        "
	::= { pm10001otu4CfgClientStartupEntry 14 }


--- *****************************************************
---     LEAF for the table 2190
--- *****************************************************

pm10001otu4CfgLineStartupTable OBJECT-TYPE
	SYNTAX  SEQUENCE OF Pm10001otu4CfgLineStartupEntry
	MAX-ACCESS not-accessible
	STATUS current
	DESCRIPTION
        "
        List of  Article
        "
	::= { pm10001otu4CfgStartup 2 }


pm10001otu4CfgLineStartupEntry OBJECT-TYPE
	SYNTAX Pm10001otu4CfgLineStartupEntry
	MAX-ACCESS not-accessible
	STATUS current
	DESCRIPTION
        "
        Row definition for the startup
        table
        "
	INDEX   { pm10001otu4CfgLineStartupIndex }
	::= { pm10001otu4CfgLineStartupTable 1 }


Pm10001otu4CfgLineStartupEntry ::=
	SEQUENCE {
	pm10001otu4CfgLineStartupIndex
		INTEGER,
	pm10001otu4CfgSystConfLinePortn
		Unsigned32,
	pm10001otu4CfgOptionsLinePortn
		Unsigned32
	}


pm10001otu4CfgLineStartupIndex OBJECT-TYPE
	SYNTAX  INTEGER(0..128)
	MAX-ACCESS  read-only
	STATUS current
	DESCRIPTION
        "
        Index definition for the lineStartup
        table
        "
	::= { pm10001otu4CfgLineStartupEntry 1 }


pm10001otu4CfgSystConfLinePortn OBJECT-TYPE
	SYNTAX  Unsigned32 (0..65536)
	MAX-ACCESS read-write
	STATUS current
	DESCRIPTION
        "
        Default Settings on Line :This
        register configures the default
        initialisation settings on Line
        "
	::= { pm10001otu4CfgLineStartupEntry 3 }


pm10001otu4CfgOptionsLinePortn OBJECT-TYPE
	SYNTAX  Unsigned32 (0..65536)
	MAX-ACCESS read-write
	STATUS current
	DESCRIPTION
        "
        Default Options on Line :This
         register configures the default
        options on the line
        "
	::= { pm10001otu4CfgLineStartupEntry 14 }


--- *****************************************************
---     LEAF for the table 21AB
--- *****************************************************

pm10001otu4CfgXfpTable OBJECT-TYPE
	SYNTAX  SEQUENCE OF Pm10001otu4CfgXfpEntry
	MAX-ACCESS not-accessible
	STATUS current
	DESCRIPTION
        "
        List of  Article
        "
	::= { pm10001otu4CfgStartup 3 }


pm10001otu4CfgXfpEntry OBJECT-TYPE
	SYNTAX Pm10001otu4CfgXfpEntry
	MAX-ACCESS not-accessible
	STATUS current
	DESCRIPTION
        "
        Row definition for the startup
        table
        "
	INDEX   { pm10001otu4CfgXfpIndex }
	::= { pm10001otu4CfgXfpTable 1 }


Pm10001otu4CfgXfpEntry ::=
	SEQUENCE {
	pm10001otu4CfgXfpIndex
		INTEGER,
	pm10001otu4CfgSystConfMsaLinePortn
		Unsigned32,
	pm10001otu4CfgCompDispChromValuePortn
		Unsigned32
	}


pm10001otu4CfgXfpIndex OBJECT-TYPE
	SYNTAX  INTEGER(0..128)
	MAX-ACCESS  read-only
	STATUS current
	DESCRIPTION
        "
        Index definition for the xfp table
        "
	::= { pm10001otu4CfgXfpEntry 1 }


pm10001otu4CfgSystConfMsaLinePortn OBJECT-TYPE
	SYNTAX  Unsigned32 (0..65536)
	MAX-ACCESS read-write
	STATUS current
	DESCRIPTION
        "
        Default settings on MSA :This
         register configures the default
        initialisation settings on MSA
        "
	::= { pm10001otu4CfgXfpEntry 3 }


pm10001otu4CfgCompDispChromValuePortn OBJECT-TYPE
	SYNTAX  Unsigned32 (0..65536)
	MAX-ACCESS read-write
	STATUS current
	DESCRIPTION
        "
        Default settings on MSA :This
         register configures the default
        chromatic dispersion compensation
        value
        "
	::= { pm10001otu4CfgXfpEntry 4 }


--- *****************************************************
---     LEAF for the table Group labels
--- *****************************************************

pm10001otu4CfgLabels OBJECT IDENTIFIER ::= { pm10001otu4Config 3 }



--- *****************************************************
---     LEAF for the table 0003
--- *****************************************************

pm10001otu4CfgLabelclientTable OBJECT-TYPE
	SYNTAX  SEQUENCE OF Pm10001otu4CfgLabelclientEntry
	MAX-ACCESS not-accessible
	STATUS current
	DESCRIPTION
        "
        List of  Article
        "
	::= { pm10001otu4CfgLabels 1 }


pm10001otu4CfgLabelclientEntry OBJECT-TYPE
	SYNTAX Pm10001otu4CfgLabelclientEntry
	MAX-ACCESS not-accessible
	STATUS current
	DESCRIPTION
        "
        Row definition for the labels
         table
        "
	INDEX   { pm10001otu4CfgLabelclientIndex }
	::= { pm10001otu4CfgLabelclientTable 1 }


Pm10001otu4CfgLabelclientEntry ::=
	SEQUENCE {
	pm10001otu4CfgLabelclientIndex
		INTEGER,
	pm10001otu4CfgLabelclientPortn
		DisplayString
	}


pm10001otu4CfgLabelclientIndex OBJECT-TYPE
	SYNTAX  INTEGER(0..128)
	MAX-ACCESS  read-only
	STATUS current
	DESCRIPTION
        "
        Index definition for the labelclient
        table
        "
	::= { pm10001otu4CfgLabelclientEntry 1 }


pm10001otu4CfgLabelclientPortn OBJECT-TYPE
	SYNTAX  DisplayString( SIZE(1..16))
	MAX-ACCESS read-write
	STATUS current
	DESCRIPTION
        "
        Default settings on the label
         of the Ports :These registers
         configures the default initialisation
        settings of the labels of the ports.
        "
	::= { pm10001otu4CfgLabelclientEntry 3 }


--- *****************************************************
---     LEAF for the table 0004
--- *****************************************************

pm10001otu4CfgLabellineTable OBJECT-TYPE
	SYNTAX  SEQUENCE OF Pm10001otu4CfgLabellineEntry
	MAX-ACCESS not-accessible
	STATUS current
	DESCRIPTION
        "
        List of  Article
        "
	::= { pm10001otu4CfgLabels 2 }


pm10001otu4CfgLabellineEntry OBJECT-TYPE
	SYNTAX Pm10001otu4CfgLabellineEntry
	MAX-ACCESS not-accessible
	STATUS current
	DESCRIPTION
        "
        Row definition for the labels
         table
        "
	INDEX   { pm10001otu4CfgLabellineIndex }
	::= { pm10001otu4CfgLabellineTable 1 }


Pm10001otu4CfgLabellineEntry ::=
	SEQUENCE {
	pm10001otu4CfgLabellineIndex
		INTEGER,
	pm10001otu4CfgLabellinePortn
		DisplayString
	}


pm10001otu4CfgLabellineIndex OBJECT-TYPE
	SYNTAX  INTEGER(0..128)
	MAX-ACCESS  read-only
	STATUS current
	DESCRIPTION
        "
        Index definition for the labelline
        table
        "
	::= { pm10001otu4CfgLabellineEntry 1 }


pm10001otu4CfgLabellinePortn OBJECT-TYPE
	SYNTAX  DisplayString( SIZE(1..16))
	MAX-ACCESS read-write
	STATUS current
	DESCRIPTION
        "
        Default settings on the label
         of the lines :These registers
         configures the default initialisation
        settings of the labels of the lines.
        "
	::= { pm10001otu4CfgLabellineEntry 3 }


--- *****************************************************
---     LEAF for the table Group startuptlh
--- *****************************************************

pm10001otu4CfgStartuptlh OBJECT IDENTIFIER ::= { pm10001otu4Config 4 }



--- *****************************************************
---     LEAF for the table 25AB
--- *****************************************************

pm10001otu4CfgOtxtlhTable OBJECT-TYPE
	SYNTAX  SEQUENCE OF Pm10001otu4CfgOtxtlhEntry
	MAX-ACCESS not-accessible
	STATUS current
	DESCRIPTION
        "
        List of  Article
        "
	::= { pm10001otu4CfgStartuptlh 1 }


pm10001otu4CfgOtxtlhEntry OBJECT-TYPE
	SYNTAX Pm10001otu4CfgOtxtlhEntry
	MAX-ACCESS not-accessible
	STATUS current
	DESCRIPTION
        "
        Row definition for the startuptlh
        table
        "
	INDEX   { pm10001otu4CfgOtxtlhIndex }
	::= { pm10001otu4CfgOtxtlhTable 1 }


Pm10001otu4CfgOtxtlhEntry ::=
	SEQUENCE {
	pm10001otu4CfgOtxtlhIndex
		INTEGER,
	pm10001otu4CfgLinePwrLaserPortn
		Unsigned32,
	pm10001otu4CfgLineFCurrentPortn
		Unsigned32,
	pm10001otu4CfgLineGridCurrentPortn
		Unsigned32,
	pm10001otu4CfgFPortn
		Unsigned32,
	pm10001otu4CfgRxLineFCurrentPortn
		Unsigned32
	}


pm10001otu4CfgOtxtlhIndex OBJECT-TYPE
	SYNTAX  INTEGER(0..128)
	MAX-ACCESS  read-only
	STATUS current
	DESCRIPTION
        "
        Index definition for the otxtlh
        table
        "
	::= { pm10001otu4CfgOtxtlhEntry 1 }


pm10001otu4CfgLinePwrLaserPortn OBJECT-TYPE
	SYNTAX  Unsigned32 (0..65536)
	MAX-ACCESS read-write
	STATUS current
	DESCRIPTION
        "
        Defaut Line output Power :This
        register configures the start-up
        output power of the Line tranceiver
         (Unit = dBm)
        "
	::= { pm10001otu4CfgOtxtlhEntry 6 }


pm10001otu4CfgLineFCurrentPortn OBJECT-TYPE
	SYNTAX  Unsigned32 (0..65536)
	MAX-ACCESS read-write
	STATUS current
	DESCRIPTION
        "
        Default Line transceiver Tx Channel
        :This register configures the start-up
        laser channel of the Line Tx transceiver
        "
	::= { pm10001otu4CfgOtxtlhEntry 7 }


pm10001otu4CfgLineGridCurrentPortn OBJECT-TYPE
	SYNTAX  Unsigned32 (0..65536)
	MAX-ACCESS read-write
	STATUS current
	DESCRIPTION
        "
        Default Line transceiver Grid
         :This register configures the
         start-up laser grid of the Line
        transceiver
        "
	::= { pm10001otu4CfgOtxtlhEntry 8 }


pm10001otu4CfgFPortn OBJECT-TYPE
	SYNTAX  Unsigned32 (0..65536)
	MAX-ACCESS read-write
	STATUS current
	DESCRIPTION
        "
        Default Line TRX lowest Freq :This
        register configures the start-up
        lowest frequency of the Line transceiver
        "
	::= { pm10001otu4CfgOtxtlhEntry 9 }


pm10001otu4CfgRxLineFCurrentPortn OBJECT-TYPE
	SYNTAX  Unsigned32 (0..65536)
	MAX-ACCESS read-write
	STATUS current
	DESCRIPTION
        "
        Default Line transceiver Rx Channel
        :This register configures the start-up
        laser channel of the Line Rx transceiver
        "
	::= { pm10001otu4CfgOtxtlhEntry 10 }


--- *****************************************************
---     LEAF for the table Group other
--- *****************************************************

pm10001otu4CfgOther OBJECT IDENTIFIER ::= { pm10001otu4Config 5 }



--- *****************************************************
---     LEAF for the table 2300
--- *****************************************************

pm10001otu4tablemoduleOther OBJECT IDENTIFIER ::= { pm10001otu4CfgOther 1 }



pm10001otu4Cfgmode OBJECT-TYPE
	  SYNTAX Unsigned32 (0..65536)
	  MAX-ACCESS read-write
	  STATUS current
	  DESCRIPTION
        "
        Default settings on Module :This
        register selects the configuration
        mode of the module
        "
	  ::= { pm10001otu4tablemoduleOther 2 }



pm10001otu4CfgnonLinearEffectsThresholds OBJECT-TYPE
	  SYNTAX Unsigned32 (0..65536)
	  MAX-ACCESS read-write
	  STATUS current
	  DESCRIPTION
        "
        Default settings on Module :This
        register selects the CPR and CMA
        parameters applied to the line
        "
	  ::= { pm10001otu4tablemoduleOther 3 }



pm10001otu4CfgfanHighSpeedThreshold OBJECT-TYPE
	  SYNTAX Unsigned32 (0..65536)
	  MAX-ACCESS read-write
	  STATUS current
	  DESCRIPTION
        "
        Default settings on Module :This
        register selects the speed threshold
        of the fan's
        "
	  ::= { pm10001otu4tablemoduleOther 4 }



--- *****************************************************
---     LEAF for the table Group startuptablefive
--- *****************************************************

pm10001otu4CfgStartuptablefive OBJECT IDENTIFIER ::= { pm10001otu4Config 6 }



--- *****************************************************
---     LEAF for the table 0005
--- *****************************************************

pm10001otu4CfgOtxtlhcapabilitiesTable OBJECT-TYPE
	SYNTAX  SEQUENCE OF Pm10001otu4CfgOtxtlhcapabilitiesEntry
	MAX-ACCESS not-accessible
	STATUS current
	DESCRIPTION
        "
        List of  Article
        "
	::= { pm10001otu4CfgStartuptablefive 1 }


pm10001otu4CfgOtxtlhcapabilitiesEntry OBJECT-TYPE
	SYNTAX Pm10001otu4CfgOtxtlhcapabilitiesEntry
	MAX-ACCESS not-accessible
	STATUS current
	DESCRIPTION
        "
        Row definition for the startuptablefive
        table
        "
	INDEX   { pm10001otu4CfgOtxtlhcapabilitiesIndex }
	::= { pm10001otu4CfgOtxtlhcapabilitiesTable 1 }


Pm10001otu4CfgOtxtlhcapabilitiesEntry ::=
	SEQUENCE {
	pm10001otu4CfgOtxtlhcapabilitiesIndex
		INTEGER,
	pm10001otu4CfgComponentTypePortn
		Unsigned32,
	pm10001otu4CfgMiscellaneousPortn
		Unsigned32,
	pm10001otu4CfgFirstChannelPortn
		Unsigned32,
	pm10001otu4CfgLastChannelPortn
		Unsigned32,
	pm10001otu4CfgGridPortn
		Unsigned32
	}


pm10001otu4CfgOtxtlhcapabilitiesIndex OBJECT-TYPE
	SYNTAX  INTEGER(0..128)
	MAX-ACCESS  read-only
	STATUS current
	DESCRIPTION
        "
        Index definition for the otxtlhcapabilities
        table
        "
	::= { pm10001otu4CfgOtxtlhcapabilitiesEntry 1 }


pm10001otu4CfgComponentTypePortn OBJECT-TYPE
	SYNTAX  Unsigned32 (0..65536)
	MAX-ACCESS read-only
	STATUS current
	DESCRIPTION
        "
        Component parameters :This OID
        defines the component parameters
        "
	::= { pm10001otu4CfgOtxtlhcapabilitiesEntry 3 }


pm10001otu4CfgMiscellaneousPortn OBJECT-TYPE
	SYNTAX  Unsigned32 (0..65536)
	MAX-ACCESS read-only
	STATUS current
	DESCRIPTION
        "
        Miscellaneous default settings
        :This OID defines the miscellaneous
        parameters
        "
	::= { pm10001otu4CfgOtxtlhcapabilitiesEntry 4 }


pm10001otu4CfgFirstChannelPortn OBJECT-TYPE
	SYNTAX  Unsigned32 (0..65536)
	MAX-ACCESS read-only
	STATUS current
	DESCRIPTION
        "
        Number of the first channel of
        the component :This OID defines
        the first channel number of the
        PM
        "
	::= { pm10001otu4CfgOtxtlhcapabilitiesEntry 5 }


pm10001otu4CfgLastChannelPortn OBJECT-TYPE
	SYNTAX  Unsigned32 (0..65536)
	MAX-ACCESS read-only
	STATUS current
	DESCRIPTION
        "
        Number of the last channel of
         the component :This OID defines
        the last channel number of the
         PM
        "
	::= { pm10001otu4CfgOtxtlhcapabilitiesEntry 6 }


pm10001otu4CfgGridPortn OBJECT-TYPE
	SYNTAX  Unsigned32 (0..65536)
	MAX-ACCESS read-only
	STATUS current
	DESCRIPTION
        "
        Grid value of the component :This
        OID defines the grid of the PM
        "
	::= { pm10001otu4CfgOtxtlhcapabilitiesEntry 7 }


--- *****************************************************
---     LEAF for the table Group startuptableslot
--- *****************************************************

pm10001otu4CfgStartuptableslot OBJECT IDENTIFIER ::= { pm10001otu4Config 7 }



--- *****************************************************
---     LEAF for the table 4210
--- *****************************************************

pm10001otu4CfgLinePtmsiAccOtnTable OBJECT-TYPE
	SYNTAX  SEQUENCE OF Pm10001otu4CfgLinePtmsiAccOtnEntry
	MAX-ACCESS not-accessible
	STATUS current
	DESCRIPTION
        "
        List of  Article
        "
	::= { pm10001otu4CfgStartuptableslot 1 }


pm10001otu4CfgLinePtmsiAccOtnEntry OBJECT-TYPE
	SYNTAX Pm10001otu4CfgLinePtmsiAccOtnEntry
	MAX-ACCESS not-accessible
	STATUS current
	DESCRIPTION
        "
        Row definition for the startuptableslot
        table
        "
	INDEX   { pm10001otu4CfgLinePtmsiAccOtnIndex }
	::= { pm10001otu4CfgLinePtmsiAccOtnTable 1 }


Pm10001otu4CfgLinePtmsiAccOtnEntry ::=
	SEQUENCE {
	pm10001otu4CfgLinePtmsiAccOtnIndex
		INTEGER,
	pm10001otu4CfgPayloadtypePortn
		Unsigned32,
	pm10001otu4CfgPtmsireservedPortn
		Unsigned32,
	pm10001otu4CfgTimeslot1valPortn
		Unsigned32,
	pm10001otu4CfgTimeslot2valPortn
		Unsigned32,
	pm10001otu4CfgTimeslot3valPortn
		Unsigned32,
	pm10001otu4CfgTimeslot4valPortn
		Unsigned32,
	pm10001otu4CfgTimeslot5valPortn
		Unsigned32,
	pm10001otu4CfgTimeslot6valPortn
		Unsigned32,
	pm10001otu4CfgTimeslot7valPortn
		Unsigned32,
	pm10001otu4CfgTimeslot8valPortn
		Unsigned32,
	pm10001otu4CfgTimeslot9valPortn
		Unsigned32,
	pm10001otu4CfgTimeslot10valPortn
		Unsigned32,
	pm10001otu4CfgTimeslot11valPortn
		Unsigned32,
	pm10001otu4CfgTimeslot12valPortn
		Unsigned32,
	pm10001otu4CfgTimeslot13valPortn
		Unsigned32,
	pm10001otu4CfgTimeslot14valPortn
		Unsigned32,
	pm10001otu4CfgTimeslot15valPortn
		Unsigned32,
	pm10001otu4CfgTimeslot16valPortn
		Unsigned32,
	pm10001otu4CfgTimeslot17valPortn
		Unsigned32,
	pm10001otu4CfgTimeslot18valPortn
		Unsigned32,
	pm10001otu4CfgTimeslot19valPortn
		Unsigned32,
	pm10001otu4CfgTimeslot20valPortn
		Unsigned32,
	pm10001otu4CfgTimeslot21valPortn
		Unsigned32,
	pm10001otu4CfgTimeslot22valPortn
		Unsigned32,
	pm10001otu4CfgTimeslot23valPortn
		Unsigned32,
	pm10001otu4CfgTimeslot24valPortn
		Unsigned32,
	pm10001otu4CfgTimeslot25valPortn
		Unsigned32,
	pm10001otu4CfgTimeslot26valPortn
		Unsigned32,
	pm10001otu4CfgTimeslot27valPortn
		Unsigned32,
	pm10001otu4CfgTimeslot28valPortn
		Unsigned32,
	pm10001otu4CfgTimeslot29valPortn
		Unsigned32,
	pm10001otu4CfgTimeslot30valPortn
		Unsigned32,
	pm10001otu4CfgTimeslot31valPortn
		Unsigned32,
	pm10001otu4CfgTimeslot32valPortn
		Unsigned32,
	pm10001otu4CfgTimeslot33valPortn
		Unsigned32,
	pm10001otu4CfgTimeslot34valPortn
		Unsigned32,
	pm10001otu4CfgTimeslot35valPortn
		Unsigned32,
	pm10001otu4CfgTimeslot36valPortn
		Unsigned32,
	pm10001otu4CfgTimeslot37valPortn
		Unsigned32,
	pm10001otu4CfgTimeslot38valPortn
		Unsigned32,
	pm10001otu4CfgTimeslot39valPortn
		Unsigned32,
	pm10001otu4CfgTimeslot40valPortn
		Unsigned32,
	pm10001otu4CfgTimeslot41valPortn
		Unsigned32,
	pm10001otu4CfgTimeslot42valPortn
		Unsigned32,
	pm10001otu4CfgTimeslot43valPortn
		Unsigned32,
	pm10001otu4CfgTimeslot44valPortn
		Unsigned32,
	pm10001otu4CfgTimeslot45valPortn
		Unsigned32,
	pm10001otu4CfgTimeslot46valPortn
		Unsigned32,
	pm10001otu4CfgTimeslot47valPortn
		Unsigned32,
	pm10001otu4CfgTimeslot48valPortn
		Unsigned32,
	pm10001otu4CfgTimeslot49valPortn
		Unsigned32,
	pm10001otu4CfgTimeslot50valPortn
		Unsigned32,
	pm10001otu4CfgTimeslot51valPortn
		Unsigned32,
	pm10001otu4CfgTimeslot52valPortn
		Unsigned32,
	pm10001otu4CfgTimeslot53valPortn
		Unsigned32,
	pm10001otu4CfgTimeslot54valPortn
		Unsigned32,
	pm10001otu4CfgTimeslot55valPortn
		Unsigned32,
	pm10001otu4CfgTimeslot56valPortn
		Unsigned32,
	pm10001otu4CfgTimeslot57valPortn
		Unsigned32,
	pm10001otu4CfgTimeslot58valPortn
		Unsigned32,
	pm10001otu4CfgTimeslot59valPortn
		Unsigned32,
	pm10001otu4CfgTimeslot60valPortn
		Unsigned32,
	pm10001otu4CfgTimeslot61valPortn
		Unsigned32,
	pm10001otu4CfgTimeslot62valPortn
		Unsigned32,
	pm10001otu4CfgTimeslot63valPortn
		Unsigned32,
	pm10001otu4CfgTimeslot64valPortn
		Unsigned32,
	pm10001otu4CfgTimeslot65valPortn
		Unsigned32,
	pm10001otu4CfgTimeslot66valPortn
		Unsigned32,
	pm10001otu4CfgTimeslot67valPortn
		Unsigned32,
	pm10001otu4CfgTimeslot68valPortn
		Unsigned32,
	pm10001otu4CfgTimeslot69valPortn
		Unsigned32,
	pm10001otu4CfgTimeslot70valPortn
		Unsigned32,
	pm10001otu4CfgTimeslot71valPortn
		Unsigned32,
	pm10001otu4CfgTimeslot72valPortn
		Unsigned32,
	pm10001otu4CfgTimeslot73valPortn
		Unsigned32,
	pm10001otu4CfgTimeslot74valPortn
		Unsigned32,
	pm10001otu4CfgTimeslot75valPortn
		Unsigned32,
	pm10001otu4CfgTimeslot76valPortn
		Unsigned32,
	pm10001otu4CfgTimeslot77valPortn
		Unsigned32,
	pm10001otu4CfgTimeslot78valPortn
		Unsigned32,
	pm10001otu4CfgTimeslot79valPortn
		Unsigned32,
	pm10001otu4CfgTimeslot80valPortn
		Unsigned32
	}


pm10001otu4CfgLinePtmsiAccOtnIndex OBJECT-TYPE
	SYNTAX  INTEGER(0..128)
	MAX-ACCESS  read-only
	STATUS current
	DESCRIPTION
        "
        Index definition for the linePtmsiAccOtn
        table
        "
	::= { pm10001otu4CfgLinePtmsiAccOtnEntry 1 }


pm10001otu4CfgPayloadtypePortn OBJECT-TYPE
	SYNTAX  Unsigned32 (0..65536)
	MAX-ACCESS read-only
	STATUS current
	DESCRIPTION
        "
        Payload Type :This register contains
        the value of the Payload Type
        "
	::= { pm10001otu4CfgLinePtmsiAccOtnEntry 3 }


pm10001otu4CfgPtmsireservedPortn OBJECT-TYPE
	SYNTAX  Unsigned32 (0..65536)
	MAX-ACCESS read-only
	STATUS current
	DESCRIPTION
        "
        Reserved :Reserved
        "
	::= { pm10001otu4CfgLinePtmsiAccOtnEntry 4 }


pm10001otu4CfgTimeslot1valPortn OBJECT-TYPE
	SYNTAX  Unsigned32 (0..65536)
	MAX-ACCESS read-only
	STATUS current
	DESCRIPTION
        "
        Time Slot 1 :This register contains
        the value of the Time Slot
        "
	::= { pm10001otu4CfgLinePtmsiAccOtnEntry 5 }


pm10001otu4CfgTimeslot2valPortn OBJECT-TYPE
	SYNTAX  Unsigned32 (0..65536)
	MAX-ACCESS read-only
	STATUS current
	DESCRIPTION
        "
        Time Slot 2 :This register contains
        the value of the Time Slot
        "
	::= { pm10001otu4CfgLinePtmsiAccOtnEntry 6 }


pm10001otu4CfgTimeslot3valPortn OBJECT-TYPE
	SYNTAX  Unsigned32 (0..65536)
	MAX-ACCESS read-only
	STATUS current
	DESCRIPTION
        "
        Time Slot 3 :This register contains
        the value of the Time Slot
        "
	::= { pm10001otu4CfgLinePtmsiAccOtnEntry 7 }


pm10001otu4CfgTimeslot4valPortn OBJECT-TYPE
	SYNTAX  Unsigned32 (0..65536)
	MAX-ACCESS read-only
	STATUS current
	DESCRIPTION
        "
        Time Slot 4 :This register contains
        the value of the Time Slot
        "
	::= { pm10001otu4CfgLinePtmsiAccOtnEntry 8 }


pm10001otu4CfgTimeslot5valPortn OBJECT-TYPE
	SYNTAX  Unsigned32 (0..65536)
	MAX-ACCESS read-only
	STATUS current
	DESCRIPTION
        "
        Time Slot 5 :This register contains
        the value of the Time Slot
        "
	::= { pm10001otu4CfgLinePtmsiAccOtnEntry 9 }


pm10001otu4CfgTimeslot6valPortn OBJECT-TYPE
	SYNTAX  Unsigned32 (0..65536)
	MAX-ACCESS read-only
	STATUS current
	DESCRIPTION
        "
        Time Slot 6 :This register contains
        the value of the Time Slot
        "
	::= { pm10001otu4CfgLinePtmsiAccOtnEntry 10 }


pm10001otu4CfgTimeslot7valPortn OBJECT-TYPE
	SYNTAX  Unsigned32 (0..65536)
	MAX-ACCESS read-only
	STATUS current
	DESCRIPTION
        "
        Time Slot 7 :This register contains
        the value of the Time Slot
        "
	::= { pm10001otu4CfgLinePtmsiAccOtnEntry 11 }


pm10001otu4CfgTimeslot8valPortn OBJECT-TYPE
	SYNTAX  Unsigned32 (0..65536)
	MAX-ACCESS read-only
	STATUS current
	DESCRIPTION
        "
        Time Slot 8 :This register contains
        the value of the Time Slot
        "
	::= { pm10001otu4CfgLinePtmsiAccOtnEntry 12 }


pm10001otu4CfgTimeslot9valPortn OBJECT-TYPE
	SYNTAX  Unsigned32 (0..65536)
	MAX-ACCESS read-only
	STATUS current
	DESCRIPTION
        "
        Time Slot 9 :This register contains
        the value of the Time Slot
        "
	::= { pm10001otu4CfgLinePtmsiAccOtnEntry 13 }


pm10001otu4CfgTimeslot10valPortn OBJECT-TYPE
	SYNTAX  Unsigned32 (0..65536)
	MAX-ACCESS read-only
	STATUS current
	DESCRIPTION
        "
        Time Slot 10 :This register contains
        the value of the Time Slot
        "
	::= { pm10001otu4CfgLinePtmsiAccOtnEntry 14 }


pm10001otu4CfgTimeslot11valPortn OBJECT-TYPE
	SYNTAX  Unsigned32 (0..65536)
	MAX-ACCESS read-only
	STATUS current
	DESCRIPTION
        "
        Time Slot 11 :This register contains
        the value of the Time Slot
        "
	::= { pm10001otu4CfgLinePtmsiAccOtnEntry 15 }


pm10001otu4CfgTimeslot12valPortn OBJECT-TYPE
	SYNTAX  Unsigned32 (0..65536)
	MAX-ACCESS read-only
	STATUS current
	DESCRIPTION
        "
        Time Slot 12 :This register contains
        the value of the Time Slot
        "
	::= { pm10001otu4CfgLinePtmsiAccOtnEntry 16 }


pm10001otu4CfgTimeslot13valPortn OBJECT-TYPE
	SYNTAX  Unsigned32 (0..65536)
	MAX-ACCESS read-only
	STATUS current
	DESCRIPTION
        "
        Time Slot 13 :This register contains
        the value of the Time Slot
        "
	::= { pm10001otu4CfgLinePtmsiAccOtnEntry 17 }


pm10001otu4CfgTimeslot14valPortn OBJECT-TYPE
	SYNTAX  Unsigned32 (0..65536)
	MAX-ACCESS read-only
	STATUS current
	DESCRIPTION
        "
        Time Slot 14 :This register contains
        the value of the Time Slot
        "
	::= { pm10001otu4CfgLinePtmsiAccOtnEntry 18 }


pm10001otu4CfgTimeslot15valPortn OBJECT-TYPE
	SYNTAX  Unsigned32 (0..65536)
	MAX-ACCESS read-only
	STATUS current
	DESCRIPTION
        "
        Time Slot 15 :This register contains
        the value of the Time Slot
        "
	::= { pm10001otu4CfgLinePtmsiAccOtnEntry 19 }


pm10001otu4CfgTimeslot16valPortn OBJECT-TYPE
	SYNTAX  Unsigned32 (0..65536)
	MAX-ACCESS read-only
	STATUS current
	DESCRIPTION
        "
        Time Slot 16 :This register contains
        the value of the Time Slot
        "
	::= { pm10001otu4CfgLinePtmsiAccOtnEntry 20 }


pm10001otu4CfgTimeslot17valPortn OBJECT-TYPE
	SYNTAX  Unsigned32 (0..65536)
	MAX-ACCESS read-only
	STATUS current
	DESCRIPTION
        "
        Time Slot 17 :This register contains
        the value of the Time Slot
        "
	::= { pm10001otu4CfgLinePtmsiAccOtnEntry 21 }


pm10001otu4CfgTimeslot18valPortn OBJECT-TYPE
	SYNTAX  Unsigned32 (0..65536)
	MAX-ACCESS read-only
	STATUS current
	DESCRIPTION
        "
        Time Slot 18 :This register contains
        the value of the Time Slot
        "
	::= { pm10001otu4CfgLinePtmsiAccOtnEntry 22 }


pm10001otu4CfgTimeslot19valPortn OBJECT-TYPE
	SYNTAX  Unsigned32 (0..65536)
	MAX-ACCESS read-only
	STATUS current
	DESCRIPTION
        "
        Time Slot 19 :This register contains
        the value of the Time Slot
        "
	::= { pm10001otu4CfgLinePtmsiAccOtnEntry 23 }


pm10001otu4CfgTimeslot20valPortn OBJECT-TYPE
	SYNTAX  Unsigned32 (0..65536)
	MAX-ACCESS read-only
	STATUS current
	DESCRIPTION
        "
        Time Slot 20 :This register contains
        the value of the Time Slot
        "
	::= { pm10001otu4CfgLinePtmsiAccOtnEntry 24 }


pm10001otu4CfgTimeslot21valPortn OBJECT-TYPE
	SYNTAX  Unsigned32 (0..65536)
	MAX-ACCESS read-only
	STATUS current
	DESCRIPTION
        "
        Time Slot 21 :This register contains
        the value of the Time Slot
        "
	::= { pm10001otu4CfgLinePtmsiAccOtnEntry 25 }


pm10001otu4CfgTimeslot22valPortn OBJECT-TYPE
	SYNTAX  Unsigned32 (0..65536)
	MAX-ACCESS read-only
	STATUS current
	DESCRIPTION
        "
        Time Slot 22 :This register contains
        the value of the Time Slot
        "
	::= { pm10001otu4CfgLinePtmsiAccOtnEntry 26 }


pm10001otu4CfgTimeslot23valPortn OBJECT-TYPE
	SYNTAX  Unsigned32 (0..65536)
	MAX-ACCESS read-only
	STATUS current
	DESCRIPTION
        "
        Time Slot 23 :This register contains
        the value of the Time Slot
        "
	::= { pm10001otu4CfgLinePtmsiAccOtnEntry 27 }


pm10001otu4CfgTimeslot24valPortn OBJECT-TYPE
	SYNTAX  Unsigned32 (0..65536)
	MAX-ACCESS read-only
	STATUS current
	DESCRIPTION
        "
        Time Slot 24 :This register contains
        the value of the Time Slot
        "
	::= { pm10001otu4CfgLinePtmsiAccOtnEntry 28 }


pm10001otu4CfgTimeslot25valPortn OBJECT-TYPE
	SYNTAX  Unsigned32 (0..65536)
	MAX-ACCESS read-only
	STATUS current
	DESCRIPTION
        "
        Time Slot 25 :This register contains
        the value of the Time Slot
        "
	::= { pm10001otu4CfgLinePtmsiAccOtnEntry 29 }


pm10001otu4CfgTimeslot26valPortn OBJECT-TYPE
	SYNTAX  Unsigned32 (0..65536)
	MAX-ACCESS read-only
	STATUS current
	DESCRIPTION
        "
        Time Slot 26 :This register contains
        the value of the Time Slot
        "
	::= { pm10001otu4CfgLinePtmsiAccOtnEntry 30 }


pm10001otu4CfgTimeslot27valPortn OBJECT-TYPE
	SYNTAX  Unsigned32 (0..65536)
	MAX-ACCESS read-only
	STATUS current
	DESCRIPTION
        "
        Time Slot 27 :This register contains
        the value of the Time Slot
        "
	::= { pm10001otu4CfgLinePtmsiAccOtnEntry 31 }


pm10001otu4CfgTimeslot28valPortn OBJECT-TYPE
	SYNTAX  Unsigned32 (0..65536)
	MAX-ACCESS read-only
	STATUS current
	DESCRIPTION
        "
        Time Slot 28 :This register contains
        the value of the Time Slot
        "
	::= { pm10001otu4CfgLinePtmsiAccOtnEntry 32 }


pm10001otu4CfgTimeslot29valPortn OBJECT-TYPE
	SYNTAX  Unsigned32 (0..65536)
	MAX-ACCESS read-only
	STATUS current
	DESCRIPTION
        "
        Time Slot 29 :This register contains
        the value of the Time Slot
        "
	::= { pm10001otu4CfgLinePtmsiAccOtnEntry 33 }


pm10001otu4CfgTimeslot30valPortn OBJECT-TYPE
	SYNTAX  Unsigned32 (0..65536)
	MAX-ACCESS read-only
	STATUS current
	DESCRIPTION
        "
        Time Slot 30 :This register contains
        the value of the Time Slot
        "
	::= { pm10001otu4CfgLinePtmsiAccOtnEntry 34 }


pm10001otu4CfgTimeslot31valPortn OBJECT-TYPE
	SYNTAX  Unsigned32 (0..65536)
	MAX-ACCESS read-only
	STATUS current
	DESCRIPTION
        "
        Time Slot 31 :This register contains
        the value of the Time Slot
        "
	::= { pm10001otu4CfgLinePtmsiAccOtnEntry 35 }


pm10001otu4CfgTimeslot32valPortn OBJECT-TYPE
	SYNTAX  Unsigned32 (0..65536)
	MAX-ACCESS read-only
	STATUS current
	DESCRIPTION
        "
        Time Slot 32 :This register contains
        the value of the Time Slot
        "
	::= { pm10001otu4CfgLinePtmsiAccOtnEntry 36 }


pm10001otu4CfgTimeslot33valPortn OBJECT-TYPE
	SYNTAX  Unsigned32 (0..65536)
	MAX-ACCESS read-only
	STATUS current
	DESCRIPTION
        "
        Time Slot 33 :This register contains
        the value of the Time Slot
        "
	::= { pm10001otu4CfgLinePtmsiAccOtnEntry 37 }


pm10001otu4CfgTimeslot34valPortn OBJECT-TYPE
	SYNTAX  Unsigned32 (0..65536)
	MAX-ACCESS read-only
	STATUS current
	DESCRIPTION
        "
        Time Slot 34 :This register contains
        the value of the Time Slot
        "
	::= { pm10001otu4CfgLinePtmsiAccOtnEntry 38 }


pm10001otu4CfgTimeslot35valPortn OBJECT-TYPE
	SYNTAX  Unsigned32 (0..65536)
	MAX-ACCESS read-only
	STATUS current
	DESCRIPTION
        "
        Time Slot 35 :This register contains
        the value of the Time Slot
        "
	::= { pm10001otu4CfgLinePtmsiAccOtnEntry 39 }


pm10001otu4CfgTimeslot36valPortn OBJECT-TYPE
	SYNTAX  Unsigned32 (0..65536)
	MAX-ACCESS read-only
	STATUS current
	DESCRIPTION
        "
        Time Slot 36 :This register contains
        the value of the Time Slot
        "
	::= { pm10001otu4CfgLinePtmsiAccOtnEntry 40 }


pm10001otu4CfgTimeslot37valPortn OBJECT-TYPE
	SYNTAX  Unsigned32 (0..65536)
	MAX-ACCESS read-only
	STATUS current
	DESCRIPTION
        "
        Time Slot 37 :This register contains
        the value of the Time Slot
        "
	::= { pm10001otu4CfgLinePtmsiAccOtnEntry 41 }


pm10001otu4CfgTimeslot38valPortn OBJECT-TYPE
	SYNTAX  Unsigned32 (0..65536)
	MAX-ACCESS read-only
	STATUS current
	DESCRIPTION
        "
        Time Slot 38 :This register contains
        the value of the Time Slot
        "
	::= { pm10001otu4CfgLinePtmsiAccOtnEntry 42 }


pm10001otu4CfgTimeslot39valPortn OBJECT-TYPE
	SYNTAX  Unsigned32 (0..65536)
	MAX-ACCESS read-only
	STATUS current
	DESCRIPTION
        "
        Time Slot 39 :This register contains
        the value of the Time Slot
        "
	::= { pm10001otu4CfgLinePtmsiAccOtnEntry 43 }


pm10001otu4CfgTimeslot40valPortn OBJECT-TYPE
	SYNTAX  Unsigned32 (0..65536)
	MAX-ACCESS read-only
	STATUS current
	DESCRIPTION
        "
        Time Slot 40 :This register contains
        the value of the Time Slot
        "
	::= { pm10001otu4CfgLinePtmsiAccOtnEntry 44 }


pm10001otu4CfgTimeslot41valPortn OBJECT-TYPE
	SYNTAX  Unsigned32 (0..65536)
	MAX-ACCESS read-only
	STATUS current
	DESCRIPTION
        "
        Time Slot 41 :This register contains
        the value of the Time Slot
        "
	::= { pm10001otu4CfgLinePtmsiAccOtnEntry 45 }


pm10001otu4CfgTimeslot42valPortn OBJECT-TYPE
	SYNTAX  Unsigned32 (0..65536)
	MAX-ACCESS read-only
	STATUS current
	DESCRIPTION
        "
        Time Slot 42 :This register contains
        the value of the Time Slot
        "
	::= { pm10001otu4CfgLinePtmsiAccOtnEntry 46 }


pm10001otu4CfgTimeslot43valPortn OBJECT-TYPE
	SYNTAX  Unsigned32 (0..65536)
	MAX-ACCESS read-only
	STATUS current
	DESCRIPTION
        "
        Time Slot 43 :This register contains
        the value of the Time Slot
        "
	::= { pm10001otu4CfgLinePtmsiAccOtnEntry 47 }


pm10001otu4CfgTimeslot44valPortn OBJECT-TYPE
	SYNTAX  Unsigned32 (0..65536)
	MAX-ACCESS read-only
	STATUS current
	DESCRIPTION
        "
        Time Slot 44 :This register contains
        the value of the Time Slot
        "
	::= { pm10001otu4CfgLinePtmsiAccOtnEntry 48 }


pm10001otu4CfgTimeslot45valPortn OBJECT-TYPE
	SYNTAX  Unsigned32 (0..65536)
	MAX-ACCESS read-only
	STATUS current
	DESCRIPTION
        "
        Time Slot 45 :This register contains
        the value of the Time Slot
        "
	::= { pm10001otu4CfgLinePtmsiAccOtnEntry 49 }


pm10001otu4CfgTimeslot46valPortn OBJECT-TYPE
	SYNTAX  Unsigned32 (0..65536)
	MAX-ACCESS read-only
	STATUS current
	DESCRIPTION
        "
        Time Slot 46 :This register contains
        the value of the Time Slot
        "
	::= { pm10001otu4CfgLinePtmsiAccOtnEntry 50 }


pm10001otu4CfgTimeslot47valPortn OBJECT-TYPE
	SYNTAX  Unsigned32 (0..65536)
	MAX-ACCESS read-only
	STATUS current
	DESCRIPTION
        "
        Time Slot 47 :This register contains
        the value of the Time Slot
        "
	::= { pm10001otu4CfgLinePtmsiAccOtnEntry 51 }


pm10001otu4CfgTimeslot48valPortn OBJECT-TYPE
	SYNTAX  Unsigned32 (0..65536)
	MAX-ACCESS read-only
	STATUS current
	DESCRIPTION
        "
        Time Slot 48 :This register contains
        the value of the Time Slot
        "
	::= { pm10001otu4CfgLinePtmsiAccOtnEntry 52 }


pm10001otu4CfgTimeslot49valPortn OBJECT-TYPE
	SYNTAX  Unsigned32 (0..65536)
	MAX-ACCESS read-only
	STATUS current
	DESCRIPTION
        "
        Time Slot 49 :This register contains
        the value of the Time Slot
        "
	::= { pm10001otu4CfgLinePtmsiAccOtnEntry 53 }


pm10001otu4CfgTimeslot50valPortn OBJECT-TYPE
	SYNTAX  Unsigned32 (0..65536)
	MAX-ACCESS read-only
	STATUS current
	DESCRIPTION
        "
        Time Slot 50 :This register contains
        the value of the Time Slot
        "
	::= { pm10001otu4CfgLinePtmsiAccOtnEntry 54 }


pm10001otu4CfgTimeslot51valPortn OBJECT-TYPE
	SYNTAX  Unsigned32 (0..65536)
	MAX-ACCESS read-only
	STATUS current
	DESCRIPTION
        "
        Time Slot 51 :This register contains
        the value of the Time Slot
        "
	::= { pm10001otu4CfgLinePtmsiAccOtnEntry 55 }


pm10001otu4CfgTimeslot52valPortn OBJECT-TYPE
	SYNTAX  Unsigned32 (0..65536)
	MAX-ACCESS read-only
	STATUS current
	DESCRIPTION
        "
        Time Slot 52 :This register contains
        the value of the Time Slot
        "
	::= { pm10001otu4CfgLinePtmsiAccOtnEntry 56 }


pm10001otu4CfgTimeslot53valPortn OBJECT-TYPE
	SYNTAX  Unsigned32 (0..65536)
	MAX-ACCESS read-only
	STATUS current
	DESCRIPTION
        "
        Time Slot 53 :This register contains
        the value of the Time Slot
        "
	::= { pm10001otu4CfgLinePtmsiAccOtnEntry 57 }


pm10001otu4CfgTimeslot54valPortn OBJECT-TYPE
	SYNTAX  Unsigned32 (0..65536)
	MAX-ACCESS read-only
	STATUS current
	DESCRIPTION
        "
        Time Slot 54 :This register contains
        the value of the Time Slot
        "
	::= { pm10001otu4CfgLinePtmsiAccOtnEntry 58 }


pm10001otu4CfgTimeslot55valPortn OBJECT-TYPE
	SYNTAX  Unsigned32 (0..65536)
	MAX-ACCESS read-only
	STATUS current
	DESCRIPTION
        "
        Time Slot 55 :This register contains
        the value of the Time Slot
        "
	::= { pm10001otu4CfgLinePtmsiAccOtnEntry 59 }


pm10001otu4CfgTimeslot56valPortn OBJECT-TYPE
	SYNTAX  Unsigned32 (0..65536)
	MAX-ACCESS read-only
	STATUS current
	DESCRIPTION
        "
        Time Slot 56 :This register contains
        the value of the Time Slot
        "
	::= { pm10001otu4CfgLinePtmsiAccOtnEntry 60 }


pm10001otu4CfgTimeslot57valPortn OBJECT-TYPE
	SYNTAX  Unsigned32 (0..65536)
	MAX-ACCESS read-only
	STATUS current
	DESCRIPTION
        "
        Time Slot 57 :This register contains
        the value of the Time Slot
        "
	::= { pm10001otu4CfgLinePtmsiAccOtnEntry 61 }


pm10001otu4CfgTimeslot58valPortn OBJECT-TYPE
	SYNTAX  Unsigned32 (0..65536)
	MAX-ACCESS read-only
	STATUS current
	DESCRIPTION
        "
        Time Slot 58 :This register contains
        the value of the Time Slot
        "
	::= { pm10001otu4CfgLinePtmsiAccOtnEntry 62 }


pm10001otu4CfgTimeslot59valPortn OBJECT-TYPE
	SYNTAX  Unsigned32 (0..65536)
	MAX-ACCESS read-only
	STATUS current
	DESCRIPTION
        "
        Time Slot 59 :This register contains
        the value of the Time Slot
        "
	::= { pm10001otu4CfgLinePtmsiAccOtnEntry 63 }


pm10001otu4CfgTimeslot60valPortn OBJECT-TYPE
	SYNTAX  Unsigned32 (0..65536)
	MAX-ACCESS read-only
	STATUS current
	DESCRIPTION
        "
        Time Slot 60 :This register contains
        the value of the Time Slot
        "
	::= { pm10001otu4CfgLinePtmsiAccOtnEntry 64 }


pm10001otu4CfgTimeslot61valPortn OBJECT-TYPE
	SYNTAX  Unsigned32 (0..65536)
	MAX-ACCESS read-only
	STATUS current
	DESCRIPTION
        "
        Time Slot 61 :This register contains
        the value of the Time Slot
        "
	::= { pm10001otu4CfgLinePtmsiAccOtnEntry 65 }


pm10001otu4CfgTimeslot62valPortn OBJECT-TYPE
	SYNTAX  Unsigned32 (0..65536)
	MAX-ACCESS read-only
	STATUS current
	DESCRIPTION
        "
        Time Slot 62 :This register contains
        the value of the Time Slot
        "
	::= { pm10001otu4CfgLinePtmsiAccOtnEntry 66 }


pm10001otu4CfgTimeslot63valPortn OBJECT-TYPE
	SYNTAX  Unsigned32 (0..65536)
	MAX-ACCESS read-only
	STATUS current
	DESCRIPTION
        "
        Time Slot 63 :This register contains
        the value of the Time Slot
        "
	::= { pm10001otu4CfgLinePtmsiAccOtnEntry 67 }


pm10001otu4CfgTimeslot64valPortn OBJECT-TYPE
	SYNTAX  Unsigned32 (0..65536)
	MAX-ACCESS read-only
	STATUS current
	DESCRIPTION
        "
        Time Slot 64 :This register contains
        the value of the Time Slot
        "
	::= { pm10001otu4CfgLinePtmsiAccOtnEntry 68 }


pm10001otu4CfgTimeslot65valPortn OBJECT-TYPE
	SYNTAX  Unsigned32 (0..65536)
	MAX-ACCESS read-only
	STATUS current
	DESCRIPTION
        "
        Time Slot 65 :This register contains
        the value of the Time Slot
        "
	::= { pm10001otu4CfgLinePtmsiAccOtnEntry 69 }


pm10001otu4CfgTimeslot66valPortn OBJECT-TYPE
	SYNTAX  Unsigned32 (0..65536)
	MAX-ACCESS read-only
	STATUS current
	DESCRIPTION
        "
        Time Slot 66 :This register contains
        the value of the Time Slot
        "
	::= { pm10001otu4CfgLinePtmsiAccOtnEntry 70 }


pm10001otu4CfgTimeslot67valPortn OBJECT-TYPE
	SYNTAX  Unsigned32 (0..65536)
	MAX-ACCESS read-only
	STATUS current
	DESCRIPTION
        "
        Time Slot 67 :This register contains
        the value of the Time Slot
        "
	::= { pm10001otu4CfgLinePtmsiAccOtnEntry 71 }


pm10001otu4CfgTimeslot68valPortn OBJECT-TYPE
	SYNTAX  Unsigned32 (0..65536)
	MAX-ACCESS read-only
	STATUS current
	DESCRIPTION
        "
        Time Slot 68 :This register contains
        the value of the Time Slot
        "
	::= { pm10001otu4CfgLinePtmsiAccOtnEntry 72 }


pm10001otu4CfgTimeslot69valPortn OBJECT-TYPE
	SYNTAX  Unsigned32 (0..65536)
	MAX-ACCESS read-only
	STATUS current
	DESCRIPTION
        "
        Time Slot 69 :This register contains
        the value of the Time Slot
        "
	::= { pm10001otu4CfgLinePtmsiAccOtnEntry 73 }


pm10001otu4CfgTimeslot70valPortn OBJECT-TYPE
	SYNTAX  Unsigned32 (0..65536)
	MAX-ACCESS read-only
	STATUS current
	DESCRIPTION
        "
        Time Slot 70 :This register contains
        the value of the Time Slot
        "
	::= { pm10001otu4CfgLinePtmsiAccOtnEntry 74 }


pm10001otu4CfgTimeslot71valPortn OBJECT-TYPE
	SYNTAX  Unsigned32 (0..65536)
	MAX-ACCESS read-only
	STATUS current
	DESCRIPTION
        "
        Time Slot 71 :This register contains
        the value of the Time Slot
        "
	::= { pm10001otu4CfgLinePtmsiAccOtnEntry 75 }


pm10001otu4CfgTimeslot72valPortn OBJECT-TYPE
	SYNTAX  Unsigned32 (0..65536)
	MAX-ACCESS read-only
	STATUS current
	DESCRIPTION
        "
        Time Slot 72 :This register contains
        the value of the Time Slot
        "
	::= { pm10001otu4CfgLinePtmsiAccOtnEntry 76 }


pm10001otu4CfgTimeslot73valPortn OBJECT-TYPE
	SYNTAX  Unsigned32 (0..65536)
	MAX-ACCESS read-only
	STATUS current
	DESCRIPTION
        "
        Time Slot 73 :This register contains
        the value of the Time Slot
        "
	::= { pm10001otu4CfgLinePtmsiAccOtnEntry 77 }


pm10001otu4CfgTimeslot74valPortn OBJECT-TYPE
	SYNTAX  Unsigned32 (0..65536)
	MAX-ACCESS read-only
	STATUS current
	DESCRIPTION
        "
        Time Slot 74 :This register contains
        the value of the Time Slot
        "
	::= { pm10001otu4CfgLinePtmsiAccOtnEntry 78 }


pm10001otu4CfgTimeslot75valPortn OBJECT-TYPE
	SYNTAX  Unsigned32 (0..65536)
	MAX-ACCESS read-only
	STATUS current
	DESCRIPTION
        "
        Time Slot 75 :This register contains
        the value of the Time Slot
        "
	::= { pm10001otu4CfgLinePtmsiAccOtnEntry 79 }


pm10001otu4CfgTimeslot76valPortn OBJECT-TYPE
	SYNTAX  Unsigned32 (0..65536)
	MAX-ACCESS read-only
	STATUS current
	DESCRIPTION
        "
        Time Slot 76 :This register contains
        the value of the Time Slot
        "
	::= { pm10001otu4CfgLinePtmsiAccOtnEntry 80 }


pm10001otu4CfgTimeslot77valPortn OBJECT-TYPE
	SYNTAX  Unsigned32 (0..65536)
	MAX-ACCESS read-only
	STATUS current
	DESCRIPTION
        "
        Time Slot 77 :This register contains
        the value of the Time Slot
        "
	::= { pm10001otu4CfgLinePtmsiAccOtnEntry 81 }


pm10001otu4CfgTimeslot78valPortn OBJECT-TYPE
	SYNTAX  Unsigned32 (0..65536)
	MAX-ACCESS read-only
	STATUS current
	DESCRIPTION
        "
        Time Slot 78 :This register contains
        the value of the Time Slot
        "
	::= { pm10001otu4CfgLinePtmsiAccOtnEntry 82 }


pm10001otu4CfgTimeslot79valPortn OBJECT-TYPE
	SYNTAX  Unsigned32 (0..65536)
	MAX-ACCESS read-only
	STATUS current
	DESCRIPTION
        "
        Time Slot 79 :This register contains
        the value of the Time Slot
        "
	::= { pm10001otu4CfgLinePtmsiAccOtnEntry 83 }


pm10001otu4CfgTimeslot80valPortn OBJECT-TYPE
	SYNTAX  Unsigned32 (0..65536)
	MAX-ACCESS read-only
	STATUS current
	DESCRIPTION
        "
        Time Slot 80 :This register contains
        the value of the Time Slot
        "
	::= { pm10001otu4CfgLinePtmsiAccOtnEntry 84 }



pm10001otu4CfgWriteConfiguration  OBJECT-TYPE
	SYNTAX EkiOnOff
	MAX-ACCESS read-write
	STATUS current
	DESCRIPTION
	"Write configuration to module:This OID
	 writes the complete configuration to the module"
	::= { pm10001otu4Config 257 }






--- *****************************************************
---     TRAP OBJECTS
--- *****************************************************

pm10001otu4trapPortNumber OBJECT-TYPE
	SYNTAX INTEGER(1..64)
	MAX-ACCESS read-only
	STATUS current
	DESCRIPTION
	"Last port which generates a trap"
	::= { pm10001otu4traps 2 }

pm10001otu4trapLineNumber OBJECT-TYPE
	SYNTAX INTEGER(1..64)
	MAX-ACCESS read-only
	STATUS current
	DESCRIPTION
	"Last Line which generates a trap"
	::= { pm10001otu4traps 3 }

pm10001otu4trapBoardNumber OBJECT-TYPE
	SYNTAX INTEGER(1..64)
	MAX-ACCESS read-only
	STATUS current
	DESCRIPTION
	"Last module which generates a trap"
	::= { pm10001otu4traps 4 }







--- *****************************************************
---     LINE TRAPS
--- *****************************************************

pm10001otu4LineTrapNotUrgentGoesOn NOTIFICATION-TYPE
	OBJECTS {pm10001otu4AlmLineDdmWarningPortn, pm10001otu4trapLineNumber, pm10001otu4trapBoardNumber}
	STATUS current
	--&FILTNAME    "PM10001OTU4 Line Not Urgent ON"
	--&ACTIONS     { log, minor }
	--&MATCH       { pm10001otu4AlmLineDdmWarningPortn "on", pm10001otu4trapLineNumber "$2", pm10001otu4trapBoardNumber "$3"}
	--&MESG        "DDM Warning appears on Line Port $2 of PM10001OTU4 in Slot $3 ($A)"
	DESCRIPTION "Not urgent Line default is activated"
	::= { pm10001otu4traps 30 }

pm10001otu4LineTrapNotUrgentGoesOff NOTIFICATION-TYPE
	OBJECTS {pm10001otu4AlmLineDdmWarningPortn, pm10001otu4trapLineNumber, pm10001otu4trapBoardNumber}
	STATUS current
	--&FILTNAME    "PM10001OTU4 Line Not Urgent OFF"
	--&ACTIONS     { log, normal }
	--&CLEARS      { "PM10001OTU4 Line Not Urgent ON" }
	--&MATCH       { pm10001otu4AlmLineDdmWarningPortn "on", pm10001otu4trapLineNumber "$2", pm10001otu4trapBoardNumber "$3"}
	--&MESG        "DDM Warning disappears on Line Port $2 of PM10001OTU4 in Slot $3 ($A)"
	DESCRIPTION "Not urgent Line default disappeared"
	::= { pm10001otu4traps 31 }

pm10001otu4LineTrapUrgentGoesOn NOTIFICATION-TYPE
	OBJECTS {pm10001otu4AlmLineDdmAlmPortn, pm10001otu4trapLineNumber, pm10001otu4trapBoardNumber}
	STATUS current
	--&FILTNAME    "PM10001OTU4 Line Urgent ON"
	--&ACTIONS     { log, major }
	--&MATCH       { pm10001otu4AlmLineDdmAlmPortn "on", pm10001otu4trapLineNumber "$2", pm10001otu4trapBoardNumber "$3"}
	--&MESG        "DDM Alarm appears on Line Port $2 of PM10001OTU4 in Slot $3 ($A)"
	DESCRIPTION "Urgent Line default is activated"
	::= { pm10001otu4traps 32 }

pm10001otu4LineTrapUrgentGoesOff NOTIFICATION-TYPE
	OBJECTS {pm10001otu4AlmLineDdmAlmPortn, pm10001otu4trapLineNumber, pm10001otu4trapBoardNumber}
	STATUS current
	--&FILTNAME    "PM10001OTU4 Line Urgent OFF"
	--&ACTIONS     { log, normal }
	--&CLEARS      { "PM10001OTU4 Line Urgent ON" }
	--&MATCH       { pm10001otu4AlmLineDdmAlmPortn "on", pm10001otu4trapLineNumber "$2", pm10001otu4trapBoardNumber "$3"}
	--&MESG        "DDM Alarm disappears on Line Port $2 of PM10001OTU4 in Slot $3 ($A)"
	DESCRIPTION "Urgent Line default disappeared"
	::= { pm10001otu4traps 33 }

pm10001otu4LineTrapCritGoesOn NOTIFICATION-TYPE
	OBJECTS {pm10001otu4AlmLineFailPortn , pm10001otu4AlmLineHwFailPortn , pm10001otu4trapLineNumber, pm10001otu4trapBoardNumber}
	STATUS current
	--&FILTNAME    "PM10001OTU4 Line Fail ON"
	--&ACTIONS     { log, critical }
	--&MATCH       { pm10001otu4AlmLineFailPortn "on", pm10001otu4AlmLineHwFailPortn "*", pm10001otu4trapLineNumber "$3", pm10001otu4trapBoardNumber "$4"}
	--&MESG        "Line Port $3 Down on PM10001OTU4 in Slot $4 ($A)"

	--&FILTNAME    "PM10001OTU4 Line HW Fail ON (Hidden)"
	--&ACTIONS     { info }
	--&MATCH       { pm10001otu4AlmLineFailPortn "*", pm10001otu4AlmLineHwFailPortn "on", pm10001otu4trapLineNumber "$3", pm10001otu4trapBoardNumber "$4"}
	--&MESG        "Line Port $3 Down on PM10001OTU4 in Slot $4 ($A)"
	DESCRIPTION "Critical Line default is activated"
	::= { pm10001otu4traps 34 }

pm10001otu4LineTrapCritGoesOff NOTIFICATION-TYPE
	OBJECTS {pm10001otu4AlmLineFailPortn , pm10001otu4AlmLineHwFailPortn , pm10001otu4trapLineNumber, pm10001otu4trapBoardNumber}
	STATUS current
	--&FILTNAME    "PM10001OTU4 Line Fail OFF"
	--&ACTIONS     { log,  normal }
	--&CLEARS      { "PM10001OTU4 Line Fail ON" }
	--&MATCH       { pm10001otu4AlmLineFailPortn "on", pm10001otu4AlmLineHwFailPortn "*", pm10001otu4trapLineNumber "$3", pm10001otu4trapBoardNumber "$4"}
	--&MESG        "Line Port $3 Up on PM10001OTU4 in Slot $4 ($A)"

	--&FILTNAME    "PM10001OTU4 Line HW Fail OFF (Hidden)"
	--&ACTIONS     { info }
	--&MATCH       { pm10001otu4AlmLineFailPortn "*", pm10001otu4AlmLineHwFailPortn "on", pm10001otu4trapLineNumber "$3", pm10001otu4trapBoardNumber "$4"}
	--&MESG        "Line Port $3 Up on PM10001OTU4 in Slot $4 ($A)"
	DESCRIPTION "Critical Line default disappeared"
	::= { pm10001otu4traps 35 }






--- *****************************************************
---     CLIENT TRAPS
--- *****************************************************

pm10001otu4ClientTrapNotUrgentGoesOn NOTIFICATION-TYPE
	OBJECTS {pm10001otu4AlmSfpDdmWarningPortn, pm10001otu4trapPortNumber, pm10001otu4trapBoardNumber}
	STATUS current
		--&FILTNAME    "PM10001OTU4 Client Not Urgent ON"
		--&ACTIONS     { log, minor }
		--&MATCH       { pm10001otu4AlmSfpDdmWarningPortn "on", pm10001otu4trapPortNumber "$2", pm10001otu4trapBoardNumber "$3"}
		--&MESG        "DDM Warning appears on Client Port $2 of PM10001OTU4 in Slot $3 ($A)"
	DESCRIPTION "Not urgent client default is activated"
	::= { pm10001otu4traps 40 }

pm10001otu4ClientTrapNotUrgentGoesOff NOTIFICATION-TYPE
	OBJECTS {pm10001otu4AlmSfpDdmWarningPortn, pm10001otu4trapPortNumber, pm10001otu4trapBoardNumber}
	STATUS current
		--&FILTNAME    "PM10001OTU4 Client Not Urgent OFF"
		--&ACTIONS     { log, normal }
		--&CLEARS      { "PM10001OTU4 Client Not Urgent ON" }
		--&MATCH       { pm10001otu4AlmSfpDdmWarningPortn "on", pm10001otu4trapPortNumber "$2", pm10001otu4trapBoardNumber "$3"}
		--&MESG        "DDM Warning appears on Client Port $2 of PM10001OTU4 in Slot $3 ($A)"
	DESCRIPTION "Not urgent client default disappeared"
	::= { pm10001otu4traps 41 }

pm10001otu4ClientTrapUrgentGoesOn NOTIFICATION-TYPE
	OBJECTS {pm10001otu4AlmSfpDdmAlmPortn, pm10001otu4trapPortNumber, pm10001otu4trapBoardNumber}
	STATUS current
		--&FILTNAME    "PM10001OTU4 Client Urgent ON"
		--&ACTIONS     { log, major }
		--&MATCH       { pm10001otu4AlmSfpDdmAlmPortn "on", pm10001otu4trapPortNumber "$2", pm10001otu4trapBoardNumber "$3"}
		--&MESG        "DDM Alarm appears on Client Port $2 of PM10001OTU4 in Slot $3 ($A)"
	DESCRIPTION "Urgent client default is activated"
	::= { pm10001otu4traps 42 }

pm10001otu4ClientTrapUrgentGoesOff NOTIFICATION-TYPE
	OBJECTS {pm10001otu4AlmSfpDdmAlmPortn, pm10001otu4trapPortNumber, pm10001otu4trapBoardNumber}
	STATUS current
		--&FILTNAME    "PM10001OTU4 Client Urgent OFF"
		--&ACTIONS     { log, normal }
		--&CLEARS      { "PM10001OTU4 Client Urgent ON" }
		--&MATCH       { pm10001otu4AlmSfpDdmAlmPortn "on", pm10001otu4trapPortNumber "$2", pm10001otu4trapBoardNumber "$3"}
		--&MESG        "DDM Alarm disappears on Client Port $2 of PM10001OTU4 in Slot $3 ($A)"
	DESCRIPTION "Urgent client default disappeared"
	::= { pm10001otu4traps 43 }

pm10001otu4ClientTrapCritGoesOn NOTIFICATION-TYPE
	OBJECTS {pm10001otu4AlmFailAccPortn, pm10001otu4AlmHwFailAccPortn, pm10001otu4trapPortNumber, pm10001otu4trapBoardNumber}
	STATUS current
		--&FILTNAME    "PM10001OTU4 Client Fail ON"
		--&ACTIONS     { log, critical }
		--&MATCH       { pm10001otu4AlmFailAccPortn "on", pm10001otu4AlmHwFailAccPortn "*", pm10001otu4trapPortNumber "$3", pm10001otu4trapBoardNumber "$4"}
		--&MESG        "Client Port $3 Down on PM10001OTU4 in Slot $4 ($A)"

		--&FILTNAME    "PM10001OTU4 Client HW Fail ON (Hidden)"
		--&ACTIONS     { info }
		--&MATCH       { pm10001otu4AlmFailAccPortn "*", pm10001otu4AlmHwFailAccPortn "on", pm10001otu4trapPortNumber "$3", pm10001otu4trapBoardNumber "$4"}
		--&MESG        "Client Port $3 Down on PM10001OTU4 in Slot $4 ($A)"
	DESCRIPTION "Critical client default is activated"
	::= { pm10001otu4traps 44 }

pm10001otu4ClientTrapCritGoesOff NOTIFICATION-TYPE
	OBJECTS {pm10001otu4AlmFailAccPortn, pm10001otu4AlmHwFailAccPortn, pm10001otu4trapPortNumber, pm10001otu4trapBoardNumber}
	STATUS current
		--&FILTNAME    "PM10001OTU4 Client Fail OFF"
		--&ACTIONS     { log, normal }
		--&CLEARS      { "PM10001OTU4 Client Fail ON" }
		--&MATCH       { pm10001otu4AlmFailAccPortn "on", pm10001otu4AlmHwFailAccPortn "*", pm10001otu4trapPortNumber "$3", pm10001otu4trapBoardNumber "$4"}
		--&MESG        "Client Port $3 Up on PM10001OTU4 in Slot $4 ($A)"

		--&FILTNAME    "PM10001OTU4 Client HW Fail OFF (Hidden)"
		--&ACTIONS     { info }
		--&MATCH       { pm10001otu4AlmFailAccPortn "*", pm10001otu4AlmHwFailAccPortn "on", pm10001otu4trapPortNumber "$3", pm10001otu4trapBoardNumber "$4"}
		--&MESG        "Client Port $3 Up on PM10001OTU4 in Slot $4 ($A)"
	DESCRIPTION "Critical client default disappeared"
	::= { pm10001otu4traps 45 }






--- *****************************************************
---     HW TRAPS
--- *****************************************************

pm10001otu4PowerTrapUrgentGoesOn NOTIFICATION-TYPE
	OBJECTS {pm10001otu4AlmDefFuseB, pm10001otu4AlmDefFuseA , pm10001otu4trapBoardNumber}
	STATUS current
		--&FILTNAME    "PM10001OTU4 Fuse A Fail ON"
		--&ACTIONS     { log, major }
		--&MATCH       { pm10001otu4AlmDefFuseB "*", pm10001otu4AlmDefFuseA "on", pm10001otu4trapBoardNumber "$3"}
		--&MESG        "Power Input A Fail on PM10001OTU4 in Slot $3 ($A)"

		--&FILTNAME    "PM10001OTU4 Fuse B Fail ON"
		--&ACTIONS     { log, major }
		--&MATCH       { pm10001otu4AlmDefFuseB "on", pm10001otu4AlmDefFuseA "*", pm10001otu4trapBoardNumber "$3"}
		--&MESG        "Power Input B Fail on PM10001OTU4 in Slot $3 ($A)"
	DESCRIPTION "Urgent power supply default is activated"
	::= { pm10001otu4traps 50 }

pm10001otu4PowerTrapUrgentGoesOff NOTIFICATION-TYPE
	OBJECTS {pm10001otu4AlmDefFuseB, pm10001otu4AlmDefFuseA , pm10001otu4trapBoardNumber}
	STATUS current
		--&FILTNAME    "PM10001OTU4 Fuse A&B Fail OFF"
		--&ACTIONS     { log, normal}
		--&CLEARS      { "PM10001OTU4 Fuse A Fail ON", "PM10001OTU4 Fuse B Fail ON" }
		--&MATCH       { pm10001otu4AlmDefFuseB "on", pm10001otu4AlmDefFuseA "on", pm10001otu4trapBoardNumber "$3"}
		--&MESG        "Power Inputs A and B Present on PM10001OTU4 in Slot $3 ($A)"
	DESCRIPTION "Urgent power supply default disappeared"
	::= { pm10001otu4traps 51 }






END
