-- *****************************************************************
-- EKINOPS-Pm1008.TXT:  MIB
--
--MIB Part Number:3MI00001ALAE
--MIB Version:03
--
-- Copyright (c) 2016 by Ekinops
-- All rights reserved.
--
-- *****************************************************************

EKINOPS-Pm1008-MIB DEFINITIONS ::= BEGIN

IMPORTS
	ekinops,
	EkiState,
	EkiOnOff,
	EkiMode,
	EkiProtocol,
	EkiApiState,
	EkiSynchroMode,
	EkiMeasureType
			FROM EKINOPS-MIB
        MODULE-IDENTITY,
        OBJECT-TYPE,
        NOTIFICATION-TYPE,
	Unsigned32,
	Integer32,
	Counter32,
	IpAddress
        		FROM SNMPv2-SMI
 	TEXTUAL-CONVENTION,
	DisplayString
                FROM SNMPv2-TC;

modulePm1008 MODULE-IDENTITY
        LAST-UPDATED "201606020000Z"
        ORGANIZATION "Ekinops"
        CONTACT-INFO
         "Ekinops

          3, rue Blaise Pascal
          F-22300 Lannion / FRANCE

          Tel : +33 (0)2 96 05 00 30
          Fax : +33 (0)2 96 48 62 39

          E-mail: support@ekinops.net"
        DESCRIPTION
          "MIB for managing Ekinops modules with PM1008 software"
	REVISION "200412200000Z"
	DESCRIPTION
	  "Initial Version."
	REVISION "200506030000Z"
	DESCRIPTION
	  "Adding performance application"
	REVISION "200509090000Z"
	DESCRIPTION
	  "Adding Multiple Lines objects"
	REVISION "200510210000Z"
	DESCRIPTION
	  "Adding Line Degrade alarm"
	REVISION "200511040000Z"
	DESCRIPTION
	  "New monitoring branch"
	REVISION "200601310000Z"
	DESCRIPTION
	  "Adding FEC control"
	REVISION "200702210000Z"
	DESCRIPTION
	  "Adding module init fail alarms"
	REVISION "200709170000Z"
	DESCRIPTION
	  "Inventory syntax is DisplayString instead of OCTET STRING"
	REVISION "200711090000Z"
	DESCRIPTION
	  "Update Ekinops address, Helps on leds and Objects, Ports labels,MR features"
	REVISION "200805280000Z"
	DESCRIPTION
	  "Add OTX-TLH features"
	REVISION "200812090000Z"
	DESCRIPTION
	  "Cosmetics for mib compilers"
	REVISION "200904090000Z"
	DESCRIPTION
	  "Add DCC ans MAINTENANCE control"
	REVISION "200905070000Z"
	DESCRIPTION
	  "CondType parameters insertion"
	REVISION "201002150000Z"
	DESCRIPTION
	  "Probcause,AlarmType - NMS"
	REVISION "201010270000Z"
	DESCRIPTION
	  "Formulas and Event on XFP init"
	REVISION "201010270000Z"
	DESCRIPTION
	  "Event fixed"
	REVISION "201207020000Z"
	DESCRIPTION
	  "Minor cosmetic updates"
	REVISION "201304020000Z"
	DESCRIPTION
	  "S1,K1,K2 suppress"
	REVISION "201403250000Z"
	DESCRIPTION
	  "Probcause,AlarmType - NMS completion"
	REVISION "201412180000Z"
	DESCRIPTION
	  "Labels cosmetic updates"
	REVISION "201605190000Z"
	DESCRIPTION
	  "New AlarmType -    synthesisAlarm(12)"
	REVISION "201606020000Z"
	DESCRIPTION
	  "Capabilities objects of Table 5"
        ::= { ekinops 3 }



--- *****************************************************
---     LEAF LEVEL 2
--- *****************************************************


pm1008alarms OBJECT IDENTIFIER ::= { modulePm1008 2 }
pm1008AlmOther OBJECT IDENTIFIER ::= { pm1008alarms 1 }
pm1008AlmOtherNurg OBJECT IDENTIFIER ::= { pm1008AlmOther 1 }
pm1008AlmOtherUrg OBJECT IDENTIFIER ::= { pm1008AlmOther 2 }
pm1008AlmOtherCrit OBJECT IDENTIFIER ::= { pm1008AlmOther 3 }

pm1008AlmClient OBJECT IDENTIFIER ::= { pm1008alarms 2 }
pm1008AlmClientNurg OBJECT IDENTIFIER ::= { pm1008AlmClient 1 }
pm1008AlmClientUrg OBJECT IDENTIFIER ::= { pm1008AlmClient 2 }
pm1008AlmClientCrit OBJECT IDENTIFIER ::= { pm1008AlmClient 3 }

pm1008AlmLine OBJECT IDENTIFIER ::= { pm1008alarms 3 }
pm1008AlmLineNurg OBJECT IDENTIFIER ::= { pm1008AlmLine 1 }
pm1008AlmLineUrg OBJECT IDENTIFIER ::= { pm1008AlmLine 2 }
pm1008AlmLineCrit OBJECT IDENTIFIER ::= { pm1008AlmLine 3 }





pm1008measures OBJECT IDENTIFIER ::= { modulePm1008 3 }
pm1008MesrOther OBJECT IDENTIFIER ::= { pm1008measures 1 }
pm1008MesrClient OBJECT IDENTIFIER ::= { pm1008measures 2 }
pm1008MesrLine OBJECT IDENTIFIER ::= { pm1008measures 3 }




pm1008counters OBJECT IDENTIFIER ::= { modulePm1008 4 }
pm1008CntOther OBJECT IDENTIFIER ::= { pm1008counters 1 }
pm1008CntClient OBJECT IDENTIFIER ::= { pm1008counters 2 }
pm1008CntLine OBJECT IDENTIFIER ::= { pm1008counters 3 }


pm1008controlsWrite OBJECT IDENTIFIER ::= { modulePm1008 6 }
pm1008CtrlOther OBJECT IDENTIFIER ::= { pm1008controlsWrite 1 }
pm1008CtrlClient OBJECT IDENTIFIER ::= { pm1008controlsWrite 2 }
pm1008CtrlLine OBJECT IDENTIFIER ::= { pm1008controlsWrite 3 }

pm1008ri OBJECT IDENTIFIER ::= { modulePm1008 7 }
pm1008riTable OBJECT IDENTIFIER ::= { pm1008ri 1 }

pm1008download OBJECT IDENTIFIER ::= { modulePm1008 8 }
pm1008DwlOther OBJECT IDENTIFIER ::= { pm1008download 1 }
pm1008DwlClient OBJECT IDENTIFIER ::= { pm1008download 2 }
pm1008DwlLine OBJECT IDENTIFIER ::= { pm1008download 3 }


pm1008Config OBJECT IDENTIFIER ::= { modulePm1008 9 }

pm1008traps OBJECT IDENTIFIER ::= { modulePm1008 10 }



pm1008Monitoring OBJECT IDENTIFIER ::= { modulePm1008 11}

pm1008MonOther OBJECT IDENTIFIER ::= { pm1008Monitoring 1 }
pm1008MonRmon OBJECT IDENTIFIER ::= { pm1008MonOther 3 }

pm1008MonClient OBJECT IDENTIFIER ::= { pm1008Monitoring 2 }
pm1008MonClientRmonCounter OBJECT IDENTIFIER ::= { pm1008MonClient 4 }


--- *****************************************************
--- $$$$$$$$$$$$$$$$$$$$$$$$$$$$$$$$$$$$$$$$$$$$$$$$$$$$$
---     TEXTUAL-CONVENTION
--- $$$$$$$$$$$$$$$$$$$$$$$$$$$$$$$$$$$$$$$$$$$$$$$$$$$$$
--- *****************************************************

Pm1008MultiRate ::= TEXTUAL-CONVENTION
    STATUS      current
    DESCRIPTION "different rate for a client port"
    SYNTAX INTEGER {
		rate100Mhz(0),
		rate250Mhz(1),
		rate500Mhz(2),
		rate1Ghz(3)
           }

Pm1008OtxMode ::= TEXTUAL-CONVENTION
    STATUS      current
    DESCRIPTION "Different modes on OTX-TLH on client and line ports"
    SYNTAX INTEGER {
		otx80mode(1),
		otx60mode(2),
		otxadjustmode(4)
           }

Pm1008OtxGrid ::= TEXTUAL-CONVENTION
    STATUS      current
    DESCRIPTION "Different grids on OTX-TLH on client and line ports"
    SYNTAX INTEGER {
		otxgrid200(200),
		otxgrid100(100),
		otxgrid50(50)
           }

Pm1008AdjustValue ::= TEXTUAL-CONVENTION
    STATUS      current
    DESCRIPTION "Different values in Adjust mode on OTX-TLH on client and line ports"
    SYNTAX INTEGER {
		otxadjustvalue0(0),
		otxadjustvalue1(1),
		otxadjustvalue2(2),
		otxadjustvalue3(3),
		otxadjustvalue4(4),
		otxadjustvalue5(5),
		otxadjustvalue6(6),
		otxadjustvalue7(7),
		otxadjustvalue8(8),
		otxadjustvalue9(9),
		otxadjustvalue10(10)
           }

Pm1008OtxChannel ::= TEXTUAL-CONVENTION
    STATUS      current
    DESCRIPTION "Channel selection on OTX-TLH on client and line ports"
    SYNTAX INTEGER


--- *****************************************************
--- $$$$$$$$$$$$$$$$$$$$$$$$$$$$$$$$$$$$$$$$$$$$$$$$$$$$$
---     REMOTE INVENTORY
--- $$$$$$$$$$$$$$$$$$$$$$$$$$$$$$$$$$$$$$$$$$$$$$$$$$$$$
--- *****************************************************

pm1008RinvReloadInventory OBJECT-TYPE
  SYNTAX EkiOnOff
  MAX-ACCESS read-write
  STATUS current
  DESCRIPTION
        "Reload the inventory: This OID triggers an
         inventory reload."
  ::= { pm1008ri 2 }

pm1008RinvHwPlatform OBJECT-TYPE
  SYNTAX DisplayString
  MAX-ACCESS read-only
  STATUS current
  DESCRIPTION
        "HW platform description: This OID contains the
         description of the Hardware platform."
  ::= { pm1008ri 3 }

pm1008RinvModulePlatform OBJECT-TYPE
  SYNTAX DisplayString
  MAX-ACCESS read-only
  STATUS current
  DESCRIPTION
        "Module platform description: This OID contains the
         description of the Module."
  ::= { pm1008ri 4 }

pm1008RinvSwPlatform OBJECT-TYPE
  SYNTAX DisplayString
  MAX-ACCESS read-only
  STATUS current
  DESCRIPTION
        "SW platform description: This OID contains the
         description of the Software platform."
  ::= { pm1008ri 5 }

pm1008RinvGwPlatform OBJECT-TYPE
  SYNTAX DisplayString
  MAX-ACCESS read-only
  STATUS current
  DESCRIPTION
        "GW platform desciption: This OID contains the
         description of the Gateware platform."
  ::= { pm1008ri 6 }


pm1008RinvSfpTable OBJECT-TYPE
      SYNTAX  SEQUENCE OF Pm1008RinvSfpEntry
      MAX-ACCESS  not-accessible
      STATUS  current
      DESCRIPTION
              "List of the SFPs on the selected module"
      ::= { pm1008riTable 1 }

pm1008RinvSfpEntry OBJECT-TYPE
        SYNTAX  Pm1008RinvSfpEntry
        MAX-ACCESS  not-accessible
        STATUS  current
        DESCRIPTION
              "Row definition for the SFP table"
        INDEX   { pm1008RinvSfpIndex }
        ::= { pm1008RinvSfpTable 1 }



Pm1008RinvSfpEntry::=
        SEQUENCE {
          pm1008RinvSfpIndex
              Integer32,
          pm1008Rinvsfp
              DisplayString
        }


    pm1008RinvSfpIndex OBJECT-TYPE
        SYNTAX  Integer32(1..16)
        MAX-ACCESS  read-only
        STATUS  current
        DESCRIPTION
              "Index for SFP table"
        ::= { pm1008RinvSfpEntry 1 }


    pm1008Rinvsfp OBJECT-TYPE
        SYNTAX  DisplayString
        MAX-ACCESS  read-only
        STATUS  current
        DESCRIPTION
              "Inventory for the SFP: This OID contains the inventory for the SFP"
        ::= { pm1008RinvSfpEntry 2 }




pm1008RinvLineTable OBJECT-TYPE
      SYNTAX  SEQUENCE OF Pm1008RinvLineEntry
      MAX-ACCESS  not-accessible
      STATUS  current
      DESCRIPTION
              "List of the XFPs on the selected module"
      ::= { pm1008riTable 2 }

pm1008RinvLineEntry OBJECT-TYPE
        SYNTAX  Pm1008RinvLineEntry
        MAX-ACCESS  not-accessible
        STATUS  current
        DESCRIPTION
              "Row definition for the XFP table"
        INDEX   { pm1008RinvLineIndex }
        ::= { pm1008RinvLineTable 1 }



Pm1008RinvLineEntry::=
        SEQUENCE {
          pm1008RinvLineIndex
              Integer32,
          pm1008RinvxfpLine
              DisplayString
        }


    pm1008RinvLineIndex OBJECT-TYPE
        SYNTAX  Integer32(1..16)
        MAX-ACCESS  read-only
        STATUS  current
        DESCRIPTION
              "Index for XFP table"
        ::= { pm1008RinvLineEntry 1 }


    pm1008RinvxfpLine OBJECT-TYPE
        SYNTAX  DisplayString
        MAX-ACCESS  read-only
        STATUS  current
        DESCRIPTION
              "Inventory for the XFP: This OID contains the inventory for the XFP"
        ::= { pm1008RinvLineEntry 2 }









--- *****************************************************
--- $$$$$$$$$$$$$$$$$$$$$$$$$$$$$$$$$$$$$$$$$$$$$$$$$$$$$
---     ALARMS
--- $$$$$$$$$$$$$$$$$$$$$$$$$$$$$$$$$$$$$$$$$$$$$$$$$$$$$
--- *****************************************************



--- *****************************************************
---     LEAF for the synthAlm0 article
--- *****************************************************
pm1008AlmsynthAlm0 OBJECT IDENTIFIER ::= { pm1008AlmOtherCrit 0 }




pm1008AlmDefFuseB OBJECT-TYPE
	  SYNTAX EkiOnOff
	  MAX-ACCESS read-only
	  STATUS current
	  DESCRIPTION
        "
        Fuse B Fail :This OID indicates
        that the fuse of the power input
        B is in fail condition  <Help>
          Status of the Fuse B <Condtype>
        DEF_FUSE_B <Probcause> powerProblem
        (36) <Alarmtype> equipmentAlarm
        (5) <Polarity> (2)
        "
	  ::= { pm1008AlmsynthAlm0 16 }



pm1008AlmDefFuseA OBJECT-TYPE
	  SYNTAX EkiOnOff
	  MAX-ACCESS read-only
	  STATUS current
	  DESCRIPTION
        "
        Fuse A Fail :This OID indicates
        that the fuse of the power input
        A is in fail condition  <Help>
          Status of the Fuse A <Condtype>
        DEF_FUSE_A <Probcause> powerProblem
        (36) <Alarmtype> equipmentAlarm
        (5) <Polarity> (2)
        "
	  ::= { pm1008AlmsynthAlm0 15 }



pm1008AlmModGlobFail OBJECT-TYPE
	  SYNTAX EkiOnOff
	  MAX-ACCESS read-only
	  STATUS current
	  DESCRIPTION
        "
        Module Failure :This OID is set
        on detection of a failure originating
        from the PM <Condtype> MOD_GLOB_FAIL
        <Probcause> equipmentMalfunction
        (16) <Alarmtype> synthesisAlarm
        (12) <Polarity> (2)
        "
	  ::= { pm1008AlmsynthAlm0 9 }



--- *****************************************************
---     LEAF for the synthAlm2 article
--- *****************************************************
pm1008AlmsynthAlm2 OBJECT IDENTIFIER ::= { pm1008AlmOtherNurg 2 }




pm1008AlmMaintenanceOn OBJECT-TYPE
	  SYNTAX EkiOnOff
	  MAX-ACCESS read-only
	  STATUS current
	  DESCRIPTION
        "
        Maintenance Mode :This OID indicates
        that the PM is in maintenance mode.
         <Help>  This alarm indicates that
        the maintenance mode is enabled
        on the PM <Condtype> MAINTENANCE_ON
        <Probcause> other (1) <Alarmtype>
        other (1) <Polarity> (2)
        "
	  ::= { pm1008AlmsynthAlm2 5 }



pm1008AlmCorrelatOff OBJECT-TYPE
	  SYNTAX EkiOnOff
	  MAX-ACCESS read-only
	  STATUS current
	  DESCRIPTION
        "
        Not Used :This OID, when set,
         indicates that alarm correlation
        is not being performed. <Condtype>
        CORRELAT_OFF <Probcause> other
         (1) <Alarmtype> other (1) <Polarity>
        (2)
        "
	  ::= { pm1008AlmsynthAlm2 4 }



pm1008AlmConfTableLoad OBJECT-TYPE
	  SYNTAX EkiOnOff
	  MAX-ACCESS read-only
	  STATUS current
	  DESCRIPTION
        "
        PM Configuration Load :This OID
         is at 1 during the loading of
         configuration tables in the modules
        RAM. <Condtype> CONF_TABLE_LOAD
        <Probcause> other (1) <Alarmtype>
        other (1) <Polarity> (2)
        "
	  ::= { pm1008AlmsynthAlm2 3 }



pm1008AlmInvUpload OBJECT-TYPE
	  SYNTAX EkiOnOff
	  MAX-ACCESS read-only
	  STATUS current
	  DESCRIPTION
        "
        Inventory Upload :This OID is
         at 1 during the uploading of PM
        inventory information. <Condtype>
        INV_UPLOAD <Probcause> other (1)
        <Alarmtype> other (1) <Polarity>
        (2)
        "
	  ::= { pm1008AlmsynthAlm2 2 }



pm1008AlmConfTableSave OBJECT-TYPE
	  SYNTAX EkiOnOff
	  MAX-ACCESS read-only
	  STATUS current
	  DESCRIPTION
        "
        PM Configuration Save :This OID
        is at 1 during the saving of a
         new configuration table in the
        module Flash memory. <Condtype>
        CONF_TABLE_SAVE <Probcause> other
        (1) <Alarmtype> other (1) <Polarity>
        (2)
        "
	  ::= { pm1008AlmsynthAlm2 1 }



--- *********************************************************
---     TABLE for the pm1008AlmsynthAlmLine articles
--- *********************************************************

pm1008AlmsynthAlmLineTable OBJECT-TYPE
	SYNTAX  SEQUENCE OF Pm1008AlmsynthAlmLineEntry
	MAX-ACCESS not-accessible
	STATUS current
	DESCRIPTION
        "
        List of pm1008AlmsynthAlmLine
         Article
        "
	::= { pm1008AlmLineCrit 7 }


pm1008AlmsynthAlmLineEntry OBJECT-TYPE
	SYNTAX Pm1008AlmsynthAlmLineEntry
	MAX-ACCESS not-accessible
	STATUS current
	DESCRIPTION
        "
        Row definition for the pm1008AlmsynthAlmLine
        table
        "
	INDEX   { pm1008AlmsynthAlmLineIndex }
	::= { pm1008AlmsynthAlmLineTable 1 }


Pm1008AlmsynthAlmLineEntry ::=
	SEQUENCE {
	pm1008AlmsynthAlmLineIndex
		INTEGER,
	pm1008AlmLineActivePortn
		EkiOnOff,
	pm1008AlmLineFailPortn
		EkiOnOff,
	pm1008AlmLineDdmAlmPortn
		EkiOnOff,
	pm1008AlmLineDdmWarningPortn
		EkiOnOff,
	pm1008AlmUpRdiInsPortn
		EkiOnOff,
	pm1008AlmLineLocalOosPortn
		EkiOnOff,
	pm1008AlmXfpTxOffPortn
		EkiOnOff,
	pm1008AlmLineHwFailPortn
		EkiOnOff,
	pm1008AlmXfpInitNotComplPortn
		EkiOnOff,
	pm1008AlmXfpAbsentPortn
		EkiOnOff
	}


pm1008AlmsynthAlmLineIndex OBJECT-TYPE
	SYNTAX  INTEGER(0..128)
	MAX-ACCESS  read-only
	STATUS current
	DESCRIPTION
        "
        Index definition for the pm1008AlmsynthAlmLine
        table
        "
	::= { pm1008AlmsynthAlmLineEntry 1 }


pm1008AlmLineActivePortn OBJECT-TYPE
	SYNTAX  EkiOnOff
	MAX-ACCESS read-only
	STATUS current
	DESCRIPTION
        "
        Line Active :This bit indicates
        the line #n is active on receive
        side  <Help>  This status indicates
        whether the line is active or standby.
        <Condtype> LINE_ACTIVE <Probcause>
        informationalStatus(1000) <Alarmtype>
        other (1) <Polarity> (2)
        "
	::= { pm1008AlmsynthAlmLineEntry 17 }


pm1008AlmLineFailPortn OBJECT-TYPE
	SYNTAX  EkiOnOff
	MAX-ACCESS read-only
	STATUS current
	DESCRIPTION
        "
        Line Port Failure :This OID indicates
        a failure on the line port <Condtype>
        LINE_FAIL <Probcause> equipmentMalfunction
        (16) <Alarmtype> synthesisAlarm
        (12) <Polarity> (2)
        "
	::= { pm1008AlmsynthAlmLineEntry 13 }


pm1008AlmLineDdmAlmPortn OBJECT-TYPE
	SYNTAX  EkiOnOff
	MAX-ACCESS read-only
	STATUS current
	DESCRIPTION
        "
        Alarm On Line Optical Module DDM
        :This OID indicates an alarm is
        present coming out of Line optical
        interface DDM  <Help>  This alarm
        indicates if a DDM Alarm has been
        detected on the line transceiver
        <Condtype> LINE_DDM_ALM <Probcause>
        equipmentMalfunction (16) <Alarmtype>
        synthesisAlarm (12) <Polarity>
         (2)
        "
	::= { pm1008AlmsynthAlmLineEntry 11 }


pm1008AlmLineDdmWarningPortn OBJECT-TYPE
	SYNTAX  EkiOnOff
	MAX-ACCESS read-only
	STATUS current
	DESCRIPTION
        "
        Warning On Line Optical Module
        DDM :This OID indicates a warning
        is present coming out of Line optical
        interface DDM  <Help>  This alarm
        indicates if a DDM Warning has
         been detected on the line transceiver
        <Condtype> LINE_DDM_WARNING <Probcause>
        equipmentMalfunction (16) <Alarmtype>
        synthesisAlarm (12) <Polarity>
         (2)
        "
	::= { pm1008AlmsynthAlmLineEntry 10 }


pm1008AlmUpRdiInsPortn OBJECT-TYPE
	SYNTAX  EkiOnOff
	MAX-ACCESS read-only
	STATUS current
	DESCRIPTION
        "
        MS-RDI/L-RDI Inserted On Line
         :This OID indicates an upstream
        MS-RDI/L-RDI has been inserted
         in the outgoing 10 Gb/s SDH/SONET
        signal.   <Help>  This status indicates
        if a MS-RDI/L-RDI is currently
         inserted on the line interface.
        <Condtype> UP_RDI_INS <Probcause>
        informationalStatus(1000) <Alarmtype>
        other (1) <Polarity> (2)
        "
	::= { pm1008AlmsynthAlmLineEntry 9 }


pm1008AlmLineLocalOosPortn OBJECT-TYPE
	SYNTAX  EkiOnOff
	MAX-ACCESS read-only
	STATUS current
	DESCRIPTION
        "
        Line Port In Service :This OID
        indicates that the Line port is
        In Service (1) of Out or Service
        (2)  <Help>  This status indicates
        if the line port is in service
         <Condtype> LINE_LOCAL_OOS <Probcause>
        informationalStatus(1000) <Alarmtype>
        other (1) <Polarity> (2)
        "
	::= { pm1008AlmsynthAlmLineEntry 7 }


pm1008AlmXfpTxOffPortn OBJECT-TYPE
	SYNTAX  EkiOnOff
	MAX-ACCESS read-only
	STATUS current
	DESCRIPTION
        "
        Line Optical Module Laser Shutdown
        :This OID indicates the line optical
        output power is on  <Help>  This
        status indicates if the line transceiver
        laser is ON or OFF <Condtype> XFP_TX_OFF
        <Probcause> other (1) <Alarmtype>
        equipmentAlarm (5) <Polarity> (2)
        "
	::= { pm1008AlmsynthAlmLineEntry 6 }


pm1008AlmLineHwFailPortn OBJECT-TYPE
	SYNTAX  EkiOnOff
	MAX-ACCESS read-only
	STATUS current
	DESCRIPTION
        "
        Line Port HW Failure :This OID
        indicates a failure on line port,
        most probably caused by a HW issue
        <Condtype> LINE_HW_FAIL <Probcause>
        equipmentMalfunction (16) <Alarmtype>
        synthesisAlarm (12) <Polarity>
         (2)
        "
	::= { pm1008AlmsynthAlmLineEntry 5 }


pm1008AlmXfpInitNotComplPortn OBJECT-TYPE
	SYNTAX  EkiOnOff
	MAX-ACCESS read-only
	STATUS current
	DESCRIPTION
        "
        Line Optical Module Ready :This
        OID indicates that the optical
         interface (XFP or OTX) is not
         operational.  <Help>  This status
        indicates if the line transceiver
        has been correctly initialized
         <Condtype> XFP_INIT_NOT_COMPL
         <Probcause> equipmentMalfunction
        (16) <Alarmtype> equipmentAlarm
        (5) <Polarity> (2) <Event> ObjectCDINV
        "
	::= { pm1008AlmsynthAlmLineEntry 3 }


pm1008AlmXfpAbsentPortn OBJECT-TYPE
	SYNTAX  EkiOnOff
	MAX-ACCESS read-only
	STATUS current
	DESCRIPTION
        "
        Line Optical Module Absent :This
        OID indicates that the line optical
        interface (XFP or OTX) is not plugged
        in.  <Help>  This alarm indicates
        if the line transceiver is present.
        <Condtype> XFP_ABSENT <Probcause>
        inputOutputDeviceError (24) <Alarmtype>
        equipmentAlarm (5) <Polarity> (2)
        <Event> ObjectCDINV
        "
	::= { pm1008AlmsynthAlmLineEntry 2 }


--- *********************************************************
---     TABLE for the pm1008AlmsynthAlmPort articles
--- *********************************************************

pm1008AlmsynthAlmPortTable OBJECT-TYPE
	SYNTAX  SEQUENCE OF Pm1008AlmsynthAlmPortEntry
	MAX-ACCESS not-accessible
	STATUS current
	DESCRIPTION
        "
        List of pm1008AlmsynthAlmPort
         Article
        "
	::= { pm1008AlmClientCrit 8 }


pm1008AlmsynthAlmPortEntry OBJECT-TYPE
	SYNTAX Pm1008AlmsynthAlmPortEntry
	MAX-ACCESS not-accessible
	STATUS current
	DESCRIPTION
        "
        Row definition for the pm1008AlmsynthAlmPort
        table
        "
	INDEX   { pm1008AlmsynthAlmPortIndex }
	::= { pm1008AlmsynthAlmPortTable 1 }


Pm1008AlmsynthAlmPortEntry ::=
	SEQUENCE {
	pm1008AlmsynthAlmPortIndex
		INTEGER,
	pm1008AlmUpCsfPortn
		EkiOnOff,
	pm1008AlmFailAccPortn
		EkiOnOff,
	pm1008AlmSfpDdmAlmPortn
		EkiOnOff,
	pm1008AlmSfpDdmWarningPortn
		EkiOnOff,
	pm1008AlmDwCaisPortn
		EkiOnOff,
	pm1008AlmClientRemoteOosPortn
		EkiOnOff,
	pm1008AlmClientLocalOosPortn
		EkiOnOff,
	pm1008AlmDwLsdPortn
		EkiOnOff,
	pm1008AlmHwFailAccPortn
		EkiOnOff,
	pm1008AlmDdmAbsentPortn
		EkiOnOff,
	pm1008AlmSfpAbsentPortn
		EkiOnOff
	}


pm1008AlmsynthAlmPortIndex OBJECT-TYPE
	SYNTAX  INTEGER(0..128)
	MAX-ACCESS  read-only
	STATUS current
	DESCRIPTION
        "
        Index definition for the pm1008AlmsynthAlmPort
        table
        "
	::= { pm1008AlmsynthAlmPortEntry 1 }


pm1008AlmUpCsfPortn OBJECT-TYPE
	SYNTAX  EkiOnOff
	MAX-ACCESS read-only
	STATUS current
	DESCRIPTION
        "
        Client Signal Fail Inserted :This
        OID indicates a CSF has been inserted
        in the upstream client port.  <Help>
         This status indicates if a Client
        Signal Fail is currently inserted
        on the line signal for this client
        port <Condtype> UP_CSF_1 <Probcause>
        other (1) <Alarmtype> other (1)
        <Polarity> (2)
        "
	::= { pm1008AlmsynthAlmPortEntry 17 }


pm1008AlmFailAccPortn OBJECT-TYPE
	SYNTAX  EkiOnOff
	MAX-ACCESS read-only
	STATUS current
	DESCRIPTION
        "
        Client Access Fail :This OID indicates
        a failure on the Client port <Condtype>
        FAIL_ACC_1 <Probcause> equipmentMalfunction
        (16) <Alarmtype> synthesisAlarm
        (12) <Polarity> (2)
        "
	::= { pm1008AlmsynthAlmPortEntry 13 }


pm1008AlmSfpDdmAlmPortn OBJECT-TYPE
	SYNTAX  EkiOnOff
	MAX-ACCESS read-only
	STATUS current
	DESCRIPTION
        "
        Alarm On Client SFP DDM :This
         OID indicates an alarm is being
        received from the Client SFP DDM
         <Help>  This alarm indicates if
        a DDM Alarm has been detected on
        the client transceiver <Condtype>
        SFP_DDM_ALM_1 <Probcause> equipmentMalfunction
        (16) <Alarmtype> synthesisAlarm
        (12) <Polarity> (2)
        "
	::= { pm1008AlmsynthAlmPortEntry 11 }


pm1008AlmSfpDdmWarningPortn OBJECT-TYPE
	SYNTAX  EkiOnOff
	MAX-ACCESS read-only
	STATUS current
	DESCRIPTION
        "
        Warning On Client SFP DDM :This
        OID indicates a warning is being
        received from the Client SFP DDM
         <Help>  This alarm indicates if
        a DDM Warning has been detected
        on the client transceiver <Condtype>
        SFP_DDM_WARNING_1 <Probcause> equipmentMalfunction
        (16) <Alarmtype> synthesisAlarm
        (12) <Polarity> (2)
        "
	::= { pm1008AlmsynthAlmPortEntry 10 }


pm1008AlmDwCaisPortn OBJECT-TYPE
	SYNTAX  EkiOnOff
	MAX-ACCESS read-only
	STATUS current
	DESCRIPTION
        "
        Client AIS Inserted :This OID
         indicates a CAIS has been inserted
        on the output client port.  <Help>
         This status indictaes if a Client
        Alarm Indication Signal is currently
        inserted on the client interface
        <Condtype> DW_CAIS_1 <Probcause>
        informationalStatus(1000) <Alarmtype>
        other (1) <Polarity> (2)
        "
	::= { pm1008AlmsynthAlmPortEntry 9 }


pm1008AlmClientRemoteOosPortn OBJECT-TYPE
	SYNTAX  EkiOnOff
	MAX-ACCESS read-only
	STATUS current
	DESCRIPTION
        "
        Remote Client Port In Service
         :This OID indicates that the remote
        Client port is In Service (1) or
        Out of Service (2)  <Help>  This
        status indicates if the remote
         client port is in service <Condtype>
        CLIENT_REMOTE_OOS <Probcause> informationalStatus(1000)
        <Alarmtype> other (1) <Polarity>
        (2)
        "
	::= { pm1008AlmsynthAlmPortEntry 8 }


pm1008AlmClientLocalOosPortn OBJECT-TYPE
	SYNTAX  EkiOnOff
	MAX-ACCESS read-only
	STATUS current
	DESCRIPTION
        "
        Local Client Port In Service :This
        OID indicates that the local Client
        port is In Service (1) or Out of
        Service (2)  <Help>  This status
        indicates if the local client port
        is in service <Condtype> CLIENT_LOCAL_OOS
        <Probcause> informationalStatus(1000)
        <Alarmtype> other (1) <Polarity>
        (2)
        "
	::= { pm1008AlmsynthAlmPortEntry 7 }


pm1008AlmDwLsdPortn OBJECT-TYPE
	SYNTAX  EkiOnOff
	MAX-ACCESS read-only
	STATUS current
	DESCRIPTION
        "
        Client SFP Laser Shutdown :This
        OID indicates the Client SFP transmitter
        output is ON.   <Help>  This status
        indicates if the client transceiver
        laser is ON or OFF <Condtype> DW_LSD_1
        <Probcause> other (1) <Alarmtype>
        equipmentAlarm (5) <Polarity> (2)
        "
	::= { pm1008AlmsynthAlmPortEntry 6 }


pm1008AlmHwFailAccPortn OBJECT-TYPE
	SYNTAX  EkiOnOff
	MAX-ACCESS read-only
	STATUS current
	DESCRIPTION
        "
        Client HW Fail :This OID indicates
        a failure on client port, most
         probably caused by a HW issue.
        <Condtype> HW_FAIL_ACC_1 <Probcause>
        equipmentMalfunction (16) <Alarmtype>
        synthesisAlarm (12) <Polarity>
         (2)
        "
	::= { pm1008AlmsynthAlmPortEntry 5 }


pm1008AlmDdmAbsentPortn OBJECT-TYPE
	SYNTAX  EkiOnOff
	MAX-ACCESS read-only
	STATUS current
	DESCRIPTION
        "
        DDM Supported On Client SFP :This
        OID indicates that the Client SFP
        module supports the Digital Diagnostic
        Monitoring function  <Help>  This
        status indicates if the client
         transceiver includes the DDM feature
        <Condtype> DDM_ABSENT_1 <Probcause>
        informationalStatus(1000) <Alarmtype>
        other (1) <Polarity> (2)
        "
	::= { pm1008AlmsynthAlmPortEntry 3 }


pm1008AlmSfpAbsentPortn OBJECT-TYPE
	SYNTAX  EkiOnOff
	MAX-ACCESS read-only
	STATUS current
	DESCRIPTION
        "
        Client SFP Absent :This OID indicates
        that the SFP module is not present
        in the client port.  <Help>  This
        alarm indicates if the client transceiver
        is present. <Condtype> SFP_ABSENT_1
        <Probcause> inputOutputDeviceError
        (24) <Alarmtype> equipmentAlarm
        (5) <Polarity> (2) <Event> ObjectCDINV
        "
	::= { pm1008AlmsynthAlmPortEntry 2 }


--- *********************************************************
---     TABLE for the pm1008AlmaccessioAlm articles
--- *********************************************************

pm1008AlmaccessioAlmTable OBJECT-TYPE
	SYNTAX  SEQUENCE OF Pm1008AlmaccessioAlmEntry
	MAX-ACCESS not-accessible
	STATUS current
	DESCRIPTION
        "
        List of pm1008AlmaccessioAlm Article
        "
	::= { pm1008AlmClientCrit 16 }


pm1008AlmaccessioAlmEntry OBJECT-TYPE
	SYNTAX Pm1008AlmaccessioAlmEntry
	MAX-ACCESS not-accessible
	STATUS current
	DESCRIPTION
        "
        Row definition for the pm1008AlmaccessioAlm
        table
        "
	INDEX   { pm1008AlmaccessioAlmIndex }
	::= { pm1008AlmaccessioAlmTable 1 }


Pm1008AlmaccessioAlmEntry ::=
	SEQUENCE {
	pm1008AlmaccessioAlmIndex
		INTEGER,
	pm1008AlmUpLosPortn
		EkiOnOff,
	pm1008AlmDwLasFailPortn
		EkiOnOff
	}


pm1008AlmaccessioAlmIndex OBJECT-TYPE
	SYNTAX  INTEGER(0..128)
	MAX-ACCESS  read-only
	STATUS current
	DESCRIPTION
        "
        Index definition for the pm1008AlmaccessioAlm
        table
        "
	::= { pm1008AlmaccessioAlmEntry 1 }


pm1008AlmUpLosPortn OBJECT-TYPE
	SYNTAX  EkiOnOff
	MAX-ACCESS read-only
	STATUS current
	DESCRIPTION
        "
        Client Input Loss Of Signal :This
        OID indicates that no signal is
        present on the SFP of the client
        port  <Help>  This alarm indicates
        if an optical signal is detected
        on the client transceiver input
        <Condtype> UP_LOS_1 <Probcause>
        receiveFailure (41) <Alarmtype>
        physicalViolation (9) <Polarity>
        (2)
        "
	::= { pm1008AlmaccessioAlmEntry 5 }


pm1008AlmDwLasFailPortn OBJECT-TYPE
	SYNTAX  EkiOnOff
	MAX-ACCESS read-only
	STATUS current
	DESCRIPTION
        "
        Client SFP Tx Failed :This OID
        indicates that the transmitter
         fails for the SFP plugged into
        the client port (this alarm reports
        the transmitter failure alarm generated
        by the SFPs)  <Help>  This alarm
        indicates if the laser of the client
        transceiver is in fail condition
        <Condtype> DW_LAS_FAIL_1 <Probcause>
        transmitterFailure (56) <Alarmtype>
        equipmentAlarm (5) <Polarity> (2)
        "
	::= { pm1008AlmaccessioAlmEntry 2 }


--- *********************************************************
---     TABLE for the pm1008AlmsfpAlmDdm articles
--- *********************************************************

pm1008AlmsfpAlmDdmTable OBJECT-TYPE
	SYNTAX  SEQUENCE OF Pm1008AlmsfpAlmDdmEntry
	MAX-ACCESS not-accessible
	STATUS current
	DESCRIPTION
        "
        List of pm1008AlmsfpAlmDdm Article
        "
	::= { pm1008AlmClientUrg 32 }


pm1008AlmsfpAlmDdmEntry OBJECT-TYPE
	SYNTAX Pm1008AlmsfpAlmDdmEntry
	MAX-ACCESS not-accessible
	STATUS current
	DESCRIPTION
        "
        Row definition for the pm1008AlmsfpAlmDdm
        table
        "
	INDEX   { pm1008AlmsfpAlmDdmIndex }
	::= { pm1008AlmsfpAlmDdmTable 1 }


Pm1008AlmsfpAlmDdmEntry ::=
	SEQUENCE {
	pm1008AlmsfpAlmDdmIndex
		INTEGER,
	pm1008AlmRxPwrHighAlaPortn
		EkiOnOff,
	pm1008AlmRxPwrLowAlaPortn
		EkiOnOff,
	pm1008AlmTempHighAlaPortn
		EkiOnOff,
	pm1008AlmTempLowAlaPortn
		EkiOnOff,
	pm1008AlmVccHighAlaPortn
		EkiOnOff,
	pm1008AlmVccLowAlaPortn
		EkiOnOff,
	pm1008AlmTxBiasHighAlaPortn
		EkiOnOff,
	pm1008AlmTxBiasLowAlaPortn
		EkiOnOff,
	pm1008AlmTxPwrHighAlaPortn
		EkiOnOff,
	pm1008AlmTxPwrLowAlaPortn
		EkiOnOff
	}


pm1008AlmsfpAlmDdmIndex OBJECT-TYPE
	SYNTAX  INTEGER(0..128)
	MAX-ACCESS  read-only
	STATUS current
	DESCRIPTION
        "
        Index definition for the pm1008AlmsfpAlmDdm
        table
        "
	::= { pm1008AlmsfpAlmDdmEntry 1 }


pm1008AlmRxPwrHighAlaPortn OBJECT-TYPE
	SYNTAX  EkiOnOff
	MAX-ACCESS read-only
	STATUS current
	DESCRIPTION
        "
        Client SFP Rx Power High :Alarm
        indicating that the SFP input power
        of port is higher than the threshold
        value written in the SFP EEPROM
        <Condtype> RX_PWR_HIGH_ALA_1 <Probcause>
        receiveFailure (41) <Alarmtype>
        equipmentAlarm (5) <Polarity> (2)
        "
	::= { pm1008AlmsfpAlmDdmEntry 17 }


pm1008AlmRxPwrLowAlaPortn OBJECT-TYPE
	SYNTAX  EkiOnOff
	MAX-ACCESS read-only
	STATUS current
	DESCRIPTION
        "
        Client SFP Rx Power Low :Alarm
        indicating that the SFP input power
        of port is lower than the threshold
        value written in the SFP EEPROM
        <Condtype> RX_PWR_LOW_ALA_1 <Probcause>
        receiveFailure (41) <Alarmtype>
        equipmentAlarm (5) <Polarity> (2)
        "
	::= { pm1008AlmsfpAlmDdmEntry 16 }


pm1008AlmTempHighAlaPortn OBJECT-TYPE
	SYNTAX  EkiOnOff
	MAX-ACCESS read-only
	STATUS current
	DESCRIPTION
        "
        Client SFP Temp High :Alarm indicating
        that the SFP temperature of port
        is higher than the threshold value
        written in the SFP EEPROM <Condtype>
        TEMP_HIGH_ALA_1 <Probcause> temperatureUnacceptable
        (51) <Alarmtype> equipmentAlarm
        (5) <Polarity> (2)
        "
	::= { pm1008AlmsfpAlmDdmEntry 9 }


pm1008AlmTempLowAlaPortn OBJECT-TYPE
	SYNTAX  EkiOnOff
	MAX-ACCESS read-only
	STATUS current
	DESCRIPTION
        "
        Client SFP Temp Low :Alarm indicating
        that the SFP temperature of port
        is lower than the threshold value
        written in the SFP EEPROM <Condtype>
        TEMP_LOW_ALA_1 <Probcause> temperatureUnacceptable
        (51) <Alarmtype> equipmentAlarm
        (5) <Polarity> (2)
        "
	::= { pm1008AlmsfpAlmDdmEntry 8 }


pm1008AlmVccHighAlaPortn OBJECT-TYPE
	SYNTAX  EkiOnOff
	MAX-ACCESS read-only
	STATUS current
	DESCRIPTION
        "
        Client SFP Power Supply High :Alarm
        indicating that the SFP power supply
        of port is higher than the threshold
        value written in the SFP EEPROM
         <Condtype> VCC_HIGH_ALA_1 <Probcause>
        powerProblem (36) <Alarmtype> equipmentAlarm
        (5) <Polarity> (2)
        "
	::= { pm1008AlmsfpAlmDdmEntry 7 }


pm1008AlmVccLowAlaPortn OBJECT-TYPE
	SYNTAX  EkiOnOff
	MAX-ACCESS read-only
	STATUS current
	DESCRIPTION
        "
        Client SFP Power Supply Low :Alarm
        indicating that the SFP power supply
        of port is lower than the threshold
        value written in the SFP EEPROM
         <Condtype> VCC_LOW_ALA_1 <Probcause>
        powerProblem (36) <Alarmtype> equipmentAlarm
        (5) <Polarity> (2)
        "
	::= { pm1008AlmsfpAlmDdmEntry 6 }


pm1008AlmTxBiasHighAlaPortn OBJECT-TYPE
	SYNTAX  EkiOnOff
	MAX-ACCESS read-only
	STATUS current
	DESCRIPTION
        "
        Client SFP Bias High :Alarm indicating
        that the SFP laser bias current
        of port is higher than the threshold
        value written in the SFP EEPROM
        <Condtype> TX_BIAS_HIGH_ALA_1 <Probcause>
        transmitterFailure (56) <Alarmtype>
        equipmentAlarm (5) <Polarity> (2)
        "
	::= { pm1008AlmsfpAlmDdmEntry 5 }


pm1008AlmTxBiasLowAlaPortn OBJECT-TYPE
	SYNTAX  EkiOnOff
	MAX-ACCESS read-only
	STATUS current
	DESCRIPTION
        "
        Client SFP Bias Low :Alarm indicating
        that the SFP laser bias current
        of port is lower than the threshold
        value written in the SFP EEPROM
        <Condtype> TX_BIAS_LOW_ALA_1 <Probcause>
        transmitterFailure (56) <Alarmtype>
        equipmentAlarm (5) <Polarity> (2)
        "
	::= { pm1008AlmsfpAlmDdmEntry 4 }


pm1008AlmTxPwrHighAlaPortn OBJECT-TYPE
	SYNTAX  EkiOnOff
	MAX-ACCESS read-only
	STATUS current
	DESCRIPTION
        "
        Client SFP Tx Power High :Alarm
        indicating that the SFP output
         power of port is higher than the
        threshold value written in the
         SFP EEPROM <Condtype> TX_PWR_HIGH_ALA_1
        <Probcause> transmitterFailure
         (56) <Alarmtype> equipmentAlarm
        (5) <Polarity> (2)
        "
	::= { pm1008AlmsfpAlmDdmEntry 3 }


pm1008AlmTxPwrLowAlaPortn OBJECT-TYPE
	SYNTAX  EkiOnOff
	MAX-ACCESS read-only
	STATUS current
	DESCRIPTION
        "
        Client SFP Tx Power Low :Alarm
        indicating that the SFP output
         power of port is lower than the
        threshold value written in the
         SFP EEPROM <Condtype> TX_PWR_LOW_ALA_1
        <Probcause> transmitterFailure
         (56) <Alarmtype> equipmentAlarm
        (5) <Polarity> (2)
        "
	::= { pm1008AlmsfpAlmDdmEntry 2 }


--- *********************************************************
---     TABLE for the pm1008AlmsfpWarnDdm articles
--- *********************************************************

pm1008AlmsfpWarnDdmTable OBJECT-TYPE
	SYNTAX  SEQUENCE OF Pm1008AlmsfpWarnDdmEntry
	MAX-ACCESS not-accessible
	STATUS current
	DESCRIPTION
        "
        List of pm1008AlmsfpWarnDdm Article
        "
	::= { pm1008AlmClientNurg 48 }


pm1008AlmsfpWarnDdmEntry OBJECT-TYPE
	SYNTAX Pm1008AlmsfpWarnDdmEntry
	MAX-ACCESS not-accessible
	STATUS current
	DESCRIPTION
        "
        Row definition for the pm1008AlmsfpWarnDdm
        table
        "
	INDEX   { pm1008AlmsfpWarnDdmIndex }
	::= { pm1008AlmsfpWarnDdmTable 1 }


Pm1008AlmsfpWarnDdmEntry ::=
	SEQUENCE {
	pm1008AlmsfpWarnDdmIndex
		INTEGER,
	pm1008AlmRxPwrHighWngPortn
		EkiOnOff,
	pm1008AlmRxPwrLowWngPortn
		EkiOnOff,
	pm1008AlmTempHighWngPortn
		EkiOnOff,
	pm1008AlmTempLowWngPortn
		EkiOnOff,
	pm1008AlmVccHighWngPortn
		EkiOnOff,
	pm1008AlmVccLowWngPortn
		EkiOnOff,
	pm1008AlmTxBiasHighWngPortn
		EkiOnOff,
	pm1008AlmTxBiasLowWngPortn
		EkiOnOff,
	pm1008AlmTxPwrHighWngPortn
		EkiOnOff,
	pm1008AlmTxPwLowWngPortn
		EkiOnOff
	}


pm1008AlmsfpWarnDdmIndex OBJECT-TYPE
	SYNTAX  INTEGER(0..128)
	MAX-ACCESS  read-only
	STATUS current
	DESCRIPTION
        "
        Index definition for the pm1008AlmsfpWarnDdm
        table
        "
	::= { pm1008AlmsfpWarnDdmEntry 1 }


pm1008AlmRxPwrHighWngPortn OBJECT-TYPE
	SYNTAX  EkiOnOff
	MAX-ACCESS read-only
	STATUS current
	DESCRIPTION
        "
        Client SFP Rx Power High Warning
        :Warning indicating that the SFP
        input power of port is higher than
        the threshold value written in
         the SFP EEPROM <Condtype> RX_PWR_HIGH_WNG_1
        <Probcause> receiveFailure (41)
        <Alarmtype> equipmentAlarm (5)
         <Polarity> (2)
        "
	::= { pm1008AlmsfpWarnDdmEntry 17 }


pm1008AlmRxPwrLowWngPortn OBJECT-TYPE
	SYNTAX  EkiOnOff
	MAX-ACCESS read-only
	STATUS current
	DESCRIPTION
        "
        Client SFP Rx Power Low Warning
        :Warning indicating that the SFP
        input power of port is lower than
        the threshold value written in
         the SFP EEPROM <Condtype> RX_PWR_LOW_WNG_1
        <Probcause> receiveFailure (41)
        <Alarmtype> equipmentAlarm (5)
         <Polarity> (2)
        "
	::= { pm1008AlmsfpWarnDdmEntry 16 }


pm1008AlmTempHighWngPortn OBJECT-TYPE
	SYNTAX  EkiOnOff
	MAX-ACCESS read-only
	STATUS current
	DESCRIPTION
        "
        Client SFP Temp High Warning :Warning
        indicating that the SFP temperature
        of port is higher than the threshold
        value written in the SFP EEPROM
        <Condtype> TEMP_HIGH_WNG_1 <Probcause>
        temperatureUnacceptable (51) <Alarmtype>
        equipmentAlarm (5) <Polarity> (2)
        "
	::= { pm1008AlmsfpWarnDdmEntry 9 }


pm1008AlmTempLowWngPortn OBJECT-TYPE
	SYNTAX  EkiOnOff
	MAX-ACCESS read-only
	STATUS current
	DESCRIPTION
        "
        Client SFP Temp Low Warning :Warning
        indicating that the SFP temperature
        of port is lower than the threshold
        value written in the SFP EEPROM
        <Condtype> TEMP_LOW_WNG_1 <Probcause>
        temperatureUnacceptable (51) <Alarmtype>
        equipmentAlarm (5) <Polarity> (2)
        "
	::= { pm1008AlmsfpWarnDdmEntry 8 }


pm1008AlmVccHighWngPortn OBJECT-TYPE
	SYNTAX  EkiOnOff
	MAX-ACCESS read-only
	STATUS current
	DESCRIPTION
        "
        Client SFP Power Supply High Warning
        :Warning indicating that the SFP
        power supply of port is higher
         than the threshold value written
        in the SFP EEPROM  <Condtype> VCC_HIGH_WNG_1
        <Probcause> powerProblem (36) <Alarmtype>
        equipmentAlarm (5) <Polarity> (2)
        "
	::= { pm1008AlmsfpWarnDdmEntry 7 }


pm1008AlmVccLowWngPortn OBJECT-TYPE
	SYNTAX  EkiOnOff
	MAX-ACCESS read-only
	STATUS current
	DESCRIPTION
        "
        Client SFP Power Supply Low Warning
        :Warning indicating that the SFP
        power supply of port is lower than
        the threshold value written in
         the SFP EEPROM  <Condtype> VCC_LOW_WNG_1
        <Probcause> powerProblem (36) <Alarmtype>
        equipmentAlarm (5) <Polarity> (2)
        "
	::= { pm1008AlmsfpWarnDdmEntry 6 }


pm1008AlmTxBiasHighWngPortn OBJECT-TYPE
	SYNTAX  EkiOnOff
	MAX-ACCESS read-only
	STATUS current
	DESCRIPTION
        "
        Client SFP Bias High Warning :Warning
        indicating that the SFP laser bias
        current of port is higher than
         the threshold value written in
        the SFP EEPROM <Condtype> TX_BIAS_HIGH_WNG_1
        <Probcause> transmitterFailure
         (56) <Alarmtype> equipmentAlarm
        (5) <Polarity> (2)
        "
	::= { pm1008AlmsfpWarnDdmEntry 5 }


pm1008AlmTxBiasLowWngPortn OBJECT-TYPE
	SYNTAX  EkiOnOff
	MAX-ACCESS read-only
	STATUS current
	DESCRIPTION
        "
        Client SFP Bias Low Warning :Warning
        indicating that the SFP laser bias
        current of port is lower than the
        threshold value written in the
         SFP EEPROM <Condtype> TX_BIAS_LOW_WNG_1
        <Probcause> transmitterFailure
         (56) <Alarmtype> equipmentAlarm
        (5) <Polarity> (2)
        "
	::= { pm1008AlmsfpWarnDdmEntry 4 }


pm1008AlmTxPwrHighWngPortn OBJECT-TYPE
	SYNTAX  EkiOnOff
	MAX-ACCESS read-only
	STATUS current
	DESCRIPTION
        "
        Client SFP Tx Power High Warning
        :Warning indicating that the SFP
        output power of port is higher
         than the threshold value written
        in the SFP EEPROM <Condtype> TX_PWR_HIGH_WNG_1
        <Probcause> transmitterFailure
         (56) <Alarmtype> equipmentAlarm
        (5) <Polarity> (2)
        "
	::= { pm1008AlmsfpWarnDdmEntry 3 }


pm1008AlmTxPwLowWngPortn OBJECT-TYPE
	SYNTAX  EkiOnOff
	MAX-ACCESS read-only
	STATUS current
	DESCRIPTION
        "
        Client SFP Tx Power Low Warning
        :Warning indicating that the SFP
        output power of port is lower than
        the threshold value written in
         the SFP EEPROM <Condtype> TX_PW_LOW_WNG_1
        <Probcause> transmitterFailure
         (56) <Alarmtype> equipmentAlarm
        (5) <Polarity> (2)
        "
	::= { pm1008AlmsfpWarnDdmEntry 2 }


--- *********************************************************
---     TABLE for the pm1008AlmmapperDeAlm articles
--- *********************************************************

pm1008AlmmapperDeAlmTable OBJECT-TYPE
	SYNTAX  SEQUENCE OF Pm1008AlmmapperDeAlmEntry
	MAX-ACCESS not-accessible
	STATUS current
	DESCRIPTION
        "
        List of pm1008AlmmapperDeAlm Article
        "
	::= { pm1008AlmClientCrit 72 }


pm1008AlmmapperDeAlmEntry OBJECT-TYPE
	SYNTAX Pm1008AlmmapperDeAlmEntry
	MAX-ACCESS not-accessible
	STATUS current
	DESCRIPTION
        "
        Row definition for the pm1008AlmmapperDeAlm
        table
        "
	INDEX   { pm1008AlmmapperDeAlmIndex }
	::= { pm1008AlmmapperDeAlmTable 1 }


Pm1008AlmmapperDeAlmEntry ::=
	SEQUENCE {
	pm1008AlmmapperDeAlmIndex
		INTEGER,
	pm1008AlmDwBufferOvlPortn
		EkiOnOff,
	pm1008AlmDwCsfDetPortn
		EkiOnOff,
	pm1008AlmUpBufferOvlPortn
		EkiOnOff,
	pm1008AlmUpAccOosPortn
		EkiOnOff
	}


pm1008AlmmapperDeAlmIndex OBJECT-TYPE
	SYNTAX  INTEGER(0..128)
	MAX-ACCESS  read-only
	STATUS current
	DESCRIPTION
        "
        Index definition for the pm1008AlmmapperDeAlm
        table
        "
	::= { pm1008AlmmapperDeAlmEntry 1 }


pm1008AlmDwBufferOvlPortn OBJECT-TYPE
	SYNTAX  EkiOnOff
	MAX-ACCESS read-only
	STATUS current
	DESCRIPTION
        "
        Client Downstream Buffer Overload
        :This OID indicates that the de-mapper
        buffer for client port is in overload.
         <Help>  This alarm indicates if
        there is a downstream FIFO overload
        for this client port <Condtype>
        DW_BUFFER_OVL_1 <Probcause> equipmentMalfunction
        (16) <Alarmtype> equipmentAlarm
        (5) <Polarity> (2)
        "
	::= { pm1008AlmmapperDeAlmEntry 15 }


pm1008AlmDwCsfDetPortn OBJECT-TYPE
	SYNTAX  EkiOnOff
	MAX-ACCESS read-only
	STATUS current
	DESCRIPTION
        "
        Client Signal Fail Detected :This
        OID indicates that a CSF has been
        detected on client port in the
         downstream direction   <Help>
          This alarm indicates if a Client
        Signal Fail has been detected in
        the incoming line frame for this
        client port <Condtype> DW_CSF_DET_1
        <Probcause> receiveFailure (41)
        <Alarmtype> other (1) <Polarity>
        (2)
        "
	::= { pm1008AlmmapperDeAlmEntry 12 }


pm1008AlmUpBufferOvlPortn OBJECT-TYPE
	SYNTAX  EkiOnOff
	MAX-ACCESS read-only
	STATUS current
	DESCRIPTION
        "
        Client Upstream Buffer Overload
        :This OID indicates that the rate
        adaptation buffer for client port
        is in overload.  <Help>  This alarm
        indicates if there is a upstream
        FIFO overload for this client port
        <Condtype> UP_BUFFER_OVL_1 <Probcause>
        receiveFailure (41) <Alarmtype>
        integrityViolation (7) <Polarity>
        (2)
        "
	::= { pm1008AlmmapperDeAlmEntry 11 }


pm1008AlmUpAccOosPortn OBJECT-TYPE
	SYNTAX  EkiOnOff
	MAX-ACCESS read-only
	STATUS current
	DESCRIPTION
        "
        Client Loss Of 10b/8b Synchro
         :This OID indicates the upstream
        client input port has lost synchronization
        on its 10B/8B decoder  <Help>
         This alarms indicates if the input
        client signal is correctly synchronized
        with the 10b/8b decoder <Condtype>
        UP_ACC_OOS_1 <Probcause> receiveFailure
        (41) <Alarmtype> integrityViolation
        (7) <Polarity> (2)
        "
	::= { pm1008AlmmapperDeAlmEntry 2 }


--- *********************************************************
---     TABLE for the pm1008AlmdfrmAlm articles
--- *********************************************************

pm1008AlmdfrmAlmTable OBJECT-TYPE
	SYNTAX  SEQUENCE OF Pm1008AlmdfrmAlmEntry
	MAX-ACCESS not-accessible
	STATUS current
	DESCRIPTION
        "
        List of pm1008AlmdfrmAlm Article
        "
	::= { pm1008AlmLineCrit 128 }


pm1008AlmdfrmAlmEntry OBJECT-TYPE
	SYNTAX Pm1008AlmdfrmAlmEntry
	MAX-ACCESS not-accessible
	STATUS current
	DESCRIPTION
        "
        Row definition for the pm1008AlmdfrmAlm
        table
        "
	INDEX   { pm1008AlmdfrmAlmIndex }
	::= { pm1008AlmdfrmAlmTable 1 }


Pm1008AlmdfrmAlmEntry ::=
	SEQUENCE {
	pm1008AlmdfrmAlmIndex
		INTEGER,
	pm1008AlmTxDccBroadStormPortn
		EkiOnOff,
	pm1008AlmRxDccBroadStormPortn
		EkiOnOff,
	pm1008AlmDccLoopbackPortn
		EkiOnOff,
	pm1008AlmDwLofPortn
		EkiOnOff,
	pm1008AlmDwOofPortn
		EkiOnOff,
	pm1008AlmDwRdiDetPortn
		EkiOnOff,
	pm1008AlmDwAisDetPortn
		EkiOnOff
	}


pm1008AlmdfrmAlmIndex OBJECT-TYPE
	SYNTAX  INTEGER(0..128)
	MAX-ACCESS  read-only
	STATUS current
	DESCRIPTION
        "
        Index definition for the pm1008AlmdfrmAlm
        table
        "
	::= { pm1008AlmdfrmAlmEntry 1 }


pm1008AlmTxDccBroadStormPortn OBJECT-TYPE
	SYNTAX  EkiOnOff
	MAX-ACCESS read-only
	STATUS current
	DESCRIPTION
        "
        Tx DCC Ethernet Broadcast Storm
        :This OID indicates that a storm
        of Broadcast/Multicast packets
         have been detected on the DCC
         channel on the Transmit Line side
         <Help>  This alarm indicates if
        a Tx DCC broadcast storm is detected
        on the DCC channel <Condtype> TX_DCC_BROAD_STORM
        <Probcause> lanError (26) <Alarmtype>
        other (1) <Polarity> (2)
        "
	::= { pm1008AlmdfrmAlmEntry 17 }


pm1008AlmRxDccBroadStormPortn OBJECT-TYPE
	SYNTAX  EkiOnOff
	MAX-ACCESS read-only
	STATUS current
	DESCRIPTION
        "
        Rx DCC Ethernet Broadcast Storm
        :This OID indicates that a storm
        of Broadcast/Multicast packets
         have been detected on the DCC
         channel on the Receive Line side
         <Help>  This alarm indicates if
        a Rx DCC broadcast storm is detected
        on the DCC channel <Condtype> RX_DCC_BROAD_STORM
        <Probcause> lanError (26) <Alarmtype>
        other (1) <Polarity> (2)
        "
	::= { pm1008AlmdfrmAlmEntry 16 }


pm1008AlmDccLoopbackPortn OBJECT-TYPE
	SYNTAX  EkiOnOff
	MAX-ACCESS read-only
	STATUS current
	DESCRIPTION
        "
        DCC Traffic Loopback :This OID
        indicates a loopback condition
         detected on DCC over the network
         <Help>  This alarms indicates
         if a DCC loopback is detected.
        <Condtype> DCC_LOOPBACK <Probcause>
        lanError (26) <Alarmtype> other
        (1) <Polarity> (2)
        "
	::= { pm1008AlmdfrmAlmEntry 15 }


pm1008AlmDwLofPortn OBJECT-TYPE
	SYNTAX  EkiOnOff
	MAX-ACCESS read-only
	STATUS current
	DESCRIPTION
        "
        SONET/SDH Line Loss Of Frame :This
        OID indicates that a Loss Of Frame
        has been detected on incoming
         OC-48c/STM-16c input signal  <Help>
         This alarm indicates if there
         is a Loss of Frame is detected
        on the line input signal <Condtype>
        DW_LOF_1 <Probcause> receiveFailure
        (41) <Alarmtype> integrityViolation
        (7) <Polarity> (2)
        "
	::= { pm1008AlmdfrmAlmEntry 5 }


pm1008AlmDwOofPortn OBJECT-TYPE
	SYNTAX  EkiOnOff
	MAX-ACCESS read-only
	STATUS current
	DESCRIPTION
        "
        SONET/SDH Line Out Of Frame :This
        OID indicates that an Out Of Frame
        has been detected on incoming
         OC-48c/STM-16c input signal  <Help>
         This alarm indicates if there
         is a Out of Frame is detected
         on the line input signal <Condtype>
        DW_OOF_1 <Probcause> receiveFailure
        (41) <Alarmtype> integrityViolation
        (7) <Polarity> (2)
        "
	::= { pm1008AlmdfrmAlmEntry 4 }


pm1008AlmDwRdiDetPortn OBJECT-TYPE
	SYNTAX  EkiOnOff
	MAX-ACCESS read-only
	STATUS current
	DESCRIPTION
        "
        MS-RDI/L-RDI Detected On Line
         Input :This OID indicates that
        an MS-RDI has been detected on
         incoming  OC-48c/STM-16c input
        signal  <Help>  This alarm indicates
        if there is a MS-RDI/L-RDI is detected
        on the line input signal <Condtype>
        DW_RDI_DET_1 <Probcause> remoteNodeTransmissionError
        (43) <Alarmtype> other (1) <Polarity>
        (2)
        "
	::= { pm1008AlmdfrmAlmEntry 3 }


pm1008AlmDwAisDetPortn OBJECT-TYPE
	SYNTAX  EkiOnOff
	MAX-ACCESS read-only
	STATUS current
	DESCRIPTION
        "
        MS-AIS/L-AIS Detected On Line
         Input :This OID indicates that
        an MS-AIS has been detected on
         incoming  OC-48c/STM-16c input
        signal  <Help>  This alarm indicates
        if there is a MS-AIS/L-AIS is detected
        on the line input signal <Condtype>
        DW_AIS_DET_1 <Probcause> receiveFailure
        (41) <Alarmtype> operationalViolation
        (8) <Polarity> (2)
        "
	::= { pm1008AlmdfrmAlmEntry 2 }


--- *********************************************************
---     TABLE for the pm1008AlmdfrmBer articles
--- *********************************************************

pm1008AlmdfrmBerTable OBJECT-TYPE
	SYNTAX  SEQUENCE OF Pm1008AlmdfrmBerEntry
	MAX-ACCESS not-accessible
	STATUS current
	DESCRIPTION
        "
        List of pm1008AlmdfrmBer Article
        "
	::= { pm1008AlmLineUrg 129 }


pm1008AlmdfrmBerEntry OBJECT-TYPE
	SYNTAX Pm1008AlmdfrmBerEntry
	MAX-ACCESS not-accessible
	STATUS current
	DESCRIPTION
        "
        Row definition for the pm1008AlmdfrmBer
        table
        "
	INDEX   { pm1008AlmdfrmBerIndex }
	::= { pm1008AlmdfrmBerTable 1 }


Pm1008AlmdfrmBerEntry ::=
	SEQUENCE {
	pm1008AlmdfrmBerIndex
		INTEGER,
	pm1008AlmLineDegradePortn
		EkiOnOff,
	pm1008AlmLineSignalFailPortn
		EkiOnOff,
	pm1008AlmLineSignalDegradePortn
		EkiOnOff
	}


pm1008AlmdfrmBerIndex OBJECT-TYPE
	SYNTAX  INTEGER(0..128)
	MAX-ACCESS  read-only
	STATUS current
	DESCRIPTION
        "
        Index definition for the pm1008AlmdfrmBer
        table
        "
	::= { pm1008AlmdfrmBerEntry 1 }


pm1008AlmLineDegradePortn OBJECT-TYPE
	SYNTAX  EkiOnOff
	MAX-ACCESS read-only
	STATUS current
	DESCRIPTION
        "
        Fixed Line Signal Degrade :This
        OID indicates that the line input
        signal is DEGRADE. The assetion
        hysteresis is fixed to 10-8 (assertion)
        and 10-9 (de-assertion) <Condtype>
        LINE_DEGRADE_1 <Probcause> degradedSignal
        (13) <Alarmtype> qualityOfServiceAlarm
        (3) <Polarity> (2)
        "
	::= { pm1008AlmdfrmBerEntry 6 }


pm1008AlmLineSignalFailPortn OBJECT-TYPE
	SYNTAX  EkiOnOff
	MAX-ACCESS read-only
	STATUS current
	DESCRIPTION
        "
        Custom Line Signal Fail :This
         OID indicates that the line input
        signal is FAIL. The assertion hysteresis
        can be customized by the host <Condtype>
        LINE_SIGNAL_FAIL_1 <Probcause>
         receiveFailure (41) <Alarmtype>
        integrityViolation (7) <Polarity>
        (2)
        "
	::= { pm1008AlmdfrmBerEntry 3 }


pm1008AlmLineSignalDegradePortn OBJECT-TYPE
	SYNTAX  EkiOnOff
	MAX-ACCESS read-only
	STATUS current
	DESCRIPTION
        "
        Custom Line Signal Degrade :This
        OID indicates that the line input
        signal is DEGRADE. The assertion
        hysteresis can customized by the
        host <Condtype> LINE_SIGNAL_DEGRADE_1
        <Probcause> degradedSignal (13)
        <Alarmtype> qualityOfServiceAlarm
        (3) <Polarity> (2)
        "
	::= { pm1008AlmdfrmBerEntry 2 }


--- *********************************************************
---     TABLE for the pm1008AlmlineSyncAlarms articles
--- *********************************************************

pm1008AlmlineSyncAlarmsTable OBJECT-TYPE
	SYNTAX  SEQUENCE OF Pm1008AlmlineSyncAlarmsEntry
	MAX-ACCESS not-accessible
	STATUS current
	DESCRIPTION
        "
        List of pm1008AlmlineSyncAlarms
        Article
        "
	::= { pm1008AlmLineCrit 133 }


pm1008AlmlineSyncAlarmsEntry OBJECT-TYPE
	SYNTAX Pm1008AlmlineSyncAlarmsEntry
	MAX-ACCESS not-accessible
	STATUS current
	DESCRIPTION
        "
        Row definition for the pm1008AlmlineSyncAlarms
        table
        "
	INDEX   { pm1008AlmlineSyncAlarmsIndex }
	::= { pm1008AlmlineSyncAlarmsTable 1 }


Pm1008AlmlineSyncAlarmsEntry ::=
	SEQUENCE {
	pm1008AlmlineSyncAlarmsIndex
		INTEGER,
	pm1008AlmDwLosPortn
		EkiOnOff,
	pm1008AlmUpLockerrPortn
		EkiOnOff,
	pm1008AlmDwLockerrPortn
		EkiOnOff
	}


pm1008AlmlineSyncAlarmsIndex OBJECT-TYPE
	SYNTAX  INTEGER(0..128)
	MAX-ACCESS  read-only
	STATUS current
	DESCRIPTION
        "
        Index definition for the pm1008AlmlineSyncAlarms
        table
        "
	::= { pm1008AlmlineSyncAlarmsEntry 1 }


pm1008AlmDwLosPortn OBJECT-TYPE
	SYNTAX  EkiOnOff
	MAX-ACCESS read-only
	STATUS current
	DESCRIPTION
        "
        Line Input Loss Of Signal :This
        OID indicates a loss of signal
         on the 10 Gb/s input.  <Help>
          This alarm indicates if an optical
        signal is detected on the line
         transceiver input <Condtype> DW_LOS
        <Probcause> receiveFailure (41)
        <Alarmtype> physicalViolation (9)
        <Polarity> (2)
        "
	::= { pm1008AlmlineSyncAlarmsEntry 17 }


pm1008AlmUpLockerrPortn OBJECT-TYPE
	SYNTAX  EkiOnOff
	MAX-ACCESS read-only
	STATUS current
	DESCRIPTION
        "
        Upstream Clock Lock Error :This
        OID indicates that the serializer
        output 10 Gb/s clock multiplier
        unit is not locked. <Condtype>
         UP_LOCKERR <Probcause> receiveFailure
        (41) <Alarmtype> equipmentAlarm
        (5) <Polarity> (2)
        "
	::= { pm1008AlmlineSyncAlarmsEntry 14 }


pm1008AlmDwLockerrPortn OBJECT-TYPE
	SYNTAX  EkiOnOff
	MAX-ACCESS read-only
	STATUS current
	DESCRIPTION
        "
        Downstream Clock Lock Error :This
        OID indicates that the deserializer
        input 10 Gb/s clock recovery is
        not locked. <Condtype> DW_LOCKERR
        <Probcause> receiveFailure (41)
        <Alarmtype> equipmentAlarm (5)
         <Polarity> (2)
        "
	::= { pm1008AlmlineSyncAlarmsEntry 13 }


--- *****************************************************
---     LEAF for the modInitFailLevel2 article
--- *****************************************************
pm1008AlmmodInitFailLevel2 OBJECT IDENTIFIER ::= { pm1008AlmOtherUrg 194 }




pm1008AlmSwInitFail OBJECT-TYPE
	  SYNTAX EkiOnOff
	  MAX-ACCESS read-only
	  STATUS current
	  DESCRIPTION
        "
        SW Init Fail :This OID indicates
        that the SW intialization has caused
        unknown intial conditions  <Help>
         This alarm indicates if the SW
        module is correctly initialized
        <Condtype> SW_INIT_FAIL <Probcause>
        softwareError (47) <Alarmtype>
         processingErrorAlarm (4) <Polarity>
        (2)
        "
	  ::= { pm1008AlmmodInitFailLevel2 5 }



pm1008AlmResetHwInitFail OBJECT-TYPE
	  SYNTAX EkiOnOff
	  MAX-ACCESS read-only
	  STATUS current
	  DESCRIPTION
        "
        Reset HW Init Fail :This OID indicates
        that the HW intialization has caused
        unknown intial conditions  <Help>
         This alarm indicates if the HW
        has been correctly initialized
         <Condtype> RESET_HW_INIT_FAIL
         <Probcause> softwareError (47)
        <Alarmtype> processingErrorAlarm
        (4) <Polarity> (2)
        "
	  ::= { pm1008AlmmodInitFailLevel2 4 }



pm1008AlmBootUndone OBJECT-TYPE
	  SYNTAX EkiOnOff
	  MAX-ACCESS read-only
	  STATUS current
	  DESCRIPTION
        "
        Boot Undone :This OID indicates
        that the boot has not been correctly
        achieved  <Help>  This alarm indicates
        if the module has correctly boot
        <Condtype> BOOT_UNDONE <Probcause>
        softwareError (47) <Alarmtype>
         processingErrorAlarm (4) <Polarity>
        (2)
        "
	  ::= { pm1008AlmmodInitFailLevel2 3 }



pm1008AlmNextColdBootForced OBJECT-TYPE
	  SYNTAX EkiOnOff
	  MAX-ACCESS read-only
	  STATUS current
	  DESCRIPTION
        "
        Next Cold Boot Forced :This OID
        indicates that the next Reset will
        be forced Cold  <Help>  This alarm
        indicates that the next reset of
        the module will be forced to cold
        reset <Condtype> NEXT_COLD_BOOT_FORCED
        <Probcause> informationalStatus(1000)
        <Alarmtype> other (1) <Polarity>
        (2)
        "
	  ::= { pm1008AlmmodInitFailLevel2 2 }



pm1008AlmLedFail OBJECT-TYPE
	  SYNTAX EkiOnOff
	  MAX-ACCESS read-only
	  STATUS current
	  DESCRIPTION
        "
        Led Fail :This OID indicates that
        Led register has not been correctly
        initalized  <Help>  This alarm
         indicates if the module LEDs are
        correctly initialized <Condtype>
        LED_FAIL <Probcause> softwareError
        (47) <Alarmtype> processingErrorAlarm
        (4) <Polarity> (2)
        "
	  ::= { pm1008AlmmodInitFailLevel2 1 }



--- *****************************************************
---     LEAF for the modInitFailLevel3 article
--- *****************************************************
pm1008AlmmodInitFailLevel3 OBJECT IDENTIFIER ::= { pm1008AlmOtherUrg 195 }




pm1008AlmClient8InitFail OBJECT-TYPE
	  SYNTAX EkiOnOff
	  MAX-ACCESS read-only
	  STATUS current
	  DESCRIPTION
        "
        Client8 Init Fail :This OID indicates
        that Client 8 registers subset
         has not been correctly initialized
         <Help>  This alarm indicates if
        the client port 8 is correctly
         initialized <Condtype> CLIENT8_INIT_FAIL
        <Probcause> softwareError (47)
         <Alarmtype> processingErrorAlarm
        (4) <Polarity> (2)
        "
	  ::= { pm1008AlmmodInitFailLevel3 16 }



pm1008AlmClient7InitFail OBJECT-TYPE
	  SYNTAX EkiOnOff
	  MAX-ACCESS read-only
	  STATUS current
	  DESCRIPTION
        "
        Client7 Init Fail :This OID indicates
        that Client 7 registers subset
         has not been correctly initialized
         <Help>  This alarm indicates if
        the client port 7 is correctly
         initialized <Condtype> CLIENT7_INIT_FAIL
        <Probcause> softwareError (47)
         <Alarmtype> processingErrorAlarm
        (4) <Polarity> (2)
        "
	  ::= { pm1008AlmmodInitFailLevel3 15 }



pm1008AlmClient6InitFail OBJECT-TYPE
	  SYNTAX EkiOnOff
	  MAX-ACCESS read-only
	  STATUS current
	  DESCRIPTION
        "
        Client6 Init Fail :This OID indicates
        that Client 6 registers subset
         has not been correctly initialized
         <Help>  This alarm indicates if
        the client port 6 is correctly
         initialized <Condtype> CLIENT6_INIT_FAIL
        <Probcause> softwareError (47)
         <Alarmtype> processingErrorAlarm
        (4) <Polarity> (2)
        "
	  ::= { pm1008AlmmodInitFailLevel3 14 }



pm1008AlmClient5InitFail OBJECT-TYPE
	  SYNTAX EkiOnOff
	  MAX-ACCESS read-only
	  STATUS current
	  DESCRIPTION
        "
        Client5 Init Fail :This OID indicates
        that Client 5 registers subset
         has not been correctly initialized
         <Help>  This alarm indicates if
        the client port 5 is correctly
         initialized <Condtype> CLIENT5_INIT_FAIL
        <Probcause> softwareError (47)
         <Alarmtype> processingErrorAlarm
        (4) <Polarity> (2)
        "
	  ::= { pm1008AlmmodInitFailLevel3 13 }



pm1008AlmClient4InitFail OBJECT-TYPE
	  SYNTAX EkiOnOff
	  MAX-ACCESS read-only
	  STATUS current
	  DESCRIPTION
        "
        Client4 Init Fail :This OID indicates
        that Client 4 registers subset
         has not been correctly initialized
         <Help>  This alarm indicates if
        the client port 4 is correctly
         initialized <Condtype> CLIENT4_INIT_FAIL
        <Probcause> softwareError (47)
         <Alarmtype> processingErrorAlarm
        (4) <Polarity> (2)
        "
	  ::= { pm1008AlmmodInitFailLevel3 12 }



pm1008AlmClient3InitFail OBJECT-TYPE
	  SYNTAX EkiOnOff
	  MAX-ACCESS read-only
	  STATUS current
	  DESCRIPTION
        "
        Client3 Init Fail :This OID indicates
        that Client 3 registers subset
         has not been correctly initialized
         <Help>  This alarm indicates if
        the client port 3 is correctly
         initialized <Condtype> CLIENT3_INIT_FAIL
        <Probcause> softwareError (47)
         <Alarmtype> processingErrorAlarm
        (4) <Polarity> (2)
        "
	  ::= { pm1008AlmmodInitFailLevel3 11 }



pm1008AlmClient2InitFail OBJECT-TYPE
	  SYNTAX EkiOnOff
	  MAX-ACCESS read-only
	  STATUS current
	  DESCRIPTION
        "
        Client2 Init Fail :This OID indicates
        that Client 2 registers subset
         has not been correctly initialized
         <Help>  This alarm indicates if
        the client port 2 is correctly
         initialized <Condtype> CLIENT2_INIT_FAIL
        <Probcause> softwareError (47)
         <Alarmtype> processingErrorAlarm
        (4) <Polarity> (2)
        "
	  ::= { pm1008AlmmodInitFailLevel3 10 }



pm1008AlmClient1InitFail OBJECT-TYPE
	  SYNTAX EkiOnOff
	  MAX-ACCESS read-only
	  STATUS current
	  DESCRIPTION
        "
        Client1 Init Fail :This OID indicates
        that Client 1 registers subset
         has not been correctly initialized
         <Help>  This alarm indicates if
        the client port 1 is correctly
         initialized <Condtype> CLIENT1_INIT_FAIL
        <Probcause> softwareError (47)
         <Alarmtype> processingErrorAlarm
        (4) <Polarity> (2)
        "
	  ::= { pm1008AlmmodInitFailLevel3 9 }



pm1008AlmLine2InitFail OBJECT-TYPE
	  SYNTAX EkiOnOff
	  MAX-ACCESS read-only
	  STATUS current
	  DESCRIPTION
        "
        Line2 Init Fail :This OID indicates
        that the Line register subset has
        not been correctly initialized
          <Help>  This alarm indicates
         if the line port 2 is correctly
        initialized <Condtype> LINE2_INIT_FAIL
        <Probcause> softwareError (47)
         <Alarmtype> processingErrorAlarm
        (4) <Polarity> (2)
        "
	  ::= { pm1008AlmmodInitFailLevel3 8 }



pm1008AlmLine1InitFail OBJECT-TYPE
	  SYNTAX EkiOnOff
	  MAX-ACCESS read-only
	  STATUS current
	  DESCRIPTION
        "
        Line1 Init Fail :This OID indicates
        that the Line registersvsubset
         has not been correctly initialized
         <Help>  This alarm indicates if
        the line port 1 is correctly initialized
        <Condtype> LINE1_INIT_FAIL <Probcause>
        softwareError (47) <Alarmtype>
         processingErrorAlarm (4) <Polarity>
        (2)
        "
	  ::= { pm1008AlmmodInitFailLevel3 7 }



pm1008AlmXfp2InitFail OBJECT-TYPE
	  SYNTAX EkiOnOff
	  MAX-ACCESS read-only
	  STATUS current
	  DESCRIPTION
        "
        XFP2 Init Fail :This OID indicates
        that the XFP has not been correctly
        initialized  <Help>  This alarm
        indicates if the line transceiver
        2 is correctly initialized <Condtype>
        XFP2_INIT_FAIL <Probcause> softwareError
        (47) <Alarmtype> processingErrorAlarm
        (4) <Polarity> (2)
        "
	  ::= { pm1008AlmmodInitFailLevel3 6 }



pm1008AlmXfp1InitFail OBJECT-TYPE
	  SYNTAX EkiOnOff
	  MAX-ACCESS read-only
	  STATUS current
	  DESCRIPTION
        "
        XFP1 Init Fail :This OID indicates
        that the XFP has not been correctly
        initialized  <Help>  This alarm
        indicates if the line transceiver
        1 is correctly initialized <Condtype>
        XFP1_INIT_FAIL <Probcause> softwareError
        (47) <Alarmtype> processingErrorAlarm
        (4) <Polarity> (2)
        "
	  ::= { pm1008AlmmodInitFailLevel3 5 }



pm1008AlmInitModuleFail OBJECT-TYPE
	  SYNTAX EkiOnOff
	  MAX-ACCESS read-only
	  STATUS current
	  DESCRIPTION
        "
        Init Module Fail :This OID indicates
        that the Module has not been correctly
        initialized  <Help>  This alarm
        indicates if the SW module is correctly
        initialized <Condtype> INIT_MODULE_FAIL
        <Probcause> softwareError (47)
         <Alarmtype> processingErrorAlarm
        (4) <Polarity> (2)
        "
	  ::= { pm1008AlmmodInitFailLevel3 3 }



pm1008AlmObmTypeReadFail OBJECT-TYPE
	  SYNTAX EkiOnOff
	  MAX-ACCESS read-only
	  STATUS current
	  DESCRIPTION
        "
        OBM Type Read Fail :This OID indicates
        that OBM type has not been recognized
         <Help>  This alarm indicates if
        the OBM board has been correctly
        identified <Condtype> OBM_TYPE_READ_FAIL
        <Probcause> softwareError (47)
         <Alarmtype> processingErrorAlarm
        (4) <Polarity> (2)
        "
	  ::= { pm1008AlmmodInitFailLevel3 2 }



pm1008AlmGwIdentFail OBJECT-TYPE
	  SYNTAX EkiOnOff
	  MAX-ACCESS read-only
	  STATUS current
	  DESCRIPTION
        "
        GW Ident Fail :This OID indicates
        that GW identification has not
         been read  <Help>  This alarm
         indicates if the GW has been correctly
        identified <Condtype> GW_IDENT_FAIL
        <Probcause> softwareError (47)
         <Alarmtype> processingErrorAlarm
        (4) <Polarity> (2)
        "
	  ::= { pm1008AlmmodInitFailLevel3 1 }



--- *********************************************************
---     TABLE for the pm1008AlmlineXfp1Alarm articles
--- *********************************************************

pm1008AlmlineXfp1AlarmTable OBJECT-TYPE
	SYNTAX  SEQUENCE OF Pm1008AlmlineXfp1AlarmEntry
	MAX-ACCESS not-accessible
	STATUS current
	DESCRIPTION
        "
        List of pm1008AlmlineXfp1Alarm
        Article
        "
	::= { pm1008AlmLineUrg 208 }


pm1008AlmlineXfp1AlarmEntry OBJECT-TYPE
	SYNTAX Pm1008AlmlineXfp1AlarmEntry
	MAX-ACCESS not-accessible
	STATUS current
	DESCRIPTION
        "
        Row definition for the pm1008AlmlineXfp1Alarm
        table
        "
	INDEX   { pm1008AlmlineXfp1AlarmIndex }
	::= { pm1008AlmlineXfp1AlarmTable 1 }


Pm1008AlmlineXfp1AlarmEntry ::=
	SEQUENCE {
	pm1008AlmlineXfp1AlarmIndex
		INTEGER,
	pm1008AlmRxPowerHighAlarmPortn
		EkiOnOff,
	pm1008AlmRxPowerLowAlarmPortn
		EkiOnOff,
	pm1008AlmTempHighAlarmPortn
		EkiOnOff,
	pm1008AlmTempLowAlarmPortn
		EkiOnOff,
	pm1008AlmTxBiasHighAlarmPortn
		EkiOnOff,
	pm1008AlmTxBiasLowAlarmPortn
		EkiOnOff,
	pm1008AlmTxPowerHighAlarmPortn
		EkiOnOff,
	pm1008AlmTxPowerLowAlarmPortn
		EkiOnOff
	}


pm1008AlmlineXfp1AlarmIndex OBJECT-TYPE
	SYNTAX  INTEGER(0..128)
	MAX-ACCESS  read-only
	STATUS current
	DESCRIPTION
        "
        Index definition for the pm1008AlmlineXfp1Alarm
        table
        "
	::= { pm1008AlmlineXfp1AlarmEntry 1 }


pm1008AlmRxPowerHighAlarmPortn OBJECT-TYPE
	SYNTAX  EkiOnOff
	MAX-ACCESS read-only
	STATUS current
	DESCRIPTION
        "
        Line Optical Rx Power High :Alarm
        indicating that the XFP received
        optical power is higher than the
        threshold value written in the
         XFP EEPROM <Condtype> RX_POWER_HIGH_ALARM_1
        <Probcause> receiveFailure (41)
        <Alarmtype> equipmentAlarm (5)
         <Polarity> (2)
        "
	::= { pm1008AlmlineXfp1AlarmEntry 17 }


pm1008AlmRxPowerLowAlarmPortn OBJECT-TYPE
	SYNTAX  EkiOnOff
	MAX-ACCESS read-only
	STATUS current
	DESCRIPTION
        "
        Line Optical Rx Power Low :Alarm
        indicating that the XFP received
        optical power is lower than the
        threshold value written in the
         XFP EEPROM  <Condtype> RX_POWER_LOW_ALARM_1
        <Probcause> receiveFailure (41)
        <Alarmtype> equipmentAlarm (5)
         <Polarity> (2)
        "
	::= { pm1008AlmlineXfp1AlarmEntry 16 }


pm1008AlmTempHighAlarmPortn OBJECT-TYPE
	SYNTAX  EkiOnOff
	MAX-ACCESS read-only
	STATUS current
	DESCRIPTION
        "
        Line Transceiver Temp High :Alarm
        indicating that the XFP/OTX temperature
        is higher than the threshold value
        written in the XFP EEPROM <Condtype>
        TEMP_HIGH_ALARM_1 <Probcause> temperatureUnacceptable
        (51) <Alarmtype> equipmentAlarm
        (5) <Polarity> (2)
        "
	::= { pm1008AlmlineXfp1AlarmEntry 9 }


pm1008AlmTempLowAlarmPortn OBJECT-TYPE
	SYNTAX  EkiOnOff
	MAX-ACCESS read-only
	STATUS current
	DESCRIPTION
        "
        Line Transceiver Temp Low :Alarm
        indicating that the XFP/OTX temperature
        is lower than the threshold value
        written in the XFP/OTX EEPROM <Condtype>
        TEMP_LOW_ALARM_1 <Probcause> temperatureUnacceptable
        (51) <Alarmtype> equipmentAlarm
        (5) <Polarity> (2)
        "
	::= { pm1008AlmlineXfp1AlarmEntry 8 }


pm1008AlmTxBiasHighAlarmPortn OBJECT-TYPE
	SYNTAX  EkiOnOff
	MAX-ACCESS read-only
	STATUS current
	DESCRIPTION
        "
        Line Transceiver Bias High :Alarm
        indicating that the XFP/OTX transmitter
        laser bias current is higher than
        the threshold value written in
         the XFP EEPROM <Condtype> TX_BIAS_HIGH_ALARM_1
        <Probcause> transmitterFailure
         (56) <Alarmtype> equipmentAlarm
        (5) <Polarity> (2)
        "
	::= { pm1008AlmlineXfp1AlarmEntry 5 }


pm1008AlmTxBiasLowAlarmPortn OBJECT-TYPE
	SYNTAX  EkiOnOff
	MAX-ACCESS read-only
	STATUS current
	DESCRIPTION
        "
        Line Transceiver Bias Low :Alarm
        indicating that the XFP/OTX transmitter
        laser bias current is lower than
        the threshold value written in
         the XFP/OTX EEPROM <Condtype>
         TX_BIAS_LOW_ALARM_1 <Probcause>
        transmitterFailure (56) <Alarmtype>
        equipmentAlarm (5) <Polarity> (2)
        "
	::= { pm1008AlmlineXfp1AlarmEntry 4 }


pm1008AlmTxPowerHighAlarmPortn OBJECT-TYPE
	SYNTAX  EkiOnOff
	MAX-ACCESS read-only
	STATUS current
	DESCRIPTION
        "
        Line Optical Tx Power High :Alarm
        indicating that the XFP/OTX transmitter
        transmitter output power is higher
        than the threshold value written
        in the XFP EEPROM <Condtype> TX_POWER_HIGH_ALARM_1
        <Probcause> transmitterFailure
         (56) <Alarmtype> equipmentAlarm
        (5) <Polarity> (2)
        "
	::= { pm1008AlmlineXfp1AlarmEntry 3 }


pm1008AlmTxPowerLowAlarmPortn OBJECT-TYPE
	SYNTAX  EkiOnOff
	MAX-ACCESS read-only
	STATUS current
	DESCRIPTION
        "
        Line Optical Tx Power Low :Alarm
        indicating that the XFP/OTX transmitter
        transmitter output power is lower
        than the threshold value written
        in the XFP/OTX EEPROM <Condtype>
        TX_POWER_LOW_ALARM_1 <Probcause>
        transmitterFailure (56) <Alarmtype>
        equipmentAlarm (5) <Polarity> (2)
        "
	::= { pm1008AlmlineXfp1AlarmEntry 2 }


--- *********************************************************
---     TABLE for the pm1008AlmlineXfp1Warnings articles
--- *********************************************************

pm1008AlmlineXfp1WarningsTable OBJECT-TYPE
	SYNTAX  SEQUENCE OF Pm1008AlmlineXfp1WarningsEntry
	MAX-ACCESS not-accessible
	STATUS current
	DESCRIPTION
        "
        List of pm1008AlmlineXfp1Warnings
        Article
        "
	::= { pm1008AlmLineNurg 209 }


pm1008AlmlineXfp1WarningsEntry OBJECT-TYPE
	SYNTAX Pm1008AlmlineXfp1WarningsEntry
	MAX-ACCESS not-accessible
	STATUS current
	DESCRIPTION
        "
        Row definition for the pm1008AlmlineXfp1Warnings
        table
        "
	INDEX   { pm1008AlmlineXfp1WarningsIndex }
	::= { pm1008AlmlineXfp1WarningsTable 1 }


Pm1008AlmlineXfp1WarningsEntry ::=
	SEQUENCE {
	pm1008AlmlineXfp1WarningsIndex
		INTEGER,
	pm1008AlmRxPowerHighWarningPortn
		EkiOnOff,
	pm1008AlmRxPowerLowWarningPortn
		EkiOnOff,
	pm1008AlmTempHighWarningPortn
		EkiOnOff,
	pm1008AlmTempLowWarningPortn
		EkiOnOff,
	pm1008AlmTxBiasHighWarningPortn
		EkiOnOff,
	pm1008AlmTxBiasLowWarningPortn
		EkiOnOff,
	pm1008AlmTxPowerHighWarningPortn
		EkiOnOff,
	pm1008AlmTxPowerLowWarningPortn
		EkiOnOff
	}


pm1008AlmlineXfp1WarningsIndex OBJECT-TYPE
	SYNTAX  INTEGER(0..128)
	MAX-ACCESS  read-only
	STATUS current
	DESCRIPTION
        "
        Index definition for the pm1008AlmlineXfp1Warnings
        table
        "
	::= { pm1008AlmlineXfp1WarningsEntry 1 }


pm1008AlmRxPowerHighWarningPortn OBJECT-TYPE
	SYNTAX  EkiOnOff
	MAX-ACCESS read-only
	STATUS current
	DESCRIPTION
        "
        Line Optical Rx Power High Warning
        :Warning indicating that the XFP
        received optical power is higher
        than the threshold value written
        in the XFP EEPROM <Condtype> RX_POWER_HIGH_WARNING_1
        <Probcause> receiveFailure (41)
        <Alarmtype> equipmentAlarm (5)
         <Polarity> (2)
        "
	::= { pm1008AlmlineXfp1WarningsEntry 17 }


pm1008AlmRxPowerLowWarningPortn OBJECT-TYPE
	SYNTAX  EkiOnOff
	MAX-ACCESS read-only
	STATUS current
	DESCRIPTION
        "
        Line Optical Rx Power Low Warning
        :Warning indicating that the XFP
        received optical power is lower
        than the threshold value written
        in the XFP EEPROM  <Condtype> RX_POWER_LOW_WARNING_1
        <Probcause> receiveFailure (41)
        <Alarmtype> equipmentAlarm (5)
         <Polarity> (2)
        "
	::= { pm1008AlmlineXfp1WarningsEntry 16 }


pm1008AlmTempHighWarningPortn OBJECT-TYPE
	SYNTAX  EkiOnOff
	MAX-ACCESS read-only
	STATUS current
	DESCRIPTION
        "
        Line Transceiver Temp High Warning
        :Warning indicating that the XFP/OTX
        temperature is higher than the
         threshold value written in the
        XFP EEPROM <Condtype> TEMP_HIGH_WARNING_1
        <Probcause> temperatureUnacceptable
        (51) <Alarmtype> equipmentAlarm
        (5) <Polarity> (2)
        "
	::= { pm1008AlmlineXfp1WarningsEntry 9 }


pm1008AlmTempLowWarningPortn OBJECT-TYPE
	SYNTAX  EkiOnOff
	MAX-ACCESS read-only
	STATUS current
	DESCRIPTION
        "
        Line Transceiver Temp Low Warning
        :Warning indicating that the XFP/OTX
        temperature is lower than the threshold
        value written in the XFP/OTX EEPROM
        <Condtype> TEMP_LOW_WARNING_1 <Probcause>
        temperatureUnacceptable (51) <Alarmtype>
        equipmentAlarm (5) <Polarity> (2)
        "
	::= { pm1008AlmlineXfp1WarningsEntry 8 }


pm1008AlmTxBiasHighWarningPortn OBJECT-TYPE
	SYNTAX  EkiOnOff
	MAX-ACCESS read-only
	STATUS current
	DESCRIPTION
        "
        Line Transceiver Bias High Warning
        :Warning indicating that the XFP/OTX
        transmitter laser bias current
         is higher than the threshold value
        written in the XFP EEPROM <Condtype>
        TX_BIAS_HIGH_WARNING_1 <Probcause>
        transmitterFailure (56) <Alarmtype>
        equipmentAlarm (5) <Polarity> (2)
        "
	::= { pm1008AlmlineXfp1WarningsEntry 5 }


pm1008AlmTxBiasLowWarningPortn OBJECT-TYPE
	SYNTAX  EkiOnOff
	MAX-ACCESS read-only
	STATUS current
	DESCRIPTION
        "
        Line Transceiver Bias Low Warning
        :Warning indicating that the XFP/OTX
        transmitter laser bias current
         is lower than the threshold value
        written in the XFP/OTX EEPROM <Condtype>
        TX_BIAS_LOW_WARNING_1 <Probcause>
        transmitterFailure (56) <Alarmtype>
        equipmentAlarm (5) <Polarity> (2)
        "
	::= { pm1008AlmlineXfp1WarningsEntry 4 }


pm1008AlmTxPowerHighWarningPortn OBJECT-TYPE
	SYNTAX  EkiOnOff
	MAX-ACCESS read-only
	STATUS current
	DESCRIPTION
        "
        Line Optical Tx Power High Warning
        :Warning indicating that the XFP/OTX
        transmitter transmitter output
         power is higher than the threshold
        value written in the XFP EEPROM
        <Condtype> TX_POWER_HIGH_WARNING_1
        <Probcause> transmitterFailure
         (56) <Alarmtype> equipmentAlarm
        (5) <Polarity> (2)
        "
	::= { pm1008AlmlineXfp1WarningsEntry 3 }


pm1008AlmTxPowerLowWarningPortn OBJECT-TYPE
	SYNTAX  EkiOnOff
	MAX-ACCESS read-only
	STATUS current
	DESCRIPTION
        "
        Line Optical Tx Power Low Warning
        :Warning indicating that the XFP/OTX
        transmitter transmitter output
         power is lower than the threshold
        value written in the XFP/OTX EEPROM
        <Condtype> TX_POWER_LOW_WARNING_1
        <Probcause> transmitterFailure
         (56) <Alarmtype> equipmentAlarm
        (5) <Polarity> (2)
        "
	::= { pm1008AlmlineXfp1WarningsEntry 2 }


--- *********************************************************
---     TABLE for the pm1008AlmlineXfp1Alarms articles
--- *********************************************************

pm1008AlmlineXfp1AlarmsTable OBJECT-TYPE
	SYNTAX  SEQUENCE OF Pm1008AlmlineXfp1AlarmsEntry
	MAX-ACCESS not-accessible
	STATUS current
	DESCRIPTION
        "
        List of pm1008AlmlineXfp1Alarms
        Article
        "
	::= { pm1008AlmLineCrit 211 }


pm1008AlmlineXfp1AlarmsEntry OBJECT-TYPE
	SYNTAX Pm1008AlmlineXfp1AlarmsEntry
	MAX-ACCESS not-accessible
	STATUS current
	DESCRIPTION
        "
        Row definition for the pm1008AlmlineXfp1Alarms
        table
        "
	INDEX   { pm1008AlmlineXfp1AlarmsIndex }
	::= { pm1008AlmlineXfp1AlarmsTable 1 }


Pm1008AlmlineXfp1AlarmsEntry ::=
	SEQUENCE {
	pm1008AlmlineXfp1AlarmsIndex
		INTEGER,
	pm1008AlmApdSupplyFaultPortn
		EkiOnOff,
	pm1008AlmTecFaultPortn
		EkiOnOff,
	pm1008AlmWavelengthUnlockedPortn
		EkiOnOff,
	pm1008AlmTxNrPortn
		EkiOnOff,
	pm1008AlmTxFaultPortn
		EkiOnOff,
	pm1008AlmTxCdrNotLockedPortn
		EkiOnOff,
	pm1008AlmRxNrPortn
		EkiOnOff,
	pm1008AlmRxCdrNotLockedPortn
		EkiOnOff,
	pm1008AlmModNrPortn
		EkiOnOff
	}


pm1008AlmlineXfp1AlarmsIndex OBJECT-TYPE
	SYNTAX  INTEGER(0..128)
	MAX-ACCESS  read-only
	STATUS current
	DESCRIPTION
        "
        Index definition for the pm1008AlmlineXfp1Alarms
        table
        "
	::= { pm1008AlmlineXfp1AlarmsEntry 1 }


pm1008AlmApdSupplyFaultPortn OBJECT-TYPE
	SYNTAX  EkiOnOff
	MAX-ACCESS read-only
	STATUS current
	DESCRIPTION
        "
        Line Rx Photodiode Power Failed
        :This OID indicates a failure on
        the APD power supply  <Help>  This
        alarm indicates if the APD power
        supply is in fail condition <Condtype>
        APD_SUPPLY_FAULT_1 <Probcause>
         receiverFailure (42) <Alarmtype>
        equipmentAlarm (5) <Polarity> (2)
        "
	::= { pm1008AlmlineXfp1AlarmsEntry 17 }


pm1008AlmTecFaultPortn OBJECT-TYPE
	SYNTAX  EkiOnOff
	MAX-ACCESS read-only
	STATUS current
	DESCRIPTION
        "
        Line Optical Tx Temp Regul Failed
        :This OID indicates a failure on
        the TEC module  <Help>  This alarm
        indicates if the TEC of the line
        transceiver is in fail condition
        <Condtype> TEC_FAULT_1 <Probcause>
        transmitterFailure (56) <Alarmtype>
        equipmentAlarm (5) <Polarity> (2)
        "
	::= { pm1008AlmlineXfp1AlarmsEntry 16 }


pm1008AlmWavelengthUnlockedPortn OBJECT-TYPE
	SYNTAX  EkiOnOff
	MAX-ACCESS read-only
	STATUS current
	DESCRIPTION
        "
        Line Optical Tx Wavelength Unlocked
        :This OID indicates that the wavelength
        error is exceeding the manufacturer
        tolerance  <Help>  This alarm indicates
        if the wavelenght of the line transceiver
        is locked <Condtype> WAVELENGTH_UNLOCKED_1
        <Probcause> transmitterFailure
         (56) <Alarmtype> equipmentAlarm
        (5) <Polarity> (2)
        "
	::= { pm1008AlmlineXfp1AlarmsEntry 15 }


pm1008AlmTxNrPortn OBJECT-TYPE
	SYNTAX  EkiOnOff
	MAX-ACCESS read-only
	STATUS current
	DESCRIPTION
        "
        Line Optical Tx Not Ready :This
        OID indicates a condition has arisen
        leading to invalid data on the
         transmitting side  <Help>  This
        alarm indicates if the Tx part
         of the line transceiver is ready
        <Condtype> TX_NR_1 <Probcause>
         transmitterFailure (56) <Alarmtype>
        equipmentAlarm (5) <Polarity> (2)
        "
	::= { pm1008AlmlineXfp1AlarmsEntry 9 }


pm1008AlmTxFaultPortn OBJECT-TYPE
	SYNTAX  EkiOnOff
	MAX-ACCESS read-only
	STATUS current
	DESCRIPTION
        "
        Line Optical Tx Failure :This
         OID indicates a fault condition
        on the laser detected by the safety
        syste  <Help>  This alarm indicates
        if the laser of the line transceiver
        is in fail condition <Condtype>
        TX_FAULT_1 <Probcause> transmitterFailure
        (56) <Alarmtype> equipmentAlarm
        (5) <Polarity> (2)
        "
	::= { pm1008AlmlineXfp1AlarmsEntry 8 }


pm1008AlmTxCdrNotLockedPortn OBJECT-TYPE
	SYNTAX  EkiOnOff
	MAX-ACCESS read-only
	STATUS current
	DESCRIPTION
        "
        Line Optical Tx CDR Unlocked :This
        OID indicates a loss of lock on
        the transmitting side CDR has been
        detected.  <Help>  This alarm indicates
        if the Tx CDR is locked in the
         line transceiver <Condtype> TX_CDR_NOT_LOCKED1_1
        <Probcause> transmitterFailure
         (56) <Alarmtype> equipmentAlarm
        (5) <Polarity> (2)
        "
	::= { pm1008AlmlineXfp1AlarmsEntry 7 }


pm1008AlmRxNrPortn OBJECT-TYPE
	SYNTAX  EkiOnOff
	MAX-ACCESS read-only
	STATUS current
	DESCRIPTION
        "
        Line Optical Rx Not Ready :This
        OID indicates that a condition
         has arisen leading to invalid
         data on the receiving side.  <Help>
         This alarm indicates if the Rx
        part of the line transceiver is
        ready <Condtype> RX_NR_1 <Probcause>
        receiveFailure (41) <Alarmtype>
        equipmentAlarm (5) <Polarity> (2)
        "
	::= { pm1008AlmlineXfp1AlarmsEntry 6 }


pm1008AlmRxCdrNotLockedPortn OBJECT-TYPE
	SYNTAX  EkiOnOff
	MAX-ACCESS read-only
	STATUS current
	DESCRIPTION
        "
        Line Optical Rx CDR Unlocked :This
        OID indicates that a loss of lock
        on the receiving side CDR has been
        detected  <Help>  This alarm indicates
        if the Rx CDR is locked in the
         line transceiver <Condtype> RX_CDR_NOT_LOCKED1_1
        <Probcause> receiveFailure (41)
        <Alarmtype> equipmentAlarm (5)
         <Polarity> (2)
        "
	::= { pm1008AlmlineXfp1AlarmsEntry 4 }


pm1008AlmModNrPortn OBJECT-TYPE
	SYNTAX  EkiOnOff
	MAX-ACCESS read-only
	STATUS current
	DESCRIPTION
        "
        Line Optical Module Not Ready
         :This OID indicates that the module
        is unable to determine correct
         data.  <Help>  This alarm indicates
        if the line transceiver is ready
        <Condtype> MOD_NR_1 <Probcause>
        receiveFailure (41) <Alarmtype>
        equipmentAlarm (5) <Polarity> (2)
        "
	::= { pm1008AlmlineXfp1AlarmsEntry 3 }


--- *********************************************************
---     TABLE for the pm1008AlmlineXfp1SupplyAlarm articles
--- *********************************************************

pm1008AlmlineXfp1SupplyAlarmTable OBJECT-TYPE
	SYNTAX  SEQUENCE OF Pm1008AlmlineXfp1SupplyAlarmEntry
	MAX-ACCESS not-accessible
	STATUS current
	DESCRIPTION
        "
        List of pm1008AlmlineXfp1SupplyAlarm
        Article
        "
	::= { pm1008AlmLineUrg 212 }


pm1008AlmlineXfp1SupplyAlarmEntry OBJECT-TYPE
	SYNTAX Pm1008AlmlineXfp1SupplyAlarmEntry
	MAX-ACCESS not-accessible
	STATUS current
	DESCRIPTION
        "
        Row definition for the pm1008AlmlineXfp1SupplyAlarm
        table
        "
	INDEX   { pm1008AlmlineXfp1SupplyAlarmIndex }
	::= { pm1008AlmlineXfp1SupplyAlarmTable 1 }


Pm1008AlmlineXfp1SupplyAlarmEntry ::=
	SEQUENCE {
	pm1008AlmlineXfp1SupplyAlarmIndex
		INTEGER,
	pm1008AlmVcc5HighWarningPortn
		EkiOnOff,
	pm1008AlmVcc5LowWarningPortn
		EkiOnOff,
	pm1008AlmVcc3HighWarningPortn
		EkiOnOff,
	pm1008AlmVcc3LowWarningPortn
		EkiOnOff,
	pm1008AlmVcc2HighWarningPortn
		EkiOnOff,
	pm1008AlmVcc2LowWarningPortn
		EkiOnOff,
	pm1008AlmVee5HighWarningPortn
		EkiOnOff,
	pm1008AlmVee5LowWarningPortn
		EkiOnOff,
	pm1008AlmVcc5HighAlarmPortn
		EkiOnOff,
	pm1008AlmVcc5LowAlarmPortn
		EkiOnOff,
	pm1008AlmVcc3HighAlarmPortn
		EkiOnOff,
	pm1008AlmVcc3LowAlarmPortn
		EkiOnOff,
	pm1008AlmVcc2HighAlarmPortn
		EkiOnOff,
	pm1008AlmVcc2LowAlarmPortn
		EkiOnOff,
	pm1008AlmVee5HighAlarmPortn
		EkiOnOff,
	pm1008AlmVee5LowAlarmPortn
		EkiOnOff
	}


pm1008AlmlineXfp1SupplyAlarmIndex OBJECT-TYPE
	SYNTAX  INTEGER(0..128)
	MAX-ACCESS  read-only
	STATUS current
	DESCRIPTION
        "
        Index definition for the pm1008AlmlineXfp1SupplyAlarm
        table
        "
	::= { pm1008AlmlineXfp1SupplyAlarmEntry 1 }


pm1008AlmVcc5HighWarningPortn OBJECT-TYPE
	SYNTAX  EkiOnOff
	MAX-ACCESS read-only
	STATUS current
	DESCRIPTION
        "
        VCC5 Power Supply High Warning
        :Warning indicating the XFP/OTX
        VCC5 power supply is higher than
        the threshold written in the EEPROM
        <Condtype> VCC5_HIGH_WARNING_1
         <Probcause> powerProblem (36)
         <Alarmtype> equipmentAlarm (5)
        <Polarity> (2)
        "
	::= { pm1008AlmlineXfp1SupplyAlarmEntry 17 }


pm1008AlmVcc5LowWarningPortn OBJECT-TYPE
	SYNTAX  EkiOnOff
	MAX-ACCESS read-only
	STATUS current
	DESCRIPTION
        "
        VCC5 Power Supply Low Warning
         :Warning indicating the XFP/OTX
        VCC5 power supply is lower than
        the threshold written in the EEPROM
        <Condtype> VCC5_LOW_WARNING_1 <Probcause>
        powerProblem (36) <Alarmtype> equipmentAlarm
        (5) <Polarity> (2)
        "
	::= { pm1008AlmlineXfp1SupplyAlarmEntry 16 }


pm1008AlmVcc3HighWarningPortn OBJECT-TYPE
	SYNTAX  EkiOnOff
	MAX-ACCESS read-only
	STATUS current
	DESCRIPTION
        "
        VCC3 Power Supply High Warning
        :Warning indicating the XFP/OTX
        VCC3 power supply is higher than
        the threshold written in the EEPROM
        <Condtype> VCC3_HIGH_WARNING_1
         <Probcause> powerProblem (36)
         <Alarmtype> equipmentAlarm (5)
        <Polarity> (2)
        "
	::= { pm1008AlmlineXfp1SupplyAlarmEntry 15 }


pm1008AlmVcc3LowWarningPortn OBJECT-TYPE
	SYNTAX  EkiOnOff
	MAX-ACCESS read-only
	STATUS current
	DESCRIPTION
        "
        VCC3 Power Supply Low Warning
         :Warning indicating the XFP/OTX
        VCC3 power supply is lower than
        the threshold written in the EEPROM
        <Condtype> VCC3_LOW_WARNING_1 <Probcause>
        powerProblem (36) <Alarmtype> equipmentAlarm
        (5) <Polarity> (2)
        "
	::= { pm1008AlmlineXfp1SupplyAlarmEntry 14 }


pm1008AlmVcc2HighWarningPortn OBJECT-TYPE
	SYNTAX  EkiOnOff
	MAX-ACCESS read-only
	STATUS current
	DESCRIPTION
        "
        VCC2 Power Supply High Warning
        :Warning indicating the XFP/OTX
        VCC2 power supply is higher than
        the threshold written in the EEPROM
        <Condtype> VCC2_HIGH_WARNING_1
         <Probcause> powerProblem (36)
         <Alarmtype> equipmentAlarm (5)
        <Polarity> (2)
        "
	::= { pm1008AlmlineXfp1SupplyAlarmEntry 13 }


pm1008AlmVcc2LowWarningPortn OBJECT-TYPE
	SYNTAX  EkiOnOff
	MAX-ACCESS read-only
	STATUS current
	DESCRIPTION
        "
        VCC2 Power Supply Low Warning
         :Warning indicating the XFP/OTX
        VCC2 power supply is lower than
        the threshold written in the EEPROM
        <Condtype> VCC2_LOW_WARNING_1 <Probcause>
        powerProblem (36) <Alarmtype> equipmentAlarm
        (5) <Polarity> (2)
        "
	::= { pm1008AlmlineXfp1SupplyAlarmEntry 12 }


pm1008AlmVee5HighWarningPortn OBJECT-TYPE
	SYNTAX  EkiOnOff
	MAX-ACCESS read-only
	STATUS current
	DESCRIPTION
        "
        VEE5 Power Supply High Warning
        :Warning indicating the XFP/OTX
        VEE5 power supply is higher than
        the threshold written in the EEPROM
        <Condtype> VEE5_HIGH_WARNING_1
         <Probcause> powerProblem (36)
         <Alarmtype> equipmentAlarm (5)
        <Polarity> (2)
        "
	::= { pm1008AlmlineXfp1SupplyAlarmEntry 11 }


pm1008AlmVee5LowWarningPortn OBJECT-TYPE
	SYNTAX  EkiOnOff
	MAX-ACCESS read-only
	STATUS current
	DESCRIPTION
        "
        VEE5 Power Supply Low Warning
         :Warning indicating the XFP/OTX
        VEE5 power supply is lower than
        the threshold written in the EEPROM
        <Condtype> VEE5_LOW_WARNING_1 <Probcause>
        powerProblem (36) <Alarmtype> equipmentAlarm
        (5) <Polarity> (2)
        "
	::= { pm1008AlmlineXfp1SupplyAlarmEntry 10 }


pm1008AlmVcc5HighAlarmPortn OBJECT-TYPE
	SYNTAX  EkiOnOff
	MAX-ACCESS read-only
	STATUS current
	DESCRIPTION
        "
        VCC5 Power Supply High :Alarm
         indicating the XFP/OTX VCC5 power
        supply is higher than the threshold
        written in the EEPROM <Condtype>
        VCC5_HIGH_ALARM_1 <Probcause> powerProblem
        (36) <Alarmtype> equipmentAlarm
        (5) <Polarity> (2)
        "
	::= { pm1008AlmlineXfp1SupplyAlarmEntry 9 }


pm1008AlmVcc5LowAlarmPortn OBJECT-TYPE
	SYNTAX  EkiOnOff
	MAX-ACCESS read-only
	STATUS current
	DESCRIPTION
        "
        VCC5 Power Supply Low :Alarm indicating
        the XFP/OTX VCC5 power supply is
        lower than the threshold written
        in the EEPROM <Condtype> VCC5_LOW_ALARM_1
        <Probcause> powerProblem (36) <Alarmtype>
        equipmentAlarm (5) <Polarity> (2)
        "
	::= { pm1008AlmlineXfp1SupplyAlarmEntry 8 }


pm1008AlmVcc3HighAlarmPortn OBJECT-TYPE
	SYNTAX  EkiOnOff
	MAX-ACCESS read-only
	STATUS current
	DESCRIPTION
        "
        VCC3 Power Supply High :Alarm
         indicating the XFP/OTX VCC3 power
        supply is higher than the threshold
        written in the EEPROM <Condtype>
        VCC3_HIGH_ALARM_1 <Probcause> powerProblem
        (36) <Alarmtype> equipmentAlarm
        (5) <Polarity> (2)
        "
	::= { pm1008AlmlineXfp1SupplyAlarmEntry 7 }


pm1008AlmVcc3LowAlarmPortn OBJECT-TYPE
	SYNTAX  EkiOnOff
	MAX-ACCESS read-only
	STATUS current
	DESCRIPTION
        "
        VCC3 Power Supply Low :Alarm indicating
        the XFP/OTX VCC3 power supply is
        lower than the threshold written
        in the EEPROM <Condtype> VCC3_LOW_ALARM_1
        <Probcause> powerProblem (36) <Alarmtype>
        equipmentAlarm (5) <Polarity> (2)
        "
	::= { pm1008AlmlineXfp1SupplyAlarmEntry 6 }


pm1008AlmVcc2HighAlarmPortn OBJECT-TYPE
	SYNTAX  EkiOnOff
	MAX-ACCESS read-only
	STATUS current
	DESCRIPTION
        "
        VCC2 Power Supply High :Alarm
         indicating the XFP/OTX VCC2 power
        supply is higher than the threshold
        written in the EEPROM <Condtype>
        VCC2_HIGH_ALARM_1 <Probcause> powerProblem
        (36) <Alarmtype> equipmentAlarm
        (5) <Polarity> (2)
        "
	::= { pm1008AlmlineXfp1SupplyAlarmEntry 5 }


pm1008AlmVcc2LowAlarmPortn OBJECT-TYPE
	SYNTAX  EkiOnOff
	MAX-ACCESS read-only
	STATUS current
	DESCRIPTION
        "
        VCC2 Power Supply Low :Alarm indicating
        the XFP/OTX VCC2 power supply is
        lower than the threshold written
        in the EEPROM <Condtype> VCC2_LOW_ALARM_1
        <Probcause> powerProblem (36) <Alarmtype>
        equipmentAlarm (5) <Polarity> (2)
        "
	::= { pm1008AlmlineXfp1SupplyAlarmEntry 4 }


pm1008AlmVee5HighAlarmPortn OBJECT-TYPE
	SYNTAX  EkiOnOff
	MAX-ACCESS read-only
	STATUS current
	DESCRIPTION
        "
        VEE5 Power Supply High :Alarm
         indicating the XFP/OTX VEE5 power
        supply is higher than the threshold
        written in the EEPROM <Condtype>
        VEE5_HIGH_ALARM_1 <Probcause> powerProblem
        (36) <Alarmtype> equipmentAlarm
        (5) <Polarity> (2)
        "
	::= { pm1008AlmlineXfp1SupplyAlarmEntry 3 }


pm1008AlmVee5LowAlarmPortn OBJECT-TYPE
	SYNTAX  EkiOnOff
	MAX-ACCESS read-only
	STATUS current
	DESCRIPTION
        "
        VEE5 Power Supply Low :Alarm indicating
        the XFP/OTX VEE5 power supply is
        lower than the threshold written
        in the EEPROM <Condtype> VEE5_LOW_ALARM_1
        <Probcause> powerProblem (36) <Alarmtype>
        equipmentAlarm (5) <Polarity> (2)
        "
	::= { pm1008AlmlineXfp1SupplyAlarmEntry 2 }


--- *********************************************************
---     TABLE for the pm1008AlmlineOtx1TlhAlarms articles
--- *********************************************************

pm1008AlmlineOtx1TlhAlarmsTable OBJECT-TYPE
	SYNTAX  SEQUENCE OF Pm1008AlmlineOtx1TlhAlarmsEntry
	MAX-ACCESS not-accessible
	STATUS current
	DESCRIPTION
        "
        List of pm1008AlmlineOtx1TlhAlarms
        Article
        "
	::= { pm1008AlmLineUrg 224 }


pm1008AlmlineOtx1TlhAlarmsEntry OBJECT-TYPE
	SYNTAX Pm1008AlmlineOtx1TlhAlarmsEntry
	MAX-ACCESS not-accessible
	STATUS current
	DESCRIPTION
        "
        Row definition for the pm1008AlmlineOtx1TlhAlarms
        table
        "
	INDEX   { pm1008AlmlineOtx1TlhAlarmsIndex }
	::= { pm1008AlmlineOtx1TlhAlarmsTable 1 }


Pm1008AlmlineOtx1TlhAlarmsEntry ::=
	SEQUENCE {
	pm1008AlmlineOtx1TlhAlarmsIndex
		INTEGER,
	pm1008AlmLineLaserTempHighAlaPortn
		EkiOnOff,
	pm1008AlmLineFreqDevHighAlaPortn
		EkiOnOff,
	pm1008AlmLineAgingHighAlaPortn
		EkiOnOff,
	pm1008AlmLineModulatorAgingHighAlaPortn
		EkiOnOff
	}


pm1008AlmlineOtx1TlhAlarmsIndex OBJECT-TYPE
	SYNTAX  INTEGER(0..128)
	MAX-ACCESS  read-only
	STATUS current
	DESCRIPTION
        "
        Index definition for the pm1008AlmlineOtx1TlhAlarms
        table
        "
	::= { pm1008AlmlineOtx1TlhAlarmsEntry 1 }


pm1008AlmLineLaserTempHighAlaPortn OBJECT-TYPE
	SYNTAX  EkiOnOff
	MAX-ACCESS read-only
	STATUS current
	DESCRIPTION
        "
        Line Laser Temp. High Alarm :Alarm
        indicating the Line OTX TLH laser
        temperature is higher than the
         threshold written in the EEPROM
        <Condtype> LINE_LASER_TEMP_HIGH_ALA_1
        <Probcause> temperatureUnacceptable
        (51) <Alarmtype> equipmentAlarm
        (5) <Polarity> (2)
        "
	::= { pm1008AlmlineOtx1TlhAlarmsEntry 15 }


pm1008AlmLineFreqDevHighAlaPortn OBJECT-TYPE
	SYNTAX  EkiOnOff
	MAX-ACCESS read-only
	STATUS current
	DESCRIPTION
        "
        Line Freq. Deviation High Alarm
        :Alarm indicating the Line OTX
         TLH frequency deviation is higher
        than the threshold written in the
        EEPROM <Condtype> LINE_FREQ_DEV_HIGH_ALA_1
        <Probcause> transmitterFailure
         (56) <Alarmtype> equipmentAlarm
        (5) <Polarity> (2)
        "
	::= { pm1008AlmlineOtx1TlhAlarmsEntry 13 }


pm1008AlmLineAgingHighAlaPortn OBJECT-TYPE
	SYNTAX  EkiOnOff
	MAX-ACCESS read-only
	STATUS current
	DESCRIPTION
        "
        Line OTX TLH Aging High Alarm
         :Alarm indicating the Line OTX
        TLH aging is higher than the threshold
        written in the EEPROM <Condtype>
        LINE_AGING_HIGH_ALA_1 <Probcause>
        transmitterFailure (56) <Alarmtype>
        equipmentAlarm (5) <Polarity> (2)
        "
	::= { pm1008AlmlineOtx1TlhAlarmsEntry 7 }


pm1008AlmLineModulatorAgingHighAlaPortn OBJECT-TYPE
	SYNTAX  EkiOnOff
	MAX-ACCESS read-only
	STATUS current
	DESCRIPTION
        "
        Line Modulator Aging High Alarm
        :Alarm indicating the Line OTX
         TLH modulator aging is higher
         than the threshold written in
         the EEPROM <Condtype> LINE_MODULATOR_AGING_HIGH_ALA_1
        <Probcause> transmitterFailure
         (56) <Alarmtype> equipmentAlarm
        (5) <Polarity> (2)
        "
	::= { pm1008AlmlineOtx1TlhAlarmsEntry 6 }


--- *********************************************************
---     TABLE for the pm1008AlmlineOtx1TlhWarnings articles
--- *********************************************************

pm1008AlmlineOtx1TlhWarningsTable OBJECT-TYPE
	SYNTAX  SEQUENCE OF Pm1008AlmlineOtx1TlhWarningsEntry
	MAX-ACCESS not-accessible
	STATUS current
	DESCRIPTION
        "
        List of pm1008AlmlineOtx1TlhWarnings
        Article
        "
	::= { pm1008AlmLineNurg 225 }


pm1008AlmlineOtx1TlhWarningsEntry OBJECT-TYPE
	SYNTAX Pm1008AlmlineOtx1TlhWarningsEntry
	MAX-ACCESS not-accessible
	STATUS current
	DESCRIPTION
        "
        Row definition for the pm1008AlmlineOtx1TlhWarnings
        table
        "
	INDEX   { pm1008AlmlineOtx1TlhWarningsIndex }
	::= { pm1008AlmlineOtx1TlhWarningsTable 1 }


Pm1008AlmlineOtx1TlhWarningsEntry ::=
	SEQUENCE {
	pm1008AlmlineOtx1TlhWarningsIndex
		INTEGER,
	pm1008AlmLineLaserTempHighWarningPortn
		EkiOnOff,
	pm1008AlmLineFreqDevHighWarningPortn
		EkiOnOff,
	pm1008AlmLineAgingHighWarningPortn
		EkiOnOff,
	pm1008AlmLineModulatorAgingHighWarningPortn
		EkiOnOff
	}


pm1008AlmlineOtx1TlhWarningsIndex OBJECT-TYPE
	SYNTAX  INTEGER(0..128)
	MAX-ACCESS  read-only
	STATUS current
	DESCRIPTION
        "
        Index definition for the pm1008AlmlineOtx1TlhWarnings
        table
        "
	::= { pm1008AlmlineOtx1TlhWarningsEntry 1 }


pm1008AlmLineLaserTempHighWarningPortn OBJECT-TYPE
	SYNTAX  EkiOnOff
	MAX-ACCESS read-only
	STATUS current
	DESCRIPTION
        "
        Line Laser Temp. High Warning
         :Warning indicating the Line OTX
        TLH laser temperature is higher
        than the threshold written in the
        EEPROM <Condtype> LINE_LASER_TEMP_HIGH_WARNING_1
        <Probcause> temperatureUnacceptable
        (51) <Alarmtype> equipmentAlarm
        (5) <Polarity> (2)
        "
	::= { pm1008AlmlineOtx1TlhWarningsEntry 15 }


pm1008AlmLineFreqDevHighWarningPortn OBJECT-TYPE
	SYNTAX  EkiOnOff
	MAX-ACCESS read-only
	STATUS current
	DESCRIPTION
        "
        Line Freq. Deviation High Warning
        :Warning indicating the Line OTX
        TLH frequency deviation is higher
        than the threshold written in the
        EEPROM <Condtype> LINE_FREQ_DEV_HIGH_WARNING_1
        <Probcause> transmitterFailure
         (56) <Alarmtype> equipmentAlarm
        (5) <Polarity> (2)
        "
	::= { pm1008AlmlineOtx1TlhWarningsEntry 13 }


pm1008AlmLineAgingHighWarningPortn OBJECT-TYPE
	SYNTAX  EkiOnOff
	MAX-ACCESS read-only
	STATUS current
	DESCRIPTION
        "
        Line OTX TLH Aging High Warning
        :Warning indicating the Line OTX
        TLH aging is higher than the threshold
        written in the EEPROM <Condtype>
        LINE_AGING_HIGH_WARNING_1 <Probcause>
        transmitterFailure (56) <Alarmtype>
        equipmentAlarm (5) <Polarity> (2)
        "
	::= { pm1008AlmlineOtx1TlhWarningsEntry 7 }


pm1008AlmLineModulatorAgingHighWarningPortn OBJECT-TYPE
	SYNTAX  EkiOnOff
	MAX-ACCESS read-only
	STATUS current
	DESCRIPTION
        "
        Line Modulator Aging High Warning
        :Warning indicating the Line OTX
        TLH modulator aging is higher than
        the threshold written in the EEPROM
        <Condtype> LINE_MODULATOR_AGING_HIGH_WARNING_1
        <Probcause> transmitterFailure
         (56) <Alarmtype> equipmentAlarm
        (5) <Polarity> (2)
        "
	::= { pm1008AlmlineOtx1TlhWarningsEntry 6 }







--- *****************************************************
--- $$$$$$$$$$$$$$$$$$$$$$$$$$$$$$$$$$$$$$$$$$$$$$$$$$$$$
---     CONTROLS
--- $$$$$$$$$$$$$$$$$$$$$$$$$$$$$$$$$$$$$$$$$$$$$$$$$$$$$
--- *****************************************************



--- *****************************************************
---     LEAF for the confMgnt1 article
--- *****************************************************
pm1008CtrlconfMgnt1 OBJECT IDENTIFIER ::= { pm1008CtrlOther 1 }




pm1008CtrlConf2Clear1 OBJECT-TYPE
	  SYNTAX EkiOnOff
	  MAX-ACCESS read-write
	  STATUS current
	  DESCRIPTION
        "
        Clear Configuration Tables :This
        OID clears the configuration tables
        from configuration2 in the flash.
         <Help>  This control restores
         the default configuration of the
        module
        "
	  ::= { pm1008CtrlconfMgnt1 14 }



pm1008CtrlConf2Flash1 OBJECT-TYPE
	  SYNTAX EkiOnOff
	  MAX-ACCESS read-write
	  STATUS current
	  DESCRIPTION
        "
        Write Configuration Tables :This
        OID saves the current configuration
        of the PM as configuration2 in
         the flash.  <Help>  This control
        saves the customer configuration
        on the module
        "
	  ::= { pm1008CtrlconfMgnt1 10 }



pm1008CtrlConf2Load1 OBJECT-TYPE
	  SYNTAX EkiOnOff
	  MAX-ACCESS read-write
	  STATUS current
	  DESCRIPTION
        "
        Load Configuration Tables Set
         Nb 2 :When set this OID enables
        loading from flash configuration2
        into the PM.
        "
	  ::= { pm1008CtrlconfMgnt1 2 }



pm1008CtrlConf1Load1 OBJECT-TYPE
	  SYNTAX EkiOnOff
	  MAX-ACCESS read-write
	  STATUS current
	  DESCRIPTION
        "
        Load Configuration Tables Set
         Nb 1 :When set this OID enables
        loading from flash configuration1
        into the PM.
        "
	  ::= { pm1008CtrlconfMgnt1 1 }



--- *****************************************************
---     LEAF for the synth4 article
--- *****************************************************
pm1008Ctrlsynth4 OBJECT IDENTIFIER ::= { pm1008CtrlOther 4 }




pm1008CtrlCorrelatOff OBJECT-TYPE
	  SYNTAX EkiOnOff
	  MAX-ACCESS read-write
	  STATUS current
	  DESCRIPTION
        "
        Disable Alarm Correlation :This
        OID disables the alarm correlation
        in the PM.
        "
	  ::= { pm1008Ctrlsynth4 2 }



pm1008CtrlCorrelatOn OBJECT-TYPE
	  SYNTAX EkiOnOff
	  MAX-ACCESS read-write
	  STATUS current
	  DESCRIPTION
        "
        Enable Alarm Correlation :This
        OID enables the alarm correlation
        in the PM.
        "
	  ::= { pm1008Ctrlsynth4 1 }



--- *****************************************************
---     LEAF for the swMgnt article
--- *****************************************************
pm1008CtrlswMgnt OBJECT IDENTIFIER ::= { pm1008CtrlOther 5 }




pm1008CtrlLoadSwBank2 OBJECT-TYPE
	  SYNTAX EkiOnOff
	  MAX-ACCESS read-write
	  STATUS current
	  DESCRIPTION
        "
        Set Software Nb 2 As Active :This
        OID, when set, loads the SW from
        bank2 into the PM. It must be followed
        by a reset.  <Help>  This controls
        selects the second SW bank as the
        active bank for the next module
        reset
        "
	  ::= { pm1008CtrlswMgnt 6 }



pm1008CtrlLoadSwBank1 OBJECT-TYPE
	  SYNTAX EkiOnOff
	  MAX-ACCESS read-write
	  STATUS current
	  DESCRIPTION
        "
        Set Software Nb 1 As Active :This
        OID, when set, loads the SW from
        bank1 into the PM. It must be followed
        by a reset.  <Help>  This controls
        selects the first SW bank as the
        active bank for the next module
        reset
        "
	  ::= { pm1008CtrlswMgnt 5 }



pm1008CtrlWarmReset OBJECT-TYPE
	  SYNTAX EkiOnOff
	  MAX-ACCESS read-write
	  STATUS current
	  DESCRIPTION
        "
        PM Warm Reset :This OID, when
         set, causes a warm reset of the
        PM. This reset is not traffic affecting,
        and the configuration of PM remains
        unchanged.  <Help>  This control
        initiates a warm reset of the module.
        "
	  ::= { pm1008CtrlswMgnt 3 }



pm1008CtrlColdReset OBJECT-TYPE
	  SYNTAX EkiOnOff
	  MAX-ACCESS read-write
	  STATUS current
	  DESCRIPTION
        "
        PM Cold Reset :This OID, when
         set, causes a cold reset of the
        PM. This reset is traffic affecting,
        and the configuration of PM is
         reloaded on start-up.  <Help>
          This control initiates a cold
        reset of the module.
        "
	  ::= { pm1008CtrlswMgnt 2 }



--- *****************************************************
---     LEAF for the gwMgnt article
--- *****************************************************
pm1008CtrlgwMgnt OBJECT IDENTIFIER ::= { pm1008CtrlOther 6 }




pm1008CtrlLoadGwBank4 OBJECT-TYPE
	  SYNTAX EkiOnOff
	  MAX-ACCESS read-write
	  STATUS current
	  DESCRIPTION
        "
        Set Gateware Nb 4 As Active :This
        OID, when set, loads the GW from
        bank4 (Flash) into the PM. It is
        followed by an automatic gateware
        cold reset.
        "
	  ::= { pm1008CtrlgwMgnt 8 }



pm1008CtrlLoadGwBank3 OBJECT-TYPE
	  SYNTAX EkiOnOff
	  MAX-ACCESS read-write
	  STATUS current
	  DESCRIPTION
        "
        Set Gateware Nb 3 As Active :This
        OID, when set, loads the GW from
        bank3 (Flash) into the PM. It is
        followed by an automatic gateware
        cold reset.  <Help>  This controls
        initiates a cold reset of the module
        and select the third GW bank as
        the active bank
        "
	  ::= { pm1008CtrlgwMgnt 7 }



pm1008CtrlLoadGwBank2 OBJECT-TYPE
	  SYNTAX EkiOnOff
	  MAX-ACCESS read-write
	  STATUS current
	  DESCRIPTION
        "
        Set Gateware Nb 2 As Active :This
        OID, when set, loads the GW from
        bank2 (Flash) into the PM. It is
        followed by an automatic gateware
        cold reset.
        "
	  ::= { pm1008CtrlgwMgnt 6 }



pm1008CtrlLoadGwBank1 OBJECT-TYPE
	  SYNTAX EkiOnOff
	  MAX-ACCESS read-write
	  STATUS current
	  DESCRIPTION
        "
        Set Gateware Nb 1 As Active :This
        OID, when set, loads the GW from
        bank1 (Flash) into the PM. It is
        followed by an automatic gateware
        cold reset.  <Help>  This controls
        initiates a cold reset of the module
        and select the first GW bank as
        the active bank
        "
	  ::= { pm1008CtrlgwMgnt 5 }



pm1008CtrlCurrentGwReset OBJECT-TYPE
	  SYNTAX EkiOnOff
	  MAX-ACCESS read-write
	  STATUS current
	  DESCRIPTION
        "
        Active Gateware Reset :This OID,
        when set, resets the active gateware.
        It is traffic affecting.
        "
	  ::= { pm1008CtrlgwMgnt 1 }



--- *********************************************************
---     TABLE for the pm1008CtrlaccessLoop articles
--- *********************************************************

pm1008CtrlaccessLoopTable OBJECT-TYPE
	SYNTAX  SEQUENCE OF Pm1008CtrlaccessLoopEntry
	MAX-ACCESS not-accessible
	STATUS current
	DESCRIPTION
        "
        List of pm1008CtrlaccessLoop Article
        "
	::= { pm1008CtrlClient 16 }


pm1008CtrlaccessLoopEntry OBJECT-TYPE
	SYNTAX Pm1008CtrlaccessLoopEntry
	MAX-ACCESS not-accessible
	STATUS current
	DESCRIPTION
        "
        Row definition for the pm1008CtrlaccessLoop
        table
        "
	INDEX   { pm1008CtrlaccessLoopIndex }
	::= { pm1008CtrlaccessLoopTable 1 }


Pm1008CtrlaccessLoopEntry ::=
	SEQUENCE {
	pm1008CtrlaccessLoopIndex
		INTEGER,
	pm1008CtrlaccessLoopPortn
		EkiState
	}


pm1008CtrlaccessLoopIndex OBJECT-TYPE
	SYNTAX  INTEGER(0..128)
	MAX-ACCESS  read-only
	STATUS current
	DESCRIPTION
        "
        Index definition for the pm1008CtrlaccessLoop
        table
        "
	::= { pm1008CtrlaccessLoopEntry 1 }


pm1008CtrlaccessLoopPortn OBJECT-TYPE
	SYNTAX  EkiState
	MAX-ACCESS read-write
	STATUS current
	DESCRIPTION
        "
        Client Facility Loopback :This
        OID operates a Client Facility
         Loopback, looping client input
        signal on the client output port.
        The loop is located on the client
        transceiver  <Help> This maintenance
        parameter operates a Client Facility
        Loopback, looping client input
         signal on the client output port.
        The loop is located on the client
        transceiver
        "
	::= { pm1008CtrlaccessLoopEntry 2 }


--- *********************************************************
---     TABLE for the pm1008CtrlportOosMode articles
--- *********************************************************

pm1008CtrlportOosModeTable OBJECT-TYPE
	SYNTAX  SEQUENCE OF Pm1008CtrlportOosModeEntry
	MAX-ACCESS not-accessible
	STATUS current
	DESCRIPTION
        "
        List of pm1008CtrlportOosMode
         Article
        "
	::= { pm1008CtrlClient 18 }


pm1008CtrlportOosModeEntry OBJECT-TYPE
	SYNTAX Pm1008CtrlportOosModeEntry
	MAX-ACCESS not-accessible
	STATUS current
	DESCRIPTION
        "
        Row definition for the pm1008CtrlportOosMode
        table
        "
	INDEX   { pm1008CtrlportOosModeIndex }
	::= { pm1008CtrlportOosModeTable 1 }


Pm1008CtrlportOosModeEntry ::=
	SEQUENCE {
	pm1008CtrlportOosModeIndex
		INTEGER,
	pm1008CtrlportOosModePortn
		EkiState
	}


pm1008CtrlportOosModeIndex OBJECT-TYPE
	SYNTAX  INTEGER(0..128)
	MAX-ACCESS  read-only
	STATUS current
	DESCRIPTION
        "
        Index definition for the pm1008CtrlportOosMode
        table
        "
	::= { pm1008CtrlportOosModeEntry 1 }


pm1008CtrlportOosModePortn OBJECT-TYPE
	SYNTAX  EkiState
	MAX-ACCESS read-write
	STATUS current
	DESCRIPTION
        "
        Client Port Out Of Service :This
        OID sets the client port Out Of
        Service  <Help>  This controls
         defines the service state of the
        client port
        "
	::= { pm1008CtrlportOosModeEntry 2 }


--- *********************************************************
---     TABLE for the pm1008CtrlsfpOnCtrl articles
--- *********************************************************

pm1008CtrlsfpOnCtrlTable OBJECT-TYPE
	SYNTAX  SEQUENCE OF Pm1008CtrlsfpOnCtrlEntry
	MAX-ACCESS not-accessible
	STATUS current
	DESCRIPTION
        "
        List of pm1008CtrlsfpOnCtrl Article
        "
	::= { pm1008CtrlClient 19 }


pm1008CtrlsfpOnCtrlEntry OBJECT-TYPE
	SYNTAX Pm1008CtrlsfpOnCtrlEntry
	MAX-ACCESS not-accessible
	STATUS current
	DESCRIPTION
        "
        Row definition for the pm1008CtrlsfpOnCtrl
        table
        "
	INDEX   { pm1008CtrlsfpOnCtrlIndex }
	::= { pm1008CtrlsfpOnCtrlTable 1 }


Pm1008CtrlsfpOnCtrlEntry ::=
	SEQUENCE {
	pm1008CtrlsfpOnCtrlIndex
		INTEGER,
	pm1008CtrlsfpOnCtrlPortn
		EkiState
	}


pm1008CtrlsfpOnCtrlIndex OBJECT-TYPE
	SYNTAX  INTEGER(0..128)
	MAX-ACCESS  read-only
	STATUS current
	DESCRIPTION
        "
        Index definition for the pm1008CtrlsfpOnCtrl
        table
        "
	::= { pm1008CtrlsfpOnCtrlEntry 1 }


pm1008CtrlsfpOnCtrlPortn OBJECT-TYPE
	SYNTAX  EkiState
	MAX-ACCESS read-write
	STATUS current
	DESCRIPTION
        "
        Client SFP Optical Laser ON :This
        OID switches on the SFP.
        "
	::= { pm1008CtrlsfpOnCtrlEntry 2 }


--- *********************************************************
---     TABLE for the pm1008CtrlsfpOffCtrl articles
--- *********************************************************

pm1008CtrlsfpOffCtrlTable OBJECT-TYPE
	SYNTAX  SEQUENCE OF Pm1008CtrlsfpOffCtrlEntry
	MAX-ACCESS not-accessible
	STATUS current
	DESCRIPTION
        "
        List of pm1008CtrlsfpOffCtrl Article
        "
	::= { pm1008CtrlClient 20 }


pm1008CtrlsfpOffCtrlEntry OBJECT-TYPE
	SYNTAX Pm1008CtrlsfpOffCtrlEntry
	MAX-ACCESS not-accessible
	STATUS current
	DESCRIPTION
        "
        Row definition for the pm1008CtrlsfpOffCtrl
        table
        "
	INDEX   { pm1008CtrlsfpOffCtrlIndex }
	::= { pm1008CtrlsfpOffCtrlTable 1 }


Pm1008CtrlsfpOffCtrlEntry ::=
	SEQUENCE {
	pm1008CtrlsfpOffCtrlIndex
		INTEGER,
	pm1008CtrlsfpOffCtrlPortn
		EkiState
	}


pm1008CtrlsfpOffCtrlIndex OBJECT-TYPE
	SYNTAX  INTEGER(0..128)
	MAX-ACCESS  read-only
	STATUS current
	DESCRIPTION
        "
        Index definition for the pm1008CtrlsfpOffCtrl
        table
        "
	::= { pm1008CtrlsfpOffCtrlEntry 1 }


pm1008CtrlsfpOffCtrlPortn OBJECT-TYPE
	SYNTAX  EkiState
	MAX-ACCESS read-write
	STATUS current
	DESCRIPTION
        "
        Client SFP Laser Shutdown :This
        OID switches off the SFP.  <Help>
         This control defines the laser
        state of the client transceiver
        "
	::= { pm1008CtrlsfpOffCtrlEntry 2 }


--- *********************************************************
---     TABLE for the pm1008CtrlcsfUpIns articles
--- *********************************************************

pm1008CtrlcsfUpInsTable OBJECT-TYPE
	SYNTAX  SEQUENCE OF Pm1008CtrlcsfUpInsEntry
	MAX-ACCESS not-accessible
	STATUS current
	DESCRIPTION
        "
        List of pm1008CtrlcsfUpIns Article
        "
	::= { pm1008CtrlClient 21 }


pm1008CtrlcsfUpInsEntry OBJECT-TYPE
	SYNTAX Pm1008CtrlcsfUpInsEntry
	MAX-ACCESS not-accessible
	STATUS current
	DESCRIPTION
        "
        Row definition for the pm1008CtrlcsfUpIns
        table
        "
	INDEX   { pm1008CtrlcsfUpInsIndex }
	::= { pm1008CtrlcsfUpInsTable 1 }


Pm1008CtrlcsfUpInsEntry ::=
	SEQUENCE {
	pm1008CtrlcsfUpInsIndex
		INTEGER,
	pm1008CtrlcsfUpInsPortn
		EkiState
	}


pm1008CtrlcsfUpInsIndex OBJECT-TYPE
	SYNTAX  INTEGER(0..128)
	MAX-ACCESS  read-only
	STATUS current
	DESCRIPTION
        "
        Index definition for the pm1008CtrlcsfUpIns
        table
        "
	::= { pm1008CtrlcsfUpInsEntry 1 }


pm1008CtrlcsfUpInsPortn OBJECT-TYPE
	SYNTAX  EkiState
	MAX-ACCESS read-write
	STATUS current
	DESCRIPTION
        "
        Client Signal Fail Insertion :This
        OID, when set, inserts  a client
        signal fail in the upstream client
        Port.  <Help>  This control inserts
        a Client Signal Fail for the client
        port
        "
	::= { pm1008CtrlcsfUpInsEntry 2 }


--- *********************************************************
---     TABLE for the pm1008CtrlcaisDwIns articles
--- *********************************************************

pm1008CtrlcaisDwInsTable OBJECT-TYPE
	SYNTAX  SEQUENCE OF Pm1008CtrlcaisDwInsEntry
	MAX-ACCESS not-accessible
	STATUS current
	DESCRIPTION
        "
        List of pm1008CtrlcaisDwIns Article
        "
	::= { pm1008CtrlClient 22 }


pm1008CtrlcaisDwInsEntry OBJECT-TYPE
	SYNTAX Pm1008CtrlcaisDwInsEntry
	MAX-ACCESS not-accessible
	STATUS current
	DESCRIPTION
        "
        Row definition for the pm1008CtrlcaisDwIns
        table
        "
	INDEX   { pm1008CtrlcaisDwInsIndex }
	::= { pm1008CtrlcaisDwInsTable 1 }


Pm1008CtrlcaisDwInsEntry ::=
	SEQUENCE {
	pm1008CtrlcaisDwInsIndex
		INTEGER,
	pm1008CtrlcaisDwInsPortn
		EkiState
	}


pm1008CtrlcaisDwInsIndex OBJECT-TYPE
	SYNTAX  INTEGER(0..128)
	MAX-ACCESS  read-only
	STATUS current
	DESCRIPTION
        "
        Index definition for the pm1008CtrlcaisDwIns
        table
        "
	::= { pm1008CtrlcaisDwInsEntry 1 }


pm1008CtrlcaisDwInsPortn OBJECT-TYPE
	SYNTAX  EkiState
	MAX-ACCESS read-write
	STATUS current
	DESCRIPTION
        "
        Client AIS Insertion :This OID,
        when set, inserts a client AIS
         on the downstream client Port.
         <Help>  This control inserts a
        Client AIS for the client port
        "
	::= { pm1008CtrlcaisDwInsEntry 2 }


--- *********************************************************
---     TABLE for the pm1008CtrlflowControl articles
--- *********************************************************

pm1008CtrlflowControlTable OBJECT-TYPE
	SYNTAX  SEQUENCE OF Pm1008CtrlflowControlEntry
	MAX-ACCESS not-accessible
	STATUS current
	DESCRIPTION
        "
        List of pm1008CtrlflowControl
         Article
        "
	::= { pm1008CtrlClient 23 }


pm1008CtrlflowControlEntry OBJECT-TYPE
	SYNTAX Pm1008CtrlflowControlEntry
	MAX-ACCESS not-accessible
	STATUS current
	DESCRIPTION
        "
        Row definition for the pm1008CtrlflowControl
        table
        "
	INDEX   { pm1008CtrlflowControlIndex }
	::= { pm1008CtrlflowControlTable 1 }


Pm1008CtrlflowControlEntry ::=
	SEQUENCE {
	pm1008CtrlflowControlIndex
		INTEGER,
	pm1008CtrlflowControlPortn
		EkiState
	}


pm1008CtrlflowControlIndex OBJECT-TYPE
	SYNTAX  INTEGER(0..128)
	MAX-ACCESS  read-only
	STATUS current
	DESCRIPTION
        "
        Index definition for the pm1008CtrlflowControl
        table
        "
	::= { pm1008CtrlflowControlEntry 1 }


pm1008CtrlflowControlPortn OBJECT-TYPE
	SYNTAX  EkiState
	MAX-ACCESS read-write
	STATUS current
	DESCRIPTION
        "
        Flow Control Assertion :This OID,
        when set, asserts a Pause Frame
        management on the client Port
        "
	::= { pm1008CtrlflowControlEntry 2 }


--- *********************************************************
---     TABLE for the pm1008CtrlclientAccessTermLoop articles
--- *********************************************************

pm1008CtrlclientAccessTermLoopTable OBJECT-TYPE
	SYNTAX  SEQUENCE OF Pm1008CtrlclientAccessTermLoopEntry
	MAX-ACCESS not-accessible
	STATUS current
	DESCRIPTION
        "
        List of pm1008CtrlclientAccessTermLoop
        Article
        "
	::= { pm1008CtrlClient 26 }


pm1008CtrlclientAccessTermLoopEntry OBJECT-TYPE
	SYNTAX Pm1008CtrlclientAccessTermLoopEntry
	MAX-ACCESS not-accessible
	STATUS current
	DESCRIPTION
        "
        Row definition for the pm1008CtrlclientAccessTermLoop
        table
        "
	INDEX   { pm1008CtrlclientAccessTermLoopIndex }
	::= { pm1008CtrlclientAccessTermLoopTable 1 }


Pm1008CtrlclientAccessTermLoopEntry ::=
	SEQUENCE {
	pm1008CtrlclientAccessTermLoopIndex
		INTEGER,
	pm1008CtrlclientAccessTermLoopPortn
		EkiState
	}


pm1008CtrlclientAccessTermLoopIndex OBJECT-TYPE
	SYNTAX  INTEGER(0..128)
	MAX-ACCESS  read-only
	STATUS current
	DESCRIPTION
        "
        Index definition for the pm1008CtrlclientAccessTermLoop
        table
        "
	::= { pm1008CtrlclientAccessTermLoopEntry 1 }


pm1008CtrlclientAccessTermLoopPortn OBJECT-TYPE
	SYNTAX  EkiState
	MAX-ACCESS read-write
	STATUS current
	DESCRIPTION
        "
        Client Terminal Loopback :This
        OID operates a Client Terminal
         Loopback, looping client input
        signal on the client output port.
        The loop is located on the line
        transceiver  <Help> This maintenance
        parameter operates a Client Terminal
        Loopback, looping client input
         signal on the client output port.
        The loop is located on the line
        transceiver
        "
	::= { pm1008CtrlclientAccessTermLoopEntry 2 }


--- *********************************************************
---     TABLE for the pm1008CtrlselectMultirate articles
--- *********************************************************

pm1008CtrlselectMultirateTable OBJECT-TYPE
	SYNTAX  SEQUENCE OF Pm1008CtrlselectMultirateEntry
	MAX-ACCESS not-accessible
	STATUS current
	DESCRIPTION
        "
        List of pm1008CtrlselectMultirate
        Article
        "
	::= { pm1008CtrlClient 42 }


pm1008CtrlselectMultirateEntry OBJECT-TYPE
	SYNTAX Pm1008CtrlselectMultirateEntry
	MAX-ACCESS not-accessible
	STATUS current
	DESCRIPTION
        "
        Row definition for the pm1008CtrlselectMultirate
        table
        "
	INDEX   { pm1008CtrlselectMultirateIndex }
	::= { pm1008CtrlselectMultirateTable 1 }


Pm1008CtrlselectMultirateEntry ::=
	SEQUENCE {
	pm1008CtrlselectMultirateIndex
		INTEGER,
	pm1008CtrlselectMultiratePortn
		Pm1008MultiRate
	}


pm1008CtrlselectMultirateIndex OBJECT-TYPE
	SYNTAX  INTEGER(0..128)
	MAX-ACCESS  read-only
	STATUS current
	DESCRIPTION
        "
        Index definition for the pm1008CtrlselectMultirate
        table
        "
	::= { pm1008CtrlselectMultirateEntry 1 }


pm1008CtrlselectMultiratePortn OBJECT-TYPE
	SYNTAX  Pm1008MultiRate
	MAX-ACCESS read-write
	STATUS current
	DESCRIPTION
        "
        Input Bandwidth Limitation :This
        control defines the input bandwidth
        limitation (100 Mb/s, 250 Mb/s,
        500 Mb/s or 1Gb/s).   <Help> This
        control defines the input bandwidth
        limitation (100 Mb/s, 250 Mb/s,
        500 Mb/s or 1Gb/s
        "
	::= { pm1008CtrlselectMultirateEntry 2 }


--- *********************************************************
---     TABLE for the pm1008Ctrlprotocol articles
--- *********************************************************

pm1008CtrlprotocolTable OBJECT-TYPE
	SYNTAX  SEQUENCE OF Pm1008CtrlprotocolEntry
	MAX-ACCESS not-accessible
	STATUS current
	DESCRIPTION
        "
        List of pm1008Ctrlprotocol Article
        "
	::= { pm1008CtrlClient 48 }


pm1008CtrlprotocolEntry OBJECT-TYPE
	SYNTAX Pm1008CtrlprotocolEntry
	MAX-ACCESS not-accessible
	STATUS current
	DESCRIPTION
        "
        Row definition for the pm1008Ctrlprotocol
        table
        "
	INDEX   { pm1008CtrlprotocolIndex }
	::= { pm1008CtrlprotocolTable 1 }


Pm1008CtrlprotocolEntry ::=
	SEQUENCE {
	pm1008CtrlprotocolIndex
		INTEGER,
	pm1008CtrlprotocolPortn
		EkiProtocol
	}


pm1008CtrlprotocolIndex OBJECT-TYPE
	SYNTAX  INTEGER(0..128)
	MAX-ACCESS  read-only
	STATUS current
	DESCRIPTION
        "
        Index definition for the pm1008Ctrlprotocol
        table
        "
	::= { pm1008CtrlprotocolEntry 1 }


pm1008CtrlprotocolPortn OBJECT-TYPE
	SYNTAX  EkiProtocol
	MAX-ACCESS read-write
	STATUS current
	DESCRIPTION
        "
        Client Protocol: This OID sets
        the protocol of the Client port.
        "
	::= { pm1008CtrlprotocolEntry 2 }


--- *****************************************************
---     LEAF for the commAccessLoop article
--- *****************************************************
pm1008CtrlcommAccessLoop OBJECT IDENTIFIER ::= { pm1008CtrlLine 64 }




pm1008CtrlCommAccessloop OBJECT-TYPE
	  SYNTAX EkiOnOff
	  MAX-ACCESS read-write
	  STATUS deprecated
	  DESCRIPTION
        "
        PM Full Access Loop Mode :This
        OID, when set, puts the module
         in common access loop back, looping
        the 10 Gb/s output signal on the
        10 Gb/s input.
        "
	  ::= { pm1008CtrlcommAccessLoop 1 }



--- *****************************************************
---     LEAF for the lineLoop article
--- *****************************************************
pm1008CtrllineLoop OBJECT IDENTIFIER ::= { pm1008CtrlLine 66 }




pm1008CtrlLineLoop OBJECT-TYPE
	  SYNTAX EkiOnOff
	  MAX-ACCESS read-write
	  STATUS deprecated
	  DESCRIPTION
        "
        PM Line Loop Mode :This OID, when
        set at '1' puts the module in line
        loopback mode, looping the received
        10 Gb/s signal on the transmit
         10 Gb/s output. The Upstream part
        of the module is timed on the 10
        Gb/s recovered clock in that case.
        "
	  ::= { pm1008CtrllineLoop 1 }



--- *****************************************************
---     LEAF for the msAis article
--- *****************************************************
pm1008CtrlmsAis OBJECT IDENTIFIER ::= { pm1008CtrlLine 67 }




pm1008CtrlMsAis OBJECT-TYPE
	  SYNTAX EkiOnOff
	  MAX-ACCESS read-write
	  STATUS current
	  DESCRIPTION
        "
        Insert MS-AIS/L-AIS On Line Output
        :This OID, when set, inserts an
        MS-AIS/L-AIS in the outgoing STM-64/OC-192
        signal.
        "
	  ::= { pm1008CtrlmsAis 1 }



--- *********************************************************
---     TABLE for the pm1008CtrlfecDisable articles
--- *********************************************************

pm1008CtrlfecDisableTable OBJECT-TYPE
	SYNTAX  SEQUENCE OF Pm1008CtrlfecDisableEntry
	MAX-ACCESS not-accessible
	STATUS current
	DESCRIPTION
        "
        List of pm1008CtrlfecDisable Article
        "
	::= { pm1008CtrlLine 69 }


pm1008CtrlfecDisableEntry OBJECT-TYPE
	SYNTAX Pm1008CtrlfecDisableEntry
	MAX-ACCESS not-accessible
	STATUS current
	DESCRIPTION
        "
        Row definition for the pm1008CtrlfecDisable
        table
        "
	INDEX   { pm1008CtrlfecDisableIndex }
	::= { pm1008CtrlfecDisableTable 1 }


Pm1008CtrlfecDisableEntry ::=
	SEQUENCE {
	pm1008CtrlfecDisableIndex
		INTEGER,
	pm1008CtrlfecDisablePortn
		EkiState
	}


pm1008CtrlfecDisableIndex OBJECT-TYPE
	SYNTAX  INTEGER(0..128)
	MAX-ACCESS  read-only
	STATUS current
	DESCRIPTION
        "
        Index definition for the pm1008CtrlfecDisable
        table
        "
	::= { pm1008CtrlfecDisableEntry 1 }


pm1008CtrlfecDisablePortn OBJECT-TYPE
	SYNTAX  EkiState
	MAX-ACCESS read-write
	STATUS current
	DESCRIPTION
        "
        Forward Error Correction Inhibition
        :This OID, when set, inhibits the
        Forward Error Correction feature
        on the line input  <Help>  This
        control enables/disables the Forward
        Error Correction on the line interface
        "
	::= { pm1008CtrlfecDisableEntry 2 }


--- *****************************************************
---     LEAF for the protMgnt article
--- *****************************************************
pm1008CtrlProtMgnt OBJECT IDENTIFIER ::= { pm1008CtrlLine 73 }




pm1008CtrlLineNumber OBJECT-TYPE
	  SYNTAX Unsigned32 (0..3)
	  MAX-ACCESS read-write
	  STATUS current
	  DESCRIPTION
        "
        Active Line Number : This OID
         sets the active line number
        "
	  ::= { pm1008CtrlProtMgnt 1 }



pm1008CtrlProtMode OBJECT-TYPE
	  SYNTAX EkiMode
	  MAX-ACCESS read-write
	  STATUS current
	  DESCRIPTION
        "
        Line Switch Mode (Auto Or Manual)
        :This bit selects the manual (1)
        or automatic (0) switch method
          <Help>  This control defines
         the protection switch mode on
         the line interface
        "
	  ::= { pm1008CtrlProtMgnt 2 }



--- *********************************************************
---     TABLE for the pm1008CtrllineOosMode articles
--- *********************************************************

pm1008CtrllineOosModeTable OBJECT-TYPE
	SYNTAX  SEQUENCE OF Pm1008CtrllineOosModeEntry
	MAX-ACCESS not-accessible
	STATUS current
	DESCRIPTION
        "
        List of pm1008CtrllineOosMode
         Article
        "
	::= { pm1008CtrlLine 74 }


pm1008CtrllineOosModeEntry OBJECT-TYPE
	SYNTAX Pm1008CtrllineOosModeEntry
	MAX-ACCESS not-accessible
	STATUS current
	DESCRIPTION
        "
        Row definition for the pm1008CtrllineOosMode
        table
        "
	INDEX   { pm1008CtrllineOosModeIndex }
	::= { pm1008CtrllineOosModeTable 1 }


Pm1008CtrllineOosModeEntry ::=
	SEQUENCE {
	pm1008CtrllineOosModeIndex
		INTEGER,
	pm1008CtrllineOosModePortn
		EkiState
	}


pm1008CtrllineOosModeIndex OBJECT-TYPE
	SYNTAX  INTEGER(0..128)
	MAX-ACCESS  read-only
	STATUS current
	DESCRIPTION
        "
        Index definition for the pm1008CtrllineOosMode
        table
        "
	::= { pm1008CtrllineOosModeEntry 1 }


pm1008CtrllineOosModePortn OBJECT-TYPE
	SYNTAX  EkiState
	MAX-ACCESS read-write
	STATUS current
	DESCRIPTION
        "
        Line Port Out Of Service :This
        OID sets the line port Out Of Service
         <Help>  This control defines the
        service state of the line port
        "
	::= { pm1008CtrllineOosModeEntry 2 }


--- *****************************************************
---     LEAF for the ledTest article
--- *****************************************************
pm1008CtrlledTest OBJECT IDENTIFIER ::= { pm1008CtrlOther 192 }




pm1008CtrlLedOff OBJECT-TYPE
	  SYNTAX EkiOnOff
	  MAX-ACCESS read-write
	  STATUS current
	  DESCRIPTION
        "
        Leds Off :This OID switches off
        all the Leds as a test feature.
         <Help>  This control initiates
        a test leds turning all the LEDs
        to OFF
        "
	  ::= { pm1008CtrlledTest 3 }



pm1008CtrlRedLed OBJECT-TYPE
	  SYNTAX EkiOnOff
	  MAX-ACCESS read-write
	  STATUS current
	  DESCRIPTION
        "
        Red Leds Test :This OID switches
        on all the red Leds as a test feature.
         <Help>  This control initiates
        a test leds turning all the LEDs
        to red
        "
	  ::= { pm1008CtrlledTest 2 }



pm1008CtrlGreenLed OBJECT-TYPE
	  SYNTAX EkiOnOff
	  MAX-ACCESS read-write
	  STATUS current
	  DESCRIPTION
        "
        Green Leds Test :This OID switches
        on all the green Leds as a test
        feature.  <Help>  This control
         initiates a test leds turning
         all the LEDs to green
        "
	  ::= { pm1008CtrlledTest 1 }



--- *****************************************************
---     LEAF for the moduleOosMode article
--- *****************************************************
pm1008CtrlmoduleOosMode OBJECT IDENTIFIER ::= { pm1008CtrlOther 193 }




pm1008CtrlModuleOosMode OBJECT-TYPE
	  SYNTAX EkiOnOff
	  MAX-ACCESS read-write
	  STATUS current
	  DESCRIPTION
        "
        PM Out Of Service :This OID sets
        the PM Out Of Service  <Help>
         This control defines the service
        state of the complete module
        "
	  ::= { pm1008CtrlmoduleOosMode 1 }



--- *****************************************************
---     LEAF for the maintenanceMode article
--- *****************************************************
pm1008CtrlmaintenanceMode OBJECT IDENTIFIER ::= { pm1008CtrlOther 197 }




pm1008CtrlMaintenanceMode OBJECT-TYPE
	  SYNTAX EkiOnOff
	  MAX-ACCESS read-write
	  STATUS current
	  DESCRIPTION
        "
        Module Maintenance Mode :This
         OID enables the maintenance mode
        on the PM.  <Help>   This control
        enables the maintenance mode on
        the PM.
        "
	  ::= { pm1008CtrlmaintenanceMode 1 }



--- *****************************************************
---     LEAF for the dccEnable article
--- *****************************************************
pm1008CtrldccEnable OBJECT IDENTIFIER ::= { pm1008CtrlOther 198 }




pm1008CtrlDccEnable OBJECT-TYPE
	  SYNTAX EkiOnOff
	  MAX-ACCESS read-write
	  STATUS current
	  DESCRIPTION
        "
        DCC Enable :This OID enables the
        DCC mode on the PM   <Help>   This
        control enables the DCC mode on
        the PM
        "
	  ::= { pm1008CtrldccEnable 1 }



--- *********************************************************
---     TABLE for the pm1008CtrlxfpOnoff articles
--- *********************************************************

pm1008CtrlxfpOnoffTable OBJECT-TYPE
	SYNTAX  SEQUENCE OF Pm1008CtrlxfpOnoffEntry
	MAX-ACCESS not-accessible
	STATUS current
	DESCRIPTION
        "
        List of pm1008CtrlxfpOnoff Article
        "
	::= { pm1008CtrlLine 208 }


pm1008CtrlxfpOnoffEntry OBJECT-TYPE
	SYNTAX Pm1008CtrlxfpOnoffEntry
	MAX-ACCESS not-accessible
	STATUS current
	DESCRIPTION
        "
        Row definition for the pm1008CtrlxfpOnoff
        table
        "
	INDEX   { pm1008CtrlxfpOnoffIndex }
	::= { pm1008CtrlxfpOnoffTable 1 }


Pm1008CtrlxfpOnoffEntry ::=
	SEQUENCE {
	pm1008CtrlxfpOnoffIndex
		INTEGER,
	pm1008CtrlxfpOnoffPortn
		EkiState
	}


pm1008CtrlxfpOnoffIndex OBJECT-TYPE
	SYNTAX  INTEGER(0..128)
	MAX-ACCESS  read-only
	STATUS current
	DESCRIPTION
        "
        Index definition for the pm1008CtrlxfpOnoff
        table
        "
	::= { pm1008CtrlxfpOnoffEntry 1 }


pm1008CtrlxfpOnoffPortn OBJECT-TYPE
	SYNTAX  EkiState
	MAX-ACCESS read-write
	STATUS current
	DESCRIPTION
        "
        Line Optical Laser Shutdown :This
        OID switches off the XFP or the
        OTX  <Help>  This control defines
        the laser state of the line transceiver
        "
	::= { pm1008CtrlxfpOnoffEntry 2 }


--- *********************************************************
---     TABLE for the pm1008CtrlxfpLineLoop articles
--- *********************************************************

pm1008CtrlxfpLineLoopTable OBJECT-TYPE
	SYNTAX  SEQUENCE OF Pm1008CtrlxfpLineLoopEntry
	MAX-ACCESS not-accessible
	STATUS current
	DESCRIPTION
        "
        List of pm1008CtrlxfpLineLoop
         Article
        "
	::= { pm1008CtrlLine 209 }


pm1008CtrlxfpLineLoopEntry OBJECT-TYPE
	SYNTAX Pm1008CtrlxfpLineLoopEntry
	MAX-ACCESS not-accessible
	STATUS current
	DESCRIPTION
        "
        Row definition for the pm1008CtrlxfpLineLoop
        table
        "
	INDEX   { pm1008CtrlxfpLineLoopIndex }
	::= { pm1008CtrlxfpLineLoopTable 1 }


Pm1008CtrlxfpLineLoopEntry ::=
	SEQUENCE {
	pm1008CtrlxfpLineLoopIndex
		INTEGER,
	pm1008CtrlxfpLineLoopPortn
		EkiState
	}


pm1008CtrlxfpLineLoopIndex OBJECT-TYPE
	SYNTAX  INTEGER(0..128)
	MAX-ACCESS  read-only
	STATUS current
	DESCRIPTION
        "
        Index definition for the pm1008CtrlxfpLineLoop
        table
        "
	::= { pm1008CtrlxfpLineLoopEntry 1 }


pm1008CtrlxfpLineLoopPortn OBJECT-TYPE
	SYNTAX  EkiState
	MAX-ACCESS read-write
	STATUS current
	DESCRIPTION
        "
        Line Facility Loopback :This OID
        operates a Line Facility Loopback,
        looping line input signal on the
        line output port. The loop is located
        on the line transceiver. If the
        Line signal carries DCC, the management
        network is impacted  <Help> This
        maintenance parameter operates
         a Line Facility Loopback, looping
        line input signal on the line output
        port. The loop is located on the
        line transceiver. If the Line signal
        carries DCC, the management network
        is impacted
        "
	::= { pm1008CtrlxfpLineLoopEntry 2 }


--- *********************************************************
---     TABLE for the pm1008CtrlxfpXfiLoop articles
--- *********************************************************

pm1008CtrlxfpXfiLoopTable OBJECT-TYPE
	SYNTAX  SEQUENCE OF Pm1008CtrlxfpXfiLoopEntry
	MAX-ACCESS not-accessible
	STATUS current
	DESCRIPTION
        "
        List of pm1008CtrlxfpXfiLoop Article
        "
	::= { pm1008CtrlLine 210 }


pm1008CtrlxfpXfiLoopEntry OBJECT-TYPE
	SYNTAX Pm1008CtrlxfpXfiLoopEntry
	MAX-ACCESS not-accessible
	STATUS current
	DESCRIPTION
        "
        Row definition for the pm1008CtrlxfpXfiLoop
        table
        "
	INDEX   { pm1008CtrlxfpXfiLoopIndex }
	::= { pm1008CtrlxfpXfiLoopTable 1 }


Pm1008CtrlxfpXfiLoopEntry ::=
	SEQUENCE {
	pm1008CtrlxfpXfiLoopIndex
		INTEGER,
	pm1008CtrlxfpXfiLoopPortn
		EkiState
	}


pm1008CtrlxfpXfiLoopIndex OBJECT-TYPE
	SYNTAX  INTEGER(0..128)
	MAX-ACCESS  read-only
	STATUS current
	DESCRIPTION
        "
        Index definition for the pm1008CtrlxfpXfiLoop
        table
        "
	::= { pm1008CtrlxfpXfiLoopEntry 1 }


pm1008CtrlxfpXfiLoopPortn OBJECT-TYPE
	SYNTAX  EkiState
	MAX-ACCESS read-write
	STATUS current
	DESCRIPTION
        "
        Line Terminal Loopback :This OID
        operates a Line Terminal Loopback,
        looping line input signal on the
        line output port. The loop is located
        on all client transceivers  <Help>
        This maintenance parameter operates
        a Line Terminal Loopback, looping
        line input signal on the line output
        port. The loop is located on all
        client transceivers.
        "
	::= { pm1008CtrlxfpXfiLoopEntry 2 }


--- *********************************************************
---     TABLE for the pm1008CtrllineTunableChannel articles
--- *********************************************************

pm1008CtrllineTunableChannelTable OBJECT-TYPE
	SYNTAX  SEQUENCE OF Pm1008CtrllineTunableChannelEntry
	MAX-ACCESS not-accessible
	STATUS current
	DESCRIPTION
        "
        List of pm1008CtrllineTunableChannel
        Article
        "
	::= { pm1008CtrlLine 212 }


pm1008CtrllineTunableChannelEntry OBJECT-TYPE
	SYNTAX Pm1008CtrllineTunableChannelEntry
	MAX-ACCESS not-accessible
	STATUS current
	DESCRIPTION
        "
        Row definition for the pm1008CtrllineTunableChannel
        table
        "
	INDEX   { pm1008CtrllineTunableChannelIndex }
	::= { pm1008CtrllineTunableChannelTable 1 }


Pm1008CtrllineTunableChannelEntry ::=
	SEQUENCE {
	pm1008CtrllineTunableChannelIndex
		INTEGER,
	pm1008CtrllineTunableChannelPortn
		Pm1008OtxChannel
	}


pm1008CtrllineTunableChannelIndex OBJECT-TYPE
	SYNTAX  INTEGER(0..128)
	MAX-ACCESS  read-only
	STATUS current
	DESCRIPTION
        "
        Index definition for the pm1008CtrllineTunableChannel
        table
        "
	::= { pm1008CtrllineTunableChannelEntry 1 }


pm1008CtrllineTunableChannelPortn OBJECT-TYPE
	SYNTAX  Pm1008OtxChannel
	MAX-ACCESS read-write
	STATUS current
	DESCRIPTION
        "
        ITU Channel :This OID selects
         the ITU channel of the Line OTX
        TLH Laser  <Help>   This control
        defines the ITU channel of the
         Line OTX TLH Laser
        "
	::= { pm1008CtrllineTunableChannelEntry 2 }


--- *********************************************************
---     TABLE for the pm1008CtrllinePhotodiodeMode articles
--- *********************************************************

pm1008CtrllinePhotodiodeModeTable OBJECT-TYPE
	SYNTAX  SEQUENCE OF Pm1008CtrllinePhotodiodeModeEntry
	MAX-ACCESS not-accessible
	STATUS current
	DESCRIPTION
        "
        List of pm1008CtrllinePhotodiodeMode
        Article
        "
	::= { pm1008CtrlLine 213 }


pm1008CtrllinePhotodiodeModeEntry OBJECT-TYPE
	SYNTAX Pm1008CtrllinePhotodiodeModeEntry
	MAX-ACCESS not-accessible
	STATUS current
	DESCRIPTION
        "
        Row definition for the pm1008CtrllinePhotodiodeMode
        table
        "
	INDEX   { pm1008CtrllinePhotodiodeModeIndex }
	::= { pm1008CtrllinePhotodiodeModeTable 1 }


Pm1008CtrllinePhotodiodeModeEntry ::=
	SEQUENCE {
	pm1008CtrllinePhotodiodeModeIndex
		INTEGER,
	pm1008CtrllinePhotodiodeModePortn
		Pm1008OtxMode
	}


pm1008CtrllinePhotodiodeModeIndex OBJECT-TYPE
	SYNTAX  INTEGER(0..128)
	MAX-ACCESS  read-only
	STATUS current
	DESCRIPTION
        "
        Index definition for the pm1008CtrllinePhotodiodeMode
        table
        "
	::= { pm1008CtrllinePhotodiodeModeEntry 1 }


pm1008CtrllinePhotodiodeModePortn OBJECT-TYPE
	SYNTAX  Pm1008OtxMode
	MAX-ACCESS read-write
	STATUS current
	DESCRIPTION
        "
        OTX TLH Rx Sens. Mode :This OID
        defines the Rx sensiblity mode
         of the Line OTX TLH  <Help>
         This control defines the receiver
        sensibility mode of the Line OTX
        TLH Laser (OTX60, OTX80 or Custom)
        "
	::= { pm1008CtrllinePhotodiodeModeEntry 2 }


--- *********************************************************
---     TABLE for the pm1008CtrllinePhotodiodeValue articles
--- *********************************************************

pm1008CtrllinePhotodiodeValueTable OBJECT-TYPE
	SYNTAX  SEQUENCE OF Pm1008CtrllinePhotodiodeValueEntry
	MAX-ACCESS not-accessible
	STATUS current
	DESCRIPTION
        "
        List of pm1008CtrllinePhotodiodeValue
        Article
        "
	::= { pm1008CtrlLine 214 }


pm1008CtrllinePhotodiodeValueEntry OBJECT-TYPE
	SYNTAX Pm1008CtrllinePhotodiodeValueEntry
	MAX-ACCESS not-accessible
	STATUS current
	DESCRIPTION
        "
        Row definition for the pm1008CtrllinePhotodiodeValue
        table
        "
	INDEX   { pm1008CtrllinePhotodiodeValueIndex }
	::= { pm1008CtrllinePhotodiodeValueTable 1 }


Pm1008CtrllinePhotodiodeValueEntry ::=
	SEQUENCE {
	pm1008CtrllinePhotodiodeValueIndex
		INTEGER,
	pm1008CtrllinePhotodiodeValuePortn
		Pm1008AdjustValue
	}


pm1008CtrllinePhotodiodeValueIndex OBJECT-TYPE
	SYNTAX  INTEGER(0..128)
	MAX-ACCESS  read-only
	STATUS current
	DESCRIPTION
        "
        Index definition for the pm1008CtrllinePhotodiodeValue
        table
        "
	::= { pm1008CtrllinePhotodiodeValueEntry 1 }


pm1008CtrllinePhotodiodeValuePortn OBJECT-TYPE
	SYNTAX  Pm1008AdjustValue
	MAX-ACCESS read-write
	STATUS current
	DESCRIPTION
        "
        OTX TLH Rx Sensibility :This OID
        sets the Rx sensibility of the
         Line OTX TLH (custom mode only)
         <Help>   This control defines
         the receiver sensibility value
        (only in Custom mode) of the Line
        OTX TLH Laser
        "
	::= { pm1008CtrllinePhotodiodeValueEntry 2 }


--- *********************************************************
---     TABLE for the pm1008CtrllinePowerLaser articles
--- *********************************************************

pm1008CtrllinePowerLaserTable OBJECT-TYPE
	SYNTAX  SEQUENCE OF Pm1008CtrllinePowerLaserEntry
	MAX-ACCESS not-accessible
	STATUS current
	DESCRIPTION
        "
        List of pm1008CtrllinePowerLaser
        Article
        "
	::= { pm1008CtrlLine 215 }


pm1008CtrllinePowerLaserEntry OBJECT-TYPE
	SYNTAX Pm1008CtrllinePowerLaserEntry
	MAX-ACCESS not-accessible
	STATUS current
	DESCRIPTION
        "
        Row definition for the pm1008CtrllinePowerLaser
        table
        "
	INDEX   { pm1008CtrllinePowerLaserIndex }
	::= { pm1008CtrllinePowerLaserTable 1 }


Pm1008CtrllinePowerLaserEntry ::=
	SEQUENCE {
	pm1008CtrllinePowerLaserIndex
		INTEGER,
	pm1008CtrllinePowerLaserPortn
		INTEGER
	}


pm1008CtrllinePowerLaserIndex OBJECT-TYPE
	SYNTAX  INTEGER(0..128)
	MAX-ACCESS  read-only
	STATUS current
	DESCRIPTION
        "
        Index definition for the pm1008CtrllinePowerLaser
        table
        "
	::= { pm1008CtrllinePowerLaserEntry 1 }


pm1008CtrllinePowerLaserPortn OBJECT-TYPE
	SYNTAX  INTEGER (0..255)
	MAX-ACCESS read-write
	STATUS current
	DESCRIPTION
        "
        Line Laser Output Power [3-5]
         :This OID sets the output power
        value on the laser of the Line
         OTX TLH (AV=Power*10+158) (Unit
        = dBm)  <Help>   This control defines
        the start-up output power of the
        Line OTX TLH
        "
	::= { pm1008CtrllinePowerLaserEntry 2 }







--- *****************************************************
--- $$$$$$$$$$$$$$$$$$$$$$$$$$$$$$$$$$$$$$$$$$$$$$$$$$$$$
---     COUNTERS
--- $$$$$$$$$$$$$$$$$$$$$$$$$$$$$$$$$$$$$$$$$$$$$$$$$$$$$
--- *****************************************************



--- *********************************************************
---     TABLE for the pm1008CntupRaRemCnt articles
--- *********************************************************

pm1008CntupRaRemCntTable OBJECT-TYPE
	SYNTAX  SEQUENCE OF Pm1008CntupRaRemCntEntry
	MAX-ACCESS not-accessible
	STATUS current
	DESCRIPTION
        "
        List of pm1008CntupRaRemCnt Article
        "
	::= { pm1008CntClient 16 }


pm1008CntupRaRemCntEntry OBJECT-TYPE
	SYNTAX Pm1008CntupRaRemCntEntry
	MAX-ACCESS not-accessible
	STATUS current
	DESCRIPTION
        "
        Row definition for the pm1008CntupRaRemCnt
        table
        "
	INDEX   { pm1008CntupRaRemCntIndex }
	::= { pm1008CntupRaRemCntTable 1 }


Pm1008CntupRaRemCntEntry ::=
	SEQUENCE {
	pm1008CntupRaRemCntIndex
		INTEGER,
	pm1008CntupRaRemCntValuePortn
		Counter32,
	pm1008CntupRaRemCntErrorPortn
		EkiOnOff,
	pm1008CntupRaRemCntOverloadPortn
		EkiOnOff
	}


pm1008CntupRaRemCntIndex OBJECT-TYPE
	SYNTAX  INTEGER(0..128)
	MAX-ACCESS  read-only
	STATUS current
	DESCRIPTION
        "
        Index definition for the pm1008CntupRaRemCnt
        table
        "
	::= { pm1008CntupRaRemCntEntry 1 }


pm1008CntupRaRemCntValuePortn OBJECT-TYPE
	SYNTAX  Counter32
	MAX-ACCESS read-only
	STATUS current
	DESCRIPTION
        "
        Client Rate Adapt. Words Removal
        :This counter is incremented each
        time a rate adaptation 10B word
        is removed from the Client input
        stream
        "
	::= { pm1008CntupRaRemCntEntry 2 }


pm1008CntupRaRemCntErrorPortn OBJECT-TYPE
	SYNTAX  EkiOnOff
	MAX-ACCESS read-only
	STATUS current
	DESCRIPTION
        "
        Client Counter Error :This OID
        when set indicates the rate adaptation
        removal counter value is invalid
        on Port
        "
	::= { pm1008CntupRaRemCntEntry 3 }


pm1008CntupRaRemCntOverloadPortn OBJECT-TYPE
	SYNTAX  EkiOnOff
	MAX-ACCESS read-only
	STATUS current
	DESCRIPTION
        "
        Client Counter Overload :This
         OID when set indicates a rate
         adaptation removal counter overload
        on Port
        "
	::= { pm1008CntupRaRemCntEntry 4 }


--- *********************************************************
---     TABLE for the pm1008CntupRaInsCnt articles
--- *********************************************************

pm1008CntupRaInsCntTable OBJECT-TYPE
	SYNTAX  SEQUENCE OF Pm1008CntupRaInsCntEntry
	MAX-ACCESS not-accessible
	STATUS current
	DESCRIPTION
        "
        List of pm1008CntupRaInsCnt Article
        "
	::= { pm1008CntClient 24 }


pm1008CntupRaInsCntEntry OBJECT-TYPE
	SYNTAX Pm1008CntupRaInsCntEntry
	MAX-ACCESS not-accessible
	STATUS current
	DESCRIPTION
        "
        Row definition for the pm1008CntupRaInsCnt
        table
        "
	INDEX   { pm1008CntupRaInsCntIndex }
	::= { pm1008CntupRaInsCntTable 1 }


Pm1008CntupRaInsCntEntry ::=
	SEQUENCE {
	pm1008CntupRaInsCntIndex
		INTEGER,
	pm1008CntupRaInsCntValuePortn
		Counter32,
	pm1008CntupRaInsCntErrorPortn
		EkiOnOff,
	pm1008CntupRaInsCntOverloadPortn
		EkiOnOff
	}


pm1008CntupRaInsCntIndex OBJECT-TYPE
	SYNTAX  INTEGER(0..128)
	MAX-ACCESS  read-only
	STATUS current
	DESCRIPTION
        "
        Index definition for the pm1008CntupRaInsCnt
        table
        "
	::= { pm1008CntupRaInsCntEntry 1 }


pm1008CntupRaInsCntValuePortn OBJECT-TYPE
	SYNTAX  Counter32
	MAX-ACCESS read-only
	STATUS current
	DESCRIPTION
        "
        Client Rate Adapt. Words Insertion
        :This counter is incremented each
        time a rate adaptation 10B word
        is inserted in the Client input
        stream
        "
	::= { pm1008CntupRaInsCntEntry 2 }


pm1008CntupRaInsCntErrorPortn OBJECT-TYPE
	SYNTAX  EkiOnOff
	MAX-ACCESS read-only
	STATUS current
	DESCRIPTION
        "
        Client Counter Error :This OID
        when set indicates the rate adaptation
        insertion counter value is invalid
        on Port
        "
	::= { pm1008CntupRaInsCntEntry 3 }


pm1008CntupRaInsCntOverloadPortn OBJECT-TYPE
	SYNTAX  EkiOnOff
	MAX-ACCESS read-only
	STATUS current
	DESCRIPTION
        "
        Client Counter Overload :This
         OID when set indicates a rate
         adaptation insertion counter overload
        on Port
        "
	::= { pm1008CntupRaInsCntEntry 4 }


--- *********************************************************
---     TABLE for the pm1008CntupRdErrCnt articles
--- *********************************************************

pm1008CntupRdErrCntTable OBJECT-TYPE
	SYNTAX  SEQUENCE OF Pm1008CntupRdErrCntEntry
	MAX-ACCESS not-accessible
	STATUS current
	DESCRIPTION
        "
        List of pm1008CntupRdErrCnt Article
        "
	::= { pm1008CntClient 32 }


pm1008CntupRdErrCntEntry OBJECT-TYPE
	SYNTAX Pm1008CntupRdErrCntEntry
	MAX-ACCESS not-accessible
	STATUS current
	DESCRIPTION
        "
        Row definition for the pm1008CntupRdErrCnt
        table
        "
	INDEX   { pm1008CntupRdErrCntIndex }
	::= { pm1008CntupRdErrCntTable 1 }


Pm1008CntupRdErrCntEntry ::=
	SEQUENCE {
	pm1008CntupRdErrCntIndex
		INTEGER,
	pm1008CntupRdErrCntValuePortn
		Counter32,
	pm1008CntupRdErrCntErrorPortn
		EkiOnOff,
	pm1008CntupRdErrCntOverloadPortn
		EkiOnOff
	}


pm1008CntupRdErrCntIndex OBJECT-TYPE
	SYNTAX  INTEGER(0..128)
	MAX-ACCESS  read-only
	STATUS current
	DESCRIPTION
        "
        Index definition for the pm1008CntupRdErrCnt
        table
        "
	::= { pm1008CntupRdErrCntEntry 1 }


pm1008CntupRdErrCntValuePortn OBJECT-TYPE
	SYNTAX  Counter32
	MAX-ACCESS read-only
	STATUS current
	DESCRIPTION
        "
        Client Input Errors :This counter
        is increased each time a 10b/8b
        running disparity error is detected
        on the Client input stream  <Help>
         This counter gives the number
         of 10b/8b running disparity errors
        on the client port
        "
	::= { pm1008CntupRdErrCntEntry 2 }


pm1008CntupRdErrCntErrorPortn OBJECT-TYPE
	SYNTAX  EkiOnOff
	MAX-ACCESS read-only
	STATUS current
	DESCRIPTION
        "
        Client Counter Error :This OID
        when set indicates the client error
        counter value is invalid on Port
        "
	::= { pm1008CntupRdErrCntEntry 3 }


pm1008CntupRdErrCntOverloadPortn OBJECT-TYPE
	SYNTAX  EkiOnOff
	MAX-ACCESS read-only
	STATUS current
	DESCRIPTION
        "
        Client Counter Overload :This
         OID when set indicates a client
        input error counter overload on
        Port
        "
	::= { pm1008CntupRdErrCntEntry 4 }


--- *********************************************************
---     TABLE for the pm1008CntupTimCnt articles
--- *********************************************************

pm1008CntupTimCntTable OBJECT-TYPE
	SYNTAX  SEQUENCE OF Pm1008CntupTimCntEntry
	MAX-ACCESS not-accessible
	STATUS current
	DESCRIPTION
        "
        List of pm1008CntupTimCnt Article
        "
	::= { pm1008CntClient 40 }


pm1008CntupTimCntEntry OBJECT-TYPE
	SYNTAX Pm1008CntupTimCntEntry
	MAX-ACCESS not-accessible
	STATUS current
	DESCRIPTION
        "
        Row definition for the pm1008CntupTimCnt
        table
        "
	INDEX   { pm1008CntupTimCntIndex }
	::= { pm1008CntupTimCntTable 1 }


Pm1008CntupTimCntEntry ::=
	SEQUENCE {
	pm1008CntupTimCntIndex
		INTEGER,
	pm1008CntupTimCntValuePortn
		Counter32,
	pm1008CntupTimCntErrorPortn
		EkiOnOff,
	pm1008CntupTimCntOverloadPortn
		EkiOnOff
	}


pm1008CntupTimCntIndex OBJECT-TYPE
	SYNTAX  INTEGER(0..128)
	MAX-ACCESS  read-only
	STATUS current
	DESCRIPTION
        "
        Index definition for the pm1008CntupTimCnt
        table
        "
	::= { pm1008CntupTimCntEntry 1 }


pm1008CntupTimCntValuePortn OBJECT-TYPE
	SYNTAX  Counter32
	MAX-ACCESS read-only
	STATUS current
	DESCRIPTION
        "
        Client Upstream Timer Counter
         :This is the timing counter dedicated
        to the upstream access counters.
        It is incremented every 125 us.
        "
	::= { pm1008CntupTimCntEntry 2 }


pm1008CntupTimCntErrorPortn OBJECT-TYPE
	SYNTAX  EkiOnOff
	MAX-ACCESS read-only
	STATUS current
	DESCRIPTION
        "
        Client Counter Error :This OID
        when set indicates the upstream
        timing counter value is invalid
        on Port
        "
	::= { pm1008CntupTimCntEntry 3 }


pm1008CntupTimCntOverloadPortn OBJECT-TYPE
	SYNTAX  EkiOnOff
	MAX-ACCESS read-only
	STATUS current
	DESCRIPTION
        "
        Client Counter Overload :This
         OID when set indicates a upstream
        timing counter overload on Port
        "
	::= { pm1008CntupTimCntEntry 4 }


--- *********************************************************
---     TABLE for the pm1008CntupCvErrCnt articles
--- *********************************************************

pm1008CntupCvErrCntTable OBJECT-TYPE
	SYNTAX  SEQUENCE OF Pm1008CntupCvErrCntEntry
	MAX-ACCESS not-accessible
	STATUS current
	DESCRIPTION
        "
        List of pm1008CntupCvErrCnt Article
        "
	::= { pm1008CntClient 48 }


pm1008CntupCvErrCntEntry OBJECT-TYPE
	SYNTAX Pm1008CntupCvErrCntEntry
	MAX-ACCESS not-accessible
	STATUS current
	DESCRIPTION
        "
        Row definition for the pm1008CntupCvErrCnt
        table
        "
	INDEX   { pm1008CntupCvErrCntIndex }
	::= { pm1008CntupCvErrCntTable 1 }


Pm1008CntupCvErrCntEntry ::=
	SEQUENCE {
	pm1008CntupCvErrCntIndex
		INTEGER,
	pm1008CntupCvErrCntValuePortn
		Counter32,
	pm1008CntupCvErrCntErrorPortn
		EkiOnOff,
	pm1008CntupCvErrCntOverloadPortn
		EkiOnOff
	}


pm1008CntupCvErrCntIndex OBJECT-TYPE
	SYNTAX  INTEGER(0..128)
	MAX-ACCESS  read-only
	STATUS current
	DESCRIPTION
        "
        Index definition for the pm1008CntupCvErrCnt
        table
        "
	::= { pm1008CntupCvErrCntEntry 1 }


pm1008CntupCvErrCntValuePortn OBJECT-TYPE
	SYNTAX  Counter32
	MAX-ACCESS read-only
	STATUS current
	DESCRIPTION
        "
        Client Coding Violation Counter
        :This counter is increased each
        time a 10b/8b coding violation
         is detected on the Client input
        stream
        "
	::= { pm1008CntupCvErrCntEntry 2 }


pm1008CntupCvErrCntErrorPortn OBJECT-TYPE
	SYNTAX  EkiOnOff
	MAX-ACCESS read-only
	STATUS current
	DESCRIPTION
        "
        Client Counter Error :This OID
        when set indicates the coding violation
        counter value is invalid on Port
        "
	::= { pm1008CntupCvErrCntEntry 3 }


pm1008CntupCvErrCntOverloadPortn OBJECT-TYPE
	SYNTAX  EkiOnOff
	MAX-ACCESS read-only
	STATUS current
	DESCRIPTION
        "
        Client Counter Overload :This
         OID when set indicates a coding
        violation counter overload on Port
        "
	::= { pm1008CntupCvErrCntEntry 4 }


--- *********************************************************
---     TABLE for the pm1008CntdwCbipCnt articles
--- *********************************************************

pm1008CntdwCbipCntTable OBJECT-TYPE
	SYNTAX  SEQUENCE OF Pm1008CntdwCbipCntEntry
	MAX-ACCESS not-accessible
	STATUS current
	DESCRIPTION
        "
        List of pm1008CntdwCbipCnt Article
        "
	::= { pm1008CntClient 64 }


pm1008CntdwCbipCntEntry OBJECT-TYPE
	SYNTAX Pm1008CntdwCbipCntEntry
	MAX-ACCESS not-accessible
	STATUS current
	DESCRIPTION
        "
        Row definition for the pm1008CntdwCbipCnt
        table
        "
	INDEX   { pm1008CntdwCbipCntIndex }
	::= { pm1008CntdwCbipCntTable 1 }


Pm1008CntdwCbipCntEntry ::=
	SEQUENCE {
	pm1008CntdwCbipCntIndex
		INTEGER,
	pm1008CntdwCbipCntValuePortn
		Counter32,
	pm1008CntdwCbipCntErrorPortn
		EkiOnOff,
	pm1008CntdwCbipCntOverloadPortn
		EkiOnOff
	}


pm1008CntdwCbipCntIndex OBJECT-TYPE
	SYNTAX  INTEGER(0..128)
	MAX-ACCESS  read-only
	STATUS current
	DESCRIPTION
        "
        Index definition for the pm1008CntdwCbipCnt
        table
        "
	::= { pm1008CntdwCbipCntEntry 1 }


pm1008CntdwCbipCntValuePortn OBJECT-TYPE
	SYNTAX  Counter32
	MAX-ACCESS read-only
	STATUS current
	DESCRIPTION
        "
        Client Output Errors :This counter
        is incremented each time a CBIP
        parity error is detected on the
        Client output stream  <Help>  This
        counter gives the number of CBIP
        errors on the client port
        "
	::= { pm1008CntdwCbipCntEntry 2 }


pm1008CntdwCbipCntErrorPortn OBJECT-TYPE
	SYNTAX  EkiOnOff
	MAX-ACCESS read-only
	STATUS current
	DESCRIPTION
        "
        Client Counter Error :This OID
        when set indicates the CBIP error
        counter value is invalid on Port
        "
	::= { pm1008CntdwCbipCntEntry 3 }


pm1008CntdwCbipCntOverloadPortn OBJECT-TYPE
	SYNTAX  EkiOnOff
	MAX-ACCESS read-only
	STATUS current
	DESCRIPTION
        "
        Client CBIP Counter Overload :This
        OID when set indicates a CBIP error
        counter overload on Port
        "
	::= { pm1008CntdwCbipCntEntry 4 }


--- *********************************************************
---     TABLE for the pm1008CntdwTimCnt articles
--- *********************************************************

pm1008CntdwTimCntTable OBJECT-TYPE
	SYNTAX  SEQUENCE OF Pm1008CntdwTimCntEntry
	MAX-ACCESS not-accessible
	STATUS current
	DESCRIPTION
        "
        List of pm1008CntdwTimCnt Article
        "
	::= { pm1008CntClient 72 }


pm1008CntdwTimCntEntry OBJECT-TYPE
	SYNTAX Pm1008CntdwTimCntEntry
	MAX-ACCESS not-accessible
	STATUS current
	DESCRIPTION
        "
        Row definition for the pm1008CntdwTimCnt
        table
        "
	INDEX   { pm1008CntdwTimCntIndex }
	::= { pm1008CntdwTimCntTable 1 }


Pm1008CntdwTimCntEntry ::=
	SEQUENCE {
	pm1008CntdwTimCntIndex
		INTEGER,
	pm1008CntdwTimCntValuePortn
		Counter32,
	pm1008CntdwTimCntErrorPortn
		EkiOnOff,
	pm1008CntdwTimCntOverloadPortn
		EkiOnOff
	}


pm1008CntdwTimCntIndex OBJECT-TYPE
	SYNTAX  INTEGER(0..128)
	MAX-ACCESS  read-only
	STATUS current
	DESCRIPTION
        "
        Index definition for the pm1008CntdwTimCnt
        table
        "
	::= { pm1008CntdwTimCntEntry 1 }


pm1008CntdwTimCntValuePortn OBJECT-TYPE
	SYNTAX  Counter32
	MAX-ACCESS read-only
	STATUS current
	DESCRIPTION
        "
        Client Downstream Timer Counter
        :This is the timing counter dedicated
        to the downstream access counters.
        It is incremented every 125 us.
        "
	::= { pm1008CntdwTimCntEntry 2 }


pm1008CntdwTimCntErrorPortn OBJECT-TYPE
	SYNTAX  EkiOnOff
	MAX-ACCESS read-only
	STATUS current
	DESCRIPTION
        "
        Client Counter Error :This OID
        when set indicates the downstream
        timer counter value is invalid
         on Port
        "
	::= { pm1008CntdwTimCntEntry 3 }


pm1008CntdwTimCntOverloadPortn OBJECT-TYPE
	SYNTAX  EkiOnOff
	MAX-ACCESS read-only
	STATUS current
	DESCRIPTION
        "
        Client Counter Overload :This
         OID when set indicates a downstream
        timer counter overload on Port
        "
	::= { pm1008CntdwTimCntEntry 4 }


--- *********************************************************
---     TABLE for the pm1008CntdfrmB1ErrCnt articles
--- *********************************************************

pm1008CntdfrmB1ErrCntTable OBJECT-TYPE
	SYNTAX  SEQUENCE OF Pm1008CntdfrmB1ErrCntEntry
	MAX-ACCESS not-accessible
	STATUS current
	DESCRIPTION
        "
        List of pm1008CntdfrmB1ErrCnt
         Article
        "
	::= { pm1008CntLine 152 }


pm1008CntdfrmB1ErrCntEntry OBJECT-TYPE
	SYNTAX Pm1008CntdfrmB1ErrCntEntry
	MAX-ACCESS not-accessible
	STATUS current
	DESCRIPTION
        "
        Row definition for the pm1008CntdfrmB1ErrCnt
        table
        "
	INDEX   { pm1008CntdfrmB1ErrCntIndex }
	::= { pm1008CntdfrmB1ErrCntTable 1 }


Pm1008CntdfrmB1ErrCntEntry ::=
	SEQUENCE {
	pm1008CntdfrmB1ErrCntIndex
		INTEGER,
	pm1008CntdfrmB1ErrCntValuePortn
		Counter32,
	pm1008CntdfrmB1ErrCntErrorPortn
		EkiOnOff,
	pm1008CntdfrmB1ErrCntOverloadPortn
		EkiOnOff
	}


pm1008CntdfrmB1ErrCntIndex OBJECT-TYPE
	SYNTAX  INTEGER(0..128)
	MAX-ACCESS  read-only
	STATUS current
	DESCRIPTION
        "
        Index definition for the pm1008CntdfrmB1ErrCnt
        table
        "
	::= { pm1008CntdfrmB1ErrCntEntry 1 }


pm1008CntdfrmB1ErrCntValuePortn OBJECT-TYPE
	SYNTAX  Counter32
	MAX-ACCESS read-only
	STATUS current
	DESCRIPTION
        "
        Line Input B1 Errors :This counter
        is incremented each time a B1 error
        is detected on the Deframer input
        stream.  <Help>  This counter gives
        the number of B1 errors on the
         line port
        "
	::= { pm1008CntdfrmB1ErrCntEntry 2 }


pm1008CntdfrmB1ErrCntErrorPortn OBJECT-TYPE
	SYNTAX  EkiOnOff
	MAX-ACCESS read-only
	STATUS current
	DESCRIPTION
        "
        Line Counter Error :This OID when
        set indicates the B1 error counter
        value is invalid on Port
        "
	::= { pm1008CntdfrmB1ErrCntEntry 3 }


pm1008CntdfrmB1ErrCntOverloadPortn OBJECT-TYPE
	SYNTAX  EkiOnOff
	MAX-ACCESS read-only
	STATUS current
	DESCRIPTION
        "
        Line Counter Overload :This OID
        when set indicates a B1 error counter
        overload on Port
        "
	::= { pm1008CntdfrmB1ErrCntEntry 4 }


--- *********************************************************
---     TABLE for the pm1008CntdfrmTimCnt articles
--- *********************************************************

pm1008CntdfrmTimCntTable OBJECT-TYPE
	SYNTAX  SEQUENCE OF Pm1008CntdfrmTimCntEntry
	MAX-ACCESS not-accessible
	STATUS current
	DESCRIPTION
        "
        List of pm1008CntdfrmTimCnt Article
        "
	::= { pm1008CntLine 153 }


pm1008CntdfrmTimCntEntry OBJECT-TYPE
	SYNTAX Pm1008CntdfrmTimCntEntry
	MAX-ACCESS not-accessible
	STATUS current
	DESCRIPTION
        "
        Row definition for the pm1008CntdfrmTimCnt
        table
        "
	INDEX   { pm1008CntdfrmTimCntIndex }
	::= { pm1008CntdfrmTimCntTable 1 }


Pm1008CntdfrmTimCntEntry ::=
	SEQUENCE {
	pm1008CntdfrmTimCntIndex
		INTEGER,
	pm1008CntdfrmTimCntValuePortn
		Counter32,
	pm1008CntdfrmTimCntErrorPortn
		EkiOnOff,
	pm1008CntdfrmTimCntOverloadPortn
		EkiOnOff
	}


pm1008CntdfrmTimCntIndex OBJECT-TYPE
	SYNTAX  INTEGER(0..128)
	MAX-ACCESS  read-only
	STATUS current
	DESCRIPTION
        "
        Index definition for the pm1008CntdfrmTimCnt
        table
        "
	::= { pm1008CntdfrmTimCntEntry 1 }


pm1008CntdfrmTimCntValuePortn OBJECT-TYPE
	SYNTAX  Counter32
	MAX-ACCESS read-only
	STATUS current
	DESCRIPTION
        "
        Line Timer Counter :This is the
        timing counter dedicated to the
        downstream deframer counters. It
        is incremented every 125 us.
        "
	::= { pm1008CntdfrmTimCntEntry 2 }


pm1008CntdfrmTimCntErrorPortn OBJECT-TYPE
	SYNTAX  EkiOnOff
	MAX-ACCESS read-only
	STATUS current
	DESCRIPTION
        "
        Line Counter Error :This OID when
        set indicates the deframer timer
        counter value is invalid on Port
        "
	::= { pm1008CntdfrmTimCntEntry 3 }


pm1008CntdfrmTimCntOverloadPortn OBJECT-TYPE
	SYNTAX  EkiOnOff
	MAX-ACCESS read-only
	STATUS current
	DESCRIPTION
        "
        Line Counter Overload :This OID
        when set indicates a deframer timer
        counter overload on Port
        "
	::= { pm1008CntdfrmTimCntEntry 4 }


--- *********************************************************
---     TABLE for the pm1008CntdfrmPrimLineErrCnt articles
--- *********************************************************

pm1008CntdfrmPrimLineErrCntTable OBJECT-TYPE
	SYNTAX  SEQUENCE OF Pm1008CntdfrmPrimLineErrCntEntry
	MAX-ACCESS not-accessible
	STATUS current
	DESCRIPTION
        "
        List of pm1008CntdfrmPrimLineErrCnt
        Article
        "
	::= { pm1008CntLine 154 }


pm1008CntdfrmPrimLineErrCntEntry OBJECT-TYPE
	SYNTAX Pm1008CntdfrmPrimLineErrCntEntry
	MAX-ACCESS not-accessible
	STATUS current
	DESCRIPTION
        "
        Row definition for the pm1008CntdfrmPrimLineErrCnt
        table
        "
	INDEX   { pm1008CntdfrmPrimLineErrCntIndex }
	::= { pm1008CntdfrmPrimLineErrCntTable 1 }


Pm1008CntdfrmPrimLineErrCntEntry ::=
	SEQUENCE {
	pm1008CntdfrmPrimLineErrCntIndex
		INTEGER,
	pm1008CntdfrmPrimLineErrCntValuePortn
		Counter32,
	pm1008CntdfrmPrimLineErrCntErrorPortn
		EkiOnOff,
	pm1008CntdfrmPrimLineErrCntOverloadPortn
		EkiOnOff
	}


pm1008CntdfrmPrimLineErrCntIndex OBJECT-TYPE
	SYNTAX  INTEGER(0..128)
	MAX-ACCESS  read-only
	STATUS current
	DESCRIPTION
        "
        Index definition for the pm1008CntdfrmPrimLineErrCnt
        table
        "
	::= { pm1008CntdfrmPrimLineErrCntEntry 1 }


pm1008CntdfrmPrimLineErrCntValuePortn OBJECT-TYPE
	SYNTAX  Counter32
	MAX-ACCESS read-only
	STATUS current
	DESCRIPTION
        "
        Line Input FEC Corrected Errors
        :This counter is incremented each
        time the FEC is correcting an error
        on the line input stream.  <Help>
         This counter gives the number
         of errors corrected by the FEC
        on the line port
        "
	::= { pm1008CntdfrmPrimLineErrCntEntry 2 }


pm1008CntdfrmPrimLineErrCntErrorPortn OBJECT-TYPE
	SYNTAX  EkiOnOff
	MAX-ACCESS read-only
	STATUS current
	DESCRIPTION
        "
        FEC Counter Error :This bit when
        set indicates the FEC corrected
        errors counter value is invalid
        on Line
        "
	::= { pm1008CntdfrmPrimLineErrCntEntry 3 }


pm1008CntdfrmPrimLineErrCntOverloadPortn OBJECT-TYPE
	SYNTAX  EkiOnOff
	MAX-ACCESS read-only
	STATUS current
	DESCRIPTION
        "
        FEC Counter Overload :This bit
        when set indicates a FEC corrected
        errors counter overload on Line
        "
	::= { pm1008CntdfrmPrimLineErrCntEntry 4 }


pm1008CntCountersReset  OBJECT-TYPE
	SYNTAX EkiOnOff
	MAX-ACCESS read-write
	STATUS current
	DESCRIPTION
	"Counters Reset:This OID resets and restarts all the counters"
	::= { pm1008counters  259 }

pm1008CntCountersStop  OBJECT-TYPE
	SYNTAX EkiOnOff
	MAX-ACCESS read-write
	STATUS current
	DESCRIPTION
	"Counters stop:This OID stops all the counters"
	::= { pm1008counters 260 }






--- *****************************************************
--- $$$$$$$$$$$$$$$$$$$$$$$$$$$$$$$$$$$$$$$$$$$$$$$$$$$$$
---     RMON
--- $$$$$$$$$$$$$$$$$$$$$$$$$$$$$$$$$$$$$$$$$$$$$$$$$$$$$
--- *****************************************************



--- *********************************************************
---     TABLE for the pm1008MonupRmonByteCnt articles
--- *********************************************************

pm1008MonupRmonByteCntTable OBJECT-TYPE
	SYNTAX  SEQUENCE OF Pm1008MonupRmonByteCntEntry
	MAX-ACCESS not-accessible
	STATUS current
	DESCRIPTION
        "
        List of pm1008MonupRmonByteCnt
        Article
        "
	::= { pm1008MonClientRmonCounter 16 }


pm1008MonupRmonByteCntEntry OBJECT-TYPE
	SYNTAX Pm1008MonupRmonByteCntEntry
	MAX-ACCESS not-accessible
	STATUS current
	DESCRIPTION
        "
        Row definition for the pm1008MonupRmonByteCnt
        table
        "
	INDEX   { pm1008MonupRmonByteCntIndex }
	::= { pm1008MonupRmonByteCntTable 1 }


Pm1008MonupRmonByteCntEntry ::=
	SEQUENCE {
	pm1008MonupRmonByteCntIndex
		INTEGER,
	pm1008MonupRmonByteCntValuePortn
		Counter64,
	pm1008MonupRmonByteCntErrorPortn
		EkiOnOff,
	pm1008MonupRmonByteCntOverloadPortn
		EkiOnOff
	}


pm1008MonupRmonByteCntIndex OBJECT-TYPE
	SYNTAX  INTEGER(0..128)
	MAX-ACCESS  read-only
	STATUS current
	DESCRIPTION
        "
        Index definition for the pm1008MonupRmonByteCnt
        table
        "
	::= { pm1008MonupRmonByteCntEntry 1 }


pm1008MonupRmonByteCntValuePortn OBJECT-TYPE
	SYNTAX  Counter64
	MAX-ACCESS read-only
	STATUS current
	DESCRIPTION
        "
        Client Input Bytes :This counter
        is increased each time a data byte
        is received on the client port
          <Help>  This counter gives the
        number of bytes received on the
        client port
        "
	::= { pm1008MonupRmonByteCntEntry 2 }


pm1008MonupRmonByteCntErrorPortn OBJECT-TYPE
	SYNTAX  EkiOnOff
	MAX-ACCESS read-only
	STATUS current
	DESCRIPTION
        "
        Bytes Counter Error :This OID
         when set indicates the Bytes counter
        value is invalid on clinet port
        "
	::= { pm1008MonupRmonByteCntEntry 3 }


pm1008MonupRmonByteCntOverloadPortn OBJECT-TYPE
	SYNTAX  EkiOnOff
	MAX-ACCESS read-only
	STATUS current
	DESCRIPTION
        "
        Bytes Counter Overload :This OID
        when set indicates a Bytes counter
        overload on client port
        "
	::= { pm1008MonupRmonByteCntEntry 4 }


--- *********************************************************
---     TABLE for the pm1008MonupRmonCrcErrorCnt articles
--- *********************************************************

pm1008MonupRmonCrcErrorCntTable OBJECT-TYPE
	SYNTAX  SEQUENCE OF Pm1008MonupRmonCrcErrorCntEntry
	MAX-ACCESS not-accessible
	STATUS current
	DESCRIPTION
        "
        List of pm1008MonupRmonCrcErrorCnt
        Article
        "
	::= { pm1008MonClientRmonCounter 24 }


pm1008MonupRmonCrcErrorCntEntry OBJECT-TYPE
	SYNTAX Pm1008MonupRmonCrcErrorCntEntry
	MAX-ACCESS not-accessible
	STATUS current
	DESCRIPTION
        "
        Row definition for the pm1008MonupRmonCrcErrorCnt
        table
        "
	INDEX   { pm1008MonupRmonCrcErrorCntIndex }
	::= { pm1008MonupRmonCrcErrorCntTable 1 }


Pm1008MonupRmonCrcErrorCntEntry ::=
	SEQUENCE {
	pm1008MonupRmonCrcErrorCntIndex
		INTEGER,
	pm1008MonupRmonCrcErrorCntValuePortn
		Counter64,
	pm1008MonupRmonCrcErrorCntErrorPortn
		EkiOnOff,
	pm1008MonupRmonCrcErrorCntOverloadPortn
		EkiOnOff
	}


pm1008MonupRmonCrcErrorCntIndex OBJECT-TYPE
	SYNTAX  INTEGER(0..128)
	MAX-ACCESS  read-only
	STATUS current
	DESCRIPTION
        "
        Index definition for the pm1008MonupRmonCrcErrorCnt
        table
        "
	::= { pm1008MonupRmonCrcErrorCntEntry 1 }


pm1008MonupRmonCrcErrorCntValuePortn OBJECT-TYPE
	SYNTAX  Counter64
	MAX-ACCESS read-only
	STATUS current
	DESCRIPTION
        "
        Client Input CRC Errors :This
         counter is increased each time
        a CRC error is detected on the
         client port  <Help>  This counter
        gives the number of CRC Errors
         received on the client port
        "
	::= { pm1008MonupRmonCrcErrorCntEntry 2 }


pm1008MonupRmonCrcErrorCntErrorPortn OBJECT-TYPE
	SYNTAX  EkiOnOff
	MAX-ACCESS read-only
	STATUS current
	DESCRIPTION
        "
        CRC Errors Counter Error :This
        OID when set indicates the CRC
         Errors counter value is invalid
        on clinet port
        "
	::= { pm1008MonupRmonCrcErrorCntEntry 3 }


pm1008MonupRmonCrcErrorCntOverloadPortn OBJECT-TYPE
	SYNTAX  EkiOnOff
	MAX-ACCESS read-only
	STATUS current
	DESCRIPTION
        "
        CRC Errors Counter Overload :This
        OID when set indicates a CRC Errors
        counter overload on client port
        "
	::= { pm1008MonupRmonCrcErrorCntEntry 4 }


--- *********************************************************
---     TABLE for the pm1008MonupRmonPacketsCnt articles
--- *********************************************************

pm1008MonupRmonPacketsCntTable OBJECT-TYPE
	SYNTAX  SEQUENCE OF Pm1008MonupRmonPacketsCntEntry
	MAX-ACCESS not-accessible
	STATUS current
	DESCRIPTION
        "
        List of pm1008MonupRmonPacketsCnt
        Article
        "
	::= { pm1008MonClientRmonCounter 32 }


pm1008MonupRmonPacketsCntEntry OBJECT-TYPE
	SYNTAX Pm1008MonupRmonPacketsCntEntry
	MAX-ACCESS not-accessible
	STATUS current
	DESCRIPTION
        "
        Row definition for the pm1008MonupRmonPacketsCnt
        table
        "
	INDEX   { pm1008MonupRmonPacketsCntIndex }
	::= { pm1008MonupRmonPacketsCntTable 1 }


Pm1008MonupRmonPacketsCntEntry ::=
	SEQUENCE {
	pm1008MonupRmonPacketsCntIndex
		INTEGER,
	pm1008MonupRmonPacketsCntValuePortn
		Counter64,
	pm1008MonupRmonPacketsCntErrorPortn
		EkiOnOff,
	pm1008MonupRmonPacketsCntOverloadPortn
		EkiOnOff
	}


pm1008MonupRmonPacketsCntIndex OBJECT-TYPE
	SYNTAX  INTEGER(0..128)
	MAX-ACCESS  read-only
	STATUS current
	DESCRIPTION
        "
        Index definition for the pm1008MonupRmonPacketsCnt
        table
        "
	::= { pm1008MonupRmonPacketsCntEntry 1 }


pm1008MonupRmonPacketsCntValuePortn OBJECT-TYPE
	SYNTAX  Counter64
	MAX-ACCESS read-only
	STATUS current
	DESCRIPTION
        "
        Client Input Packets :This counter
        is increased each time a packet
        is received on the client port
          <Help>  This counter gives the
        number of packets received on the
        client port
        "
	::= { pm1008MonupRmonPacketsCntEntry 2 }


pm1008MonupRmonPacketsCntErrorPortn OBJECT-TYPE
	SYNTAX  EkiOnOff
	MAX-ACCESS read-only
	STATUS current
	DESCRIPTION
        "
        Packets Counter Error :This OID
        when set indicates the Packets
         counter value is invalid on clinet
        port
        "
	::= { pm1008MonupRmonPacketsCntEntry 3 }


pm1008MonupRmonPacketsCntOverloadPortn OBJECT-TYPE
	SYNTAX  EkiOnOff
	MAX-ACCESS read-only
	STATUS current
	DESCRIPTION
        "
        Packets Counter Overload :This
        OID when set indicates a Packets
        counter overload on client port
        "
	::= { pm1008MonupRmonPacketsCntEntry 4 }


--- *********************************************************
---     TABLE for the pm1008MonupRmonBroadcastCnt articles
--- *********************************************************

pm1008MonupRmonBroadcastCntTable OBJECT-TYPE
	SYNTAX  SEQUENCE OF Pm1008MonupRmonBroadcastCntEntry
	MAX-ACCESS not-accessible
	STATUS current
	DESCRIPTION
        "
        List of pm1008MonupRmonBroadcastCnt
        Article
        "
	::= { pm1008MonClientRmonCounter 40 }


pm1008MonupRmonBroadcastCntEntry OBJECT-TYPE
	SYNTAX Pm1008MonupRmonBroadcastCntEntry
	MAX-ACCESS not-accessible
	STATUS current
	DESCRIPTION
        "
        Row definition for the pm1008MonupRmonBroadcastCnt
        table
        "
	INDEX   { pm1008MonupRmonBroadcastCntIndex }
	::= { pm1008MonupRmonBroadcastCntTable 1 }


Pm1008MonupRmonBroadcastCntEntry ::=
	SEQUENCE {
	pm1008MonupRmonBroadcastCntIndex
		INTEGER,
	pm1008MonupRmonBroadcastCntValuePortn
		Counter64,
	pm1008MonupRmonBroadcastCntErrorPortn
		EkiOnOff,
	pm1008MonupRmonBroadcastCntOverloadPortn
		EkiOnOff
	}


pm1008MonupRmonBroadcastCntIndex OBJECT-TYPE
	SYNTAX  INTEGER(0..128)
	MAX-ACCESS  read-only
	STATUS current
	DESCRIPTION
        "
        Index definition for the pm1008MonupRmonBroadcastCnt
        table
        "
	::= { pm1008MonupRmonBroadcastCntEntry 1 }


pm1008MonupRmonBroadcastCntValuePortn OBJECT-TYPE
	SYNTAX  Counter64
	MAX-ACCESS read-only
	STATUS current
	DESCRIPTION
        "
        Client Input Broadcast Packets
        :This counter is increased each
        time a broadcast packet is received
        on the client port  <Help>  This
        counter gives the number of Broadcast
        packets received on the client
         port
        "
	::= { pm1008MonupRmonBroadcastCntEntry 2 }


pm1008MonupRmonBroadcastCntErrorPortn OBJECT-TYPE
	SYNTAX  EkiOnOff
	MAX-ACCESS read-only
	STATUS current
	DESCRIPTION
        "
        Broadcast Counter Error :This
         OID when set indicates the Broadcast
        counter value is invalid on clinet
        port
        "
	::= { pm1008MonupRmonBroadcastCntEntry 3 }


pm1008MonupRmonBroadcastCntOverloadPortn OBJECT-TYPE
	SYNTAX  EkiOnOff
	MAX-ACCESS read-only
	STATUS current
	DESCRIPTION
        "
        Broadcast Counter Overload :This
        OID when set indicates a Broadcast
        counter overload on client port
        "
	::= { pm1008MonupRmonBroadcastCntEntry 4 }


--- *********************************************************
---     TABLE for the pm1008MonupRmonMulticastCnt articles
--- *********************************************************

pm1008MonupRmonMulticastCntTable OBJECT-TYPE
	SYNTAX  SEQUENCE OF Pm1008MonupRmonMulticastCntEntry
	MAX-ACCESS not-accessible
	STATUS current
	DESCRIPTION
        "
        List of pm1008MonupRmonMulticastCnt
        Article
        "
	::= { pm1008MonClientRmonCounter 48 }


pm1008MonupRmonMulticastCntEntry OBJECT-TYPE
	SYNTAX Pm1008MonupRmonMulticastCntEntry
	MAX-ACCESS not-accessible
	STATUS current
	DESCRIPTION
        "
        Row definition for the pm1008MonupRmonMulticastCnt
        table
        "
	INDEX   { pm1008MonupRmonMulticastCntIndex }
	::= { pm1008MonupRmonMulticastCntTable 1 }


Pm1008MonupRmonMulticastCntEntry ::=
	SEQUENCE {
	pm1008MonupRmonMulticastCntIndex
		INTEGER,
	pm1008MonupRmonMulticastCntValuePortn
		Counter64,
	pm1008MonupRmonMulticastCntErrorPortn
		EkiOnOff,
	pm1008MonupRmonMulticastCntOverloadPortn
		EkiOnOff
	}


pm1008MonupRmonMulticastCntIndex OBJECT-TYPE
	SYNTAX  INTEGER(0..128)
	MAX-ACCESS  read-only
	STATUS current
	DESCRIPTION
        "
        Index definition for the pm1008MonupRmonMulticastCnt
        table
        "
	::= { pm1008MonupRmonMulticastCntEntry 1 }


pm1008MonupRmonMulticastCntValuePortn OBJECT-TYPE
	SYNTAX  Counter64
	MAX-ACCESS read-only
	STATUS current
	DESCRIPTION
        "
        Client Input Multicast Packets
        :This counter is increased each
        time a Multicast packet is received
        on the client port  <Help>  This
        counter gives the number of Multicast
        packets received on the client
         port
        "
	::= { pm1008MonupRmonMulticastCntEntry 2 }


pm1008MonupRmonMulticastCntErrorPortn OBJECT-TYPE
	SYNTAX  EkiOnOff
	MAX-ACCESS read-only
	STATUS current
	DESCRIPTION
        "
        Multicast Counter Error :This
         OID when set indicates the Multicast
        counter value is invalid on clinet
        port
        "
	::= { pm1008MonupRmonMulticastCntEntry 3 }


pm1008MonupRmonMulticastCntOverloadPortn OBJECT-TYPE
	SYNTAX  EkiOnOff
	MAX-ACCESS read-only
	STATUS current
	DESCRIPTION
        "
        Multicast Counter Overload :This
        OID when set indicates a Multicast
        counter overload on client port
        "
	::= { pm1008MonupRmonMulticastCntEntry 4 }


pm1008MonCountersReset  OBJECT-TYPE
	SYNTAX EkiOnOff
	MAX-ACCESS read-write
	STATUS current
	DESCRIPTION
	"RMON Counters Reset:This OID resets and restarts all the RMON counters"
	::= { pm1008MonRmon   359 }

pm1008MonCountersStop  OBJECT-TYPE
	SYNTAX EkiOnOff
	MAX-ACCESS read-write
	STATUS current
	DESCRIPTION
	"RMON Counters stop:This OID stops all the RMON counters"
	::= { pm1008MonRmon  360 }






--- *****************************************************
--- $$$$$$$$$$$$$$$$$$$$$$$$$$$$$$$$$$$$$$$$$$$$$$$$$$$$$
---     MEASURES
--- $$$$$$$$$$$$$$$$$$$$$$$$$$$$$$$$$$$$$$$$$$$$$$$$$$$$$
--- *****************************************************



pm1008Mesrsynth0 OBJECT-TYPE
	  SYNTAX EkiMeasureType
	  MAX-ACCESS read-only
	  STATUS deprecated
	  DESCRIPTION
        "
        Not Used :This OID gives the unit
        used on AUX1 measurement of XFP#1
         (Unit = )
        "
	  ::= { pm1008MesrOther 0 }



pm1008Mesrsynth1 OBJECT-TYPE
	  SYNTAX EkiMeasureType
	  MAX-ACCESS read-only
	  STATUS deprecated
	  DESCRIPTION
        "
        Not Used :This OID gives the unit
        used on AUX2 measurement of XFP#1
         (Unit = )
        "
	  ::= { pm1008MesrOther 1 }



--- *********************************************************
---     TABLE for the pm1008MesrtempMeas articles
--- *********************************************************

pm1008MesrtempMeasTable OBJECT-TYPE
	SYNTAX  SEQUENCE OF Pm1008MesrtempMeasEntry
	MAX-ACCESS not-accessible
	STATUS current
	DESCRIPTION
        "
        List of pm1008MesrtempMeas Article
        "
	::= { pm1008MesrClient 16 }


pm1008MesrtempMeasEntry OBJECT-TYPE
	SYNTAX Pm1008MesrtempMeasEntry
	MAX-ACCESS not-accessible
	STATUS current
	DESCRIPTION
        "
        Row definition for the pm1008MesrtempMeas
        table
        "
	INDEX   { pm1008MesrtempMeasIndex }
	::= { pm1008MesrtempMeasTable 1 }


Pm1008MesrtempMeasEntry ::=
	SEQUENCE {
	pm1008MesrtempMeasIndex
		INTEGER,
	pm1008MesrtempMeasPortn
		INTEGER
	}


pm1008MesrtempMeasIndex OBJECT-TYPE
	SYNTAX  INTEGER(0..128)
	MAX-ACCESS  read-only
	STATUS current
	DESCRIPTION
        "
        Index definition for the pm1008MesrtempMeas
        table
        "
	::= { pm1008MesrtempMeasEntry 1 }


pm1008MesrtempMeasPortn OBJECT-TYPE
	SYNTAX  INTEGER (0..65535)
	MAX-ACCESS read-only
	STATUS current
	DESCRIPTION
        "
        Client SFP Temperature :This OID
        gives the temperature value of
         the SFP plugged in port, read
         from the DDM (Digital Diagnostic
        Monitoring) (Temperature = AV/256)
        (Unit = C)  <Help>  This measure
        gives the temperature of the client
        transceiver
        "
	::= { pm1008MesrtempMeasEntry 2 }


--- *********************************************************
---     TABLE for the pm1008MesrvoltMeas articles
--- *********************************************************

pm1008MesrvoltMeasTable OBJECT-TYPE
	SYNTAX  SEQUENCE OF Pm1008MesrvoltMeasEntry
	MAX-ACCESS not-accessible
	STATUS current
	DESCRIPTION
        "
        List of pm1008MesrvoltMeas Article
        "
	::= { pm1008MesrClient 24 }


pm1008MesrvoltMeasEntry OBJECT-TYPE
	SYNTAX Pm1008MesrvoltMeasEntry
	MAX-ACCESS not-accessible
	STATUS current
	DESCRIPTION
        "
        Row definition for the pm1008MesrvoltMeas
        table
        "
	INDEX   { pm1008MesrvoltMeasIndex }
	::= { pm1008MesrvoltMeasTable 1 }


Pm1008MesrvoltMeasEntry ::=
	SEQUENCE {
	pm1008MesrvoltMeasIndex
		INTEGER,
	pm1008MesrvoltMeasPortn
		INTEGER
	}


pm1008MesrvoltMeasIndex OBJECT-TYPE
	SYNTAX  INTEGER(0..128)
	MAX-ACCESS  read-only
	STATUS current
	DESCRIPTION
        "
        Index definition for the pm1008MesrvoltMeas
        table
        "
	::= { pm1008MesrvoltMeasEntry 1 }


pm1008MesrvoltMeasPortn OBJECT-TYPE
	SYNTAX  INTEGER (0..65535)
	MAX-ACCESS read-only
	STATUS current
	DESCRIPTION
        "
        Client SFP Power Supply :This
         OID gives the 3V3 voltage value
        of the SFP plugged into port, read
        from the DDM (Digital Diagnostic
        Monitoring) (Voltage = AV/10000)
        (Unit = V)  <Help>  This measure
        gives the 3V3 voltage of the client
        transceiver
        "
	::= { pm1008MesrvoltMeasEntry 2 }


--- *********************************************************
---     TABLE for the pm1008MesrbiasMeas articles
--- *********************************************************

pm1008MesrbiasMeasTable OBJECT-TYPE
	SYNTAX  SEQUENCE OF Pm1008MesrbiasMeasEntry
	MAX-ACCESS not-accessible
	STATUS current
	DESCRIPTION
        "
        List of pm1008MesrbiasMeas Article
        "
	::= { pm1008MesrClient 32 }


pm1008MesrbiasMeasEntry OBJECT-TYPE
	SYNTAX Pm1008MesrbiasMeasEntry
	MAX-ACCESS not-accessible
	STATUS current
	DESCRIPTION
        "
        Row definition for the pm1008MesrbiasMeas
        table
        "
	INDEX   { pm1008MesrbiasMeasIndex }
	::= { pm1008MesrbiasMeasTable 1 }


Pm1008MesrbiasMeasEntry ::=
	SEQUENCE {
	pm1008MesrbiasMeasIndex
		INTEGER,
	pm1008MesrbiasMeasPortn
		INTEGER
	}


pm1008MesrbiasMeasIndex OBJECT-TYPE
	SYNTAX  INTEGER(0..128)
	MAX-ACCESS  read-only
	STATUS current
	DESCRIPTION
        "
        Index definition for the pm1008MesrbiasMeas
        table
        "
	::= { pm1008MesrbiasMeasEntry 1 }


pm1008MesrbiasMeasPortn OBJECT-TYPE
	SYNTAX  INTEGER (0..65535)
	MAX-ACCESS read-only
	STATUS current
	DESCRIPTION
        "
        Client SFP Laser Bias :This OID
        gives the bias value of the SFP
        plugged into port, read from the
        DDM (Digital Diagnostic Monitoring)
        (Bias = AV/500) (Unit = mA)  <Help>
         This measure gives the bias of
        the client transceiver
        "
	::= { pm1008MesrbiasMeasEntry 2 }


--- *********************************************************
---     TABLE for the pm1008MesrtxpwrMeas articles
--- *********************************************************

pm1008MesrtxpwrMeasTable OBJECT-TYPE
	SYNTAX  SEQUENCE OF Pm1008MesrtxpwrMeasEntry
	MAX-ACCESS not-accessible
	STATUS current
	DESCRIPTION
        "
        List of pm1008MesrtxpwrMeas Article
        "
	::= { pm1008MesrClient 40 }


pm1008MesrtxpwrMeasEntry OBJECT-TYPE
	SYNTAX Pm1008MesrtxpwrMeasEntry
	MAX-ACCESS not-accessible
	STATUS current
	DESCRIPTION
        "
        Row definition for the pm1008MesrtxpwrMeas
        table
        "
	INDEX   { pm1008MesrtxpwrMeasIndex }
	::= { pm1008MesrtxpwrMeasTable 1 }


Pm1008MesrtxpwrMeasEntry ::=
	SEQUENCE {
	pm1008MesrtxpwrMeasIndex
		INTEGER,
	pm1008MesrtxpwrMeasPortn
		INTEGER
	}


pm1008MesrtxpwrMeasIndex OBJECT-TYPE
	SYNTAX  INTEGER(0..128)
	MAX-ACCESS  read-only
	STATUS current
	DESCRIPTION
        "
        Index definition for the pm1008MesrtxpwrMeas
        table
        "
	::= { pm1008MesrtxpwrMeasEntry 1 }


pm1008MesrtxpwrMeasPortn OBJECT-TYPE
	SYNTAX  INTEGER (0..65535)
	MAX-ACCESS read-only
	STATUS current
	DESCRIPTION
        "
        Client SFP Tx Power :This OID
         gives the transmit power value
        of the SFP plugged into port, read
        from the DDM (Digital Diagnostic
        Monitoring) (Power = 10*log(AV)-40)
        (Unit = dBm)  <Help>  This measure
        gives the Tx optical power of the
        client transceiver
        "
	::= { pm1008MesrtxpwrMeasEntry 2 }


--- *********************************************************
---     TABLE for the pm1008MesrrxpwrMeas articles
--- *********************************************************

pm1008MesrrxpwrMeasTable OBJECT-TYPE
	SYNTAX  SEQUENCE OF Pm1008MesrrxpwrMeasEntry
	MAX-ACCESS not-accessible
	STATUS current
	DESCRIPTION
        "
        List of pm1008MesrrxpwrMeas Article
        "
	::= { pm1008MesrClient 48 }


pm1008MesrrxpwrMeasEntry OBJECT-TYPE
	SYNTAX Pm1008MesrrxpwrMeasEntry
	MAX-ACCESS not-accessible
	STATUS current
	DESCRIPTION
        "
        Row definition for the pm1008MesrrxpwrMeas
        table
        "
	INDEX   { pm1008MesrrxpwrMeasIndex }
	::= { pm1008MesrrxpwrMeasTable 1 }


Pm1008MesrrxpwrMeasEntry ::=
	SEQUENCE {
	pm1008MesrrxpwrMeasIndex
		INTEGER,
	pm1008MesrrxpwrMeasPortn
		INTEGER
	}


pm1008MesrrxpwrMeasIndex OBJECT-TYPE
	SYNTAX  INTEGER(0..128)
	MAX-ACCESS  read-only
	STATUS current
	DESCRIPTION
        "
        Index definition for the pm1008MesrrxpwrMeas
        table
        "
	::= { pm1008MesrrxpwrMeasEntry 1 }


pm1008MesrrxpwrMeasPortn OBJECT-TYPE
	SYNTAX  INTEGER (0..65535)
	MAX-ACCESS read-only
	STATUS current
	DESCRIPTION
        "
        Client SFP Rx Power :This OID
         gives the receive power value
         of the SFP plugged into port,
         read in the DDM (Digital Diagnostic
        Monitoring) (Power = 10*log(AV)-40)
        (Unit = dBm)  <Help>  This measure
        gives the Rx optical power of the
        client transceiver
        "
	::= { pm1008MesrrxpwrMeasEntry 2 }


--- *********************************************************
---     TABLE for the pm1008Mesrxfp1LxModTempMeas articles
--- *********************************************************

pm1008Mesrxfp1LxModTempMeasTable OBJECT-TYPE
	SYNTAX  SEQUENCE OF Pm1008Mesrxfp1LxModTempMeasEntry
	MAX-ACCESS not-accessible
	STATUS current
	DESCRIPTION
        "
        List of pm1008Mesrxfp1LxModTempMeas
        Article
        "
	::= { pm1008MesrLine 208 }


pm1008Mesrxfp1LxModTempMeasEntry OBJECT-TYPE
	SYNTAX Pm1008Mesrxfp1LxModTempMeasEntry
	MAX-ACCESS not-accessible
	STATUS current
	DESCRIPTION
        "
        Row definition for the pm1008Mesrxfp1LxModTempMeas
        table
        "
	INDEX   { pm1008Mesrxfp1LxModTempMeasIndex }
	::= { pm1008Mesrxfp1LxModTempMeasTable 1 }


Pm1008Mesrxfp1LxModTempMeasEntry ::=
	SEQUENCE {
	pm1008Mesrxfp1LxModTempMeasIndex
		INTEGER,
	pm1008Mesrxfp1LxModTempMeasPortn
		INTEGER
	}


pm1008Mesrxfp1LxModTempMeasIndex OBJECT-TYPE
	SYNTAX  INTEGER(0..128)
	MAX-ACCESS  read-only
	STATUS current
	DESCRIPTION
        "
        Index definition for the pm1008Mesrxfp1LxModTempMeas
        table
        "
	::= { pm1008Mesrxfp1LxModTempMeasEntry 1 }


pm1008Mesrxfp1LxModTempMeasPortn OBJECT-TYPE
	SYNTAX  INTEGER (0..65535)
	MAX-ACCESS read-only
	STATUS current
	DESCRIPTION
        "
        Line Optical Module Temperature
        :This OID gives the temperature
        of the XFP or OTX plugged in line#n,
        read from the DDM (Digital Diagnostic
        Monitoring)  (Temperature = AV/256)
        (Unit = C)  <Help>  This measure
        gives the temperature of the line
        transceiver
        "
	::= { pm1008Mesrxfp1LxModTempMeasEntry 2 }


--- *********************************************************
---     TABLE for the pm1008Mesrxfp1Reserved articles
--- *********************************************************

pm1008Mesrxfp1ReservedTable OBJECT-TYPE
	SYNTAX  SEQUENCE OF Pm1008Mesrxfp1ReservedEntry
	MAX-ACCESS not-accessible
	STATUS deprecated
	DESCRIPTION
        "
        List of pm1008Mesrxfp1Reserved
        Article
        "
	::= { pm1008MesrLine 209 }


pm1008Mesrxfp1ReservedEntry OBJECT-TYPE
	SYNTAX Pm1008Mesrxfp1ReservedEntry
	MAX-ACCESS not-accessible
	STATUS deprecated
	DESCRIPTION
        "
        Row definition for the pm1008Mesrxfp1Reserved
        table
        "
	INDEX   { pm1008Mesrxfp1ReservedIndex }
	::= { pm1008Mesrxfp1ReservedTable 1 }


Pm1008Mesrxfp1ReservedEntry ::=
	SEQUENCE {
	pm1008Mesrxfp1ReservedIndex
		INTEGER,
	pm1008Mesrxfp1ReservedPortn
		INTEGER
	}


pm1008Mesrxfp1ReservedIndex OBJECT-TYPE
	SYNTAX  INTEGER(0..128)
	MAX-ACCESS  read-only
	STATUS deprecated
	DESCRIPTION
        "
        Index definition for the pm1008Mesrxfp1Reserved
        table
        "
	::= { pm1008Mesrxfp1ReservedEntry 1 }


pm1008Mesrxfp1ReservedPortn OBJECT-TYPE
	SYNTAX  INTEGER (0..65535)
	MAX-ACCESS read-only
	STATUS deprecated
	DESCRIPTION
        "
        Not Used :Reserved
        "
	::= { pm1008Mesrxfp1ReservedEntry 2 }


--- *********************************************************
---     TABLE for the pm1008Mesrxfp1LoBiasCurrentMeas articles
--- *********************************************************

pm1008Mesrxfp1LoBiasCurrentMeasTable OBJECT-TYPE
	SYNTAX  SEQUENCE OF Pm1008Mesrxfp1LoBiasCurrentMeasEntry
	MAX-ACCESS not-accessible
	STATUS current
	DESCRIPTION
        "
        List of pm1008Mesrxfp1LoBiasCurrentMeas
        Article
        "
	::= { pm1008MesrLine 210 }


pm1008Mesrxfp1LoBiasCurrentMeasEntry OBJECT-TYPE
	SYNTAX Pm1008Mesrxfp1LoBiasCurrentMeasEntry
	MAX-ACCESS not-accessible
	STATUS current
	DESCRIPTION
        "
        Row definition for the pm1008Mesrxfp1LoBiasCurrentMeas
        table
        "
	INDEX   { pm1008Mesrxfp1LoBiasCurrentMeasIndex }
	::= { pm1008Mesrxfp1LoBiasCurrentMeasTable 1 }


Pm1008Mesrxfp1LoBiasCurrentMeasEntry ::=
	SEQUENCE {
	pm1008Mesrxfp1LoBiasCurrentMeasIndex
		INTEGER,
	pm1008Mesrxfp1LoBiasCurrentMeasPortn
		INTEGER
	}


pm1008Mesrxfp1LoBiasCurrentMeasIndex OBJECT-TYPE
	SYNTAX  INTEGER(0..128)
	MAX-ACCESS  read-only
	STATUS current
	DESCRIPTION
        "
        Index definition for the pm1008Mesrxfp1LoBiasCurrentMeas
        table
        "
	::= { pm1008Mesrxfp1LoBiasCurrentMeasEntry 1 }


pm1008Mesrxfp1LoBiasCurrentMeasPortn OBJECT-TYPE
	SYNTAX  INTEGER (0..65535)
	MAX-ACCESS read-only
	STATUS current
	DESCRIPTION
        "
        Line Optical Module Laser Bias
        :This OID gives the bias value
         of the XFP or OTX plugged in line
        #n, read from the DDM (Digital
         Diagnostic Monitoring) (Bias =
        AV/500) (Unit = mA)  <Help>  This
        measure gives the bias of the line
        transceiver
        "
	::= { pm1008Mesrxfp1LoBiasCurrentMeasEntry 2 }


--- *********************************************************
---     TABLE for the pm1008Mesrxfp1LoTxPowerMeas articles
--- *********************************************************

pm1008Mesrxfp1LoTxPowerMeasTable OBJECT-TYPE
	SYNTAX  SEQUENCE OF Pm1008Mesrxfp1LoTxPowerMeasEntry
	MAX-ACCESS not-accessible
	STATUS current
	DESCRIPTION
        "
        List of pm1008Mesrxfp1LoTxPowerMeas
        Article
        "
	::= { pm1008MesrLine 211 }


pm1008Mesrxfp1LoTxPowerMeasEntry OBJECT-TYPE
	SYNTAX Pm1008Mesrxfp1LoTxPowerMeasEntry
	MAX-ACCESS not-accessible
	STATUS current
	DESCRIPTION
        "
        Row definition for the pm1008Mesrxfp1LoTxPowerMeas
        table
        "
	INDEX   { pm1008Mesrxfp1LoTxPowerMeasIndex }
	::= { pm1008Mesrxfp1LoTxPowerMeasTable 1 }


Pm1008Mesrxfp1LoTxPowerMeasEntry ::=
	SEQUENCE {
	pm1008Mesrxfp1LoTxPowerMeasIndex
		INTEGER,
	pm1008Mesrxfp1LoTxPowerMeasPortn
		INTEGER
	}


pm1008Mesrxfp1LoTxPowerMeasIndex OBJECT-TYPE
	SYNTAX  INTEGER(0..128)
	MAX-ACCESS  read-only
	STATUS current
	DESCRIPTION
        "
        Index definition for the pm1008Mesrxfp1LoTxPowerMeas
        table
        "
	::= { pm1008Mesrxfp1LoTxPowerMeasEntry 1 }


pm1008Mesrxfp1LoTxPowerMeasPortn OBJECT-TYPE
	SYNTAX  INTEGER (0..65535)
	MAX-ACCESS read-only
	STATUS current
	DESCRIPTION
        "
        Line Optical Module Tx Power :This
        OID gives the transmit power value
        of the XFP or OTX plugged in line
        #n, read from the DDM (Digital
           Diagnostic Monitoring) (Power
        = 10*log(AV)-40)  (Unit = dBm)
          <Help>  This measure gives the
        Tx optical power of the line transceiver
        "
	::= { pm1008Mesrxfp1LoTxPowerMeasEntry 2 }


--- *********************************************************
---     TABLE for the pm1008Mesrxfp1LiRxPowerMeas articles
--- *********************************************************

pm1008Mesrxfp1LiRxPowerMeasTable OBJECT-TYPE
	SYNTAX  SEQUENCE OF Pm1008Mesrxfp1LiRxPowerMeasEntry
	MAX-ACCESS not-accessible
	STATUS current
	DESCRIPTION
        "
        List of pm1008Mesrxfp1LiRxPowerMeas
        Article
        "
	::= { pm1008MesrLine 212 }


pm1008Mesrxfp1LiRxPowerMeasEntry OBJECT-TYPE
	SYNTAX Pm1008Mesrxfp1LiRxPowerMeasEntry
	MAX-ACCESS not-accessible
	STATUS current
	DESCRIPTION
        "
        Row definition for the pm1008Mesrxfp1LiRxPowerMeas
        table
        "
	INDEX   { pm1008Mesrxfp1LiRxPowerMeasIndex }
	::= { pm1008Mesrxfp1LiRxPowerMeasTable 1 }


Pm1008Mesrxfp1LiRxPowerMeasEntry ::=
	SEQUENCE {
	pm1008Mesrxfp1LiRxPowerMeasIndex
		INTEGER,
	pm1008Mesrxfp1LiRxPowerMeasPortn
		INTEGER
	}


pm1008Mesrxfp1LiRxPowerMeasIndex OBJECT-TYPE
	SYNTAX  INTEGER(0..128)
	MAX-ACCESS  read-only
	STATUS current
	DESCRIPTION
        "
        Index definition for the pm1008Mesrxfp1LiRxPowerMeas
        table
        "
	::= { pm1008Mesrxfp1LiRxPowerMeasEntry 1 }


pm1008Mesrxfp1LiRxPowerMeasPortn OBJECT-TYPE
	SYNTAX  INTEGER (0..65535)
	MAX-ACCESS read-only
	STATUS current
	DESCRIPTION
        "
        Line Optical Module Rx Power :This
        OID gives the receive power value
        of the XFP or OTX plugged in line
        #n, read from the DDM (Digital
         Diagnostic Monitoring)  (Power
        = 10*log(AV)-40)  (Unit = dBm)
          <Help>  This measure gives the
        Rx optical power of the line transceiver
        "
	::= { pm1008Mesrxfp1LiRxPowerMeasEntry 2 }


--- *********************************************************
---     TABLE for the pm1008Mesrxfp1LxAux1Meas articles
--- *********************************************************

pm1008Mesrxfp1LxAux1MeasTable OBJECT-TYPE
	SYNTAX  SEQUENCE OF Pm1008Mesrxfp1LxAux1MeasEntry
	MAX-ACCESS not-accessible
	STATUS deprecated
	DESCRIPTION
        "
        List of pm1008Mesrxfp1LxAux1Meas
        Article
        "
	::= { pm1008MesrLine 213 }


pm1008Mesrxfp1LxAux1MeasEntry OBJECT-TYPE
	SYNTAX Pm1008Mesrxfp1LxAux1MeasEntry
	MAX-ACCESS not-accessible
	STATUS deprecated
	DESCRIPTION
        "
        Row definition for the pm1008Mesrxfp1LxAux1Meas
        table
        "
	INDEX   { pm1008Mesrxfp1LxAux1MeasIndex }
	::= { pm1008Mesrxfp1LxAux1MeasTable 1 }


Pm1008Mesrxfp1LxAux1MeasEntry ::=
	SEQUENCE {
	pm1008Mesrxfp1LxAux1MeasIndex
		INTEGER,
	pm1008Mesrxfp1LxAux1MeasPortn
		INTEGER
	}


pm1008Mesrxfp1LxAux1MeasIndex OBJECT-TYPE
	SYNTAX  INTEGER(0..128)
	MAX-ACCESS  read-only
	STATUS deprecated
	DESCRIPTION
        "
        Index definition for the pm1008Mesrxfp1LxAux1Meas
        table
        "
	::= { pm1008Mesrxfp1LxAux1MeasEntry 1 }


pm1008Mesrxfp1LxAux1MeasPortn OBJECT-TYPE
	SYNTAX  INTEGER (0..65535)
	MAX-ACCESS read-only
	STATUS deprecated
	DESCRIPTION
        "
        Not Used :This OID gives the receive
        power value read in the DDM (Digital
        Diagnostic Monitoring) of the XFP
        or OTX plugged in line #n (Unit
        = ?)
        "
	::= { pm1008Mesrxfp1LxAux1MeasEntry 2 }


--- *********************************************************
---     TABLE for the pm1008Mesrxfp1LxAux2Meas articles
--- *********************************************************

pm1008Mesrxfp1LxAux2MeasTable OBJECT-TYPE
	SYNTAX  SEQUENCE OF Pm1008Mesrxfp1LxAux2MeasEntry
	MAX-ACCESS not-accessible
	STATUS deprecated
	DESCRIPTION
        "
        List of pm1008Mesrxfp1LxAux2Meas
        Article
        "
	::= { pm1008MesrLine 214 }


pm1008Mesrxfp1LxAux2MeasEntry OBJECT-TYPE
	SYNTAX Pm1008Mesrxfp1LxAux2MeasEntry
	MAX-ACCESS not-accessible
	STATUS deprecated
	DESCRIPTION
        "
        Row definition for the pm1008Mesrxfp1LxAux2Meas
        table
        "
	INDEX   { pm1008Mesrxfp1LxAux2MeasIndex }
	::= { pm1008Mesrxfp1LxAux2MeasTable 1 }


Pm1008Mesrxfp1LxAux2MeasEntry ::=
	SEQUENCE {
	pm1008Mesrxfp1LxAux2MeasIndex
		INTEGER,
	pm1008Mesrxfp1LxAux2MeasPortn
		INTEGER
	}


pm1008Mesrxfp1LxAux2MeasIndex OBJECT-TYPE
	SYNTAX  INTEGER(0..128)
	MAX-ACCESS  read-only
	STATUS deprecated
	DESCRIPTION
        "
        Index definition for the pm1008Mesrxfp1LxAux2Meas
        table
        "
	::= { pm1008Mesrxfp1LxAux2MeasEntry 1 }


pm1008Mesrxfp1LxAux2MeasPortn OBJECT-TYPE
	SYNTAX  INTEGER (0..65535)
	MAX-ACCESS read-only
	STATUS deprecated
	DESCRIPTION
        "
        Not Used :This OID gives the receive
        power value read in the DDM (Digital
        Diagnostic Monitoring) of the XFP
        or OTX plugged in line #n (Unit
        = ?)
        "
	::= { pm1008Mesrxfp1LxAux2MeasEntry 2 }


--- *********************************************************
---     TABLE for the pm1008Mesrotx1Aging articles
--- *********************************************************

pm1008Mesrotx1AgingTable OBJECT-TYPE
	SYNTAX  SEQUENCE OF Pm1008Mesrotx1AgingEntry
	MAX-ACCESS not-accessible
	STATUS current
	DESCRIPTION
        "
        List of pm1008Mesrotx1Aging Article
        "
	::= { pm1008MesrLine 224 }


pm1008Mesrotx1AgingEntry OBJECT-TYPE
	SYNTAX Pm1008Mesrotx1AgingEntry
	MAX-ACCESS not-accessible
	STATUS current
	DESCRIPTION
        "
        Row definition for the pm1008Mesrotx1Aging
        table
        "
	INDEX   { pm1008Mesrotx1AgingIndex }
	::= { pm1008Mesrotx1AgingTable 1 }


Pm1008Mesrotx1AgingEntry ::=
	SEQUENCE {
	pm1008Mesrotx1AgingIndex
		INTEGER,
	pm1008Mesrotx1AgingPortn
		INTEGER
	}


pm1008Mesrotx1AgingIndex OBJECT-TYPE
	SYNTAX  INTEGER(0..128)
	MAX-ACCESS  read-only
	STATUS current
	DESCRIPTION
        "
        Index definition for the pm1008Mesrotx1Aging
        table
        "
	::= { pm1008Mesrotx1AgingEntry 1 }


pm1008Mesrotx1AgingPortn OBJECT-TYPE
	SYNTAX  INTEGER (0..65535)
	MAX-ACCESS read-only
	STATUS current
	DESCRIPTION
        "
        Line OTX TLH Aging :This OID gives
        the aging of the Line OTX TLH,
         read from the DDM (Digital Diagnostic
        Monitoring)   (Aging = AV) (Unit
        = %)  <Help>  This measure gives
        the aging of the Line OTX TLH
        "
	::= { pm1008Mesrotx1AgingEntry 2 }


--- *********************************************************
---     TABLE for the pm1008Mesrotx1LaserTemperature articles
--- *********************************************************

pm1008Mesrotx1LaserTemperatureTable OBJECT-TYPE
	SYNTAX  SEQUENCE OF Pm1008Mesrotx1LaserTemperatureEntry
	MAX-ACCESS not-accessible
	STATUS deprecated
	DESCRIPTION
        "
        List of pm1008Mesrotx1LaserTemperature
        Article
        "
	::= { pm1008MesrLine 225 }


pm1008Mesrotx1LaserTemperatureEntry OBJECT-TYPE
	SYNTAX Pm1008Mesrotx1LaserTemperatureEntry
	MAX-ACCESS not-accessible
	STATUS deprecated
	DESCRIPTION
        "
        Row definition for the pm1008Mesrotx1LaserTemperature
        table
        "
	INDEX   { pm1008Mesrotx1LaserTemperatureIndex }
	::= { pm1008Mesrotx1LaserTemperatureTable 1 }


Pm1008Mesrotx1LaserTemperatureEntry ::=
	SEQUENCE {
	pm1008Mesrotx1LaserTemperatureIndex
		INTEGER,
	pm1008Mesrotx1LaserTemperaturePortn
		INTEGER
	}


pm1008Mesrotx1LaserTemperatureIndex OBJECT-TYPE
	SYNTAX  INTEGER(0..128)
	MAX-ACCESS  read-only
	STATUS deprecated
	DESCRIPTION
        "
        Index definition for the pm1008Mesrotx1LaserTemperature
        table
        "
	::= { pm1008Mesrotx1LaserTemperatureEntry 1 }


pm1008Mesrotx1LaserTemperaturePortn OBJECT-TYPE
	SYNTAX  INTEGER (0..65535)
	MAX-ACCESS read-only
	STATUS deprecated
	DESCRIPTION
        "
        Line OTX TLH Laser Temperature
        :This OID gives the laser temperature
        of the Line OTX TLH, read from
         the DDM (Digital Diagnostic Monitoring)
        (Temperature = AV/256) (Unit =
         C)  <Help>  This measure gives
        the laser temperature of the Line
        OTX TLH
        "
	::= { pm1008Mesrotx1LaserTemperatureEntry 2 }


--- *********************************************************
---     TABLE for the pm1008Mesrotx1FreqDeviation articles
--- *********************************************************

pm1008Mesrotx1FreqDeviationTable OBJECT-TYPE
	SYNTAX  SEQUENCE OF Pm1008Mesrotx1FreqDeviationEntry
	MAX-ACCESS not-accessible
	STATUS current
	DESCRIPTION
        "
        List of pm1008Mesrotx1FreqDeviation
        Article
        "
	::= { pm1008MesrLine 226 }


pm1008Mesrotx1FreqDeviationEntry OBJECT-TYPE
	SYNTAX Pm1008Mesrotx1FreqDeviationEntry
	MAX-ACCESS not-accessible
	STATUS current
	DESCRIPTION
        "
        Row definition for the pm1008Mesrotx1FreqDeviation
        table
        "
	INDEX   { pm1008Mesrotx1FreqDeviationIndex }
	::= { pm1008Mesrotx1FreqDeviationTable 1 }


Pm1008Mesrotx1FreqDeviationEntry ::=
	SEQUENCE {
	pm1008Mesrotx1FreqDeviationIndex
		INTEGER,
	pm1008Mesrotx1FreqDeviationPortn
		INTEGER
	}


pm1008Mesrotx1FreqDeviationIndex OBJECT-TYPE
	SYNTAX  INTEGER(0..128)
	MAX-ACCESS  read-only
	STATUS current
	DESCRIPTION
        "
        Index definition for the pm1008Mesrotx1FreqDeviation
        table
        "
	::= { pm1008Mesrotx1FreqDeviationEntry 1 }


pm1008Mesrotx1FreqDeviationPortn OBJECT-TYPE
	SYNTAX  INTEGER (0..65535)
	MAX-ACCESS read-only
	STATUS current
	DESCRIPTION
        "
        Line OTX TLH Frequency Deviation
        :This OID gives the frequency deviation
        of the Line OTX TLH, read from
         the DDM (Digital Diagnostic Monitoring)
         (Deviation = (AV-32768)*100) (Unit
        = MHz)  <Help>  This measure gives
        the frequency deviation of the
         Line OTX TLH
        "
	::= { pm1008Mesrotx1FreqDeviationEntry 2 }


--- *********************************************************
---     TABLE for the pm1008Mesrotx1LaserWvlength articles
--- *********************************************************

pm1008Mesrotx1LaserWvlengthTable OBJECT-TYPE
	SYNTAX  SEQUENCE OF Pm1008Mesrotx1LaserWvlengthEntry
	MAX-ACCESS not-accessible
	STATUS current
	DESCRIPTION
        "
        List of pm1008Mesrotx1LaserWvlength
        Article
        "
	::= { pm1008MesrLine 227 }


pm1008Mesrotx1LaserWvlengthEntry OBJECT-TYPE
	SYNTAX Pm1008Mesrotx1LaserWvlengthEntry
	MAX-ACCESS not-accessible
	STATUS current
	DESCRIPTION
        "
        Row definition for the pm1008Mesrotx1LaserWvlength
        table
        "
	INDEX   { pm1008Mesrotx1LaserWvlengthIndex }
	::= { pm1008Mesrotx1LaserWvlengthTable 1 }


Pm1008Mesrotx1LaserWvlengthEntry ::=
	SEQUENCE {
	pm1008Mesrotx1LaserWvlengthIndex
		INTEGER,
	pm1008Mesrotx1LaserWvlengthPortn
		INTEGER
	}


pm1008Mesrotx1LaserWvlengthIndex OBJECT-TYPE
	SYNTAX  INTEGER(0..128)
	MAX-ACCESS  read-only
	STATUS current
	DESCRIPTION
        "
        Index definition for the pm1008Mesrotx1LaserWvlength
        table
        "
	::= { pm1008Mesrotx1LaserWvlengthEntry 1 }


pm1008Mesrotx1LaserWvlengthPortn OBJECT-TYPE
	SYNTAX  INTEGER (0..65535)
	MAX-ACCESS read-only
	STATUS current
	DESCRIPTION
        "
        Line Optical Module Wavelength
        :This OID gives the laser wavelength
        of the Line OTX TLH, read from
         the DDM (Digital Diagnostic Monitoring)
        (Wavelength=299792458/((193,100+(AV-32768
        )*12,5)*10 3)) (Unit = nm)  <Help>
         This measure gives the laser wavelength
        of the Line OTX TLH
        "
	::= { pm1008Mesrotx1LaserWvlengthEntry 2 }







--- *****************************************************
--- $$$$$$$$$$$$$$$$$$$$$$$$$$$$$$$$$$$$$$$$$$$$$$$$$$$$$
---     DOWNLOAD
--- $$$$$$$$$$$$$$$$$$$$$$$$$$$$$$$$$$$$$$$$$$$$$$$$$$$$$
--- *****************************************************



--- *****************************************************
---     LEAF for the restartProcess article
--- *****************************************************
pm1008DwlrestartProcess OBJECT IDENTIFIER ::= { pm1008DwlOther 0 }




pm1008DwlColdRestartProcessed OBJECT-TYPE
	  SYNTAX EkiOnOff
	  MAX-ACCESS read-only
	  STATUS current
	  DESCRIPTION
        "
        Cold Restart :This OID indicates
        that the module last restart was
        a Cold RESTART
        "
	  ::= { pm1008DwlrestartProcess 2 }



pm1008DwlWarmRestartProcessed OBJECT-TYPE
	  SYNTAX EkiOnOff
	  MAX-ACCESS read-only
	  STATUS current
	  DESCRIPTION
        "
        Warm Restart :This OID indicates
        that the module last restart was
        a Warm RESTART
        "
	  ::= { pm1008DwlrestartProcess 1 }



--- *****************************************************
---     LEAF for the swBanksUsed article
--- *****************************************************
pm1008DwlswBanksUsed OBJECT IDENTIFIER ::= { pm1008DwlOther 1 }




pm1008DwlSwBank2Notempty OBJECT-TYPE
	  SYNTAX EkiOnOff
	  MAX-ACCESS read-only
	  STATUS current
	  DESCRIPTION
        "
        SW bank 2 loaded :This OID indicates
        a software is loaded in SW bank
        2  <Help>  This status indicates
        if the SW bank 2 contains SW package
        "
	  ::= { pm1008DwlswBanksUsed 6 }



pm1008DwlSwBank1Notempty OBJECT-TYPE
	  SYNTAX EkiOnOff
	  MAX-ACCESS read-only
	  STATUS current
	  DESCRIPTION
        "
        SW bank 1 loaded :This OID indicates
        a software is loaded in SW bank
        1  <Help>  This status indicates
        if the SW bank 1 contains SW package
        "
	  ::= { pm1008DwlswBanksUsed 5 }



pm1008DwlSwBank2Used OBJECT-TYPE
	  SYNTAX EkiOnOff
	  MAX-ACCESS read-only
	  STATUS current
	  DESCRIPTION
        "
        SW bank 2 active :This OID indicates
        the module is working on SW bank
        2  <Help>  This status indicates
        if the SW bank 2 is active or standby
        "
	  ::= { pm1008DwlswBanksUsed 2 }



pm1008DwlSwBank1Used OBJECT-TYPE
	  SYNTAX EkiOnOff
	  MAX-ACCESS read-only
	  STATUS current
	  DESCRIPTION
        "
        SW bank 1 active :This OID indicates
        the module is working on SW bank
        1  <Help>  This status indicates
        if the SW bank 1 is active or standby
        "
	  ::= { pm1008DwlswBanksUsed 1 }



--- *****************************************************
---     LEAF for the gwBanksUsed article
--- *****************************************************
pm1008DwlgwBanksUsed OBJECT IDENTIFIER ::= { pm1008DwlOther 2 }




pm1008DwlGwBank4Notempty OBJECT-TYPE
	  SYNTAX EkiOnOff
	  MAX-ACCESS read-only
	  STATUS current
	  DESCRIPTION
        "
        GW bank 4 loaded :This OID indicates
        a gateware is loaded in GW bank
        4
        "
	  ::= { pm1008DwlgwBanksUsed 8 }



pm1008DwlGwBank3Notempty OBJECT-TYPE
	  SYNTAX EkiOnOff
	  MAX-ACCESS read-only
	  STATUS current
	  DESCRIPTION
        "
        GW bank 3 loaded :This OID indicates
        a gateware is loaded in GW bank
        3  <Help>  This status indicates
        if the GW bank 3 contains GW package
        "
	  ::= { pm1008DwlgwBanksUsed 7 }



pm1008DwlGwBank2Notempty OBJECT-TYPE
	  SYNTAX EkiOnOff
	  MAX-ACCESS read-only
	  STATUS current
	  DESCRIPTION
        "
        GW bank 2 loaded :This OID indicates
        a gateware is loaded in GW bank
        2
        "
	  ::= { pm1008DwlgwBanksUsed 6 }



pm1008DwlGwBank1Notempty OBJECT-TYPE
	  SYNTAX EkiOnOff
	  MAX-ACCESS read-only
	  STATUS current
	  DESCRIPTION
        "
        GW bank 1 loaded :This OID indicates
        a gateware is loaded in GW bank
        1  <Help>  This status indicates
        if the GW bank 1 contains GW package
        "
	  ::= { pm1008DwlgwBanksUsed 5 }



pm1008DwlGwBank4Used OBJECT-TYPE
	  SYNTAX EkiOnOff
	  MAX-ACCESS read-only
	  STATUS current
	  DESCRIPTION
        "
        GW bank 4 active :This OID indicates
        the module is working on GW bank
        4
        "
	  ::= { pm1008DwlgwBanksUsed 4 }



pm1008DwlGwBank3Used OBJECT-TYPE
	  SYNTAX EkiOnOff
	  MAX-ACCESS read-only
	  STATUS current
	  DESCRIPTION
        "
        GW bank 3 active :This OID indicates
        the module is working on GW bank
        3  <Help>  This status indicates
        if the GW bank 3 is active or standby
        "
	  ::= { pm1008DwlgwBanksUsed 3 }



pm1008DwlGwBank2Used OBJECT-TYPE
	  SYNTAX EkiOnOff
	  MAX-ACCESS read-only
	  STATUS current
	  DESCRIPTION
        "
        GW bank 2 active :This OID indicates
        the module is working on GW bank
        2
        "
	  ::= { pm1008DwlgwBanksUsed 2 }



pm1008DwlGwBank1Used OBJECT-TYPE
	  SYNTAX EkiOnOff
	  MAX-ACCESS read-only
	  STATUS current
	  DESCRIPTION
        "
        GW bank 1 active :This OID indicates
        the module is working on GW bank
        1  <Help>  This status indicates
        if the GW bank 1 is active or standby
        "
	  ::= { pm1008DwlgwBanksUsed 1 }








--- *****************************************************
--- $$$$$$$$$$$$$$$$$$$$$$$$$$$$$$$$$$$$$$$$$$$$$$$$$$$$$
---     CONFIG
--- $$$$$$$$$$$$$$$$$$$$$$$$$$$$$$$$$$$$$$$$$$$$$$$$$$$$$
--- *****************************************************



--- *****************************************************
---     LEAF for the table Group accessCAisCsf
--- *****************************************************

pm1008CfgAccessCAisCsf OBJECT IDENTIFIER ::= { pm1008Config 1 }



--- *****************************************************
---     LEAF for the table 0012
--- *****************************************************

pm1008CfgClientcaiscsfTable OBJECT-TYPE
	SYNTAX  SEQUENCE OF Pm1008CfgClientcaiscsfEntry
	MAX-ACCESS not-accessible
	STATUS current
	DESCRIPTION
        "
        List of  Article
        "
	::= { pm1008CfgAccessCAisCsf 1 }


pm1008CfgClientcaiscsfEntry OBJECT-TYPE
	SYNTAX Pm1008CfgClientcaiscsfEntry
	MAX-ACCESS not-accessible
	STATUS current
	DESCRIPTION
        "
        Row definition for the accessCAisCsf
        table
        "
	INDEX   { pm1008CfgClientcaiscsfIndex }
	::= { pm1008CfgClientcaiscsfTable 1 }


Pm1008CfgClientcaiscsfEntry ::=
	SEQUENCE {
	pm1008CfgClientcaiscsfIndex
		INTEGER,
	pm1008CfgCAisModePortn
		Unsigned32,
	pm1008CfgUpAccessioAlmPortn
		Unsigned32,
	pm1008CfgUpMapperDeAlmPortn
		Unsigned32,
	pm1008CfgDownAccessioAlmPortn
		Unsigned32,
	pm1008CfgDownMapperDeAlmPortn
		Unsigned32,
	pm1008CfgDownDfrmAlmPortn
		Unsigned32,
	pm1008CfgDownLineSyncAlarmsPortn
		Unsigned32
	}


pm1008CfgClientcaiscsfIndex OBJECT-TYPE
	SYNTAX  INTEGER(0..128)
	MAX-ACCESS  read-only
	STATUS current
	DESCRIPTION
        "
        Index definition for the clientcaiscsf
        table
        "
	::= { pm1008CfgClientcaiscsfEntry 1 }


pm1008CfgCAisModePortn OBJECT-TYPE
	SYNTAX  Unsigned32 (0..65536)
	MAX-ACCESS read-write
	STATUS current
	DESCRIPTION
        "
        CAIS mode  on Client Port :This
        register enables/disables port
          laser shutdown on CAIS insertion
        condition
        "
	::= { pm1008CfgClientcaiscsfEntry 3 }


pm1008CfgUpAccessioAlmPortn OBJECT-TYPE
	SYNTAX  Unsigned32 (0..65536)
	MAX-ACCESS read-write
	STATUS current
	DESCRIPTION
        "
        CSF contributors on Client Port
        :This register configures the contributors
        to upstream CSF insertion on the
        port.
        "
	::= { pm1008CfgClientcaiscsfEntry 9 }


pm1008CfgUpMapperDeAlmPortn OBJECT-TYPE
	SYNTAX  Unsigned32 (0..65536)
	MAX-ACCESS read-write
	STATUS current
	DESCRIPTION
        "
        CSF contributors on Client Port
        :This register configures the contributors
        to upstream CSF insertion on the
        port.
        "
	::= { pm1008CfgClientcaiscsfEntry 10 }


pm1008CfgDownAccessioAlmPortn OBJECT-TYPE
	SYNTAX  Unsigned32 (0..65536)
	MAX-ACCESS read-write
	STATUS current
	DESCRIPTION
        "
        CAIS contributors on Client Port
        :This register configures the contributors
        to downstream CAIS insertion on
         port.
        "
	::= { pm1008CfgClientcaiscsfEntry 17 }


pm1008CfgDownMapperDeAlmPortn OBJECT-TYPE
	SYNTAX  Unsigned32 (0..65536)
	MAX-ACCESS read-write
	STATUS current
	DESCRIPTION
        "
        CAIS contributors on Client Port
        :This register configures the contributors
        to downstream CAIS insertion on
         port.
        "
	::= { pm1008CfgClientcaiscsfEntry 18 }


pm1008CfgDownDfrmAlmPortn OBJECT-TYPE
	SYNTAX  Unsigned32 (0..65536)
	MAX-ACCESS read-write
	STATUS current
	DESCRIPTION
        "
        CAIS contributors on Client Port
        :This register configures the contributors
        to downstream CAIS insertion on
         port.
        "
	::= { pm1008CfgClientcaiscsfEntry 19 }


pm1008CfgDownLineSyncAlarmsPortn OBJECT-TYPE
	SYNTAX  Unsigned32 (0..65536)
	MAX-ACCESS read-write
	STATUS deprecated
	DESCRIPTION
        "
        CAIS contributors on Client Port
        :This register configures the contributors
        to downstream CAIS insertion on
         port.
        "
	::= { pm1008CfgClientcaiscsfEntry 20 }


--- *****************************************************
---     LEAF for the table Group startup
--- *****************************************************

pm1008CfgStartup OBJECT IDENTIFIER ::= { pm1008Config 2 }



--- *****************************************************
---     LEAF for the table 2111
--- *****************************************************

pm1008CfgClientStartupTable OBJECT-TYPE
	SYNTAX  SEQUENCE OF Pm1008CfgClientStartupEntry
	MAX-ACCESS not-accessible
	STATUS current
	DESCRIPTION
        "
        List of  Article
        "
	::= { pm1008CfgStartup 1 }


pm1008CfgClientStartupEntry OBJECT-TYPE
	SYNTAX Pm1008CfgClientStartupEntry
	MAX-ACCESS not-accessible
	STATUS current
	DESCRIPTION
        "
        Row definition for the startup
        table
        "
	INDEX   { pm1008CfgClientStartupIndex }
	::= { pm1008CfgClientStartupTable 1 }


Pm1008CfgClientStartupEntry ::=
	SEQUENCE {
	pm1008CfgClientStartupIndex
		INTEGER,
	pm1008CfgSystConfPortPortn
		Unsigned32,
	pm1008CfgNetConfPortPortn
		Unsigned32,
	pm1008CfgOptionsPortPortn
		Unsigned32
	}


pm1008CfgClientStartupIndex OBJECT-TYPE
	SYNTAX  INTEGER(0..128)
	MAX-ACCESS  read-only
	STATUS current
	DESCRIPTION
        "
        Index definition for the clientStartup
        table
        "
	::= { pm1008CfgClientStartupEntry 1 }


pm1008CfgSystConfPortPortn OBJECT-TYPE
	SYNTAX  Unsigned32 (0..65536)
	MAX-ACCESS read-write
	STATUS current
	DESCRIPTION
        "
        Default Settings on Client Port
        :This  register configures the
         default initialisation settings
        on the port.
        "
	::= { pm1008CfgClientStartupEntry 3 }


pm1008CfgNetConfPortPortn OBJECT-TYPE
	SYNTAX  Unsigned32 (0..65536)
	MAX-ACCESS read-write
	STATUS current
	DESCRIPTION
        "
        Default Protocol on Client Port
        :This register configures the default
        initialisation protocol on the
         port.
        "
	::= { pm1008CfgClientStartupEntry 4 }


pm1008CfgOptionsPortPortn OBJECT-TYPE
	SYNTAX  Unsigned32 (0..65536)
	MAX-ACCESS read-write
	STATUS current
	DESCRIPTION
        "
        Default Options on Client Port
        :This register configures the default
        options on the port.
        "
	::= { pm1008CfgClientStartupEntry 6 }


--- *****************************************************
---     LEAF for the table 2191
--- *****************************************************

pm1008tablelineStartup OBJECT IDENTIFIER ::= { pm1008CfgStartup 2 }



pm1008CfgsystConfLine1 OBJECT-TYPE
	  SYNTAX Unsigned32 (0..65536)
	  MAX-ACCESS read-write
	  STATUS current
	  DESCRIPTION
        "
        Default Settings on Line 1 :This
        register configures the default
        initialisation settings on Line
        port 1.
        "
	  ::= { pm1008tablelineStartup 2 }



pm1008CfglineOptions1 OBJECT-TYPE
	  SYNTAX Unsigned32 (0..65536)
	  MAX-ACCESS read-write
	  STATUS current
	  DESCRIPTION
        "
        Default Options on Active Line
        Port :This register configures
         the default options on the active
        line port
        "
	  ::= { pm1008tablelineStartup 5 }



pm1008CfgsystConfLine2 OBJECT-TYPE
	  SYNTAX Unsigned32 (0..65536)
	  MAX-ACCESS read-write
	  STATUS current
	  DESCRIPTION
        "
        Default Settings on Line 2 :This
        register configures the default
        initialisation settings on Line
        port 2.
        "
	  ::= { pm1008tablelineStartup 6 }



pm1008CfglineSelection OBJECT-TYPE
	  SYNTAX Unsigned32 (0..65536)
	  MAX-ACCESS read-write
	  STATUS current
	  DESCRIPTION
        "
        Default Settings of active line
        :This  register configures the
         start up active line.
        "
	  ::= { pm1008tablelineStartup 7 }



--- *****************************************************
---     LEAF for the table 21AB
--- *****************************************************

pm1008CfgXfpTable OBJECT-TYPE
	SYNTAX  SEQUENCE OF Pm1008CfgXfpEntry
	MAX-ACCESS not-accessible
	STATUS current
	DESCRIPTION
        "
        List of  Article
        "
	::= { pm1008CfgStartup 3 }


pm1008CfgXfpEntry OBJECT-TYPE
	SYNTAX Pm1008CfgXfpEntry
	MAX-ACCESS not-accessible
	STATUS current
	DESCRIPTION
        "
        Row definition for the startup
        table
        "
	INDEX   { pm1008CfgXfpIndex }
	::= { pm1008CfgXfpTable 1 }


Pm1008CfgXfpEntry ::=
	SEQUENCE {
	pm1008CfgXfpIndex
		INTEGER,
	pm1008CfgSystConfXfpPortn
		Unsigned32,
	pm1008CfgDataRateConfXfpPortn
		Unsigned32
	}


pm1008CfgXfpIndex OBJECT-TYPE
	SYNTAX  INTEGER(0..128)
	MAX-ACCESS  read-only
	STATUS current
	DESCRIPTION
        "
        Index definition for the xfp table
        "
	::= { pm1008CfgXfpEntry 1 }


pm1008CfgSystConfXfpPortn OBJECT-TYPE
	SYNTAX  Unsigned32 (0..65536)
	MAX-ACCESS read-write
	STATUS current
	DESCRIPTION
        "
        Default settings on XFP Port :This
        register configures the default
        initialisation settings on XFP
         port.
        "
	::= { pm1008CfgXfpEntry 3 }


pm1008CfgDataRateConfXfpPortn OBJECT-TYPE
	SYNTAX  Unsigned32 (0..65536)
	MAX-ACCESS read-write
	STATUS deprecated
	DESCRIPTION
        "
        :Reserved
        "
	::= { pm1008CfgXfpEntry 4 }


--- *****************************************************
---     LEAF for the table Group labels
--- *****************************************************

pm1008CfgLabels OBJECT IDENTIFIER ::= { pm1008Config 3 }



--- *****************************************************
---     LEAF for the table NO_VALUE
--- *****************************************************

pm1008CfgLabelclientTable OBJECT-TYPE
	SYNTAX  SEQUENCE OF Pm1008CfgLabelclientEntry
	MAX-ACCESS not-accessible
	STATUS current
	DESCRIPTION
        "
        List of  Article
        "
	::= { pm1008CfgLabels 1 }


pm1008CfgLabelclientEntry OBJECT-TYPE
	SYNTAX Pm1008CfgLabelclientEntry
	MAX-ACCESS not-accessible
	STATUS current
	DESCRIPTION
        "
        Row definition for the labels
         table
        "
	INDEX   { pm1008CfgLabelclientIndex }
	::= { pm1008CfgLabelclientTable 1 }


Pm1008CfgLabelclientEntry ::=
	SEQUENCE {
	pm1008CfgLabelclientIndex
		INTEGER,
	pm1008CfgLabelclientPortn
		DisplayString
	}


pm1008CfgLabelclientIndex OBJECT-TYPE
	SYNTAX  INTEGER(0..128)
	MAX-ACCESS  read-only
	STATUS current
	DESCRIPTION
        "
        Index definition for the labelclient
        table
        "
	::= { pm1008CfgLabelclientEntry 1 }


pm1008CfgLabelclientPortn OBJECT-TYPE
	SYNTAX  DisplayString( SIZE(1..16))
	MAX-ACCESS read-write
	STATUS current
	DESCRIPTION
        "
        Default settings on the label
         of the Ports :These registers
         configures the default initialisation
        settings of the labels of the ports.
        "
	::= { pm1008CfgLabelclientEntry 3 }


--- *****************************************************
---     LEAF for the table NO_VALUE
--- *****************************************************

pm1008CfgLabellineTable OBJECT-TYPE
	SYNTAX  SEQUENCE OF Pm1008CfgLabellineEntry
	MAX-ACCESS not-accessible
	STATUS current
	DESCRIPTION
        "
        List of  Article
        "
	::= { pm1008CfgLabels 2 }


pm1008CfgLabellineEntry OBJECT-TYPE
	SYNTAX Pm1008CfgLabellineEntry
	MAX-ACCESS not-accessible
	STATUS current
	DESCRIPTION
        "
        Row definition for the labels
         table
        "
	INDEX   { pm1008CfgLabellineIndex }
	::= { pm1008CfgLabellineTable 1 }


Pm1008CfgLabellineEntry ::=
	SEQUENCE {
	pm1008CfgLabellineIndex
		INTEGER,
	pm1008CfgLabellinePortn
		DisplayString
	}


pm1008CfgLabellineIndex OBJECT-TYPE
	SYNTAX  INTEGER(0..128)
	MAX-ACCESS  read-only
	STATUS current
	DESCRIPTION
        "
        Index definition for the labelline
        table
        "
	::= { pm1008CfgLabellineEntry 1 }


pm1008CfgLabellinePortn OBJECT-TYPE
	SYNTAX  DisplayString( SIZE(1..16))
	MAX-ACCESS read-write
	STATUS current
	DESCRIPTION
        "
        Default settings on the label
         of the lines :These registers
         configures the default initialisation
        settings of the labels of the lines.
        "
	::= { pm1008CfgLabellineEntry 3 }


--- *****************************************************
---     LEAF for the table Group startuptlh
--- *****************************************************

pm1008CfgStartuptlh OBJECT IDENTIFIER ::= { pm1008Config 4 }



--- *****************************************************
---     LEAF for the table 25A8
--- *****************************************************

pm1008CfgOtxtlhTable OBJECT-TYPE
	SYNTAX  SEQUENCE OF Pm1008CfgOtxtlhEntry
	MAX-ACCESS not-accessible
	STATUS current
	DESCRIPTION
        "
        List of  Article
        "
	::= { pm1008CfgStartuptlh 1 }


pm1008CfgOtxtlhEntry OBJECT-TYPE
	SYNTAX Pm1008CfgOtxtlhEntry
	MAX-ACCESS not-accessible
	STATUS current
	DESCRIPTION
        "
        Row definition for the startuptlh
        table
        "
	INDEX   { pm1008CfgOtxtlhIndex }
	::= { pm1008CfgOtxtlhTable 1 }


Pm1008CfgOtxtlhEntry ::=
	SEQUENCE {
	pm1008CfgOtxtlhIndex
		INTEGER,
	pm1008CfgNuPortn
		Unsigned32,
	pm1008CfgLineDitherRatePortn
		Unsigned32,
	pm1008CfgLineDitherFhzPortn
		Unsigned32,
	pm1008CfgLinePwrLaserPortn
		Unsigned32,
	pm1008CfgLineFCurrentPortn
		Unsigned32,
	pm1008CfgLineGridCurrentPortn
		Unsigned32,
	pm1008CfgFPortn
		Unsigned32,
	pm1008CfgReservedPortn
		Unsigned32,
	pm1008CfgLinePhotodiodeModePortn
		Unsigned32,
	pm1008CfgLinePhotodiodeValuePortn
		Unsigned32
	}


pm1008CfgOtxtlhIndex OBJECT-TYPE
	SYNTAX  INTEGER(0..128)
	MAX-ACCESS  read-only
	STATUS current
	DESCRIPTION
        "
        Index definition for the otxtlh
        table
        "
	::= { pm1008CfgOtxtlhEntry 1 }


pm1008CfgNuPortn OBJECT-TYPE
	SYNTAX  Unsigned32 (0..65536)
	MAX-ACCESS read-write
	STATUS deprecated
	DESCRIPTION
        "
        :
        "
	::= { pm1008CfgOtxtlhEntry 3 }


pm1008CfgLineDitherRatePortn OBJECT-TYPE
	SYNTAX  Unsigned32 (0..65536)
	MAX-ACCESS read-write
	STATUS current
	DESCRIPTION
        "
        Default Line OTX TLH FM amplitude
        :This register configures the start-up
        width of the frequency modulation
        of the Line OTX TLH
        "
	::= { pm1008CfgOtxtlhEntry 4 }


pm1008CfgLineDitherFhzPortn OBJECT-TYPE
	SYNTAX  Unsigned32 (0..65536)
	MAX-ACCESS read-write
	STATUS current
	DESCRIPTION
        "
        Default Line OTX TLH FM frequency
        :This register configures the start-up
        frequency of the frequency modulation
        of the Line OTX TLH
        "
	::= { pm1008CfgOtxtlhEntry 5 }


pm1008CfgLinePwrLaserPortn OBJECT-TYPE
	SYNTAX  Unsigned32 (0..65536)
	MAX-ACCESS read-write
	STATUS current
	DESCRIPTION
        "
        Defaut Line OTX TLH output Power
        :This register configures the start-up
        output power of the Line OTX TLH
         (Unit = dBm)
        "
	::= { pm1008CfgOtxtlhEntry 6 }


pm1008CfgLineFCurrentPortn OBJECT-TYPE
	SYNTAX  Unsigned32 (0..65536)
	MAX-ACCESS read-write
	STATUS current
	DESCRIPTION
        "
        Default Line OTX TLH Channel :This
        register configures the start-up
        laser channel of the Line OTX TLH
        "
	::= { pm1008CfgOtxtlhEntry 7 }


pm1008CfgLineGridCurrentPortn OBJECT-TYPE
	SYNTAX  Unsigned32 (0..65536)
	MAX-ACCESS read-write
	STATUS current
	DESCRIPTION
        "
        Default Line OTX TLH Grid :This
        register configures the start-up
        laser grid of the Line OTX TLH
        "
	::= { pm1008CfgOtxtlhEntry 8 }


pm1008CfgFPortn OBJECT-TYPE
	SYNTAX  Unsigned32 (0..65536)
	MAX-ACCESS read-write
	STATUS current
	DESCRIPTION
        "
        Default Line OTX TLH lowest Freq
        :This register configures the start-up
        lowest frequency supported on the
        Line OTX TLH
        "
	::= { pm1008CfgOtxtlhEntry 9 }


pm1008CfgReservedPortn OBJECT-TYPE
	SYNTAX  Unsigned32 (0..65536)
	MAX-ACCESS read-write
	STATUS deprecated
	DESCRIPTION
        "
        :
        "
	::= { pm1008CfgOtxtlhEntry 10 }


pm1008CfgLinePhotodiodeModePortn OBJECT-TYPE
	SYNTAX  Unsigned32 (0..65536)
	MAX-ACCESS read-write
	STATUS current
	DESCRIPTION
        "
        Default Line OTX TLH APD mode
         :This register configures the
         start-up APD mode of the Line
         OTX TLH
        "
	::= { pm1008CfgOtxtlhEntry 11 }


pm1008CfgLinePhotodiodeValuePortn OBJECT-TYPE
	SYNTAX  Unsigned32 (0..65536)
	MAX-ACCESS read-write
	STATUS current
	DESCRIPTION
        "
        Default Line OTX TLH APD atten.
        :This register configures the start-up
        APD attenuation on the Line OTX
        TLH
        "
	::= { pm1008CfgOtxtlhEntry 12 }


--- *****************************************************
---     LEAF for the table Group startuptablefive
--- *****************************************************

pm1008CfgStartuptablefive OBJECT IDENTIFIER ::= { pm1008Config 5 }



--- *****************************************************
---     LEAF for the table 0005
--- *****************************************************

pm1008CfgOtxtlhcapabilitiesTable OBJECT-TYPE
	SYNTAX  SEQUENCE OF Pm1008CfgOtxtlhcapabilitiesEntry
	MAX-ACCESS not-accessible
	STATUS current
	DESCRIPTION
        "
        List of  Article
        "
	::= { pm1008CfgStartuptablefive 1 }


pm1008CfgOtxtlhcapabilitiesEntry OBJECT-TYPE
	SYNTAX Pm1008CfgOtxtlhcapabilitiesEntry
	MAX-ACCESS not-accessible
	STATUS current
	DESCRIPTION
        "
        Row definition for the startuptablefive
        table
        "
	INDEX   { pm1008CfgOtxtlhcapabilitiesIndex }
	::= { pm1008CfgOtxtlhcapabilitiesTable 1 }


Pm1008CfgOtxtlhcapabilitiesEntry ::=
	SEQUENCE {
	pm1008CfgOtxtlhcapabilitiesIndex
		INTEGER,
	pm1008CfgComponentTypePortn
		Unsigned32,
	pm1008CfgMiscellaneousPortn
		Unsigned32,
	pm1008CfgFirstChannelPortn
		Unsigned32,
	pm1008CfgLastChannelPortn
		Unsigned32,
	pm1008CfgGridPortn
		Unsigned32
	}


pm1008CfgOtxtlhcapabilitiesIndex OBJECT-TYPE
	SYNTAX  INTEGER(0..128)
	MAX-ACCESS  read-only
	STATUS current
	DESCRIPTION
        "
        Index definition for the otxtlhcapabilities
        table
        "
	::= { pm1008CfgOtxtlhcapabilitiesEntry 1 }


pm1008CfgComponentTypePortn OBJECT-TYPE
	SYNTAX  Unsigned32 (0..65536)
	MAX-ACCESS read-only
	STATUS current
	DESCRIPTION
        "
        Component parameters :This OID
        defines the component parameters
        "
	::= { pm1008CfgOtxtlhcapabilitiesEntry 3 }


pm1008CfgMiscellaneousPortn OBJECT-TYPE
	SYNTAX  Unsigned32 (0..65536)
	MAX-ACCESS read-only
	STATUS current
	DESCRIPTION
        "
        Miscellaneous default settings
        :This OID defines the miscellaneous
        parameters
        "
	::= { pm1008CfgOtxtlhcapabilitiesEntry 4 }


pm1008CfgFirstChannelPortn OBJECT-TYPE
	SYNTAX  Unsigned32 (0..65536)
	MAX-ACCESS read-only
	STATUS current
	DESCRIPTION
        "
        Number of the first channel of
        the component :This OID defines
        the first channel number of the
        PM
        "
	::= { pm1008CfgOtxtlhcapabilitiesEntry 5 }


pm1008CfgLastChannelPortn OBJECT-TYPE
	SYNTAX  Unsigned32 (0..65536)
	MAX-ACCESS read-only
	STATUS current
	DESCRIPTION
        "
        Number of the last channel of
         the component :This OID defines
        the last channel number of the
         PM
        "
	::= { pm1008CfgOtxtlhcapabilitiesEntry 6 }


pm1008CfgGridPortn OBJECT-TYPE
	SYNTAX  Unsigned32 (0..65536)
	MAX-ACCESS read-only
	STATUS current
	DESCRIPTION
        "
        Grid value of the component :This
        OID defines the grid of the PM
        "
	::= { pm1008CfgOtxtlhcapabilitiesEntry 7 }



pm1008CfgWriteConfiguration  OBJECT-TYPE
	SYNTAX EkiOnOff
	MAX-ACCESS read-write
	STATUS current
	DESCRIPTION
	"Write configuration to module:This OID
	 writes the complete configuration to the module"
	::= { pm1008Config 257 }






--- *****************************************************
---     TRAP OBJECTS
--- *****************************************************

pm1008trapPortNumber OBJECT-TYPE
	SYNTAX INTEGER(1..64)
	MAX-ACCESS read-only
	STATUS current
	DESCRIPTION
	"Last port which generates a trap"
	::= { pm1008traps 2 }

pm1008trapLineNumber OBJECT-TYPE
	SYNTAX INTEGER(1..64)
	MAX-ACCESS read-only
	STATUS current
	DESCRIPTION
	"Last Line which generates a trap"
	::= { pm1008traps 3 }

pm1008trapBoardNumber OBJECT-TYPE
	SYNTAX INTEGER(1..64)
	MAX-ACCESS read-only
	STATUS current
	DESCRIPTION
	"Last module which generates a trap"
	::= { pm1008traps 4 }







--- *****************************************************
---     LINE TRAPS
--- *****************************************************

pm1008LineTrapNotUrgentGoesOn NOTIFICATION-TYPE
	OBJECTS {pm1008AlmLineDdmWarningPortn, pm1008trapLineNumber, pm1008trapBoardNumber}
	STATUS current
	--&FILTNAME    "PM1008 Line Not Urgent ON"
	--&ACTIONS     { log, minor }
	--&MATCH       { pm1008AlmLineDdmWarningPortn "on", pm1008trapLineNumber "$2", pm1008trapBoardNumber "$3"}
	--&MESG        "DDM Warning appears on Line Port $2 of PM1008(LH) in Slot $3 ($A)"
	DESCRIPTION "Not urgent Line default is activated"
	::= { pm1008traps 30 }

pm1008LineTrapNotUrgentGoesOff NOTIFICATION-TYPE
	OBJECTS {pm1008AlmLineDdmWarningPortn, pm1008trapLineNumber, pm1008trapBoardNumber}
	STATUS current
	--&FILTNAME    "PM1008 Line Not Urgent OFF"
	--&ACTIONS     { log, normal }
	--&CLEARS      { "PM1008 Line Not Urgent ON" }
	--&MATCH       { pm1008AlmLineDdmWarningPortn "on", pm1008trapLineNumber "$2", pm1008trapBoardNumber "$3"}
	--&MESG        "DDM Warning disappears on Line Port $2 of PM1008(LH) in Slot $3 ($A)"
	DESCRIPTION "Not urgent Line default disappeared"
	::= { pm1008traps 31 }

pm1008LineTrapUrgentGoesOn NOTIFICATION-TYPE
	OBJECTS {pm1008AlmLineDdmAlmPortn, pm1008trapLineNumber, pm1008trapBoardNumber}
	STATUS current
	--&FILTNAME    "PM1008 Line Urgent ON"
	--&ACTIONS     { log, major }
	--&MATCH       { pm1008AlmLineDdmAlmPortn "on", pm1008trapLineNumber "$2", pm1008trapBoardNumber "$3"}
	--&MESG        "DDM Alarm appears on Line Port $2 of PM1008(LH) in Slot $3 ($A)"
	DESCRIPTION "Urgent Line default is activated"
	::= { pm1008traps 32 }

pm1008LineTrapUrgentGoesOff NOTIFICATION-TYPE
	OBJECTS {pm1008AlmLineDdmAlmPortn, pm1008trapLineNumber, pm1008trapBoardNumber}
	STATUS current
	--&FILTNAME    "PM1008 Line Urgent OFF"
	--&ACTIONS     { log, normal }
	--&CLEARS      { "PM1008 Line Urgent ON" }
	--&MATCH       { pm1008AlmLineDdmAlmPortn "on", pm1008trapLineNumber "$2", pm1008trapBoardNumber "$3"}
	--&MESG        "DDM Alarm disappears on Line Port $2 of PM1008(LH) in Slot $3 ($A)"
	DESCRIPTION "Urgent Line default disappeared"
	::= { pm1008traps 33 }

pm1008LineTrapCritGoesOn NOTIFICATION-TYPE
	OBJECTS {pm1008AlmLineFailPortn , pm1008AlmLineHwFailPortn , pm1008trapLineNumber, pm1008trapBoardNumber}
	STATUS current
	--&FILTNAME    "PM1008 Line Fail ON"
	--&ACTIONS     { log, critical }
	--&MATCH       { pm1008AlmLineFailPortn "on", pm1008AlmLineHwFailPortn "*", pm1008trapLineNumber "$3", pm1008trapBoardNumber "$4"}
	--&MESG        "Line Port $3 Down on PM1008(LH) in Slot $4 ($A)"

	--&FILTNAME    "PM1008 Line HW Fail ON (Hidden)"
	--&ACTIONS     { info }
	--&MATCH       { pm1008AlmLineFailPortn "*", pm1008AlmLineHwFailPortn "on", pm1008trapLineNumber "$3", pm1008trapBoardNumber "$4"}
	--&MESG        "Line Port $3 Down on PM1008(LH) in Slot $4 ($A)"
	DESCRIPTION "Critical Line default is activated"
	::= { pm1008traps 34 }

pm1008LineTrapCritGoesOff NOTIFICATION-TYPE
	OBJECTS {pm1008AlmLineFailPortn , pm1008AlmLineHwFailPortn , pm1008trapLineNumber, pm1008trapBoardNumber}
	STATUS current
	--&FILTNAME    "PM1008 Line Fail OFF"
	--&ACTIONS     { log,  normal }
	--&CLEARS      { "PM1008 Line Fail ON" }
	--&MATCH       { pm1008AlmLineFailPortn "on", pm1008AlmLineHwFailPortn "*", pm1008trapLineNumber "$3", pm1008trapBoardNumber "$4"}
	--&MESG        "Line Port $3 Up on PM1008(LH) in Slot $4 ($A)"

	--&FILTNAME    "PM1008 Line HW Fail OFF (Hidden)"
	--&ACTIONS     { info }
	--&MATCH       { pm1008AlmLineFailPortn "*", pm1008AlmLineHwFailPortn "on", pm1008trapLineNumber "$3", pm1008trapBoardNumber "$4"}
	--&MESG        "Line Port $3 Up on PM1008(LH) in Slot $4 ($A)"
	DESCRIPTION "Critical Line default disappeared"
	::= { pm1008traps 35 }






--- *****************************************************
---     CLIENT TRAPS
--- *****************************************************

pm1008ClientTrapNotUrgentGoesOn NOTIFICATION-TYPE
	OBJECTS {pm1008AlmSfpDdmWarningPortn, pm1008trapPortNumber, pm1008trapBoardNumber}
	STATUS current
	--&FILTNAME    "PM1008 Client Not Urgent ON"
	--&ACTIONS     { log, minor }
	--&MATCH       { pm1008AlmSfpDdmWarningPortn "on", pm1008trapPortNumber "$2", pm1008trapBoardNumber "$3"}
	--&MESG        "DDM Warning appears on Client Port $2 of PM1008(LH) in Slot $3 ($A)"
	DESCRIPTION "Not urgent client default is activated"
	::= { pm1008traps 40 }

pm1008ClientTrapNotUrgentGoesOff NOTIFICATION-TYPE
	OBJECTS {pm1008AlmSfpDdmWarningPortn, pm1008trapPortNumber, pm1008trapBoardNumber}
	STATUS current
	--&FILTNAME    "PM1008 Client Not Urgent OFF"
	--&ACTIONS     { log, normal }
	--&CLEARS      { "PM1008 Client Not Urgent ON" }
	--&MATCH       { pm1008AlmSfpDdmWarningPortn "on", pm1008trapPortNumber "$2", pm1008trapBoardNumber "$3"}
	--&MESG        "DDM Warning appears on Client Port $2 of PM1008(LH) in Slot $3 ($A)"
	DESCRIPTION "Not urgent client default disappeared"
	::= { pm1008traps 41 }

pm1008ClientTrapUrgentGoesOn NOTIFICATION-TYPE
	OBJECTS {pm1008AlmSfpDdmAlmPortn, pm1008trapPortNumber, pm1008trapBoardNumber}
	STATUS current
	--&FILTNAME    "PM1008 Client Urgent ON"
	--&ACTIONS     { log, major }
	--&MATCH       { pm1008AlmSfpDdmAlmPortn "on", pm1008trapPortNumber "$2", pm1008trapBoardNumber "$3"}
	--&MESG        "DDM Alarm appears on Client Port $2 of PM1008(LH) in Slot $3 ($A)"
	DESCRIPTION "Urgent client default is activated"
	::= { pm1008traps 42 }

pm1008ClientTrapUrgentGoesOff NOTIFICATION-TYPE
	OBJECTS {pm1008AlmSfpDdmAlmPortn, pm1008trapPortNumber, pm1008trapBoardNumber}
	STATUS current
	--&FILTNAME    "PM1008 Client Urgent OFF"
	--&ACTIONS     { log, normal }
	--&CLEARS      { "PM1008 Client Urgent ON" }
	--&MATCH       { pm1008AlmSfpDdmAlmPortn "on", pm1008trapPortNumber "$2", pm1008trapBoardNumber "$3"}
	--&MESG        "DDM Alarm disappears on Client Port $2 of PM1008(LH) in Slot $3 ($A)"
	DESCRIPTION "Urgent client default disappeared"
	::= { pm1008traps 43 }

pm1008ClientTrapCritGoesOn NOTIFICATION-TYPE
	OBJECTS {pm1008AlmFailAccPortn, pm1008AlmHwFailAccPortn, pm1008trapPortNumber, pm1008trapBoardNumber}
	STATUS current
	--&FILTNAME    "PM1008 Client Fail ON"
	--&ACTIONS     { log, critical }
	--&MATCH       { pm1008AlmFailAccPortn "on", pm1008AlmHwFailAccPortn "*", pm1008trapPortNumber "$3", pm1008trapBoardNumber "$4"}
	--&MESG        "Client Port $3 Down on PM1008(LH) in Slot $4 ($A)"

	--&FILTNAME    "PM1008 Client HW Fail ON (Hidden)"
	--&ACTIONS     { info }
	--&MATCH       { pm1008AlmFailAccPortn "*", pm1008AlmHwFailAccPortn "on", pm1008trapPortNumber "$3", pm1008trapBoardNumber "$4"}
	--&MESG        "Client Port $3 Down on PM1008(LH) in Slot $4 ($A)"
	DESCRIPTION "Critical client default is activated"
	::= { pm1008traps 44 }

pm1008ClientTrapCritGoesOff NOTIFICATION-TYPE
	OBJECTS {pm1008AlmFailAccPortn, pm1008AlmHwFailAccPortn, pm1008trapPortNumber, pm1008trapBoardNumber}
	STATUS current
	--&FILTNAME    "PM1008 Client Fail OFF"
	--&ACTIONS     { log, normal }
	--&CLEARS      { "PM1008 Client Fail ON" }
	--&MATCH       { pm1008AlmFailAccPortn "on", pm1008AlmHwFailAccPortn "*", pm1008trapPortNumber "$3", pm1008trapBoardNumber "$4"}
	--&MESG        "Client Port $3 Up on PM1008(LH) in Slot $4 ($A)"

	--&FILTNAME    "PM1008 Client HW Fail OFF (Hidden)"
	--&ACTIONS     { info }
	--&MATCH       { pm1008AlmFailAccPortn "*", pm1008AlmHwFailAccPortn "on", pm1008trapPortNumber "$3", pm1008trapBoardNumber "$4"}
	--&MESG        "Client Port $3 Up on PM1008(LH) in Slot $4 ($A)"
	DESCRIPTION "Critical client default disappeared"
	::= { pm1008traps 45 }






--- *****************************************************
---     HW TRAPS
--- *****************************************************

pm1008PowerTrapUrgentGoesOn NOTIFICATION-TYPE
	OBJECTS {pm1008AlmDefFuseB, pm1008AlmDefFuseA , pm1008trapBoardNumber}
	STATUS current
	--&FILTNAME    "PM1008 Fuse A Fail ON"
	--&ACTIONS     { log, major }
	--&MATCH       { pm1008AlmDefFuseB "*", pm1008AlmDefFuseA "on", pm1008trapBoardNumber "$3"}
	--&MESG        "Power Input A Fail on PM1008(LH) in Slot $3 ($A)"

	--&FILTNAME    "PM1008 Fuse B Fail ON"
	--&ACTIONS     { log, major }
	--&MATCH       { pm1008AlmDefFuseB "on", pm1008AlmDefFuseA "*", pm1008trapBoardNumber "$3"}
	--&MESG        "Power Input B Fail on PM1008(LH) in Slot $3 ($A)"
	DESCRIPTION "Urgent power supply default is activated"
	::= { pm1008traps 50 }

pm1008PowerTrapUrgentGoesOff NOTIFICATION-TYPE
	OBJECTS {pm1008AlmDefFuseB, pm1008AlmDefFuseA , pm1008trapBoardNumber}
	STATUS current
	--&FILTNAME    "PM1008 Fuse A&B Fail OFF"
	--&ACTIONS     { log, normal}
	--&CLEARS      { "PM1008 Fuse A Fail ON", "PM1008 Fuse B Fail ON" }
	--&MATCH       { pm1008AlmDefFuseB "on", pm1008AlmDefFuseA "on", pm1008trapBoardNumber "$3"}
	--&MESG        "Power Inputs A and B Present on PM1008(LH) in Slot $3 ($A)"

	DESCRIPTION "Urgent power supply default disappeared"
	::= { pm1008traps 51 }






END
