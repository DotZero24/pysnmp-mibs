-- *****************************************************************
-- EKINOPS-Pm1001RR.TXT:  MIB
--
--MIB Part Number:3MI00100AJAE
--MIB Version:03
--
-- Copyright (c) 2016 by Ekinops
-- All rights reserved.
--
-- *****************************************************************

EKINOPS-Pm1001RR-MIB DEFINITIONS ::= BEGIN

IMPORTS
	ekinops,
	EkiState,
	EkiOnOff,
	EkiMode,
	EkiProtocol,
	EkiApiState,
	EkiSynchroMode,
	EkiMeasureType
			FROM EKINOPS-MIB
        MODULE-IDENTITY,
        OBJECT-TYPE,
        NOTIFICATION-TYPE,
	Unsigned32,
	Integer32,
	Counter32,
	IpAddress
        		FROM SNMPv2-SMI
 	TEXTUAL-CONVENTION,
	DisplayString
                FROM SNMPv2-TC;

modulePm1001RR MODULE-IDENTITY
        LAST-UPDATED "201606070000Z"
        ORGANIZATION "Ekinops"
        CONTACT-INFO
         "Ekinops

          3, rue Blaise Pascal
          F-22300 Lannion / FRANCE

          Tel : +33 (0)2 96 05 00 30
          Fax : +33 (0)2 96 48 62 39

          E-mail: support@ekinops.net"
        DESCRIPTION
          "MIB for the Ekinops Pm1001RR hardware."
	REVISION "200512130000Z"
	DESCRIPTION
	  "Initial Version."
	REVISION "200707020000Z"
	DESCRIPTION
	  "Change °C to C."
	REVISION "200708280000Z"
	DESCRIPTION
	  "Change Labels"
	REVISION "200711210000Z"
	DESCRIPTION
	  "UPdate Ekinops address, Helps on objects, Ports Labels"
	REVISION "200802130000Z"
	DESCRIPTION
	  "Adding OTX-TLH features"
	REVISION "200812040000Z"
	DESCRIPTION
	  "Cosmetics for mib compilers"
	REVISION "200906110000Z"
	DESCRIPTION
	  "CondType parameters insertion"
	REVISION "201001280000Z"
	DESCRIPTION
	  "XFP-T and OTX-VLH parameters"
	REVISION "201002230000Z"
	DESCRIPTION
	  "Probcause,AlarmType - NMS"
	REVISION "201003090000Z"
	DESCRIPTION
	  "OTX-VLH-Reset"
	REVISION "201011030000Z"
	DESCRIPTION
	  "Formula in comments, Event on XFP init"
	REVISION "201207040000Z"
	DESCRIPTION
	  "Minor cosmetic updates"
	REVISION "201403250000Z"
	DESCRIPTION
	  "Probcause,AlarmType - NMS completion"
	REVISION "201501140000Z"
	DESCRIPTION
	  "Add Loopback objects"
	REVISION "201501140000Z"
	DESCRIPTION
	  "Labels cosmetic updates"
	REVISION "201605230000Z"
	DESCRIPTION
	  "New AlarmType – synthesisAlarm (12)"
	REVISION "201606070000Z"
	DESCRIPTION
	  "Capabilities objects of Table 5"
        ::= { ekinops 8 }



--- *****************************************************
---     LEAF LEVEL 2
--- *****************************************************


pm1001rralarms OBJECT IDENTIFIER ::= { modulePm1001RR 2 }
pm1001rrAlmOther OBJECT IDENTIFIER ::= { pm1001rralarms 1 }
pm1001rrAlmOtherNurg OBJECT IDENTIFIER ::= { pm1001rrAlmOther 1 }
pm1001rrAlmOtherUrg OBJECT IDENTIFIER ::= { pm1001rrAlmOther 2 }
pm1001rrAlmOtherCrit OBJECT IDENTIFIER ::= { pm1001rrAlmOther 3 }

pm1001rrAlmClient OBJECT IDENTIFIER ::= { pm1001rralarms 2 }
pm1001rrAlmClientNurg OBJECT IDENTIFIER ::= { pm1001rrAlmClient 1 }
pm1001rrAlmClientUrg OBJECT IDENTIFIER ::= { pm1001rrAlmClient 2 }
pm1001rrAlmClientCrit OBJECT IDENTIFIER ::= { pm1001rrAlmClient 3 }

pm1001rrAlmLine OBJECT IDENTIFIER ::= { pm1001rralarms 3 }
pm1001rrAlmLineNurg OBJECT IDENTIFIER ::= { pm1001rrAlmLine 1 }
pm1001rrAlmLineUrg OBJECT IDENTIFIER ::= { pm1001rrAlmLine 2 }
pm1001rrAlmLineCrit OBJECT IDENTIFIER ::= { pm1001rrAlmLine 3 }


pm1001rrmeasures OBJECT IDENTIFIER ::= { modulePm1001RR 3 }
pm1001rrMesrOther OBJECT IDENTIFIER ::= { pm1001rrmeasures 1 }
pm1001rrMesrClient OBJECT IDENTIFIER ::= { pm1001rrmeasures 2 }
pm1001rrMesrLine OBJECT IDENTIFIER ::= { pm1001rrmeasures 3 }


pm1001rrcontrolsWrite OBJECT IDENTIFIER ::= { modulePm1001RR 6 }
pm1001rrCtrlOther OBJECT IDENTIFIER ::= { pm1001rrcontrolsWrite 1 }
pm1001rrCtrlClient OBJECT IDENTIFIER ::= { pm1001rrcontrolsWrite 2 }
pm1001rrCtrlLine OBJECT IDENTIFIER ::= { pm1001rrcontrolsWrite 3 }

pm1001rrri OBJECT IDENTIFIER ::= { modulePm1001RR 7 }


pm1001rrConfig OBJECT IDENTIFIER ::= { modulePm1001RR 9 }

pm1001rrtraps OBJECT IDENTIFIER ::= { modulePm1001RR 10 }


--- *****************************************************
--- $$$$$$$$$$$$$$$$$$$$$$$$$$$$$$$$$$$$$$$$$$$$$$$$$$$$$
---     TEXTUAL-CONVENTION
--- $$$$$$$$$$$$$$$$$$$$$$$$$$$$$$$$$$$$$$$$$$$$$$$$$$$$$
--- *****************************************************

Pm1001rrBitRate ::= TEXTUAL-CONVENTION
    STATUS      current
    DESCRIPTION "different rates for a client and line ports"
    SYNTAX INTEGER {
		rateOC192(0),
		rate10GBELAN(1),
		rate10GBEWAN(2),
		rate10GFC(3),
		rate10FECG975(4),
		rate10FECG709(5),
		rate10DYNAFEC(6)
           }

Pm1001rrOtxMode ::= TEXTUAL-CONVENTION
    STATUS      current
    DESCRIPTION "Different modes on OTX-TLH on client and line ports"
    SYNTAX INTEGER {
		otx80mode(1),
		otx60mode(2),
		otxadjustmode(4)
           }

Pm1001rrOtxGrid ::= TEXTUAL-CONVENTION
    STATUS      current
    DESCRIPTION "Different grids on OTX-TLH on client and line ports"
    SYNTAX INTEGER {
		otxgrid200(200),
		otxgrid100(100),
		otxgrid50(50)
           }

Pm1001rrAdjustValue ::= TEXTUAL-CONVENTION
    STATUS      current
    DESCRIPTION "Different values in Adjust mode on OTX-TLH on client and line ports"
    SYNTAX INTEGER {
		otxadjustvalue0(0),
		otxadjustvalue1(1),
		otxadjustvalue2(2),
		otxadjustvalue3(3),
		otxadjustvalue4(4),
		otxadjustvalue5(5),
		otxadjustvalue6(6),
		otxadjustvalue7(7),
		otxadjustvalue8(8),
		otxadjustvalue9(9),
		otxadjustvalue10(10)
           }

Pm1001rrOtxChannel ::= TEXTUAL-CONVENTION
    STATUS      current
    DESCRIPTION "Channel selection on OTX-TLH on client and line ports"
    SYNTAX INTEGER


--- *****************************************************
--- $$$$$$$$$$$$$$$$$$$$$$$$$$$$$$$$$$$$$$$$$$$$$$$$$$$$$
---     REMOTE INVENTORY
--- $$$$$$$$$$$$$$$$$$$$$$$$$$$$$$$$$$$$$$$$$$$$$$$$$$$$$
--- *****************************************************

pm1001rrRinvReloadInventory OBJECT-TYPE
  SYNTAX EkiOnOff
  MAX-ACCESS read-write
  STATUS current
  DESCRIPTION
        "Reload the inventory: This OID triggers an
         inventory reload."
  ::= { pm1001rrri 2 }


pm1001rrRinvHwPlatform OBJECT-TYPE
  SYNTAX DisplayString
  MAX-ACCESS read-only
  STATUS current
  DESCRIPTION
        "Module platform description: This OID contains the
         description of the Module."
  ::= { pm1001rrri 4 }

pm1001rrRinvSwPlatform OBJECT-TYPE
  SYNTAX DisplayString
  MAX-ACCESS read-only
  STATUS current
  DESCRIPTION
        "SW platform description: This OID contains the
         description of the Software platform."
  ::= { pm1001rrri 5 }

pm1001rrRinvClientXFP OBJECT-TYPE
  SYNTAX DisplayString
  MAX-ACCESS read-only
  STATUS current
  DESCRIPTION
        "Inventory for the XFP: This OID contains the inventory for the Client XFP"
  ::= { pm1001rrri 6 }


pm1001rrRinvLineXFP OBJECT-TYPE
  SYNTAX DisplayString
  MAX-ACCESS read-only
  STATUS current
  DESCRIPTION
        "Inventory for the XFP: This OID contains the inventory for the Line XFP"
  ::= { pm1001rrri 7 }






--- *****************************************************
--- $$$$$$$$$$$$$$$$$$$$$$$$$$$$$$$$$$$$$$$$$$$$$$$$$$$$$
---     ALARMS
--- $$$$$$$$$$$$$$$$$$$$$$$$$$$$$$$$$$$$$$$$$$$$$$$$$$$$$
--- *****************************************************



--- *****************************************************
---     LEAF for the synthAlm0 article
--- *****************************************************
pm1001rrAlmsynthAlm0 OBJECT IDENTIFIER ::= { pm1001rrAlmOtherCrit 0 }




pm1001rrAlmDefFuseB OBJECT-TYPE
	  SYNTAX EkiOnOff
	  MAX-ACCESS read-only
	  STATUS current
	  DESCRIPTION
        "
        Fuse B Fail :This OID indicates
        that the fuse of the power input
        B is in fail condition  <Help>
          Status of the Fuse B <Condtype>
        DEF_FUSE_B <Probcause> powerProblem
        (36) <Alarmtype> equipmentAlarm
        (5) <Polarity> (2)
        "
	  ::= { pm1001rrAlmsynthAlm0 16 }



pm1001rrAlmDefFuseA OBJECT-TYPE
	  SYNTAX EkiOnOff
	  MAX-ACCESS read-only
	  STATUS current
	  DESCRIPTION
        "
        Fuse A Fail :This OID indicates
        that the fuse of the power input
        A is in fail condition  <Help>
          Status of the Fuse A <Condtype>
        DEF_FUSE_A <Probcause> powerProblem
        (36) <Alarmtype> equipmentAlarm
        (5) <Polarity> (2)
        "
	  ::= { pm1001rrAlmsynthAlm0 15 }



pm1001rrAlmModuleGlobFailure OBJECT-TYPE
	  SYNTAX EkiOnOff
	  MAX-ACCESS read-only
	  STATUS current
	  DESCRIPTION
        "
        Module Failure :This OID is set
        on detection of a failure originating
        from the PM <Condtype> MODULE_GLOB_FAILURE
        <Probcause> equipmentMalfunction
        (16) <Alarmtype> synthesisAlarm
        (12)  <Polarity> (2)
        "
	  ::= { pm1001rrAlmsynthAlm0 9 }



--- *****************************************************
---     LEAF for the synthAlm7 article
--- *****************************************************
pm1001rrAlmsynthAlm7 OBJECT IDENTIFIER ::= { pm1001rrAlmLineCrit 7 }




pm1001rrAlmLineVccAlarm OBJECT-TYPE
	  SYNTAX EkiOnOff
	  MAX-ACCESS read-only
	  STATUS current
	  DESCRIPTION
        "
        Line 2 VCC Alarm :This OID indicates
        an overall VCC alarm is set over
        the Line 2 XFP <Condtype> LINE_VCC_ALARM
        <Probcause> powerProblem (36) <Alarmtype>
        equipmentAlarm (5) <Polarity> (2)
        "
	  ::= { pm1001rrAlmsynthAlm7 15 }



pm1001rrAlmLineVccWarning OBJECT-TYPE
	  SYNTAX EkiOnOff
	  MAX-ACCESS read-only
	  STATUS current
	  DESCRIPTION
        "
        Line 2 VCC Warning :This OID indicates
        an overall VCC warning is set over
        the Line 2 XFP <Condtype> LINE_VCC_WARNING
        <Probcause> powerProblem (36) <Alarmtype>
        equipmentAlarm (5) <Polarity> (2)
        "
	  ::= { pm1001rrAlmsynthAlm7 14 }



pm1001rrAlmLineFail OBJECT-TYPE
	  SYNTAX EkiOnOff
	  MAX-ACCESS read-only
	  STATUS current
	  DESCRIPTION
        "
        Line 2 Port Failure :This OID
         indicates a failure on the Line
        2 port <Condtype> LINE_FAIL <Probcause>
        equipmentMalfunction (16) <Alarmtype>
        synthesisAlarm (12)  <Polarity>
        (2)
        "
	  ::= { pm1001rrAlmsynthAlm7 12 }



pm1001rrAlmLineDdmAlm OBJECT-TYPE
	  SYNTAX EkiOnOff
	  MAX-ACCESS read-only
	  STATUS current
	  DESCRIPTION
        "
        Alarm On Line 2 Optical Module
        DDM :This OID indicates an alarm
        is present coming out of Line 2
        optical interface DDM  <Help>
         This alarm indicates if a DDM
         Alarm has been detected on the
        line 2 transceiver <Condtype> LINE_DDM_ALM
        <Probcause> equipmentMalfunction
        (16) <Alarmtype> synthesisAlarm
        (12)  <Polarity> (2)
        "
	  ::= { pm1001rrAlmsynthAlm7 10 }



pm1001rrAlmLineDdmWarning OBJECT-TYPE
	  SYNTAX EkiOnOff
	  MAX-ACCESS read-only
	  STATUS current
	  DESCRIPTION
        "
        Warning On Line 2 Optical Module
        DDM :This OID indicates a warning
        is present coming out of Line 2
        optical interface DDM  <Help>
         This alarm indicates if a DDM
         Warning has been detected on the
        line 2 transceiver <Condtype> LINE_DDM_WARNING
        <Probcause> equipmentMalfunction
        (16) <Alarmtype> synthesisAlarm
        (12)  <Polarity> (2)
        "
	  ::= { pm1001rrAlmsynthAlm7 9 }



pm1001rrAlmLineXfpTxOff OBJECT-TYPE
	  SYNTAX EkiOnOff
	  MAX-ACCESS read-only
	  STATUS current
	  DESCRIPTION
        "
        Line 2 Optical Module Laser Shutdown
        :This OID indicates the Line 2
         optical output power is off  <Help>
         This status indicates if the line
        2 transceiver laser is ON or OFF
        <Condtype> LINE_XFP_TX_OFF <Probcause>
        other (1) <Alarmtype> equipmentAlarm
        (5) <Polarity> (2)
        "
	  ::= { pm1001rrAlmsynthAlm7 5 }



pm1001rrAlmLineHwFail OBJECT-TYPE
	  SYNTAX EkiOnOff
	  MAX-ACCESS read-only
	  STATUS current
	  DESCRIPTION
        "
        Line 2 Port HW Failure :This OID
        indicates a failure on Line 2 port,
        most probably caused by a HW issue
        <Condtype> LINE_HW_FAIL <Probcause>
        equipmentMalfunction (16) <Alarmtype>
        synthesisAlarm (12)  <Polarity>
        (2)
        "
	  ::= { pm1001rrAlmsynthAlm7 4 }



pm1001rrAlmLineInitNotCompl OBJECT-TYPE
	  SYNTAX EkiOnOff
	  MAX-ACCESS read-only
	  STATUS current
	  DESCRIPTION
        "
        Line 2 Optical Module Ready :This
        OID indicates the optical interface
        (XFP or OTX) is not operational

         <Help>  This status indicates
         if the line 2 transceiver has
         been correctly initialized <Condtype>
        LINE_INIT_NOT_COMPL <Probcause>
        equipmentMalfunction (16) <Alarmtype>
        equipmentAlarm (5) <Polarity> (2)
        <Event> ObjectCDINV
        "
	  ::= { pm1001rrAlmsynthAlm7 2 }



pm1001rrAlmLineXfpAbsent OBJECT-TYPE
	  SYNTAX EkiOnOff
	  MAX-ACCESS read-only
	  STATUS current
	  DESCRIPTION
        "
        Line 2 Optical Module Absent :This
        OID indicates the Line 2 optical
        interface (XFP or OTX) is not present
        in the PM  <Help>  This alarm indicates
        if the line 2 transceiver is present.
        <Condtype> LINE_XFP_ABSENT <Probcause>
        inputOutputDeviceError (24) <Alarmtype>
        equipmentAlarm (5) <Polarity> (2)
        <Event> ObjectCDINV
        "
	  ::= { pm1001rrAlmsynthAlm7 1 }



--- *****************************************************
---     LEAF for the synthAlm8 article
--- *****************************************************
pm1001rrAlmsynthAlm8 OBJECT IDENTIFIER ::= { pm1001rrAlmClientCrit 8 }




pm1001rrAlmClientVccAlarm OBJECT-TYPE
	  SYNTAX EkiOnOff
	  MAX-ACCESS read-only
	  STATUS current
	  DESCRIPTION
        "
        Line 1 VCC Alarm :This OID indicates
        an overall VCC alarm is set over
        the Line 1 XFP <Condtype> CLIENT_VCC_ALARM
        <Probcause> powerProblem (36) <Alarmtype>
        equipmentAlarm (5) <Polarity> (2)
        "
	  ::= { pm1001rrAlmsynthAlm8 15 }



pm1001rrAlmClientVccWarning OBJECT-TYPE
	  SYNTAX EkiOnOff
	  MAX-ACCESS read-only
	  STATUS current
	  DESCRIPTION
        "
        Line 1VCC Warning :This OID indicates
        an overall VCC warning is set over
        the Line 1 XFP <Condtype> CLIENT_VCC_WARNING
        <Probcause> powerProblem (36) <Alarmtype>
        equipmentAlarm (5) <Polarity> (2)
        "
	  ::= { pm1001rrAlmsynthAlm8 14 }



pm1001rrAlmClientFail OBJECT-TYPE
	  SYNTAX EkiOnOff
	  MAX-ACCESS read-only
	  STATUS current
	  DESCRIPTION
        "
        Line 1 Port Failure :This OID
         indicates a failure on the Line
        1 port <Condtype> CLIENT_FAIL <Probcause>
        equipmentMalfunction (16) <Alarmtype>
        synthesisAlarm (12)  <Polarity>
        (2)
        "
	  ::= { pm1001rrAlmsynthAlm8 12 }



pm1001rrAlmClientDdmAlm OBJECT-TYPE
	  SYNTAX EkiOnOff
	  MAX-ACCESS read-only
	  STATUS current
	  DESCRIPTION
        "
        Alarm On Line 1 Optical Module
        DDM :This OID indicates an alarm
        is present coming out of Line 1
        optical interface DDM  <Help>
         This alarm indicates if a DDM
         Alarm has been detected on the
        line 1 transceiver <Condtype> CLIENT_DDM_ALM
        <Probcause> equipmentMalfunction
        (16) <Alarmtype> synthesisAlarm
        (12)  <Polarity> (2)
        "
	  ::= { pm1001rrAlmsynthAlm8 10 }



pm1001rrAlmClientDdmWarning OBJECT-TYPE
	  SYNTAX EkiOnOff
	  MAX-ACCESS read-only
	  STATUS current
	  DESCRIPTION
        "
        Warning On Line 1 Optical Module
        DDM :This OID indicates a warning
        is present coming out of Line 1
        optical interface DDM  <Help>
         This alarm indicates if a DDM
         Warning has been detected on the
        line 1 transceiver <Condtype> CLIENT_DDM_WARNING
        <Probcause> equipmentMalfunction
        (16) <Alarmtype> synthesisAlarm
        (12)  <Polarity> (2)
        "
	  ::= { pm1001rrAlmsynthAlm8 9 }



pm1001rrAlmClientXfpTxOff OBJECT-TYPE
	  SYNTAX EkiOnOff
	  MAX-ACCESS read-only
	  STATUS current
	  DESCRIPTION
        "
        Line 1 Optical Module Laser Shutdown
        :This OID indicates the Line 1
         optical output power is off  <Help>
         This status indicates if the line
        1 transceiver laser is ON or OFF
        <Condtype> CLIENT_XFP_TX_OFF <Probcause>
        other (1) <Alarmtype> equipmentAlarm
        (5) <Polarity> (2)
        "
	  ::= { pm1001rrAlmsynthAlm8 5 }



pm1001rrAlmClientHwFail OBJECT-TYPE
	  SYNTAX EkiOnOff
	  MAX-ACCESS read-only
	  STATUS current
	  DESCRIPTION
        "
        Line 1 Port HW Failure :This OID
        indicates a failure on Line 1 port,
        most probably caused by a HW issue.
        <Condtype> CLIENT_HW_FAIL <Probcause>
        equipmentMalfunction (16) <Alarmtype>
        synthesisAlarm (12)  <Polarity>
        (2)
        "
	  ::= { pm1001rrAlmsynthAlm8 4 }



pm1001rrAlmClientInitNotCompl OBJECT-TYPE
	  SYNTAX EkiOnOff
	  MAX-ACCESS read-only
	  STATUS current
	  DESCRIPTION
        "
        Line 1 Optical Module Ready :This
        OID indicates the optical interface
        (XFP or OTX) is not operational

         <Help>  This status indicates
         if the line 1 transceiver has
         been correctly initialized <Condtype>
        CLIENT_INIT_NOT_COMPL <Probcause>
        equipmentMalfunction (16) <Alarmtype>
        equipmentAlarm (5) <Polarity> (2)
        <Event> ObjectCDINV
        "
	  ::= { pm1001rrAlmsynthAlm8 2 }



pm1001rrAlmClientXfpAbsent OBJECT-TYPE
	  SYNTAX EkiOnOff
	  MAX-ACCESS read-only
	  STATUS current
	  DESCRIPTION
        "
        Line 1 Optical Module Absent :This
        OID indicates the Line 1 optical
        interface (XFP or OTX) is not present
        in the PM  <Help>  This alarm indicates
        if the line 1 transceiver is present.
        <Condtype> CLIENT_XFP_ABSENT <Probcause>
        inputOutputDeviceError (24) <Alarmtype>
        equipmentAlarm (5) <Polarity> (2)
        <Event> ObjectCDINV
        "
	  ::= { pm1001rrAlmsynthAlm8 1 }



--- *****************************************************
---     LEAF for the clientXfpAlarm1 article
--- *****************************************************
pm1001rrAlmclientXfpAlarm1 OBJECT IDENTIFIER ::= { pm1001rrAlmClientUrg 16 }




pm1001rrAlmClientRxPwrHighAla OBJECT-TYPE
	  SYNTAX EkiOnOff
	  MAX-ACCESS read-only
	  STATUS current
	  DESCRIPTION
        "
        Line 1 Optical Rx Power High :Alarm
        indicating that the Line 1 XFP/OTX
        received optical power is higher
        than the threshold value written
        in the Line 1 XFP/OTX EEPROM <Condtype>
        CLIENT_RX_PWR_HIGH_ALA <Probcause>
        receiveFailure (41) <Alarmtype>
        equipmentAlarm (5) <Polarity> (2)
        "
	  ::= { pm1001rrAlmclientXfpAlarm1 16 }



pm1001rrAlmClientRxPwrLowAla OBJECT-TYPE
	  SYNTAX EkiOnOff
	  MAX-ACCESS read-only
	  STATUS current
	  DESCRIPTION
        "
        Line 1 Optical Rx Power Low :Alarm
        indicating that the Line 1 XFP/OTX
        received optical power is lower
        than the threshold value written
        in the Line 1 XFP/OTX EEPROM  <Condtype>
        CLIENT_RX_PWR_LOW_ALA <Probcause>
        receiveFailure (41) <Alarmtype>
        equipmentAlarm (5) <Polarity> (2)
        "
	  ::= { pm1001rrAlmclientXfpAlarm1 15 }



pm1001rrAlmClientTempHighAla OBJECT-TYPE
	  SYNTAX EkiOnOff
	  MAX-ACCESS read-only
	  STATUS current
	  DESCRIPTION
        "
        Line 1 Transceiver Temp High :Alarm
        indicating that the Line 1 XFP/OTX
        temperature is higher than the
         threshold value written in the
        Line 1 XFP/OTX EEPROM <Condtype>
        CLIENT_TEMP_HIGH_ALA <Probcause>
        temperatureUnacceptable (51) <Alarmtype>
        equipmentAlarm (5) <Polarity> (2)
        "
	  ::= { pm1001rrAlmclientXfpAlarm1 8 }



pm1001rrAlmClientTempLowAla OBJECT-TYPE
	  SYNTAX EkiOnOff
	  MAX-ACCESS read-only
	  STATUS current
	  DESCRIPTION
        "
        Line 1 Transceiver Temp Low :Alarm
        indicating that the Line 1 XFP/OTX
        temperature is lower than the threshold
        value written in the Line 1 XFP/OTX
        EEPROM <Condtype> CLIENT_TEMP_LOW_ALA
        <Probcause> temperatureUnacceptable
        (51) <Alarmtype> equipmentAlarm
        (5) <Polarity> (2)
        "
	  ::= { pm1001rrAlmclientXfpAlarm1 7 }



pm1001rrAlmClientTxBiasHighAla OBJECT-TYPE
	  SYNTAX EkiOnOff
	  MAX-ACCESS read-only
	  STATUS current
	  DESCRIPTION
        "
        Line 1 Transceiver Bias High :Alarm
        indicating that the Line 1 XFP/OTX
        transmitter laser bias current
         is higher than the threshold value
        written in the Line 1 XFP/OTX EEPROM
        <Condtype> CLIENT_TX_BIAS_HIGH_ALA
        <Probcause> transmitterFailure
         (56) <Alarmtype> equipmentAlarm
        (5) <Polarity> (2)
        "
	  ::= { pm1001rrAlmclientXfpAlarm1 4 }



pm1001rrAlmClientTxBiasLowAla OBJECT-TYPE
	  SYNTAX EkiOnOff
	  MAX-ACCESS read-only
	  STATUS current
	  DESCRIPTION
        "
        Line 1 Transceiver Bias Low :Alarm
        indicating that the Line 1 XFP/OTX
        transmitter laser bias current
         is lower than the threshold value
        written in the Line 1 XFP/OTX EEPROM
        <Condtype> CLIENT_TX_BIAS_LOW_ALA
        <Probcause> transmitterFailure
         (56) <Alarmtype> equipmentAlarm
        (5) <Polarity> (2)
        "
	  ::= { pm1001rrAlmclientXfpAlarm1 3 }



pm1001rrAlmClientTxPwrHighAla OBJECT-TYPE
	  SYNTAX EkiOnOff
	  MAX-ACCESS read-only
	  STATUS current
	  DESCRIPTION
        "
        Line 1 Optical Tx Power High :Alarm
        indicating that the Line 1 XFP/OTX
        transmitter transmitter output
         power is higher than the threshold
        value written in the Line 1 XFP/OTX
        EEPROM <Condtype> CLIENT_TX_PWR_HIGH_ALA
        <Probcause> transmitterFailure
         (56) <Alarmtype> equipmentAlarm
        (5) <Polarity> (2)
        "
	  ::= { pm1001rrAlmclientXfpAlarm1 2 }



pm1001rrAlmClientTxPwrLowAla OBJECT-TYPE
	  SYNTAX EkiOnOff
	  MAX-ACCESS read-only
	  STATUS current
	  DESCRIPTION
        "
        Line 1 Optical Tx Power Low :Alarm
        indicating that the Line 1 XFP/OTX
        transmitter transmitter output
         power is lower than the threshold
        value written in the Line 1 XFP/OTX
        EEPROM <Condtype> CLIENT_TX_PWR_LOW_ALA
        <Probcause> transmitterFailure
         (56) <Alarmtype> equipmentAlarm
        (5) <Polarity> (2)
        "
	  ::= { pm1001rrAlmclientXfpAlarm1 1 }



--- *****************************************************
---     LEAF for the clientXfpWarnings article
--- *****************************************************
pm1001rrAlmclientXfpWarnings OBJECT IDENTIFIER ::= { pm1001rrAlmClientNurg 17 }




pm1001rrAlmClientRxPwrHighWng OBJECT-TYPE
	  SYNTAX EkiOnOff
	  MAX-ACCESS read-only
	  STATUS current
	  DESCRIPTION
        "
        Line 1 Optical Rx Power High Warning
        :Warning indicating that the Line
        1 XFP/OTX received optical power
        is higher than the threshold value
        written in the Line 1 XFP/OTX EEPROM
        <Condtype> CLIENT_RX_PWR_HIGH_WNG
        <Probcause> receiveFailure (41)
        <Alarmtype> equipmentAlarm (5)
         <Polarity> (2)
        "
	  ::= { pm1001rrAlmclientXfpWarnings 16 }



pm1001rrAlmClientRxPwrLowWng OBJECT-TYPE
	  SYNTAX EkiOnOff
	  MAX-ACCESS read-only
	  STATUS current
	  DESCRIPTION
        "
        Line 1 Optical Rx Power Low Warning
        :Warning indicating that the Line
        1 XFP/OTX received optical power
        is lower than the threshold value
        written in the Line 1 XFP/OTX EEPROM
         <Condtype> CLIENT_RX_PWR_LOW_WNG
        <Probcause> receiveFailure (41)
        <Alarmtype> equipmentAlarm (5)
         <Polarity> (2)
        "
	  ::= { pm1001rrAlmclientXfpWarnings 15 }



pm1001rrAlmClientTempHighWng OBJECT-TYPE
	  SYNTAX EkiOnOff
	  MAX-ACCESS read-only
	  STATUS current
	  DESCRIPTION
        "
        Line 1 Transceiver Temp High Warning
        :Warning indicating that the Line
        1 XFP/OTX temperature is higher
        than the threshold value written
        in the Line 1 XFP/OTX EEPROM <Condtype>
        CLIENT_TEMP_HIGH_WNG <Probcause>
        temperatureUnacceptable (51) <Alarmtype>
        equipmentAlarm (5) <Polarity> (2)
        "
	  ::= { pm1001rrAlmclientXfpWarnings 8 }



pm1001rrAlmClientTempLowWng OBJECT-TYPE
	  SYNTAX EkiOnOff
	  MAX-ACCESS read-only
	  STATUS current
	  DESCRIPTION
        "
        Line 1 Transceiver Temp Low Warning
        :Warning indicating that the Line
        1 XFP/OTX temperature is lower
         than the threshold value written
        in the Line 1 XFP/OTX EEPROM <Condtype>
        CLIENT_TEMP_LOW_WNG <Probcause>
        temperatureUnacceptable (51) <Alarmtype>
        equipmentAlarm (5) <Polarity> (2)
        "
	  ::= { pm1001rrAlmclientXfpWarnings 7 }



pm1001rrAlmClientTxBiasHighWng OBJECT-TYPE
	  SYNTAX EkiOnOff
	  MAX-ACCESS read-only
	  STATUS current
	  DESCRIPTION
        "
        Line 1 Transceiver Bias High Warning
        :Warning indicating that the Line
        1 XFP/OTX transmitter laser bias
        current is higher than the threshold
        value written in the Line 1 XFP/OTX
        EEPROM <Condtype> CLIENT_TX_BIAS_HIGH_WNG
        <Probcause> transmitterFailure
         (56) <Alarmtype> equipmentAlarm
        (5) <Polarity> (2)
        "
	  ::= { pm1001rrAlmclientXfpWarnings 4 }



pm1001rrAlmClientTxBiasLowWng OBJECT-TYPE
	  SYNTAX EkiOnOff
	  MAX-ACCESS read-only
	  STATUS current
	  DESCRIPTION
        "
        Line 1 Transceiver Bias Low Warning
        :Warning indicating that the Line
        1 XFP/OTX transmitter laser bias
        current is lower than the threshold
        value written in the Line 1 XFP/OTX
        EEPROM <Condtype> CLIENT_TX_BIAS_LOW_WNG
        <Probcause> transmitterFailure
         (56) <Alarmtype> equipmentAlarm
        (5) <Polarity> (2)
        "
	  ::= { pm1001rrAlmclientXfpWarnings 3 }



pm1001rrAlmClientTxPwrHighWng OBJECT-TYPE
	  SYNTAX EkiOnOff
	  MAX-ACCESS read-only
	  STATUS current
	  DESCRIPTION
        "
        Line 1 Optical Tx Power High Warning
        :Warning indicating that the Line
        1 XFP/OTX transmitter transmitter
        output power is higher than the
        threshold value written in the
         Line 1 XFP/OTX EEPROM <Condtype>
        CLIENT_TX_PWR_HIGH_WNG <Probcause>
        transmitterFailure (56) <Alarmtype>
        equipmentAlarm (5) <Polarity> (2)
        "
	  ::= { pm1001rrAlmclientXfpWarnings 2 }



pm1001rrAlmClientTxPwrLowWng OBJECT-TYPE
	  SYNTAX EkiOnOff
	  MAX-ACCESS read-only
	  STATUS current
	  DESCRIPTION
        "
        Line 1 Optical Tx Power Low Warning
        :Warning indicating that the Line
        1 XFP/OTX transmitter transmitter
        output power is lower than the
         threshold value written in the
        Line 1 XFP/OTX EEPROM <Condtype>
        CLIENT_TX_PWR_LOW_WNG <Probcause>
        transmitterFailure (56) <Alarmtype>
        equipmentAlarm (5) <Polarity> (2)
        "
	  ::= { pm1001rrAlmclientXfpWarnings 1 }



--- *****************************************************
---     LEAF for the clientXfpAlarms2 article
--- *****************************************************
pm1001rrAlmclientXfpAlarms2 OBJECT IDENTIFIER ::= { pm1001rrAlmClientCrit 19 }




pm1001rrAlmClientApdSupplyFault OBJECT-TYPE
	  SYNTAX EkiOnOff
	  MAX-ACCESS read-only
	  STATUS current
	  DESCRIPTION
        "
        Line 1 Rx Photodiode Power Failed
        :This OID indicates a failure on
        the Line 1 APD power supply <Condtype>
        CLIENT_APD_SUPPLY_FAULT <Probcause>
        receiverFailure (42) <Alarmtype>
        equipmentAlarm (5) <Polarity> (2)
        "
	  ::= { pm1001rrAlmclientXfpAlarms2 16 }



pm1001rrAlmClientTecFault OBJECT-TYPE
	  SYNTAX EkiOnOff
	  MAX-ACCESS read-only
	  STATUS current
	  DESCRIPTION
        "
        Line 1 Optical Tx Temp Regul.
         Failed :This OID indicates a failure
        on the Line 1 TEC module <Condtype>
        CLIENT_TEC_FAULT <Probcause> transmitterFailure
        (56) <Alarmtype> equipmentAlarm
        (5) <Polarity> (2)
        "
	  ::= { pm1001rrAlmclientXfpAlarms2 15 }



pm1001rrAlmClientWavelengthUnlocked OBJECT-TYPE
	  SYNTAX EkiOnOff
	  MAX-ACCESS read-only
	  STATUS current
	  DESCRIPTION
        "
        Line 1 Optical Tx Wavelength Unlocked
        :This OID indicates that the Line
        1 wavelength error is exceeding
        the manufacturer tolerance <Condtype>
        CLIENT_WAVELENGTH_UNLOCKED <Probcause>
        transmitterFailure (56) <Alarmtype>
        equipmentAlarm (5) <Polarity> (2)
        "
	  ::= { pm1001rrAlmclientXfpAlarms2 14 }



pm1001rrAlmClientChannelNotAcquired OBJECT-TYPE
	  SYNTAX EkiOnOff
	  MAX-ACCESS read-only
	  STATUS current
	  DESCRIPTION
        "
        Line 1 DWDM Channel Not Acquired
        :This OID indicates the transceiver
        didn't tune the DWDM Channel succesfully.
         <Help>  This status indicates
         the transceiver has not tuned
         the DWDM Channel succesfully.
         <Condtype> CLIENT_CHANNEL_NOT_ACQUIRED
        <Probcause> transmitterFailure
         (56) <Alarmtype> equipmentAlarm
        (5) <Polarity> (2)
        "
	  ::= { pm1001rrAlmclientXfpAlarms2 10 }



pm1001rrAlmClientTxNr OBJECT-TYPE
	  SYNTAX EkiOnOff
	  MAX-ACCESS read-only
	  STATUS current
	  DESCRIPTION
        "
        Line 1 Optical Tx Not Ready :This
        OID indicates a condition has arisen
        leading to invalid data on the
         Line 1 transmitting side <Condtype>
        CLIENT_TX_NR <Probcause> transmitterFailure
        (56) <Alarmtype> equipmentAlarm
        (5) <Polarity> (2)
        "
	  ::= { pm1001rrAlmclientXfpAlarms2 8 }



pm1001rrAlmClientTxFault OBJECT-TYPE
	  SYNTAX EkiOnOff
	  MAX-ACCESS read-only
	  STATUS current
	  DESCRIPTION
        "
        Line 1 Optical Tx Failure :This
        OID indicates a fault condition
        on the Line 1 laser detected by
        the safety syste <Condtype> CLIENT_TX_FAULT
        <Probcause> transmitterFailure
         (56) <Alarmtype> equipmentAlarm
        (5) <Polarity> (2)
        "
	  ::= { pm1001rrAlmclientXfpAlarms2 7 }



pm1001rrAlmClientTxCdrNotLocked OBJECT-TYPE
	  SYNTAX EkiOnOff
	  MAX-ACCESS read-only
	  STATUS current
	  DESCRIPTION
        "
        Line 1 Optical Tx CDR Unlocked
        :This OID indicates a loss of lock
        on the Line 1 transmitting side
        CDR has been detected. <Condtype>
        CLIENT_TX_CDR_NOT_LOCKED <Probcause>
        transmitterFailure (56) <Alarmtype>
        equipmentAlarm (5) <Polarity> (2)
        "
	  ::= { pm1001rrAlmclientXfpAlarms2 6 }



pm1001rrAlmClientRxNr OBJECT-TYPE
	  SYNTAX EkiOnOff
	  MAX-ACCESS read-only
	  STATUS current
	  DESCRIPTION
        "
        Line 1 Optical Rx Not Ready :This
        OID indicates that a condition
         has arisen leading to invalid
         data on the Line 1 receiving side.
        <Condtype> CLIENT_RX_NR <Probcause>
        receiveFailure (41) <Alarmtype>
        equipmentAlarm (5) <Polarity> (2)
        "
	  ::= { pm1001rrAlmclientXfpAlarms2 5 }



pm1001rrAlmClientRxLos OBJECT-TYPE
	  SYNTAX EkiOnOff
	  MAX-ACCESS read-only
	  STATUS current
	  DESCRIPTION
        "
        Line 1 Loss Of Optical Signal
         :This bit indicates an absence
        of signal on the XFP/OTX  <Help>
         This alarm indicates if an optical
        signal is detected on the line
         1 transceiver input <Condtype>
        CLIENT_RX_LOS <Probcause> receiveFailure
        (41) <Alarmtype> physicalViolation
        (9) <Polarity> (2)
        "
	  ::= { pm1001rrAlmclientXfpAlarms2 4 }



pm1001rrAlmClientRxCdrNotLocked OBJECT-TYPE
	  SYNTAX EkiOnOff
	  MAX-ACCESS read-only
	  STATUS current
	  DESCRIPTION
        "
        Line 1 Optical Rx CDR Unlocked
        :This OID indicates that a loss
        of lock on the Line 1 receiving
        side CDR has been detected <Condtype>
        CLIENT_RX_CDR_NOT_LOCKED <Probcause>
        receiveFailure (41) <Alarmtype>
        equipmentAlarm (5) <Polarity> (2)
        "
	  ::= { pm1001rrAlmclientXfpAlarms2 3 }



pm1001rrAlmClientResetComplete OBJECT-TYPE
	  SYNTAX EkiOnOff
	  MAX-ACCESS read-only
	  STATUS current
	  DESCRIPTION
        "
        Not Used :This bit indicates that
        the internal reset process is completed
        and the data are available <Condtype>
        CLIENT_RESET_COMPLETE <Probcause>
        other (1) <Alarmtype> other (1)
        <Polarity> (2)
        "
	  ::= { pm1001rrAlmclientXfpAlarms2 1 }



--- *****************************************************
---     LEAF for the clientOtxTlhAlarms3 article
--- *****************************************************
pm1001rrAlmclientOtxTlhAlarms3 OBJECT IDENTIFIER ::= { pm1001rrAlmClientUrg 22 }




pm1001rrAlmClientLaserTempHighAla OBJECT-TYPE
	  SYNTAX EkiOnOff
	  MAX-ACCESS read-only
	  STATUS current
	  DESCRIPTION
        "
        Line 1 Laser Temp. High Alarm
         :Alarm indicating the Line 1 OTX
        TLH laser temperature is higher
        than the threshold written in the
        EEPROM <Condtype> CLIENT_LASER_TEMP_HIGH_ALA
        <Probcause> temperatureUnacceptable
        (51) <Alarmtype> equipmentAlarm
        (5) <Polarity> (2)
        "
	  ::= { pm1001rrAlmclientOtxTlhAlarms3 14 }



pm1001rrAlmClientFreqDevHighAla OBJECT-TYPE
	  SYNTAX EkiOnOff
	  MAX-ACCESS read-only
	  STATUS current
	  DESCRIPTION
        "
        Line 1 Freq. Deviation High Alarm
        :Alarm indicating the Line 1 OTX
        TLH frequency deviation is higher
        than the threshold written in the
        EEPROM <Condtype> CLIENT_FREQ_DEV_HIGH_ALA
        <Probcause> transmitterFailure
         (56) <Alarmtype> equipmentAlarm
        (5) <Polarity> (2)
        "
	  ::= { pm1001rrAlmclientOtxTlhAlarms3 12 }



pm1001rrAlmClientCdrNotReady OBJECT-TYPE
	  SYNTAX EkiOnOff
	  MAX-ACCESS read-only
	  STATUS current
	  DESCRIPTION
        "
        Line 1 CDR Not Ready :This OID
        indicates the Clock Data Recovery
        unit is not yet initialized
         <Help>   This alarm indicates
         the Clock Data Recovery unit is
        not yet initialized. <Condtype>
        CLIENT_CDR_NOT_READY <Probcause>
        receiveFailure (41) <Alarmtype>
        equipmentAlarm (5) <Polarity> (2)
        "
	  ::= { pm1001rrAlmclientOtxTlhAlarms3 9 }



pm1001rrAlmClientAgingHighAla OBJECT-TYPE
	  SYNTAX EkiOnOff
	  MAX-ACCESS read-only
	  STATUS current
	  DESCRIPTION
        "
        Line 1 OTX TLH Aging High Alarm
        :Alarm indicating the Line 1 OTX
        TLH aging is higher than the threshold
        written in the EEPROM <Condtype>
        CLIENT_AGING_HIGH_ALA <Probcause>
        transmitterFailure (56) <Alarmtype>
        equipmentAlarm (5) <Polarity> (2)
        "
	  ::= { pm1001rrAlmclientOtxTlhAlarms3 6 }



pm1001rrAlmClientModulatorAgingHighAla OBJECT-TYPE
	  SYNTAX EkiOnOff
	  MAX-ACCESS read-only
	  STATUS current
	  DESCRIPTION
        "
        Line 1 Modulator Aging High Alarm
        :Alarm indicating the Line 1 OTX
        TLH modulator aging is higher than
        the threshold written in the EEPROM
        <Condtype> CLIENT_MODULATOR_AGING_HIGH_ALA
        <Probcause> transmitterFailure
         (56) <Alarmtype> equipmentAlarm
        (5) <Polarity> (2)
        "
	  ::= { pm1001rrAlmclientOtxTlhAlarms3 5 }



--- *****************************************************
---     LEAF for the clientOtxTlhWarnings article
--- *****************************************************
pm1001rrAlmclientOtxTlhWarnings OBJECT IDENTIFIER ::= { pm1001rrAlmClientNurg 23 }




pm1001rrAlmClientLaserTempHighWarning OBJECT-TYPE
	  SYNTAX EkiOnOff
	  MAX-ACCESS read-only
	  STATUS current
	  DESCRIPTION
        "
        Line 1 Laser Temp. High Warning
        :Warning indicating the Line 1
         OTX TLH laser temperature is higher
        than the threshold written in the
        EEPROM <Condtype> CLIENT_LASER_TEMP_HIGH_WARNING
        <Probcause> temperatureUnacceptable
        (51) <Alarmtype> equipmentAlarm
        (5) <Polarity> (2)
        "
	  ::= { pm1001rrAlmclientOtxTlhWarnings 14 }



pm1001rrAlmClientFreqDevHighWarning OBJECT-TYPE
	  SYNTAX EkiOnOff
	  MAX-ACCESS read-only
	  STATUS current
	  DESCRIPTION
        "
        Line 1 Freq. Deviation High Warning
        :Warning indicating the Line 1
         OTX TLH frequency deviation is
        higher than the threshold written
        in the EEPROM <Condtype> CLIENT_FREQ_DEV_HIGH_WARNING
        <Probcause> transmitterFailure
         (56) <Alarmtype> equipmentAlarm
        (5) <Polarity> (2)
        "
	  ::= { pm1001rrAlmclientOtxTlhWarnings 12 }



pm1001rrAlmClientAgingHighWarning OBJECT-TYPE
	  SYNTAX EkiOnOff
	  MAX-ACCESS read-only
	  STATUS current
	  DESCRIPTION
        "
        Line 1 OTX TLH Aging High Warning
        :Warning indicating the Line 1
         OTX TLH aging is higher than the
        threshold written in the EEPROM
        <Condtype> CLIENT_AGING_HIGH_WARNING
        <Probcause> transmitterFailure
         (56) <Alarmtype> equipmentAlarm
        (5) <Polarity> (2)
        "
	  ::= { pm1001rrAlmclientOtxTlhWarnings 6 }



pm1001rrAlmClientModulatorAgingHighWarning OBJECT-TYPE
	  SYNTAX EkiOnOff
	  MAX-ACCESS read-only
	  STATUS current
	  DESCRIPTION
        "
        Line 1 Modulator Aging High Warning
        :Warning indicating the Line 1
         OTX TLH modulator aging is higher
        than the threshold written in the
        EEPROM <Condtype> CLIENT_MODULATOR_AGING_HIGH_WARNING
        <Probcause> transmitterFailure
         (56) <Alarmtype> equipmentAlarm
        (5) <Polarity> (2)
        "
	  ::= { pm1001rrAlmclientOtxTlhWarnings 5 }



--- *****************************************************
---     LEAF for the lineXfpAlarm1 article
--- *****************************************************
pm1001rrAlmlineXfpAlarm1 OBJECT IDENTIFIER ::= { pm1001rrAlmLineUrg 24 }




pm1001rrAlmLineRxPwrHighAla OBJECT-TYPE
	  SYNTAX EkiOnOff
	  MAX-ACCESS read-only
	  STATUS current
	  DESCRIPTION
        "
        Line 2 Optical Rx Power High :Alarm
        indicating that the Line 2 XFP/OTX
        received optical power is higher
        than the threshold value written
        in the Line 2 XFP/OTX EEPROM <Condtype>
        LINE_RX_PWR_HIGH_ALA <Probcause>
        receiveFailure (41) <Alarmtype>
        equipmentAlarm (5) <Polarity> (2)
        "
	  ::= { pm1001rrAlmlineXfpAlarm1 16 }



pm1001rrAlmLineRxPwrLowAla OBJECT-TYPE
	  SYNTAX EkiOnOff
	  MAX-ACCESS read-only
	  STATUS current
	  DESCRIPTION
        "
        Line 2 Optical Rx Power Low :Alarm
        indicating that the Line 2 XFP/OTX
        received optical power is lower
        than the threshold value written
        in the Line 2 XFP/OTX EEPROM  <Condtype>
        LINE_RX_PWR_LOW_ALA <Probcause>
        receiveFailure (41) <Alarmtype>
        equipmentAlarm (5) <Polarity> (2)
        "
	  ::= { pm1001rrAlmlineXfpAlarm1 15 }



pm1001rrAlmLineTempHighAla OBJECT-TYPE
	  SYNTAX EkiOnOff
	  MAX-ACCESS read-only
	  STATUS current
	  DESCRIPTION
        "
        Line 2 Transceiver Temp High :Alarm
        indicating that the Line 2 XFP/OTX
        temperature is higher than the
         threshold value written in the
        Line 2 XFP/OTX EEPROM <Condtype>
        LINE_TEMP_HIGH_ALA <Probcause>
         temperatureUnacceptable (51) <Alarmtype>
        equipmentAlarm (5) <Polarity> (2)
        "
	  ::= { pm1001rrAlmlineXfpAlarm1 8 }



pm1001rrAlmLineTempLowAla OBJECT-TYPE
	  SYNTAX EkiOnOff
	  MAX-ACCESS read-only
	  STATUS current
	  DESCRIPTION
        "
        Line 2 Transceiver Temp Low :Alarm
        indicating that the Line 2 XFP/OTX
        temperature is lower than the threshold
        value written in the Line 2 XFP/OTX
        EEPROM <Condtype> LINE_TEMP_LOW_ALA
        <Probcause> temperatureUnacceptable
        (51) <Alarmtype> equipmentAlarm
        (5) <Polarity> (2)
        "
	  ::= { pm1001rrAlmlineXfpAlarm1 7 }



pm1001rrAlmLineTxBiasHighAla OBJECT-TYPE
	  SYNTAX EkiOnOff
	  MAX-ACCESS read-only
	  STATUS current
	  DESCRIPTION
        "
        Line 2 Transceiver Bias High :Alarm
        indicating that the Line 2 XFP/OTX
        transmitter laser bias current
         is higher than the threshold value
        written in the Line 2 XFP/OTX EEPROM
        <Condtype> LINE_TX_BIAS_HIGH_ALA
        <Probcause> transmitterFailure
         (56) <Alarmtype> equipmentAlarm
        (5) <Polarity> (2)
        "
	  ::= { pm1001rrAlmlineXfpAlarm1 4 }



pm1001rrAlmLineTxBiasLowAla OBJECT-TYPE
	  SYNTAX EkiOnOff
	  MAX-ACCESS read-only
	  STATUS current
	  DESCRIPTION
        "
        Line 2 Transceiver Bias Low :Alarm
        indicating that the Line 2 XFP/OTX
        transmitter laser bias current
         is lower than the threshold value
        written in the Line 2 XFP/OTX EEPROM
        <Condtype> LINE_TX_BIAS_LOW_ALA
        <Probcause> transmitterFailure
         (56) <Alarmtype> equipmentAlarm
        (5) <Polarity> (2)
        "
	  ::= { pm1001rrAlmlineXfpAlarm1 3 }



pm1001rrAlmLineTxPwrHighAla OBJECT-TYPE
	  SYNTAX EkiOnOff
	  MAX-ACCESS read-only
	  STATUS current
	  DESCRIPTION
        "
        Line 2 Optical Tx Power High :Alarm
        indicating that the Line 2 XFP/OTX
        transmitter transmitter output
         power is higher than the threshold
        value written in the Line 2 XFP/OTX
        EEPROM <Condtype> LINE_TX_PWR_HIGH_ALA
        <Probcause> transmitterFailure
         (56) <Alarmtype> equipmentAlarm
        (5) <Polarity> (2)
        "
	  ::= { pm1001rrAlmlineXfpAlarm1 2 }



pm1001rrAlmLineTxPwrLowAla OBJECT-TYPE
	  SYNTAX EkiOnOff
	  MAX-ACCESS read-only
	  STATUS current
	  DESCRIPTION
        "
        Line 2 Optical Tx Power Low :Alarm
        indicating that the Line 2 XFP/OTX
        transmitter transmitter output
         power is lower than the threshold
        value written in the Line 2 XFP/OTX
        EEPROM <Condtype> LINE_TX_PWR_LOW_ALA
        <Probcause> transmitterFailure
         (56) <Alarmtype> equipmentAlarm
        (5) <Polarity> (2)
        "
	  ::= { pm1001rrAlmlineXfpAlarm1 1 }



--- *****************************************************
---     LEAF for the lineXfpWarnings article
--- *****************************************************
pm1001rrAlmlineXfpWarnings OBJECT IDENTIFIER ::= { pm1001rrAlmLineNurg 25 }




pm1001rrAlmLineRxPwrHighWng OBJECT-TYPE
	  SYNTAX EkiOnOff
	  MAX-ACCESS read-only
	  STATUS current
	  DESCRIPTION
        "
        Line 2 Optical Rx Power High Warning
        :Warning indicating that the Line
        2 XFP/OTX received optical power
        is higher than the threshold value
        written in the Line 2 XFP/OTX EEPROM
        <Condtype> LINE_RX_PWR_HIGH_WNG
        <Probcause> receiveFailure (41)
        <Alarmtype> equipmentAlarm (5)
         <Polarity> (2)
        "
	  ::= { pm1001rrAlmlineXfpWarnings 16 }



pm1001rrAlmLineRxPwrLowWng OBJECT-TYPE
	  SYNTAX EkiOnOff
	  MAX-ACCESS read-only
	  STATUS current
	  DESCRIPTION
        "
        Line 2 Optical Rx Power Low Warning
        :Warning indicating that the Line
        2 XFP/OTX received optical power
        is lower than the threshold value
        written in the Line 2 XFP/OTX EEPROM
         <Condtype> LINE_RX_PWR_LOW_WNG
        <Probcause> receiveFailure (41)
        <Alarmtype> equipmentAlarm (5)
         <Polarity> (2)
        "
	  ::= { pm1001rrAlmlineXfpWarnings 15 }



pm1001rrAlmLineTempHighWng OBJECT-TYPE
	  SYNTAX EkiOnOff
	  MAX-ACCESS read-only
	  STATUS current
	  DESCRIPTION
        "
        Line 2 Transceiver Temp High Warning
        :Warning indicating that the Line
        2 XFP/OTX temperature is higher
        than the threshold value written
        in the Line 2 XFP/OTX EEPROM <Condtype>
        LINE_TEMP_HIGH_WNG <Probcause>
         temperatureUnacceptable (51) <Alarmtype>
        equipmentAlarm (5) <Polarity> (2)
        "
	  ::= { pm1001rrAlmlineXfpWarnings 8 }



pm1001rrAlmLineTempLowWng OBJECT-TYPE
	  SYNTAX EkiOnOff
	  MAX-ACCESS read-only
	  STATUS current
	  DESCRIPTION
        "
        Line 2 Transceiver Temp Low Warning
        :Warning indicating that the Line
        2 XFP/OTX temperature is lower
         than the threshold value written
        in the Line 2 XFP/OTX EEPROM <Condtype>
        LINE_TEMP_LOW_WNG <Probcause> temperatureUnacceptable
        (51) <Alarmtype> equipmentAlarm
        (5) <Polarity> (2)
        "
	  ::= { pm1001rrAlmlineXfpWarnings 7 }



pm1001rrAlmLineTxBiasHighWng OBJECT-TYPE
	  SYNTAX EkiOnOff
	  MAX-ACCESS read-only
	  STATUS current
	  DESCRIPTION
        "
        Line 2 Transceiver Bias High Warning
        :Warning indicating that the Line
        2 XFP/OTX transmitter laser bias
        current is higher than the threshold
        value written in the Line 2 XFP/OTX
        EEPROM <Condtype> LINE_TX_BIAS_HIGH_WNG
        <Probcause> transmitterFailure
         (56) <Alarmtype> equipmentAlarm
        (5) <Polarity> (2)
        "
	  ::= { pm1001rrAlmlineXfpWarnings 4 }



pm1001rrAlmLineTxBiasLowWng OBJECT-TYPE
	  SYNTAX EkiOnOff
	  MAX-ACCESS read-only
	  STATUS current
	  DESCRIPTION
        "
        Line 2 Transceiver Bias Low Warning
        :Warning indicating that the Line
        2 XFP/OTX transmitter laser bias
        current is lower than the threshold
        value written in the Line 2 XFP/OTX
        EEPROM <Condtype> LINE_TX_BIAS_LOW_WNG
        <Probcause> transmitterFailure
         (56) <Alarmtype> equipmentAlarm
        (5) <Polarity> (2)
        "
	  ::= { pm1001rrAlmlineXfpWarnings 3 }



pm1001rrAlmLineTxPwrHighWng OBJECT-TYPE
	  SYNTAX EkiOnOff
	  MAX-ACCESS read-only
	  STATUS current
	  DESCRIPTION
        "
        Line 2 Optical Tx Power High Warning
        :Warning indicating that the Line
        2 XFP/OTX transmitter transmitter
        output power is higher than the
        threshold value written in the
         Line 2 XFP/OTX EEPROM <Condtype>
        LINE_TX_PWR_HIGH_WNG <Probcause>
        transmitterFailure (56) <Alarmtype>
        equipmentAlarm (5) <Polarity> (2)
        "
	  ::= { pm1001rrAlmlineXfpWarnings 2 }



pm1001rrAlmLineTxPwrLowWng OBJECT-TYPE
	  SYNTAX EkiOnOff
	  MAX-ACCESS read-only
	  STATUS current
	  DESCRIPTION
        "
        Line 2 Optical Tx Power Low Warning
        :Warning indicating that the Line
        2 XFP/OTX transmitter transmitter
        output power is lower than the
         threshold value written in the
        Line 2 XFP/OTX EEPROM <Condtype>
        LINE_TX_PWR_LOW_WNG <Probcause>
        transmitterFailure (56) <Alarmtype>
        equipmentAlarm (5) <Polarity> (2)
        "
	  ::= { pm1001rrAlmlineXfpWarnings 1 }



--- *****************************************************
---     LEAF for the lineXfpAlarms2 article
--- *****************************************************
pm1001rrAlmlineXfpAlarms2 OBJECT IDENTIFIER ::= { pm1001rrAlmLineCrit 27 }




pm1001rrAlmLineApdSupplyFault OBJECT-TYPE
	  SYNTAX EkiOnOff
	  MAX-ACCESS read-only
	  STATUS current
	  DESCRIPTION
        "
        Line 2 Rx Photodiode Power Failed
        :This OID indicates a failure on
        the Line 2 APD power supply <Condtype>
        LINE_APD_SUPPLY_FAULT <Probcause>
        receiverFailure (42) <Alarmtype>
        equipmentAlarm (5) <Polarity> (2)
        "
	  ::= { pm1001rrAlmlineXfpAlarms2 16 }



pm1001rrAlmLineTecFault OBJECT-TYPE
	  SYNTAX EkiOnOff
	  MAX-ACCESS read-only
	  STATUS current
	  DESCRIPTION
        "
        Line 2 Optical Tx Temp Regul.
         Failed :This OID indicates a failure
        on the Line 2 TEC module <Condtype>
        LINE_TEC_FAULT <Probcause> transmitterFailure
        (56) <Alarmtype> equipmentAlarm
        (5) <Polarity> (2)
        "
	  ::= { pm1001rrAlmlineXfpAlarms2 15 }



pm1001rrAlmLineWavelengthUnlocked OBJECT-TYPE
	  SYNTAX EkiOnOff
	  MAX-ACCESS read-only
	  STATUS current
	  DESCRIPTION
        "
        Line 2 Optical Tx Wavelength Unlocked
        :This OID indicates that the Line
        2 wavelength error is exceeding
        the manufacturer tolerance <Condtype>
        LINE_WAVELENGTH_UNLOCKED <Probcause>
        transmitterFailure (56) <Alarmtype>
        equipmentAlarm (5) <Polarity> (2)
        "
	  ::= { pm1001rrAlmlineXfpAlarms2 14 }



pm1001rrAlmLineChannelNotAcquired OBJECT-TYPE
	  SYNTAX EkiOnOff
	  MAX-ACCESS read-only
	  STATUS current
	  DESCRIPTION
        "
        Line 2 DWDM Channel Not Acquired
        :This OID indicates the transceiver
        didn't tune the DWDM Channel succesfully.
         <Help>  This status indicates
         the transceiver has not tuned
         the DWDM Channel succesfully.
         <Condtype> LINE_CHANNEL_NOT_ACQUIRED
        <Probcause> transmitterFailure
         (56) <Alarmtype> equipmentAlarm
        (5) <Polarity> (2)
        "
	  ::= { pm1001rrAlmlineXfpAlarms2 10 }



pm1001rrAlmLineTxNr OBJECT-TYPE
	  SYNTAX EkiOnOff
	  MAX-ACCESS read-only
	  STATUS current
	  DESCRIPTION
        "
        Line 2 Optical Tx Not Ready :This
        OID indicates a condition has arisen
        leading to invalid data on the
         Line 2 transmitting side <Condtype>
        LINE_TX_NR <Probcause> transmitterFailure
        (56) <Alarmtype> equipmentAlarm
        (5) <Polarity> (2)
        "
	  ::= { pm1001rrAlmlineXfpAlarms2 8 }



pm1001rrAlmLineTxFault OBJECT-TYPE
	  SYNTAX EkiOnOff
	  MAX-ACCESS read-only
	  STATUS current
	  DESCRIPTION
        "
        Line 2 Optical Tx Failure :This
        OID indicates a fault condition
        on the Line 2 laser detected by
        the safety syste <Condtype> LINE_TX_FAULT
        <Probcause> transmitterFailure
         (56) <Alarmtype> equipmentAlarm
        (5) <Polarity> (2)
        "
	  ::= { pm1001rrAlmlineXfpAlarms2 7 }



pm1001rrAlmLineTxCdrNotLocked OBJECT-TYPE
	  SYNTAX EkiOnOff
	  MAX-ACCESS read-only
	  STATUS current
	  DESCRIPTION
        "
        Line 2 Optical Tx CDR Unlocked
        :This OID indicates a loss of lock
        on the Line 2 transmitting side
        CDR has been detected. <Condtype>
        LINE_TX_CDR_NOT_LOCKED <Probcause>
        transmitterFailure (56) <Alarmtype>
        equipmentAlarm (5) <Polarity> (2)
        "
	  ::= { pm1001rrAlmlineXfpAlarms2 6 }



pm1001rrAlmLineRxNr OBJECT-TYPE
	  SYNTAX EkiOnOff
	  MAX-ACCESS read-only
	  STATUS current
	  DESCRIPTION
        "
        Line 2 Optical Rx Not Ready :This
        OID indicates that a condition
         has arisen leading to invalid
         data on the Line 2 receiving side.
        <Condtype> LINE_RX_NR <Probcause>
        receiveFailure (41) <Alarmtype>
        equipmentAlarm (5) <Polarity> (2)
        "
	  ::= { pm1001rrAlmlineXfpAlarms2 5 }



pm1001rrAlmLineRxLos OBJECT-TYPE
	  SYNTAX EkiOnOff
	  MAX-ACCESS read-only
	  STATUS current
	  DESCRIPTION
        "
        Line 2 Loss Of Optical Signal
         :This bit indicates an absence
        of signal on the XFP/OTX  <Help>
         This alarm indicates if an optical
        signal is detected on the line
         2 transceiver input <Condtype>
        LINE_RX_LOS <Probcause> receiveFailure
        (41) <Alarmtype> physicalViolation
        (9) <Polarity> (2)
        "
	  ::= { pm1001rrAlmlineXfpAlarms2 4 }



pm1001rrAlmLineRxCdrNotLocked OBJECT-TYPE
	  SYNTAX EkiOnOff
	  MAX-ACCESS read-only
	  STATUS current
	  DESCRIPTION
        "
        Line 2 Optical Rx CDR Unlocked
        :This OID indicates that a loss
        of lock on the Line 2 receiving
        side CDR has been detected <Condtype>
        LINE_RX_CDR_NOT_LOCKED <Probcause>
        receiveFailure (41) <Alarmtype>
        equipmentAlarm (5) <Polarity> (2)
        "
	  ::= { pm1001rrAlmlineXfpAlarms2 3 }



pm1001rrAlmLineResetComplete OBJECT-TYPE
	  SYNTAX EkiOnOff
	  MAX-ACCESS read-only
	  STATUS current
	  DESCRIPTION
        "
        Not Used :This bit indicates that
        the internal reset process is completed
        and the data are available <Condtype>
        LINE_RESET_COMPLETE <Probcause>
        other (1) <Alarmtype> other (1)
        <Polarity> (2)
        "
	  ::= { pm1001rrAlmlineXfpAlarms2 1 }



--- *****************************************************
---     LEAF for the rrLineOtxTlhAlarms3 article
--- *****************************************************
pm1001rrAlmrrLineOtxTlhAlarms3 OBJECT IDENTIFIER ::= { pm1001rrAlmLineUrg 30 }




pm1001rrAlmLineLaserTempHighAla OBJECT-TYPE
	  SYNTAX EkiOnOff
	  MAX-ACCESS read-only
	  STATUS current
	  DESCRIPTION
        "
        Line 2 Laser Temp. High Alarm
         :Alarm indicating the Line 2 OTX
        TLH laser temperature is higher
        than the threshold written in the
        EEPROM <Condtype> LINE_LASER_TEMP_HIGH_ALA
        <Probcause> temperatureUnacceptable
        (51) <Alarmtype> equipmentAlarm
        (5) <Polarity> (2)
        "
	  ::= { pm1001rrAlmrrLineOtxTlhAlarms3 14 }



pm1001rrAlmLineFreqDevHighAla OBJECT-TYPE
	  SYNTAX EkiOnOff
	  MAX-ACCESS read-only
	  STATUS current
	  DESCRIPTION
        "
        Line 2 Freq. Deviation High Alarm
        :Alarm indicating the Line 2 OTX
        TLH frequency deviation is higher
        than the threshold written in the
        EEPROM <Condtype> LINE_FREQ_DEV_HIGH_ALA
        <Probcause> transmitterFailure
         (56) <Alarmtype> equipmentAlarm
        (5) <Polarity> (2)
        "
	  ::= { pm1001rrAlmrrLineOtxTlhAlarms3 12 }



pm1001rrAlmLineCdrNotReady OBJECT-TYPE
	  SYNTAX EkiOnOff
	  MAX-ACCESS read-only
	  STATUS current
	  DESCRIPTION
        "
        Line 2 CDR Not Ready :This OID
        indicates the Clock Data Recovery
        unit is not yet initialized
         <Help>   This alarm indicates
         the Clock Data Recovery unit is
        not yet initialized. <Condtype>
        LINE_CDR_NOT_READY <Probcause>
         receiveFailure (41) <Alarmtype>
        equipmentAlarm (5) <Polarity> (2)
        "
	  ::= { pm1001rrAlmrrLineOtxTlhAlarms3 9 }



pm1001rrAlmLineAgingHighAla OBJECT-TYPE
	  SYNTAX EkiOnOff
	  MAX-ACCESS read-only
	  STATUS current
	  DESCRIPTION
        "
        Line 2 OTX TLH Aging High Alarm
        :Alarm indicating the Line 2 OTX
        TLH aging is higher than the threshold
        written in the EEPROM <Condtype>
        LINE_AGING_HIGH_ALA <Probcause>
        transmitterFailure (56) <Alarmtype>
        equipmentAlarm (5) <Polarity> (2)
        "
	  ::= { pm1001rrAlmrrLineOtxTlhAlarms3 6 }



pm1001rrAlmLineModulatorAgingHighAla OBJECT-TYPE
	  SYNTAX EkiOnOff
	  MAX-ACCESS read-only
	  STATUS current
	  DESCRIPTION
        "
        Line 2 Modulator Aging High Alarm
        :Alarm indicating the Line 2 OTX
        TLH modulator aging is higher than
        the threshold written in the EEPROM
        <Condtype> LINE_MODULATOR_AGING_HIGH_ALA
        <Probcause> transmitterFailure
         (56) <Alarmtype> equipmentAlarm
        (5) <Polarity> (2)
        "
	  ::= { pm1001rrAlmrrLineOtxTlhAlarms3 5 }



--- *****************************************************
---     LEAF for the rrLineOtxTlhWarnings article
--- *****************************************************
pm1001rrAlmrrLineOtxTlhWarnings OBJECT IDENTIFIER ::= { pm1001rrAlmLineNurg 31 }




pm1001rrAlmLineLaserTempHighWarning OBJECT-TYPE
	  SYNTAX EkiOnOff
	  MAX-ACCESS read-only
	  STATUS current
	  DESCRIPTION
        "
        Line 2 Laser Temp. High Warning
        :Warning indicating the Line 2
         OTX TLH laser temperature is higher
        than the threshold written in the
        EEPROM <Condtype> LINE_LASER_TEMP_HIGH_WARNING
        <Probcause> temperatureUnacceptable
        (51) <Alarmtype> equipmentAlarm
        (5) <Polarity> (2)
        "
	  ::= { pm1001rrAlmrrLineOtxTlhWarnings 14 }



pm1001rrAlmLineFreqDevHighWarning OBJECT-TYPE
	  SYNTAX EkiOnOff
	  MAX-ACCESS read-only
	  STATUS current
	  DESCRIPTION
        "
        Line 2 Freq. Deviation High Warning
        :Warning indicating the Line 2
         OTX TLH frequency deviation is
        higher than the threshold written
        in the EEPROM <Condtype> LINE_FREQ_DEV_HIGH_WARNING
        <Probcause> transmitterFailure
         (56) <Alarmtype> equipmentAlarm
        (5) <Polarity> (2)
        "
	  ::= { pm1001rrAlmrrLineOtxTlhWarnings 12 }



pm1001rrAlmLineAgingHighWarning OBJECT-TYPE
	  SYNTAX EkiOnOff
	  MAX-ACCESS read-only
	  STATUS current
	  DESCRIPTION
        "
        Line 2 OTX TLH Aging High Warning
        :Warning indicating the Line 2
         OTX TLH aging is higher than the
        threshold written in the EEPROM
        <Condtype> LINE_AGING_HIGH_WARNING
        <Probcause> transmitterFailure
         (56) <Alarmtype> equipmentAlarm
        (5) <Polarity> (2)
        "
	  ::= { pm1001rrAlmrrLineOtxTlhWarnings 6 }



pm1001rrAlmLineModulatorAgingHighWarning OBJECT-TYPE
	  SYNTAX EkiOnOff
	  MAX-ACCESS read-only
	  STATUS current
	  DESCRIPTION
        "
        Line 2 Modulator Aging High Warning
        :Warning indicating the Line 2
         OTX TLH modulator aging is higher
        than the threshold written in the
        EEPROM <Condtype> LINE_MODULATOR_AGING_HIGH_WARNING
        <Probcause> transmitterFailure
         (56) <Alarmtype> equipmentAlarm
        (5) <Polarity> (2)
        "
	  ::= { pm1001rrAlmrrLineOtxTlhWarnings 5 }








--- *****************************************************
--- $$$$$$$$$$$$$$$$$$$$$$$$$$$$$$$$$$$$$$$$$$$$$$$$$$$$$
---     CONTROLS
--- $$$$$$$$$$$$$$$$$$$$$$$$$$$$$$$$$$$$$$$$$$$$$$$$$$$$$
--- *****************************************************



--- *****************************************************
---     LEAF for the synth0 article
--- *****************************************************
pm1001rrCtrlsynth0 OBJECT IDENTIFIER ::= { pm1001rrCtrlOther 0 }




pm1001rrCtrlConfClear OBJECT-TYPE
	  SYNTAX EkiOnOff
	  MAX-ACCESS read-write
	  STATUS current
	  DESCRIPTION
        "
        Clear Configuration Tables :This
        bit clears the configuration tables
        from configuration in the flash.
         <Help>  This control restores
         the default configuration of the
        module
        "
	  ::= { pm1001rrCtrlsynth0 13 }



pm1001rrCtrlConfFlash OBJECT-TYPE
	  SYNTAX EkiOnOff
	  MAX-ACCESS read-write
	  STATUS current
	  DESCRIPTION
        "
        Write Configuration Tables :This
        bit saves the current configuration
        of the module as configuration
         in the flash.  <Help>  This control
        saves the customer configuration
        on the module
        "
	  ::= { pm1001rrCtrlsynth0 9 }



pm1001rrCtrlConfLoad OBJECT-TYPE
	  SYNTAX EkiOnOff
	  MAX-ACCESS read-write
	  STATUS current
	  DESCRIPTION
        "
        Load Configuration Tables :When
        set this enables loading from flash
        configuration1 into the module.
        "
	  ::= { pm1001rrCtrlsynth0 1 }



--- *****************************************************
---     LEAF for the synth4 article
--- *****************************************************
pm1001rrCtrlsynth4 OBJECT IDENTIFIER ::= { pm1001rrCtrlOther 4 }




pm1001rrCtrlCorrelatOff OBJECT-TYPE
	  SYNTAX EkiOnOff
	  MAX-ACCESS read-write
	  STATUS current
	  DESCRIPTION
        "
        Disable Alarm Correlation :This
        OID disables the alarm correlation
        in the PM
        "
	  ::= { pm1001rrCtrlsynth4 2 }



pm1001rrCtrlCorrelatOn OBJECT-TYPE
	  SYNTAX EkiOnOff
	  MAX-ACCESS read-write
	  STATUS current
	  DESCRIPTION
        "
        Enable Alarm Correlation :This
        OID enables the alarm correlation
        in the PM
        "
	  ::= { pm1001rrCtrlsynth4 1 }



--- *****************************************************
---     LEAF for the swMgnt article
--- *****************************************************
pm1001rrCtrlswMgnt OBJECT IDENTIFIER ::= { pm1001rrCtrlOther 5 }




pm1001rrCtrlWarmReset OBJECT-TYPE
	  SYNTAX EkiOnOff
	  MAX-ACCESS read-write
	  STATUS current
	  DESCRIPTION
        "
        Software Warm Reset :This OID,
        when set, causes a warm reset of
        the Software. This reset is not
        traffic affecting, and the configuration
        of the Sofwtare remains unchanged.
         <Help>  This control initiates
        a warm reset of the module.
        "
	  ::= { pm1001rrCtrlswMgnt 3 }



pm1001rrCtrlColdReset OBJECT-TYPE
	  SYNTAX EkiOnOff
	  MAX-ACCESS read-write
	  STATUS current
	  DESCRIPTION
        "
        Software Cold Reset :This OID,
        when set, causes a cold reset of
        the Software. This reset is traffic
        affecting, and the configuration
        of Software is reloaded on start-up.
         <Help>  This control initiates
        a cold reset of the module.
        "
	  ::= { pm1001rrCtrlswMgnt 2 }



--- *****************************************************
---     LEAF for the clientXfpOnoff article
--- *****************************************************
pm1001rrCtrlclientXfpOnoff OBJECT IDENTIFIER ::= { pm1001rrCtrlClient 16 }




pm1001rrCtrlClientXfpOnoff OBJECT-TYPE
	  SYNTAX EkiOnOff
	  MAX-ACCESS read-write
	  STATUS current
	  DESCRIPTION
        "
        Line 1 Optical Laser Shutdown
         :This OID switches off the Line
        1 XFP/OTX  <Help>  This control
        defines the laser state of the
         line 1 transceiver
        "
	  ::= { pm1001rrCtrlclientXfpOnoff 1 }



--- *****************************************************
---     LEAF for the clientXfpLineLoop article
--- *****************************************************
pm1001rrCtrlclientXfpLineLoop OBJECT IDENTIFIER ::= { pm1001rrCtrlClient 17 }




pm1001rrCtrlClientXfpLineLoop OBJECT-TYPE
	  SYNTAX EkiOnOff
	  MAX-ACCESS read-write
	  STATUS current
	  DESCRIPTION
        "
        Line 1 Facility Loopback :This
        OID operates a Line 1 Facility
         Loopback, looping line 1 input
        signal on the line 1 output port.
        The loop is located on the line
        1 transceiver   <Help> This maintenance
        parameter operates a Line 1 Facility
        Loopback, looping line 1 input
         signal on the line 1 output port.
        The loop is located on the line
        1 transceiver
        "
	  ::= { pm1001rrCtrlclientXfpLineLoop 1 }



--- *****************************************************
---     LEAF for the clientXfiLoop article
--- *****************************************************
pm1001rrCtrlclientXfiLoop OBJECT IDENTIFIER ::= { pm1001rrCtrlClient 18 }




pm1001rrCtrlClientXfiLoop OBJECT-TYPE
	  SYNTAX EkiOnOff
	  MAX-ACCESS read-write
	  STATUS current
	  DESCRIPTION
        "
        Line 1 Terminal Loopback :This
        OID operates a Line 1 Terminal
         Loopback, looping line 2 input
        signal on the line 2 output port.
        The loop is located on the line
        1 transceiver  <Help> This maintenance
        parameter operates a Line 1 Terminal
        Loopback, looping line 2 input
         signal on the line 2 output port.
        The loop is located on the line
        1 transceiver
        "
	  ::= { pm1001rrCtrlclientXfiLoop 1 }



--- *****************************************************
---     LEAF for the clientTunableChannel article
--- *****************************************************

pm1001rrCtrlclientTunableChannel OBJECT-TYPE
	  SYNTAX Pm1001rrOtxChannel
	  MAX-ACCESS read-write
	  STATUS current
	  DESCRIPTION
        "
        ITU Channel :This OID selects
         the ITU channel of the Line 1
         OTX TLH Laser  <Help>   This control
        defines the ITU channel of the
         Line 1 OTX TLH Laser
        "
	  ::= { pm1001rrCtrlClient 19 }



--- *****************************************************
---     LEAF for the clientPhotodiodeMode article
--- *****************************************************

pm1001rrCtrlclientPhotodiodeMode OBJECT-TYPE
	  SYNTAX Pm1001rrOtxMode
	  MAX-ACCESS read-write
	  STATUS current
	  DESCRIPTION
        "
        OTX TLH Rx Sens. Mode :This OID
        defines the Rx sensiblity mode
         of the Line 1 OTX TLH  <Help>
           This control defines the receiver
        sensibility mode of the Line 1
         OTX TLH Laser (OTX60, OTX80 or
        Custom)
        "
	  ::= { pm1001rrCtrlClient 20 }



--- *****************************************************
---     LEAF for the clientPhotodiodeValue article
--- *****************************************************

pm1001rrCtrlclientPhotodiodeValue OBJECT-TYPE
	  SYNTAX Pm1001rrAdjustValue
	  MAX-ACCESS read-write
	  STATUS current
	  DESCRIPTION
        "
        OTX TLH Rx Sensibility :This OID
        sets the Rx sensibility of the
         Line 1 OTX TLH (custom mode only)
         <Help>   This control defines
         the receiver sensibility value
        (only in Custom mode) of the Line
        1 OTX TLH Laser
        "
	  ::= { pm1001rrCtrlClient 21 }



--- *****************************************************
---     LEAF for the clientPowerLaser article
--- *****************************************************

pm1001rrCtrlclientPowerLaser OBJECT-TYPE
	  SYNTAX Unsigned32 (0..65535)
	  MAX-ACCESS read-write
	  STATUS current
	  DESCRIPTION
        "
        Laser Output Power [3-5] :This
        OID sets the output power value
        on the laser of the Line 1 OTX
         TLH (AV=Power*10+158) (Unit =
         dBm)  <Help>   This control defines
        the start-up output power of the
        Line 1 OTX TLH
        "
	  ::= { pm1001rrCtrlClient 22 }



--- *****************************************************
---     LEAF for the clientOtxVlhReset article
--- *****************************************************
pm1001rrCtrlclientOtxVlhReset OBJECT IDENTIFIER ::= { pm1001rrCtrlLine 23 }




pm1001rrCtrlClientOtxVlhReset OBJECT-TYPE
	  SYNTAX EkiOnOff
	  MAX-ACCESS read-write
	  STATUS current
	  DESCRIPTION
        "
        Line 1 OTX-VLH Reset :This OID
        resets the OTX-VLH module   <Help>
         This control resets the OTX-TLH
        and its parameters
        "
	  ::= { pm1001rrCtrlclientOtxVlhReset 1 }



--- *****************************************************
---     LEAF for the lineXfpOnoff article
--- *****************************************************
pm1001rrCtrllineXfpOnoff OBJECT IDENTIFIER ::= { pm1001rrCtrlLine 24 }




pm1001rrCtrlLineXfpOnoff OBJECT-TYPE
	  SYNTAX EkiOnOff
	  MAX-ACCESS read-write
	  STATUS current
	  DESCRIPTION
        "
        Line 2 Optical Laser Shutdown
         :This OID switches off the Line
        2 XFP/OTX  <Help>  This control
        defines the laser state of the
         line 2 transceiver
        "
	  ::= { pm1001rrCtrllineXfpOnoff 1 }



--- *****************************************************
---     LEAF for the lineXfpLineLoop article
--- *****************************************************
pm1001rrCtrllineXfpLineLoop OBJECT IDENTIFIER ::= { pm1001rrCtrlLine 25 }




pm1001rrCtrlLineXfpLineLoop OBJECT-TYPE
	  SYNTAX EkiOnOff
	  MAX-ACCESS read-write
	  STATUS current
	  DESCRIPTION
        "
        Line 2 Facility Loopback :This
        OID operates a Line 2 Facility
         Loopback, looping line 2 input
        signal on the line 2 output port.
        The loop is located on the line
        2 transceiver. If the Line signal
        carries DCC, the management network
        is impacted  <Help> This maintenance
        parameter operates a Line 2 Facility
        Loopback, looping line 2 input
         signal on the line 2 output port.
        The loop is located on the line
        2 transceiver. If the Line signal
        carries DCC, the management network
        is impacted
        "
	  ::= { pm1001rrCtrllineXfpLineLoop 1 }



--- *****************************************************
---     LEAF for the lineXfiLoop article
--- *****************************************************
pm1001rrCtrllineXfiLoop OBJECT IDENTIFIER ::= { pm1001rrCtrlLine 26 }




pm1001rrCtrlLineXfiLoop OBJECT-TYPE
	  SYNTAX EkiOnOff
	  MAX-ACCESS read-write
	  STATUS current
	  DESCRIPTION
        "
        Line 2 Terminal Loopback :This
        OID operates a Line 2 Terminal
         Loopback, looping line 1 input
        signal on the line 1 output port.
        The loop is located on the line
        2 transceiver  <Help> This maintenance
        parameter operates a Line 2 Terminal
        Loopback, looping line 1 input
         signal on the line 1 output port.
        The loop is located on the line
        2 transceiver
        "
	  ::= { pm1001rrCtrllineXfiLoop 1 }



--- *****************************************************
---     LEAF for the lineTunableChannel article
--- *****************************************************

pm1001rrCtrllineTunableChannel OBJECT-TYPE
	  SYNTAX Pm1001rrOtxChannel
	  MAX-ACCESS read-write
	  STATUS current
	  DESCRIPTION
        "
        ITU Channel :This OID selects
         the ITU channel of the Line 2
         OTX TLH Laser  <Help>   This control
        defines the ITU channel of the
         Line 2 OTX TLH Laser
        "
	  ::= { pm1001rrCtrlLine 27 }



--- *****************************************************
---     LEAF for the linePhotodiodeMode article
--- *****************************************************

pm1001rrCtrllinePhotodiodeMode OBJECT-TYPE
	  SYNTAX Pm1001rrOtxMode
	  MAX-ACCESS read-write
	  STATUS current
	  DESCRIPTION
        "
        OTX TLH Rx Sens. Mode :This OID
        defines the Rx sensiblity mode
         of the Line 2 OTX TLH  <Help>
           This control defines the receiver
        sensibility mode of the Line 2
         OTX TLH Laser (OTX60, OTX80 or
        Custom)
        "
	  ::= { pm1001rrCtrlLine 28 }



--- *****************************************************
---     LEAF for the linePhotodiodeValue article
--- *****************************************************

pm1001rrCtrllinePhotodiodeValue OBJECT-TYPE
	  SYNTAX Pm1001rrAdjustValue
	  MAX-ACCESS read-write
	  STATUS current
	  DESCRIPTION
        "
        OTX TLH Rx Sensibility :This OID
        sets the Rx sensibility of the
         Line 2 OTX TLH (custom mode only)
         <Help>   This control defines
         the receiver sensibility value
        (only in Custom mode) of the Line
        2 OTX TLH Laser
        "
	  ::= { pm1001rrCtrlLine 29 }



--- *****************************************************
---     LEAF for the linePowerLaser article
--- *****************************************************

pm1001rrCtrllinePowerLaser OBJECT-TYPE
	  SYNTAX Unsigned32 (0..65535)
	  MAX-ACCESS read-write
	  STATUS current
	  DESCRIPTION
        "
        Laser Output Power [3-5] :This
        OID sets the output power value
        on the laser of the Line 2 OTX
         TLH (AV=Power*10+158) (Unit =
         dBm)  <Help>   This control defines
        the start-up output power of the
        Line 2 OTX TLH
        "
	  ::= { pm1001rrCtrlLine 30 }



--- *****************************************************
---     LEAF for the lineOtxVlhReset article
--- *****************************************************
pm1001rrCtrllineOtxVlhReset OBJECT IDENTIFIER ::= { pm1001rrCtrlLine 31 }




pm1001rrCtrlLineOtxVlhReset OBJECT-TYPE
	  SYNTAX EkiOnOff
	  MAX-ACCESS read-write
	  STATUS current
	  DESCRIPTION
        "
        Line 2 OTX-VLH Reset :This OID
        resets the OTX-VLH module   <Help>
         This control resets the OTX-TLH
        and its parameters
        "
	  ::= { pm1001rrCtrllineOtxVlhReset 1 }



--- *****************************************************
---     LEAF for the ledTest article
--- *****************************************************
pm1001rrCtrlledTest OBJECT IDENTIFIER ::= { pm1001rrCtrlOther 64 }




pm1001rrCtrlLedOff OBJECT-TYPE
	  SYNTAX EkiOnOff
	  MAX-ACCESS read-write
	  STATUS current
	  DESCRIPTION
        "
        Leds Off :This OID switches off
        all the Leds as a test feature.
         <Help>  This control initiates
        a test leds turning all the LEDs
        to OFF
        "
	  ::= { pm1001rrCtrlledTest 3 }



pm1001rrCtrlRedLed OBJECT-TYPE
	  SYNTAX EkiOnOff
	  MAX-ACCESS read-write
	  STATUS current
	  DESCRIPTION
        "
        Red Leds Test :This OID switches
        on all the red Leds as a test feature.
         <Help>  This control initiates
        a test leds turning all the LEDs
        to red
        "
	  ::= { pm1001rrCtrlledTest 2 }



pm1001rrCtrlGreenLed OBJECT-TYPE
	  SYNTAX EkiOnOff
	  MAX-ACCESS read-write
	  STATUS current
	  DESCRIPTION
        "
        Green Leds Test :This OID switches
        on all the green Leds as a test
        feature.  <Help>  This control
         initiates a test leds turning
         all the LEDs to green
        "
	  ::= { pm1001rrCtrlledTest 1 }








--- *****************************************************
--- $$$$$$$$$$$$$$$$$$$$$$$$$$$$$$$$$$$$$$$$$$$$$$$$$$$$$
---     MEASURES
--- $$$$$$$$$$$$$$$$$$$$$$$$$$$$$$$$$$$$$$$$$$$$$$$$$$$$$
--- *****************************************************



--- *****************************************************
---     LEAF for the clientTemperature article
--- *****************************************************

pm1001rrMesrclientTemperature OBJECT-TYPE
	  SYNTAX Unsigned32 (0..65535)
	  MAX-ACCESS read-only
	  STATUS current
	  DESCRIPTION
        "
        Line 1 Optical Module Temperature
        :This OID gives the temperature
        of the Client XFP/OTX, read from
        the DDM (Digital Diagnostic Monitoring)
         (Temperature = AV/256) (Unit =
        C)  <Help>  This measure gives
         the temperature of the line 1
         transceiver
        "
	  ::= { pm1001rrMesrClient 16 }



--- *****************************************************
---     LEAF for the clientTxBias article
--- *****************************************************

pm1001rrMesrclientTxBias OBJECT-TYPE
	  SYNTAX Unsigned32 (0..65535)
	  MAX-ACCESS read-only
	  STATUS current
	  DESCRIPTION
        "
        Line 1 XFP/OTX Tx Bias Current
        :This OID gives the bias value
         of the Client XFP/OTX, read from
        the DDM (Digital Diagnostic Monitoring)
        (Bias = AV/500) (Unit = mA)  <Help>
         This measure gives the bias of
        the line 1 transceiver
        "
	  ::= { pm1001rrMesrClient 18 }



--- *****************************************************
---     LEAF for the clientTxPower article
--- *****************************************************

pm1001rrMesrclientTxPower OBJECT-TYPE
	  SYNTAX Unsigned32 (0..65535)
	  MAX-ACCESS read-only
	  STATUS current
	  DESCRIPTION
        "
        Line 1 Optical Module Tx Power
        :This OID gives the transmit power
        value of the Client XFP/OTX, read
        from the DDM (Digital   Diagnostic
        Monitoring) (Power = 10*log(AV)-40)
        (Unit = dBm)  <Help>  This measure
        gives the Tx optical power of the
        line 1 transceiver
        "
	  ::= { pm1001rrMesrClient 19 }



--- *****************************************************
---     LEAF for the clientRxPower article
--- *****************************************************

pm1001rrMesrclientRxPower OBJECT-TYPE
	  SYNTAX Unsigned32 (0..65535)
	  MAX-ACCESS read-only
	  STATUS current
	  DESCRIPTION
        "
        Line 1 Optical Module Rx Power
        :This OID gives the receive power
        value of the Client XFP/OTX, read
        from the DDM (Digital Diagnostic
        Monitoring) (Power = 10*log(AV)-40)
        (Unit = dBm)  <Help>  This measure
        gives the Rx optical power of the
        line 1 transceiver
        "
	  ::= { pm1001rrMesrClient 20 }



--- *****************************************************
---     LEAF for the lineTemperature article
--- *****************************************************

pm1001rrMesrlineTemperature OBJECT-TYPE
	  SYNTAX Unsigned32 (0..65535)
	  MAX-ACCESS read-only
	  STATUS current
	  DESCRIPTION
        "
        Line 2 Optical Module Temperature
        :This OID gives the temperature
        of the Line XFP/OTX, read from
         the DDM (Digital Diagnostic Monitoring)
         (Temperature = AV/256) (Unit =
        C)  <Help>  This measure gives
         the temperature of the line 2
         transceiver
        "
	  ::= { pm1001rrMesrLine 24 }



--- *****************************************************
---     LEAF for the lineTxBias article
--- *****************************************************

pm1001rrMesrlineTxBias OBJECT-TYPE
	  SYNTAX Unsigned32 (0..65535)
	  MAX-ACCESS read-only
	  STATUS current
	  DESCRIPTION
        "
        Line 2 XFP/OTX Tx Bias Current
        :This OID gives the bias value
         of the Line XFP/OTX, read from
        the DDM (Digital Diagnostic Monitoring)
        (Bias = AV/500) (Unit = mA)  <Help>
         This measure gives the bias of
        the line 2 transceiver
        "
	  ::= { pm1001rrMesrLine 26 }



--- *****************************************************
---     LEAF for the lineTxPower article
--- *****************************************************

pm1001rrMesrlineTxPower OBJECT-TYPE
	  SYNTAX Unsigned32 (0..65535)
	  MAX-ACCESS read-only
	  STATUS current
	  DESCRIPTION
        "
        Line 2 Optical Module Tx Power
        :This OID gives the transmit power
        value of the Line XFP/OTX, read
        from the DDM (Digital   Diagnostic
        Monitoring)  (Power = 10*log(AV)-40)
        (Unit = dBm)  <Help>  This measure
        gives the Tx optical power of the
        line 2 transceiver
        "
	  ::= { pm1001rrMesrLine 27 }



--- *****************************************************
---     LEAF for the lineRxPower article
--- *****************************************************

pm1001rrMesrlineRxPower OBJECT-TYPE
	  SYNTAX Unsigned32 (0..65535)
	  MAX-ACCESS read-only
	  STATUS current
	  DESCRIPTION
        "
        Line 2 Optical Module Rx Power
        :This OID gives the receive power
        value of the Line XFP/OTX, read
        from the DDM (Digital Diagnostic
        Monitoring) (Power = 10*log(AV)-40)
        (Unit = dBm)  <Help>  This measure
        gives the Rx optical power of the
        line 2 transceiver
        "
	  ::= { pm1001rrMesrLine 28 }



--- *****************************************************
---     LEAF for the clientAging article
--- *****************************************************

pm1001rrMesrclientAging OBJECT-TYPE
	  SYNTAX Unsigned32 (0..65535)
	  MAX-ACCESS read-only
	  STATUS current
	  DESCRIPTION
        "
        Line 1 OTX TLH Aging :This OID
        gives the aging of the Line 1 OTX
        TLH, read from the DDM (Digital
        Diagnostic Monitoring) (Aging =
        AV) (Unit = %)  <Help>  This measure
        gives the aging of the line 1 OTX
        TLH
        "
	  ::= { pm1001rrMesrClient 32 }



--- *****************************************************
---     LEAF for the clientLaserTemperature article
--- *****************************************************

pm1001rrMesrclientLaserTemperature OBJECT-TYPE
	  SYNTAX Unsigned32 (0..65535)
	  MAX-ACCESS read-only
	  STATUS current
	  DESCRIPTION
        "
        Line 1 OTX TLH Laser Temperature
        :This OID gives the laser temperature
        of the Line 1 OTX TLH, read from
        the DDM (Digital Diagnostic Monitoring)
         (Temperature = AV/256) (Unit =
        C)  <Help>  This measure gives
         the laser temperature of the line
        1 OTX TLH
        "
	  ::= { pm1001rrMesrClient 33 }



--- *****************************************************
---     LEAF for the clientFreqDeviation article
--- *****************************************************

pm1001rrMesrclientFreqDeviation OBJECT-TYPE
	  SYNTAX Unsigned32 (0..65535)
	  MAX-ACCESS read-only
	  STATUS current
	  DESCRIPTION
        "
        Line 1 OTX TLH Frequency Deviation
        :This OID gives the frequency deviation
        of the Line 1 OTX TLH, read from
        the DDM (Digital Diagnostic Monitoring)
        (Deviation = (AV-32768)*100) (Unit
        = MHz)  <Help>   This measure gives
        the frequency deviation of the
         line 1 OTX TLH
        "
	  ::= { pm1001rrMesrClient 34 }



--- *****************************************************
---     LEAF for the clientLaserWvlength article
--- *****************************************************

pm1001rrMesrclientLaserWvlength OBJECT-TYPE
	  SYNTAX Unsigned32 (0..65535)
	  MAX-ACCESS read-only
	  STATUS current
	  DESCRIPTION
        "
        Line 1 Optical Module Wavelength
        :This OID gives the laser wavelength
        of the Line 1 OTX TLH, read from
        the DDM (Digital Diagnostic Monitoring)
        (Wavelength=299792458/((193,100+(AV-32768
        )*12,5)*10 3)) (Unit = nm)  <Help>
          This measure gives the laser
         wavelength of the line 1 OTX TLH
        "
	  ::= { pm1001rrMesrClient 35 }



--- *****************************************************
---     LEAF for the lineAging article
--- *****************************************************

pm1001rrMesrlineAging OBJECT-TYPE
	  SYNTAX Unsigned32 (0..65535)
	  MAX-ACCESS read-only
	  STATUS current
	  DESCRIPTION
        "
        Line 2 OTX TLH Aging :This OID
        gives the aging of the Line 2 OTX
        TLH, read from the DDM (Digital
        Diagnostic Monitoring) (Aging =
        AV) (Unit = %)  <Help>  This measure
        gives the aging of the line 2 OTX
        TLH
        "
	  ::= { pm1001rrMesrLine 40 }



--- *****************************************************
---     LEAF for the lineLaserTemperature article
--- *****************************************************

pm1001rrMesrlineLaserTemperature OBJECT-TYPE
	  SYNTAX Unsigned32 (0..65535)
	  MAX-ACCESS read-only
	  STATUS current
	  DESCRIPTION
        "
        Line 2 OTX TLH Laser Temperature
        :This OID gives the laser temperature
        of the Line 2 OTX TLH, read from
        the DDM (Digital Diagnostic Monitoring)
         (Temperature = AV/256) (Unit =
        C)  <Help>  This measure gives
         the laser temperature of the line
        2 OTX TLH
        "
	  ::= { pm1001rrMesrLine 41 }



--- *****************************************************
---     LEAF for the lineFreqDeviation article
--- *****************************************************

pm1001rrMesrlineFreqDeviation OBJECT-TYPE
	  SYNTAX Unsigned32 (0..65535)
	  MAX-ACCESS read-only
	  STATUS current
	  DESCRIPTION
        "
        Line 2 OTX TLH Frequency Deviation
        :This OID gives the frequency deviation
        of the Line 2 OTX TLH, read from
        the DDM (Digital Diagnostic Monitoring)
        (Deviation = (AV-32768)*100) (Unit
        = MHz)  <Help>  This measure gives
        the frequency deviation of the
         line 2 OTX TLH
        "
	  ::= { pm1001rrMesrLine 42 }



--- *****************************************************
---     LEAF for the lineLaserWvlength article
--- *****************************************************

pm1001rrMesrlineLaserWvlength OBJECT-TYPE
	  SYNTAX Unsigned32 (0..65535)
	  MAX-ACCESS read-only
	  STATUS current
	  DESCRIPTION
        "
        Line 2 Optical Module Wavelength
        :This OID gives the laser wavelength
        of the Line 2 OTX TLH, read from
        the DDM (Digital Diagnostic Monitoring)
        (Wavelength=299792458/((193,100+(AV-32768
        )*12,5)*10 3)) (Unit = nm)  <Help>
         This measure gives the laser wavelength
        of the line 2 OTX TLH
        "
	  ::= { pm1001rrMesrLine 43 }








--- *****************************************************
--- $$$$$$$$$$$$$$$$$$$$$$$$$$$$$$$$$$$$$$$$$$$$$$$$$$$$$
---     CONFIG
--- $$$$$$$$$$$$$$$$$$$$$$$$$$$$$$$$$$$$$$$$$$$$$$$$$$$$$
--- *****************************************************



--- *****************************************************
---     LEAF for the table Group lsd
--- *****************************************************

pm1001rrCfgLsd OBJECT IDENTIFIER ::= { pm1001rrConfig 1 }



--- *****************************************************
---     LEAF for the table 0012
--- *****************************************************

pm1001rrtableclientLsd OBJECT IDENTIFIER ::= { pm1001rrCfgLsd 1 }



pm1001rrCfglsdMode OBJECT-TYPE
	  SYNTAX Unsigned32 (0..65536)
	  MAX-ACCESS read-write
	  STATUS current
	  DESCRIPTION
        "
        LSD mode  on Client/Line Port
         :This OID enables/disables the
        automatic laser shutdown on the
        Client and Line ports
        "
	  ::= { pm1001rrtableclientLsd 2 }



pm1001rrCfgclientXfpAlarms OBJECT-TYPE
	  SYNTAX Unsigned32 (0..65536)
	  MAX-ACCESS read-write
	  STATUS current
	  DESCRIPTION
        "
        LSD contributors on Client port
        :This OID configures the contributors
        for the automatic laser shutdown
        of the client port
        "
	  ::= { pm1001rrtableclientLsd 3 }



pm1001rrCfgclientXfpAbsence OBJECT-TYPE
	  SYNTAX Unsigned32 (0..65536)
	  MAX-ACCESS read-write
	  STATUS current
	  DESCRIPTION
        "
        LSD contributors on Client port
        :This OID configures the contributors
        for the automatic laser shutdown
        of the client port
        "
	  ::= { pm1001rrtableclientLsd 4 }



pm1001rrCfglineXfpAlarms OBJECT-TYPE
	  SYNTAX Unsigned32 (0..65536)
	  MAX-ACCESS read-write
	  STATUS current
	  DESCRIPTION
        "
        LSD contributors on Line port
         :This OID configures the contributors
        for the automatic laser shutdown
        of the line port
        "
	  ::= { pm1001rrtableclientLsd 5 }



pm1001rrCfglineXfpAbsence OBJECT-TYPE
	  SYNTAX Unsigned32 (0..65536)
	  MAX-ACCESS read-write
	  STATUS current
	  DESCRIPTION
        "
        LSD contributors on Line port
         :This OID configures the contributors
        for the automatic laser shutdown
        of the line port
        "
	  ::= { pm1001rrtableclientLsd 6 }



--- *****************************************************
---     LEAF for the table Group startUp
--- *****************************************************

pm1001rrCfgStartUp OBJECT IDENTIFIER ::= { pm1001rrConfig 2 }



--- *****************************************************
---     LEAF for the table 2111
--- *****************************************************

pm1001rrtableclientStartup OBJECT IDENTIFIER ::= { pm1001rrCfgStartUp 1 }



pm1001rrCfgclientXfpCtrl OBJECT-TYPE
	  SYNTAX Unsigned32 (0..65536)
	  MAX-ACCESS read-write
	  STATUS current
	  DESCRIPTION
        "
        Default Settings on Line 1 Port
        :This  register configures the
         default initialisation settings
        on the client port.
        "
	  ::= { pm1001rrtableclientStartup 2 }



--- *****************************************************
---     LEAF for the table 2191
--- *****************************************************

pm1001rrtablelineStartup OBJECT IDENTIFIER ::= { pm1001rrCfgStartUp 2 }



pm1001rrCfglineXfpCtrl OBJECT-TYPE
	  SYNTAX Unsigned32 (0..65536)
	  MAX-ACCESS read-write
	  STATUS current
	  DESCRIPTION
        "
        Default Settings on Line 2 Port
        :This  register configures the
         default initialisation settings
        on the line port.
        "
	  ::= { pm1001rrtablelineStartup 2 }



pm1001rrCfgprotocolSelect OBJECT-TYPE
	  SYNTAX Unsigned32 (0..65536)
	  MAX-ACCESS read-write
	  STATUS current
	  DESCRIPTION
        "
        Bitrate selection on Line/Client
        port :This OID register configure
        the bitrate for the client and
         line interface (0=9,953 Gb/s -
        1=10,3125 Gb/s - 2=9,953 Gb/s -
        3=10,518 Gb/s - 4=10,664 Gb/s -
        5=10,709 Gb/s - 6=11,06 Gb/s).
        "
	  ::= { pm1001rrtablelineStartup 18 }



--- *****************************************************
---     LEAF for the table 2511
--- *****************************************************

pm1001rrtableclientOtxtlh OBJECT IDENTIFIER ::= { pm1001rrCfgStartUp 3 }



pm1001rrCfgclientDitherControl OBJECT-TYPE
	  SYNTAX Unsigned32 (0..65536)
	  MAX-ACCESS read-write
	  STATUS current
	  DESCRIPTION
        "
        Default Settings on Dither Line
        1 :This  register configures the
        default initialisation settings
        on the dither of the client port.
        "
	  ::= { pm1001rrtableclientOtxtlh 2 }



pm1001rrCfgclientDitherRate OBJECT-TYPE
	  SYNTAX Unsigned32 (0..65536)
	  MAX-ACCESS read-write
	  STATUS current
	  DESCRIPTION
        "
        Default Line 1 OTX TLH FM amplitude
        :This register configures the start-up
        width of the frequency modulation
        of the line 1 OTX TLH
        "
	  ::= { pm1001rrtableclientOtxtlh 3 }



pm1001rrCfgclientDitherFhz OBJECT-TYPE
	  SYNTAX Unsigned32 (0..65536)
	  MAX-ACCESS read-write
	  STATUS current
	  DESCRIPTION
        "
        Default Line 1 OTX TLH FM frequency
        :This register configures the start-up
        frequency of the frequency modulation
        of the line 1 OTX TLH
        "
	  ::= { pm1001rrtableclientOtxtlh 4 }



pm1001rrCfgclientPwrLaser OBJECT-TYPE
	  SYNTAX Unsigned32 (0..65536)
	  MAX-ACCESS read-write
	  STATUS current
	  DESCRIPTION
        "
        Defaut Line 1 OTX TLH output Power
        :This register configures the start-up
        output power of the line 1 OTX
         TLH  (Unit = dBm)
        "
	  ::= { pm1001rrtableclientOtxtlh 5 }



pm1001rrCfgclientFCurrent OBJECT-TYPE
	  SYNTAX Unsigned32 (0..65536)
	  MAX-ACCESS read-write
	  STATUS current
	  DESCRIPTION
        "
        Default Line 1 OTX TLH Channel
        :This register configures the start-up
        laser channel of the line 1 OTX
        TLH
        "
	  ::= { pm1001rrtableclientOtxtlh 6 }



pm1001rrCfgclientGridCurrent OBJECT-TYPE
	  SYNTAX Unsigned32 (0..65536)
	  MAX-ACCESS read-write
	  STATUS current
	  DESCRIPTION
        "
        Default Line 1 OTX TLH Grid :This
        register configures the start-up
        laser grid of the line 1 OTX TLH
        "
	  ::= { pm1001rrtableclientOtxtlh 7 }



pm1001rrCfgclientF0 OBJECT-TYPE
	  SYNTAX Unsigned32 (0..65536)
	  MAX-ACCESS read-write
	  STATUS current
	  DESCRIPTION
        "
        Default Line 1 OTX TLH lowest
         Freq :This register configures
        the start-up lowest frequency supported
        on the line 1 OTX TLH
        "
	  ::= { pm1001rrtableclientOtxtlh 8 }



pm1001rrCfgclientPhotodiodeMode OBJECT-TYPE
	  SYNTAX Unsigned32 (0..65536)
	  MAX-ACCESS read-write
	  STATUS current
	  DESCRIPTION
        "
        Default Line 1 OTX TLH APD mode
        :This register configures the start-up
        APD mode of the line 1 OTX TLH
        "
	  ::= { pm1001rrtableclientOtxtlh 10 }



pm1001rrCfgclientPhotodiodeValue OBJECT-TYPE
	  SYNTAX Unsigned32 (0..65536)
	  MAX-ACCESS read-write
	  STATUS current
	  DESCRIPTION
        "
        Default Line 1 OTX TLH APD atten.
        :This register configures the start-up
        APD attenuation on the line 1 OTX
        TLH
        "
	  ::= { pm1001rrtableclientOtxtlh 11 }



--- *****************************************************
---     LEAF for the table 2591
--- *****************************************************

pm1001rrtablelineOtxtlh OBJECT IDENTIFIER ::= { pm1001rrCfgStartUp 4 }



pm1001rrCfglineDitherControl OBJECT-TYPE
	  SYNTAX Unsigned32 (0..65536)
	  MAX-ACCESS read-write
	  STATUS current
	  DESCRIPTION
        "
        Default Settings on Dither Line
        2 :This  register configures the
        default initialisation settings
        on the dither of the client port.
        "
	  ::= { pm1001rrtablelineOtxtlh 2 }



pm1001rrCfglineDitherRate OBJECT-TYPE
	  SYNTAX Unsigned32 (0..65536)
	  MAX-ACCESS read-write
	  STATUS current
	  DESCRIPTION
        "
        Default Line 2 OTX TLH FM amplitude
        :This register configures the start-up
        width of the frequency modulation
        of the line 2 OTX TLH
        "
	  ::= { pm1001rrtablelineOtxtlh 3 }



pm1001rrCfglineDitherFhz OBJECT-TYPE
	  SYNTAX Unsigned32 (0..65536)
	  MAX-ACCESS read-write
	  STATUS current
	  DESCRIPTION
        "
        Default Line 2 OTX TLH FM frequency
        :This register configures the start-up
        frequency of the frequency modulation
        of the line 2 OTX TLH
        "
	  ::= { pm1001rrtablelineOtxtlh 4 }



pm1001rrCfglinePwrLaser OBJECT-TYPE
	  SYNTAX Unsigned32 (0..65536)
	  MAX-ACCESS read-write
	  STATUS current
	  DESCRIPTION
        "
        Defaut Line 2 OTX TLH output Power
        :This register configures the start-up
        output power of the line 2 OTX
         TLH (Unit = dBm)
        "
	  ::= { pm1001rrtablelineOtxtlh 5 }



pm1001rrCfglineFCurrent OBJECT-TYPE
	  SYNTAX Unsigned32 (0..65536)
	  MAX-ACCESS read-write
	  STATUS current
	  DESCRIPTION
        "
        Default Line 2 OTX TLH Channel
        :This register configures the start-up
        laser channel of the line 2 OTX
        TLH
        "
	  ::= { pm1001rrtablelineOtxtlh 6 }



pm1001rrCfglineGridCurrent OBJECT-TYPE
	  SYNTAX Unsigned32 (0..65536)
	  MAX-ACCESS read-write
	  STATUS current
	  DESCRIPTION
        "
        Default Line 2 OTX TLH Grid :This
        register configures the start-up
        laser grid of the line 2 OTX TLH
        "
	  ::= { pm1001rrtablelineOtxtlh 7 }



pm1001rrCfglineF0 OBJECT-TYPE
	  SYNTAX Unsigned32 (0..65536)
	  MAX-ACCESS read-write
	  STATUS current
	  DESCRIPTION
        "
        Default Line 2 OTX TLH lowest
         Freq :This register configures
        the start-up lowest frequency supported
        on the line 2 OTX TLH
        "
	  ::= { pm1001rrtablelineOtxtlh 8 }



pm1001rrCfglinePhotodiodeMode OBJECT-TYPE
	  SYNTAX Unsigned32 (0..65536)
	  MAX-ACCESS read-write
	  STATUS current
	  DESCRIPTION
        "
        Default Line 2 OTX TLH APD mode
        :This register configures the start-up
        APD mode of the line 2 OTX TLH
        "
	  ::= { pm1001rrtablelineOtxtlh 10 }



pm1001rrCfglinePhotodiodeValue OBJECT-TYPE
	  SYNTAX Unsigned32 (0..65536)
	  MAX-ACCESS read-write
	  STATUS current
	  DESCRIPTION
        "
        Default Line 2 OTX TLH APD atten.
        :This register configures the start-up
        APD attenuation on the line 2 OTX
        TLH
        "
	  ::= { pm1001rrtablelineOtxtlh 11 }



--- *****************************************************
---     LEAF for the table Group labels
--- *****************************************************

pm1001rrCfgLabels OBJECT IDENTIFIER ::= { pm1001rrConfig 3 }



--- *****************************************************
---     LEAF for the table NO_VALUE
--- *****************************************************

pm1001rrCfgLabelclientTable OBJECT-TYPE
	SYNTAX  SEQUENCE OF Pm1001rrCfgLabelclientEntry
	MAX-ACCESS not-accessible
	STATUS current
	DESCRIPTION
        "
        List of  Article
        "
	::= { pm1001rrCfgLabels 1 }


pm1001rrCfgLabelclientEntry OBJECT-TYPE
	SYNTAX Pm1001rrCfgLabelclientEntry
	MAX-ACCESS not-accessible
	STATUS current
	DESCRIPTION
        "
        Row definition for the labels
         table
        "
	INDEX   { pm1001rrCfgLabelclientIndex }
	::= { pm1001rrCfgLabelclientTable 1 }


Pm1001rrCfgLabelclientEntry ::=
	SEQUENCE {
	pm1001rrCfgLabelclientIndex
		INTEGER,
	pm1001rrCfgLabelclientPortn
		DisplayString
	}


pm1001rrCfgLabelclientIndex OBJECT-TYPE
	SYNTAX  INTEGER(0..128)
	MAX-ACCESS  read-only
	STATUS current
	DESCRIPTION
        "
        Index definition for the labelclient
        table
        "
	::= { pm1001rrCfgLabelclientEntry 1 }


pm1001rrCfgLabelclientPortn OBJECT-TYPE
	SYNTAX  DisplayString( SIZE(1..16))
	MAX-ACCESS read-write
	STATUS current
	DESCRIPTION
        "
        Default settings on the label
         of the Ports :These registers
         configures the default initialisation
        settings of the labels of the ports.
        "
	::= { pm1001rrCfgLabelclientEntry 3 }


--- *****************************************************
---     LEAF for the table NO_VALUE
--- *****************************************************

pm1001rrCfgLabellineTable OBJECT-TYPE
	SYNTAX  SEQUENCE OF Pm1001rrCfgLabellineEntry
	MAX-ACCESS not-accessible
	STATUS current
	DESCRIPTION
        "
        List of  Article
        "
	::= { pm1001rrCfgLabels 2 }


pm1001rrCfgLabellineEntry OBJECT-TYPE
	SYNTAX Pm1001rrCfgLabellineEntry
	MAX-ACCESS not-accessible
	STATUS current
	DESCRIPTION
        "
        Row definition for the labels
         table
        "
	INDEX   { pm1001rrCfgLabellineIndex }
	::= { pm1001rrCfgLabellineTable 1 }


Pm1001rrCfgLabellineEntry ::=
	SEQUENCE {
	pm1001rrCfgLabellineIndex
		INTEGER,
	pm1001rrCfgLabellinePortn
		DisplayString
	}


pm1001rrCfgLabellineIndex OBJECT-TYPE
	SYNTAX  INTEGER(0..128)
	MAX-ACCESS  read-only
	STATUS current
	DESCRIPTION
        "
        Index definition for the labelline
        table
        "
	::= { pm1001rrCfgLabellineEntry 1 }


pm1001rrCfgLabellinePortn OBJECT-TYPE
	SYNTAX  DisplayString( SIZE(1..16))
	MAX-ACCESS read-write
	STATUS current
	DESCRIPTION
        "
        Default settings on the label
         of the lines :These registers
         configures the default initialisation
        settings of the labels of the lines.
        "
	::= { pm1001rrCfgLabellineEntry 3 }


--- *****************************************************
---     LEAF for the table Group startuptablefive
--- *****************************************************

pm1001rrCfgStartuptablefive OBJECT IDENTIFIER ::= { pm1001rrConfig 4 }



--- *****************************************************
---     LEAF for the table 0005
--- *****************************************************

pm1001rrCfgOtxtlhcapabilitiesTable OBJECT-TYPE
	SYNTAX  SEQUENCE OF Pm1001rrCfgOtxtlhcapabilitiesEntry
	MAX-ACCESS not-accessible
	STATUS current
	DESCRIPTION
        "
        List of  Article
        "
	::= { pm1001rrCfgStartuptablefive 1 }


pm1001rrCfgOtxtlhcapabilitiesEntry OBJECT-TYPE
	SYNTAX Pm1001rrCfgOtxtlhcapabilitiesEntry
	MAX-ACCESS not-accessible
	STATUS current
	DESCRIPTION
        "
        Row definition for the startuptablefive
        table
        "
	INDEX   { pm1001rrCfgOtxtlhcapabilitiesIndex }
	::= { pm1001rrCfgOtxtlhcapabilitiesTable 1 }


Pm1001rrCfgOtxtlhcapabilitiesEntry ::=
	SEQUENCE {
	pm1001rrCfgOtxtlhcapabilitiesIndex
		INTEGER,
	pm1001rrCfgComponentTypePortn
		Unsigned32,
	pm1001rrCfgMiscellaneousPortn
		Unsigned32,
	pm1001rrCfgFirstChannelPortn
		Unsigned32,
	pm1001rrCfgLastChannelPortn
		Unsigned32,
	pm1001rrCfgGridPortn
		Unsigned32
	}


pm1001rrCfgOtxtlhcapabilitiesIndex OBJECT-TYPE
	SYNTAX  INTEGER(0..128)
	MAX-ACCESS  read-only
	STATUS current
	DESCRIPTION
        "
        Index definition for the otxtlhcapabilities
        table
        "
	::= { pm1001rrCfgOtxtlhcapabilitiesEntry 1 }


pm1001rrCfgComponentTypePortn OBJECT-TYPE
	SYNTAX  Unsigned32 (0..65536)
	MAX-ACCESS read-only
	STATUS current
	DESCRIPTION
        "
        Component parameters :This OID
        defines the component parameters
        "
	::= { pm1001rrCfgOtxtlhcapabilitiesEntry 3 }


pm1001rrCfgMiscellaneousPortn OBJECT-TYPE
	SYNTAX  Unsigned32 (0..65536)
	MAX-ACCESS read-only
	STATUS current
	DESCRIPTION
        "
        Miscellaneous default settings
        :This OID defines the miscellaneous
        parameters
        "
	::= { pm1001rrCfgOtxtlhcapabilitiesEntry 4 }


pm1001rrCfgFirstChannelPortn OBJECT-TYPE
	SYNTAX  Unsigned32 (0..65536)
	MAX-ACCESS read-only
	STATUS current
	DESCRIPTION
        "
        Number of the first channel of
        the component :This OID defines
        the first channel number of the
        PM
        "
	::= { pm1001rrCfgOtxtlhcapabilitiesEntry 5 }


pm1001rrCfgLastChannelPortn OBJECT-TYPE
	SYNTAX  Unsigned32 (0..65536)
	MAX-ACCESS read-only
	STATUS current
	DESCRIPTION
        "
        Number of the last channel of
         the component :This OID defines
        the last channel number of the
         PM
        "
	::= { pm1001rrCfgOtxtlhcapabilitiesEntry 6 }


pm1001rrCfgGridPortn OBJECT-TYPE
	SYNTAX  Unsigned32 (0..65536)
	MAX-ACCESS read-only
	STATUS current
	DESCRIPTION
        "
        Grid value of the component :This
        OID defines the grid of the PM
        "
	::= { pm1001rrCfgOtxtlhcapabilitiesEntry 7 }



pm1001rrCfgWriteConfiguration  OBJECT-TYPE
	SYNTAX EkiOnOff
	MAX-ACCESS read-write
	STATUS current
	DESCRIPTION
	"Write configuration to module:This OID
	 writes the complete configuration to the module"
	::= { pm1001rrConfig 257 }






--- *****************************************************
---     TRAP OBJECTS
--- *****************************************************

pm1001rrtrapBoardNumber OBJECT-TYPE
	SYNTAX INTEGER(1..64)
	MAX-ACCESS read-only
	STATUS current
	DESCRIPTION
	"Last module which generates a trap"
	::= { pm1001rrtraps 4 }







--- *****************************************************
---     GLOBAL TRAPS
--- *****************************************************

pm1001rrLineTrapNotUrgentGoesOn NOTIFICATION-TYPE
	OBJECTS {pm1001rrAlmLineDdmWarning, pm1001rrtrapBoardNumber}
	STATUS current
	--&FILTNAME    "PM1001RR Line Not Urgent ON"
	--&ACTIONS     { log, minor }
	--&MATCH       { pm1001rrAlmLineDdmWarning "on", pm1001rrtrapBoardNumber "$2"}
	--&MESG        "DDM Warning appears on Line Port of PM1001RR in Slot $2 ($A)"
	DESCRIPTION "Not urgent Line default is activated"
	::= { pm1001rrtraps 30 }

pm1001rrLineTrapNotUrgentGoesOff NOTIFICATION-TYPE
	OBJECTS {pm1001rrAlmLineDdmWarning, pm1001rrtrapBoardNumber}
	STATUS current
	--&FILTNAME    "PM1001RR Line Not Urgent OFF"
	--&ACTIONS     { log, normal }
	--&CLEARS      { "PM1001RR Line Not Urgent ON" }
	--&MATCH       { pm1001rrAlmLineDdmWarning "on", pm1001rrtrapBoardNumber "$2"}
	--&MESG        "DDM Warning disappears on Line Port of PM1001RR in Slot $2 ($A)"
	DESCRIPTION "Not urgent Line default disappeared"
	::= { pm1001rrtraps 31 }

pm1001rrLineTrapUrgentGoesOn NOTIFICATION-TYPE
	OBJECTS {pm1001rrAlmLineDdmAlm, pm1001rrtrapBoardNumber}
	STATUS current
	--&FILTNAME    "PM1001RR Line Urgent ON"
	--&ACTIONS     { log, major }
	--&MATCH       { pm1001rrAlmLineDdmAlm "on", pm1001rrtrapBoardNumber "$2"}
	--&MESG        "DDM Alarm appears on Line Port of PM1001RR in Slot $2 ($A)"
	DESCRIPTION "Urgent Line default is activated"
	::= { pm1001rrtraps 32 }

pm1001rrLineTrapUrgentGoesOff NOTIFICATION-TYPE
	OBJECTS {pm1001rrAlmLineDdmAlm, pm1001rrtrapBoardNumber}
	STATUS current
	--&FILTNAME    "PM1001RR Line Urgent OFF"
	--&ACTIONS     { log, normal }
	--&CLEARS      { "PM1001RR Line Urgent ON" }
	--&MATCH       { pm1001rrAlmLineDdmAlm "on", pm1001rrtrapBoardNumber "$2"}
	--&MESG        "DDM Alarm disappears on Line Port of PM1001RR in Slot $2 ($A)"
	DESCRIPTION "Urgent Line default disappeared"
	::= { pm1001rrtraps 33 }

pm1001rrLineTrapCritGoesOn NOTIFICATION-TYPE
	OBJECTS {pm1001rrAlmLineFail, pm1001rrAlmLineHwFail, pm1001rrtrapBoardNumber}
	STATUS current
	--&FILTNAME    "PM1001RR Line Fail ON"
	--&ACTIONS     { log, critical }
	--&MATCH       { pm1001rrAlmLineFail "on", pm1001rrAlmLineHwFail "*", pm1001rrtrapBoardNumber "$3"}
	--&MESG        "Line Port Down on PM1001RR in Slot $3 ($A)"

	--&FILTNAME    "PM1001RR Line HW Fail ON (Hidden)"
	--&ACTIONS     { info }
	--&MATCH       { pm1001rrAlmLineFail "*", pm1001rrAlmLineHwFail "on", pm1001rrtrapBoardNumber "$3"}
	--&MESG        "Line Port Down on PM1001RR in Slot $3 ($A)"
	DESCRIPTION "Critical Line default is activated"
	::= { pm1001rrtraps 34 }

pm1001rrLineTrapCritGoesOff NOTIFICATION-TYPE
	OBJECTS {pm1001rrAlmLineFail, pm1001rrAlmLineHwFail, pm1001rrtrapBoardNumber}
	STATUS current
	--&FILTNAME    "PM1001RR Line Fail OFF"
	--&ACTIONS     { log,  normal }
	--&CLEARS      { "PM1001RR Line Fail ON" }
	--&MATCH       { pm1001rrAlmLineFail "on", pm1001rrAlmLineHwFail "*", pm1001rrtrapBoardNumber "$3"}
	--&MESG        "Line Port Up on PM1001RR in Slot $3 ($A)"

	--&FILTNAME    "PM1001RR Line HW Fail OFF (Hidden)"
	--&ACTIONS     { info }
	--&MATCH       { pm1001rrAlmLineFail "*", pm1001rrAlmLineHwFail "on", pm1001rrtrapBoardNumber "$3"}
	--&MESG        "Line Port Up on PM1001RR in Slot $3 ($A)"
	DESCRIPTION "Critical Line default disappeared"
	::= { pm1001rrtraps 35 }






--- *****************************************************
---     PORTS TRAPS
--- *****************************************************

pm1001rrClientTrapNotUrgentGoesOn NOTIFICATION-TYPE
	OBJECTS {pm1001rrAlmClientDdmWarning, pm1001rrtrapBoardNumber}
	STATUS current
	--&FILTNAME    "PM1001RR Client Not Urgent ON"
	--&ACTIONS     { log, minor }
	--&MATCH       { pm1001rrAlmClientDdmWarning "on", pm1001rrtrapBoardNumber "$2"}
	--&MESG        "DDM Warning appears on Client Port of PM1001RR in Slot $2 ($A)"
	DESCRIPTION "Not urgent client default is activated"
	::= { pm1001rrtraps 40 }

pm1001rrClientTrapNotUrgentGoesOff NOTIFICATION-TYPE
	OBJECTS {pm1001rrAlmClientDdmWarning, pm1001rrtrapBoardNumber}
	STATUS current
	--&FILTNAME    "PM1001RR Client Not Urgent OFF"
	--&ACTIONS     { log, normal }
	--&CLEARS      { "PM1001RR Client Not Urgent ON" }
	--&MATCH       { pm1001rrAlmClientDdmWarning "on", pm1001rrtrapBoardNumber "$2"}
	--&MESG        "DDM Warning appears on Client Port of PM1001RR in Slot $2 ($A)"
	DESCRIPTION "Not urgent client default disappeared"
	::= { pm1001rrtraps 41 }

pm1001rrClientTrapUrgentGoesOn NOTIFICATION-TYPE
	OBJECTS {pm1001rrAlmClientDdmAlm, pm1001rrtrapBoardNumber}
	STATUS current
	--&FILTNAME    "PM1001RR Client Urgent ON"
	--&ACTIONS     { log, major }
	--&MATCH       { pm1001rrAlmClientDdmAlm "on", pm1001rrtrapBoardNumber "$2"}
	--&MESG        "DDM Alarm appears on Client Port of PM1001RR in Slot $2 ($A)"
	DESCRIPTION "Urgent client default is activated"
	::= { pm1001rrtraps 42 }

pm1001rrClientTrapUrgentGoesOff NOTIFICATION-TYPE
	OBJECTS {pm1001rrAlmClientDdmAlm, pm1001rrtrapBoardNumber}
	STATUS current
	--&FILTNAME    "PM1001RR Client Urgent OFF"
	--&ACTIONS     { log, normal }
	--&CLEARS      { "PM1001RR Client Urgent ON" }
	--&MATCH       { pm1001rrAlmClientDdmAlm "on", pm1001rrtrapBoardNumber "$2"}
	--&MESG        "DDM Alarm disappears on Client Port of PM1001RR in Slot $2 ($A)"
	DESCRIPTION "Urgent client default disappeared"
	::= { pm1001rrtraps 43 }

pm1001rrClientTrapCritGoesOn NOTIFICATION-TYPE
	OBJECTS {pm1001rrAlmClientFail, pm1001rrAlmClientHwFail, pm1001rrtrapBoardNumber}
	STATUS current
	--&FILTNAME    "PM1001RR Client Fail ON"
	--&ACTIONS     { log, critical }
	--&MATCH       { pm1001rrAlmClientFail "on", pm1001rrAlmClientHwFail "*", pm1001rrtrapBoardNumber "$3"}
	--&MESG        "Client Port Down on PM1001RR in Slot $3 ($A)"

	--&FILTNAME    "PM1001RR Client HW Fail ON (Hidden)"
	--&ACTIONS     { info }
	--&MATCH       { pm1001rrAlmClientFail "*", pm1001rrAlmClientHwFail "on", pm1001rrtrapBoardNumber "$3"}
	--&MESG        "Client Port Down on PM1001RR in Slot $3 ($A)"
	DESCRIPTION "Critical client default is activated"
	::= { pm1001rrtraps 44 }

pm1001rrClientTrapCritGoesOff NOTIFICATION-TYPE
	OBJECTS {pm1001rrAlmClientFail, pm1001rrAlmClientHwFail, pm1001rrtrapBoardNumber}
	STATUS current
	--&FILTNAME    "PM1001RR Client Fail OFF"
	--&ACTIONS     { log, normal }
	--&CLEARS      { "PM1001RR Client Fail ON" }
	--&MATCH       { pm1001rrAlmClientFail "on", pm1001rrAlmClientHwFail "*", pm1001rrtrapBoardNumber "$3"}
	--&MESG        "Client Port Up on PM1001RR in Slot $3 ($A)"

	--&FILTNAME    "PM1001RR Client HW Fail OFF (Hidden)"
	--&ACTIONS     { info }
	--&MATCH       { pm1001rrAlmClientFail "*", pm1001rrAlmClientHwFail "on", pm1001rrtrapBoardNumber "$3"}
	--&MESG        "Client Port Up on PM1001RR in Slot $3 ($A)"
	DESCRIPTION "Critical client default disappeared"
	::= { pm1001rrtraps 45 }






--- *****************************************************
---     HW TRAPS
--- *****************************************************

pm1001rrPowerTrapUrgentGoesOn NOTIFICATION-TYPE
	OBJECTS {pm1001rrAlmDefFuseB, pm1001rrAlmDefFuseA , pm1001rrtrapBoardNumber}
	STATUS current
	--&FILTNAME    "PM1001RR Fuse A Fail ON"
	--&ACTIONS     { log, major }
	--&MATCH       { pm1001rrAlmDefFuseB "*", pm1001rrAlmDefFuseA "on", pm1001rrtrapBoardNumber "$3"}
	--&MESG        "Power Input A Fail on PM1001RR in Slot $3 ($A)"

	--&FILTNAME    "PM1001RR Fuse B Fail ON"
	--&ACTIONS     { log, major }
	--&MATCH       { pm1001rrAlmDefFuseB "on", pm1001rrAlmDefFuseA "*", pm1001rrtrapBoardNumber "$3"}
	--&MESG        "Power Input B Fail on PM1001RR in Slot $3 ($A)"
	DESCRIPTION "Urgent power supply default is activated"
	::= { pm1001rrtraps 50 }
pm1001rrPowerTrapUrgentGoesOff NOTIFICATION-TYPE
	OBJECTS {pm1001rrAlmDefFuseB, pm1001rrAlmDefFuseA , pm1001rrtrapBoardNumber}
	STATUS current
	--&FILTNAME    "PM1001RR Fuse A&B Fail OFF"
	--&ACTIONS     { log, normal}
	--&CLEARS      { "PM1001RR Fuse A Fail ON", "PM1001RR Fuse B Fail ON" }
	--&MATCH       { pm1001rrAlmDefFuseB "on", pm1001rrAlmDefFuseA "on", pm1001rrtrapBoardNumber "$3"}
	--&MESG        "Power Inputs A and B Present on PM1001RR in Slot $3 ($A)"
	DESCRIPTION "Urgent power supply default disappeared"
	::= { pm1001rrtraps 51 }






END
