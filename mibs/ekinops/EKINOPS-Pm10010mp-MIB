-- *****************************************************************
-- EKINOPS-Pm10010mp.TXT:  MIB
--
--MIB Part Number:3MI00030AABC
--MIB Version:02
--
-- Copyright (c) 2016 by Ekinops
-- All rights reserved.
--
-- *****************************************************************

EKINOPS-Pm10010mp-MIB DEFINITIONS ::= BEGIN

IMPORTS
	ekinops,
	EkiState,
	EkiOnOff,
	EkiMode,
	EkiProtocol,
	EkiApiState,
	EkiSynchroMode,
	EkiMeasureType
			FROM EKINOPS-MIB
        MODULE-IDENTITY,
        OBJECT-TYPE,
        NOTIFICATION-TYPE,
	Unsigned32,
	Integer32,
	Counter32,
	IpAddress
        		FROM SNMPv2-SMI
 	TEXTUAL-CONVENTION,
	DisplayString
                FROM SNMPv2-TC;

modulePm10010mp MODULE-IDENTITY
        LAST-UPDATED "201606020000Z"
        ORGANIZATION "Ekinops"
        CONTACT-INFO
         "Ekinops

          3, rue Blaise Pascal
          F-22300 Lannion / FRANCE

          Tel : +33 (0)2 96 05 00 30
          Fax : +33 (0)2 96 48 62 39

          E-mail: support@ekinops.fr"
        DESCRIPTION
          "Creation."

	REVISION "201309260000Z"
	DESCRIPTION
	  "Creation for PM 100G MP"
	REVISION "201401160000Z"
	DESCRIPTION
	  "Add ProbCause on CSF detected"
	REVISION "201404010000Z"
	DESCRIPTION
	  "Probcause,AlarmType - NMS completion"
	REVISION "201410140000Z"
	DESCRIPTION
	  "OSNR help completion"
	REVISION "201501220000Z"
	DESCRIPTION
	  "Labels cosmetic updates"
	REVISION "201504230000Z"
	DESCRIPTION
	  "Tunability on Client"
	REVISION "201510210000Z"
	DESCRIPTION
	  "Add F0 objet"
	REVISION "201605200000Z"
	DESCRIPTION
	  "New AlarmType – synthesisAlarm (12)"
	REVISION "201606020000Z"
	DESCRIPTION
	  "Capabilities objects of Table 5"
        ::= { ekinops 58 }



--- *****************************************************
---     LEAF LEVEL 2
--- *****************************************************


pm10010mpalarms OBJECT IDENTIFIER ::= { modulePm10010mp 2 }
pm10010mpAlmOther OBJECT IDENTIFIER ::= { pm10010mpalarms 1 }
pm10010mpAlmOtherNurg OBJECT IDENTIFIER ::= { pm10010mpAlmOther 1 }
pm10010mpAlmOtherUrg OBJECT IDENTIFIER ::= { pm10010mpAlmOther 2 }
pm10010mpAlmOtherCrit OBJECT IDENTIFIER ::= { pm10010mpAlmOther 3 }

pm10010mpAlmClient OBJECT IDENTIFIER ::= { pm10010mpalarms 2 }
pm10010mpAlmClientNurg OBJECT IDENTIFIER ::= { pm10010mpAlmClient 1 }
pm10010mpAlmClientUrg OBJECT IDENTIFIER ::= { pm10010mpAlmClient 2 }
pm10010mpAlmClientCrit OBJECT IDENTIFIER ::= { pm10010mpAlmClient 3 }

pm10010mpAlmLine OBJECT IDENTIFIER ::= { pm10010mpalarms 3 }
pm10010mpAlmLineNurg OBJECT IDENTIFIER ::= { pm10010mpAlmLine 1 }
pm10010mpAlmLineUrg OBJECT IDENTIFIER ::= { pm10010mpAlmLine 2 }
pm10010mpAlmLineCrit OBJECT IDENTIFIER ::= { pm10010mpAlmLine 3 }





pm10010mpmeasures OBJECT IDENTIFIER ::= { modulePm10010mp 3 }
pm10010mpMesrOther OBJECT IDENTIFIER ::= { pm10010mpmeasures 1 }
pm10010mpMesrClient OBJECT IDENTIFIER ::= { pm10010mpmeasures 2 }
pm10010mpMesrLine OBJECT IDENTIFIER ::= { pm10010mpmeasures 3 }




pm10010mpcounters OBJECT IDENTIFIER ::= { modulePm10010mp 4 }
pm10010mpCntOther OBJECT IDENTIFIER ::= { pm10010mpcounters 1 }
pm10010mpCntClient OBJECT IDENTIFIER ::= { pm10010mpcounters 2 }
pm10010mpCntLine OBJECT IDENTIFIER ::= { pm10010mpcounters 3 }


pm10010mpcontrolsWrite OBJECT IDENTIFIER ::= { modulePm10010mp 6 }
pm10010mpCtrlOther OBJECT IDENTIFIER ::= { pm10010mpcontrolsWrite 1 }
pm10010mpCtrlClient OBJECT IDENTIFIER ::= { pm10010mpcontrolsWrite 2 }
pm10010mpCtrlLine OBJECT IDENTIFIER ::= { pm10010mpcontrolsWrite 3 }

pm10010mpri OBJECT IDENTIFIER ::= { modulePm10010mp 7 }
pm10010mpriTable OBJECT IDENTIFIER ::= { pm10010mpri 1 }

pm10010mpdownload OBJECT IDENTIFIER ::= { modulePm10010mp 8 }
pm10010mpDwlOther OBJECT IDENTIFIER ::= { pm10010mpdownload 1 }
pm10010mpDwlClient OBJECT IDENTIFIER ::= { pm10010mpdownload 2 }
pm10010mpDwlLine OBJECT IDENTIFIER ::= { pm10010mpdownload 3 }


pm10010mpConfig OBJECT IDENTIFIER ::= { modulePm10010mp 9 }

pm10010mptraps OBJECT IDENTIFIER ::= { modulePm10010mp 10 }



pm10010mpMonitoring OBJECT IDENTIFIER ::= { modulePm10010mp 11}

pm10010mpMonOther OBJECT IDENTIFIER ::= { pm10010mpMonitoring 1 }
pm10010mpMonRmon OBJECT IDENTIFIER ::= { pm10010mpMonOther 3 }

pm10010mpMonClient OBJECT IDENTIFIER ::= { pm10010mpMonitoring 2 }
pm10010mpMonClientRmonCounter OBJECT IDENTIFIER ::= { pm10010mpMonClient 4 }


--- *****************************************************
--- $$$$$$$$$$$$$$$$$$$$$$$$$$$$$$$$$$$$$$$$$$$$$$$$$$$$$
---     TEXTUAL-CONVENTION
--- $$$$$$$$$$$$$$$$$$$$$$$$$$$$$$$$$$$$$$$$$$$$$$$$$$$$$
--- *****************************************************

Pm10010mpMultiRate ::= TEXTUAL-CONVENTION
    STATUS      current
    DESCRIPTION "different rate for a client port"
    SYNTAX INTEGER {
		rate100Mhz(0),
		rate250Mhz(1),
		rate500Mhz(2),
		rate1Ghz(3)
           }

Pm10010mpOtxMode ::= TEXTUAL-CONVENTION
    STATUS      current
    DESCRIPTION "Different modes on OTX-TLH on client and line ports"
    SYNTAX INTEGER {
		otx80mode(1),
		otx60mode(2),
		otxadjustmode(4)
           }

Pm10010mpOtxGrid ::= TEXTUAL-CONVENTION
    STATUS      current
    DESCRIPTION "Different grids on OTX-TLH on client and line ports"
    SYNTAX INTEGER {
		otxgrid200(200),
		otxgrid100(100),
		otxgrid50(50)
           }

Pm10010mpAdjustValue ::= TEXTUAL-CONVENTION
    STATUS      current
    DESCRIPTION "Different values in Adjust mode on OTX-TLH on client and line ports"
    SYNTAX INTEGER {
		otxadjustvalue0(0),
		otxadjustvalue1(1),
		otxadjustvalue2(2),
		otxadjustvalue3(3),
		otxadjustvalue4(4),
		otxadjustvalue5(5),
		otxadjustvalue6(6),
		otxadjustvalue7(7),
		otxadjustvalue8(8),
		otxadjustvalue9(9),
		otxadjustvalue10(10)
           }

Pm10010mpClientProtocol ::= TEXTUAL-CONVENTION
    STATUS      current
    DESCRIPTION "Different values on the protocol on the client ports"
    SYNTAX INTEGER {
		protocolclientvalue0(0),
		protocolclientvalue1(1),
		protocolclientvalue2(2),
		protocolclientvalue3(3),
		protocolclientvalue4(4),
		protocolclientvalue5(5),
		protocolclientvalue6(6),
		protocolclientvalue7(7),
		protocolclientvalue8(8)
           }

Pm10010mpProtocolMode ::= TEXTUAL-CONVENTION
    STATUS      current
    DESCRIPTION "Different values on the protocol mode"
    SYNTAX INTEGER {
		protocolmodevalue0(0),
		protocolmodevalue1(1),
		protocolmodevalue2(2),
		protocolmodevalue3(3)
           }

Pm10010mpOtxChannel ::= TEXTUAL-CONVENTION
    STATUS      current
    DESCRIPTION "Channel selection on transceiver Tx line ports"
    SYNTAX INTEGER

Pm10010mpOrxChannel ::= TEXTUAL-CONVENTION
    STATUS      current
    DESCRIPTION "Channel selection on transceiver Rx line ports"
    SYNTAX INTEGER

--- *****************************************************
--- $$$$$$$$$$$$$$$$$$$$$$$$$$$$$$$$$$$$$$$$$$$$$$$$$$$$$
---     REMOTE INVENTORY
--- $$$$$$$$$$$$$$$$$$$$$$$$$$$$$$$$$$$$$$$$$$$$$$$$$$$$$
--- *****************************************************

pm10010mpRinvReloadInventory OBJECT-TYPE
  SYNTAX EkiOnOff
  MAX-ACCESS read-write
  STATUS current
  DESCRIPTION
        "Reload the inventory: This OID triggers an
         inventory reload."
  ::= { pm10010mpri 2 }

pm10010mpRinvHwPlatform OBJECT-TYPE
  SYNTAX DisplayString
  MAX-ACCESS read-only
  STATUS current
  DESCRIPTION
        "HW platform description: This OID contains the
         description of the Hardware platform."
  ::= { pm10010mpri 3 }

pm10010mpRinvModulePlatform OBJECT-TYPE
  SYNTAX DisplayString
  MAX-ACCESS read-only
  STATUS current
  DESCRIPTION
        "Module platform description: This OID contains the
         description of the Module."
  ::= { pm10010mpri 4 }

pm10010mpRinvSwPlatform OBJECT-TYPE
  SYNTAX DisplayString
  MAX-ACCESS read-only
  STATUS current
  DESCRIPTION
        "SW platform description: This OID contains the
         description of the Software platform."
  ::= { pm10010mpri 5 }

pm10010mpRinvGwPlatform OBJECT-TYPE
  SYNTAX DisplayString
  MAX-ACCESS read-only
  STATUS current
  DESCRIPTION
        "GW platform desciption: This OID contains the
         description of the Gateware platform."
  ::= { pm10010mpri 6 }


pm10010mpRinvSfpTable OBJECT-TYPE
      SYNTAX  SEQUENCE OF Pm10010mpRinvSfpEntry
      MAX-ACCESS  not-accessible
      STATUS  current
      DESCRIPTION
              "List of the SFPs on the selected module"
      ::= { pm10010mpriTable 1 }

pm10010mpRinvSfpEntry OBJECT-TYPE
        SYNTAX  Pm10010mpRinvSfpEntry
        MAX-ACCESS  not-accessible
        STATUS  current
        DESCRIPTION
              "Row definition for the SFP table"
        INDEX   { pm10010mpRinvSfpIndex }
        ::= { pm10010mpRinvSfpTable 1 }



Pm10010mpRinvSfpEntry::=
        SEQUENCE {
          pm10010mpRinvSfpIndex
              Integer32,
          pm10010mpRinvsfp
              DisplayString
        }


    pm10010mpRinvSfpIndex OBJECT-TYPE
        SYNTAX  Integer32(1..16)
        MAX-ACCESS  read-only
        STATUS  current
        DESCRIPTION
              "Index for SFP table"
        ::= { pm10010mpRinvSfpEntry 1 }


    pm10010mpRinvsfp OBJECT-TYPE
        SYNTAX  DisplayString
        MAX-ACCESS  read-only
        STATUS  current
        DESCRIPTION
              "Inventory for the SFP: This OID contains the inventory for the SFP"
        ::= { pm10010mpRinvSfpEntry 2 }




pm10010mpRinvLineTable OBJECT-TYPE
      SYNTAX  SEQUENCE OF Pm10010mpRinvLineEntry
      MAX-ACCESS  not-accessible
      STATUS  current
      DESCRIPTION
              "List of the XFPs on the selected module"
      ::= { pm10010mpriTable 2 }

pm10010mpRinvLineEntry OBJECT-TYPE
        SYNTAX  Pm10010mpRinvLineEntry
        MAX-ACCESS  not-accessible
        STATUS  current
        DESCRIPTION
              "Row definition for the XFP table"
        INDEX   { pm10010mpRinvLineIndex }
        ::= { pm10010mpRinvLineTable 1 }



Pm10010mpRinvLineEntry::=
        SEQUENCE {
          pm10010mpRinvLineIndex
              Integer32,
          pm10010mpRinvxfpLine
              DisplayString
        }


    pm10010mpRinvLineIndex OBJECT-TYPE
        SYNTAX  Integer32(1..16)
        MAX-ACCESS  read-only
        STATUS  current
        DESCRIPTION
              "Index for XFP table"
        ::= { pm10010mpRinvLineEntry 1 }


    pm10010mpRinvxfpLine OBJECT-TYPE
        SYNTAX  DisplayString
        MAX-ACCESS  read-only
        STATUS  current
        DESCRIPTION
              "Inventory for the XFP: This OID contains the inventory for the XFP"
        ::= { pm10010mpRinvLineEntry 2 }









--- *****************************************************
--- $$$$$$$$$$$$$$$$$$$$$$$$$$$$$$$$$$$$$$$$$$$$$$$$$$$$$
---     ALARMS
--- $$$$$$$$$$$$$$$$$$$$$$$$$$$$$$$$$$$$$$$$$$$$$$$$$$$$$
--- *****************************************************



--- *****************************************************
---     LEAF for the synthAlm0 article
--- *****************************************************
pm10010mpAlmsynthAlm0 OBJECT IDENTIFIER ::= { pm10010mpAlmOtherCrit 0 }




pm10010mpAlmDefFuseB OBJECT-TYPE
	  SYNTAX EkiOnOff
	  MAX-ACCESS read-only
	  STATUS current
	  DESCRIPTION
        "
        Fuse B Fail :This OID indicates
        that the fuse of the power input
        B is in fail condition <Help> Status
        of the Fuse B <Condtype> DEF_FUSE_B
        <Probcause> powerProblem (36) <Alarmtype>
        equipmentAlarm (5) <Polarity> (2)
        "
	  ::= { pm10010mpAlmsynthAlm0 16 }



pm10010mpAlmDefFuseA OBJECT-TYPE
	  SYNTAX EkiOnOff
	  MAX-ACCESS read-only
	  STATUS current
	  DESCRIPTION
        "
        Fuse A Fail :This OID indicates
        that the fuse of the power input
        A is in fail condition <Help> Status
        of the Fuse A <Condtype> DEF_FUSE_A
        <Probcause> powerProblem (36) <Alarmtype>
        equipmentAlarm (5) <Polarity> (2)
        "
	  ::= { pm10010mpAlmsynthAlm0 15 }



pm10010mpAlmModGlobFail OBJECT-TYPE
	  SYNTAX EkiOnOff
	  MAX-ACCESS read-only
	  STATUS current
	  DESCRIPTION
        "
        Module Failure :This OID is set
        on detection of a failure originating
        from the RM <Help> This alarm is
        set on detection of a failure originating
        from the equipment <Condtype> MOD_GLOB_FAIL
        <Probcause> other (1) <Alarmtype>
        synthesisAlarm (12) ) <Polarity>
        (2)
        "
	  ::= { pm10010mpAlmsynthAlm0 9 }



pm10010mpAlmFailFan OBJECT-TYPE
	  SYNTAX EkiOnOff
	  MAX-ACCESS read-only
	  STATUS current
	  DESCRIPTION
        "
        Fan Fail :This OID is at 1 when
        any fail occurs on the fan tray
        <Help> This alarm indicates that
        the Fan tray module is in a failure
        condition <Condtype> FAIL_FAN <Probcause>
        equipmentMalfunction (16) <Alarmtype>
        equipmentAlarm (5) <Polarity> (2)
        "
	  ::= { pm10010mpAlmsynthAlm0 2 }



--- *****************************************************
---     LEAF for the synthAlm2 article
--- *****************************************************
pm10010mpAlmsynthAlm2 OBJECT IDENTIFIER ::= { pm10010mpAlmOtherNurg 2 }




pm10010mpAlmMaintenanceOn OBJECT-TYPE
	  SYNTAX EkiOnOff
	  MAX-ACCESS read-only
	  STATUS current
	  DESCRIPTION
        "
        Maintenance Mode :This OID indicates
        that the RM is in maintenance mode.
        <Help> This alarm indicates that
        the maintenance mode is enabled
        on the PM <Condtype> MAINTENANCE_ON
        <Probcause> informationalStatus(1000)
        <Alarmtype> other (1) <Polarity>
        (2)
        "
	  ::= { pm10010mpAlmsynthAlm2 5 }



pm10010mpAlmCorrelatOff OBJECT-TYPE
	  SYNTAX EkiOnOff
	  MAX-ACCESS read-only
	  STATUS current
	  DESCRIPTION
        "
        Not Used :This OID, when set,
         indicates that alarm correlation
        is not being performed. <Condtype>
        CORRELAT_OFF <Probcause> informationalStatus(1000)
        <Alarmtype> other (1) <Polarity>
        (2)
        "
	  ::= { pm10010mpAlmsynthAlm2 4 }



pm10010mpAlmConfTableLoad OBJECT-TYPE
	  SYNTAX EkiOnOff
	  MAX-ACCESS read-only
	  STATUS current
	  DESCRIPTION
        "
        PM Configuration Load :This OID
         is at 1 during the loading of
         configuration tables in the modules
        RAM. <Condtype> CONF_TABLE_LOAD
        <Probcause> informationalStatus(1000)
        <Alarmtype> other (1) <Polarity>
        (2)
        "
	  ::= { pm10010mpAlmsynthAlm2 3 }



pm10010mpAlmInvUpload OBJECT-TYPE
	  SYNTAX EkiOnOff
	  MAX-ACCESS read-only
	  STATUS current
	  DESCRIPTION
        "
        Inventory Upload :This OID is
         at 1 during the uploading of PM
        inventory information. <Condtype>
        INV_UPLOAD <Probcause> informationalStatus(1000)
        <Alarmtype> other (1) <Polarity>
        (2)
        "
	  ::= { pm10010mpAlmsynthAlm2 2 }



pm10010mpAlmConfTableSave OBJECT-TYPE
	  SYNTAX EkiOnOff
	  MAX-ACCESS read-only
	  STATUS current
	  DESCRIPTION
        "
        PM Configuration Save :This OID
        is at 1 during the saving of a
         new configuration table in the
        module Flash memory. <Condtype>
        CONF_TABLE_SAVE <Probcause> informationalStatus(1000)
        <Alarmtype> other (1) <Polarity>
        (2)
        "
	  ::= { pm10010mpAlmsynthAlm2 1 }



--- *********************************************************
---     TABLE for the pm10010mpAlmsynthAlmPort articles
--- *********************************************************

pm10010mpAlmsynthAlmPortTable OBJECT-TYPE
	SYNTAX  SEQUENCE OF Pm10010mpAlmsynthAlmPortEntry
	MAX-ACCESS not-accessible
	STATUS current
	DESCRIPTION
        "
        List of pm10010mpAlmsynthAlmPort
        Article
        "
	::= { pm10010mpAlmClientCrit 8 }


pm10010mpAlmsynthAlmPortEntry OBJECT-TYPE
	SYNTAX Pm10010mpAlmsynthAlmPortEntry
	MAX-ACCESS not-accessible
	STATUS current
	DESCRIPTION
        "
        Row definition for the pm10010mpAlmsynthAlmPort
        table
        "
	INDEX   { pm10010mpAlmsynthAlmPortIndex }
	::= { pm10010mpAlmsynthAlmPortTable 1 }


Pm10010mpAlmsynthAlmPortEntry ::=
	SEQUENCE {
	pm10010mpAlmsynthAlmPortIndex
		INTEGER,
	pm10010mpAlmUpCsfPortn
		EkiOnOff,
	pm10010mpAlmFailAccPortn
		EkiOnOff,
	pm10010mpAlmSfpDdmAlmPortn
		EkiOnOff,
	pm10010mpAlmSfpDdmWarningPortn
		EkiOnOff,
	pm10010mpAlmDwCaisPortn
		EkiOnOff,
	pm10010mpAlmClientRemoteOosPortn
		EkiOnOff,
	pm10010mpAlmClientLocalOosPortn
		EkiOnOff,
	pm10010mpAlmDwLsdPortn
		EkiOnOff,
	pm10010mpAlmHwFailAccPortn
		EkiOnOff,
	pm10010mpAlmDdmAbsentPortn
		EkiOnOff,
	pm10010mpAlmSfpAbsentPortn
		EkiOnOff
	}


pm10010mpAlmsynthAlmPortIndex OBJECT-TYPE
	SYNTAX  INTEGER(0..128)
	MAX-ACCESS  read-only
	STATUS current
	DESCRIPTION
        "
        Index definition for the pm10010mpAlmsynthAlmPort
        table
        "
	::= { pm10010mpAlmsynthAlmPortEntry 1 }


pm10010mpAlmUpCsfPortn OBJECT-TYPE
	SYNTAX  EkiOnOff
	MAX-ACCESS read-only
	STATUS current
	DESCRIPTION
        "
        Client Signal Fail Inserted :This
        OID indicates a CSF has been inserted
        in the upstream client port. <Help>
        This status indicates if a Client
        Signal Fail is currently inserted
        on the line signal for this client
        port <Condtype> UP_CSF_1 <Probcause>
        informationalStatus(1000) <Alarmtype>
        other (1) <Polarity> (2)
        "
	::= { pm10010mpAlmsynthAlmPortEntry 17 }


pm10010mpAlmFailAccPortn OBJECT-TYPE
	SYNTAX  EkiOnOff
	MAX-ACCESS read-only
	STATUS current
	DESCRIPTION
        "
        Client Access Fail :This OID indicates
        a failure on the Client port <Help>
        This alarm indicates a failure
         on the Client port <Condtype>
         FAIL_ACC_1 <Probcause> equipmentMalfunction
        (16) <Alarmtype> synthesisAlarm
        (12)  <Polarity> (2)
        "
	::= { pm10010mpAlmsynthAlmPortEntry 13 }


pm10010mpAlmSfpDdmAlmPortn OBJECT-TYPE
	SYNTAX  EkiOnOff
	MAX-ACCESS read-only
	STATUS current
	DESCRIPTION
        "
        Alarm On Client Trscv DDM :This
        OID indicates an alarm is being
        received from the Client Transceiver
        DDM <Help> This alarm indicates
        if a DDM Alarm has been detected
        on the client transceiver <Condtype>
        SFP_DDM_ALM_1 <Probcause> inputOutputDeviceError
        (24) <Alarmtype> synthesisAlarm
        (12)  <Polarity> (2)
        "
	::= { pm10010mpAlmsynthAlmPortEntry 11 }


pm10010mpAlmSfpDdmWarningPortn OBJECT-TYPE
	SYNTAX  EkiOnOff
	MAX-ACCESS read-only
	STATUS current
	DESCRIPTION
        "
        Warning On Client Trscv DDM :This
        OID indicates a warning is being
        received from the Client Transceiver
        DDM <Help> This alarm indicates
        if a DDM Warning has been detected
        on the client transceiver <Condtype>
        SFP_DDM_WARNING_1 <Probcause> inputOutputDeviceError
        (24) <Alarmtype> synthesisAlarm
        (12)  <Polarity> (2)
        "
	::= { pm10010mpAlmsynthAlmPortEntry 10 }


pm10010mpAlmDwCaisPortn OBJECT-TYPE
	SYNTAX  EkiOnOff
	MAX-ACCESS read-only
	STATUS current
	DESCRIPTION
        "
        Client AIS Inserted :This OID
         indicates a CAIS has been inserted
        on the output client port. <Help>
        This status indicates if a Client
        Alarm Indication Signal is currently
        inserted on the client interface
        <Condtype> DW_CAIS_1 <Probcause>
        informationalStatus(1000) <Alarmtype>
        other (1) <Polarity> (2)
        "
	::= { pm10010mpAlmsynthAlmPortEntry 9 }


pm10010mpAlmClientRemoteOosPortn OBJECT-TYPE
	SYNTAX  EkiOnOff
	MAX-ACCESS read-only
	STATUS current
	DESCRIPTION
        "
        Remote Client Port In Service
         :This OID indicates that the remote
        Client port is In Service (1) or
        Out of Service (2) <Help> This
         status indicates if the remote
        client port is in service <Condtype>
        CLIENT_REMOTE_OOS <Probcause> informationalStatus(1000)
        <Alarmtype> other (1) <Polarity>
        (2)
        "
	::= { pm10010mpAlmsynthAlmPortEntry 8 }


pm10010mpAlmClientLocalOosPortn OBJECT-TYPE
	SYNTAX  EkiOnOff
	MAX-ACCESS read-only
	STATUS current
	DESCRIPTION
        "
        Local Client Port In Service :This
        OID indicates that the local Client
        port is In Service (1) or Out of
        Service (2) <Help> This status
         indicates if the local client
         port is in service <Condtype>
         CLIENT_LOCAL_OOS <Probcause> informationalStatus(1000)
        <Alarmtype> other (1) <Polarity>
        (2)
        "
	::= { pm10010mpAlmsynthAlmPortEntry 7 }


pm10010mpAlmDwLsdPortn OBJECT-TYPE
	SYNTAX  EkiOnOff
	MAX-ACCESS read-only
	STATUS current
	DESCRIPTION
        "
        Client Trscv Laser Shutdown :This
        OID indicates the Client transceiver
        laser is shutdown <Help> This status
        indicates if the client transceiver
        laser is shutdown <Condtype> DW_LSD_1
        <Probcause> other (1) <Alarmtype>
        equipmentAlarm (5) <Polarity> (2)
        "
	::= { pm10010mpAlmsynthAlmPortEntry 6 }


pm10010mpAlmHwFailAccPortn OBJECT-TYPE
	SYNTAX  EkiOnOff
	MAX-ACCESS read-only
	STATUS current
	DESCRIPTION
        "
        Client HW Fail :This OID indicates
        a failure on client port, most
         probably caused by a HW issue.
        <Help> This alarm indicates a failure
        on client port, most probably caused
        by a HW issue. <Condtype> HW_FAIL_ACC_1
        <Probcause> equipmentMalfunction
        (16) <Alarmtype> synthesisAlarm
        (12)  <Polarity> (2)
        "
	::= { pm10010mpAlmsynthAlmPortEntry 5 }


pm10010mpAlmDdmAbsentPortn OBJECT-TYPE
	SYNTAX  EkiOnOff
	MAX-ACCESS read-only
	STATUS current
	DESCRIPTION
        "
        DDM Supported On Client Trscv
         :This OID indicates that the Client
        transceiver supports the Digital
        Diagnostic Monitoring function
         <Help> This status indicates if
        the client transceiver includes
        the DDM feature <Condtype> DDM_ABSENT_1
        <Probcause> informationalStatus(1000)
        <Alarmtype> other (1) <Polarity>
        (2)
        "
	::= { pm10010mpAlmsynthAlmPortEntry 3 }


pm10010mpAlmSfpAbsentPortn OBJECT-TYPE
	SYNTAX  EkiOnOff
	MAX-ACCESS read-only
	STATUS current
	DESCRIPTION
        "
        Client Optical Module Absent :This
        OID indicates that the Transceiver
        is not present in the client port.
        <Help> This alarm indicates if
         the client transceiver is not
         plugged <Condtype> SFP_ABSENT_1
        <Probcause> inputOutputDeviceError
        (24) <Alarmtype> equipmentAlarm
        (5) <Polarity> (2) <Event> ObjectCDINV
        "
	::= { pm10010mpAlmsynthAlmPortEntry 2 }


--- *********************************************************
---     TABLE for the pm10010mpAlmsynthAlmLine articles
--- *********************************************************

pm10010mpAlmsynthAlmLineTable OBJECT-TYPE
	SYNTAX  SEQUENCE OF Pm10010mpAlmsynthAlmLineEntry
	MAX-ACCESS not-accessible
	STATUS current
	DESCRIPTION
        "
        List of pm10010mpAlmsynthAlmLine
        Article
        "
	::= { pm10010mpAlmLineCrit 24 }


pm10010mpAlmsynthAlmLineEntry OBJECT-TYPE
	SYNTAX Pm10010mpAlmsynthAlmLineEntry
	MAX-ACCESS not-accessible
	STATUS current
	DESCRIPTION
        "
        Row definition for the pm10010mpAlmsynthAlmLine
        table
        "
	INDEX   { pm10010mpAlmsynthAlmLineIndex }
	::= { pm10010mpAlmsynthAlmLineTable 1 }


Pm10010mpAlmsynthAlmLineEntry ::=
	SEQUENCE {
	pm10010mpAlmsynthAlmLineIndex
		INTEGER,
	pm10010mpAlmLineActivePortn
		EkiOnOff,
	pm10010mpAlmLineFailPortn
		EkiOnOff,
	pm10010mpAlmLineDdmAlmPortn
		EkiOnOff,
	pm10010mpAlmLineDdmWarningPortn
		EkiOnOff,
	pm10010mpAlmUpRdiInsPortn
		EkiOnOff,
	pm10010mpAlmLineLocalOosPortn
		EkiOnOff,
	pm10010mpAlmXfpTxOffPortn
		EkiOnOff,
	pm10010mpAlmLineHwFailPortn
		EkiOnOff,
	pm10010mpAlmXfpInitNotComplPortn
		EkiOnOff,
	pm10010mpAlmXfpAbsentPortn
		EkiOnOff
	}


pm10010mpAlmsynthAlmLineIndex OBJECT-TYPE
	SYNTAX  INTEGER(0..128)
	MAX-ACCESS  read-only
	STATUS current
	DESCRIPTION
        "
        Index definition for the pm10010mpAlmsynthAlmLine
        table
        "
	::= { pm10010mpAlmsynthAlmLineEntry 1 }


pm10010mpAlmLineActivePortn OBJECT-TYPE
	SYNTAX  EkiOnOff
	MAX-ACCESS read-only
	STATUS current
	DESCRIPTION
        "
        Line Active :This OID indicates
        whether the line is active or standby.
        <Help> This status indicates whether
        the line is active or standby.
         <Condtype> LINE_ACTIVE <Probcause>
        informationalStatus(1000) <Alarmtype>
        other (1) <Polarity> (2)
        "
	::= { pm10010mpAlmsynthAlmLineEntry 17 }


pm10010mpAlmLineFailPortn OBJECT-TYPE
	SYNTAX  EkiOnOff
	MAX-ACCESS read-only
	STATUS current
	DESCRIPTION
        "
        Line Port Failure :This OID indicates
        a failure on the line port <Help>
        This alarm indicates a failure
         on the line port <Condtype> LINE_FAIL
        <Probcause> equipmentMalfunction
        (16) <Alarmtype> synthesisAlarm
        (12)  <Polarity> (2)
        "
	::= { pm10010mpAlmsynthAlmLineEntry 13 }


pm10010mpAlmLineDdmAlmPortn OBJECT-TYPE
	SYNTAX  EkiOnOff
	MAX-ACCESS read-only
	STATUS current
	DESCRIPTION
        "
        Alarm On Line Optical Module DDM
        :This OID indicates an alarm is
        present coming out of Line transceiver
        DDM <Help> This alarm indicates
        if a DDM Alarm has been detected
        on the line transceiver <Condtype>
        LINE_DDM_ALM <Probcause> inputOutputDeviceError
        (24) <Alarmtype> synthesisAlarm
        (12)  <Polarity> (2)
        "
	::= { pm10010mpAlmsynthAlmLineEntry 11 }


pm10010mpAlmLineDdmWarningPortn OBJECT-TYPE
	SYNTAX  EkiOnOff
	MAX-ACCESS read-only
	STATUS current
	DESCRIPTION
        "
        Warning On Line Optical Module
        DDM :This OID indicates a warning
        is present coming out of Line transceiver
        DDM <Help> This alarm indicates
        if a DDM Warning has been detected
        on the line transceiver <Condtype>
        LINE_DDM_WARNING <Probcause> inputOutputDeviceError
        (24) <Alarmtype> synthesisAlarm
        (12)  <Polarity> (2)
        "
	::= { pm10010mpAlmsynthAlmLineEntry 10 }


pm10010mpAlmUpRdiInsPortn OBJECT-TYPE
	SYNTAX  EkiOnOff
	MAX-ACCESS read-only
	STATUS current
	DESCRIPTION
        "
        MS-RDI/L-RDI Inserted On Line
         :This OID indicates an upstream
        MS-RDI/L-RDI has been inserted
         in the outgoing 10 Gb/s SDH/SONET
        signal. <Help> This status indicates
        if a MS-RDI/L-RDI is currently
         inserted on the line interface.
        <Condtype> UP_RDI_INS <Probcause>
        informationalStatus(1000) <Alarmtype>
        other (1) <Polarity> (2)
        "
	::= { pm10010mpAlmsynthAlmLineEntry 9 }


pm10010mpAlmLineLocalOosPortn OBJECT-TYPE
	SYNTAX  EkiOnOff
	MAX-ACCESS read-only
	STATUS current
	DESCRIPTION
        "
        Line Port In Service :This OID
        indicates that the Line port is
        In Service (1) of Out or Service
        (2) <Help> This status indicates
        if the line port is in service
         <Condtype> LINE_LOCAL_OOS <Probcause>
        informationalStatus(1000) <Alarmtype>
        other (1) <Polarity> (2)
        "
	::= { pm10010mpAlmsynthAlmLineEntry 7 }


pm10010mpAlmXfpTxOffPortn OBJECT-TYPE
	SYNTAX  EkiOnOff
	MAX-ACCESS read-only
	STATUS current
	DESCRIPTION
        "
        Line Trscv Laser Shutdown :This
        OID indicates the Line transceiver
        laser is shutdown <Help> This status
        indicates if the Line transceiver
        laser is shutdown <Condtype> XFP_TX_OFF
        <Probcause> other (1) <Alarmtype>
        equipmentAlarm (5) <Polarity> (2)
        "
	::= { pm10010mpAlmsynthAlmLineEntry 6 }


pm10010mpAlmLineHwFailPortn OBJECT-TYPE
	SYNTAX  EkiOnOff
	MAX-ACCESS read-only
	STATUS current
	DESCRIPTION
        "
        Line Port HW Failure :This OID
        indicates a failure on line port,
        most probably caused by a HW issue
        <Help> This alarm indicates a failure
        on line port, most probably caused
        by a HW issue <Condtype> LINE_HW_FAIL
        <Probcause> equipmentMalfunction
        (16) <Alarmtype> synthesisAlarm
        (12)  <Polarity> (2)
        "
	::= { pm10010mpAlmsynthAlmLineEntry 5 }


pm10010mpAlmXfpInitNotComplPortn OBJECT-TYPE
	SYNTAX  EkiOnOff
	MAX-ACCESS read-only
	STATUS current
	DESCRIPTION
        "
        Line Optical Module Ready :This
        OID indicates that the optical
         interface is not operational.
         <Help> This status indicates if
        the line transceiver has been correctly
        initialized <Condtype> XFP_INIT_NOT_COMPL
        <Probcause> equipmentMalfunction
        (16) <Alarmtype> equipmentAlarm
        (5) <Polarity> (2)
        "
	::= { pm10010mpAlmsynthAlmLineEntry 3 }


pm10010mpAlmXfpAbsentPortn OBJECT-TYPE
	SYNTAX  EkiOnOff
	MAX-ACCESS read-only
	STATUS current
	DESCRIPTION
        "
        Line Optical Module Absent :This
        OID indicates that the line optical
        interface is not present. <Help>
        This alarm indicates if the line
        transceiver is not plugged <Condtype>
        XFP_ABSENT <Probcause> inputOutputDeviceError
        (24) <Alarmtype> equipmentAlarm
        (5) <Polarity> (2)
        "
	::= { pm10010mpAlmsynthAlmLineEntry 2 }


--- *****************************************************
---     LEAF for the clientModuleState article
--- *****************************************************
pm10010mpAlmclientModuleState OBJECT IDENTIFIER ::= { pm10010mpAlmOtherCrit 40 }




pm10010mpAlmCfpHighPowerDown OBJECT-TYPE
	  SYNTAX EkiOnOff
	  MAX-ACCESS read-only
	  STATUS current
	  DESCRIPTION
        "
        Client Trscv High Power Down :This
        OID indicates the Client Trscv
         is entering Low Power state <Help>
        Status indicating the Client Trscv
        is entering Low Power state <Condtype>
        CFP_HIGH_POWER_DOWN <Probcause>
        informationalStatus(1000) <Alarmtype>
        other (1) <Polarity> (2)
        "
	  ::= { pm10010mpAlmclientModuleState 9 }



pm10010mpAlmCfpTxTurnOff OBJECT-TYPE
	  SYNTAX EkiOnOff
	  MAX-ACCESS read-only
	  STATUS current
	  DESCRIPTION
        "
        Client Trscv Laser Turn Off :This
        OID indicates the Client Trscv
         is turning off its laser <Help>
        Status indicating the Client Trscv
        is turning off its laser <Condtype>
        CFP_TX_TURN_OFF <Probcause> informationalStatus(1000)
        <Alarmtype> other (1) <Polarity>
        (2)
        "
	  ::= { pm10010mpAlmclientModuleState 8 }



pm10010mpAlmCfpFault OBJECT-TYPE
	  SYNTAX EkiOnOff
	  MAX-ACCESS read-only
	  STATUS current
	  DESCRIPTION
        "
        Client Trscv Fault :This OID indicates
        the Client Trscv is in Fault state
        <Help> Status indicating the Client
        Trscv is in Fault state <Condtype>
        CFP_FAULT <Probcause> informationalStatus(1000)
        <Alarmtype> other (1) <Polarity>
        (2)
        "
	  ::= { pm10010mpAlmclientModuleState 7 }



pm10010mpAlmCfpReady OBJECT-TYPE
	  SYNTAX EkiOnOff
	  MAX-ACCESS read-only
	  STATUS current
	  DESCRIPTION
        "
        Client Trscv Ready :This OID indicates
        the Client Trscv is ready to operate
        <Help> Status indicating the Client
        Trscv is ready to operate <Condtype>
        CFP_READY <Probcause> informationalStatus(1000)
        <Alarmtype> other (1) <Polarity>
        (2)
        "
	  ::= { pm10010mpAlmclientModuleState 6 }



pm10010mpAlmCfpTxTurnOn OBJECT-TYPE
	  SYNTAX EkiOnOff
	  MAX-ACCESS read-only
	  STATUS current
	  DESCRIPTION
        "
        Client Trscv Laser Turn On :This
        OID indicates the Client Trscv
         is turning on its laser <Help>
        Status indicating the Client Trscv
        is turning on its laser <Condtype>
        CFP_TX_TURN_ON <Probcause> informationalStatus(1000)
        <Alarmtype> other (1) <Polarity>
        (2)
        "
	  ::= { pm10010mpAlmclientModuleState 5 }



pm10010mpAlmCfpTxOff OBJECT-TYPE
	  SYNTAX EkiOnOff
	  MAX-ACCESS read-only
	  STATUS current
	  DESCRIPTION
        "
        Client Trscv Laser Shutdown :This
        OID indicates the Client Trscv
         Laser is OFF <Help> Status indicating
        the Client Trscv Laser is OFF <Condtype>
        CFP_TX_OFF <Probcause> informationalStatus(1000)
        <Alarmtype> other (1) <Polarity>
        (2)
        "
	  ::= { pm10010mpAlmclientModuleState 4 }



pm10010mpAlmCfpHighPowerUp OBJECT-TYPE
	  SYNTAX EkiOnOff
	  MAX-ACCESS read-only
	  STATUS current
	  DESCRIPTION
        "
        Client Trscv High Power Up :This
        OID indicates the Client Trscv
         is leaving Low Power state <Help>
        Status indicating the Client Trscv
        is leaving Low Power state <Condtype>
        CFP_HIGH_POWER_UP <Probcause> informationalStatus(1000)
        <Alarmtype> other (1) <Polarity>
        (2)
        "
	  ::= { pm10010mpAlmclientModuleState 3 }



pm10010mpAlmCfpLowPower OBJECT-TYPE
	  SYNTAX EkiOnOff
	  MAX-ACCESS read-only
	  STATUS current
	  DESCRIPTION
        "
        Client Trscv Low Power :This OID
        indicates the Client Trscv is in
        low power state <Help> Status indicating
        the Client Trscv is in low power
        state <Condtype> CFP_LOW_POWER
         <Probcause> informationalStatus(1000)
        <Alarmtype> other (1) <Polarity>
        (2)
        "
	  ::= { pm10010mpAlmclientModuleState 2 }



pm10010mpAlmCfpInitialize OBJECT-TYPE
	  SYNTAX EkiOnOff
	  MAX-ACCESS read-only
	  STATUS current
	  DESCRIPTION
        "
        Client Trscv Initialize :This
         OID indicates the Client Trscv
        initialization is in progress <Help>
        Status indicating the Client Trscv
        initialization is in progress <Condtype>
        CFP_INITIALIZE <Probcause> informationalStatus(1000)
        <Alarmtype> other (1) <Polarity>
        (2)
        "
	  ::= { pm10010mpAlmclientModuleState 1 }



--- *****************************************************
---     LEAF for the clientModuleGeneralStatus article
--- *****************************************************
pm10010mpAlmclientModuleGeneralStatus OBJECT IDENTIFIER ::= { pm10010mpAlmOtherCrit 41 }




pm10010mpAlmCfpHwInterlock OBJECT-TYPE
	  SYNTAX EkiOnOff
	  MAX-ACCESS read-only
	  STATUS current
	  DESCRIPTION
        "
        Client Trscv Hardware Interlock
        :This OID indicates the Client
         Trscv power is higher than the
        cooling capacity <Help> Alarm indicating
        the Client Trscv power is higher
        than the cooling capacity <Condtype>
        CFP_HW_INTERLOCK <Probcause> temperatureUnacceptable
        (51) <Alarmtype> equipmentAlarm
        (5) <Polarity> (2)
        "
	  ::= { pm10010mpAlmclientModuleGeneralStatus 14 }



pm10010mpAlmCfpLossOfRefclk OBJECT-TYPE
	  SYNTAX EkiOnOff
	  MAX-ACCESS read-only
	  STATUS current
	  DESCRIPTION
        "
        Client Trscv Loss Of Ref Clock
        :This OID indicates a Loss of Reference
        clock is detected on the Client
        Trscv <Help> Alarm indicating a
        Loss of Reference clock is detected
        on the Client Trscv <Condtype>
         CFP_LOSS_OF_REFCLK <Probcause>
        inputOutputDeviceError (24) <Alarmtype>
        equipmentAlarm (5) <Polarity> (2)
        "
	  ::= { pm10010mpAlmclientModuleGeneralStatus 11 }



pm10010mpAlmCfpTxJitterPllLol OBJECT-TYPE
	  SYNTAX EkiOnOff
	  MAX-ACCESS read-only
	  STATUS current
	  DESCRIPTION
        "
        Client Trscv Tx Jitter PLL Loss
        Of Lock :This OID indicates a Tx
        Jitter PLL Loss of Lock is dtected
        on the Client Trscv <Help> Alarm
        indicating a Tx Jitter PLL Loss
        of Lock is dtected on the Client
        Trscv <Condtype> CFP_TX_JITTER_PLL_LOL
        <Probcause> inputOutputDeviceError
        (24) <Alarmtype> equipmentAlarm
        (5) <Polarity> (2)
        "
	  ::= { pm10010mpAlmclientModuleGeneralStatus 10 }



pm10010mpAlmCfpTxCmuLol OBJECT-TYPE
	  SYNTAX EkiOnOff
	  MAX-ACCESS read-only
	  STATUS current
	  DESCRIPTION
        "
        Client Trscv CMU Loss Of Lock
         :This OID indicates a Clock Multiplier
        Unit Loss of Lock is detected on
        the Client Trscv <Help> Alarm indicating
        a Clock Multiplier Unit Loss of
        Lock is detected on the Client
         Trscv <Condtype> CFP_TX_CMU_LOL
        <Probcause> inputOutputDeviceError
        (24) <Alarmtype> equipmentAlarm
        (5) <Polarity> (2)
        "
	  ::= { pm10010mpAlmclientModuleGeneralStatus 9 }



pm10010mpAlmCfpTxLosf OBJECT-TYPE
	  SYNTAX EkiOnOff
	  MAX-ACCESS read-only
	  STATUS current
	  DESCRIPTION
        "
        Client Trscv Loss Of Signal Functionality
        :This OID indicates a Loss of Signal
        functionality is detected on the
        Client Trscv <Help> Alarm indicating
        a Loss of Signal functionality
         is detected on the Client Trscv
        <Condtype> CFP_TX_LOSF <Probcause>
        lossOfSignal (30) <Alarmtype> equipmentAlarm
        (5) <Polarity> (2)
        "
	  ::= { pm10010mpAlmclientModuleGeneralStatus 8 }



pm10010mpAlmCfpTxHostLol OBJECT-TYPE
	  SYNTAX EkiOnOff
	  MAX-ACCESS read-only
	  STATUS current
	  DESCRIPTION
        "
        Client Trscv Tx Host Loss Of Lock
        :This OID indicates of Loss of
         Lock is detected on the Client
        Trscv Tx Host interface <Help>
         Alarm indicating of Loss of Lock
        is detected on the Client Trscv
        Tx Host interface <Condtype> CFP_TX_HOST_LOL
        <Probcause> receiverFailure (42)
        <Alarmtype> equipmentAlarm (5)
         <Polarity> (2)
        "
	  ::= { pm10010mpAlmclientModuleGeneralStatus 7 }



pm10010mpAlmCfpRxLos OBJECT-TYPE
	  SYNTAX EkiOnOff
	  MAX-ACCESS read-only
	  STATUS current
	  DESCRIPTION
        "
        Client Trscv Loss Of Signal :This
        OID indicates a Loss of Signal
         is detected on the Client Trscv
        <Help> Alarm indicating a Loss
         of Signal is detected on the Client
        Trscv <Condtype> CFP_RX_LOS <Probcause>
        lossOfSignal (30) <Alarmtype> equipmentAlarm
        (5) <Polarity> (2)
        "
	  ::= { pm10010mpAlmclientModuleGeneralStatus 6 }



pm10010mpAlmCfpRxNetworkLol OBJECT-TYPE
	  SYNTAX EkiOnOff
	  MAX-ACCESS read-only
	  STATUS current
	  DESCRIPTION
        "
        Client Trscv Rx Network Loss Of
        Lock :This OID indicates of Loss
        of Lock is dected on the Client
        Trscv Rx Network interface <Help>
        Alarm indicating of Loss of Lock
        is dected on the Client Trscv Rx
        Network interface <Condtype> CFP_RX_NETWORK_LOL
        <Probcause> receiverFailure (42)
        <Alarmtype> equipmentAlarm (5)
         <Polarity> (2)
        "
	  ::= { pm10010mpAlmclientModuleGeneralStatus 5 }



pm10010mpAlmCfpOutOfAlignment OBJECT-TYPE
	  SYNTAX EkiOnOff
	  MAX-ACCESS read-only
	  STATUS current
	  DESCRIPTION
        "
        Client Trscv Out Of Alignment
         :This OID indicates an Out of
         alignment on the Client Trscv
         Host Interface <Help> Alarm indicating
        an Out of alignment on the Client
        Trscv Host Interface <Condtype>
        CFP_OUT_OF_ALIGNMENT <Probcause>
        receiverFailure (42) <Alarmtype>
        equipmentAlarm (5) <Polarity> (2)
        "
	  ::= { pm10010mpAlmclientModuleGeneralStatus 4 }



--- *****************************************************
---     LEAF for the clientGlobalAlarmSummary article
--- *****************************************************
pm10010mpAlmclientGlobalAlarmSummary OBJECT IDENTIFIER ::= { pm10010mpAlmOtherCrit 42 }




pm10010mpAlmCfpGlobAlarmAssertion  OBJECT-TYPE
	  SYNTAX EkiOnOff
	  MAX-ACCESS read-only
	  STATUS current
	  DESCRIPTION
        "
        Client Trscv Global Alarm :This
        OID indicates at least one  Fault
        or Status is detected on the Client
        Trscv module <Help> Synthesis alarm
        indicating at least one Alarm,
         Warning, Fault or Status is detected
        on the Client Trscv module <Condtype>
        CFP_GLOB_ALARM_ASSERTION  <Probcause>
        informationalStatus(1000) <Alarmtype>
        other (1) <Polarity> (2)
        "
	  ::= { pm10010mpAlmclientGlobalAlarmSummary 16 }



pm10010mpAlmCfpHostLaneFaultStatus  OBJECT-TYPE
	  SYNTAX EkiOnOff
	  MAX-ACCESS read-only
	  STATUS current
	  DESCRIPTION
        "
        Client Trscv Host Fault And Status
        :This OID indicates at least one
        Fault or Status is detected on
         the Client Trscv Host Interface
        <Help> Synthesis alarm indicating
        at least one Fault or Status is
        detected on the Client Trscv Host
        Interface <Condtype> CFP_HOST_LANE_FAULT_STATUS
         <Probcause> informationalStatus(1000)
        <Alarmtype> other (1) <Polarity>
        (2)
        "
	  ::= { pm10010mpAlmclientGlobalAlarmSummary 15 }



pm10010mpAlmCfpNetworkLaneFaultStatus  OBJECT-TYPE
	  SYNTAX EkiOnOff
	  MAX-ACCESS read-only
	  STATUS current
	  DESCRIPTION
        "
        Client Trscv Network Fault And
        Status :This OID indicates at least
        one Fault or Status is detected
        on the Client Trscv Network Interface
        <Help> Synthesis alarm indicating
        at least one Fault or Status is
        detected on the Client Trscv Network
        Interface <Condtype> CFP_NETWORK_LANE_FAULT_STATUS
         <Probcause> informationalStatus(1000)
        <Alarmtype> other (1) <Polarity>
        (2)
        "
	  ::= { pm10010mpAlmclientGlobalAlarmSummary 14 }



pm10010mpAlmCfpNetworkLaneAlarmWarning1 OBJECT-TYPE
	  SYNTAX EkiOnOff
	  MAX-ACCESS read-only
	  STATUS current
	  DESCRIPTION
        "
        Client Trscv Network Alarm And
        Warning 1 :This OID indicates at
        least one DDM  is detected on the
        Client Trscv Network Interface
         <Help> Synthesis alarm indicating
        at least one DDM Alarm or DDM Warning
        is detected on the Client Trscv
        Network Interface <Condtype> CFP_NETWORK_LANE_ALARM_WARNING_1
        <Probcause> informationalStatus(1000)
        <Alarmtype> other (1) <Polarity>
        (2)
        "
	  ::= { pm10010mpAlmclientGlobalAlarmSummary 13 }



pm10010mpAlmCfpModuleAlarmWarning2 OBJECT-TYPE
	  SYNTAX EkiOnOff
	  MAX-ACCESS read-only
	  STATUS current
	  DESCRIPTION
        "
        Client Trscv Module Alarm And
         Warning 2 :This OID indicates
         at least one DDM is detected on
        the Client Trscv module <Help>
         Synthesis alarm indicating at
         least one DDM Alarm or DDM Warning
        is detected on the Client Trscv
        module <Condtype> CFP_MODULE_ALARM_WARNING_2
        <Probcause> informationalStatus(1000)
        <Alarmtype> other (1) <Polarity>
        (2)
        "
	  ::= { pm10010mpAlmclientGlobalAlarmSummary 12 }



pm10010mpAlmCfpModuleAlarmWarning1  OBJECT-TYPE
	  SYNTAX EkiOnOff
	  MAX-ACCESS read-only
	  STATUS current
	  DESCRIPTION
        "
        Client Trscv Module Alarm And
         Warning 1 :This OID indicates
         at least one DDM  This OID is
         detected on the Client Trscv module
        <Help> Synthesis alarm indicating
        at least one DDM Alarm or DDM Warning
        is detected on the Client Trscv
        module <Condtype> CFP_MODULE_ALARM_WARNING_1
         <Probcause> informationalStatus(1000)
        <Alarmtype> other (1) <Polarity>
        (2)
        "
	  ::= { pm10010mpAlmclientGlobalAlarmSummary 11 }



pm10010mpAlmCfpModuleFault  OBJECT-TYPE
	  SYNTAX EkiOnOff
	  MAX-ACCESS read-only
	  STATUS current
	  DESCRIPTION
        "
        Client Trscv Module Fault :This
        OID indicates at least one Fault
        is detected on the Client Trscv
        module <Help> Synthesis alarm indicating
        at least one Fault is detected
         on the Client Trscv module <Condtype>
        CFP_MODULE_FAULT  <Probcause> informationalStatus(1000)
        <Alarmtype> other (1) <Polarity>
        (2)
        "
	  ::= { pm10010mpAlmclientGlobalAlarmSummary 10 }



pm10010mpAlmCfpModuleGeneralStatus  OBJECT-TYPE
	  SYNTAX EkiOnOff
	  MAX-ACCESS read-only
	  STATUS current
	  DESCRIPTION
        "
        Client Trscv General Status :This
        OID indicates the Client Trscv
         module general status <Help> Synthesis
        alarm indicating the Client Trscv
        module general status <Condtype>
        CFP_MODULE_GENERAL_STATUS  <Probcause>
        informationalStatus(1000) <Alarmtype>
        other (1) <Polarity> (2)
        "
	  ::= { pm10010mpAlmclientGlobalAlarmSummary 9 }



pm10010mpAlmCfpModuleState  OBJECT-TYPE
	  SYNTAX EkiOnOff
	  MAX-ACCESS read-only
	  STATUS current
	  DESCRIPTION
        "
        Client Trscv Module State :This
        OID indicates the Client Trscv
         module state <Help> Synthesis
         alarm indicating the Client Trscv
        module state <Condtype> CFP_MODULE_STATE
         <Probcause> informationalStatus(1000)
        <Alarmtype> other (1) <Polarity>
        (2)
        "
	  ::= { pm10010mpAlmclientGlobalAlarmSummary 8 }



pm10010mpAlmCfpNetworkLaneAlarmWarning2 OBJECT-TYPE
	  SYNTAX EkiOnOff
	  MAX-ACCESS read-only
	  STATUS current
	  DESCRIPTION
        "
        Client Trscv Network Alarm And
        Warning 2 :This OID indicates at
        least one DDM is detected on the
        Client Trscv Network Interface
         <Help> Synthesis alarm indicating
        at least one DDM Alarm or DDM Warning
        is detected on the Client Trscv
        Network Interface <Condtype> CFP_NETWORK_LANE_ALARM_WARNING_2
        <Probcause> informationalStatus(1000)
        <Alarmtype> other (1) <Polarity>
        (2)
        "
	  ::= { pm10010mpAlmclientGlobalAlarmSummary 7 }



pm10010mpAlmCfpSoftGlobAlarmTest  OBJECT-TYPE
	  SYNTAX EkiOnOff
	  MAX-ACCESS read-only
	  STATUS current
	  DESCRIPTION
        "
        Client Trscv Global Alarm SW Test
        :This OID indicates the Client
         Trscv Global Alarm This OID is
        raised by SW request for test purpose
        <Help> Status indicating the Client
        Trscv Global Alarm is raised by
        SW request for test purpose <Condtype>
        CFP_SOFT_GLOB_ALARM_TEST  <Probcause>
        informationalStatus(1000) <Alarmtype>
        other (1) <Polarity> (2)
        "
	  ::= { pm10010mpAlmclientGlobalAlarmSummary 1 }



--- *****************************************************
---     LEAF for the msaModuleState article
--- *****************************************************
pm10010mpAlmmsaModuleState OBJECT IDENTIFIER ::= { pm10010mpAlmOtherCrit 46 }




pm10010mpAlmMsaHighPowerDown OBJECT-TYPE
	  SYNTAX EkiOnOff
	  MAX-ACCESS read-only
	  STATUS current
	  DESCRIPTION
        "
        Line Trscv High Power Down :This
        OID indicates the Line Trscv is
        entering Low Power state <Help>
        Status indicating the Line Trscv
        is entering Low Power state <Condtype>
        MSA_HIGH_POWER_DOWN <Probcause>
        informationalStatus(1000) <Alarmtype>
        other (1) <Polarity> (2)
        "
	  ::= { pm10010mpAlmmsaModuleState 9 }



pm10010mpAlmMsaTxTurnOff OBJECT-TYPE
	  SYNTAX EkiOnOff
	  MAX-ACCESS read-only
	  STATUS current
	  DESCRIPTION
        "
        Line Trscv Laser Turn Off :This
        OID indicates the Line Trscv is
        turning off its laser <Help> Status
        indicating the Line Trscv is turning
        off its laser <Condtype> MSA_TX_TURN_OFF
        <Probcause> informationalStatus(1000)
        <Alarmtype> other (1) <Polarity>
        (2)
        "
	  ::= { pm10010mpAlmmsaModuleState 8 }



pm10010mpAlmMsaFault OBJECT-TYPE
	  SYNTAX EkiOnOff
	  MAX-ACCESS read-only
	  STATUS current
	  DESCRIPTION
        "
        Line Trscv Fault :This OID indicates
        the Line Trscv is in Fault state
        <Help> Status indicating the Line
        Trscv is in Fault state <Condtype>
        MSA_FAULT <Probcause> informationalStatus(1000)
        <Alarmtype> other (1) <Polarity>
        (2)
        "
	  ::= { pm10010mpAlmmsaModuleState 7 }



pm10010mpAlmMsaReady OBJECT-TYPE
	  SYNTAX EkiOnOff
	  MAX-ACCESS read-only
	  STATUS current
	  DESCRIPTION
        "
        Line Trscv Ready :This OID indicates
        the Line Trscv is ready to operate
        <Help> Status indicating the Line
        Trscv is ready to operate <Condtype>
        MSA_READY <Probcause> informationalStatus(1000)
        <Alarmtype> other (1) <Polarity>
        (2)
        "
	  ::= { pm10010mpAlmmsaModuleState 6 }



pm10010mpAlmMsaTxTurnOn OBJECT-TYPE
	  SYNTAX EkiOnOff
	  MAX-ACCESS read-only
	  STATUS current
	  DESCRIPTION
        "
        Line Trscv Laser Turn On :This
        OID indicates the Line Trscv is
        turning on its laser <Help> Status
        indicating the Line Trscv is turning
        on its laser <Condtype> MSA_TX_TURN_ON
        <Probcause> informationalStatus(1000)
        <Alarmtype> other (1) <Polarity>
        (2)
        "
	  ::= { pm10010mpAlmmsaModuleState 5 }



pm10010mpAlmMsaTxOff OBJECT-TYPE
	  SYNTAX EkiOnOff
	  MAX-ACCESS read-only
	  STATUS current
	  DESCRIPTION
        "
        Line Trscv Laser Shutdown :This
        OID indicates the Line Trscv Laser
        is OFF <Help> Status indicating
        the Line Trscv Laser is OFF <Condtype>
        MSA_TX_OFF <Probcause> informationalStatus(1000)
        <Alarmtype> other (1) <Polarity>
        (2)
        "
	  ::= { pm10010mpAlmmsaModuleState 4 }



pm10010mpAlmMsaHighPowerUp OBJECT-TYPE
	  SYNTAX EkiOnOff
	  MAX-ACCESS read-only
	  STATUS current
	  DESCRIPTION
        "
        Line Trscv High Power Up :This
        OID indicates the Line Trscv is
        leaving Low Power state <Help>
         Status indicating the Line Trscv
        is leaving Low Power state <Condtype>
        MSA_HIGH_POWER_UP <Probcause> informationalStatus(1000)
        <Alarmtype> other (1) <Polarity>
        (2)
        "
	  ::= { pm10010mpAlmmsaModuleState 3 }



pm10010mpAlmMsaLowPower OBJECT-TYPE
	  SYNTAX EkiOnOff
	  MAX-ACCESS read-only
	  STATUS current
	  DESCRIPTION
        "
        Line Trscv Low Power :This OID
        indicates the Line Trscv is in
         low power state <Help> Status
         indicating the Line Trscv is in
        low power state <Condtype> MSA_LOW_POWER
        <Probcause> informationalStatus(1000)
        <Alarmtype> other (1) <Polarity>
        (2)
        "
	  ::= { pm10010mpAlmmsaModuleState 2 }



pm10010mpAlmMsaInitialize OBJECT-TYPE
	  SYNTAX EkiOnOff
	  MAX-ACCESS read-only
	  STATUS current
	  DESCRIPTION
        "
        Line Trscv Initialize :This OID
        indicates the Line Trscv initialization
        is in progress <Help> Status indicating
        the Line Trscv initialization is
        in progress <Condtype> MSA_INITIALIZE
        <Probcause> informationalStatus(1000)
        <Alarmtype> other (1) <Polarity>
        (2)
        "
	  ::= { pm10010mpAlmmsaModuleState 1 }



--- *****************************************************
---     LEAF for the msaModuleGeneralStatus article
--- *****************************************************
pm10010mpAlmmsaModuleGeneralStatus OBJECT IDENTIFIER ::= { pm10010mpAlmOtherCrit 47 }




pm10010mpAlmMsaHwInterlock OBJECT-TYPE
	  SYNTAX EkiOnOff
	  MAX-ACCESS read-only
	  STATUS current
	  DESCRIPTION
        "
        Line Trscv Hardware Interlock
         :This OID indicates the Line Trscv
        power is higher than the cooling
        capacity <Help> Alarm indicating
        the Line Trscv power is higher
         than the cooling capacity <Condtype>
        MSA_HW_INTERLOCK <Probcause> temperatureUnacceptable
        (51) <Alarmtype> equipmentAlarm
        (5) <Polarity> (2)
        "
	  ::= { pm10010mpAlmmsaModuleGeneralStatus 14 }



pm10010mpAlmMsaLossOfRefclk OBJECT-TYPE
	  SYNTAX EkiOnOff
	  MAX-ACCESS read-only
	  STATUS current
	  DESCRIPTION
        "
        Line Trscv Loss Of Ref Clock :This
        OID indicates a Loss of Reference
        clock is detected on the Line Trscv
        <Help> Alarm indicating a Loss
         of Reference clock is detected
        on the Line Trscv <Condtype> MSA_LOSS_OF_REFCLK
        <Probcause> inputOutputDeviceError
        (24) <Alarmtype> equipmentAlarm
        (5) <Polarity> (2)
        "
	  ::= { pm10010mpAlmmsaModuleGeneralStatus 11 }



pm10010mpAlmMsaTxJitterPllLol OBJECT-TYPE
	  SYNTAX EkiOnOff
	  MAX-ACCESS read-only
	  STATUS current
	  DESCRIPTION
        "
        Line Trscv Tx Jitter PLL Loss
         Of Lock :This OID indicates a
         Tx Jitter PLL Loss of Lock is
         detected on the Line Trscv <Help>
        Alarm indicating a Tx Jitter PLL
        Loss of Lock is detected on the
        Line Trscv <Condtype> MSA_TX_JITTER_PLL_LOL
        <Probcause> inputOutputDeviceError
        (24) <Alarmtype> equipmentAlarm
        (5) <Polarity> (2)
        "
	  ::= { pm10010mpAlmmsaModuleGeneralStatus 10 }



pm10010mpAlmMsaTxCmuLol OBJECT-TYPE
	  SYNTAX EkiOnOff
	  MAX-ACCESS read-only
	  STATUS current
	  DESCRIPTION
        "
        Line Trscv CMU Loss Of Lock :This
        OID indicates a Clock Multiplier
        Unit Loss of Lock is detected on
        the Line Trscv <Help> Alarm indicating
        a Clock Multiplier Unit Loss of
        Lock is detected on the Line Trscv
        <Condtype> MSA_TX_CMU_LOL <Probcause>
        inputOutputDeviceError (24) <Alarmtype>
        equipmentAlarm (5) <Polarity> (2)
        "
	  ::= { pm10010mpAlmmsaModuleGeneralStatus 9 }



pm10010mpAlmMsaTxLosf OBJECT-TYPE
	  SYNTAX EkiOnOff
	  MAX-ACCESS read-only
	  STATUS current
	  DESCRIPTION
        "
        Line Trscv Loss Of Signal Functionality
        :This OID indicates a Loss of Signal
        functionality is detected on the
        Line Trscv <Help> Alarm indicating
        a Loss of Signal functionality
         is detected on the Line Trscv
         <Condtype> MSA_TX_LOSF <Probcause>
        lossOfSignal (30) <Alarmtype> equipmentAlarm
        (5) <Polarity> (2)
        "
	  ::= { pm10010mpAlmmsaModuleGeneralStatus 8 }



pm10010mpAlmMsaTxHostLol OBJECT-TYPE
	  SYNTAX EkiOnOff
	  MAX-ACCESS read-only
	  STATUS current
	  DESCRIPTION
        "
        Line Trscv Tx Host Loss Of Lock
        :This OID indicates of Loss of
         Lock is detected on the Line Trscv
        Tx Host interface <Help> Alarm
         indicating of Loss of Lock is
         detected on the Line Trscv Tx
         Host interface <Condtype> MSA_TX_HOST_LOL
        <Probcause> receiverFailure (42)
        <Alarmtype> equipmentAlarm (5)
         <Polarity> (2)
        "
	  ::= { pm10010mpAlmmsaModuleGeneralStatus 7 }



pm10010mpAlmMsaRxLos OBJECT-TYPE
	  SYNTAX EkiOnOff
	  MAX-ACCESS read-only
	  STATUS current
	  DESCRIPTION
        "
        Line Trscv Loss Of Signal :This
        OID indicates a Loss of Signal
         is detected on the Line Trscv
         <Help> Alarm indicating a Loss
        of Signal is detected on the Line
        Trscv <Condtype> MSA_RX_LOS <Probcause>
        lossOfSignal (30) <Alarmtype> equipmentAlarm
        (5) <Polarity> (2)
        "
	  ::= { pm10010mpAlmmsaModuleGeneralStatus 6 }



pm10010mpAlmMsaRxNetworkLol OBJECT-TYPE
	  SYNTAX EkiOnOff
	  MAX-ACCESS read-only
	  STATUS current
	  DESCRIPTION
        "
        Line Trscv Rx Network Loss Of
         Lock :This OID indicates of Loss
        of Lock is detected on the Line
        Trscv Rx Network interface <Help>
        Alarm indicating of Loss of Lock
        is detected on the Line Trscv Rx
        Network interface <Condtype> MSA_RX_NETWORK_LOL
        <Probcause> receiverFailure (42)
        <Alarmtype> equipmentAlarm (5)
         <Polarity> (2)
        "
	  ::= { pm10010mpAlmmsaModuleGeneralStatus 5 }



pm10010mpAlmMsaOutOfAlignment OBJECT-TYPE
	  SYNTAX EkiOnOff
	  MAX-ACCESS read-only
	  STATUS current
	  DESCRIPTION
        "
        Line Trscv Out Of Alignment :This
        OID indicates an Out of alignment
        on the Line Trscv Host Interface
        <Help> Alarm indicating an Out
         of alignment on the Line Trscv
        Host Interface <Condtype> MSA_OUT_OF_ALIGNMENT
        <Probcause> receiverFailure (42)
        <Alarmtype> equipmentAlarm (5)
         <Polarity> (2)
        "
	  ::= { pm10010mpAlmmsaModuleGeneralStatus 4 }



--- *****************************************************
---     LEAF for the msaGlobalAlarmSummary article
--- *****************************************************
pm10010mpAlmmsaGlobalAlarmSummary OBJECT IDENTIFIER ::= { pm10010mpAlmOtherCrit 48 }




pm10010mpAlmMsaGlobAlarmAssertion  OBJECT-TYPE
	  SYNTAX EkiOnOff
	  MAX-ACCESS read-only
	  STATUS current
	  DESCRIPTION
        "
        Line Trscv Global Alarm :This
         OID indicates at least one Fault
        or Status is detected on the Line
        Trscv module <Help> Synthesis alarm
        indicating at least one Alarm,
         Warning, Fault or Status is detected
        on the Line Trscv module <Condtype>
        MSA_GLOB_ALARM_ASSERTION  <Probcause>
        informationalStatus(1000) <Alarmtype>
        other (1) <Polarity> (2)
        "
	  ::= { pm10010mpAlmmsaGlobalAlarmSummary 16 }



pm10010mpAlmMsaHostLaneFaultStatus  OBJECT-TYPE
	  SYNTAX EkiOnOff
	  MAX-ACCESS read-only
	  STATUS current
	  DESCRIPTION
        "
        Line Trscv Host Fault And Status
        :This OID indicates at least one
        Fault or Status is detected on
         the Line Trscv Host Interface
         <Help> Synthesis alarm indicating
        at least one Fault or Status is
        detected on the Line Trscv Host
        Interface <Condtype> MSA_HOST_LANE_FAULT_STATUS
         <Probcause> informationalStatus(1000)
        <Alarmtype> other (1) <Polarity>
        (2)
        "
	  ::= { pm10010mpAlmmsaGlobalAlarmSummary 15 }



pm10010mpAlmMsaNetworkLaneFaultStatus  OBJECT-TYPE
	  SYNTAX EkiOnOff
	  MAX-ACCESS read-only
	  STATUS current
	  DESCRIPTION
        "
        Line Trscv Network Fault And Status
        :This OID indicates at least one
        Fault or Status is detected on
         the Line Trscv Network Interface
        <Help> Synthesis alarm indicating
        at least one Fault or Status is
        detected on the Line Trscv Network
        Interface <Condtype> MSA_NETWORK_LANE_FAULT_STATUS
         <Probcause> informationalStatus(1000)
        <Alarmtype> other (1) <Polarity>
        (2)
        "
	  ::= { pm10010mpAlmmsaGlobalAlarmSummary 14 }



pm10010mpAlmMsaNetworkLaneAlarmWarning1 OBJECT-TYPE
	  SYNTAX EkiOnOff
	  MAX-ACCESS read-only
	  STATUS current
	  DESCRIPTION
        "
        Line Trscv Network Alarm And Warning
        1 :This OID indicates at least
         one DDM is detected on the Line
        Trscv Network Interface <Help>
         Synthesis alarm indicating at
         least one DDM Alarm or DDM Warning
        is detected on the Line Trscv Network
        Interface <Condtype> MSA_NETWORK_LANE_ALARM_WARNING_1
        <Probcause> informationalStatus(1000)
        <Alarmtype> other (1) <Polarity>
        (2)
        "
	  ::= { pm10010mpAlmmsaGlobalAlarmSummary 13 }



pm10010mpAlmMsaModuleAlarmWarning2 OBJECT-TYPE
	  SYNTAX EkiOnOff
	  MAX-ACCESS read-only
	  STATUS current
	  DESCRIPTION
        "
        Line Trscv Module Alarm And Warning
        2 :This OID indicates at least
         one DDM is detected on the Line
        Trscv module <Help> Synthesis alarm
        indicating at least one DDM Alarm
        or DDM Warning is detected on the
        Line Trscv module <Condtype> MSA_MODULE_ALARM_WARNING_2
        <Probcause> informationalStatus(1000)
        <Alarmtype> other (1) <Polarity>
        (2)
        "
	  ::= { pm10010mpAlmmsaGlobalAlarmSummary 12 }



pm10010mpAlmMsaModuleAlarmWarning1  OBJECT-TYPE
	  SYNTAX EkiOnOff
	  MAX-ACCESS read-only
	  STATUS current
	  DESCRIPTION
        "
        Line Trscv Module Alarm And Warning
        1 :This OID indicates at least
         one DDM is detected on the Line
        Trscv module <Help> Synthesis alarm
        indicating at least one DDM Alarm
        or DDM Warning is detected on the
        Line Trscv module <Condtype> MSA_MODULE_ALARM_WARNING_1
         <Probcause> informationalStatus(1000)
        <Alarmtype> other (1) <Polarity>
        (2)
        "
	  ::= { pm10010mpAlmmsaGlobalAlarmSummary 11 }



pm10010mpAlmModuleFault  OBJECT-TYPE
	  SYNTAX EkiOnOff
	  MAX-ACCESS read-only
	  STATUS current
	  DESCRIPTION
        "
        Line Trscv Module Fault :This
         OID indicates at least one Fault
        is detected on the Line Trscv module
        <Help> Synthesis alarm indicating
        at least one Fault is detected
         on the Line Trscv module <Condtype>
        MODULE_FAULT  <Probcause> informationalStatus(1000)
        <Alarmtype> other (1) <Polarity>
        (2)
        "
	  ::= { pm10010mpAlmmsaGlobalAlarmSummary 10 }



pm10010mpAlmMsaModuleGeneralStatus  OBJECT-TYPE
	  SYNTAX EkiOnOff
	  MAX-ACCESS read-only
	  STATUS current
	  DESCRIPTION
        "
        Line Trscv General Status :This
        OID indicates the Line Trscv module
        general <Help> Synthesis alarm
         indicating the Line Trscv module
        general status <Condtype> MSA_MODULE_GENERAL_STATUS
         <Probcause> informationalStatus(1000)
        <Alarmtype> other (1) <Polarity>
        (2)
        "
	  ::= { pm10010mpAlmmsaGlobalAlarmSummary 9 }



pm10010mpAlmMsaModuleState  OBJECT-TYPE
	  SYNTAX EkiOnOff
	  MAX-ACCESS read-only
	  STATUS current
	  DESCRIPTION
        "
        Line Trscv Module State :This
         OID indicates the Line Trscv module
        state <Help> Synthesis alarm indicating
        the Line Trscv module state <Condtype>
        MSA_MODULE_STATE  <Probcause> informationalStatus(1000)
        <Alarmtype> other (1) <Polarity>
        (2)
        "
	  ::= { pm10010mpAlmmsaGlobalAlarmSummary 8 }



pm10010mpAlmMsaNetworkLaneAlarmWarning2 OBJECT-TYPE
	  SYNTAX EkiOnOff
	  MAX-ACCESS read-only
	  STATUS current
	  DESCRIPTION
        "
        Line Trscv Network Alarm And Warning
        2 :This OID indicates at least
         one DDM This OID is detected on
        the Line Trscv Network Interface
        <Help> Synthesis alarm indicating
        at least one DDM Alarm or DDM Warning
        is detected on the Line Trscv Network
        Interface <Condtype> MSA_NETWORK_LANE_ALARM_WARNING_2
        <Probcause> informationalStatus(1000)
        <Alarmtype> other (1) <Polarity>
        (2)
        "
	  ::= { pm10010mpAlmmsaGlobalAlarmSummary 7 }



pm10010mpAlmMsaNetworkHostAlarmStatus OBJECT-TYPE
	  SYNTAX EkiOnOff
	  MAX-ACCESS read-only
	  STATUS current
	  DESCRIPTION
        "
        Line Trscv Network/Host Alarm
         Status :This OID indicates the
        state of the Network and Host interface
        of the Line Trscv <Help> Synthesis
        alarm indicating the alarm state
        of the Network and Host interface
        of the Line Trscv <Condtype> MSA_NETWORK_HOST_ALARM_STATUS
        <Probcause> informationalStatus(1000)
        <Alarmtype> other (1) <Polarity>
        (2)
        "
	  ::= { pm10010mpAlmmsaGlobalAlarmSummary 6 }



pm10010mpAlmMsaSoftGlobAlarmTest  OBJECT-TYPE
	  SYNTAX EkiOnOff
	  MAX-ACCESS read-only
	  STATUS current
	  DESCRIPTION
        "
        Line Trscv Global Alarm SW Test
        :This OID indicates the Line Trscv
        Global alarm This OID is raised
        by SW request for test purpose
         <Help> Status indicating the Line
        Trscv Global Alarm is raised by
        SW request for test purpose <Condtype>
        MSA_SOFT_GLOB_ALARM_TEST  <Probcause>
        informationalStatus(1000) <Alarmtype>
        other (1) <Polarity> (2)
        "
	  ::= { pm10010mpAlmmsaGlobalAlarmSummary 1 }



--- *****************************************************
---     LEAF for the msaNetworkTxAlignment article
--- *****************************************************
pm10010mpAlmmsaNetworkTxAlignment OBJECT IDENTIFIER ::= { pm10010mpAlmOtherCrit 49 }




pm10010mpAlmNetTxLossOfAlignment OBJECT-TYPE
	  SYNTAX EkiOnOff
	  MAX-ACCESS read-only
	  STATUS current
	  DESCRIPTION
        "
        Line Trscv Network Tx Loss Of
         Alignment :This OID indicates
         a Tx Loss of Alignment is detected
        on the Line Trscv Network interface
        <Help> Alarm indicating a Tx Loss
        of Alignment is detected on the
        Line Trscv Network interface <Condtype>
        NET_TX_LOSS_OF_ALIGNMENT <Probcause>
        transmitterFailure (56) <Alarmtype>
        equipmentAlarm (5) <Polarity> (2)
        "
	  ::= { pm10010mpAlmmsaNetworkTxAlignment 16 }



pm10010mpAlmNetTxOutOfAlignment OBJECT-TYPE
	  SYNTAX EkiOnOff
	  MAX-ACCESS read-only
	  STATUS current
	  DESCRIPTION
        "
        Line Trscv Network Tx Out Of Alignment
        :This OID indicates a Tx Out of
        Alignment is detected on the Line
        Trscv Network interface <Help>
         Alarm indicating a Tx Out of Alignment
        is detected on the Line Trscv Network
        interface <Condtype> NET_TX_OUT_OF_ALIGNMENT
        <Probcause> transmitterFailure
         (56) <Alarmtype> equipmentAlarm
        (5) <Polarity> (2)
        "
	  ::= { pm10010mpAlmmsaNetworkTxAlignment 15 }



pm10010mpAlmNetTxCmuLockFault OBJECT-TYPE
	  SYNTAX EkiOnOff
	  MAX-ACCESS read-only
	  STATUS current
	  DESCRIPTION
        "
        Line Trscv Network Tx CMU Lock
        Fault :This OID indicates a Tx
         Clock Multiplier Unit Lock Fault
        is detected on the Line Trscv Network
        interface <Help> Alarm indicating
        a Tx Clock Multiplier Unit Lock
        Fault is detected on the Line Trscv
        Network interface <Condtype> NET_TX_CMU_LOCK_FAULT
        <Probcause> transmitterFailure
         (56) <Alarmtype> equipmentAlarm
        (5) <Polarity> (2)
        "
	  ::= { pm10010mpAlmmsaNetworkTxAlignment 14 }



pm10010mpAlmNetTxReferenceClockFault OBJECT-TYPE
	  SYNTAX EkiOnOff
	  MAX-ACCESS read-only
	  STATUS current
	  DESCRIPTION
        "
        Line Trscv Network Tx Ref Clock
        Fault :This OID indicates a Tx
         Reference Clock Fault is detected
        on the Line Trscv Network interface
        <Help> Alarm indicating a Tx Reference
        Clock Fault is detected on the
         Line Trscv Network interface <Condtype>
        NET_TX_REFERENCE_CLOCK_FAULT <Probcause>
        transmitterFailure (56) <Alarmtype>
        equipmentAlarm (5) <Polarity> (2)
        "
	  ::= { pm10010mpAlmmsaNetworkTxAlignment 13 }



pm10010mpAlmNetTxTimingFault OBJECT-TYPE
	  SYNTAX EkiOnOff
	  MAX-ACCESS read-only
	  STATUS current
	  DESCRIPTION
        "
        Line Trscv Network Tx Timing Fault
        :This OID indicates a Tx Timing
        Fault is detected on the Line Trscv
        Network interface <Help> Alarm
         indicating a Tx Timing Fault is
        detected on the Line Trscv Network
        interface <Condtype> NET_TX_TIMING_FAULT
        <Probcause> transmitterFailure
         (56) <Alarmtype> equipmentAlarm
        (5) <Polarity> (2)
        "
	  ::= { pm10010mpAlmmsaNetworkTxAlignment 12 }



--- *****************************************************
---     LEAF for the msaNetworkRxAlignment article
--- *****************************************************
pm10010mpAlmmsaNetworkRxAlignment OBJECT IDENTIFIER ::= { pm10010mpAlmOtherCrit 50 }




pm10010mpAlmNetRxModemSyncDetectFault OBJECT-TYPE
	  SYNTAX EkiOnOff
	  MAX-ACCESS read-only
	  STATUS current
	  DESCRIPTION
        "
        Line Trscv Network Rx Modem Sync
        Detect Fault :This OID indicates
        a Rx Modem Synchronisation Detection
        Fault is detected on the Line Trscv
        Network interface <Help> Alarm
         indicating a Rx Modem Synchronisation
        Detection Fault is detected on
         the Line Trscv Network interface
        <Condtype> NET_RX_MODEM_SYNC_DETECT_FAULT
        <Probcause> receiverFailure (42)
        <Alarmtype> equipmentAlarm (5)
         <Polarity> (2)
        "
	  ::= { pm10010mpAlmmsaNetworkRxAlignment 16 }



pm10010mpAlmNetRxModemLockFault OBJECT-TYPE
	  SYNTAX EkiOnOff
	  MAX-ACCESS read-only
	  STATUS current
	  DESCRIPTION
        "
        Line Trscv Network Rx Modem Lock
        Fault :This OID indicates a Rx
         Modem Lock Fault is detected on
        the Line Trscv Network interface
        <Help> Alarm indicating a Rx Modem
        Lock Fault is detected on the Line
        Trscv Network interface <Condtype>
        NET_RX_MODEM_LOCK_FAULT <Probcause>
        receiverFailure (42) <Alarmtype>
        equipmentAlarm (5) <Polarity> (2)
        "
	  ::= { pm10010mpAlmmsaNetworkRxAlignment 15 }



pm10010mpAlmNetRxLossOfAlignment OBJECT-TYPE
	  SYNTAX EkiOnOff
	  MAX-ACCESS read-only
	  STATUS current
	  DESCRIPTION
        "
        Line Trscv Network Rx Loss Of
         Alignment :This OID indicates
         a Rx Loss of Alignment is detected
        on the Line Trscv Network interface
        <Help> Alarm indicating a Rx Loss
        of Alignment is detected on the
        Line Trscv Network interface <Condtype>
        NET_RX_LOSS_OF_ALIGNMENT <Probcause>
        receiverFailure (42) <Alarmtype>
        equipmentAlarm (5) <Polarity> (2)
        "
	  ::= { pm10010mpAlmmsaNetworkRxAlignment 14 }



pm10010mpAlmNetRxOutOfAlignment OBJECT-TYPE
	  SYNTAX EkiOnOff
	  MAX-ACCESS read-only
	  STATUS current
	  DESCRIPTION
        "
        Line Trscv Network Rx Out Of Alignment
        :This OID indicates a Rx Out of
        Alignment is detected on the Line
        Trscv Network interface <Help>
         Alarm indicating a Rx Out of Alignment
        is detected on the Line Trscv Network
        interface <Condtype> NET_RX_OUT_OF_ALIGNMENT
        <Probcause> receiverFailure (42)
        <Alarmtype> equipmentAlarm (5)
         <Polarity> (2)
        "
	  ::= { pm10010mpAlmmsaNetworkRxAlignment 13 }



pm10010mpAlmNetRxTimingFault OBJECT-TYPE
	  SYNTAX EkiOnOff
	  MAX-ACCESS read-only
	  STATUS current
	  DESCRIPTION
        "
        Line Trscv Network Rx Timing Fault
        :This OID indicates a Rx Timing
        Fault is detected on the Line Trscv
        Network interface <Help> Alarm
         indicating a Rx Timing Fault is
        detected on the Line Trscv Network
        interface <Condtype> NET_RX_TIMING_FAULT
        <Probcause> receiverFailure (42)
        <Alarmtype> equipmentAlarm (5)
         <Polarity> (2)
        "
	  ::= { pm10010mpAlmmsaNetworkRxAlignment 12 }



--- *****************************************************
---     LEAF for the msaNetworkHostNetworkAlarmSummary article
--- *****************************************************
pm10010mpAlmmsaNetworkHostNetworkAlarmSummary OBJECT IDENTIFIER ::= { pm10010mpAlmOtherCrit 51 }




pm10010mpAlmHostTxOtnStatus OBJECT-TYPE
	  SYNTAX EkiOnOff
	  MAX-ACCESS read-only
	  STATUS current
	  DESCRIPTION
        "
        Line Trscv Host Tx OTN :This OID
        indicates a Tx OTN Fault is detected
        on the Line Trscv Host interface
        <Help> Synthesis Alarm indicating
        a Tx OTN Fault is detected on the
        Line Trscv Host interface <Condtype>
        HOST_TX_OTN_STATUS <Probcause>
         informationalStatus(1000) <Alarmtype>
        other (1) <Polarity> (2)
        "
	  ::= { pm10010mpAlmmsaNetworkHostNetworkAlarmSummary 16 }



pm10010mpAlmHostTxAlignment OBJECT-TYPE
	  SYNTAX EkiOnOff
	  MAX-ACCESS read-only
	  STATUS current
	  DESCRIPTION
        "
        Line Trscv Host Tx Alignment :This
        OID indicates a Tx Alignment Fault
        is detected on the Line Trscv Host
        interface <Help> Synthesis Alarm
        indicating a Tx Alignment Fault
        is detected on the Line Trscv Host
        interface <Condtype> HOST_TX_ALIGNMENT
        <Probcause> informationalStatus(1000)
        <Alarmtype> other (1) <Polarity>
        (2)
        "
	  ::= { pm10010mpAlmmsaNetworkHostNetworkAlarmSummary 15 }



pm10010mpAlmHostRxAlignment OBJECT-TYPE
	  SYNTAX EkiOnOff
	  MAX-ACCESS read-only
	  STATUS current
	  DESCRIPTION
        "
        Line Trscv Host Rx Alignment :This
        OID indicates a Rx Alignment Fault
        is detected on the Line Trscv Host
        interface <Help> Synthesis Alarm
        indicating a Rx Alignment Fault
        is detected on the Line Trscv Host
        interface <Condtype> HOST_RX_ALIGNMENT
        <Probcause> informationalStatus(1000)
        <Alarmtype> other (1) <Polarity>
        (2)
        "
	  ::= { pm10010mpAlmmsaNetworkHostNetworkAlarmSummary 14 }



pm10010mpAlmNetworkRxOtn OBJECT-TYPE
	  SYNTAX EkiOnOff
	  MAX-ACCESS read-only
	  STATUS current
	  DESCRIPTION
        "
        Line Trscv Network Rx OTN :This
        OID indicates a Rx OTN Fault is
        detected on the Line Trscv Network
        interface <Help> Synthesis Alarm
        indicating a Rx OTN Fault is detected
        on the Line Trscv Network interface
        <Condtype> NETWORK_RX_OTN <Probcause>
        informationalStatus(1000) <Alarmtype>
        other (1) <Polarity> (2)
        "
	  ::= { pm10010mpAlmmsaNetworkHostNetworkAlarmSummary 13 }



pm10010mpAlmNetworkRxAlignment OBJECT-TYPE
	  SYNTAX EkiOnOff
	  MAX-ACCESS read-only
	  STATUS current
	  DESCRIPTION
        "
        Line Trscv Network Rx Alignment
        :This OID indicates a Rx Alignment
        Fault is detected on the Line Trscv
        Network interface <Help> Synthesis
        Alarm indicating a Rx Alignment
        Fault is detected on the Line Trscv
        Network interface <Condtype> NETWORK_RX_ALIGNMENT
        <Probcause> informationalStatus(1000)
        <Alarmtype> other (1) <Polarity>
        (2)
        "
	  ::= { pm10010mpAlmmsaNetworkHostNetworkAlarmSummary 12 }



pm10010mpAlmNetworkTxAlignment OBJECT-TYPE
	  SYNTAX EkiOnOff
	  MAX-ACCESS read-only
	  STATUS current
	  DESCRIPTION
        "
        Line Trscv Network Tx Alignment
        :This OID indicates a Tx Alignment
        Fault is detected on the Line Trscv
        Network interface <Help> Synthesis
        Alarm indicating a Tx Alignment
        Fault is detected on the Line Trscv
        Network interface <Condtype> NETWORK_TX_ALIGNMENT
        <Probcause> informationalStatus(1000)
        <Alarmtype> other (1) <Polarity>
        (2)
        "
	  ::= { pm10010mpAlmmsaNetworkHostNetworkAlarmSummary 11 }



--- *****************************************************
---     LEAF for the msaHostTxAlignment article
--- *****************************************************
pm10010mpAlmmsaHostTxAlignment OBJECT IDENTIFIER ::= { pm10010mpAlmOtherCrit 52 }




pm10010mpAlmHostTxCdrLockFault OBJECT-TYPE
	  SYNTAX EkiOnOff
	  MAX-ACCESS read-only
	  STATUS current
	  DESCRIPTION
        "
        Line Trscv Host Tx CDR Lock Fault
        :This OID indicates a Tx Clock
         Data Recovery Lock Fault is detected
        on the Line Trscv Host interface
        <Help> Alarm indicating a Tx Clock
        Data Recovery Lock Fault is detected
        on the Line Trscv Host interface
        <Condtype> HOST_TX_CDR_LOCK_FAULT
        <Probcause> receiverFailure (42)
        <Alarmtype> equipmentAlarm (5)
         <Polarity> (2)
        "
	  ::= { pm10010mpAlmmsaHostTxAlignment 16 }



pm10010mpAlmHostTxLossOfAlignment OBJECT-TYPE
	  SYNTAX EkiOnOff
	  MAX-ACCESS read-only
	  STATUS current
	  DESCRIPTION
        "
        Line Trscv Host Tx Loss Of Alignment
        :This OID indicates a Tx Loss of
        Alignment is detected on the Line
        Trscv Host interface <Help> Alarm
        indicating a Tx Loss of Alignment
        is detected on the Line Trscv Host
        interface <Condtype> HOST_TX_LOSS_OF_ALIGNMENT
        <Probcause> receiverFailure (42)
        <Alarmtype> equipmentAlarm (5)
         <Polarity> (2)
        "
	  ::= { pm10010mpAlmmsaHostTxAlignment 15 }



pm10010mpAlmHostTxOutOfAlignment OBJECT-TYPE
	  SYNTAX EkiOnOff
	  MAX-ACCESS read-only
	  STATUS current
	  DESCRIPTION
        "
        Line Trscv Host Tx Out Of Alignment
        :This OID indicates a Tx Out of
        Alignment is detected on the Line
        Trscv Host interface <Help> Alarm
        indicating a Tx Out of Alignment
        is detected on the Line Trscv Host
        interface <Condtype> HOST_TX_OUT_OF_ALIGNMENT
        <Probcause> receiverFailure (42)
        <Alarmtype> equipmentAlarm (5)
         <Polarity> (2)
        "
	  ::= { pm10010mpAlmmsaHostTxAlignment 14 }



pm10010mpAlmHostTxDeskewLockFault OBJECT-TYPE
	  SYNTAX EkiOnOff
	  MAX-ACCESS read-only
	  STATUS current
	  DESCRIPTION
        "
        Line Trscv Host Tx Deskew Lock
        Fault :This OID indicates a Tx
         Deskew Lock Fault is detected
         on  the Line Trscv Host interface
        <Help> Alarm indicating a Tx Deskew
        Lock Fault is detected on  the
         Line Trscv Host interface <Condtype>
        HOST_TX_DESKEW_LOCK_FAULT <Probcause>
        receiverFailure (42) <Alarmtype>
        equipmentAlarm (5) <Polarity> (2)
        "
	  ::= { pm10010mpAlmmsaHostTxAlignment 13 }



--- *****************************************************
---     LEAF for the msaHostRxAlignment article
--- *****************************************************
pm10010mpAlmmsaHostRxAlignment OBJECT IDENTIFIER ::= { pm10010mpAlmOtherCrit 53 }




pm10010mpAlmHostRxLossOfAlignment OBJECT-TYPE
	  SYNTAX EkiOnOff
	  MAX-ACCESS read-only
	  STATUS current
	  DESCRIPTION
        "
        Line Trscv Host Rx Loss Of Alignment
        :This OID indicates a Rx Loss of
        Alignment is detected on the Line
        Trscv Host interface <Help> Alarm
        indicating a Rx Loss of Alignment
        is detected on the Line Trscv Host
        interface <Condtype> HOST_RX_LOSS_OF_ALIGNMENT
        <Probcause> transmitterFailure
         (56) <Alarmtype> equipmentAlarm
        (5) <Polarity> (2)
        "
	  ::= { pm10010mpAlmmsaHostRxAlignment 16 }



pm10010mpAlmHostRxOutOfAlignment OBJECT-TYPE
	  SYNTAX EkiOnOff
	  MAX-ACCESS read-only
	  STATUS current
	  DESCRIPTION
        "
        Line Trscv Host Rx Out Of Alignment
        :This OID indicates a Rx Out of
        Alignment is detected on the Line
        Trscv Host interface <Help> Alarm
        indicating a Rx Out of Alignment
        is detected on the Line Trscv Host
        interface <Condtype> HOST_RX_OUT_OF_ALIGNMENT
        <Probcause> transmitterFailure
         (56) <Alarmtype> equipmentAlarm
        (5) <Polarity> (2)
        "
	  ::= { pm10010mpAlmmsaHostRxAlignment 15 }



pm10010mpAlmHostRxCmuLockFault OBJECT-TYPE
	  SYNTAX EkiOnOff
	  MAX-ACCESS read-only
	  STATUS current
	  DESCRIPTION
        "
        Line Trscv Host Rx CMU Lock Fault
        :This OID indicates a Rx Clock
         Multiplier Unit Lock Fault is
         detected on the Line Trscv Host
        interface <Help> Alarm indicating
        a Rx Clock Multiplier Unit Lock
        Fault is detected on the Line Trscv
        Host interface <Condtype> HOST_RX_CMU_LOCK_FAULT
        <Probcause> transmitterFailure
         (56) <Alarmtype> equipmentAlarm
        (5) <Polarity> (2)
        "
	  ::= { pm10010mpAlmmsaHostRxAlignment 14 }



--- *********************************************************
---     TABLE for the pm10010mpAlmclientNetworkLaneAlarmWarning articles
--- *********************************************************

pm10010mpAlmclientNetworkLaneAlarmWarningTable OBJECT-TYPE
	SYNTAX  SEQUENCE OF Pm10010mpAlmclientNetworkLaneAlarmWarningEntry
	MAX-ACCESS not-accessible
	STATUS current
	DESCRIPTION
        "
        List of pm10010mpAlmclientNetworkLaneAlarmWarning
        Article
        "
	::= { pm10010mpAlmClientNurg 56 }


pm10010mpAlmclientNetworkLaneAlarmWarningEntry OBJECT-TYPE
	SYNTAX Pm10010mpAlmclientNetworkLaneAlarmWarningEntry
	MAX-ACCESS not-accessible
	STATUS current
	DESCRIPTION
        "
        Row definition for the pm10010mpAlmclientNetworkLaneAlarmWarning
        table
        "
	INDEX   { pm10010mpAlmclientNetworkLaneAlarmWarningIndex }
	::= { pm10010mpAlmclientNetworkLaneAlarmWarningTable 1 }


Pm10010mpAlmclientNetworkLaneAlarmWarningEntry ::=
	SEQUENCE {
	pm10010mpAlmclientNetworkLaneAlarmWarningIndex
		INTEGER,
	pm10010mpAlmClientBiasHighAlarmPortn
		EkiOnOff,
	pm10010mpAlmClientBiasHighWarningPortn
		EkiOnOff,
	pm10010mpAlmClientBiasLowWarningPortn
		EkiOnOff,
	pm10010mpAlmClientBiasLowAlarmPortn
		EkiOnOff,
	pm10010mpAlmClientTxPowerHighAlarmPortn
		EkiOnOff,
	pm10010mpAlmClientTxPowerHighWarningPortn
		EkiOnOff,
	pm10010mpAlmClientTxPowerLowWarningPortn
		EkiOnOff,
	pm10010mpAlmClientTxPowerLowAlarmPortn
		EkiOnOff,
	pm10010mpAlmClientLaserTempHighAlarmPortn
		EkiOnOff,
	pm10010mpAlmClientLaserTempHighWarningPortn
		EkiOnOff,
	pm10010mpAlmClientLaserTempLowWarningPortn
		EkiOnOff,
	pm10010mpAlmLaserTempLowAlarmPortn
		EkiOnOff,
	pm10010mpAlmClientRxPowerHighAlarmPortn
		EkiOnOff,
	pm10010mpAlmClientRxPowerHighWarningPortn
		EkiOnOff,
	pm10010mpAlmClientRxPowerLowWarningPortn
		EkiOnOff,
	pm10010mpAlmClientRxPowerLowAlarmPortn
		EkiOnOff
	}


pm10010mpAlmclientNetworkLaneAlarmWarningIndex OBJECT-TYPE
	SYNTAX  INTEGER(0..128)
	MAX-ACCESS  read-only
	STATUS current
	DESCRIPTION
        "
        Index definition for the pm10010mpAlmclientNetworkLaneAlarmWarning
        table
        "
	::= { pm10010mpAlmclientNetworkLaneAlarmWarningEntry 1 }


pm10010mpAlmClientBiasHighAlarmPortn OBJECT-TYPE
	SYNTAX  EkiOnOff
	MAX-ACCESS read-only
	STATUS current
	DESCRIPTION
        "
        Client Trscv Bias High Alarm :This
        OID indicates that the Trscv laser
        bias current is higher than the
        threshold value written in the
         Trscv EEPROM <Help> Alarm indicating
        that the Trscv laser bias current
        is higher than the threshold value
        written in the Trscv EEPROM <Condtype>
        CLIENT_BIAS_HIGH_ALARM <Probcause>
        transmitterFailure (56) <Alarmtype>
        equipmentAlarm (5) <Polarity> (2)
        "
	::= { pm10010mpAlmclientNetworkLaneAlarmWarningEntry 17 }


pm10010mpAlmClientBiasHighWarningPortn OBJECT-TYPE
	SYNTAX  EkiOnOff
	MAX-ACCESS read-only
	STATUS current
	DESCRIPTION
        "
        Client Trscv Bias High Warning
        :This OID indicates that the Trscv
        laser bias current is higher than
        the threshold value written in
         the Trscv EEPROM <Help> Warning
        indicating that the Trscv laser
        bias current is higher than the
        threshold value written in the
         Trscv EEPROM <Condtype> CLIENT_BIAS_HIGH_WARNING
        <Probcause> transmitterFailure
         (56) <Alarmtype> equipmentAlarm
        (5) <Polarity> (2)
        "
	::= { pm10010mpAlmclientNetworkLaneAlarmWarningEntry 16 }


pm10010mpAlmClientBiasLowWarningPortn OBJECT-TYPE
	SYNTAX  EkiOnOff
	MAX-ACCESS read-only
	STATUS current
	DESCRIPTION
        "
        Client Trscv Bias Low Warning
         :This OID indicates that the Trscv
        laser bias current is lower than
        the threshold value written in
         the Trscv EEPROM <Help> Warning
        indicating that the Trscv laser
        bias current is lower than the
         threshold value written in the
        Trscv EEPROM <Condtype> CLIENT_BIAS_LOW_WARNING
        <Probcause> transmitterFailure
         (56) <Alarmtype> equipmentAlarm
        (5) <Polarity> (2)
        "
	::= { pm10010mpAlmclientNetworkLaneAlarmWarningEntry 15 }


pm10010mpAlmClientBiasLowAlarmPortn OBJECT-TYPE
	SYNTAX  EkiOnOff
	MAX-ACCESS read-only
	STATUS current
	DESCRIPTION
        "
        Client Trscv Bias Low Alarm :This
        OID indicates that the Trscv laser
        bias current is lower than the
         threshold value written in the
        Trscv EEPROM <Help> Alarm indicating
        that the Trscv laser bias current
        is lower than the threshold value
        written in the Trscv EEPROM <Condtype>
        CLIENT_BIAS_LOW_ALARM <Probcause>
        transmitterFailure (56) <Alarmtype>
        equipmentAlarm (5) <Polarity> (2)
        "
	::= { pm10010mpAlmclientNetworkLaneAlarmWarningEntry 14 }


pm10010mpAlmClientTxPowerHighAlarmPortn OBJECT-TYPE
	SYNTAX  EkiOnOff
	MAX-ACCESS read-only
	STATUS current
	DESCRIPTION
        "
        Client Trscv Tx Power High Alarm
        :This OID indicates that the Trscv
        output power is higher than the
        threshold value written in the
         Trscv EEPROM <Help> Alarm indicating
        that the Trscv output power is
         higher than the threshold value
        written in the Trscv EEPROM <Condtype>
        CLIENT_TX_POWER_HIGH_ALARM <Probcause>
        transmitterFailure (56) <Alarmtype>
        equipmentAlarm (5) <Polarity> (2)
        "
	::= { pm10010mpAlmclientNetworkLaneAlarmWarningEntry 13 }


pm10010mpAlmClientTxPowerHighWarningPortn OBJECT-TYPE
	SYNTAX  EkiOnOff
	MAX-ACCESS read-only
	STATUS current
	DESCRIPTION
        "
        Client Trscv Tx Power High Warning
        :This OID indicates that the Trscv
        output power is higher than the
        threshold value written in the
         Trscv EEPROM <Help> Warning indicating
        that the Trscv output power is
         higher than the threshold value
        written in the Trscv EEPROM <Condtype>
        CLIENT_TX_POWER_HIGH_WARNING <Probcause>
        transmitterFailure (56) <Alarmtype>
        equipmentAlarm (5) <Polarity> (2)
        "
	::= { pm10010mpAlmclientNetworkLaneAlarmWarningEntry 12 }


pm10010mpAlmClientTxPowerLowWarningPortn OBJECT-TYPE
	SYNTAX  EkiOnOff
	MAX-ACCESS read-only
	STATUS current
	DESCRIPTION
        "
        Client Trscv Tx Power Low Warning
        :This OID indicates that the Trscv
        output power is lower than the
         threshold value written in the
        Trscv EEPROM <Help> Warning indicating
        that the Trscv output power is
         lower than the threshold value
        written in the Trscv EEPROM <Condtype>
        CLIENT_TX_POWER_LOW_WARNING <Probcause>
        transmitterFailure (56) <Alarmtype>
        equipmentAlarm (5) <Polarity> (2)
        "
	::= { pm10010mpAlmclientNetworkLaneAlarmWarningEntry 11 }


pm10010mpAlmClientTxPowerLowAlarmPortn OBJECT-TYPE
	SYNTAX  EkiOnOff
	MAX-ACCESS read-only
	STATUS current
	DESCRIPTION
        "
        Client Trscv Tx Power Low Alarm
        :This OID indicates that the Trscv
        output power is lower than the
         threshold value written in the
        Trscv EEPROM <Help> Alarm indicating
        that the Trscv output power is
         lower than the threshold value
        written in the Trscv EEPROM <Condtype>
        CLIENT_TX_POWER_LOW_ALARM <Probcause>
        transmitterFailure (56) <Alarmtype>
        equipmentAlarm (5) <Polarity> (2)
        "
	::= { pm10010mpAlmclientNetworkLaneAlarmWarningEntry 10 }


pm10010mpAlmClientLaserTempHighAlarmPortn OBJECT-TYPE
	SYNTAX  EkiOnOff
	MAX-ACCESS read-only
	STATUS current
	DESCRIPTION
        "
        Client Trscv Laser Temp High Alarm
        :This OID indicates that the Trscv
        Laser Temperature is higher than
        the threshold value written in
         the Trscv EEPROM <Help> Alarm
         indicating that the Trscv Laser
        Temperature is higher than the
         threshold value written in the
        Trscv EEPROM <Condtype> CLIENT_LASER_TEMP_HIGH_ALARM
        <Probcause> temperatureUnacceptable
        (51) <Alarmtype> equipmentAlarm
        (5) <Polarity> (2)
        "
	::= { pm10010mpAlmclientNetworkLaneAlarmWarningEntry 9 }


pm10010mpAlmClientLaserTempHighWarningPortn OBJECT-TYPE
	SYNTAX  EkiOnOff
	MAX-ACCESS read-only
	STATUS current
	DESCRIPTION
        "
        Client Trscv Laser Temp High Warning
        :This OID indicates that the Trscv
        Laser Temperature is higher than
        the threshold value written in
         the Trscv EEPROM <Help> Warning
        indicating that the Trscv Laser
        Temperature is higher than the
         threshold value written in the
        Trscv EEPROM <Condtype> CLIENT_LASER_TEMP_HIGH_WARNING
        <Probcause> temperatureUnacceptable
        (51) <Alarmtype> equipmentAlarm
        (5) <Polarity> (2)
        "
	::= { pm10010mpAlmclientNetworkLaneAlarmWarningEntry 8 }


pm10010mpAlmClientLaserTempLowWarningPortn OBJECT-TYPE
	SYNTAX  EkiOnOff
	MAX-ACCESS read-only
	STATUS current
	DESCRIPTION
        "
        Client Trscv Laser Temp Low Warning
        :This OID indicates that the Trscv
        Laser Temperature is lower than
        the threshold value written in
         the Trscv EEPROM <Help> Warning
        indicating that the Trscv Laser
        Temperature is lower than the threshold
        value written in the Trscv EEPROM
        <Condtype> CLIENT_LASER_TEMP_LOW_WARNING
        <Probcause> temperatureUnacceptable
        (51) <Alarmtype> equipmentAlarm
        (5) <Polarity> (2)
        "
	::= { pm10010mpAlmclientNetworkLaneAlarmWarningEntry 7 }


pm10010mpAlmLaserTempLowAlarmPortn OBJECT-TYPE
	SYNTAX  EkiOnOff
	MAX-ACCESS read-only
	STATUS current
	DESCRIPTION
        "
        Client Trscv Laser Temp Low Alarm
        :This OID indicates that the Trscv
        Laser Temperature is lower than
        the threshold value written in
         the Trscv EEPROM <Help> Alarm
         indicating that the Trscv Laser
        Temperature is lower than the threshold
        value written in the Trscv EEPROM
        <Condtype> LASER_TEMP_LOW_ALARM
        <Probcause> temperatureUnacceptable
        (51) <Alarmtype> equipmentAlarm
        (5) <Polarity> (2)
        "
	::= { pm10010mpAlmclientNetworkLaneAlarmWarningEntry 6 }


pm10010mpAlmClientRxPowerHighAlarmPortn OBJECT-TYPE
	SYNTAX  EkiOnOff
	MAX-ACCESS read-only
	STATUS current
	DESCRIPTION
        "
        Client Trscv Rx Power High Alarm
        :This OID indicates that the Trscv
        input power is higher than the
         threshold value written in the
        Trscv EEPROM <Help> Alarm indicating
        that the Trscv input power is higher
        than the threshold value written
        in the Trscv EEPROM <Condtype>
         CLIENT_RX_POWER_HIGH_ALARM <Probcause>
        receiveFailure (41) <Alarmtype>
        equipmentAlarm (5) <Polarity> (2)
        "
	::= { pm10010mpAlmclientNetworkLaneAlarmWarningEntry 5 }


pm10010mpAlmClientRxPowerHighWarningPortn OBJECT-TYPE
	SYNTAX  EkiOnOff
	MAX-ACCESS read-only
	STATUS current
	DESCRIPTION
        "
        Client Trscv Rx Power High Warning
        :This OID indicates that the Trscv
        input power is higher than the
         threshold value written in the
        Trscv EEPROM <Help> Warning indicating
        that the Trscv input power is higher
        than the threshold value written
        in the Trscv EEPROM <Condtype>
         CLIENT_RX_POWER_HIGH_WARNING <Probcause>
        receiveFailure (41) <Alarmtype>
        equipmentAlarm (5) <Polarity> (2)
        "
	::= { pm10010mpAlmclientNetworkLaneAlarmWarningEntry 4 }


pm10010mpAlmClientRxPowerLowWarningPortn OBJECT-TYPE
	SYNTAX  EkiOnOff
	MAX-ACCESS read-only
	STATUS current
	DESCRIPTION
        "
        Client Trscv Rx Power Low Warning
        :This OID indicates that the Trscv
        input power is lower than the threshold
        value written in the Trscv EEPROM
        <Help> Warning indicating that
         the Trscv input power is lower
        than the threshold value written
        in the Trscv EEPROM <Condtype>
         CLIENT_RX_POWER_LOW_WARNING <Probcause>
        receiveFailure (41) <Alarmtype>
        equipmentAlarm (5) <Polarity> (2)
        "
	::= { pm10010mpAlmclientNetworkLaneAlarmWarningEntry 3 }


pm10010mpAlmClientRxPowerLowAlarmPortn OBJECT-TYPE
	SYNTAX  EkiOnOff
	MAX-ACCESS read-only
	STATUS current
	DESCRIPTION
        "
        Client Trscv Rx Power Low Alarm
        :This OID indicates that the Trscv
        input power is lower than the threshold
        value written in the Trscv EEPROM
        <Help> Alarm indicating that the
        Trscv input power is lower than
        the threshold value written in
         the Trscv EEPROM <Condtype> CLIENT_RX_POWER_LOW_ALARM
        <Probcause> receiveFailure (41)
        <Alarmtype> equipmentAlarm (5)
         <Polarity> (2)
        "
	::= { pm10010mpAlmclientNetworkLaneAlarmWarningEntry 2 }


--- *********************************************************
---     TABLE for the pm10010mpAlmclientNetworkLaneFault articles
--- *********************************************************

pm10010mpAlmclientNetworkLaneFaultTable OBJECT-TYPE
	SYNTAX  SEQUENCE OF Pm10010mpAlmclientNetworkLaneFaultEntry
	MAX-ACCESS not-accessible
	STATUS current
	DESCRIPTION
        "
        List of pm10010mpAlmclientNetworkLaneFault
        Article
        "
	::= { pm10010mpAlmClientUrg 72 }


pm10010mpAlmclientNetworkLaneFaultEntry OBJECT-TYPE
	SYNTAX Pm10010mpAlmclientNetworkLaneFaultEntry
	MAX-ACCESS not-accessible
	STATUS current
	DESCRIPTION
        "
        Row definition for the pm10010mpAlmclientNetworkLaneFault
        table
        "
	INDEX   { pm10010mpAlmclientNetworkLaneFaultIndex }
	::= { pm10010mpAlmclientNetworkLaneFaultTable 1 }


Pm10010mpAlmclientNetworkLaneFaultEntry ::=
	SEQUENCE {
	pm10010mpAlmclientNetworkLaneFaultIndex
		INTEGER,
	pm10010mpAlmClientLaneTecFaultPortn
		EkiOnOff,
	pm10010mpAlmClientLaneWavelengthUnlockedPortn
		EkiOnOff,
	pm10010mpAlmClientLaneApdPowerSupplyPortn
		EkiOnOff,
	pm10010mpAlmClientLaneTxLosfPortn
		EkiOnOff,
	pm10010mpAlmClientLaneTxLolPortn
		EkiOnOff,
	pm10010mpAlmClientLaneRxLosPortn
		EkiOnOff,
	pm10010mpAlmClientLaneRxLolPortn
		EkiOnOff,
	pm10010mpAlmClientLaneRxFifoErrorPortn
		EkiOnOff
	}


pm10010mpAlmclientNetworkLaneFaultIndex OBJECT-TYPE
	SYNTAX  INTEGER(0..128)
	MAX-ACCESS  read-only
	STATUS current
	DESCRIPTION
        "
        Index definition for the pm10010mpAlmclientNetworkLaneFault
        table
        "
	::= { pm10010mpAlmclientNetworkLaneFaultEntry 1 }


pm10010mpAlmClientLaneTecFaultPortn OBJECT-TYPE
	SYNTAX  EkiOnOff
	MAX-ACCESS read-only
	STATUS current
	DESCRIPTION
        "
        Client Network Lane TEC Fault
         :This OID indicates a TEC Fault
        on the Client Trscv Network Lane
        <Help> Alarm indicating a TEC Fault
        on the Client Trscv Network Lane
        <Condtype> CLIENT_LANE_TEC_FAULT
        <Probcause> transmitterFailure
         (56) <Alarmtype> equipmentAlarm
        (5) <Polarity> (2)
        "
	::= { pm10010mpAlmclientNetworkLaneFaultEntry 17 }


pm10010mpAlmClientLaneWavelengthUnlockedPortn OBJECT-TYPE
	SYNTAX  EkiOnOff
	MAX-ACCESS read-only
	STATUS current
	DESCRIPTION
        "
        Client Network Lane Wavelength
        Unlock :This OID indicates a Wavelength
        unlock on the Client Trscv Network
        Lane <Help> Alarm indicating a
         Wavelength unlock on the Client
        Trscv Network Lane <Condtype> CLIENT_LANE_WAVELENGTH_UNLOCKED
        <Probcause> transmitterFailure
         (56) <Alarmtype> equipmentAlarm
        (5) <Polarity> (2)
        "
	::= { pm10010mpAlmclientNetworkLaneFaultEntry 16 }


pm10010mpAlmClientLaneApdPowerSupplyPortn OBJECT-TYPE
	SYNTAX  EkiOnOff
	MAX-ACCESS read-only
	STATUS current
	DESCRIPTION
        "
        Client Network Lane APD Power
         Supply :This OID indicates an
         APD Power supply failure on the
        Client Trscv Network Lane <Help>
        Alarm indicating an APD Power supply
        failure on the Client Trscv Network
        Lane <Condtype> CLIENT_LANE_APD_POWER_SUPPLY
        <Probcause> transmitterFailure
         (56) <Alarmtype> equipmentAlarm
        (5) <Polarity> (2)
        "
	::= { pm10010mpAlmclientNetworkLaneFaultEntry 15 }


pm10010mpAlmClientLaneTxLosfPortn OBJECT-TYPE
	SYNTAX  EkiOnOff
	MAX-ACCESS read-only
	STATUS current
	DESCRIPTION
        "
        Client Network Lane Tx Loss Of
        Signal Functionality :This OID
         indicates a Tx Loss of Signal
         Functionality on the Client Trscv
        Network Lane <Help> Alarm indicating
        a Tx Loss of Signal Functionality
        on the Client Trscv Network Lane
        <Condtype> CLIENT_LANE_TX_LOSF
         <Probcause> transmitterFailure
        (56) <Alarmtype> equipmentAlarm
        (5) <Polarity> (2)
        "
	::= { pm10010mpAlmclientNetworkLaneFaultEntry 9 }


pm10010mpAlmClientLaneTxLolPortn OBJECT-TYPE
	SYNTAX  EkiOnOff
	MAX-ACCESS read-only
	STATUS current
	DESCRIPTION
        "
        Client Network Lane Tx Loss Of
        Lock :This OID indicates a Tx Loss
        of Lock on the Client Trscv Network
        Lane <Help> Alarm indicating a
         Tx Loss of Lock on the Client
         Trscv Network Lane <Condtype>
         CLIENT_LANE_TX_LOL <Probcause>
        transmitterFailure (56) <Alarmtype>
        equipmentAlarm (5) <Polarity> (2)
        "
	::= { pm10010mpAlmclientNetworkLaneFaultEntry 8 }


pm10010mpAlmClientLaneRxLosPortn OBJECT-TYPE
	SYNTAX  EkiOnOff
	MAX-ACCESS read-only
	STATUS current
	DESCRIPTION
        "
        Client Network Lane Rx Loss Of
        Signal :This OID indicates a Rx
        Loss of Signal on the Client Trscv
        Network Lane <Help> Alarm indicating
        a Rx Loss of Signal on the Client
        Trscv Network Lane <Condtype> CLIENT_LANE_RX_LOS
        <Probcause> receiveFailure (41)
        <Alarmtype> physicalViolation (9)
        <Polarity> (2)
        "
	::= { pm10010mpAlmclientNetworkLaneFaultEntry 6 }


pm10010mpAlmClientLaneRxLolPortn OBJECT-TYPE
	SYNTAX  EkiOnOff
	MAX-ACCESS read-only
	STATUS current
	DESCRIPTION
        "
        Client Network Lane Rx Loss Of
        Lock :This OID indicates a Rx Loss
        of Lock on the Client Trscv Network
        Lane <Help> Alarm indicating a
         Rx Loss of Lock on the Client
         Trscv Network Lane <Condtype>
         CLIENT_LANE_RX_LOL <Probcause>
        receiverFailure (42) <Alarmtype>
        equipmentAlarm (5) <Polarity> (2)
        "
	::= { pm10010mpAlmclientNetworkLaneFaultEntry 5 }


pm10010mpAlmClientLaneRxFifoErrorPortn OBJECT-TYPE
	SYNTAX  EkiOnOff
	MAX-ACCESS read-only
	STATUS current
	DESCRIPTION
        "
        Client Network Lane Rx FIFO Error
        :This OID indicates a Rx FIFO Error
        on the Client Trscv Network Lane
        <Help> Alarm indicating a Rx FIFO
        Error on the Client Trscv Network
        Lane <Condtype> CLIENT_LANE_RX_FIFO_ERROR
        <Probcause> receiverFailure (42)
        <Alarmtype> equipmentAlarm (5)
         <Polarity> (2)
        "
	::= { pm10010mpAlmclientNetworkLaneFaultEntry 4 }


--- *********************************************************
---     TABLE for the pm10010mpAlmclientHostLaneFault articles
--- *********************************************************

pm10010mpAlmclientHostLaneFaultTable OBJECT-TYPE
	SYNTAX  SEQUENCE OF Pm10010mpAlmclientHostLaneFaultEntry
	MAX-ACCESS not-accessible
	STATUS current
	DESCRIPTION
        "
        List of pm10010mpAlmclientHostLaneFault
        Article
        "
	::= { pm10010mpAlmClientUrg 88 }


pm10010mpAlmclientHostLaneFaultEntry OBJECT-TYPE
	SYNTAX Pm10010mpAlmclientHostLaneFaultEntry
	MAX-ACCESS not-accessible
	STATUS current
	DESCRIPTION
        "
        Row definition for the pm10010mpAlmclientHostLaneFault
        table
        "
	INDEX   { pm10010mpAlmclientHostLaneFaultIndex }
	::= { pm10010mpAlmclientHostLaneFaultTable 1 }


Pm10010mpAlmclientHostLaneFaultEntry ::=
	SEQUENCE {
	pm10010mpAlmclientHostLaneFaultIndex
		INTEGER,
	pm10010mpAlmClientLaneTxFifoErrorPortn
		EkiOnOff,
	pm10010mpAlmClientTxHostLolPortn
		EkiOnOff,
	pm10010mpAlmClientCsfDetectedPortn
		EkiOnOff,
	pm10010mpAlmClientLanesNotAlignedPortn
		EkiOnOff,
	pm10010mpAlmClientLanes6466UnlockPortn
		EkiOnOff,
	pm10010mpAlmClientLanesMarkerUnlockPortn
		EkiOnOff,
	pm10010mpAlmClientInputLossOfSigPortn
		EkiOnOff,
	pm10010mpAlmClientLossOfSyncPortn
		EkiOnOff
	}


pm10010mpAlmclientHostLaneFaultIndex OBJECT-TYPE
	SYNTAX  INTEGER(0..128)
	MAX-ACCESS  read-only
	STATUS current
	DESCRIPTION
        "
        Index definition for the pm10010mpAlmclientHostLaneFault
        table
        "
	::= { pm10010mpAlmclientHostLaneFaultEntry 1 }


pm10010mpAlmClientLaneTxFifoErrorPortn OBJECT-TYPE
	SYNTAX  EkiOnOff
	MAX-ACCESS read-only
	STATUS current
	DESCRIPTION
        "
        Client Host Lane Tx FIFO Error
        :This OID indicates a Tx FIFO Error
        on the Client Trscv Host Lane <Help>
        Alarm indicating a Tx FIFO Error
        on the Client Trscv Host Lane <Condtype>
        CLIENT_LANE_TX_FIFO_ERROR <Probcause>
        receiverFailure (42) <Alarmtype>
        equipmentAlarm (5) <Polarity> (2)
        "
	::= { pm10010mpAlmclientHostLaneFaultEntry 11 }


pm10010mpAlmClientTxHostLolPortn OBJECT-TYPE
	SYNTAX  EkiOnOff
	MAX-ACCESS read-only
	STATUS current
	DESCRIPTION
        "
        Client Host Lane Tx Loss Of Lock
        :This OID indicates a Tx Loss of
        Lock on the Client Trscv Host Lane
        <Help> Alarm indicating a Tx Loss
        of Lock on the Client Trscv Host
        Lane <Condtype> CLIENT_TX_HOST_LOL
        <Probcause> receiverFailure (42)
        <Alarmtype> equipmentAlarm (5)
         <Polarity> (2)
        "
	::= { pm10010mpAlmclientHostLaneFaultEntry 10 }


pm10010mpAlmClientCsfDetectedPortn OBJECT-TYPE
	SYNTAX  EkiOnOff
	MAX-ACCESS read-only
	STATUS current
	DESCRIPTION
        "
        Client Signal Fail Detected :This
        OID indicates that a CSF has been
        detected on client port in the
         downstream direction   <Help>
          This alarm indicates if a Client
        Signal Fail has been detected in
        the incoming line frame for this
        client port <Condtype> CLIENT_CSF_DETECTED
        <Probcause> receiveFailure (41)
        <Alarmtype> other(1) <Polarity>
        (2)
        "
	::= { pm10010mpAlmclientHostLaneFaultEntry 7 }


pm10010mpAlmClientLanesNotAlignedPortn OBJECT-TYPE
	SYNTAX  EkiOnOff
	MAX-ACCESS read-only
	STATUS current
	DESCRIPTION
        "
        Client Lanes Not Aligned :This
        OID indicates the Client lanes
         are not aligned <Help> Alarm indicating
        the Client lanes are not aligned
        <Condtype> CLIENT_LANES_NOT_ALIGNED
        <Probcause> receiveFailure (41)
        <Alarmtype> integrityViolation
         (7) <Polarity> (2)
        "
	::= { pm10010mpAlmclientHostLaneFaultEntry 6 }


pm10010mpAlmClientLanes6466UnlockPortn OBJECT-TYPE
	SYNTAX  EkiOnOff
	MAX-ACCESS read-only
	STATUS current
	DESCRIPTION
        "
        Client Lanes 64/66b Unlock :This
        OID indicates the Client 64/66b
        decoder is not lock <Help> Alarm
        indicating the Client 64/66b decoder
        is not lock <Condtype> CLIENT_LANES_64_66_UNLOCK
        <Probcause> receiveFailure (41)
        <Alarmtype> integrityViolation
         (7) <Polarity> (2)
        "
	::= { pm10010mpAlmclientHostLaneFaultEntry 5 }


pm10010mpAlmClientLanesMarkerUnlockPortn OBJECT-TYPE
	SYNTAX  EkiOnOff
	MAX-ACCESS read-only
	STATUS current
	DESCRIPTION
        "
        Client Lanes Marker Unlock :This
        OID indicates the Client lanes
         marker alignment is not lock <Help>
        Alarm indicating the Client lanes
        marker alignment is not lock <Condtype>
        CLIENT_LANES_MARKER_UNLOCK <Probcause>
        receiveFailure (41) <Alarmtype>
        integrityViolation (7) <Polarity>
        (2)
        "
	::= { pm10010mpAlmclientHostLaneFaultEntry 4 }


pm10010mpAlmClientInputLossOfSigPortn OBJECT-TYPE
	SYNTAX  EkiOnOff
	MAX-ACCESS read-only
	STATUS current
	DESCRIPTION
        "
        Client Input Loss Of Signal :This
        OID indicates a Loss of Signal
         is detected on the Client Trscv
        <Help> Alarm indicating a Loss
         of Signal is detected on the Client
        Trscv <Condtype> CLIENT_INPUT_LOSS_OF_SIG
        <Probcause> receiveFailure (41)
        <Alarmtype> physicalViolation (9)
        <Polarity> (2)
        "
	::= { pm10010mpAlmclientHostLaneFaultEntry 3 }


pm10010mpAlmClientLossOfSyncPortn OBJECT-TYPE
	SYNTAX  EkiOnOff
	MAX-ACCESS read-only
	STATUS current
	DESCRIPTION
        "
        Client Frame Alignment Loss :This
        OID indicates the module is not
        aligned with the incoming Client
        signal <Help> Alarm indicating
         the module is not aligned with
        the incoming client signal <Condtype>
        CLIENT_LOSS_OF_SYNC <Probcause>
        receiveFailure (41) <Alarmtype>
        integrityViolation (7) <Polarity>
        (2)
        "
	::= { pm10010mpAlmclientHostLaneFaultEntry 2 }


--- *********************************************************
---     TABLE for the pm10010mpAlmlineNetworkLaneAlarmWarning1 articles
--- *********************************************************

pm10010mpAlmlineNetworkLaneAlarmWarning1Table OBJECT-TYPE
	SYNTAX  SEQUENCE OF Pm10010mpAlmlineNetworkLaneAlarmWarning1Entry
	MAX-ACCESS not-accessible
	STATUS current
	DESCRIPTION
        "
        List of pm10010mpAlmlineNetworkLaneAlarmWarning1
        Article
        "
	::= { pm10010mpAlmLineNurg 104 }


pm10010mpAlmlineNetworkLaneAlarmWarning1Entry OBJECT-TYPE
	SYNTAX Pm10010mpAlmlineNetworkLaneAlarmWarning1Entry
	MAX-ACCESS not-accessible
	STATUS current
	DESCRIPTION
        "
        Row definition for the pm10010mpAlmlineNetworkLaneAlarmWarning1
        table
        "
	INDEX   { pm10010mpAlmlineNetworkLaneAlarmWarning1Index }
	::= { pm10010mpAlmlineNetworkLaneAlarmWarning1Table 1 }


Pm10010mpAlmlineNetworkLaneAlarmWarning1Entry ::=
	SEQUENCE {
	pm10010mpAlmlineNetworkLaneAlarmWarning1Index
		INTEGER,
	pm10010mpAlmLineBiasHighAlarmPortn
		EkiOnOff,
	pm10010mpAlmLineBiasHighWarningPortn
		EkiOnOff,
	pm10010mpAlmLineBiasLowWarningPortn
		EkiOnOff,
	pm10010mpAlmLineBiasLowAlarmPortn
		EkiOnOff,
	pm10010mpAlmLineTxPowerHighAlarmPortn
		EkiOnOff,
	pm10010mpAlmLineTxPowerHighWarningPortn
		EkiOnOff,
	pm10010mpAlmLineTxPowerLowWarningPortn
		EkiOnOff,
	pm10010mpAlmLineTxPowerLowAlarmPortn
		EkiOnOff,
	pm10010mpAlmLineLaserTempHighAlarmPortn
		EkiOnOff,
	pm10010mpAlmLineLaserTempHighWarningPortn
		EkiOnOff,
	pm10010mpAlmLineLaserTempLowWarningPortn
		EkiOnOff,
	pm10010mpAlmLineLaserTempLowAlarmPortn
		EkiOnOff,
	pm10010mpAlmLineRxPowerHighAlarmPortn
		EkiOnOff,
	pm10010mpAlmLineRxPowerHighWarningPortn
		EkiOnOff,
	pm10010mpAlmLineRxPowerLowWarningPortn
		EkiOnOff,
	pm10010mpAlmLineRxPowerLowAlarmPortn
		EkiOnOff
	}


pm10010mpAlmlineNetworkLaneAlarmWarning1Index OBJECT-TYPE
	SYNTAX  INTEGER(0..128)
	MAX-ACCESS  read-only
	STATUS current
	DESCRIPTION
        "
        Index definition for the pm10010mpAlmlineNetworkLaneAlarmWarning1
        table
        "
	::= { pm10010mpAlmlineNetworkLaneAlarmWarning1Entry 1 }


pm10010mpAlmLineBiasHighAlarmPortn OBJECT-TYPE
	SYNTAX  EkiOnOff
	MAX-ACCESS read-only
	STATUS current
	DESCRIPTION
        "
        Line Trscv Tx Bias High Alarm
         :This OID indicates that the Trscv
        laser bias current is higher than
        the threshold value written in
         the Trscv EEPROM <Help> Alarm
         indicating that the Trscv laser
        bias current is higher than the
        threshold value written in the
         Trscv EEPROM <Condtype> LINE_BIAS_HIGH_ALARM
        <Probcause> transmitterFailure
         (56) <Alarmtype> equipmentAlarm
        (5) <Polarity> (2)
        "
	::= { pm10010mpAlmlineNetworkLaneAlarmWarning1Entry 17 }


pm10010mpAlmLineBiasHighWarningPortn OBJECT-TYPE
	SYNTAX  EkiOnOff
	MAX-ACCESS read-only
	STATUS current
	DESCRIPTION
        "
        Line Trscv Tx Bias High Warning
        :This OID indicates that the Trscv
        laser bias current is higher than
        the threshold value written in
         the Trscv EEPROM <Help> Warning
        indicating that the Trscv laser
        bias current is higher than the
        threshold value written in the
         Trscv EEPROM <Condtype> LINE_BIAS_HIGH_WARNING
        <Probcause> transmitterFailure
         (56) <Alarmtype> equipmentAlarm
        (5) <Polarity> (2)
        "
	::= { pm10010mpAlmlineNetworkLaneAlarmWarning1Entry 16 }


pm10010mpAlmLineBiasLowWarningPortn OBJECT-TYPE
	SYNTAX  EkiOnOff
	MAX-ACCESS read-only
	STATUS current
	DESCRIPTION
        "
        Line Trscv Tx Bias Low Warning
        :This OID indicates that the Trscv
        laser bias current is lower than
        the threshold value written in
         the Trscv EEPROM <Help> Warning
        indicating that the Trscv laser
        bias current is lower than the
         threshold value written in the
        Trscv EEPROM <Condtype> LINE_BIAS_LOW_WARNING
        <Probcause> transmitterFailure
         (56) <Alarmtype> equipmentAlarm
        (5) <Polarity> (2)
        "
	::= { pm10010mpAlmlineNetworkLaneAlarmWarning1Entry 15 }


pm10010mpAlmLineBiasLowAlarmPortn OBJECT-TYPE
	SYNTAX  EkiOnOff
	MAX-ACCESS read-only
	STATUS current
	DESCRIPTION
        "
        Line Trscv Tx Bias Low Alarm :This
        OID indicates that the Trscv laser
        bias current is lower than the
         threshold value written in the
        Trscv EEPROM <Help> Alarm indicating
        that the Trscv laser bias current
        is lower than the threshold value
        written in the Trscv EEPROM <Condtype>
        LINE_BIAS_LOW_ALARM <Probcause>
        transmitterFailure (56) <Alarmtype>
        equipmentAlarm (5) <Polarity> (2)
        "
	::= { pm10010mpAlmlineNetworkLaneAlarmWarning1Entry 14 }


pm10010mpAlmLineTxPowerHighAlarmPortn OBJECT-TYPE
	SYNTAX  EkiOnOff
	MAX-ACCESS read-only
	STATUS current
	DESCRIPTION
        "
        Line Trscv Tx Power High Alarm
        :This OID indicates that the Trscv
        output power is higher than the
        threshold value written in the
         Trscv EEPROM <Help> Alarm indicating
        that the Trscv output power is
         higher than the threshold value
        written in the Trscv EEPROM <Condtype>
        LINE_TX_POWER_HIGH_ALARM <Probcause>
        transmitterFailure (56) <Alarmtype>
        equipmentAlarm (5) <Polarity> (2)
        "
	::= { pm10010mpAlmlineNetworkLaneAlarmWarning1Entry 13 }


pm10010mpAlmLineTxPowerHighWarningPortn OBJECT-TYPE
	SYNTAX  EkiOnOff
	MAX-ACCESS read-only
	STATUS current
	DESCRIPTION
        "
        Line Trscv Tx Power High Warning
        :This OID indicates that the Trscv
        output power is higher than the
        threshold value written in the
         Trscv EEPROM <Help> Warning indicating
        that the Trscv output power is
         higher than the threshold value
        written in the Trscv EEPROM <Condtype>
        LINE_TX_POWER_HIGH_WARNING <Probcause>
        transmitterFailure (56) <Alarmtype>
        equipmentAlarm (5) <Polarity> (2)
        "
	::= { pm10010mpAlmlineNetworkLaneAlarmWarning1Entry 12 }


pm10010mpAlmLineTxPowerLowWarningPortn OBJECT-TYPE
	SYNTAX  EkiOnOff
	MAX-ACCESS read-only
	STATUS current
	DESCRIPTION
        "
        Line Trscv Tx Power Low Warning
        :This OID indicates that the Trscv
        output power is lower than the
         threshold value written in the
        Trscv EEPROM <Help> Warning indicating
        that the Trscv output power is
         lower than the threshold value
        written in the Trscv EEPROM <Condtype>
        LINE_TX_POWER_LOW_WARNING <Probcause>
        transmitterFailure (56) <Alarmtype>
        equipmentAlarm (5) <Polarity> (2)
        "
	::= { pm10010mpAlmlineNetworkLaneAlarmWarning1Entry 11 }


pm10010mpAlmLineTxPowerLowAlarmPortn OBJECT-TYPE
	SYNTAX  EkiOnOff
	MAX-ACCESS read-only
	STATUS current
	DESCRIPTION
        "
        Line Trscv Tx Power Low Alarm
         :This OID indicates that the Trscv
        output power is lower than the
         threshold value written in the
        Trscv EEPROM <Help> Alarm indicating
        that the Trscv output power is
         lower than the threshold value
        written in the Trscv EEPROM <Condtype>
        LINE_TX_POWER_LOW_ALARM <Probcause>
        transmitterFailure (56) <Alarmtype>
        equipmentAlarm (5) <Polarity> (2)
        "
	::= { pm10010mpAlmlineNetworkLaneAlarmWarning1Entry 10 }


pm10010mpAlmLineLaserTempHighAlarmPortn OBJECT-TYPE
	SYNTAX  EkiOnOff
	MAX-ACCESS read-only
	STATUS current
	DESCRIPTION
        "
        Line Trscv Tx Laser Temp High
         Alarm :This OID indicates that
        the Trscv Tx Laser Temperature
         is higher than the threshold value
        written in the Trscv EEPROM <Help>
        Alarm indicating that the Trscv
        Tx Laser Temperature is higher
         than the threshold value written
        in the Trscv EEPROM <Condtype>
         LINE_LASER_TEMP_HIGH_ALARM <Probcause>
        temperatureUnacceptable (51) <Alarmtype>
        equipmentAlarm (5) <Polarity> (2)
        "
	::= { pm10010mpAlmlineNetworkLaneAlarmWarning1Entry 9 }


pm10010mpAlmLineLaserTempHighWarningPortn OBJECT-TYPE
	SYNTAX  EkiOnOff
	MAX-ACCESS read-only
	STATUS current
	DESCRIPTION
        "
        Line Trscv Tx Laser Temp High
         Warning :This OID indicates that
        the Trscv Tx Laser Temperature
         is higher than the threshold value
        written in the Trscv EEPROM <Help>
        Warning indicating that the Trscv
        Tx Laser Temperature is higher
         than the threshold value written
        in the Trscv EEPROM <Condtype>
         LINE_LASER_TEMP_HIGH_WARNING <Probcause>
        temperatureUnacceptable (51) <Alarmtype>
        equipmentAlarm (5) <Polarity> (2)
        "
	::= { pm10010mpAlmlineNetworkLaneAlarmWarning1Entry 8 }


pm10010mpAlmLineLaserTempLowWarningPortn OBJECT-TYPE
	SYNTAX  EkiOnOff
	MAX-ACCESS read-only
	STATUS current
	DESCRIPTION
        "
        Line Trscv Tx Laser Temp Low Warning
        :This OID indicates that the Trscv
        Tx Laser Temperature is lower than
        the threshold value written in
         the Trscv EEPROM <Help> Warning
        indicating that the Trscv Tx Laser
        Temperature is lower than the threshold
        value written in the Trscv EEPROM
        <Condtype> LINE_LASER_TEMP_LOW_WARNING
        <Probcause> temperatureUnacceptable
        (51) <Alarmtype> equipmentAlarm
        (5) <Polarity> (2)
        "
	::= { pm10010mpAlmlineNetworkLaneAlarmWarning1Entry 7 }


pm10010mpAlmLineLaserTempLowAlarmPortn OBJECT-TYPE
	SYNTAX  EkiOnOff
	MAX-ACCESS read-only
	STATUS current
	DESCRIPTION
        "
        Line Trscv Tx Laser Temp Low Alarm
        :This OID indicates that the Trscv
        Tx Laser Temperature is lower than
        the threshold value written in
         the Trscv EEPROM <Help> Alarm
         indicating that the Trscv Tx Laser
        Temperature is lower than the threshold
        value written in the Trscv EEPROM
        <Condtype> LINE_LASER_TEMP_LOW_ALARM
        <Probcause> temperatureUnacceptable
        (51) <Alarmtype> equipmentAlarm
        (5) <Polarity> (2)
        "
	::= { pm10010mpAlmlineNetworkLaneAlarmWarning1Entry 6 }


pm10010mpAlmLineRxPowerHighAlarmPortn OBJECT-TYPE
	SYNTAX  EkiOnOff
	MAX-ACCESS read-only
	STATUS current
	DESCRIPTION
        "
        Line Trscv Rx Power High Alarm
        :This OID indicates that the Trscv
        input power is higher than the
         threshold value written in the
        Trscv EEPROM <Help> Alarm indicating
        that the Trscv input power is higher
        than the threshold value written
        in the Trscv EEPROM <Condtype>
         LINE_RX_POWER_HIGH_ALARM <Probcause>
        receiveFailure (41) <Alarmtype>
        equipmentAlarm (5) <Polarity> (2)
        "
	::= { pm10010mpAlmlineNetworkLaneAlarmWarning1Entry 5 }


pm10010mpAlmLineRxPowerHighWarningPortn OBJECT-TYPE
	SYNTAX  EkiOnOff
	MAX-ACCESS read-only
	STATUS current
	DESCRIPTION
        "
        Line Trscv Rx Power High Warning
        :This OID indicates that the Trscv
        input power is higher than the
         threshold value written in the
        Trscv EEPROM <Help> Warning indicating
        that the Trscv input power is higher
        than the threshold value written
        in the Trscv EEPROM <Condtype>
         LINE_RX_POWER_HIGH_WARNING <Probcause>
        receiveFailure (41) <Alarmtype>
        equipmentAlarm (5) <Polarity> (2)
        "
	::= { pm10010mpAlmlineNetworkLaneAlarmWarning1Entry 4 }


pm10010mpAlmLineRxPowerLowWarningPortn OBJECT-TYPE
	SYNTAX  EkiOnOff
	MAX-ACCESS read-only
	STATUS current
	DESCRIPTION
        "
        Line Trscv Rx Power Low Warning
        :This OID indicates that the Trscv
        input power is lower than the threshold
        value written in the Trscv EEPROM
        <Help> Warning indicating that
         the Trscv input power is lower
        than the threshold value written
        in the Trscv EEPROM <Condtype>
         LINE_RX_POWER_LOW_WARNING <Probcause>
        receiveFailure (41) <Alarmtype>
        equipmentAlarm (5) <Polarity> (2)
        "
	::= { pm10010mpAlmlineNetworkLaneAlarmWarning1Entry 3 }


pm10010mpAlmLineRxPowerLowAlarmPortn OBJECT-TYPE
	SYNTAX  EkiOnOff
	MAX-ACCESS read-only
	STATUS current
	DESCRIPTION
        "
        Line Trscv Rx Power Low Alarm
         :This OID indicates that the Trscv
        input power is lower than the threshold
        value written in the Trscv EEPROM
        <Help> Alarm indicating that the
        Trscv input power is lower than
        the threshold value written in
         the Trscv EEPROM <Condtype> LINE_RX_POWER_LOW_ALARM
        <Probcause> receiveFailure (41)
        <Alarmtype> equipmentAlarm (5)
         <Polarity> (2)
        "
	::= { pm10010mpAlmlineNetworkLaneAlarmWarning1Entry 2 }


--- *********************************************************
---     TABLE for the pm10010mpAlmlineNetworkLaneAlarmWarning2 articles
--- *********************************************************

pm10010mpAlmlineNetworkLaneAlarmWarning2Table OBJECT-TYPE
	SYNTAX  SEQUENCE OF Pm10010mpAlmlineNetworkLaneAlarmWarning2Entry
	MAX-ACCESS not-accessible
	STATUS current
	DESCRIPTION
        "
        List of pm10010mpAlmlineNetworkLaneAlarmWarning2
        Article
        "
	::= { pm10010mpAlmLineNurg 120 }


pm10010mpAlmlineNetworkLaneAlarmWarning2Entry OBJECT-TYPE
	SYNTAX Pm10010mpAlmlineNetworkLaneAlarmWarning2Entry
	MAX-ACCESS not-accessible
	STATUS current
	DESCRIPTION
        "
        Row definition for the pm10010mpAlmlineNetworkLaneAlarmWarning2
        table
        "
	INDEX   { pm10010mpAlmlineNetworkLaneAlarmWarning2Index }
	::= { pm10010mpAlmlineNetworkLaneAlarmWarning2Table 1 }


Pm10010mpAlmlineNetworkLaneAlarmWarning2Entry ::=
	SEQUENCE {
	pm10010mpAlmlineNetworkLaneAlarmWarning2Index
		INTEGER,
	pm10010mpAlmRxLaserBiasHighAlarmPortn
		EkiOnOff,
	pm10010mpAlmRxLaserBiasHighWarningPortn
		EkiOnOff,
	pm10010mpAlmRxLaserBiasLowWarningPortn
		EkiOnOff,
	pm10010mpAlmRxLaserBiasLowAlarmPortn
		EkiOnOff,
	pm10010mpAlmRxLaserOutputHighAlarmPortn
		EkiOnOff,
	pm10010mpAlmRxLaserOutputHighWarningPortn
		EkiOnOff,
	pm10010mpAlmRxLaserOutputLowWarningPortn
		EkiOnOff,
	pm10010mpAlmRxLaserOutputLowAlarmPortn
		EkiOnOff,
	pm10010mpAlmRxLaserTempHighAlarmPortn
		EkiOnOff,
	pm10010mpAlmRxLaserTempHighWarningPortn
		EkiOnOff,
	pm10010mpAlmRxLaserTempLowWarningPortn
		EkiOnOff,
	pm10010mpAlmRxLaserTempLowAlarmPortn
		EkiOnOff,
	pm10010mpAlmTxModulatorBiasHighAlarmPortn
		EkiOnOff,
	pm10010mpAlmTxModulatorBiasHighWarningPortn
		EkiOnOff,
	pm10010mpAlmTxModulatorBiasLowWarningPortn
		EkiOnOff,
	pm10010mpAlmTxModulatorBiasLowAlarmPortn
		EkiOnOff
	}


pm10010mpAlmlineNetworkLaneAlarmWarning2Index OBJECT-TYPE
	SYNTAX  INTEGER(0..128)
	MAX-ACCESS  read-only
	STATUS current
	DESCRIPTION
        "
        Index definition for the pm10010mpAlmlineNetworkLaneAlarmWarning2
        table
        "
	::= { pm10010mpAlmlineNetworkLaneAlarmWarning2Entry 1 }


pm10010mpAlmRxLaserBiasHighAlarmPortn OBJECT-TYPE
	SYNTAX  EkiOnOff
	MAX-ACCESS read-only
	STATUS current
	DESCRIPTION
        "
        Line Trscv Rx Bias High Alarm
         :This OID indicates that the Trscv
        Rx laser bias current is higher
        than the threshold value written
        in the Trscv EEPROM <Help> Alarm
        indicating that the Trscv Rx laser
        bias current is higher than the
        threshold value written in the
         Trscv EEPROM <Condtype> RX_LASER_BIAS_HIGH_ALARM
        <Probcause> receiveFailure (41)
        <Alarmtype> equipmentAlarm (5)
         <Polarity> (2)
        "
	::= { pm10010mpAlmlineNetworkLaneAlarmWarning2Entry 17 }


pm10010mpAlmRxLaserBiasHighWarningPortn OBJECT-TYPE
	SYNTAX  EkiOnOff
	MAX-ACCESS read-only
	STATUS current
	DESCRIPTION
        "
        Line Trscv Rx Bias High Warning
        :This OID indicates that the Trscv
        Rx laser bias current is higher
        than the threshold value written
        in the Trscv EEPROM <Help> Warning
        indicating that the Trscv Rx laser
        bias current is higher than the
        threshold value written in the
         Trscv EEPROM <Condtype> RX_LASER_BIAS_HIGH_WARNING
        <Probcause> receiveFailure (41)
        <Alarmtype> equipmentAlarm (5)
         <Polarity> (2)
        "
	::= { pm10010mpAlmlineNetworkLaneAlarmWarning2Entry 16 }


pm10010mpAlmRxLaserBiasLowWarningPortn OBJECT-TYPE
	SYNTAX  EkiOnOff
	MAX-ACCESS read-only
	STATUS current
	DESCRIPTION
        "
        Line Trscv Rx Bias Low Warning
        :This OID indicates that the Trscv
        Rx laser bias current is lower
         than the threshold value written
        in the Trscv EEPROM <Help> Warning
        indicating that the Trscv Rx laser
        bias current is lower than the
         threshold value written in the
        Trscv EEPROM <Condtype> RX_LASER_BIAS_LOW_WARNING
        <Probcause> receiveFailure (41)
        <Alarmtype> equipmentAlarm (5)
         <Polarity> (2)
        "
	::= { pm10010mpAlmlineNetworkLaneAlarmWarning2Entry 15 }


pm10010mpAlmRxLaserBiasLowAlarmPortn OBJECT-TYPE
	SYNTAX  EkiOnOff
	MAX-ACCESS read-only
	STATUS current
	DESCRIPTION
        "
        Line Trscv Rx Bias Low Alarm :This
        OID indicates that the Trscv Rx
        laser bias current is lower than
        the threshold value written in
         the Trscv EEPROM <Help> Alarm
         indicating that the Trscv Rx laser
        bias current is lower than the
         threshold value written in the
        Trscv EEPROM <Condtype> RX_LASER_BIAS_LOW_ALARM
        <Probcause> receiveFailure (41)
        <Alarmtype> equipmentAlarm (5)
         <Polarity> (2)
        "
	::= { pm10010mpAlmlineNetworkLaneAlarmWarning2Entry 14 }


pm10010mpAlmRxLaserOutputHighAlarmPortn OBJECT-TYPE
	SYNTAX  EkiOnOff
	MAX-ACCESS read-only
	STATUS current
	DESCRIPTION
        "
        Line Trscv Rx Output Power High
        Alarm :This OID indicates that
         the Trscv Rx output power is higher
        than the threshold value written
        in the Trscv EEPROM <Help> Alarm
        indicating that the Trscv Rx output
        power is higher than the threshold
        value written in the Trscv EEPROM
        <Condtype> RX_LASER_OUTPUT_HIGH_ALARM
        <Probcause> receiveFailure (41)
        <Alarmtype> equipmentAlarm (5)
         <Polarity> (2)
        "
	::= { pm10010mpAlmlineNetworkLaneAlarmWarning2Entry 13 }


pm10010mpAlmRxLaserOutputHighWarningPortn OBJECT-TYPE
	SYNTAX  EkiOnOff
	MAX-ACCESS read-only
	STATUS current
	DESCRIPTION
        "
        Line Trscv Rx Output Power High
        Warning :This OID indicates that
        the Trscv Rx output power is higher
        than the threshold value written
        in the Trscv EEPROM <Help> Warning
        indicating that the Trscv Rx output
        power is higher than the threshold
        value written in the Trscv EEPROM
        <Condtype> RX_LASER_OUTPUT_HIGH_WARNING
        <Probcause> receiveFailure (41)
        <Alarmtype> equipmentAlarm (5)
         <Polarity> (2)
        "
	::= { pm10010mpAlmlineNetworkLaneAlarmWarning2Entry 12 }


pm10010mpAlmRxLaserOutputLowWarningPortn OBJECT-TYPE
	SYNTAX  EkiOnOff
	MAX-ACCESS read-only
	STATUS current
	DESCRIPTION
        "
        Line Trscv Rx Output Power Low
        Warning :This OID indicates that
        the Trscv Rx output power is lower
        than the threshold value written
        in the Trscv EEPROM <Help> Warning
        indicating that the Trscv Rx output
        power is lower than the threshold
        value written in the Trscv EEPROM
        <Condtype> RX_LASER_OUTPUT_LOW_WARNING
        <Probcause> receiveFailure (41)
        <Alarmtype> equipmentAlarm (5)
         <Polarity> (2)
        "
	::= { pm10010mpAlmlineNetworkLaneAlarmWarning2Entry 11 }


pm10010mpAlmRxLaserOutputLowAlarmPortn OBJECT-TYPE
	SYNTAX  EkiOnOff
	MAX-ACCESS read-only
	STATUS current
	DESCRIPTION
        "
        Line Trscv Rx Output Power Low
        Alarm :This OID indicates that
         the Trscv Rx output power is lower
        than the threshold value written
        in the Trscv EEPROM <Help> Alarm
        indicating that the Trscv Rx output
        power is lower than the threshold
        value written in the Trscv EEPROM
        <Condtype> RX_LASER_OUTPUT_LOW_ALARM
        <Probcause> receiveFailure (41)
        <Alarmtype> equipmentAlarm (5)
         <Polarity> (2)
        "
	::= { pm10010mpAlmlineNetworkLaneAlarmWarning2Entry 10 }


pm10010mpAlmRxLaserTempHighAlarmPortn OBJECT-TYPE
	SYNTAX  EkiOnOff
	MAX-ACCESS read-only
	STATUS current
	DESCRIPTION
        "
        Line Trscv Rx Laser Temp High
         Alarm :This OID indicates that
        the Trscv Rx Laser Temperature
         is higher than the threshold value
        written in the Trscv EEPROM <Help>
        Alarm indicating that the Trscv
        Rx Laser Temperature is higher
         than the threshold value written
        in the Trscv EEPROM <Condtype>
         RX_LASER_TEMP_HIGH_ALARM <Probcause>
        temperatureUnacceptable (51) <Alarmtype>
        equipmentAlarm (5) <Polarity> (2)
        "
	::= { pm10010mpAlmlineNetworkLaneAlarmWarning2Entry 9 }


pm10010mpAlmRxLaserTempHighWarningPortn OBJECT-TYPE
	SYNTAX  EkiOnOff
	MAX-ACCESS read-only
	STATUS current
	DESCRIPTION
        "
        Line Trscv Rx Laser Temp High
         Warning :This OID indicates that
        the Trscv Rx Laser Temperature
         is higher than the threshold value
        written in the Trscv EEPROM <Help>
        Warning indicating that the Trscv
        Rx Laser Temperature is higher
         than the threshold value written
        in the Trscv EEPROM <Condtype>
         RX_LASER_TEMP_HIGH_WARNING <Probcause>
        temperatureUnacceptable (51) <Alarmtype>
        equipmentAlarm (5) <Polarity> (2)
        "
	::= { pm10010mpAlmlineNetworkLaneAlarmWarning2Entry 8 }


pm10010mpAlmRxLaserTempLowWarningPortn OBJECT-TYPE
	SYNTAX  EkiOnOff
	MAX-ACCESS read-only
	STATUS current
	DESCRIPTION
        "
        Line Trscv Rx Laser Temp Low Warning
        :This OID indicates that the Trscv
        Rx Laser Temperature is lower than
        the threshold value written in
         the Trscv EEPROM <Help> Warning
        indicating that the Trscv Rx Laser
        Temperature is lower than the threshold
        value written in the Trscv EEPROM
        <Condtype> RX_LASER_TEMP_LOW_WARNING
        <Probcause> temperatureUnacceptable
        (51) <Alarmtype> equipmentAlarm
        (5) <Polarity> (2)
        "
	::= { pm10010mpAlmlineNetworkLaneAlarmWarning2Entry 7 }


pm10010mpAlmRxLaserTempLowAlarmPortn OBJECT-TYPE
	SYNTAX  EkiOnOff
	MAX-ACCESS read-only
	STATUS current
	DESCRIPTION
        "
        Line Trscv Rx Laser Temp Low Alarm
        :This OID indicates that the Trscv
        Rx Laser Temperature is lower than
        the threshold value written in
         the Trscv EEPROM <Help> Alarm
         indicating that the Trscv Rx Laser
        Temperature is lower than the threshold
        value written in the Trscv EEPROM
        <Condtype> RX_LASER_TEMP_LOW_ALARM
        <Probcause> temperatureUnacceptable
        (51) <Alarmtype> equipmentAlarm
        (5) <Polarity> (2)
        "
	::= { pm10010mpAlmlineNetworkLaneAlarmWarning2Entry 6 }


pm10010mpAlmTxModulatorBiasHighAlarmPortn OBJECT-TYPE
	SYNTAX  EkiOnOff
	MAX-ACCESS read-only
	STATUS current
	DESCRIPTION
        "
        Line Trscv Tx Modulator Bias High
        Alarm :This OID indicates that
         the Trscv Tx modulator bias current
        is higher than the threshold value
        written in the Trscv EEPROM <Help>
        Alarm indicating that the Trscv
        Tx modulator bias current is higher
        than the threshold value written
        in the Trscv EEPROM <Condtype>
         TX_MODULATOR_BIAS_HIGH_ALARM <Probcause>
        transmitterFailure (56) <Alarmtype>
        equipmentAlarm (5) <Polarity> (2)
        "
	::= { pm10010mpAlmlineNetworkLaneAlarmWarning2Entry 5 }


pm10010mpAlmTxModulatorBiasHighWarningPortn OBJECT-TYPE
	SYNTAX  EkiOnOff
	MAX-ACCESS read-only
	STATUS current
	DESCRIPTION
        "
        Line Trscv Tx Modulator Bias High
        Warning :This OID indicates that
        the Trscv Tx modulator bias current
        is higher than the threshold value
        written in the Trscv EEPROM <Help>
        Warning indicating that the Trscv
        Tx modulator bias current is higher
        than the threshold value written
        in the Trscv EEPROM <Condtype>
         TX_MODULATOR_BIAS_HIGH_WARNING
        <Probcause> transmitterFailure
         (56) <Alarmtype> equipmentAlarm
        (5) <Polarity> (2)
        "
	::= { pm10010mpAlmlineNetworkLaneAlarmWarning2Entry 4 }


pm10010mpAlmTxModulatorBiasLowWarningPortn OBJECT-TYPE
	SYNTAX  EkiOnOff
	MAX-ACCESS read-only
	STATUS current
	DESCRIPTION
        "
        Line Trscv Tx Modulator Bias Low
        Warning :This OID indicates that
        the Trscv Tx modulator bias current
        is lower than the threshold value
        written in the Trscv EEPROM <Help>
        Warning indicating that the Trscv
        Tx modulator bias current is lower
        than the threshold value written
        in the Trscv EEPROM <Condtype>
         TX_MODULATOR_BIAS_LOW_WARNING
         <Probcause> transmitterFailure
        (56) <Alarmtype> equipmentAlarm
        (5) <Polarity> (2)
        "
	::= { pm10010mpAlmlineNetworkLaneAlarmWarning2Entry 3 }


pm10010mpAlmTxModulatorBiasLowAlarmPortn OBJECT-TYPE
	SYNTAX  EkiOnOff
	MAX-ACCESS read-only
	STATUS current
	DESCRIPTION
        "
        Line Trscv Tx Modulator Bias Low
        Alarm :This OID indicates that
         the Trscv Tx modulator bias current
        is lower than the threshold value
        written in the Trscv EEPROM <Help>
        Alarm indicating that the Trscv
        Tx modulator bias current is lower
        than the threshold value written
        in the Trscv EEPROM <Condtype>
         TX_MODULATOR_BIAS_LOW_ALARM <Probcause>
        transmitterFailure (56) <Alarmtype>
        equipmentAlarm (5) <Polarity> (2)
        "
	::= { pm10010mpAlmlineNetworkLaneAlarmWarning2Entry 2 }


--- *********************************************************
---     TABLE for the pm10010mpAlmlineNetworkLaneFault articles
--- *********************************************************

pm10010mpAlmlineNetworkLaneFaultTable OBJECT-TYPE
	SYNTAX  SEQUENCE OF Pm10010mpAlmlineNetworkLaneFaultEntry
	MAX-ACCESS not-accessible
	STATUS current
	DESCRIPTION
        "
        List of pm10010mpAlmlineNetworkLaneFault
        Article
        "
	::= { pm10010mpAlmLineUrg 136 }


pm10010mpAlmlineNetworkLaneFaultEntry OBJECT-TYPE
	SYNTAX Pm10010mpAlmlineNetworkLaneFaultEntry
	MAX-ACCESS not-accessible
	STATUS current
	DESCRIPTION
        "
        Row definition for the pm10010mpAlmlineNetworkLaneFault
        table
        "
	INDEX   { pm10010mpAlmlineNetworkLaneFaultIndex }
	::= { pm10010mpAlmlineNetworkLaneFaultTable 1 }


Pm10010mpAlmlineNetworkLaneFaultEntry ::=
	SEQUENCE {
	pm10010mpAlmlineNetworkLaneFaultIndex
		INTEGER,
	pm10010mpAlmLineLaneTecFaultPortn
		EkiOnOff,
	pm10010mpAlmLineLaneWavelengthUnlockedPortn
		EkiOnOff,
	pm10010mpAlmLineLaneApdPowerSupplyPortn
		EkiOnOff,
	pm10010mpAlmLineLaneTxLosfPortn
		EkiOnOff,
	pm10010mpAlmLineLaneTxLolPortn
		EkiOnOff,
	pm10010mpAlmLineLaneRxLosPortn
		EkiOnOff,
	pm10010mpAlmLineLaneRxLolPortn
		EkiOnOff,
	pm10010mpAlmLineLaneRxFifoErrorPortn
		EkiOnOff,
	pm10010mpAlmLineLaneRxTecFaultPortn
		EkiOnOff
	}


pm10010mpAlmlineNetworkLaneFaultIndex OBJECT-TYPE
	SYNTAX  INTEGER(0..128)
	MAX-ACCESS  read-only
	STATUS current
	DESCRIPTION
        "
        Index definition for the pm10010mpAlmlineNetworkLaneFault
        table
        "
	::= { pm10010mpAlmlineNetworkLaneFaultEntry 1 }


pm10010mpAlmLineLaneTecFaultPortn OBJECT-TYPE
	SYNTAX  EkiOnOff
	MAX-ACCESS read-only
	STATUS current
	DESCRIPTION
        "
        Line Network Lane TEC Fault :This
        OID indicates a Tx TEC Fault on
        the Line Trscv Network Lane <Help>
        Alarm indicating a Tx TEC Fault
        on the Line Trscv Network Lane
         <Condtype> LINE_LANE_TEC_FAULT
        <Probcause> transmitterFailure
         (56) <Alarmtype> equipmentAlarm
        (5) <Polarity> (2)
        "
	::= { pm10010mpAlmlineNetworkLaneFaultEntry 17 }


pm10010mpAlmLineLaneWavelengthUnlockedPortn OBJECT-TYPE
	SYNTAX  EkiOnOff
	MAX-ACCESS read-only
	STATUS current
	DESCRIPTION
        "
        Line Network Lane Wavelength Unlock
        :This OID indicates a Wavelength
        unlock on the Line Trscv Network
        Lane <Help> Alarm indicating a
         Wavelength unlock on the Line
         Trscv Network Lane <Condtype>
         LINE_LANE_WAVELENGTH_UNLOCKED
         <Probcause> transmitterFailure
        (56) <Alarmtype> equipmentAlarm
        (5) <Polarity> (2)
        "
	::= { pm10010mpAlmlineNetworkLaneFaultEntry 16 }


pm10010mpAlmLineLaneApdPowerSupplyPortn OBJECT-TYPE
	SYNTAX  EkiOnOff
	MAX-ACCESS read-only
	STATUS current
	DESCRIPTION
        "
        Line Network Lane APD Power Supply
        :This OID indicates an APD Power
        supply failure on the Line Trscv
        Network Lane <Help> Alarm indicating
        an APD Power supply failure on
         the Line Trscv Network Lane <Condtype>
        LINE_LANE_APD_POWER_SUPPLY <Probcause>
        transmitterFailure (56) <Alarmtype>
        equipmentAlarm (5) <Polarity> (2)
        "
	::= { pm10010mpAlmlineNetworkLaneFaultEntry 15 }


pm10010mpAlmLineLaneTxLosfPortn OBJECT-TYPE
	SYNTAX  EkiOnOff
	MAX-ACCESS read-only
	STATUS current
	DESCRIPTION
        "
        Line Network Lane Tx Loss Of Signal
        Functionality :This OID indicates
        a Tx Loss of Signal Functionality
        on the Line Trscv Network Lane
         <Help> Alarm indicating a Tx Loss
        of Signal Functionality on the
         Line Trscv Network Lane <Condtype>
        LINE_LANE_TX_LOSF <Probcause> transmitterFailure
        (56) <Alarmtype> equipmentAlarm
        (5) <Polarity> (2)
        "
	::= { pm10010mpAlmlineNetworkLaneFaultEntry 9 }


pm10010mpAlmLineLaneTxLolPortn OBJECT-TYPE
	SYNTAX  EkiOnOff
	MAX-ACCESS read-only
	STATUS current
	DESCRIPTION
        "
        Line Network Lane Tx Loss Of Lock
        :This OID indicates a Tx Loss of
        Lock on the Line Trscv Network
         Lane <Help> Alarm indicating a
        Tx Loss of Lock on the Line Trscv
        Network Lane <Condtype> LINE_LANE_TX_LOL
        <Probcause> transmitterFailure
         (56) <Alarmtype> equipmentAlarm
        (5) <Polarity> (2)
        "
	::= { pm10010mpAlmlineNetworkLaneFaultEntry 8 }


pm10010mpAlmLineLaneRxLosPortn OBJECT-TYPE
	SYNTAX  EkiOnOff
	MAX-ACCESS read-only
	STATUS current
	DESCRIPTION
        "
        Line Network Lane Rx Loss Of Signal
        :This OID indicates a Rx Loss of
        Signal on the Line Trscv Network
        Lane <Help> Alarm indicating a
         Rx Loss of Signal on the Line
         Trscv Network Lane <Condtype>
         LINE_LANE_RX_LOS <Probcause> receiveFailure
        (41) <Alarmtype> physicalViolation
        (9) <Polarity> (2)
        "
	::= { pm10010mpAlmlineNetworkLaneFaultEntry 6 }


pm10010mpAlmLineLaneRxLolPortn OBJECT-TYPE
	SYNTAX  EkiOnOff
	MAX-ACCESS read-only
	STATUS current
	DESCRIPTION
        "
        Line Network Lane Rx Loss Of Lock
        :This OID indicates a Rx Loss of
        Lock on the Line Trscv Network
         Lane <Help> Alarm indicating a
        Rx Loss of Lock on the Line Trscv
        Network Lane <Condtype> LINE_LANE_RX_LOL
        <Probcause> receiverFailure (42)
        <Alarmtype> equipmentAlarm (5)
         <Polarity> (2)
        "
	::= { pm10010mpAlmlineNetworkLaneFaultEntry 5 }


pm10010mpAlmLineLaneRxFifoErrorPortn OBJECT-TYPE
	SYNTAX  EkiOnOff
	MAX-ACCESS read-only
	STATUS current
	DESCRIPTION
        "
        Line Network Lane Rx FIFO Error
        :This OID indicates a Rx FIFO Error
        on the Line Trscv Network Lane
         <Help> Alarm indicating a Rx FIFO
        Error on the Line Trscv Network
        Lane <Condtype> LINE_LANE_RX_FIFO_ERROR
        <Probcause> receiverFailure (42)
        <Alarmtype> equipmentAlarm (5)
         <Polarity> (2)
        "
	::= { pm10010mpAlmlineNetworkLaneFaultEntry 4 }


pm10010mpAlmLineLaneRxTecFaultPortn OBJECT-TYPE
	SYNTAX  EkiOnOff
	MAX-ACCESS read-only
	STATUS current
	DESCRIPTION
        "
        Line Network Lane Rx TEC Fault
        :This OID indicates a Rx TEC Fault
        on the Line Trscv Network Lane
         <Help> Alarm indicating a Rx TEC
        Fault on the Line Trscv Network
        Lane <Condtype> LINE_LANE_RX_TEC_FAULT
        <Probcause> receiverFailure (42)
        <Alarmtype> equipmentAlarm (5)
         <Polarity> (2)
        "
	::= { pm10010mpAlmlineNetworkLaneFaultEntry 3 }


--- *********************************************************
---     TABLE for the pm10010mpAlmlineHostLaneFault articles
--- *********************************************************

pm10010mpAlmlineHostLaneFaultTable OBJECT-TYPE
	SYNTAX  SEQUENCE OF Pm10010mpAlmlineHostLaneFaultEntry
	MAX-ACCESS not-accessible
	STATUS current
	DESCRIPTION
        "
        List of pm10010mpAlmlineHostLaneFault
        Article
        "
	::= { pm10010mpAlmLineUrg 152 }


pm10010mpAlmlineHostLaneFaultEntry OBJECT-TYPE
	SYNTAX Pm10010mpAlmlineHostLaneFaultEntry
	MAX-ACCESS not-accessible
	STATUS current
	DESCRIPTION
        "
        Row definition for the pm10010mpAlmlineHostLaneFault
        table
        "
	INDEX   { pm10010mpAlmlineHostLaneFaultIndex }
	::= { pm10010mpAlmlineHostLaneFaultTable 1 }


Pm10010mpAlmlineHostLaneFaultEntry ::=
	SEQUENCE {
	pm10010mpAlmlineHostLaneFaultIndex
		INTEGER,
	pm10010mpAlmLineLaneTxFifoErrorPortn
		EkiOnOff,
	pm10010mpAlmLineTxHostLolPortn
		EkiOnOff,
	pm10010mpAlmLineSmIaeDetectedPortn
		EkiOnOff,
	pm10010mpAlmLineSmIaeInsertedPortn
		EkiOnOff,
	pm10010mpAlmLineSmBdiDetectedPortn
		EkiOnOff,
	pm10010mpAlmLineSmBdiInsertedPortn
		EkiOnOff,
	pm10010mpAlmLineLossOfFramePortn
		EkiOnOff,
	pm10010mpAlmLineInputLossOfSignalPortn
		EkiOnOff
	}


pm10010mpAlmlineHostLaneFaultIndex OBJECT-TYPE
	SYNTAX  INTEGER(0..128)
	MAX-ACCESS  read-only
	STATUS current
	DESCRIPTION
        "
        Index definition for the pm10010mpAlmlineHostLaneFault
        table
        "
	::= { pm10010mpAlmlineHostLaneFaultEntry 1 }


pm10010mpAlmLineLaneTxFifoErrorPortn OBJECT-TYPE
	SYNTAX  EkiOnOff
	MAX-ACCESS read-only
	STATUS current
	DESCRIPTION
        "
        Line Host Lane Tx FIFO Error :This
        OID indicates a Tx FIFO Error on
        the Line Trscv Host Lane <Help>
        Alarm indicating a Tx FIFO Error
        on the Line Trscv Host Lane <Condtype>
        LINE_LANE_TX_FIFO_ERROR <Probcause>
        receiverFailure (42) <Alarmtype>
        equipmentAlarm (5) <Polarity> (2)
        "
	::= { pm10010mpAlmlineHostLaneFaultEntry 11 }


pm10010mpAlmLineTxHostLolPortn OBJECT-TYPE
	SYNTAX  EkiOnOff
	MAX-ACCESS read-only
	STATUS current
	DESCRIPTION
        "
        Line Host Lane Tx Loss Of Lock
        :This OID indicates a Tx Loss of
        Lock on the Line Trscv Host Lane
        <Help> Alarm indicating a Tx Loss
        of Lock on the Line Trscv Host
         Lane <Condtype> LINE_TX_HOST_LOL
        <Probcause> receiverFailure (42)
        <Alarmtype> equipmentAlarm (5)
         <Polarity> (2)
        "
	::= { pm10010mpAlmlineHostLaneFaultEntry 10 }


pm10010mpAlmLineSmIaeDetectedPortn OBJECT-TYPE
	SYNTAX  EkiOnOff
	MAX-ACCESS read-only
	STATUS current
	DESCRIPTION
        "
        Line SM IAE Detected :This OID
        indicates a SM Incoming Alignment
        Error is detected on the incoming
        Line signal <Help> Alarm indicating
        a SM Incoming Alignment Error is
        detected on the incoming Line signal
        <Condtype> LINE_SM_IAE_DETECTED
        <Probcause> receiveFailure (41)
        <Alarmtype> integrityViolation
         (7) <Polarity> (2)
        "
	::= { pm10010mpAlmlineHostLaneFaultEntry 7 }


pm10010mpAlmLineSmIaeInsertedPortn OBJECT-TYPE
	SYNTAX  EkiOnOff
	MAX-ACCESS read-only
	STATUS current
	DESCRIPTION
        "
        Line SM IAE Inserted :This OID
        indicates a SM Incoming Alignment
        Error is inserted on the outgoing
        Line signal <Help> Status indicating
        a SM Incoming Alignment Error is
        inserted on the outgoing Line signal
        <Condtype> LINE_SM_IAE_INSERTED
        <Probcause> informationalStatus(1000)
        <Alarmtype> other (1) <Polarity>
        (2)
        "
	::= { pm10010mpAlmlineHostLaneFaultEntry 6 }


pm10010mpAlmLineSmBdiDetectedPortn OBJECT-TYPE
	SYNTAX  EkiOnOff
	MAX-ACCESS read-only
	STATUS current
	DESCRIPTION
        "
        Line SM BDI Detected :This OID
        indicates a SM Backward Defect
         Indication is detected on the
         incoming Line signal <Help> Alarm
        indicating a SM Backward Defect
        Indication is detected on the incoming
        Line signal <Condtype> LINE_SM_BDI_DETECTED
        <Probcause> receiveFailure (41)
        <Alarmtype> integrityViolation
         (7) <Polarity> (2)
        "
	::= { pm10010mpAlmlineHostLaneFaultEntry 5 }


pm10010mpAlmLineSmBdiInsertedPortn OBJECT-TYPE
	SYNTAX  EkiOnOff
	MAX-ACCESS read-only
	STATUS current
	DESCRIPTION
        "
        Line SM BDI Inserted :This OID
        indicates a SM Backward Defect
         Indication is inserted on the
         outgoing Line signal <Help> Status
        indicating a SM Backward Defect
        Indication is inserted on the outgoing
        Line signal <Condtype> LINE_SM_BDI_INSERTED
        <Probcause> informationalStatus(1000)
        <Alarmtype> other (1) <Polarity>
        (2)
        "
	::= { pm10010mpAlmlineHostLaneFaultEntry 4 }


pm10010mpAlmLineLossOfFramePortn OBJECT-TYPE
	SYNTAX  EkiOnOff
	MAX-ACCESS read-only
	STATUS current
	DESCRIPTION
        "
        Line Loss Of Frame :This OID indicates
        the module is not aligned with
         the incoming Line signal <Help>
        Alarm indicating the module is
         not aligned with the incoming
         Line signal <Condtype> LINE_LOSS_OF_FRAME
        <Probcause> receiveFailure (41)
        <Alarmtype> integrityViolation
         (7) <Polarity> (2)
        "
	::= { pm10010mpAlmlineHostLaneFaultEntry 3 }


pm10010mpAlmLineInputLossOfSignalPortn OBJECT-TYPE
	SYNTAX  EkiOnOff
	MAX-ACCESS read-only
	STATUS current
	DESCRIPTION
        "
        Line Input Loss Of Signal :This
        OID indicates a Loss of Signal
         is detected on the Line Trscv
         <Help> Alarm indicating a Loss
        of Signal is detected on the Line
        Trscv <Condtype> LINE_INPUT_LOSS_OF_SIGNAL
        <Probcause> receiveFailure (41)
        <Alarmtype> physicalViolation (9)
        <Polarity> (2)
        "
	::= { pm10010mpAlmlineHostLaneFaultEntry 2 }


--- *********************************************************
---     TABLE for the pm10010mpAlmlineNetworkLaneRxOtn articles
--- *********************************************************

pm10010mpAlmlineNetworkLaneRxOtnTable OBJECT-TYPE
	SYNTAX  SEQUENCE OF Pm10010mpAlmlineNetworkLaneRxOtnEntry
	MAX-ACCESS not-accessible
	STATUS current
	DESCRIPTION
        "
        List of pm10010mpAlmlineNetworkLaneRxOtn
        Article
        "
	::= { pm10010mpAlmLineUrg 168 }


pm10010mpAlmlineNetworkLaneRxOtnEntry OBJECT-TYPE
	SYNTAX Pm10010mpAlmlineNetworkLaneRxOtnEntry
	MAX-ACCESS not-accessible
	STATUS current
	DESCRIPTION
        "
        Row definition for the pm10010mpAlmlineNetworkLaneRxOtn
        table
        "
	INDEX   { pm10010mpAlmlineNetworkLaneRxOtnIndex }
	::= { pm10010mpAlmlineNetworkLaneRxOtnTable 1 }


Pm10010mpAlmlineNetworkLaneRxOtnEntry ::=
	SEQUENCE {
	pm10010mpAlmlineNetworkLaneRxOtnIndex
		INTEGER,
	pm10010mpAlmLineRxOtnLofPortn
		EkiOnOff,
	pm10010mpAlmLineRxOtnOofPortn
		EkiOnOff,
	pm10010mpAlmLineRxOtnLomPortn
		EkiOnOff,
	pm10010mpAlmLineRxOtnOomPortn
		EkiOnOff,
	pm10010mpAlmLineRxOtnIaePortn
		EkiOnOff,
	pm10010mpAlmLineRxSmBdiPortn
		EkiOnOff,
	pm10010mpAlmLineRxOtnOtuAisPortn
		EkiOnOff,
	pm10010mpAlmLineRxOtnOduAisPortn
		EkiOnOff
	}


pm10010mpAlmlineNetworkLaneRxOtnIndex OBJECT-TYPE
	SYNTAX  INTEGER(0..128)
	MAX-ACCESS  read-only
	STATUS current
	DESCRIPTION
        "
        Index definition for the pm10010mpAlmlineNetworkLaneRxOtn
        table
        "
	::= { pm10010mpAlmlineNetworkLaneRxOtnEntry 1 }


pm10010mpAlmLineRxOtnLofPortn OBJECT-TYPE
	SYNTAX  EkiOnOff
	MAX-ACCESS read-only
	STATUS current
	DESCRIPTION
        "
        Line Network Rx LOF :This OID
         indicates a Loss of Frame is detected
        on the Rx Network interface of
         the Line Trscv <Help> Alarm indicating
        a Loss of Frame is detected on
         the Rx Network interface of the
        Line Trscv <Condtype> LINE_RX_OTN_LOF
        <Probcause> receiveFailure (41)
        <Alarmtype> equipmentAlarm (5)
         <Polarity> (2)
        "
	::= { pm10010mpAlmlineNetworkLaneRxOtnEntry 17 }


pm10010mpAlmLineRxOtnOofPortn OBJECT-TYPE
	SYNTAX  EkiOnOff
	MAX-ACCESS read-only
	STATUS current
	DESCRIPTION
        "
        Line Network Rx OOF :This OID
         indicates an Out of Frame is detected
        on the Rx Network interface of
         the Line Trscv <Help> Alarm indicating
        an Out of Frame is detected on
         the Rx Network interface of the
        Line Trscv <Condtype> LINE_RX_OTN_OOF
        <Probcause> receiveFailure (41)
        <Alarmtype> equipmentAlarm (5)
         <Polarity> (2)
        "
	::= { pm10010mpAlmlineNetworkLaneRxOtnEntry 16 }


pm10010mpAlmLineRxOtnLomPortn OBJECT-TYPE
	SYNTAX  EkiOnOff
	MAX-ACCESS read-only
	STATUS current
	DESCRIPTION
        "
        Line Network Rx LOM :This OID
         indicates a Loss of Multiframe
        is detected on the Rx Network interface
        of the Line Trscv <Help> Alarm
         indicating a Loss of Multiframe
        is detected on the Rx Network interface
        of the Line Trscv <Condtype> LINE_RX_OTN_LOM
        <Probcause> receiveFailure (41)
        <Alarmtype> equipmentAlarm (5)
         <Polarity> (2)
        "
	::= { pm10010mpAlmlineNetworkLaneRxOtnEntry 15 }


pm10010mpAlmLineRxOtnOomPortn OBJECT-TYPE
	SYNTAX  EkiOnOff
	MAX-ACCESS read-only
	STATUS current
	DESCRIPTION
        "
        Line Network Rx OOM :This OID
         indicates an Out of Multiframe
        is detected on the Rx Network interface
        of the Line Trscv <Help> Alarm
         indicating an Out of Multiframe
        is detected on the Rx Network interface
        of the Line Trscv <Condtype> LINE_RX_OTN_OOM
        <Probcause> receiveFailure (41)
        <Alarmtype> equipmentAlarm (5)
         <Polarity> (2)
        "
	::= { pm10010mpAlmlineNetworkLaneRxOtnEntry 14 }


pm10010mpAlmLineRxOtnIaePortn OBJECT-TYPE
	SYNTAX  EkiOnOff
	MAX-ACCESS read-only
	STATUS current
	DESCRIPTION
        "
        Line Network Rx IAE :This OID
         indicates an Incoming Alignment
        Error is detected on the Rx Network
        interface of the Line Trscv <Help>
        Alarm indicating an Incoming Alignment
        Error is detected on the Rx Network
        interface of the Line Trscv <Condtype>
        LINE_RX_OTN_IAE <Probcause> receiveFailure
        (41) <Alarmtype> equipmentAlarm
        (5) <Polarity> (2)
        "
	::= { pm10010mpAlmlineNetworkLaneRxOtnEntry 13 }


pm10010mpAlmLineRxSmBdiPortn OBJECT-TYPE
	SYNTAX  EkiOnOff
	MAX-ACCESS read-only
	STATUS current
	DESCRIPTION
        "
        Line Network Rx SM BDI :This OID
        indicates an SM Backward Defect
        Indication is detected on the Rx
        Network interface of the Line Trscv
        <Help> Alarm indicating an SM Backward
        Defect Indication is detected on
        the Rx Network interface of the
        Line Trscv <Condtype> LINE_RX_SM_BDI
        <Probcause> informationalStatus(1000)
        <Alarmtype> other (1) <Polarity>
        (2)
        "
	::= { pm10010mpAlmlineNetworkLaneRxOtnEntry 12 }


pm10010mpAlmLineRxOtnOtuAisPortn OBJECT-TYPE
	SYNTAX  EkiOnOff
	MAX-ACCESS read-only
	STATUS current
	DESCRIPTION
        "
        Line Network Rx OTU AIS :This
         OID indicates an OTU This OID
         Indication Signal is detected
         on the Rx Network interface of
        the Line Trscv <Help> Alarm indicating
        an OTU Alarm Indication Signal
         is detected on the Rx Network
         interface of the Line Trscv <Condtype>
        LINE_RX_OTN_OTU_AIS <Probcause>
        receiveFailure (41) <Alarmtype>
        equipmentAlarm (5) <Polarity> (2)
        "
	::= { pm10010mpAlmlineNetworkLaneRxOtnEntry 11 }


pm10010mpAlmLineRxOtnOduAisPortn OBJECT-TYPE
	SYNTAX  EkiOnOff
	MAX-ACCESS read-only
	STATUS current
	DESCRIPTION
        "
        Line Network Rx ODU AIS :This
         OID indicates an ODU This OID
         Indication Signal is detected
         on the Rx Network interface of
        the Line Trscv <Help> Alarm indicating
        an ODU Alarm Indication Signal
         is detected on the Rx Network
         interface of the Line Trscv <Condtype>
        LINE_RX_OTN_ODU_AIS <Probcause>
        receiveFailure (41) <Alarmtype>
        equipmentAlarm (5) <Polarity> (2)
        "
	::= { pm10010mpAlmlineNetworkLaneRxOtnEntry 10 }


--- *********************************************************
---     TABLE for the pm10010mpAlmlineHostLaneTxOtn articles
--- *********************************************************

pm10010mpAlmlineHostLaneTxOtnTable OBJECT-TYPE
	SYNTAX  SEQUENCE OF Pm10010mpAlmlineHostLaneTxOtnEntry
	MAX-ACCESS not-accessible
	STATUS current
	DESCRIPTION
        "
        List of pm10010mpAlmlineHostLaneTxOtn
        Article
        "
	::= { pm10010mpAlmLineUrg 184 }


pm10010mpAlmlineHostLaneTxOtnEntry OBJECT-TYPE
	SYNTAX Pm10010mpAlmlineHostLaneTxOtnEntry
	MAX-ACCESS not-accessible
	STATUS current
	DESCRIPTION
        "
        Row definition for the pm10010mpAlmlineHostLaneTxOtn
        table
        "
	INDEX   { pm10010mpAlmlineHostLaneTxOtnIndex }
	::= { pm10010mpAlmlineHostLaneTxOtnTable 1 }


Pm10010mpAlmlineHostLaneTxOtnEntry ::=
	SEQUENCE {
	pm10010mpAlmlineHostLaneTxOtnIndex
		INTEGER,
	pm10010mpAlmLineTxOtnLofPortn
		EkiOnOff,
	pm10010mpAlmLineTxOtnOofPortn
		EkiOnOff,
	pm10010mpAlmLineTxOtnLomPortn
		EkiOnOff,
	pm10010mpAlmLineTxOtnOomPortn
		EkiOnOff,
	pm10010mpAlmLineTxOtnIaePortn
		EkiOnOff,
	pm10010mpAlmLineTxSmBdiPortn
		EkiOnOff,
	pm10010mpAlmLineTxOtnOtuAisPortn
		EkiOnOff,
	pm10010mpAlmLineTxOtnOduAisPortn
		EkiOnOff
	}


pm10010mpAlmlineHostLaneTxOtnIndex OBJECT-TYPE
	SYNTAX  INTEGER(0..128)
	MAX-ACCESS  read-only
	STATUS current
	DESCRIPTION
        "
        Index definition for the pm10010mpAlmlineHostLaneTxOtn
        table
        "
	::= { pm10010mpAlmlineHostLaneTxOtnEntry 1 }


pm10010mpAlmLineTxOtnLofPortn OBJECT-TYPE
	SYNTAX  EkiOnOff
	MAX-ACCESS read-only
	STATUS current
	DESCRIPTION
        "
        Line Host Tx LOF :This OID indicates
        a Loss of Frame is detected on
         the Tx Host interface of the Line
        Trscv <Help> Alarm indicating a
        Loss of Frame is detected on the
        Tx Host interface of the Line Trscv
        <Condtype> LINE_TX_OTN_LOF <Probcause>
        receiveFailure (41) <Alarmtype>
        equipmentAlarm (5) <Polarity> (2)
        "
	::= { pm10010mpAlmlineHostLaneTxOtnEntry 17 }


pm10010mpAlmLineTxOtnOofPortn OBJECT-TYPE
	SYNTAX  EkiOnOff
	MAX-ACCESS read-only
	STATUS current
	DESCRIPTION
        "
        Line Host Tx OOF :This OID indicates
        an Out of Frame is detected on
         the Tx Host interface of the Line
        Trscv <Help> Alarm indicating an
        Out of Frame is detected on the
        Tx Host interface of the Line Trscv
        <Condtype> LINE_TX_OTN_OOF <Probcause>
        receiveFailure (41) <Alarmtype>
        equipmentAlarm (5) <Polarity> (2)
        "
	::= { pm10010mpAlmlineHostLaneTxOtnEntry 16 }


pm10010mpAlmLineTxOtnLomPortn OBJECT-TYPE
	SYNTAX  EkiOnOff
	MAX-ACCESS read-only
	STATUS current
	DESCRIPTION
        "
        Line Host Tx LOM :This OID indicates
        a Loss of Multiframe is detected
        on the Tx Host interface of the
        Line Trscv <Help> Alarm indicating
        a Loss of Multiframe is detected
        on the Tx Host interface of the
        Line Trscv <Condtype> LINE_TX_OTN_LOM
        <Probcause> receiveFailure (41)
        <Alarmtype> equipmentAlarm (5)
         <Polarity> (2)
        "
	::= { pm10010mpAlmlineHostLaneTxOtnEntry 15 }


pm10010mpAlmLineTxOtnOomPortn OBJECT-TYPE
	SYNTAX  EkiOnOff
	MAX-ACCESS read-only
	STATUS current
	DESCRIPTION
        "
        Line Host Tx OOM :This OID indicates
        an Out of Multiframe is detected
        on the Tx Host interface of the
        Line Trscv <Help> Alarm indicating
        an Out of Multiframe is detected
        on the Tx Host interface of the
        Line Trscv <Condtype> LINE_TX_OTN_OOM
        <Probcause> receiveFailure (41)
        <Alarmtype> equipmentAlarm (5)
         <Polarity> (2)
        "
	::= { pm10010mpAlmlineHostLaneTxOtnEntry 14 }


pm10010mpAlmLineTxOtnIaePortn OBJECT-TYPE
	SYNTAX  EkiOnOff
	MAX-ACCESS read-only
	STATUS current
	DESCRIPTION
        "
        Line Host Tx IAE :This OID indicates
        an Incoming Alignment Error is
         detected on the Tx Host interface
        of the Line Trscv <Help> Alarm
         indicating an Incoming Alignment
        Error is detected on the Tx Host
        interface of the Line Trscv <Condtype>
        LINE_TX_OTN_IAE <Probcause> receiveFailure
        (41) <Alarmtype> equipmentAlarm
        (5) <Polarity> (2)
        "
	::= { pm10010mpAlmlineHostLaneTxOtnEntry 13 }


pm10010mpAlmLineTxSmBdiPortn OBJECT-TYPE
	SYNTAX  EkiOnOff
	MAX-ACCESS read-only
	STATUS current
	DESCRIPTION
        "
        Line Host Tx SM BDI :This OID
         indicates an SM Backward Defect
        Indication is detected on the Tx
        Host interface of the Line Trscv
        <Help> Alarm indicating an SM Backward
        Defect Indication is detected on
        the Tx Host interface of the Line
        Trscv <Condtype> LINE_TX_SM_BDI
        <Probcause> informationalStatus(1000)
        <Alarmtype> other (1) <Polarity>
        (2)
        "
	::= { pm10010mpAlmlineHostLaneTxOtnEntry 12 }


pm10010mpAlmLineTxOtnOtuAisPortn OBJECT-TYPE
	SYNTAX  EkiOnOff
	MAX-ACCESS read-only
	STATUS current
	DESCRIPTION
        "
        Line Host Tx OTU AIS :This OID
        indicates an OTU This OID Indication
        Signal is detected on the Tx Host
        interface of the Line Trscv <Help>
        Alarm indicating an OTU Alarm Indication
        Signal is detected on the Tx Host
        interface of the Line Trscv <Condtype>
        LINE_TX_OTN_OTU_AIS <Probcause>
        receiveFailure (41) <Alarmtype>
        equipmentAlarm (5) <Polarity> (2)
        "
	::= { pm10010mpAlmlineHostLaneTxOtnEntry 11 }


pm10010mpAlmLineTxOtnOduAisPortn OBJECT-TYPE
	SYNTAX  EkiOnOff
	MAX-ACCESS read-only
	STATUS current
	DESCRIPTION
        "
        Line Host Tx ODU AIS :This OID
        indicates an ODU This OID Indication
        Signal is detected on the Tx Host
        interface of the Line Trscv <Help>
        Alarm indicating an ODU Alarm Indication
        Signal is detected on the Tx Host
        interface of the Line Trscv <Condtype>
        LINE_TX_OTN_ODU_AIS <Probcause>
        receiveFailure (41) <Alarmtype>
        equipmentAlarm (5) <Polarity> (2)
        "
	::= { pm10010mpAlmlineHostLaneTxOtnEntry 10 }


--- *********************************************************
---     TABLE for the pm10010mpAlmclientSfpAlmDdm articles
--- *********************************************************

pm10010mpAlmclientSfpAlmDdmTable OBJECT-TYPE
	SYNTAX  SEQUENCE OF Pm10010mpAlmclientSfpAlmDdmEntry
	MAX-ACCESS not-accessible
	STATUS current
	DESCRIPTION
        "
        List of pm10010mpAlmclientSfpAlmDdm
        Article
        "
	::= { pm10010mpAlmClientUrg 216 }


pm10010mpAlmclientSfpAlmDdmEntry OBJECT-TYPE
	SYNTAX Pm10010mpAlmclientSfpAlmDdmEntry
	MAX-ACCESS not-accessible
	STATUS current
	DESCRIPTION
        "
        Row definition for the pm10010mpAlmclientSfpAlmDdm
        table
        "
	INDEX   { pm10010mpAlmclientSfpAlmDdmIndex }
	::= { pm10010mpAlmclientSfpAlmDdmTable 1 }


Pm10010mpAlmclientSfpAlmDdmEntry ::=
	SEQUENCE {
	pm10010mpAlmclientSfpAlmDdmIndex
		INTEGER,
	pm10010mpAlmRxPwrHighAlaPortn
		EkiOnOff,
	pm10010mpAlmRxPwrLowAlaPortn
		EkiOnOff,
	pm10010mpAlmTempHighAlaPortn
		EkiOnOff,
	pm10010mpAlmTempLowAlaPortn
		EkiOnOff,
	pm10010mpAlmVccHighAlaPortn
		EkiOnOff,
	pm10010mpAlmVccLowAlaPortn
		EkiOnOff,
	pm10010mpAlmTxBiasHighAlaPortn
		EkiOnOff,
	pm10010mpAlmTxBiasLowAlaPortn
		EkiOnOff,
	pm10010mpAlmTxPwrHighAlaPortn
		EkiOnOff,
	pm10010mpAlmTxPwrLowAlaPortn
		EkiOnOff
	}


pm10010mpAlmclientSfpAlmDdmIndex OBJECT-TYPE
	SYNTAX  INTEGER(0..128)
	MAX-ACCESS  read-only
	STATUS current
	DESCRIPTION
        "
        Index definition for the pm10010mpAlmclientSfpAlmDdm
        table
        "
	::= { pm10010mpAlmclientSfpAlmDdmEntry 1 }


pm10010mpAlmRxPwrHighAlaPortn OBJECT-TYPE
	SYNTAX  EkiOnOff
	MAX-ACCESS read-only
	STATUS current
	DESCRIPTION
        "
        Client Trscv Rx Power High :This
        OID indicates that the Trscv input
        power of port is higher than the
        threshold value written in the
         Trscv EEPROM <Help> Alarm indicating
        that the Trscv input power of port
        is higher than the threshold value
        written in the Trscv EEPROM <Condtype>
        RX_PWR_HIGH_ALA_1 <Probcause> receiveFailure
        (41) <Alarmtype> equipmentAlarm
        (5) <Polarity> (2)
        "
	::= { pm10010mpAlmclientSfpAlmDdmEntry 17 }


pm10010mpAlmRxPwrLowAlaPortn OBJECT-TYPE
	SYNTAX  EkiOnOff
	MAX-ACCESS read-only
	STATUS current
	DESCRIPTION
        "
        Client Trscv Rx Power Low :This
        OID indicates that the Trscv input
        power of port is lower than the
        threshold value written in the
         Trscv EEPROM <Help> Alarm indicating
        that the Trscv input power of port
        is lower than the threshold value
        written in the Trscv EEPROM <Condtype>
        RX_PWR_LOW_ALA_1 <Probcause> receiveFailure
        (41) <Alarmtype> equipmentAlarm
        (5) <Polarity> (2)
        "
	::= { pm10010mpAlmclientSfpAlmDdmEntry 16 }


pm10010mpAlmTempHighAlaPortn OBJECT-TYPE
	SYNTAX  EkiOnOff
	MAX-ACCESS read-only
	STATUS current
	DESCRIPTION
        "
        Client Trscv Temp High :This OID
        indicates that the Trscv temperature
        of port is higher than the threshold
        value written in the Trscv EEPROM
        <Help> Alarm indicating that the
        Trscv temperature of port is higher
        than the threshold value written
        in the Trscv EEPROM <Condtype>
         TEMP_HIGH_ALA_1 <Probcause> temperatureUnacceptable
        (51) <Alarmtype> equipmentAlarm
        (5) <Polarity> (2)
        "
	::= { pm10010mpAlmclientSfpAlmDdmEntry 9 }


pm10010mpAlmTempLowAlaPortn OBJECT-TYPE
	SYNTAX  EkiOnOff
	MAX-ACCESS read-only
	STATUS current
	DESCRIPTION
        "
        Client Trscv Temp Low :This OID
        indicates that the Trscv temperature
        of port is lower than the threshold
        value written in the Trscv EEPROM
        <Help> Alarm indicating that the
        Trscv temperature of port is lower
        than the threshold value written
        in the Trscv EEPROM <Condtype>
         TEMP_LOW_ALA_1 <Probcause> temperatureUnacceptable
        (51) <Alarmtype> equipmentAlarm
        (5) <Polarity> (2)
        "
	::= { pm10010mpAlmclientSfpAlmDdmEntry 8 }


pm10010mpAlmVccHighAlaPortn OBJECT-TYPE
	SYNTAX  EkiOnOff
	MAX-ACCESS read-only
	STATUS current
	DESCRIPTION
        "
        Client Trscv Power Supply High
        :This OID indicates that the Trscv
        power supply of port is higher
         than the threshold value written
        in the Trscv EEPROM <Help> Alarm
        indicating that the Trscv power
        supply of port is higher than the
        threshold value written in the
         Trscv EEPROM <Condtype> VCC_HIGH_ALA_1
        <Probcause> powerProblem (36) <Alarmtype>
        equipmentAlarm (5) <Polarity> (2)
        "
	::= { pm10010mpAlmclientSfpAlmDdmEntry 7 }


pm10010mpAlmVccLowAlaPortn OBJECT-TYPE
	SYNTAX  EkiOnOff
	MAX-ACCESS read-only
	STATUS current
	DESCRIPTION
        "
        Client Trscv Power Supply Low
         :This OID indicates that the Trscv
        power supply of port is lower than
        the threshold value written in
         the Trscv EEPROM <Help> Alarm
         indicating that the Trscv power
        supply of port is lower than the
        threshold value written in the
         Trscv EEPROM <Condtype> VCC_LOW_ALA_1
        <Probcause> powerProblem (36) <Alarmtype>
        equipmentAlarm (5) <Polarity> (2)
        "
	::= { pm10010mpAlmclientSfpAlmDdmEntry 6 }


pm10010mpAlmTxBiasHighAlaPortn OBJECT-TYPE
	SYNTAX  EkiOnOff
	MAX-ACCESS read-only
	STATUS current
	DESCRIPTION
        "
        Client Trscv Bias High :This OID
        indicates that the Trscv laser
         bias current of port is higher
        than the threshold value written
        in the Trscv EEPROM <Help> Alarm
        indicating that the Trscv laser
        bias current of port is higher
         than the threshold value written
        in the Trscv EEPROM <Condtype>
         TX_BIAS_HIGH_ALA_1 <Probcause>
        transmitterFailure (56) <Alarmtype>
        equipmentAlarm (5) <Polarity> (2)
        "
	::= { pm10010mpAlmclientSfpAlmDdmEntry 5 }


pm10010mpAlmTxBiasLowAlaPortn OBJECT-TYPE
	SYNTAX  EkiOnOff
	MAX-ACCESS read-only
	STATUS current
	DESCRIPTION
        "
        Client Trscv Bias Low :This OID
        indicates that the Trscv laser
         bias current of port is lower
         than the threshold value written
        in the Trscv EEPROM <Help> Alarm
        indicating that the Trscv laser
        bias current of port is lower than
        the threshold value written in
         the Trscv EEPROM <Condtype> TX_BIAS_LOW_ALA_1
        <Probcause> transmitterFailure
         (56) <Alarmtype> equipmentAlarm
        (5) <Polarity> (2)
        "
	::= { pm10010mpAlmclientSfpAlmDdmEntry 4 }


pm10010mpAlmTxPwrHighAlaPortn OBJECT-TYPE
	SYNTAX  EkiOnOff
	MAX-ACCESS read-only
	STATUS current
	DESCRIPTION
        "
        Client Trscv Tx Power High :This
        OID indicates that the Trscv output
        power of port is higher than the
        threshold value written in the
         Trscv EEPROM <Help> Alarm indicating
        that the Trscv output power of
         port is higher than the threshold
        value written in the Trscv EEPROM
        <Condtype> TX_PWR_HIGH_ALA_1 <Probcause>
        transmitterFailure (56) <Alarmtype>
        equipmentAlarm (5) <Polarity> (2)
        "
	::= { pm10010mpAlmclientSfpAlmDdmEntry 3 }


pm10010mpAlmTxPwrLowAlaPortn OBJECT-TYPE
	SYNTAX  EkiOnOff
	MAX-ACCESS read-only
	STATUS current
	DESCRIPTION
        "
        Client Trscv Tx Power Low :This
        OID indicates that the Trscv output
        power of port is lower than the
        threshold value written in the
         Trscv EEPROM <Help> Alarm indicating
        that the Trscv output power of
         port is lower than the threshold
        value written in the Trscv EEPROM
        <Condtype> TX_PWR_LOW_ALA_1 <Probcause>
        transmitterFailure (56) <Alarmtype>
        equipmentAlarm (5) <Polarity> (2)
        "
	::= { pm10010mpAlmclientSfpAlmDdmEntry 2 }


--- *********************************************************
---     TABLE for the pm10010mpAlmclientSfpWarnDdm articles
--- *********************************************************

pm10010mpAlmclientSfpWarnDdmTable OBJECT-TYPE
	SYNTAX  SEQUENCE OF Pm10010mpAlmclientSfpWarnDdmEntry
	MAX-ACCESS not-accessible
	STATUS current
	DESCRIPTION
        "
        List of pm10010mpAlmclientSfpWarnDdm
        Article
        "
	::= { pm10010mpAlmClientNurg 232 }


pm10010mpAlmclientSfpWarnDdmEntry OBJECT-TYPE
	SYNTAX Pm10010mpAlmclientSfpWarnDdmEntry
	MAX-ACCESS not-accessible
	STATUS current
	DESCRIPTION
        "
        Row definition for the pm10010mpAlmclientSfpWarnDdm
        table
        "
	INDEX   { pm10010mpAlmclientSfpWarnDdmIndex }
	::= { pm10010mpAlmclientSfpWarnDdmTable 1 }


Pm10010mpAlmclientSfpWarnDdmEntry ::=
	SEQUENCE {
	pm10010mpAlmclientSfpWarnDdmIndex
		INTEGER,
	pm10010mpAlmRxPwrHighWngPortn
		EkiOnOff,
	pm10010mpAlmRxPwrLowWngPortn
		EkiOnOff,
	pm10010mpAlmTempHighWngPortn
		EkiOnOff,
	pm10010mpAlmTempLowWngPortn
		EkiOnOff,
	pm10010mpAlmVccHighWngPortn
		EkiOnOff,
	pm10010mpAlmVccLowWngPortn
		EkiOnOff,
	pm10010mpAlmTxBiasHighWngPortn
		EkiOnOff,
	pm10010mpAlmTxBiasLowWngPortn
		EkiOnOff,
	pm10010mpAlmTxPwrHighWngPortn
		EkiOnOff,
	pm10010mpAlmTxPwLowWngPortn
		EkiOnOff
	}


pm10010mpAlmclientSfpWarnDdmIndex OBJECT-TYPE
	SYNTAX  INTEGER(0..128)
	MAX-ACCESS  read-only
	STATUS current
	DESCRIPTION
        "
        Index definition for the pm10010mpAlmclientSfpWarnDdm
        table
        "
	::= { pm10010mpAlmclientSfpWarnDdmEntry 1 }


pm10010mpAlmRxPwrHighWngPortn OBJECT-TYPE
	SYNTAX  EkiOnOff
	MAX-ACCESS read-only
	STATUS current
	DESCRIPTION
        "
        Client Trscv Rx Power High Warning
        :This OID indicates that the Trscv
        input power is higher than the
         threshold value written in the
        Trscv EEPROM <Help> Warning indicating
        that the Trscv input power is higher
        than the threshold value written
        in the Trscv EEPROM <Condtype>
         RX_PWR_HIGH_WNG_1 <Probcause>
         receiveFailure (41) <Alarmtype>
        equipmentAlarm (5) <Polarity> (2)
        "
	::= { pm10010mpAlmclientSfpWarnDdmEntry 17 }


pm10010mpAlmRxPwrLowWngPortn OBJECT-TYPE
	SYNTAX  EkiOnOff
	MAX-ACCESS read-only
	STATUS current
	DESCRIPTION
        "
        Client Trscv Rx Power Low Warning
        :This OID indicates that the Trscv
        input power is lower than the threshold
        value written in the Trscv EEPROM
        <Help> Warning indicating that
         the Trscv input power is lower
        than the threshold value written
        in the Trscv EEPROM <Condtype>
         RX_PWR_LOW_WNG_1 <Probcause> receiveFailure
        (41) <Alarmtype> equipmentAlarm
        (5) <Polarity> (2)
        "
	::= { pm10010mpAlmclientSfpWarnDdmEntry 16 }


pm10010mpAlmTempHighWngPortn OBJECT-TYPE
	SYNTAX  EkiOnOff
	MAX-ACCESS read-only
	STATUS current
	DESCRIPTION
        "
        Client Trscv Temp High Warning
        :This OID indicates that the Trscv
        temperature is higher than the
         threshold value written in the
        Trscv EEPROM <Help> Warning indicating
        that the Trscv temperature is higher
        than the threshold value written
        in the Trscv EEPROM <Condtype>
         TEMP_HIGH_WNG_1 <Probcause> temperatureUnacceptable
        (51) <Alarmtype> equipmentAlarm
        (5) <Polarity> (2)
        "
	::= { pm10010mpAlmclientSfpWarnDdmEntry 9 }


pm10010mpAlmTempLowWngPortn OBJECT-TYPE
	SYNTAX  EkiOnOff
	MAX-ACCESS read-only
	STATUS current
	DESCRIPTION
        "
        Client Trscv Temp Low Warning
         :This OID indicates that the Trscv
        temperature is lower than the threshold
        value written in the Trscv EEPROM
        <Help> Warning indicating that
         the Trscv temperature is lower
        than the threshold value written
        in the Trscv EEPROM <Condtype>
         TEMP_LOW_WNG_1 <Probcause> temperatureUnacceptable
        (51) <Alarmtype> equipmentAlarm
        (5) <Polarity> (2)
        "
	::= { pm10010mpAlmclientSfpWarnDdmEntry 8 }


pm10010mpAlmVccHighWngPortn OBJECT-TYPE
	SYNTAX  EkiOnOff
	MAX-ACCESS read-only
	STATUS current
	DESCRIPTION
        "
        Client Trscv Power Supply High
        Warning :This OID indicates that
        the Trscv power supply is higher
        than the threshold value written
        in the Trscv EEPROM <Help> Warning
        indicating that the Trscv power
        supply is higher than the threshold
        value written in the Trscv EEPROM
        <Condtype> VCC_HIGH_WNG_1 <Probcause>
        powerProblem (36) <Alarmtype> equipmentAlarm
        (5) <Polarity> (2)
        "
	::= { pm10010mpAlmclientSfpWarnDdmEntry 7 }


pm10010mpAlmVccLowWngPortn OBJECT-TYPE
	SYNTAX  EkiOnOff
	MAX-ACCESS read-only
	STATUS current
	DESCRIPTION
        "
        Client Trscv Power Supply Low
         Warning :This OID indicates that
        the Trscv power supply is lower
        than the threshold value written
        in the Trscv EEPROM <Help> Warning
        indicating that the Trscv power
        supply is lower than the threshold
        value written in the Trscv EEPROM
        <Condtype> VCC_LOW_WNG_1 <Probcause>
        powerProblem (36) <Alarmtype> equipmentAlarm
        (5) <Polarity> (2)
        "
	::= { pm10010mpAlmclientSfpWarnDdmEntry 6 }


pm10010mpAlmTxBiasHighWngPortn OBJECT-TYPE
	SYNTAX  EkiOnOff
	MAX-ACCESS read-only
	STATUS current
	DESCRIPTION
        "
        Client Trscv Bias High Warning
        :This OID indicates that the Trscv
        laser bias current is higher than
        the threshold value written in
         the Trscv EEPROM <Help> Warning
        indicating that the Trscv laser
        bias current is higher than the
        threshold value written in the
         Trscv EEPROM <Condtype> TX_BIAS_HIGH_WNG_1
        <Probcause> transmitterFailure
         (56) <Alarmtype> equipmentAlarm
        (5) <Polarity> (2)
        "
	::= { pm10010mpAlmclientSfpWarnDdmEntry 5 }


pm10010mpAlmTxBiasLowWngPortn OBJECT-TYPE
	SYNTAX  EkiOnOff
	MAX-ACCESS read-only
	STATUS current
	DESCRIPTION
        "
        Client Trscv Bias Low Warning
         :This OID indicates that the Trscv
        laser bias current is lower than
        the threshold value written in
         the Trscv EEPROM <Help> Warning
        indicating that the Trscv laser
        bias current is lower than the
         threshold value written in the
        Trscv EEPROM <Condtype> TX_BIAS_LOW_WNG_1
        <Probcause> transmitterFailure
         (56) <Alarmtype> equipmentAlarm
        (5) <Polarity> (2)
        "
	::= { pm10010mpAlmclientSfpWarnDdmEntry 4 }


pm10010mpAlmTxPwrHighWngPortn OBJECT-TYPE
	SYNTAX  EkiOnOff
	MAX-ACCESS read-only
	STATUS current
	DESCRIPTION
        "
        Client Trscv Tx Power High Warning
        :This OID indicates that the Trscv
        output power is higher than the
        threshold value written in the
         Trscv EEPROM <Help> Warning indicating
        that the Trscv output power is
         higher than the threshold value
        written in the Trscv EEPROM <Condtype>
        TX_PWR_HIGH_WNG_1 <Probcause> transmitterFailure
        (56) <Alarmtype> equipmentAlarm
        (5) <Polarity> (2)
        "
	::= { pm10010mpAlmclientSfpWarnDdmEntry 3 }


pm10010mpAlmTxPwLowWngPortn OBJECT-TYPE
	SYNTAX  EkiOnOff
	MAX-ACCESS read-only
	STATUS current
	DESCRIPTION
        "
        Client Trscv Tx Power Low Warning
        :This OID indicates that the Trscv
        output power is lower than the
         threshold value written in the
        Trscv EEPROM <Help> Warning indicating
        that the Trscv output power is
         lower than the threshold value
        written in the Trscv EEPROM <Condtype>
        TX_PW_LOW_WNG_1 <Probcause> transmitterFailure
        (56) <Alarmtype> equipmentAlarm
        (5) <Polarity> (2)
        "
	::= { pm10010mpAlmclientSfpWarnDdmEntry 2 }







--- *****************************************************
--- $$$$$$$$$$$$$$$$$$$$$$$$$$$$$$$$$$$$$$$$$$$$$$$$$$$$$
---     CONTROLS
--- $$$$$$$$$$$$$$$$$$$$$$$$$$$$$$$$$$$$$$$$$$$$$$$$$$$$$
--- *****************************************************



--- *****************************************************
---     LEAF for the confMgnt1 article
--- *****************************************************
pm10010mpCtrlconfMgnt1 OBJECT IDENTIFIER ::= { pm10010mpCtrlOther 1 }




pm10010mpCtrlConf2Clear1 OBJECT-TYPE
	  SYNTAX EkiOnOff
	  MAX-ACCESS read-write
	  STATUS current
	  DESCRIPTION
        "
        Clear Configuration Tables :This
        OID clears the configuration tables
        from configuration2 in the flash.
         <Help>  This control restores
         the default configuration of the
        module
        "
	  ::= { pm10010mpCtrlconfMgnt1 14 }



pm10010mpCtrlConf2Flash1 OBJECT-TYPE
	  SYNTAX EkiOnOff
	  MAX-ACCESS read-write
	  STATUS current
	  DESCRIPTION
        "
        Write Configuration Tables :This
        OID saves the current configuration
        of the PM as configuration2 in
         the flash.  <Help>  This control
        saves the customer configuration
        on the module
        "
	  ::= { pm10010mpCtrlconfMgnt1 10 }



pm10010mpCtrlConf2Load1 OBJECT-TYPE
	  SYNTAX EkiOnOff
	  MAX-ACCESS read-write
	  STATUS current
	  DESCRIPTION
        "
        Load Configuration Tables Set
         Nb 2 :When set this OID enables
        loading from flash configuration2
        into the PM.
        "
	  ::= { pm10010mpCtrlconfMgnt1 2 }



pm10010mpCtrlConf1Load1 OBJECT-TYPE
	  SYNTAX EkiOnOff
	  MAX-ACCESS read-write
	  STATUS current
	  DESCRIPTION
        "
        Load Configuration Tables Set
         Nb 1 :When set this OID enables
        loading from flash configuration1
        into the PM.
        "
	  ::= { pm10010mpCtrlconfMgnt1 1 }



--- *****************************************************
---     LEAF for the synth4 article
--- *****************************************************
pm10010mpCtrlsynth4 OBJECT IDENTIFIER ::= { pm10010mpCtrlOther 4 }




pm10010mpCtrlCorrelatOff OBJECT-TYPE
	  SYNTAX EkiOnOff
	  MAX-ACCESS read-write
	  STATUS current
	  DESCRIPTION
        "
        Disable Alarm Correlation :This
        OID disables the alarm correlation
        in the PM.
        "
	  ::= { pm10010mpCtrlsynth4 2 }



pm10010mpCtrlCorrelatOn OBJECT-TYPE
	  SYNTAX EkiOnOff
	  MAX-ACCESS read-write
	  STATUS current
	  DESCRIPTION
        "
        Enable Alarm Correlation :This
        OID enables the alarm correlation
        in the PM.
        "
	  ::= { pm10010mpCtrlsynth4 1 }



--- *****************************************************
---     LEAF for the swMgnt article
--- *****************************************************
pm10010mpCtrlswMgnt OBJECT IDENTIFIER ::= { pm10010mpCtrlOther 5 }




pm10010mpCtrlLoadSwBank2 OBJECT-TYPE
	  SYNTAX EkiOnOff
	  MAX-ACCESS read-write
	  STATUS current
	  DESCRIPTION
        "
        Set Software Nb 2 As Active :This
        OID, when set, loads the SW from
        bank2 into the PM. It must be followed
        by a reset.  <Help>  This controls
        selects the second SW bank as the
        active bank for the next module
        reset
        "
	  ::= { pm10010mpCtrlswMgnt 6 }



pm10010mpCtrlLoadSwBank1 OBJECT-TYPE
	  SYNTAX EkiOnOff
	  MAX-ACCESS read-write
	  STATUS current
	  DESCRIPTION
        "
        Set Software Nb 1 As Active :This
        OID, when set, loads the SW from
        bank1 into the PM. It must be followed
        by a reset.  <Help>  This controls
        selects the first SW bank as the
        active bank for the next module
        reset
        "
	  ::= { pm10010mpCtrlswMgnt 5 }



pm10010mpCtrlWarmReset OBJECT-TYPE
	  SYNTAX EkiOnOff
	  MAX-ACCESS read-write
	  STATUS current
	  DESCRIPTION
        "
        PM Warm Reset :This OID, when
         set, causes a warm reset of the
        PM. This reset is not traffic affecting,
        and the configuration of PM remains
        unchanged.  <Help>  This control
        initiates a warm reset of the module.
        "
	  ::= { pm10010mpCtrlswMgnt 3 }



pm10010mpCtrlColdReset OBJECT-TYPE
	  SYNTAX EkiOnOff
	  MAX-ACCESS read-write
	  STATUS current
	  DESCRIPTION
        "
        PM Cold Reset :This OID, when
         set, causes a cold reset of the
        PM. This reset is traffic affecting,
        and the configuration of PM is
         reloaded on start-up.  <Help>
          This control initiates a cold
        reset of the module.
        "
	  ::= { pm10010mpCtrlswMgnt 2 }



--- *****************************************************
---     LEAF for the gwMgnt article
--- *****************************************************
pm10010mpCtrlgwMgnt OBJECT IDENTIFIER ::= { pm10010mpCtrlOther 6 }




pm10010mpCtrlLoadGwBank4 OBJECT-TYPE
	  SYNTAX EkiOnOff
	  MAX-ACCESS read-write
	  STATUS current
	  DESCRIPTION
        "
        Set Gateware Nb 4 As Active :This
        OID, when set, loads the GW from
        bank4 (Flash) into the PM. It is
        followed by an automatic gateware
        cold reset.
        "
	  ::= { pm10010mpCtrlgwMgnt 8 }



pm10010mpCtrlLoadGwBank3 OBJECT-TYPE
	  SYNTAX EkiOnOff
	  MAX-ACCESS read-write
	  STATUS current
	  DESCRIPTION
        "
        Set Gateware Nb 3 As Active :This
        OID, when set, loads the GW from
        bank3 (Flash) into the PM. It is
        followed by an automatic gateware
        cold reset.  <Help>  This controls
        initiates a cold reset of the module
        and select the third GW bank as
        the active bank
        "
	  ::= { pm10010mpCtrlgwMgnt 7 }



pm10010mpCtrlLoadGwBank2 OBJECT-TYPE
	  SYNTAX EkiOnOff
	  MAX-ACCESS read-write
	  STATUS current
	  DESCRIPTION
        "
        Set Gateware Nb 2 As Active :This
        OID, when set, loads the GW from
        bank2 (Flash) into the PM. It is
        followed by an automatic gateware
        cold reset.
        "
	  ::= { pm10010mpCtrlgwMgnt 6 }



pm10010mpCtrlLoadGwBank1 OBJECT-TYPE
	  SYNTAX EkiOnOff
	  MAX-ACCESS read-write
	  STATUS current
	  DESCRIPTION
        "
        Set Gateware Nb 1 As Active :This
        OID, when set, loads the GW from
        bank1 (Flash) into the PM. It is
        followed by an automatic gateware
        cold reset.  <Help>  This controls
        initiates a cold reset of the module
        and select the first GW bank as
        the active bank
        "
	  ::= { pm10010mpCtrlgwMgnt 5 }



pm10010mpCtrlCurrentGwReset OBJECT-TYPE
	  SYNTAX EkiOnOff
	  MAX-ACCESS read-write
	  STATUS current
	  DESCRIPTION
        "
        Active Gateware Reset :This OID,
        when set, resets the active gateware.
        It is traffic affecting.
        "
	  ::= { pm10010mpCtrlgwMgnt 1 }



--- *********************************************************
---     TABLE for the pm10010mpCtrlaccessLoop articles
--- *********************************************************

pm10010mpCtrlaccessLoopTable OBJECT-TYPE
	SYNTAX  SEQUENCE OF Pm10010mpCtrlaccessLoopEntry
	MAX-ACCESS not-accessible
	STATUS current
	DESCRIPTION
        "
        List of pm10010mpCtrlaccessLoop
        Article
        "
	::= { pm10010mpCtrlClient 16 }


pm10010mpCtrlaccessLoopEntry OBJECT-TYPE
	SYNTAX Pm10010mpCtrlaccessLoopEntry
	MAX-ACCESS not-accessible
	STATUS current
	DESCRIPTION
        "
        Row definition for the pm10010mpCtrlaccessLoop
        table
        "
	INDEX   { pm10010mpCtrlaccessLoopIndex }
	::= { pm10010mpCtrlaccessLoopTable 1 }


Pm10010mpCtrlaccessLoopEntry ::=
	SEQUENCE {
	pm10010mpCtrlaccessLoopIndex
		INTEGER,
	pm10010mpCtrlaccessLoopPortn
		EkiState
	}


pm10010mpCtrlaccessLoopIndex OBJECT-TYPE
	SYNTAX  INTEGER(0..128)
	MAX-ACCESS  read-only
	STATUS current
	DESCRIPTION
        "
        Index definition for the pm10010mpCtrlaccessLoop
        table
        "
	::= { pm10010mpCtrlaccessLoopEntry 1 }


pm10010mpCtrlaccessLoopPortn OBJECT-TYPE
	SYNTAX  EkiState
	MAX-ACCESS read-write
	STATUS current
	DESCRIPTION
        "
        Client Facility Loopback :This
        OID, when set at '1' puts the client
        port in loopback, looping the received
        10 Gb/s signal on the transmit
         10 Gb/s output.  <Help> This control
        enables the Out Loopback on the
        client port, looping the client
        input signal on the client output
        "
	::= { pm10010mpCtrlaccessLoopEntry 2 }


--- *********************************************************
---     TABLE for the pm10010mpCtrlclientLoopToLine articles
--- *********************************************************

pm10010mpCtrlclientLoopToLineTable OBJECT-TYPE
	SYNTAX  SEQUENCE OF Pm10010mpCtrlclientLoopToLineEntry
	MAX-ACCESS not-accessible
	STATUS current
	DESCRIPTION
        "
        List of pm10010mpCtrlclientLoopToLine
        Article
        "
	::= { pm10010mpCtrlClient 17 }


pm10010mpCtrlclientLoopToLineEntry OBJECT-TYPE
	SYNTAX Pm10010mpCtrlclientLoopToLineEntry
	MAX-ACCESS not-accessible
	STATUS current
	DESCRIPTION
        "
        Row definition for the pm10010mpCtrlclientLoopToLine
        table
        "
	INDEX   { pm10010mpCtrlclientLoopToLineIndex }
	::= { pm10010mpCtrlclientLoopToLineTable 1 }


Pm10010mpCtrlclientLoopToLineEntry ::=
	SEQUENCE {
	pm10010mpCtrlclientLoopToLineIndex
		INTEGER,
	pm10010mpCtrlclientLoopToLinePortn
		EkiState
	}


pm10010mpCtrlclientLoopToLineIndex OBJECT-TYPE
	SYNTAX  INTEGER(0..128)
	MAX-ACCESS  read-only
	STATUS current
	DESCRIPTION
        "
        Index definition for the pm10010mpCtrlclientLoopToLine
        table
        "
	::= { pm10010mpCtrlclientLoopToLineEntry 1 }


pm10010mpCtrlclientLoopToLinePortn OBJECT-TYPE
	SYNTAX  EkiState
	MAX-ACCESS read-write
	STATUS current
	DESCRIPTION
        "
        Client Terminal Loopback :This
        OID, when set, puts the client
         port in loop back, looping the
        10 Gb/s output signal on the 10
        Gb/s input.<Help> This control
         enables the In Loopback on the
        client port, looping the client
        output signal on the client input
        "
	::= { pm10010mpCtrlclientLoopToLineEntry 2 }


--- *********************************************************
---     TABLE for the pm10010mpCtrlcsfUpIns articles
--- *********************************************************

pm10010mpCtrlcsfUpInsTable OBJECT-TYPE
	SYNTAX  SEQUENCE OF Pm10010mpCtrlcsfUpInsEntry
	MAX-ACCESS not-accessible
	STATUS current
	DESCRIPTION
        "
        List of pm10010mpCtrlcsfUpIns
         Article
        "
	::= { pm10010mpCtrlClient 21 }


pm10010mpCtrlcsfUpInsEntry OBJECT-TYPE
	SYNTAX Pm10010mpCtrlcsfUpInsEntry
	MAX-ACCESS not-accessible
	STATUS current
	DESCRIPTION
        "
        Row definition for the pm10010mpCtrlcsfUpIns
        table
        "
	INDEX   { pm10010mpCtrlcsfUpInsIndex }
	::= { pm10010mpCtrlcsfUpInsTable 1 }


Pm10010mpCtrlcsfUpInsEntry ::=
	SEQUENCE {
	pm10010mpCtrlcsfUpInsIndex
		INTEGER,
	pm10010mpCtrlcsfUpInsPortn
		EkiState
	}


pm10010mpCtrlcsfUpInsIndex OBJECT-TYPE
	SYNTAX  INTEGER(0..128)
	MAX-ACCESS  read-only
	STATUS current
	DESCRIPTION
        "
        Index definition for the pm10010mpCtrlcsfUpIns
        table
        "
	::= { pm10010mpCtrlcsfUpInsEntry 1 }


pm10010mpCtrlcsfUpInsPortn OBJECT-TYPE
	SYNTAX  EkiState
	MAX-ACCESS read-write
	STATUS current
	DESCRIPTION
        "
        Client Signal Fail Insertion :This
        OID, when set, inserts  a client
        signal fail in the upstream client
        Port.  <Help>  This control inserts
        a Client Signal Fail for the client
        port
        "
	::= { pm10010mpCtrlcsfUpInsEntry 2 }


--- *********************************************************
---     TABLE for the pm10010mpCtrlcaisDwIns articles
--- *********************************************************

pm10010mpCtrlcaisDwInsTable OBJECT-TYPE
	SYNTAX  SEQUENCE OF Pm10010mpCtrlcaisDwInsEntry
	MAX-ACCESS not-accessible
	STATUS current
	DESCRIPTION
        "
        List of pm10010mpCtrlcaisDwIns
        Article
        "
	::= { pm10010mpCtrlClient 22 }


pm10010mpCtrlcaisDwInsEntry OBJECT-TYPE
	SYNTAX Pm10010mpCtrlcaisDwInsEntry
	MAX-ACCESS not-accessible
	STATUS current
	DESCRIPTION
        "
        Row definition for the pm10010mpCtrlcaisDwIns
        table
        "
	INDEX   { pm10010mpCtrlcaisDwInsIndex }
	::= { pm10010mpCtrlcaisDwInsTable 1 }


Pm10010mpCtrlcaisDwInsEntry ::=
	SEQUENCE {
	pm10010mpCtrlcaisDwInsIndex
		INTEGER,
	pm10010mpCtrlcaisDwInsPortn
		EkiState
	}


pm10010mpCtrlcaisDwInsIndex OBJECT-TYPE
	SYNTAX  INTEGER(0..128)
	MAX-ACCESS  read-only
	STATUS current
	DESCRIPTION
        "
        Index definition for the pm10010mpCtrlcaisDwIns
        table
        "
	::= { pm10010mpCtrlcaisDwInsEntry 1 }


pm10010mpCtrlcaisDwInsPortn OBJECT-TYPE
	SYNTAX  EkiState
	MAX-ACCESS read-write
	STATUS current
	DESCRIPTION
        "
        Client AIS Insertion :This OID,
        when set, inserts a client AIS
         on the downstream client Port.
         <Help>  This control inserts a
        Client AIS for the client port
        "
	::= { pm10010mpCtrlcaisDwInsEntry 2 }


--- *********************************************************
---     TABLE for the pm10010mpCtrlcommAccessLoop articles
--- *********************************************************

pm10010mpCtrlcommAccessLoopTable OBJECT-TYPE
	SYNTAX  SEQUENCE OF Pm10010mpCtrlcommAccessLoopEntry
	MAX-ACCESS not-accessible
	STATUS current
	DESCRIPTION
        "
        List of pm10010mpCtrlcommAccessLoop
        Article
        "
	::= { pm10010mpCtrlLine 64 }


pm10010mpCtrlcommAccessLoopEntry OBJECT-TYPE
	SYNTAX Pm10010mpCtrlcommAccessLoopEntry
	MAX-ACCESS not-accessible
	STATUS current
	DESCRIPTION
        "
        Row definition for the pm10010mpCtrlcommAccessLoop
        table
        "
	INDEX   { pm10010mpCtrlcommAccessLoopIndex }
	::= { pm10010mpCtrlcommAccessLoopTable 1 }


Pm10010mpCtrlcommAccessLoopEntry ::=
	SEQUENCE {
	pm10010mpCtrlcommAccessLoopIndex
		INTEGER,
	pm10010mpCtrlcommAccessLoopPortn
		EkiState
	}


pm10010mpCtrlcommAccessLoopIndex OBJECT-TYPE
	SYNTAX  INTEGER(0..128)
	MAX-ACCESS  read-only
	STATUS current
	DESCRIPTION
        "
        Index definition for the pm10010mpCtrlcommAccessLoop
        table
        "
	::= { pm10010mpCtrlcommAccessLoopEntry 1 }


pm10010mpCtrlcommAccessLoopPortn OBJECT-TYPE
	SYNTAX  EkiState
	MAX-ACCESS read-write
	STATUS current
	DESCRIPTION
        "
        Line Terminal Loopback :This OID,
        when set, puts the module in common
        access loop back, looping the 100
        Gb/s output signal on the 100 Gb/s
        input.<Help> This control enables
        the In Loopback on the line port,
        looping the 100 Gb/s output signal
        on the 100 Gb/s input
        "
	::= { pm10010mpCtrlcommAccessLoopEntry 2 }


--- *********************************************************
---     TABLE for the pm10010mpCtrllineLoop articles
--- *********************************************************

pm10010mpCtrllineLoopTable OBJECT-TYPE
	SYNTAX  SEQUENCE OF Pm10010mpCtrllineLoopEntry
	MAX-ACCESS not-accessible
	STATUS current
	DESCRIPTION
        "
        List of pm10010mpCtrllineLoop
         Article
        "
	::= { pm10010mpCtrlLine 66 }


pm10010mpCtrllineLoopEntry OBJECT-TYPE
	SYNTAX Pm10010mpCtrllineLoopEntry
	MAX-ACCESS not-accessible
	STATUS current
	DESCRIPTION
        "
        Row definition for the pm10010mpCtrllineLoop
        table
        "
	INDEX   { pm10010mpCtrllineLoopIndex }
	::= { pm10010mpCtrllineLoopTable 1 }


Pm10010mpCtrllineLoopEntry ::=
	SEQUENCE {
	pm10010mpCtrllineLoopIndex
		INTEGER,
	pm10010mpCtrllineLoopPortn
		EkiState
	}


pm10010mpCtrllineLoopIndex OBJECT-TYPE
	SYNTAX  INTEGER(0..128)
	MAX-ACCESS  read-only
	STATUS current
	DESCRIPTION
        "
        Index definition for the pm10010mpCtrllineLoop
        table
        "
	::= { pm10010mpCtrllineLoopEntry 1 }


pm10010mpCtrllineLoopPortn OBJECT-TYPE
	SYNTAX  EkiState
	MAX-ACCESS read-write
	STATUS current
	DESCRIPTION
        "
        Line Facility Loopback :This OID,
        when set at '1' puts the module
        in line loopback mode, looping
         the received 100 Gb/s signal on
        the transmit 100 Gb/s output. The
        Upstream part of the module is
         timed on the 100 Gb/s recovered
        clock in that case.<Help> This
         control enables the Out Loopback
        on the line port, looping the 100
        Gb/s input signal on the 100 Gb/s
        output
        "
	::= { pm10010mpCtrllineLoopEntry 2 }


--- *********************************************************
---     TABLE for the pm10010mpCtrlfecDisable articles
--- *********************************************************

pm10010mpCtrlfecDisableTable OBJECT-TYPE
	SYNTAX  SEQUENCE OF Pm10010mpCtrlfecDisableEntry
	MAX-ACCESS not-accessible
	STATUS current
	DESCRIPTION
        "
        List of pm10010mpCtrlfecDisable
        Article
        "
	::= { pm10010mpCtrlLine 69 }


pm10010mpCtrlfecDisableEntry OBJECT-TYPE
	SYNTAX Pm10010mpCtrlfecDisableEntry
	MAX-ACCESS not-accessible
	STATUS current
	DESCRIPTION
        "
        Row definition for the pm10010mpCtrlfecDisable
        table
        "
	INDEX   { pm10010mpCtrlfecDisableIndex }
	::= { pm10010mpCtrlfecDisableTable 1 }


Pm10010mpCtrlfecDisableEntry ::=
	SEQUENCE {
	pm10010mpCtrlfecDisableIndex
		INTEGER,
	pm10010mpCtrlfecDisablePortn
		EkiState
	}


pm10010mpCtrlfecDisableIndex OBJECT-TYPE
	SYNTAX  INTEGER(0..128)
	MAX-ACCESS  read-only
	STATUS current
	DESCRIPTION
        "
        Index definition for the pm10010mpCtrlfecDisable
        table
        "
	::= { pm10010mpCtrlfecDisableEntry 1 }


pm10010mpCtrlfecDisablePortn OBJECT-TYPE
	SYNTAX  EkiState
	MAX-ACCESS read-write
	STATUS current
	DESCRIPTION
        "
        Forward Error Correction Inhibition
        :This OID, when set, inhibits the
        Forward Error Correction feature
        on the line input  <Help>  This
        control enables/disables the Forward
        Error Correction on the line interface
        "
	::= { pm10010mpCtrlfecDisableEntry 2 }


--- *****************************************************
---     LEAF for the ledTest article
--- *****************************************************
pm10010mpCtrlledTest OBJECT IDENTIFIER ::= { pm10010mpCtrlOther 192 }




pm10010mpCtrlLedOff OBJECT-TYPE
	  SYNTAX EkiOnOff
	  MAX-ACCESS read-write
	  STATUS current
	  DESCRIPTION
        "
        Leds Off :This OID switches off
        all the Leds as a test feature.
         <Help>  This control initiates
        a test leds turning all the LEDs
        to OFF
        "
	  ::= { pm10010mpCtrlledTest 3 }



pm10010mpCtrlRedLed OBJECT-TYPE
	  SYNTAX EkiOnOff
	  MAX-ACCESS read-write
	  STATUS current
	  DESCRIPTION
        "
        Red Leds Test :This OID switches
        on all the red Leds as a test feature.
         <Help>  This control initiates
        a test leds turning all the LEDs
        to red
        "
	  ::= { pm10010mpCtrlledTest 2 }



pm10010mpCtrlGreenLed OBJECT-TYPE
	  SYNTAX EkiOnOff
	  MAX-ACCESS read-write
	  STATUS current
	  DESCRIPTION
        "
        Green Leds Test :This OID switches
        on all the green Leds as a test
        feature.  <Help>  This control
         initiates a test leds turning
         all the LEDs to green
        "
	  ::= { pm10010mpCtrlledTest 1 }



--- *****************************************************
---     LEAF for the initSwitchMarvell article
--- *****************************************************
pm10010mpCtrlinitSwitchMarvell OBJECT IDENTIFIER ::= { pm10010mpCtrlOther 201 }




pm10010mpCtrlInitSwitchMarvell OBJECT-TYPE
	  SYNTAX EkiOnOff
	  MAX-ACCESS read-write
	  STATUS current
	  DESCRIPTION
        "
        Switch Initialization :This OID
        operates an initialization of the
        switch managed through the module
         <Help>  This control activates
        an initialization of the switch
        managed through the module
        "
	  ::= { pm10010mpCtrlinitSwitchMarvell 1 }



--- *********************************************************
---     TABLE for the pm10010mpCtrlmsaLineLoop articles
--- *********************************************************

pm10010mpCtrlmsaLineLoopTable OBJECT-TYPE
	SYNTAX  SEQUENCE OF Pm10010mpCtrlmsaLineLoopEntry
	MAX-ACCESS not-accessible
	STATUS current
	DESCRIPTION
        "
        List of pm10010mpCtrlmsaLineLoop
        Article
        "
	::= { pm10010mpCtrlLine 209 }


pm10010mpCtrlmsaLineLoopEntry OBJECT-TYPE
	SYNTAX Pm10010mpCtrlmsaLineLoopEntry
	MAX-ACCESS not-accessible
	STATUS current
	DESCRIPTION
        "
        Row definition for the pm10010mpCtrlmsaLineLoop
        table
        "
	INDEX   { pm10010mpCtrlmsaLineLoopIndex }
	::= { pm10010mpCtrlmsaLineLoopTable 1 }


Pm10010mpCtrlmsaLineLoopEntry ::=
	SEQUENCE {
	pm10010mpCtrlmsaLineLoopIndex
		INTEGER,
	pm10010mpCtrlmsaLineLoopPortn
		EkiState
	}


pm10010mpCtrlmsaLineLoopIndex OBJECT-TYPE
	SYNTAX  INTEGER(0..128)
	MAX-ACCESS  read-only
	STATUS current
	DESCRIPTION
        "
        Index definition for the pm10010mpCtrlmsaLineLoop
        table
        "
	::= { pm10010mpCtrlmsaLineLoopEntry 1 }


pm10010mpCtrlmsaLineLoopPortn OBJECT-TYPE
	SYNTAX  EkiState
	MAX-ACCESS read-write
	STATUS current
	DESCRIPTION
        "
        MSA Line Loop :This OID operates
        a line loopback on the MSA Line
         <Help>  This control defines the
        line loop back of the line transceiver
        "
	::= { pm10010mpCtrlmsaLineLoopEntry 2 }


--- *********************************************************
---     TABLE for the pm10010mpCtrlmsaTxReset articles
--- *********************************************************

pm10010mpCtrlmsaTxResetTable OBJECT-TYPE
	SYNTAX  SEQUENCE OF Pm10010mpCtrlmsaTxResetEntry
	MAX-ACCESS not-accessible
	STATUS current
	DESCRIPTION
        "
        List of pm10010mpCtrlmsaTxReset
        Article
        "
	::= { pm10010mpCtrlLine 210 }


pm10010mpCtrlmsaTxResetEntry OBJECT-TYPE
	SYNTAX Pm10010mpCtrlmsaTxResetEntry
	MAX-ACCESS not-accessible
	STATUS current
	DESCRIPTION
        "
        Row definition for the pm10010mpCtrlmsaTxReset
        table
        "
	INDEX   { pm10010mpCtrlmsaTxResetIndex }
	::= { pm10010mpCtrlmsaTxResetTable 1 }


Pm10010mpCtrlmsaTxResetEntry ::=
	SEQUENCE {
	pm10010mpCtrlmsaTxResetIndex
		INTEGER,
	pm10010mpCtrlmsaTxResetPortn
		EkiState
	}


pm10010mpCtrlmsaTxResetIndex OBJECT-TYPE
	SYNTAX  INTEGER(0..128)
	MAX-ACCESS  read-only
	STATUS current
	DESCRIPTION
        "
        Index definition for the pm10010mpCtrlmsaTxReset
        table
        "
	::= { pm10010mpCtrlmsaTxResetEntry 1 }


pm10010mpCtrlmsaTxResetPortn OBJECT-TYPE
	SYNTAX  EkiState
	MAX-ACCESS read-write
	STATUS current
	DESCRIPTION
        "
        Line MSA TX Reset :This OID resets
        the TX portion of the MSA line
         module  <Help > This control
         initiates a reset of the transmitting
        side
        "
	::= { pm10010mpCtrlmsaTxResetEntry 2 }


--- *********************************************************
---     TABLE for the pm10010mpCtrlmsaRxReset articles
--- *********************************************************

pm10010mpCtrlmsaRxResetTable OBJECT-TYPE
	SYNTAX  SEQUENCE OF Pm10010mpCtrlmsaRxResetEntry
	MAX-ACCESS not-accessible
	STATUS current
	DESCRIPTION
        "
        List of pm10010mpCtrlmsaRxReset
        Article
        "
	::= { pm10010mpCtrlLine 211 }


pm10010mpCtrlmsaRxResetEntry OBJECT-TYPE
	SYNTAX Pm10010mpCtrlmsaRxResetEntry
	MAX-ACCESS not-accessible
	STATUS current
	DESCRIPTION
        "
        Row definition for the pm10010mpCtrlmsaRxReset
        table
        "
	INDEX   { pm10010mpCtrlmsaRxResetIndex }
	::= { pm10010mpCtrlmsaRxResetTable 1 }


Pm10010mpCtrlmsaRxResetEntry ::=
	SEQUENCE {
	pm10010mpCtrlmsaRxResetIndex
		INTEGER,
	pm10010mpCtrlmsaRxResetPortn
		EkiState
	}


pm10010mpCtrlmsaRxResetIndex OBJECT-TYPE
	SYNTAX  INTEGER(0..128)
	MAX-ACCESS  read-only
	STATUS current
	DESCRIPTION
        "
        Index definition for the pm10010mpCtrlmsaRxReset
        table
        "
	::= { pm10010mpCtrlmsaRxResetEntry 1 }


pm10010mpCtrlmsaRxResetPortn OBJECT-TYPE
	SYNTAX  EkiState
	MAX-ACCESS read-write
	STATUS current
	DESCRIPTION
        "
        Line MSA RX Reset :This OID resets
        the RX portion of the MSA line
         module  <Help > This control
         initiates a reset of the receiving
        side
        "
	::= { pm10010mpCtrlmsaRxResetEntry 2 }


--- *********************************************************
---     TABLE for the pm10010mpCtrlmsaShutdown articles
--- *********************************************************

pm10010mpCtrlmsaShutdownTable OBJECT-TYPE
	SYNTAX  SEQUENCE OF Pm10010mpCtrlmsaShutdownEntry
	MAX-ACCESS not-accessible
	STATUS current
	DESCRIPTION
        "
        List of pm10010mpCtrlmsaShutdown
        Article
        "
	::= { pm10010mpCtrlLine 212 }


pm10010mpCtrlmsaShutdownEntry OBJECT-TYPE
	SYNTAX Pm10010mpCtrlmsaShutdownEntry
	MAX-ACCESS not-accessible
	STATUS current
	DESCRIPTION
        "
        Row definition for the pm10010mpCtrlmsaShutdown
        table
        "
	INDEX   { pm10010mpCtrlmsaShutdownIndex }
	::= { pm10010mpCtrlmsaShutdownTable 1 }


Pm10010mpCtrlmsaShutdownEntry ::=
	SEQUENCE {
	pm10010mpCtrlmsaShutdownIndex
		INTEGER,
	pm10010mpCtrlmsaShutdownPortn
		EkiState
	}


pm10010mpCtrlmsaShutdownIndex OBJECT-TYPE
	SYNTAX  INTEGER(0..128)
	MAX-ACCESS  read-only
	STATUS current
	DESCRIPTION
        "
        Index definition for the pm10010mpCtrlmsaShutdown
        table
        "
	::= { pm10010mpCtrlmsaShutdownEntry 1 }


pm10010mpCtrlmsaShutdownPortn OBJECT-TYPE
	SYNTAX  EkiState
	MAX-ACCESS read-write
	STATUS current
	DESCRIPTION
        "
        Line MSA Shutdown :This OID enters
        a process to shutdown the MSA line
        module  <Help > This control  initiates
        a shutdown of the module
        "
	::= { pm10010mpCtrlmsaShutdownEntry 2 }


--- *****************************************************
---     LEAF for the resetCount article
--- *****************************************************
pm10010mpCtrlresetCount OBJECT IDENTIFIER ::= { pm10010mpCtrlOther 259 }




pm10010mpCtrlResetcount OBJECT-TYPE
	  SYNTAX EkiOnOff
	  MAX-ACCESS read-write
	  STATUS current
	  DESCRIPTION
        "
        Module Count Global Reset :This
        OID resets all the errors counters
        on the module  <Help > This control
         initiates a reset of the errors
        counters on the module
        "
	  ::= { pm10010mpCtrlresetCount 1 }



--- *****************************************************
---     LEAF for the resetRmon article
--- *****************************************************
pm10010mpCtrlresetRmon OBJECT IDENTIFIER ::= { pm10010mpCtrlOther 260 }




pm10010mpCtrlResetrmon OBJECT-TYPE
	  SYNTAX EkiOnOff
	  MAX-ACCESS read-write
	  STATUS current
	  DESCRIPTION
        "
        Module Rmon Global Reset :This
        OID resets all the Rmon counters
        on the module  <Help > This control
         initiates a reset of the Rmon
         counters on the module
        "
	  ::= { pm10010mpCtrlresetRmon 1 }



--- *****************************************************
---     LEAF for the resetMeasurements article
--- *****************************************************
pm10010mpCtrlresetMeasurements OBJECT IDENTIFIER ::= { pm10010mpCtrlOther 261 }




pm10010mpCtrlResetmeasurements OBJECT-TYPE
	  SYNTAX EkiOnOff
	  MAX-ACCESS read-write
	  STATUS current
	  DESCRIPTION
        "
        Management Meas Global Reset :This
        OID resets some measurements on
        the management  <Help > This control
         initiates a reset of some measurements
        on the management
        "
	  ::= { pm10010mpCtrlresetMeasurements 1 }








--- *****************************************************
--- $$$$$$$$$$$$$$$$$$$$$$$$$$$$$$$$$$$$$$$$$$$$$$$$$$$$$
---     COUNTERS
--- $$$$$$$$$$$$$$$$$$$$$$$$$$$$$$$$$$$$$$$$$$$$$$$$$$$$$
--- *****************************************************



--- *********************************************************
---     TABLE for the pm10010mpCntclientInputErrorCounterLaneOne articles
--- *********************************************************

pm10010mpCntclientInputErrorCounterLaneOneTable OBJECT-TYPE
	SYNTAX  SEQUENCE OF Pm10010mpCntclientInputErrorCounterLaneOneEntry
	MAX-ACCESS not-accessible
	STATUS current
	DESCRIPTION
        "
        List of pm10010mpCntclientInputErrorCounterLaneOne
        Article
        "
	::= { pm10010mpCntClient 16 }


pm10010mpCntclientInputErrorCounterLaneOneEntry OBJECT-TYPE
	SYNTAX Pm10010mpCntclientInputErrorCounterLaneOneEntry
	MAX-ACCESS not-accessible
	STATUS current
	DESCRIPTION
        "
        Row definition for the pm10010mpCntclientInputErrorCounterLaneOne
        table
        "
	INDEX   { pm10010mpCntclientInputErrorCounterLaneOneIndex }
	::= { pm10010mpCntclientInputErrorCounterLaneOneTable 1 }


Pm10010mpCntclientInputErrorCounterLaneOneEntry ::=
	SEQUENCE {
	pm10010mpCntclientInputErrorCounterLaneOneIndex
		INTEGER,
	pm10010mpCntclientInputErrorCounterLaneOneValuePortn
		Counter32,
	pm10010mpCntclientInputErrorCounterLaneOneErrorPortn
		EkiOnOff,
	pm10010mpCntclientInputErrorCounterLaneOneOverloadPortn
		EkiOnOff
	}


pm10010mpCntclientInputErrorCounterLaneOneIndex OBJECT-TYPE
	SYNTAX  INTEGER(0..128)
	MAX-ACCESS  read-only
	STATUS current
	DESCRIPTION
        "
        Index definition for the pm10010mpCntclientInputErrorCounterLaneOne
        table
        "
	::= { pm10010mpCntclientInputErrorCounterLaneOneEntry 1 }


pm10010mpCntclientInputErrorCounterLaneOneValuePortn OBJECT-TYPE
	SYNTAX  Counter32
	MAX-ACCESS read-only
	STATUS current
	DESCRIPTION
        "
        Client_Input_Error_Counter_Lane1
        :This counter is incremented each
        time a coding violation is detected
        on the host lane of the client
         transceiver <Help> This counter
        is incremented each time a coding
        violation is detected on the host
        lane of the client transceiver
        "
	::= { pm10010mpCntclientInputErrorCounterLaneOneEntry 2 }


pm10010mpCntclientInputErrorCounterLaneOneErrorPortn OBJECT-TYPE
	SYNTAX  EkiOnOff
	MAX-ACCESS read-only
	STATUS current
	DESCRIPTION
        "
        Client Input Counter Error :This
        OID when set indicates the rate
        adaptation removal counter value
        is invalid on Port
        "
	::= { pm10010mpCntclientInputErrorCounterLaneOneEntry 3 }


pm10010mpCntclientInputErrorCounterLaneOneOverloadPortn OBJECT-TYPE
	SYNTAX  EkiOnOff
	MAX-ACCESS read-only
	STATUS current
	DESCRIPTION
        "
        Client Input Counter Overload
         :This OID when set indicates a
        rate adaptation removal counter
        overload on Port
        "
	::= { pm10010mpCntclientInputErrorCounterLaneOneEntry 4 }


--- *********************************************************
---     TABLE for the pm10010mpCntclientInputErrorCounterLaneTwo articles
--- *********************************************************

pm10010mpCntclientInputErrorCounterLaneTwoTable OBJECT-TYPE
	SYNTAX  SEQUENCE OF Pm10010mpCntclientInputErrorCounterLaneTwoEntry
	MAX-ACCESS not-accessible
	STATUS current
	DESCRIPTION
        "
        List of pm10010mpCntclientInputErrorCounterLaneTwo
        Article
        "
	::= { pm10010mpCntClient 32 }


pm10010mpCntclientInputErrorCounterLaneTwoEntry OBJECT-TYPE
	SYNTAX Pm10010mpCntclientInputErrorCounterLaneTwoEntry
	MAX-ACCESS not-accessible
	STATUS current
	DESCRIPTION
        "
        Row definition for the pm10010mpCntclientInputErrorCounterLaneTwo
        table
        "
	INDEX   { pm10010mpCntclientInputErrorCounterLaneTwoIndex }
	::= { pm10010mpCntclientInputErrorCounterLaneTwoTable 1 }


Pm10010mpCntclientInputErrorCounterLaneTwoEntry ::=
	SEQUENCE {
	pm10010mpCntclientInputErrorCounterLaneTwoIndex
		INTEGER,
	pm10010mpCntclientInputErrorCounterLaneTwoValuePortn
		Counter32,
	pm10010mpCntclientInputErrorCounterLaneTwoErrorPortn
		EkiOnOff,
	pm10010mpCntclientInputErrorCounterLaneTwoOverloadPortn
		EkiOnOff
	}


pm10010mpCntclientInputErrorCounterLaneTwoIndex OBJECT-TYPE
	SYNTAX  INTEGER(0..128)
	MAX-ACCESS  read-only
	STATUS current
	DESCRIPTION
        "
        Index definition for the pm10010mpCntclientInputErrorCounterLaneTwo
        table
        "
	::= { pm10010mpCntclientInputErrorCounterLaneTwoEntry 1 }


pm10010mpCntclientInputErrorCounterLaneTwoValuePortn OBJECT-TYPE
	SYNTAX  Counter32
	MAX-ACCESS read-only
	STATUS current
	DESCRIPTION
        "
        Client_Input_Error_Counter_Lane2
        :This counter is incremented each
        time a coding violation is detected
        on the host lane of the client
         transceiver <Help> This counter
        is incremented each time a coding
        violation is detected on the host
        lane of the client transceiver
        "
	::= { pm10010mpCntclientInputErrorCounterLaneTwoEntry 2 }


pm10010mpCntclientInputErrorCounterLaneTwoErrorPortn OBJECT-TYPE
	SYNTAX  EkiOnOff
	MAX-ACCESS read-only
	STATUS current
	DESCRIPTION
        "
        Client Input Counter Error :This
        OID when set indicates the client
        error counter value is invalid
         on Port
        "
	::= { pm10010mpCntclientInputErrorCounterLaneTwoEntry 3 }


pm10010mpCntclientInputErrorCounterLaneTwoOverloadPortn OBJECT-TYPE
	SYNTAX  EkiOnOff
	MAX-ACCESS read-only
	STATUS current
	DESCRIPTION
        "
        Client Input Counter Overload
         :This OID when set indicates a
        client input error counter overload
        on Port
        "
	::= { pm10010mpCntclientInputErrorCounterLaneTwoEntry 4 }


--- *********************************************************
---     TABLE for the pm10010mpCntclientInputErrorCounter articles
--- *********************************************************

pm10010mpCntclientInputErrorCounterTable OBJECT-TYPE
	SYNTAX  SEQUENCE OF Pm10010mpCntclientInputErrorCounterEntry
	MAX-ACCESS not-accessible
	STATUS current
	DESCRIPTION
        "
        List of pm10010mpCntclientInputErrorCounter
        Article
        "
	::= { pm10010mpCntClient 80 }


pm10010mpCntclientInputErrorCounterEntry OBJECT-TYPE
	SYNTAX Pm10010mpCntclientInputErrorCounterEntry
	MAX-ACCESS not-accessible
	STATUS current
	DESCRIPTION
        "
        Row definition for the pm10010mpCntclientInputErrorCounter
        table
        "
	INDEX   { pm10010mpCntclientInputErrorCounterIndex }
	::= { pm10010mpCntclientInputErrorCounterTable 1 }


Pm10010mpCntclientInputErrorCounterEntry ::=
	SEQUENCE {
	pm10010mpCntclientInputErrorCounterIndex
		INTEGER,
	pm10010mpCntclientInputErrorCounterValuePortn
		Counter32,
	pm10010mpCntclientInputErrorCounterErrorPortn
		EkiOnOff,
	pm10010mpCntclientInputErrorCounterOverloadPortn
		EkiOnOff
	}


pm10010mpCntclientInputErrorCounterIndex OBJECT-TYPE
	SYNTAX  INTEGER(0..128)
	MAX-ACCESS  read-only
	STATUS current
	DESCRIPTION
        "
        Index definition for the pm10010mpCntclientInputErrorCounter
        table
        "
	::= { pm10010mpCntclientInputErrorCounterEntry 1 }


pm10010mpCntclientInputErrorCounterValuePortn OBJECT-TYPE
	SYNTAX  Counter32
	MAX-ACCESS read-only
	STATUS current
	DESCRIPTION
        "
        Client Input Errors :This counter
        is increased each time a 10b/8b
        running disparity error is detected
        on the Client input stream  <Help>
         This counter gives the number
         of 10b/8b running disparity errors
        on the client port
        "
	::= { pm10010mpCntclientInputErrorCounterEntry 2 }


pm10010mpCntclientInputErrorCounterErrorPortn OBJECT-TYPE
	SYNTAX  EkiOnOff
	MAX-ACCESS read-only
	STATUS current
	DESCRIPTION
        "
        Client Counter Error :This OID
        when set indicates the client error
        counter value is invalid on Port
        "
	::= { pm10010mpCntclientInputErrorCounterEntry 3 }


pm10010mpCntclientInputErrorCounterOverloadPortn OBJECT-TYPE
	SYNTAX  EkiOnOff
	MAX-ACCESS read-only
	STATUS current
	DESCRIPTION
        "
        Client Counter Overload :This
         OID when set indicates a client
        input error counter overload on
        Port
        "
	::= { pm10010mpCntclientInputErrorCounterEntry 4 }


--- *********************************************************
---     TABLE for the pm10010mpCntclientCbipCounter articles
--- *********************************************************

pm10010mpCntclientCbipCounterTable OBJECT-TYPE
	SYNTAX  SEQUENCE OF Pm10010mpCntclientCbipCounterEntry
	MAX-ACCESS not-accessible
	STATUS current
	DESCRIPTION
        "
        List of pm10010mpCntclientCbipCounter
        Article
        "
	::= { pm10010mpCntClient 96 }


pm10010mpCntclientCbipCounterEntry OBJECT-TYPE
	SYNTAX Pm10010mpCntclientCbipCounterEntry
	MAX-ACCESS not-accessible
	STATUS current
	DESCRIPTION
        "
        Row definition for the pm10010mpCntclientCbipCounter
        table
        "
	INDEX   { pm10010mpCntclientCbipCounterIndex }
	::= { pm10010mpCntclientCbipCounterTable 1 }


Pm10010mpCntclientCbipCounterEntry ::=
	SEQUENCE {
	pm10010mpCntclientCbipCounterIndex
		INTEGER,
	pm10010mpCntclientCbipCounterValuePortn
		Counter32,
	pm10010mpCntclientCbipCounterErrorPortn
		EkiOnOff,
	pm10010mpCntclientCbipCounterOverloadPortn
		EkiOnOff
	}


pm10010mpCntclientCbipCounterIndex OBJECT-TYPE
	SYNTAX  INTEGER(0..128)
	MAX-ACCESS  read-only
	STATUS current
	DESCRIPTION
        "
        Index definition for the pm10010mpCntclientCbipCounter
        table
        "
	::= { pm10010mpCntclientCbipCounterEntry 1 }


pm10010mpCntclientCbipCounterValuePortn OBJECT-TYPE
	SYNTAX  Counter32
	MAX-ACCESS read-only
	STATUS current
	DESCRIPTION
        "
        Client Output Errors :This counter
        is incremented each time a CBIP
        parity error is detected on the
        Client output stream  <Help>  This
        counter gives the number of CBIP
        errors on the client port
        "
	::= { pm10010mpCntclientCbipCounterEntry 2 }


pm10010mpCntclientCbipCounterErrorPortn OBJECT-TYPE
	SYNTAX  EkiOnOff
	MAX-ACCESS read-only
	STATUS current
	DESCRIPTION
        "
        Client Counter Error :This OID
        when set indicates the CBIP error
        counter value is invalid on Port
        "
	::= { pm10010mpCntclientCbipCounterEntry 3 }


pm10010mpCntclientCbipCounterOverloadPortn OBJECT-TYPE
	SYNTAX  EkiOnOff
	MAX-ACCESS read-only
	STATUS current
	DESCRIPTION
        "
        Client CBIP Counter Overload :This
        OID when set indicates a CBIP error
        counter overload on Port
        "
	::= { pm10010mpCntclientCbipCounterEntry 4 }


--- *********************************************************
---     TABLE for the pm10010mpCntlocalLineSmBip8ErrorCounter articles
--- *********************************************************

pm10010mpCntlocalLineSmBip8ErrorCounterTable OBJECT-TYPE
	SYNTAX  SEQUENCE OF Pm10010mpCntlocalLineSmBip8ErrorCounterEntry
	MAX-ACCESS not-accessible
	STATUS current
	DESCRIPTION
        "
        List of pm10010mpCntlocalLineSmBip8ErrorCounter
        Article
        "
	::= { pm10010mpCntLine 192 }


pm10010mpCntlocalLineSmBip8ErrorCounterEntry OBJECT-TYPE
	SYNTAX Pm10010mpCntlocalLineSmBip8ErrorCounterEntry
	MAX-ACCESS not-accessible
	STATUS current
	DESCRIPTION
        "
        Row definition for the pm10010mpCntlocalLineSmBip8ErrorCounter
        table
        "
	INDEX   { pm10010mpCntlocalLineSmBip8ErrorCounterIndex }
	::= { pm10010mpCntlocalLineSmBip8ErrorCounterTable 1 }


Pm10010mpCntlocalLineSmBip8ErrorCounterEntry ::=
	SEQUENCE {
	pm10010mpCntlocalLineSmBip8ErrorCounterIndex
		INTEGER,
	pm10010mpCntlocalLineSmBip8ErrorCounterValuePortn
		Counter64,
	pm10010mpCntlocalLineSmBip8ErrorCounterErrorPortn
		EkiOnOff,
	pm10010mpCntlocalLineSmBip8ErrorCounterOverloadPortn
		EkiOnOff
	}


pm10010mpCntlocalLineSmBip8ErrorCounterIndex OBJECT-TYPE
	SYNTAX  INTEGER(0..128)
	MAX-ACCESS  read-only
	STATUS current
	DESCRIPTION
        "
        Index definition for the pm10010mpCntlocalLineSmBip8ErrorCounter
        table
        "
	::= { pm10010mpCntlocalLineSmBip8ErrorCounterEntry 1 }


pm10010mpCntlocalLineSmBip8ErrorCounterValuePortn OBJECT-TYPE
	SYNTAX  Counter64
	MAX-ACCESS read-only
	STATUS current
	DESCRIPTION
        "
        Line Input SM-BIP8 Errors :This
        OID gives the current Bit Error
        Rate (residual SM-BIP8 error) after
        FEC   <Help> This counter gives
        the current Bit Error Rate (residual
        SM-BIP8 error) after FEC
        "
	::= { pm10010mpCntlocalLineSmBip8ErrorCounterEntry 2 }


pm10010mpCntlocalLineSmBip8ErrorCounterErrorPortn OBJECT-TYPE
	SYNTAX  EkiOnOff
	MAX-ACCESS read-only
	STATUS current
	DESCRIPTION
        "
        Line Counter Error :This OID when
        set indicates the B1 error counter
        value is invalid on Port
        "
	::= { pm10010mpCntlocalLineSmBip8ErrorCounterEntry 3 }


pm10010mpCntlocalLineSmBip8ErrorCounterOverloadPortn OBJECT-TYPE
	SYNTAX  EkiOnOff
	MAX-ACCESS read-only
	STATUS current
	DESCRIPTION
        "
        Line Counter Overload :This OID
        when set indicates a B1 error counter
        overload on Port
        "
	::= { pm10010mpCntlocalLineSmBip8ErrorCounterEntry 4 }


--- *********************************************************
---     TABLE for the pm10010mpCntlocalLineFecCorrectedErrorsCounter articles
--- *********************************************************

pm10010mpCntlocalLineFecCorrectedErrorsCounterTable OBJECT-TYPE
	SYNTAX  SEQUENCE OF Pm10010mpCntlocalLineFecCorrectedErrorsCounterEntry
	MAX-ACCESS not-accessible
	STATUS current
	DESCRIPTION
        "
        List of pm10010mpCntlocalLineFecCorrectedErrorsCounter
        Article
        "
	::= { pm10010mpCntLine 193 }


pm10010mpCntlocalLineFecCorrectedErrorsCounterEntry OBJECT-TYPE
	SYNTAX Pm10010mpCntlocalLineFecCorrectedErrorsCounterEntry
	MAX-ACCESS not-accessible
	STATUS current
	DESCRIPTION
        "
        Row definition for the pm10010mpCntlocalLineFecCorrectedErrorsCounter
        table
        "
	INDEX   { pm10010mpCntlocalLineFecCorrectedErrorsCounterIndex }
	::= { pm10010mpCntlocalLineFecCorrectedErrorsCounterTable 1 }


Pm10010mpCntlocalLineFecCorrectedErrorsCounterEntry ::=
	SEQUENCE {
	pm10010mpCntlocalLineFecCorrectedErrorsCounterIndex
		INTEGER,
	pm10010mpCntlocalLineFecCorrectedErrorsCounterValuePortn
		Counter64,
	pm10010mpCntlocalLineFecCorrectedErrorsCounterErrorPortn
		EkiOnOff,
	pm10010mpCntlocalLineFecCorrectedErrorsCounterOverloadPortn
		EkiOnOff
	}


pm10010mpCntlocalLineFecCorrectedErrorsCounterIndex OBJECT-TYPE
	SYNTAX  INTEGER(0..128)
	MAX-ACCESS  read-only
	STATUS current
	DESCRIPTION
        "
        Index definition for the pm10010mpCntlocalLineFecCorrectedErrorsCounter
        table
        "
	::= { pm10010mpCntlocalLineFecCorrectedErrorsCounterEntry 1 }


pm10010mpCntlocalLineFecCorrectedErrorsCounterValuePortn OBJECT-TYPE
	SYNTAX  Counter64
	MAX-ACCESS read-only
	STATUS current
	DESCRIPTION
        "
        Line Input HD FEC Corrected Errors
        :This OID gives the current Bit
        Error Rate before the Hard Decision
        FEC  <Help> This counter gives
         the current Bit Error Rate before
        the Hard Decision FEC
        "
	::= { pm10010mpCntlocalLineFecCorrectedErrorsCounterEntry 2 }


pm10010mpCntlocalLineFecCorrectedErrorsCounterErrorPortn OBJECT-TYPE
	SYNTAX  EkiOnOff
	MAX-ACCESS read-only
	STATUS current
	DESCRIPTION
        "
        FEC Counter Error :This bit when
        set indicates the FEC corrected
        errors counter value is invalid
        on Line
        "
	::= { pm10010mpCntlocalLineFecCorrectedErrorsCounterEntry 3 }


pm10010mpCntlocalLineFecCorrectedErrorsCounterOverloadPortn OBJECT-TYPE
	SYNTAX  EkiOnOff
	MAX-ACCESS read-only
	STATUS current
	DESCRIPTION
        "
        FEC Counter Overload :This bit
        when set indicates a FEC corrected
        errors counter overload on Line
        "
	::= { pm10010mpCntlocalLineFecCorrectedErrorsCounterEntry 4 }


--- *********************************************************
---     TABLE for the pm10010mpCntremoteLineSmBip8ErrorCounter articles
--- *********************************************************

pm10010mpCntremoteLineSmBip8ErrorCounterTable OBJECT-TYPE
	SYNTAX  SEQUENCE OF Pm10010mpCntremoteLineSmBip8ErrorCounterEntry
	MAX-ACCESS not-accessible
	STATUS current
	DESCRIPTION
        "
        List of pm10010mpCntremoteLineSmBip8ErrorCounter
        Article
        "
	::= { pm10010mpCntLine 194 }


pm10010mpCntremoteLineSmBip8ErrorCounterEntry OBJECT-TYPE
	SYNTAX Pm10010mpCntremoteLineSmBip8ErrorCounterEntry
	MAX-ACCESS not-accessible
	STATUS current
	DESCRIPTION
        "
        Row definition for the pm10010mpCntremoteLineSmBip8ErrorCounter
        table
        "
	INDEX   { pm10010mpCntremoteLineSmBip8ErrorCounterIndex }
	::= { pm10010mpCntremoteLineSmBip8ErrorCounterTable 1 }


Pm10010mpCntremoteLineSmBip8ErrorCounterEntry ::=
	SEQUENCE {
	pm10010mpCntremoteLineSmBip8ErrorCounterIndex
		INTEGER,
	pm10010mpCntremoteLineSmBip8ErrorCounterValuePortn
		Counter64,
	pm10010mpCntremoteLineSmBip8ErrorCounterErrorPortn
		EkiOnOff,
	pm10010mpCntremoteLineSmBip8ErrorCounterOverloadPortn
		EkiOnOff
	}


pm10010mpCntremoteLineSmBip8ErrorCounterIndex OBJECT-TYPE
	SYNTAX  INTEGER(0..128)
	MAX-ACCESS  read-only
	STATUS current
	DESCRIPTION
        "
        Index definition for the pm10010mpCntremoteLineSmBip8ErrorCounter
        table
        "
	::= { pm10010mpCntremoteLineSmBip8ErrorCounterEntry 1 }


pm10010mpCntremoteLineSmBip8ErrorCounterValuePortn OBJECT-TYPE
	SYNTAX  Counter64
	MAX-ACCESS read-only
	STATUS current
	DESCRIPTION
        "
        Remote SM BIP8 :This OID gives
        the current Bit Error Rate (residual
        SM-BIP8 error) after FEC on the
        remote side  <Help> This counter
        gives the current Bit Error Rate
        (residual SM-BIP8 error) after
         FEC on the remote side
        "
	::= { pm10010mpCntremoteLineSmBip8ErrorCounterEntry 2 }


pm10010mpCntremoteLineSmBip8ErrorCounterErrorPortn OBJECT-TYPE
	SYNTAX  EkiOnOff
	MAX-ACCESS read-only
	STATUS current
	DESCRIPTION
        "
        Remote Counter Error :
        "
	::= { pm10010mpCntremoteLineSmBip8ErrorCounterEntry 3 }


pm10010mpCntremoteLineSmBip8ErrorCounterOverloadPortn OBJECT-TYPE
	SYNTAX  EkiOnOff
	MAX-ACCESS read-only
	STATUS current
	DESCRIPTION
        "
        Remote Counter Overload :
        "
	::= { pm10010mpCntremoteLineSmBip8ErrorCounterEntry 4 }


--- *********************************************************
---     TABLE for the pm10010mpCntlineDfrmTimCnt articles
--- *********************************************************

pm10010mpCntlineDfrmTimCntTable OBJECT-TYPE
	SYNTAX  SEQUENCE OF Pm10010mpCntlineDfrmTimCntEntry
	MAX-ACCESS not-accessible
	STATUS current
	DESCRIPTION
        "
        List of pm10010mpCntlineDfrmTimCnt
        Article
        "
	::= { pm10010mpCntLine 195 }


pm10010mpCntlineDfrmTimCntEntry OBJECT-TYPE
	SYNTAX Pm10010mpCntlineDfrmTimCntEntry
	MAX-ACCESS not-accessible
	STATUS current
	DESCRIPTION
        "
        Row definition for the pm10010mpCntlineDfrmTimCnt
        table
        "
	INDEX   { pm10010mpCntlineDfrmTimCntIndex }
	::= { pm10010mpCntlineDfrmTimCntTable 1 }


Pm10010mpCntlineDfrmTimCntEntry ::=
	SEQUENCE {
	pm10010mpCntlineDfrmTimCntIndex
		INTEGER,
	pm10010mpCntlineDfrmTimCntValuePortn
		Counter64,
	pm10010mpCntlineDfrmTimCntErrorPortn
		EkiOnOff,
	pm10010mpCntlineDfrmTimCntOverloadPortn
		EkiOnOff
	}


pm10010mpCntlineDfrmTimCntIndex OBJECT-TYPE
	SYNTAX  INTEGER(0..128)
	MAX-ACCESS  read-only
	STATUS current
	DESCRIPTION
        "
        Index definition for the pm10010mpCntlineDfrmTimCnt
        table
        "
	::= { pm10010mpCntlineDfrmTimCntEntry 1 }


pm10010mpCntlineDfrmTimCntValuePortn OBJECT-TYPE
	SYNTAX  Counter64
	MAX-ACCESS read-only
	STATUS current
	DESCRIPTION
        "
        Line Timer Counter :
        "
	::= { pm10010mpCntlineDfrmTimCntEntry 2 }


pm10010mpCntlineDfrmTimCntErrorPortn OBJECT-TYPE
	SYNTAX  EkiOnOff
	MAX-ACCESS read-only
	STATUS current
	DESCRIPTION
        "
        Line Counter Error :This OID when
        set indicates the deframer timer
        counter value is invalid on Port
        "
	::= { pm10010mpCntlineDfrmTimCntEntry 3 }


pm10010mpCntlineDfrmTimCntOverloadPortn OBJECT-TYPE
	SYNTAX  EkiOnOff
	MAX-ACCESS read-only
	STATUS current
	DESCRIPTION
        "
        Line Counter Overload :This OID
        when set indicates a deframer timer
        counter overload on Port
        "
	::= { pm10010mpCntlineDfrmTimCntEntry 4 }


--- *********************************************************
---     TABLE for the pm10010mpCntlocalLineTrscvFecCorrectedErrorCounter articles
--- *********************************************************

pm10010mpCntlocalLineTrscvFecCorrectedErrorCounterTable OBJECT-TYPE
	SYNTAX  SEQUENCE OF Pm10010mpCntlocalLineTrscvFecCorrectedErrorCounterEntry
	MAX-ACCESS not-accessible
	STATUS current
	DESCRIPTION
        "
        List of pm10010mpCntlocalLineTrscvFecCorrectedErrorCounter
        Article
        "
	::= { pm10010mpCntLine 196 }


pm10010mpCntlocalLineTrscvFecCorrectedErrorCounterEntry OBJECT-TYPE
	SYNTAX Pm10010mpCntlocalLineTrscvFecCorrectedErrorCounterEntry
	MAX-ACCESS not-accessible
	STATUS current
	DESCRIPTION
        "
        Row definition for the pm10010mpCntlocalLineTrscvFecCorrectedErrorCounter
        table
        "
	INDEX   { pm10010mpCntlocalLineTrscvFecCorrectedErrorCounterIndex }
	::= { pm10010mpCntlocalLineTrscvFecCorrectedErrorCounterTable 1 }


Pm10010mpCntlocalLineTrscvFecCorrectedErrorCounterEntry ::=
	SEQUENCE {
	pm10010mpCntlocalLineTrscvFecCorrectedErrorCounterIndex
		INTEGER,
	pm10010mpCntlocalLineTrscvFecCorrectedErrorCounterValuePortn
		Counter64,
	pm10010mpCntlocalLineTrscvFecCorrectedErrorCounterErrorPortn
		EkiOnOff,
	pm10010mpCntlocalLineTrscvFecCorrectedErrorCounterOverloadPortn
		EkiOnOff
	}


pm10010mpCntlocalLineTrscvFecCorrectedErrorCounterIndex OBJECT-TYPE
	SYNTAX  INTEGER(0..128)
	MAX-ACCESS  read-only
	STATUS current
	DESCRIPTION
        "
        Index definition for the pm10010mpCntlocalLineTrscvFecCorrectedErrorCounter
        table
        "
	::= { pm10010mpCntlocalLineTrscvFecCorrectedErrorCounterEntry 1 }


pm10010mpCntlocalLineTrscvFecCorrectedErrorCounterValuePortn OBJECT-TYPE
	SYNTAX  Counter64
	MAX-ACCESS read-only
	STATUS current
	DESCRIPTION
        "
        Line Input SD FEC Corrected Errors
        :This OID gives the current Bit
        Error Rate before the Soft Decision
        FEC  <Help> This counter gives
         the current Bit Error Rate before
        the Soft Decision FEC
        "
	::= { pm10010mpCntlocalLineTrscvFecCorrectedErrorCounterEntry 2 }


pm10010mpCntlocalLineTrscvFecCorrectedErrorCounterErrorPortn OBJECT-TYPE
	SYNTAX  EkiOnOff
	MAX-ACCESS read-only
	STATUS current
	DESCRIPTION
        "
        Line Counter Error :This OID when
        set indicates the deframer timer
        counter value is invalid on Port
        "
	::= { pm10010mpCntlocalLineTrscvFecCorrectedErrorCounterEntry 3 }


pm10010mpCntlocalLineTrscvFecCorrectedErrorCounterOverloadPortn OBJECT-TYPE
	SYNTAX  EkiOnOff
	MAX-ACCESS read-only
	STATUS current
	DESCRIPTION
        "
        Line Counter Overload :This OID
        when set indicates a deframer timer
        counter overload on Port
        "
	::= { pm10010mpCntlocalLineTrscvFecCorrectedErrorCounterEntry 4 }


--- *********************************************************
---     TABLE for the pm10010mpCntlocalLineTrscvFecUncorrectedErrorCounter articles
--- *********************************************************

pm10010mpCntlocalLineTrscvFecUncorrectedErrorCounterTable OBJECT-TYPE
	SYNTAX  SEQUENCE OF Pm10010mpCntlocalLineTrscvFecUncorrectedErrorCounterEntry
	MAX-ACCESS not-accessible
	STATUS current
	DESCRIPTION
        "
        List of pm10010mpCntlocalLineTrscvFecUncorrectedErrorCounter
        Article
        "
	::= { pm10010mpCntLine 197 }


pm10010mpCntlocalLineTrscvFecUncorrectedErrorCounterEntry OBJECT-TYPE
	SYNTAX Pm10010mpCntlocalLineTrscvFecUncorrectedErrorCounterEntry
	MAX-ACCESS not-accessible
	STATUS current
	DESCRIPTION
        "
        Row definition for the pm10010mpCntlocalLineTrscvFecUncorrectedErrorCounter
        table
        "
	INDEX   { pm10010mpCntlocalLineTrscvFecUncorrectedErrorCounterIndex }
	::= { pm10010mpCntlocalLineTrscvFecUncorrectedErrorCounterTable 1 }


Pm10010mpCntlocalLineTrscvFecUncorrectedErrorCounterEntry ::=
	SEQUENCE {
	pm10010mpCntlocalLineTrscvFecUncorrectedErrorCounterIndex
		INTEGER,
	pm10010mpCntlocalLineTrscvFecUncorrectedErrorCounterValuePortn
		Counter64,
	pm10010mpCntlocalLineTrscvFecUncorrectedErrorCounterErrorPortn
		EkiOnOff,
	pm10010mpCntlocalLineTrscvFecUncorrectedErrorCounterOverloadPortn
		EkiOnOff
	}


pm10010mpCntlocalLineTrscvFecUncorrectedErrorCounterIndex OBJECT-TYPE
	SYNTAX  INTEGER(0..128)
	MAX-ACCESS  read-only
	STATUS current
	DESCRIPTION
        "
        Index definition for the pm10010mpCntlocalLineTrscvFecUncorrectedErrorCounter
        table
        "
	::= { pm10010mpCntlocalLineTrscvFecUncorrectedErrorCounterEntry 1 }


pm10010mpCntlocalLineTrscvFecUncorrectedErrorCounterValuePortn OBJECT-TYPE
	SYNTAX  Counter64
	MAX-ACCESS read-only
	STATUS current
	DESCRIPTION
        "
        SD Uncorrected :This OID gives
        the current Bit Error Rate after
        the Soft Decision FEC (residual)
         <Help> This counter gives the
         current Bit Error Rate after the
        Soft Decision FEC (residual)
        "
	::= { pm10010mpCntlocalLineTrscvFecUncorrectedErrorCounterEntry 2 }


pm10010mpCntlocalLineTrscvFecUncorrectedErrorCounterErrorPortn OBJECT-TYPE
	SYNTAX  EkiOnOff
	MAX-ACCESS read-only
	STATUS current
	DESCRIPTION
        "
        Line Counter Error :This OID when
        set indicates the deframer timer
        counter value is invalid on Port
        "
	::= { pm10010mpCntlocalLineTrscvFecUncorrectedErrorCounterEntry 3 }


pm10010mpCntlocalLineTrscvFecUncorrectedErrorCounterOverloadPortn OBJECT-TYPE
	SYNTAX  EkiOnOff
	MAX-ACCESS read-only
	STATUS current
	DESCRIPTION
        "
        Line Counter Overload :This OID
        when set indicates a deframer timer
        counter overload on Port
        "
	::= { pm10010mpCntlocalLineTrscvFecUncorrectedErrorCounterEntry 4 }







--- *****************************************************
--- $$$$$$$$$$$$$$$$$$$$$$$$$$$$$$$$$$$$$$$$$$$$$$$$$$$$$
---     RMON
--- $$$$$$$$$$$$$$$$$$$$$$$$$$$$$$$$$$$$$$$$$$$$$$$$$$$$$
--- *****************************************************



--- *********************************************************
---     TABLE for the pm10010mpMonupRmonBytesCounterClientInput articles
--- *********************************************************

pm10010mpMonupRmonBytesCounterClientInputTable OBJECT-TYPE
	SYNTAX  SEQUENCE OF Pm10010mpMonupRmonBytesCounterClientInputEntry
	MAX-ACCESS not-accessible
	STATUS current
	DESCRIPTION
        "
        List of pm10010mpMonupRmonBytesCounterClientInput
        Article
        "
	::= { pm10010mpMonClientRmonCounter 16 }


pm10010mpMonupRmonBytesCounterClientInputEntry OBJECT-TYPE
	SYNTAX Pm10010mpMonupRmonBytesCounterClientInputEntry
	MAX-ACCESS not-accessible
	STATUS current
	DESCRIPTION
        "
        Row definition for the pm10010mpMonupRmonBytesCounterClientInput
        table
        "
	INDEX   { pm10010mpMonupRmonBytesCounterClientInputIndex }
	::= { pm10010mpMonupRmonBytesCounterClientInputTable 1 }


Pm10010mpMonupRmonBytesCounterClientInputEntry ::=
	SEQUENCE {
	pm10010mpMonupRmonBytesCounterClientInputIndex
		INTEGER,
	pm10010mpMonupRmonBytesCounterClientInputValuePortn
		Counter64,
	pm10010mpMonupRmonBytesCounterClientInputErrorPortn
		EkiOnOff,
	pm10010mpMonupRmonBytesCounterClientInputOverloadPortn
		EkiOnOff
	}


pm10010mpMonupRmonBytesCounterClientInputIndex OBJECT-TYPE
	SYNTAX  INTEGER(0..128)
	MAX-ACCESS  read-only
	STATUS current
	DESCRIPTION
        "
        Index definition for the pm10010mpMonupRmonBytesCounterClientInput
        table
        "
	::= { pm10010mpMonupRmonBytesCounterClientInputEntry 1 }


pm10010mpMonupRmonBytesCounterClientInputValuePortn OBJECT-TYPE
	SYNTAX  Counter64
	MAX-ACCESS read-only
	STATUS current
	DESCRIPTION
        "
        Client Input Bytes :This counter
        is increased each time a data byte
        is received on the client port
          <Help>  This counter gives the
        number of bytes received on the
        client port
        "
	::= { pm10010mpMonupRmonBytesCounterClientInputEntry 2 }


pm10010mpMonupRmonBytesCounterClientInputErrorPortn OBJECT-TYPE
	SYNTAX  EkiOnOff
	MAX-ACCESS read-only
	STATUS current
	DESCRIPTION
        "
        Bytes Counter Error :This OID
         when set indicates the Bytes counter
        value is invalid on client port
        "
	::= { pm10010mpMonupRmonBytesCounterClientInputEntry 3 }


pm10010mpMonupRmonBytesCounterClientInputOverloadPortn OBJECT-TYPE
	SYNTAX  EkiOnOff
	MAX-ACCESS read-only
	STATUS current
	DESCRIPTION
        "
        Bytes Counter Overload :This OID
        when set indicates a Bytes counter
        overload on client port
        "
	::= { pm10010mpMonupRmonBytesCounterClientInputEntry 4 }


--- *********************************************************
---     TABLE for the pm10010mpMonupRmonCrcErrorsCounterClientInput articles
--- *********************************************************

pm10010mpMonupRmonCrcErrorsCounterClientInputTable OBJECT-TYPE
	SYNTAX  SEQUENCE OF Pm10010mpMonupRmonCrcErrorsCounterClientInputEntry
	MAX-ACCESS not-accessible
	STATUS current
	DESCRIPTION
        "
        List of pm10010mpMonupRmonCrcErrorsCounterClientInput
        Article
        "
	::= { pm10010mpMonClientRmonCounter 32 }


pm10010mpMonupRmonCrcErrorsCounterClientInputEntry OBJECT-TYPE
	SYNTAX Pm10010mpMonupRmonCrcErrorsCounterClientInputEntry
	MAX-ACCESS not-accessible
	STATUS current
	DESCRIPTION
        "
        Row definition for the pm10010mpMonupRmonCrcErrorsCounterClientInput
        table
        "
	INDEX   { pm10010mpMonupRmonCrcErrorsCounterClientInputIndex }
	::= { pm10010mpMonupRmonCrcErrorsCounterClientInputTable 1 }


Pm10010mpMonupRmonCrcErrorsCounterClientInputEntry ::=
	SEQUENCE {
	pm10010mpMonupRmonCrcErrorsCounterClientInputIndex
		INTEGER,
	pm10010mpMonupRmonCrcErrorsCounterClientInputValuePortn
		Counter64,
	pm10010mpMonupRmonCrcErrorsCounterClientInputErrorPortn
		EkiOnOff,
	pm10010mpMonupRmonCrcErrorsCounterClientInputOverloadPortn
		EkiOnOff
	}


pm10010mpMonupRmonCrcErrorsCounterClientInputIndex OBJECT-TYPE
	SYNTAX  INTEGER(0..128)
	MAX-ACCESS  read-only
	STATUS current
	DESCRIPTION
        "
        Index definition for the pm10010mpMonupRmonCrcErrorsCounterClientInput
        table
        "
	::= { pm10010mpMonupRmonCrcErrorsCounterClientInputEntry 1 }


pm10010mpMonupRmonCrcErrorsCounterClientInputValuePortn OBJECT-TYPE
	SYNTAX  Counter64
	MAX-ACCESS read-only
	STATUS current
	DESCRIPTION
        "
        Client Input B1/CRC Errors :This
        counter is increased each time
         a B1/CRC error is detected on
         the client port  <Help>  This
         counter gives the number of B1/CRC
        Errors received on the client port
        "
	::= { pm10010mpMonupRmonCrcErrorsCounterClientInputEntry 2 }


pm10010mpMonupRmonCrcErrorsCounterClientInputErrorPortn OBJECT-TYPE
	SYNTAX  EkiOnOff
	MAX-ACCESS read-only
	STATUS current
	DESCRIPTION
        "
        CRC Errors Counter Error :This
        OID when set indicates the CRC
         Errors counter value is invalid
        on client port
        "
	::= { pm10010mpMonupRmonCrcErrorsCounterClientInputEntry 3 }


pm10010mpMonupRmonCrcErrorsCounterClientInputOverloadPortn OBJECT-TYPE
	SYNTAX  EkiOnOff
	MAX-ACCESS read-only
	STATUS current
	DESCRIPTION
        "
        CRC Errors Counter Overload :This
        OID when set indicates a CRC Errors
        counter overload on client port
        "
	::= { pm10010mpMonupRmonCrcErrorsCounterClientInputEntry 4 }


--- *********************************************************
---     TABLE for the pm10010mpMonupRmonPacketsCounterClientInput articles
--- *********************************************************

pm10010mpMonupRmonPacketsCounterClientInputTable OBJECT-TYPE
	SYNTAX  SEQUENCE OF Pm10010mpMonupRmonPacketsCounterClientInputEntry
	MAX-ACCESS not-accessible
	STATUS current
	DESCRIPTION
        "
        List of pm10010mpMonupRmonPacketsCounterClientInput
        Article
        "
	::= { pm10010mpMonClientRmonCounter 48 }


pm10010mpMonupRmonPacketsCounterClientInputEntry OBJECT-TYPE
	SYNTAX Pm10010mpMonupRmonPacketsCounterClientInputEntry
	MAX-ACCESS not-accessible
	STATUS current
	DESCRIPTION
        "
        Row definition for the pm10010mpMonupRmonPacketsCounterClientInput
        table
        "
	INDEX   { pm10010mpMonupRmonPacketsCounterClientInputIndex }
	::= { pm10010mpMonupRmonPacketsCounterClientInputTable 1 }


Pm10010mpMonupRmonPacketsCounterClientInputEntry ::=
	SEQUENCE {
	pm10010mpMonupRmonPacketsCounterClientInputIndex
		INTEGER,
	pm10010mpMonupRmonPacketsCounterClientInputValuePortn
		Counter64,
	pm10010mpMonupRmonPacketsCounterClientInputErrorPortn
		EkiOnOff,
	pm10010mpMonupRmonPacketsCounterClientInputOverloadPortn
		EkiOnOff
	}


pm10010mpMonupRmonPacketsCounterClientInputIndex OBJECT-TYPE
	SYNTAX  INTEGER(0..128)
	MAX-ACCESS  read-only
	STATUS current
	DESCRIPTION
        "
        Index definition for the pm10010mpMonupRmonPacketsCounterClientInput
        table
        "
	::= { pm10010mpMonupRmonPacketsCounterClientInputEntry 1 }


pm10010mpMonupRmonPacketsCounterClientInputValuePortn OBJECT-TYPE
	SYNTAX  Counter64
	MAX-ACCESS read-only
	STATUS current
	DESCRIPTION
        "
        Client Input Packets :This counter
        is increased each time a packet
        is received on the client port
          <Help>  This counter gives the
        number of packets received on the
        client port
        "
	::= { pm10010mpMonupRmonPacketsCounterClientInputEntry 2 }


pm10010mpMonupRmonPacketsCounterClientInputErrorPortn OBJECT-TYPE
	SYNTAX  EkiOnOff
	MAX-ACCESS read-only
	STATUS current
	DESCRIPTION
        "
        Packets Counter Error :This OID
        when set indicates the Packets
         counter value is invalid on client
        port
        "
	::= { pm10010mpMonupRmonPacketsCounterClientInputEntry 3 }


pm10010mpMonupRmonPacketsCounterClientInputOverloadPortn OBJECT-TYPE
	SYNTAX  EkiOnOff
	MAX-ACCESS read-only
	STATUS current
	DESCRIPTION
        "
        Packets Counter Overload :This
        OID when set indicates a Packets
        counter overload on client port
        "
	::= { pm10010mpMonupRmonPacketsCounterClientInputEntry 4 }


--- *********************************************************
---     TABLE for the pm10010mpMonupRmonBroadcastCounterClientInput articles
--- *********************************************************

pm10010mpMonupRmonBroadcastCounterClientInputTable OBJECT-TYPE
	SYNTAX  SEQUENCE OF Pm10010mpMonupRmonBroadcastCounterClientInputEntry
	MAX-ACCESS not-accessible
	STATUS current
	DESCRIPTION
        "
        List of pm10010mpMonupRmonBroadcastCounterClientInput
        Article
        "
	::= { pm10010mpMonClientRmonCounter 64 }


pm10010mpMonupRmonBroadcastCounterClientInputEntry OBJECT-TYPE
	SYNTAX Pm10010mpMonupRmonBroadcastCounterClientInputEntry
	MAX-ACCESS not-accessible
	STATUS current
	DESCRIPTION
        "
        Row definition for the pm10010mpMonupRmonBroadcastCounterClientInput
        table
        "
	INDEX   { pm10010mpMonupRmonBroadcastCounterClientInputIndex }
	::= { pm10010mpMonupRmonBroadcastCounterClientInputTable 1 }


Pm10010mpMonupRmonBroadcastCounterClientInputEntry ::=
	SEQUENCE {
	pm10010mpMonupRmonBroadcastCounterClientInputIndex
		INTEGER,
	pm10010mpMonupRmonBroadcastCounterClientInputValuePortn
		Counter64,
	pm10010mpMonupRmonBroadcastCounterClientInputErrorPortn
		EkiOnOff,
	pm10010mpMonupRmonBroadcastCounterClientInputOverloadPortn
		EkiOnOff
	}


pm10010mpMonupRmonBroadcastCounterClientInputIndex OBJECT-TYPE
	SYNTAX  INTEGER(0..128)
	MAX-ACCESS  read-only
	STATUS current
	DESCRIPTION
        "
        Index definition for the pm10010mpMonupRmonBroadcastCounterClientInput
        table
        "
	::= { pm10010mpMonupRmonBroadcastCounterClientInputEntry 1 }


pm10010mpMonupRmonBroadcastCounterClientInputValuePortn OBJECT-TYPE
	SYNTAX  Counter64
	MAX-ACCESS read-only
	STATUS current
	DESCRIPTION
        "
        Client Input Broadcast Packets
        :This counter is increased each
        time a broadcast packet is received
        on the client port  <Help>  This
        counter gives the number of Broadcast
        packets received on the client
         port
        "
	::= { pm10010mpMonupRmonBroadcastCounterClientInputEntry 2 }


pm10010mpMonupRmonBroadcastCounterClientInputErrorPortn OBJECT-TYPE
	SYNTAX  EkiOnOff
	MAX-ACCESS read-only
	STATUS current
	DESCRIPTION
        "
        Broadcast Counter Error :This
         OID when set indicates the Broadcast
        counter value is invalid on client
        port
        "
	::= { pm10010mpMonupRmonBroadcastCounterClientInputEntry 3 }


pm10010mpMonupRmonBroadcastCounterClientInputOverloadPortn OBJECT-TYPE
	SYNTAX  EkiOnOff
	MAX-ACCESS read-only
	STATUS current
	DESCRIPTION
        "
        Broadcast Counter Overload :This
        OID when set indicates a Broadcast
        counter overload on client port
        "
	::= { pm10010mpMonupRmonBroadcastCounterClientInputEntry 4 }


--- *********************************************************
---     TABLE for the pm10010mpMonupRmonMulticastCounterClientInput articles
--- *********************************************************

pm10010mpMonupRmonMulticastCounterClientInputTable OBJECT-TYPE
	SYNTAX  SEQUENCE OF Pm10010mpMonupRmonMulticastCounterClientInputEntry
	MAX-ACCESS not-accessible
	STATUS current
	DESCRIPTION
        "
        List of pm10010mpMonupRmonMulticastCounterClientInput
        Article
        "
	::= { pm10010mpMonClientRmonCounter 80 }


pm10010mpMonupRmonMulticastCounterClientInputEntry OBJECT-TYPE
	SYNTAX Pm10010mpMonupRmonMulticastCounterClientInputEntry
	MAX-ACCESS not-accessible
	STATUS current
	DESCRIPTION
        "
        Row definition for the pm10010mpMonupRmonMulticastCounterClientInput
        table
        "
	INDEX   { pm10010mpMonupRmonMulticastCounterClientInputIndex }
	::= { pm10010mpMonupRmonMulticastCounterClientInputTable 1 }


Pm10010mpMonupRmonMulticastCounterClientInputEntry ::=
	SEQUENCE {
	pm10010mpMonupRmonMulticastCounterClientInputIndex
		INTEGER,
	pm10010mpMonupRmonMulticastCounterClientInputValuePortn
		Counter64,
	pm10010mpMonupRmonMulticastCounterClientInputErrorPortn
		EkiOnOff,
	pm10010mpMonupRmonMulticastCounterClientInputOverloadPortn
		EkiOnOff
	}


pm10010mpMonupRmonMulticastCounterClientInputIndex OBJECT-TYPE
	SYNTAX  INTEGER(0..128)
	MAX-ACCESS  read-only
	STATUS current
	DESCRIPTION
        "
        Index definition for the pm10010mpMonupRmonMulticastCounterClientInput
        table
        "
	::= { pm10010mpMonupRmonMulticastCounterClientInputEntry 1 }


pm10010mpMonupRmonMulticastCounterClientInputValuePortn OBJECT-TYPE
	SYNTAX  Counter64
	MAX-ACCESS read-only
	STATUS current
	DESCRIPTION
        "
        Client Input Multicast Packets
        :This counter is increased each
        time a Multicast packet is received
        on the client port  <Help>  This
        counter gives the number of Multicast
        packets received on the client
         port
        "
	::= { pm10010mpMonupRmonMulticastCounterClientInputEntry 2 }


pm10010mpMonupRmonMulticastCounterClientInputErrorPortn OBJECT-TYPE
	SYNTAX  EkiOnOff
	MAX-ACCESS read-only
	STATUS current
	DESCRIPTION
        "
        Multicast Counter Error :This
         OID when set indicates the Multicast
        counter value is invalid on client
        port
        "
	::= { pm10010mpMonupRmonMulticastCounterClientInputEntry 3 }


pm10010mpMonupRmonMulticastCounterClientInputOverloadPortn OBJECT-TYPE
	SYNTAX  EkiOnOff
	MAX-ACCESS read-only
	STATUS current
	DESCRIPTION
        "
        Multicast Counter Overload :This
        OID when set indicates a Multicast
        counter overload on client port
        "
	::= { pm10010mpMonupRmonMulticastCounterClientInputEntry 4 }


--- *********************************************************
---     TABLE for the pm10010mpMonupRmonPauseFrameCounterClientInput articles
--- *********************************************************

pm10010mpMonupRmonPauseFrameCounterClientInputTable OBJECT-TYPE
	SYNTAX  SEQUENCE OF Pm10010mpMonupRmonPauseFrameCounterClientInputEntry
	MAX-ACCESS not-accessible
	STATUS current
	DESCRIPTION
        "
        List of pm10010mpMonupRmonPauseFrameCounterClientInput
        Article
        "
	::= { pm10010mpMonClientRmonCounter 96 }


pm10010mpMonupRmonPauseFrameCounterClientInputEntry OBJECT-TYPE
	SYNTAX Pm10010mpMonupRmonPauseFrameCounterClientInputEntry
	MAX-ACCESS not-accessible
	STATUS current
	DESCRIPTION
        "
        Row definition for the pm10010mpMonupRmonPauseFrameCounterClientInput
        table
        "
	INDEX   { pm10010mpMonupRmonPauseFrameCounterClientInputIndex }
	::= { pm10010mpMonupRmonPauseFrameCounterClientInputTable 1 }


Pm10010mpMonupRmonPauseFrameCounterClientInputEntry ::=
	SEQUENCE {
	pm10010mpMonupRmonPauseFrameCounterClientInputIndex
		INTEGER,
	pm10010mpMonupRmonPauseFrameCounterClientInputValuePortn
		Counter64,
	pm10010mpMonupRmonPauseFrameCounterClientInputErrorPortn
		EkiOnOff,
	pm10010mpMonupRmonPauseFrameCounterClientInputOverloadPortn
		EkiOnOff
	}


pm10010mpMonupRmonPauseFrameCounterClientInputIndex OBJECT-TYPE
	SYNTAX  INTEGER(0..128)
	MAX-ACCESS  read-only
	STATUS current
	DESCRIPTION
        "
        Index definition for the pm10010mpMonupRmonPauseFrameCounterClientInput
        table
        "
	::= { pm10010mpMonupRmonPauseFrameCounterClientInputEntry 1 }


pm10010mpMonupRmonPauseFrameCounterClientInputValuePortn OBJECT-TYPE
	SYNTAX  Counter64
	MAX-ACCESS read-only
	STATUS current
	DESCRIPTION
        "
        Client Input Pause Frames :This
        counter is increased each time
         a Pause frame is received on the
        client port  <Help>  This counter
        gives the number of Pause frames
        received on the client port
        "
	::= { pm10010mpMonupRmonPauseFrameCounterClientInputEntry 2 }


pm10010mpMonupRmonPauseFrameCounterClientInputErrorPortn OBJECT-TYPE
	SYNTAX  EkiOnOff
	MAX-ACCESS read-only
	STATUS current
	DESCRIPTION
        "
        Pause Counter Error :This OID
         when set indicates the Pause counter
        value is invalid on client port
        "
	::= { pm10010mpMonupRmonPauseFrameCounterClientInputEntry 3 }


pm10010mpMonupRmonPauseFrameCounterClientInputOverloadPortn OBJECT-TYPE
	SYNTAX  EkiOnOff
	MAX-ACCESS read-only
	STATUS current
	DESCRIPTION
        "
        Pause Counter Overload :This OID
        when set indicates a Pause counter
        overload on client port
        "
	::= { pm10010mpMonupRmonPauseFrameCounterClientInputEntry 4 }







--- *****************************************************
--- $$$$$$$$$$$$$$$$$$$$$$$$$$$$$$$$$$$$$$$$$$$$$$$$$$$$$
---     MEASURES
--- $$$$$$$$$$$$$$$$$$$$$$$$$$$$$$$$$$$$$$$$$$$$$$$$$$$$$
--- *****************************************************



pm10010mpMesrsynth0 OBJECT-TYPE
	  SYNTAX EkiMeasureType
	  MAX-ACCESS read-only
	  STATUS deprecated
	  DESCRIPTION
        "
        Not Used :
        "
	  ::= { pm10010mpMesrOther 0 }



pm10010mpMesrsynth1 OBJECT-TYPE
	  SYNTAX EkiMeasureType
	  MAX-ACCESS read-only
	  STATUS deprecated
	  DESCRIPTION
        "
        Not Used :
        "
	  ::= { pm10010mpMesrOther 1 }



--- *****************************************************
---     LEAF for the pmIntervalNumber article
--- *****************************************************

pm10010mpMesrpmIntervalNumber OBJECT-TYPE
	  SYNTAX Unsigned32 (0..65535)
	  MAX-ACCESS read-only
	  STATUS current
	  DESCRIPTION
        "
        PM Interval Counter :
        "
	  ::= { pm10010mpMesrOther 7 }



--- *****************************************************
---     LEAF for the clientCfpTemp article
--- *****************************************************

pm10010mpMesrclientCfpTemp OBJECT-TYPE
	  SYNTAX Unsigned32 (0..65535)
	  MAX-ACCESS read-only
	  STATUS current
	  DESCRIPTION
        "
        Client Trscv Temperature :This
        OID gives the temperature value
        of the Client Transceiver, read
        from the DDM (Digital Diagnostic
        Monitoring) (Temperature = AV/256)
        (Unit = C) <Help> This Measure
         gives the temperature value of
        the Client Transceiver
        "
	  ::= { pm10010mpMesrClient 8 }



--- *****************************************************
---     LEAF for the clientCfp3v3Voltage article
--- *****************************************************

pm10010mpMesrclientCfp3v3Voltage OBJECT-TYPE
	  SYNTAX Unsigned32 (0..65535)
	  MAX-ACCESS read-only
	  STATUS current
	  DESCRIPTION
        "
        Client Trscv Voltage :This OID
        gives the 3V3 voltage value of
         the Client Transceiver, read from
        the DDM (Digital Diagnostic Monitoring)
         (Voltage = AV/1000) (Unit = V)
        <Help> This Measure gives the 3V3
        voltage value of the Client Transceiver
        "
	  ::= { pm10010mpMesrClient 9 }



--- *****************************************************
---     LEAF for the clientSoaBiasCurrent article
--- *****************************************************

pm10010mpMesrclientSoaBiasCurrent OBJECT-TYPE
	  SYNTAX Unsigned32 (0..65535)
	  MAX-ACCESS read-only
	  STATUS current
	  DESCRIPTION
        "
        Client Trscv SOA Bias :This OID
        gives the SOA bias value of the
        Client Transceiver, read from the
        DDM (Digital Diagnostic Monitoring)
         (Bias = AV/500) (Unit = mA) <Help>
        This Measure gives the SOA bias
        value of the Client Transceiver
        "
	  ::= { pm10010mpMesrClient 10 }



--- *****************************************************
---     LEAF for the lineMsaTemp article
--- *****************************************************

pm10010mpMesrlineMsaTemp OBJECT-TYPE
	  SYNTAX Unsigned32 (0..65535)
	  MAX-ACCESS read-only
	  STATUS current
	  DESCRIPTION
        "
        Line Trscv Temperature :This OID
        gives the temperature value of
         the Line Transceiver, read from
        the DDM (Digital Diagnostic Monitoring)
         (Temperature = AV/256) (Unit =
        C) <Help> This Measure gives the
        temperature value of the Line Transceiver.This
        temperature must remain below 95°C
        for proper operation
        "
	  ::= { pm10010mpMesrLine 12 }



--- *****************************************************
---     LEAF for the lineMsa3v3Voltage article
--- *****************************************************

pm10010mpMesrlineMsa3v3Voltage OBJECT-TYPE
	  SYNTAX Unsigned32 (0..65535)
	  MAX-ACCESS read-only
	  STATUS current
	  DESCRIPTION
        "
        Line Trscv Voltage :This OID gives
        the 3V3 voltage value of the Line
        Transceiver, read from the DDM
         (Digital Diagnostic Monitoring)
        (Voltage = AV/1000) (Unit = V)
         <Help> This Measure gives the
         3V3 voltage value of the Line
         Transceiver
        "
	  ::= { pm10010mpMesrLine 13 }



--- *****************************************************
---     LEAF for the lineSoaBiasCurrent article
--- *****************************************************

pm10010mpMesrlineSoaBiasCurrent OBJECT-TYPE
	  SYNTAX Unsigned32 (0..65535)
	  MAX-ACCESS read-only
	  STATUS current
	  DESCRIPTION
        "
        Line Trscv SOA Bias :This OID
         gives the SOA bias value of the
        Line Transceiver,read from the
         DDM (Digital Diagnostic Monitoring)
         (Bias = AV/500) (Unit = mA) <Help>
        This Measure gives the SOA bias
        value of the Line Transceiver
        "
	  ::= { pm10010mpMesrLine 14 }



--- *********************************************************
---     TABLE for the pm10010mpMesrclientNetTxTemp articles
--- *********************************************************

pm10010mpMesrclientNetTxTempTable OBJECT-TYPE
	SYNTAX  SEQUENCE OF Pm10010mpMesrclientNetTxTempEntry
	MAX-ACCESS not-accessible
	STATUS current
	DESCRIPTION
        "
        List of pm10010mpMesrclientNetTxTemp
        Article
        "
	::= { pm10010mpMesrClient 16 }


pm10010mpMesrclientNetTxTempEntry OBJECT-TYPE
	SYNTAX Pm10010mpMesrclientNetTxTempEntry
	MAX-ACCESS not-accessible
	STATUS current
	DESCRIPTION
        "
        Row definition for the pm10010mpMesrclientNetTxTemp
        table
        "
	INDEX   { pm10010mpMesrclientNetTxTempIndex }
	::= { pm10010mpMesrclientNetTxTempTable 1 }


Pm10010mpMesrclientNetTxTempEntry ::=
	SEQUENCE {
	pm10010mpMesrclientNetTxTempIndex
		INTEGER,
	pm10010mpMesrclientNetTxTempPortn
		INTEGER
	}


pm10010mpMesrclientNetTxTempIndex OBJECT-TYPE
	SYNTAX  INTEGER(0..128)
	MAX-ACCESS  read-only
	STATUS current
	DESCRIPTION
        "
        Index definition for the pm10010mpMesrclientNetTxTemp
        table
        "
	::= { pm10010mpMesrclientNetTxTempEntry 1 }


pm10010mpMesrclientNetTxTempPortn OBJECT-TYPE
	SYNTAX  INTEGER (0..65535)
	MAX-ACCESS read-only
	STATUS current
	DESCRIPTION
        "
        Client Trscv Temperature :This
        OID gives the Laser temperature
        value of the Client Transceiver,
        read from the DDM (Digital Diagnostic
        Monitoring) (Temperature = AV/256)
        (Unit = C) <Help> This Measure
         gives the Laser temperature value
        of the Client Transceiver
        "
	::= { pm10010mpMesrclientNetTxTempEntry 2 }


--- *********************************************************
---     TABLE for the pm10010mpMesrclientNetTxBias articles
--- *********************************************************

pm10010mpMesrclientNetTxBiasTable OBJECT-TYPE
	SYNTAX  SEQUENCE OF Pm10010mpMesrclientNetTxBiasEntry
	MAX-ACCESS not-accessible
	STATUS current
	DESCRIPTION
        "
        List of pm10010mpMesrclientNetTxBias
        Article
        "
	::= { pm10010mpMesrClient 32 }


pm10010mpMesrclientNetTxBiasEntry OBJECT-TYPE
	SYNTAX Pm10010mpMesrclientNetTxBiasEntry
	MAX-ACCESS not-accessible
	STATUS current
	DESCRIPTION
        "
        Row definition for the pm10010mpMesrclientNetTxBias
        table
        "
	INDEX   { pm10010mpMesrclientNetTxBiasIndex }
	::= { pm10010mpMesrclientNetTxBiasTable 1 }


Pm10010mpMesrclientNetTxBiasEntry ::=
	SEQUENCE {
	pm10010mpMesrclientNetTxBiasIndex
		INTEGER,
	pm10010mpMesrclientNetTxBiasPortn
		INTEGER
	}


pm10010mpMesrclientNetTxBiasIndex OBJECT-TYPE
	SYNTAX  INTEGER(0..128)
	MAX-ACCESS  read-only
	STATUS current
	DESCRIPTION
        "
        Index definition for the pm10010mpMesrclientNetTxBias
        table
        "
	::= { pm10010mpMesrclientNetTxBiasEntry 1 }


pm10010mpMesrclientNetTxBiasPortn OBJECT-TYPE
	SYNTAX  INTEGER (0..65535)
	MAX-ACCESS read-only
	STATUS current
	DESCRIPTION
        "
        Client Trscv Laser Bias :This
         OID gives the Laser bias value
        of the Client Transceiver, read
        from the DDM (Digital Diagnostic
        Monitoring) (Bias = AV/500) (Unit
        = mA) <Help> This Measure gives
        the Laser bias value of the Client
        Transceiver
        "
	::= { pm10010mpMesrclientNetTxBiasEntry 2 }


--- *********************************************************
---     TABLE for the pm10010mpMesrclientNetTxPwr articles
--- *********************************************************

pm10010mpMesrclientNetTxPwrTable OBJECT-TYPE
	SYNTAX  SEQUENCE OF Pm10010mpMesrclientNetTxPwrEntry
	MAX-ACCESS not-accessible
	STATUS current
	DESCRIPTION
        "
        List of pm10010mpMesrclientNetTxPwr
        Article
        "
	::= { pm10010mpMesrClient 48 }


pm10010mpMesrclientNetTxPwrEntry OBJECT-TYPE
	SYNTAX Pm10010mpMesrclientNetTxPwrEntry
	MAX-ACCESS not-accessible
	STATUS current
	DESCRIPTION
        "
        Row definition for the pm10010mpMesrclientNetTxPwr
        table
        "
	INDEX   { pm10010mpMesrclientNetTxPwrIndex }
	::= { pm10010mpMesrclientNetTxPwrTable 1 }


Pm10010mpMesrclientNetTxPwrEntry ::=
	SEQUENCE {
	pm10010mpMesrclientNetTxPwrIndex
		INTEGER,
	pm10010mpMesrclientNetTxPwrPortn
		INTEGER
	}


pm10010mpMesrclientNetTxPwrIndex OBJECT-TYPE
	SYNTAX  INTEGER(0..128)
	MAX-ACCESS  read-only
	STATUS current
	DESCRIPTION
        "
        Index definition for the pm10010mpMesrclientNetTxPwr
        table
        "
	::= { pm10010mpMesrclientNetTxPwrEntry 1 }


pm10010mpMesrclientNetTxPwrPortn OBJECT-TYPE
	SYNTAX  INTEGER (0..65535)
	MAX-ACCESS read-only
	STATUS current
	DESCRIPTION
        "
        Client Trscv Tx Power :This OID
        gives the transmit power value
         of the Client Transceiver, read
        from the DDM (Digital Diagnostic
        Monitoring) (Power = 10*log(AV)-40)
        (Unit = dBm) <Help> This Measure
        gives the transmit power value
         of the Client Transceiver
        "
	::= { pm10010mpMesrclientNetTxPwrEntry 2 }


--- *********************************************************
---     TABLE for the pm10010mpMesrclientNetRxPwr articles
--- *********************************************************

pm10010mpMesrclientNetRxPwrTable OBJECT-TYPE
	SYNTAX  SEQUENCE OF Pm10010mpMesrclientNetRxPwrEntry
	MAX-ACCESS not-accessible
	STATUS current
	DESCRIPTION
        "
        List of pm10010mpMesrclientNetRxPwr
        Article
        "
	::= { pm10010mpMesrClient 64 }


pm10010mpMesrclientNetRxPwrEntry OBJECT-TYPE
	SYNTAX Pm10010mpMesrclientNetRxPwrEntry
	MAX-ACCESS not-accessible
	STATUS current
	DESCRIPTION
        "
        Row definition for the pm10010mpMesrclientNetRxPwr
        table
        "
	INDEX   { pm10010mpMesrclientNetRxPwrIndex }
	::= { pm10010mpMesrclientNetRxPwrTable 1 }


Pm10010mpMesrclientNetRxPwrEntry ::=
	SEQUENCE {
	pm10010mpMesrclientNetRxPwrIndex
		INTEGER,
	pm10010mpMesrclientNetRxPwrPortn
		INTEGER
	}


pm10010mpMesrclientNetRxPwrIndex OBJECT-TYPE
	SYNTAX  INTEGER(0..128)
	MAX-ACCESS  read-only
	STATUS current
	DESCRIPTION
        "
        Index definition for the pm10010mpMesrclientNetRxPwr
        table
        "
	::= { pm10010mpMesrclientNetRxPwrEntry 1 }


pm10010mpMesrclientNetRxPwrPortn OBJECT-TYPE
	SYNTAX  INTEGER (0..65535)
	MAX-ACCESS read-only
	STATUS current
	DESCRIPTION
        "
        Client Trscv Rx Power :This OID
        gives the receive power value of
        the Client Transceiver, read in
        the DDM (Digital Diagnostic Monitoring)
        (Power = 10*log(AV)-40) (Unit =
        dBm) <Help> This Measure gives
         the receive power value of the
        Client Transceiver
        "
	::= { pm10010mpMesrclientNetRxPwrEntry 2 }


--- *********************************************************
---     TABLE for the pm10010mpMesrlineNetTxLaserOutputPwr articles
--- *********************************************************

pm10010mpMesrlineNetTxLaserOutputPwrTable OBJECT-TYPE
	SYNTAX  SEQUENCE OF Pm10010mpMesrlineNetTxLaserOutputPwrEntry
	MAX-ACCESS not-accessible
	STATUS current
	DESCRIPTION
        "
        List of pm10010mpMesrlineNetTxLaserOutputPwr
        Article
        "
	::= { pm10010mpMesrLine 80 }


pm10010mpMesrlineNetTxLaserOutputPwrEntry OBJECT-TYPE
	SYNTAX Pm10010mpMesrlineNetTxLaserOutputPwrEntry
	MAX-ACCESS not-accessible
	STATUS current
	DESCRIPTION
        "
        Row definition for the pm10010mpMesrlineNetTxLaserOutputPwr
        table
        "
	INDEX   { pm10010mpMesrlineNetTxLaserOutputPwrIndex }
	::= { pm10010mpMesrlineNetTxLaserOutputPwrTable 1 }


Pm10010mpMesrlineNetTxLaserOutputPwrEntry ::=
	SEQUENCE {
	pm10010mpMesrlineNetTxLaserOutputPwrIndex
		INTEGER,
	pm10010mpMesrlineNetTxLaserOutputPwrPortn
		INTEGER
	}


pm10010mpMesrlineNetTxLaserOutputPwrIndex OBJECT-TYPE
	SYNTAX  INTEGER(0..128)
	MAX-ACCESS  read-only
	STATUS current
	DESCRIPTION
        "
        Index definition for the pm10010mpMesrlineNetTxLaserOutputPwr
        table
        "
	::= { pm10010mpMesrlineNetTxLaserOutputPwrEntry 1 }


pm10010mpMesrlineNetTxLaserOutputPwrPortn OBJECT-TYPE
	SYNTAX  INTEGER (0..65535)
	MAX-ACCESS read-only
	STATUS current
	DESCRIPTION
        "
        Current Line Trscv Tx Power :This
        OID gives the Tx Laser transmit
        power value of the Line Transceiver,
        read in the DDM (Digital Diagnostic
        Monitoring) (Power = AV/100) (Unit
        = dBm) <Help> This Measure gives
        the Tx Laser transmit power value
        of the Line Transceiver
        "
	::= { pm10010mpMesrlineNetTxLaserOutputPwrEntry 2 }


--- *********************************************************
---     TABLE for the pm10010mpMesrlineNetTxLaserTemp articles
--- *********************************************************

pm10010mpMesrlineNetTxLaserTempTable OBJECT-TYPE
	SYNTAX  SEQUENCE OF Pm10010mpMesrlineNetTxLaserTempEntry
	MAX-ACCESS not-accessible
	STATUS current
	DESCRIPTION
        "
        List of pm10010mpMesrlineNetTxLaserTemp
        Article
        "
	::= { pm10010mpMesrLine 96 }


pm10010mpMesrlineNetTxLaserTempEntry OBJECT-TYPE
	SYNTAX Pm10010mpMesrlineNetTxLaserTempEntry
	MAX-ACCESS not-accessible
	STATUS current
	DESCRIPTION
        "
        Row definition for the pm10010mpMesrlineNetTxLaserTemp
        table
        "
	INDEX   { pm10010mpMesrlineNetTxLaserTempIndex }
	::= { pm10010mpMesrlineNetTxLaserTempTable 1 }


Pm10010mpMesrlineNetTxLaserTempEntry ::=
	SEQUENCE {
	pm10010mpMesrlineNetTxLaserTempIndex
		INTEGER,
	pm10010mpMesrlineNetTxLaserTempPortn
		INTEGER
	}


pm10010mpMesrlineNetTxLaserTempIndex OBJECT-TYPE
	SYNTAX  INTEGER(0..128)
	MAX-ACCESS  read-only
	STATUS current
	DESCRIPTION
        "
        Index definition for the pm10010mpMesrlineNetTxLaserTemp
        table
        "
	::= { pm10010mpMesrlineNetTxLaserTempEntry 1 }


pm10010mpMesrlineNetTxLaserTempPortn OBJECT-TYPE
	SYNTAX  INTEGER (0..65535)
	MAX-ACCESS read-only
	STATUS current
	DESCRIPTION
        "
        Current Line Trscv Tx Laser Temperature
        :This OID gives the Tx Laser Temperature
        value of the Line Transceiver,
         read from the DDM (Digital Diagnostic
        Monitoring) (Temperature = AV/256)
        (Unit = C) <Help> This Measure
         gives the Tx Laser Temperature
        value of the Line Transceiver
        "
	::= { pm10010mpMesrlineNetTxLaserTempEntry 2 }


--- *********************************************************
---     TABLE for the pm10010mpMesrlineNetTxBiasCurrent articles
--- *********************************************************

pm10010mpMesrlineNetTxBiasCurrentTable OBJECT-TYPE
	SYNTAX  SEQUENCE OF Pm10010mpMesrlineNetTxBiasCurrentEntry
	MAX-ACCESS not-accessible
	STATUS current
	DESCRIPTION
        "
        List of pm10010mpMesrlineNetTxBiasCurrent
        Article
        "
	::= { pm10010mpMesrLine 112 }


pm10010mpMesrlineNetTxBiasCurrentEntry OBJECT-TYPE
	SYNTAX Pm10010mpMesrlineNetTxBiasCurrentEntry
	MAX-ACCESS not-accessible
	STATUS current
	DESCRIPTION
        "
        Row definition for the pm10010mpMesrlineNetTxBiasCurrent
        table
        "
	INDEX   { pm10010mpMesrlineNetTxBiasCurrentIndex }
	::= { pm10010mpMesrlineNetTxBiasCurrentTable 1 }


Pm10010mpMesrlineNetTxBiasCurrentEntry ::=
	SEQUENCE {
	pm10010mpMesrlineNetTxBiasCurrentIndex
		INTEGER,
	pm10010mpMesrlineNetTxBiasCurrentPortn
		INTEGER
	}


pm10010mpMesrlineNetTxBiasCurrentIndex OBJECT-TYPE
	SYNTAX  INTEGER(0..128)
	MAX-ACCESS  read-only
	STATUS current
	DESCRIPTION
        "
        Index definition for the pm10010mpMesrlineNetTxBiasCurrent
        table
        "
	::= { pm10010mpMesrlineNetTxBiasCurrentEntry 1 }


pm10010mpMesrlineNetTxBiasCurrentPortn OBJECT-TYPE
	SYNTAX  INTEGER (0..65535)
	MAX-ACCESS read-only
	STATUS current
	DESCRIPTION
        "
        Current Line Trscv Tx Laser Bias
        :This OID gives the Tx Laser Bias
        value of the Line Transceiver,
         read from the DDM (Digital Diagnostic
        Monitoring) (Bias = AV/10) (Unit
        = mA) <Help> This Measure gives
        the Tx Laser Bias value of the
         Line Transceiver
        "
	::= { pm10010mpMesrlineNetTxBiasCurrentEntry 2 }


--- *********************************************************
---     TABLE for the pm10010mpMesrlineNetRxInputPwr articles
--- *********************************************************

pm10010mpMesrlineNetRxInputPwrTable OBJECT-TYPE
	SYNTAX  SEQUENCE OF Pm10010mpMesrlineNetRxInputPwrEntry
	MAX-ACCESS not-accessible
	STATUS current
	DESCRIPTION
        "
        List of pm10010mpMesrlineNetRxInputPwr
        Article
        "
	::= { pm10010mpMesrLine 128 }


pm10010mpMesrlineNetRxInputPwrEntry OBJECT-TYPE
	SYNTAX Pm10010mpMesrlineNetRxInputPwrEntry
	MAX-ACCESS not-accessible
	STATUS current
	DESCRIPTION
        "
        Row definition for the pm10010mpMesrlineNetRxInputPwr
        table
        "
	INDEX   { pm10010mpMesrlineNetRxInputPwrIndex }
	::= { pm10010mpMesrlineNetRxInputPwrTable 1 }


Pm10010mpMesrlineNetRxInputPwrEntry ::=
	SEQUENCE {
	pm10010mpMesrlineNetRxInputPwrIndex
		INTEGER,
	pm10010mpMesrlineNetRxInputPwrPortn
		INTEGER
	}


pm10010mpMesrlineNetRxInputPwrIndex OBJECT-TYPE
	SYNTAX  INTEGER(0..128)
	MAX-ACCESS  read-only
	STATUS current
	DESCRIPTION
        "
        Index definition for the pm10010mpMesrlineNetRxInputPwr
        table
        "
	::= { pm10010mpMesrlineNetRxInputPwrEntry 1 }


pm10010mpMesrlineNetRxInputPwrPortn OBJECT-TYPE
	SYNTAX  INTEGER (0..65535)
	MAX-ACCESS read-only
	STATUS current
	DESCRIPTION
        "
        Current Line Trscv Rx Power :This
        OID gives the Receive power value
        of the Line Transceiver, read in
        the DDM (Digital Diagnostic Monitoring)
        (Power = AV/100) (Unit = dBm) <Help>
        This Measure gives the Receive
         power value of the Line Transceiver
        "
	::= { pm10010mpMesrlineNetRxInputPwrEntry 2 }


--- *********************************************************
---     TABLE for the pm10010mpMesrlineResidualChromaticDisp articles
--- *********************************************************

pm10010mpMesrlineResidualChromaticDispTable OBJECT-TYPE
	SYNTAX  SEQUENCE OF Pm10010mpMesrlineResidualChromaticDispEntry
	MAX-ACCESS not-accessible
	STATUS current
	DESCRIPTION
        "
        List of pm10010mpMesrlineResidualChromaticDisp
        Article
        "
	::= { pm10010mpMesrLine 144 }


pm10010mpMesrlineResidualChromaticDispEntry OBJECT-TYPE
	SYNTAX Pm10010mpMesrlineResidualChromaticDispEntry
	MAX-ACCESS not-accessible
	STATUS current
	DESCRIPTION
        "
        Row definition for the pm10010mpMesrlineResidualChromaticDisp
        table
        "
	INDEX   { pm10010mpMesrlineResidualChromaticDispIndex }
	::= { pm10010mpMesrlineResidualChromaticDispTable 1 }


Pm10010mpMesrlineResidualChromaticDispEntry ::=
	SEQUENCE {
	pm10010mpMesrlineResidualChromaticDispIndex
		INTEGER,
	pm10010mpMesrlineResidualChromaticDispPortn
		INTEGER
	}


pm10010mpMesrlineResidualChromaticDispIndex OBJECT-TYPE
	SYNTAX  INTEGER(0..128)
	MAX-ACCESS  read-only
	STATUS current
	DESCRIPTION
        "
        Index definition for the pm10010mpMesrlineResidualChromaticDisp
        table
        "
	::= { pm10010mpMesrlineResidualChromaticDispEntry 1 }


pm10010mpMesrlineResidualChromaticDispPortn OBJECT-TYPE
	SYNTAX  INTEGER (0..65535)
	MAX-ACCESS read-only
	STATUS current
	DESCRIPTION
        "
        Current Residual Chromatic Dispersion
        :This OID gives the current Residual
        Chromatic Dispersion on the Line
        interface  (Unit = ps/nm)<Help>
        This measure gives the current
         Residual Chromatic Dispersion
         on the Line interface.
        "
	::= { pm10010mpMesrlineResidualChromaticDispEntry 2 }


--- *********************************************************
---     TABLE for the pm10010mpMesrlineDiffGroupDelay articles
--- *********************************************************

pm10010mpMesrlineDiffGroupDelayTable OBJECT-TYPE
	SYNTAX  SEQUENCE OF Pm10010mpMesrlineDiffGroupDelayEntry
	MAX-ACCESS not-accessible
	STATUS current
	DESCRIPTION
        "
        List of pm10010mpMesrlineDiffGroupDelay
        Article
        "
	::= { pm10010mpMesrLine 148 }


pm10010mpMesrlineDiffGroupDelayEntry OBJECT-TYPE
	SYNTAX Pm10010mpMesrlineDiffGroupDelayEntry
	MAX-ACCESS not-accessible
	STATUS current
	DESCRIPTION
        "
        Row definition for the pm10010mpMesrlineDiffGroupDelay
        table
        "
	INDEX   { pm10010mpMesrlineDiffGroupDelayIndex }
	::= { pm10010mpMesrlineDiffGroupDelayTable 1 }


Pm10010mpMesrlineDiffGroupDelayEntry ::=
	SEQUENCE {
	pm10010mpMesrlineDiffGroupDelayIndex
		INTEGER,
	pm10010mpMesrlineDiffGroupDelayPortn
		INTEGER
	}


pm10010mpMesrlineDiffGroupDelayIndex OBJECT-TYPE
	SYNTAX  INTEGER(0..128)
	MAX-ACCESS  read-only
	STATUS current
	DESCRIPTION
        "
        Index definition for the pm10010mpMesrlineDiffGroupDelay
        table
        "
	::= { pm10010mpMesrlineDiffGroupDelayEntry 1 }


pm10010mpMesrlineDiffGroupDelayPortn OBJECT-TYPE
	SYNTAX  INTEGER (0..65535)
	MAX-ACCESS read-only
	STATUS current
	DESCRIPTION
        "
        Current Differential Group Delay
        :This OID gives the current Differential
        Group Delay on the Line interface
          (Unit = ps)<Help> This measure
        gives the current Differential
         Group Delay on the Line interface.
        "
	::= { pm10010mpMesrlineDiffGroupDelayEntry 2 }


--- *********************************************************
---     TABLE for the pm10010mpMesrlineQFactor articles
--- *********************************************************

pm10010mpMesrlineQFactorTable OBJECT-TYPE
	SYNTAX  SEQUENCE OF Pm10010mpMesrlineQFactorEntry
	MAX-ACCESS not-accessible
	STATUS current
	DESCRIPTION
        "
        List of pm10010mpMesrlineQFactor
        Article
        "
	::= { pm10010mpMesrLine 152 }


pm10010mpMesrlineQFactorEntry OBJECT-TYPE
	SYNTAX Pm10010mpMesrlineQFactorEntry
	MAX-ACCESS not-accessible
	STATUS current
	DESCRIPTION
        "
        Row definition for the pm10010mpMesrlineQFactor
        table
        "
	INDEX   { pm10010mpMesrlineQFactorIndex }
	::= { pm10010mpMesrlineQFactorTable 1 }


Pm10010mpMesrlineQFactorEntry ::=
	SEQUENCE {
	pm10010mpMesrlineQFactorIndex
		INTEGER,
	pm10010mpMesrlineQFactorPortn
		INTEGER
	}


pm10010mpMesrlineQFactorIndex OBJECT-TYPE
	SYNTAX  INTEGER(0..128)
	MAX-ACCESS  read-only
	STATUS current
	DESCRIPTION
        "
        Index definition for the pm10010mpMesrlineQFactor
        table
        "
	::= { pm10010mpMesrlineQFactorEntry 1 }


pm10010mpMesrlineQFactorPortn OBJECT-TYPE
	SYNTAX  INTEGER (0..65535)
	MAX-ACCESS read-only
	STATUS current
	DESCRIPTION
        "
        Current Q Factor :This OID gives
        the current Q Factor on the Line
        interface   (Unit = dB) <Help>
         This measure gives the current
        Q Factor on the Line interface.
        "
	::= { pm10010mpMesrlineQFactorEntry 2 }


--- *********************************************************
---     TABLE for the pm10010mpMesrlineCarrierFreqOffset articles
--- *********************************************************

pm10010mpMesrlineCarrierFreqOffsetTable OBJECT-TYPE
	SYNTAX  SEQUENCE OF Pm10010mpMesrlineCarrierFreqOffsetEntry
	MAX-ACCESS not-accessible
	STATUS current
	DESCRIPTION
        "
        List of pm10010mpMesrlineCarrierFreqOffset
        Article
        "
	::= { pm10010mpMesrLine 156 }


pm10010mpMesrlineCarrierFreqOffsetEntry OBJECT-TYPE
	SYNTAX Pm10010mpMesrlineCarrierFreqOffsetEntry
	MAX-ACCESS not-accessible
	STATUS current
	DESCRIPTION
        "
        Row definition for the pm10010mpMesrlineCarrierFreqOffset
        table
        "
	INDEX   { pm10010mpMesrlineCarrierFreqOffsetIndex }
	::= { pm10010mpMesrlineCarrierFreqOffsetTable 1 }


Pm10010mpMesrlineCarrierFreqOffsetEntry ::=
	SEQUENCE {
	pm10010mpMesrlineCarrierFreqOffsetIndex
		INTEGER,
	pm10010mpMesrlineCarrierFreqOffsetPortn
		INTEGER
	}


pm10010mpMesrlineCarrierFreqOffsetIndex OBJECT-TYPE
	SYNTAX  INTEGER(0..128)
	MAX-ACCESS  read-only
	STATUS current
	DESCRIPTION
        "
        Index definition for the pm10010mpMesrlineCarrierFreqOffset
        table
        "
	::= { pm10010mpMesrlineCarrierFreqOffsetEntry 1 }


pm10010mpMesrlineCarrierFreqOffsetPortn OBJECT-TYPE
	SYNTAX  INTEGER (0..65535)
	MAX-ACCESS read-only
	STATUS current
	DESCRIPTION
        "
        Current Carrier Frequency Offset
        :This OID gives the current Carrier
        Frequency Offset on the Line interface
          (Unit = Mhz)<Help> This measure
        gives the current Carrier Frequency
        Offset on the Line interface.
        "
	::= { pm10010mpMesrlineCarrierFreqOffsetEntry 2 }


--- *********************************************************
---     TABLE for the pm10010mpMesrlineOsnr articles
--- *********************************************************

pm10010mpMesrlineOsnrTable OBJECT-TYPE
	SYNTAX  SEQUENCE OF Pm10010mpMesrlineOsnrEntry
	MAX-ACCESS not-accessible
	STATUS current
	DESCRIPTION
        "
        List of pm10010mpMesrlineOsnr
         Article
        "
	::= { pm10010mpMesrLine 160 }


pm10010mpMesrlineOsnrEntry OBJECT-TYPE
	SYNTAX Pm10010mpMesrlineOsnrEntry
	MAX-ACCESS not-accessible
	STATUS current
	DESCRIPTION
        "
        Row definition for the pm10010mpMesrlineOsnr
        table
        "
	INDEX   { pm10010mpMesrlineOsnrIndex }
	::= { pm10010mpMesrlineOsnrTable 1 }


Pm10010mpMesrlineOsnrEntry ::=
	SEQUENCE {
	pm10010mpMesrlineOsnrIndex
		INTEGER,
	pm10010mpMesrlineOsnrPortn
		INTEGER
	}


pm10010mpMesrlineOsnrIndex OBJECT-TYPE
	SYNTAX  INTEGER(0..128)
	MAX-ACCESS  read-only
	STATUS current
	DESCRIPTION
        "
        Index definition for the pm10010mpMesrlineOsnr
        table
        "
	::= { pm10010mpMesrlineOsnrEntry 1 }


pm10010mpMesrlineOsnrPortn OBJECT-TYPE
	SYNTAX  INTEGER (0..65535)
	MAX-ACCESS read-only
	STATUS current
	DESCRIPTION
        "
        Current OSNR :This OID gives the
        current OSNR on the Line interface
          (OSNR = AV/10) (Unit = dB)<Help>
        This measure gives the current
         OSNR on the Line interface.
        "
	::= { pm10010mpMesrlineOsnrEntry 2 }


--- *****************************************************
---     LEAF for the lineNetTxLaserOutputPwrAverage article
--- *****************************************************

pm10010mpMesrlineNetTxLaserOutputPwrAverage OBJECT-TYPE
	  SYNTAX Unsigned32 (0..65535)
	  MAX-ACCESS read-only
	  STATUS current
	  DESCRIPTION
        "
        Average Line Trscv Tx Power :This
        OID gives the average Tx Laser
         transmit power value among the
        network lanes of the Line Transceiver,
        read in the DDM (Digital Diagnostic
        Monitoring)  (Power = AV/100) (Unit
        = dBm) (Unit = dBm) <Help> This
        Measure gives the average Tx Laser
        transmit power value among the
         network lanes of the Line Transceiver
        "
	  ::= { pm10010mpMesrOther 180 }



--- *****************************************************
---     LEAF for the lineNetTxLaserTempAverage article
--- *****************************************************

pm10010mpMesrlineNetTxLaserTempAverage OBJECT-TYPE
	  SYNTAX Unsigned32 (0..65535)
	  MAX-ACCESS read-only
	  STATUS current
	  DESCRIPTION
        "
        Average Line Trscv Tx Laser Temperature
        :This OID gives the average Tx
         Laser Temperature value among
         the network lanes of the Line
         Transceiver, read from the DDM
        (Digital Diagnostic Monitoring)
        (Temperature = AV/256) (Unit =
         C) <Help> This Measure gives the
        average Tx Laser Temperature value
        among the network lanes of the
         Line Transceiver
        "
	  ::= { pm10010mpMesrOther 181 }



--- *****************************************************
---     LEAF for the lineNetTxBiasCurrentAverage article
--- *****************************************************

pm10010mpMesrlineNetTxBiasCurrentAverage OBJECT-TYPE
	  SYNTAX Unsigned32 (0..65535)
	  MAX-ACCESS read-only
	  STATUS current
	  DESCRIPTION
        "
        Average Line Trscv Tx Laser Bias
        :This OID gives the average Tx
         Laser Bias value among the network
        lanes of the Line Transceiver,
         read from the DDM (Digital Diagnostic
        Monitoring) (Bias = AV/10) (Unit
        = mA) <Help> This Measure gives
        the average Tx Laser Bias value
        among the network lanes of the
         Line Transceiver
        "
	  ::= { pm10010mpMesrOther 182 }



--- *****************************************************
---     LEAF for the lineNetRxInputPwrAverage article
--- *****************************************************

pm10010mpMesrlineNetRxInputPwrAverage OBJECT-TYPE
	  SYNTAX Unsigned32 (0..65535)
	  MAX-ACCESS read-only
	  STATUS current
	  DESCRIPTION
        "
        Average Line Trscv Rx Power :This
        OID gives the average Receive power
        value among the network lanes of
        the Line Transceiver, read in the
        DDM (Digital Diagnostic Monitoring)
        (Power = AV/100) (Unit = dBm) <Help>
        This Measure gives the average
         Receive power value among the
         network lanes of the Line Transceiver
        "
	  ::= { pm10010mpMesrOther 183 }



--- *****************************************************
---     LEAF for the lineResidualChromaticDispAverage article
--- *****************************************************

pm10010mpMesrlineResidualChromaticDispAverage OBJECT-TYPE
	  SYNTAX Unsigned32 (0..65535)
	  MAX-ACCESS read-only
	  STATUS current
	  DESCRIPTION
        "
        Average Residual Chromatic Dispersion
        :This OID gives the average Residual
        Chromatic Dispersion on the Line
        interface since the last measure
        reset <Help> This measure gives
        the average Residual Chromatic
         Dispersion on the Line interface
        since the last measure reset.
        "
	  ::= { pm10010mpMesrOther 184 }



--- *****************************************************
---     LEAF for the lineDiffGroupDelayAverage article
--- *****************************************************

pm10010mpMesrlineDiffGroupDelayAverage OBJECT-TYPE
	  SYNTAX Unsigned32 (0..65535)
	  MAX-ACCESS read-only
	  STATUS current
	  DESCRIPTION
        "
        Average Differential Group Delay
        :This OID gives the average Group
        Delay on the Line interface since
        the last measure reset <Help> This
        measure gives the average Differential
        Group Delay on the Line interface
        since the last measure reset.
        "
	  ::= { pm10010mpMesrOther 185 }



--- *****************************************************
---     LEAF for the lineQFactorAverage article
--- *****************************************************

pm10010mpMesrlineQFactorAverage OBJECT-TYPE
	  SYNTAX Unsigned32 (0..65535)
	  MAX-ACCESS read-only
	  STATUS current
	  DESCRIPTION
        "
        Average Q Factor :This OID gives
        the average Q Factor on the Line
        interface since the last measure
        reset <Help> This measure gives
        the average Q Factor on the Line
        interface since the last measure
        reset.
        "
	  ::= { pm10010mpMesrOther 186 }



--- *****************************************************
---     LEAF for the lineCarrierFreqOffsetAverage article
--- *****************************************************

pm10010mpMesrlineCarrierFreqOffsetAverage OBJECT-TYPE
	  SYNTAX Unsigned32 (0..65535)
	  MAX-ACCESS read-only
	  STATUS current
	  DESCRIPTION
        "
        Average Carrier Frequency Offset
        :This OID gives the average Carrier
        Frequency Offset on the Line interface
        since the last measure reset <Help>
        This measure gives the average
         Carrier Frequency Offset on the
        Line interface since the last measure
        reset
        "
	  ::= { pm10010mpMesrOther 187 }



--- *****************************************************
---     LEAF for the lineOsnrAverage article
--- *****************************************************

pm10010mpMesrlineOsnrAverage OBJECT-TYPE
	  SYNTAX Unsigned32 (0..65535)
	  MAX-ACCESS read-only
	  STATUS current
	  DESCRIPTION
        "
        Average OSNR :This OID gives the
        average OSNR on the Line interface
        since the last measure reset <Help>
        This measure gives the average
         OSNR on the Line interface since
        the last measure reset.
        "
	  ::= { pm10010mpMesrOther 188 }



--- *****************************************************
---     LEAF for the clientNetTxTempMin article
--- *****************************************************

pm10010mpMesrclientNetTxTempMin OBJECT-TYPE
	  SYNTAX Unsigned32 (0..65535)
	  MAX-ACCESS read-only
	  STATUS current
	  DESCRIPTION
        "
        Min Client Trscv Laser Temperature
        :This OID gives the minimum Laser
        temperature value among the network
        lanes of the Client Transceiver,
        read from the DDM (Digital Diagnostic
        Monitoring) (Temperature = AV/256)
        (Unit = C) <Help> This Measure
         gives the minimum Laser temperature
        value among the network lanes of
        the Client Transceiver
        "
	  ::= { pm10010mpMesrOther 192 }



--- *****************************************************
---     LEAF for the clientNetTxBiasMin article
--- *****************************************************

pm10010mpMesrclientNetTxBiasMin OBJECT-TYPE
	  SYNTAX Unsigned32 (0..65535)
	  MAX-ACCESS read-only
	  STATUS current
	  DESCRIPTION
        "
        Min Client Trscv Laser Bias :This
        OID gives the minimum Laser bias
        value among the network lanes of
        the Client Transceiver, read from
        the DDM (Digital Diagnostic Monitoring)
        (Bias = AV/500) (Unit = mA) <Help>
        This Measure gives the minimum
         Laser bias value among the network
        lanes of the Client Transceiver
        "
	  ::= { pm10010mpMesrOther 193 }



--- *****************************************************
---     LEAF for the clientNetTxPwrMin article
--- *****************************************************

pm10010mpMesrclientNetTxPwrMin OBJECT-TYPE
	  SYNTAX Unsigned32 (0..65535)
	  MAX-ACCESS read-only
	  STATUS current
	  DESCRIPTION
        "
        Min Client Trscv Tx Power :This
        OID gives the minimum transmit
         power value among the network
         lanes of the Client Transceiver,
        read from the DDM (Digital Diagnostic
        Monitoring) (Power = 10*log(AV)-40)
        (Unit = dBm) <Help> This Measure
        gives the minimum transmit power
        value among the network lanes of
        the Client Transceiver
        "
	  ::= { pm10010mpMesrOther 194 }



--- *****************************************************
---     LEAF for the clientNetRxPwrMin article
--- *****************************************************

pm10010mpMesrclientNetRxPwrMin OBJECT-TYPE
	  SYNTAX Unsigned32 (0..65535)
	  MAX-ACCESS read-only
	  STATUS current
	  DESCRIPTION
        "
        Min Client Trscv Rx Power :This
        OID gives the minimum receive power
        value among the network lanes of
        the Client Transceiver, read in
        the DDM (Digital Diagnostic Monitoring)
        (Power = 10*log(AV)-40) (Unit =
        dBm) <Help> This Measure gives
         the minimum receive power value
        among the network lanes of the
         Client Transceiver
        "
	  ::= { pm10010mpMesrOther 195 }



--- *****************************************************
---     LEAF for the lineNetTxLaserOutputPwrMin article
--- *****************************************************

pm10010mpMesrlineNetTxLaserOutputPwrMin OBJECT-TYPE
	  SYNTAX Unsigned32 (0..65535)
	  MAX-ACCESS read-only
	  STATUS current
	  DESCRIPTION
        "
        Min Line Trscv Tx Power :This
         OID gives the minimum Tx Laser
        transmit power value among the
         network lanes of the Line Transceiver,
        read in the DDM (Digital Diagnostic
        Monitoring)  (Power = AV/100) (Unit
        = dBm) (Unit = dBm) <Help> This
        Measure gives the minimum Tx Laser
        transmit power value among the
         network lanes of the Line Transceiver
        "
	  ::= { pm10010mpMesrOther 196 }



--- *****************************************************
---     LEAF for the lineNetTxLaserTempMin article
--- *****************************************************

pm10010mpMesrlineNetTxLaserTempMin OBJECT-TYPE
	  SYNTAX Unsigned32 (0..65535)
	  MAX-ACCESS read-only
	  STATUS current
	  DESCRIPTION
        "
        Min Line Trscv Tx Laser Temperature
        :This OID gives the minimum Tx
         Laser Temperature value among
         the network lanes of the Line
         Transceiver, read from the DDM
        (Digital Diagnostic Monitoring)
        (Temperature = AV/256) (Unit =
         C) <Help> This Measure gives the
        minimum Tx Laser Temperature value
        among the network lanes of the
         Line Transceiver
        "
	  ::= { pm10010mpMesrOther 197 }



--- *****************************************************
---     LEAF for the lineNetTxBiasCurrentMin article
--- *****************************************************

pm10010mpMesrlineNetTxBiasCurrentMin OBJECT-TYPE
	  SYNTAX Unsigned32 (0..65535)
	  MAX-ACCESS read-only
	  STATUS current
	  DESCRIPTION
        "
        Min Line Trscv Tx Laser Bias :This
        OID gives the minimum Tx Laser
         Bias value among the network lanes
        of the Line Transceiver, read from
        the DDM (Digital Diagnostic Monitoring)
        (Bias = AV/10) (Unit = mA) <Help>
        This Measure gives the minimum
         Tx Laser Bias value among the
         network lanes of the Line Transceiver
        "
	  ::= { pm10010mpMesrOther 198 }



--- *****************************************************
---     LEAF for the lineNetRxInputPwrMin article
--- *****************************************************

pm10010mpMesrlineNetRxInputPwrMin OBJECT-TYPE
	  SYNTAX Unsigned32 (0..65535)
	  MAX-ACCESS read-only
	  STATUS current
	  DESCRIPTION
        "
        Min Line Trscv Rx Power :This
         OID gives the minimum Receive
         power value among the network
         lanes of the Line Transceiver,
        read in the DDM (Digital Diagnostic
        Monitoring) (Power = AV/100) (Unit
        = dBm) <Help> This Measure gives
        the minimum Receive power value
        among the network lanes of the
         Line Transceiver
        "
	  ::= { pm10010mpMesrOther 199 }



--- *****************************************************
---     LEAF for the lineResidualChromaticDispMin article
--- *****************************************************

pm10010mpMesrlineResidualChromaticDispMin OBJECT-TYPE
	  SYNTAX Unsigned32 (0..65535)
	  MAX-ACCESS read-only
	  STATUS current
	  DESCRIPTION
        "
        Min Residual Chromatic Dispersion
        :This OID gives the minimum Residual
        Chromatic Dispersion on the Line
        interface since the last measure
        reset  (Unit = ps/nm)<Help> This
        measure gives the minimum Residual
        Chromatic Dispersion on the Line
        interface since the last measure
        reset.
        "
	  ::= { pm10010mpMesrOther 200 }



--- *****************************************************
---     LEAF for the lineDiffGroupDelayMin article
--- *****************************************************

pm10010mpMesrlineDiffGroupDelayMin OBJECT-TYPE
	  SYNTAX Unsigned32 (0..65535)
	  MAX-ACCESS read-only
	  STATUS current
	  DESCRIPTION
        "
        Min Differential Group Delay :This
        OID gives the minimum Differential
        Group Delay  on the Line interface
        since the last measure reset  (Unit
        = ps)<Help> This measure gives
         the minimum Differential Group
        Delay on the Line interface since
        the last measure reset.
        "
	  ::= { pm10010mpMesrOther 201 }



--- *****************************************************
---     LEAF for the lineQFactorMin article
--- *****************************************************

pm10010mpMesrlineQFactorMin OBJECT-TYPE
	  SYNTAX Unsigned32 (0..65535)
	  MAX-ACCESS read-only
	  STATUS current
	  DESCRIPTION
        "
        Min Q Factor :This OID gives the
        minimum Q Factor on the Line interface
        since the last measure reset  (Unit
        = dB)<Help> This measure gives
         the minimum Q Factor on the Line
        interface since the last measure
        reset.
        "
	  ::= { pm10010mpMesrOther 202 }



--- *****************************************************
---     LEAF for the lineCarrierFreqOffsetMin article
--- *****************************************************

pm10010mpMesrlineCarrierFreqOffsetMin OBJECT-TYPE
	  SYNTAX Unsigned32 (0..65535)
	  MAX-ACCESS read-only
	  STATUS current
	  DESCRIPTION
        "
        Min Carrier Frequency Offset :This
        OID gives the minimum Carrier Frequency
        Offset on the Line interface since
        the last measure reset  (Unit =
        Mhz)<Help> This measure gives the
        minimum Carrier Frequency Offset
        on the Line interface since the
        last measure reset
        "
	  ::= { pm10010mpMesrOther 203 }



--- *****************************************************
---     LEAF for the lineOsnrMin article
--- *****************************************************

pm10010mpMesrlineOsnrMin OBJECT-TYPE
	  SYNTAX Unsigned32 (0..65535)
	  MAX-ACCESS read-only
	  STATUS current
	  DESCRIPTION
        "
        Min OSNR :This OID gives the minimum
        OSNR on the Line interface since
        the last measure reset  (OSNR =
        AV/10) (Unit = dB)<Help> This measure
        gives the minimum OSNR on the Line
        interface since the last measure
        reset.
        "
	  ::= { pm10010mpMesrOther 204 }



--- *****************************************************
---     LEAF for the clientNetTxTempMax article
--- *****************************************************

pm10010mpMesrclientNetTxTempMax OBJECT-TYPE
	  SYNTAX Unsigned32 (0..65535)
	  MAX-ACCESS read-only
	  STATUS current
	  DESCRIPTION
        "
        Max Client Trscv Laser Temperature
        :This OID gives the maximum Laser
        temperature value among the network
        lanes of the Client Transceiver,
        read from the DDM (Digital Diagnostic
        Monitoring) (Temperature = AV/256)
        (Unit = C) <Help> This Measure
         gives the maximum Laser temperature
        value among the network lanes of
        the Client Transceiver
        "
	  ::= { pm10010mpMesrOther 208 }



--- *****************************************************
---     LEAF for the clientNetTxBiasMax article
--- *****************************************************

pm10010mpMesrclientNetTxBiasMax OBJECT-TYPE
	  SYNTAX Unsigned32 (0..65535)
	  MAX-ACCESS read-only
	  STATUS current
	  DESCRIPTION
        "
        Max Client Trscv Laser Bias :This
        OID gives the maximum Laser bias
        value among the network lanes of
        the Client Transceiver, read from
        the DDM (Digital Diagnostic Monitoring)
        (Bias = AV/500) (Unit = mA) <Help>
        This Measure gives the maximum
         Laser bias value among the network
        lanes of the Client Transceiver
        "
	  ::= { pm10010mpMesrOther 209 }



--- *****************************************************
---     LEAF for the clientNetTxPwrMax article
--- *****************************************************

pm10010mpMesrclientNetTxPwrMax OBJECT-TYPE
	  SYNTAX Unsigned32 (0..65535)
	  MAX-ACCESS read-only
	  STATUS current
	  DESCRIPTION
        "
        Max Client Trscv Tx Power :This
        OID gives the maximum transmit
         power value among the network
         lanes of the Client Transceiver,
        read from the DDM (Digital Diagnostic
        Monitoring) (Power = 10*log(AV)-40)
        (Unit = dBm) <Help> This Measure
        gives the maximum transmit power
        value among the network lanes of
        the Client Transceiver
        "
	  ::= { pm10010mpMesrOther 210 }



--- *****************************************************
---     LEAF for the clientNetRxPwrMax article
--- *****************************************************

pm10010mpMesrclientNetRxPwrMax OBJECT-TYPE
	  SYNTAX Unsigned32 (0..65535)
	  MAX-ACCESS read-only
	  STATUS current
	  DESCRIPTION
        "
        Max Client Trscv Rx Power :This
        OID gives the maximum receive power
        value among the network lanes of
        the Client Transceiver, read in
        the DDM (Digital Diagnostic Monitoring)
        (Power = 10*log(AV)-40) (Unit =
        dBm) <Help> This Measure gives
         the maximum receive power value
        among the network lanes of the
         Client Transceiver
        "
	  ::= { pm10010mpMesrOther 211 }



--- *****************************************************
---     LEAF for the lineNetTxLaserOutputPwrMax article
--- *****************************************************

pm10010mpMesrlineNetTxLaserOutputPwrMax OBJECT-TYPE
	  SYNTAX Unsigned32 (0..65535)
	  MAX-ACCESS read-only
	  STATUS current
	  DESCRIPTION
        "
        Max Line Trscv Tx Power :This
         OID gives the maximum Tx Laser
        transmit power value among the
         network lanes of the Line Transceiver,
        read in the DDM (Digital Diagnostic
        Monitoring) (Power = 10*log(AV)-40)
        (Unit = dBm) <Help> This Measure
        gives the maximum Tx Laser transmit
        power value among the network lanes
        of the Line Transceiver
        "
	  ::= { pm10010mpMesrOther 212 }



--- *****************************************************
---     LEAF for the lineNetTxLaserTempMax article
--- *****************************************************

pm10010mpMesrlineNetTxLaserTempMax OBJECT-TYPE
	  SYNTAX Unsigned32 (0..65535)
	  MAX-ACCESS read-only
	  STATUS current
	  DESCRIPTION
        "
        Max Line Trscv Tx Laser Temperature
        :This OID gives the maximum Tx
         Laser Temperature value among
         the network lanes of the Line
         Transceiver, read from the DDM
        (Digital Diagnostic Monitoring)
        (Temperature = AV/256) (Unit =
         C) <Help> This Measure gives the
        maximum Tx Laser Temperature value
        among the network lanes of the
         Line Transceiver
        "
	  ::= { pm10010mpMesrOther 213 }



--- *****************************************************
---     LEAF for the lineNetTxBiasCurrentMax article
--- *****************************************************

pm10010mpMesrlineNetTxBiasCurrentMax OBJECT-TYPE
	  SYNTAX Unsigned32 (0..65535)
	  MAX-ACCESS read-only
	  STATUS current
	  DESCRIPTION
        "
        Max Line Trscv Tx Laser Bias :This
        OID gives the maximum Tx Laser
         Bias value among the network lanes
        of the Line Transceiver, read from
        the DDM (Digital Diagnostic Monitoring)
        (Bias = AV/10) (Unit = mA) <Help>
        This Measure gives the maximum
         Tx Laser Bias value among the
         network lanes of the Line Transceiver
        "
	  ::= { pm10010mpMesrOther 214 }



--- *****************************************************
---     LEAF for the lineNetRxInputPwrMax article
--- *****************************************************

pm10010mpMesrlineNetRxInputPwrMax OBJECT-TYPE
	  SYNTAX Unsigned32 (0..65535)
	  MAX-ACCESS read-only
	  STATUS current
	  DESCRIPTION
        "
        Max Line Trscv Rx Power :This
         OID gives the maximum Receive
         power value among the network
         lanes of the Line Transceiver,
        read in the DDM (Digital Diagnostic
        Monitoring) (Power = 10*log(AV)-40)
        (Unit = dBm) <Help> This Measure
        gives the maximum Receive power
        value among the network lanes of
        the Line Transceiver
        "
	  ::= { pm10010mpMesrOther 215 }



--- *****************************************************
---     LEAF for the lineResidualChromaticDispMax article
--- *****************************************************

pm10010mpMesrlineResidualChromaticDispMax OBJECT-TYPE
	  SYNTAX Unsigned32 (0..65535)
	  MAX-ACCESS read-only
	  STATUS current
	  DESCRIPTION
        "
        Max Residual Chromatic Dispersion
        :This OID gives the maximum Residual
        Chromatic Dispersion on the Line
        interface since the last measure
        reset  (Unit = ps/nm)<Help> This
        measure gives the maximum Residual
        Chromatic Dispersion on the Line
        interface since the last measure
        reset.
        "
	  ::= { pm10010mpMesrOther 216 }



--- *****************************************************
---     LEAF for the lineDiffGroupDelayMax article
--- *****************************************************

pm10010mpMesrlineDiffGroupDelayMax OBJECT-TYPE
	  SYNTAX Unsigned32 (0..65535)
	  MAX-ACCESS read-only
	  STATUS current
	  DESCRIPTION
        "
        Max Differential Group Delay :This
        OID gives the maximum Differential
        Group Delay  on the Line interface
        since the last measure reset
         (Unit = ps)<Help> This measure
        gives the maximum Differential
         Group Delay on the Line interface
        since the last measure reset.
        "
	  ::= { pm10010mpMesrOther 217 }



--- *****************************************************
---     LEAF for the lineQFactorMax article
--- *****************************************************

pm10010mpMesrlineQFactorMax OBJECT-TYPE
	  SYNTAX Unsigned32 (0..65535)
	  MAX-ACCESS read-only
	  STATUS current
	  DESCRIPTION
        "
        Max Q Factor :This OID gives the
        maximum Q Factor on the Line interface
        since the last measure reset  (Unit
        = dB)<Help> This measure gives
         the maximum Q Factor on the Line
        interface since the last measure
        reset.
        "
	  ::= { pm10010mpMesrOther 218 }



--- *****************************************************
---     LEAF for the lineCarrierFreqOffsetMax article
--- *****************************************************

pm10010mpMesrlineCarrierFreqOffsetMax OBJECT-TYPE
	  SYNTAX Unsigned32 (0..65535)
	  MAX-ACCESS read-only
	  STATUS current
	  DESCRIPTION
        "
        Max Carrier Frequency Offset :This
        OID gives the maximum Carrier Frequency
        Offset on the Line interface since
        the last measure reset   (Unit
         = Mhz)<Help> This measure gives
        the maximum Carrier Frequency Offset
        on the Line interface since the
        last measure reset.
        "
	  ::= { pm10010mpMesrOther 219 }



--- *****************************************************
---     LEAF for the lineOsnrMax article
--- *****************************************************

pm10010mpMesrlineOsnrMax OBJECT-TYPE
	  SYNTAX Unsigned32 (0..65535)
	  MAX-ACCESS read-only
	  STATUS current
	  DESCRIPTION
        "
        Max OSNR :This OID gives the maximum
        OSNR on the Line interface since
        the last measure reset  (OSNR =
        AV/10) (Unit = dB)<Help> This measure
        gives the maximum OSNR on the Line
        interface since the last measure
        reset
        "
	  ::= { pm10010mpMesrOther 220 }








--- *****************************************************
--- $$$$$$$$$$$$$$$$$$$$$$$$$$$$$$$$$$$$$$$$$$$$$$$$$$$$$
---     DOWNLOAD
--- $$$$$$$$$$$$$$$$$$$$$$$$$$$$$$$$$$$$$$$$$$$$$$$$$$$$$
--- *****************************************************



--- *****************************************************
---     LEAF for the restartProcess article
--- *****************************************************
pm10010mpDwlrestartProcess OBJECT IDENTIFIER ::= { pm10010mpDwlOther 0 }




pm10010mpDwlColdRestartProcessed OBJECT-TYPE
	  SYNTAX EkiOnOff
	  MAX-ACCESS read-only
	  STATUS current
	  DESCRIPTION
        "
        Cold Restart :This OID indicates
        that the module last restart was
        a Cold RESTART
        "
	  ::= { pm10010mpDwlrestartProcess 2 }



pm10010mpDwlWarmRestartProcessed OBJECT-TYPE
	  SYNTAX EkiOnOff
	  MAX-ACCESS read-only
	  STATUS current
	  DESCRIPTION
        "
        Warm Restart :This OID indicates
        that the module last restart was
        a Warm RESTART
        "
	  ::= { pm10010mpDwlrestartProcess 1 }



--- *****************************************************
---     LEAF for the swBanksUsed article
--- *****************************************************
pm10010mpDwlswBanksUsed OBJECT IDENTIFIER ::= { pm10010mpDwlOther 1 }




pm10010mpDwlSwBank2Notempty OBJECT-TYPE
	  SYNTAX EkiOnOff
	  MAX-ACCESS read-only
	  STATUS current
	  DESCRIPTION
        "
        SW bank 2 loaded :This OID indicates
        a software is loaded in SW bank
        2  <Help>  This status indicates
        if the SW bank 2 contains SW package
        "
	  ::= { pm10010mpDwlswBanksUsed 6 }



pm10010mpDwlSwBank1Notempty OBJECT-TYPE
	  SYNTAX EkiOnOff
	  MAX-ACCESS read-only
	  STATUS current
	  DESCRIPTION
        "
        SW bank 1 loaded :This OID indicates
        a software is loaded in SW bank
        1  <Help>  This status indicates
        if the SW bank 1 contains SW package
        "
	  ::= { pm10010mpDwlswBanksUsed 5 }



pm10010mpDwlSwBank2Used OBJECT-TYPE
	  SYNTAX EkiOnOff
	  MAX-ACCESS read-only
	  STATUS current
	  DESCRIPTION
        "
        SW bank 2 active :This OID indicates
        the module is working on SW bank
        2  <Help>  This status indicates
        if the SW bank 2 is active or standby
        "
	  ::= { pm10010mpDwlswBanksUsed 2 }



pm10010mpDwlSwBank1Used OBJECT-TYPE
	  SYNTAX EkiOnOff
	  MAX-ACCESS read-only
	  STATUS current
	  DESCRIPTION
        "
        SW bank 1 active :This OID indicates
        the module is working on SW bank
        1  <Help>  This status indicates
        if the SW bank 1 is active or standby
        "
	  ::= { pm10010mpDwlswBanksUsed 1 }



--- *****************************************************
---     LEAF for the gwBanksUsed article
--- *****************************************************
pm10010mpDwlgwBanksUsed OBJECT IDENTIFIER ::= { pm10010mpDwlOther 2 }




pm10010mpDwlGwBank4Notempty OBJECT-TYPE
	  SYNTAX EkiOnOff
	  MAX-ACCESS read-only
	  STATUS current
	  DESCRIPTION
        "
        GW bank 4 loaded :This OID indicates
        a gateware is loaded in GW bank
        4
        "
	  ::= { pm10010mpDwlgwBanksUsed 8 }



pm10010mpDwlGwBank3Notempty OBJECT-TYPE
	  SYNTAX EkiOnOff
	  MAX-ACCESS read-only
	  STATUS current
	  DESCRIPTION
        "
        GW bank 3 loaded :This OID indicates
        a gateware is loaded in GW bank
        3  <Help>  This status indicates
        if the GW bank 3 contains GW package
        "
	  ::= { pm10010mpDwlgwBanksUsed 7 }



pm10010mpDwlGwBank2Notempty OBJECT-TYPE
	  SYNTAX EkiOnOff
	  MAX-ACCESS read-only
	  STATUS current
	  DESCRIPTION
        "
        GW bank 2 loaded :This OID indicates
        a gateware is loaded in GW bank
        2
        "
	  ::= { pm10010mpDwlgwBanksUsed 6 }



pm10010mpDwlGwBank1Notempty OBJECT-TYPE
	  SYNTAX EkiOnOff
	  MAX-ACCESS read-only
	  STATUS current
	  DESCRIPTION
        "
        GW bank 1 loaded :This OID indicates
        a gateware is loaded in GW bank
        1  <Help>  This status indicates
        if the GW bank 1 contains GW package
        "
	  ::= { pm10010mpDwlgwBanksUsed 5 }



pm10010mpDwlGwBank4Used OBJECT-TYPE
	  SYNTAX EkiOnOff
	  MAX-ACCESS read-only
	  STATUS current
	  DESCRIPTION
        "
        GW bank 4 active :This OID indicates
        the module is working on GW bank
        4
        "
	  ::= { pm10010mpDwlgwBanksUsed 4 }



pm10010mpDwlGwBank3Used OBJECT-TYPE
	  SYNTAX EkiOnOff
	  MAX-ACCESS read-only
	  STATUS current
	  DESCRIPTION
        "
        GW bank 3 active :This OID indicates
        the module is working on GW bank
        3  <Help>  This status indicates
        if the GW bank 3 is active or standby
        "
	  ::= { pm10010mpDwlgwBanksUsed 3 }



pm10010mpDwlGwBank2Used OBJECT-TYPE
	  SYNTAX EkiOnOff
	  MAX-ACCESS read-only
	  STATUS current
	  DESCRIPTION
        "
        GW bank 2 active :This OID indicates
        the module is working on GW bank
        2
        "
	  ::= { pm10010mpDwlgwBanksUsed 2 }



pm10010mpDwlGwBank1Used OBJECT-TYPE
	  SYNTAX EkiOnOff
	  MAX-ACCESS read-only
	  STATUS current
	  DESCRIPTION
        "
        GW bank 1 active :This OID indicates
        the module is working on GW bank
        1  <Help>  This status indicates
        if the GW bank 1 is active or standby
        "
	  ::= { pm10010mpDwlgwBanksUsed 1 }








--- *****************************************************
--- $$$$$$$$$$$$$$$$$$$$$$$$$$$$$$$$$$$$$$$$$$$$$$$$$$$$$
---     CONFIG
--- $$$$$$$$$$$$$$$$$$$$$$$$$$$$$$$$$$$$$$$$$$$$$$$$$$$$$
--- *****************************************************



--- *****************************************************
---     LEAF for the table Group accessCAisCsf
--- *****************************************************

pm10010mpCfgAccessCAisCsf OBJECT IDENTIFIER ::= { pm10010mpConfig 1 }



--- *****************************************************
---     LEAF for the table 0012
--- *****************************************************

pm10010mpCfgClientcaiscsfTable OBJECT-TYPE
	SYNTAX  SEQUENCE OF Pm10010mpCfgClientcaiscsfEntry
	MAX-ACCESS not-accessible
	STATUS current
	DESCRIPTION
        "
        List of  Article
        "
	::= { pm10010mpCfgAccessCAisCsf 1 }


pm10010mpCfgClientcaiscsfEntry OBJECT-TYPE
	SYNTAX Pm10010mpCfgClientcaiscsfEntry
	MAX-ACCESS not-accessible
	STATUS current
	DESCRIPTION
        "
        Row definition for the accessCAisCsf
        table
        "
	INDEX   { pm10010mpCfgClientcaiscsfIndex }
	::= { pm10010mpCfgClientcaiscsfTable 1 }


Pm10010mpCfgClientcaiscsfEntry ::=
	SEQUENCE {
	pm10010mpCfgClientcaiscsfIndex
		INTEGER,
	pm10010mpCfgReservePortn
		Unsigned32
	}


pm10010mpCfgClientcaiscsfIndex OBJECT-TYPE
	SYNTAX  INTEGER(0..128)
	MAX-ACCESS  read-only
	STATUS current
	DESCRIPTION
        "
        Index definition for the clientcaiscsf
        table
        "
	::= { pm10010mpCfgClientcaiscsfEntry 1 }


pm10010mpCfgReservePortn OBJECT-TYPE
	SYNTAX  Unsigned32 (0..65536)
	MAX-ACCESS read-write
	STATUS current
	DESCRIPTION
        "
        CAIS mode  on Client Port :This
        register enables/disables port
          laser shutdown on CAIS insertion
        condition
        "
	::= { pm10010mpCfgClientcaiscsfEntry 3 }


--- *****************************************************
---     LEAF for the table Group startup
--- *****************************************************

pm10010mpCfgStartup OBJECT IDENTIFIER ::= { pm10010mpConfig 2 }



--- *****************************************************
---     LEAF for the table 2110
--- *****************************************************

pm10010mpCfgClientStartupTable OBJECT-TYPE
	SYNTAX  SEQUENCE OF Pm10010mpCfgClientStartupEntry
	MAX-ACCESS not-accessible
	STATUS current
	DESCRIPTION
        "
        List of  Article
        "
	::= { pm10010mpCfgStartup 1 }


pm10010mpCfgClientStartupEntry OBJECT-TYPE
	SYNTAX Pm10010mpCfgClientStartupEntry
	MAX-ACCESS not-accessible
	STATUS current
	DESCRIPTION
        "
        Row definition for the startup
        table
        "
	INDEX   { pm10010mpCfgClientStartupIndex }
	::= { pm10010mpCfgClientStartupTable 1 }


Pm10010mpCfgClientStartupEntry ::=
	SEQUENCE {
	pm10010mpCfgClientStartupIndex
		INTEGER,
	pm10010mpCfgSystConfPortPortn
		Unsigned32,
	pm10010mpCfgNetConfPortPortn
		Unsigned32,
	pm10010mpCfgOptionsPortPortn
		Unsigned32
	}


pm10010mpCfgClientStartupIndex OBJECT-TYPE
	SYNTAX  INTEGER(0..128)
	MAX-ACCESS  read-only
	STATUS current
	DESCRIPTION
        "
        Index definition for the clientStartup
        table
        "
	::= { pm10010mpCfgClientStartupEntry 1 }


pm10010mpCfgSystConfPortPortn OBJECT-TYPE
	SYNTAX  Unsigned32 (0..65536)
	MAX-ACCESS read-write
	STATUS current
	DESCRIPTION
        "
        Default Settings on Client Port
        :This  register configures the
         default initialisation settings
        on the port.
        "
	::= { pm10010mpCfgClientStartupEntry 3 }


pm10010mpCfgNetConfPortPortn OBJECT-TYPE
	SYNTAX  Unsigned32 (0..65536)
	MAX-ACCESS read-write
	STATUS current
	DESCRIPTION
        "
        Default Settings on Client Port
        :This  register configures the
         default initialisation settings
        on the port.
        "
	::= { pm10010mpCfgClientStartupEntry 4 }


pm10010mpCfgOptionsPortPortn OBJECT-TYPE
	SYNTAX  Unsigned32 (0..65536)
	MAX-ACCESS read-write
	STATUS current
	DESCRIPTION
        "
        Default Options on Client Port
        :This register configures the default
        options on the port.
        "
	::= { pm10010mpCfgClientStartupEntry 14 }


--- *****************************************************
---     LEAF for the table 2190
--- *****************************************************

pm10010mpCfgLineStartupTable OBJECT-TYPE
	SYNTAX  SEQUENCE OF Pm10010mpCfgLineStartupEntry
	MAX-ACCESS not-accessible
	STATUS current
	DESCRIPTION
        "
        List of  Article
        "
	::= { pm10010mpCfgStartup 2 }


pm10010mpCfgLineStartupEntry OBJECT-TYPE
	SYNTAX Pm10010mpCfgLineStartupEntry
	MAX-ACCESS not-accessible
	STATUS current
	DESCRIPTION
        "
        Row definition for the startup
        table
        "
	INDEX   { pm10010mpCfgLineStartupIndex }
	::= { pm10010mpCfgLineStartupTable 1 }


Pm10010mpCfgLineStartupEntry ::=
	SEQUENCE {
	pm10010mpCfgLineStartupIndex
		INTEGER,
	pm10010mpCfgSystConfLinePortn
		Unsigned32,
	pm10010mpCfgOptionsLinePortn
		Unsigned32
	}


pm10010mpCfgLineStartupIndex OBJECT-TYPE
	SYNTAX  INTEGER(0..128)
	MAX-ACCESS  read-only
	STATUS current
	DESCRIPTION
        "
        Index definition for the lineStartup
        table
        "
	::= { pm10010mpCfgLineStartupEntry 1 }


pm10010mpCfgSystConfLinePortn OBJECT-TYPE
	SYNTAX  Unsigned32 (0..65536)
	MAX-ACCESS read-write
	STATUS current
	DESCRIPTION
        "
        Default Settings on Line :This
        register configures the default
        initialisation settings on Line
        "
	::= { pm10010mpCfgLineStartupEntry 3 }


pm10010mpCfgOptionsLinePortn OBJECT-TYPE
	SYNTAX  Unsigned32 (0..65536)
	MAX-ACCESS read-write
	STATUS current
	DESCRIPTION
        "
        Default Options on Line :This
         register configures the default
        options on the line
        "
	::= { pm10010mpCfgLineStartupEntry 14 }


--- *****************************************************
---     LEAF for the table 21AB
--- *****************************************************

pm10010mpCfgXfpTable OBJECT-TYPE
	SYNTAX  SEQUENCE OF Pm10010mpCfgXfpEntry
	MAX-ACCESS not-accessible
	STATUS current
	DESCRIPTION
        "
        List of  Article
        "
	::= { pm10010mpCfgStartup 3 }


pm10010mpCfgXfpEntry OBJECT-TYPE
	SYNTAX Pm10010mpCfgXfpEntry
	MAX-ACCESS not-accessible
	STATUS current
	DESCRIPTION
        "
        Row definition for the startup
        table
        "
	INDEX   { pm10010mpCfgXfpIndex }
	::= { pm10010mpCfgXfpTable 1 }


Pm10010mpCfgXfpEntry ::=
	SEQUENCE {
	pm10010mpCfgXfpIndex
		INTEGER,
	pm10010mpCfgSystConfMsaLinePortn
		Unsigned32
	}


pm10010mpCfgXfpIndex OBJECT-TYPE
	SYNTAX  INTEGER(0..128)
	MAX-ACCESS  read-only
	STATUS current
	DESCRIPTION
        "
        Index definition for the xfp table
        "
	::= { pm10010mpCfgXfpEntry 1 }


pm10010mpCfgSystConfMsaLinePortn OBJECT-TYPE
	SYNTAX  Unsigned32 (0..65536)
	MAX-ACCESS read-write
	STATUS current
	DESCRIPTION
        "
        Default settings on MSA :This
         register configures the default
        initialisation settings on MSA
        "
	::= { pm10010mpCfgXfpEntry 3 }


--- *****************************************************
---     LEAF for the table 2610
--- *****************************************************

pm10010mpCfgClientOtxtlhTable OBJECT-TYPE
	SYNTAX  SEQUENCE OF Pm10010mpCfgClientOtxtlhEntry
	MAX-ACCESS not-accessible
	STATUS current
	DESCRIPTION
        "
        List of  Article
        "
	::= { pm10010mpCfgStartup 4 }


pm10010mpCfgClientOtxtlhEntry OBJECT-TYPE
	SYNTAX Pm10010mpCfgClientOtxtlhEntry
	MAX-ACCESS not-accessible
	STATUS current
	DESCRIPTION
        "
        Row definition for the startup
        table
        "
	INDEX   { pm10010mpCfgClientOtxtlhIndex }
	::= { pm10010mpCfgClientOtxtlhTable 1 }


Pm10010mpCfgClientOtxtlhEntry ::=
	SEQUENCE {
	pm10010mpCfgClientOtxtlhIndex
		INTEGER,
	pm10010mpCfgControlsPortn
		Unsigned32,
	pm10010mpCfgClientPwrLaserPortn
		Unsigned32,
	pm10010mpCfgClientFCurrentPortn
		Unsigned32,
	pm10010mpCfgClientGridCurrentPortn
		Unsigned32,
	pm10010mpCfgClientFoPortn
		Unsigned32
	}


pm10010mpCfgClientOtxtlhIndex OBJECT-TYPE
	SYNTAX  INTEGER(0..128)
	MAX-ACCESS  read-only
	STATUS current
	DESCRIPTION
        "
        Index definition for the clientOtxtlh
        table
        "
	::= { pm10010mpCfgClientOtxtlhEntry 1 }


pm10010mpCfgControlsPortn OBJECT-TYPE
	SYNTAX  Unsigned32 (0..65536)
	MAX-ACCESS read-write
	STATUS deprecated
	DESCRIPTION
        "
        Defaut Client settings :This register
        configures the start-up settings
        on the ports
        "
	::= { pm10010mpCfgClientOtxtlhEntry 3 }


pm10010mpCfgClientPwrLaserPortn OBJECT-TYPE
	SYNTAX  Unsigned32 (0..65536)
	MAX-ACCESS read-write
	STATUS current
	DESCRIPTION
        "
        Defaut Client output Power :This
        register configures the start-up
        output power of the client transceiver
         (Unit = dBm)
        "
	::= { pm10010mpCfgClientOtxtlhEntry 6 }


pm10010mpCfgClientFCurrentPortn OBJECT-TYPE
	SYNTAX  Unsigned32 (0..65536)
	MAX-ACCESS read-write
	STATUS current
	DESCRIPTION
        "
        Default Client transceiver Channel
        :This register configures the start-up
        laser channel of the client  transceiver
        "
	::= { pm10010mpCfgClientOtxtlhEntry 7 }


pm10010mpCfgClientGridCurrentPortn OBJECT-TYPE
	SYNTAX  Unsigned32 (0..65536)
	MAX-ACCESS read-write
	STATUS current
	DESCRIPTION
        "
        Default Client transceiver Grid
        :This register configures the start-up
        laser grid of the client transceiver
        "
	::= { pm10010mpCfgClientOtxtlhEntry 8 }


pm10010mpCfgClientFoPortn OBJECT-TYPE
	SYNTAX  Unsigned32 (0..65536)
	MAX-ACCESS read-write
	STATUS current
	DESCRIPTION
        "
        Default Client first Frequency
        :This register configures the start-up
        first frequency of the client transceiver
        "
	::= { pm10010mpCfgClientOtxtlhEntry 9 }


--- *****************************************************
---     LEAF for the table Group labels
--- *****************************************************

pm10010mpCfgLabels OBJECT IDENTIFIER ::= { pm10010mpConfig 3 }



--- *****************************************************
---     LEAF for the table 0003
--- *****************************************************

pm10010mpCfgLabelclientTable OBJECT-TYPE
	SYNTAX  SEQUENCE OF Pm10010mpCfgLabelclientEntry
	MAX-ACCESS not-accessible
	STATUS current
	DESCRIPTION
        "
        List of  Article
        "
	::= { pm10010mpCfgLabels 1 }


pm10010mpCfgLabelclientEntry OBJECT-TYPE
	SYNTAX Pm10010mpCfgLabelclientEntry
	MAX-ACCESS not-accessible
	STATUS current
	DESCRIPTION
        "
        Row definition for the labels
         table
        "
	INDEX   { pm10010mpCfgLabelclientIndex }
	::= { pm10010mpCfgLabelclientTable 1 }


Pm10010mpCfgLabelclientEntry ::=
	SEQUENCE {
	pm10010mpCfgLabelclientIndex
		INTEGER,
	pm10010mpCfgLabelclientPortn
		DisplayString
	}


pm10010mpCfgLabelclientIndex OBJECT-TYPE
	SYNTAX  INTEGER(0..128)
	MAX-ACCESS  read-only
	STATUS current
	DESCRIPTION
        "
        Index definition for the labelclient
        table
        "
	::= { pm10010mpCfgLabelclientEntry 1 }


pm10010mpCfgLabelclientPortn OBJECT-TYPE
	SYNTAX  DisplayString( SIZE(1..16))
	MAX-ACCESS read-write
	STATUS current
	DESCRIPTION
        "
        Default settings on the label
         of the Ports :These registers
         configures the default initialisation
        settings of the labels of the ports.
        "
	::= { pm10010mpCfgLabelclientEntry 3 }


--- *****************************************************
---     LEAF for the table 0004
--- *****************************************************

pm10010mpCfgLabellineTable OBJECT-TYPE
	SYNTAX  SEQUENCE OF Pm10010mpCfgLabellineEntry
	MAX-ACCESS not-accessible
	STATUS current
	DESCRIPTION
        "
        List of  Article
        "
	::= { pm10010mpCfgLabels 2 }


pm10010mpCfgLabellineEntry OBJECT-TYPE
	SYNTAX Pm10010mpCfgLabellineEntry
	MAX-ACCESS not-accessible
	STATUS current
	DESCRIPTION
        "
        Row definition for the labels
         table
        "
	INDEX   { pm10010mpCfgLabellineIndex }
	::= { pm10010mpCfgLabellineTable 1 }


Pm10010mpCfgLabellineEntry ::=
	SEQUENCE {
	pm10010mpCfgLabellineIndex
		INTEGER,
	pm10010mpCfgLabellinePortn
		DisplayString
	}


pm10010mpCfgLabellineIndex OBJECT-TYPE
	SYNTAX  INTEGER(0..128)
	MAX-ACCESS  read-only
	STATUS current
	DESCRIPTION
        "
        Index definition for the labelline
        table
        "
	::= { pm10010mpCfgLabellineEntry 1 }


pm10010mpCfgLabellinePortn OBJECT-TYPE
	SYNTAX  DisplayString( SIZE(1..16))
	MAX-ACCESS read-write
	STATUS current
	DESCRIPTION
        "
        Default settings on the label
         of the lines :These registers
         configures the default initialisation
        settings of the labels of the lines.
        "
	::= { pm10010mpCfgLabellineEntry 3 }


--- *****************************************************
---     LEAF for the table Group startuptlh
--- *****************************************************

pm10010mpCfgStartuptlh OBJECT IDENTIFIER ::= { pm10010mpConfig 4 }



--- *****************************************************
---     LEAF for the table 25AB
--- *****************************************************

pm10010mpCfgOtxtlhTable OBJECT-TYPE
	SYNTAX  SEQUENCE OF Pm10010mpCfgOtxtlhEntry
	MAX-ACCESS not-accessible
	STATUS current
	DESCRIPTION
        "
        List of  Article
        "
	::= { pm10010mpCfgStartuptlh 1 }


pm10010mpCfgOtxtlhEntry OBJECT-TYPE
	SYNTAX Pm10010mpCfgOtxtlhEntry
	MAX-ACCESS not-accessible
	STATUS current
	DESCRIPTION
        "
        Row definition for the startuptlh
        table
        "
	INDEX   { pm10010mpCfgOtxtlhIndex }
	::= { pm10010mpCfgOtxtlhTable 1 }


Pm10010mpCfgOtxtlhEntry ::=
	SEQUENCE {
	pm10010mpCfgOtxtlhIndex
		INTEGER,
	pm10010mpCfgLinePwrLaserPortn
		Unsigned32,
	pm10010mpCfgLineFCurrentPortn
		Unsigned32,
	pm10010mpCfgLineGridCurrentPortn
		Unsigned32,
	pm10010mpCfgFPortn
		Unsigned32,
	pm10010mpCfgRxLineFCurrentPortn
		Unsigned32
	}


pm10010mpCfgOtxtlhIndex OBJECT-TYPE
	SYNTAX  INTEGER(0..128)
	MAX-ACCESS  read-only
	STATUS current
	DESCRIPTION
        "
        Index definition for the otxtlh
        table
        "
	::= { pm10010mpCfgOtxtlhEntry 1 }


pm10010mpCfgLinePwrLaserPortn OBJECT-TYPE
	SYNTAX  Unsigned32 (0..65536)
	MAX-ACCESS read-write
	STATUS current
	DESCRIPTION
        "
        Defaut Line output Power :This
        register configures the start-up
        output power of the Line tranceiver
         (Unit = dBm)
        "
	::= { pm10010mpCfgOtxtlhEntry 6 }


pm10010mpCfgLineFCurrentPortn OBJECT-TYPE
	SYNTAX  Unsigned32 (0..65536)
	MAX-ACCESS read-write
	STATUS current
	DESCRIPTION
        "
        Default Line transceiver Tx Channel
        :This register configures the start-up
        laser channel of the Line Tx transceiver
        "
	::= { pm10010mpCfgOtxtlhEntry 7 }


pm10010mpCfgLineGridCurrentPortn OBJECT-TYPE
	SYNTAX  Unsigned32 (0..65536)
	MAX-ACCESS read-write
	STATUS current
	DESCRIPTION
        "
        Default Line transceiver Grid
         :This register configures the
         start-up laser grid of the Line
        transceiver
        "
	::= { pm10010mpCfgOtxtlhEntry 8 }


pm10010mpCfgFPortn OBJECT-TYPE
	SYNTAX  Unsigned32 (0..65536)
	MAX-ACCESS read-write
	STATUS current
	DESCRIPTION
        "
        Default Line TRX lowest Freq :This
        register configures the start-up
        lowest frequency of the Line transceiver
        "
	::= { pm10010mpCfgOtxtlhEntry 9 }


pm10010mpCfgRxLineFCurrentPortn OBJECT-TYPE
	SYNTAX  Unsigned32 (0..65536)
	MAX-ACCESS read-write
	STATUS current
	DESCRIPTION
        "
        Default Line transceiver Rx Channel
        :This register configures the start-up
        laser channel of the Line Rx transceiver
        "
	::= { pm10010mpCfgOtxtlhEntry 10 }


--- *****************************************************
---     LEAF for the table Group other
--- *****************************************************

pm10010mpCfgOther OBJECT IDENTIFIER ::= { pm10010mpConfig 5 }



--- *****************************************************
---     LEAF for the table 2300
--- *****************************************************

pm10010mptablemoduleOther OBJECT IDENTIFIER ::= { pm10010mpCfgOther 1 }



pm10010mpCfgmode OBJECT-TYPE
	  SYNTAX Unsigned32 (0..65536)
	  MAX-ACCESS read-write
	  STATUS current
	  DESCRIPTION
        "
        Default settings on Module :This
        register selects the configuration
        mode of the module
        "
	  ::= { pm10010mptablemoduleOther 2 }



pm10010mpCfgfanLowSpeedThreshold OBJECT-TYPE
	  SYNTAX Unsigned32 (0..65536)
	  MAX-ACCESS read-write
	  STATUS current
	  DESCRIPTION
        "
        Default settings on Module :This
        register selects the speed threshold
        of the fan's
        "
	  ::= { pm10010mptablemoduleOther 3 }



pm10010mpCfgfanHighSpeedThreshold OBJECT-TYPE
	  SYNTAX Unsigned32 (0..65536)
	  MAX-ACCESS read-write
	  STATUS current
	  DESCRIPTION
        "
        Default settings on Module :This
        register selects the speed threshold
        of the fan's
        "
	  ::= { pm10010mptablemoduleOther 4 }



--- *****************************************************
---     LEAF for the table Group startuptablefive
--- *****************************************************

pm10010mpCfgStartuptablefive OBJECT IDENTIFIER ::= { pm10010mpConfig 6 }



--- *****************************************************
---     LEAF for the table 0005
--- *****************************************************

pm10010mpCfgOtxtlhcapabilitiesTable OBJECT-TYPE
	SYNTAX  SEQUENCE OF Pm10010mpCfgOtxtlhcapabilitiesEntry
	MAX-ACCESS not-accessible
	STATUS current
	DESCRIPTION
        "
        List of  Article
        "
	::= { pm10010mpCfgStartuptablefive 1 }


pm10010mpCfgOtxtlhcapabilitiesEntry OBJECT-TYPE
	SYNTAX Pm10010mpCfgOtxtlhcapabilitiesEntry
	MAX-ACCESS not-accessible
	STATUS current
	DESCRIPTION
        "
        Row definition for the startuptablefive
        table
        "
	INDEX   { pm10010mpCfgOtxtlhcapabilitiesIndex }
	::= { pm10010mpCfgOtxtlhcapabilitiesTable 1 }


Pm10010mpCfgOtxtlhcapabilitiesEntry ::=
	SEQUENCE {
	pm10010mpCfgOtxtlhcapabilitiesIndex
		INTEGER,
	pm10010mpCfgComponentTypePortn
		Unsigned32,
	pm10010mpCfgMiscellaneousPortn
		Unsigned32,
	pm10010mpCfgFirstChannelPortn
		Unsigned32,
	pm10010mpCfgLastChannelPortn
		Unsigned32,
	pm10010mpCfgGridPortn
		Unsigned32
	}


pm10010mpCfgOtxtlhcapabilitiesIndex OBJECT-TYPE
	SYNTAX  INTEGER(0..128)
	MAX-ACCESS  read-only
	STATUS current
	DESCRIPTION
        "
        Index definition for the otxtlhcapabilities
        table
        "
	::= { pm10010mpCfgOtxtlhcapabilitiesEntry 1 }


pm10010mpCfgComponentTypePortn OBJECT-TYPE
	SYNTAX  Unsigned32 (0..65536)
	MAX-ACCESS read-only
	STATUS current
	DESCRIPTION
        "
        Component parameters :This OID
        defines the component parameters
        "
	::= { pm10010mpCfgOtxtlhcapabilitiesEntry 3 }


pm10010mpCfgMiscellaneousPortn OBJECT-TYPE
	SYNTAX  Unsigned32 (0..65536)
	MAX-ACCESS read-only
	STATUS current
	DESCRIPTION
        "
        Miscellaneous default settings
        :This OID defines the miscellaneous
        parameters
        "
	::= { pm10010mpCfgOtxtlhcapabilitiesEntry 4 }


pm10010mpCfgFirstChannelPortn OBJECT-TYPE
	SYNTAX  Unsigned32 (0..65536)
	MAX-ACCESS read-only
	STATUS current
	DESCRIPTION
        "
        Number of the first channel of
        the component :This OID defines
        the first channel number of the
        PM
        "
	::= { pm10010mpCfgOtxtlhcapabilitiesEntry 5 }


pm10010mpCfgLastChannelPortn OBJECT-TYPE
	SYNTAX  Unsigned32 (0..65536)
	MAX-ACCESS read-only
	STATUS current
	DESCRIPTION
        "
        Number of the last channel of
         the component :This OID defines
        the last channel number of the
         PM
        "
	::= { pm10010mpCfgOtxtlhcapabilitiesEntry 6 }


pm10010mpCfgGridPortn OBJECT-TYPE
	SYNTAX  Unsigned32 (0..65536)
	MAX-ACCESS read-only
	STATUS current
	DESCRIPTION
        "
        Grid value of the component :This
        OID defines the grid of the PM
        "
	::= { pm10010mpCfgOtxtlhcapabilitiesEntry 7 }



pm10010mpCfgWriteConfiguration  OBJECT-TYPE
	SYNTAX EkiOnOff
	MAX-ACCESS read-write
	STATUS current
	DESCRIPTION
	"Write configuration to module:This OID
	 writes the complete configuration to the module"
	::= { pm10010mpConfig 257 }






--- *****************************************************
---     TRAP OBJECTS
--- *****************************************************

pm10010mptrapPortNumber OBJECT-TYPE
	SYNTAX INTEGER(1..64)
	MAX-ACCESS read-only
	STATUS current
	DESCRIPTION
	"Last port which generates a trap"
	::= { pm10010mptraps 2 }

pm10010mptrapLineNumber OBJECT-TYPE
	SYNTAX INTEGER(1..64)
	MAX-ACCESS read-only
	STATUS current
	DESCRIPTION
	"Last Line which generates a trap"
	::= { pm10010mptraps 3 }

pm10010mptrapBoardNumber OBJECT-TYPE
	SYNTAX INTEGER(1..64)
	MAX-ACCESS read-only
	STATUS current
	DESCRIPTION
	"Last module which generates a trap"
	::= { pm10010mptraps 4 }







--- *****************************************************
---     LINE TRAPS
--- *****************************************************

pm10010mpLineTrapNotUrgentGoesOn NOTIFICATION-TYPE
	OBJECTS {pm10010mpAlmLineDdmWarningPortn, pm10010mptrapLineNumber, pm10010mptrapBoardNumber}
	STATUS current
	--&FILTNAME    "PM10010MP Line Not Urgent ON"
	--&ACTIONS     { log, minor }
	--&MATCH       { pm10010mpAlmLineDdmWarningPortn "on", pm10010mptrapLineNumber "$2", pm10010mptrapBoardNumber "$3"}
	--&MESG        "DDM Warning appears on Line Port $2 of PM10010MP in Slot $3 ($A)"
	DESCRIPTION "Not urgent Line default is activated"
	::= { pm10010mptraps 30 }

pm10010mpLineTrapNotUrgentGoesOff NOTIFICATION-TYPE
	OBJECTS {pm10010mpAlmLineDdmWarningPortn, pm10010mptrapLineNumber, pm10010mptrapBoardNumber}
	STATUS current
	--&FILTNAME    "PM10010MP Line Not Urgent OFF"
	--&ACTIONS     { log, normal }
	--&CLEARS      { "PM10010MP Line Not Urgent ON" }
	--&MATCH       { pm10010mpAlmLineDdmWarningPortn "on", pm10010mptrapLineNumber "$2", pm10010mptrapBoardNumber "$3"}
	--&MESG        "DDM Warning disappears on Line Port $2 of PM10010MP in Slot $3 ($A)"
	DESCRIPTION "Not urgent Line default disappeared"
	::= { pm10010mptraps 31 }

pm10010mpLineTrapUrgentGoesOn NOTIFICATION-TYPE
	OBJECTS {pm10010mpAlmLineDdmAlmPortn, pm10010mptrapLineNumber, pm10010mptrapBoardNumber}
	STATUS current
	--&FILTNAME    "PM10010MP Line Urgent ON"
	--&ACTIONS     { log, major }
	--&MATCH       { pm10010mpAlmLineDdmAlmPortn "on", pm10010mptrapLineNumber "$2", pm10010mptrapBoardNumber "$3"}
	--&MESG        "DDM Alarm appears on Line Port $2 of PM10010MP in Slot $3 ($A)"
	DESCRIPTION "Urgent Line default is activated"
	::= { pm10010mptraps 32 }

pm10010mpLineTrapUrgentGoesOff NOTIFICATION-TYPE
	OBJECTS {pm10010mpAlmLineDdmAlmPortn, pm10010mptrapLineNumber, pm10010mptrapBoardNumber}
	STATUS current
	--&FILTNAME    "PM10010MP Line Urgent OFF"
	--&ACTIONS     { log, normal }
	--&CLEARS      { "PM10010MP Line Urgent ON" }
	--&MATCH       { pm10010mpAlmLineDdmAlmPortn "on", pm10010mptrapLineNumber "$2", pm10010mptrapBoardNumber "$3"}
	--&MESG        "DDM Alarm disappears on Line Port $2 of PM10010MP in Slot $3 ($A)"
	DESCRIPTION "Urgent Line default disappeared"
	::= { pm10010mptraps 33 }

pm10010mpLineTrapCritGoesOn NOTIFICATION-TYPE
	OBJECTS {pm10010mpAlmLineFailPortn , pm10010mpAlmLineHwFailPortn , pm10010mptrapLineNumber, pm10010mptrapBoardNumber}
	STATUS current
	--&FILTNAME    "PM10010MP Line Fail ON"
	--&ACTIONS     { log, critical }
	--&MATCH       { pm10010mpAlmLineFailPortn "on", pm10010mpAlmLineHwFailPortn "*", pm10010mptrapLineNumber "$3", pm10010mptrapBoardNumber "$4"}
	--&MESG        "Line Port $3 Down on PM10010MP in Slot $4 ($A)"

	--&FILTNAME    "PM10010MP Line HW Fail ON (Hidden)"
	--&ACTIONS     { info }
	--&MATCH       { pm10010mpAlmLineFailPortn "*", pm10010mpAlmLineHwFailPortn "on", pm10010mptrapLineNumber "$3", pm10010mptrapBoardNumber "$4"}
	--&MESG        "Line Port $3 Down on PM10010MP in Slot $4 ($A)"
	DESCRIPTION "Critical Line default is activated"
	::= { pm10010mptraps 34 }

pm10010mpLineTrapCritGoesOff NOTIFICATION-TYPE
	OBJECTS {pm10010mpAlmLineFailPortn , pm10010mpAlmLineHwFailPortn , pm10010mptrapLineNumber, pm10010mptrapBoardNumber}
	STATUS current
	--&FILTNAME    "PM10010MP Line Fail OFF"
	--&ACTIONS     { log,  normal }
	--&CLEARS      { "PM10010MP Line Fail ON" }
	--&MATCH       { pm10010mpAlmLineFailPortn "on", pm10010mpAlmLineHwFailPortn "*", pm10010mptrapLineNumber "$3", pm10010mptrapBoardNumber "$4"}
	--&MESG        "Line Port $3 Up on PM10010MP in Slot $4 ($A)"

	--&FILTNAME    "PM10010MP Line HW Fail OFF (Hidden)"
	--&ACTIONS     { info }
	--&MATCH       { pm10010mpAlmLineFailPortn "*", pm10010mpAlmLineHwFailPortn "on", pm10010mptrapLineNumber "$3", pm10010mptrapBoardNumber "$4"}
	--&MESG        "Line Port $3 Up on PM10010MP in Slot $4 ($A)"
	DESCRIPTION "Critical Line default disappeared"
	::= { pm10010mptraps 35 }






--- *****************************************************
---     CLIENT TRAPS
--- *****************************************************

pm10010mpClientTrapNotUrgentGoesOn NOTIFICATION-TYPE
	OBJECTS {pm10010mpAlmSfpDdmWarningPortn, pm10010mptrapPortNumber, pm10010mptrapBoardNumber}
	STATUS current
		--&FILTNAME    "PM10010MP Client Not Urgent ON"
		--&ACTIONS     { log, minor }
		--&MATCH       { pm10010mpAlmSfpDdmWarningPortn "on", pm10010mptrapPortNumber "$2", pm10010mptrapBoardNumber "$3"}
		--&MESG        "DDM Warning appears on Client Port $2 of PM10010MP in Slot $3 ($A)"
	DESCRIPTION "Not urgent client default is activated"
	::= { pm10010mptraps 40 }

pm10010mpClientTrapNotUrgentGoesOff NOTIFICATION-TYPE
	OBJECTS {pm10010mpAlmSfpDdmWarningPortn, pm10010mptrapPortNumber, pm10010mptrapBoardNumber}
	STATUS current
		--&FILTNAME    "PM10010MP Client Not Urgent OFF"
		--&ACTIONS     { log, normal }
		--&CLEARS      { "PM10010MP Client Not Urgent ON" }
		--&MATCH       { pm10010mpAlmSfpDdmWarningPortn "on", pm10010mptrapPortNumber "$2", pm10010mptrapBoardNumber "$3"}
		--&MESG        "DDM Warning appears on Client Port $2 of PM10010MP in Slot $3 ($A)"
	DESCRIPTION "Not urgent client default disappeared"
	::= { pm10010mptraps 41 }

pm10010mpClientTrapUrgentGoesOn NOTIFICATION-TYPE
	OBJECTS {pm10010mpAlmSfpDdmAlmPortn, pm10010mptrapPortNumber, pm10010mptrapBoardNumber}
	STATUS current
		--&FILTNAME    "PM10010MP Client Urgent ON"
		--&ACTIONS     { log, major }
		--&MATCH       { pm10010mpAlmSfpDdmAlmPortn "on", pm10010mptrapPortNumber "$2", pm10010mptrapBoardNumber "$3"}
		--&MESG        "DDM Alarm appears on Client Port $2 of PM10010MP in Slot $3 ($A)"
	DESCRIPTION "Urgent client default is activated"
	::= { pm10010mptraps 42 }

pm10010mpClientTrapUrgentGoesOff NOTIFICATION-TYPE
	OBJECTS {pm10010mpAlmSfpDdmAlmPortn, pm10010mptrapPortNumber, pm10010mptrapBoardNumber}
	STATUS current
		--&FILTNAME    "PM10010MP Client Urgent OFF"
		--&ACTIONS     { log, normal }
		--&CLEARS      { "PM10010MP Client Urgent ON" }
		--&MATCH       { pm10010mpAlmSfpDdmAlmPortn "on", pm10010mptrapPortNumber "$2", pm10010mptrapBoardNumber "$3"}
		--&MESG        "DDM Alarm disappears on Client Port $2 of PM10010MP in Slot $3 ($A)"
	DESCRIPTION "Urgent client default disappeared"
	::= { pm10010mptraps 43 }

pm10010mpClientTrapCritGoesOn NOTIFICATION-TYPE
	OBJECTS {pm10010mpAlmFailAccPortn, pm10010mpAlmHwFailAccPortn, pm10010mptrapPortNumber, pm10010mptrapBoardNumber}
	STATUS current
		--&FILTNAME    "PM10010MP Client Fail ON"
		--&ACTIONS     { log, critical }
		--&MATCH       { pm10010mpAlmFailAccPortn "on", pm10010mpAlmHwFailAccPortn "*", pm10010mptrapPortNumber "$3", pm10010mptrapBoardNumber "$4"}
		--&MESG        "Client Port $3 Down on PM10010MP in Slot $4 ($A)"

		--&FILTNAME    "PM10010MP Client HW Fail ON (Hidden)"
		--&ACTIONS     { info }
		--&MATCH       { pm10010mpAlmFailAccPortn "*", pm10010mpAlmHwFailAccPortn "on", pm10010mptrapPortNumber "$3", pm10010mptrapBoardNumber "$4"}
		--&MESG        "Client Port $3 Down on PM10010MP in Slot $4 ($A)"
	DESCRIPTION "Critical client default is activated"
	::= { pm10010mptraps 44 }

pm10010mpClientTrapCritGoesOff NOTIFICATION-TYPE
	OBJECTS {pm10010mpAlmFailAccPortn, pm10010mpAlmHwFailAccPortn, pm10010mptrapPortNumber, pm10010mptrapBoardNumber}
	STATUS current
		--&FILTNAME    "PM10010MP Client Fail OFF"
		--&ACTIONS     { log, normal }
		--&CLEARS      { "PM10010MP Client Fail ON" }
		--&MATCH       { pm10010mpAlmFailAccPortn "on", pm10010mpAlmHwFailAccPortn "*", pm10010mptrapPortNumber "$3", pm10010mptrapBoardNumber "$4"}
		--&MESG        "Client Port $3 Up on PM10010MP in Slot $4 ($A)"

		--&FILTNAME    "PM10010MP Client HW Fail OFF (Hidden)"
		--&ACTIONS     { info }
		--&MATCH       { pm10010mpAlmFailAccPortn "*", pm10010mpAlmHwFailAccPortn "on", pm10010mptrapPortNumber "$3", pm10010mptrapBoardNumber "$4"}
		--&MESG        "Client Port $3 Up on PM10010MP in Slot $4 ($A)"
	DESCRIPTION "Critical client default disappeared"
	::= { pm10010mptraps 45 }






--- *****************************************************
---     HW TRAPS
--- *****************************************************

pm10010mpPowerTrapUrgentGoesOn NOTIFICATION-TYPE
	OBJECTS {pm10010mpAlmDefFuseB, pm10010mpAlmDefFuseA , pm10010mptrapBoardNumber}
	STATUS current
		--&FILTNAME    "PM10010MP Fuse A Fail ON"
		--&ACTIONS     { log, major }
		--&MATCH       { pm10010mpAlmDefFuseB "*", pm10010mpAlmDefFuseA "on", pm10010mptrapBoardNumber "$3"}
		--&MESG        "Power Input A Fail on PM10010MP in Slot $3 ($A)"

		--&FILTNAME    "PM10010MP Fuse B Fail ON"
		--&ACTIONS     { log, major }
		--&MATCH       { pm10010mpAlmDefFuseB "on", pm10010mpAlmDefFuseA "*", pm10010mptrapBoardNumber "$3"}
		--&MESG        "Power Input B Fail on PM10010MP in Slot $3 ($A)"
	DESCRIPTION "Urgent power supply default is activated"
	::= { pm10010mptraps 50 }

pm10010mpPowerTrapUrgentGoesOff NOTIFICATION-TYPE
	OBJECTS {pm10010mpAlmDefFuseB, pm10010mpAlmDefFuseA , pm10010mptrapBoardNumber}
	STATUS current
		--&FILTNAME    "PM10010MP Fuse A&B Fail OFF"
		--&ACTIONS     { log, normal}
		--&CLEARS      { "PM10010MP Fuse A Fail ON", "PM10010MP Fuse B Fail ON" }
		--&MATCH       { pm10010mpAlmDefFuseB "on", pm10010mpAlmDefFuseA "on", pm10010mptrapBoardNumber "$3"}
		--&MESG        "Power Inputs A and B Present on PM10010MP in Slot $3 ($A)"
	DESCRIPTION "Urgent power supply default disappeared"
	::= { pm10010mptraps 51 }






END
