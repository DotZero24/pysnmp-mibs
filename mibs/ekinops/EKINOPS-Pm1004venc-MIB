-- *****************************************************************
-- EKINOPS-Pm1004venc.TXT:  MIB
--
--MIB Part Number:3MI00022AFAD
--MIB Version:1
--
-- Copyright (c) 2016 by Ekinops
-- All rights reserved.
--
-- *****************************************************************

EKINOPS-Pm1004venc-MIB DEFINITIONS ::= BEGIN

IMPORTS
	ekinops,
	EkiState,
	EkiOnOff,
	EkiMode,
	EkiProtocol,
	EkiApiState,
	EkiSynchroMode,
	EkiMeasureType
			FROM EKINOPS-MIB
        MODULE-IDENTITY,
        OBJECT-TYPE,
        NOTIFICATION-TYPE,
	Unsigned32,
	Integer32,
	Counter32,
	IpAddress
        		FROM SNMPv2-SMI
 	TEXTUAL-CONVENTION,
	DisplayString
                FROM SNMPv2-TC;

modulePm1004venc MODULE-IDENTITY
        LAST-UPDATED "201606020000Z"
        ORGANIZATION "Ekinops"
        CONTACT-INFO
         "Ekinops


          3, rue Blaise Pascal
          F-22300 Lannion / FRANCE

          Tel : +33 (0)2 96 05 00 30
          Fax : +33 (0)2 96 48 62 39

          E-mail: support@ekinops.net"

        DESCRIPTION
          "MIB for managing Ekinops modules with PM1004VENC software"
	REVISION "200909180000Z"
	DESCRIPTION
	  "Creation"
	REVISION "200910270000Z"
	DESCRIPTION
	  "Add LOSynchro on line side"
	REVISION "200910280000Z"
	DESCRIPTION
	  "Add AES Decod Fail alarm"
	REVISION "201003030000Z"
	DESCRIPTION
	  "Probcause,AlarmType - NMS"
	REVISION "201005250000Z"
	DESCRIPTION
	  "OTX-TLH parameters insertion"
	REVISION "201012130000Z"
	DESCRIPTION
	  "Add Inventory of the video client"
	REVISION "201102040000Z"
	DESCRIPTION
	  "Formulas in comments and Event on XFP init"
	REVISION "201207040000Z"
	DESCRIPTION
	  "Minor cosmetic updates"
	REVISION "201403280000Z"
	DESCRIPTION
	  "Probcause,AlarmType - NMS completion"
	REVISION "201412240000Z"
	DESCRIPTION
	  "Labels cosmetic updates"
	REVISION "201605200000Z"
	DESCRIPTION
	  "New AlarmType – synthesisAlarm (12)"
	REVISION "201606020000Z"
	DESCRIPTION
	  "Capabilities objects of Table 5"
        ::= { ekinops 43 }



--- *****************************************************
---     LEAF LEVEL 2
--- *****************************************************


pm1004vencalarms OBJECT IDENTIFIER ::= { modulePm1004venc 2 }
pm1004vencAlmOther OBJECT IDENTIFIER ::= { pm1004vencalarms 1 }
pm1004vencAlmOtherNurg OBJECT IDENTIFIER ::= { pm1004vencAlmOther 1 }
pm1004vencAlmOtherUrg OBJECT IDENTIFIER ::= { pm1004vencAlmOther 2 }
pm1004vencAlmOtherCrit OBJECT IDENTIFIER ::= { pm1004vencAlmOther 3 }

pm1004vencAlmClient OBJECT IDENTIFIER ::= { pm1004vencalarms 2 }
pm1004vencAlmClientNurg OBJECT IDENTIFIER ::= { pm1004vencAlmClient 1 }
pm1004vencAlmClientUrg OBJECT IDENTIFIER ::= { pm1004vencAlmClient 2 }
pm1004vencAlmClientCrit OBJECT IDENTIFIER ::= { pm1004vencAlmClient 3 }

pm1004vencAlmLine OBJECT IDENTIFIER ::= { pm1004vencalarms 3 }
pm1004vencAlmLineNurg OBJECT IDENTIFIER ::= { pm1004vencAlmLine 1 }
pm1004vencAlmLineUrg OBJECT IDENTIFIER ::= { pm1004vencAlmLine 2 }
pm1004vencAlmLineCrit OBJECT IDENTIFIER ::= { pm1004vencAlmLine 3 }





pm1004vencmeasures OBJECT IDENTIFIER ::= { modulePm1004venc 3 }
pm1004vencMesrOther OBJECT IDENTIFIER ::= { pm1004vencmeasures 1 }
pm1004vencMesrClient OBJECT IDENTIFIER ::= { pm1004vencmeasures 2 }
pm1004vencMesrLine OBJECT IDENTIFIER ::= { pm1004vencmeasures 3 }




pm1004venccounters OBJECT IDENTIFIER ::= { modulePm1004venc 4 }
pm1004vencCntOther OBJECT IDENTIFIER ::= { pm1004venccounters 1 }
pm1004vencCntClient OBJECT IDENTIFIER ::= { pm1004venccounters 2 }
pm1004vencCntLine OBJECT IDENTIFIER ::= { pm1004venccounters 3 }


pm1004venccontrolsWrite OBJECT IDENTIFIER ::= { modulePm1004venc 6 }
pm1004vencCtrlOther OBJECT IDENTIFIER ::= { pm1004venccontrolsWrite 1 }
pm1004vencCtrlClient OBJECT IDENTIFIER ::= { pm1004venccontrolsWrite 2 }
pm1004vencCtrlLine OBJECT IDENTIFIER ::= { pm1004venccontrolsWrite 3 }

pm1004vencri OBJECT IDENTIFIER ::= { modulePm1004venc 7 }
pm1004vencriTable OBJECT IDENTIFIER ::= { pm1004vencri 1 }

pm1004vencdownload OBJECT IDENTIFIER ::= { modulePm1004venc 8 }
pm1004vencDwlOther OBJECT IDENTIFIER ::= { pm1004vencdownload 1 }
pm1004vencDwlClient OBJECT IDENTIFIER ::= { pm1004vencdownload 2 }
pm1004vencDwlLine OBJECT IDENTIFIER ::= { pm1004vencdownload 3 }


pm1004vencConfig OBJECT IDENTIFIER ::= { modulePm1004venc 9 }

pm1004venctraps OBJECT IDENTIFIER ::= { modulePm1004venc 10 }



pm1004vencMonitoring OBJECT IDENTIFIER ::= { modulePm1004venc 11}

pm1004vencMonOther OBJECT IDENTIFIER ::= { pm1004vencMonitoring 1 }
pm1004vencMonRmon OBJECT IDENTIFIER ::= { pm1004vencMonOther 3 }

pm1004vencMonClient OBJECT IDENTIFIER ::= { pm1004vencMonitoring 2 }
pm1004vencMonClientRmonCounter OBJECT IDENTIFIER ::= { pm1004vencMonClient 4 }
pm1004vencMonLine OBJECT IDENTIFIER ::= { pm1004vencMonitoring 3 }
pm1004vencMonLineRmonCounter OBJECT IDENTIFIER ::= { pm1004vencMonLine 4 }


--- *****************************************************
--- $$$$$$$$$$$$$$$$$$$$$$$$$$$$$$$$$$$$$$$$$$$$$$$$$$$$$
---     TEXTUAL-CONVENTION
--- $$$$$$$$$$$$$$$$$$$$$$$$$$$$$$$$$$$$$$$$$$$$$$$$$$$$$
--- *****************************************************

Pm1004vencModeTimeSlot ::= TEXTUAL-CONVENTION
    STATUS      current
    DESCRIPTION "different mode for time slot"
    SYNTAX INTEGER {
		singleSplitSelect(256)
           }


Pm1004vencModeAddDrop ::= TEXTUAL-CONVENTION
    STATUS      current
    DESCRIPTION "different mode for client"
    SYNTAX INTEGER {
		singleSplitSelect(256)
           }


Pm1004vencProtectionTimeSlot ::= TEXTUAL-CONVENTION
    STATUS      current
    DESCRIPTION "protection for control"
    SYNTAX INTEGER {
		auto(0),
		manualX2Line2(257),
		manualX1Line1(513)
           }

Pm1004vencProtectionStartUp ::= TEXTUAL-CONVENTION
    STATUS      current
    DESCRIPTION "protection for startup"
    SYNTAX INTEGER {
		auto(2),
		manualX2Line2(0),
		manualX1Line1(1)
           }


Pm1004vencDccMode ::= TEXTUAL-CONVENTION
    STATUS      current
    DESCRIPTION "Mode for DCC"
    SYNTAX INTEGER {
		dccNo(0),
		dcctermLine1(1),
		dcctermLine2(2),
		dcctermLines12(3),
		dccmaster(4),
		dccslaveLine12(7)
           }

Pm1004vencClientOosMode ::= TEXTUAL-CONVENTION
    STATUS      current
    DESCRIPTION "Mode for OOS on client ports"
    SYNTAX INTEGER {
		clientportis(0),
		clienttxoos(1),
		clientrxoos(2),
		clientportoos(3)
           }

Pm1004vencKeyMode ::= TEXTUAL-CONVENTION
    STATUS      current
    DESCRIPTION "Mode for encryption key"
    SYNTAX INTEGER {
		key1(0),
		key2(1)
           }

Pm1004vencOtxMode ::= TEXTUAL-CONVENTION
    STATUS      current
    DESCRIPTION "Different modes on OTX-TLH on line ports"
    SYNTAX INTEGER {
		otx80mode(1),
		otx60mode(2),
		otxadjustmode(4),
           }

Pm1004vencOtxGrid ::= TEXTUAL-CONVENTION
    STATUS      current
    DESCRIPTION "Different grids on OTX-TLH on line ports"
    SYNTAX INTEGER {
		otxgrid200(200),
		otxgrid100(100),
		otxgrid50(50),
           }

Pm1004vencAdjustValue ::= TEXTUAL-CONVENTION
    STATUS      current
    DESCRIPTION "Different values in Adjust mode on OTX-TLH on line ports"
    SYNTAX INTEGER {
		otxadjustvalue0(0),
		otxadjustvalue1(1),
		otxadjustvalue2(2),
		otxadjustvalue3(3),
		otxadjustvalue4(4),
		otxadjustvalue5(5),
		otxadjustvalue6(6),
		otxadjustvalue7(7),
		otxadjustvalue8(8),
		otxadjustvalue9(9),
		otxadjustvalue10(10),
           }

Pm1004vencOtxChannel ::= TEXTUAL-CONVENTION
    STATUS      current
    DESCRIPTION "Channel selection on OTX-TLH on line ports"
    SYNTAX INTEGER {

           }

--- *****************************************************
--- $$$$$$$$$$$$$$$$$$$$$$$$$$$$$$$$$$$$$$$$$$$$$$$$$$$$$
---     REMOTE INVENTORY
--- $$$$$$$$$$$$$$$$$$$$$$$$$$$$$$$$$$$$$$$$$$$$$$$$$$$$$
--- *****************************************************

pm1004vencRinvReloadInventory OBJECT-TYPE
  SYNTAX EkiOnOff
  MAX-ACCESS read-write
  STATUS current
  DESCRIPTION
        "Reload the inventory: This OID triggers an
         inventory reload."
  ::= { pm1004vencri 2 }

pm1004vencRinvHwPlatform OBJECT-TYPE
  SYNTAX DisplayString
  MAX-ACCESS read-only
  STATUS current
  DESCRIPTION
        "HW platform description: This OID contains the
         description of the Hardware platform."
  ::= { pm1004vencri 3 }

pm1004vencRinvModulePlatform OBJECT-TYPE
  SYNTAX DisplayString
  MAX-ACCESS read-only
  STATUS current
  DESCRIPTION
        "Module platform description: This OID contains the
         description of the Module."
  ::= { pm1004vencri 4 }

pm1004vencRinvSwPlatform OBJECT-TYPE
  SYNTAX DisplayString
  MAX-ACCESS read-only
  STATUS current
  DESCRIPTION
        "SW platform description: This OID contains the
         description of the Software platform."
  ::= { pm1004vencri 5 }

pm1004vencRinvGwPlatform OBJECT-TYPE
  SYNTAX DisplayString
  MAX-ACCESS read-only
  STATUS current
  DESCRIPTION
        "GW platform desciption: This OID contains the
         description of the Gateware platform."
  ::= { pm1004vencri 6 }



pm1004vencRinvLineTable OBJECT-TYPE
      SYNTAX  SEQUENCE OF Pm1004vencRinvLineEntry
      MAX-ACCESS  not-accessible
      STATUS  current
      DESCRIPTION
              "List of the XFPs on the selected module"
      ::= { pm1004vencriTable 2 }

pm1004vencRinvLineEntry OBJECT-TYPE
        SYNTAX  Pm1004vencRinvLineEntry
        MAX-ACCESS  not-accessible
        STATUS  current
        DESCRIPTION
              "Row definition for the XFP table"
        INDEX   { pm1004vencRinvLineIndex }
        ::= { pm1004vencRinvLineTable 1 }



Pm1004vencRinvLineEntry::=
        SEQUENCE {
          pm1004vencRinvLineIndex
              Integer32,
          pm1004vencRinvxfpLine
              DisplayString
        }


    pm1004vencRinvLineIndex OBJECT-TYPE
        SYNTAX  Integer32(1..16)
        MAX-ACCESS  read-only
        STATUS  current
        DESCRIPTION
              "Index for XFP table"
        ::= { pm1004vencRinvLineEntry 1 }


    pm1004vencRinvxfpLine OBJECT-TYPE
        SYNTAX  DisplayString
        MAX-ACCESS  read-only
        STATUS  current
        DESCRIPTION
              "Inventory for the XFP: This OID contains the inventory for the XFP"
        ::= { pm1004vencRinvLineEntry 2 }




pm1004vencRinvClientTable OBJECT-TYPE
      SYNTAX  SEQUENCE OF Pm1004vencRinvClientEntry
      MAX-ACCESS  not-accessible
      STATUS  current
      DESCRIPTION
              "List of the video clients on the selected module"
      ::= { pm1004vencriTable 1 }

pm1004vencRinvClientEntry OBJECT-TYPE
        SYNTAX  Pm1004vencRinvClientEntry
        MAX-ACCESS  not-accessible
        STATUS  current
        DESCRIPTION
              "Row definition for the video client table"
        INDEX   { pm1004vencRinvClientIndex }
        ::= { pm1004vencRinvClientTable 1 }



Pm1004vencRinvClientEntry::=
        SEQUENCE {
          pm1004vencRinvClientIndex
              Integer32,
          pm1004vencRinvClient
              DisplayString
        }


    pm1004vencRinvClientIndex OBJECT-TYPE
        SYNTAX  Integer32(1..16)
        MAX-ACCESS  read-only
        STATUS  current
        DESCRIPTION
              "Index for video client table"
        ::= { pm1004vencRinvClientEntry 1 }


    pm1004vencRinvClient OBJECT-TYPE
        SYNTAX  DisplayString
        MAX-ACCESS  read-only
        STATUS  current
        DESCRIPTION
              "Inventory for the video client: This OID contains the inventory for the video client"
        ::= { pm1004vencRinvClientEntry 2 }







--- *****************************************************
--- $$$$$$$$$$$$$$$$$$$$$$$$$$$$$$$$$$$$$$$$$$$$$$$$$$$$$
---     ALARMS
--- $$$$$$$$$$$$$$$$$$$$$$$$$$$$$$$$$$$$$$$$$$$$$$$$$$$$$
--- *****************************************************



--- *****************************************************
---     LEAF for the synthAlm0 article
--- *****************************************************
pm1004vencAlmsynthAlm0 OBJECT IDENTIFIER ::= { pm1004vencAlmOtherCrit 0 }




pm1004vencAlmDefFuseB OBJECT-TYPE
	  SYNTAX EkiOnOff
	  MAX-ACCESS read-only
	  STATUS current
	  DESCRIPTION
        "
        Fuse B Fail :This OID indicates
        that the fuse of the power input
        B is in fail condition  <Help>
          Status of the Fuse B <Condtype>
        DEF_FUSE_B <Probcause> powerProblem
        (36) <Alarmtype> equipmentAlarm
        (5) <Polarity> (2)
        "
	  ::= { pm1004vencAlmsynthAlm0 16 }



pm1004vencAlmDefFuseA OBJECT-TYPE
	  SYNTAX EkiOnOff
	  MAX-ACCESS read-only
	  STATUS current
	  DESCRIPTION
        "
        Fuse A Fail :This OID indicates
        that the fuse of the power input
        A is in fail condition  <Help>
          Status of the Fuse A <Condtype>
        DEF_FUSE_A <Probcause> powerProblem
        (36) <Alarmtype> equipmentAlarm
        (5) <Polarity> (2)
        "
	  ::= { pm1004vencAlmsynthAlm0 15 }



pm1004vencAlmModGlobFail OBJECT-TYPE
	  SYNTAX EkiOnOff
	  MAX-ACCESS read-only
	  STATUS current
	  DESCRIPTION
        "
        Module Failure :This OID is set
        on detection of a failure originating
        from the PM <Condtype> MOD_GLOB_FAIL
        <Probcause> equipmentMalfunction
        (16) <Alarmtype> synthesisAlarm
        (12)  <Polarity> (2)
        "
	  ::= { pm1004vencAlmsynthAlm0 9 }



--- *****************************************************
---     LEAF for the synthAlm2 article
--- *****************************************************
pm1004vencAlmsynthAlm2 OBJECT IDENTIFIER ::= { pm1004vencAlmOtherNurg 2 }




pm1004vencAlmMaintenanceOn OBJECT-TYPE
	  SYNTAX EkiOnOff
	  MAX-ACCESS read-only
	  STATUS current
	  DESCRIPTION
        "
        Maintenance Mode :This OID indicates
        that the PM is in maintenance mode.
         <Help>  This alarm indicates that
        the maintenance mode is enabled
        on the PM <Condtype> MAINTENANCE_ON
        <Probcause> other (1) <Alarmtype>
        other (1) <Polarity> (2)
        "
	  ::= { pm1004vencAlmsynthAlm2 5 }



pm1004vencAlmCorrelatOff OBJECT-TYPE
	  SYNTAX EkiOnOff
	  MAX-ACCESS read-only
	  STATUS current
	  DESCRIPTION
        "
        Not Used :This OID, when set,
         indicates that alarm correlation
        is not being performed. <Condtype>
        CORRELAT_OFF <Probcause> other
         (1) <Alarmtype> other (1) <Polarity>
        (2)
        "
	  ::= { pm1004vencAlmsynthAlm2 4 }



pm1004vencAlmConfTableLoad OBJECT-TYPE
	  SYNTAX EkiOnOff
	  MAX-ACCESS read-only
	  STATUS current
	  DESCRIPTION
        "
        PM Configuration Load :This OID
         is at 1 during the loading of
         configuration tables in the modules
        RAM. <Condtype> CONF_TABLE_LOAD
        <Probcause> other (1) <Alarmtype>
        other (1) <Polarity> (2)
        "
	  ::= { pm1004vencAlmsynthAlm2 3 }



pm1004vencAlmInvUpload OBJECT-TYPE
	  SYNTAX EkiOnOff
	  MAX-ACCESS read-only
	  STATUS current
	  DESCRIPTION
        "
        Inventory Upload :This OID is
         at 1 during the uploading of PM
        inventory information. <Condtype>
        INV_UPLOAD <Probcause> other (1)
        <Alarmtype> other (1) <Polarity>
        (2)
        "
	  ::= { pm1004vencAlmsynthAlm2 2 }



pm1004vencAlmConfTableSave OBJECT-TYPE
	  SYNTAX EkiOnOff
	  MAX-ACCESS read-only
	  STATUS current
	  DESCRIPTION
        "
        PM Configuration Save :This OID
        is at 1 during the saving of a
         new configuration table in the
        module Flash memory. <Condtype>
        CONF_TABLE_SAVE <Probcause> other
        (1) <Alarmtype> other (1) <Polarity>
        (2)
        "
	  ::= { pm1004vencAlmsynthAlm2 1 }



--- *********************************************************
---     TABLE for the pm1004vencAlmsynthAlmLine articles
--- *********************************************************

pm1004vencAlmsynthAlmLineTable OBJECT-TYPE
	SYNTAX  SEQUENCE OF Pm1004vencAlmsynthAlmLineEntry
	MAX-ACCESS not-accessible
	STATUS current
	DESCRIPTION
        "
        List of pm1004vencAlmsynthAlmLine
        Article
        "
	::= { pm1004vencAlmLineCrit 7 }


pm1004vencAlmsynthAlmLineEntry OBJECT-TYPE
	SYNTAX Pm1004vencAlmsynthAlmLineEntry
	MAX-ACCESS not-accessible
	STATUS current
	DESCRIPTION
        "
        Row definition for the pm1004vencAlmsynthAlmLine
        table
        "
	INDEX   { pm1004vencAlmsynthAlmLineIndex }
	::= { pm1004vencAlmsynthAlmLineTable 1 }


Pm1004vencAlmsynthAlmLineEntry ::=
	SEQUENCE {
	pm1004vencAlmsynthAlmLineIndex
		INTEGER,
	pm1004vencAlmLineActivePortn
		EkiOnOff,
	pm1004vencAlmLineFailPortn
		EkiOnOff,
	pm1004vencAlmLineDdmCritPortn
		EkiOnOff,
	pm1004vencAlmLineDdmAlmPortn
		EkiOnOff,
	pm1004vencAlmLineDdmWarningPortn
		EkiOnOff,
	pm1004vencAlmLineLocalOosPortn
		EkiOnOff,
	pm1004vencAlmXfpTxOffPortn
		EkiOnOff,
	pm1004vencAlmLineHwFailPortn
		EkiOnOff,
	pm1004vencAlmXfpInitNotComplPortn
		EkiOnOff,
	pm1004vencAlmXfpAbsentPortn
		EkiOnOff
	}


pm1004vencAlmsynthAlmLineIndex OBJECT-TYPE
	SYNTAX  INTEGER(0..128)
	MAX-ACCESS  read-only
	STATUS current
	DESCRIPTION
        "
        Index definition for the pm1004vencAlmsynthAlmLine
        table
        "
	::= { pm1004vencAlmsynthAlmLineEntry 1 }


pm1004vencAlmLineActivePortn OBJECT-TYPE
	SYNTAX  EkiOnOff
	MAX-ACCESS read-only
	STATUS current
	DESCRIPTION
        "
        Line Active :This bit indicates
        the line #n is active on receive
        side  <Help>  This status indicates
        whether the line is active or standby.
        <Condtype> LINE_ACTIVE <Probcause>
        informationalStatus(1000) <Alarmtype>
        other (1) <Polarity> (2)
        "
	::= { pm1004vencAlmsynthAlmLineEntry 17 }


pm1004vencAlmLineFailPortn OBJECT-TYPE
	SYNTAX  EkiOnOff
	MAX-ACCESS read-only
	STATUS current
	DESCRIPTION
        "
        Line Port Failure :This OID indicates
        a failure on the line port <Condtype>
        LINE_FAIL <Probcause> equipmentMalfunction
        (16) <Alarmtype> synthesisAlarm
        (12)  <Polarity> (2)
        "
	::= { pm1004vencAlmsynthAlmLineEntry 13 }


pm1004vencAlmLineDdmCritPortn OBJECT-TYPE
	SYNTAX  EkiOnOff
	MAX-ACCESS read-only
	STATUS current
	DESCRIPTION
        "
        Custom Alarm On Line XFP/OTX DDM
        :This OID indicates a Custom alarm
        is present coming out of Line optical
        interface DDM    <Help>   This
         alarm indicates if a DDM Custom
        Alarm has been detected on the
         line transceiver <Condtype> LINE_DDM_CRIT
        <Probcause> equipmentMalfunction
        (16) <Alarmtype> synthesisAlarm
        (12)  <Polarity> (2)
        "
	::= { pm1004vencAlmsynthAlmLineEntry 12 }


pm1004vencAlmLineDdmAlmPortn OBJECT-TYPE
	SYNTAX  EkiOnOff
	MAX-ACCESS read-only
	STATUS current
	DESCRIPTION
        "
        Alarm On Line Optical Module DDM
        :This OID indicates an alarm is
        present coming out of Line optical
        interface DDM  <Help>  This alarm
        indicates if a DDM Alarm has been
        detected on the line transceiver
        <Condtype> LINE_DDM_ALM <Probcause>
        equipmentMalfunction (16) <Alarmtype>
        synthesisAlarm (12)  <Polarity>
        (2)
        "
	::= { pm1004vencAlmsynthAlmLineEntry 11 }


pm1004vencAlmLineDdmWarningPortn OBJECT-TYPE
	SYNTAX  EkiOnOff
	MAX-ACCESS read-only
	STATUS current
	DESCRIPTION
        "
        Warning On Line Optical Module
        DDM :This OID indicates a warning
        is present coming out of Line optical
        interface DDM  <Help>  This alarm
        indicates if a DDM Warning has
         been detected on the line transceiver
        <Condtype> LINE_DDM_WARNING <Probcause>
        equipmentMalfunction (16) <Alarmtype>
        synthesisAlarm (12)  <Polarity>
        (2)
        "
	::= { pm1004vencAlmsynthAlmLineEntry 10 }


pm1004vencAlmLineLocalOosPortn OBJECT-TYPE
	SYNTAX  EkiOnOff
	MAX-ACCESS read-only
	STATUS current
	DESCRIPTION
        "
        Line Port In Service :This OID
        indicates that the Line port is
        In Service (1) of Out or Service
        (2)  <Help>  This status indicates
        if the line port is in service
         <Condtype> LINE_LOCAL_OOS <Probcause>
        informationalStatus(1000) <Alarmtype>
        other (1) <Polarity> (2)
        "
	::= { pm1004vencAlmsynthAlmLineEntry 7 }


pm1004vencAlmXfpTxOffPortn OBJECT-TYPE
	SYNTAX  EkiOnOff
	MAX-ACCESS read-only
	STATUS current
	DESCRIPTION
        "
        Line Optical Module Laser Shutdown
        :This OID indicates the line optical
        output power is on  <Help>  This
        status indicates if the line transceiver
        laser is ON or OFF <Condtype> XFP_TX_OFF
        <Probcause> other (1) <Alarmtype>
        equipmentAlarm (5) <Polarity> (2)
        "
	::= { pm1004vencAlmsynthAlmLineEntry 6 }


pm1004vencAlmLineHwFailPortn OBJECT-TYPE
	SYNTAX  EkiOnOff
	MAX-ACCESS read-only
	STATUS current
	DESCRIPTION
        "
        Line Port HW Failure :This OID
        indicates a failure on line port,
        most probably caused by a HW issue
        <Condtype> LINE_HW_FAIL <Probcause>
        equipmentMalfunction (16) <Alarmtype>
        synthesisAlarm (12)  <Polarity>
        (2)
        "
	::= { pm1004vencAlmsynthAlmLineEntry 5 }


pm1004vencAlmXfpInitNotComplPortn OBJECT-TYPE
	SYNTAX  EkiOnOff
	MAX-ACCESS read-only
	STATUS current
	DESCRIPTION
        "
        Line Optical Module Ready :This
        OID indicates that the optical
         interface (XFP or OTX) is not
         operational.  <Help>  This status
        indicates if the line transceiver
        has been correctly initialized
         <Condtype> XFP_INIT_NOT_COMPL
         <Probcause> equipmentMalfunction
        (16) <Alarmtype>  <Polarity> (2)
        <Event> ObjectCDINV
        "
	::= { pm1004vencAlmsynthAlmLineEntry 3 }


pm1004vencAlmXfpAbsentPortn OBJECT-TYPE
	SYNTAX  EkiOnOff
	MAX-ACCESS read-only
	STATUS current
	DESCRIPTION
        "
        Line Optical Module Absent :This
        OID indicates that the line optical
        interface (XFP or OTX) is not plugged
        in.  <Help>  This alarm indicates
        if the line transceiver is present.
        <Condtype> XFP_ABSENT <Probcause>
        inputOutputDeviceError (24) <Alarmtype>
         <Polarity> (2) <Event> ObjectCDINV
        "
	::= { pm1004vencAlmsynthAlmLineEntry 2 }


--- *********************************************************
---     TABLE for the pm1004vencAlmsynthAlmPort articles
--- *********************************************************

pm1004vencAlmsynthAlmPortTable OBJECT-TYPE
	SYNTAX  SEQUENCE OF Pm1004vencAlmsynthAlmPortEntry
	MAX-ACCESS not-accessible
	STATUS current
	DESCRIPTION
        "
        List of pm1004vencAlmsynthAlmPort
        Article
        "
	::= { pm1004vencAlmClientCrit 8 }


pm1004vencAlmsynthAlmPortEntry OBJECT-TYPE
	SYNTAX Pm1004vencAlmsynthAlmPortEntry
	MAX-ACCESS not-accessible
	STATUS current
	DESCRIPTION
        "
        Row definition for the pm1004vencAlmsynthAlmPort
        table
        "
	INDEX   { pm1004vencAlmsynthAlmPortIndex }
	::= { pm1004vencAlmsynthAlmPortTable 1 }


Pm1004vencAlmsynthAlmPortEntry ::=
	SEQUENCE {
	pm1004vencAlmsynthAlmPortIndex
		INTEGER,
	pm1004vencAlmUpCsfPortn
		EkiOnOff,
	pm1004vencAlmFailAccPortn
		EkiOnOff,
	pm1004vencAlmDwCaisPortn
		EkiOnOff,
	pm1004vencAlmClientLocalOosRxPortn
		EkiOnOff,
	pm1004vencAlmClientLocalOosTxPortn
		EkiOnOff,
	pm1004vencAlmDwLsdPortn
		EkiOnOff,
	pm1004vencAlmHwFailAccPortn
		EkiOnOff
	}


pm1004vencAlmsynthAlmPortIndex OBJECT-TYPE
	SYNTAX  INTEGER(0..128)
	MAX-ACCESS  read-only
	STATUS current
	DESCRIPTION
        "
        Index definition for the pm1004vencAlmsynthAlmPort
        table
        "
	::= { pm1004vencAlmsynthAlmPortEntry 1 }


pm1004vencAlmUpCsfPortn OBJECT-TYPE
	SYNTAX  EkiOnOff
	MAX-ACCESS read-only
	STATUS current
	DESCRIPTION
        "
        Client Signal Fail Inserted :This
        OID indicates a CSF has been inserted
        in the upstream client port.  <Help>
         This status indicates if a Client
        Signal Fail is currently inserted
        on the line signal for this client
        port <Condtype> UP_CSF_1 <Probcause>
        other (1) <Alarmtype> other (1)
        <Polarity> (2)
        "
	::= { pm1004vencAlmsynthAlmPortEntry 17 }


pm1004vencAlmFailAccPortn OBJECT-TYPE
	SYNTAX  EkiOnOff
	MAX-ACCESS read-only
	STATUS current
	DESCRIPTION
        "
        Client Access Fail :This OID indicates
        a failure on the Client port <Condtype>
        FAIL_ACC_1 <Probcause> equipmentMalfunction
        (16) <Alarmtype> synthesisAlarm
        (12)  <Polarity> (2)
        "
	::= { pm1004vencAlmsynthAlmPortEntry 13 }


pm1004vencAlmDwCaisPortn OBJECT-TYPE
	SYNTAX  EkiOnOff
	MAX-ACCESS read-only
	STATUS current
	DESCRIPTION
        "
        Client AIS Inserted :This OID
         indicates a CAIS has been inserted
        on the output client port.  <Help>
          This status indictaes if a Client
        Alarm Indication Signal is currently
        inserted on the client interface
        <Condtype> DW_CAIS_1 <Probcause>
        informationalStatus(1000) <Alarmtype>
        other (1) <Polarity> (2)
        "
	::= { pm1004vencAlmsynthAlmPortEntry 9 }


pm1004vencAlmClientLocalOosRxPortn OBJECT-TYPE
	SYNTAX  EkiOnOff
	MAX-ACCESS read-only
	STATUS current
	DESCRIPTION
        "
        Rx Client Port In Service :This
        OID indicates that the local Rx
        Client port is In Service (1) or
        Out of Service (2)  <Help>   This
        status indicates if the local Rx
        client port is in service <Condtype>
        CLIENT_LOCAL_OOS_RX <Probcause>
        informationalStatus(1000) <Alarmtype>
        other (1) <Polarity> (2)
        "
	::= { pm1004vencAlmsynthAlmPortEntry 8 }


pm1004vencAlmClientLocalOosTxPortn OBJECT-TYPE
	SYNTAX  EkiOnOff
	MAX-ACCESS read-only
	STATUS current
	DESCRIPTION
        "
        Tx Client Port In Service :This
        OID indicates that the local Tx
        Client port is In Service (1) or
        Out of Service (2)  <Help>   This
        status indicates if the local Tx
        client port is in service
 <Condtype>
        CLIENT_LOCAL_OOS_TX <Probcause>
        informationalStatus(1000) <Alarmtype>
        other (1) <Polarity> (2)
        "
	::= { pm1004vencAlmsynthAlmPortEntry 7 }


pm1004vencAlmDwLsdPortn OBJECT-TYPE
	SYNTAX  EkiOnOff
	MAX-ACCESS read-only
	STATUS current
	DESCRIPTION
        "
        Client Signal Shutdown :This OID
        indicates the Client SFP transmitter
        output is ON.   <Help>   This status
        indicates if the client transceiver
         is ON or OFF <Condtype> DW_LSD_1
        <Probcause> other (1) <Alarmtype>
        equipmentAlarm (5) <Polarity> (2)
        "
	::= { pm1004vencAlmsynthAlmPortEntry 6 }


pm1004vencAlmHwFailAccPortn OBJECT-TYPE
	SYNTAX  EkiOnOff
	MAX-ACCESS read-only
	STATUS current
	DESCRIPTION
        "
        Client HW Fail :This OID indicates
        a failure on client port, most
         probably caused by a HW issue.
        <Condtype> HW_FAIL_ACC_1 <Probcause>
        equipmentMalfunction (16) <Alarmtype>
        synthesisAlarm (12)  <Polarity>
        (2)
        "
	::= { pm1004vencAlmsynthAlmPortEntry 5 }


--- *********************************************************
---     TABLE for the pm1004vencAlmaccessioAlm articles
--- *********************************************************

pm1004vencAlmaccessioAlmTable OBJECT-TYPE
	SYNTAX  SEQUENCE OF Pm1004vencAlmaccessioAlmEntry
	MAX-ACCESS not-accessible
	STATUS current
	DESCRIPTION
        "
        List of pm1004vencAlmaccessioAlm
        Article
        "
	::= { pm1004vencAlmClientCrit 16 }


pm1004vencAlmaccessioAlmEntry OBJECT-TYPE
	SYNTAX Pm1004vencAlmaccessioAlmEntry
	MAX-ACCESS not-accessible
	STATUS current
	DESCRIPTION
        "
        Row definition for the pm1004vencAlmaccessioAlm
        table
        "
	INDEX   { pm1004vencAlmaccessioAlmIndex }
	::= { pm1004vencAlmaccessioAlmTable 1 }


Pm1004vencAlmaccessioAlmEntry ::=
	SEQUENCE {
	pm1004vencAlmaccessioAlmIndex
		INTEGER,
	pm1004vencAlmUpLosPortn
		EkiOnOff
	}


pm1004vencAlmaccessioAlmIndex OBJECT-TYPE
	SYNTAX  INTEGER(0..128)
	MAX-ACCESS  read-only
	STATUS current
	DESCRIPTION
        "
        Index definition for the pm1004vencAlmaccessioAlm
        table
        "
	::= { pm1004vencAlmaccessioAlmEntry 1 }


pm1004vencAlmUpLosPortn OBJECT-TYPE
	SYNTAX  EkiOnOff
	MAX-ACCESS read-only
	STATUS current
	DESCRIPTION
        "
        Client Input Loss Of Signal :This
        OID indicates that no signal is
        present on the client port  <Help>
          This alarm indicates if a signal
        is detected on the client input
        <Condtype> UP_LOS_1 <Probcause>
        receiveFailure (41) <Alarmtype>
        physicalViolation (9) <Polarity>
        (2)
        "
	::= { pm1004vencAlmaccessioAlmEntry 5 }


--- *********************************************************
---     TABLE for the pm1004vencAlmmapperDeAlm articles
--- *********************************************************

pm1004vencAlmmapperDeAlmTable OBJECT-TYPE
	SYNTAX  SEQUENCE OF Pm1004vencAlmmapperDeAlmEntry
	MAX-ACCESS not-accessible
	STATUS current
	DESCRIPTION
        "
        List of pm1004vencAlmmapperDeAlm
        Article
        "
	::= { pm1004vencAlmClientCrit 72 }


pm1004vencAlmmapperDeAlmEntry OBJECT-TYPE
	SYNTAX Pm1004vencAlmmapperDeAlmEntry
	MAX-ACCESS not-accessible
	STATUS current
	DESCRIPTION
        "
        Row definition for the pm1004vencAlmmapperDeAlm
        table
        "
	INDEX   { pm1004vencAlmmapperDeAlmIndex }
	::= { pm1004vencAlmmapperDeAlmTable 1 }


Pm1004vencAlmmapperDeAlmEntry ::=
	SEQUENCE {
	pm1004vencAlmmapperDeAlmIndex
		INTEGER,
	pm1004vencAlmDwBufferOvlPortn
		EkiOnOff,
	pm1004vencAlmDwCsfDetPortn
		EkiOnOff,
	pm1004vencAlmUpBufferOvlPortn
		EkiOnOff,
	pm1004vencAlmUpAccOosPortn
		EkiOnOff
	}


pm1004vencAlmmapperDeAlmIndex OBJECT-TYPE
	SYNTAX  INTEGER(0..128)
	MAX-ACCESS  read-only
	STATUS current
	DESCRIPTION
        "
        Index definition for the pm1004vencAlmmapperDeAlm
        table
        "
	::= { pm1004vencAlmmapperDeAlmEntry 1 }


pm1004vencAlmDwBufferOvlPortn OBJECT-TYPE
	SYNTAX  EkiOnOff
	MAX-ACCESS read-only
	STATUS current
	DESCRIPTION
        "
        Client Downstream Buffer Overload
        :This OID indicates that the de-mapper
        buffer for client port is in overload.
         <Help>  This alarm indicates if
        there is a downstream FIFO overload
        for this client port <Condtype>
        DW_BUFFER_OVL_1 <Probcause> equipmentMalfunction
        (16) <Alarmtype> equipmentAlarm
        (5) <Polarity> (2)
        "
	::= { pm1004vencAlmmapperDeAlmEntry 15 }


pm1004vencAlmDwCsfDetPortn OBJECT-TYPE
	SYNTAX  EkiOnOff
	MAX-ACCESS read-only
	STATUS current
	DESCRIPTION
        "
        Client Signal Fail Detected :This
        OID indicates that a CSF has been
        detected on client port in the
         downstream direction   <Help>
          This alarm indicates if a Client
        Signal Fail has been detected in
        the incoming line frame for this
        client port <Condtype> DW_CSF_DET_1
        <Probcause> receiveFailure (41)
        <Alarmtype> equipmentAlarm (5)
         <Polarity> (2)
        "
	::= { pm1004vencAlmmapperDeAlmEntry 12 }


pm1004vencAlmUpBufferOvlPortn OBJECT-TYPE
	SYNTAX  EkiOnOff
	MAX-ACCESS read-only
	STATUS current
	DESCRIPTION
        "
        Client Upstream Buffer Overload
        :This OID indicates that the rate
        adaptation buffer for client port
        is in overload.  <Help>  This alarm
        indicates if there is a upstream
        FIFO overload for this client port
        <Condtype> UP_BUFFER_OVL_1 <Probcause>
        receiveFailure (41) <Alarmtype>
        integrityViolation (7) <Polarity>
        (2)
        "
	::= { pm1004vencAlmmapperDeAlmEntry 11 }


pm1004vencAlmUpAccOosPortn OBJECT-TYPE
	SYNTAX  EkiOnOff
	MAX-ACCESS read-only
	STATUS current
	DESCRIPTION
        "
        Client Loss Of Synchro :This OID
        indicates the upstream client input
        port has lost synchronization on
        its decoder   <Help>   This alarms
        indicates if the input client signal
        is correctly synchronized with
         the decoder <Condtype> UP_ACC_OOS_1
        <Probcause> receiveFailure (41)
        <Alarmtype> integrityViolation
         (7) <Polarity> (2)
        "
	::= { pm1004vencAlmmapperDeAlmEntry 2 }


--- *********************************************************
---     TABLE for the pm1004vencAlmvideoProtocolStatus articles
--- *********************************************************

pm1004vencAlmvideoProtocolStatusTable OBJECT-TYPE
	SYNTAX  SEQUENCE OF Pm1004vencAlmvideoProtocolStatusEntry
	MAX-ACCESS not-accessible
	STATUS current
	DESCRIPTION
        "
        List of pm1004vencAlmvideoProtocolStatus
        Article
        "
	::= { pm1004vencAlmClientCrit 112 }


pm1004vencAlmvideoProtocolStatusEntry OBJECT-TYPE
	SYNTAX Pm1004vencAlmvideoProtocolStatusEntry
	MAX-ACCESS not-accessible
	STATUS current
	DESCRIPTION
        "
        Row definition for the pm1004vencAlmvideoProtocolStatus
        table
        "
	INDEX   { pm1004vencAlmvideoProtocolStatusIndex }
	::= { pm1004vencAlmvideoProtocolStatusTable 1 }


Pm1004vencAlmvideoProtocolStatusEntry ::=
	SEQUENCE {
	pm1004vencAlmvideoProtocolStatusIndex
		INTEGER,
	pm1004vencAlmDvbAsiRxPortn
		EkiOnOff,
	pm1004vencAlmHdSdiNtscRxPortn
		EkiOnOff,
	pm1004vencAlmHdSdiPalRxPortn
		EkiOnOff,
	pm1004vencAlmSdiRxPortn
		EkiOnOff,
	pm1004vencAlmDvbAsiTxPortn
		EkiOnOff,
	pm1004vencAlmHdSdiNtscTxPortn
		EkiOnOff,
	pm1004vencAlmHdSdiPalTxPortn
		EkiOnOff,
	pm1004vencAlmSdiTxPortn
		EkiOnOff
	}


pm1004vencAlmvideoProtocolStatusIndex OBJECT-TYPE
	SYNTAX  INTEGER(0..128)
	MAX-ACCESS  read-only
	STATUS current
	DESCRIPTION
        "
        Index definition for the pm1004vencAlmvideoProtocolStatus
        table
        "
	::= { pm1004vencAlmvideoProtocolStatusEntry 1 }


pm1004vencAlmDvbAsiRxPortn OBJECT-TYPE
	SYNTAX  EkiOnOff
	MAX-ACCESS read-only
	STATUS current
	DESCRIPTION
        "
        DVB-ASI Detected On Rx :This OID
        indicates that the DVB-ASI protocol
        has been detected on the receive
        side of the port (only significant
        on Video2 to Video 5 ports)  <Help>
          This status indicates that the
        DVB-ASI protocol has been detected
        on the receive side of the port
        (only significant on Video2 to
         Video 5 ports) <Condtype> DVB_ASI_RX_1
        <Probcause> informationalStatus(1000)
        <Alarmtype> other (1) <Polarity>
        (2)
        "
	::= { pm1004vencAlmvideoProtocolStatusEntry 13 }


pm1004vencAlmHdSdiNtscRxPortn OBJECT-TYPE
	SYNTAX  EkiOnOff
	MAX-ACCESS read-only
	STATUS current
	DESCRIPTION
        "
        HD-SDI-NTSC Detected On Rx :This
        OID indicates that the HD-SDI-NTSC
        protocol has been detected on the
        receive side of the port (only
         significant on Video2 to Video
        5 ports)
  <Help>   This status
        indicates that the HD-SDI-NTSC
         protocol has been detected on
         the receive side of the port (only
        significant on Video2 to Video
         5 ports) <Condtype> HD_SDI_NTSC_RX_1
        <Probcause> informationalStatus(1000)
        <Alarmtype> other (1) <Polarity>
        (2)
        "
	::= { pm1004vencAlmvideoProtocolStatusEntry 12 }


pm1004vencAlmHdSdiPalRxPortn OBJECT-TYPE
	SYNTAX  EkiOnOff
	MAX-ACCESS read-only
	STATUS current
	DESCRIPTION
        "
        HD-SDI-PAL Detected On Rx :This
        OID indicates that the HD-SDI-PAL
        protocol has been detected on the
        receive side of the port (only
         significant on Video2 to Video
        5 ports)
  <Help>   This status
        indicates that the HD-SDI-PAL protocol
        has been detected on the receive
        side of the port (only significant
        on Video2 to Video 5 ports) <Condtype>
        HD_SDI_PAL_RX_1 <Probcause> informationalStatus(1000)
        <Alarmtype> other (1) <Polarity>
        (2)
        "
	::= { pm1004vencAlmvideoProtocolStatusEntry 11 }


pm1004vencAlmSdiRxPortn OBJECT-TYPE
	SYNTAX  EkiOnOff
	MAX-ACCESS read-only
	STATUS current
	DESCRIPTION
        "
        SDI Detected On Rx :This OID indicates
        that the SDI protocol has been
         detected on the receive side of
        the port (only significant on Video2
        to Video 5 ports)
  <Help>   This
        status indicates that the SDI protocol
        has been detected on the receive
        side of the port (only significant
        on Video2 to Video 5 ports) <Condtype>
        SDI_RX_1 <Probcause> informationalStatus(1000)
        <Alarmtype> other (1) <Polarity>
        (2)
        "
	::= { pm1004vencAlmvideoProtocolStatusEntry 10 }


pm1004vencAlmDvbAsiTxPortn OBJECT-TYPE
	SYNTAX  EkiOnOff
	MAX-ACCESS read-only
	STATUS current
	DESCRIPTION
        "
        DVB-ASI Detected On Tx :This OID
        indicates that the DVB-ASI protocol
        has been detected on the transmit
        side of the port (only significant
        on Video2 to Video 5 ports)
  <Help>
          This status indicates that the
        DVB-ASI protocol has been detected
        on the transmit side of the port
        (only significant on Video2 to
         Video 5 ports) <Condtype> DVB_ASI_TX_1
        <Probcause> informationalStatus(1000)
        <Alarmtype> other (1) <Polarity>
        (2)
        "
	::= { pm1004vencAlmvideoProtocolStatusEntry 5 }


pm1004vencAlmHdSdiNtscTxPortn OBJECT-TYPE
	SYNTAX  EkiOnOff
	MAX-ACCESS read-only
	STATUS current
	DESCRIPTION
        "
        HD-SDI-NTSC Detected On Tx :This
        OID indicates that the HD-SDI-NTSC
        protocol has been detected on the
        transmit side of the port (only
        significant on Video2 to Video
         5 ports)
  <Help>   This status
        indicates that the HD-SDI-NTSC
         protocol has been detected on
         the transmit side of the port
         (only significant on Video2 to
        Video 5 ports) <Condtype> HD_SDI_NTSC_TX_1
        <Probcause> informationalStatus(1000)
        <Alarmtype> other (1) <Polarity>
        (2)
        "
	::= { pm1004vencAlmvideoProtocolStatusEntry 4 }


pm1004vencAlmHdSdiPalTxPortn OBJECT-TYPE
	SYNTAX  EkiOnOff
	MAX-ACCESS read-only
	STATUS current
	DESCRIPTION
        "
        HD-SDI-PAL Detected On Tx :This
        OID indicates that the HD-SDI-PAL
        protocol has been detected on the
        transmit side of the port (only
        significant on Video2 to Video
         5 ports)  <Help>   This status
        indicates that the HD-SDI-PAL protocol
        has been detected on the transmit
        side of the port (only significant
        on Video2 to Video 5 ports) <Condtype>
        HD_SDI_PAL_TX_1 <Probcause> informationalStatus(1000)
        <Alarmtype> other (1) <Polarity>
        (2)
        "
	::= { pm1004vencAlmvideoProtocolStatusEntry 3 }


pm1004vencAlmSdiTxPortn OBJECT-TYPE
	SYNTAX  EkiOnOff
	MAX-ACCESS read-only
	STATUS current
	DESCRIPTION
        "
        SDI Detected On Tx :This OID indicates
        that the SDI protocol has been
         detected on the transmit side
         of the port (only significant
         on Video2 to Video 5 ports)
         <Help>   This status indicates
        that the SDI protocol has been
         detected on the transmit side
         of the port (only significant
         on Video2 to Video 5 ports) <Condtype>
        SDI_TX_1 <Probcause> informationalStatus(1000)
        <Alarmtype> other (1) <Polarity>
        (2)
        "
	::= { pm1004vencAlmvideoProtocolStatusEntry 2 }


--- *********************************************************
---     TABLE for the pm1004vencAlmdfrmAlm articles
--- *********************************************************

pm1004vencAlmdfrmAlmTable OBJECT-TYPE
	SYNTAX  SEQUENCE OF Pm1004vencAlmdfrmAlmEntry
	MAX-ACCESS not-accessible
	STATUS current
	DESCRIPTION
        "
        List of pm1004vencAlmdfrmAlm Article
        "
	::= { pm1004vencAlmLineCrit 128 }


pm1004vencAlmdfrmAlmEntry OBJECT-TYPE
	SYNTAX Pm1004vencAlmdfrmAlmEntry
	MAX-ACCESS not-accessible
	STATUS current
	DESCRIPTION
        "
        Row definition for the pm1004vencAlmdfrmAlm
        table
        "
	INDEX   { pm1004vencAlmdfrmAlmIndex }
	::= { pm1004vencAlmdfrmAlmTable 1 }


Pm1004vencAlmdfrmAlmEntry ::=
	SEQUENCE {
	pm1004vencAlmdfrmAlmIndex
		INTEGER,
	pm1004vencAlmLineLossofsyncPortn
		EkiOnOff
	}


pm1004vencAlmdfrmAlmIndex OBJECT-TYPE
	SYNTAX  INTEGER(0..128)
	MAX-ACCESS  read-only
	STATUS current
	DESCRIPTION
        "
        Index definition for the pm1004vencAlmdfrmAlm
        table
        "
	::= { pm1004vencAlmdfrmAlmEntry 1 }


pm1004vencAlmLineLossofsyncPortn OBJECT-TYPE
	SYNTAX  EkiOnOff
	MAX-ACCESS read-only
	STATUS current
	DESCRIPTION
        "
        Loss Of Synchronisation :This
         OID indicates the upstream line
        input port is in Loss of Synchronization.
         <Help>  This alarms indicates
         if the input signal is correctly
        synchronized <Condtype> LINE_LOSSOFSYNC_1
        <Probcause> receiveFailure (41)
        <Alarmtype>  physicalViolation
         (9) <Polarity> (2)
        "
	::= { pm1004vencAlmdfrmAlmEntry 5 }


--- *********************************************************
---     TABLE for the pm1004vencAlmlineSyncAlarms articles
--- *********************************************************

pm1004vencAlmlineSyncAlarmsTable OBJECT-TYPE
	SYNTAX  SEQUENCE OF Pm1004vencAlmlineSyncAlarmsEntry
	MAX-ACCESS not-accessible
	STATUS current
	DESCRIPTION
        "
        List of pm1004vencAlmlineSyncAlarms
        Article
        "
	::= { pm1004vencAlmLineCrit 133 }


pm1004vencAlmlineSyncAlarmsEntry OBJECT-TYPE
	SYNTAX Pm1004vencAlmlineSyncAlarmsEntry
	MAX-ACCESS not-accessible
	STATUS current
	DESCRIPTION
        "
        Row definition for the pm1004vencAlmlineSyncAlarms
        table
        "
	INDEX   { pm1004vencAlmlineSyncAlarmsIndex }
	::= { pm1004vencAlmlineSyncAlarmsTable 1 }


Pm1004vencAlmlineSyncAlarmsEntry ::=
	SEQUENCE {
	pm1004vencAlmlineSyncAlarmsIndex
		INTEGER,
	pm1004vencAlmDwLosPortn
		EkiOnOff,
	pm1004vencAlmUpLockerrPortn
		EkiOnOff,
	pm1004vencAlmDwLockerrPortn
		EkiOnOff
	}


pm1004vencAlmlineSyncAlarmsIndex OBJECT-TYPE
	SYNTAX  INTEGER(0..128)
	MAX-ACCESS  read-only
	STATUS current
	DESCRIPTION
        "
        Index definition for the pm1004vencAlmlineSyncAlarms
        table
        "
	::= { pm1004vencAlmlineSyncAlarmsEntry 1 }


pm1004vencAlmDwLosPortn OBJECT-TYPE
	SYNTAX  EkiOnOff
	MAX-ACCESS read-only
	STATUS current
	DESCRIPTION
        "
        Line Input Loss Of Signal :This
        OID indicates a loss of signal
         on the 10 Gb/s input.  <Help>
          This alarm indicates if an optical
        signal is detected on the line
         transceiver input <Condtype> DW_LOS
        <Probcause> receiveFailure (41)
        <Alarmtype> physicalViolation (9)
        <Polarity> (2)
        "
	::= { pm1004vencAlmlineSyncAlarmsEntry 17 }


pm1004vencAlmUpLockerrPortn OBJECT-TYPE
	SYNTAX  EkiOnOff
	MAX-ACCESS read-only
	STATUS current
	DESCRIPTION
        "
        Upstream Clock Lock Error :This
        OID indicates that the serializer
        output 10 Gb/s clock multiplier
        unit is not locked. <Condtype>
         UP_LOCKERR <Probcause> receiveFailure
        (41) <Alarmtype> equipmentAlarm
        (5) <Polarity> (2)
        "
	::= { pm1004vencAlmlineSyncAlarmsEntry 14 }


pm1004vencAlmDwLockerrPortn OBJECT-TYPE
	SYNTAX  EkiOnOff
	MAX-ACCESS read-only
	STATUS current
	DESCRIPTION
        "
        Downstream Clock Lock Error :This
        OID indicates that the deserializer
        input 10 Gb/s clock recovery is
        not locked. <Condtype> DW_LOCKERR
        <Probcause> receiveFailure (41)
        <Alarmtype> equipmentAlarm (5)
         <Polarity> (2)
        "
	::= { pm1004vencAlmlineSyncAlarmsEntry 13 }


--- *****************************************************
---     LEAF for the modInitFailLevel2 article
--- *****************************************************
pm1004vencAlmmodInitFailLevel2 OBJECT IDENTIFIER ::= { pm1004vencAlmOtherUrg 194 }




pm1004vencAlmSwInitFail OBJECT-TYPE
	  SYNTAX EkiOnOff
	  MAX-ACCESS read-only
	  STATUS current
	  DESCRIPTION
        "
        SW Init Fail :This OID indicates
        that the SW intialization has caused
        unknown intial conditions  <Help>
         This alarm indicates if the SW
        module is correctly initialized
        <Condtype> SW_INIT_FAIL <Probcause>
        softwareError (47) <Alarmtype>
         processingErrorAlarm (4) <Polarity>
        (2)
        "
	  ::= { pm1004vencAlmmodInitFailLevel2 5 }



pm1004vencAlmResetHwInitFail OBJECT-TYPE
	  SYNTAX EkiOnOff
	  MAX-ACCESS read-only
	  STATUS current
	  DESCRIPTION
        "
        Reset HW Init Fail :This OID indicates
        that the HW intialization has caused
        unknown intial conditions  <Help>
         This alarm indicates if the HW
        has been correctly initialized
         <Condtype> RESET_HW_INIT_FAIL
         <Probcause> softwareError (47)
        <Alarmtype> processingErrorAlarm
        (4) <Polarity> (2)
        "
	  ::= { pm1004vencAlmmodInitFailLevel2 4 }



pm1004vencAlmBootUndone OBJECT-TYPE
	  SYNTAX EkiOnOff
	  MAX-ACCESS read-only
	  STATUS current
	  DESCRIPTION
        "
        Boot Undone :This OID indicates
        that the boot has not been correctly
        achieved  <Help>  This alarm indicates
        if the module has correctly boot
        <Condtype> BOOT_UNDONE <Probcause>
        softwareError (47) <Alarmtype>
         processingErrorAlarm (4) <Polarity>
        (2)
        "
	  ::= { pm1004vencAlmmodInitFailLevel2 3 }



pm1004vencAlmNextColdBootForced OBJECT-TYPE
	  SYNTAX EkiOnOff
	  MAX-ACCESS read-only
	  STATUS current
	  DESCRIPTION
        "
        Next Cold Boot Forced :This OID
        indicates that the next Reset will
        be forced Cold  <Help>  This alarm
        indicates that the next reset of
        the module will be forced to cold
        reset <Condtype> NEXT_COLD_BOOT_FORCED
        <Probcause> informationalStatus(1000)
        <Alarmtype> other (1) <Polarity>
        (2)
        "
	  ::= { pm1004vencAlmmodInitFailLevel2 2 }



pm1004vencAlmLedFail OBJECT-TYPE
	  SYNTAX EkiOnOff
	  MAX-ACCESS read-only
	  STATUS current
	  DESCRIPTION
        "
        Led Fail :This OID indicates that
        Led register has not been correctly
        initalized  <Help>  This alarm
         indicates if the module LEDs are
        correctly initialized <Condtype>
        LED_FAIL <Probcause> softwareError
        (47) <Alarmtype> processingErrorAlarm
        (4) <Polarity> (2)
        "
	  ::= { pm1004vencAlmmodInitFailLevel2 1 }



--- *****************************************************
---     LEAF for the modInitFailLevel3 article
--- *****************************************************
pm1004vencAlmmodInitFailLevel3 OBJECT IDENTIFIER ::= { pm1004vencAlmOtherUrg 195 }




pm1004vencAlmClient4InitFail OBJECT-TYPE
	  SYNTAX EkiOnOff
	  MAX-ACCESS read-only
	  STATUS current
	  DESCRIPTION
        "
        Client4 Init Fail :This OID indicates
        that Client 4 registers subset
         has not been correctly initialized
         <Help>  This alarm indicates if
        the client port 4 is correctly
         initialized <Condtype> CLIENT4_INIT_FAIL
        <Probcause> softwareError (47)
         <Alarmtype> processingErrorAlarm
        (4) <Polarity> (2)
        "
	  ::= { pm1004vencAlmmodInitFailLevel3 12 }



pm1004vencAlmClient3InitFail OBJECT-TYPE
	  SYNTAX EkiOnOff
	  MAX-ACCESS read-only
	  STATUS current
	  DESCRIPTION
        "
        Client3 Init Fail :This OID indicates
        that Client 3 registers subset
         has not been correctly initialized
         <Help>  This alarm indicates if
        the client port 3 is correctly
         initialized <Condtype> CLIENT3_INIT_FAIL
        <Probcause> softwareError (47)
         <Alarmtype> processingErrorAlarm
        (4) <Polarity> (2)
        "
	  ::= { pm1004vencAlmmodInitFailLevel3 11 }



pm1004vencAlmClient2InitFail OBJECT-TYPE
	  SYNTAX EkiOnOff
	  MAX-ACCESS read-only
	  STATUS current
	  DESCRIPTION
        "
        Client2 Init Fail :This OID indicates
        that Client 2 registers subset
         has not been correctly initialized
         <Help>  This alarm indicates if
        the client port 2 is correctly
         initialized <Condtype> CLIENT2_INIT_FAIL
        <Probcause> softwareError (47)
         <Alarmtype> processingErrorAlarm
        (4) <Polarity> (2)
        "
	  ::= { pm1004vencAlmmodInitFailLevel3 10 }



pm1004vencAlmClient1InitFail OBJECT-TYPE
	  SYNTAX EkiOnOff
	  MAX-ACCESS read-only
	  STATUS current
	  DESCRIPTION
        "
        Client1 Init Fail :This OID indicates
        that Client 1 registers subset
         has not been correctly initialized
         <Help>  This alarm indicates if
        the client port 1 is correctly
         initialized <Condtype> CLIENT1_INIT_FAIL
        <Probcause> softwareError (47)
         <Alarmtype> processingErrorAlarm
        (4) <Polarity> (2)
        "
	  ::= { pm1004vencAlmmodInitFailLevel3 9 }



pm1004vencAlmLine2InitFail OBJECT-TYPE
	  SYNTAX EkiOnOff
	  MAX-ACCESS read-only
	  STATUS current
	  DESCRIPTION
        "
        Line2 Init Fail :This OID indicates
        that the Line register subset has
        not been correctly initialized
          <Help>  This alarm indicates
         if the line port 2 is correctly
        initialized <Condtype> LINE2_INIT_FAIL
        <Probcause> softwareError (47)
         <Alarmtype> processingErrorAlarm
        (4) <Polarity> (2)
        "
	  ::= { pm1004vencAlmmodInitFailLevel3 8 }



pm1004vencAlmLine1InitFail OBJECT-TYPE
	  SYNTAX EkiOnOff
	  MAX-ACCESS read-only
	  STATUS current
	  DESCRIPTION
        "
        Line1 Init Fail :This OID indicates
        that the Line registersvsubset
         has not been correctly initialized
         <Help>  This alarm indicates if
        the line port 1 is correctly initialized
        <Condtype> LINE1_INIT_FAIL <Probcause>
        softwareError (47) <Alarmtype>
         processingErrorAlarm (4) <Polarity>
        (2)
        "
	  ::= { pm1004vencAlmmodInitFailLevel3 7 }



pm1004vencAlmXfp2InitFail OBJECT-TYPE
	  SYNTAX EkiOnOff
	  MAX-ACCESS read-only
	  STATUS current
	  DESCRIPTION
        "
        XFP2 Init Fail :This OID indicates
        that the XFP has not been correctly
        initialized  <Help>  This alarm
        indicates if the line transceiver
        2 is correctly initialized <Condtype>
        XFP2_INIT_FAIL <Probcause> softwareError
        (47) <Alarmtype> processingErrorAlarm
        (4) <Polarity> (2)
        "
	  ::= { pm1004vencAlmmodInitFailLevel3 6 }



pm1004vencAlmXfp1InitFail OBJECT-TYPE
	  SYNTAX EkiOnOff
	  MAX-ACCESS read-only
	  STATUS current
	  DESCRIPTION
        "
        XFP1 Init Fail :This OID indicates
        that the XFP has not been correctly
        initialized  <Help>  This alarm
        indicates if the line transceiver
        1 is correctly initialized <Condtype>
        XFP1_INIT_FAIL <Probcause> softwareError
        (47) <Alarmtype> processingErrorAlarm
        (4) <Polarity> (2)
        "
	  ::= { pm1004vencAlmmodInitFailLevel3 5 }



pm1004vencAlmInitModuleFail OBJECT-TYPE
	  SYNTAX EkiOnOff
	  MAX-ACCESS read-only
	  STATUS current
	  DESCRIPTION
        "
        Init Module Fail :This OID indicates
        that the Module has not been correctly
        initialized  <Help>  This alarm
        indicates if the SW module is correctly
        initialized <Condtype> INIT_MODULE_FAIL
        <Probcause> softwareError (47)
         <Alarmtype> processingErrorAlarm
        (4) <Polarity> (2)
        "
	  ::= { pm1004vencAlmmodInitFailLevel3 3 }



pm1004vencAlmObmTypeReadFail OBJECT-TYPE
	  SYNTAX EkiOnOff
	  MAX-ACCESS read-only
	  STATUS current
	  DESCRIPTION
        "
        OBM Type Read Fail :This OID indicates
        that OBM type has not been recognized
         <Help>  This alarm indicates if
        the OBM board has been correctly
        identified <Condtype> OBM_TYPE_READ_FAIL
        <Probcause> softwareError (47)
         <Alarmtype> processingErrorAlarm
        (4) <Polarity> (2)
        "
	  ::= { pm1004vencAlmmodInitFailLevel3 2 }



pm1004vencAlmGwIdentFail OBJECT-TYPE
	  SYNTAX EkiOnOff
	  MAX-ACCESS read-only
	  STATUS current
	  DESCRIPTION
        "
        GW Ident Fail :This OID indicates
        that GW identification has not
         been read  <Help>  This alarm
         indicates if the GW has been correctly
        identified <Condtype> GW_IDENT_FAIL
        <Probcause> softwareError (47)
         <Alarmtype> processingErrorAlarm
        (4) <Polarity> (2)
        "
	  ::= { pm1004vencAlmmodInitFailLevel3 1 }



--- *****************************************************
---     LEAF for the clientRxProt article
--- *****************************************************
pm1004vencAlmclientRxProt OBJECT IDENTIFIER ::= { pm1004vencAlmOtherUrg 198 }




pm1004vencAlmAdddropClient4East OBJECT-TYPE
	  SYNTAX EkiOnOff
	  MAX-ACCESS read-only
	  STATUS current
	  DESCRIPTION
        "
        Client East Rx Side Active :This
        OID indicates the Client is active
        on East receiving side <Condtype>
        ADDDROP_CLIENT4_EAST <Probcause>
        other (1) <Alarmtype> other (1)
        <Polarity> (2)
        "
	  ::= { pm1004vencAlmclientRxProt 12 }



pm1004vencAlmAdddropClient3East OBJECT-TYPE
	  SYNTAX EkiOnOff
	  MAX-ACCESS read-only
	  STATUS current
	  DESCRIPTION
        "
        Client East Rx Side Active :This
        OID indicates the Client is active
        on East receiving side <Condtype>
        ADDDROP_CLIENT3_EAST <Probcause>
        other (1) <Alarmtype> other (1)
        <Polarity> (2)
        "
	  ::= { pm1004vencAlmclientRxProt 11 }



pm1004vencAlmAdddropClient2East OBJECT-TYPE
	  SYNTAX EkiOnOff
	  MAX-ACCESS read-only
	  STATUS current
	  DESCRIPTION
        "
        Client East Rx Side Active :This
        OID indicates the Client is active
        on East receiving side <Condtype>
        ADDDROP_CLIENT2_EAST <Probcause>
        other (1) <Alarmtype> other (1)
        <Polarity> (2)
        "
	  ::= { pm1004vencAlmclientRxProt 10 }



pm1004vencAlmAdddropClient1East OBJECT-TYPE
	  SYNTAX EkiOnOff
	  MAX-ACCESS read-only
	  STATUS current
	  DESCRIPTION
        "
        Client East Rx Side Active :This
        OID indicates the Client is active
        on East receiving side <Condtype>
        ADDDROP_CLIENT1_EAST <Probcause>
        other (1) <Alarmtype> other (1)
        <Polarity> (2)
        "
	  ::= { pm1004vencAlmclientRxProt 9 }



pm1004vencAlmAdddropClient4West OBJECT-TYPE
	  SYNTAX EkiOnOff
	  MAX-ACCESS read-only
	  STATUS current
	  DESCRIPTION
        "
        Client West Rx Side Active :This
        OID indicates the Client is active
        on West receiving side <Condtype>
        ADDDROP_CLIENT4_WEST <Probcause>
        other (1) <Alarmtype> other (1)
        <Polarity> (2)
        "
	  ::= { pm1004vencAlmclientRxProt 4 }



pm1004vencAlmAdddropClient3West OBJECT-TYPE
	  SYNTAX EkiOnOff
	  MAX-ACCESS read-only
	  STATUS current
	  DESCRIPTION
        "
        Client West Rx Side Active :This
        OID indicates the Client is active
        on West receiving side <Condtype>
        ADDDROP_CLIENT3_WEST <Probcause>
        other (1) <Alarmtype> other (1)
        <Polarity> (2)
        "
	  ::= { pm1004vencAlmclientRxProt 3 }



pm1004vencAlmAdddropClient2West OBJECT-TYPE
	  SYNTAX EkiOnOff
	  MAX-ACCESS read-only
	  STATUS current
	  DESCRIPTION
        "
        Client West Rx Side Active :This
        OID indicates the Client is active
        on West receiving side <Condtype>
        ADDDROP_CLIENT2_WEST <Probcause>
        other (1) <Alarmtype> other (1)
        <Polarity> (2)
        "
	  ::= { pm1004vencAlmclientRxProt 2 }



pm1004vencAlmAdddropClient1West OBJECT-TYPE
	  SYNTAX EkiOnOff
	  MAX-ACCESS read-only
	  STATUS current
	  DESCRIPTION
        "
        Client West Rx Side Active :This
        OID indicates the Client is active
        on West receiving side <Condtype>
        ADDDROP_CLIENT1_WEST <Probcause>
        other (1) <Alarmtype> other (1)
        <Polarity> (2)
        "
	  ::= { pm1004vencAlmclientRxProt 1 }



--- *****************************************************
---     LEAF for the modOther article
--- *****************************************************
pm1004vencAlmmodOther OBJECT IDENTIFIER ::= { pm1004vencAlmOtherUrg 199 }




pm1004vencAlmAesDecodFail OBJECT-TYPE
	  SYNTAX EkiOnOff
	  MAX-ACCESS read-only
	  STATUS current
	  DESCRIPTION
        "
        AES Decoding Failure :This OID
        indicates the AES Decoding process
        failed.   <Help>  This alarm indicates
        the AES Decoding process failed.
        <Condtype> AES_DECOD_FAIL <Probcause>
        transmitterFailure (56) <Alarmtype>
        equipmentAlarm (5) <Polarity> (2)
        "
	  ::= { pm1004vencAlmmodOther 1 }



--- *********************************************************
---     TABLE for the pm1004vencAlmlineXfp1Alarm articles
--- *********************************************************

pm1004vencAlmlineXfp1AlarmTable OBJECT-TYPE
	SYNTAX  SEQUENCE OF Pm1004vencAlmlineXfp1AlarmEntry
	MAX-ACCESS not-accessible
	STATUS current
	DESCRIPTION
        "
        List of pm1004vencAlmlineXfp1Alarm
        Article
        "
	::= { pm1004vencAlmLineUrg 208 }


pm1004vencAlmlineXfp1AlarmEntry OBJECT-TYPE
	SYNTAX Pm1004vencAlmlineXfp1AlarmEntry
	MAX-ACCESS not-accessible
	STATUS current
	DESCRIPTION
        "
        Row definition for the pm1004vencAlmlineXfp1Alarm
        table
        "
	INDEX   { pm1004vencAlmlineXfp1AlarmIndex }
	::= { pm1004vencAlmlineXfp1AlarmTable 1 }


Pm1004vencAlmlineXfp1AlarmEntry ::=
	SEQUENCE {
	pm1004vencAlmlineXfp1AlarmIndex
		INTEGER,
	pm1004vencAlmRxPowerHighAlarmPortn
		EkiOnOff,
	pm1004vencAlmRxPowerLowAlarmPortn
		EkiOnOff,
	pm1004vencAlmTempHighAlarmPortn
		EkiOnOff,
	pm1004vencAlmTempLowAlarmPortn
		EkiOnOff,
	pm1004vencAlmTxBiasHighAlarmPortn
		EkiOnOff,
	pm1004vencAlmTxBiasLowAlarmPortn
		EkiOnOff,
	pm1004vencAlmTxPowerHighAlarmPortn
		EkiOnOff,
	pm1004vencAlmTxPowerLowAlarmPortn
		EkiOnOff
	}


pm1004vencAlmlineXfp1AlarmIndex OBJECT-TYPE
	SYNTAX  INTEGER(0..128)
	MAX-ACCESS  read-only
	STATUS current
	DESCRIPTION
        "
        Index definition for the pm1004vencAlmlineXfp1Alarm
        table
        "
	::= { pm1004vencAlmlineXfp1AlarmEntry 1 }


pm1004vencAlmRxPowerHighAlarmPortn OBJECT-TYPE
	SYNTAX  EkiOnOff
	MAX-ACCESS read-only
	STATUS current
	DESCRIPTION
        "
        Line Optical Rx Power High :Alarm
        indicating that the XFP received
        optical power is higher than the
        threshold value written in the
         XFP EEPROM <Condtype> RX_POWER_HIGH_ALARM_1
        <Probcause> receiveFailure (41)
        <Alarmtype> equipmentAlarm (5)
         <Polarity> (2)
        "
	::= { pm1004vencAlmlineXfp1AlarmEntry 17 }


pm1004vencAlmRxPowerLowAlarmPortn OBJECT-TYPE
	SYNTAX  EkiOnOff
	MAX-ACCESS read-only
	STATUS current
	DESCRIPTION
        "
        Line Optical Rx Power Low :Alarm
        indicating that the XFP received
        optical power is lower than the
        threshold value written in the
         XFP EEPROM  <Condtype> RX_POWER_LOW_ALARM_1
        <Probcause> receiveFailure (41)
        <Alarmtype> equipmentAlarm (5)
         <Polarity> (2)
        "
	::= { pm1004vencAlmlineXfp1AlarmEntry 16 }


pm1004vencAlmTempHighAlarmPortn OBJECT-TYPE
	SYNTAX  EkiOnOff
	MAX-ACCESS read-only
	STATUS current
	DESCRIPTION
        "
        Line Transceiver Temp High :Alarm
        indicating that the XFP/OTX temperature
        is higher than the threshold value
        written in the XFP EEPROM <Condtype>
        TEMP_HIGH_ALARM_1 <Probcause> temperatureUnacceptable
        (51) <Alarmtype> equipmentAlarm
        (5) <Polarity> (2)
        "
	::= { pm1004vencAlmlineXfp1AlarmEntry 9 }


pm1004vencAlmTempLowAlarmPortn OBJECT-TYPE
	SYNTAX  EkiOnOff
	MAX-ACCESS read-only
	STATUS current
	DESCRIPTION
        "
        Line Transceiver Temp Low :Alarm
        indicating that the XFP/OTX temperature
        is lower than the threshold value
        written in the XFP/OTX EEPROM <Condtype>
        TEMP_LOW_ALARM_1 <Probcause> temperatureUnacceptable
        (51) <Alarmtype> equipmentAlarm
        (5) <Polarity> (2)
        "
	::= { pm1004vencAlmlineXfp1AlarmEntry 8 }


pm1004vencAlmTxBiasHighAlarmPortn OBJECT-TYPE
	SYNTAX  EkiOnOff
	MAX-ACCESS read-only
	STATUS current
	DESCRIPTION
        "
        Line Transceiver Bias High :Alarm
        indicating that the XFP/OTX transmitter
        laser bias current is higher than
        the threshold value written in
         the XFP EEPROM <Condtype> TX_BIAS_HIGH_ALARM_1
        <Probcause> transmitterFailure
         (56) <Alarmtype> equipmentAlarm
        (5) <Polarity> (2)
        "
	::= { pm1004vencAlmlineXfp1AlarmEntry 5 }


pm1004vencAlmTxBiasLowAlarmPortn OBJECT-TYPE
	SYNTAX  EkiOnOff
	MAX-ACCESS read-only
	STATUS current
	DESCRIPTION
        "
        Line Transceiver Bias Low :Alarm
        indicating that the XFP/OTX transmitter
        laser bias current is lower than
        the threshold value written in
         the XFP/OTX EEPROM <Condtype>
         TX_BIAS_LOW_ALARM_1 <Probcause>
        transmitterFailure (56) <Alarmtype>
        equipmentAlarm (5) <Polarity> (2)
        "
	::= { pm1004vencAlmlineXfp1AlarmEntry 4 }


pm1004vencAlmTxPowerHighAlarmPortn OBJECT-TYPE
	SYNTAX  EkiOnOff
	MAX-ACCESS read-only
	STATUS current
	DESCRIPTION
        "
        Line Optical Tx Power High :Alarm
        indicating that the XFP/OTX transmitter
        transmitter output power is higher
        than the threshold value written
        in the XFP EEPROM <Condtype> TX_POWER_HIGH_ALARM_1
        <Probcause> transmitterFailure
         (56) <Alarmtype> equipmentAlarm
        (5) <Polarity> (2)
        "
	::= { pm1004vencAlmlineXfp1AlarmEntry 3 }


pm1004vencAlmTxPowerLowAlarmPortn OBJECT-TYPE
	SYNTAX  EkiOnOff
	MAX-ACCESS read-only
	STATUS current
	DESCRIPTION
        "
        Line Optical Tx Power Low :Alarm
        indicating that the XFP/OTX transmitter
        transmitter output power is lower
        than the threshold value written
        in the XFP/OTX EEPROM <Condtype>
        TX_POWER_LOW_ALARM_1 <Probcause>
        transmitterFailure (56) <Alarmtype>
        equipmentAlarm (5) <Polarity> (2)
        "
	::= { pm1004vencAlmlineXfp1AlarmEntry 2 }


--- *********************************************************
---     TABLE for the pm1004vencAlmlineXfp1Warnings articles
--- *********************************************************

pm1004vencAlmlineXfp1WarningsTable OBJECT-TYPE
	SYNTAX  SEQUENCE OF Pm1004vencAlmlineXfp1WarningsEntry
	MAX-ACCESS not-accessible
	STATUS current
	DESCRIPTION
        "
        List of pm1004vencAlmlineXfp1Warnings
        Article
        "
	::= { pm1004vencAlmLineNurg 209 }


pm1004vencAlmlineXfp1WarningsEntry OBJECT-TYPE
	SYNTAX Pm1004vencAlmlineXfp1WarningsEntry
	MAX-ACCESS not-accessible
	STATUS current
	DESCRIPTION
        "
        Row definition for the pm1004vencAlmlineXfp1Warnings
        table
        "
	INDEX   { pm1004vencAlmlineXfp1WarningsIndex }
	::= { pm1004vencAlmlineXfp1WarningsTable 1 }


Pm1004vencAlmlineXfp1WarningsEntry ::=
	SEQUENCE {
	pm1004vencAlmlineXfp1WarningsIndex
		INTEGER,
	pm1004vencAlmRxPowerHighWarningPortn
		EkiOnOff,
	pm1004vencAlmRxPowerLowWarningPortn
		EkiOnOff,
	pm1004vencAlmTempHighWarningPortn
		EkiOnOff,
	pm1004vencAlmTempLowWarningPortn
		EkiOnOff,
	pm1004vencAlmTxBiasHighWarningPortn
		EkiOnOff,
	pm1004vencAlmTxBiasLowWarningPortn
		EkiOnOff,
	pm1004vencAlmTxPowerHighWarningPortn
		EkiOnOff,
	pm1004vencAlmTxPowerLowWarningPortn
		EkiOnOff
	}


pm1004vencAlmlineXfp1WarningsIndex OBJECT-TYPE
	SYNTAX  INTEGER(0..128)
	MAX-ACCESS  read-only
	STATUS current
	DESCRIPTION
        "
        Index definition for the pm1004vencAlmlineXfp1Warnings
        table
        "
	::= { pm1004vencAlmlineXfp1WarningsEntry 1 }


pm1004vencAlmRxPowerHighWarningPortn OBJECT-TYPE
	SYNTAX  EkiOnOff
	MAX-ACCESS read-only
	STATUS current
	DESCRIPTION
        "
        Line Optical Rx Power High Warning
        :Warning indicating that the XFP
        received optical power is higher
        than the threshold value written
        in the XFP EEPROM <Condtype> RX_POWER_HIGH_WARNING_1
        <Probcause> receiveFailure (41)
        <Alarmtype> equipmentAlarm (5)
         <Polarity> (2)
        "
	::= { pm1004vencAlmlineXfp1WarningsEntry 17 }


pm1004vencAlmRxPowerLowWarningPortn OBJECT-TYPE
	SYNTAX  EkiOnOff
	MAX-ACCESS read-only
	STATUS current
	DESCRIPTION
        "
        Line Optical Rx Power Low Warning
        :Warning indicating that the XFP
        received optical power is lower
        than the threshold value written
        in the XFP EEPROM  <Condtype> RX_POWER_LOW_WARNING_1
        <Probcause> receiveFailure (41)
        <Alarmtype> equipmentAlarm (5)
         <Polarity> (2)
        "
	::= { pm1004vencAlmlineXfp1WarningsEntry 16 }


pm1004vencAlmTempHighWarningPortn OBJECT-TYPE
	SYNTAX  EkiOnOff
	MAX-ACCESS read-only
	STATUS current
	DESCRIPTION
        "
        Line Transceiver Temp High Warning
        :Warning indicating that the XFP/OTX
        temperature is higher than the
         threshold value written in the
        XFP EEPROM <Condtype> TEMP_HIGH_WARNING_1
        <Probcause> temperatureUnacceptable
        (51) <Alarmtype> equipmentAlarm
        (5) <Polarity> (2)
        "
	::= { pm1004vencAlmlineXfp1WarningsEntry 9 }


pm1004vencAlmTempLowWarningPortn OBJECT-TYPE
	SYNTAX  EkiOnOff
	MAX-ACCESS read-only
	STATUS current
	DESCRIPTION
        "
        Line Transceiver Temp Low Warning
        :Warning indicating that the XFP/OTX
        temperature is lower than the threshold
        value written in the XFP/OTX EEPROM
        <Condtype> TEMP_LOW_WARNING_1 <Probcause>
        temperatureUnacceptable (51) <Alarmtype>
        equipmentAlarm (5) <Polarity> (2)
        "
	::= { pm1004vencAlmlineXfp1WarningsEntry 8 }


pm1004vencAlmTxBiasHighWarningPortn OBJECT-TYPE
	SYNTAX  EkiOnOff
	MAX-ACCESS read-only
	STATUS current
	DESCRIPTION
        "
        Line Transceiver Bias High Warning
        :Warning indicating that the XFP/OTX
        transmitter laser bias current
         is higher than the threshold value
        written in the XFP EEPROM <Condtype>
        TX_BIAS_HIGH_WARNING_1 <Probcause>
        transmitterFailure (56) <Alarmtype>
        equipmentAlarm (5) <Polarity> (2)
        "
	::= { pm1004vencAlmlineXfp1WarningsEntry 5 }


pm1004vencAlmTxBiasLowWarningPortn OBJECT-TYPE
	SYNTAX  EkiOnOff
	MAX-ACCESS read-only
	STATUS current
	DESCRIPTION
        "
        Line Transceiver Bias Low Warning
        :Warning indicating that the XFP/OTX
        transmitter laser bias current
         is lower than the threshold value
        written in the XFP/OTX EEPROM <Condtype>
        TX_BIAS_LOW_WARNING_1 <Probcause>
        transmitterFailure (56) <Alarmtype>
        equipmentAlarm (5) <Polarity> (2)
        "
	::= { pm1004vencAlmlineXfp1WarningsEntry 4 }


pm1004vencAlmTxPowerHighWarningPortn OBJECT-TYPE
	SYNTAX  EkiOnOff
	MAX-ACCESS read-only
	STATUS current
	DESCRIPTION
        "
        Line Optical Tx Power High Warning
        :Warning indicating that the XFP/OTX
        transmitter transmitter output
         power is higher than the threshold
        value written in the XFP EEPROM
        <Condtype> TX_POWER_HIGH_WARNING_1
        <Probcause> transmitterFailure
         (56) <Alarmtype> equipmentAlarm
        (5) <Polarity> (2)
        "
	::= { pm1004vencAlmlineXfp1WarningsEntry 3 }


pm1004vencAlmTxPowerLowWarningPortn OBJECT-TYPE
	SYNTAX  EkiOnOff
	MAX-ACCESS read-only
	STATUS current
	DESCRIPTION
        "
        Line Optical Tx Power Low Warning
        :Warning indicating that the XFP/OTX
        transmitter transmitter output
         power is lower than the threshold
        value written in the XFP/OTX EEPROM
        <Condtype> TX_POWER_LOW_WARNING_1
        <Probcause> transmitterFailure
         (56) <Alarmtype> equipmentAlarm
        (5) <Polarity> (2)
        "
	::= { pm1004vencAlmlineXfp1WarningsEntry 2 }


--- *********************************************************
---     TABLE for the pm1004vencAlmlineXfp1Crit articles
--- *********************************************************

pm1004vencAlmlineXfp1CritTable OBJECT-TYPE
	SYNTAX  SEQUENCE OF Pm1004vencAlmlineXfp1CritEntry
	MAX-ACCESS not-accessible
	STATUS current
	DESCRIPTION
        "
        List of pm1004vencAlmlineXfp1Crit
        Article
        "
	::= { pm1004vencAlmLineUrg 210 }


pm1004vencAlmlineXfp1CritEntry OBJECT-TYPE
	SYNTAX Pm1004vencAlmlineXfp1CritEntry
	MAX-ACCESS not-accessible
	STATUS current
	DESCRIPTION
        "
        Row definition for the pm1004vencAlmlineXfp1Crit
        table
        "
	INDEX   { pm1004vencAlmlineXfp1CritIndex }
	::= { pm1004vencAlmlineXfp1CritTable 1 }


Pm1004vencAlmlineXfp1CritEntry ::=
	SEQUENCE {
	pm1004vencAlmlineXfp1CritIndex
		INTEGER,
	pm1004vencAlmRxPowerHighCritPortn
		EkiOnOff,
	pm1004vencAlmRxPowerLowCritPortn
		EkiOnOff,
	pm1004vencAlmTxPowerHighCritPortn
		EkiOnOff,
	pm1004vencAlmTxPowerLowCritPortn
		EkiOnOff
	}


pm1004vencAlmlineXfp1CritIndex OBJECT-TYPE
	SYNTAX  INTEGER(0..128)
	MAX-ACCESS  read-only
	STATUS current
	DESCRIPTION
        "
        Index definition for the pm1004vencAlmlineXfp1Crit
        table
        "
	::= { pm1004vencAlmlineXfp1CritEntry 1 }


pm1004vencAlmRxPowerHighCritPortn OBJECT-TYPE
	SYNTAX  EkiOnOff
	MAX-ACCESS read-only
	STATUS current
	DESCRIPTION
        "
        Line Custom Rx Power High :Custom
        Alarm indicating that the XFP/OTX
        input power of port is higher than
        the custom threshold defined in
        configuration  <Help>  Custom Alarm
        indicating that the XFP/OTX input
        power of port is higher than the
        custom threshold defined in custom
        configuration <Condtype> RX_POWER_HIGH_CRIT_1
        <Probcause> receiveFailure (41)
        <Alarmtype> equipmentAlarm (5)
         <Polarity> (2)
        "
	::= { pm1004vencAlmlineXfp1CritEntry 17 }


pm1004vencAlmRxPowerLowCritPortn OBJECT-TYPE
	SYNTAX  EkiOnOff
	MAX-ACCESS read-only
	STATUS current
	DESCRIPTION
        "
        Line Custom Rx Power Low :Custom
        Alarm indicating that the XFP/OTX
        input power of port is lower than
        the custom threshold defined in
        configuration  <Help>  Custom Alarm
        indicating that the XFP/OTX input
        power of port is lower than the
        custom threshold defined in custom
        configuration <Condtype> RX_POWER_LOW_CRIT_1
        <Probcause> receiveFailure (41)
        <Alarmtype> equipmentAlarm (5)
         <Polarity> (2)
        "
	::= { pm1004vencAlmlineXfp1CritEntry 16 }


pm1004vencAlmTxPowerHighCritPortn OBJECT-TYPE
	SYNTAX  EkiOnOff
	MAX-ACCESS read-only
	STATUS current
	DESCRIPTION
        "
        Line Custom Tx Power High :Custom
        Alarm indicating that the XFP/OTX
        output power of port is higher
         than the custom threshold defined
        in configuration  <Help>  Custom
        Alarm indicating that the XFP/OTX
        output power of port is higher
         than the custom threshold defined
        in custom configuration <Condtype>
        TX_POWER_HIGH_CRIT_1 <Probcause>
        transmitterFailure (56) <Alarmtype>
        equipmentAlarm (5) <Polarity> (2)
        "
	::= { pm1004vencAlmlineXfp1CritEntry 3 }


pm1004vencAlmTxPowerLowCritPortn OBJECT-TYPE
	SYNTAX  EkiOnOff
	MAX-ACCESS read-only
	STATUS current
	DESCRIPTION
        "
        Line Custom Tx Power Low :Custom
        Alarm indicating that the XFP/OTX
        output power of port is lower than
        the custom threshold defined in
        configuration  <Help>  Custom Alarm
        indicating that the XFP/OTX output
        power of port is lower than the
        custom threshold defined in custom
        configuration <Condtype> TX_POWER_LOW_CRIT_1
        <Probcause> transmitterFailure
         (56) <Alarmtype> equipmentAlarm
        (5) <Polarity> (2)
        "
	::= { pm1004vencAlmlineXfp1CritEntry 2 }


--- *********************************************************
---     TABLE for the pm1004vencAlmlineXfp1Alarms articles
--- *********************************************************

pm1004vencAlmlineXfp1AlarmsTable OBJECT-TYPE
	SYNTAX  SEQUENCE OF Pm1004vencAlmlineXfp1AlarmsEntry
	MAX-ACCESS not-accessible
	STATUS current
	DESCRIPTION
        "
        List of pm1004vencAlmlineXfp1Alarms
        Article
        "
	::= { pm1004vencAlmLineCrit 211 }


pm1004vencAlmlineXfp1AlarmsEntry OBJECT-TYPE
	SYNTAX Pm1004vencAlmlineXfp1AlarmsEntry
	MAX-ACCESS not-accessible
	STATUS current
	DESCRIPTION
        "
        Row definition for the pm1004vencAlmlineXfp1Alarms
        table
        "
	INDEX   { pm1004vencAlmlineXfp1AlarmsIndex }
	::= { pm1004vencAlmlineXfp1AlarmsTable 1 }


Pm1004vencAlmlineXfp1AlarmsEntry ::=
	SEQUENCE {
	pm1004vencAlmlineXfp1AlarmsIndex
		INTEGER,
	pm1004vencAlmApdSupplyFaultPortn
		EkiOnOff,
	pm1004vencAlmTecFaultPortn
		EkiOnOff,
	pm1004vencAlmWavelengthUnlockedPortn
		EkiOnOff,
	pm1004vencAlmTxNrPortn
		EkiOnOff,
	pm1004vencAlmTxFaultPortn
		EkiOnOff,
	pm1004vencAlmTxCdrNotLockedPortn
		EkiOnOff,
	pm1004vencAlmRxNrPortn
		EkiOnOff,
	pm1004vencAlmRxCdrNotLockedPortn
		EkiOnOff,
	pm1004vencAlmModNrPortn
		EkiOnOff
	}


pm1004vencAlmlineXfp1AlarmsIndex OBJECT-TYPE
	SYNTAX  INTEGER(0..128)
	MAX-ACCESS  read-only
	STATUS current
	DESCRIPTION
        "
        Index definition for the pm1004vencAlmlineXfp1Alarms
        table
        "
	::= { pm1004vencAlmlineXfp1AlarmsEntry 1 }


pm1004vencAlmApdSupplyFaultPortn OBJECT-TYPE
	SYNTAX  EkiOnOff
	MAX-ACCESS read-only
	STATUS current
	DESCRIPTION
        "
        Line Rx Photodiode Power Failed
        :This OID indicates a failure on
        the APD power supply  <Help>  This
        alarm indicates if the APD power
        supply is in fail condition <Condtype>
        APD_SUPPLY_FAULT_1 <Probcause>
         receiverFailure (42) <Alarmtype>
        equipmentAlarm (5) <Polarity> (2)
        "
	::= { pm1004vencAlmlineXfp1AlarmsEntry 17 }


pm1004vencAlmTecFaultPortn OBJECT-TYPE
	SYNTAX  EkiOnOff
	MAX-ACCESS read-only
	STATUS current
	DESCRIPTION
        "
        Line Optical Tx Temp Regul Failed
        :This OID indicates a failure on
        the TEC module  <Help>  This alarm
        indicates if the TEC of the line
        transceiver is in fail condition
        <Condtype> TEC_FAULT_1 <Probcause>
        transmitterFailure (56) <Alarmtype>
        equipmentAlarm (5) <Polarity> (2)
        "
	::= { pm1004vencAlmlineXfp1AlarmsEntry 16 }


pm1004vencAlmWavelengthUnlockedPortn OBJECT-TYPE
	SYNTAX  EkiOnOff
	MAX-ACCESS read-only
	STATUS current
	DESCRIPTION
        "
        Line Optical Tx Wavelength Unlocked
        :This OID indicates that the wavelength
        error is exceeding the manufacturer
        tolerance  <Help>  This alarm indicates
        if the wavelenght of the line transceiver
        is locked <Condtype> WAVELENGTH_UNLOCKED_1
        <Probcause> transmitterFailure
         (56) <Alarmtype> equipmentAlarm
        (5) <Polarity> (2)
        "
	::= { pm1004vencAlmlineXfp1AlarmsEntry 15 }


pm1004vencAlmTxNrPortn OBJECT-TYPE
	SYNTAX  EkiOnOff
	MAX-ACCESS read-only
	STATUS current
	DESCRIPTION
        "
        Line Optical Tx Not Ready :This
        OID indicates a condition has arisen
        leading to invalid data on the
         transmitting side  <Help>  This
        alarm indicates if the Tx part
         of the line transceiver is ready
        <Condtype> TX_NR_1 <Probcause>
         transmitterFailure (56) <Alarmtype>
        equipmentAlarm (5) <Polarity> (2)
        "
	::= { pm1004vencAlmlineXfp1AlarmsEntry 9 }


pm1004vencAlmTxFaultPortn OBJECT-TYPE
	SYNTAX  EkiOnOff
	MAX-ACCESS read-only
	STATUS current
	DESCRIPTION
        "
        Line Optical Tx Failure :This
         OID indicates a fault condition
        on the laser detected by the safety
        syste  <Help>  This alarm indicates
        if the laser of the line transceiver
        is in fail condition <Condtype>
        TX_FAULT_1 <Probcause> transmitterFailure
        (56) <Alarmtype> equipmentAlarm
        (5) <Polarity> (2)
        "
	::= { pm1004vencAlmlineXfp1AlarmsEntry 8 }


pm1004vencAlmTxCdrNotLockedPortn OBJECT-TYPE
	SYNTAX  EkiOnOff
	MAX-ACCESS read-only
	STATUS current
	DESCRIPTION
        "
        Line Optical Tx CDR Unlocked :This
        OID indicates a loss of lock on
        the transmitting side CDR has been
        detected.  <Help>  This alarm indicates
        if the Tx CDR is locked in the
         line transceiver <Condtype> TX_CDR_NOT_LOCKED1_1
        <Probcause> transmitterFailure
         (56) <Alarmtype> equipmentAlarm
        (5) <Polarity> (2)
        "
	::= { pm1004vencAlmlineXfp1AlarmsEntry 7 }


pm1004vencAlmRxNrPortn OBJECT-TYPE
	SYNTAX  EkiOnOff
	MAX-ACCESS read-only
	STATUS current
	DESCRIPTION
        "
        Line Optical Rx Not Ready :This
        OID indicates that a condition
         has arisen leading to invalid
         data on the receiving side.  <Help>
         This alarm indicates if the Rx
        part of the line transceiver is
        ready <Condtype> RX_NR_1 <Probcause>
        receiveFailure (41) <Alarmtype>
        equipmentAlarm (5) <Polarity> (2)
        "
	::= { pm1004vencAlmlineXfp1AlarmsEntry 6 }


pm1004vencAlmRxCdrNotLockedPortn OBJECT-TYPE
	SYNTAX  EkiOnOff
	MAX-ACCESS read-only
	STATUS current
	DESCRIPTION
        "
        Line Optical Rx CDR Unlocked :This
        OID indicates that a loss of lock
        on the receiving side CDR has been
        detected  <Help>  This alarm indicates
        if the Rx CDR is locked in the
         line transceiver <Condtype> RX_CDR_NOT_LOCKED1_1
        <Probcause> receiveFailure (41)
        <Alarmtype> equipmentAlarm (5)
         <Polarity> (2)
        "
	::= { pm1004vencAlmlineXfp1AlarmsEntry 4 }


pm1004vencAlmModNrPortn OBJECT-TYPE
	SYNTAX  EkiOnOff
	MAX-ACCESS read-only
	STATUS current
	DESCRIPTION
        "
        Line Optical Module Not Ready
         :This OID indicates that the module
        is unable to determine correct
         data.  <Help>  This alarm indicates
        if the line transceiver is ready
        <Condtype> MOD_NR_1 <Probcause>
        receiveFailure (41) <Alarmtype>
        equipmentAlarm (5) <Polarity> (2)
        "
	::= { pm1004vencAlmlineXfp1AlarmsEntry 3 }


--- *********************************************************
---     TABLE for the pm1004vencAlmlineXfp1SupplyAlarm articles
--- *********************************************************

pm1004vencAlmlineXfp1SupplyAlarmTable OBJECT-TYPE
	SYNTAX  SEQUENCE OF Pm1004vencAlmlineXfp1SupplyAlarmEntry
	MAX-ACCESS not-accessible
	STATUS current
	DESCRIPTION
        "
        List of pm1004vencAlmlineXfp1SupplyAlarm
        Article
        "
	::= { pm1004vencAlmLineUrg 212 }


pm1004vencAlmlineXfp1SupplyAlarmEntry OBJECT-TYPE
	SYNTAX Pm1004vencAlmlineXfp1SupplyAlarmEntry
	MAX-ACCESS not-accessible
	STATUS current
	DESCRIPTION
        "
        Row definition for the pm1004vencAlmlineXfp1SupplyAlarm
        table
        "
	INDEX   { pm1004vencAlmlineXfp1SupplyAlarmIndex }
	::= { pm1004vencAlmlineXfp1SupplyAlarmTable 1 }


Pm1004vencAlmlineXfp1SupplyAlarmEntry ::=
	SEQUENCE {
	pm1004vencAlmlineXfp1SupplyAlarmIndex
		INTEGER,
	pm1004vencAlmVcc5HighWarningPortn
		EkiOnOff,
	pm1004vencAlmVcc5LowWarningPortn
		EkiOnOff,
	pm1004vencAlmVcc3HighWarningPortn
		EkiOnOff,
	pm1004vencAlmVcc3LowWarningPortn
		EkiOnOff,
	pm1004vencAlmVcc2HighWarningPortn
		EkiOnOff,
	pm1004vencAlmVcc2LowWarningPortn
		EkiOnOff,
	pm1004vencAlmVee5HighWarningPortn
		EkiOnOff,
	pm1004vencAlmVee5LowWarningPortn
		EkiOnOff,
	pm1004vencAlmVcc5HighAlarmPortn
		EkiOnOff,
	pm1004vencAlmVcc5LowAlarmPortn
		EkiOnOff,
	pm1004vencAlmVcc3HighAlarmPortn
		EkiOnOff,
	pm1004vencAlmVcc3LowAlarmPortn
		EkiOnOff,
	pm1004vencAlmVcc2HighAlarmPortn
		EkiOnOff,
	pm1004vencAlmVcc2LowAlarmPortn
		EkiOnOff,
	pm1004vencAlmVee5HighAlarmPortn
		EkiOnOff,
	pm1004vencAlmVee5LowAlarmPortn
		EkiOnOff
	}


pm1004vencAlmlineXfp1SupplyAlarmIndex OBJECT-TYPE
	SYNTAX  INTEGER(0..128)
	MAX-ACCESS  read-only
	STATUS current
	DESCRIPTION
        "
        Index definition for the pm1004vencAlmlineXfp1SupplyAlarm
        table
        "
	::= { pm1004vencAlmlineXfp1SupplyAlarmEntry 1 }


pm1004vencAlmVcc5HighWarningPortn OBJECT-TYPE
	SYNTAX  EkiOnOff
	MAX-ACCESS read-only
	STATUS current
	DESCRIPTION
        "
        VCC5 Power Supply High Warning
        :Warning indicating the XFP/OTX
        VCC5 power supply is higher than
        the threshold written in the EEPROM
        <Condtype> VCC5_HIGH_WARNING_1
         <Probcause> powerProblem (36)
         <Alarmtype> equipmentAlarm (5)
        <Polarity> (2)
        "
	::= { pm1004vencAlmlineXfp1SupplyAlarmEntry 17 }


pm1004vencAlmVcc5LowWarningPortn OBJECT-TYPE
	SYNTAX  EkiOnOff
	MAX-ACCESS read-only
	STATUS current
	DESCRIPTION
        "
        VCC5 Power Supply Low Warning
         :Warning indicating the XFP/OTX
        VCC5 power supply is lower than
        the threshold written in the EEPROM
        <Condtype> VCC5_LOW_WARNING_1 <Probcause>
        powerProblem (36) <Alarmtype> equipmentAlarm
        (5) <Polarity> (2)
        "
	::= { pm1004vencAlmlineXfp1SupplyAlarmEntry 16 }


pm1004vencAlmVcc3HighWarningPortn OBJECT-TYPE
	SYNTAX  EkiOnOff
	MAX-ACCESS read-only
	STATUS current
	DESCRIPTION
        "
        VCC3 Power Supply High Warning
        :Warning indicating the XFP/OTX
        VCC3 power supply is higher than
        the threshold written in the EEPROM
        <Condtype> VCC3_HIGH_WARNING_1
         <Probcause> powerProblem (36)
         <Alarmtype> equipmentAlarm (5)
        <Polarity> (2)
        "
	::= { pm1004vencAlmlineXfp1SupplyAlarmEntry 15 }


pm1004vencAlmVcc3LowWarningPortn OBJECT-TYPE
	SYNTAX  EkiOnOff
	MAX-ACCESS read-only
	STATUS current
	DESCRIPTION
        "
        VCC3 Power Supply Low Warning
         :Warning indicating the XFP/OTX
        VCC3 power supply is lower than
        the threshold written in the EEPROM
        <Condtype> VCC3_LOW_WARNING_1 <Probcause>
        powerProblem (36) <Alarmtype> equipmentAlarm
        (5) <Polarity> (2)
        "
	::= { pm1004vencAlmlineXfp1SupplyAlarmEntry 14 }


pm1004vencAlmVcc2HighWarningPortn OBJECT-TYPE
	SYNTAX  EkiOnOff
	MAX-ACCESS read-only
	STATUS current
	DESCRIPTION
        "
        VCC2 Power Supply High Warning
        :Warning indicating the XFP/OTX
        VCC2 power supply is higher than
        the threshold written in the EEPROM
        <Condtype> VCC2_HIGH_WARNING_1
         <Probcause> powerProblem (36)
         <Alarmtype> equipmentAlarm (5)
        <Polarity> (2)
        "
	::= { pm1004vencAlmlineXfp1SupplyAlarmEntry 13 }


pm1004vencAlmVcc2LowWarningPortn OBJECT-TYPE
	SYNTAX  EkiOnOff
	MAX-ACCESS read-only
	STATUS current
	DESCRIPTION
        "
        VCC2 Power Supply Low Warning
         :Warning indicating the XFP/OTX
        VCC2 power supply is lower than
        the threshold written in the EEPROM
        <Condtype> VCC2_LOW_WARNING_1 <Probcause>
        powerProblem (36) <Alarmtype> equipmentAlarm
        (5) <Polarity> (2)
        "
	::= { pm1004vencAlmlineXfp1SupplyAlarmEntry 12 }


pm1004vencAlmVee5HighWarningPortn OBJECT-TYPE
	SYNTAX  EkiOnOff
	MAX-ACCESS read-only
	STATUS current
	DESCRIPTION
        "
        VEE5 Power Supply High Warning
        :Warning indicating the XFP/OTX
        VEE5 power supply is higher than
        the threshold written in the EEPROM
        <Condtype> VEE5_HIGH_WARNING_1
         <Probcause> powerProblem (36)
         <Alarmtype> equipmentAlarm (5)
        <Polarity> (2)
        "
	::= { pm1004vencAlmlineXfp1SupplyAlarmEntry 11 }


pm1004vencAlmVee5LowWarningPortn OBJECT-TYPE
	SYNTAX  EkiOnOff
	MAX-ACCESS read-only
	STATUS current
	DESCRIPTION
        "
        VEE5 Power Supply Low Warning
         :Warning indicating the XFP/OTX
        VEE5 power supply is lower than
        the threshold written in the EEPROM
        <Condtype> VEE5_LOW_WARNING_1 <Probcause>
        powerProblem (36) <Alarmtype> equipmentAlarm
        (5) <Polarity> (2)
        "
	::= { pm1004vencAlmlineXfp1SupplyAlarmEntry 10 }


pm1004vencAlmVcc5HighAlarmPortn OBJECT-TYPE
	SYNTAX  EkiOnOff
	MAX-ACCESS read-only
	STATUS current
	DESCRIPTION
        "
        VCC5 Power Supply High :Alarm
         indicating the XFP/OTX VCC5 power
        supply is higher than the threshold
        written in the EEPROM <Condtype>
        VCC5_HIGH_ALARM_1 <Probcause> powerProblem
        (36) <Alarmtype> equipmentAlarm
        (5) <Polarity> (2)
        "
	::= { pm1004vencAlmlineXfp1SupplyAlarmEntry 9 }


pm1004vencAlmVcc5LowAlarmPortn OBJECT-TYPE
	SYNTAX  EkiOnOff
	MAX-ACCESS read-only
	STATUS current
	DESCRIPTION
        "
        VCC5 Power Supply Low :Alarm indicating
        the XFP/OTX VCC5 power supply is
        lower than the threshold written
        in the EEPROM <Condtype> VCC5_LOW_ALARM_1
        <Probcause> powerProblem (36) <Alarmtype>
        equipmentAlarm (5) <Polarity> (2)
        "
	::= { pm1004vencAlmlineXfp1SupplyAlarmEntry 8 }


pm1004vencAlmVcc3HighAlarmPortn OBJECT-TYPE
	SYNTAX  EkiOnOff
	MAX-ACCESS read-only
	STATUS current
	DESCRIPTION
        "
        VCC3 Power Supply High :Alarm
         indicating the XFP/OTX VCC3 power
        supply is higher than the threshold
        written in the EEPROM <Condtype>
        VCC3_HIGH_ALARM_1 <Probcause> powerProblem
        (36) <Alarmtype> equipmentAlarm
        (5) <Polarity> (2)
        "
	::= { pm1004vencAlmlineXfp1SupplyAlarmEntry 7 }


pm1004vencAlmVcc3LowAlarmPortn OBJECT-TYPE
	SYNTAX  EkiOnOff
	MAX-ACCESS read-only
	STATUS current
	DESCRIPTION
        "
        VCC3 Power Supply Low :Alarm indicating
        the XFP/OTX VCC3 power supply is
        lower than the threshold written
        in the EEPROM <Condtype> VCC3_LOW_ALARM_1
        <Probcause> powerProblem (36) <Alarmtype>
        equipmentAlarm (5) <Polarity> (2)
        "
	::= { pm1004vencAlmlineXfp1SupplyAlarmEntry 6 }


pm1004vencAlmVcc2HighAlarmPortn OBJECT-TYPE
	SYNTAX  EkiOnOff
	MAX-ACCESS read-only
	STATUS current
	DESCRIPTION
        "
        VCC2 Power Supply High :Alarm
         indicating the XFP/OTX VCC2 power
        supply is higher than the threshold
        written in the EEPROM <Condtype>
        VCC2_HIGH_ALARM_1 <Probcause> powerProblem
        (36) <Alarmtype> equipmentAlarm
        (5) <Polarity> (2)
        "
	::= { pm1004vencAlmlineXfp1SupplyAlarmEntry 5 }


pm1004vencAlmVcc2LowAlarmPortn OBJECT-TYPE
	SYNTAX  EkiOnOff
	MAX-ACCESS read-only
	STATUS current
	DESCRIPTION
        "
        VCC2 Power Supply Low :Alarm indicating
        the XFP/OTX VCC2 power supply is
        lower than the threshold written
        in the EEPROM <Condtype> VCC2_LOW_ALARM_1
        <Probcause> powerProblem (36) <Alarmtype>
        equipmentAlarm (5) <Polarity> (2)
        "
	::= { pm1004vencAlmlineXfp1SupplyAlarmEntry 4 }


pm1004vencAlmVee5HighAlarmPortn OBJECT-TYPE
	SYNTAX  EkiOnOff
	MAX-ACCESS read-only
	STATUS current
	DESCRIPTION
        "
        VEE5 Power Supply High :Alarm
         indicating the XFP/OTX VEE5 power
        supply is higher than the threshold
        written in the EEPROM <Condtype>
        VEE5_HIGH_ALARM_1 <Probcause> powerProblem
        (36) <Alarmtype> equipmentAlarm
        (5) <Polarity> (2)
        "
	::= { pm1004vencAlmlineXfp1SupplyAlarmEntry 3 }


pm1004vencAlmVee5LowAlarmPortn OBJECT-TYPE
	SYNTAX  EkiOnOff
	MAX-ACCESS read-only
	STATUS current
	DESCRIPTION
        "
        VEE5 Power Supply Low :Alarm indicating
        the XFP/OTX VEE5 power supply is
        lower than the threshold written
        in the EEPROM <Condtype> VEE5_LOW_ALARM_1
        <Probcause> powerProblem (36) <Alarmtype>
        equipmentAlarm (5) <Polarity> (2)
        "
	::= { pm1004vencAlmlineXfp1SupplyAlarmEntry 2 }


--- *********************************************************
---     TABLE for the pm1004vencAlmlineOtx1TlhAlarms articles
--- *********************************************************

pm1004vencAlmlineOtx1TlhAlarmsTable OBJECT-TYPE
	SYNTAX  SEQUENCE OF Pm1004vencAlmlineOtx1TlhAlarmsEntry
	MAX-ACCESS not-accessible
	STATUS current
	DESCRIPTION
        "
        List of pm1004vencAlmlineOtx1TlhAlarms
        Article
        "
	::= { pm1004vencAlmLineUrg 224 }


pm1004vencAlmlineOtx1TlhAlarmsEntry OBJECT-TYPE
	SYNTAX Pm1004vencAlmlineOtx1TlhAlarmsEntry
	MAX-ACCESS not-accessible
	STATUS current
	DESCRIPTION
        "
        Row definition for the pm1004vencAlmlineOtx1TlhAlarms
        table
        "
	INDEX   { pm1004vencAlmlineOtx1TlhAlarmsIndex }
	::= { pm1004vencAlmlineOtx1TlhAlarmsTable 1 }


Pm1004vencAlmlineOtx1TlhAlarmsEntry ::=
	SEQUENCE {
	pm1004vencAlmlineOtx1TlhAlarmsIndex
		INTEGER,
	pm1004vencAlmLineLaserTempHighAlaPortn
		EkiOnOff,
	pm1004vencAlmLineFreqDevHighAlaPortn
		EkiOnOff,
	pm1004vencAlmLineAgingHighAlaPortn
		EkiOnOff,
	pm1004vencAlmLineModulatorAgingHighAlaPortn
		EkiOnOff
	}


pm1004vencAlmlineOtx1TlhAlarmsIndex OBJECT-TYPE
	SYNTAX  INTEGER(0..128)
	MAX-ACCESS  read-only
	STATUS current
	DESCRIPTION
        "
        Index definition for the pm1004vencAlmlineOtx1TlhAlarms
        table
        "
	::= { pm1004vencAlmlineOtx1TlhAlarmsEntry 1 }


pm1004vencAlmLineLaserTempHighAlaPortn OBJECT-TYPE
	SYNTAX  EkiOnOff
	MAX-ACCESS read-only
	STATUS current
	DESCRIPTION
        "
        Line Laser Temp. High Alarm :Alarm
        indicating the Line OTX TLH laser
        temperature is higher than the
         threshold written in the EEPROM
        <Condtype> LINE_LASER_TEMP_HIGH_ALA_1
        "
	::= { pm1004vencAlmlineOtx1TlhAlarmsEntry 15 }


pm1004vencAlmLineFreqDevHighAlaPortn OBJECT-TYPE
	SYNTAX  EkiOnOff
	MAX-ACCESS read-only
	STATUS current
	DESCRIPTION
        "
        Line Freq. Deviation High Alarm
        :Alarm indicating the Line OTX
         TLH frequency deviation is higher
        than the threshold written in the
        EEPROM <Condtype> LINE_FREQ_DEV_HIGH_ALA_1
        "
	::= { pm1004vencAlmlineOtx1TlhAlarmsEntry 13 }


pm1004vencAlmLineAgingHighAlaPortn OBJECT-TYPE
	SYNTAX  EkiOnOff
	MAX-ACCESS read-only
	STATUS current
	DESCRIPTION
        "
        Line OTX TLH Aging High Alarm
         :Alarm indicating the Line OTX
        TLH aging is higher than the threshold
        written in the EEPROM <Condtype>
        LINE_AGING_HIGH_ALA_1
        "
	::= { pm1004vencAlmlineOtx1TlhAlarmsEntry 7 }


pm1004vencAlmLineModulatorAgingHighAlaPortn OBJECT-TYPE
	SYNTAX  EkiOnOff
	MAX-ACCESS read-only
	STATUS current
	DESCRIPTION
        "
        Line Modulator Aging High Alarm
        :Alarm indicating the Line OTX
         TLH modulator aging is higher
         than the threshold written in
         the EEPROM <Condtype> LINE_MODULATOR_AGING_HIGH_ALA_1
        "
	::= { pm1004vencAlmlineOtx1TlhAlarmsEntry 6 }


--- *********************************************************
---     TABLE for the pm1004vencAlmlineOtx1TlhWarnings articles
--- *********************************************************

pm1004vencAlmlineOtx1TlhWarningsTable OBJECT-TYPE
	SYNTAX  SEQUENCE OF Pm1004vencAlmlineOtx1TlhWarningsEntry
	MAX-ACCESS not-accessible
	STATUS current
	DESCRIPTION
        "
        List of pm1004vencAlmlineOtx1TlhWarnings
        Article
        "
	::= { pm1004vencAlmLineNurg 225 }


pm1004vencAlmlineOtx1TlhWarningsEntry OBJECT-TYPE
	SYNTAX Pm1004vencAlmlineOtx1TlhWarningsEntry
	MAX-ACCESS not-accessible
	STATUS current
	DESCRIPTION
        "
        Row definition for the pm1004vencAlmlineOtx1TlhWarnings
        table
        "
	INDEX   { pm1004vencAlmlineOtx1TlhWarningsIndex }
	::= { pm1004vencAlmlineOtx1TlhWarningsTable 1 }


Pm1004vencAlmlineOtx1TlhWarningsEntry ::=
	SEQUENCE {
	pm1004vencAlmlineOtx1TlhWarningsIndex
		INTEGER,
	pm1004vencAlmLineLaserTempHighWarningPortn
		EkiOnOff,
	pm1004vencAlmLineFreqDevHighWarningPortn
		EkiOnOff,
	pm1004vencAlmLineAgingHighWarningPortn
		EkiOnOff,
	pm1004vencAlmLineModulatorAgingHighWarningPortn
		EkiOnOff
	}


pm1004vencAlmlineOtx1TlhWarningsIndex OBJECT-TYPE
	SYNTAX  INTEGER(0..128)
	MAX-ACCESS  read-only
	STATUS current
	DESCRIPTION
        "
        Index definition for the pm1004vencAlmlineOtx1TlhWarnings
        table
        "
	::= { pm1004vencAlmlineOtx1TlhWarningsEntry 1 }


pm1004vencAlmLineLaserTempHighWarningPortn OBJECT-TYPE
	SYNTAX  EkiOnOff
	MAX-ACCESS read-only
	STATUS current
	DESCRIPTION
        "
        Line Laser Temp. High Warning
         :Warning indicating the Line OTX
        TLH laser temperature is higher
        than the threshold written in the
        EEPROM <Condtype> LINE_LASER_TEMP_HIGH_WARNING_1
        "
	::= { pm1004vencAlmlineOtx1TlhWarningsEntry 15 }


pm1004vencAlmLineFreqDevHighWarningPortn OBJECT-TYPE
	SYNTAX  EkiOnOff
	MAX-ACCESS read-only
	STATUS current
	DESCRIPTION
        "
        Line Freq. Deviation High Warning
        :Warning indicating the Line OTX
        TLH frequency deviation is higher
        than the threshold written in the
        EEPROM <Condtype> LINE_FREQ_DEV_HIGH_WARNING_1
        "
	::= { pm1004vencAlmlineOtx1TlhWarningsEntry 13 }


pm1004vencAlmLineAgingHighWarningPortn OBJECT-TYPE
	SYNTAX  EkiOnOff
	MAX-ACCESS read-only
	STATUS current
	DESCRIPTION
        "
        Line OTX TLH Aging High Warning
        :Warning indicating the Line OTX
        TLH aging is higher than the threshold
        written in the EEPROM <Condtype>
        LINE_AGING_HIGH_WARNING_1
        "
	::= { pm1004vencAlmlineOtx1TlhWarningsEntry 7 }


pm1004vencAlmLineModulatorAgingHighWarningPortn OBJECT-TYPE
	SYNTAX  EkiOnOff
	MAX-ACCESS read-only
	STATUS current
	DESCRIPTION
        "
        Line Modulator Aging High Warning
        :Warning indicating the Line OTX
        TLH modulator aging is higher than
        the threshold written in the EEPROM
        <Condtype> LINE_MODULATOR_AGING_HIGH_WARNING_1
        "
	::= { pm1004vencAlmlineOtx1TlhWarningsEntry 6 }







--- *****************************************************
--- $$$$$$$$$$$$$$$$$$$$$$$$$$$$$$$$$$$$$$$$$$$$$$$$$$$$$
---     CONTROLS
--- $$$$$$$$$$$$$$$$$$$$$$$$$$$$$$$$$$$$$$$$$$$$$$$$$$$$$
--- *****************************************************



--- *****************************************************
---     LEAF for the confMgnt1 article
--- *****************************************************
pm1004vencCtrlconfMgnt1 OBJECT IDENTIFIER ::= { pm1004vencCtrlOther 1 }




pm1004vencCtrlConf2Clear1 OBJECT-TYPE
	  SYNTAX EkiOnOff
	  MAX-ACCESS read-write
	  STATUS current
	  DESCRIPTION
        "
        Clear Configuration Tables :This
        OID clears the configuration tables
        from configuration2 in the flash.
         <Help>  This control restores
         the default configuration of the
        module
        "
	  ::= { pm1004vencCtrlconfMgnt1 14 }



pm1004vencCtrlConf2Flash1 OBJECT-TYPE
	  SYNTAX EkiOnOff
	  MAX-ACCESS read-write
	  STATUS current
	  DESCRIPTION
        "
        Write Configuration Tables :This
        OID saves the current configuration
        of the PM as configuration2 in
         the flash.  <Help>  This control
        saves the customer configuration
        on the module
        "
	  ::= { pm1004vencCtrlconfMgnt1 10 }



pm1004vencCtrlConf2Load1 OBJECT-TYPE
	  SYNTAX EkiOnOff
	  MAX-ACCESS read-write
	  STATUS current
	  DESCRIPTION
        "
        Load Configuration Tables Set
         Nb 2 :When set this OID enables
        loading from flash configuration2
        into the PM.
        "
	  ::= { pm1004vencCtrlconfMgnt1 2 }



pm1004vencCtrlConf1Load1 OBJECT-TYPE
	  SYNTAX EkiOnOff
	  MAX-ACCESS read-write
	  STATUS current
	  DESCRIPTION
        "
        Load Configuration Tables Set
         Nb 1 :When set this OID enables
        loading from flash configuration1
        into the PM.
        "
	  ::= { pm1004vencCtrlconfMgnt1 1 }



--- *****************************************************
---     LEAF for the synth4 article
--- *****************************************************
pm1004vencCtrlsynth4 OBJECT IDENTIFIER ::= { pm1004vencCtrlOther 4 }




pm1004vencCtrlCorrelatOff OBJECT-TYPE
	  SYNTAX EkiOnOff
	  MAX-ACCESS read-write
	  STATUS current
	  DESCRIPTION
        "
        Disable Alarm Correlation :This
        OID disables the alarm correlation
        in the PM.
        "
	  ::= { pm1004vencCtrlsynth4 2 }



pm1004vencCtrlCorrelatOn OBJECT-TYPE
	  SYNTAX EkiOnOff
	  MAX-ACCESS read-write
	  STATUS current
	  DESCRIPTION
        "
        Enable Alarm Correlation :This
        OID enables the alarm correlation
        in the PM.
        "
	  ::= { pm1004vencCtrlsynth4 1 }



--- *****************************************************
---     LEAF for the swMgnt article
--- *****************************************************
pm1004vencCtrlswMgnt OBJECT IDENTIFIER ::= { pm1004vencCtrlOther 5 }




pm1004vencCtrlLoadSwBank2 OBJECT-TYPE
	  SYNTAX EkiOnOff
	  MAX-ACCESS read-write
	  STATUS current
	  DESCRIPTION
        "
        Set Software Nb 2 As Active :This
        OID, when set, loads the SW from
        bank2 into the PM. It must be followed
        by a reset.  <Help>  This controls
        selects the second SW bank as the
        active bank for the next module
        reset
        "
	  ::= { pm1004vencCtrlswMgnt 6 }



pm1004vencCtrlLoadSwBank1 OBJECT-TYPE
	  SYNTAX EkiOnOff
	  MAX-ACCESS read-write
	  STATUS current
	  DESCRIPTION
        "
        Set Software Nb 1 As Active :This
        OID, when set, loads the SW from
        bank1 into the PM. It must be followed
        by a reset.  <Help>  This controls
        selects the first SW bank as the
        active bank for the next module
        reset
        "
	  ::= { pm1004vencCtrlswMgnt 5 }



pm1004vencCtrlWarmReset OBJECT-TYPE
	  SYNTAX EkiOnOff
	  MAX-ACCESS read-write
	  STATUS current
	  DESCRIPTION
        "
        PM Warm Reset :This OID, when
         set, causes a warm reset of the
        PM. This reset is not traffic affecting,
        and the configuration of PM remains
        unchanged.  <Help>  This control
        initiates a warm reset of the module.
        "
	  ::= { pm1004vencCtrlswMgnt 3 }



pm1004vencCtrlColdReset OBJECT-TYPE
	  SYNTAX EkiOnOff
	  MAX-ACCESS read-write
	  STATUS current
	  DESCRIPTION
        "
        PM Cold Reset :This OID, when
         set, causes a cold reset of the
        PM. This reset is traffic affecting,
        and the configuration of PM is
         reloaded on start-up.  <Help>
          This control initiates a cold
        reset of the module.
        "
	  ::= { pm1004vencCtrlswMgnt 2 }



--- *****************************************************
---     LEAF for the gwMgnt article
--- *****************************************************
pm1004vencCtrlgwMgnt OBJECT IDENTIFIER ::= { pm1004vencCtrlOther 6 }




pm1004vencCtrlLoadGwBank4 OBJECT-TYPE
	  SYNTAX EkiOnOff
	  MAX-ACCESS read-write
	  STATUS current
	  DESCRIPTION
        "
        Set Gateware Nb 4 As Active :This
        OID, when set, loads the GW from
        bank4 (Flash) into the PM. It is
        followed by an automatic gateware
        cold reset.
        "
	  ::= { pm1004vencCtrlgwMgnt 8 }



pm1004vencCtrlLoadGwBank3 OBJECT-TYPE
	  SYNTAX EkiOnOff
	  MAX-ACCESS read-write
	  STATUS current
	  DESCRIPTION
        "
        Set Gateware Nb 3 As Active :This
        OID, when set, loads the GW from
        bank3 (Flash) into the PM. It is
        followed by an automatic gateware
        cold reset.  <Help>  This controls
        initiates a cold reset of the module
        and select the third GW bank as
        the active bank
        "
	  ::= { pm1004vencCtrlgwMgnt 7 }



pm1004vencCtrlLoadGwBank2 OBJECT-TYPE
	  SYNTAX EkiOnOff
	  MAX-ACCESS read-write
	  STATUS current
	  DESCRIPTION
        "
        Set Gateware Nb 2 As Active :This
        OID, when set, loads the GW from
        bank2 (Flash) into the PM. It is
        followed by an automatic gateware
        cold reset.
        "
	  ::= { pm1004vencCtrlgwMgnt 6 }



pm1004vencCtrlLoadGwBank1 OBJECT-TYPE
	  SYNTAX EkiOnOff
	  MAX-ACCESS read-write
	  STATUS current
	  DESCRIPTION
        "
        Set Gateware Nb 1 As Active :This
        OID, when set, loads the GW from
        bank1 (Flash) into the PM. It is
        followed by an automatic gateware
        cold reset.  <Help>  This controls
        initiates a cold reset of the module
        and select the first GW bank as
        the active bank
        "
	  ::= { pm1004vencCtrlgwMgnt 5 }



pm1004vencCtrlCurrentGwReset OBJECT-TYPE
	  SYNTAX EkiOnOff
	  MAX-ACCESS read-write
	  STATUS current
	  DESCRIPTION
        "
        Active Gateware Reset :This OID,
        when set, resets the active gateware.
        It is traffic affecting.
        "
	  ::= { pm1004vencCtrlgwMgnt 1 }



--- *********************************************************
---     TABLE for the pm1004vencCtrlaccessLoop articles
--- *********************************************************

pm1004vencCtrlaccessLoopTable OBJECT-TYPE
	SYNTAX  SEQUENCE OF Pm1004vencCtrlaccessLoopEntry
	MAX-ACCESS not-accessible
	STATUS current
	DESCRIPTION
        "
        List of pm1004vencCtrlaccessLoop
        Article
        "
	::= { pm1004vencCtrlClient 16 }


pm1004vencCtrlaccessLoopEntry OBJECT-TYPE
	SYNTAX Pm1004vencCtrlaccessLoopEntry
	MAX-ACCESS not-accessible
	STATUS current
	DESCRIPTION
        "
        Row definition for the pm1004vencCtrlaccessLoop
        table
        "
	INDEX   { pm1004vencCtrlaccessLoopIndex }
	::= { pm1004vencCtrlaccessLoopTable 1 }


Pm1004vencCtrlaccessLoopEntry ::=
	SEQUENCE {
	pm1004vencCtrlaccessLoopIndex
		INTEGER,
	pm1004vencCtrlaccessLoopPortn
		EkiState
	}


pm1004vencCtrlaccessLoopIndex OBJECT-TYPE
	SYNTAX  INTEGER(0..128)
	MAX-ACCESS  read-only
	STATUS current
	DESCRIPTION
        "
        Index definition for the pm1004vencCtrlaccessLoop
        table
        "
	::= { pm1004vencCtrlaccessLoopEntry 1 }


pm1004vencCtrlaccessLoopPortn OBJECT-TYPE
	SYNTAX  EkiState
	MAX-ACCESS read-write
	STATUS current
	DESCRIPTION
        "
        Client Facility Loopback :This
        OID operates a Client Facility
         Loopback, looping client input
        signal on the client output port.
        The loop is located on the client
        transceiver  <Help> This maintenance
        parameter operates a Client Facility
        Loopback, looping client input
         signal on the client output port.
        The loop is located on the client
        transceiver
        "
	::= { pm1004vencCtrlaccessLoopEntry 2 }


--- *********************************************************
---     TABLE for the pm1004vencCtrlportOosMode articles
--- *********************************************************

pm1004vencCtrlportOosModeTable OBJECT-TYPE
	SYNTAX  SEQUENCE OF Pm1004vencCtrlportOosModeEntry
	MAX-ACCESS not-accessible
	STATUS current
	DESCRIPTION
        "
        List of pm1004vencCtrlportOosMode
        Article
        "
	::= { pm1004vencCtrlClient 18 }


pm1004vencCtrlportOosModeEntry OBJECT-TYPE
	SYNTAX Pm1004vencCtrlportOosModeEntry
	MAX-ACCESS not-accessible
	STATUS current
	DESCRIPTION
        "
        Row definition for the pm1004vencCtrlportOosMode
        table
        "
	INDEX   { pm1004vencCtrlportOosModeIndex }
	::= { pm1004vencCtrlportOosModeTable 1 }


Pm1004vencCtrlportOosModeEntry ::=
	SEQUENCE {
	pm1004vencCtrlportOosModeIndex
		INTEGER,
	pm1004vencCtrlportOosModePortn
		Pm1004vencClientOosMode
	}


pm1004vencCtrlportOosModeIndex OBJECT-TYPE
	SYNTAX  INTEGER(0..128)
	MAX-ACCESS  read-only
	STATUS current
	DESCRIPTION
        "
        Index definition for the pm1004vencCtrlportOosMode
        table
        "
	::= { pm1004vencCtrlportOosModeEntry 1 }


pm1004vencCtrlportOosModePortn OBJECT-TYPE
	SYNTAX  Pm1004vencClientOosMode
	MAX-ACCESS read-write
	STATUS current
	DESCRIPTION
        "
        Client Out Of Service :This OID
        sets the Service state of the client
        port (In Service, Tx Out of Service,
        Rx Out of Service or Port (Rx and
        Tx) Out of Service)  <Help>  This
        controls defines the service state
        of the client port (In Service,
        Tx Out of Service, Rx Out of Service
         or Port (Rx and Tx) Out of Service)
        "
	::= { pm1004vencCtrlportOosModeEntry 2 }


--- *********************************************************
---     TABLE for the pm1004vencCtrlsfpOffCtrl articles
--- *********************************************************

pm1004vencCtrlsfpOffCtrlTable OBJECT-TYPE
	SYNTAX  SEQUENCE OF Pm1004vencCtrlsfpOffCtrlEntry
	MAX-ACCESS not-accessible
	STATUS current
	DESCRIPTION
        "
        List of pm1004vencCtrlsfpOffCtrl
        Article
        "
	::= { pm1004vencCtrlClient 20 }


pm1004vencCtrlsfpOffCtrlEntry OBJECT-TYPE
	SYNTAX Pm1004vencCtrlsfpOffCtrlEntry
	MAX-ACCESS not-accessible
	STATUS current
	DESCRIPTION
        "
        Row definition for the pm1004vencCtrlsfpOffCtrl
        table
        "
	INDEX   { pm1004vencCtrlsfpOffCtrlIndex }
	::= { pm1004vencCtrlsfpOffCtrlTable 1 }


Pm1004vencCtrlsfpOffCtrlEntry ::=
	SEQUENCE {
	pm1004vencCtrlsfpOffCtrlIndex
		INTEGER,
	pm1004vencCtrlsfpOffCtrlPortn
		EkiState
	}


pm1004vencCtrlsfpOffCtrlIndex OBJECT-TYPE
	SYNTAX  INTEGER(0..128)
	MAX-ACCESS  read-only
	STATUS current
	DESCRIPTION
        "
        Index definition for the pm1004vencCtrlsfpOffCtrl
        table
        "
	::= { pm1004vencCtrlsfpOffCtrlEntry 1 }


pm1004vencCtrlsfpOffCtrlPortn OBJECT-TYPE
	SYNTAX  EkiState
	MAX-ACCESS read-write
	STATUS current
	DESCRIPTION
        "
        Signal OFF :This OID switches
         off the SFP.  <Help>   This control
        defines the laser state of the
         client transceiver
        "
	::= { pm1004vencCtrlsfpOffCtrlEntry 2 }


--- *********************************************************
---     TABLE for the pm1004vencCtrlcsfUpIns articles
--- *********************************************************

pm1004vencCtrlcsfUpInsTable OBJECT-TYPE
	SYNTAX  SEQUENCE OF Pm1004vencCtrlcsfUpInsEntry
	MAX-ACCESS not-accessible
	STATUS current
	DESCRIPTION
        "
        List of pm1004vencCtrlcsfUpIns
        Article
        "
	::= { pm1004vencCtrlClient 21 }


pm1004vencCtrlcsfUpInsEntry OBJECT-TYPE
	SYNTAX Pm1004vencCtrlcsfUpInsEntry
	MAX-ACCESS not-accessible
	STATUS current
	DESCRIPTION
        "
        Row definition for the pm1004vencCtrlcsfUpIns
        table
        "
	INDEX   { pm1004vencCtrlcsfUpInsIndex }
	::= { pm1004vencCtrlcsfUpInsTable 1 }


Pm1004vencCtrlcsfUpInsEntry ::=
	SEQUENCE {
	pm1004vencCtrlcsfUpInsIndex
		INTEGER,
	pm1004vencCtrlcsfUpInsPortn
		EkiState
	}


pm1004vencCtrlcsfUpInsIndex OBJECT-TYPE
	SYNTAX  INTEGER(0..128)
	MAX-ACCESS  read-only
	STATUS current
	DESCRIPTION
        "
        Index definition for the pm1004vencCtrlcsfUpIns
        table
        "
	::= { pm1004vencCtrlcsfUpInsEntry 1 }


pm1004vencCtrlcsfUpInsPortn OBJECT-TYPE
	SYNTAX  EkiState
	MAX-ACCESS read-write
	STATUS current
	DESCRIPTION
        "
        Client Signal Fail Insertion :This
        OID, when set, inserts  a client
        signal fail in the upstream client
        Port.  <Help>  This control inserts
        a Client Signal Fail for the client
        port
        "
	::= { pm1004vencCtrlcsfUpInsEntry 2 }


--- *********************************************************
---     TABLE for the pm1004vencCtrlcaisDwIns articles
--- *********************************************************

pm1004vencCtrlcaisDwInsTable OBJECT-TYPE
	SYNTAX  SEQUENCE OF Pm1004vencCtrlcaisDwInsEntry
	MAX-ACCESS not-accessible
	STATUS current
	DESCRIPTION
        "
        List of pm1004vencCtrlcaisDwIns
        Article
        "
	::= { pm1004vencCtrlClient 22 }


pm1004vencCtrlcaisDwInsEntry OBJECT-TYPE
	SYNTAX Pm1004vencCtrlcaisDwInsEntry
	MAX-ACCESS not-accessible
	STATUS current
	DESCRIPTION
        "
        Row definition for the pm1004vencCtrlcaisDwIns
        table
        "
	INDEX   { pm1004vencCtrlcaisDwInsIndex }
	::= { pm1004vencCtrlcaisDwInsTable 1 }


Pm1004vencCtrlcaisDwInsEntry ::=
	SEQUENCE {
	pm1004vencCtrlcaisDwInsIndex
		INTEGER,
	pm1004vencCtrlcaisDwInsPortn
		EkiState
	}


pm1004vencCtrlcaisDwInsIndex OBJECT-TYPE
	SYNTAX  INTEGER(0..128)
	MAX-ACCESS  read-only
	STATUS current
	DESCRIPTION
        "
        Index definition for the pm1004vencCtrlcaisDwIns
        table
        "
	::= { pm1004vencCtrlcaisDwInsEntry 1 }


pm1004vencCtrlcaisDwInsPortn OBJECT-TYPE
	SYNTAX  EkiState
	MAX-ACCESS read-write
	STATUS current
	DESCRIPTION
        "
        Client AIS Insertion :This OID,
        when set, inserts a client AIS
         on the downstream client Port.
         <Help>  This control inserts a
        Client AIS for the client port
        "
	::= { pm1004vencCtrlcaisDwInsEntry 2 }


--- *********************************************************
---     TABLE for the pm1004vencCtrlclientAccessTermLoop articles
--- *********************************************************

pm1004vencCtrlclientAccessTermLoopTable OBJECT-TYPE
	SYNTAX  SEQUENCE OF Pm1004vencCtrlclientAccessTermLoopEntry
	MAX-ACCESS not-accessible
	STATUS current
	DESCRIPTION
        "
        List of pm1004vencCtrlclientAccessTermLoop
        Article
        "
	::= { pm1004vencCtrlClient 26 }


pm1004vencCtrlclientAccessTermLoopEntry OBJECT-TYPE
	SYNTAX Pm1004vencCtrlclientAccessTermLoopEntry
	MAX-ACCESS not-accessible
	STATUS current
	DESCRIPTION
        "
        Row definition for the pm1004vencCtrlclientAccessTermLoop
        table
        "
	INDEX   { pm1004vencCtrlclientAccessTermLoopIndex }
	::= { pm1004vencCtrlclientAccessTermLoopTable 1 }


Pm1004vencCtrlclientAccessTermLoopEntry ::=
	SEQUENCE {
	pm1004vencCtrlclientAccessTermLoopIndex
		INTEGER,
	pm1004vencCtrlclientAccessTermLoopPortn
		EkiState
	}


pm1004vencCtrlclientAccessTermLoopIndex OBJECT-TYPE
	SYNTAX  INTEGER(0..128)
	MAX-ACCESS  read-only
	STATUS current
	DESCRIPTION
        "
        Index definition for the pm1004vencCtrlclientAccessTermLoop
        table
        "
	::= { pm1004vencCtrlclientAccessTermLoopEntry 1 }


pm1004vencCtrlclientAccessTermLoopPortn OBJECT-TYPE
	SYNTAX  EkiState
	MAX-ACCESS read-write
	STATUS current
	DESCRIPTION
        "
        Client Terminal Loopback :This
        OID operates a Client Terminal
         Loopback, looping client input
        signal on the client output port.
        The loop is located on the line
        transceiver  <Help> This maintenance
        parameter operates a Client Terminal
        Loopback, looping client input
         signal on the client output port.
        The loop is located on the line
        transceiver
        "
	::= { pm1004vencCtrlclientAccessTermLoopEntry 2 }


--- *********************************************************
---     TABLE for the pm1004vencCtrlrxVideoProtocol articles
--- *********************************************************

pm1004vencCtrlrxVideoProtocolTable OBJECT-TYPE
	SYNTAX  SEQUENCE OF Pm1004vencCtrlrxVideoProtocolEntry
	MAX-ACCESS not-accessible
	STATUS current
	DESCRIPTION
        "
        List of pm1004vencCtrlrxVideoProtocol
        Article
        "
	::= { pm1004vencCtrlClient 43 }


pm1004vencCtrlrxVideoProtocolEntry OBJECT-TYPE
	SYNTAX Pm1004vencCtrlrxVideoProtocolEntry
	MAX-ACCESS not-accessible
	STATUS current
	DESCRIPTION
        "
        Row definition for the pm1004vencCtrlrxVideoProtocol
        table
        "
	INDEX   { pm1004vencCtrlrxVideoProtocolIndex }
	::= { pm1004vencCtrlrxVideoProtocolTable 1 }


Pm1004vencCtrlrxVideoProtocolEntry ::=
	SEQUENCE {
	pm1004vencCtrlrxVideoProtocolIndex
		INTEGER,
	pm1004vencCtrlrxVideoProtocolPortn
		EkiState
	}


pm1004vencCtrlrxVideoProtocolIndex OBJECT-TYPE
	SYNTAX  INTEGER(0..128)
	MAX-ACCESS  read-only
	STATUS current
	DESCRIPTION
        "
        Index definition for the pm1004vencCtrlrxVideoProtocol
        table
        "
	::= { pm1004vencCtrlrxVideoProtocolEntry 1 }


pm1004vencCtrlrxVideoProtocolPortn OBJECT-TYPE
	SYNTAX  EkiState
	MAX-ACCESS read-write
	STATUS current
	DESCRIPTION
        "
        Force DVB ASI On RX Side
 :This
        OID selects the DVB ASI protocol
        on the client port and disable
         the auto-sensing feature
  <Help>
         This control selects the DVB ASI
        protocol on the client port and
        disable the auto-sensing feature

        "
	::= { pm1004vencCtrlrxVideoProtocolEntry 2 }


--- *****************************************************
---     LEAF for the commAccessLoop article
--- *****************************************************
pm1004vencCtrlcommAccessLoop OBJECT IDENTIFIER ::= { pm1004vencCtrlLine 64 }




pm1004vencCtrlCommAccessloop OBJECT-TYPE
	  SYNTAX EkiOnOff
	  MAX-ACCESS read-write
	  STATUS deprecated
	  DESCRIPTION
        "
        PM Full Access Loop Mode :This
        OID, when set, puts the module
         in common access loop back, looping
        the 10 Gb/s output signal on the
        10 Gb/s input.
        "
	  ::= { pm1004vencCtrlcommAccessLoop 1 }



--- *****************************************************
---     LEAF for the lineLoop article
--- *****************************************************
pm1004vencCtrllineLoop OBJECT IDENTIFIER ::= { pm1004vencCtrlLine 66 }




pm1004vencCtrlLineLoop OBJECT-TYPE
	  SYNTAX EkiOnOff
	  MAX-ACCESS read-write
	  STATUS deprecated
	  DESCRIPTION
        "
        PM Line Loop Mode :This OID, when
        set at '1' puts the module in line
        loopback mode, looping the received
        10 Gb/s signal on the transmit
         10 Gb/s output. The Upstream part
        of the module is timed on the 10
        Gb/s recovered clock in that case.
        "
	  ::= { pm1004vencCtrllineLoop 1 }



--- *****************************************************
---     LEAF for the protMgnt article
--- *****************************************************
pm1004vencCtrlProtMgnt OBJECT IDENTIFIER ::= { pm1004vencCtrlLine 73 }




pm1004vencCtrlLineNumber OBJECT-TYPE
	  SYNTAX Unsigned32 (0..3)
	  MAX-ACCESS read-write
	  STATUS current
	  DESCRIPTION
        "
        Active Line Number : This OID
         sets the active line number
        "
	  ::= { pm1004vencCtrlProtMgnt 1 }



pm1004vencCtrlProtMode OBJECT-TYPE
	  SYNTAX EkiMode
	  MAX-ACCESS read-write
	  STATUS current
	  DESCRIPTION
        "
        Line Switch Mode (Auto Or Manual)
        :This bit selects the manual (1)
        or automatic (0) switch method
          <Help>  This control defines
         the protection switch mode on
         the line interface
        "
	  ::= { pm1004vencCtrlProtMgnt 2 }



--- *********************************************************
---     TABLE for the pm1004vencCtrllineOosMode articles
--- *********************************************************

pm1004vencCtrllineOosModeTable OBJECT-TYPE
	SYNTAX  SEQUENCE OF Pm1004vencCtrllineOosModeEntry
	MAX-ACCESS not-accessible
	STATUS current
	DESCRIPTION
        "
        List of pm1004vencCtrllineOosMode
        Article
        "
	::= { pm1004vencCtrlLine 74 }


pm1004vencCtrllineOosModeEntry OBJECT-TYPE
	SYNTAX Pm1004vencCtrllineOosModeEntry
	MAX-ACCESS not-accessible
	STATUS current
	DESCRIPTION
        "
        Row definition for the pm1004vencCtrllineOosMode
        table
        "
	INDEX   { pm1004vencCtrllineOosModeIndex }
	::= { pm1004vencCtrllineOosModeTable 1 }


Pm1004vencCtrllineOosModeEntry ::=
	SEQUENCE {
	pm1004vencCtrllineOosModeIndex
		INTEGER,
	pm1004vencCtrllineOosModePortn
		EkiState
	}


pm1004vencCtrllineOosModeIndex OBJECT-TYPE
	SYNTAX  INTEGER(0..128)
	MAX-ACCESS  read-only
	STATUS current
	DESCRIPTION
        "
        Index definition for the pm1004vencCtrllineOosMode
        table
        "
	::= { pm1004vencCtrllineOosModeEntry 1 }


pm1004vencCtrllineOosModePortn OBJECT-TYPE
	SYNTAX  EkiState
	MAX-ACCESS read-write
	STATUS current
	DESCRIPTION
        "
        Line Out Of Service (!Laser OFF!)
        :This OID sets the line port Out
        Of Service  <Help>  This control
        defines the service state of the
        line port
        "
	::= { pm1004vencCtrllineOosModeEntry 2 }


--- *********************************************************
---     TABLE for the pm1004vencCtrladddropClientRxProtect articles
--- *********************************************************

pm1004vencCtrladddropClientRxProtectTable OBJECT-TYPE
	SYNTAX  SEQUENCE OF Pm1004vencCtrladddropClientRxProtectEntry
	MAX-ACCESS not-accessible
	STATUS current
	DESCRIPTION
        "
        List of pm1004vencCtrladddropClientRxProtect
        Article
        "
	::= { pm1004vencCtrlClient 128 }


pm1004vencCtrladddropClientRxProtectEntry OBJECT-TYPE
	SYNTAX Pm1004vencCtrladddropClientRxProtectEntry
	MAX-ACCESS not-accessible
	STATUS current
	DESCRIPTION
        "
        Row definition for the pm1004vencCtrladddropClientRxProtect
        table
        "
	INDEX   { pm1004vencCtrladddropClientRxProtectIndex }
	::= { pm1004vencCtrladddropClientRxProtectTable 1 }


Pm1004vencCtrladddropClientRxProtectEntry ::=
	SEQUENCE {
	pm1004vencCtrladddropClientRxProtectIndex
		INTEGER,
	pm1004vencCtrladddropClientRxProtectPortn
		Pm1004vencProtectionTimeSlot
	}


pm1004vencCtrladddropClientRxProtectIndex OBJECT-TYPE
	SYNTAX  INTEGER(0..128)
	MAX-ACCESS  read-only
	STATUS current
	DESCRIPTION
        "
        Index definition for the pm1004vencCtrladddropClientRxProtect
        table
        "
	::= { pm1004vencCtrladddropClientRxProtectEntry 1 }


pm1004vencCtrladddropClientRxProtectPortn OBJECT-TYPE
	SYNTAX  Pm1004vencProtectionTimeSlot
	MAX-ACCESS read-write
	STATUS current
	DESCRIPTION
        "
        Client Switch Mode :This bit selects
        the manual (1) or automatic (0)
        switch method  <Help>  This control
        defines the protection switch mode
        on the client interface
        "
	::= { pm1004vencCtrladddropClientRxProtectEntry 2 }


--- *********************************************************
---     TABLE for the pm1004vencCtrladddropTsClientMode articles
--- *********************************************************

pm1004vencCtrladddropTsClientModeTable OBJECT-TYPE
	SYNTAX  SEQUENCE OF Pm1004vencCtrladddropTsClientModeEntry
	MAX-ACCESS not-accessible
	STATUS current
	DESCRIPTION
        "
        List of pm1004vencCtrladddropTsClientMode
        Article
        "
	::= { pm1004vencCtrlClient 136 }


pm1004vencCtrladddropTsClientModeEntry OBJECT-TYPE
	SYNTAX Pm1004vencCtrladddropTsClientModeEntry
	MAX-ACCESS not-accessible
	STATUS current
	DESCRIPTION
        "
        Row definition for the pm1004vencCtrladddropTsClientMode
        table
        "
	INDEX   { pm1004vencCtrladddropTsClientModeIndex }
	::= { pm1004vencCtrladddropTsClientModeTable 1 }


Pm1004vencCtrladddropTsClientModeEntry ::=
	SEQUENCE {
	pm1004vencCtrladddropTsClientModeIndex
		INTEGER,
	pm1004vencCtrladddropTsClientModePortn
		Pm1004vencModeTimeSlot
	}


pm1004vencCtrladddropTsClientModeIndex OBJECT-TYPE
	SYNTAX  INTEGER(0..128)
	MAX-ACCESS  read-only
	STATUS current
	DESCRIPTION
        "
        Index definition for the pm1004vencCtrladddropTsClientMode
        table
        "
	::= { pm1004vencCtrladddropTsClientModeEntry 1 }


pm1004vencCtrladddropTsClientModePortn OBJECT-TYPE
	SYNTAX  Pm1004vencModeTimeSlot
	MAX-ACCESS read-write
	STATUS current
	DESCRIPTION
        "
        Client Mode :This OID selects
         the mode on the client  <Help>
          This control defines the mode
        (Add/Drop or Split&Select) of the
        Client
        "
	::= { pm1004vencCtrladddropTsClientModeEntry 2 }


--- *****************************************************
---     LEAF for the ledTest article
--- *****************************************************
pm1004vencCtrlledTest OBJECT IDENTIFIER ::= { pm1004vencCtrlOther 192 }




pm1004vencCtrlLedOff OBJECT-TYPE
	  SYNTAX EkiOnOff
	  MAX-ACCESS read-write
	  STATUS current
	  DESCRIPTION
        "
        Leds Off :This OID switches off
        all the Leds as a test feature.
         <Help>  This control initiates
        a test leds turning all the LEDs
        to OFF
        "
	  ::= { pm1004vencCtrlledTest 3 }



pm1004vencCtrlRedLed OBJECT-TYPE
	  SYNTAX EkiOnOff
	  MAX-ACCESS read-write
	  STATUS current
	  DESCRIPTION
        "
        Red Leds Test :This OID switches
        on all the red Leds as a test feature.
         <Help>  This control initiates
        a test leds turning all the LEDs
        to red
        "
	  ::= { pm1004vencCtrlledTest 2 }



pm1004vencCtrlGreenLed OBJECT-TYPE
	  SYNTAX EkiOnOff
	  MAX-ACCESS read-write
	  STATUS current
	  DESCRIPTION
        "
        Green Leds Test :This OID switches
        on all the green Leds as a test
        feature.  <Help>  This control
         initiates a test leds turning
         all the LEDs to green
        "
	  ::= { pm1004vencCtrlledTest 1 }



--- *****************************************************
---     LEAF for the moduleOosMode article
--- *****************************************************
pm1004vencCtrlmoduleOosMode OBJECT IDENTIFIER ::= { pm1004vencCtrlOther 193 }




pm1004vencCtrlModuleOosMode OBJECT-TYPE
	  SYNTAX EkiOnOff
	  MAX-ACCESS read-write
	  STATUS current
	  DESCRIPTION
        "
        PM Out Of Service :This OID sets
        the PM Out Of Service  <Help>
         This control defines the service
        state of the complete module
        "
	  ::= { pm1004vencCtrlmoduleOosMode 1 }



--- *****************************************************
---     LEAF for the maintenanceMode article
--- *****************************************************
pm1004vencCtrlmaintenanceMode OBJECT IDENTIFIER ::= { pm1004vencCtrlOther 197 }




pm1004vencCtrlMaintenanceMode OBJECT-TYPE
	  SYNTAX EkiOnOff
	  MAX-ACCESS read-write
	  STATUS current
	  DESCRIPTION
        "
        Enable Maintenance :This OID enables
        the maintenance mode on the PM.
         <Help>  This control enables the
        maintenance mode on the PM.
        "
	  ::= { pm1004vencCtrlmaintenanceMode 1 }



--- *********************************************************
---     TABLE for the pm1004vencCtrldccEnable articles
--- *********************************************************

pm1004vencCtrldccEnableTable OBJECT-TYPE
	SYNTAX  SEQUENCE OF Pm1004vencCtrldccEnableEntry
	MAX-ACCESS not-accessible
	STATUS current
	DESCRIPTION
        "
        List of pm1004vencCtrldccEnable
        Article
        "
	::= { pm1004vencCtrlLine 198 }


pm1004vencCtrldccEnableEntry OBJECT-TYPE
	SYNTAX Pm1004vencCtrldccEnableEntry
	MAX-ACCESS not-accessible
	STATUS current
	DESCRIPTION
        "
        Row definition for the pm1004vencCtrldccEnable
        table
        "
	INDEX   { pm1004vencCtrldccEnableIndex }
	::= { pm1004vencCtrldccEnableTable 1 }


Pm1004vencCtrldccEnableEntry ::=
	SEQUENCE {
	pm1004vencCtrldccEnableIndex
		INTEGER,
	pm1004vencCtrldccEnablePortn
		EkiState
	}


pm1004vencCtrldccEnableIndex OBJECT-TYPE
	SYNTAX  INTEGER(0..128)
	MAX-ACCESS  read-only
	STATUS current
	DESCRIPTION
        "
        Index definition for the pm1004vencCtrldccEnable
        table
        "
	::= { pm1004vencCtrldccEnableEntry 1 }


pm1004vencCtrldccEnablePortn OBJECT-TYPE
	SYNTAX  EkiState
	MAX-ACCESS read-write
	STATUS current
	DESCRIPTION
        "
        DCC Enable : This OID enables
         the DCC mode on the PM  <Help>
          This control enables the DCC
         mode on the PM
        "
	::= { pm1004vencCtrldccEnableEntry 2 }


--- *****************************************************
---     LEAF for the encryptionSelect article
--- *****************************************************

pm1004vencCtrlencryptionSelect OBJECT-TYPE
	  SYNTAX Pm1004vencKeyMode
	  MAX-ACCESS read-write
	  STATUS current
	  DESCRIPTION
        "
        Encryption Key Selection :This
        OID selects the key (first key:0
        or second key:1) to use to encrypt/decrypt
        the video stream.  <Help>  This
        control selects the key to use
         to encrypt/decrypt the video stream.
        "
	  ::= { pm1004vencCtrlOther 200 }



--- *********************************************************
---     TABLE for the pm1004vencCtrlxfpOnoff articles
--- *********************************************************

pm1004vencCtrlxfpOnoffTable OBJECT-TYPE
	SYNTAX  SEQUENCE OF Pm1004vencCtrlxfpOnoffEntry
	MAX-ACCESS not-accessible
	STATUS current
	DESCRIPTION
        "
        List of pm1004vencCtrlxfpOnoff
        Article
        "
	::= { pm1004vencCtrlLine 208 }


pm1004vencCtrlxfpOnoffEntry OBJECT-TYPE
	SYNTAX Pm1004vencCtrlxfpOnoffEntry
	MAX-ACCESS not-accessible
	STATUS current
	DESCRIPTION
        "
        Row definition for the pm1004vencCtrlxfpOnoff
        table
        "
	INDEX   { pm1004vencCtrlxfpOnoffIndex }
	::= { pm1004vencCtrlxfpOnoffTable 1 }


Pm1004vencCtrlxfpOnoffEntry ::=
	SEQUENCE {
	pm1004vencCtrlxfpOnoffIndex
		INTEGER,
	pm1004vencCtrlxfpOnoffPortn
		EkiState
	}


pm1004vencCtrlxfpOnoffIndex OBJECT-TYPE
	SYNTAX  INTEGER(0..128)
	MAX-ACCESS  read-only
	STATUS current
	DESCRIPTION
        "
        Index definition for the pm1004vencCtrlxfpOnoff
        table
        "
	::= { pm1004vencCtrlxfpOnoffEntry 1 }


pm1004vencCtrlxfpOnoffPortn OBJECT-TYPE
	SYNTAX  EkiState
	MAX-ACCESS read-write
	STATUS current
	DESCRIPTION
        "
        Line Optical Laser Shutdown :This
        OID switches off the XFP or the
        OTX  <Help>  This control defines
        the laser state of the line transceiver
        "
	::= { pm1004vencCtrlxfpOnoffEntry 2 }


--- *********************************************************
---     TABLE for the pm1004vencCtrlxfpLineLoop articles
--- *********************************************************

pm1004vencCtrlxfpLineLoopTable OBJECT-TYPE
	SYNTAX  SEQUENCE OF Pm1004vencCtrlxfpLineLoopEntry
	MAX-ACCESS not-accessible
	STATUS current
	DESCRIPTION
        "
        List of pm1004vencCtrlxfpLineLoop
        Article
        "
	::= { pm1004vencCtrlLine 209 }


pm1004vencCtrlxfpLineLoopEntry OBJECT-TYPE
	SYNTAX Pm1004vencCtrlxfpLineLoopEntry
	MAX-ACCESS not-accessible
	STATUS current
	DESCRIPTION
        "
        Row definition for the pm1004vencCtrlxfpLineLoop
        table
        "
	INDEX   { pm1004vencCtrlxfpLineLoopIndex }
	::= { pm1004vencCtrlxfpLineLoopTable 1 }


Pm1004vencCtrlxfpLineLoopEntry ::=
	SEQUENCE {
	pm1004vencCtrlxfpLineLoopIndex
		INTEGER,
	pm1004vencCtrlxfpLineLoopPortn
		EkiState
	}


pm1004vencCtrlxfpLineLoopIndex OBJECT-TYPE
	SYNTAX  INTEGER(0..128)
	MAX-ACCESS  read-only
	STATUS current
	DESCRIPTION
        "
        Index definition for the pm1004vencCtrlxfpLineLoop
        table
        "
	::= { pm1004vencCtrlxfpLineLoopEntry 1 }


pm1004vencCtrlxfpLineLoopPortn OBJECT-TYPE
	SYNTAX  EkiState
	MAX-ACCESS read-write
	STATUS current
	DESCRIPTION
        "
        Line Facility Loopback :This OID
        operates a Line Facility Loopback,
        looping line input signal on the
        line output port. The loop is located
        on the line transceiver. If the
        Line signal carries DCC, the management
        network is impacted  <Help> This
        maintenance parameter operates
         a Line Facility Loopback, looping
        line input signal on the line output
        port. The loop is located on the
        line transceiver. If the Line signal
        carries DCC, the management network
        is impacted
        "
	::= { pm1004vencCtrlxfpLineLoopEntry 2 }


--- *********************************************************
---     TABLE for the pm1004vencCtrlxfpXfiLoop articles
--- *********************************************************

pm1004vencCtrlxfpXfiLoopTable OBJECT-TYPE
	SYNTAX  SEQUENCE OF Pm1004vencCtrlxfpXfiLoopEntry
	MAX-ACCESS not-accessible
	STATUS current
	DESCRIPTION
        "
        List of pm1004vencCtrlxfpXfiLoop
        Article
        "
	::= { pm1004vencCtrlLine 210 }


pm1004vencCtrlxfpXfiLoopEntry OBJECT-TYPE
	SYNTAX Pm1004vencCtrlxfpXfiLoopEntry
	MAX-ACCESS not-accessible
	STATUS current
	DESCRIPTION
        "
        Row definition for the pm1004vencCtrlxfpXfiLoop
        table
        "
	INDEX   { pm1004vencCtrlxfpXfiLoopIndex }
	::= { pm1004vencCtrlxfpXfiLoopTable 1 }


Pm1004vencCtrlxfpXfiLoopEntry ::=
	SEQUENCE {
	pm1004vencCtrlxfpXfiLoopIndex
		INTEGER,
	pm1004vencCtrlxfpXfiLoopPortn
		EkiState
	}


pm1004vencCtrlxfpXfiLoopIndex OBJECT-TYPE
	SYNTAX  INTEGER(0..128)
	MAX-ACCESS  read-only
	STATUS current
	DESCRIPTION
        "
        Index definition for the pm1004vencCtrlxfpXfiLoop
        table
        "
	::= { pm1004vencCtrlxfpXfiLoopEntry 1 }


pm1004vencCtrlxfpXfiLoopPortn OBJECT-TYPE
	SYNTAX  EkiState
	MAX-ACCESS read-write
	STATUS current
	DESCRIPTION
        "
        Line Terminal Loopback :This OID
        operates a Line Terminal Loopback,
        looping line input signal on the
        line output port. The loop is located
        on all client transceivers  <Help>
        This maintenance parameter operates
        a Line Terminal Loopback, looping
        line input signal on the line output
        port. The loop is located on all
        client transceivers.
        "
	::= { pm1004vencCtrlxfpXfiLoopEntry 2 }


--- *********************************************************
---     TABLE for the pm1004vencCtrllineTunableChannel articles
--- *********************************************************

pm1004vencCtrllineTunableChannelTable OBJECT-TYPE
	SYNTAX  SEQUENCE OF Pm1004vencCtrllineTunableChannelEntry
	MAX-ACCESS not-accessible
	STATUS current
	DESCRIPTION
        "
        List of pm1004vencCtrllineTunableChannel
        Article
        "
	::= { pm1004vencCtrlLine 212 }


pm1004vencCtrllineTunableChannelEntry OBJECT-TYPE
	SYNTAX Pm1004vencCtrllineTunableChannelEntry
	MAX-ACCESS not-accessible
	STATUS current
	DESCRIPTION
        "
        Row definition for the pm1004vencCtrllineTunableChannel
        table
        "
	INDEX   { pm1004vencCtrllineTunableChannelIndex }
	::= { pm1004vencCtrllineTunableChannelTable 1 }


Pm1004vencCtrllineTunableChannelEntry ::=
	SEQUENCE {
	pm1004vencCtrllineTunableChannelIndex
		INTEGER,
	pm1004vencCtrllineTunableChannelPortn
		Pm1004vencOtxChannel
	}


pm1004vencCtrllineTunableChannelIndex OBJECT-TYPE
	SYNTAX  INTEGER(0..128)
	MAX-ACCESS  read-only
	STATUS current
	DESCRIPTION
        "
        Index definition for the pm1004vencCtrllineTunableChannel
        table
        "
	::= { pm1004vencCtrllineTunableChannelEntry 1 }


pm1004vencCtrllineTunableChannelPortn OBJECT-TYPE
	SYNTAX  Pm1004vencOtxChannel
	MAX-ACCESS read-write
	STATUS current
	DESCRIPTION
        "
        ITU Channel :This OID selects
         the ITU channel of the Line OTX
        TLH Laser  <Help>   This control
        defines the ITU channel of the
         Line OTX TLH Laser
        "
	::= { pm1004vencCtrllineTunableChannelEntry 2 }


--- *********************************************************
---     TABLE for the pm1004vencCtrllinePhotodiodeMode articles
--- *********************************************************

pm1004vencCtrllinePhotodiodeModeTable OBJECT-TYPE
	SYNTAX  SEQUENCE OF Pm1004vencCtrllinePhotodiodeModeEntry
	MAX-ACCESS not-accessible
	STATUS current
	DESCRIPTION
        "
        List of pm1004vencCtrllinePhotodiodeMode
        Article
        "
	::= { pm1004vencCtrlLine 213 }


pm1004vencCtrllinePhotodiodeModeEntry OBJECT-TYPE
	SYNTAX Pm1004vencCtrllinePhotodiodeModeEntry
	MAX-ACCESS not-accessible
	STATUS current
	DESCRIPTION
        "
        Row definition for the pm1004vencCtrllinePhotodiodeMode
        table
        "
	INDEX   { pm1004vencCtrllinePhotodiodeModeIndex }
	::= { pm1004vencCtrllinePhotodiodeModeTable 1 }


Pm1004vencCtrllinePhotodiodeModeEntry ::=
	SEQUENCE {
	pm1004vencCtrllinePhotodiodeModeIndex
		INTEGER,
	pm1004vencCtrllinePhotodiodeModePortn
		Pm1004vencOtxMode
	}


pm1004vencCtrllinePhotodiodeModeIndex OBJECT-TYPE
	SYNTAX  INTEGER(0..128)
	MAX-ACCESS  read-only
	STATUS current
	DESCRIPTION
        "
        Index definition for the pm1004vencCtrllinePhotodiodeMode
        table
        "
	::= { pm1004vencCtrllinePhotodiodeModeEntry 1 }


pm1004vencCtrllinePhotodiodeModePortn OBJECT-TYPE
	SYNTAX  Pm1004vencOtxMode
	MAX-ACCESS read-write
	STATUS current
	DESCRIPTION
        "
        OTX TLH Rx Sens. Mode :This OID
        defines the Rx sensiblity mode
         of the Line OTX TLH  <Help>
         This control defines the receiver
        sensibility mode of the Line OTX
        TLH Laser (OTX60, OTX80 or Custom)
        "
	::= { pm1004vencCtrllinePhotodiodeModeEntry 2 }


--- *********************************************************
---     TABLE for the pm1004vencCtrllinePhotodiodeValue articles
--- *********************************************************

pm1004vencCtrllinePhotodiodeValueTable OBJECT-TYPE
	SYNTAX  SEQUENCE OF Pm1004vencCtrllinePhotodiodeValueEntry
	MAX-ACCESS not-accessible
	STATUS current
	DESCRIPTION
        "
        List of pm1004vencCtrllinePhotodiodeValue
        Article
        "
	::= { pm1004vencCtrlLine 214 }


pm1004vencCtrllinePhotodiodeValueEntry OBJECT-TYPE
	SYNTAX Pm1004vencCtrllinePhotodiodeValueEntry
	MAX-ACCESS not-accessible
	STATUS current
	DESCRIPTION
        "
        Row definition for the pm1004vencCtrllinePhotodiodeValue
        table
        "
	INDEX   { pm1004vencCtrllinePhotodiodeValueIndex }
	::= { pm1004vencCtrllinePhotodiodeValueTable 1 }


Pm1004vencCtrllinePhotodiodeValueEntry ::=
	SEQUENCE {
	pm1004vencCtrllinePhotodiodeValueIndex
		INTEGER,
	pm1004vencCtrllinePhotodiodeValuePortn
		Pm1004vencAdjustValue
	}


pm1004vencCtrllinePhotodiodeValueIndex OBJECT-TYPE
	SYNTAX  INTEGER(0..128)
	MAX-ACCESS  read-only
	STATUS current
	DESCRIPTION
        "
        Index definition for the pm1004vencCtrllinePhotodiodeValue
        table
        "
	::= { pm1004vencCtrllinePhotodiodeValueEntry 1 }


pm1004vencCtrllinePhotodiodeValuePortn OBJECT-TYPE
	SYNTAX  Pm1004vencAdjustValue
	MAX-ACCESS read-write
	STATUS current
	DESCRIPTION
        "
        OTX TLH Rx Sensibility :This OID
        sets the Rx sensibility of the
         Line OTX TLH (custom mode only)
         <Help>   This control defines
         the receiver sensibility value
        (only in Custom mode) of the Line
        OTX TLH Laser
        "
	::= { pm1004vencCtrllinePhotodiodeValueEntry 2 }


--- *********************************************************
---     TABLE for the pm1004vencCtrllinePowerLaser articles
--- *********************************************************

pm1004vencCtrllinePowerLaserTable OBJECT-TYPE
	SYNTAX  SEQUENCE OF Pm1004vencCtrllinePowerLaserEntry
	MAX-ACCESS not-accessible
	STATUS current
	DESCRIPTION
        "
        List of pm1004vencCtrllinePowerLaser
        Article
        "
	::= { pm1004vencCtrlLine 215 }


pm1004vencCtrllinePowerLaserEntry OBJECT-TYPE
	SYNTAX Pm1004vencCtrllinePowerLaserEntry
	MAX-ACCESS not-accessible
	STATUS current
	DESCRIPTION
        "
        Row definition for the pm1004vencCtrllinePowerLaser
        table
        "
	INDEX   { pm1004vencCtrllinePowerLaserIndex }
	::= { pm1004vencCtrllinePowerLaserTable 1 }


Pm1004vencCtrllinePowerLaserEntry ::=
	SEQUENCE {
	pm1004vencCtrllinePowerLaserIndex
		INTEGER,
	pm1004vencCtrllinePowerLaserPortn
		INTEGER
	}


pm1004vencCtrllinePowerLaserIndex OBJECT-TYPE
	SYNTAX  INTEGER(0..128)
	MAX-ACCESS  read-only
	STATUS current
	DESCRIPTION
        "
        Index definition for the pm1004vencCtrllinePowerLaser
        table
        "
	::= { pm1004vencCtrllinePowerLaserEntry 1 }


pm1004vencCtrllinePowerLaserPortn OBJECT-TYPE
	SYNTAX  INTEGER
	MAX-ACCESS read-write
	STATUS current
	DESCRIPTION
        "
        Line Laser Output Power [3-5]
         :This OID sets the output power
        value on the laser of the Line
         OTX TLH  (AV=Power*10+158)  (Unit
        = dBm)  <Help>   This control defines
        the start-up output power of the
        Line OTX TLH
        "
	::= { pm1004vencCtrllinePowerLaserEntry 2 }







--- *****************************************************
--- $$$$$$$$$$$$$$$$$$$$$$$$$$$$$$$$$$$$$$$$$$$$$$$$$$$$$
---     COUNTERS
--- $$$$$$$$$$$$$$$$$$$$$$$$$$$$$$$$$$$$$$$$$$$$$$$$$$$$$
--- *****************************************************



--- *********************************************************
---     TABLE for the pm1004vencCntdfrmB1ErrCnt articles
--- *********************************************************

pm1004vencCntdfrmB1ErrCntTable OBJECT-TYPE
	SYNTAX  SEQUENCE OF Pm1004vencCntdfrmB1ErrCntEntry
	MAX-ACCESS not-accessible
	STATUS current
	DESCRIPTION
        "
        List of pm1004vencCntdfrmB1ErrCnt
        Article
        "
	::= { pm1004vencCntLine 152 }


pm1004vencCntdfrmB1ErrCntEntry OBJECT-TYPE
	SYNTAX Pm1004vencCntdfrmB1ErrCntEntry
	MAX-ACCESS not-accessible
	STATUS current
	DESCRIPTION
        "
        Row definition for the pm1004vencCntdfrmB1ErrCnt
        table
        "
	INDEX   { pm1004vencCntdfrmB1ErrCntIndex }
	::= { pm1004vencCntdfrmB1ErrCntTable 1 }


Pm1004vencCntdfrmB1ErrCntEntry ::=
	SEQUENCE {
	pm1004vencCntdfrmB1ErrCntIndex
		INTEGER,
	pm1004vencCntdfrmB1ErrCntValuePortn
		Counter32,
	pm1004vencCntdfrmB1ErrCntErrorPortn
		EkiOnOff,
	pm1004vencCntdfrmB1ErrCntOverloadPortn
		EkiOnOff
	}


pm1004vencCntdfrmB1ErrCntIndex OBJECT-TYPE
	SYNTAX  INTEGER(0..128)
	MAX-ACCESS  read-only
	STATUS current
	DESCRIPTION
        "
        Index definition for the pm1004vencCntdfrmB1ErrCnt
        table
        "
	::= { pm1004vencCntdfrmB1ErrCntEntry 1 }


pm1004vencCntdfrmB1ErrCntValuePortn OBJECT-TYPE
	SYNTAX  Counter32
	MAX-ACCESS read-only
	STATUS current
	DESCRIPTION
        "
        Line Input SM-BIP8 Errors :This
        counter is incremented each time
        a B1 error is detected on the Deframer
        input stream.  <Help>  This counter
        gives the number of B1 errors on
        the line port
        "
	::= { pm1004vencCntdfrmB1ErrCntEntry 2 }


pm1004vencCntdfrmB1ErrCntErrorPortn OBJECT-TYPE
	SYNTAX  EkiOnOff
	MAX-ACCESS read-only
	STATUS current
	DESCRIPTION
        "
        Line Counter Error :This OID when
        set indicates the B1 error counter
        value is invalid on Port
        "
	::= { pm1004vencCntdfrmB1ErrCntEntry 3 }


pm1004vencCntdfrmB1ErrCntOverloadPortn OBJECT-TYPE
	SYNTAX  EkiOnOff
	MAX-ACCESS read-only
	STATUS current
	DESCRIPTION
        "
        Line Counter Overload :This OID
        when set indicates a B1 error counter
        overload on Port
        "
	::= { pm1004vencCntdfrmB1ErrCntEntry 4 }


--- *********************************************************
---     TABLE for the pm1004vencCntdfrmTimCnt articles
--- *********************************************************

pm1004vencCntdfrmTimCntTable OBJECT-TYPE
	SYNTAX  SEQUENCE OF Pm1004vencCntdfrmTimCntEntry
	MAX-ACCESS not-accessible
	STATUS current
	DESCRIPTION
        "
        List of pm1004vencCntdfrmTimCnt
        Article
        "
	::= { pm1004vencCntLine 153 }


pm1004vencCntdfrmTimCntEntry OBJECT-TYPE
	SYNTAX Pm1004vencCntdfrmTimCntEntry
	MAX-ACCESS not-accessible
	STATUS current
	DESCRIPTION
        "
        Row definition for the pm1004vencCntdfrmTimCnt
        table
        "
	INDEX   { pm1004vencCntdfrmTimCntIndex }
	::= { pm1004vencCntdfrmTimCntTable 1 }


Pm1004vencCntdfrmTimCntEntry ::=
	SEQUENCE {
	pm1004vencCntdfrmTimCntIndex
		INTEGER,
	pm1004vencCntdfrmTimCntValuePortn
		Counter32,
	pm1004vencCntdfrmTimCntErrorPortn
		EkiOnOff,
	pm1004vencCntdfrmTimCntOverloadPortn
		EkiOnOff
	}


pm1004vencCntdfrmTimCntIndex OBJECT-TYPE
	SYNTAX  INTEGER(0..128)
	MAX-ACCESS  read-only
	STATUS current
	DESCRIPTION
        "
        Index definition for the pm1004vencCntdfrmTimCnt
        table
        "
	::= { pm1004vencCntdfrmTimCntEntry 1 }


pm1004vencCntdfrmTimCntValuePortn OBJECT-TYPE
	SYNTAX  Counter32
	MAX-ACCESS read-only
	STATUS current
	DESCRIPTION
        "
        Line Timer Counter :This is the
        timing counter dedicated to the
        downstream deframer counters. It
        is incremented every 125 us.
        "
	::= { pm1004vencCntdfrmTimCntEntry 2 }


pm1004vencCntdfrmTimCntErrorPortn OBJECT-TYPE
	SYNTAX  EkiOnOff
	MAX-ACCESS read-only
	STATUS current
	DESCRIPTION
        "
        Line Counter Error :This OID when
        set indicates the deframer timer
        counter value is invalid on Port
        "
	::= { pm1004vencCntdfrmTimCntEntry 3 }


pm1004vencCntdfrmTimCntOverloadPortn OBJECT-TYPE
	SYNTAX  EkiOnOff
	MAX-ACCESS read-only
	STATUS current
	DESCRIPTION
        "
        Line Counter Overload :This OID
        when set indicates a deframer timer
        counter overload on Port
        "
	::= { pm1004vencCntdfrmTimCntEntry 4 }


pm1004vencCntCountersReset  OBJECT-TYPE
	SYNTAX EkiOnOff
	MAX-ACCESS read-write
	STATUS current
	DESCRIPTION
	"Counters Reset:This OID resets and restarts all the counters"
	::= { pm1004venccounters  259 }

pm1004vencCntCountersStop  OBJECT-TYPE
	SYNTAX EkiOnOff
	MAX-ACCESS read-write
	STATUS current
	DESCRIPTION
	"Counters stop:This OID stops all the counters"
	::= { pm1004venccounters 260 }






--- *****************************************************
--- $$$$$$$$$$$$$$$$$$$$$$$$$$$$$$$$$$$$$$$$$$$$$$$$$$$$$
---     RMON
--- $$$$$$$$$$$$$$$$$$$$$$$$$$$$$$$$$$$$$$$$$$$$$$$$$$$$$
--- *****************************************************



--- *********************************************************
---     TABLE for the pm1004vencMonupRmonByteCnt articles
--- *********************************************************

pm1004vencMonupRmonByteCntTable OBJECT-TYPE
	SYNTAX  SEQUENCE OF Pm1004vencMonupRmonByteCntEntry
	MAX-ACCESS not-accessible
	STATUS current
	DESCRIPTION
        "
        List of pm1004vencMonupRmonByteCnt
        Article
        "
	::= { pm1004vencMonClientRmonCounter 16 }


pm1004vencMonupRmonByteCntEntry OBJECT-TYPE
	SYNTAX Pm1004vencMonupRmonByteCntEntry
	MAX-ACCESS not-accessible
	STATUS current
	DESCRIPTION
        "
        Row definition for the pm1004vencMonupRmonByteCnt
        table
        "
	INDEX   { pm1004vencMonupRmonByteCntIndex }
	::= { pm1004vencMonupRmonByteCntTable 1 }


Pm1004vencMonupRmonByteCntEntry ::=
	SEQUENCE {
	pm1004vencMonupRmonByteCntIndex
		INTEGER,
	pm1004vencMonupRmonByteCntValuePortn
		Counter64,
	pm1004vencMonupRmonByteCntErrorPortn
		EkiOnOff,
	pm1004vencMonupRmonByteCntOverloadPortn
		EkiOnOff
	}


pm1004vencMonupRmonByteCntIndex OBJECT-TYPE
	SYNTAX  INTEGER(0..128)
	MAX-ACCESS  read-only
	STATUS current
	DESCRIPTION
        "
        Index definition for the pm1004vencMonupRmonByteCnt
        table
        "
	::= { pm1004vencMonupRmonByteCntEntry 1 }


pm1004vencMonupRmonByteCntValuePortn OBJECT-TYPE
	SYNTAX  Counter64
	MAX-ACCESS read-only
	STATUS current
	DESCRIPTION
        "
        Client Input Bytes :This counter
        is increased each time a data byte
        is received on the client port
          <Help>  This counter gives the
        number of bytes received on the
        client port
        "
	::= { pm1004vencMonupRmonByteCntEntry 2 }


pm1004vencMonupRmonByteCntErrorPortn OBJECT-TYPE
	SYNTAX  EkiOnOff
	MAX-ACCESS read-only
	STATUS current
	DESCRIPTION
        "
        Bytes Counter Error :This OID
         when set indicates the Bytes counter
        value is invalid on clinet port
        "
	::= { pm1004vencMonupRmonByteCntEntry 3 }


pm1004vencMonupRmonByteCntOverloadPortn OBJECT-TYPE
	SYNTAX  EkiOnOff
	MAX-ACCESS read-only
	STATUS current
	DESCRIPTION
        "
        Bytes Counter Overload :This OID
        when set indicates a Bytes counter
        overload on client port
        "
	::= { pm1004vencMonupRmonByteCntEntry 4 }


--- *********************************************************
---     TABLE for the pm1004vencMonupRmonCrcErrorCnt articles
--- *********************************************************

pm1004vencMonupRmonCrcErrorCntTable OBJECT-TYPE
	SYNTAX  SEQUENCE OF Pm1004vencMonupRmonCrcErrorCntEntry
	MAX-ACCESS not-accessible
	STATUS current
	DESCRIPTION
        "
        List of pm1004vencMonupRmonCrcErrorCnt
        Article
        "
	::= { pm1004vencMonClientRmonCounter 24 }


pm1004vencMonupRmonCrcErrorCntEntry OBJECT-TYPE
	SYNTAX Pm1004vencMonupRmonCrcErrorCntEntry
	MAX-ACCESS not-accessible
	STATUS current
	DESCRIPTION
        "
        Row definition for the pm1004vencMonupRmonCrcErrorCnt
        table
        "
	INDEX   { pm1004vencMonupRmonCrcErrorCntIndex }
	::= { pm1004vencMonupRmonCrcErrorCntTable 1 }


Pm1004vencMonupRmonCrcErrorCntEntry ::=
	SEQUENCE {
	pm1004vencMonupRmonCrcErrorCntIndex
		INTEGER,
	pm1004vencMonupRmonCrcErrorCntValuePortn
		Counter64,
	pm1004vencMonupRmonCrcErrorCntErrorPortn
		EkiOnOff,
	pm1004vencMonupRmonCrcErrorCntOverloadPortn
		EkiOnOff
	}


pm1004vencMonupRmonCrcErrorCntIndex OBJECT-TYPE
	SYNTAX  INTEGER(0..128)
	MAX-ACCESS  read-only
	STATUS current
	DESCRIPTION
        "
        Index definition for the pm1004vencMonupRmonCrcErrorCnt
        table
        "
	::= { pm1004vencMonupRmonCrcErrorCntEntry 1 }


pm1004vencMonupRmonCrcErrorCntValuePortn OBJECT-TYPE
	SYNTAX  Counter64
	MAX-ACCESS read-only
	STATUS current
	DESCRIPTION
        "
        Client Input CRC Errors :This
         counter is increased each time
        a CRC error is detected on the
         client port  <Help>  This counter
        gives the number of CRC Errors
         received on the client port
        "
	::= { pm1004vencMonupRmonCrcErrorCntEntry 2 }


pm1004vencMonupRmonCrcErrorCntErrorPortn OBJECT-TYPE
	SYNTAX  EkiOnOff
	MAX-ACCESS read-only
	STATUS current
	DESCRIPTION
        "
        CRC Errors Counter Error :This
        OID when set indicates the CRC
         Errors counter value is invalid
        on clinet port
        "
	::= { pm1004vencMonupRmonCrcErrorCntEntry 3 }


pm1004vencMonupRmonCrcErrorCntOverloadPortn OBJECT-TYPE
	SYNTAX  EkiOnOff
	MAX-ACCESS read-only
	STATUS current
	DESCRIPTION
        "
        CRC Errors Counter Overload :This
        OID when set indicates a CRC Errors
        counter overload on client port
        "
	::= { pm1004vencMonupRmonCrcErrorCntEntry 4 }


--- *********************************************************
---     TABLE for the pm1004vencMonupRmonPacketsCnt articles
--- *********************************************************

pm1004vencMonupRmonPacketsCntTable OBJECT-TYPE
	SYNTAX  SEQUENCE OF Pm1004vencMonupRmonPacketsCntEntry
	MAX-ACCESS not-accessible
	STATUS current
	DESCRIPTION
        "
        List of pm1004vencMonupRmonPacketsCnt
        Article
        "
	::= { pm1004vencMonClientRmonCounter 32 }


pm1004vencMonupRmonPacketsCntEntry OBJECT-TYPE
	SYNTAX Pm1004vencMonupRmonPacketsCntEntry
	MAX-ACCESS not-accessible
	STATUS current
	DESCRIPTION
        "
        Row definition for the pm1004vencMonupRmonPacketsCnt
        table
        "
	INDEX   { pm1004vencMonupRmonPacketsCntIndex }
	::= { pm1004vencMonupRmonPacketsCntTable 1 }


Pm1004vencMonupRmonPacketsCntEntry ::=
	SEQUENCE {
	pm1004vencMonupRmonPacketsCntIndex
		INTEGER,
	pm1004vencMonupRmonPacketsCntValuePortn
		Counter64,
	pm1004vencMonupRmonPacketsCntErrorPortn
		EkiOnOff,
	pm1004vencMonupRmonPacketsCntOverloadPortn
		EkiOnOff
	}


pm1004vencMonupRmonPacketsCntIndex OBJECT-TYPE
	SYNTAX  INTEGER(0..128)
	MAX-ACCESS  read-only
	STATUS current
	DESCRIPTION
        "
        Index definition for the pm1004vencMonupRmonPacketsCnt
        table
        "
	::= { pm1004vencMonupRmonPacketsCntEntry 1 }


pm1004vencMonupRmonPacketsCntValuePortn OBJECT-TYPE
	SYNTAX  Counter64
	MAX-ACCESS read-only
	STATUS current
	DESCRIPTION
        "
        Client Input Packets :This counter
        is increased each time a packet
        is received on the client port
          <Help>  This counter gives the
        number of packets received on the
        client port
        "
	::= { pm1004vencMonupRmonPacketsCntEntry 2 }


pm1004vencMonupRmonPacketsCntErrorPortn OBJECT-TYPE
	SYNTAX  EkiOnOff
	MAX-ACCESS read-only
	STATUS current
	DESCRIPTION
        "
        Packets Counter Error :This OID
        when set indicates the Packets
         counter value is invalid on clinet
        port
        "
	::= { pm1004vencMonupRmonPacketsCntEntry 3 }


pm1004vencMonupRmonPacketsCntOverloadPortn OBJECT-TYPE
	SYNTAX  EkiOnOff
	MAX-ACCESS read-only
	STATUS current
	DESCRIPTION
        "
        Packets Counter Overload :This
        OID when set indicates a Packets
        counter overload on client port
        "
	::= { pm1004vencMonupRmonPacketsCntEntry 4 }


--- *********************************************************
---     TABLE for the pm1004vencMonupRmonBroadcastCnt articles
--- *********************************************************

pm1004vencMonupRmonBroadcastCntTable OBJECT-TYPE
	SYNTAX  SEQUENCE OF Pm1004vencMonupRmonBroadcastCntEntry
	MAX-ACCESS not-accessible
	STATUS current
	DESCRIPTION
        "
        List of pm1004vencMonupRmonBroadcastCnt
        Article
        "
	::= { pm1004vencMonClientRmonCounter 40 }


pm1004vencMonupRmonBroadcastCntEntry OBJECT-TYPE
	SYNTAX Pm1004vencMonupRmonBroadcastCntEntry
	MAX-ACCESS not-accessible
	STATUS current
	DESCRIPTION
        "
        Row definition for the pm1004vencMonupRmonBroadcastCnt
        table
        "
	INDEX   { pm1004vencMonupRmonBroadcastCntIndex }
	::= { pm1004vencMonupRmonBroadcastCntTable 1 }


Pm1004vencMonupRmonBroadcastCntEntry ::=
	SEQUENCE {
	pm1004vencMonupRmonBroadcastCntIndex
		INTEGER,
	pm1004vencMonupRmonBroadcastCntValuePortn
		Counter64,
	pm1004vencMonupRmonBroadcastCntErrorPortn
		EkiOnOff,
	pm1004vencMonupRmonBroadcastCntOverloadPortn
		EkiOnOff
	}


pm1004vencMonupRmonBroadcastCntIndex OBJECT-TYPE
	SYNTAX  INTEGER(0..128)
	MAX-ACCESS  read-only
	STATUS current
	DESCRIPTION
        "
        Index definition for the pm1004vencMonupRmonBroadcastCnt
        table
        "
	::= { pm1004vencMonupRmonBroadcastCntEntry 1 }


pm1004vencMonupRmonBroadcastCntValuePortn OBJECT-TYPE
	SYNTAX  Counter64
	MAX-ACCESS read-only
	STATUS current
	DESCRIPTION
        "
        Client Input Broadcast Packets
        :This counter is increased each
        time a broadcast packet is received
        on the client port  <Help>  This
        counter gives the number of Broadcast
        packets received on the client
         port
        "
	::= { pm1004vencMonupRmonBroadcastCntEntry 2 }


pm1004vencMonupRmonBroadcastCntErrorPortn OBJECT-TYPE
	SYNTAX  EkiOnOff
	MAX-ACCESS read-only
	STATUS current
	DESCRIPTION
        "
        Broadcast Counter Error :This
         OID when set indicates the Broadcast
        counter value is invalid on clinet
        port
        "
	::= { pm1004vencMonupRmonBroadcastCntEntry 3 }


pm1004vencMonupRmonBroadcastCntOverloadPortn OBJECT-TYPE
	SYNTAX  EkiOnOff
	MAX-ACCESS read-only
	STATUS current
	DESCRIPTION
        "
        Broadcast Counter Overload :This
        OID when set indicates a Broadcast
        counter overload on client port
        "
	::= { pm1004vencMonupRmonBroadcastCntEntry 4 }


--- *********************************************************
---     TABLE for the pm1004vencMonupRmonMulticastCnt articles
--- *********************************************************

pm1004vencMonupRmonMulticastCntTable OBJECT-TYPE
	SYNTAX  SEQUENCE OF Pm1004vencMonupRmonMulticastCntEntry
	MAX-ACCESS not-accessible
	STATUS current
	DESCRIPTION
        "
        List of pm1004vencMonupRmonMulticastCnt
        Article
        "
	::= { pm1004vencMonClientRmonCounter 48 }


pm1004vencMonupRmonMulticastCntEntry OBJECT-TYPE
	SYNTAX Pm1004vencMonupRmonMulticastCntEntry
	MAX-ACCESS not-accessible
	STATUS current
	DESCRIPTION
        "
        Row definition for the pm1004vencMonupRmonMulticastCnt
        table
        "
	INDEX   { pm1004vencMonupRmonMulticastCntIndex }
	::= { pm1004vencMonupRmonMulticastCntTable 1 }


Pm1004vencMonupRmonMulticastCntEntry ::=
	SEQUENCE {
	pm1004vencMonupRmonMulticastCntIndex
		INTEGER,
	pm1004vencMonupRmonMulticastCntValuePortn
		Counter64,
	pm1004vencMonupRmonMulticastCntErrorPortn
		EkiOnOff,
	pm1004vencMonupRmonMulticastCntOverloadPortn
		EkiOnOff
	}


pm1004vencMonupRmonMulticastCntIndex OBJECT-TYPE
	SYNTAX  INTEGER(0..128)
	MAX-ACCESS  read-only
	STATUS current
	DESCRIPTION
        "
        Index definition for the pm1004vencMonupRmonMulticastCnt
        table
        "
	::= { pm1004vencMonupRmonMulticastCntEntry 1 }


pm1004vencMonupRmonMulticastCntValuePortn OBJECT-TYPE
	SYNTAX  Counter64
	MAX-ACCESS read-only
	STATUS current
	DESCRIPTION
        "
        Client Input Multicast Packets
        :This counter is increased each
        time a Multicast packet is received
        on the client port  <Help>  This
        counter gives the number of Multicast
        packets received on the client
         port
        "
	::= { pm1004vencMonupRmonMulticastCntEntry 2 }


pm1004vencMonupRmonMulticastCntErrorPortn OBJECT-TYPE
	SYNTAX  EkiOnOff
	MAX-ACCESS read-only
	STATUS current
	DESCRIPTION
        "
        Multicast Counter Error :This
         OID when set indicates the Multicast
        counter value is invalid on clinet
        port
        "
	::= { pm1004vencMonupRmonMulticastCntEntry 3 }


pm1004vencMonupRmonMulticastCntOverloadPortn OBJECT-TYPE
	SYNTAX  EkiOnOff
	MAX-ACCESS read-only
	STATUS current
	DESCRIPTION
        "
        Multicast Counter Overload :This
        OID when set indicates a Multicast
        counter overload on client port
        "
	::= { pm1004vencMonupRmonMulticastCntEntry 4 }


--- *********************************************************
---     TABLE for the pm1004vencMonupLineRmonByteCnt articles
--- *********************************************************

pm1004vencMonupLineRmonByteCntTable OBJECT-TYPE
	SYNTAX  SEQUENCE OF Pm1004vencMonupLineRmonByteCntEntry
	MAX-ACCESS not-accessible
	STATUS current
	DESCRIPTION
        "
        List of pm1004vencMonupLineRmonByteCnt
        Article
        "
	::= { pm1004vencMonClientRmonCounter 208 }


pm1004vencMonupLineRmonByteCntEntry OBJECT-TYPE
	SYNTAX Pm1004vencMonupLineRmonByteCntEntry
	MAX-ACCESS not-accessible
	STATUS current
	DESCRIPTION
        "
        Row definition for the pm1004vencMonupLineRmonByteCnt
        table
        "
	INDEX   { pm1004vencMonupLineRmonByteCntIndex }
	::= { pm1004vencMonupLineRmonByteCntTable 1 }


Pm1004vencMonupLineRmonByteCntEntry ::=
	SEQUENCE {
	pm1004vencMonupLineRmonByteCntIndex
		INTEGER,
	pm1004vencMonupLineRmonByteCntValuePortn
		Counter64,
	pm1004vencMonupLineRmonByteCntErrorPortn
		EkiOnOff,
	pm1004vencMonupLineRmonByteCntOverloadPortn
		EkiOnOff
	}


pm1004vencMonupLineRmonByteCntIndex OBJECT-TYPE
	SYNTAX  INTEGER(0..128)
	MAX-ACCESS  read-only
	STATUS current
	DESCRIPTION
        "
        Index definition for the pm1004vencMonupLineRmonByteCnt
        table
        "
	::= { pm1004vencMonupLineRmonByteCntEntry 1 }


pm1004vencMonupLineRmonByteCntValuePortn OBJECT-TYPE
	SYNTAX  Counter64
	MAX-ACCESS read-only
	STATUS current
	DESCRIPTION
        "
        Line Input Bytes :This counter
        is increased each time a data byte
        is received on the Line port  <Help>
         This counter gives the number
         of bytes received on the Line
         port
        "
	::= { pm1004vencMonupLineRmonByteCntEntry 2 }


pm1004vencMonupLineRmonByteCntErrorPortn OBJECT-TYPE
	SYNTAX  EkiOnOff
	MAX-ACCESS read-only
	STATUS current
	DESCRIPTION
        "
        Bytes Counter Error :This OID
         when set indicates the Bytes counter
        value is invalid on line port
        "
	::= { pm1004vencMonupLineRmonByteCntEntry 3 }


pm1004vencMonupLineRmonByteCntOverloadPortn OBJECT-TYPE
	SYNTAX  EkiOnOff
	MAX-ACCESS read-only
	STATUS current
	DESCRIPTION
        "
        Bytes Counter Overload :This OID
        when set indicates a Bytes counter
        overload on line port
        "
	::= { pm1004vencMonupLineRmonByteCntEntry 4 }


--- *********************************************************
---     TABLE for the pm1004vencMonupLineRmonCrcErrorCnt articles
--- *********************************************************

pm1004vencMonupLineRmonCrcErrorCntTable OBJECT-TYPE
	SYNTAX  SEQUENCE OF Pm1004vencMonupLineRmonCrcErrorCntEntry
	MAX-ACCESS not-accessible
	STATUS current
	DESCRIPTION
        "
        List of pm1004vencMonupLineRmonCrcErrorCnt
        Article
        "
	::= { pm1004vencMonClientRmonCounter 209 }


pm1004vencMonupLineRmonCrcErrorCntEntry OBJECT-TYPE
	SYNTAX Pm1004vencMonupLineRmonCrcErrorCntEntry
	MAX-ACCESS not-accessible
	STATUS current
	DESCRIPTION
        "
        Row definition for the pm1004vencMonupLineRmonCrcErrorCnt
        table
        "
	INDEX   { pm1004vencMonupLineRmonCrcErrorCntIndex }
	::= { pm1004vencMonupLineRmonCrcErrorCntTable 1 }


Pm1004vencMonupLineRmonCrcErrorCntEntry ::=
	SEQUENCE {
	pm1004vencMonupLineRmonCrcErrorCntIndex
		INTEGER,
	pm1004vencMonupLineRmonCrcErrorCntValuePortn
		Counter64,
	pm1004vencMonupLineRmonCrcErrorCntErrorPortn
		EkiOnOff,
	pm1004vencMonupLineRmonCrcErrorCntOverloadPortn
		EkiOnOff
	}


pm1004vencMonupLineRmonCrcErrorCntIndex OBJECT-TYPE
	SYNTAX  INTEGER(0..128)
	MAX-ACCESS  read-only
	STATUS current
	DESCRIPTION
        "
        Index definition for the pm1004vencMonupLineRmonCrcErrorCnt
        table
        "
	::= { pm1004vencMonupLineRmonCrcErrorCntEntry 1 }


pm1004vencMonupLineRmonCrcErrorCntValuePortn OBJECT-TYPE
	SYNTAX  Counter64
	MAX-ACCESS read-only
	STATUS current
	DESCRIPTION
        "
        Line Input CRC Errors :This counter
        is increased each time a CRC error
        is detected on the Line port  <Help>
         This counter gives the number
         of CRC Errors received on the
         Line port
        "
	::= { pm1004vencMonupLineRmonCrcErrorCntEntry 2 }


pm1004vencMonupLineRmonCrcErrorCntErrorPortn OBJECT-TYPE
	SYNTAX  EkiOnOff
	MAX-ACCESS read-only
	STATUS current
	DESCRIPTION
        "
        CRC Errors Counter Error :This
        OID when set indicates the CRC
         Errors counter value is invalid
        on line port
        "
	::= { pm1004vencMonupLineRmonCrcErrorCntEntry 3 }


pm1004vencMonupLineRmonCrcErrorCntOverloadPortn OBJECT-TYPE
	SYNTAX  EkiOnOff
	MAX-ACCESS read-only
	STATUS current
	DESCRIPTION
        "
        CRC Errors Counter Overload :This
        OID when set indicates a CRC Errors
        counter overload on line port
        "
	::= { pm1004vencMonupLineRmonCrcErrorCntEntry 4 }


--- *********************************************************
---     TABLE for the pm1004vencMonupLineRmonPacketsCnt articles
--- *********************************************************

pm1004vencMonupLineRmonPacketsCntTable OBJECT-TYPE
	SYNTAX  SEQUENCE OF Pm1004vencMonupLineRmonPacketsCntEntry
	MAX-ACCESS not-accessible
	STATUS current
	DESCRIPTION
        "
        List of pm1004vencMonupLineRmonPacketsCnt
        Article
        "
	::= { pm1004vencMonClientRmonCounter 210 }


pm1004vencMonupLineRmonPacketsCntEntry OBJECT-TYPE
	SYNTAX Pm1004vencMonupLineRmonPacketsCntEntry
	MAX-ACCESS not-accessible
	STATUS current
	DESCRIPTION
        "
        Row definition for the pm1004vencMonupLineRmonPacketsCnt
        table
        "
	INDEX   { pm1004vencMonupLineRmonPacketsCntIndex }
	::= { pm1004vencMonupLineRmonPacketsCntTable 1 }


Pm1004vencMonupLineRmonPacketsCntEntry ::=
	SEQUENCE {
	pm1004vencMonupLineRmonPacketsCntIndex
		INTEGER,
	pm1004vencMonupLineRmonPacketsCntValuePortn
		Counter64,
	pm1004vencMonupLineRmonPacketsCntErrorPortn
		EkiOnOff,
	pm1004vencMonupLineRmonPacketsCntOverloadPortn
		EkiOnOff
	}


pm1004vencMonupLineRmonPacketsCntIndex OBJECT-TYPE
	SYNTAX  INTEGER(0..128)
	MAX-ACCESS  read-only
	STATUS current
	DESCRIPTION
        "
        Index definition for the pm1004vencMonupLineRmonPacketsCnt
        table
        "
	::= { pm1004vencMonupLineRmonPacketsCntEntry 1 }


pm1004vencMonupLineRmonPacketsCntValuePortn OBJECT-TYPE
	SYNTAX  Counter64
	MAX-ACCESS read-only
	STATUS current
	DESCRIPTION
        "
        Line Input Packets :This counter
        is increased each time a packet
        is received on the Line port  <Help>
         This counter gives the number
         of packets received on the Line
        port
        "
	::= { pm1004vencMonupLineRmonPacketsCntEntry 2 }


pm1004vencMonupLineRmonPacketsCntErrorPortn OBJECT-TYPE
	SYNTAX  EkiOnOff
	MAX-ACCESS read-only
	STATUS current
	DESCRIPTION
        "
        Packets Counter Error :This OID
        when set indicates the Packets
         counter value is invalid on client
        port
        "
	::= { pm1004vencMonupLineRmonPacketsCntEntry 3 }


pm1004vencMonupLineRmonPacketsCntOverloadPortn OBJECT-TYPE
	SYNTAX  EkiOnOff
	MAX-ACCESS read-only
	STATUS current
	DESCRIPTION
        "
        Packets Counter Overload :This
        OID when set indicates a Packets
        counter overload on line port
        "
	::= { pm1004vencMonupLineRmonPacketsCntEntry 4 }


pm1004vencMonCountersReset  OBJECT-TYPE
	SYNTAX EkiOnOff
	MAX-ACCESS read-write
	STATUS current
	DESCRIPTION
	"RMON Counters Reset:This OID resets and restarts all the RMON counters"
	::= { pm1004vencMonRmon   359 }

pm1004vencMonCountersStop  OBJECT-TYPE
	SYNTAX EkiOnOff
	MAX-ACCESS read-write
	STATUS current
	DESCRIPTION
	"RMON Counters stop:This OID stops all the RMON counters"
	::= { pm1004vencMonRmon  360 }






--- *****************************************************
--- $$$$$$$$$$$$$$$$$$$$$$$$$$$$$$$$$$$$$$$$$$$$$$$$$$$$$
---     MEASURES
--- $$$$$$$$$$$$$$$$$$$$$$$$$$$$$$$$$$$$$$$$$$$$$$$$$$$$$
--- *****************************************************



pm1004vencMesrsynth0 OBJECT-TYPE
	  SYNTAX EkiMeasureType
	  MAX-ACCESS read-only
	  STATUS deprecated
	  DESCRIPTION
        "
        Not Used :This OID gives the unit
        used on AUX1 measurement of XFP#1
         (Unit = )
        "
	  ::= { pm1004vencMesrOther 0 }



pm1004vencMesrsynth1 OBJECT-TYPE
	  SYNTAX EkiMeasureType
	  MAX-ACCESS read-only
	  STATUS deprecated
	  DESCRIPTION
        "
        Not Used :This OID gives the unit
        used on AUX2 measurement of XFP#1
         (Unit = )
        "
	  ::= { pm1004vencMesrOther 1 }



--- *********************************************************
---     TABLE for the pm1004vencMesrxfp1LxModTempMeas articles
--- *********************************************************

pm1004vencMesrxfp1LxModTempMeasTable OBJECT-TYPE
	SYNTAX  SEQUENCE OF Pm1004vencMesrxfp1LxModTempMeasEntry
	MAX-ACCESS not-accessible
	STATUS current
	DESCRIPTION
        "
        List of pm1004vencMesrxfp1LxModTempMeas
        Article
        "
	::= { pm1004vencMesrLine 208 }


pm1004vencMesrxfp1LxModTempMeasEntry OBJECT-TYPE
	SYNTAX Pm1004vencMesrxfp1LxModTempMeasEntry
	MAX-ACCESS not-accessible
	STATUS current
	DESCRIPTION
        "
        Row definition for the pm1004vencMesrxfp1LxModTempMeas
        table
        "
	INDEX   { pm1004vencMesrxfp1LxModTempMeasIndex }
	::= { pm1004vencMesrxfp1LxModTempMeasTable 1 }


Pm1004vencMesrxfp1LxModTempMeasEntry ::=
	SEQUENCE {
	pm1004vencMesrxfp1LxModTempMeasIndex
		INTEGER,
	pm1004vencMesrxfp1LxModTempMeasPortn
		INTEGER
	}


pm1004vencMesrxfp1LxModTempMeasIndex OBJECT-TYPE
	SYNTAX  INTEGER(0..128)
	MAX-ACCESS  read-only
	STATUS current
	DESCRIPTION
        "
        Index definition for the pm1004vencMesrxfp1LxModTempMeas
        table
        "
	::= { pm1004vencMesrxfp1LxModTempMeasEntry 1 }


pm1004vencMesrxfp1LxModTempMeasPortn OBJECT-TYPE
	SYNTAX  INTEGER (0..65535)
	MAX-ACCESS read-only
	STATUS current
	DESCRIPTION
        "
        Line Optical Module Temperature
        :This OID gives the temperature
        of the XFP or OTX plugged in line#n,
        read from the DDM (Digital Diagnostic
        Monitoring) (Temperature = AV/256)
        (Unit = C)  <Help>  This measure
        gives the temperature of the line
        transceiver
        "
	::= { pm1004vencMesrxfp1LxModTempMeasEntry 2 }


--- *********************************************************
---     TABLE for the pm1004vencMesrxfp1Reserved articles
--- *********************************************************

pm1004vencMesrxfp1ReservedTable OBJECT-TYPE
	SYNTAX  SEQUENCE OF Pm1004vencMesrxfp1ReservedEntry
	MAX-ACCESS not-accessible
	STATUS deprecated
	DESCRIPTION
        "
        List of pm1004vencMesrxfp1Reserved
        Article
        "
	::= { pm1004vencMesrLine 209 }


pm1004vencMesrxfp1ReservedEntry OBJECT-TYPE
	SYNTAX Pm1004vencMesrxfp1ReservedEntry
	MAX-ACCESS not-accessible
	STATUS deprecated
	DESCRIPTION
        "
        Row definition for the pm1004vencMesrxfp1Reserved
        table
        "
	INDEX   { pm1004vencMesrxfp1ReservedIndex }
	::= { pm1004vencMesrxfp1ReservedTable 1 }


Pm1004vencMesrxfp1ReservedEntry ::=
	SEQUENCE {
	pm1004vencMesrxfp1ReservedIndex
		INTEGER,
	pm1004vencMesrxfp1ReservedPortn
		INTEGER
	}


pm1004vencMesrxfp1ReservedIndex OBJECT-TYPE
	SYNTAX  INTEGER(0..128)
	MAX-ACCESS  read-only
	STATUS deprecated
	DESCRIPTION
        "
        Index definition for the pm1004vencMesrxfp1Reserved
        table
        "
	::= { pm1004vencMesrxfp1ReservedEntry 1 }


pm1004vencMesrxfp1ReservedPortn OBJECT-TYPE
	SYNTAX  INTEGER (0..65535)
	MAX-ACCESS read-only
	STATUS deprecated
	DESCRIPTION
        "
        Not Used :Reserved
        "
	::= { pm1004vencMesrxfp1ReservedEntry 2 }


--- *********************************************************
---     TABLE for the pm1004vencMesrxfp1LoBiasCurrentMeas articles
--- *********************************************************

pm1004vencMesrxfp1LoBiasCurrentMeasTable OBJECT-TYPE
	SYNTAX  SEQUENCE OF Pm1004vencMesrxfp1LoBiasCurrentMeasEntry
	MAX-ACCESS not-accessible
	STATUS current
	DESCRIPTION
        "
        List of pm1004vencMesrxfp1LoBiasCurrentMeas
        Article
        "
	::= { pm1004vencMesrLine 210 }


pm1004vencMesrxfp1LoBiasCurrentMeasEntry OBJECT-TYPE
	SYNTAX Pm1004vencMesrxfp1LoBiasCurrentMeasEntry
	MAX-ACCESS not-accessible
	STATUS current
	DESCRIPTION
        "
        Row definition for the pm1004vencMesrxfp1LoBiasCurrentMeas
        table
        "
	INDEX   { pm1004vencMesrxfp1LoBiasCurrentMeasIndex }
	::= { pm1004vencMesrxfp1LoBiasCurrentMeasTable 1 }


Pm1004vencMesrxfp1LoBiasCurrentMeasEntry ::=
	SEQUENCE {
	pm1004vencMesrxfp1LoBiasCurrentMeasIndex
		INTEGER,
	pm1004vencMesrxfp1LoBiasCurrentMeasPortn
		INTEGER
	}


pm1004vencMesrxfp1LoBiasCurrentMeasIndex OBJECT-TYPE
	SYNTAX  INTEGER(0..128)
	MAX-ACCESS  read-only
	STATUS current
	DESCRIPTION
        "
        Index definition for the pm1004vencMesrxfp1LoBiasCurrentMeas
        table
        "
	::= { pm1004vencMesrxfp1LoBiasCurrentMeasEntry 1 }


pm1004vencMesrxfp1LoBiasCurrentMeasPortn OBJECT-TYPE
	SYNTAX  INTEGER (0..65535)
	MAX-ACCESS read-only
	STATUS current
	DESCRIPTION
        "
        Line Optical Module Laser Bias
        :This OID gives the bias value
         of the XFP or OTX plugged in line
        #n, read from the DDM (Digital
         Diagnostic Monitoring) (Bias =
        AV/500) (Unit = mA)  <Help>  This
        measure gives the bias of the line
        transceiver
        "
	::= { pm1004vencMesrxfp1LoBiasCurrentMeasEntry 2 }


--- *********************************************************
---     TABLE for the pm1004vencMesrxfp1LoTxPowerMeas articles
--- *********************************************************

pm1004vencMesrxfp1LoTxPowerMeasTable OBJECT-TYPE
	SYNTAX  SEQUENCE OF Pm1004vencMesrxfp1LoTxPowerMeasEntry
	MAX-ACCESS not-accessible
	STATUS current
	DESCRIPTION
        "
        List of pm1004vencMesrxfp1LoTxPowerMeas
        Article
        "
	::= { pm1004vencMesrLine 211 }


pm1004vencMesrxfp1LoTxPowerMeasEntry OBJECT-TYPE
	SYNTAX Pm1004vencMesrxfp1LoTxPowerMeasEntry
	MAX-ACCESS not-accessible
	STATUS current
	DESCRIPTION
        "
        Row definition for the pm1004vencMesrxfp1LoTxPowerMeas
        table
        "
	INDEX   { pm1004vencMesrxfp1LoTxPowerMeasIndex }
	::= { pm1004vencMesrxfp1LoTxPowerMeasTable 1 }


Pm1004vencMesrxfp1LoTxPowerMeasEntry ::=
	SEQUENCE {
	pm1004vencMesrxfp1LoTxPowerMeasIndex
		INTEGER,
	pm1004vencMesrxfp1LoTxPowerMeasPortn
		INTEGER
	}


pm1004vencMesrxfp1LoTxPowerMeasIndex OBJECT-TYPE
	SYNTAX  INTEGER(0..128)
	MAX-ACCESS  read-only
	STATUS current
	DESCRIPTION
        "
        Index definition for the pm1004vencMesrxfp1LoTxPowerMeas
        table
        "
	::= { pm1004vencMesrxfp1LoTxPowerMeasEntry 1 }


pm1004vencMesrxfp1LoTxPowerMeasPortn OBJECT-TYPE
	SYNTAX  INTEGER (0..65535)
	MAX-ACCESS read-only
	STATUS current
	DESCRIPTION
        "
        Line Optical Module Tx Power :This
        OID gives the transmit power value
        of the XFP or OTX plugged in line
        #n, read from the DDM (Digital
           Diagnostic Monitoring) (Power
        = 10*log(AV)-40) (Unit = dBm)
         <Help>  This measure gives the
        Tx optical power of the line transceiver
        "
	::= { pm1004vencMesrxfp1LoTxPowerMeasEntry 2 }


--- *********************************************************
---     TABLE for the pm1004vencMesrxfp1LiRxPowerMeas articles
--- *********************************************************

pm1004vencMesrxfp1LiRxPowerMeasTable OBJECT-TYPE
	SYNTAX  SEQUENCE OF Pm1004vencMesrxfp1LiRxPowerMeasEntry
	MAX-ACCESS not-accessible
	STATUS current
	DESCRIPTION
        "
        List of pm1004vencMesrxfp1LiRxPowerMeas
        Article
        "
	::= { pm1004vencMesrLine 212 }


pm1004vencMesrxfp1LiRxPowerMeasEntry OBJECT-TYPE
	SYNTAX Pm1004vencMesrxfp1LiRxPowerMeasEntry
	MAX-ACCESS not-accessible
	STATUS current
	DESCRIPTION
        "
        Row definition for the pm1004vencMesrxfp1LiRxPowerMeas
        table
        "
	INDEX   { pm1004vencMesrxfp1LiRxPowerMeasIndex }
	::= { pm1004vencMesrxfp1LiRxPowerMeasTable 1 }


Pm1004vencMesrxfp1LiRxPowerMeasEntry ::=
	SEQUENCE {
	pm1004vencMesrxfp1LiRxPowerMeasIndex
		INTEGER,
	pm1004vencMesrxfp1LiRxPowerMeasPortn
		INTEGER
	}


pm1004vencMesrxfp1LiRxPowerMeasIndex OBJECT-TYPE
	SYNTAX  INTEGER(0..128)
	MAX-ACCESS  read-only
	STATUS current
	DESCRIPTION
        "
        Index definition for the pm1004vencMesrxfp1LiRxPowerMeas
        table
        "
	::= { pm1004vencMesrxfp1LiRxPowerMeasEntry 1 }


pm1004vencMesrxfp1LiRxPowerMeasPortn OBJECT-TYPE
	SYNTAX  INTEGER (0..65535)
	MAX-ACCESS read-only
	STATUS current
	DESCRIPTION
        "
        Line Optical Module Rx Power :This
        OID gives the receive power value
        of the XFP or OTX plugged in line
        #n, read from the DDM (Digital
         Diagnostic Monitoring) (Power
         = 10*log(AV)-40)  (Unit = dBm)
         <Help>  This measure gives the
        Rx optical power of the line transceiver
        "
	::= { pm1004vencMesrxfp1LiRxPowerMeasEntry 2 }


--- *********************************************************
---     TABLE for the pm1004vencMesrxfp1LxAux1Meas articles
--- *********************************************************

pm1004vencMesrxfp1LxAux1MeasTable OBJECT-TYPE
	SYNTAX  SEQUENCE OF Pm1004vencMesrxfp1LxAux1MeasEntry
	MAX-ACCESS not-accessible
	STATUS deprecated
	DESCRIPTION
        "
        List of pm1004vencMesrxfp1LxAux1Meas
        Article
        "
	::= { pm1004vencMesrLine 213 }


pm1004vencMesrxfp1LxAux1MeasEntry OBJECT-TYPE
	SYNTAX Pm1004vencMesrxfp1LxAux1MeasEntry
	MAX-ACCESS not-accessible
	STATUS deprecated
	DESCRIPTION
        "
        Row definition for the pm1004vencMesrxfp1LxAux1Meas
        table
        "
	INDEX   { pm1004vencMesrxfp1LxAux1MeasIndex }
	::= { pm1004vencMesrxfp1LxAux1MeasTable 1 }


Pm1004vencMesrxfp1LxAux1MeasEntry ::=
	SEQUENCE {
	pm1004vencMesrxfp1LxAux1MeasIndex
		INTEGER,
	pm1004vencMesrxfp1LxAux1MeasPortn
		INTEGER
	}


pm1004vencMesrxfp1LxAux1MeasIndex OBJECT-TYPE
	SYNTAX  INTEGER(0..128)
	MAX-ACCESS  read-only
	STATUS deprecated
	DESCRIPTION
        "
        Index definition for the pm1004vencMesrxfp1LxAux1Meas
        table
        "
	::= { pm1004vencMesrxfp1LxAux1MeasEntry 1 }


pm1004vencMesrxfp1LxAux1MeasPortn OBJECT-TYPE
	SYNTAX  INTEGER (0..65535)
	MAX-ACCESS read-only
	STATUS deprecated
	DESCRIPTION
        "
        Not Used :This OID gives the receive
        power value read in the DDM (Digital
        Diagnostic Monitoring) of the XFP
        or OTX plugged in line #n (Unit
        = ?)
        "
	::= { pm1004vencMesrxfp1LxAux1MeasEntry 2 }


--- *********************************************************
---     TABLE for the pm1004vencMesrxfp1LxAux2Meas articles
--- *********************************************************

pm1004vencMesrxfp1LxAux2MeasTable OBJECT-TYPE
	SYNTAX  SEQUENCE OF Pm1004vencMesrxfp1LxAux2MeasEntry
	MAX-ACCESS not-accessible
	STATUS deprecated
	DESCRIPTION
        "
        List of pm1004vencMesrxfp1LxAux2Meas
        Article
        "
	::= { pm1004vencMesrLine 214 }


pm1004vencMesrxfp1LxAux2MeasEntry OBJECT-TYPE
	SYNTAX Pm1004vencMesrxfp1LxAux2MeasEntry
	MAX-ACCESS not-accessible
	STATUS deprecated
	DESCRIPTION
        "
        Row definition for the pm1004vencMesrxfp1LxAux2Meas
        table
        "
	INDEX   { pm1004vencMesrxfp1LxAux2MeasIndex }
	::= { pm1004vencMesrxfp1LxAux2MeasTable 1 }


Pm1004vencMesrxfp1LxAux2MeasEntry ::=
	SEQUENCE {
	pm1004vencMesrxfp1LxAux2MeasIndex
		INTEGER,
	pm1004vencMesrxfp1LxAux2MeasPortn
		INTEGER
	}


pm1004vencMesrxfp1LxAux2MeasIndex OBJECT-TYPE
	SYNTAX  INTEGER(0..128)
	MAX-ACCESS  read-only
	STATUS deprecated
	DESCRIPTION
        "
        Index definition for the pm1004vencMesrxfp1LxAux2Meas
        table
        "
	::= { pm1004vencMesrxfp1LxAux2MeasEntry 1 }


pm1004vencMesrxfp1LxAux2MeasPortn OBJECT-TYPE
	SYNTAX  INTEGER (0..65535)
	MAX-ACCESS read-only
	STATUS deprecated
	DESCRIPTION
        "
        Not Used :This OID gives the receive
        power value read in the DDM (Digital
        Diagnostic Monitoring) of the XFP
        or OTX plugged in line #n (Unit
        = ?)
        "
	::= { pm1004vencMesrxfp1LxAux2MeasEntry 2 }


--- *********************************************************
---     TABLE for the pm1004vencMesrotx1Aging articles
--- *********************************************************

pm1004vencMesrotx1AgingTable OBJECT-TYPE
	SYNTAX  SEQUENCE OF Pm1004vencMesrotx1AgingEntry
	MAX-ACCESS not-accessible
	STATUS current
	DESCRIPTION
        "
        List of pm1004vencMesrotx1Aging
        Article
        "
	::= { pm1004vencMesrLine 224 }


pm1004vencMesrotx1AgingEntry OBJECT-TYPE
	SYNTAX Pm1004vencMesrotx1AgingEntry
	MAX-ACCESS not-accessible
	STATUS current
	DESCRIPTION
        "
        Row definition for the pm1004vencMesrotx1Aging
        table
        "
	INDEX   { pm1004vencMesrotx1AgingIndex }
	::= { pm1004vencMesrotx1AgingTable 1 }


Pm1004vencMesrotx1AgingEntry ::=
	SEQUENCE {
	pm1004vencMesrotx1AgingIndex
		INTEGER,
	pm1004vencMesrotx1AgingPortn
		INTEGER
	}


pm1004vencMesrotx1AgingIndex OBJECT-TYPE
	SYNTAX  INTEGER(0..128)
	MAX-ACCESS  read-only
	STATUS current
	DESCRIPTION
        "
        Index definition for the pm1004vencMesrotx1Aging
        table
        "
	::= { pm1004vencMesrotx1AgingEntry 1 }


pm1004vencMesrotx1AgingPortn OBJECT-TYPE
	SYNTAX  INTEGER (0..65535)
	MAX-ACCESS read-only
	STATUS current
	DESCRIPTION
        "
        Line OTX TLH Aging :This OID gives
        the aging of the Line OTX TLH,
         read from the DDM (Digital Diagnostic
        Monitoring) (Aging = AV)  (Unit
        = %)  <Help>  This measure gives
        the aging of the Line OTX TLH
        "
	::= { pm1004vencMesrotx1AgingEntry 2 }


--- *********************************************************
---     TABLE for the pm1004vencMesrotx1LaserTemperature articles
--- *********************************************************

pm1004vencMesrotx1LaserTemperatureTable OBJECT-TYPE
	SYNTAX  SEQUENCE OF Pm1004vencMesrotx1LaserTemperatureEntry
	MAX-ACCESS not-accessible
	STATUS deprecated
	DESCRIPTION
        "
        List of pm1004vencMesrotx1LaserTemperature
        Article
        "
	::= { pm1004vencMesrLine 225 }


pm1004vencMesrotx1LaserTemperatureEntry OBJECT-TYPE
	SYNTAX Pm1004vencMesrotx1LaserTemperatureEntry
	MAX-ACCESS not-accessible
	STATUS deprecated
	DESCRIPTION
        "
        Row definition for the pm1004vencMesrotx1LaserTemperature
        table
        "
	INDEX   { pm1004vencMesrotx1LaserTemperatureIndex }
	::= { pm1004vencMesrotx1LaserTemperatureTable 1 }


Pm1004vencMesrotx1LaserTemperatureEntry ::=
	SEQUENCE {
	pm1004vencMesrotx1LaserTemperatureIndex
		INTEGER,
	pm1004vencMesrotx1LaserTemperaturePortn
		INTEGER
	}


pm1004vencMesrotx1LaserTemperatureIndex OBJECT-TYPE
	SYNTAX  INTEGER(0..128)
	MAX-ACCESS  read-only
	STATUS deprecated
	DESCRIPTION
        "
        Index definition for the pm1004vencMesrotx1LaserTemperature
        table
        "
	::= { pm1004vencMesrotx1LaserTemperatureEntry 1 }


pm1004vencMesrotx1LaserTemperaturePortn OBJECT-TYPE
	SYNTAX  INTEGER (0..65535)
	MAX-ACCESS read-only
	STATUS deprecated
	DESCRIPTION
        "
        Line OTX TLH Laser Temperature
        :This OID gives the laser temperature
        of the Line OTX TLH, read from
         the DDM (Digital Diagnostic Monitoring)
        (Temperature = AV/256) (Unit =
         C)  <Help>  This measure gives
        the laser temperature of the Line
        OTX TLH
        "
	::= { pm1004vencMesrotx1LaserTemperatureEntry 2 }


--- *********************************************************
---     TABLE for the pm1004vencMesrotx1FreqDeviation articles
--- *********************************************************

pm1004vencMesrotx1FreqDeviationTable OBJECT-TYPE
	SYNTAX  SEQUENCE OF Pm1004vencMesrotx1FreqDeviationEntry
	MAX-ACCESS not-accessible
	STATUS current
	DESCRIPTION
        "
        List of pm1004vencMesrotx1FreqDeviation
        Article
        "
	::= { pm1004vencMesrLine 226 }


pm1004vencMesrotx1FreqDeviationEntry OBJECT-TYPE
	SYNTAX Pm1004vencMesrotx1FreqDeviationEntry
	MAX-ACCESS not-accessible
	STATUS current
	DESCRIPTION
        "
        Row definition for the pm1004vencMesrotx1FreqDeviation
        table
        "
	INDEX   { pm1004vencMesrotx1FreqDeviationIndex }
	::= { pm1004vencMesrotx1FreqDeviationTable 1 }


Pm1004vencMesrotx1FreqDeviationEntry ::=
	SEQUENCE {
	pm1004vencMesrotx1FreqDeviationIndex
		INTEGER,
	pm1004vencMesrotx1FreqDeviationPortn
		INTEGER
	}


pm1004vencMesrotx1FreqDeviationIndex OBJECT-TYPE
	SYNTAX  INTEGER(0..128)
	MAX-ACCESS  read-only
	STATUS current
	DESCRIPTION
        "
        Index definition for the pm1004vencMesrotx1FreqDeviation
        table
        "
	::= { pm1004vencMesrotx1FreqDeviationEntry 1 }


pm1004vencMesrotx1FreqDeviationPortn OBJECT-TYPE
	SYNTAX  INTEGER (0..65535)
	MAX-ACCESS read-only
	STATUS current
	DESCRIPTION
        "
        Line OTX TLH Frequency Deviation
        :This OID gives the frequency deviation
        of the Line OTX TLH, read from
         the DDM (Digital Diagnostic Monitoring)
        (Deviation = (AV-32768)*100) (Unit
        = MHz)  <Help>  This measure gives
        the frequency deviation of the
         Line OTX TLH
        "
	::= { pm1004vencMesrotx1FreqDeviationEntry 2 }


--- *********************************************************
---     TABLE for the pm1004vencMesrotx1LaserWvlength articles
--- *********************************************************

pm1004vencMesrotx1LaserWvlengthTable OBJECT-TYPE
	SYNTAX  SEQUENCE OF Pm1004vencMesrotx1LaserWvlengthEntry
	MAX-ACCESS not-accessible
	STATUS current
	DESCRIPTION
        "
        List of pm1004vencMesrotx1LaserWvlength
        Article
        "
	::= { pm1004vencMesrLine 227 }


pm1004vencMesrotx1LaserWvlengthEntry OBJECT-TYPE
	SYNTAX Pm1004vencMesrotx1LaserWvlengthEntry
	MAX-ACCESS not-accessible
	STATUS current
	DESCRIPTION
        "
        Row definition for the pm1004vencMesrotx1LaserWvlength
        table
        "
	INDEX   { pm1004vencMesrotx1LaserWvlengthIndex }
	::= { pm1004vencMesrotx1LaserWvlengthTable 1 }


Pm1004vencMesrotx1LaserWvlengthEntry ::=
	SEQUENCE {
	pm1004vencMesrotx1LaserWvlengthIndex
		INTEGER,
	pm1004vencMesrotx1LaserWvlengthPortn
		INTEGER
	}


pm1004vencMesrotx1LaserWvlengthIndex OBJECT-TYPE
	SYNTAX  INTEGER(0..128)
	MAX-ACCESS  read-only
	STATUS current
	DESCRIPTION
        "
        Index definition for the pm1004vencMesrotx1LaserWvlength
        table
        "
	::= { pm1004vencMesrotx1LaserWvlengthEntry 1 }


pm1004vencMesrotx1LaserWvlengthPortn OBJECT-TYPE
	SYNTAX  INTEGER (0..65535)
	MAX-ACCESS read-only
	STATUS current
	DESCRIPTION
        "
        Line Optical Module Wavelength
        :This OID gives the laser wavelength
        of the Line OTX TLH, read from
         the DDM (Digital Diagnostic Monitoring)
        (Wavelength=299792458/((193,100+(AV-32768
        )*12,5)*10 3)) (Unit = nm)  <Help>
         This measure gives the laser wavelength
        of the Line OTX TLH
        "
	::= { pm1004vencMesrotx1LaserWvlengthEntry 2 }







--- *****************************************************
--- $$$$$$$$$$$$$$$$$$$$$$$$$$$$$$$$$$$$$$$$$$$$$$$$$$$$$
---     DOWNLOAD
--- $$$$$$$$$$$$$$$$$$$$$$$$$$$$$$$$$$$$$$$$$$$$$$$$$$$$$
--- *****************************************************



--- *****************************************************
---     LEAF for the restartProcess article
--- *****************************************************
pm1004vencDwlrestartProcess OBJECT IDENTIFIER ::= { pm1004vencDwlOther 0 }




pm1004vencDwlColdRestartProcessed OBJECT-TYPE
	  SYNTAX EkiOnOff
	  MAX-ACCESS read-only
	  STATUS current
	  DESCRIPTION
        "
        Cold Restart :This OID indicates
        that the module last restart was
        a Cold RESTART
        "
	  ::= { pm1004vencDwlrestartProcess 2 }



pm1004vencDwlWarmRestartProcessed OBJECT-TYPE
	  SYNTAX EkiOnOff
	  MAX-ACCESS read-only
	  STATUS current
	  DESCRIPTION
        "
        Warm Restart :This OID indicates
        that the module last restart was
        a Warm RESTART
        "
	  ::= { pm1004vencDwlrestartProcess 1 }



--- *****************************************************
---     LEAF for the swBanksUsed article
--- *****************************************************
pm1004vencDwlswBanksUsed OBJECT IDENTIFIER ::= { pm1004vencDwlOther 1 }




pm1004vencDwlSwBank2Notempty OBJECT-TYPE
	  SYNTAX EkiOnOff
	  MAX-ACCESS read-only
	  STATUS current
	  DESCRIPTION
        "
        SW bank 2 loaded :This OID indicates
        a software is loaded in SW bank
        2  <Help>  This status indicates
        if the SW bank 2 contains SW package
        "
	  ::= { pm1004vencDwlswBanksUsed 6 }



pm1004vencDwlSwBank1Notempty OBJECT-TYPE
	  SYNTAX EkiOnOff
	  MAX-ACCESS read-only
	  STATUS current
	  DESCRIPTION
        "
        SW bank 1 loaded :This OID indicates
        a software is loaded in SW bank
        1  <Help>  This status indicates
        if the SW bank 1 contains SW package
        "
	  ::= { pm1004vencDwlswBanksUsed 5 }



pm1004vencDwlSwBank2Used OBJECT-TYPE
	  SYNTAX EkiOnOff
	  MAX-ACCESS read-only
	  STATUS current
	  DESCRIPTION
        "
        SW bank 2 active :This OID indicates
        the module is working on SW bank
        2  <Help>  This status indicates
        if the SW bank 2 is active or standby
        "
	  ::= { pm1004vencDwlswBanksUsed 2 }



pm1004vencDwlSwBank1Used OBJECT-TYPE
	  SYNTAX EkiOnOff
	  MAX-ACCESS read-only
	  STATUS current
	  DESCRIPTION
        "
        SW bank 1 active :This OID indicates
        the module is working on SW bank
        1  <Help>  This status indicates
        if the SW bank 1 is active or standby
        "
	  ::= { pm1004vencDwlswBanksUsed 1 }



--- *****************************************************
---     LEAF for the gwBanksUsed article
--- *****************************************************
pm1004vencDwlgwBanksUsed OBJECT IDENTIFIER ::= { pm1004vencDwlOther 2 }




pm1004vencDwlGwBank4Notempty OBJECT-TYPE
	  SYNTAX EkiOnOff
	  MAX-ACCESS read-only
	  STATUS current
	  DESCRIPTION
        "
        GW bank 4 loaded :This OID indicates
        a gateware is loaded in GW bank
        4
        "
	  ::= { pm1004vencDwlgwBanksUsed 8 }



pm1004vencDwlGwBank3Notempty OBJECT-TYPE
	  SYNTAX EkiOnOff
	  MAX-ACCESS read-only
	  STATUS current
	  DESCRIPTION
        "
        GW bank 3 loaded :This OID indicates
        a gateware is loaded in GW bank
        3  <Help>  This status indicates
        if the GW bank 3 contains GW package
        "
	  ::= { pm1004vencDwlgwBanksUsed 7 }



pm1004vencDwlGwBank2Notempty OBJECT-TYPE
	  SYNTAX EkiOnOff
	  MAX-ACCESS read-only
	  STATUS current
	  DESCRIPTION
        "
        GW bank 2 loaded :This OID indicates
        a gateware is loaded in GW bank
        2
        "
	  ::= { pm1004vencDwlgwBanksUsed 6 }



pm1004vencDwlGwBank1Notempty OBJECT-TYPE
	  SYNTAX EkiOnOff
	  MAX-ACCESS read-only
	  STATUS current
	  DESCRIPTION
        "
        GW bank 1 loaded  :This OID indicates
        a gateware is loaded in GW bank
        1  <Help>  This status indicates
        if the GW bank 1 contains GW package
        "
	  ::= { pm1004vencDwlgwBanksUsed 5 }



pm1004vencDwlGwBank4Used OBJECT-TYPE
	  SYNTAX EkiOnOff
	  MAX-ACCESS read-only
	  STATUS current
	  DESCRIPTION
        "
        GW bank 4 active  :This OID indicates
        the module is working on GW bank
        4
        "
	  ::= { pm1004vencDwlgwBanksUsed 4 }



pm1004vencDwlGwBank3Used OBJECT-TYPE
	  SYNTAX EkiOnOff
	  MAX-ACCESS read-only
	  STATUS current
	  DESCRIPTION
        "
        GW bank 3 active :This OID indicates
        the module is working on GW bank
        3  <Help>  This status indicates
        if the GW bank 3 is active or standby
        "
	  ::= { pm1004vencDwlgwBanksUsed 3 }



pm1004vencDwlGwBank2Used OBJECT-TYPE
	  SYNTAX EkiOnOff
	  MAX-ACCESS read-only
	  STATUS current
	  DESCRIPTION
        "
        GW bank 2 active :This OID indicates
        the module is working on GW bank
        2
        "
	  ::= { pm1004vencDwlgwBanksUsed 2 }



pm1004vencDwlGwBank1Used OBJECT-TYPE
	  SYNTAX EkiOnOff
	  MAX-ACCESS read-only
	  STATUS current
	  DESCRIPTION
        "
        GW bank 1 active  :This OID indicates
        the module is working on GW bank
        1  <Help>  This status indicates
        if the GW bank 1 is active or standby
        "
	  ::= { pm1004vencDwlgwBanksUsed 1 }








--- *****************************************************
--- $$$$$$$$$$$$$$$$$$$$$$$$$$$$$$$$$$$$$$$$$$$$$$$$$$$$$
---     CONFIG
--- $$$$$$$$$$$$$$$$$$$$$$$$$$$$$$$$$$$$$$$$$$$$$$$$$$$$$
--- *****************************************************



--- *****************************************************
---     LEAF for the table Group accessCAisCsf
--- *****************************************************

pm1004vencCfgAccessCAisCsf OBJECT IDENTIFIER ::= { pm1004vencConfig 1 }



--- *****************************************************
---     LEAF for the table 0012
--- *****************************************************

pm1004vencCfgClientcaiscsfTable OBJECT-TYPE
	SYNTAX  SEQUENCE OF Pm1004vencCfgClientcaiscsfEntry
	MAX-ACCESS not-accessible
	STATUS current
	DESCRIPTION
        "
        List of  Article
        "
	::= { pm1004vencCfgAccessCAisCsf 1 }


pm1004vencCfgClientcaiscsfEntry OBJECT-TYPE
	SYNTAX Pm1004vencCfgClientcaiscsfEntry
	MAX-ACCESS not-accessible
	STATUS current
	DESCRIPTION
        "
        Row definition for the accessCAisCsf
        table
        "
	INDEX   { pm1004vencCfgClientcaiscsfIndex }
	::= { pm1004vencCfgClientcaiscsfTable 1 }


Pm1004vencCfgClientcaiscsfEntry ::=
	SEQUENCE {
	pm1004vencCfgClientcaiscsfIndex
		INTEGER,
	pm1004vencCfgCAisModePortn
		Unsigned32,
	pm1004vencCfgUpAccessioAlmPortn
		Unsigned32,
	pm1004vencCfgUpMapperDeAlmPortn
		Unsigned32,
	pm1004vencCfgDownAccessioAlmPortn
		Unsigned32,
	pm1004vencCfgDownMapperDeAlmPortn
		Unsigned32,
	pm1004vencCfgDownDfrmAlmPortn
		Unsigned32,
	pm1004vencCfgDownLineSyncAlarmsPortn
		Unsigned32
	}


pm1004vencCfgClientcaiscsfIndex OBJECT-TYPE
	SYNTAX  INTEGER(0..128)
	MAX-ACCESS  read-only
	STATUS current
	DESCRIPTION
        "
        Index definition for the clientcaiscsf
        table
        "
	::= { pm1004vencCfgClientcaiscsfEntry 1 }


pm1004vencCfgCAisModePortn OBJECT-TYPE
	SYNTAX  Unsigned32 (0..65536)
	MAX-ACCESS read-write
	STATUS current
	DESCRIPTION
        "
        CAIS mode  on Client Port :This
        register enables/disables port
          laser shutdown on CAIS insertion
        condition
        "
	::= { pm1004vencCfgClientcaiscsfEntry 3 }


pm1004vencCfgUpAccessioAlmPortn OBJECT-TYPE
	SYNTAX  Unsigned32 (0..65536)
	MAX-ACCESS read-write
	STATUS current
	DESCRIPTION
        "
        CSF contributors on Client Port
        :This register configures the contributors
        to upstream CSF insertion on the
        port.
        "
	::= { pm1004vencCfgClientcaiscsfEntry 9 }


pm1004vencCfgUpMapperDeAlmPortn OBJECT-TYPE
	SYNTAX  Unsigned32 (0..65536)
	MAX-ACCESS read-write
	STATUS current
	DESCRIPTION
        "
        CSF contributors on Client Port
        :This register configures the contributors
        to upstream CSF insertion on the
        port.
        "
	::= { pm1004vencCfgClientcaiscsfEntry 10 }


pm1004vencCfgDownAccessioAlmPortn OBJECT-TYPE
	SYNTAX  Unsigned32 (0..65536)
	MAX-ACCESS read-write
	STATUS current
	DESCRIPTION
        "
        CAIS contributors on Client Port
        :This register configures the contributors
        to downstream CAIS insertion on
         port.
        "
	::= { pm1004vencCfgClientcaiscsfEntry 17 }


pm1004vencCfgDownMapperDeAlmPortn OBJECT-TYPE
	SYNTAX  Unsigned32 (0..65536)
	MAX-ACCESS read-write
	STATUS current
	DESCRIPTION
        "
        CAIS contributors on Client Port
        :This register configures the contributors
        to downstream CAIS insertion on
         port.
        "
	::= { pm1004vencCfgClientcaiscsfEntry 18 }


pm1004vencCfgDownDfrmAlmPortn OBJECT-TYPE
	SYNTAX  Unsigned32 (0..65536)
	MAX-ACCESS read-write
	STATUS current
	DESCRIPTION
        "
        CAIS contributors on Client Port
        :This register configures the contributors
        to downstream CAIS insertion on
         port.
        "
	::= { pm1004vencCfgClientcaiscsfEntry 19 }


pm1004vencCfgDownLineSyncAlarmsPortn OBJECT-TYPE
	SYNTAX  Unsigned32 (0..65536)
	MAX-ACCESS read-write
	STATUS deprecated
	DESCRIPTION
        "
        CAIS contributors on Client Port
        :This register configures the contributors
        to downstream CAIS insertion on
         port.
        "
	::= { pm1004vencCfgClientcaiscsfEntry 20 }


--- *****************************************************
---     LEAF for the table Group startup
--- *****************************************************

pm1004vencCfgStartup OBJECT IDENTIFIER ::= { pm1004vencConfig 2 }



--- *****************************************************
---     LEAF for the table 2111
--- *****************************************************

pm1004vencCfgClientStartupTable OBJECT-TYPE
	SYNTAX  SEQUENCE OF Pm1004vencCfgClientStartupEntry
	MAX-ACCESS not-accessible
	STATUS current
	DESCRIPTION
        "
        List of  Article
        "
	::= { pm1004vencCfgStartup 1 }


pm1004vencCfgClientStartupEntry OBJECT-TYPE
	SYNTAX Pm1004vencCfgClientStartupEntry
	MAX-ACCESS not-accessible
	STATUS current
	DESCRIPTION
        "
        Row definition for the startup
        table
        "
	INDEX   { pm1004vencCfgClientStartupIndex }
	::= { pm1004vencCfgClientStartupTable 1 }


Pm1004vencCfgClientStartupEntry ::=
	SEQUENCE {
	pm1004vencCfgClientStartupIndex
		INTEGER,
	pm1004vencCfgSystConfPortPortn
		Unsigned32,
	pm1004vencCfgNetConfPortPortn
		Unsigned32,
	pm1004vencCfgAdddropConfPortPortn
		Unsigned32
	}


pm1004vencCfgClientStartupIndex OBJECT-TYPE
	SYNTAX  INTEGER(0..128)
	MAX-ACCESS  read-only
	STATUS current
	DESCRIPTION
        "
        Index definition for the clientStartup
        table
        "
	::= { pm1004vencCfgClientStartupEntry 1 }


pm1004vencCfgSystConfPortPortn OBJECT-TYPE
	SYNTAX  Unsigned32 (0..65536)
	MAX-ACCESS read-write
	STATUS current
	DESCRIPTION
        "
        Default Settings on Client Port
        :This  register configures the
         default initialisation settings
        on the port.
        "
	::= { pm1004vencCfgClientStartupEntry 3 }


pm1004vencCfgNetConfPortPortn OBJECT-TYPE
	SYNTAX  Unsigned32 (0..65536)
	MAX-ACCESS read-write
	STATUS current
	DESCRIPTION
        "
        Default Protocol on Client Port
        :This register configures the default
        initialisation protocol on the
         port.
        "
	::= { pm1004vencCfgClientStartupEntry 4 }


pm1004vencCfgAdddropConfPortPortn OBJECT-TYPE
	SYNTAX  Unsigned32 (0..65536)
	MAX-ACCESS read-write
	STATUS deprecated
	DESCRIPTION
        "
        Default Add&Drop mode on Client
        Port :This register configures
         the default Add&Drop mode on the
        port.
        "
	::= { pm1004vencCfgClientStartupEntry 5 }


--- *****************************************************
---     LEAF for the table 2191
--- *****************************************************

pm1004venctablelineStartup OBJECT IDENTIFIER ::= { pm1004vencCfgStartup 2 }



pm1004vencCfgsystConfLine1 OBJECT-TYPE
	  SYNTAX Unsigned32 (0..65536)
	  MAX-ACCESS read-write
	  STATUS current
	  DESCRIPTION
        "
        Default Settings on Line 1 :This
        register configures the default
        initialisation settings on Line
        port 1.
        "
	  ::= { pm1004venctablelineStartup 2 }



pm1004vencCfglineOptions1 OBJECT-TYPE
	  SYNTAX Unsigned32 (0..65536)
	  MAX-ACCESS read-write
	  STATUS current
	  DESCRIPTION
        "
        Default Options on Active Line
        Port :This register configures
         the default options on the active
        line port
        "
	  ::= { pm1004venctablelineStartup 5 }



pm1004vencCfgsystConfLine2 OBJECT-TYPE
	  SYNTAX Unsigned32 (0..65536)
	  MAX-ACCESS read-write
	  STATUS current
	  DESCRIPTION
        "
        Default Settings on Line 2 :This
        register configures the default
        initialisation settings on Line
        port 2.
        "
	  ::= { pm1004venctablelineStartup 6 }



pm1004vencCfglineSelection OBJECT-TYPE
	  SYNTAX Unsigned32 (0..65536)
	  MAX-ACCESS read-write
	  STATUS current
	  DESCRIPTION
        "
        Default Settings of active line
        :This  register configures the
         start up active line.
        "
	  ::= { pm1004venctablelineStartup 7 }



pm1004vencCfglineOptions2 OBJECT-TYPE
	  SYNTAX Unsigned32 (0..65536)
	  MAX-ACCESS read-write
	  STATUS current
	  DESCRIPTION
        "
        Default Options on Active Line
        Port :This register configures
         the default options on the active
        line port
        "
	  ::= { pm1004venctablelineStartup 9 }



--- *****************************************************
---     LEAF for the table 21AB
--- *****************************************************

pm1004vencCfgXfpTable OBJECT-TYPE
	SYNTAX  SEQUENCE OF Pm1004vencCfgXfpEntry
	MAX-ACCESS not-accessible
	STATUS current
	DESCRIPTION
        "
        List of  Article
        "
	::= { pm1004vencCfgStartup 3 }


pm1004vencCfgXfpEntry OBJECT-TYPE
	SYNTAX Pm1004vencCfgXfpEntry
	MAX-ACCESS not-accessible
	STATUS current
	DESCRIPTION
        "
        Row definition for the startup
        table
        "
	INDEX   { pm1004vencCfgXfpIndex }
	::= { pm1004vencCfgXfpTable 1 }


Pm1004vencCfgXfpEntry ::=
	SEQUENCE {
	pm1004vencCfgXfpIndex
		INTEGER,
	pm1004vencCfgSystConfXfpPortn
		Unsigned32,
	pm1004vencCfgDataRateConfXfpPortn
		Unsigned32
	}


pm1004vencCfgXfpIndex OBJECT-TYPE
	SYNTAX  INTEGER(0..128)
	MAX-ACCESS  read-only
	STATUS current
	DESCRIPTION
        "
        Index definition for the xfp table
        "
	::= { pm1004vencCfgXfpEntry 1 }


pm1004vencCfgSystConfXfpPortn OBJECT-TYPE
	SYNTAX  Unsigned32 (0..65536)
	MAX-ACCESS read-write
	STATUS current
	DESCRIPTION
        "
        Default settings on XFP Port :This
        register configures the default
        initialisation settings on XFP
         port.
        "
	::= { pm1004vencCfgXfpEntry 3 }


pm1004vencCfgDataRateConfXfpPortn OBJECT-TYPE
	SYNTAX  Unsigned32 (0..65536)
	MAX-ACCESS read-write
	STATUS deprecated
	DESCRIPTION
        "
        :
        "
	::= { pm1004vencCfgXfpEntry 4 }


--- *****************************************************
---     LEAF for the table Group labels
--- *****************************************************

pm1004vencCfgLabels OBJECT IDENTIFIER ::= { pm1004vencConfig 3 }



--- *****************************************************
---     LEAF for the table NO_VALUE
--- *****************************************************

pm1004vencCfgLabelclientTable OBJECT-TYPE
	SYNTAX  SEQUENCE OF Pm1004vencCfgLabelclientEntry
	MAX-ACCESS not-accessible
	STATUS current
	DESCRIPTION
        "
        List of  Article
        "
	::= { pm1004vencCfgLabels 1 }


pm1004vencCfgLabelclientEntry OBJECT-TYPE
	SYNTAX Pm1004vencCfgLabelclientEntry
	MAX-ACCESS not-accessible
	STATUS current
	DESCRIPTION
        "
        Row definition for the labels
         table
        "
	INDEX   { pm1004vencCfgLabelclientIndex }
	::= { pm1004vencCfgLabelclientTable 1 }


Pm1004vencCfgLabelclientEntry ::=
	SEQUENCE {
	pm1004vencCfgLabelclientIndex
		INTEGER,
	pm1004vencCfgLabelclientPortn
		DisplayString
	}


pm1004vencCfgLabelclientIndex OBJECT-TYPE
	SYNTAX  INTEGER(0..128)
	MAX-ACCESS  read-only
	STATUS current
	DESCRIPTION
        "
        Index definition for the labelclient
        table
        "
	::= { pm1004vencCfgLabelclientEntry 1 }


pm1004vencCfgLabelclientPortn OBJECT-TYPE
	SYNTAX  DisplayString( SIZE(1..16))
	MAX-ACCESS read-write
	STATUS current
	DESCRIPTION
        "
        Default settings on the label
         of the Ports :These registers
         configures the default initialisation
        settings of the labels of the ports.
        "
	::= { pm1004vencCfgLabelclientEntry 3 }


--- *****************************************************
---     LEAF for the table NO_VALUE
--- *****************************************************

pm1004vencCfgLabellineTable OBJECT-TYPE
	SYNTAX  SEQUENCE OF Pm1004vencCfgLabellineEntry
	MAX-ACCESS not-accessible
	STATUS current
	DESCRIPTION
        "
        List of  Article
        "
	::= { pm1004vencCfgLabels 2 }


pm1004vencCfgLabellineEntry OBJECT-TYPE
	SYNTAX Pm1004vencCfgLabellineEntry
	MAX-ACCESS not-accessible
	STATUS current
	DESCRIPTION
        "
        Row definition for the labels
         table
        "
	INDEX   { pm1004vencCfgLabellineIndex }
	::= { pm1004vencCfgLabellineTable 1 }


Pm1004vencCfgLabellineEntry ::=
	SEQUENCE {
	pm1004vencCfgLabellineIndex
		INTEGER,
	pm1004vencCfgLabellinePortn
		DisplayString
	}


pm1004vencCfgLabellineIndex OBJECT-TYPE
	SYNTAX  INTEGER(0..128)
	MAX-ACCESS  read-only
	STATUS current
	DESCRIPTION
        "
        Index definition for the labelline
        table
        "
	::= { pm1004vencCfgLabellineEntry 1 }


pm1004vencCfgLabellinePortn OBJECT-TYPE
	SYNTAX  DisplayString( SIZE(1..16))
	MAX-ACCESS read-write
	STATUS current
	DESCRIPTION
        "
        Default settings on the label
         of the lines :These registers
         configures the default initialisation
        settings of the labels of the lines.
        "
	::= { pm1004vencCfgLabellineEntry 3 }


--- *****************************************************
---     LEAF for the table Group startupthresholds
--- *****************************************************

pm1004vencCfgStartupthresholds OBJECT IDENTIFIER ::= { pm1004vencConfig 4 }



--- *****************************************************
---     LEAF for the table 5012
--- *****************************************************

pm1004vencCfgClientStartupThreshTable OBJECT-TYPE
	SYNTAX  SEQUENCE OF Pm1004vencCfgClientStartupThreshEntry
	MAX-ACCESS not-accessible
	STATUS current
	DESCRIPTION
        "
        List of  Article
        "
	::= { pm1004vencCfgStartupthresholds 1 }


pm1004vencCfgClientStartupThreshEntry OBJECT-TYPE
	SYNTAX Pm1004vencCfgClientStartupThreshEntry
	MAX-ACCESS not-accessible
	STATUS current
	DESCRIPTION
        "
        Row definition for the startupthresholds
        table
        "
	INDEX   { pm1004vencCfgClientStartupThreshIndex }
	::= { pm1004vencCfgClientStartupThreshTable 1 }


Pm1004vencCfgClientStartupThreshEntry ::=
	SEQUENCE {
	pm1004vencCfgClientStartupThreshIndex
		INTEGER,
	pm1004vencCfgClientThreshtxpowhighPortn
		Unsigned32,
	pm1004vencCfgClientThreshtxpowlowPortn
		Unsigned32,
	pm1004vencCfgClientThreshrxpowhighPortn
		Unsigned32,
	pm1004vencCfgClientThreshrxpowlowPortn
		Unsigned32
	}


pm1004vencCfgClientStartupThreshIndex OBJECT-TYPE
	SYNTAX  INTEGER(0..128)
	MAX-ACCESS  read-only
	STATUS current
	DESCRIPTION
        "
        Index definition for the clientStartupThresh
        table
        "
	::= { pm1004vencCfgClientStartupThreshEntry 1 }


pm1004vencCfgClientThreshtxpowhighPortn OBJECT-TYPE
	SYNTAX  Unsigned32 (0..65536)
	MAX-ACCESS read-write
	STATUS current
	DESCRIPTION
        "
        Default Setting on Tx Power high
        threshold :This register configures
        the default initialisation of the
        high threshold of the Transmit
         power on the port.
        "
	::= { pm1004vencCfgClientStartupThreshEntry 15 }


pm1004vencCfgClientThreshtxpowlowPortn OBJECT-TYPE
	SYNTAX  Unsigned32 (0..65536)
	MAX-ACCESS read-write
	STATUS current
	DESCRIPTION
        "
        Default Setting on Tx Power low
        threshold :This register configures
        the default initialisation of the
        low threshold of the Transmit power
        on the port.
        "
	::= { pm1004vencCfgClientStartupThreshEntry 16 }


pm1004vencCfgClientThreshrxpowhighPortn OBJECT-TYPE
	SYNTAX  Unsigned32 (0..65536)
	MAX-ACCESS read-write
	STATUS current
	DESCRIPTION
        "
        Default Setting on Rx Power high
        threshold :This register configures
        the default initialisation of the
        high threshold of the received
         power on the port.
        "
	::= { pm1004vencCfgClientStartupThreshEntry 19 }


pm1004vencCfgClientThreshrxpowlowPortn OBJECT-TYPE
	SYNTAX  Unsigned32 (0..65536)
	MAX-ACCESS read-write
	STATUS current
	DESCRIPTION
        "
        Default Setting on Rx Power low
        threshold :This register configures
        the default initialisation of the
        low threshold of the received power
        on the port.
        "
	::= { pm1004vencCfgClientStartupThreshEntry 20 }


--- *****************************************************
---     LEAF for the table 50A1
--- *****************************************************

pm1004vencCfgLineStartupThreshTable OBJECT-TYPE
	SYNTAX  SEQUENCE OF Pm1004vencCfgLineStartupThreshEntry
	MAX-ACCESS not-accessible
	STATUS current
	DESCRIPTION
        "
        List of  Article
        "
	::= { pm1004vencCfgStartupthresholds 2 }


pm1004vencCfgLineStartupThreshEntry OBJECT-TYPE
	SYNTAX Pm1004vencCfgLineStartupThreshEntry
	MAX-ACCESS not-accessible
	STATUS current
	DESCRIPTION
        "
        Row definition for the startupthresholds
        table
        "
	INDEX   { pm1004vencCfgLineStartupThreshIndex }
	::= { pm1004vencCfgLineStartupThreshTable 1 }


Pm1004vencCfgLineStartupThreshEntry ::=
	SEQUENCE {
	pm1004vencCfgLineStartupThreshIndex
		INTEGER,
	pm1004vencCfgLineThreshtxpowhighPortn
		Unsigned32,
	pm1004vencCfgLineThreshtxpowlowPortn
		Unsigned32,
	pm1004vencCfgLineThreshrxpowhighPortn
		Unsigned32,
	pm1004vencCfgLineThreshrxpowlowPortn
		Unsigned32
	}


pm1004vencCfgLineStartupThreshIndex OBJECT-TYPE
	SYNTAX  INTEGER(0..128)
	MAX-ACCESS  read-only
	STATUS current
	DESCRIPTION
        "
        Index definition for the lineStartupThresh
        table
        "
	::= { pm1004vencCfgLineStartupThreshEntry 1 }


pm1004vencCfgLineThreshtxpowhighPortn OBJECT-TYPE
	SYNTAX  Unsigned32 (0..65536)
	MAX-ACCESS read-write
	STATUS current
	DESCRIPTION
        "
        Default Setting on Tx Power high
        threshold :This register configures
        the default initialisation of the
        high threshold of the Transmit
         power on the line.
        "
	::= { pm1004vencCfgLineStartupThreshEntry 15 }


pm1004vencCfgLineThreshtxpowlowPortn OBJECT-TYPE
	SYNTAX  Unsigned32 (0..65536)
	MAX-ACCESS read-write
	STATUS current
	DESCRIPTION
        "
        Default Setting on Tx Power low
        threshold :This register configures
        the default initialisation of the
        low threshold of the Transmit power
        on the line.
        "
	::= { pm1004vencCfgLineStartupThreshEntry 16 }


pm1004vencCfgLineThreshrxpowhighPortn OBJECT-TYPE
	SYNTAX  Unsigned32 (0..65536)
	MAX-ACCESS read-write
	STATUS current
	DESCRIPTION
        "
        Default Setting on Rx Power high
        threshold :This register configures
        the default initialisation of the
        high threshold of the received
         power on the line.
        "
	::= { pm1004vencCfgLineStartupThreshEntry 19 }


pm1004vencCfgLineThreshrxpowlowPortn OBJECT-TYPE
	SYNTAX  Unsigned32 (0..65536)
	MAX-ACCESS read-write
	STATUS current
	DESCRIPTION
        "
        Default Setting on Rx Power low
        threshold :This register configures
        the default initialisation of the
        low threshold of the received power
        on the line.
        "
	::= { pm1004vencCfgLineStartupThreshEntry 20 }


--- *****************************************************
---     LEAF for the table Group other
--- *****************************************************

pm1004vencCfgOther OBJECT IDENTIFIER ::= { pm1004vencConfig 5 }



--- *****************************************************
---     LEAF for the table 2300
--- *****************************************************

pm1004venctablemoduleOther OBJECT IDENTIFIER ::= { pm1004vencCfgOther 1 }



pm1004vencCfgmode OBJECT-TYPE
	  SYNTAX Unsigned32 (0..65536)
	  MAX-ACCESS read-write
	  STATUS current
	  DESCRIPTION
        "
        Default encryption mode on Module
        :This register selects the encryption
         configuration of the PM
        "
	  ::= { pm1004venctablemoduleOther 2 }



--- *****************************************************
---     LEAF for the table Group startuptlh
--- *****************************************************

pm1004vencCfgStartuptlh OBJECT IDENTIFIER ::= { pm1004vencConfig 6 }



--- *****************************************************
---     LEAF for the table 25A8
--- *****************************************************

pm1004vencCfgOtxtlhTable OBJECT-TYPE
	SYNTAX  SEQUENCE OF Pm1004vencCfgOtxtlhEntry
	MAX-ACCESS not-accessible
	STATUS current
	DESCRIPTION
        "
        List of  Article
        "
	::= { pm1004vencCfgStartuptlh 1 }


pm1004vencCfgOtxtlhEntry OBJECT-TYPE
	SYNTAX Pm1004vencCfgOtxtlhEntry
	MAX-ACCESS not-accessible
	STATUS current
	DESCRIPTION
        "
        Row definition for the startuptlh
        table
        "
	INDEX   { pm1004vencCfgOtxtlhIndex }
	::= { pm1004vencCfgOtxtlhTable 1 }


Pm1004vencCfgOtxtlhEntry ::=
	SEQUENCE {
	pm1004vencCfgOtxtlhIndex
		INTEGER,
	pm1004vencCfgNuPortn
		Unsigned32,
	pm1004vencCfgLineDitherRatePortn
		Unsigned32,
	pm1004vencCfgLineDitherFhzPortn
		Unsigned32,
	pm1004vencCfgLinePwrLaserPortn
		Unsigned32,
	pm1004vencCfgLineFCurrentPortn
		Unsigned32,
	pm1004vencCfgLineGridCurrentPortn
		Unsigned32,
	pm1004vencCfgFPortn
		Unsigned32,
	pm1004vencCfgReservedPortn
		Unsigned32,
	pm1004vencCfgLinePhotodiodeModePortn
		Unsigned32,
	pm1004vencCfgLinePhotodiodeValuePortn
		Unsigned32
	}


pm1004vencCfgOtxtlhIndex OBJECT-TYPE
	SYNTAX  INTEGER(0..128)
	MAX-ACCESS  read-only
	STATUS current
	DESCRIPTION
        "
        Index definition for the otxtlh
        table
        "
	::= { pm1004vencCfgOtxtlhEntry 1 }


pm1004vencCfgNuPortn OBJECT-TYPE
	SYNTAX  Unsigned32 (0..65536)
	MAX-ACCESS read-write
	STATUS deprecated
	DESCRIPTION
        "
        :
        "
	::= { pm1004vencCfgOtxtlhEntry 3 }


pm1004vencCfgLineDitherRatePortn OBJECT-TYPE
	SYNTAX  Unsigned32 (0..65536)
	MAX-ACCESS read-write
	STATUS current
	DESCRIPTION
        "
        Default Line OTX TLH FM amplitude
        :This register configures the start-up
        width of the frequency modulation
        of the Line OTX TLH
        "
	::= { pm1004vencCfgOtxtlhEntry 4 }


pm1004vencCfgLineDitherFhzPortn OBJECT-TYPE
	SYNTAX  Unsigned32 (0..65536)
	MAX-ACCESS read-write
	STATUS current
	DESCRIPTION
        "
        Default Line OTX TLH FM frequency
        :This register configures the start-up
        frequency of the frequency modulation
        of the Line OTX TLH
        "
	::= { pm1004vencCfgOtxtlhEntry 5 }


pm1004vencCfgLinePwrLaserPortn OBJECT-TYPE
	SYNTAX  Unsigned32 (0..65536)
	MAX-ACCESS read-write
	STATUS current
	DESCRIPTION
        "
        Defaut Line OTX TLH output Power
        :This register configures the start-up
        output power of the Line OTX TLH
         (Unit = dBm)
        "
	::= { pm1004vencCfgOtxtlhEntry 6 }


pm1004vencCfgLineFCurrentPortn OBJECT-TYPE
	SYNTAX  Unsigned32 (0..65536)
	MAX-ACCESS read-write
	STATUS current
	DESCRIPTION
        "
        Default Line OTX TLH Channel :This
        register configures the start-up
        laser channel of the Line OTX TLH
        "
	::= { pm1004vencCfgOtxtlhEntry 7 }


pm1004vencCfgLineGridCurrentPortn OBJECT-TYPE
	SYNTAX  Unsigned32 (0..65536)
	MAX-ACCESS read-write
	STATUS current
	DESCRIPTION
        "
        Default Line OTX TLH Grid :This
        register configures the start-up
        laser grid of the Line OTX TLH
        "
	::= { pm1004vencCfgOtxtlhEntry 8 }


pm1004vencCfgFPortn OBJECT-TYPE
	SYNTAX  Unsigned32 (0..65536)
	MAX-ACCESS read-write
	STATUS current
	DESCRIPTION
        "
        Default Line OTX TLH lowest Freq
        :This register configures the start-up
        lowest frequency supported on the
        Line OTX TLH
        "
	::= { pm1004vencCfgOtxtlhEntry 9 }


pm1004vencCfgReservedPortn OBJECT-TYPE
	SYNTAX  Unsigned32 (0..65536)
	MAX-ACCESS read-write
	STATUS deprecated
	DESCRIPTION
        "
        :
        "
	::= { pm1004vencCfgOtxtlhEntry 10 }


pm1004vencCfgLinePhotodiodeModePortn OBJECT-TYPE
	SYNTAX  Unsigned32 (0..65536)
	MAX-ACCESS read-write
	STATUS current
	DESCRIPTION
        "
        Default Line OTX TLH APD mode
         :This register configures the
         start-up APD mode of the Line
         OTX TLH
        "
	::= { pm1004vencCfgOtxtlhEntry 11 }


pm1004vencCfgLinePhotodiodeValuePortn OBJECT-TYPE
	SYNTAX  Unsigned32 (0..65536)
	MAX-ACCESS read-write
	STATUS current
	DESCRIPTION
        "
        Default Line OTX TLH APD atten.
        :This register configures the start-up
        APD attenuation on the Line OTX
        TLH
        "
	::= { pm1004vencCfgOtxtlhEntry 12 }


--- *****************************************************
---     LEAF for the table Group startuptablefive
--- *****************************************************

pm1004vencCfgStartuptablefive OBJECT IDENTIFIER ::= { pm1004vencConfig 7 }



--- *****************************************************
---     LEAF for the table 0005
--- *****************************************************

pm1004vencCfgOtxtlhcapabilitiesTable OBJECT-TYPE
	SYNTAX  SEQUENCE OF Pm1004vencCfgOtxtlhcapabilitiesEntry
	MAX-ACCESS not-accessible
	STATUS current
	DESCRIPTION
        "
        List of  Article
        "
	::= { pm1004vencCfgStartuptablefive 1 }


pm1004vencCfgOtxtlhcapabilitiesEntry OBJECT-TYPE
	SYNTAX Pm1004vencCfgOtxtlhcapabilitiesEntry
	MAX-ACCESS not-accessible
	STATUS current
	DESCRIPTION
        "
        Row definition for the startuptablefive
        table
        "
	INDEX   { pm1004vencCfgOtxtlhcapabilitiesIndex }
	::= { pm1004vencCfgOtxtlhcapabilitiesTable 1 }


Pm1004vencCfgOtxtlhcapabilitiesEntry ::=
	SEQUENCE {
	pm1004vencCfgOtxtlhcapabilitiesIndex
		INTEGER,
	pm1004vencCfgComponentTypePortn
		Unsigned32,
	pm1004vencCfgMiscellaneousPortn
		Unsigned32,
	pm1004vencCfgFirstChannelPortn
		Unsigned32,
	pm1004vencCfgLastChannelPortn
		Unsigned32,
	pm1004vencCfgGridPortn
		Unsigned32
	}


pm1004vencCfgOtxtlhcapabilitiesIndex OBJECT-TYPE
	SYNTAX  INTEGER(0..128)
	MAX-ACCESS  read-only
	STATUS current
	DESCRIPTION
        "
        Index definition for the otxtlhcapabilities
        table
        "
	::= { pm1004vencCfgOtxtlhcapabilitiesEntry 1 }


pm1004vencCfgComponentTypePortn OBJECT-TYPE
	SYNTAX  Unsigned32 (0..65536)
	MAX-ACCESS read-only
	STATUS current
	DESCRIPTION
        "
        Component parameters :This OID
        defines the component parameters
        "
	::= { pm1004vencCfgOtxtlhcapabilitiesEntry 3 }


pm1004vencCfgMiscellaneousPortn OBJECT-TYPE
	SYNTAX  Unsigned32 (0..65536)
	MAX-ACCESS read-only
	STATUS current
	DESCRIPTION
        "
        Miscellaneous default settings
        :This OID defines the miscellaneous
        parameters
        "
	::= { pm1004vencCfgOtxtlhcapabilitiesEntry 4 }


pm1004vencCfgFirstChannelPortn OBJECT-TYPE
	SYNTAX  Unsigned32 (0..65536)
	MAX-ACCESS read-only
	STATUS current
	DESCRIPTION
        "
        Number of the first channel of
        the component :This OID defines
        the first channel number of the
        PM
        "
	::= { pm1004vencCfgOtxtlhcapabilitiesEntry 5 }


pm1004vencCfgLastChannelPortn OBJECT-TYPE
	SYNTAX  Unsigned32 (0..65536)
	MAX-ACCESS read-only
	STATUS current
	DESCRIPTION
        "
        Number of the last channel of
         the component :This OID defines
        the last channel number of the
         PM
        "
	::= { pm1004vencCfgOtxtlhcapabilitiesEntry 6 }


pm1004vencCfgGridPortn OBJECT-TYPE
	SYNTAX  Unsigned32 (0..65536)
	MAX-ACCESS read-only
	STATUS current
	DESCRIPTION
        "
        Grid value of the component :This
        OID defines the grid of the PM
        "
	::= { pm1004vencCfgOtxtlhcapabilitiesEntry 7 }



pm1004vencCfgWriteConfiguration  OBJECT-TYPE
	SYNTAX EkiOnOff
	MAX-ACCESS read-write
	STATUS current
	DESCRIPTION
	"Write configuration to module:This OID
	 writes the complete configuration to the module"
	::= { pm1004vencConfig 257 }






--- *****************************************************
---     TRAP OBJECTS
--- *****************************************************

pm1004venctrapPortNumber OBJECT-TYPE
	SYNTAX INTEGER(1..64)
	MAX-ACCESS read-only
	STATUS current
	DESCRIPTION
	"Last port which generates a trap"
	::= { pm1004venctraps 2 }

pm1004venctrapLineNumber OBJECT-TYPE
	SYNTAX INTEGER(1..64)
	MAX-ACCESS read-only
	STATUS current
	DESCRIPTION
	"Last Line which generates a trap"
	::= { pm1004venctraps 3 }

pm1004venctrapBoardNumber OBJECT-TYPE
	SYNTAX INTEGER(1..64)
	MAX-ACCESS read-only
	STATUS current
	DESCRIPTION
	"Last module which generates a trap"
	::= { pm1004venctraps 4 }







--- *****************************************************
---     LINE TRAPS
--- *****************************************************

pm1004vencLineTrapNotUrgentGoesOn NOTIFICATION-TYPE
	OBJECTS {pm1004vencAlmLineDdmWarningPortn, pm1004venctrapLineNumber, pm1004venctrapBoardNumber}
	STATUS current
	DESCRIPTION "Not urgent Line default is activated"
	::= { pm1004venctraps 30 }

pm1004vencLineTrapNotUrgentGoesOff NOTIFICATION-TYPE
	OBJECTS {pm1004vencAlmLineDdmWarningPortn, pm1004venctrapLineNumber, pm1004venctrapBoardNumber}
	STATUS current
	DESCRIPTION "Not urgent Line default disappeared"
	::= { pm1004venctraps 31 }

pm1004vencLineTrapUrgentGoesOn NOTIFICATION-TYPE
	OBJECTS {pm1004vencAlmLineDdmAlmPortn, pm1004venctrapLineNumber, pm1004venctrapBoardNumber}
	STATUS current
	DESCRIPTION "Urgent Line default is activated"
	::= { pm1004venctraps 32 }

pm1004vencLineTrapUrgentGoesOff NOTIFICATION-TYPE
	OBJECTS {pm1004vencAlmLineDdmAlmPortn, pm1004venctrapLineNumber, pm1004venctrapBoardNumber}
	STATUS current
	DESCRIPTION "Urgent Line default disappeared"
	::= { pm1004venctraps 33 }

pm1004vencLineTrapCritGoesOn NOTIFICATION-TYPE
	OBJECTS {pm1004vencAlmLineFailPortn , pm1004vencAlmLineHwFailPortn , pm1004venctrapLineNumber, pm1004venctrapBoardNumber}
	STATUS current
	DESCRIPTION "Critical Line default is activated"
	::= { pm1004venctraps 34 }

pm1004vencLineTrapCritGoesOff NOTIFICATION-TYPE
	OBJECTS {pm1004vencAlmLineFailPortn , pm1004vencAlmLineHwFailPortn , pm1004venctrapLineNumber, pm1004venctrapBoardNumber}
	STATUS current
	DESCRIPTION "Critical Line default disappeared"
	::= { pm1004venctraps 35 }






--- *****************************************************
---     CLIENT TRAPS
--- *****************************************************

pm1004vencClientTrapCritGoesOn NOTIFICATION-TYPE
	OBJECTS {pm1004vencAlmFailAccPortn, pm1004vencAlmHwFailAccPortn, pm1004venctrapPortNumber, pm1004venctrapBoardNumber}
	STATUS current
	DESCRIPTION "Critical client default is activated"
	::= { pm1004venctraps 44 }

pm1004vencClientTrapCritGoesOff NOTIFICATION-TYPE
	OBJECTS {pm1004vencAlmFailAccPortn, pm1004vencAlmHwFailAccPortn, pm1004venctrapPortNumber, pm1004venctrapBoardNumber}
	STATUS current
	DESCRIPTION "Critical client default disappeared"
	::= { pm1004venctraps 45 }






--- *****************************************************
---     HW TRAPS
--- *****************************************************

pm1004vencPowerTrapUrgentGoesOn NOTIFICATION-TYPE
	OBJECTS {pm1004vencAlmDefFuseB, pm1004vencAlmDefFuseA , pm1004venctrapBoardNumber}
	STATUS current
	DESCRIPTION "Urgent power supply default is activated"
	::= { pm1004venctraps 50 }

pm1004vencPowerTrapUrgentGoesOff NOTIFICATION-TYPE
	OBJECTS {pm1004vencAlmDefFuseB, pm1004vencAlmDefFuseA , pm1004venctrapBoardNumber}
	STATUS current
	DESCRIPTION "Urgent power supply default disappeared"
	::= { pm1004venctraps 51 }






END
