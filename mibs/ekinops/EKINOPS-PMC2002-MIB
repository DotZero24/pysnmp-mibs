-- *****************************************************************
-- EKINOPS-pmc2002.TXT:  MIB
--
--MIB Part Number:3MI00026ABAF
--MIB Version:02
--
-- Copyright (c) 2016 by Ekinops
-- All rights reserved.
--
-- *****************************************************************

EKINOPS-PMC2002-MIB DEFINITIONS ::= BEGIN

IMPORTS
	ekinops,
	EkiState,
	EkiOnOff,
	EkiMode,
	EkiProtocol,
	EkiApiState,
	EkiSynchroMode,
	EkiMeasureType
			FROM EKINOPS-MIB
        MODULE-IDENTITY,
        OBJECT-TYPE,
        NOTIFICATION-TYPE,
	Unsigned32,
	Integer32,
	Counter32,
	IpAddress
        		FROM SNMPv2-SMI
 	TEXTUAL-CONVENTION,
	DisplayString
                FROM SNMPv2-TC;

modulepmc2002 MODULE-IDENTITY
        LAST-UPDATED "201606020000Z"
        ORGANIZATION "Ekinops"
        CONTACT-INFO
         "Ekinops

          3, rue Blaise Pascal
          F-22300 Lannion / FRANCE

          Tel : +33 (0)2 96 05 00 30
          Fax : +33 (0)2 96 48 62 39

          E-mail: support@ekinops.net"
        DESCRIPTION
          "MIB for managing Ekinops modules with PMC2002 software"
	REVISION "201101040000Z"
	DESCRIPTION
	  "Initial Version."

	REVISION "201110140000Z"
	DESCRIPTION
	  "Creation"
	REVISION "201207030000Z"
	DESCRIPTION
	  "Minor cosmetic updates"
	REVISION "201304030000Z"
	DESCRIPTION
	  "S1,K1,K2 suppress"
	REVISION "201403260000Z"
	DESCRIPTION
	  "Probcause,AlarmType - NMS completion"
	REVISION "201411180000Z"
	DESCRIPTION
	  "Labels cosmetic updates"
	REVISION "201502200000Z"
	DESCRIPTION
	  "Labels cosmetic updates"

	REVISION "201605240000Z"
	DESCRIPTION
	  "New AlarmType – synthesisAlarm (12)"
	REVISION "201606020000Z"
	DESCRIPTION
	  "Capabilities objects of Table 5"
        ::= { ekinops 52 }



--- *****************************************************
---     LEAF LEVEL 2
--- *****************************************************


pmc2002alarms OBJECT IDENTIFIER ::= { modulepmc2002 2 }
pmc2002AlmOther OBJECT IDENTIFIER ::= { pmc2002alarms 1 }
pmc2002AlmOtherNurg OBJECT IDENTIFIER ::= { pmc2002AlmOther 1 }
pmc2002AlmOtherUrg OBJECT IDENTIFIER ::= { pmc2002AlmOther 2 }
pmc2002AlmOtherCrit OBJECT IDENTIFIER ::= { pmc2002AlmOther 3 }

pmc2002AlmClient OBJECT IDENTIFIER ::= { pmc2002alarms 2 }
pmc2002AlmClientNurg OBJECT IDENTIFIER ::= { pmc2002AlmClient 1 }
pmc2002AlmClientUrg OBJECT IDENTIFIER ::= { pmc2002AlmClient 2 }
pmc2002AlmClientCrit OBJECT IDENTIFIER ::= { pmc2002AlmClient 3 }

pmc2002AlmLine OBJECT IDENTIFIER ::= { pmc2002alarms 3 }
pmc2002AlmLineNurg OBJECT IDENTIFIER ::= { pmc2002AlmLine 1 }
pmc2002AlmLineUrg OBJECT IDENTIFIER ::= { pmc2002AlmLine 2 }
pmc2002AlmLineCrit OBJECT IDENTIFIER ::= { pmc2002AlmLine 3 }





pmc2002measures OBJECT IDENTIFIER ::= { modulepmc2002 3 }
pmc2002MesrOther OBJECT IDENTIFIER ::= { pmc2002measures 1 }
pmc2002MesrClient OBJECT IDENTIFIER ::= { pmc2002measures 2 }
pmc2002MesrLine OBJECT IDENTIFIER ::= { pmc2002measures 3 }




pmc2002counters OBJECT IDENTIFIER ::= { modulepmc2002 4 }
pmc2002CntOther OBJECT IDENTIFIER ::= { pmc2002counters 1 }
pmc2002CntClient OBJECT IDENTIFIER ::= { pmc2002counters 2 }
pmc2002CntLine OBJECT IDENTIFIER ::= { pmc2002counters 3 }


pmc2002controlsWrite OBJECT IDENTIFIER ::= { modulepmc2002 6 }
pmc2002CtrlOther OBJECT IDENTIFIER ::= { pmc2002controlsWrite 1 }
pmc2002CtrlClient OBJECT IDENTIFIER ::= { pmc2002controlsWrite 2 }
pmc2002CtrlLine OBJECT IDENTIFIER ::= { pmc2002controlsWrite 3 }

pmc2002ri OBJECT IDENTIFIER ::= { modulepmc2002 7 }
pmc2002riTable OBJECT IDENTIFIER ::= { pmc2002ri 1 }

pmc2002download OBJECT IDENTIFIER ::= { modulepmc2002 8 }
pmc2002DwlOther OBJECT IDENTIFIER ::= { pmc2002download 1 }
pmc2002DwlClient OBJECT IDENTIFIER ::= { pmc2002download 2 }
pmc2002DwlLine OBJECT IDENTIFIER ::= { pmc2002download 3 }

pmc2002Config OBJECT IDENTIFIER ::= { modulepmc2002 10 }

pmc2002traps OBJECT IDENTIFIER ::= { modulepmc2002 11 }

pmc2002Monitoring OBJECT IDENTIFIER ::= { modulepmc2002 12}

pmc2002MonOther OBJECT IDENTIFIER ::= { pmc2002Monitoring 1 }
pmc2002MonSync OBJECT IDENTIFIER ::= { pmc2002MonOther 1 }
pmc2002MonTimeStamp OBJECT IDENTIFIER ::= { pmc2002MonOther 2 }

pmc2002MonClient OBJECT IDENTIFIER ::= { pmc2002Monitoring 2 }

pmc2002MonLine OBJECT IDENTIFIER ::= { pmc2002Monitoring 3 }

pmc2002Rmon OBJECT IDENTIFIER ::= { pmc2002Monitoring 4 }

pmc2002RmonClient OBJECT IDENTIFIER ::= { pmc2002Rmon 1 }
pmc2002RmonLine OBJECT IDENTIFIER ::= { pmc2002Rmon 2 }
pmc2002RmonOther OBJECT IDENTIFIER ::= { pmc2002Rmon 3 }

--- *****************************************************
--- $$$$$$$$$$$$$$$$$$$$$$$$$$$$$$$$$$$$$$$$$$$$$$$$$$$$$
---     TEXTUAL-CONVENTION
--- $$$$$$$$$$$$$$$$$$$$$$$$$$$$$$$$$$$$$$$$$$$$$$$$$$$$$
--- *****************************************************

Pmc2002OtxMode ::= TEXTUAL-CONVENTION
    STATUS      current
    DESCRIPTION "Different modes on OTX-TLH on client and line ports"
    SYNTAX INTEGER {
		otx80mode(1),
		otx60mode(2),
		otxadjustmode(4)
           }

Pmc2002OtxGrid ::= TEXTUAL-CONVENTION
    STATUS      current
    DESCRIPTION "Different grids on OTX-TLH on client and line ports"
    SYNTAX INTEGER {
		otxgrid200(200),
		otxgrid100(100),
		otxgrid50(50)
           }

Pmc2002AdjustValue ::= TEXTUAL-CONVENTION
    STATUS      current
    DESCRIPTION "Different values in Adjust mode on OTX-TLH on client and line ports"
    SYNTAX INTEGER {
		otxadjustvalue0(0),
		otxadjustvalue1(1),
		otxadjustvalue2(2),
		otxadjustvalue3(3),
		otxadjustvalue4(4),
		otxadjustvalue5(5),
		otxadjustvalue6(6),
		otxadjustvalue7(7),
		otxadjustvalue8(8),
		otxadjustvalue9(9),
		otxadjustvalue10(10)
           }

Pmc2002OtxChannel ::= TEXTUAL-CONVENTION
    STATUS      current
    DESCRIPTION "Channel selection on OTX-TLH on client and line ports"
    SYNTAX INTEGER

Pmc2002DccMode ::= TEXTUAL-CONVENTION
    STATUS      current
    DESCRIPTION "Mode for DCC"
    SYNTAX INTEGER {
		dccNo(0),
		dcctermLine1(1),
		dcctermLine2(2),
		dcctermLines12(3),
		dccmaster(4),
		dccslaveLine12(7)
           }

Pmc2002Mode ::= TEXTUAL-CONVENTION
    STATUS      current
    DESCRIPTION "Different modes for the module"
    SYNTAX INTEGER {
		modedual(0),
		modeprotect(1),
		moderegen(2)
           }

--- *****************************************************
--- $$$$$$$$$$$$$$$$$$$$$$$$$$$$$$$$$$$$$$$$$$$$$$$$$$$$$
---     REMOTE INVENTORY
--- $$$$$$$$$$$$$$$$$$$$$$$$$$$$$$$$$$$$$$$$$$$$$$$$$$$$$
--- *****************************************************

pmc2002RinvReloadInventory OBJECT-TYPE
  SYNTAX EkiOnOff
  MAX-ACCESS read-write
  STATUS current
  DESCRIPTION
        "Reload the inventory: This OID triggers an
         inventory reload."
  ::= { pmc2002ri 2 }

pmc2002RinvHwPlatform OBJECT-TYPE
  SYNTAX DisplayString
  MAX-ACCESS read-only
  STATUS current
  DESCRIPTION
        "HW platform description: This OID contains the
         description of the Hardware platform."
  ::= { pmc2002ri 3 }

pmc2002RinvModulePlatform OBJECT-TYPE
  SYNTAX DisplayString
  MAX-ACCESS read-only
  STATUS current
  DESCRIPTION
        "Module platform description: This OID contains the
         description of the Module."
  ::= { pmc2002ri 4 }

pmc2002RinvSwPlatform OBJECT-TYPE
  SYNTAX DisplayString
  MAX-ACCESS read-only
  STATUS current
  DESCRIPTION
        "SW platform description: This OID contains the
         description of the Software platform."
  ::= { pmc2002ri 5 }

pmc2002RinvGwPlatform OBJECT-TYPE
  SYNTAX DisplayString
  MAX-ACCESS read-only
  STATUS current
  DESCRIPTION
        "GW platform desciption: This OID contains the
         description of the Gateware platform."
  ::= { pmc2002ri 6 }



pmc2002RinvClientTable OBJECT-TYPE
      SYNTAX  SEQUENCE OF Pmc2002RinvClientEntry
      MAX-ACCESS  not-accessible
      STATUS  current
      DESCRIPTION
              "List of the Clients on the selected module"
      ::= { pmc2002riTable 1 }

pmc2002RinvClientEntry OBJECT-TYPE
        SYNTAX  Pmc2002RinvClientEntry
        MAX-ACCESS  not-accessible
        STATUS  current
        DESCRIPTION
              "Row definition for the Client table"
        INDEX   { pmc2002RinvClientIndex }
        ::= { pmc2002RinvClientTable 1 }



Pmc2002RinvClientEntry::=
        SEQUENCE {
          pmc2002RinvClientIndex
              Integer32,
          pmc2002RinvClient
              DisplayString
        }


    pmc2002RinvClientIndex OBJECT-TYPE
        SYNTAX  Integer32(1..16)
        MAX-ACCESS  read-only
        STATUS  current
        DESCRIPTION
              "Index for Client table"
        ::= { pmc2002RinvClientEntry 1 }


    pmc2002RinvClient OBJECT-TYPE
        SYNTAX  DisplayString
        MAX-ACCESS  read-only
        STATUS  current
        DESCRIPTION
              "Inventory for the Client: This OID contains the inventory for the Client Port"
        ::= { pmc2002RinvClientEntry 2 }




pmc2002RinvLineTable OBJECT-TYPE
      SYNTAX  SEQUENCE OF Pmc2002RinvLineEntry
      MAX-ACCESS  not-accessible
      STATUS  current
      DESCRIPTION
              "List of the Lines on the selected module"
      ::= { pmc2002riTable 2 }

pmc2002RinvLineEntry OBJECT-TYPE
        SYNTAX  Pmc2002RinvLineEntry
        MAX-ACCESS  not-accessible
        STATUS  current
        DESCRIPTION
              "Row definition for the Line table"
        INDEX   { pmc2002RinvLineIndex }
        ::= { pmc2002RinvLineTable 1 }



Pmc2002RinvLineEntry::=
        SEQUENCE {
          pmc2002RinvLineIndex
              Integer32,
          pmc2002RinvxfpLine
              DisplayString
        }


    pmc2002RinvLineIndex OBJECT-TYPE
        SYNTAX  Integer32(1..16)
        MAX-ACCESS  read-only
        STATUS  current
        DESCRIPTION
              "Index for XFP table"
        ::= { pmc2002RinvLineEntry 1 }


    pmc2002RinvxfpLine OBJECT-TYPE
        SYNTAX  DisplayString
        MAX-ACCESS  read-only
        STATUS  current
        DESCRIPTION
              "Inventory for the Line: This OID contains the inventory for the Line"
        ::= { pmc2002RinvLineEntry 2 }






--- *****************************************************
--- $$$$$$$$$$$$$$$$$$$$$$$$$$$$$$$$$$$$$$$$$$$$$$$$$$$$$
---     ALARMS
--- $$$$$$$$$$$$$$$$$$$$$$$$$$$$$$$$$$$$$$$$$$$$$$$$$$$$$
--- *****************************************************



--- *****************************************************
---     LEAF for the synthAlm0 article
--- *****************************************************
pmc2002AlmsynthAlm0 OBJECT IDENTIFIER ::= { pmc2002AlmOtherCrit 0 }




pmc2002AlmDefFuseB OBJECT-TYPE
	  SYNTAX EkiOnOff
	  MAX-ACCESS read-only
	  STATUS current
	  DESCRIPTION
        "
        Fuse B Fail :This OID indicates
        that the fuse of the power input
        B is in fail condition  <Help>
          Status of the Fuse B <Condtype>
        DEF_FUSE_B <Probcause> powerProblem
        (36) <Alarmtype> equipmentAlarm
        (5) <Polarity> (2)
        "
	  ::= { pmc2002AlmsynthAlm0 16 }



pmc2002AlmDefFuseA OBJECT-TYPE
	  SYNTAX EkiOnOff
	  MAX-ACCESS read-only
	  STATUS current
	  DESCRIPTION
        "
        Fuse A Fail :This OID indicates
        that the fuse of the power input
        A is in fail condition  <Help>
          Status of the Fuse A <Condtype>
        DEF_FUSE_A <Probcause> powerProblem
        (36) <Alarmtype> equipmentAlarm
        (5) <Polarity> (2)
        "
	  ::= { pmc2002AlmsynthAlm0 15 }



pmc2002AlmModGlobFail OBJECT-TYPE
	  SYNTAX EkiOnOff
	  MAX-ACCESS read-only
	  STATUS current
	  DESCRIPTION
        "
        Module Failure :This OID is set
        on detection of a failure originating
        from the PM <Condtype> MOD_GLOB_FAIL
        <Probcause> equipmentMalfunction
        (16) <Alarmtype> synthesisAlarm
        (12)  <Polarity> (2)
        "
	  ::= { pmc2002AlmsynthAlm0 9 }



pmc2002AlmLineLosSynth OBJECT-TYPE
	  SYNTAX EkiOnOff
	  MAX-ACCESS read-only
	  STATUS current
	  DESCRIPTION
        "
        20G Line Input Loss Of Signal
         :This OID indicates a loss of
         signal on the 20 Gb/s input.
         <Help>   This alarm indicates
         if an optical signal is detected
        on the line transceiver input <Condtype>
        LINE_LOS_SYNTH <Probcause> receiveFailure
        (41) <Alarmtype> physicalViolation
        (9) <Polarity> (2)
        "
	  ::= { pmc2002AlmsynthAlm0 2 }



pmc2002AlmLineFailSynth OBJECT-TYPE
	  SYNTAX EkiOnOff
	  MAX-ACCESS read-only
	  STATUS current
	  DESCRIPTION
        "
        20G Line Port Failure :This OID
        indicates a failure on the 20G
         line port <Condtype> LINE_FAIL_SYNTH
        <Probcause> equipmentMalfunction
        (16) <Alarmtype> equipmentAlarm
        (5) <Polarity> (2)
        "
	  ::= { pmc2002AlmsynthAlm0 1 }



--- *****************************************************
---     LEAF for the synthAlm2 article
--- *****************************************************
pmc2002AlmsynthAlm2 OBJECT IDENTIFIER ::= { pmc2002AlmOtherNurg 2 }




pmc2002AlmMaintenanceOn OBJECT-TYPE
	  SYNTAX EkiOnOff
	  MAX-ACCESS read-only
	  STATUS current
	  DESCRIPTION
        "
        Maintenance Mode :This OID indicates
        that the PM is in maintenance mode.
         <Help>  This alarm indicates that
        the maintenance mode is enabled
        on the PM <Condtype> MAINTENANCE_ON
        <Probcause> other (1) <Alarmtype>
        other (1) <Polarity> (2)
        "
	  ::= { pmc2002AlmsynthAlm2 5 }



pmc2002AlmCorrelatOff OBJECT-TYPE
	  SYNTAX EkiOnOff
	  MAX-ACCESS read-only
	  STATUS current
	  DESCRIPTION
        "
        Not Used :This OID, when set,
         indicates that alarm correlation
        is not being performed. <Condtype>
        CORRELAT_OFF <Probcause> other
         (1) <Alarmtype> other (1) <Polarity>
        (2)
        "
	  ::= { pmc2002AlmsynthAlm2 4 }



pmc2002AlmConfTableLoad OBJECT-TYPE
	  SYNTAX EkiOnOff
	  MAX-ACCESS read-only
	  STATUS current
	  DESCRIPTION
        "
        PM Configuration Load :This OID
         is at 1 during the loading of
         configuration tables in the modules
        RAM. <Condtype> CONF_TABLE_LOAD
        <Probcause> other (1) <Alarmtype>
        other (1) <Polarity> (2)
        "
	  ::= { pmc2002AlmsynthAlm2 3 }



pmc2002AlmInvUpload OBJECT-TYPE
	  SYNTAX EkiOnOff
	  MAX-ACCESS read-only
	  STATUS current
	  DESCRIPTION
        "
        Inventory Upload :This OID is
         at 1 during the uploading of PM
        inventory information. <Condtype>
        INV_UPLOAD <Probcause> other (1)
        <Alarmtype> other (1) <Polarity>
        (2)
        "
	  ::= { pmc2002AlmsynthAlm2 2 }



pmc2002AlmConfTableSave OBJECT-TYPE
	  SYNTAX EkiOnOff
	  MAX-ACCESS read-only
	  STATUS current
	  DESCRIPTION
        "
        PM Configuration Save :This OID
        is at 1 during the saving of a
         new configuration table in the
        module Flash memory. <Condtype>
        CONF_TABLE_SAVE <Probcause> other
        (1) <Alarmtype> other (1) <Polarity>
        (2)
        "
	  ::= { pmc2002AlmsynthAlm2 1 }



--- *********************************************************
---     TABLE for the pmc2002AlmsynthAlmLine articles
--- *********************************************************

pmc2002AlmsynthAlmLineTable OBJECT-TYPE
	SYNTAX  SEQUENCE OF Pmc2002AlmsynthAlmLineEntry
	MAX-ACCESS not-accessible
	STATUS current
	DESCRIPTION
        "
        List of pmc2002AlmsynthAlmLine
        Article
        "
	::= { pmc2002AlmLineCrit 7 }


pmc2002AlmsynthAlmLineEntry OBJECT-TYPE
	SYNTAX Pmc2002AlmsynthAlmLineEntry
	MAX-ACCESS not-accessible
	STATUS current
	DESCRIPTION
        "
        Row definition for the pmc2002AlmsynthAlmLine
        table
        "
	INDEX   { pmc2002AlmsynthAlmLineIndex }
	::= { pmc2002AlmsynthAlmLineTable 1 }


Pmc2002AlmsynthAlmLineEntry ::=
	SEQUENCE {
	pmc2002AlmsynthAlmLineIndex
		INTEGER,
	pmc2002AlmLineFailPortn
		EkiOnOff,
	pmc2002AlmLineDdmAlmPortn
		EkiOnOff,
	pmc2002AlmLineDdmWarningPortn
		EkiOnOff,
	pmc2002AlmLineUpRdiInsPortn
		EkiOnOff,
	pmc2002AlmLineLocalOosPortn
		EkiOnOff,
	pmc2002AlmLineXfpTxOffPortn
		EkiOnOff,
	pmc2002AlmLineHwFailPortn
		EkiOnOff,
	pmc2002AlmLineXfpInitNotComplPortn
		EkiOnOff,
	pmc2002AlmLineXfpAbsentPortn
		EkiOnOff
	}


pmc2002AlmsynthAlmLineIndex OBJECT-TYPE
	SYNTAX  INTEGER(0..128)
	MAX-ACCESS  read-only
	STATUS current
	DESCRIPTION
        "
        Index definition for the pmc2002AlmsynthAlmLine
        table
        "
	::= { pmc2002AlmsynthAlmLineEntry 1 }


pmc2002AlmLineFailPortn OBJECT-TYPE
	SYNTAX  EkiOnOff
	MAX-ACCESS read-only
	STATUS current
	DESCRIPTION
        "
        Subcarrier Port Failure :This
         OID indicates a failure on the
        line port <Condtype> LINE_FAIL
         <Probcause> equipmentMalfunction
        (16) <Alarmtype> synthesisAlarm
        (12)  <Polarity> (2)
        "
	::= { pmc2002AlmsynthAlmLineEntry 13 }


pmc2002AlmLineDdmAlmPortn OBJECT-TYPE
	SYNTAX  EkiOnOff
	MAX-ACCESS read-only
	STATUS current
	DESCRIPTION
        "
        Alarm On Subcarrier Optical Module
        DDM :This OID indicates an alarm
        is present coming out of Line optical
        interface DDM  <Help>  This alarm
        indicates if a DDM Alarm has been
        detected on the line transceiver
        <Condtype> LINE_DDM_ALM <Probcause>
        equipmentMalfunction (16) <Alarmtype>
        synthesisAlarm (12)  <Polarity>
        (2)
        "
	::= { pmc2002AlmsynthAlmLineEntry 11 }


pmc2002AlmLineDdmWarningPortn OBJECT-TYPE
	SYNTAX  EkiOnOff
	MAX-ACCESS read-only
	STATUS current
	DESCRIPTION
        "
        Warning On Subcarrier Optical
         Module DDM :This OID indicates
        a warning is present coming out
        of Line optical interface DDM
         <Help>  This alarm indicates if
        a DDM Warning has been detected
        on the line transceiver <Condtype>
        LINE_DDM_WARNING <Probcause> equipmentMalfunction
        (16) <Alarmtype> synthesisAlarm
        (12)  <Polarity> (2)
        "
	::= { pmc2002AlmsynthAlmLineEntry 10 }


pmc2002AlmLineUpRdiInsPortn OBJECT-TYPE
	SYNTAX  EkiOnOff
	MAX-ACCESS read-only
	STATUS current
	DESCRIPTION
        "
        MS-RDI/L-RDI Inserted On Subcarrier
        :This OID indicates an upstream
        RDI has been inserted in the outgoing
        10 Gb/s signal.   <Help>  This
         status indicates if a MS-RDI/L-RDI
        is currently inserted on the line
        interface. <Condtype> LINE_UP_RDI_INS
        <Probcause> informationalStatus(1000)
        <Alarmtype> other (1) <Polarity>
        (2)
        "
	::= { pmc2002AlmsynthAlmLineEntry 9 }


pmc2002AlmLineLocalOosPortn OBJECT-TYPE
	SYNTAX  EkiOnOff
	MAX-ACCESS read-only
	STATUS current
	DESCRIPTION
        "
        Subcarrier In Service :This OID
        indicates that the Line port is
        In Service (1) of Out or Service
        (2)  <Help>  This status indicates
        if the line port is in service
         <Condtype> LINE_LOCAL_OOS <Probcause>
        informationalStatus(1000) <Alarmtype>
        other (1) <Polarity> (2)
        "
	::= { pmc2002AlmsynthAlmLineEntry 7 }


pmc2002AlmLineXfpTxOffPortn OBJECT-TYPE
	SYNTAX  EkiOnOff
	MAX-ACCESS read-only
	STATUS current
	DESCRIPTION
        "
        Subcarrier Optical Module Laser
        Shutdown :This OID indicates the
        line optical output power is on
         <Help>  This status indicates
         if the line transceiver laser
         is ON or OFF <Condtype> LINE_XFP_TX_OFF
        <Probcause> other (1) <Alarmtype>
        equipmentAlarm (5) <Polarity> (2)
        "
	::= { pmc2002AlmsynthAlmLineEntry 6 }


pmc2002AlmLineHwFailPortn OBJECT-TYPE
	SYNTAX  EkiOnOff
	MAX-ACCESS read-only
	STATUS current
	DESCRIPTION
        "
        Subcarrier Port HW Failure :This
        OID indicates a failure on line
        port, most probably caused by a
        HW issue <Condtype> LINE_HW_FAIL
        <Probcause> equipmentMalfunction
        (16) <Alarmtype> synthesisAlarm
        (12)  <Polarity> (2)
        "
	::= { pmc2002AlmsynthAlmLineEntry 5 }


pmc2002AlmLineXfpInitNotComplPortn OBJECT-TYPE
	SYNTAX  EkiOnOff
	MAX-ACCESS read-only
	STATUS current
	DESCRIPTION
        "
        Subcarrier Optical Module Ready
        :This OID indicates that the line
        optical interface (XFP or OTX)
         is not operational.  <Help>  This
        status indicates if the line transceiver
        has been correctly initialized
         <Condtype> LINE_XFP_INIT_NOT_COMPL
        <Probcause> equipmentMalfunction
        (16) <Alarmtype> equipmentAlarm
        (5) <Polarity> (2) <Event> ObjectCDINV
        "
	::= { pmc2002AlmsynthAlmLineEntry 3 }


pmc2002AlmLineXfpAbsentPortn OBJECT-TYPE
	SYNTAX  EkiOnOff
	MAX-ACCESS read-only
	STATUS current
	DESCRIPTION
        "
        Subcarrier Optical Module Absent
        :This OID indicates that the line
        optical interface (XFP or OTX)
         is not plugged in.  <Help>  This
        alarm indicates if the line transceiver
        is present. <Condtype> LINE_XFP_ABSENT
        <Probcause> inputOutputDeviceError
        (24) <Alarmtype> equipmentAlarm
        (5) <Polarity> (2) <Event> ObjectCDINV
        "
	::= { pmc2002AlmsynthAlmLineEntry 2 }


--- *********************************************************
---     TABLE for the pmc2002AlmsynthAlmPort articles
--- *********************************************************

pmc2002AlmsynthAlmPortTable OBJECT-TYPE
	SYNTAX  SEQUENCE OF Pmc2002AlmsynthAlmPortEntry
	MAX-ACCESS not-accessible
	STATUS current
	DESCRIPTION
        "
        List of pmc2002AlmsynthAlmPort
        Article
        "
	::= { pmc2002AlmClientCrit 8 }


pmc2002AlmsynthAlmPortEntry OBJECT-TYPE
	SYNTAX Pmc2002AlmsynthAlmPortEntry
	MAX-ACCESS not-accessible
	STATUS current
	DESCRIPTION
        "
        Row definition for the pmc2002AlmsynthAlmPort
        table
        "
	INDEX   { pmc2002AlmsynthAlmPortIndex }
	::= { pmc2002AlmsynthAlmPortTable 1 }


Pmc2002AlmsynthAlmPortEntry ::=
	SEQUENCE {
	pmc2002AlmsynthAlmPortIndex
		INTEGER,
	pmc2002AlmClientUpCsfPortn
		EkiOnOff,
	pmc2002AlmClientFailPortn
		EkiOnOff,
	pmc2002AlmClientSfpDdmAlmPortn
		EkiOnOff,
	pmc2002AlmClientSfpDdmWarningPortn
		EkiOnOff,
	pmc2002AlmClientDwCaisPortn
		EkiOnOff,
	pmc2002AlmClientLocalOosPortn
		EkiOnOff,
	pmc2002AlmClientDwLsdPortn
		EkiOnOff,
	pmc2002AlmClientHwFailPortn
		EkiOnOff,
	pmc2002AlmClientDdmAbsentPortn
		EkiOnOff,
	pmc2002AlmClientSfpAbsentPortn
		EkiOnOff
	}


pmc2002AlmsynthAlmPortIndex OBJECT-TYPE
	SYNTAX  INTEGER(0..128)
	MAX-ACCESS  read-only
	STATUS current
	DESCRIPTION
        "
        Index definition for the pmc2002AlmsynthAlmPort
        table
        "
	::= { pmc2002AlmsynthAlmPortEntry 1 }


pmc2002AlmClientUpCsfPortn OBJECT-TYPE
	SYNTAX  EkiOnOff
	MAX-ACCESS read-only
	STATUS current
	DESCRIPTION
        "
        Client Signal Fail Inserted :This
        OID indicates a CSF has been inserted
        in the upstream client port.  <Help>
         This status indicates if a Client
        Signal Fail is currently inserted
        on the line signal for this client
        port <Condtype> CLIENT_UP_CSF <Probcause>
        informationalStatus(1000) <Alarmtype>
        other (1) <Polarity> (2)
        "
	::= { pmc2002AlmsynthAlmPortEntry 17 }


pmc2002AlmClientFailPortn OBJECT-TYPE
	SYNTAX  EkiOnOff
	MAX-ACCESS read-only
	STATUS current
	DESCRIPTION
        "
        Client Access Fail :This OID indicates
        a failure on the Client port <Condtype>
        CLIENT_FAIL <Probcause> equipmentMalfunction
        (16) <Alarmtype> synthesisAlarm
        (12)  <Polarity> (2)
        "
	::= { pmc2002AlmsynthAlmPortEntry 13 }


pmc2002AlmClientSfpDdmAlmPortn OBJECT-TYPE
	SYNTAX  EkiOnOff
	MAX-ACCESS read-only
	STATUS current
	DESCRIPTION
        "
        Alarm On Client SFP+ DDM :This
        OID indicates an alarm is being
        received from the Client XFP DDM
         <Help>  This alarm indicates if
        a DDM Alarm has been detected on
        the client transceiver <Condtype>
        CLIENT_SFP_DDM_ALM <Probcause>
         equipmentMalfunction (16) <Alarmtype>
        synthesisAlarm (12)  <Polarity>
        (2)
        "
	::= { pmc2002AlmsynthAlmPortEntry 11 }


pmc2002AlmClientSfpDdmWarningPortn OBJECT-TYPE
	SYNTAX  EkiOnOff
	MAX-ACCESS read-only
	STATUS current
	DESCRIPTION
        "
        Warning On Client SFP+ DDM :This
        OID indicates a warning is being
        received from the Client XFP DDM
         <Help>  This alarm indicates if
        a DDM Warning has been detected
        on the client transceiver <Condtype>
        CLIENT_SFP_DDM_WARNING <Probcause>
        equipmentMalfunction (16) <Alarmtype>
        synthesisAlarm (12)  <Polarity>
        (2)
        "
	::= { pmc2002AlmsynthAlmPortEntry 10 }


pmc2002AlmClientDwCaisPortn OBJECT-TYPE
	SYNTAX  EkiOnOff
	MAX-ACCESS read-only
	STATUS current
	DESCRIPTION
        "
        Client AIS Inserted :This OID
         indicates a CAIS has been inserted
        on the output client port.  <Help>
         This status indicates if a Client
        Alarm Indication Signal is currently
        inserted on the client interface
        <Condtype> CLIENT_DW_CAIS <Probcause>
        informationalStatus(1000) <Alarmtype>
        other (1) <Polarity> (2)
        "
	::= { pmc2002AlmsynthAlmPortEntry 9 }


pmc2002AlmClientLocalOosPortn OBJECT-TYPE
	SYNTAX  EkiOnOff
	MAX-ACCESS read-only
	STATUS current
	DESCRIPTION
        "
        Local Client Port In Service :This
        OID indicates that the local Client
        port is In Service (1) or Out of
        Service (2)  <Help>  This status
        indicates if the local client port
        is in service <Condtype> CLIENT_LOCAL_OOS
        <Probcause> informationalStatus(1000)
        <Alarmtype> other (1) <Polarity>
        (2)
        "
	::= { pmc2002AlmsynthAlmPortEntry 7 }


pmc2002AlmClientDwLsdPortn OBJECT-TYPE
	SYNTAX  EkiOnOff
	MAX-ACCESS read-only
	STATUS current
	DESCRIPTION
        "
        Client SFP+ Laser Shutdown :This
        OID indicates the Client XFP transmitter
        output is ON.   <Help>  This status
        indicates if the client transceiver
        laser is ON or OFF <Condtype> CLIENT_DW_LSD
        <Probcause> other (1) <Alarmtype>
        equipmentAlarm (5) <Polarity> (2)
        "
	::= { pmc2002AlmsynthAlmPortEntry 6 }


pmc2002AlmClientHwFailPortn OBJECT-TYPE
	SYNTAX  EkiOnOff
	MAX-ACCESS read-only
	STATUS current
	DESCRIPTION
        "
        Client HW Fail :This OID indicates
        a failure on client port, most
         probably caused by a HW issue.
        <Condtype> CLIENT_HW_FAIL <Probcause>
        equipmentMalfunction (16) <Alarmtype>
        synthesisAlarm (12)  <Polarity>
        (2)
        "
	::= { pmc2002AlmsynthAlmPortEntry 5 }


pmc2002AlmClientDdmAbsentPortn OBJECT-TYPE
	SYNTAX  EkiOnOff
	MAX-ACCESS read-only
	STATUS current
	DESCRIPTION
        "
        DDM Supported On Client SFP+ :This
        OID indicates that the client optical
        interface (XFP or OTX) is not operational.
         <Help>  This status indicates
         if the client transceiver has
         been correctly initialized <Condtype>
        CLIENT_DDM_ABSENT <Probcause> equipmentMalfunction
        (16) <Alarmtype> equipmentAlarm
        (5) <Polarity> (2)
        "
	::= { pmc2002AlmsynthAlmPortEntry 3 }


pmc2002AlmClientSfpAbsentPortn OBJECT-TYPE
	SYNTAX  EkiOnOff
	MAX-ACCESS read-only
	STATUS current
	DESCRIPTION
        "
        Client Optical Module Absent :This
        OID indicates that the XFP module
        is not present in the client port.
         <Help>  This alarm indicates if
        the client transceiver is present.
        <Condtype> CLIENT_SFP_ABSENT <Probcause>
        inputOutputDeviceError (24) <Alarmtype>
        equipmentAlarm (5) <Polarity> (2)
        <Event> ObjectCDINV
        "
	::= { pmc2002AlmsynthAlmPortEntry 2 }


--- *********************************************************
---     TABLE for the pmc2002AlmclientAccessioAlm articles
--- *********************************************************

pmc2002AlmclientAccessioAlmTable OBJECT-TYPE
	SYNTAX  SEQUENCE OF Pmc2002AlmclientAccessioAlmEntry
	MAX-ACCESS not-accessible
	STATUS current
	DESCRIPTION
        "
        List of pmc2002AlmclientAccessioAlm
        Article
        "
	::= { pmc2002AlmClientCrit 16 }


pmc2002AlmclientAccessioAlmEntry OBJECT-TYPE
	SYNTAX Pmc2002AlmclientAccessioAlmEntry
	MAX-ACCESS not-accessible
	STATUS current
	DESCRIPTION
        "
        Row definition for the pmc2002AlmclientAccessioAlm
        table
        "
	INDEX   { pmc2002AlmclientAccessioAlmIndex }
	::= { pmc2002AlmclientAccessioAlmTable 1 }


Pmc2002AlmclientAccessioAlmEntry ::=
	SEQUENCE {
	pmc2002AlmclientAccessioAlmIndex
		INTEGER,
	pmc2002AlmClientUpLosPortn
		EkiOnOff,
	pmc2002AlmClientDwLasFailPortn
		EkiOnOff
	}


pmc2002AlmclientAccessioAlmIndex OBJECT-TYPE
	SYNTAX  INTEGER(0..128)
	MAX-ACCESS  read-only
	STATUS current
	DESCRIPTION
        "
        Index definition for the pmc2002AlmclientAccessioAlm
        table
        "
	::= { pmc2002AlmclientAccessioAlmEntry 1 }


pmc2002AlmClientUpLosPortn OBJECT-TYPE
	SYNTAX  EkiOnOff
	MAX-ACCESS read-only
	STATUS current
	DESCRIPTION
        "
        Client Input Loss Of Signal :This
        OID indicates that no signal is
        present on the XFP of the client
        port  <Help>  This alarm indicates
        if an optical signal is detected
        on the client transceiver input
        <Condtype> CLIENT_UP_LOS <Probcause>
        receiveFailure (41) <Alarmtype>
        physicalViolation (9) <Polarity>
        (2)
        "
	::= { pmc2002AlmclientAccessioAlmEntry 5 }


pmc2002AlmClientDwLasFailPortn OBJECT-TYPE
	SYNTAX  EkiOnOff
	MAX-ACCESS read-only
	STATUS current
	DESCRIPTION
        "
        Client XFP Tx Failed :This OID
        indicates that the transmitter
         fails for the XFP plugged into
        the client port (this alarm reports
        the transmitter failure alarm generated
        by the XFPs) <Condtype> CLIENT_DW_LAS_FAIL
        <Probcause> transmitterFailure
         (56) <Alarmtype> equipmentAlarm
        (5) <Polarity> (2)
        "
	::= { pmc2002AlmclientAccessioAlmEntry 2 }


--- *********************************************************
---     TABLE for the pmc2002AlmclientXfpAlarm1 articles
--- *********************************************************

pmc2002AlmclientXfpAlarm1Table OBJECT-TYPE
	SYNTAX  SEQUENCE OF Pmc2002AlmclientXfpAlarm1Entry
	MAX-ACCESS not-accessible
	STATUS current
	DESCRIPTION
        "
        List of pmc2002AlmclientXfpAlarm1
        Article
        "
	::= { pmc2002AlmClientUrg 32 }


pmc2002AlmclientXfpAlarm1Entry OBJECT-TYPE
	SYNTAX Pmc2002AlmclientXfpAlarm1Entry
	MAX-ACCESS not-accessible
	STATUS current
	DESCRIPTION
        "
        Row definition for the pmc2002AlmclientXfpAlarm1
        table
        "
	INDEX   { pmc2002AlmclientXfpAlarm1Index }
	::= { pmc2002AlmclientXfpAlarm1Table 1 }


Pmc2002AlmclientXfpAlarm1Entry ::=
	SEQUENCE {
	pmc2002AlmclientXfpAlarm1Index
		INTEGER,
	pmc2002AlmClientRxPowerHighAlarmPortn
		EkiOnOff,
	pmc2002AlmClientRxPowerLowAlarmPortn
		EkiOnOff,
	pmc2002AlmClientTempHighAlarmPortn
		EkiOnOff,
	pmc2002AlmClientTempLowAlarmPortn
		EkiOnOff,
	pmc2002AlmClientTxBiasHighAlarmPortn
		EkiOnOff,
	pmc2002AlmClientTxBiasLowAlarmPortn
		EkiOnOff,
	pmc2002AlmClientTxPowerHighAlarmPortn
		EkiOnOff,
	pmc2002AlmClientTxPowerLowAlarmPortn
		EkiOnOff
	}


pmc2002AlmclientXfpAlarm1Index OBJECT-TYPE
	SYNTAX  INTEGER(0..128)
	MAX-ACCESS  read-only
	STATUS current
	DESCRIPTION
        "
        Index definition for the pmc2002AlmclientXfpAlarm1
        table
        "
	::= { pmc2002AlmclientXfpAlarm1Entry 1 }


pmc2002AlmClientRxPowerHighAlarmPortn OBJECT-TYPE
	SYNTAX  EkiOnOff
	MAX-ACCESS read-only
	STATUS current
	DESCRIPTION
        "
        Client Optical Rx Power High :Alarm
        indicating that the XFP received
        optical power is higher than the
        threshold value written in the
         XFP EEPROM <Condtype> CLIENT_RX_POWER_HIGH_ALARM
        <Probcause> receiveFailure (41)
        <Alarmtype> equipmentAlarm (5)
         <Polarity> (2)
        "
	::= { pmc2002AlmclientXfpAlarm1Entry 17 }


pmc2002AlmClientRxPowerLowAlarmPortn OBJECT-TYPE
	SYNTAX  EkiOnOff
	MAX-ACCESS read-only
	STATUS current
	DESCRIPTION
        "
        Client Optical Rx Power Low :Alarm
        indicating that the XFP received
        optical power is lower than the
        threshold value written in the
         XFP EEPROM  <Condtype> CLIENT_RX_POWER_LOW_ALARM
        <Probcause> receiveFailure (41)
        <Alarmtype> equipmentAlarm (5)
         <Polarity> (2)
        "
	::= { pmc2002AlmclientXfpAlarm1Entry 16 }


pmc2002AlmClientTempHighAlarmPortn OBJECT-TYPE
	SYNTAX  EkiOnOff
	MAX-ACCESS read-only
	STATUS current
	DESCRIPTION
        "
        Client Transceiver Temp High :Alarm
        indicating that the XFP/OTX temperature
        is higher than the threshold value
        written in the XFP EEPROM <Condtype>
        CLIENT_TEMP_HIGH_ALARM <Probcause>
        temperatureUnacceptable (51) <Alarmtype>
        equipmentAlarm (5) <Polarity> (2)
        "
	::= { pmc2002AlmclientXfpAlarm1Entry 9 }


pmc2002AlmClientTempLowAlarmPortn OBJECT-TYPE
	SYNTAX  EkiOnOff
	MAX-ACCESS read-only
	STATUS current
	DESCRIPTION
        "
        Client Transceiver Temp Low :Alarm
        indicating that the XFP/OTX temperature
        is lower than the threshold value
        written in the XFP/OTX EEPROM <Condtype>
        CLIENT_TEMP_LOW_ALARM <Probcause>
        temperatureUnacceptable (51) <Alarmtype>
        equipmentAlarm (5) <Polarity> (2)
        "
	::= { pmc2002AlmclientXfpAlarm1Entry 8 }


pmc2002AlmClientTxBiasHighAlarmPortn OBJECT-TYPE
	SYNTAX  EkiOnOff
	MAX-ACCESS read-only
	STATUS current
	DESCRIPTION
        "
        Client Transceiver Bias High :Alarm
        indicating that the XFP/OTX transmitter
        laser bias current is higher than
        the threshold value written in
         the XFP EEPROM <Condtype> CLIENT_TX_BIAS_HIGH_ALARM
        <Probcause> transmitterFailure
         (56) <Alarmtype> equipmentAlarm
        (5) <Polarity> (2)
        "
	::= { pmc2002AlmclientXfpAlarm1Entry 5 }


pmc2002AlmClientTxBiasLowAlarmPortn OBJECT-TYPE
	SYNTAX  EkiOnOff
	MAX-ACCESS read-only
	STATUS current
	DESCRIPTION
        "
        Client Transceiver Bias Low :Alarm
        indicating that the XFP/OTX transmitter
        laser bias current is lower than
        the threshold value written in
         the XFP/OTX EEPROM <Condtype>
         CLIENT_TX_BIAS_LOW_ALARM <Probcause>
        transmitterFailure (56) <Alarmtype>
        equipmentAlarm (5) <Polarity> (2)
        "
	::= { pmc2002AlmclientXfpAlarm1Entry 4 }


pmc2002AlmClientTxPowerHighAlarmPortn OBJECT-TYPE
	SYNTAX  EkiOnOff
	MAX-ACCESS read-only
	STATUS current
	DESCRIPTION
        "
        Client Optical Tx Power High :Alarm
        indicating that the XFP/OTX transmitter
        transmitter output power is higher
        than the threshold value written
        in the XFP EEPROM <Condtype> CLIENT_TX_POWER_HIGH_ALARM
        <Probcause> transmitterFailure
         (56) <Alarmtype> equipmentAlarm
        (5) <Polarity> (2)
        "
	::= { pmc2002AlmclientXfpAlarm1Entry 3 }


pmc2002AlmClientTxPowerLowAlarmPortn OBJECT-TYPE
	SYNTAX  EkiOnOff
	MAX-ACCESS read-only
	STATUS current
	DESCRIPTION
        "
        Client Optical Tx Power Low :Alarm
        indicating that the XFP/OTX transmitter
        transmitter output power is lower
        than the threshold value written
        in the XFP/OTX EEPROM <Condtype>
        CLIENT_TX_POWER_LOW_ALARM <Probcause>
        transmitterFailure (56) <Alarmtype>
        equipmentAlarm (5) <Polarity> (2)
        "
	::= { pmc2002AlmclientXfpAlarm1Entry 2 }


--- *********************************************************
---     TABLE for the pmc2002AlmclientXfpAlarm2 articles
--- *********************************************************

pmc2002AlmclientXfpAlarm2Table OBJECT-TYPE
	SYNTAX  SEQUENCE OF Pmc2002AlmclientXfpAlarm2Entry
	MAX-ACCESS not-accessible
	STATUS current
	DESCRIPTION
        "
        List of pmc2002AlmclientXfpAlarm2
        Article
        "
	::= { pmc2002AlmClientCrit 40 }


pmc2002AlmclientXfpAlarm2Entry OBJECT-TYPE
	SYNTAX Pmc2002AlmclientXfpAlarm2Entry
	MAX-ACCESS not-accessible
	STATUS current
	DESCRIPTION
        "
        Row definition for the pmc2002AlmclientXfpAlarm2
        table
        "
	INDEX   { pmc2002AlmclientXfpAlarm2Index }
	::= { pmc2002AlmclientXfpAlarm2Table 1 }


Pmc2002AlmclientXfpAlarm2Entry ::=
	SEQUENCE {
	pmc2002AlmclientXfpAlarm2Index
		INTEGER,
	pmc2002AlmClientApdSupplyFaultPortn
		EkiOnOff,
	pmc2002AlmClientTecFaultPortn
		EkiOnOff,
	pmc2002AlmClientWavelengthUnlockedPortn
		EkiOnOff,
	pmc2002AlmClientTxNrPortn
		EkiOnOff,
	pmc2002AlmClientTxFaultPortn
		EkiOnOff,
	pmc2002AlmClientTxCdrNotLockedPortn
		EkiOnOff,
	pmc2002AlmClientRxNrPortn
		EkiOnOff,
	pmc2002AlmClientRxCdrNotLockedPortn
		EkiOnOff,
	pmc2002AlmClientModNrPortn
		EkiOnOff
	}


pmc2002AlmclientXfpAlarm2Index OBJECT-TYPE
	SYNTAX  INTEGER(0..128)
	MAX-ACCESS  read-only
	STATUS current
	DESCRIPTION
        "
        Index definition for the pmc2002AlmclientXfpAlarm2
        table
        "
	::= { pmc2002AlmclientXfpAlarm2Entry 1 }


pmc2002AlmClientApdSupplyFaultPortn OBJECT-TYPE
	SYNTAX  EkiOnOff
	MAX-ACCESS read-only
	STATUS current
	DESCRIPTION
        "
        Client Rx Photodiode Power Failed
        :This OID indicates a failure on
        the APD power supply  <Help>  This
        alarm indicates if the APD power
        supply is in fail condition <Condtype>
        CLIENT_APD_SUPPLY_FAULT <Probcause>
        receiverFailure (42) <Alarmtype>
        equipmentAlarm (5) <Polarity> (2)
        "
	::= { pmc2002AlmclientXfpAlarm2Entry 17 }


pmc2002AlmClientTecFaultPortn OBJECT-TYPE
	SYNTAX  EkiOnOff
	MAX-ACCESS read-only
	STATUS current
	DESCRIPTION
        "
        Client Optical Tx Temp Regul.
         Failed :This OID indicates a failure
        on the TEC module  <Help>  This
        alarm indicates if the TEC of the
        Client transceiver is in fail condition
        <Condtype> CLIENT_TEC_FAULT <Probcause>
        transmitterFailure (56) <Alarmtype>
        equipmentAlarm (5) <Polarity> (2)
        "
	::= { pmc2002AlmclientXfpAlarm2Entry 16 }


pmc2002AlmClientWavelengthUnlockedPortn OBJECT-TYPE
	SYNTAX  EkiOnOff
	MAX-ACCESS read-only
	STATUS current
	DESCRIPTION
        "
        Client Optical Tx Wavelength Unlocked
        :This OID indicates that the wavelength
        error is exceeding the manufacturer
        tolerance  <Help>  This alarm indicates
        if the wavelenght of the Client
        transceiver is locked <Condtype>
        CLIENT_WAVELENGTH_UNLOCKED <Probcause>
        transmitterFailure (56) <Alarmtype>
        equipmentAlarm (5) <Polarity> (2)
        "
	::= { pmc2002AlmclientXfpAlarm2Entry 15 }


pmc2002AlmClientTxNrPortn OBJECT-TYPE
	SYNTAX  EkiOnOff
	MAX-ACCESS read-only
	STATUS current
	DESCRIPTION
        "
        Client Optical Tx Not Ready :This
        OID indicates a condition has arisen
        leading to invalid data on the
         transmitting side  <Help>  This
        alarm indicates if the Tx part
         of the Client transceiver is ready
        <Condtype> CLIENT_TX_NR <Probcause>
        transmitterFailure (56) <Alarmtype>
        equipmentAlarm (5) <Polarity> (2)
        "
	::= { pmc2002AlmclientXfpAlarm2Entry 9 }


pmc2002AlmClientTxFaultPortn OBJECT-TYPE
	SYNTAX  EkiOnOff
	MAX-ACCESS read-only
	STATUS current
	DESCRIPTION
        "
        Client Optical Tx Failure :This
        OID indicates a fault condition
        on the laser detected by the safety
        syste  <Help>  This alarm indicates
        if the laser of the Client transceiver
        is in fail condition <Condtype>
        CLIENT_TX_FAULT <Probcause> transmitterFailure
        (56) <Alarmtype> equipmentAlarm
        (5) <Polarity> (2)
        "
	::= { pmc2002AlmclientXfpAlarm2Entry 8 }


pmc2002AlmClientTxCdrNotLockedPortn OBJECT-TYPE
	SYNTAX  EkiOnOff
	MAX-ACCESS read-only
	STATUS current
	DESCRIPTION
        "
        Client Optical Tx CDR Unlocked
        :This OID indicates a loss of lock
        on the transmitting side CDR has
        been detected.  <Help>  This alarm
        indicates if the Tx CDR is locked
        in the Client transceiver <Condtype>
        CLIENT_TX_CDR_NOT_LOCKED1 <Probcause>
        transmitterFailure (56) <Alarmtype>
        equipmentAlarm (5) <Polarity> (2)
        "
	::= { pmc2002AlmclientXfpAlarm2Entry 7 }


pmc2002AlmClientRxNrPortn OBJECT-TYPE
	SYNTAX  EkiOnOff
	MAX-ACCESS read-only
	STATUS current
	DESCRIPTION
        "
        Client Optical Rx Not Ready :This
        OID indicates that a condition
         has arisen leading to invalid
         data on the receiving side.  <Help>
         This alarm indicates if the Rx
        part of the Client transceiver
         is ready <Condtype> CLIENT_RX_NR
        <Probcause> receiveFailure (41)
        <Alarmtype> equipmentAlarm (5)
         <Polarity> (2)
        "
	::= { pmc2002AlmclientXfpAlarm2Entry 6 }


pmc2002AlmClientRxCdrNotLockedPortn OBJECT-TYPE
	SYNTAX  EkiOnOff
	MAX-ACCESS read-only
	STATUS current
	DESCRIPTION
        "
        Client Optical Rx CDR Unlocked
        :This OID indicates that a loss
        of lock on the receiving side CDR
        has been detected  <Help>  This
        alarm indicates if the Rx CDR is
        locked in the Client transceiver
        <Condtype> CLIENT_RX_CDR_NOT_LOCKED1
        <Probcause> receiveFailure (41)
        <Alarmtype> equipmentAlarm (5)
         <Polarity> (2)
        "
	::= { pmc2002AlmclientXfpAlarm2Entry 4 }


pmc2002AlmClientModNrPortn OBJECT-TYPE
	SYNTAX  EkiOnOff
	MAX-ACCESS read-only
	STATUS current
	DESCRIPTION
        "
        Client Optical Module Not Ready
        :This OID indicates that the module
        is unable to determine correct
         data.  <Help>  This alarm indicates
        if the Client transceiver is ready
        <Condtype> CLIENT_MOD_NR <Probcause>
        receiveFailure (41) <Alarmtype>
        equipmentAlarm (5) <Polarity> (2)
        "
	::= { pmc2002AlmclientXfpAlarm2Entry 3 }


--- *********************************************************
---     TABLE for the pmc2002AlmclientXfpWarnings articles
--- *********************************************************

pmc2002AlmclientXfpWarningsTable OBJECT-TYPE
	SYNTAX  SEQUENCE OF Pmc2002AlmclientXfpWarningsEntry
	MAX-ACCESS not-accessible
	STATUS current
	DESCRIPTION
        "
        List of pmc2002AlmclientXfpWarnings
        Article
        "
	::= { pmc2002AlmClientNurg 48 }


pmc2002AlmclientXfpWarningsEntry OBJECT-TYPE
	SYNTAX Pmc2002AlmclientXfpWarningsEntry
	MAX-ACCESS not-accessible
	STATUS current
	DESCRIPTION
        "
        Row definition for the pmc2002AlmclientXfpWarnings
        table
        "
	INDEX   { pmc2002AlmclientXfpWarningsIndex }
	::= { pmc2002AlmclientXfpWarningsTable 1 }


Pmc2002AlmclientXfpWarningsEntry ::=
	SEQUENCE {
	pmc2002AlmclientXfpWarningsIndex
		INTEGER,
	pmc2002AlmClientRxPowerHighWarningPortn
		EkiOnOff,
	pmc2002AlmClientRxPowerLowWarningPortn
		EkiOnOff,
	pmc2002AlmClientTempHighWarningPortn
		EkiOnOff,
	pmc2002AlmClientTempLowWarningPortn
		EkiOnOff,
	pmc2002AlmClientTxBiasHighWarningPortn
		EkiOnOff,
	pmc2002AlmClientTxBiasLowWarningPortn
		EkiOnOff,
	pmc2002AlmClientTxPowerHighWarningPortn
		EkiOnOff,
	pmc2002AlmClientTxPowerLowWarningPortn
		EkiOnOff
	}


pmc2002AlmclientXfpWarningsIndex OBJECT-TYPE
	SYNTAX  INTEGER(0..128)
	MAX-ACCESS  read-only
	STATUS current
	DESCRIPTION
        "
        Index definition for the pmc2002AlmclientXfpWarnings
        table
        "
	::= { pmc2002AlmclientXfpWarningsEntry 1 }


pmc2002AlmClientRxPowerHighWarningPortn OBJECT-TYPE
	SYNTAX  EkiOnOff
	MAX-ACCESS read-only
	STATUS current
	DESCRIPTION
        "
        Client Optical Rx Pwr High Warning
        :Warning indicating that the XFP
        received optical power is higher
        than the threshold value written
        in the XFP EEPROM <Condtype> CLIENT_RX_POWER_HIGH_WARNING
        <Probcause> receiveFailure (41)
        <Alarmtype> equipmentAlarm (5)
         <Polarity> (2)
        "
	::= { pmc2002AlmclientXfpWarningsEntry 17 }


pmc2002AlmClientRxPowerLowWarningPortn OBJECT-TYPE
	SYNTAX  EkiOnOff
	MAX-ACCESS read-only
	STATUS current
	DESCRIPTION
        "
        Client Optical Rx Pwr Low Warning
        :Warning indicating that the XFP
        received optical power is lower
        than the threshold value written
        in the XFP EEPROM  <Condtype> CLIENT_RX_POWER_LOW_WARNING
        <Probcause> receiveFailure (41)
        <Alarmtype> equipmentAlarm (5)
         <Polarity> (2)
        "
	::= { pmc2002AlmclientXfpWarningsEntry 16 }


pmc2002AlmClientTempHighWarningPortn OBJECT-TYPE
	SYNTAX  EkiOnOff
	MAX-ACCESS read-only
	STATUS current
	DESCRIPTION
        "
        Client Transceiver Temp High Warning
        :Warning indicating that the XFP/OTX
        temperature is higher than the
         threshold value written in the
        XFP EEPROM <Condtype> CLIENT_TEMP_HIGH_WARNING
        <Probcause> temperatureUnacceptable
        (51) <Alarmtype> equipmentAlarm
        (5) <Polarity> (2)
        "
	::= { pmc2002AlmclientXfpWarningsEntry 9 }


pmc2002AlmClientTempLowWarningPortn OBJECT-TYPE
	SYNTAX  EkiOnOff
	MAX-ACCESS read-only
	STATUS current
	DESCRIPTION
        "
        Client Transceiver Temp Low Warning
        :Warning indicating that the XFP/OTX
        temperature is lower than the threshold
        value written in the XFP/OTX EEPROM
        <Condtype> CLIENT_TEMP_LOW_WARNING
        <Probcause> temperatureUnacceptable
        (51) <Alarmtype> equipmentAlarm
        (5) <Polarity> (2)
        "
	::= { pmc2002AlmclientXfpWarningsEntry 8 }


pmc2002AlmClientTxBiasHighWarningPortn OBJECT-TYPE
	SYNTAX  EkiOnOff
	MAX-ACCESS read-only
	STATUS current
	DESCRIPTION
        "
        Client Transceiver Bias High Warning
        :Warning indicating that the XFP/OTX
        transmitter laser bias current
         is higher than the threshold value
        written in the XFP EEPROM <Condtype>
        CLIENT_TX_BIAS_HIGH_WARNING <Probcause>
        transmitterFailure (56) <Alarmtype>
        equipmentAlarm (5) <Polarity> (2)
        "
	::= { pmc2002AlmclientXfpWarningsEntry 5 }


pmc2002AlmClientTxBiasLowWarningPortn OBJECT-TYPE
	SYNTAX  EkiOnOff
	MAX-ACCESS read-only
	STATUS current
	DESCRIPTION
        "
        Client Transceiver Bias Low Warning
        :Warning indicating that the XFP/OTX
        transmitter laser bias current
         is lower than the threshold value
        written in the XFP/OTX EEPROM <Condtype>
        CLIENT_TX_BIAS_LOW_WARNING <Probcause>
        transmitterFailure (56) <Alarmtype>
        equipmentAlarm (5) <Polarity> (2)
        "
	::= { pmc2002AlmclientXfpWarningsEntry 4 }


pmc2002AlmClientTxPowerHighWarningPortn OBJECT-TYPE
	SYNTAX  EkiOnOff
	MAX-ACCESS read-only
	STATUS current
	DESCRIPTION
        "
        Client Optical Tx Pwr High Warning
        :Warning indicating that the XFP/OTX
        transmitter transmitter output
         power is higher than the threshold
        value written in the XFP EEPROM
        <Condtype> CLIENT_TX_POWER_HIGH_WARNING
        <Probcause> transmitterFailure
         (56) <Alarmtype> equipmentAlarm
        (5) <Polarity> (2)
        "
	::= { pmc2002AlmclientXfpWarningsEntry 3 }


pmc2002AlmClientTxPowerLowWarningPortn OBJECT-TYPE
	SYNTAX  EkiOnOff
	MAX-ACCESS read-only
	STATUS current
	DESCRIPTION
        "
        Client Optical Tx Pwr Low Warning
        :Warning indicating that the XFP/OTX
        transmitter transmitter output
         power is lower than the threshold
        value written in the XFP/OTX EEPROM
        <Condtype> CLIENT_TX_POWER_LOW_WARNING
        <Probcause> transmitterFailure
         (56) <Alarmtype> equipmentAlarm
        (5) <Polarity> (2)
        "
	::= { pmc2002AlmclientXfpWarningsEntry 2 }


--- *********************************************************
---     TABLE for the pmc2002AlmclientXfpSupplyAlarm articles
--- *********************************************************

pmc2002AlmclientXfpSupplyAlarmTable OBJECT-TYPE
	SYNTAX  SEQUENCE OF Pmc2002AlmclientXfpSupplyAlarmEntry
	MAX-ACCESS not-accessible
	STATUS current
	DESCRIPTION
        "
        List of pmc2002AlmclientXfpSupplyAlarm
        Article
        "
	::= { pmc2002AlmClientUrg 64 }


pmc2002AlmclientXfpSupplyAlarmEntry OBJECT-TYPE
	SYNTAX Pmc2002AlmclientXfpSupplyAlarmEntry
	MAX-ACCESS not-accessible
	STATUS current
	DESCRIPTION
        "
        Row definition for the pmc2002AlmclientXfpSupplyAlarm
        table
        "
	INDEX   { pmc2002AlmclientXfpSupplyAlarmIndex }
	::= { pmc2002AlmclientXfpSupplyAlarmTable 1 }


Pmc2002AlmclientXfpSupplyAlarmEntry ::=
	SEQUENCE {
	pmc2002AlmclientXfpSupplyAlarmIndex
		INTEGER,
	pmc2002AlmClientVcc5HighWarningPortn
		EkiOnOff,
	pmc2002AlmClientVcc5LowWarningPortn
		EkiOnOff,
	pmc2002AlmClientVcc3HighWarningPortn
		EkiOnOff,
	pmc2002AlmClientVcc3LowWarningPortn
		EkiOnOff,
	pmc2002AlmClientVcc2HighWarningPortn
		EkiOnOff,
	pmc2002AlmClientVcc2LowWarningPortn
		EkiOnOff,
	pmc2002AlmClientVee5HighWarningPortn
		EkiOnOff,
	pmc2002AlmClientVee5LowWarningPortn
		EkiOnOff,
	pmc2002AlmClientVcc5HighAlarmPortn
		EkiOnOff,
	pmc2002AlmClientVcc5LowAlarmPortn
		EkiOnOff,
	pmc2002AlmClientVcc3HighAlarmPortn
		EkiOnOff,
	pmc2002AlmClientVcc3LowAlarmPortn
		EkiOnOff,
	pmc2002AlmClientVcc2HighAlarmPortn
		EkiOnOff,
	pmc2002AlmClientVcc2LowAlarmPortn
		EkiOnOff,
	pmc2002AlmClientVee5HighAlarmPortn
		EkiOnOff,
	pmc2002AlmClientVee5LowAlarmPortn
		EkiOnOff
	}


pmc2002AlmclientXfpSupplyAlarmIndex OBJECT-TYPE
	SYNTAX  INTEGER(0..128)
	MAX-ACCESS  read-only
	STATUS current
	DESCRIPTION
        "
        Index definition for the pmc2002AlmclientXfpSupplyAlarm
        table
        "
	::= { pmc2002AlmclientXfpSupplyAlarmEntry 1 }


pmc2002AlmClientVcc5HighWarningPortn OBJECT-TYPE
	SYNTAX  EkiOnOff
	MAX-ACCESS read-only
	STATUS current
	DESCRIPTION
        "
        VCC5 Power Supply High Warning
        :Warning indicating the XFP/OTX
        VCC5 power supply is higher than
        the threshold written in the EEPROM
        <Condtype> CLIENT_VCC5_HIGH_WARNING
        <Probcause> powerProblem (36) <Alarmtype>
        equipmentAlarm (5) <Polarity> (2)
        "
	::= { pmc2002AlmclientXfpSupplyAlarmEntry 17 }


pmc2002AlmClientVcc5LowWarningPortn OBJECT-TYPE
	SYNTAX  EkiOnOff
	MAX-ACCESS read-only
	STATUS current
	DESCRIPTION
        "
        VCC5 Power Supply Low Warning
         :Warning indicating the XFP/OTX
        VCC5 power supply is lower than
        the threshold written in the EEPROM
        <Condtype> CLIENT_VCC5_LOW_WARNING
        <Probcause> powerProblem (36) <Alarmtype>
        equipmentAlarm (5) <Polarity> (2)
        "
	::= { pmc2002AlmclientXfpSupplyAlarmEntry 16 }


pmc2002AlmClientVcc3HighWarningPortn OBJECT-TYPE
	SYNTAX  EkiOnOff
	MAX-ACCESS read-only
	STATUS current
	DESCRIPTION
        "
        VCC3 Power Supply High Warning
        :Warning indicating the XFP/OTX
        VCC3 power supply is higher than
        the threshold written in the EEPROM
        <Condtype> CLIENT_VCC3_HIGH_WARNING
        <Probcause> powerProblem (36) <Alarmtype>
        equipmentAlarm (5) <Polarity> (2)
        "
	::= { pmc2002AlmclientXfpSupplyAlarmEntry 15 }


pmc2002AlmClientVcc3LowWarningPortn OBJECT-TYPE
	SYNTAX  EkiOnOff
	MAX-ACCESS read-only
	STATUS current
	DESCRIPTION
        "
        VCC3 Power Supply Low Warning
         :Warning indicating the XFP/OTX
        VCC3 power supply is lower than
        the threshold written in the EEPROM
        <Condtype> CLIENT_VCC3_LOW_WARNING
        <Probcause> powerProblem (36) <Alarmtype>
        equipmentAlarm (5) <Polarity> (2)
        "
	::= { pmc2002AlmclientXfpSupplyAlarmEntry 14 }


pmc2002AlmClientVcc2HighWarningPortn OBJECT-TYPE
	SYNTAX  EkiOnOff
	MAX-ACCESS read-only
	STATUS current
	DESCRIPTION
        "
        VCC2 Power Supply High Warning
        :Warning indicating the XFP/OTX
        VCC2 power supply is higher than
        the threshold written in the EEPROM
        <Condtype> CLIENT_VCC2_HIGH_WARNING
        <Probcause> powerProblem (36) <Alarmtype>
        equipmentAlarm (5) <Polarity> (2)
        "
	::= { pmc2002AlmclientXfpSupplyAlarmEntry 13 }


pmc2002AlmClientVcc2LowWarningPortn OBJECT-TYPE
	SYNTAX  EkiOnOff
	MAX-ACCESS read-only
	STATUS current
	DESCRIPTION
        "
        VCC2 Power Supply Low Warning
         :Warning indicating the XFP/OTX
        VCC2 power supply is lower than
        the threshold written in the EEPROM
        <Condtype> CLIENT_VCC2_LOW_WARNING
        <Probcause> powerProblem (36) <Alarmtype>
        equipmentAlarm (5) <Polarity> (2)
        "
	::= { pmc2002AlmclientXfpSupplyAlarmEntry 12 }


pmc2002AlmClientVee5HighWarningPortn OBJECT-TYPE
	SYNTAX  EkiOnOff
	MAX-ACCESS read-only
	STATUS current
	DESCRIPTION
        "
        VEE5 Power Supply High Warning
        :Warning indicating the XFP/OTX
        VEE5 power supply is higher than
        the threshold written in the EEPROM
        <Condtype> CLIENT_VEE5_HIGH_WARNING
        <Probcause> powerProblem (36) <Alarmtype>
        equipmentAlarm (5) <Polarity> (2)
        "
	::= { pmc2002AlmclientXfpSupplyAlarmEntry 11 }


pmc2002AlmClientVee5LowWarningPortn OBJECT-TYPE
	SYNTAX  EkiOnOff
	MAX-ACCESS read-only
	STATUS current
	DESCRIPTION
        "
        VEE5 Power Supply Low Warning
         :Warning indicating the XFP/OTX
        VEE5 power supply is lower than
        the threshold written in the EEPROM
        <Condtype> CLIENT_VEE5_LOW_WARNING
        <Probcause> powerProblem (36) <Alarmtype>
        equipmentAlarm (5) <Polarity> (2)
        "
	::= { pmc2002AlmclientXfpSupplyAlarmEntry 10 }


pmc2002AlmClientVcc5HighAlarmPortn OBJECT-TYPE
	SYNTAX  EkiOnOff
	MAX-ACCESS read-only
	STATUS current
	DESCRIPTION
        "
        VCC5 Power Supply High :Alarm
         indicating the XFP/OTX VCC5 power
        supply is higher than the threshold
        written in the EEPROM <Condtype>
        CLIENT_VCC5_HIGH_ALARM <Probcause>
        powerProblem (36) <Alarmtype> equipmentAlarm
        (5) <Polarity> (2)
        "
	::= { pmc2002AlmclientXfpSupplyAlarmEntry 9 }


pmc2002AlmClientVcc5LowAlarmPortn OBJECT-TYPE
	SYNTAX  EkiOnOff
	MAX-ACCESS read-only
	STATUS current
	DESCRIPTION
        "
        VCC5 Power Supply Low :Alarm indicating
        the XFP/OTX VCC5 power supply is
        lower than the threshold written
        in the EEPROM <Condtype> CLIENT_VCC5_LOW_ALARM
        <Probcause> powerProblem (36) <Alarmtype>
        equipmentAlarm (5) <Polarity> (2)
        "
	::= { pmc2002AlmclientXfpSupplyAlarmEntry 8 }


pmc2002AlmClientVcc3HighAlarmPortn OBJECT-TYPE
	SYNTAX  EkiOnOff
	MAX-ACCESS read-only
	STATUS current
	DESCRIPTION
        "
        VCC3 Power Supply High :Alarm
         indicating the XFP/OTX VCC3 power
        supply is higher than the threshold
        written in the EEPROM <Condtype>
        CLIENT_VCC3_HIGH_ALARM <Probcause>
        powerProblem (36) <Alarmtype> equipmentAlarm
        (5) <Polarity> (2)
        "
	::= { pmc2002AlmclientXfpSupplyAlarmEntry 7 }


pmc2002AlmClientVcc3LowAlarmPortn OBJECT-TYPE
	SYNTAX  EkiOnOff
	MAX-ACCESS read-only
	STATUS current
	DESCRIPTION
        "
        VCC3 Power Supply Low :Alarm indicating
        the XFP/OTX VCC3 power supply is
        lower than the threshold written
        in the EEPROM <Condtype> CLIENT_VCC3_LOW_ALARM
        <Probcause> powerProblem (36) <Alarmtype>
        equipmentAlarm (5) <Polarity> (2)
        "
	::= { pmc2002AlmclientXfpSupplyAlarmEntry 6 }


pmc2002AlmClientVcc2HighAlarmPortn OBJECT-TYPE
	SYNTAX  EkiOnOff
	MAX-ACCESS read-only
	STATUS current
	DESCRIPTION
        "
        VCC2 Power Supply High :Alarm
         indicating the XFP/OTX VCC2 power
        supply is higher than the threshold
        written in the EEPROM <Condtype>
        CLIENT_VCC2_HIGH_ALARM <Probcause>
        powerProblem (36) <Alarmtype> equipmentAlarm
        (5) <Polarity> (2)
        "
	::= { pmc2002AlmclientXfpSupplyAlarmEntry 5 }


pmc2002AlmClientVcc2LowAlarmPortn OBJECT-TYPE
	SYNTAX  EkiOnOff
	MAX-ACCESS read-only
	STATUS current
	DESCRIPTION
        "
        VCC2 Power Supply Low :Alarm indicating
        the XFP/OTX VCC2 power supply is
        lower than the threshold written
        in the EEPROM <Condtype> CLIENT_VCC2_LOW_ALARM
        <Probcause> powerProblem (36) <Alarmtype>
        equipmentAlarm (5) <Polarity> (2)
        "
	::= { pmc2002AlmclientXfpSupplyAlarmEntry 4 }


pmc2002AlmClientVee5HighAlarmPortn OBJECT-TYPE
	SYNTAX  EkiOnOff
	MAX-ACCESS read-only
	STATUS current
	DESCRIPTION
        "
        VEE5 Power Supply High :Alarm
         indicating the XFP/OTX VEE5 power
        supply is higher than the threshold
        written in the EEPROM <Condtype>
        CLIENT_VEE5_HIGH_ALARM <Probcause>
        powerProblem (36) <Alarmtype> equipmentAlarm
        (5) <Polarity> (2)
        "
	::= { pmc2002AlmclientXfpSupplyAlarmEntry 3 }


pmc2002AlmClientVee5LowAlarmPortn OBJECT-TYPE
	SYNTAX  EkiOnOff
	MAX-ACCESS read-only
	STATUS current
	DESCRIPTION
        "
        VEE5 Power Supply Low :Alarm indicating
        the XFP/OTX VEE5 power supply is
        lower than the threshold written
        in the EEPROM <Condtype> CLIENT_VEE5_LOW_ALARM
        <Probcause> powerProblem (36) <Alarmtype>
        equipmentAlarm (5) <Polarity> (2)
        "
	::= { pmc2002AlmclientXfpSupplyAlarmEntry 2 }


--- *********************************************************
---     TABLE for the pmc2002AlmclientMapperDeAlm articles
--- *********************************************************

pmc2002AlmclientMapperDeAlmTable OBJECT-TYPE
	SYNTAX  SEQUENCE OF Pmc2002AlmclientMapperDeAlmEntry
	MAX-ACCESS not-accessible
	STATUS current
	DESCRIPTION
        "
        List of pmc2002AlmclientMapperDeAlm
        Article
        "
	::= { pmc2002AlmClientCrit 72 }


pmc2002AlmclientMapperDeAlmEntry OBJECT-TYPE
	SYNTAX Pmc2002AlmclientMapperDeAlmEntry
	MAX-ACCESS not-accessible
	STATUS current
	DESCRIPTION
        "
        Row definition for the pmc2002AlmclientMapperDeAlm
        table
        "
	INDEX   { pmc2002AlmclientMapperDeAlmIndex }
	::= { pmc2002AlmclientMapperDeAlmTable 1 }


Pmc2002AlmclientMapperDeAlmEntry ::=
	SEQUENCE {
	pmc2002AlmclientMapperDeAlmIndex
		INTEGER,
	pmc2002AlmClientDwBufferOvlPortn
		EkiOnOff,
	pmc2002AlmClientDwCsfDetPortn
		EkiOnOff,
	pmc2002AlmClientUpBufferOvlPortn
		EkiOnOff,
	pmc2002AlmClientUpAccOosPortn
		EkiOnOff
	}


pmc2002AlmclientMapperDeAlmIndex OBJECT-TYPE
	SYNTAX  INTEGER(0..128)
	MAX-ACCESS  read-only
	STATUS current
	DESCRIPTION
        "
        Index definition for the pmc2002AlmclientMapperDeAlm
        table
        "
	::= { pmc2002AlmclientMapperDeAlmEntry 1 }


pmc2002AlmClientDwBufferOvlPortn OBJECT-TYPE
	SYNTAX  EkiOnOff
	MAX-ACCESS read-only
	STATUS current
	DESCRIPTION
        "
        Client Downstream Buffer Overload
        :This OID indicates that the de-mapper
        buffer for client port is in overload.
        <Condtype> CLIENT_DW_BUFFER_OVL
        <Probcause> equipmentMalfunction
        (16) <Alarmtype> equipmentAlarm
        (5) <Polarity> (2)
        "
	::= { pmc2002AlmclientMapperDeAlmEntry 15 }


pmc2002AlmClientDwCsfDetPortn OBJECT-TYPE
	SYNTAX  EkiOnOff
	MAX-ACCESS read-only
	STATUS current
	DESCRIPTION
        "
        Client Signal Fail Detected :This
        OID indicates that a CSF has been
        detected on client port in the
         downstream direction   <Help>
          This alarm indicates if a Client
        Signal Fail has been detected in
        the incoming line frame for this
        client port <Condtype> CLIENT_DW_CSF_DET
        <Probcause> receiveFailure (41)
        <Alarmtype> other (1) <Polarity>
        (2)
        "
	::= { pmc2002AlmclientMapperDeAlmEntry 12 }


pmc2002AlmClientUpBufferOvlPortn OBJECT-TYPE
	SYNTAX  EkiOnOff
	MAX-ACCESS read-only
	STATUS current
	DESCRIPTION
        "
        Client Upstream Buffer Overload
        :This OID indicates that the rate
        adaptation buffer for client port
        is in overload. <Condtype> CLIENT_UP_BUFFER_OVL
        <Probcause> receiveFailure (41)
        <Alarmtype> integrityViolation
         (7) <Polarity> (2)
        "
	::= { pmc2002AlmclientMapperDeAlmEntry 11 }


pmc2002AlmClientUpAccOosPortn OBJECT-TYPE
	SYNTAX  EkiOnOff
	MAX-ACCESS read-only
	STATUS current
	DESCRIPTION
        "
        Client Loss Of Synchronisation
        :This OID indicates the upstream
        client input port is in Loss of
        Synchronization  <Help>  This alarms
        indicates if the input client signal
        is correctly synchronized with
         the decoder <Condtype> CLIENT_UP_ACC_OOS
        <Probcause> receiveFailure (41)
        <Alarmtype> integrityViolation
         (7) <Polarity> (2)
        "
	::= { pmc2002AlmclientMapperDeAlmEntry 2 }


--- *********************************************************
---     TABLE for the pmc2002AlmdfrmAlm articles
--- *********************************************************

pmc2002AlmdfrmAlmTable OBJECT-TYPE
	SYNTAX  SEQUENCE OF Pmc2002AlmdfrmAlmEntry
	MAX-ACCESS not-accessible
	STATUS current
	DESCRIPTION
        "
        List of pmc2002AlmdfrmAlm Article
        "
	::= { pmc2002AlmLineCrit 128 }


pmc2002AlmdfrmAlmEntry OBJECT-TYPE
	SYNTAX Pmc2002AlmdfrmAlmEntry
	MAX-ACCESS not-accessible
	STATUS current
	DESCRIPTION
        "
        Row definition for the pmc2002AlmdfrmAlm
        table
        "
	INDEX   { pmc2002AlmdfrmAlmIndex }
	::= { pmc2002AlmdfrmAlmTable 1 }


Pmc2002AlmdfrmAlmEntry ::=
	SEQUENCE {
	pmc2002AlmdfrmAlmIndex
		INTEGER,
	pmc2002AlmLineFecFailPortn
		EkiOnOff,
	pmc2002AlmLineDwLofPortn
		EkiOnOff,
	pmc2002AlmLineDwOofPortn
		EkiOnOff,
	pmc2002AlmLineDwRdiDetPortn
		EkiOnOff,
	pmc2002AlmLineDwAisDetPortn
		EkiOnOff
	}


pmc2002AlmdfrmAlmIndex OBJECT-TYPE
	SYNTAX  INTEGER(0..128)
	MAX-ACCESS  read-only
	STATUS current
	DESCRIPTION
        "
        Index definition for the pmc2002AlmdfrmAlm
        table
        "
	::= { pmc2002AlmdfrmAlmEntry 1 }


pmc2002AlmLineFecFailPortn OBJECT-TYPE
	SYNTAX  EkiOnOff
	MAX-ACCESS read-only
	STATUS current
	DESCRIPTION
        "
        FEC Decoding Fail :This OID indicates
        that the FEC decoder is in an overcapacity
        mode and not able to correct errors
          <Help>  This alarm indicates
         if the FEC decoder is in an over
        capacity mode <Condtype> LINE_FEC_FAIL
        <Probcause> receiveFailure (41)
        <Alarmtype> equipmentAlarm (5)
         <Polarity> (2)
        "
	::= { pmc2002AlmdfrmAlmEntry 6 }


pmc2002AlmLineDwLofPortn OBJECT-TYPE
	SYNTAX  EkiOnOff
	MAX-ACCESS read-only
	STATUS current
	DESCRIPTION
        "
        SONET/SDH Subcarrier Loss Of Frame
        :This OID indicates that a Loss
        Of Frame has been detected on line
        input signal  <Help>  This alarm
        indicates if there is a Loss of
        Frame is detected on the line input
        signal <Condtype> LINE_DW_LOF <Probcause>
        receiveFailure (41) <Alarmtype>
        integrityViolation (7) <Polarity>
        (2)
        "
	::= { pmc2002AlmdfrmAlmEntry 5 }


pmc2002AlmLineDwOofPortn OBJECT-TYPE
	SYNTAX  EkiOnOff
	MAX-ACCESS read-only
	STATUS current
	DESCRIPTION
        "
        SONET/SDH Subcarrier Out Of Frame
        :This OID indicates that an Out
        Of Frame has been detected on line
        input signal  <Help>  This alarm
        indicates if a Loss Of Frame is
        detected on the line input signal
        <Condtype> LINE_DW_OOF <Probcause>
        receiveFailure (41) <Alarmtype>
        integrityViolation (7) <Polarity>
        (2)
        "
	::= { pmc2002AlmdfrmAlmEntry 4 }


pmc2002AlmLineDwRdiDetPortn OBJECT-TYPE
	SYNTAX  EkiOnOff
	MAX-ACCESS read-only
	STATUS current
	DESCRIPTION
        "
        MS-RDI/L-RDI Detected On Subcarrier
        Input :This OID indicates that
         an MS-RDI has been detected on
        line input signal  <Help>  This
        alarm indicates if there is a MS-RDI/L-RDI
        is detected on the line input signal
        <Condtype> LINE_DW_RDI_DET <Probcause>
        remoteNodeTransmissionError (43)
        <Alarmtype> other (1) <Polarity>
        (2)
        "
	::= { pmc2002AlmdfrmAlmEntry 3 }


pmc2002AlmLineDwAisDetPortn OBJECT-TYPE
	SYNTAX  EkiOnOff
	MAX-ACCESS read-only
	STATUS current
	DESCRIPTION
        "
        MS-AIS/L-AIS Detected On Subcarrier
        Input :This OID indicates that
         an MS-AIS has been detected on
        line input signal  <Help>  This
        alarm indicates if there is a MS-AIS/L-AIS
        is detected on the line input signal
        <Condtype> LINE_DW_AIS_DET <Probcause>
        receiveFailure (41) <Alarmtype>
        operationalViolation (8) <Polarity>
        (2)
        "
	::= { pmc2002AlmdfrmAlmEntry 2 }


--- *********************************************************
---     TABLE for the pmc2002AlmdfrmBer articles
--- *********************************************************

pmc2002AlmdfrmBerTable OBJECT-TYPE
	SYNTAX  SEQUENCE OF Pmc2002AlmdfrmBerEntry
	MAX-ACCESS not-accessible
	STATUS current
	DESCRIPTION
        "
        List of pmc2002AlmdfrmBer Article
        "
	::= { pmc2002AlmLineUrg 129 }


pmc2002AlmdfrmBerEntry OBJECT-TYPE
	SYNTAX Pmc2002AlmdfrmBerEntry
	MAX-ACCESS not-accessible
	STATUS current
	DESCRIPTION
        "
        Row definition for the pmc2002AlmdfrmBer
        table
        "
	INDEX   { pmc2002AlmdfrmBerIndex }
	::= { pmc2002AlmdfrmBerTable 1 }


Pmc2002AlmdfrmBerEntry ::=
	SEQUENCE {
	pmc2002AlmdfrmBerIndex
		INTEGER,
	pmc2002AlmLineDegradePortn
		EkiOnOff,
	pmc2002AlmLineSignalFailPortn
		EkiOnOff,
	pmc2002AlmLineSignalDegradePortn
		EkiOnOff
	}


pmc2002AlmdfrmBerIndex OBJECT-TYPE
	SYNTAX  INTEGER(0..128)
	MAX-ACCESS  read-only
	STATUS current
	DESCRIPTION
        "
        Index definition for the pmc2002AlmdfrmBer
        table
        "
	::= { pmc2002AlmdfrmBerEntry 1 }


pmc2002AlmLineDegradePortn OBJECT-TYPE
	SYNTAX  EkiOnOff
	MAX-ACCESS read-only
	STATUS current
	DESCRIPTION
        "
        Fixed Subcarrier Signal Degrade
        :This OID indicates that the line
        input signal is DEGRADE. The assetion
        hysteresis is fixed to 10-8 (assertion)
        and 10-9 (de-assertion) <Condtype>
        LINE_DEGRADE <Probcause> degradedSignal
        (13) <Alarmtype> qualityOfServiceAlarm
        (3) <Polarity> (2)
        "
	::= { pmc2002AlmdfrmBerEntry 6 }


pmc2002AlmLineSignalFailPortn OBJECT-TYPE
	SYNTAX  EkiOnOff
	MAX-ACCESS read-only
	STATUS current
	DESCRIPTION
        "
        Custom Subcarrier Signal Fail
         :This OID indicates that the line
        input signal is FAIL. The assertion
        hysteresis can be customized by
        the host <Condtype> LINE_SIGNAL_FAIL
        <Probcause> receiveFailure (41)
        <Alarmtype> integrityViolation
         (7) <Polarity> (2)
        "
	::= { pmc2002AlmdfrmBerEntry 3 }


pmc2002AlmLineSignalDegradePortn OBJECT-TYPE
	SYNTAX  EkiOnOff
	MAX-ACCESS read-only
	STATUS current
	DESCRIPTION
        "
        Custom Subcarrier Signal Degrade
        :This OID indicates that the line
        input signal is DEGRADE. The assertion
        hysteresis can customized by the
        host <Condtype> LINE_SIGNAL_DEGRADE
        <Probcause> degradedSignal (13)
        <Alarmtype> qualityOfServiceAlarm
        (3) <Polarity> (2)
        "
	::= { pmc2002AlmdfrmBerEntry 2 }


--- *********************************************************
---     TABLE for the pmc2002AlmlineSyncAlarms articles
--- *********************************************************

pmc2002AlmlineSyncAlarmsTable OBJECT-TYPE
	SYNTAX  SEQUENCE OF Pmc2002AlmlineSyncAlarmsEntry
	MAX-ACCESS not-accessible
	STATUS current
	DESCRIPTION
        "
        List of pmc2002AlmlineSyncAlarms
        Article
        "
	::= { pmc2002AlmLineCrit 133 }


pmc2002AlmlineSyncAlarmsEntry OBJECT-TYPE
	SYNTAX Pmc2002AlmlineSyncAlarmsEntry
	MAX-ACCESS not-accessible
	STATUS current
	DESCRIPTION
        "
        Row definition for the pmc2002AlmlineSyncAlarms
        table
        "
	INDEX   { pmc2002AlmlineSyncAlarmsIndex }
	::= { pmc2002AlmlineSyncAlarmsTable 1 }


Pmc2002AlmlineSyncAlarmsEntry ::=
	SEQUENCE {
	pmc2002AlmlineSyncAlarmsIndex
		INTEGER,
	pmc2002AlmLineDwLosPortn
		EkiOnOff,
	pmc2002AlmLineUpLockerrPortn
		EkiOnOff,
	pmc2002AlmLineDwLockerrPortn
		EkiOnOff
	}


pmc2002AlmlineSyncAlarmsIndex OBJECT-TYPE
	SYNTAX  INTEGER(0..128)
	MAX-ACCESS  read-only
	STATUS current
	DESCRIPTION
        "
        Index definition for the pmc2002AlmlineSyncAlarms
        table
        "
	::= { pmc2002AlmlineSyncAlarmsEntry 1 }


pmc2002AlmLineDwLosPortn OBJECT-TYPE
	SYNTAX  EkiOnOff
	MAX-ACCESS read-only
	STATUS current
	DESCRIPTION
        "
        Subcarrier Input Loss Of Signal
        :This OID indicates a loss of signal
        on the 10 Gb/s input.  <Help>
         This alarm indicates if an optical
        signal is detected on the line
         transceiver input <Condtype> LINE_DW_LOS
        <Probcause> receiveFailure (41)
        <Alarmtype> physicalViolation (9)
        <Polarity> (2)
        "
	::= { pmc2002AlmlineSyncAlarmsEntry 17 }


pmc2002AlmLineUpLockerrPortn OBJECT-TYPE
	SYNTAX  EkiOnOff
	MAX-ACCESS read-only
	STATUS current
	DESCRIPTION
        "
        Upstream Clock Lock Error :This
        OID indicates that the serializer
        output 10 Gb/s clock multiplier
        unit is not locked. <Condtype>
         LINE_UP_LOCKERR <Probcause> receiveFailure
        (41) <Alarmtype> equipmentAlarm
        (5) <Polarity> (2)
        "
	::= { pmc2002AlmlineSyncAlarmsEntry 14 }


pmc2002AlmLineDwLockerrPortn OBJECT-TYPE
	SYNTAX  EkiOnOff
	MAX-ACCESS read-only
	STATUS current
	DESCRIPTION
        "
        Downstream Clock Lock Error :This
        OID indicates that the deserializer
        input 10 Gb/s clock recovery is
        not locked. <Condtype> LINE_DW_LOCKERR
        <Probcause> receiveFailure (41)
        <Alarmtype> equipmentAlarm (5)
         <Polarity> (2)
        "
	::= { pmc2002AlmlineSyncAlarmsEntry 13 }


--- *****************************************************
---     LEAF for the modInitFailLevel2 article
--- *****************************************************
pmc2002AlmmodInitFailLevel2 OBJECT IDENTIFIER ::= { pmc2002AlmOtherUrg 194 }




pmc2002AlmSwInitFail OBJECT-TYPE
	  SYNTAX EkiOnOff
	  MAX-ACCESS read-only
	  STATUS current
	  DESCRIPTION
        "
        SW Init Fail :This OID indicates
        that the SW intialization has caused
        unknown intial conditions  <Help>
         This alarm indicates if the SW
        module is correctly initialized
        <Condtype> SW_INIT_FAIL <Probcause>
        softwareError (47) <Alarmtype>
         processingErrorAlarm (4) <Polarity>
        (2)
        "
	  ::= { pmc2002AlmmodInitFailLevel2 5 }



pmc2002AlmResetHwInitFail OBJECT-TYPE
	  SYNTAX EkiOnOff
	  MAX-ACCESS read-only
	  STATUS current
	  DESCRIPTION
        "
        Reset HW Init Fail :This OID indicates
        that the HW intialization has caused
        unknown intial conditions  <Help>
         This alarm indicates if the HW
        has been correctly initialized
         <Condtype> RESET_HW_INIT_FAIL
         <Probcause> softwareError (47)
        <Alarmtype> processingErrorAlarm
        (4) <Polarity> (2)
        "
	  ::= { pmc2002AlmmodInitFailLevel2 4 }



pmc2002AlmBootUndone OBJECT-TYPE
	  SYNTAX EkiOnOff
	  MAX-ACCESS read-only
	  STATUS current
	  DESCRIPTION
        "
        Boot Undone :This OID indicates
        that the boot has not been correctly
        achieved  <Help>  This alarm indicates
        if the module has correctly boot
        <Condtype> BOOT_UNDONE <Probcause>
        softwareError (47) <Alarmtype>
         processingErrorAlarm (4) <Polarity>
        (2)
        "
	  ::= { pmc2002AlmmodInitFailLevel2 3 }



pmc2002AlmNextColdBootForced OBJECT-TYPE
	  SYNTAX EkiOnOff
	  MAX-ACCESS read-only
	  STATUS current
	  DESCRIPTION
        "
        Next Cold Boot Forced :This OID
        indicates that the next Reset will
        be forced Cold  <Help>  This alarm
        indicates that the next reset of
        the module will be forced to cold
        reset <Condtype> NEXT_COLD_BOOT_FORCED
        <Probcause> informationalStatus(1000)
        <Alarmtype> other (1) <Polarity>
        (2)
        "
	  ::= { pmc2002AlmmodInitFailLevel2 2 }



pmc2002AlmLedFail OBJECT-TYPE
	  SYNTAX EkiOnOff
	  MAX-ACCESS read-only
	  STATUS current
	  DESCRIPTION
        "
        Led Fail :This OID indicates that
        Led register has not been correctly
        initalized  <Help>  This alarm
         indicates if the module LEDs are
        correctly initialized <Condtype>
        LED_FAIL <Probcause> softwareError
        (47) <Alarmtype> processingErrorAlarm
        (4) <Polarity> (2)
        "
	  ::= { pmc2002AlmmodInitFailLevel2 1 }



--- *****************************************************
---     LEAF for the modInitFailLevel3 article
--- *****************************************************
pmc2002AlmmodInitFailLevel3 OBJECT IDENTIFIER ::= { pmc2002AlmOtherUrg 195 }




pmc2002AlmClient1InitFail OBJECT-TYPE
	  SYNTAX EkiOnOff
	  MAX-ACCESS read-only
	  STATUS current
	  DESCRIPTION
        "
        Client1 Init Fail :This OID indicates
        that Client 1 registers subset
         has not been correctly initialized
         <Help>  This alarm indicates if
        the client port is correctly initialized
        <Condtype> CLIENT1_INIT_FAIL <Probcause>
        softwareError (47) <Alarmtype>
         processingErrorAlarm (4) <Polarity>
        (2)
        "
	  ::= { pmc2002AlmmodInitFailLevel3 9 }



pmc2002AlmLine1InitFail OBJECT-TYPE
	  SYNTAX EkiOnOff
	  MAX-ACCESS read-only
	  STATUS current
	  DESCRIPTION
        "
        Subcarrier1 Init Fail :This OID
        indicates that the Line registersvsubset
        has not been correctly initialized
         <Help>  This alarm indicates if
        the line port is correctly initialized
        <Condtype> LINE1_INIT_FAIL <Probcause>
        softwareError (47) <Alarmtype>
         processingErrorAlarm (4) <Polarity>
        (2)
        "
	  ::= { pmc2002AlmmodInitFailLevel3 7 }



pmc2002AlmXfp2InitFail OBJECT-TYPE
	  SYNTAX EkiOnOff
	  MAX-ACCESS read-only
	  STATUS current
	  DESCRIPTION
        "
        XFP2 Init Fail :This OID indicates
        that the XFP has not been correctly
        initialized  <Help>  This alarm
        indicates if the line transceiver
        2 is correctly initialized <Condtype>
        XFP2_INIT_FAIL <Probcause> softwareError
        (47) <Alarmtype> processingErrorAlarm
        (4) <Polarity> (2)
        "
	  ::= { pmc2002AlmmodInitFailLevel3 6 }



pmc2002AlmXfp1InitFail OBJECT-TYPE
	  SYNTAX EkiOnOff
	  MAX-ACCESS read-only
	  STATUS current
	  DESCRIPTION
        "
        XFP1 Init Fail :This OID indicates
        that the XFP has not been correctly
        initialized  <Help>  This alarm
        indicates if the line transceiver
        1 is correctly initialized <Condtype>
        XFP1_INIT_FAIL <Probcause> softwareError
        (47) <Alarmtype> processingErrorAlarm
        (4) <Polarity> (2)
        "
	  ::= { pmc2002AlmmodInitFailLevel3 5 }



pmc2002AlmInitModuleFail OBJECT-TYPE
	  SYNTAX EkiOnOff
	  MAX-ACCESS read-only
	  STATUS current
	  DESCRIPTION
        "
        Init Module Fail :This OID indicates
        that the Module has not been correctly
        initialized  <Help>  This alarm
        indicates if the SW module is correctly
        initialized <Condtype> INIT_MODULE_FAIL
        <Probcause> softwareError (47)
         <Alarmtype> processingErrorAlarm
        (4) <Polarity> (2)
        "
	  ::= { pmc2002AlmmodInitFailLevel3 3 }



pmc2002AlmObmTypeReadFail OBJECT-TYPE
	  SYNTAX EkiOnOff
	  MAX-ACCESS read-only
	  STATUS current
	  DESCRIPTION
        "
        OBM Type Read Fail :This OID indicates
        that OBM type has not been recognized
         <Help>  This alarm indicates if
        the OBM board has been correctly
        identified <Condtype> OBM_TYPE_READ_FAIL
        <Probcause> softwareError (47)
         <Alarmtype> processingErrorAlarm
        (4) <Polarity> (2)
        "
	  ::= { pmc2002AlmmodInitFailLevel3 2 }



pmc2002AlmGwIdentFail OBJECT-TYPE
	  SYNTAX EkiOnOff
	  MAX-ACCESS read-only
	  STATUS current
	  DESCRIPTION
        "
        GW Ident Fail :This OID indicates
        that GW identification has not
         been read  <Help>  This alarm
         indicates if the GW has been correctly
        identified <Condtype> GW_IDENT_FAIL
        <Probcause> softwareError (47)
         <Alarmtype> processingErrorAlarm
        (4) <Polarity> (2)
        "
	  ::= { pmc2002AlmmodInitFailLevel3 1 }



--- *********************************************************
---     TABLE for the pmc2002AlmlineXfp1Alarm articles
--- *********************************************************

pmc2002AlmlineXfp1AlarmTable OBJECT-TYPE
	SYNTAX  SEQUENCE OF Pmc2002AlmlineXfp1AlarmEntry
	MAX-ACCESS not-accessible
	STATUS current
	DESCRIPTION
        "
        List of pmc2002AlmlineXfp1Alarm
        Article
        "
	::= { pmc2002AlmLineUrg 208 }


pmc2002AlmlineXfp1AlarmEntry OBJECT-TYPE
	SYNTAX Pmc2002AlmlineXfp1AlarmEntry
	MAX-ACCESS not-accessible
	STATUS current
	DESCRIPTION
        "
        Row definition for the pmc2002AlmlineXfp1Alarm
        table
        "
	INDEX   { pmc2002AlmlineXfp1AlarmIndex }
	::= { pmc2002AlmlineXfp1AlarmTable 1 }


Pmc2002AlmlineXfp1AlarmEntry ::=
	SEQUENCE {
	pmc2002AlmlineXfp1AlarmIndex
		INTEGER,
	pmc2002AlmLineRxPowerHighAlarmPortn
		EkiOnOff,
	pmc2002AlmLineRxPowerLowAlarmPortn
		EkiOnOff,
	pmc2002AlmLineTempHighAlarmPortn
		EkiOnOff,
	pmc2002AlmLineTempLowAlarmPortn
		EkiOnOff,
	pmc2002AlmLineTxBiasHighAlarmPortn
		EkiOnOff,
	pmc2002AlmLineTxBiasLowAlarmPortn
		EkiOnOff,
	pmc2002AlmLineTxPowerHighAlarmPortn
		EkiOnOff,
	pmc2002AlmLineTxPowerLowAlarmPortn
		EkiOnOff
	}


pmc2002AlmlineXfp1AlarmIndex OBJECT-TYPE
	SYNTAX  INTEGER(0..128)
	MAX-ACCESS  read-only
	STATUS current
	DESCRIPTION
        "
        Index definition for the pmc2002AlmlineXfp1Alarm
        table
        "
	::= { pmc2002AlmlineXfp1AlarmEntry 1 }


pmc2002AlmLineRxPowerHighAlarmPortn OBJECT-TYPE
	SYNTAX  EkiOnOff
	MAX-ACCESS read-only
	STATUS current
	DESCRIPTION
        "
        Subcarrier Optical Rx Power High
        Alarm :Alarm indicating that the
        XFP received optical power is higher
        than the threshold value written
        in the XFP EEPROM <Condtype> LINE_RX_POWER_HIGH_ALARM
        <Probcause> receiveFailure (41)
        <Alarmtype> equipmentAlarm (5)
         <Polarity> (2)
        "
	::= { pmc2002AlmlineXfp1AlarmEntry 17 }


pmc2002AlmLineRxPowerLowAlarmPortn OBJECT-TYPE
	SYNTAX  EkiOnOff
	MAX-ACCESS read-only
	STATUS current
	DESCRIPTION
        "
        Subcarrier Optical Rx Power Low
        Alarm :Alarm indicating that the
        XFP received optical power is lower
        than the threshold value written
        in the XFP EEPROM  <Condtype> LINE_RX_POWER_LOW_ALARM
        <Probcause> receiveFailure (41)
        <Alarmtype> equipmentAlarm (5)
         <Polarity> (2)
        "
	::= { pmc2002AlmlineXfp1AlarmEntry 16 }


pmc2002AlmLineTempHighAlarmPortn OBJECT-TYPE
	SYNTAX  EkiOnOff
	MAX-ACCESS read-only
	STATUS current
	DESCRIPTION
        "
        Subcarrier Transceiver Temp High
        Alarm :Alarm indicating that the
        XFP/OTX temperature is higher than
        the threshold value written in
         the XFP EEPROM <Condtype> LINE_TEMP_HIGH_ALARM
        <Probcause> temperatureUnacceptable
        (51) <Alarmtype> equipmentAlarm
        (5) <Polarity> (2)
        "
	::= { pmc2002AlmlineXfp1AlarmEntry 9 }


pmc2002AlmLineTempLowAlarmPortn OBJECT-TYPE
	SYNTAX  EkiOnOff
	MAX-ACCESS read-only
	STATUS current
	DESCRIPTION
        "
        Subcarrier Transceiver Temp Low
        Alarm :Alarm indicating that the
        XFP/OTX temperature is lower than
        the threshold value written in
         the XFP/OTX EEPROM <Condtype>
         LINE_TEMP_LOW_ALARM <Probcause>
        temperatureUnacceptable (51) <Alarmtype>
        equipmentAlarm (5) <Polarity> (2)
        "
	::= { pmc2002AlmlineXfp1AlarmEntry 8 }


pmc2002AlmLineTxBiasHighAlarmPortn OBJECT-TYPE
	SYNTAX  EkiOnOff
	MAX-ACCESS read-only
	STATUS current
	DESCRIPTION
        "
        Subcarrier Transceiver Bias High
        Alarm :Alarm indicating that the
        XFP/OTX transmitter laser bias
         current is higher than the threshold
        value written in the XFP EEPROM
        <Condtype> LINE_TX_BIAS_HIGH_ALARM
        <Probcause> transmitterFailure
         (56) <Alarmtype> equipmentAlarm
        (5) <Polarity> (2)
        "
	::= { pmc2002AlmlineXfp1AlarmEntry 5 }


pmc2002AlmLineTxBiasLowAlarmPortn OBJECT-TYPE
	SYNTAX  EkiOnOff
	MAX-ACCESS read-only
	STATUS current
	DESCRIPTION
        "
        Subcarrier Transceiver Bias Low
        Alarm :Alarm indicating that the
        XFP/OTX transmitter laser bias
         current is lower than the threshold
        value written in the XFP/OTX EEPROM
        <Condtype> LINE_TX_BIAS_LOW_ALARM
        <Probcause> transmitterFailure
         (56) <Alarmtype> equipmentAlarm
        (5) <Polarity> (2)
        "
	::= { pmc2002AlmlineXfp1AlarmEntry 4 }


pmc2002AlmLineTxPowerHighAlarmPortn OBJECT-TYPE
	SYNTAX  EkiOnOff
	MAX-ACCESS read-only
	STATUS current
	DESCRIPTION
        "
        Subcarrier Optical Tx Power High
        Alarm :Alarm indicating that the
        XFP/OTX transmitter transmitter
        output power is higher than the
        threshold value written in the
         XFP EEPROM <Condtype> LINE_TX_POWER_HIGH_ALARM
        <Probcause> transmitterFailure
         (56) <Alarmtype> equipmentAlarm
        (5) <Polarity> (2)
        "
	::= { pmc2002AlmlineXfp1AlarmEntry 3 }


pmc2002AlmLineTxPowerLowAlarmPortn OBJECT-TYPE
	SYNTAX  EkiOnOff
	MAX-ACCESS read-only
	STATUS current
	DESCRIPTION
        "
        Subcarrier Optical Tx Power Low
        Alarm :Alarm indicating that the
        XFP/OTX transmitter transmitter
        output power is lower than the
         threshold value written in the
        XFP/OTX EEPROM <Condtype> LINE_TX_POWER_LOW_ALARM
        <Probcause> transmitterFailure
         (56) <Alarmtype> equipmentAlarm
        (5) <Polarity> (2)
        "
	::= { pmc2002AlmlineXfp1AlarmEntry 2 }


--- *********************************************************
---     TABLE for the pmc2002AlmlineXfp1Warnings articles
--- *********************************************************

pmc2002AlmlineXfp1WarningsTable OBJECT-TYPE
	SYNTAX  SEQUENCE OF Pmc2002AlmlineXfp1WarningsEntry
	MAX-ACCESS not-accessible
	STATUS current
	DESCRIPTION
        "
        List of pmc2002AlmlineXfp1Warnings
        Article
        "
	::= { pmc2002AlmLineNurg 209 }


pmc2002AlmlineXfp1WarningsEntry OBJECT-TYPE
	SYNTAX Pmc2002AlmlineXfp1WarningsEntry
	MAX-ACCESS not-accessible
	STATUS current
	DESCRIPTION
        "
        Row definition for the pmc2002AlmlineXfp1Warnings
        table
        "
	INDEX   { pmc2002AlmlineXfp1WarningsIndex }
	::= { pmc2002AlmlineXfp1WarningsTable 1 }


Pmc2002AlmlineXfp1WarningsEntry ::=
	SEQUENCE {
	pmc2002AlmlineXfp1WarningsIndex
		INTEGER,
	pmc2002AlmLineRxPowerHighWarningPortn
		EkiOnOff,
	pmc2002AlmLineRxPowerLowWarningPortn
		EkiOnOff,
	pmc2002AlmLineTempHighWarningPortn
		EkiOnOff,
	pmc2002AlmLineTempLowWarningPortn
		EkiOnOff,
	pmc2002AlmLineTxBiasHighWarningPortn
		EkiOnOff,
	pmc2002AlmLineTxBiasLowWarningPortn
		EkiOnOff,
	pmc2002AlmLineTxPowerHighWarningPortn
		EkiOnOff,
	pmc2002AlmLineTxPowerLowWarningPortn
		EkiOnOff
	}


pmc2002AlmlineXfp1WarningsIndex OBJECT-TYPE
	SYNTAX  INTEGER(0..128)
	MAX-ACCESS  read-only
	STATUS current
	DESCRIPTION
        "
        Index definition for the pmc2002AlmlineXfp1Warnings
        table
        "
	::= { pmc2002AlmlineXfp1WarningsEntry 1 }


pmc2002AlmLineRxPowerHighWarningPortn OBJECT-TYPE
	SYNTAX  EkiOnOff
	MAX-ACCESS read-only
	STATUS current
	DESCRIPTION
        "
        Subcarrier Optical Rx Power High
        Warning :Warning indicating that
        the XFP received optical power
         is higher than the threshold value
        written in the XFP EEPROM <Condtype>
        LINE_RX_POWER_HIGH_WARNING <Probcause>
        receiveFailure (41) <Alarmtype>
        equipmentAlarm (5) <Polarity> (2)
        "
	::= { pmc2002AlmlineXfp1WarningsEntry 17 }


pmc2002AlmLineRxPowerLowWarningPortn OBJECT-TYPE
	SYNTAX  EkiOnOff
	MAX-ACCESS read-only
	STATUS current
	DESCRIPTION
        "
        Subcarrier Optical Rx Power Low
        Warning :Warning indicating that
        the XFP received optical power
         is lower than the threshold value
        written in the XFP EEPROM  <Condtype>
        LINE_RX_POWER_LOW_WARNING <Probcause>
        receiveFailure (41) <Alarmtype>
        equipmentAlarm (5) <Polarity> (2)
        "
	::= { pmc2002AlmlineXfp1WarningsEntry 16 }


pmc2002AlmLineTempHighWarningPortn OBJECT-TYPE
	SYNTAX  EkiOnOff
	MAX-ACCESS read-only
	STATUS current
	DESCRIPTION
        "
        Subcarrier Transceiver Temp High
        Warning :Warning indicating that
        the XFP/OTX temperature is higher
        than the threshold value written
        in the XFP EEPROM <Condtype> LINE_TEMP_HIGH_WARNING
        <Probcause> temperatureUnacceptable
        (51) <Alarmtype> equipmentAlarm
        (5) <Polarity> (2)
        "
	::= { pmc2002AlmlineXfp1WarningsEntry 9 }


pmc2002AlmLineTempLowWarningPortn OBJECT-TYPE
	SYNTAX  EkiOnOff
	MAX-ACCESS read-only
	STATUS current
	DESCRIPTION
        "
        Subcarrier Transceiver Temp Low
        Warning :Warning indicating that
        the XFP/OTX temperature is lower
        than the threshold value written
        in the XFP/OTX EEPROM <Condtype>
        LINE_TEMP_LOW_WARNING <Probcause>
        temperatureUnacceptable (51) <Alarmtype>
        equipmentAlarm (5) <Polarity> (2)
        "
	::= { pmc2002AlmlineXfp1WarningsEntry 8 }


pmc2002AlmLineTxBiasHighWarningPortn OBJECT-TYPE
	SYNTAX  EkiOnOff
	MAX-ACCESS read-only
	STATUS current
	DESCRIPTION
        "
        Subcarrier Transceiver Bias High
        Warning :Warning indicating that
        the XFP/OTX transmitter laser bias
        current is higher than the threshold
        value written in the XFP EEPROM
        <Condtype> LINE_TX_BIAS_HIGH_WARNING
        <Probcause> transmitterFailure
         (56) <Alarmtype> equipmentAlarm
        (5) <Polarity> (2)
        "
	::= { pmc2002AlmlineXfp1WarningsEntry 5 }


pmc2002AlmLineTxBiasLowWarningPortn OBJECT-TYPE
	SYNTAX  EkiOnOff
	MAX-ACCESS read-only
	STATUS current
	DESCRIPTION
        "
        Subcarrier Transceiver Bias Low
        Warning :Warning indicating that
        the XFP/OTX transmitter laser bias
        current is lower than the threshold
        value written in the XFP/OTX EEPROM
        <Condtype> LINE_TX_BIAS_LOW_WARNING
        <Probcause> transmitterFailure
         (56) <Alarmtype> equipmentAlarm
        (5) <Polarity> (2)
        "
	::= { pmc2002AlmlineXfp1WarningsEntry 4 }


pmc2002AlmLineTxPowerHighWarningPortn OBJECT-TYPE
	SYNTAX  EkiOnOff
	MAX-ACCESS read-only
	STATUS current
	DESCRIPTION
        "
        Subcarrier Optical Tx Power High
        Warning :Warning indicating that
        the XFP/OTX transmitter transmitter
        output power is higher than the
        threshold value written in the
         XFP EEPROM <Condtype> LINE_TX_POWER_HIGH_WARNING
        <Probcause> transmitterFailure
         (56) <Alarmtype> equipmentAlarm
        (5) <Polarity> (2)
        "
	::= { pmc2002AlmlineXfp1WarningsEntry 3 }


pmc2002AlmLineTxPowerLowWarningPortn OBJECT-TYPE
	SYNTAX  EkiOnOff
	MAX-ACCESS read-only
	STATUS current
	DESCRIPTION
        "
        Subcarrier Optical Tx Power Low
        Warning :Warning indicating that
        the XFP/OTX transmitter transmitter
        output power is lower than the
         threshold value written in the
        XFP/OTX EEPROM <Condtype> LINE_TX_POWER_LOW_WARNING
        <Probcause> transmitterFailure
         (56) <Alarmtype> equipmentAlarm
        (5) <Polarity> (2)
        "
	::= { pmc2002AlmlineXfp1WarningsEntry 2 }


--- *********************************************************
---     TABLE for the pmc2002AlmlineXfp1Alarms articles
--- *********************************************************

pmc2002AlmlineXfp1AlarmsTable OBJECT-TYPE
	SYNTAX  SEQUENCE OF Pmc2002AlmlineXfp1AlarmsEntry
	MAX-ACCESS not-accessible
	STATUS current
	DESCRIPTION
        "
        List of pmc2002AlmlineXfp1Alarms
        Article
        "
	::= { pmc2002AlmLineCrit 211 }


pmc2002AlmlineXfp1AlarmsEntry OBJECT-TYPE
	SYNTAX Pmc2002AlmlineXfp1AlarmsEntry
	MAX-ACCESS not-accessible
	STATUS current
	DESCRIPTION
        "
        Row definition for the pmc2002AlmlineXfp1Alarms
        table
        "
	INDEX   { pmc2002AlmlineXfp1AlarmsIndex }
	::= { pmc2002AlmlineXfp1AlarmsTable 1 }


Pmc2002AlmlineXfp1AlarmsEntry ::=
	SEQUENCE {
	pmc2002AlmlineXfp1AlarmsIndex
		INTEGER,
	pmc2002AlmLineApdSupplyFaultPortn
		EkiOnOff,
	pmc2002AlmLineTecFaultPortn
		EkiOnOff,
	pmc2002AlmLineWavelengthUnlockedPortn
		EkiOnOff,
	pmc2002AlmLineTxNrPortn
		EkiOnOff,
	pmc2002AlmLineTxFaultPortn
		EkiOnOff,
	pmc2002AlmLineTxCdrNotLockedPortn
		EkiOnOff,
	pmc2002AlmLineRxNrPortn
		EkiOnOff,
	pmc2002AlmLineRxCdrNotLockedPortn
		EkiOnOff,
	pmc2002AlmLineModNrPortn
		EkiOnOff
	}


pmc2002AlmlineXfp1AlarmsIndex OBJECT-TYPE
	SYNTAX  INTEGER(0..128)
	MAX-ACCESS  read-only
	STATUS current
	DESCRIPTION
        "
        Index definition for the pmc2002AlmlineXfp1Alarms
        table
        "
	::= { pmc2002AlmlineXfp1AlarmsEntry 1 }


pmc2002AlmLineApdSupplyFaultPortn OBJECT-TYPE
	SYNTAX  EkiOnOff
	MAX-ACCESS read-only
	STATUS current
	DESCRIPTION
        "
        Subcarrier Rx Photodiode Power
        Failed :This OID indicates a failure
        on the APD power supply  <Help>
         This alarm indicates if the APD
        power supply is in fail condition
        <Condtype> LINE_APD_SUPPLY_FAULT
        <Probcause> receiverFailure (42)
        <Alarmtype> equipmentAlarm (5)
         <Polarity> (2)
        "
	::= { pmc2002AlmlineXfp1AlarmsEntry 17 }


pmc2002AlmLineTecFaultPortn OBJECT-TYPE
	SYNTAX  EkiOnOff
	MAX-ACCESS read-only
	STATUS current
	DESCRIPTION
        "
        Subcarrier Optical Tx Temp Regul.
        Failed :This OID indicates a failure
        on the TEC module  <Help>  This
        alarm indicates if the TEC of the
        line transceiver is in fail condition
        <Condtype> LINE_TEC_FAULT <Probcause>
        transmitterFailure (56) <Alarmtype>
        equipmentAlarm (5) <Polarity> (2)
        "
	::= { pmc2002AlmlineXfp1AlarmsEntry 16 }


pmc2002AlmLineWavelengthUnlockedPortn OBJECT-TYPE
	SYNTAX  EkiOnOff
	MAX-ACCESS read-only
	STATUS current
	DESCRIPTION
        "
        Subcarrier Optical Tx Wavelength
        Unlock :This OID indicates that
        the wavelength error is exceeding
        the manufacturer tolerance  <Help>
         This alarm indicates if the wavelenght
        of the line transceiver is locked
        <Condtype> LINE_WAVELENGTH_UNLOCKED
        <Probcause> transmitterFailure
         (56) <Alarmtype> equipmentAlarm
        (5) <Polarity> (2)
        "
	::= { pmc2002AlmlineXfp1AlarmsEntry 15 }


pmc2002AlmLineTxNrPortn OBJECT-TYPE
	SYNTAX  EkiOnOff
	MAX-ACCESS read-only
	STATUS current
	DESCRIPTION
        "
        Subcarrier Optical Tx Not Ready
        :This OID indicates a condition
        has arisen leading to invalid data
        on the transmitting side  <Help>
         This alarm indicates if the Tx
        part of the line transceiver is
        ready <Condtype> LINE_TX_NR <Probcause>
        transmitterFailure (56) <Alarmtype>
        equipmentAlarm (5) <Polarity> (2)
        "
	::= { pmc2002AlmlineXfp1AlarmsEntry 9 }


pmc2002AlmLineTxFaultPortn OBJECT-TYPE
	SYNTAX  EkiOnOff
	MAX-ACCESS read-only
	STATUS current
	DESCRIPTION
        "
        Subcarrier Optical Tx Failure
         :This OID indicates a fault condition
        on the laser detected by the safety
        syste  <Help>  This alarm indicates
        if the laser of the line transceiver
        is in fail condition <Condtype>
        LINE_TX_FAULT <Probcause> transmitterFailure
        (56) <Alarmtype> equipmentAlarm
        (5) <Polarity> (2)
        "
	::= { pmc2002AlmlineXfp1AlarmsEntry 8 }


pmc2002AlmLineTxCdrNotLockedPortn OBJECT-TYPE
	SYNTAX  EkiOnOff
	MAX-ACCESS read-only
	STATUS current
	DESCRIPTION
        "
        Subcarrier Optical Tx CDR Unlocked
        :This OID indicates a loss of lock
        on the transmitting side CDR has
        been detected.  <Help>  This alarm
        indicates if the Tx CDR is locked
        in the line transceiver <Condtype>
        LINE_TX_CDR_NOT_LOCKED1 <Probcause>
        transmitterFailure (56) <Alarmtype>
        equipmentAlarm (5) <Polarity> (2)
        "
	::= { pmc2002AlmlineXfp1AlarmsEntry 7 }


pmc2002AlmLineRxNrPortn OBJECT-TYPE
	SYNTAX  EkiOnOff
	MAX-ACCESS read-only
	STATUS current
	DESCRIPTION
        "
        Subcarrier Optical Rx Not Ready
        :This OID indicates that a condition
        has arisen leading to invalid data
        on the receiving side.  <Help>
          This alarm indicates if the Rx
        part of the line transceiver is
        ready <Condtype> LINE_RX_NR <Probcause>
        receiveFailure (41) <Alarmtype>
        equipmentAlarm (5) <Polarity> (2)
        "
	::= { pmc2002AlmlineXfp1AlarmsEntry 6 }


pmc2002AlmLineRxCdrNotLockedPortn OBJECT-TYPE
	SYNTAX  EkiOnOff
	MAX-ACCESS read-only
	STATUS current
	DESCRIPTION
        "
        Subcarrier Optical Rx CDR Unlocked
        :This OID indicates that a loss
        of lock on the receiving side CDR
        has been detected  <Help>  This
        alarm indicates if the Rx CDR is
        locked in the line transceiver
         <Condtype> LINE_RX_CDR_NOT_LOCKED1
        <Probcause> receiveFailure (41)
        <Alarmtype> equipmentAlarm (5)
         <Polarity> (2)
        "
	::= { pmc2002AlmlineXfp1AlarmsEntry 4 }


pmc2002AlmLineModNrPortn OBJECT-TYPE
	SYNTAX  EkiOnOff
	MAX-ACCESS read-only
	STATUS current
	DESCRIPTION
        "
        Subcarrier Optical Module Not
         Ready :This OID indicates that
        the module is unable to determine
        correct data.  <Help>  This alarm
        indicates if the line transceiver
        is ready <Condtype> LINE_MOD_NR
        <Probcause> receiveFailure (41)
        <Alarmtype> equipmentAlarm (5)
         <Polarity> (2)
        "
	::= { pmc2002AlmlineXfp1AlarmsEntry 3 }


--- *********************************************************
---     TABLE for the pmc2002AlmlineXfp1SupplyAlarm articles
--- *********************************************************

pmc2002AlmlineXfp1SupplyAlarmTable OBJECT-TYPE
	SYNTAX  SEQUENCE OF Pmc2002AlmlineXfp1SupplyAlarmEntry
	MAX-ACCESS not-accessible
	STATUS current
	DESCRIPTION
        "
        List of pmc2002AlmlineXfp1SupplyAlarm
        Article
        "
	::= { pmc2002AlmLineUrg 212 }


pmc2002AlmlineXfp1SupplyAlarmEntry OBJECT-TYPE
	SYNTAX Pmc2002AlmlineXfp1SupplyAlarmEntry
	MAX-ACCESS not-accessible
	STATUS current
	DESCRIPTION
        "
        Row definition for the pmc2002AlmlineXfp1SupplyAlarm
        table
        "
	INDEX   { pmc2002AlmlineXfp1SupplyAlarmIndex }
	::= { pmc2002AlmlineXfp1SupplyAlarmTable 1 }


Pmc2002AlmlineXfp1SupplyAlarmEntry ::=
	SEQUENCE {
	pmc2002AlmlineXfp1SupplyAlarmIndex
		INTEGER,
	pmc2002AlmLineVcc5HighWarningPortn
		EkiOnOff,
	pmc2002AlmLineVcc5LowWarningPortn
		EkiOnOff,
	pmc2002AlmLineVcc3HighWarningPortn
		EkiOnOff,
	pmc2002AlmLineVcc3LowWarningPortn
		EkiOnOff,
	pmc2002AlmLineVcc2HighWarningPortn
		EkiOnOff,
	pmc2002AlmLineVcc2LowWarningPortn
		EkiOnOff,
	pmc2002AlmLineVee5HighWarningPortn
		EkiOnOff,
	pmc2002AlmLineVee5LowLineWarningPortn
		EkiOnOff,
	pmc2002AlmLineVcc5HighAlarmPortn
		EkiOnOff,
	pmc2002AlmLineVcc5LowAlarmPortn
		EkiOnOff,
	pmc2002AlmLineVcc3HighAlarmPortn
		EkiOnOff,
	pmc2002AlmLineVcc3LowAlarmPortn
		EkiOnOff,
	pmc2002AlmLineVcc2HighAlarmPortn
		EkiOnOff,
	pmc2002AlmLineVcc2LowAlarmPortn
		EkiOnOff,
	pmc2002AlmLineVee5HighAlarmPortn
		EkiOnOff,
	pmc2002AlmLineVee5LowAlarmPortn
		EkiOnOff
	}


pmc2002AlmlineXfp1SupplyAlarmIndex OBJECT-TYPE
	SYNTAX  INTEGER(0..128)
	MAX-ACCESS  read-only
	STATUS current
	DESCRIPTION
        "
        Index definition for the pmc2002AlmlineXfp1SupplyAlarm
        table
        "
	::= { pmc2002AlmlineXfp1SupplyAlarmEntry 1 }


pmc2002AlmLineVcc5HighWarningPortn OBJECT-TYPE
	SYNTAX  EkiOnOff
	MAX-ACCESS read-only
	STATUS current
	DESCRIPTION
        "
        VCC5 Power Supply High Warning
        :Warning indicating the XFP/OTX
        VCC5 power supply is higher than
        the threshold written in the EEPROM
        <Condtype> LINE_VCC5_HIGH_WARNING
        <Probcause> powerProblem (36) <Alarmtype>
        equipmentAlarm (5) <Polarity> (2)
        "
	::= { pmc2002AlmlineXfp1SupplyAlarmEntry 17 }


pmc2002AlmLineVcc5LowWarningPortn OBJECT-TYPE
	SYNTAX  EkiOnOff
	MAX-ACCESS read-only
	STATUS current
	DESCRIPTION
        "
        VCC5 Power Supply Low Warning
         :Warning indicating the XFP/OTX
        VCC5 power supply is lower than
        the threshold written in the EEPROM
        <Condtype> LINE_VCC5_LOW_WARNING
        <Probcause> powerProblem (36) <Alarmtype>
        equipmentAlarm (5) <Polarity> (2)
        "
	::= { pmc2002AlmlineXfp1SupplyAlarmEntry 16 }


pmc2002AlmLineVcc3HighWarningPortn OBJECT-TYPE
	SYNTAX  EkiOnOff
	MAX-ACCESS read-only
	STATUS current
	DESCRIPTION
        "
        VCC3 Power Supply High Warning
        :Warning indicating the XFP/OTX
        VCC3 power supply is higher than
        the threshold written in the EEPROM
        <Condtype> LINE_VCC3_HIGH_WARNING
        <Probcause> powerProblem (36) <Alarmtype>
        equipmentAlarm (5) <Polarity> (2)
        "
	::= { pmc2002AlmlineXfp1SupplyAlarmEntry 15 }


pmc2002AlmLineVcc3LowWarningPortn OBJECT-TYPE
	SYNTAX  EkiOnOff
	MAX-ACCESS read-only
	STATUS current
	DESCRIPTION
        "
        VCC3 Power Supply Low Warning
         :Warning indicating the XFP/OTX
        VCC3 power supply is lower than
        the threshold written in the EEPROM
        <Condtype> LINE_VCC3_LOW_WARNING
        <Probcause> powerProblem (36) <Alarmtype>
        equipmentAlarm (5) <Polarity> (2)
        "
	::= { pmc2002AlmlineXfp1SupplyAlarmEntry 14 }


pmc2002AlmLineVcc2HighWarningPortn OBJECT-TYPE
	SYNTAX  EkiOnOff
	MAX-ACCESS read-only
	STATUS current
	DESCRIPTION
        "
        VCC2 Power Supply High Warning
        :Warning indicating the XFP/OTX
        VCC2 power supply is higher than
        the threshold written in the EEPROM
        <Condtype> LINE_VCC2_HIGH_WARNING
        <Probcause> powerProblem (36) <Alarmtype>
        equipmentAlarm (5) <Polarity> (2)
        "
	::= { pmc2002AlmlineXfp1SupplyAlarmEntry 13 }


pmc2002AlmLineVcc2LowWarningPortn OBJECT-TYPE
	SYNTAX  EkiOnOff
	MAX-ACCESS read-only
	STATUS current
	DESCRIPTION
        "
        VCC2 Power Supply Low Warning
         :Warning indicating the XFP/OTX
        VCC2 power supply is lower than
        the threshold written in the EEPROM
        <Condtype> LINE_VCC2_LOW_WARNING
        <Probcause> powerProblem (36) <Alarmtype>
        equipmentAlarm (5) <Polarity> (2)
        "
	::= { pmc2002AlmlineXfp1SupplyAlarmEntry 12 }


pmc2002AlmLineVee5HighWarningPortn OBJECT-TYPE
	SYNTAX  EkiOnOff
	MAX-ACCESS read-only
	STATUS current
	DESCRIPTION
        "
        VEE5 Power Supply High Warning
        :Warning indicating the XFP/OTX
        VEE5 power supply is higher than
        the threshold written in the EEPROM
        <Condtype> LINE_VEE5_HIGH_WARNING
        <Probcause> powerProblem (36) <Alarmtype>
        equipmentAlarm (5) <Polarity> (2)
        "
	::= { pmc2002AlmlineXfp1SupplyAlarmEntry 11 }


pmc2002AlmLineVee5LowLineWarningPortn OBJECT-TYPE
	SYNTAX  EkiOnOff
	MAX-ACCESS read-only
	STATUS current
	DESCRIPTION
        "
        VEE5 Power Supply Low Warning
         :Warning indicating the XFP/OTX
        VEE5 power supply is lower than
        the threshold written in the EEPROM
        <Condtype> LINE_VEE5_LOW_LINE_WARNING
        <Probcause> powerProblem (36) <Alarmtype>
        equipmentAlarm (5) <Polarity> (2)
        "
	::= { pmc2002AlmlineXfp1SupplyAlarmEntry 10 }


pmc2002AlmLineVcc5HighAlarmPortn OBJECT-TYPE
	SYNTAX  EkiOnOff
	MAX-ACCESS read-only
	STATUS current
	DESCRIPTION
        "
        VCC5 Power Supply High Alarm :Alarm
        indicating the XFP/OTX VCC5 power
        supply is higher than the threshold
        written in the EEPROM <Condtype>
        LINE_VCC5_HIGH_ALARM <Probcause>
        powerProblem (36) <Alarmtype> equipmentAlarm
        (5) <Polarity> (2)
        "
	::= { pmc2002AlmlineXfp1SupplyAlarmEntry 9 }


pmc2002AlmLineVcc5LowAlarmPortn OBJECT-TYPE
	SYNTAX  EkiOnOff
	MAX-ACCESS read-only
	STATUS current
	DESCRIPTION
        "
        VCC5 Power Supply Low Alarm :Alarm
        indicating the XFP/OTX VCC5 power
        supply is lower than the threshold
        written in the EEPROM <Condtype>
        LINE_VCC5_LOW_ALARM <Probcause>
        powerProblem (36) <Alarmtype> equipmentAlarm
        (5) <Polarity> (2)
        "
	::= { pmc2002AlmlineXfp1SupplyAlarmEntry 8 }


pmc2002AlmLineVcc3HighAlarmPortn OBJECT-TYPE
	SYNTAX  EkiOnOff
	MAX-ACCESS read-only
	STATUS current
	DESCRIPTION
        "
        VCC3 Power Supply High Alarm :Alarm
        indicating the XFP/OTX VCC3 power
        supply is higher than the threshold
        written in the EEPROM <Condtype>
        LINE_VCC3_HIGH_ALARM <Probcause>
        powerProblem (36) <Alarmtype> equipmentAlarm
        (5) <Polarity> (2)
        "
	::= { pmc2002AlmlineXfp1SupplyAlarmEntry 7 }


pmc2002AlmLineVcc3LowAlarmPortn OBJECT-TYPE
	SYNTAX  EkiOnOff
	MAX-ACCESS read-only
	STATUS current
	DESCRIPTION
        "
        VCC3 Power Supply Low Alarm :Alarm
        indicating the XFP/OTX VCC3 power
        supply is lower than the threshold
        written in the EEPROM <Condtype>
        LINE_VCC3_LOW_ALARM <Probcause>
        powerProblem (36) <Alarmtype> equipmentAlarm
        (5) <Polarity> (2)
        "
	::= { pmc2002AlmlineXfp1SupplyAlarmEntry 6 }


pmc2002AlmLineVcc2HighAlarmPortn OBJECT-TYPE
	SYNTAX  EkiOnOff
	MAX-ACCESS read-only
	STATUS current
	DESCRIPTION
        "
        VCC2 Power Supply High Alarm :Alarm
        indicating the XFP/OTX VCC2 power
        supply is higher than the threshold
        written in the EEPROM <Condtype>
        LINE_VCC2_HIGH_ALARM <Probcause>
        powerProblem (36) <Alarmtype> equipmentAlarm
        (5) <Polarity> (2)
        "
	::= { pmc2002AlmlineXfp1SupplyAlarmEntry 5 }


pmc2002AlmLineVcc2LowAlarmPortn OBJECT-TYPE
	SYNTAX  EkiOnOff
	MAX-ACCESS read-only
	STATUS current
	DESCRIPTION
        "
        VCC2 Power Supply Low Alarm :Alarm
        indicating the XFP/OTX VCC2 power
        supply is lower than the threshold
        written in the EEPROM <Condtype>
        LINE_VCC2_LOW_ALARM <Probcause>
        powerProblem (36) <Alarmtype> equipmentAlarm
        (5) <Polarity> (2)
        "
	::= { pmc2002AlmlineXfp1SupplyAlarmEntry 4 }


pmc2002AlmLineVee5HighAlarmPortn OBJECT-TYPE
	SYNTAX  EkiOnOff
	MAX-ACCESS read-only
	STATUS current
	DESCRIPTION
        "
        VEE5 Power Supply High Alarm :Alarm
        indicating the XFP/OTX VEE5 power
        supply is higher than the threshold
        written in the EEPROM <Condtype>
        LINE_VEE5_HIGH_ALARM <Probcause>
        powerProblem (36) <Alarmtype> equipmentAlarm
        (5) <Polarity> (2)
        "
	::= { pmc2002AlmlineXfp1SupplyAlarmEntry 3 }


pmc2002AlmLineVee5LowAlarmPortn OBJECT-TYPE
	SYNTAX  EkiOnOff
	MAX-ACCESS read-only
	STATUS current
	DESCRIPTION
        "
        VEE5 Power Supply Low Alarm :Alarm
        indicating the XFP/OTX VEE5 power
        supply is lower than the threshold
        written in the EEPROM <Condtype>
        LINE_VEE5_LOW_ALARM <Probcause>
        powerProblem (36) <Alarmtype> equipmentAlarm
        (5) <Polarity> (2)
        "
	::= { pmc2002AlmlineXfp1SupplyAlarmEntry 2 }


--- *********************************************************
---     TABLE for the pmc2002AlmlineOtx1TlhAlarms articles
--- *********************************************************

pmc2002AlmlineOtx1TlhAlarmsTable OBJECT-TYPE
	SYNTAX  SEQUENCE OF Pmc2002AlmlineOtx1TlhAlarmsEntry
	MAX-ACCESS not-accessible
	STATUS current
	DESCRIPTION
        "
        List of pmc2002AlmlineOtx1TlhAlarms
        Article
        "
	::= { pmc2002AlmLineUrg 224 }


pmc2002AlmlineOtx1TlhAlarmsEntry OBJECT-TYPE
	SYNTAX Pmc2002AlmlineOtx1TlhAlarmsEntry
	MAX-ACCESS not-accessible
	STATUS current
	DESCRIPTION
        "
        Row definition for the pmc2002AlmlineOtx1TlhAlarms
        table
        "
	INDEX   { pmc2002AlmlineOtx1TlhAlarmsIndex }
	::= { pmc2002AlmlineOtx1TlhAlarmsTable 1 }


Pmc2002AlmlineOtx1TlhAlarmsEntry ::=
	SEQUENCE {
	pmc2002AlmlineOtx1TlhAlarmsIndex
		INTEGER,
	pmc2002AlmLineLaserTempHighAlaPortn
		EkiOnOff,
	pmc2002AlmLineFreqDevHighAlaPortn
		EkiOnOff,
	pmc2002AlmLineCdrNotReadyPortn
		EkiOnOff,
	pmc2002AlmLineAgingHighAlaPortn
		EkiOnOff,
	pmc2002AlmLineModulatorAgingHighAlaPortn
		EkiOnOff
	}


pmc2002AlmlineOtx1TlhAlarmsIndex OBJECT-TYPE
	SYNTAX  INTEGER(0..128)
	MAX-ACCESS  read-only
	STATUS current
	DESCRIPTION
        "
        Index definition for the pmc2002AlmlineOtx1TlhAlarms
        table
        "
	::= { pmc2002AlmlineOtx1TlhAlarmsEntry 1 }


pmc2002AlmLineLaserTempHighAlaPortn OBJECT-TYPE
	SYNTAX  EkiOnOff
	MAX-ACCESS read-only
	STATUS current
	DESCRIPTION
        "
        Subcarrier Laser Temp. High Alarm
        :Alarm indicating the Line OTX
         TLH laser temperature is higher
        than the threshold written in the
        EEPROM <Condtype> LINE_LASER_TEMP_HIGH_ALA
        <Probcause> temperatureUnacceptable
        (51) <Alarmtype> equipmentAlarm
        (5) <Polarity> (2)
        "
	::= { pmc2002AlmlineOtx1TlhAlarmsEntry 15 }


pmc2002AlmLineFreqDevHighAlaPortn OBJECT-TYPE
	SYNTAX  EkiOnOff
	MAX-ACCESS read-only
	STATUS current
	DESCRIPTION
        "
        Subcarrier Freq. Deviation High
        Alarm :Alarm indicating the Line
        OTX TLH frequency deviation is
         higher than the threshold written
        in the EEPROM <Condtype> LINE_FREQ_DEV_HIGH_ALA
        <Probcause> transmitterFailure
         (56) <Alarmtype> equipmentAlarm
        (5) <Polarity> (2)
        "
	::= { pmc2002AlmlineOtx1TlhAlarmsEntry 13 }


pmc2002AlmLineCdrNotReadyPortn OBJECT-TYPE
	SYNTAX  EkiOnOff
	MAX-ACCESS read-only
	STATUS current
	DESCRIPTION
        "
        CDR Not Ready :This OID indicates
        the Clock Data Recovery unit is
        not yet initialized  <Help>  This
        alarm indicates the Clock Data
         Recovery unit is not yet initialized.
        <Condtype> LINE_CDR_NOT_READY <Probcause>
        receiveFailure (41) <Alarmtype>
        equipmentAlarm (5) <Polarity> (2)
        "
	::= { pmc2002AlmlineOtx1TlhAlarmsEntry 10 }


pmc2002AlmLineAgingHighAlaPortn OBJECT-TYPE
	SYNTAX  EkiOnOff
	MAX-ACCESS read-only
	STATUS current
	DESCRIPTION
        "
        Subcarrier OTX TLH Aging High
         Alarm :Alarm indicating the Line
        OTX TLH aging is higher than the
        threshold written in the EEPROM
        <Condtype> LINE_AGING_HIGH_ALA
         <Probcause> transmitterFailure
        (56) <Alarmtype> equipmentAlarm
        (5) <Polarity> (2)
        "
	::= { pmc2002AlmlineOtx1TlhAlarmsEntry 7 }


pmc2002AlmLineModulatorAgingHighAlaPortn OBJECT-TYPE
	SYNTAX  EkiOnOff
	MAX-ACCESS read-only
	STATUS current
	DESCRIPTION
        "
        Subcarrier Modulator Aging High
        Alarm :Alarm indicating the Line
        OTX TLH modulator aging is higher
        than the threshold written in the
        EEPROM <Condtype> LINE_MODULATOR_AGING_HIGH_ALA
        <Probcause> transmitterFailure
         (56) <Alarmtype> equipmentAlarm
        (5) <Polarity> (2)
        "
	::= { pmc2002AlmlineOtx1TlhAlarmsEntry 6 }


--- *********************************************************
---     TABLE for the pmc2002AlmlineOtx1TlhWarnings articles
--- *********************************************************

pmc2002AlmlineOtx1TlhWarningsTable OBJECT-TYPE
	SYNTAX  SEQUENCE OF Pmc2002AlmlineOtx1TlhWarningsEntry
	MAX-ACCESS not-accessible
	STATUS current
	DESCRIPTION
        "
        List of pmc2002AlmlineOtx1TlhWarnings
        Article
        "
	::= { pmc2002AlmLineNurg 225 }


pmc2002AlmlineOtx1TlhWarningsEntry OBJECT-TYPE
	SYNTAX Pmc2002AlmlineOtx1TlhWarningsEntry
	MAX-ACCESS not-accessible
	STATUS current
	DESCRIPTION
        "
        Row definition for the pmc2002AlmlineOtx1TlhWarnings
        table
        "
	INDEX   { pmc2002AlmlineOtx1TlhWarningsIndex }
	::= { pmc2002AlmlineOtx1TlhWarningsTable 1 }


Pmc2002AlmlineOtx1TlhWarningsEntry ::=
	SEQUENCE {
	pmc2002AlmlineOtx1TlhWarningsIndex
		INTEGER,
	pmc2002AlmLineLaserTempHighWarningPortn
		EkiOnOff,
	pmc2002AlmLineFreqDevHighWarningPortn
		EkiOnOff,
	pmc2002AlmLineAgingHighWarningPortn
		EkiOnOff,
	pmc2002AlmLineModulatorAgingHighWarningPortn
		EkiOnOff
	}


pmc2002AlmlineOtx1TlhWarningsIndex OBJECT-TYPE
	SYNTAX  INTEGER(0..128)
	MAX-ACCESS  read-only
	STATUS current
	DESCRIPTION
        "
        Index definition for the pmc2002AlmlineOtx1TlhWarnings
        table
        "
	::= { pmc2002AlmlineOtx1TlhWarningsEntry 1 }


pmc2002AlmLineLaserTempHighWarningPortn OBJECT-TYPE
	SYNTAX  EkiOnOff
	MAX-ACCESS read-only
	STATUS current
	DESCRIPTION
        "
        Subcarrier Laser Temp. High Warning
        :Warning indicating the Line OTX
        TLH laser temperature is higher
        than the threshold written in the
        EEPROM <Condtype> LINE_LASER_TEMP_HIGH_WARNING
        <Probcause> temperatureUnacceptable
        (51) <Alarmtype> equipmentAlarm
        (5) <Polarity> (2)
        "
	::= { pmc2002AlmlineOtx1TlhWarningsEntry 15 }


pmc2002AlmLineFreqDevHighWarningPortn OBJECT-TYPE
	SYNTAX  EkiOnOff
	MAX-ACCESS read-only
	STATUS current
	DESCRIPTION
        "
        Subcarrier Freq. Deviation High
        Warning :Warning indicating the
        Line OTX TLH frequency deviation
        is higher than the threshold written
        in the EEPROM <Condtype> LINE_FREQ_DEV_HIGH_WARNING
        <Probcause> transmitterFailure
         (56) <Alarmtype> equipmentAlarm
        (5) <Polarity> (2)
        "
	::= { pmc2002AlmlineOtx1TlhWarningsEntry 13 }


pmc2002AlmLineAgingHighWarningPortn OBJECT-TYPE
	SYNTAX  EkiOnOff
	MAX-ACCESS read-only
	STATUS current
	DESCRIPTION
        "
        Subcarrier OTX TLH Aging High
         Warning :Warning indicating the
        Line OTX TLH aging is higher than
        the threshold written in the EEPROM
        <Condtype> LINE_AGING_HIGH_WARNING
        <Probcause> transmitterFailure
         (56) <Alarmtype> equipmentAlarm
        (5) <Polarity> (2)
        "
	::= { pmc2002AlmlineOtx1TlhWarningsEntry 7 }


pmc2002AlmLineModulatorAgingHighWarningPortn OBJECT-TYPE
	SYNTAX  EkiOnOff
	MAX-ACCESS read-only
	STATUS current
	DESCRIPTION
        "
        Subcarrier Modulator Aging High
        Warning :Warning indicating the
        Line OTX TLH modulator aging is
        higher than the threshold written
        in the EEPROM <Condtype> LINE_MODULATOR_AGING_HIGH_WARNING
        <Probcause> transmitterFailure
         (56) <Alarmtype> equipmentAlarm
        (5) <Polarity> (2)
        "
	::= { pmc2002AlmlineOtx1TlhWarningsEntry 6 }







--- *****************************************************
--- $$$$$$$$$$$$$$$$$$$$$$$$$$$$$$$$$$$$$$$$$$$$$$$$$$$$$
---     CONTROLS
--- $$$$$$$$$$$$$$$$$$$$$$$$$$$$$$$$$$$$$$$$$$$$$$$$$$$$$
--- *****************************************************



--- *****************************************************
---     LEAF for the confMgnt1 article
--- *****************************************************
pmc2002CtrlconfMgnt1 OBJECT IDENTIFIER ::= { pmc2002CtrlOther 1 }




pmc2002CtrlConf2Clear1 OBJECT-TYPE
	  SYNTAX EkiOnOff
	  MAX-ACCESS read-write
	  STATUS current
	  DESCRIPTION
        "
        Clear Configuration Tables :This
        OID clears the configuration tables
        from configuration2 in the flash.
         <Help>  This control restores
         the default configuration of the
        module
        "
	  ::= { pmc2002CtrlconfMgnt1 14 }



pmc2002CtrlConf2Flash1 OBJECT-TYPE
	  SYNTAX EkiOnOff
	  MAX-ACCESS read-write
	  STATUS current
	  DESCRIPTION
        "
        Write Configuration Tables :This
        OID saves the current configuration
        of the PM as configuration2 in
         the flash.  <Help>  This control
        saves the customer configuration
        on the module
        "
	  ::= { pmc2002CtrlconfMgnt1 10 }



pmc2002CtrlConf2Load1 OBJECT-TYPE
	  SYNTAX EkiOnOff
	  MAX-ACCESS read-write
	  STATUS current
	  DESCRIPTION
        "
        Load Configuration Tables Set
         Nb 2 :When set this OID enables
        loading from flash configuration2
        into the PM.
        "
	  ::= { pmc2002CtrlconfMgnt1 2 }



pmc2002CtrlConf1Load1 OBJECT-TYPE
	  SYNTAX EkiOnOff
	  MAX-ACCESS read-write
	  STATUS current
	  DESCRIPTION
        "
        Load Configuration Tables Set
         Nb 1 :When set this OID enables
        loading from flash configuration1
        into the PM.
        "
	  ::= { pmc2002CtrlconfMgnt1 1 }



--- *****************************************************
---     LEAF for the synth4 article
--- *****************************************************
pmc2002Ctrlsynth4 OBJECT IDENTIFIER ::= { pmc2002CtrlOther 4 }




pmc2002CtrlCorrelatOff OBJECT-TYPE
	  SYNTAX EkiOnOff
	  MAX-ACCESS read-write
	  STATUS current
	  DESCRIPTION
        "
        Disable Alarm Correlation :This
        OID disables the alarm correlation
        in the PM.
        "
	  ::= { pmc2002Ctrlsynth4 2 }



pmc2002CtrlCorrelatOn OBJECT-TYPE
	  SYNTAX EkiOnOff
	  MAX-ACCESS read-write
	  STATUS current
	  DESCRIPTION
        "
        Enable Alarm Correlation :This
        OID enables the alarm correlation
        in the PM.
        "
	  ::= { pmc2002Ctrlsynth4 1 }



--- *****************************************************
---     LEAF for the swMgnt article
--- *****************************************************
pmc2002CtrlswMgnt OBJECT IDENTIFIER ::= { pmc2002CtrlOther 5 }




pmc2002CtrlLoadSwBank2 OBJECT-TYPE
	  SYNTAX EkiOnOff
	  MAX-ACCESS read-write
	  STATUS current
	  DESCRIPTION
        "
        Set Software Nb 2 As Active :This
        OID, when set, loads the SW from
        bank2 into the PM. It must be followed
        by a reset.  <Help>  This controls
        selects the second SW bank as the
        active bank for the next module
        reset
        "
	  ::= { pmc2002CtrlswMgnt 6 }



pmc2002CtrlLoadSwBank1 OBJECT-TYPE
	  SYNTAX EkiOnOff
	  MAX-ACCESS read-write
	  STATUS current
	  DESCRIPTION
        "
        Set Software Nb 1 As Active :This
        OID, when set, loads the SW from
        bank1 into the PM. It must be followed
        by a reset.  <Help>  This controls
        selects the first SW bank as the
        active bank for the next module
        reset
        "
	  ::= { pmc2002CtrlswMgnt 5 }



pmc2002CtrlWarmReset OBJECT-TYPE
	  SYNTAX EkiOnOff
	  MAX-ACCESS read-write
	  STATUS current
	  DESCRIPTION
        "
        PM Warm Reset :This OID, when
         set, causes a warm reset of the
        PM. This reset is not traffic affecting,
        and the configuration of PM remains
        unchanged.  <Help>  This control
        initiates a warm reset of the module.
        "
	  ::= { pmc2002CtrlswMgnt 3 }



pmc2002CtrlColdReset OBJECT-TYPE
	  SYNTAX EkiOnOff
	  MAX-ACCESS read-write
	  STATUS current
	  DESCRIPTION
        "
        PM Cold Reset :This OID, when
         set, causes a cold reset of the
        PM. This reset is traffic affecting,
        and the configuration of PM is
         reloaded on start-up.  <Help>
          This control initiates a cold
        reset of the module.
        "
	  ::= { pmc2002CtrlswMgnt 2 }



--- *****************************************************
---     LEAF for the gwMgnt article
--- *****************************************************
pmc2002CtrlgwMgnt OBJECT IDENTIFIER ::= { pmc2002CtrlOther 6 }




pmc2002CtrlLoadGwBank4 OBJECT-TYPE
	  SYNTAX EkiOnOff
	  MAX-ACCESS read-write
	  STATUS current
	  DESCRIPTION
        "
        Set Gateware Nb 4 As Active :This
        OID, when set, loads the GW from
        bank4 (Flash) into the PM. It is
        followed by an automatic gateware
        cold reset.
        "
	  ::= { pmc2002CtrlgwMgnt 8 }



pmc2002CtrlLoadGwBank3 OBJECT-TYPE
	  SYNTAX EkiOnOff
	  MAX-ACCESS read-write
	  STATUS current
	  DESCRIPTION
        "
        Set Gateware Nb 3 As Active :This
        OID, when set, loads the GW from
        bank3 (Flash) into the PM. It is
        followed by an automatic gateware
        cold reset.  <Help>  This controls
        initiates a cold reset of the module
        and select the third GW bank as
        the active bank
        "
	  ::= { pmc2002CtrlgwMgnt 7 }



pmc2002CtrlLoadGwBank2 OBJECT-TYPE
	  SYNTAX EkiOnOff
	  MAX-ACCESS read-write
	  STATUS current
	  DESCRIPTION
        "
        Set Gateware Nb 2 As Active :This
        OID, when set, loads the GW from
        bank2 (Flash) into the PM. It is
        followed by an automatic gateware
        cold reset.
        "
	  ::= { pmc2002CtrlgwMgnt 6 }



pmc2002CtrlLoadGwBank1 OBJECT-TYPE
	  SYNTAX EkiOnOff
	  MAX-ACCESS read-write
	  STATUS current
	  DESCRIPTION
        "
        Set Gateware Nb 1 As Active :This
        OID, when set, loads the GW from
        bank1 (Flash) into the PM. It is
        followed by an automatic gateware
        cold reset.  <Help>  This controls
        initiates a cold reset of the module
        and select the first GW bank as
        the active bank
        "
	  ::= { pmc2002CtrlgwMgnt 5 }



pmc2002CtrlCurrentGwReset OBJECT-TYPE
	  SYNTAX EkiOnOff
	  MAX-ACCESS read-write
	  STATUS current
	  DESCRIPTION
        "
        Active Gateware Reset :This OID,
        when set, resets the active gateware.
        It is traffic affecting.
        "
	  ::= { pmc2002CtrlgwMgnt 1 }



--- *********************************************************
---     TABLE for the pmc2002CtrlaccessLoop articles
--- *********************************************************

pmc2002CtrlaccessLoopTable OBJECT-TYPE
	SYNTAX  SEQUENCE OF Pmc2002CtrlaccessLoopEntry
	MAX-ACCESS not-accessible
	STATUS current
	DESCRIPTION
        "
        List of pmc2002CtrlaccessLoop
         Article
        "
	::= { pmc2002CtrlClient 16 }


pmc2002CtrlaccessLoopEntry OBJECT-TYPE
	SYNTAX Pmc2002CtrlaccessLoopEntry
	MAX-ACCESS not-accessible
	STATUS current
	DESCRIPTION
        "
        Row definition for the pmc2002CtrlaccessLoop
        table
        "
	INDEX   { pmc2002CtrlaccessLoopIndex }
	::= { pmc2002CtrlaccessLoopTable 1 }


Pmc2002CtrlaccessLoopEntry ::=
	SEQUENCE {
	pmc2002CtrlaccessLoopIndex
		INTEGER,
	pmc2002CtrlaccessLoopPortn
		EkiState
	}


pmc2002CtrlaccessLoopIndex OBJECT-TYPE
	SYNTAX  INTEGER(0..128)
	MAX-ACCESS  read-only
	STATUS current
	DESCRIPTION
        "
        Index definition for the pmc2002CtrlaccessLoop
        table
        "
	::= { pmc2002CtrlaccessLoopEntry 1 }


pmc2002CtrlaccessLoopPortn OBJECT-TYPE
	SYNTAX  EkiState
	MAX-ACCESS read-write
	STATUS current
	DESCRIPTION
        "
        Client Facility Loopback :This
        OID operates a Client Facility
         Loopback, looping client input
        signal on the client output port.
        The loop is located on the client
        transceiver    <Help>  This control
        operates an out loop back on the
        Client port. The received client
        signal is looped on the transmit
        client output.
        "
	::= { pmc2002CtrlaccessLoopEntry 2 }


--- *********************************************************
---     TABLE for the pmc2002CtrlportOosMode articles
--- *********************************************************

pmc2002CtrlportOosModeTable OBJECT-TYPE
	SYNTAX  SEQUENCE OF Pmc2002CtrlportOosModeEntry
	MAX-ACCESS not-accessible
	STATUS current
	DESCRIPTION
        "
        List of pmc2002CtrlportOosMode
        Article
        "
	::= { pmc2002CtrlClient 18 }


pmc2002CtrlportOosModeEntry OBJECT-TYPE
	SYNTAX Pmc2002CtrlportOosModeEntry
	MAX-ACCESS not-accessible
	STATUS current
	DESCRIPTION
        "
        Row definition for the pmc2002CtrlportOosMode
        table
        "
	INDEX   { pmc2002CtrlportOosModeIndex }
	::= { pmc2002CtrlportOosModeTable 1 }


Pmc2002CtrlportOosModeEntry ::=
	SEQUENCE {
	pmc2002CtrlportOosModeIndex
		INTEGER,
	pmc2002CtrlportOosModePortn
		EkiState
	}


pmc2002CtrlportOosModeIndex OBJECT-TYPE
	SYNTAX  INTEGER(0..128)
	MAX-ACCESS  read-only
	STATUS current
	DESCRIPTION
        "
        Index definition for the pmc2002CtrlportOosMode
        table
        "
	::= { pmc2002CtrlportOosModeEntry 1 }


pmc2002CtrlportOosModePortn OBJECT-TYPE
	SYNTAX  EkiState
	MAX-ACCESS read-write
	STATUS current
	DESCRIPTION
        "
        Client Port Out Of Service :This
        OID sets the client port Out Of
        Service  <Help>  This controls
         defines the service state of the
        client port
        "
	::= { pmc2002CtrlportOosModeEntry 2 }


--- *********************************************************
---     TABLE for the pmc2002CtrlsfpOffCtrl articles
--- *********************************************************

pmc2002CtrlsfpOffCtrlTable OBJECT-TYPE
	SYNTAX  SEQUENCE OF Pmc2002CtrlsfpOffCtrlEntry
	MAX-ACCESS not-accessible
	STATUS current
	DESCRIPTION
        "
        List of pmc2002CtrlsfpOffCtrl
         Article
        "
	::= { pmc2002CtrlClient 20 }


pmc2002CtrlsfpOffCtrlEntry OBJECT-TYPE
	SYNTAX Pmc2002CtrlsfpOffCtrlEntry
	MAX-ACCESS not-accessible
	STATUS current
	DESCRIPTION
        "
        Row definition for the pmc2002CtrlsfpOffCtrl
        table
        "
	INDEX   { pmc2002CtrlsfpOffCtrlIndex }
	::= { pmc2002CtrlsfpOffCtrlTable 1 }


Pmc2002CtrlsfpOffCtrlEntry ::=
	SEQUENCE {
	pmc2002CtrlsfpOffCtrlIndex
		INTEGER,
	pmc2002CtrlsfpOffCtrlPortn
		EkiState
	}


pmc2002CtrlsfpOffCtrlIndex OBJECT-TYPE
	SYNTAX  INTEGER(0..128)
	MAX-ACCESS  read-only
	STATUS current
	DESCRIPTION
        "
        Index definition for the pmc2002CtrlsfpOffCtrl
        table
        "
	::= { pmc2002CtrlsfpOffCtrlEntry 1 }


pmc2002CtrlsfpOffCtrlPortn OBJECT-TYPE
	SYNTAX  EkiState
	MAX-ACCESS read-write
	STATUS current
	DESCRIPTION
        "
        Client SFP+ Optical Laser OFF
         :This OID switches off the SFP.
         <Help>  This control defines the
        laser state of the client transceiver
        "
	::= { pmc2002CtrlsfpOffCtrlEntry 2 }


--- *********************************************************
---     TABLE for the pmc2002CtrlcsfUpIns articles
--- *********************************************************

pmc2002CtrlcsfUpInsTable OBJECT-TYPE
	SYNTAX  SEQUENCE OF Pmc2002CtrlcsfUpInsEntry
	MAX-ACCESS not-accessible
	STATUS current
	DESCRIPTION
        "
        List of pmc2002CtrlcsfUpIns Article
        "
	::= { pmc2002CtrlClient 21 }


pmc2002CtrlcsfUpInsEntry OBJECT-TYPE
	SYNTAX Pmc2002CtrlcsfUpInsEntry
	MAX-ACCESS not-accessible
	STATUS current
	DESCRIPTION
        "
        Row definition for the pmc2002CtrlcsfUpIns
        table
        "
	INDEX   { pmc2002CtrlcsfUpInsIndex }
	::= { pmc2002CtrlcsfUpInsTable 1 }


Pmc2002CtrlcsfUpInsEntry ::=
	SEQUENCE {
	pmc2002CtrlcsfUpInsIndex
		INTEGER,
	pmc2002CtrlcsfUpInsPortn
		EkiState
	}


pmc2002CtrlcsfUpInsIndex OBJECT-TYPE
	SYNTAX  INTEGER(0..128)
	MAX-ACCESS  read-only
	STATUS current
	DESCRIPTION
        "
        Index definition for the pmc2002CtrlcsfUpIns
        table
        "
	::= { pmc2002CtrlcsfUpInsEntry 1 }


pmc2002CtrlcsfUpInsPortn OBJECT-TYPE
	SYNTAX  EkiState
	MAX-ACCESS read-write
	STATUS current
	DESCRIPTION
        "
        Client Signal Fail Insertion :This
        OID, when set, inserts  a client
        signal fail in the upstream client
        Port.  <Help>  This control inserts
        a Client Signal Fail for the client
        port
        "
	::= { pmc2002CtrlcsfUpInsEntry 2 }


--- *********************************************************
---     TABLE for the pmc2002CtrlcaisDwIns articles
--- *********************************************************

pmc2002CtrlcaisDwInsTable OBJECT-TYPE
	SYNTAX  SEQUENCE OF Pmc2002CtrlcaisDwInsEntry
	MAX-ACCESS not-accessible
	STATUS current
	DESCRIPTION
        "
        List of pmc2002CtrlcaisDwIns Article
        "
	::= { pmc2002CtrlClient 22 }


pmc2002CtrlcaisDwInsEntry OBJECT-TYPE
	SYNTAX Pmc2002CtrlcaisDwInsEntry
	MAX-ACCESS not-accessible
	STATUS current
	DESCRIPTION
        "
        Row definition for the pmc2002CtrlcaisDwIns
        table
        "
	INDEX   { pmc2002CtrlcaisDwInsIndex }
	::= { pmc2002CtrlcaisDwInsTable 1 }


Pmc2002CtrlcaisDwInsEntry ::=
	SEQUENCE {
	pmc2002CtrlcaisDwInsIndex
		INTEGER,
	pmc2002CtrlcaisDwInsPortn
		EkiState
	}


pmc2002CtrlcaisDwInsIndex OBJECT-TYPE
	SYNTAX  INTEGER(0..128)
	MAX-ACCESS  read-only
	STATUS current
	DESCRIPTION
        "
        Index definition for the pmc2002CtrlcaisDwIns
        table
        "
	::= { pmc2002CtrlcaisDwInsEntry 1 }


pmc2002CtrlcaisDwInsPortn OBJECT-TYPE
	SYNTAX  EkiState
	MAX-ACCESS read-write
	STATUS current
	DESCRIPTION
        "
        Client AIS Insertion :This OID,
        when set, inserts a client AIS
         on the downstream client Port.
         <Help>  This control inserts a
        Client AIS for the client port
        "
	::= { pmc2002CtrlcaisDwInsEntry 2 }


--- *********************************************************
---     TABLE for the pmc2002CtrlclientAccessTermLoop articles
--- *********************************************************

pmc2002CtrlclientAccessTermLoopTable OBJECT-TYPE
	SYNTAX  SEQUENCE OF Pmc2002CtrlclientAccessTermLoopEntry
	MAX-ACCESS not-accessible
	STATUS current
	DESCRIPTION
        "
        List of pmc2002CtrlclientAccessTermLoop
        Article
        "
	::= { pmc2002CtrlClient 26 }


pmc2002CtrlclientAccessTermLoopEntry OBJECT-TYPE
	SYNTAX Pmc2002CtrlclientAccessTermLoopEntry
	MAX-ACCESS not-accessible
	STATUS current
	DESCRIPTION
        "
        Row definition for the pmc2002CtrlclientAccessTermLoop
        table
        "
	INDEX   { pmc2002CtrlclientAccessTermLoopIndex }
	::= { pmc2002CtrlclientAccessTermLoopTable 1 }


Pmc2002CtrlclientAccessTermLoopEntry ::=
	SEQUENCE {
	pmc2002CtrlclientAccessTermLoopIndex
		INTEGER,
	pmc2002CtrlclientAccessTermLoopPortn
		EkiState
	}


pmc2002CtrlclientAccessTermLoopIndex OBJECT-TYPE
	SYNTAX  INTEGER(0..128)
	MAX-ACCESS  read-only
	STATUS current
	DESCRIPTION
        "
        Index definition for the pmc2002CtrlclientAccessTermLoop
        table
        "
	::= { pmc2002CtrlclientAccessTermLoopEntry 1 }


pmc2002CtrlclientAccessTermLoopPortn OBJECT-TYPE
	SYNTAX  EkiState
	MAX-ACCESS read-write
	STATUS current
	DESCRIPTION
        "
        Client Terminal Loopback :This
        OID operates a Client Terminal
         Loopback, looping client input
        signal on the client output port.
        The loop is located on the line
        transceiver  <Help> This maintenance
        parameter operates a Client Terminal
        Loopback, looping client input
         signal on the client output port.
        The loop is located on the line
        transceiver
        "
	::= { pmc2002CtrlclientAccessTermLoopEntry 2 }


--- *********************************************************
---     TABLE for the pmc2002Ctrlprotocol articles
--- *********************************************************

pmc2002CtrlprotocolTable OBJECT-TYPE
	SYNTAX  SEQUENCE OF Pmc2002CtrlprotocolEntry
	MAX-ACCESS not-accessible
	STATUS current
	DESCRIPTION
        "
        List of pmc2002Ctrlprotocol Article
        "
	::= { pmc2002CtrlClient 52 }


pmc2002CtrlprotocolEntry OBJECT-TYPE
	SYNTAX Pmc2002CtrlprotocolEntry
	MAX-ACCESS not-accessible
	STATUS current
	DESCRIPTION
        "
        Row definition for the pmc2002Ctrlprotocol
        table
        "
	INDEX   { pmc2002CtrlprotocolIndex }
	::= { pmc2002CtrlprotocolTable 1 }


Pmc2002CtrlprotocolEntry ::=
	SEQUENCE {
	pmc2002CtrlprotocolIndex
		INTEGER,
	pmc2002CtrlprotocolPortn
		EkiProtocol
	}


pmc2002CtrlprotocolIndex OBJECT-TYPE
	SYNTAX  INTEGER(0..128)
	MAX-ACCESS  read-only
	STATUS current
	DESCRIPTION
        "
        Index definition for the pmc2002Ctrlprotocol
        table
        "
	::= { pmc2002CtrlprotocolEntry 1 }


pmc2002CtrlprotocolPortn OBJECT-TYPE
	SYNTAX  EkiProtocol
	MAX-ACCESS read-write
	STATUS current
	DESCRIPTION
        "
        Protocol used for client port:
        This OID sets the protocol of the
        Client port.
        "
	::= { pmc2002CtrlprotocolEntry 2 }


--- *********************************************************
---     TABLE for the pmc2002CtrlcommAccessLoop articles
--- *********************************************************

pmc2002CtrlcommAccessLoopTable OBJECT-TYPE
	SYNTAX  SEQUENCE OF Pmc2002CtrlcommAccessLoopEntry
	MAX-ACCESS not-accessible
	STATUS deprecated
	DESCRIPTION
        "
        List of pmc2002CtrlcommAccessLoop
        Article
        "
	::= { pmc2002CtrlLine 64 }


pmc2002CtrlcommAccessLoopEntry OBJECT-TYPE
	SYNTAX Pmc2002CtrlcommAccessLoopEntry
	MAX-ACCESS not-accessible
	STATUS deprecated
	DESCRIPTION
        "
        Row definition for the pmc2002CtrlcommAccessLoop
        table
        "
	INDEX   { pmc2002CtrlcommAccessLoopIndex }
	::= { pmc2002CtrlcommAccessLoopTable 1 }


Pmc2002CtrlcommAccessLoopEntry ::=
	SEQUENCE {
	pmc2002CtrlcommAccessLoopIndex
		INTEGER,
	pmc2002CtrlcommAccessLoopPortn
		EkiState
	}


pmc2002CtrlcommAccessLoopIndex OBJECT-TYPE
	SYNTAX  INTEGER(0..128)
	MAX-ACCESS  read-only
	STATUS deprecated
	DESCRIPTION
        "
        Index definition for the pmc2002CtrlcommAccessLoop
        table
        "
	::= { pmc2002CtrlcommAccessLoopEntry 1 }


pmc2002CtrlcommAccessLoopPortn OBJECT-TYPE
	SYNTAX  EkiState
	MAX-ACCESS read-write
	STATUS deprecated
	DESCRIPTION
        "
        PM Full Access Loop Mode :This
        OID, when set, puts the module
         in common access loop back, looping
        the 10 Gb/s output signal on the
        10 Gb/s input.
        "
	::= { pmc2002CtrlcommAccessLoopEntry 2 }


--- *********************************************************
---     TABLE for the pmc2002CtrllineLoop articles
--- *********************************************************

pmc2002CtrllineLoopTable OBJECT-TYPE
	SYNTAX  SEQUENCE OF Pmc2002CtrllineLoopEntry
	MAX-ACCESS not-accessible
	STATUS current
	DESCRIPTION
        "
        List of pmc2002CtrllineLoop Article
        "
	::= { pmc2002CtrlLine 66 }


pmc2002CtrllineLoopEntry OBJECT-TYPE
	SYNTAX Pmc2002CtrllineLoopEntry
	MAX-ACCESS not-accessible
	STATUS current
	DESCRIPTION
        "
        Row definition for the pmc2002CtrllineLoop
        table
        "
	INDEX   { pmc2002CtrllineLoopIndex }
	::= { pmc2002CtrllineLoopTable 1 }


Pmc2002CtrllineLoopEntry ::=
	SEQUENCE {
	pmc2002CtrllineLoopIndex
		INTEGER,
	pmc2002CtrllineLoopPortn
		EkiState
	}


pmc2002CtrllineLoopIndex OBJECT-TYPE
	SYNTAX  INTEGER(0..128)
	MAX-ACCESS  read-only
	STATUS current
	DESCRIPTION
        "
        Index definition for the pmc2002CtrllineLoop
        table
        "
	::= { pmc2002CtrllineLoopEntry 1 }


pmc2002CtrllineLoopPortn OBJECT-TYPE
	SYNTAX  EkiState
	MAX-ACCESS read-write
	STATUS current
	DESCRIPTION
        "
        Line Facility Loopback :This OID
        operates a Line Facility Loopback,
        looping line input signal on the
        line output port. The loop is located
        on the line transceiver. If the
        Line signal carries DCC, the management
        network is impacted  <Help> This
        maintenance parameter operates
         a Line Facility Loopback, looping
        line input signal on the line output
        port. The loop is located on the
        line transceiver. If the Line signal
        carries DCC, the management network
        is impacted
        "
	::= { pmc2002CtrllineLoopEntry 2 }


--- *********************************************************
---     TABLE for the pmc2002CtrlmsAis articles
--- *********************************************************

pmc2002CtrlmsAisTable OBJECT-TYPE
	SYNTAX  SEQUENCE OF Pmc2002CtrlmsAisEntry
	MAX-ACCESS not-accessible
	STATUS current
	DESCRIPTION
        "
        List of pmc2002CtrlmsAis Article
        "
	::= { pmc2002CtrlLine 67 }


pmc2002CtrlmsAisEntry OBJECT-TYPE
	SYNTAX Pmc2002CtrlmsAisEntry
	MAX-ACCESS not-accessible
	STATUS current
	DESCRIPTION
        "
        Row definition for the pmc2002CtrlmsAis
        table
        "
	INDEX   { pmc2002CtrlmsAisIndex }
	::= { pmc2002CtrlmsAisTable 1 }


Pmc2002CtrlmsAisEntry ::=
	SEQUENCE {
	pmc2002CtrlmsAisIndex
		INTEGER,
	pmc2002CtrlmsAisPortn
		EkiState
	}


pmc2002CtrlmsAisIndex OBJECT-TYPE
	SYNTAX  INTEGER(0..128)
	MAX-ACCESS  read-only
	STATUS current
	DESCRIPTION
        "
        Index definition for the pmc2002CtrlmsAis
        table
        "
	::= { pmc2002CtrlmsAisEntry 1 }


pmc2002CtrlmsAisPortn OBJECT-TYPE
	SYNTAX  EkiState
	MAX-ACCESS read-write
	STATUS current
	DESCRIPTION
        "
        Insert MS-AIS/L-AIS On Line Output
        :This OID, when set, inserts an
        MS-AIS/L-AIS in the outgoing STM-64/OC-192
        signal.
        "
	::= { pmc2002CtrlmsAisEntry 2 }


--- *********************************************************
---     TABLE for the pmc2002CtrlfecDisable articles
--- *********************************************************

pmc2002CtrlfecDisableTable OBJECT-TYPE
	SYNTAX  SEQUENCE OF Pmc2002CtrlfecDisableEntry
	MAX-ACCESS not-accessible
	STATUS current
	DESCRIPTION
        "
        List of pmc2002CtrlfecDisable
         Article
        "
	::= { pmc2002CtrlLine 69 }


pmc2002CtrlfecDisableEntry OBJECT-TYPE
	SYNTAX Pmc2002CtrlfecDisableEntry
	MAX-ACCESS not-accessible
	STATUS current
	DESCRIPTION
        "
        Row definition for the pmc2002CtrlfecDisable
        table
        "
	INDEX   { pmc2002CtrlfecDisableIndex }
	::= { pmc2002CtrlfecDisableTable 1 }


Pmc2002CtrlfecDisableEntry ::=
	SEQUENCE {
	pmc2002CtrlfecDisableIndex
		INTEGER,
	pmc2002CtrlfecDisablePortn
		EkiState
	}


pmc2002CtrlfecDisableIndex OBJECT-TYPE
	SYNTAX  INTEGER(0..128)
	MAX-ACCESS  read-only
	STATUS current
	DESCRIPTION
        "
        Index definition for the pmc2002CtrlfecDisable
        table
        "
	::= { pmc2002CtrlfecDisableEntry 1 }


pmc2002CtrlfecDisablePortn OBJECT-TYPE
	SYNTAX  EkiState
	MAX-ACCESS read-write
	STATUS current
	DESCRIPTION
        "
        FEC Disable :This OID disable
         the Forward Error Correction decoder
        on the line receive side  <Help>
         This control disables the Forward
        Error Correction on the line input
        signal.
        "
	::= { pmc2002CtrlfecDisableEntry 2 }


--- *********************************************************
---     TABLE for the pmc2002CtrllineOosMode articles
--- *********************************************************

pmc2002CtrllineOosModeTable OBJECT-TYPE
	SYNTAX  SEQUENCE OF Pmc2002CtrllineOosModeEntry
	MAX-ACCESS not-accessible
	STATUS current
	DESCRIPTION
        "
        List of pmc2002CtrllineOosMode
        Article
        "
	::= { pmc2002CtrlLine 74 }


pmc2002CtrllineOosModeEntry OBJECT-TYPE
	SYNTAX Pmc2002CtrllineOosModeEntry
	MAX-ACCESS not-accessible
	STATUS current
	DESCRIPTION
        "
        Row definition for the pmc2002CtrllineOosMode
        table
        "
	INDEX   { pmc2002CtrllineOosModeIndex }
	::= { pmc2002CtrllineOosModeTable 1 }


Pmc2002CtrllineOosModeEntry ::=
	SEQUENCE {
	pmc2002CtrllineOosModeIndex
		INTEGER,
	pmc2002CtrllineOosModePortn
		EkiState
	}


pmc2002CtrllineOosModeIndex OBJECT-TYPE
	SYNTAX  INTEGER(0..128)
	MAX-ACCESS  read-only
	STATUS current
	DESCRIPTION
        "
        Index definition for the pmc2002CtrllineOosMode
        table
        "
	::= { pmc2002CtrllineOosModeEntry 1 }


pmc2002CtrllineOosModePortn OBJECT-TYPE
	SYNTAX  EkiState
	MAX-ACCESS read-write
	STATUS current
	DESCRIPTION
        "
        Line Port Out Of Service :This
        OID sets the line port Out Of Service
         <Help>  This control defines the
        service state of the line port
        "
	::= { pmc2002CtrllineOosModeEntry 2 }


--- *****************************************************
---     LEAF for the ledTest article
--- *****************************************************
pmc2002CtrlledTest OBJECT IDENTIFIER ::= { pmc2002CtrlOther 192 }




pmc2002CtrlLedOff OBJECT-TYPE
	  SYNTAX EkiOnOff
	  MAX-ACCESS read-write
	  STATUS current
	  DESCRIPTION
        "
        Leds Off :This OID switches off
        all the Leds as a test feature.
         <Help>  This control initiates
        a test leds turning all the LEDs
        to OFF
        "
	  ::= { pmc2002CtrlledTest 3 }



pmc2002CtrlRedLed OBJECT-TYPE
	  SYNTAX EkiOnOff
	  MAX-ACCESS read-write
	  STATUS current
	  DESCRIPTION
        "
        Red Leds Test :This OID switches
        on all the red Leds as a test feature.
         <Help>  This control initiates
        a test leds turning all the LEDs
        to red
        "
	  ::= { pmc2002CtrlledTest 2 }



pmc2002CtrlGreenLed OBJECT-TYPE
	  SYNTAX EkiOnOff
	  MAX-ACCESS read-write
	  STATUS current
	  DESCRIPTION
        "
        Green Leds Test :This OID switches
        on all the green Leds as a test
        feature.  <Help>  This control
         initiates a test leds turning
         all the LEDs to green
        "
	  ::= { pmc2002CtrlledTest 1 }



--- *****************************************************
---     LEAF for the moduleOosMode article
--- *****************************************************
pmc2002CtrlmoduleOosMode OBJECT IDENTIFIER ::= { pmc2002CtrlOther 193 }




pmc2002CtrlModuleOosMode OBJECT-TYPE
	  SYNTAX EkiOnOff
	  MAX-ACCESS read-write
	  STATUS current
	  DESCRIPTION
        "
        PM Out Of Service :This OID sets
        the PM1008 Out Of Service  <Help>
         This control defines the service
        state of the complete module
        "
	  ::= { pmc2002CtrlmoduleOosMode 1 }



--- *****************************************************
---     LEAF for the moduleDccMgnt article
--- *****************************************************

pmc2002CtrlmoduleDccMgnt OBJECT-TYPE
	  SYNTAX Pmc2002DccMode
	  MAX-ACCESS read-write
	  STATUS current
	  DESCRIPTION
        "
        DCC Mode :This OID defines the
        DCC mode of the PM (No DCC, Terminal
        Line 1, Terminal Line 2, Terminal
        Line 1&2)   <Help>  This control
        defines the DCC mode of the PM
         (No DCC, Terminal Line 1, Terminal
        Line 2 or Terminal Line 1&2)

        "
	  ::= { pmc2002CtrlOther 196 }



--- *****************************************************
---     LEAF for the maintenanceMode article
--- *****************************************************
pmc2002CtrlmaintenanceMode OBJECT IDENTIFIER ::= { pmc2002CtrlOther 197 }




pmc2002CtrlMaintenanceMode OBJECT-TYPE
	  SYNTAX EkiOnOff
	  MAX-ACCESS read-write
	  STATUS current
	  DESCRIPTION
        "
        Enable Maintenance :This OID enables
        the maintenance mode on the PM.
         <Help>   This control enables
         the maintenance mode on the PM.
        "
	  ::= { pmc2002CtrlmaintenanceMode 1 }



--- *********************************************************
---     TABLE for the pmc2002CtrlxfpOnoff articles
--- *********************************************************

pmc2002CtrlxfpOnoffTable OBJECT-TYPE
	SYNTAX  SEQUENCE OF Pmc2002CtrlxfpOnoffEntry
	MAX-ACCESS not-accessible
	STATUS current
	DESCRIPTION
        "
        List of pmc2002CtrlxfpOnoff Article
        "
	::= { pmc2002CtrlLine 208 }


pmc2002CtrlxfpOnoffEntry OBJECT-TYPE
	SYNTAX Pmc2002CtrlxfpOnoffEntry
	MAX-ACCESS not-accessible
	STATUS current
	DESCRIPTION
        "
        Row definition for the pmc2002CtrlxfpOnoff
        table
        "
	INDEX   { pmc2002CtrlxfpOnoffIndex }
	::= { pmc2002CtrlxfpOnoffTable 1 }


Pmc2002CtrlxfpOnoffEntry ::=
	SEQUENCE {
	pmc2002CtrlxfpOnoffIndex
		INTEGER,
	pmc2002CtrlxfpOnoffPortn
		EkiState
	}


pmc2002CtrlxfpOnoffIndex OBJECT-TYPE
	SYNTAX  INTEGER(0..128)
	MAX-ACCESS  read-only
	STATUS current
	DESCRIPTION
        "
        Index definition for the pmc2002CtrlxfpOnoff
        table
        "
	::= { pmc2002CtrlxfpOnoffEntry 1 }


pmc2002CtrlxfpOnoffPortn OBJECT-TYPE
	SYNTAX  EkiState
	MAX-ACCESS read-write
	STATUS current
	DESCRIPTION
        "
        XFP/OTX Optical Laser OFF :This
        OID switches off the XFP or the
        OTX  <Help>  This control defines
        the laser state of the line transceiver
        "
	::= { pmc2002CtrlxfpOnoffEntry 2 }


--- *********************************************************
---     TABLE for the pmc2002CtrlxfpLineLoop articles
--- *********************************************************

pmc2002CtrlxfpLineLoopTable OBJECT-TYPE
	SYNTAX  SEQUENCE OF Pmc2002CtrlxfpLineLoopEntry
	MAX-ACCESS not-accessible
	STATUS current
	DESCRIPTION
        "
        List of pmc2002CtrlxfpLineLoop
        Article
        "
	::= { pmc2002CtrlLine 209 }


pmc2002CtrlxfpLineLoopEntry OBJECT-TYPE
	SYNTAX Pmc2002CtrlxfpLineLoopEntry
	MAX-ACCESS not-accessible
	STATUS current
	DESCRIPTION
        "
        Row definition for the pmc2002CtrlxfpLineLoop
        table
        "
	INDEX   { pmc2002CtrlxfpLineLoopIndex }
	::= { pmc2002CtrlxfpLineLoopTable 1 }


Pmc2002CtrlxfpLineLoopEntry ::=
	SEQUENCE {
	pmc2002CtrlxfpLineLoopIndex
		INTEGER,
	pmc2002CtrlxfpLineLoopPortn
		EkiState
	}


pmc2002CtrlxfpLineLoopIndex OBJECT-TYPE
	SYNTAX  INTEGER(0..128)
	MAX-ACCESS  read-only
	STATUS current
	DESCRIPTION
        "
        Index definition for the pmc2002CtrlxfpLineLoop
        table
        "
	::= { pmc2002CtrlxfpLineLoopEntry 1 }


pmc2002CtrlxfpLineLoopPortn OBJECT-TYPE
	SYNTAX  EkiState
	MAX-ACCESS read-write
	STATUS current
	DESCRIPTION
        "
        Line XFP/OTX Loop :This OID operates
        a line loopback on the line XFP
        or the OTX  <Help>  This control
        defines the line loop back of the
        line transceiver
        "
	::= { pmc2002CtrlxfpLineLoopEntry 2 }


--- *********************************************************
---     TABLE for the pmc2002CtrlxfpLineXfiLoop articles
--- *********************************************************

pmc2002CtrlxfpLineXfiLoopTable OBJECT-TYPE
	SYNTAX  SEQUENCE OF Pmc2002CtrlxfpLineXfiLoopEntry
	MAX-ACCESS not-accessible
	STATUS current
	DESCRIPTION
        "
        List of pmc2002CtrlxfpLineXfiLoop
        Article
        "
	::= { pmc2002CtrlLine 210 }


pmc2002CtrlxfpLineXfiLoopEntry OBJECT-TYPE
	SYNTAX Pmc2002CtrlxfpLineXfiLoopEntry
	MAX-ACCESS not-accessible
	STATUS current
	DESCRIPTION
        "
        Row definition for the pmc2002CtrlxfpLineXfiLoop
        table
        "
	INDEX   { pmc2002CtrlxfpLineXfiLoopIndex }
	::= { pmc2002CtrlxfpLineXfiLoopTable 1 }


Pmc2002CtrlxfpLineXfiLoopEntry ::=
	SEQUENCE {
	pmc2002CtrlxfpLineXfiLoopIndex
		INTEGER,
	pmc2002CtrlxfpLineXfiLoopPortn
		EkiState
	}


pmc2002CtrlxfpLineXfiLoopIndex OBJECT-TYPE
	SYNTAX  INTEGER(0..128)
	MAX-ACCESS  read-only
	STATUS current
	DESCRIPTION
        "
        Index definition for the pmc2002CtrlxfpLineXfiLoop
        table
        "
	::= { pmc2002CtrlxfpLineXfiLoopEntry 1 }


pmc2002CtrlxfpLineXfiLoopPortn OBJECT-TYPE
	SYNTAX  EkiState
	MAX-ACCESS read-write
	STATUS current
	DESCRIPTION
        "
        Line XFP/OTX XFI Loop :This OID
        operates a XFI loopback on the
         line XFP or the OTX  <Help>  This
        control defines the XFI loop back
        of the line transceiver
        "
	::= { pmc2002CtrlxfpLineXfiLoopEntry 2 }


--- *********************************************************
---     TABLE for the pmc2002CtrllineTunableChannel articles
--- *********************************************************

pmc2002CtrllineTunableChannelTable OBJECT-TYPE
	SYNTAX  SEQUENCE OF Pmc2002CtrllineTunableChannelEntry
	MAX-ACCESS not-accessible
	STATUS current
	DESCRIPTION
        "
        List of pmc2002CtrllineTunableChannel
        Article
        "
	::= { pmc2002CtrlLine 212 }


pmc2002CtrllineTunableChannelEntry OBJECT-TYPE
	SYNTAX Pmc2002CtrllineTunableChannelEntry
	MAX-ACCESS not-accessible
	STATUS current
	DESCRIPTION
        "
        Row definition for the pmc2002CtrllineTunableChannel
        table
        "
	INDEX   { pmc2002CtrllineTunableChannelIndex }
	::= { pmc2002CtrllineTunableChannelTable 1 }


Pmc2002CtrllineTunableChannelEntry ::=
	SEQUENCE {
	pmc2002CtrllineTunableChannelIndex
		INTEGER,
	pmc2002CtrllineTunableChannelPortn
		Pmc2002OtxChannel
	}


pmc2002CtrllineTunableChannelIndex OBJECT-TYPE
	SYNTAX  INTEGER(0..128)
	MAX-ACCESS  read-only
	STATUS current
	DESCRIPTION
        "
        Index definition for the pmc2002CtrllineTunableChannel
        table
        "
	::= { pmc2002CtrllineTunableChannelEntry 1 }


pmc2002CtrllineTunableChannelPortn OBJECT-TYPE
	SYNTAX  Pmc2002OtxChannel
	MAX-ACCESS read-write
	STATUS current
	DESCRIPTION
        "
        ITU Channel :This OID selects
         the ITU channel of the Line OTX
        TLH Laser  <Help>   This control
        defines the ITU channel of the
         Line OTX TLH Laser
        "
	::= { pmc2002CtrllineTunableChannelEntry 2 }


--- *********************************************************
---     TABLE for the pmc2002CtrllinePhotodiodeMode articles
--- *********************************************************

pmc2002CtrllinePhotodiodeModeTable OBJECT-TYPE
	SYNTAX  SEQUENCE OF Pmc2002CtrllinePhotodiodeModeEntry
	MAX-ACCESS not-accessible
	STATUS current
	DESCRIPTION
        "
        List of pmc2002CtrllinePhotodiodeMode
        Article
        "
	::= { pmc2002CtrlLine 213 }


pmc2002CtrllinePhotodiodeModeEntry OBJECT-TYPE
	SYNTAX Pmc2002CtrllinePhotodiodeModeEntry
	MAX-ACCESS not-accessible
	STATUS current
	DESCRIPTION
        "
        Row definition for the pmc2002CtrllinePhotodiodeMode
        table
        "
	INDEX   { pmc2002CtrllinePhotodiodeModeIndex }
	::= { pmc2002CtrllinePhotodiodeModeTable 1 }


Pmc2002CtrllinePhotodiodeModeEntry ::=
	SEQUENCE {
	pmc2002CtrllinePhotodiodeModeIndex
		INTEGER,
	pmc2002CtrllinePhotodiodeModePortn
		Pmc2002OtxMode
	}


pmc2002CtrllinePhotodiodeModeIndex OBJECT-TYPE
	SYNTAX  INTEGER(0..128)
	MAX-ACCESS  read-only
	STATUS current
	DESCRIPTION
        "
        Index definition for the pmc2002CtrllinePhotodiodeMode
        table
        "
	::= { pmc2002CtrllinePhotodiodeModeEntry 1 }


pmc2002CtrllinePhotodiodeModePortn OBJECT-TYPE
	SYNTAX  Pmc2002OtxMode
	MAX-ACCESS read-write
	STATUS current
	DESCRIPTION
        "
        OTX TLH Rx Sens. Mode :This OID
        defines the Rx sensiblity mode
         of the Line OTX TLH  <Help>
         This control defines the receiver
        sensibility mode of the Line OTX
        TLH Laser (OTX60, OTX80 or Custom)
        "
	::= { pmc2002CtrllinePhotodiodeModeEntry 2 }


--- *********************************************************
---     TABLE for the pmc2002CtrllinePhotodiodeValue articles
--- *********************************************************

pmc2002CtrllinePhotodiodeValueTable OBJECT-TYPE
	SYNTAX  SEQUENCE OF Pmc2002CtrllinePhotodiodeValueEntry
	MAX-ACCESS not-accessible
	STATUS current
	DESCRIPTION
        "
        List of pmc2002CtrllinePhotodiodeValue
        Article
        "
	::= { pmc2002CtrlLine 214 }


pmc2002CtrllinePhotodiodeValueEntry OBJECT-TYPE
	SYNTAX Pmc2002CtrllinePhotodiodeValueEntry
	MAX-ACCESS not-accessible
	STATUS current
	DESCRIPTION
        "
        Row definition for the pmc2002CtrllinePhotodiodeValue
        table
        "
	INDEX   { pmc2002CtrllinePhotodiodeValueIndex }
	::= { pmc2002CtrllinePhotodiodeValueTable 1 }


Pmc2002CtrllinePhotodiodeValueEntry ::=
	SEQUENCE {
	pmc2002CtrllinePhotodiodeValueIndex
		INTEGER,
	pmc2002CtrllinePhotodiodeValuePortn
		Pmc2002AdjustValue
	}


pmc2002CtrllinePhotodiodeValueIndex OBJECT-TYPE
	SYNTAX  INTEGER(0..128)
	MAX-ACCESS  read-only
	STATUS current
	DESCRIPTION
        "
        Index definition for the pmc2002CtrllinePhotodiodeValue
        table
        "
	::= { pmc2002CtrllinePhotodiodeValueEntry 1 }


pmc2002CtrllinePhotodiodeValuePortn OBJECT-TYPE
	SYNTAX  Pmc2002AdjustValue
	MAX-ACCESS read-write
	STATUS current
	DESCRIPTION
        "
        OTX TLH Rx Sensibility :This OID
        sets the Rx sensibility of the
         Line OTX TLH (custom mode only)
         <Help>   This control defines
         the receiver sensibility value
        (only in Custom mode) of the Line
        OTX TLH Laser
        "
	::= { pmc2002CtrllinePhotodiodeValueEntry 2 }


--- *********************************************************
---     TABLE for the pmc2002CtrllinePowerLaser articles
--- *********************************************************

pmc2002CtrllinePowerLaserTable OBJECT-TYPE
	SYNTAX  SEQUENCE OF Pmc2002CtrllinePowerLaserEntry
	MAX-ACCESS not-accessible
	STATUS current
	DESCRIPTION
        "
        List of pmc2002CtrllinePowerLaser
        Article
        "
	::= { pmc2002CtrlLine 215 }


pmc2002CtrllinePowerLaserEntry OBJECT-TYPE
	SYNTAX Pmc2002CtrllinePowerLaserEntry
	MAX-ACCESS not-accessible
	STATUS current
	DESCRIPTION
        "
        Row definition for the pmc2002CtrllinePowerLaser
        table
        "
	INDEX   { pmc2002CtrllinePowerLaserIndex }
	::= { pmc2002CtrllinePowerLaserTable 1 }


Pmc2002CtrllinePowerLaserEntry ::=
	SEQUENCE {
	pmc2002CtrllinePowerLaserIndex
		INTEGER,
	pmc2002CtrllinePowerLaserPortn
		INTEGER
	}


pmc2002CtrllinePowerLaserIndex OBJECT-TYPE
	SYNTAX  INTEGER(0..128)
	MAX-ACCESS  read-only
	STATUS current
	DESCRIPTION
        "
        Index definition for the pmc2002CtrllinePowerLaser
        table
        "
	::= { pmc2002CtrllinePowerLaserEntry 1 }


pmc2002CtrllinePowerLaserPortn OBJECT-TYPE
	SYNTAX  INTEGER (0..255)
	MAX-ACCESS read-write
	STATUS current
	DESCRIPTION
        "
        Laser Output Power [3-5] :This
        OID sets the output power value
        on the laser of the Line OTX TLH
        (AV=Power*10+158)  (Unit = dBm)
         <Help>   This control defines
         the start-up output power of the
        Line OTX TLH
        "
	::= { pmc2002CtrllinePowerLaserEntry 2 }


--- *********************************************************
---     TABLE for the pmc2002CtrlotxVlhReset articles
--- *********************************************************

pmc2002CtrlotxVlhResetTable OBJECT-TYPE
	SYNTAX  SEQUENCE OF Pmc2002CtrlotxVlhResetEntry
	MAX-ACCESS not-accessible
	STATUS current
	DESCRIPTION
        "
        List of pmc2002CtrlotxVlhReset
        Article
        "
	::= { pmc2002CtrlLine 216 }


pmc2002CtrlotxVlhResetEntry OBJECT-TYPE
	SYNTAX Pmc2002CtrlotxVlhResetEntry
	MAX-ACCESS not-accessible
	STATUS current
	DESCRIPTION
        "
        Row definition for the pmc2002CtrlotxVlhReset
        table
        "
	INDEX   { pmc2002CtrlotxVlhResetIndex }
	::= { pmc2002CtrlotxVlhResetTable 1 }


Pmc2002CtrlotxVlhResetEntry ::=
	SEQUENCE {
	pmc2002CtrlotxVlhResetIndex
		INTEGER,
	pmc2002CtrlotxVlhResetPortn
		EkiState
	}


pmc2002CtrlotxVlhResetIndex OBJECT-TYPE
	SYNTAX  INTEGER(0..128)
	MAX-ACCESS  read-only
	STATUS current
	DESCRIPTION
        "
        Index definition for the pmc2002CtrlotxVlhReset
        table
        "
	::= { pmc2002CtrlotxVlhResetEntry 1 }


pmc2002CtrlotxVlhResetPortn OBJECT-TYPE
	SYNTAX  EkiState
	MAX-ACCESS read-write
	STATUS current
	DESCRIPTION
        "
        OTX-VLH Reset :This OID resets
        the OTX-VLH module  <Help>  This
        control resets the OTX-VLH and
         its parameters
        "
	::= { pmc2002CtrlotxVlhResetEntry 2 }


--- *********************************************************
---     TABLE for the pmc2002CtrllineLoopTransceiver articles
--- *********************************************************

pmc2002CtrllineLoopTransceiverTable OBJECT-TYPE
	SYNTAX  SEQUENCE OF Pmc2002CtrllineLoopTransceiverEntry
	MAX-ACCESS not-accessible
	STATUS current
	DESCRIPTION
        "
        List of pmc2002CtrllineLoopTransceiver
        Article
        "
	::= { pmc2002CtrlLine 218 }


pmc2002CtrllineLoopTransceiverEntry OBJECT-TYPE
	SYNTAX Pmc2002CtrllineLoopTransceiverEntry
	MAX-ACCESS not-accessible
	STATUS current
	DESCRIPTION
        "
        Row definition for the pmc2002CtrllineLoopTransceiver
        table
        "
	INDEX   { pmc2002CtrllineLoopTransceiverIndex }
	::= { pmc2002CtrllineLoopTransceiverTable 1 }


Pmc2002CtrllineLoopTransceiverEntry ::=
	SEQUENCE {
	pmc2002CtrllineLoopTransceiverIndex
		INTEGER,
	pmc2002CtrllineLoopTransceiverPortn
		EkiState
	}


pmc2002CtrllineLoopTransceiverIndex OBJECT-TYPE
	SYNTAX  INTEGER(0..128)
	MAX-ACCESS  read-only
	STATUS current
	DESCRIPTION
        "
        Index definition for the pmc2002CtrllineLoopTransceiver
        table
        "
	::= { pmc2002CtrllineLoopTransceiverEntry 1 }


pmc2002CtrllineLoopTransceiverPortn OBJECT-TYPE
	SYNTAX  EkiState
	MAX-ACCESS read-write
	STATUS current
	DESCRIPTION
        "
        Line Terminal Loopback :This OID
        operates a Line Terminal Loopback,
        looping line input signal on the
        line output port. The loop is located
        on all client transceivers  <Help>
        This maintenance parameter operates
        a Line Terminal Loopback, looping
        line input signal on the line output
        port. The loop is located on all
        client transceivers.
        "
	::= { pmc2002CtrllineLoopTransceiverEntry 2 }


--- *********************************************************
---     TABLE for the pmc2002CtrlclientResetAllCount articles
--- *********************************************************

pmc2002CtrlclientResetAllCountTable OBJECT-TYPE
	SYNTAX  SEQUENCE OF Pmc2002CtrlclientResetAllCountEntry
	MAX-ACCESS not-accessible
	STATUS current
	DESCRIPTION
        "
        List of pmc2002CtrlclientResetAllCount
        Article
        "
	::= { pmc2002CtrlClient 271 }


pmc2002CtrlclientResetAllCountEntry OBJECT-TYPE
	SYNTAX Pmc2002CtrlclientResetAllCountEntry
	MAX-ACCESS not-accessible
	STATUS current
	DESCRIPTION
        "
        Row definition for the pmc2002CtrlclientResetAllCount
        table
        "
	INDEX   { pmc2002CtrlclientResetAllCountIndex }
	::= { pmc2002CtrlclientResetAllCountTable 1 }


Pmc2002CtrlclientResetAllCountEntry ::=
	SEQUENCE {
	pmc2002CtrlclientResetAllCountIndex
		INTEGER,
	pmc2002CtrlclientResetAllCountsPortn
		EkiState
	}


pmc2002CtrlclientResetAllCountIndex OBJECT-TYPE
	SYNTAX  INTEGER(0..128)
	MAX-ACCESS  read-only
	STATUS current
	DESCRIPTION
        "
        Index definition for the pmc2002CtrlclientResetAllCount
        table
        "
	::= { pmc2002CtrlclientResetAllCountEntry 1 }


pmc2002CtrlclientResetAllCountsPortn OBJECT-TYPE
	SYNTAX  EkiState
	MAX-ACCESS read-write
	STATUS current
	DESCRIPTION
        "
        Client Counters Reset :This OID
        resets every counter on the client
        port  <Help>   This control operates
        a reset on the statistics current
        ,previous and history client port
        counters
        "
	::= { pmc2002CtrlclientResetAllCountEntry 2 }


--- *********************************************************
---     TABLE for the pmc2002CtrllineResetAllCount articles
--- *********************************************************

pmc2002CtrllineResetAllCountTable OBJECT-TYPE
	SYNTAX  SEQUENCE OF Pmc2002CtrllineResetAllCountEntry
	MAX-ACCESS not-accessible
	STATUS current
	DESCRIPTION
        "
        List of pmc2002CtrllineResetAllCount
        Article
        "
	::= { pmc2002CtrlLine 335 }


pmc2002CtrllineResetAllCountEntry OBJECT-TYPE
	SYNTAX Pmc2002CtrllineResetAllCountEntry
	MAX-ACCESS not-accessible
	STATUS current
	DESCRIPTION
        "
        Row definition for the pmc2002CtrllineResetAllCount
        table
        "
	INDEX   { pmc2002CtrllineResetAllCountIndex }
	::= { pmc2002CtrllineResetAllCountTable 1 }


Pmc2002CtrllineResetAllCountEntry ::=
	SEQUENCE {
	pmc2002CtrllineResetAllCountIndex
		INTEGER,
	pmc2002CtrllineResetAllCountsPortn
		EkiState
	}


pmc2002CtrllineResetAllCountIndex OBJECT-TYPE
	SYNTAX  INTEGER(0..128)
	MAX-ACCESS  read-only
	STATUS current
	DESCRIPTION
        "
        Index definition for the pmc2002CtrllineResetAllCount
        table
        "
	::= { pmc2002CtrllineResetAllCountEntry 1 }


pmc2002CtrllineResetAllCountsPortn OBJECT-TYPE
	SYNTAX  EkiState
	MAX-ACCESS read-write
	STATUS current
	DESCRIPTION
        "
        Line Counters Reset :This OID
         resets every counter on the line
        port  <Help>   This control operates
        a reset on the statistics current
        ,previous and history line port
        counters
        "
	::= { pmc2002CtrllineResetAllCountEntry 2 }







--- *****************************************************
--- $$$$$$$$$$$$$$$$$$$$$$$$$$$$$$$$$$$$$$$$$$$$$$$$$$$$$
---     COUNTERS
--- $$$$$$$$$$$$$$$$$$$$$$$$$$$$$$$$$$$$$$$$$$$$$$$$$$$$$
--- *****************************************************



--- *********************************************************
---     TABLE for the pmc2002CntclientUpErrCnt articles
--- *********************************************************

pmc2002CntclientUpErrCntTable OBJECT-TYPE
	SYNTAX  SEQUENCE OF Pmc2002CntclientUpErrCntEntry
	MAX-ACCESS not-accessible
	STATUS current
	DESCRIPTION
        "
        List of pmc2002CntclientUpErrCnt
        Article
        "
	::= { pmc2002CntClient 32 }


pmc2002CntclientUpErrCntEntry OBJECT-TYPE
	SYNTAX Pmc2002CntclientUpErrCntEntry
	MAX-ACCESS not-accessible
	STATUS current
	DESCRIPTION
        "
        Row definition for the pmc2002CntclientUpErrCnt
        table
        "
	INDEX   { pmc2002CntclientUpErrCntIndex }
	::= { pmc2002CntclientUpErrCntTable 1 }


Pmc2002CntclientUpErrCntEntry ::=
	SEQUENCE {
	pmc2002CntclientUpErrCntIndex
		INTEGER,
	pmc2002CntclientUpErrCntValuePortn
		Counter32,
	pmc2002CntclientUpErrCntErrorPortn
		EkiOnOff,
	pmc2002CntclientUpErrCntOverloadPortn
		EkiOnOff
	}


pmc2002CntclientUpErrCntIndex OBJECT-TYPE
	SYNTAX  INTEGER(0..128)
	MAX-ACCESS  read-only
	STATUS current
	DESCRIPTION
        "
        Index definition for the pmc2002CntclientUpErrCnt
        table
        "
	::= { pmc2002CntclientUpErrCntEntry 1 }


pmc2002CntclientUpErrCntValuePortn OBJECT-TYPE
	SYNTAX  Counter32
	MAX-ACCESS read-only
	STATUS current
	DESCRIPTION
        "
        Client Input Errors :This counter
        is increased each time a FCS error
        is detected in 10GbE mode or a
         B1 error is detected in OC-192/STM-64
        mode on the client input stream
         <Help>  This counter gives the
        number of FCS errors or B1 errors
        on the client input port
        "
	::= { pmc2002CntclientUpErrCntEntry 2 }


pmc2002CntclientUpErrCntErrorPortn OBJECT-TYPE
	SYNTAX  EkiOnOff
	MAX-ACCESS read-only
	STATUS current
	DESCRIPTION
        "
        Client Counter Error :This OID
        when set indicates the FCS error
        counter value is invalid on input
        Port
        "
	::= { pmc2002CntclientUpErrCntEntry 3 }


pmc2002CntclientUpErrCntOverloadPortn OBJECT-TYPE
	SYNTAX  EkiOnOff
	MAX-ACCESS read-only
	STATUS current
	DESCRIPTION
        "
        Client Counter Overload :This
         OID when set indicates a FCS error
        counter overload on input Port
        "
	::= { pmc2002CntclientUpErrCntEntry 4 }


--- *********************************************************
---     TABLE for the pmc2002CntclientUpTimCnt articles
--- *********************************************************

pmc2002CntclientUpTimCntTable OBJECT-TYPE
	SYNTAX  SEQUENCE OF Pmc2002CntclientUpTimCntEntry
	MAX-ACCESS not-accessible
	STATUS current
	DESCRIPTION
        "
        List of pmc2002CntclientUpTimCnt
        Article
        "
	::= { pmc2002CntClient 40 }


pmc2002CntclientUpTimCntEntry OBJECT-TYPE
	SYNTAX Pmc2002CntclientUpTimCntEntry
	MAX-ACCESS not-accessible
	STATUS current
	DESCRIPTION
        "
        Row definition for the pmc2002CntclientUpTimCnt
        table
        "
	INDEX   { pmc2002CntclientUpTimCntIndex }
	::= { pmc2002CntclientUpTimCntTable 1 }


Pmc2002CntclientUpTimCntEntry ::=
	SEQUENCE {
	pmc2002CntclientUpTimCntIndex
		INTEGER,
	pmc2002CntclientUpTimCntValuePortn
		Counter32,
	pmc2002CntclientUpTimCntErrorPortn
		EkiOnOff,
	pmc2002CntclientUpTimCntOverloadPortn
		EkiOnOff
	}


pmc2002CntclientUpTimCntIndex OBJECT-TYPE
	SYNTAX  INTEGER(0..128)
	MAX-ACCESS  read-only
	STATUS current
	DESCRIPTION
        "
        Index definition for the pmc2002CntclientUpTimCnt
        table
        "
	::= { pmc2002CntclientUpTimCntEntry 1 }


pmc2002CntclientUpTimCntValuePortn OBJECT-TYPE
	SYNTAX  Counter32
	MAX-ACCESS read-only
	STATUS current
	DESCRIPTION
        "
        Client Upstream Timer Counter
         :This is the timing counter dedicated
        to the upstream access counters.
        It is incremented every 125 us.
        "
	::= { pmc2002CntclientUpTimCntEntry 2 }


pmc2002CntclientUpTimCntErrorPortn OBJECT-TYPE
	SYNTAX  EkiOnOff
	MAX-ACCESS read-only
	STATUS current
	DESCRIPTION
        "
        Client Counter Error :This OID
        when set indicates the upstream
        timing counter value is invalid
        on Port
        "
	::= { pmc2002CntclientUpTimCntEntry 3 }


pmc2002CntclientUpTimCntOverloadPortn OBJECT-TYPE
	SYNTAX  EkiOnOff
	MAX-ACCESS read-only
	STATUS current
	DESCRIPTION
        "
        Client Counter Overload :This
         OID when set indicates a upstream
        timing counter overload on Port
        "
	::= { pmc2002CntclientUpTimCntEntry 4 }


--- *********************************************************
---     TABLE for the pmc2002CntclientDwErrCnt articles
--- *********************************************************

pmc2002CntclientDwErrCntTable OBJECT-TYPE
	SYNTAX  SEQUENCE OF Pmc2002CntclientDwErrCntEntry
	MAX-ACCESS not-accessible
	STATUS current
	DESCRIPTION
        "
        List of pmc2002CntclientDwErrCnt
        Article
        "
	::= { pmc2002CntClient 64 }


pmc2002CntclientDwErrCntEntry OBJECT-TYPE
	SYNTAX Pmc2002CntclientDwErrCntEntry
	MAX-ACCESS not-accessible
	STATUS current
	DESCRIPTION
        "
        Row definition for the pmc2002CntclientDwErrCnt
        table
        "
	INDEX   { pmc2002CntclientDwErrCntIndex }
	::= { pmc2002CntclientDwErrCntTable 1 }


Pmc2002CntclientDwErrCntEntry ::=
	SEQUENCE {
	pmc2002CntclientDwErrCntIndex
		INTEGER,
	pmc2002CntclientDwErrCntValuePortn
		Counter32,
	pmc2002CntclientDwErrCntErrorPortn
		EkiOnOff,
	pmc2002CntclientDwErrCntOverloadPortn
		EkiOnOff
	}


pmc2002CntclientDwErrCntIndex OBJECT-TYPE
	SYNTAX  INTEGER(0..128)
	MAX-ACCESS  read-only
	STATUS current
	DESCRIPTION
        "
        Index definition for the pmc2002CntclientDwErrCnt
        table
        "
	::= { pmc2002CntclientDwErrCntEntry 1 }


pmc2002CntclientDwErrCntValuePortn OBJECT-TYPE
	SYNTAX  Counter32
	MAX-ACCESS read-only
	STATUS current
	DESCRIPTION
        "
        Client Output Errors :This counter
        is increased each time a B1/FCS
        error is detected on the client
        output stream  <Help>  This counter
        gives the number of FCS errors
         or B1 errors on the client output
        port
        "
	::= { pmc2002CntclientDwErrCntEntry 2 }


pmc2002CntclientDwErrCntErrorPortn OBJECT-TYPE
	SYNTAX  EkiOnOff
	MAX-ACCESS read-only
	STATUS current
	DESCRIPTION
        "
        Client Counter Error :This OID
        when set indicates the FCS error
        counter value is invalid on output
        Port
        "
	::= { pmc2002CntclientDwErrCntEntry 3 }


pmc2002CntclientDwErrCntOverloadPortn OBJECT-TYPE
	SYNTAX  EkiOnOff
	MAX-ACCESS read-only
	STATUS current
	DESCRIPTION
        "
        Client Counter Overload :This
         OID when set indicates a FCS error
        counter overload on output Port
        "
	::= { pmc2002CntclientDwErrCntEntry 4 }


--- *********************************************************
---     TABLE for the pmc2002CntclientDwTimCnt articles
--- *********************************************************

pmc2002CntclientDwTimCntTable OBJECT-TYPE
	SYNTAX  SEQUENCE OF Pmc2002CntclientDwTimCntEntry
	MAX-ACCESS not-accessible
	STATUS current
	DESCRIPTION
        "
        List of pmc2002CntclientDwTimCnt
        Article
        "
	::= { pmc2002CntClient 72 }


pmc2002CntclientDwTimCntEntry OBJECT-TYPE
	SYNTAX Pmc2002CntclientDwTimCntEntry
	MAX-ACCESS not-accessible
	STATUS current
	DESCRIPTION
        "
        Row definition for the pmc2002CntclientDwTimCnt
        table
        "
	INDEX   { pmc2002CntclientDwTimCntIndex }
	::= { pmc2002CntclientDwTimCntTable 1 }


Pmc2002CntclientDwTimCntEntry ::=
	SEQUENCE {
	pmc2002CntclientDwTimCntIndex
		INTEGER,
	pmc2002CntclientDwTimCntValuePortn
		Counter32,
	pmc2002CntclientDwTimCntErrorPortn
		EkiOnOff,
	pmc2002CntclientDwTimCntOverloadPortn
		EkiOnOff
	}


pmc2002CntclientDwTimCntIndex OBJECT-TYPE
	SYNTAX  INTEGER(0..128)
	MAX-ACCESS  read-only
	STATUS current
	DESCRIPTION
        "
        Index definition for the pmc2002CntclientDwTimCnt
        table
        "
	::= { pmc2002CntclientDwTimCntEntry 1 }


pmc2002CntclientDwTimCntValuePortn OBJECT-TYPE
	SYNTAX  Counter32
	MAX-ACCESS read-only
	STATUS current
	DESCRIPTION
        "
        Client Downstream Timer Counter
        :This is the timing counter dedicated
        to the downstream access counters.
        It is incremented every 125 us.
        "
	::= { pmc2002CntclientDwTimCntEntry 2 }


pmc2002CntclientDwTimCntErrorPortn OBJECT-TYPE
	SYNTAX  EkiOnOff
	MAX-ACCESS read-only
	STATUS current
	DESCRIPTION
        "
        Client Counter Error :This OID
        when set indicates the downstream
        timer counter value is invalid
         on Port
        "
	::= { pmc2002CntclientDwTimCntEntry 3 }


pmc2002CntclientDwTimCntOverloadPortn OBJECT-TYPE
	SYNTAX  EkiOnOff
	MAX-ACCESS read-only
	STATUS current
	DESCRIPTION
        "
        Client Counter Overload :This
         OID when set indicates a downstream
        timer counter overload on Port
        "
	::= { pmc2002CntclientDwTimCntEntry 4 }


--- *********************************************************
---     TABLE for the pmc2002CntlineDfrmErrCnt articles
--- *********************************************************

pmc2002CntlineDfrmErrCntTable OBJECT-TYPE
	SYNTAX  SEQUENCE OF Pmc2002CntlineDfrmErrCntEntry
	MAX-ACCESS not-accessible
	STATUS current
	DESCRIPTION
        "
        List of pmc2002CntlineDfrmErrCnt
        Article
        "
	::= { pmc2002CntLine 152 }


pmc2002CntlineDfrmErrCntEntry OBJECT-TYPE
	SYNTAX Pmc2002CntlineDfrmErrCntEntry
	MAX-ACCESS not-accessible
	STATUS current
	DESCRIPTION
        "
        Row definition for the pmc2002CntlineDfrmErrCnt
        table
        "
	INDEX   { pmc2002CntlineDfrmErrCntIndex }
	::= { pmc2002CntlineDfrmErrCntTable 1 }


Pmc2002CntlineDfrmErrCntEntry ::=
	SEQUENCE {
	pmc2002CntlineDfrmErrCntIndex
		INTEGER,
	pmc2002CntlineDfrmErrCntValuePortn
		Counter32,
	pmc2002CntlineDfrmErrCntErrorPortn
		EkiOnOff,
	pmc2002CntlineDfrmErrCntOverloadPortn
		EkiOnOff
	}


pmc2002CntlineDfrmErrCntIndex OBJECT-TYPE
	SYNTAX  INTEGER(0..128)
	MAX-ACCESS  read-only
	STATUS current
	DESCRIPTION
        "
        Index definition for the pmc2002CntlineDfrmErrCnt
        table
        "
	::= { pmc2002CntlineDfrmErrCntEntry 1 }


pmc2002CntlineDfrmErrCntValuePortn OBJECT-TYPE
	SYNTAX  Counter32
	MAX-ACCESS read-only
	STATUS current
	DESCRIPTION
        "
        Subcarrier B1 Errors :This counter
        is incremented each time a B1 error
        is detected on the Deframer input
        stream.  <Help>  This counter gives
        the number of B1 errors on the
         line port
        "
	::= { pmc2002CntlineDfrmErrCntEntry 2 }


pmc2002CntlineDfrmErrCntErrorPortn OBJECT-TYPE
	SYNTAX  EkiOnOff
	MAX-ACCESS read-only
	STATUS current
	DESCRIPTION
        "
        Line Counter Error :This OID when
        set indicates the B1 error counter
        value is invalid on Port
        "
	::= { pmc2002CntlineDfrmErrCntEntry 3 }


pmc2002CntlineDfrmErrCntOverloadPortn OBJECT-TYPE
	SYNTAX  EkiOnOff
	MAX-ACCESS read-only
	STATUS current
	DESCRIPTION
        "
        Line Counter Overload :This OID
        when set indicates a B1 error counter
        overload on Port
        "
	::= { pmc2002CntlineDfrmErrCntEntry 4 }


--- *********************************************************
---     TABLE for the pmc2002CntlineDfrmTimCnt articles
--- *********************************************************

pmc2002CntlineDfrmTimCntTable OBJECT-TYPE
	SYNTAX  SEQUENCE OF Pmc2002CntlineDfrmTimCntEntry
	MAX-ACCESS not-accessible
	STATUS current
	DESCRIPTION
        "
        List of pmc2002CntlineDfrmTimCnt
        Article
        "
	::= { pmc2002CntLine 153 }


pmc2002CntlineDfrmTimCntEntry OBJECT-TYPE
	SYNTAX Pmc2002CntlineDfrmTimCntEntry
	MAX-ACCESS not-accessible
	STATUS current
	DESCRIPTION
        "
        Row definition for the pmc2002CntlineDfrmTimCnt
        table
        "
	INDEX   { pmc2002CntlineDfrmTimCntIndex }
	::= { pmc2002CntlineDfrmTimCntTable 1 }


Pmc2002CntlineDfrmTimCntEntry ::=
	SEQUENCE {
	pmc2002CntlineDfrmTimCntIndex
		INTEGER,
	pmc2002CntlineDfrmTimCntValuePortn
		Counter32,
	pmc2002CntlineDfrmTimCntErrorPortn
		EkiOnOff,
	pmc2002CntlineDfrmTimCntOverloadPortn
		EkiOnOff
	}


pmc2002CntlineDfrmTimCntIndex OBJECT-TYPE
	SYNTAX  INTEGER(0..128)
	MAX-ACCESS  read-only
	STATUS current
	DESCRIPTION
        "
        Index definition for the pmc2002CntlineDfrmTimCnt
        table
        "
	::= { pmc2002CntlineDfrmTimCntEntry 1 }


pmc2002CntlineDfrmTimCntValuePortn OBJECT-TYPE
	SYNTAX  Counter32
	MAX-ACCESS read-only
	STATUS current
	DESCRIPTION
        "
        Subcarrier Timer :This is the
         timing counter dedicated to the
        downstream deframer counters. It
        is incremented every 125 us.
        "
	::= { pmc2002CntlineDfrmTimCntEntry 2 }


pmc2002CntlineDfrmTimCntErrorPortn OBJECT-TYPE
	SYNTAX  EkiOnOff
	MAX-ACCESS read-only
	STATUS current
	DESCRIPTION
        "
        Line Counter Error :This OID when
        set indicates the deframer timer
        counter value is invalid on Port
        "
	::= { pmc2002CntlineDfrmTimCntEntry 3 }


pmc2002CntlineDfrmTimCntOverloadPortn OBJECT-TYPE
	SYNTAX  EkiOnOff
	MAX-ACCESS read-only
	STATUS current
	DESCRIPTION
        "
        Line Counter Overload :This OID
        when set indicates a deframer timer
        counter overload on Port
        "
	::= { pmc2002CntlineDfrmTimCntEntry 4 }


--- *********************************************************
---     TABLE for the pmc2002CntlineDfrmPrimErrCnt articles
--- *********************************************************

pmc2002CntlineDfrmPrimErrCntTable OBJECT-TYPE
	SYNTAX  SEQUENCE OF Pmc2002CntlineDfrmPrimErrCntEntry
	MAX-ACCESS not-accessible
	STATUS current
	DESCRIPTION
        "
        List of pmc2002CntlineDfrmPrimErrCnt
        Article
        "
	::= { pmc2002CntLine 154 }


pmc2002CntlineDfrmPrimErrCntEntry OBJECT-TYPE
	SYNTAX Pmc2002CntlineDfrmPrimErrCntEntry
	MAX-ACCESS not-accessible
	STATUS current
	DESCRIPTION
        "
        Row definition for the pmc2002CntlineDfrmPrimErrCnt
        table
        "
	INDEX   { pmc2002CntlineDfrmPrimErrCntIndex }
	::= { pmc2002CntlineDfrmPrimErrCntTable 1 }


Pmc2002CntlineDfrmPrimErrCntEntry ::=
	SEQUENCE {
	pmc2002CntlineDfrmPrimErrCntIndex
		INTEGER,
	pmc2002CntlineDfrmPrimErrCntValuePortn
		Counter32,
	pmc2002CntlineDfrmPrimErrCntErrorPortn
		EkiOnOff,
	pmc2002CntlineDfrmPrimErrCntOverloadPortn
		EkiOnOff
	}


pmc2002CntlineDfrmPrimErrCntIndex OBJECT-TYPE
	SYNTAX  INTEGER(0..128)
	MAX-ACCESS  read-only
	STATUS current
	DESCRIPTION
        "
        Index definition for the pmc2002CntlineDfrmPrimErrCnt
        table
        "
	::= { pmc2002CntlineDfrmPrimErrCntEntry 1 }


pmc2002CntlineDfrmPrimErrCntValuePortn OBJECT-TYPE
	SYNTAX  Counter32
	MAX-ACCESS read-only
	STATUS current
	DESCRIPTION
        "
        Subcarrier Input FEC Corrected
        Errors :This counter is incremented
        each time an error is corrected
        by the Forward Error Correction
        decoder  <Help>  This counter gives
        the number of errors corrected
         by the FEC on the line port
        "
	::= { pmc2002CntlineDfrmPrimErrCntEntry 2 }


pmc2002CntlineDfrmPrimErrCntErrorPortn OBJECT-TYPE
	SYNTAX  EkiOnOff
	MAX-ACCESS read-only
	STATUS current
	DESCRIPTION
        "
        Line FEC Counter Error :This bit
        when set indicates the FEC counter
        value is invalid on Port
        "
	::= { pmc2002CntlineDfrmPrimErrCntEntry 3 }


pmc2002CntlineDfrmPrimErrCntOverloadPortn OBJECT-TYPE
	SYNTAX  EkiOnOff
	MAX-ACCESS read-only
	STATUS current
	DESCRIPTION
        "
        Line FEC Counter Overload :This
        bit when set indicates a FEC counter
        overload on Port
        "
	::= { pmc2002CntlineDfrmPrimErrCntEntry 4 }


pmc2002CntCountersReset  OBJECT-TYPE
	SYNTAX EkiOnOff
	MAX-ACCESS read-write
	STATUS current
	DESCRIPTION
	"Counters Reset:This OID resets and restarts all the counters"
	::= { pmc2002counters  259 }

pmc2002CntCountersStop  OBJECT-TYPE
	SYNTAX EkiOnOff
	MAX-ACCESS read-write
	STATUS current
	DESCRIPTION
	"Counters stop:This OID stops all the counters"
	::= { pmc2002counters 260 }






--- *****************************************************
--- $$$$$$$$$$$$$$$$$$$$$$$$$$$$$$$$$$$$$$$$$$$$$$$$$$$$$
---     RMON
--- $$$$$$$$$$$$$$$$$$$$$$$$$$$$$$$$$$$$$$$$$$$$$$$$$$$$$
--- *****************************************************



--- *********************************************************
---     TABLE for the pmc2002MonupRmonByteCnt articles
--- *********************************************************

pmc2002MonupRmonByteCntTable OBJECT-TYPE
	SYNTAX  SEQUENCE OF Pmc2002MonupRmonByteCntEntry
	MAX-ACCESS not-accessible
	STATUS current
	DESCRIPTION
        "
        List of pmc2002MonupRmonByteCnt
        Article
        "
	::= { pmc2002RmonClient 16 }


pmc2002MonupRmonByteCntEntry OBJECT-TYPE
	SYNTAX Pmc2002MonupRmonByteCntEntry
	MAX-ACCESS not-accessible
	STATUS current
	DESCRIPTION
        "
        Row definition for the pmc2002MonupRmonByteCnt
        table
        "
	INDEX   { pmc2002MonupRmonByteCntIndex }
	::= { pmc2002MonupRmonByteCntTable 1 }


Pmc2002MonupRmonByteCntEntry ::=
	SEQUENCE {
	pmc2002MonupRmonByteCntIndex
		INTEGER,
	pmc2002MonupRmonByteCntValuePortn
		Counter64,
	pmc2002MonupRmonByteCntErrorPortn
		EkiOnOff,
	pmc2002MonupRmonByteCntOverloadPortn
		EkiOnOff
	}


pmc2002MonupRmonByteCntIndex OBJECT-TYPE
	SYNTAX  INTEGER(0..128)
	MAX-ACCESS  read-only
	STATUS current
	DESCRIPTION
        "
        Index definition for the pmc2002MonupRmonByteCnt
        table
        "
	::= { pmc2002MonupRmonByteCntEntry 1 }


pmc2002MonupRmonByteCntValuePortn OBJECT-TYPE
	SYNTAX  Counter64
	MAX-ACCESS read-only
	STATUS current
	DESCRIPTION
        "
        Client Input Bytes :This counter
        is increased each time a data byte
        is received on the client port
          <Help>  This counter gives the
        number of bytes received on the
        client port
        "
	::= { pmc2002MonupRmonByteCntEntry 2 }


pmc2002MonupRmonByteCntErrorPortn OBJECT-TYPE
	SYNTAX  EkiOnOff
	MAX-ACCESS read-only
	STATUS current
	DESCRIPTION
        "
        Input Bytes Counter Error :This
        OID when set indicates the input
        Bytes counter value is invalid
         on client port
        "
	::= { pmc2002MonupRmonByteCntEntry 3 }


pmc2002MonupRmonByteCntOverloadPortn OBJECT-TYPE
	SYNTAX  EkiOnOff
	MAX-ACCESS read-only
	STATUS current
	DESCRIPTION
        "
        Input Bytes Counter Overload :This
        OID when set indicates an input
        Bytes counter overload on client
        port
        "
	::= { pmc2002MonupRmonByteCntEntry 4 }


--- *********************************************************
---     TABLE for the pmc2002MonupRmonCrcErrorCnt articles
--- *********************************************************

pmc2002MonupRmonCrcErrorCntTable OBJECT-TYPE
	SYNTAX  SEQUENCE OF Pmc2002MonupRmonCrcErrorCntEntry
	MAX-ACCESS not-accessible
	STATUS current
	DESCRIPTION
        "
        List of pmc2002MonupRmonCrcErrorCnt
        Article
        "
	::= { pmc2002RmonClient 24 }


pmc2002MonupRmonCrcErrorCntEntry OBJECT-TYPE
	SYNTAX Pmc2002MonupRmonCrcErrorCntEntry
	MAX-ACCESS not-accessible
	STATUS current
	DESCRIPTION
        "
        Row definition for the pmc2002MonupRmonCrcErrorCnt
        table
        "
	INDEX   { pmc2002MonupRmonCrcErrorCntIndex }
	::= { pmc2002MonupRmonCrcErrorCntTable 1 }


Pmc2002MonupRmonCrcErrorCntEntry ::=
	SEQUENCE {
	pmc2002MonupRmonCrcErrorCntIndex
		INTEGER,
	pmc2002MonupRmonCrcErrorCntValuePortn
		Counter64,
	pmc2002MonupRmonCrcErrorCntErrorPortn
		EkiOnOff,
	pmc2002MonupRmonCrcErrorCntOverloadPortn
		EkiOnOff
	}


pmc2002MonupRmonCrcErrorCntIndex OBJECT-TYPE
	SYNTAX  INTEGER(0..128)
	MAX-ACCESS  read-only
	STATUS current
	DESCRIPTION
        "
        Index definition for the pmc2002MonupRmonCrcErrorCnt
        table
        "
	::= { pmc2002MonupRmonCrcErrorCntEntry 1 }


pmc2002MonupRmonCrcErrorCntValuePortn OBJECT-TYPE
	SYNTAX  Counter64
	MAX-ACCESS read-only
	STATUS current
	DESCRIPTION
        "
        Client Input CRC Errors :This
         counter is increased each time
        a CRC error is detected on the
         client port.   <Help>  This counter
        gives the number of CRC Errors
         received on the client port
        "
	::= { pmc2002MonupRmonCrcErrorCntEntry 2 }


pmc2002MonupRmonCrcErrorCntErrorPortn OBJECT-TYPE
	SYNTAX  EkiOnOff
	MAX-ACCESS read-only
	STATUS current
	DESCRIPTION
        "
        Input CRC Errors Counter Error
        :This OID when set indicates the
        input CRC Errors counter value
         is invalid on client port
        "
	::= { pmc2002MonupRmonCrcErrorCntEntry 3 }


pmc2002MonupRmonCrcErrorCntOverloadPortn OBJECT-TYPE
	SYNTAX  EkiOnOff
	MAX-ACCESS read-only
	STATUS current
	DESCRIPTION
        "
        Input CRC Errors Counter Overload
        :This OID when set indicates an
        input CRC Errors counter overload
        on client port
        "
	::= { pmc2002MonupRmonCrcErrorCntEntry 4 }


--- *********************************************************
---     TABLE for the pmc2002MonupRmonPacketsCnt articles
--- *********************************************************

pmc2002MonupRmonPacketsCntTable OBJECT-TYPE
	SYNTAX  SEQUENCE OF Pmc2002MonupRmonPacketsCntEntry
	MAX-ACCESS not-accessible
	STATUS current
	DESCRIPTION
        "
        List of pmc2002MonupRmonPacketsCnt
        Article
        "
	::= { pmc2002RmonClient 32 }


pmc2002MonupRmonPacketsCntEntry OBJECT-TYPE
	SYNTAX Pmc2002MonupRmonPacketsCntEntry
	MAX-ACCESS not-accessible
	STATUS current
	DESCRIPTION
        "
        Row definition for the pmc2002MonupRmonPacketsCnt
        table
        "
	INDEX   { pmc2002MonupRmonPacketsCntIndex }
	::= { pmc2002MonupRmonPacketsCntTable 1 }


Pmc2002MonupRmonPacketsCntEntry ::=
	SEQUENCE {
	pmc2002MonupRmonPacketsCntIndex
		INTEGER,
	pmc2002MonupRmonPacketsCntValuePortn
		Counter64,
	pmc2002MonupRmonPacketsCntErrorPortn
		EkiOnOff,
	pmc2002MonupRmonPacketsCntOverloadPortn
		EkiOnOff
	}


pmc2002MonupRmonPacketsCntIndex OBJECT-TYPE
	SYNTAX  INTEGER(0..128)
	MAX-ACCESS  read-only
	STATUS current
	DESCRIPTION
        "
        Index definition for the pmc2002MonupRmonPacketsCnt
        table
        "
	::= { pmc2002MonupRmonPacketsCntEntry 1 }


pmc2002MonupRmonPacketsCntValuePortn OBJECT-TYPE
	SYNTAX  Counter64
	MAX-ACCESS read-only
	STATUS current
	DESCRIPTION
        "
        Packets Counter On Client Input
        :This counter is increased each
        time a packet is received on the
        client port  <Help>  This counter
        gives the number of packets received
        on the client port
        "
	::= { pmc2002MonupRmonPacketsCntEntry 2 }


pmc2002MonupRmonPacketsCntErrorPortn OBJECT-TYPE
	SYNTAX  EkiOnOff
	MAX-ACCESS read-only
	STATUS current
	DESCRIPTION
        "
        Input Packets Counter Error :This
        OID when set indicates the input
        Packets counter value is invalid
        on client port
        "
	::= { pmc2002MonupRmonPacketsCntEntry 3 }


pmc2002MonupRmonPacketsCntOverloadPortn OBJECT-TYPE
	SYNTAX  EkiOnOff
	MAX-ACCESS read-only
	STATUS current
	DESCRIPTION
        "
        Input Packets Counter Overload
        :This OID when set indicates an
        input Packets counter overload
         on client port
        "
	::= { pmc2002MonupRmonPacketsCntEntry 4 }


--- *********************************************************
---     TABLE for the pmc2002MonupRmonBroadcastCnt articles
--- *********************************************************

pmc2002MonupRmonBroadcastCntTable OBJECT-TYPE
	SYNTAX  SEQUENCE OF Pmc2002MonupRmonBroadcastCntEntry
	MAX-ACCESS not-accessible
	STATUS current
	DESCRIPTION
        "
        List of pmc2002MonupRmonBroadcastCnt
        Article
        "
	::= { pmc2002RmonClient 40 }


pmc2002MonupRmonBroadcastCntEntry OBJECT-TYPE
	SYNTAX Pmc2002MonupRmonBroadcastCntEntry
	MAX-ACCESS not-accessible
	STATUS current
	DESCRIPTION
        "
        Row definition for the pmc2002MonupRmonBroadcastCnt
        table
        "
	INDEX   { pmc2002MonupRmonBroadcastCntIndex }
	::= { pmc2002MonupRmonBroadcastCntTable 1 }


Pmc2002MonupRmonBroadcastCntEntry ::=
	SEQUENCE {
	pmc2002MonupRmonBroadcastCntIndex
		INTEGER,
	pmc2002MonupRmonBroadcastCntValuePortn
		Counter64,
	pmc2002MonupRmonBroadcastCntErrorPortn
		EkiOnOff,
	pmc2002MonupRmonBroadcastCntOverloadPortn
		EkiOnOff
	}


pmc2002MonupRmonBroadcastCntIndex OBJECT-TYPE
	SYNTAX  INTEGER(0..128)
	MAX-ACCESS  read-only
	STATUS current
	DESCRIPTION
        "
        Index definition for the pmc2002MonupRmonBroadcastCnt
        table
        "
	::= { pmc2002MonupRmonBroadcastCntEntry 1 }


pmc2002MonupRmonBroadcastCntValuePortn OBJECT-TYPE
	SYNTAX  Counter64
	MAX-ACCESS read-only
	STATUS current
	DESCRIPTION
        "
        Client Input Broadcast Packets
        :This counter is increased each
        time a broadcast packet is received
        on the client port.   <Help>  This
        counter gives the number of Broadcast
        packets received on the client
         port
        "
	::= { pmc2002MonupRmonBroadcastCntEntry 2 }


pmc2002MonupRmonBroadcastCntErrorPortn OBJECT-TYPE
	SYNTAX  EkiOnOff
	MAX-ACCESS read-only
	STATUS current
	DESCRIPTION
        "
        Input Broadcast Counter Error
         :This OID when set indicates the
        input Broadcast counter value is
        invalid on client port
        "
	::= { pmc2002MonupRmonBroadcastCntEntry 3 }


pmc2002MonupRmonBroadcastCntOverloadPortn OBJECT-TYPE
	SYNTAX  EkiOnOff
	MAX-ACCESS read-only
	STATUS current
	DESCRIPTION
        "
        Input Broadcast Counter Overload
        :This OID when set indicates an
        input Broadcast counter overload
        on client port
        "
	::= { pmc2002MonupRmonBroadcastCntEntry 4 }


--- *********************************************************
---     TABLE for the pmc2002MonupRmonMulticastCnt articles
--- *********************************************************

pmc2002MonupRmonMulticastCntTable OBJECT-TYPE
	SYNTAX  SEQUENCE OF Pmc2002MonupRmonMulticastCntEntry
	MAX-ACCESS not-accessible
	STATUS current
	DESCRIPTION
        "
        List of pmc2002MonupRmonMulticastCnt
        Article
        "
	::= { pmc2002RmonClient 48 }


pmc2002MonupRmonMulticastCntEntry OBJECT-TYPE
	SYNTAX Pmc2002MonupRmonMulticastCntEntry
	MAX-ACCESS not-accessible
	STATUS current
	DESCRIPTION
        "
        Row definition for the pmc2002MonupRmonMulticastCnt
        table
        "
	INDEX   { pmc2002MonupRmonMulticastCntIndex }
	::= { pmc2002MonupRmonMulticastCntTable 1 }


Pmc2002MonupRmonMulticastCntEntry ::=
	SEQUENCE {
	pmc2002MonupRmonMulticastCntIndex
		INTEGER,
	pmc2002MonupRmonMulticastCntValuePortn
		Counter64,
	pmc2002MonupRmonMulticastCntErrorPortn
		EkiOnOff,
	pmc2002MonupRmonMulticastCntOverloadPortn
		EkiOnOff
	}


pmc2002MonupRmonMulticastCntIndex OBJECT-TYPE
	SYNTAX  INTEGER(0..128)
	MAX-ACCESS  read-only
	STATUS current
	DESCRIPTION
        "
        Index definition for the pmc2002MonupRmonMulticastCnt
        table
        "
	::= { pmc2002MonupRmonMulticastCntEntry 1 }


pmc2002MonupRmonMulticastCntValuePortn OBJECT-TYPE
	SYNTAX  Counter64
	MAX-ACCESS read-only
	STATUS current
	DESCRIPTION
        "
        Client Input Multicast Packets
        :This counter is increased each
        time a Multicast packet is received
        on the client port.  <Help>  This
        counter gives the number of Multicast
        packets received on the client
         port
        "
	::= { pmc2002MonupRmonMulticastCntEntry 2 }


pmc2002MonupRmonMulticastCntErrorPortn OBJECT-TYPE
	SYNTAX  EkiOnOff
	MAX-ACCESS read-only
	STATUS current
	DESCRIPTION
        "
        Input Multicast Counter Error
         :This OID when set indicates the
        input Multicast counter value is
        invalid on client port
        "
	::= { pmc2002MonupRmonMulticastCntEntry 3 }


pmc2002MonupRmonMulticastCntOverloadPortn OBJECT-TYPE
	SYNTAX  EkiOnOff
	MAX-ACCESS read-only
	STATUS current
	DESCRIPTION
        "
        Input Multicast Counter Overload
        :This OID when set indicates an
        input Multicast counter overload
        on client port
        "
	::= { pmc2002MonupRmonMulticastCntEntry 4 }


--- *********************************************************
---     TABLE for the pmc2002MonupRmonTimerCnt articles
--- *********************************************************

pmc2002MonupRmonTimerCntTable OBJECT-TYPE
	SYNTAX  SEQUENCE OF Pmc2002MonupRmonTimerCntEntry
	MAX-ACCESS not-accessible
	STATUS current
	DESCRIPTION
        "
        List of pmc2002MonupRmonTimerCnt
        Article
        "
	::= { pmc2002RmonClient 56 }


pmc2002MonupRmonTimerCntEntry OBJECT-TYPE
	SYNTAX Pmc2002MonupRmonTimerCntEntry
	MAX-ACCESS not-accessible
	STATUS current
	DESCRIPTION
        "
        Row definition for the pmc2002MonupRmonTimerCnt
        table
        "
	INDEX   { pmc2002MonupRmonTimerCntIndex }
	::= { pmc2002MonupRmonTimerCntTable 1 }


Pmc2002MonupRmonTimerCntEntry ::=
	SEQUENCE {
	pmc2002MonupRmonTimerCntIndex
		INTEGER,
	pmc2002MonupRmonTimerCntValuePortn
		Counter64,
	pmc2002MonupRmonTimerCntErrorPortn
		EkiOnOff,
	pmc2002MonupRmonTimerCntOverloadPortn
		EkiOnOff
	}


pmc2002MonupRmonTimerCntIndex OBJECT-TYPE
	SYNTAX  INTEGER(0..128)
	MAX-ACCESS  read-only
	STATUS current
	DESCRIPTION
        "
        Index definition for the pmc2002MonupRmonTimerCnt
        table
        "
	::= { pmc2002MonupRmonTimerCntEntry 1 }


pmc2002MonupRmonTimerCntValuePortn OBJECT-TYPE
	SYNTAX  Counter64
	MAX-ACCESS read-only
	STATUS current
	DESCRIPTION
        "
        RMON Timer On Client Input :This
        is the timing counter dedicated
        to the upstream RMON counters.
         It is incremented every 125 us.
        "
	::= { pmc2002MonupRmonTimerCntEntry 2 }


pmc2002MonupRmonTimerCntErrorPortn OBJECT-TYPE
	SYNTAX  EkiOnOff
	MAX-ACCESS read-only
	STATUS current
	DESCRIPTION
        "
        Input RMON Timer Error :This OID
        when set indicates the input RMON
        timer is invalid on client port
        "
	::= { pmc2002MonupRmonTimerCntEntry 3 }


pmc2002MonupRmonTimerCntOverloadPortn OBJECT-TYPE
	SYNTAX  EkiOnOff
	MAX-ACCESS read-only
	STATUS current
	DESCRIPTION
        "
        Input RMON Timer Overload :This
        OID when set indicates an input
        RMON timer overload on client port
        "
	::= { pmc2002MonupRmonTimerCntEntry 4 }


--- *********************************************************
---     TABLE for the pmc2002MonupRmonPauseFrameCnt articles
--- *********************************************************

pmc2002MonupRmonPauseFrameCntTable OBJECT-TYPE
	SYNTAX  SEQUENCE OF Pmc2002MonupRmonPauseFrameCntEntry
	MAX-ACCESS not-accessible
	STATUS current
	DESCRIPTION
        "
        List of pmc2002MonupRmonPauseFrameCnt
        Article
        "
	::= { pmc2002RmonClient 64 }


pmc2002MonupRmonPauseFrameCntEntry OBJECT-TYPE
	SYNTAX Pmc2002MonupRmonPauseFrameCntEntry
	MAX-ACCESS not-accessible
	STATUS current
	DESCRIPTION
        "
        Row definition for the pmc2002MonupRmonPauseFrameCnt
        table
        "
	INDEX   { pmc2002MonupRmonPauseFrameCntIndex }
	::= { pmc2002MonupRmonPauseFrameCntTable 1 }


Pmc2002MonupRmonPauseFrameCntEntry ::=
	SEQUENCE {
	pmc2002MonupRmonPauseFrameCntIndex
		INTEGER,
	pmc2002MonupRmonPauseFrameCntValuePortn
		Counter64,
	pmc2002MonupRmonPauseFrameCntErrorPortn
		EkiOnOff,
	pmc2002MonupRmonPauseFrameCntOverloadPortn
		EkiOnOff
	}


pmc2002MonupRmonPauseFrameCntIndex OBJECT-TYPE
	SYNTAX  INTEGER(0..128)
	MAX-ACCESS  read-only
	STATUS current
	DESCRIPTION
        "
        Index definition for the pmc2002MonupRmonPauseFrameCnt
        table
        "
	::= { pmc2002MonupRmonPauseFrameCntEntry 1 }


pmc2002MonupRmonPauseFrameCntValuePortn OBJECT-TYPE
	SYNTAX  Counter64
	MAX-ACCESS read-only
	STATUS current
	DESCRIPTION
        "
        Pause Counter On Client Input
         :This counter is increased each
        time a Pause frame is received
         on the client port
        "
	::= { pmc2002MonupRmonPauseFrameCntEntry 2 }


pmc2002MonupRmonPauseFrameCntErrorPortn OBJECT-TYPE
	SYNTAX  EkiOnOff
	MAX-ACCESS read-only
	STATUS current
	DESCRIPTION
        "
        Input Pause Counter Error :This
        OID when set indicates the input
        Pause counter value is invalid
         on client port
        "
	::= { pmc2002MonupRmonPauseFrameCntEntry 3 }


pmc2002MonupRmonPauseFrameCntOverloadPortn OBJECT-TYPE
	SYNTAX  EkiOnOff
	MAX-ACCESS read-only
	STATUS current
	DESCRIPTION
        "
        Input Pause Counter Overload :This
        OID when set indicates an input
        Pause counter overload on client
        port
        "
	::= { pmc2002MonupRmonPauseFrameCntEntry 4 }


--- *********************************************************
---     TABLE for the pmc2002MonupRmonDropFrameCnt articles
--- *********************************************************

pmc2002MonupRmonDropFrameCntTable OBJECT-TYPE
	SYNTAX  SEQUENCE OF Pmc2002MonupRmonDropFrameCntEntry
	MAX-ACCESS not-accessible
	STATUS current
	DESCRIPTION
        "
        List of pmc2002MonupRmonDropFrameCnt
        Article
        "
	::= { pmc2002RmonClient 72 }


pmc2002MonupRmonDropFrameCntEntry OBJECT-TYPE
	SYNTAX Pmc2002MonupRmonDropFrameCntEntry
	MAX-ACCESS not-accessible
	STATUS current
	DESCRIPTION
        "
        Row definition for the pmc2002MonupRmonDropFrameCnt
        table
        "
	INDEX   { pmc2002MonupRmonDropFrameCntIndex }
	::= { pmc2002MonupRmonDropFrameCntTable 1 }


Pmc2002MonupRmonDropFrameCntEntry ::=
	SEQUENCE {
	pmc2002MonupRmonDropFrameCntIndex
		INTEGER,
	pmc2002MonupRmonDropFrameCntValuePortn
		Counter64,
	pmc2002MonupRmonDropFrameCntErrorPortn
		EkiOnOff,
	pmc2002MonupRmonDropFrameCntOverloadPortn
		EkiOnOff
	}


pmc2002MonupRmonDropFrameCntIndex OBJECT-TYPE
	SYNTAX  INTEGER(0..128)
	MAX-ACCESS  read-only
	STATUS current
	DESCRIPTION
        "
        Index definition for the pmc2002MonupRmonDropFrameCnt
        table
        "
	::= { pmc2002MonupRmonDropFrameCntEntry 1 }


pmc2002MonupRmonDropFrameCntValuePortn OBJECT-TYPE
	SYNTAX  Counter64
	MAX-ACCESS read-only
	STATUS current
	DESCRIPTION
        "
        Drop Counter On Client Input :This
        counter is increased each time
         a Frame is dropped on the input
        client port
        "
	::= { pmc2002MonupRmonDropFrameCntEntry 2 }


pmc2002MonupRmonDropFrameCntErrorPortn OBJECT-TYPE
	SYNTAX  EkiOnOff
	MAX-ACCESS read-only
	STATUS current
	DESCRIPTION
        "
        Input Drop Counter Error :This
        OID when set indicates the input
        Drop counter value is invalid on
        client port
        "
	::= { pmc2002MonupRmonDropFrameCntEntry 3 }


pmc2002MonupRmonDropFrameCntOverloadPortn OBJECT-TYPE
	SYNTAX  EkiOnOff
	MAX-ACCESS read-only
	STATUS current
	DESCRIPTION
        "
        Input Drop Counter Overload :This
        OID when set indicates an input
        Drop counter overload on client
        port
        "
	::= { pmc2002MonupRmonDropFrameCntEntry 4 }


--- *********************************************************
---     TABLE for the pmc2002MonupRmonBitsCnt articles
--- *********************************************************

pmc2002MonupRmonBitsCntTable OBJECT-TYPE
	SYNTAX  SEQUENCE OF Pmc2002MonupRmonBitsCntEntry
	MAX-ACCESS not-accessible
	STATUS current
	DESCRIPTION
        "
        List of pmc2002MonupRmonBitsCnt
        Article
        "
	::= { pmc2002RmonClient 80 }


pmc2002MonupRmonBitsCntEntry OBJECT-TYPE
	SYNTAX Pmc2002MonupRmonBitsCntEntry
	MAX-ACCESS not-accessible
	STATUS current
	DESCRIPTION
        "
        Row definition for the pmc2002MonupRmonBitsCnt
        table
        "
	INDEX   { pmc2002MonupRmonBitsCntIndex }
	::= { pmc2002MonupRmonBitsCntTable 1 }


Pmc2002MonupRmonBitsCntEntry ::=
	SEQUENCE {
	pmc2002MonupRmonBitsCntIndex
		INTEGER,
	pmc2002MonupRmonBitsCntValuePortn
		Counter64,
	pmc2002MonupRmonBitsCntErrorPortn
		EkiOnOff,
	pmc2002MonupRmonBitsCntOverloadPortn
		EkiOnOff
	}


pmc2002MonupRmonBitsCntIndex OBJECT-TYPE
	SYNTAX  INTEGER(0..128)
	MAX-ACCESS  read-only
	STATUS current
	DESCRIPTION
        "
        Index definition for the pmc2002MonupRmonBitsCnt
        table
        "
	::= { pmc2002MonupRmonBitsCntEntry 1 }


pmc2002MonupRmonBitsCntValuePortn OBJECT-TYPE
	SYNTAX  Counter64
	MAX-ACCESS read-only
	STATUS current
	DESCRIPTION
        "
        Bits Counter On Client Input :This
        counter is increased each time
         a bit is received on the input
        client port
        "
	::= { pmc2002MonupRmonBitsCntEntry 2 }


pmc2002MonupRmonBitsCntErrorPortn OBJECT-TYPE
	SYNTAX  EkiOnOff
	MAX-ACCESS read-only
	STATUS current
	DESCRIPTION
        "
        Input Bits Counter Error :This
        OID when set indicates the input
        Bits counter value is invalid on
        client port
        "
	::= { pmc2002MonupRmonBitsCntEntry 3 }


pmc2002MonupRmonBitsCntOverloadPortn OBJECT-TYPE
	SYNTAX  EkiOnOff
	MAX-ACCESS read-only
	STATUS current
	DESCRIPTION
        "
        Input Bits Counter Overload :This
        OID when set indicates an input
        Bits counter overload on client
        port
        "
	::= { pmc2002MonupRmonBitsCntEntry 4 }


--- *********************************************************
---     TABLE for the pmc2002MonupRmonUnicastCnt articles
--- *********************************************************

pmc2002MonupRmonUnicastCntTable OBJECT-TYPE
	SYNTAX  SEQUENCE OF Pmc2002MonupRmonUnicastCntEntry
	MAX-ACCESS not-accessible
	STATUS current
	DESCRIPTION
        "
        List of pmc2002MonupRmonUnicastCnt
        Article
        "
	::= { pmc2002RmonClient 88 }


pmc2002MonupRmonUnicastCntEntry OBJECT-TYPE
	SYNTAX Pmc2002MonupRmonUnicastCntEntry
	MAX-ACCESS not-accessible
	STATUS current
	DESCRIPTION
        "
        Row definition for the pmc2002MonupRmonUnicastCnt
        table
        "
	INDEX   { pmc2002MonupRmonUnicastCntIndex }
	::= { pmc2002MonupRmonUnicastCntTable 1 }


Pmc2002MonupRmonUnicastCntEntry ::=
	SEQUENCE {
	pmc2002MonupRmonUnicastCntIndex
		INTEGER,
	pmc2002MonupRmonUnicastCntValuePortn
		Counter64,
	pmc2002MonupRmonUnicastCntErrorPortn
		EkiOnOff,
	pmc2002MonupRmonUnicastCntOverloadPortn
		EkiOnOff
	}


pmc2002MonupRmonUnicastCntIndex OBJECT-TYPE
	SYNTAX  INTEGER(0..128)
	MAX-ACCESS  read-only
	STATUS current
	DESCRIPTION
        "
        Index definition for the pmc2002MonupRmonUnicastCnt
        table
        "
	::= { pmc2002MonupRmonUnicastCntEntry 1 }


pmc2002MonupRmonUnicastCntValuePortn OBJECT-TYPE
	SYNTAX  Counter64
	MAX-ACCESS read-only
	STATUS current
	DESCRIPTION
        "
        Client Input Unicast Packets :This
        counter is increased each time
         a Unicast packet is received on
        client input  <Help>  This counter
        gives the number of Unicast packets
        received on the client input port
        "
	::= { pmc2002MonupRmonUnicastCntEntry 2 }


pmc2002MonupRmonUnicastCntErrorPortn OBJECT-TYPE
	SYNTAX  EkiOnOff
	MAX-ACCESS read-only
	STATUS current
	DESCRIPTION
        "
        Input Unicast Counter Error :This
        OID when set indicates the input
        Drop counter value is invalid on
        client port
        "
	::= { pmc2002MonupRmonUnicastCntEntry 3 }


pmc2002MonupRmonUnicastCntOverloadPortn OBJECT-TYPE
	SYNTAX  EkiOnOff
	MAX-ACCESS read-only
	STATUS current
	DESCRIPTION
        "
        Input Unicast Counter Overload
        :This OID when set indicates an
        input Drop counter overload on
         client port
        "
	::= { pmc2002MonupRmonUnicastCntEntry 4 }


--- *********************************************************
---     TABLE for the pmc2002MonupRmonNonUnicastCnt articles
--- *********************************************************

pmc2002MonupRmonNonUnicastCntTable OBJECT-TYPE
	SYNTAX  SEQUENCE OF Pmc2002MonupRmonNonUnicastCntEntry
	MAX-ACCESS not-accessible
	STATUS current
	DESCRIPTION
        "
        List of pmc2002MonupRmonNonUnicastCnt
        Article
        "
	::= { pmc2002RmonClient 96 }


pmc2002MonupRmonNonUnicastCntEntry OBJECT-TYPE
	SYNTAX Pmc2002MonupRmonNonUnicastCntEntry
	MAX-ACCESS not-accessible
	STATUS current
	DESCRIPTION
        "
        Row definition for the pmc2002MonupRmonNonUnicastCnt
        table
        "
	INDEX   { pmc2002MonupRmonNonUnicastCntIndex }
	::= { pmc2002MonupRmonNonUnicastCntTable 1 }


Pmc2002MonupRmonNonUnicastCntEntry ::=
	SEQUENCE {
	pmc2002MonupRmonNonUnicastCntIndex
		INTEGER,
	pmc2002MonupRmonNonUnicastCntValuePortn
		Counter64,
	pmc2002MonupRmonNonUnicastCntErrorPortn
		EkiOnOff,
	pmc2002MonupRmonNonUnicastCntOverloadPortn
		EkiOnOff
	}


pmc2002MonupRmonNonUnicastCntIndex OBJECT-TYPE
	SYNTAX  INTEGER(0..128)
	MAX-ACCESS  read-only
	STATUS current
	DESCRIPTION
        "
        Index definition for the pmc2002MonupRmonNonUnicastCnt
        table
        "
	::= { pmc2002MonupRmonNonUnicastCntEntry 1 }


pmc2002MonupRmonNonUnicastCntValuePortn OBJECT-TYPE
	SYNTAX  Counter64
	MAX-ACCESS read-only
	STATUS current
	DESCRIPTION
        "
        Client Input Not Unicast Packets
        :This counter is increased each
        time a Non Unicast packet is received
        on client input    <Help>  This
        counter gives the number of Non
        Unicast packets received on the
        client input port
        "
	::= { pmc2002MonupRmonNonUnicastCntEntry 2 }


pmc2002MonupRmonNonUnicastCntErrorPortn OBJECT-TYPE
	SYNTAX  EkiOnOff
	MAX-ACCESS read-only
	STATUS current
	DESCRIPTION
        "
        Input Non Unicast Counter Error
        :This OID when set indicates the
        input Bits counter value is invalid
        on client port
        "
	::= { pmc2002MonupRmonNonUnicastCntEntry 3 }


pmc2002MonupRmonNonUnicastCntOverloadPortn OBJECT-TYPE
	SYNTAX  EkiOnOff
	MAX-ACCESS read-only
	STATUS current
	DESCRIPTION
        "
        Input Non Unicast Counter Overload
        :This OID when set indicates an
        input Bits counter overload on
         client port
        "
	::= { pmc2002MonupRmonNonUnicastCntEntry 4 }


--- *********************************************************
---     TABLE for the pmc2002MondwRmonByteCnt articles
--- *********************************************************

pmc2002MondwRmonByteCntTable OBJECT-TYPE
	SYNTAX  SEQUENCE OF Pmc2002MondwRmonByteCntEntry
	MAX-ACCESS not-accessible
	STATUS current
	DESCRIPTION
        "
        List of pmc2002MondwRmonByteCnt
        Article
        "
	::= { pmc2002RmonClient 112 }


pmc2002MondwRmonByteCntEntry OBJECT-TYPE
	SYNTAX Pmc2002MondwRmonByteCntEntry
	MAX-ACCESS not-accessible
	STATUS current
	DESCRIPTION
        "
        Row definition for the pmc2002MondwRmonByteCnt
        table
        "
	INDEX   { pmc2002MondwRmonByteCntIndex }
	::= { pmc2002MondwRmonByteCntTable 1 }


Pmc2002MondwRmonByteCntEntry ::=
	SEQUENCE {
	pmc2002MondwRmonByteCntIndex
		INTEGER,
	pmc2002MondwRmonByteCntValuePortn
		Counter64,
	pmc2002MondwRmonByteCntErrorPortn
		EkiOnOff,
	pmc2002MondwRmonByteCntOverloadPortn
		EkiOnOff
	}


pmc2002MondwRmonByteCntIndex OBJECT-TYPE
	SYNTAX  INTEGER(0..128)
	MAX-ACCESS  read-only
	STATUS current
	DESCRIPTION
        "
        Index definition for the pmc2002MondwRmonByteCnt
        table
        "
	::= { pmc2002MondwRmonByteCntEntry 1 }


pmc2002MondwRmonByteCntValuePortn OBJECT-TYPE
	SYNTAX  Counter64
	MAX-ACCESS read-only
	STATUS current
	DESCRIPTION
        "
        Bytes Counter On Client Output
        :This counter is increased each
        time a data byte is transmitted
        on the client port.  <Help>  This
        counter gives the number of bytes
        transmitted on the client port
        "
	::= { pmc2002MondwRmonByteCntEntry 2 }


pmc2002MondwRmonByteCntErrorPortn OBJECT-TYPE
	SYNTAX  EkiOnOff
	MAX-ACCESS read-only
	STATUS current
	DESCRIPTION
        "
        Output Bytes Counter Error :This
        OID when set indicates the output
        Bytes counter value is invalid
         on client port
        "
	::= { pmc2002MondwRmonByteCntEntry 3 }


pmc2002MondwRmonByteCntOverloadPortn OBJECT-TYPE
	SYNTAX  EkiOnOff
	MAX-ACCESS read-only
	STATUS current
	DESCRIPTION
        "
        Output Bytes Counter Overload
         :This OID when set indicates an
        output Bytes counter overload on
        client port
        "
	::= { pmc2002MondwRmonByteCntEntry 4 }


--- *********************************************************
---     TABLE for the pmc2002MondwRmonCrcErrorCnt articles
--- *********************************************************

pmc2002MondwRmonCrcErrorCntTable OBJECT-TYPE
	SYNTAX  SEQUENCE OF Pmc2002MondwRmonCrcErrorCntEntry
	MAX-ACCESS not-accessible
	STATUS current
	DESCRIPTION
        "
        List of pmc2002MondwRmonCrcErrorCnt
        Article
        "
	::= { pmc2002RmonClient 120 }


pmc2002MondwRmonCrcErrorCntEntry OBJECT-TYPE
	SYNTAX Pmc2002MondwRmonCrcErrorCntEntry
	MAX-ACCESS not-accessible
	STATUS current
	DESCRIPTION
        "
        Row definition for the pmc2002MondwRmonCrcErrorCnt
        table
        "
	INDEX   { pmc2002MondwRmonCrcErrorCntIndex }
	::= { pmc2002MondwRmonCrcErrorCntTable 1 }


Pmc2002MondwRmonCrcErrorCntEntry ::=
	SEQUENCE {
	pmc2002MondwRmonCrcErrorCntIndex
		INTEGER,
	pmc2002MondwRmonCrcErrorCntValuePortn
		Counter64,
	pmc2002MondwRmonCrcErrorCntErrorPortn
		EkiOnOff,
	pmc2002MondwRmonCrcErrorCntOverloadPortn
		EkiOnOff
	}


pmc2002MondwRmonCrcErrorCntIndex OBJECT-TYPE
	SYNTAX  INTEGER(0..128)
	MAX-ACCESS  read-only
	STATUS current
	DESCRIPTION
        "
        Index definition for the pmc2002MondwRmonCrcErrorCnt
        table
        "
	::= { pmc2002MondwRmonCrcErrorCntEntry 1 }


pmc2002MondwRmonCrcErrorCntValuePortn OBJECT-TYPE
	SYNTAX  Counter64
	MAX-ACCESS read-only
	STATUS current
	DESCRIPTION
        "
        CRC Errors Counter On Client Output
        :This counter is increased each
        time a CRC error is detected on
        the output client port  <Help>
          This counter gives the number
        of CRC Errors transmitted on the
        client port
        "
	::= { pmc2002MondwRmonCrcErrorCntEntry 2 }


pmc2002MondwRmonCrcErrorCntErrorPortn OBJECT-TYPE
	SYNTAX  EkiOnOff
	MAX-ACCESS read-only
	STATUS current
	DESCRIPTION
        "
        Output CRC Errors Counter Error
        :This OID when set indicates the
        output CRC Errors counter value
        is invalid on client port
        "
	::= { pmc2002MondwRmonCrcErrorCntEntry 3 }


pmc2002MondwRmonCrcErrorCntOverloadPortn OBJECT-TYPE
	SYNTAX  EkiOnOff
	MAX-ACCESS read-only
	STATUS current
	DESCRIPTION
        "
        Output CRC Errors Counter Overload
        :This OID when set indicates an
        output CRC Errors counter overload
        on client port
        "
	::= { pmc2002MondwRmonCrcErrorCntEntry 4 }


--- *********************************************************
---     TABLE for the pmc2002MondwRmonPacketsCnt articles
--- *********************************************************

pmc2002MondwRmonPacketsCntTable OBJECT-TYPE
	SYNTAX  SEQUENCE OF Pmc2002MondwRmonPacketsCntEntry
	MAX-ACCESS not-accessible
	STATUS current
	DESCRIPTION
        "
        List of pmc2002MondwRmonPacketsCnt
        Article
        "
	::= { pmc2002RmonClient 128 }


pmc2002MondwRmonPacketsCntEntry OBJECT-TYPE
	SYNTAX Pmc2002MondwRmonPacketsCntEntry
	MAX-ACCESS not-accessible
	STATUS current
	DESCRIPTION
        "
        Row definition for the pmc2002MondwRmonPacketsCnt
        table
        "
	INDEX   { pmc2002MondwRmonPacketsCntIndex }
	::= { pmc2002MondwRmonPacketsCntTable 1 }


Pmc2002MondwRmonPacketsCntEntry ::=
	SEQUENCE {
	pmc2002MondwRmonPacketsCntIndex
		INTEGER,
	pmc2002MondwRmonPacketsCntValuePortn
		Counter64,
	pmc2002MondwRmonPacketsCntErrorPortn
		EkiOnOff,
	pmc2002MondwRmonPacketsCntOverloadPortn
		EkiOnOff
	}


pmc2002MondwRmonPacketsCntIndex OBJECT-TYPE
	SYNTAX  INTEGER(0..128)
	MAX-ACCESS  read-only
	STATUS current
	DESCRIPTION
        "
        Index definition for the pmc2002MondwRmonPacketsCnt
        table
        "
	::= { pmc2002MondwRmonPacketsCntEntry 1 }


pmc2002MondwRmonPacketsCntValuePortn OBJECT-TYPE
	SYNTAX  Counter64
	MAX-ACCESS read-only
	STATUS current
	DESCRIPTION
        "
        Packets Counter On Client Output
        :This counter is increased each
        time a packet is transmitted on
        the client port.  <Help>  This
         counter gives the number of packets
        transmitted on the client port
        "
	::= { pmc2002MondwRmonPacketsCntEntry 2 }


pmc2002MondwRmonPacketsCntErrorPortn OBJECT-TYPE
	SYNTAX  EkiOnOff
	MAX-ACCESS read-only
	STATUS current
	DESCRIPTION
        "
        Output Packets Counter Error :This
        OID when set indicates the output
        Packets counter value is invalid
        on client port
        "
	::= { pmc2002MondwRmonPacketsCntEntry 3 }


pmc2002MondwRmonPacketsCntOverloadPortn OBJECT-TYPE
	SYNTAX  EkiOnOff
	MAX-ACCESS read-only
	STATUS current
	DESCRIPTION
        "
        Output Packets Counter Overload
        :This OID when set indicates an
        output Packets counter overload
        on client port
        "
	::= { pmc2002MondwRmonPacketsCntEntry 4 }


--- *********************************************************
---     TABLE for the pmc2002MondwRmonBroadcastCnt articles
--- *********************************************************

pmc2002MondwRmonBroadcastCntTable OBJECT-TYPE
	SYNTAX  SEQUENCE OF Pmc2002MondwRmonBroadcastCntEntry
	MAX-ACCESS not-accessible
	STATUS current
	DESCRIPTION
        "
        List of pmc2002MondwRmonBroadcastCnt
        Article
        "
	::= { pmc2002RmonClient 136 }


pmc2002MondwRmonBroadcastCntEntry OBJECT-TYPE
	SYNTAX Pmc2002MondwRmonBroadcastCntEntry
	MAX-ACCESS not-accessible
	STATUS current
	DESCRIPTION
        "
        Row definition for the pmc2002MondwRmonBroadcastCnt
        table
        "
	INDEX   { pmc2002MondwRmonBroadcastCntIndex }
	::= { pmc2002MondwRmonBroadcastCntTable 1 }


Pmc2002MondwRmonBroadcastCntEntry ::=
	SEQUENCE {
	pmc2002MondwRmonBroadcastCntIndex
		INTEGER,
	pmc2002MondwRmonBroadcastCntValuePortn
		Counter64,
	pmc2002MondwRmonBroadcastCntErrorPortn
		EkiOnOff,
	pmc2002MondwRmonBroadcastCntOverloadPortn
		EkiOnOff
	}


pmc2002MondwRmonBroadcastCntIndex OBJECT-TYPE
	SYNTAX  INTEGER(0..128)
	MAX-ACCESS  read-only
	STATUS current
	DESCRIPTION
        "
        Index definition for the pmc2002MondwRmonBroadcastCnt
        table
        "
	::= { pmc2002MondwRmonBroadcastCntEntry 1 }


pmc2002MondwRmonBroadcastCntValuePortn OBJECT-TYPE
	SYNTAX  Counter64
	MAX-ACCESS read-only
	STATUS current
	DESCRIPTION
        "
        Broadcast Counter On Client Output
        :This counter is increased each
        time a broadcast packet is transmitted
        on the client port.  <Help>  This
        counter gives the number of Broadcast
        packets transmitted on the client
        port
        "
	::= { pmc2002MondwRmonBroadcastCntEntry 2 }


pmc2002MondwRmonBroadcastCntErrorPortn OBJECT-TYPE
	SYNTAX  EkiOnOff
	MAX-ACCESS read-only
	STATUS current
	DESCRIPTION
        "
        Output Broadcast Counter Error
        :This OID when set indicates the
        output Broadcast counter value
         is invalid on client port
        "
	::= { pmc2002MondwRmonBroadcastCntEntry 3 }


pmc2002MondwRmonBroadcastCntOverloadPortn OBJECT-TYPE
	SYNTAX  EkiOnOff
	MAX-ACCESS read-only
	STATUS current
	DESCRIPTION
        "
        Output Broadcast Counter Overload
        :This OID when set indicates an
        output Broadcast counter overload
        on client port
        "
	::= { pmc2002MondwRmonBroadcastCntEntry 4 }


--- *********************************************************
---     TABLE for the pmc2002MondwRmonMulticastCnt articles
--- *********************************************************

pmc2002MondwRmonMulticastCntTable OBJECT-TYPE
	SYNTAX  SEQUENCE OF Pmc2002MondwRmonMulticastCntEntry
	MAX-ACCESS not-accessible
	STATUS current
	DESCRIPTION
        "
        List of pmc2002MondwRmonMulticastCnt
        Article
        "
	::= { pmc2002RmonClient 144 }


pmc2002MondwRmonMulticastCntEntry OBJECT-TYPE
	SYNTAX Pmc2002MondwRmonMulticastCntEntry
	MAX-ACCESS not-accessible
	STATUS current
	DESCRIPTION
        "
        Row definition for the pmc2002MondwRmonMulticastCnt
        table
        "
	INDEX   { pmc2002MondwRmonMulticastCntIndex }
	::= { pmc2002MondwRmonMulticastCntTable 1 }


Pmc2002MondwRmonMulticastCntEntry ::=
	SEQUENCE {
	pmc2002MondwRmonMulticastCntIndex
		INTEGER,
	pmc2002MondwRmonMulticastCntValuePortn
		Counter64,
	pmc2002MondwRmonMulticastCntErrorPortn
		EkiOnOff,
	pmc2002MondwRmonMulticastCntOverloadPortn
		EkiOnOff
	}


pmc2002MondwRmonMulticastCntIndex OBJECT-TYPE
	SYNTAX  INTEGER(0..128)
	MAX-ACCESS  read-only
	STATUS current
	DESCRIPTION
        "
        Index definition for the pmc2002MondwRmonMulticastCnt
        table
        "
	::= { pmc2002MondwRmonMulticastCntEntry 1 }


pmc2002MondwRmonMulticastCntValuePortn OBJECT-TYPE
	SYNTAX  Counter64
	MAX-ACCESS read-only
	STATUS current
	DESCRIPTION
        "
        Multicast Counter On Client Output
        :This counter is increased each
        time a Multicast packet is tra,smitted
        on the client port.  <Help>  This
        counter gives the number of Multicast
        packets transmitted on the client
        port
        "
	::= { pmc2002MondwRmonMulticastCntEntry 2 }


pmc2002MondwRmonMulticastCntErrorPortn OBJECT-TYPE
	SYNTAX  EkiOnOff
	MAX-ACCESS read-only
	STATUS current
	DESCRIPTION
        "
        Output Multicast Counter Error
        :This OID when set indicates the
        output Multicast counter value
         is invalid on client port
        "
	::= { pmc2002MondwRmonMulticastCntEntry 3 }


pmc2002MondwRmonMulticastCntOverloadPortn OBJECT-TYPE
	SYNTAX  EkiOnOff
	MAX-ACCESS read-only
	STATUS current
	DESCRIPTION
        "
        Output Multicast Counter Overload
        :This OID when set indicates an
        output Multicast counter overload
        on client port
        "
	::= { pmc2002MondwRmonMulticastCntEntry 4 }


--- *********************************************************
---     TABLE for the pmc2002MondwRmonPauseFrameCnt articles
--- *********************************************************

pmc2002MondwRmonPauseFrameCntTable OBJECT-TYPE
	SYNTAX  SEQUENCE OF Pmc2002MondwRmonPauseFrameCntEntry
	MAX-ACCESS not-accessible
	STATUS current
	DESCRIPTION
        "
        List of pmc2002MondwRmonPauseFrameCnt
        Article
        "
	::= { pmc2002RmonClient 152 }


pmc2002MondwRmonPauseFrameCntEntry OBJECT-TYPE
	SYNTAX Pmc2002MondwRmonPauseFrameCntEntry
	MAX-ACCESS not-accessible
	STATUS current
	DESCRIPTION
        "
        Row definition for the pmc2002MondwRmonPauseFrameCnt
        table
        "
	INDEX   { pmc2002MondwRmonPauseFrameCntIndex }
	::= { pmc2002MondwRmonPauseFrameCntTable 1 }


Pmc2002MondwRmonPauseFrameCntEntry ::=
	SEQUENCE {
	pmc2002MondwRmonPauseFrameCntIndex
		INTEGER,
	pmc2002MondwRmonPauseFrameCntValuePortn
		Counter64,
	pmc2002MondwRmonPauseFrameCntErrorPortn
		EkiOnOff,
	pmc2002MondwRmonPauseFrameCntOverloadPortn
		EkiOnOff
	}


pmc2002MondwRmonPauseFrameCntIndex OBJECT-TYPE
	SYNTAX  INTEGER(0..128)
	MAX-ACCESS  read-only
	STATUS current
	DESCRIPTION
        "
        Index definition for the pmc2002MondwRmonPauseFrameCnt
        table
        "
	::= { pmc2002MondwRmonPauseFrameCntEntry 1 }


pmc2002MondwRmonPauseFrameCntValuePortn OBJECT-TYPE
	SYNTAX  Counter64
	MAX-ACCESS read-only
	STATUS current
	DESCRIPTION
        "
        Pause Counter On Client Output
        :This counter is increased each
        time a Pause frame is generated
        by the PM on the client port
        "
	::= { pmc2002MondwRmonPauseFrameCntEntry 2 }


pmc2002MondwRmonPauseFrameCntErrorPortn OBJECT-TYPE
	SYNTAX  EkiOnOff
	MAX-ACCESS read-only
	STATUS current
	DESCRIPTION
        "
        Output Pause Counter Error :This
        OID when set indicates the output
        Pause counter value is invalid
         on client port
        "
	::= { pmc2002MondwRmonPauseFrameCntEntry 3 }


pmc2002MondwRmonPauseFrameCntOverloadPortn OBJECT-TYPE
	SYNTAX  EkiOnOff
	MAX-ACCESS read-only
	STATUS current
	DESCRIPTION
        "
        Output Pause Counter Overload
         :This OID when set indicates an
        output Pause counter overload on
        client port
        "
	::= { pmc2002MondwRmonPauseFrameCntEntry 4 }


--- *********************************************************
---     TABLE for the pmc2002MondwRmonTimerCnt articles
--- *********************************************************

pmc2002MondwRmonTimerCntTable OBJECT-TYPE
	SYNTAX  SEQUENCE OF Pmc2002MondwRmonTimerCntEntry
	MAX-ACCESS not-accessible
	STATUS current
	DESCRIPTION
        "
        List of pmc2002MondwRmonTimerCnt
        Article
        "
	::= { pmc2002RmonClient 160 }


pmc2002MondwRmonTimerCntEntry OBJECT-TYPE
	SYNTAX Pmc2002MondwRmonTimerCntEntry
	MAX-ACCESS not-accessible
	STATUS current
	DESCRIPTION
        "
        Row definition for the pmc2002MondwRmonTimerCnt
        table
        "
	INDEX   { pmc2002MondwRmonTimerCntIndex }
	::= { pmc2002MondwRmonTimerCntTable 1 }


Pmc2002MondwRmonTimerCntEntry ::=
	SEQUENCE {
	pmc2002MondwRmonTimerCntIndex
		INTEGER,
	pmc2002MondwRmonTimerCntValuePortn
		Counter64,
	pmc2002MondwRmonTimerCntErrorPortn
		EkiOnOff,
	pmc2002MondwRmonTimerCntOverloadPortn
		EkiOnOff
	}


pmc2002MondwRmonTimerCntIndex OBJECT-TYPE
	SYNTAX  INTEGER(0..128)
	MAX-ACCESS  read-only
	STATUS current
	DESCRIPTION
        "
        Index definition for the pmc2002MondwRmonTimerCnt
        table
        "
	::= { pmc2002MondwRmonTimerCntEntry 1 }


pmc2002MondwRmonTimerCntValuePortn OBJECT-TYPE
	SYNTAX  Counter64
	MAX-ACCESS read-only
	STATUS current
	DESCRIPTION
        "
        RMON Timer On Client Output :This
        is the timing counter dedicated
        to the downstream RMON counters.
        It is incremented every 125 us.
        "
	::= { pmc2002MondwRmonTimerCntEntry 2 }


pmc2002MondwRmonTimerCntErrorPortn OBJECT-TYPE
	SYNTAX  EkiOnOff
	MAX-ACCESS read-only
	STATUS current
	DESCRIPTION
        "
        Output RMON Timer Error :This
         OID when set indicates the output
        RMON timer is invalid on client
        port
        "
	::= { pmc2002MondwRmonTimerCntEntry 3 }


pmc2002MondwRmonTimerCntOverloadPortn OBJECT-TYPE
	SYNTAX  EkiOnOff
	MAX-ACCESS read-only
	STATUS current
	DESCRIPTION
        "
        Output RMON Timer Overload :This
        OID when set indicates an output
        RMON timer overload on client port
        "
	::= { pmc2002MondwRmonTimerCntEntry 4 }


--- *********************************************************
---     TABLE for the pmc2002MondwRmonBitsCnt articles
--- *********************************************************

pmc2002MondwRmonBitsCntTable OBJECT-TYPE
	SYNTAX  SEQUENCE OF Pmc2002MondwRmonBitsCntEntry
	MAX-ACCESS not-accessible
	STATUS current
	DESCRIPTION
        "
        List of pmc2002MondwRmonBitsCnt
        Article
        "
	::= { pmc2002RmonClient 168 }


pmc2002MondwRmonBitsCntEntry OBJECT-TYPE
	SYNTAX Pmc2002MondwRmonBitsCntEntry
	MAX-ACCESS not-accessible
	STATUS current
	DESCRIPTION
        "
        Row definition for the pmc2002MondwRmonBitsCnt
        table
        "
	INDEX   { pmc2002MondwRmonBitsCntIndex }
	::= { pmc2002MondwRmonBitsCntTable 1 }


Pmc2002MondwRmonBitsCntEntry ::=
	SEQUENCE {
	pmc2002MondwRmonBitsCntIndex
		INTEGER,
	pmc2002MondwRmonBitsCntValuePortn
		Counter64,
	pmc2002MondwRmonBitsCntErrorPortn
		EkiOnOff,
	pmc2002MondwRmonBitsCntOverloadPortn
		EkiOnOff
	}


pmc2002MondwRmonBitsCntIndex OBJECT-TYPE
	SYNTAX  INTEGER(0..128)
	MAX-ACCESS  read-only
	STATUS current
	DESCRIPTION
        "
        Index definition for the pmc2002MondwRmonBitsCnt
        table
        "
	::= { pmc2002MondwRmonBitsCntEntry 1 }


pmc2002MondwRmonBitsCntValuePortn OBJECT-TYPE
	SYNTAX  Counter64
	MAX-ACCESS read-only
	STATUS current
	DESCRIPTION
        "
        Bits Counter On Client Output
         :This counter is increased each
        time a bit is received on the Output
        client port
        "
	::= { pmc2002MondwRmonBitsCntEntry 2 }


pmc2002MondwRmonBitsCntErrorPortn OBJECT-TYPE
	SYNTAX  EkiOnOff
	MAX-ACCESS read-only
	STATUS current
	DESCRIPTION
        "
        Output Bits Counter Error :This
        OID when set indicates the output
        Bits counter value is invalid on
        client port
        "
	::= { pmc2002MondwRmonBitsCntEntry 3 }


pmc2002MondwRmonBitsCntOverloadPortn OBJECT-TYPE
	SYNTAX  EkiOnOff
	MAX-ACCESS read-only
	STATUS current
	DESCRIPTION
        "
        Output Bits Counter Overload :This
        OID when set indicates an output
        Bits counter overload on client
        port
        "
	::= { pmc2002MondwRmonBitsCntEntry 4 }


--- *********************************************************
---     TABLE for the pmc2002MondwRmonUnicastCnt articles
--- *********************************************************

pmc2002MondwRmonUnicastCntTable OBJECT-TYPE
	SYNTAX  SEQUENCE OF Pmc2002MondwRmonUnicastCntEntry
	MAX-ACCESS not-accessible
	STATUS current
	DESCRIPTION
        "
        List of pmc2002MondwRmonUnicastCnt
        Article
        "
	::= { pmc2002RmonClient 176 }


pmc2002MondwRmonUnicastCntEntry OBJECT-TYPE
	SYNTAX Pmc2002MondwRmonUnicastCntEntry
	MAX-ACCESS not-accessible
	STATUS current
	DESCRIPTION
        "
        Row definition for the pmc2002MondwRmonUnicastCnt
        table
        "
	INDEX   { pmc2002MondwRmonUnicastCntIndex }
	::= { pmc2002MondwRmonUnicastCntTable 1 }


Pmc2002MondwRmonUnicastCntEntry ::=
	SEQUENCE {
	pmc2002MondwRmonUnicastCntIndex
		INTEGER,
	pmc2002MondwRmonUnicastCntValuePortn
		Counter64,
	pmc2002MondwRmonUnicastCntErrorPortn
		EkiOnOff,
	pmc2002MondwRmonUnicastCntOverloadPortn
		EkiOnOff
	}


pmc2002MondwRmonUnicastCntIndex OBJECT-TYPE
	SYNTAX  INTEGER(0..128)
	MAX-ACCESS  read-only
	STATUS current
	DESCRIPTION
        "
        Index definition for the pmc2002MondwRmonUnicastCnt
        table
        "
	::= { pmc2002MondwRmonUnicastCntEntry 1 }


pmc2002MondwRmonUnicastCntValuePortn OBJECT-TYPE
	SYNTAX  Counter64
	MAX-ACCESS read-only
	STATUS current
	DESCRIPTION
        "
        Unicast Counter On Client Output
        :This counter is increased each
        time a Unicast packet is transmitted
        on client port   <Help>  This counter
        gives the number of Unicast packets
        transmitted on the client output
        port
        "
	::= { pmc2002MondwRmonUnicastCntEntry 2 }


pmc2002MondwRmonUnicastCntErrorPortn OBJECT-TYPE
	SYNTAX  EkiOnOff
	MAX-ACCESS read-only
	STATUS current
	DESCRIPTION
        "
        Output Unicast Counter Error :This
        OID when set indicates the output
        RMON timer is invalid on client
        port
        "
	::= { pmc2002MondwRmonUnicastCntEntry 3 }


pmc2002MondwRmonUnicastCntOverloadPortn OBJECT-TYPE
	SYNTAX  EkiOnOff
	MAX-ACCESS read-only
	STATUS current
	DESCRIPTION
        "
        Output Unicast Counter Overload
        :This OID when set indicates an
        output RMON timer overload on client
        port
        "
	::= { pmc2002MondwRmonUnicastCntEntry 4 }


--- *********************************************************
---     TABLE for the pmc2002MondwRmonNonUnicastCnt articles
--- *********************************************************

pmc2002MondwRmonNonUnicastCntTable OBJECT-TYPE
	SYNTAX  SEQUENCE OF Pmc2002MondwRmonNonUnicastCntEntry
	MAX-ACCESS not-accessible
	STATUS current
	DESCRIPTION
        "
        List of pmc2002MondwRmonNonUnicastCnt
        Article
        "
	::= { pmc2002RmonClient 184 }


pmc2002MondwRmonNonUnicastCntEntry OBJECT-TYPE
	SYNTAX Pmc2002MondwRmonNonUnicastCntEntry
	MAX-ACCESS not-accessible
	STATUS current
	DESCRIPTION
        "
        Row definition for the pmc2002MondwRmonNonUnicastCnt
        table
        "
	INDEX   { pmc2002MondwRmonNonUnicastCntIndex }
	::= { pmc2002MondwRmonNonUnicastCntTable 1 }


Pmc2002MondwRmonNonUnicastCntEntry ::=
	SEQUENCE {
	pmc2002MondwRmonNonUnicastCntIndex
		INTEGER,
	pmc2002MondwRmonNonUnicastCntValuePortn
		Counter64,
	pmc2002MondwRmonNonUnicastCntErrorPortn
		EkiOnOff,
	pmc2002MondwRmonNonUnicastCntOverloadPortn
		EkiOnOff
	}


pmc2002MondwRmonNonUnicastCntIndex OBJECT-TYPE
	SYNTAX  INTEGER(0..128)
	MAX-ACCESS  read-only
	STATUS current
	DESCRIPTION
        "
        Index definition for the pmc2002MondwRmonNonUnicastCnt
        table
        "
	::= { pmc2002MondwRmonNonUnicastCntEntry 1 }


pmc2002MondwRmonNonUnicastCntValuePortn OBJECT-TYPE
	SYNTAX  Counter64
	MAX-ACCESS read-only
	STATUS current
	DESCRIPTION
        "
        Non Unicast Counter On Client
         Output :This counter is increased
        each time a Non Unicast packet
         is transmitted on client port
           <Help>  This counter gives the
        number of Non Unicast packets transmitted
        on the client output port
        "
	::= { pmc2002MondwRmonNonUnicastCntEntry 2 }


pmc2002MondwRmonNonUnicastCntErrorPortn OBJECT-TYPE
	SYNTAX  EkiOnOff
	MAX-ACCESS read-only
	STATUS current
	DESCRIPTION
        "
        Output Non Unicast Counter Error
        :This OID when set indicates the
        output Bits counter value is invalid
        on client port
        "
	::= { pmc2002MondwRmonNonUnicastCntEntry 3 }


pmc2002MondwRmonNonUnicastCntOverloadPortn OBJECT-TYPE
	SYNTAX  EkiOnOff
	MAX-ACCESS read-only
	STATUS current
	DESCRIPTION
        "
        Output Non Unicast Counter Overload
        :This OID when set indicates an
        output Bits counter overload on
        client port
        "
	::= { pmc2002MondwRmonNonUnicastCntEntry 4 }


pmc2002MonCountersReset  OBJECT-TYPE
	SYNTAX EkiOnOff
	MAX-ACCESS read-write
	STATUS current
	DESCRIPTION
	"RMON Counters Reset:This OID resets and restarts all the RMON counters"
	::= { pmc2002RmonOther  359 }

pmc2002MonCountersStop  OBJECT-TYPE
	SYNTAX EkiOnOff
	MAX-ACCESS read-write
	STATUS current
	DESCRIPTION
	"RMON Counters stop:This OID stops all the RMON counters"
	::= { pmc2002RmonOther  360 }






--- *****************************************************
--- $$$$$$$$$$$$$$$$$$$$$$$$$$$$$$$$$$$$$$$$$$$$$$$$$$$$$
---     MEASURES
--- $$$$$$$$$$$$$$$$$$$$$$$$$$$$$$$$$$$$$$$$$$$$$$$$$$$$$
--- *****************************************************



pmc2002Mesrsynth0 OBJECT-TYPE
	  SYNTAX EkiMeasureType
	  MAX-ACCESS read-only
	  STATUS deprecated
	  DESCRIPTION
        "
        Not Used :This OID gives the unit
        used on AUX1 measurement of XFP#1
         (Unit = )
        "
	  ::= { pmc2002MesrOther 0 }



pmc2002Mesrsynth1 OBJECT-TYPE
	  SYNTAX EkiMeasureType
	  MAX-ACCESS read-only
	  STATUS deprecated
	  DESCRIPTION
        "
        Not Used :This OID gives the unit
        used on AUX2 measurement of XFP#1
         (Unit = )
        "
	  ::= { pmc2002MesrOther 1 }



--- *********************************************************
---     TABLE for the pmc2002MesrclientModTempMeas articles
--- *********************************************************

pmc2002MesrclientModTempMeasTable OBJECT-TYPE
	SYNTAX  SEQUENCE OF Pmc2002MesrclientModTempMeasEntry
	MAX-ACCESS not-accessible
	STATUS current
	DESCRIPTION
        "
        List of pmc2002MesrclientModTempMeas
        Article
        "
	::= { pmc2002MesrClient 16 }


pmc2002MesrclientModTempMeasEntry OBJECT-TYPE
	SYNTAX Pmc2002MesrclientModTempMeasEntry
	MAX-ACCESS not-accessible
	STATUS current
	DESCRIPTION
        "
        Row definition for the pmc2002MesrclientModTempMeas
        table
        "
	INDEX   { pmc2002MesrclientModTempMeasIndex }
	::= { pmc2002MesrclientModTempMeasTable 1 }


Pmc2002MesrclientModTempMeasEntry ::=
	SEQUENCE {
	pmc2002MesrclientModTempMeasIndex
		INTEGER,
	pmc2002MesrclientModTempMeasPortn
		INTEGER
	}


pmc2002MesrclientModTempMeasIndex OBJECT-TYPE
	SYNTAX  INTEGER(0..128)
	MAX-ACCESS  read-only
	STATUS current
	DESCRIPTION
        "
        Index definition for the pmc2002MesrclientModTempMeas
        table
        "
	::= { pmc2002MesrclientModTempMeasEntry 1 }


pmc2002MesrclientModTempMeasPortn OBJECT-TYPE
	SYNTAX  INTEGER (0..65535)
	MAX-ACCESS read-only
	STATUS current
	DESCRIPTION
        "
        SFP+ Temperature :This OID gives
        the temperature value of the SFP
        plugged in port, read from the
         DDM (Digital Diagnostic Monitoring)
        (Temperature = AV/256)  (Unit =
        C)  <Help>  This measure gives
         the temperature of the client
         transceiver
        "
	::= { pmc2002MesrclientModTempMeasEntry 2 }


--- *********************************************************
---     TABLE for the pmc2002MesrclientBiasCurrentMeas articles
--- *********************************************************

pmc2002MesrclientBiasCurrentMeasTable OBJECT-TYPE
	SYNTAX  SEQUENCE OF Pmc2002MesrclientBiasCurrentMeasEntry
	MAX-ACCESS not-accessible
	STATUS current
	DESCRIPTION
        "
        List of pmc2002MesrclientBiasCurrentMeas
        Article
        "
	::= { pmc2002MesrClient 32 }


pmc2002MesrclientBiasCurrentMeasEntry OBJECT-TYPE
	SYNTAX Pmc2002MesrclientBiasCurrentMeasEntry
	MAX-ACCESS not-accessible
	STATUS current
	DESCRIPTION
        "
        Row definition for the pmc2002MesrclientBiasCurrentMeas
        table
        "
	INDEX   { pmc2002MesrclientBiasCurrentMeasIndex }
	::= { pmc2002MesrclientBiasCurrentMeasTable 1 }


Pmc2002MesrclientBiasCurrentMeasEntry ::=
	SEQUENCE {
	pmc2002MesrclientBiasCurrentMeasIndex
		INTEGER,
	pmc2002MesrclientBiasCurrentMeasPortn
		INTEGER
	}


pmc2002MesrclientBiasCurrentMeasIndex OBJECT-TYPE
	SYNTAX  INTEGER(0..128)
	MAX-ACCESS  read-only
	STATUS current
	DESCRIPTION
        "
        Index definition for the pmc2002MesrclientBiasCurrentMeas
        table
        "
	::= { pmc2002MesrclientBiasCurrentMeasEntry 1 }


pmc2002MesrclientBiasCurrentMeasPortn OBJECT-TYPE
	SYNTAX  INTEGER (0..65535)
	MAX-ACCESS read-only
	STATUS current
	DESCRIPTION
        "
        SFP+ Laser Bias :This OID gives
        the bias value of the SFP plugged
        into port, read from the DDM (Digital
        Diagnostic Monitoring)  (Bias =
        AV/500) (Unit = mA)  <Help>  This
        measure gives the bias of the client
        transceiver
        "
	::= { pmc2002MesrclientBiasCurrentMeasEntry 2 }


--- *********************************************************
---     TABLE for the pmc2002MesrclientTxPowerMeas articles
--- *********************************************************

pmc2002MesrclientTxPowerMeasTable OBJECT-TYPE
	SYNTAX  SEQUENCE OF Pmc2002MesrclientTxPowerMeasEntry
	MAX-ACCESS not-accessible
	STATUS current
	DESCRIPTION
        "
        List of pmc2002MesrclientTxPowerMeas
        Article
        "
	::= { pmc2002MesrClient 40 }


pmc2002MesrclientTxPowerMeasEntry OBJECT-TYPE
	SYNTAX Pmc2002MesrclientTxPowerMeasEntry
	MAX-ACCESS not-accessible
	STATUS current
	DESCRIPTION
        "
        Row definition for the pmc2002MesrclientTxPowerMeas
        table
        "
	INDEX   { pmc2002MesrclientTxPowerMeasIndex }
	::= { pmc2002MesrclientTxPowerMeasTable 1 }


Pmc2002MesrclientTxPowerMeasEntry ::=
	SEQUENCE {
	pmc2002MesrclientTxPowerMeasIndex
		INTEGER,
	pmc2002MesrclientTxPowerMeasPortn
		INTEGER
	}


pmc2002MesrclientTxPowerMeasIndex OBJECT-TYPE
	SYNTAX  INTEGER(0..128)
	MAX-ACCESS  read-only
	STATUS current
	DESCRIPTION
        "
        Index definition for the pmc2002MesrclientTxPowerMeas
        table
        "
	::= { pmc2002MesrclientTxPowerMeasEntry 1 }


pmc2002MesrclientTxPowerMeasPortn OBJECT-TYPE
	SYNTAX  INTEGER (0..65535)
	MAX-ACCESS read-only
	STATUS current
	DESCRIPTION
        "
        SFP+ Tx Power :This OID gives
         the transmit power value of the
        SFP plugged into port, read from
        the DDM (Digital Diagnostic Monitoring)
        (Power = 10*log(AV)-40) (Unit =
        dBm)  <Help>  This measure gives
        the Tx optical power of the client
        transceiver
        "
	::= { pmc2002MesrclientTxPowerMeasEntry 2 }


--- *********************************************************
---     TABLE for the pmc2002MesrclientRxPowerMeas articles
--- *********************************************************

pmc2002MesrclientRxPowerMeasTable OBJECT-TYPE
	SYNTAX  SEQUENCE OF Pmc2002MesrclientRxPowerMeasEntry
	MAX-ACCESS not-accessible
	STATUS current
	DESCRIPTION
        "
        List of pmc2002MesrclientRxPowerMeas
        Article
        "
	::= { pmc2002MesrClient 48 }


pmc2002MesrclientRxPowerMeasEntry OBJECT-TYPE
	SYNTAX Pmc2002MesrclientRxPowerMeasEntry
	MAX-ACCESS not-accessible
	STATUS current
	DESCRIPTION
        "
        Row definition for the pmc2002MesrclientRxPowerMeas
        table
        "
	INDEX   { pmc2002MesrclientRxPowerMeasIndex }
	::= { pmc2002MesrclientRxPowerMeasTable 1 }


Pmc2002MesrclientRxPowerMeasEntry ::=
	SEQUENCE {
	pmc2002MesrclientRxPowerMeasIndex
		INTEGER,
	pmc2002MesrclientRxPowerMeasPortn
		INTEGER
	}


pmc2002MesrclientRxPowerMeasIndex OBJECT-TYPE
	SYNTAX  INTEGER(0..128)
	MAX-ACCESS  read-only
	STATUS current
	DESCRIPTION
        "
        Index definition for the pmc2002MesrclientRxPowerMeas
        table
        "
	::= { pmc2002MesrclientRxPowerMeasEntry 1 }


pmc2002MesrclientRxPowerMeasPortn OBJECT-TYPE
	SYNTAX  INTEGER (0..65535)
	MAX-ACCESS read-only
	STATUS current
	DESCRIPTION
        "
        SFP+ Rx Power :This OID gives
         the receive power value of the
        SFP plugged into port, read in
         the DDM (Digital Diagnostic Monitoring)
        (Power = 10*log(AV)-40) (Unit =
        dBm)  <Help>  This measure gives
        the Rx optical power of the client
        transceiver
        "
	::= { pmc2002MesrclientRxPowerMeasEntry 2 }


--- *********************************************************
---     TABLE for the pmc2002Mesrline1ModTempMeas articles
--- *********************************************************

pmc2002Mesrline1ModTempMeasTable OBJECT-TYPE
	SYNTAX  SEQUENCE OF Pmc2002Mesrline1ModTempMeasEntry
	MAX-ACCESS not-accessible
	STATUS current
	DESCRIPTION
        "
        List of pmc2002Mesrline1ModTempMeas
        Article
        "
	::= { pmc2002MesrLine 208 }


pmc2002Mesrline1ModTempMeasEntry OBJECT-TYPE
	SYNTAX Pmc2002Mesrline1ModTempMeasEntry
	MAX-ACCESS not-accessible
	STATUS current
	DESCRIPTION
        "
        Row definition for the pmc2002Mesrline1ModTempMeas
        table
        "
	INDEX   { pmc2002Mesrline1ModTempMeasIndex }
	::= { pmc2002Mesrline1ModTempMeasTable 1 }


Pmc2002Mesrline1ModTempMeasEntry ::=
	SEQUENCE {
	pmc2002Mesrline1ModTempMeasIndex
		INTEGER,
	pmc2002Mesrline1ModTempMeasPortn
		INTEGER
	}


pmc2002Mesrline1ModTempMeasIndex OBJECT-TYPE
	SYNTAX  INTEGER(0..128)
	MAX-ACCESS  read-only
	STATUS current
	DESCRIPTION
        "
        Index definition for the pmc2002Mesrline1ModTempMeas
        table
        "
	::= { pmc2002Mesrline1ModTempMeasEntry 1 }


pmc2002Mesrline1ModTempMeasPortn OBJECT-TYPE
	SYNTAX  INTEGER (0..65535)
	MAX-ACCESS read-only
	STATUS current
	DESCRIPTION
        "
        OTX TLH Temperature :This OID
         gives the temperature of the OTX
        TLH plugged in line#n, read from
        the DDM (Digital Diagnostic Monitoring)
        (Temperature = AV/256) (Unit =
         C)  <Help>  This measure gives
        the temperature of the line transceiver
        "
	::= { pmc2002Mesrline1ModTempMeasEntry 2 }


--- *********************************************************
---     TABLE for the pmc2002Mesrline1Reserved articles
--- *********************************************************

pmc2002Mesrline1ReservedTable OBJECT-TYPE
	SYNTAX  SEQUENCE OF Pmc2002Mesrline1ReservedEntry
	MAX-ACCESS not-accessible
	STATUS deprecated
	DESCRIPTION
        "
        List of pmc2002Mesrline1Reserved
        Article
        "
	::= { pmc2002MesrLine 209 }


pmc2002Mesrline1ReservedEntry OBJECT-TYPE
	SYNTAX Pmc2002Mesrline1ReservedEntry
	MAX-ACCESS not-accessible
	STATUS deprecated
	DESCRIPTION
        "
        Row definition for the pmc2002Mesrline1Reserved
        table
        "
	INDEX   { pmc2002Mesrline1ReservedIndex }
	::= { pmc2002Mesrline1ReservedTable 1 }


Pmc2002Mesrline1ReservedEntry ::=
	SEQUENCE {
	pmc2002Mesrline1ReservedIndex
		INTEGER,
	pmc2002Mesrline1ReservedPortn
		INTEGER
	}


pmc2002Mesrline1ReservedIndex OBJECT-TYPE
	SYNTAX  INTEGER(0..128)
	MAX-ACCESS  read-only
	STATUS deprecated
	DESCRIPTION
        "
        Index definition for the pmc2002Mesrline1Reserved
        table
        "
	::= { pmc2002Mesrline1ReservedEntry 1 }


pmc2002Mesrline1ReservedPortn OBJECT-TYPE
	SYNTAX  INTEGER (0..65535)
	MAX-ACCESS read-only
	STATUS deprecated
	DESCRIPTION
        "
        Not Used :Reserved
        "
	::= { pmc2002Mesrline1ReservedEntry 2 }


--- *********************************************************
---     TABLE for the pmc2002Mesrline1BiasCurrentMeas articles
--- *********************************************************

pmc2002Mesrline1BiasCurrentMeasTable OBJECT-TYPE
	SYNTAX  SEQUENCE OF Pmc2002Mesrline1BiasCurrentMeasEntry
	MAX-ACCESS not-accessible
	STATUS current
	DESCRIPTION
        "
        List of pmc2002Mesrline1BiasCurrentMeas
        Article
        "
	::= { pmc2002MesrLine 210 }


pmc2002Mesrline1BiasCurrentMeasEntry OBJECT-TYPE
	SYNTAX Pmc2002Mesrline1BiasCurrentMeasEntry
	MAX-ACCESS not-accessible
	STATUS current
	DESCRIPTION
        "
        Row definition for the pmc2002Mesrline1BiasCurrentMeas
        table
        "
	INDEX   { pmc2002Mesrline1BiasCurrentMeasIndex }
	::= { pmc2002Mesrline1BiasCurrentMeasTable 1 }


Pmc2002Mesrline1BiasCurrentMeasEntry ::=
	SEQUENCE {
	pmc2002Mesrline1BiasCurrentMeasIndex
		INTEGER,
	pmc2002Mesrline1BiasCurrentMeasPortn
		INTEGER
	}


pmc2002Mesrline1BiasCurrentMeasIndex OBJECT-TYPE
	SYNTAX  INTEGER(0..128)
	MAX-ACCESS  read-only
	STATUS current
	DESCRIPTION
        "
        Index definition for the pmc2002Mesrline1BiasCurrentMeas
        table
        "
	::= { pmc2002Mesrline1BiasCurrentMeasEntry 1 }


pmc2002Mesrline1BiasCurrentMeasPortn OBJECT-TYPE
	SYNTAX  INTEGER (0..65535)
	MAX-ACCESS read-only
	STATUS current
	DESCRIPTION
        "
        OTX TLH Tx Bias Current :This
         OID gives the bias value of the
        OTX TLH plugged in line #n, read
        from the DDM (Digital Diagnostic
        Monitoring) (Bias = AV/500) (Unit
        = mA)  <Help>  This measure gives
        the bias of the line transceiver
        "
	::= { pmc2002Mesrline1BiasCurrentMeasEntry 2 }


--- *********************************************************
---     TABLE for the pmc2002Mesrline1TxPowerMeas articles
--- *********************************************************

pmc2002Mesrline1TxPowerMeasTable OBJECT-TYPE
	SYNTAX  SEQUENCE OF Pmc2002Mesrline1TxPowerMeasEntry
	MAX-ACCESS not-accessible
	STATUS current
	DESCRIPTION
        "
        List of pmc2002Mesrline1TxPowerMeas
        Article
        "
	::= { pmc2002MesrLine 211 }


pmc2002Mesrline1TxPowerMeasEntry OBJECT-TYPE
	SYNTAX Pmc2002Mesrline1TxPowerMeasEntry
	MAX-ACCESS not-accessible
	STATUS current
	DESCRIPTION
        "
        Row definition for the pmc2002Mesrline1TxPowerMeas
        table
        "
	INDEX   { pmc2002Mesrline1TxPowerMeasIndex }
	::= { pmc2002Mesrline1TxPowerMeasTable 1 }


Pmc2002Mesrline1TxPowerMeasEntry ::=
	SEQUENCE {
	pmc2002Mesrline1TxPowerMeasIndex
		INTEGER,
	pmc2002Mesrline1TxPowerMeasPortn
		INTEGER
	}


pmc2002Mesrline1TxPowerMeasIndex OBJECT-TYPE
	SYNTAX  INTEGER(0..128)
	MAX-ACCESS  read-only
	STATUS current
	DESCRIPTION
        "
        Index definition for the pmc2002Mesrline1TxPowerMeas
        table
        "
	::= { pmc2002Mesrline1TxPowerMeasEntry 1 }


pmc2002Mesrline1TxPowerMeasPortn OBJECT-TYPE
	SYNTAX  INTEGER (0..65535)
	MAX-ACCESS read-only
	STATUS current
	DESCRIPTION
        "
        OTX TLH Tx Power :This OID gives
        the transmit power value of the
        OTX TLH plugged in line #n, read
        from the DDM (Digital   Diagnostic
        Monitoring) (Power = 10*log(AV)-40)
        (Unit = dBm)  <Help>  This measure
        gives the Tx optical power of the
        line transceiver
        "
	::= { pmc2002Mesrline1TxPowerMeasEntry 2 }


--- *********************************************************
---     TABLE for the pmc2002Mesrline1RxPowerMeas articles
--- *********************************************************

pmc2002Mesrline1RxPowerMeasTable OBJECT-TYPE
	SYNTAX  SEQUENCE OF Pmc2002Mesrline1RxPowerMeasEntry
	MAX-ACCESS not-accessible
	STATUS current
	DESCRIPTION
        "
        List of pmc2002Mesrline1RxPowerMeas
        Article
        "
	::= { pmc2002MesrLine 212 }


pmc2002Mesrline1RxPowerMeasEntry OBJECT-TYPE
	SYNTAX Pmc2002Mesrline1RxPowerMeasEntry
	MAX-ACCESS not-accessible
	STATUS current
	DESCRIPTION
        "
        Row definition for the pmc2002Mesrline1RxPowerMeas
        table
        "
	INDEX   { pmc2002Mesrline1RxPowerMeasIndex }
	::= { pmc2002Mesrline1RxPowerMeasTable 1 }


Pmc2002Mesrline1RxPowerMeasEntry ::=
	SEQUENCE {
	pmc2002Mesrline1RxPowerMeasIndex
		INTEGER,
	pmc2002Mesrline1RxPowerMeasPortn
		INTEGER
	}


pmc2002Mesrline1RxPowerMeasIndex OBJECT-TYPE
	SYNTAX  INTEGER(0..128)
	MAX-ACCESS  read-only
	STATUS current
	DESCRIPTION
        "
        Index definition for the pmc2002Mesrline1RxPowerMeas
        table
        "
	::= { pmc2002Mesrline1RxPowerMeasEntry 1 }


pmc2002Mesrline1RxPowerMeasPortn OBJECT-TYPE
	SYNTAX  INTEGER (0..65535)
	MAX-ACCESS read-only
	STATUS current
	DESCRIPTION
        "
        OTX TLH Rx Power :This OID gives
        the receive power value of the
         OTX TLH plugged in line #n, read
        from the DDM (Digital Diagnostic
        Monitoring) (Power = 10*log(AV)-40)
        (Unit = dBm)  <Help>  This measure
        gives the Rx optical power of the
        line transceiver
        "
	::= { pmc2002Mesrline1RxPowerMeasEntry 2 }


--- *********************************************************
---     TABLE for the pmc2002Mesrline1Aux1Meas articles
--- *********************************************************

pmc2002Mesrline1Aux1MeasTable OBJECT-TYPE
	SYNTAX  SEQUENCE OF Pmc2002Mesrline1Aux1MeasEntry
	MAX-ACCESS not-accessible
	STATUS deprecated
	DESCRIPTION
        "
        List of pmc2002Mesrline1Aux1Meas
        Article
        "
	::= { pmc2002MesrLine 213 }


pmc2002Mesrline1Aux1MeasEntry OBJECT-TYPE
	SYNTAX Pmc2002Mesrline1Aux1MeasEntry
	MAX-ACCESS not-accessible
	STATUS deprecated
	DESCRIPTION
        "
        Row definition for the pmc2002Mesrline1Aux1Meas
        table
        "
	INDEX   { pmc2002Mesrline1Aux1MeasIndex }
	::= { pmc2002Mesrline1Aux1MeasTable 1 }


Pmc2002Mesrline1Aux1MeasEntry ::=
	SEQUENCE {
	pmc2002Mesrline1Aux1MeasIndex
		INTEGER,
	pmc2002Mesrline1Aux1MeasPortn
		INTEGER
	}


pmc2002Mesrline1Aux1MeasIndex OBJECT-TYPE
	SYNTAX  INTEGER(0..128)
	MAX-ACCESS  read-only
	STATUS deprecated
	DESCRIPTION
        "
        Index definition for the pmc2002Mesrline1Aux1Meas
        table
        "
	::= { pmc2002Mesrline1Aux1MeasEntry 1 }


pmc2002Mesrline1Aux1MeasPortn OBJECT-TYPE
	SYNTAX  INTEGER (0..65535)
	MAX-ACCESS read-only
	STATUS deprecated
	DESCRIPTION
        "
        Not Used :This OID gives the receive
        power value read in the DDM (Digital
        Diagnostic Monitoring) of the OTX
        TLH plugged in line #n (Unit =
         ?)
        "
	::= { pmc2002Mesrline1Aux1MeasEntry 2 }


--- *********************************************************
---     TABLE for the pmc2002Mesrline1Aux2Meas articles
--- *********************************************************

pmc2002Mesrline1Aux2MeasTable OBJECT-TYPE
	SYNTAX  SEQUENCE OF Pmc2002Mesrline1Aux2MeasEntry
	MAX-ACCESS not-accessible
	STATUS deprecated
	DESCRIPTION
        "
        List of pmc2002Mesrline1Aux2Meas
        Article
        "
	::= { pmc2002MesrLine 214 }


pmc2002Mesrline1Aux2MeasEntry OBJECT-TYPE
	SYNTAX Pmc2002Mesrline1Aux2MeasEntry
	MAX-ACCESS not-accessible
	STATUS deprecated
	DESCRIPTION
        "
        Row definition for the pmc2002Mesrline1Aux2Meas
        table
        "
	INDEX   { pmc2002Mesrline1Aux2MeasIndex }
	::= { pmc2002Mesrline1Aux2MeasTable 1 }


Pmc2002Mesrline1Aux2MeasEntry ::=
	SEQUENCE {
	pmc2002Mesrline1Aux2MeasIndex
		INTEGER,
	pmc2002Mesrline1Aux2MeasPortn
		INTEGER
	}


pmc2002Mesrline1Aux2MeasIndex OBJECT-TYPE
	SYNTAX  INTEGER(0..128)
	MAX-ACCESS  read-only
	STATUS deprecated
	DESCRIPTION
        "
        Index definition for the pmc2002Mesrline1Aux2Meas
        table
        "
	::= { pmc2002Mesrline1Aux2MeasEntry 1 }


pmc2002Mesrline1Aux2MeasPortn OBJECT-TYPE
	SYNTAX  INTEGER (0..65535)
	MAX-ACCESS read-only
	STATUS deprecated
	DESCRIPTION
        "
        Not Used :This OID gives the receive
        power value read in the DDM (Digital
        Diagnostic Monitoring) of the OTX
        TLH plugged in line #n (Unit =
         ?)
        "
	::= { pmc2002Mesrline1Aux2MeasEntry 2 }


--- *********************************************************
---     TABLE for the pmc2002Mesrline1Aging articles
--- *********************************************************

pmc2002Mesrline1AgingTable OBJECT-TYPE
	SYNTAX  SEQUENCE OF Pmc2002Mesrline1AgingEntry
	MAX-ACCESS not-accessible
	STATUS current
	DESCRIPTION
        "
        List of pmc2002Mesrline1Aging
         Article
        "
	::= { pmc2002MesrLine 224 }


pmc2002Mesrline1AgingEntry OBJECT-TYPE
	SYNTAX Pmc2002Mesrline1AgingEntry
	MAX-ACCESS not-accessible
	STATUS current
	DESCRIPTION
        "
        Row definition for the pmc2002Mesrline1Aging
        table
        "
	INDEX   { pmc2002Mesrline1AgingIndex }
	::= { pmc2002Mesrline1AgingTable 1 }


Pmc2002Mesrline1AgingEntry ::=
	SEQUENCE {
	pmc2002Mesrline1AgingIndex
		INTEGER,
	pmc2002Mesrline1AgingPortn
		INTEGER
	}


pmc2002Mesrline1AgingIndex OBJECT-TYPE
	SYNTAX  INTEGER(0..128)
	MAX-ACCESS  read-only
	STATUS current
	DESCRIPTION
        "
        Index definition for the pmc2002Mesrline1Aging
        table
        "
	::= { pmc2002Mesrline1AgingEntry 1 }


pmc2002Mesrline1AgingPortn OBJECT-TYPE
	SYNTAX  INTEGER (0..65535)
	MAX-ACCESS read-only
	STATUS current
	DESCRIPTION
        "
        OTX TLH Aging :This OID gives
         the aging of the Line OTX TLH,
        read from the DDM (Digital Diagnostic
        Monitoring)  (Aging = AV)  (Unit
        = %)  <Help>  This measure gives
        the aging of the Line OTX TLH
        "
	::= { pmc2002Mesrline1AgingEntry 2 }


--- *********************************************************
---     TABLE for the pmc2002Mesrline1LaserTemperature articles
--- *********************************************************

pmc2002Mesrline1LaserTemperatureTable OBJECT-TYPE
	SYNTAX  SEQUENCE OF Pmc2002Mesrline1LaserTemperatureEntry
	MAX-ACCESS not-accessible
	STATUS deprecated
	DESCRIPTION
        "
        List of pmc2002Mesrline1LaserTemperature
        Article
        "
	::= { pmc2002MesrLine 225 }


pmc2002Mesrline1LaserTemperatureEntry OBJECT-TYPE
	SYNTAX Pmc2002Mesrline1LaserTemperatureEntry
	MAX-ACCESS not-accessible
	STATUS deprecated
	DESCRIPTION
        "
        Row definition for the pmc2002Mesrline1LaserTemperature
        table
        "
	INDEX   { pmc2002Mesrline1LaserTemperatureIndex }
	::= { pmc2002Mesrline1LaserTemperatureTable 1 }


Pmc2002Mesrline1LaserTemperatureEntry ::=
	SEQUENCE {
	pmc2002Mesrline1LaserTemperatureIndex
		INTEGER,
	pmc2002Mesrline1LaserTemperaturePortn
		INTEGER
	}


pmc2002Mesrline1LaserTemperatureIndex OBJECT-TYPE
	SYNTAX  INTEGER(0..128)
	MAX-ACCESS  read-only
	STATUS deprecated
	DESCRIPTION
        "
        Index definition for the pmc2002Mesrline1LaserTemperature
        table
        "
	::= { pmc2002Mesrline1LaserTemperatureEntry 1 }


pmc2002Mesrline1LaserTemperaturePortn OBJECT-TYPE
	SYNTAX  INTEGER (0..65535)
	MAX-ACCESS read-only
	STATUS deprecated
	DESCRIPTION
        "
        OTX TLH Laser Temperature :This
        OID gives the laser temperature
        of the Line OTX TLH, read from
         the DDM (Digital Diagnostic Monitoring)
        (Temperature = AV/256) (Unit =
         C)  <Help>  This measure gives
        the laser temperature of the Line
        OTX TLH
        "
	::= { pmc2002Mesrline1LaserTemperatureEntry 2 }


--- *********************************************************
---     TABLE for the pmc2002Mesrline1FreqDeviation articles
--- *********************************************************

pmc2002Mesrline1FreqDeviationTable OBJECT-TYPE
	SYNTAX  SEQUENCE OF Pmc2002Mesrline1FreqDeviationEntry
	MAX-ACCESS not-accessible
	STATUS current
	DESCRIPTION
        "
        List of pmc2002Mesrline1FreqDeviation
        Article
        "
	::= { pmc2002MesrLine 226 }


pmc2002Mesrline1FreqDeviationEntry OBJECT-TYPE
	SYNTAX Pmc2002Mesrline1FreqDeviationEntry
	MAX-ACCESS not-accessible
	STATUS current
	DESCRIPTION
        "
        Row definition for the pmc2002Mesrline1FreqDeviation
        table
        "
	INDEX   { pmc2002Mesrline1FreqDeviationIndex }
	::= { pmc2002Mesrline1FreqDeviationTable 1 }


Pmc2002Mesrline1FreqDeviationEntry ::=
	SEQUENCE {
	pmc2002Mesrline1FreqDeviationIndex
		INTEGER,
	pmc2002Mesrline1FreqDeviationPortn
		INTEGER
	}


pmc2002Mesrline1FreqDeviationIndex OBJECT-TYPE
	SYNTAX  INTEGER(0..128)
	MAX-ACCESS  read-only
	STATUS current
	DESCRIPTION
        "
        Index definition for the pmc2002Mesrline1FreqDeviation
        table
        "
	::= { pmc2002Mesrline1FreqDeviationEntry 1 }


pmc2002Mesrline1FreqDeviationPortn OBJECT-TYPE
	SYNTAX  INTEGER (0..65535)
	MAX-ACCESS read-only
	STATUS current
	DESCRIPTION
        "
        OTX TLH Frequency Deviation :This
        OID gives the frequency deviation
        of the Line OTX TLH, read from
         the DDM (Digital Diagnostic Monitoring)
         (Deviation = (AV-32768)*100)
         (Unit = MHz)  <Help>  This measure
        gives the frequency deviation of
        the Line OTX TLH
        "
	::= { pmc2002Mesrline1FreqDeviationEntry 2 }


--- *********************************************************
---     TABLE for the pmc2002Mesrline1LaserWvlength articles
--- *********************************************************

pmc2002Mesrline1LaserWvlengthTable OBJECT-TYPE
	SYNTAX  SEQUENCE OF Pmc2002Mesrline1LaserWvlengthEntry
	MAX-ACCESS not-accessible
	STATUS current
	DESCRIPTION
        "
        List of pmc2002Mesrline1LaserWvlength
        Article
        "
	::= { pmc2002MesrLine 227 }


pmc2002Mesrline1LaserWvlengthEntry OBJECT-TYPE
	SYNTAX Pmc2002Mesrline1LaserWvlengthEntry
	MAX-ACCESS not-accessible
	STATUS current
	DESCRIPTION
        "
        Row definition for the pmc2002Mesrline1LaserWvlength
        table
        "
	INDEX   { pmc2002Mesrline1LaserWvlengthIndex }
	::= { pmc2002Mesrline1LaserWvlengthTable 1 }


Pmc2002Mesrline1LaserWvlengthEntry ::=
	SEQUENCE {
	pmc2002Mesrline1LaserWvlengthIndex
		INTEGER,
	pmc2002Mesrline1LaserWvlengthPortn
		INTEGER
	}


pmc2002Mesrline1LaserWvlengthIndex OBJECT-TYPE
	SYNTAX  INTEGER(0..128)
	MAX-ACCESS  read-only
	STATUS current
	DESCRIPTION
        "
        Index definition for the pmc2002Mesrline1LaserWvlength
        table
        "
	::= { pmc2002Mesrline1LaserWvlengthEntry 1 }


pmc2002Mesrline1LaserWvlengthPortn OBJECT-TYPE
	SYNTAX  INTEGER (0..65535)
	MAX-ACCESS read-only
	STATUS current
	DESCRIPTION
        "
        OTX TLH Laser Wavelength :This
        OID gives the laser wavelength
         of the Line OTX TLH, read from
        the DDM (Digital Diagnostic Monitoring)
        (Wavelength=299792458/((193,100+(AV-32768
        )*12,5)*10 3))  (Unit = nm)  <Help>
         This measure gives the laser wavelength
        of the Line OTX TLH
        "
	::= { pmc2002Mesrline1LaserWvlengthEntry 2 }







--- *****************************************************
--- $$$$$$$$$$$$$$$$$$$$$$$$$$$$$$$$$$$$$$$$$$$$$$$$$$$$$
---     PERFORMANCE
--- $$$$$$$$$$$$$$$$$$$$$$$$$$$$$$$$$$$$$$$$$$$$$$$$$$$$$
--- *****************************************************



--- *****************************************************
---     Leaf of the telecomClientCurrent15Stat
--- *****************************************************
--- *********************************************************
---     TABLE for the pmc2002PerfTelecomClientCurrent15Stat articles
--- *********************************************************

pmc2002PerfTelecomClientCurrent15StatTable OBJECT-TYPE
	SYNTAX  SEQUENCE OF Pmc2002PerfTelecomClientCurrent15StatEntry
	MAX-ACCESS not-accessible
	STATUS current
	DESCRIPTION
        "
        List of pmc2002PerfTelecomClientCurrent15Stat
        Article
        "
	::= { pmc2002MonClient 16 }


pmc2002PerfTelecomClientCurrent15StatEntry OBJECT-TYPE
	SYNTAX Pmc2002PerfTelecomClientCurrent15StatEntry
	MAX-ACCESS not-accessible
	STATUS current
	DESCRIPTION
        "
        Row definition for the pmc2002PerfTelecomClientCurrent15Stat
        table
        "
	INDEX   { pmc2002PerfTelecomClientCurrent15StatIndex }
	::= { pmc2002PerfTelecomClientCurrent15StatTable 1 }


Pmc2002PerfTelecomClientCurrent15StatEntry ::=
	SEQUENCE {
	pmc2002PerfTelecomClientCurrent15StatIndex
		INTEGER,
	pmc2002PerfTelecomClientCurrent15StatInvCvPortn
		EkiOnOff,
	pmc2002PerfTelecomClientCurrent15StatCvValuePortn
		Unsigned32,
	pmc2002PerfTelecomClientCurrent15StatInvEsPortn
		EkiOnOff,
	pmc2002PerfTelecomClientCurrent15StatEsValuePortn
		Unsigned32,
	pmc2002PerfTelecomClientCurrent15StatInvSesPortn
		EkiOnOff,
	pmc2002PerfTelecomClientCurrent15StatSesValuePortn
		Unsigned32,
	pmc2002PerfTelecomClientCurrent15StatInvSefsPortn
		EkiOnOff,
	pmc2002PerfTelecomClientCurrent15StatSefsValuePortn
		Unsigned32,
	pmc2002PerfTelecomClientCurrent15StatInvUasPortn
		EkiOnOff,
	pmc2002PerfTelecomClientCurrent15StatUasValuePortn
		Unsigned32
	}


pmc2002PerfTelecomClientCurrent15StatIndex OBJECT-TYPE
	SYNTAX  INTEGER(0..128)
	MAX-ACCESS  read-only
	STATUS current
	DESCRIPTION
        "
        Index definition for the pmc2002PerfTelecomClientCurrent15Stat
        table
        "
	::= { pmc2002PerfTelecomClientCurrent15StatEntry 1 }


pmc2002PerfTelecomClientCurrent15StatInvCvPortn OBJECT-TYPE
	SYNTAX  EkiOnOff
	MAX-ACCESS read-only
	STATUS current
	DESCRIPTION
        "
        Current 15-min CV counter inv.
        :This OID indicates that the current
        15-min Coding Violation counter
        is invalid
        "
	::= { pmc2002PerfTelecomClientCurrent15StatEntry 2 }


pmc2002PerfTelecomClientCurrent15StatCvValuePortn OBJECT-TYPE
	SYNTAX  Unsigned32
	MAX-ACCESS read-only
	STATUS current
	DESCRIPTION
        "
        Current 15-min CV counter :This
        OID gives the current 15-min Coding
        Violation counter value
        "
	::= { pmc2002PerfTelecomClientCurrent15StatEntry 3 }


pmc2002PerfTelecomClientCurrent15StatInvEsPortn OBJECT-TYPE
	SYNTAX  EkiOnOff
	MAX-ACCESS read-only
	STATUS current
	DESCRIPTION
        "
        Current 15-min ES counter inv.
        :This OID indicates that the current
        15-min Errored Second counter is
        invalid
        "
	::= { pmc2002PerfTelecomClientCurrent15StatEntry 4 }


pmc2002PerfTelecomClientCurrent15StatEsValuePortn OBJECT-TYPE
	SYNTAX  Unsigned32
	MAX-ACCESS read-only
	STATUS current
	DESCRIPTION
        "
        Current 15-min ES counter :This
        OID gives the current 15-min Errored
        Second counter value
        "
	::= { pmc2002PerfTelecomClientCurrent15StatEntry 5 }


pmc2002PerfTelecomClientCurrent15StatInvSesPortn OBJECT-TYPE
	SYNTAX  EkiOnOff
	MAX-ACCESS read-only
	STATUS current
	DESCRIPTION
        "
        Current 15-min SES counter inv.
        :This OID indicates that the current
        15-min severely Errored Second
         counter is invalid
        "
	::= { pmc2002PerfTelecomClientCurrent15StatEntry 6 }


pmc2002PerfTelecomClientCurrent15StatSesValuePortn OBJECT-TYPE
	SYNTAX  Unsigned32
	MAX-ACCESS read-only
	STATUS current
	DESCRIPTION
        "
        Current 15-min SES counter :This
        OID gives the current 15-min severely
        Errored Second counter value
        "
	::= { pmc2002PerfTelecomClientCurrent15StatEntry 7 }


pmc2002PerfTelecomClientCurrent15StatInvSefsPortn OBJECT-TYPE
	SYNTAX  EkiOnOff
	MAX-ACCESS read-only
	STATUS current
	DESCRIPTION
        "
        Current 15-min SEFS counter inv.
        :This OID indicates that the current
        15-min severely Errored Framing
        Second counter is invalid
        "
	::= { pmc2002PerfTelecomClientCurrent15StatEntry 8 }


pmc2002PerfTelecomClientCurrent15StatSefsValuePortn OBJECT-TYPE
	SYNTAX  Unsigned32
	MAX-ACCESS read-only
	STATUS current
	DESCRIPTION
        "
        Current 15-min SEFS counter :This
        OID gives the current 15-min severely
        Errored Framing Second counter
         value
        "
	::= { pmc2002PerfTelecomClientCurrent15StatEntry 9 }


pmc2002PerfTelecomClientCurrent15StatInvUasPortn OBJECT-TYPE
	SYNTAX  EkiOnOff
	MAX-ACCESS read-only
	STATUS current
	DESCRIPTION
        "
        Current 15-min UAS counter inv.
        :This OID indicates that the current
        15-min UnAvailable Second counter
        is invalid
        "
	::= { pmc2002PerfTelecomClientCurrent15StatEntry 10 }


pmc2002PerfTelecomClientCurrent15StatUasValuePortn OBJECT-TYPE
	SYNTAX  Unsigned32
	MAX-ACCESS read-only
	STATUS current
	DESCRIPTION
        "
        Current 15-min UAS counter :This
        OID gives the current 15-min UnAvailable
        Second counter value
        "
	::= { pmc2002PerfTelecomClientCurrent15StatEntry 11 }


--- *****************************************************
---     Leaf of the telecomClientPast15Stat
--- *****************************************************
--- *********************************************************
---     TABLE for the pmc2002PerfTelecomClientPast15StatHistory articles
--- *********************************************************

pmc2002PerfTelecomClientPast15StatHistoryPort1Table OBJECT-TYPE
	SYNTAX  SEQUENCE OF Pmc2002PerfTelecomClientPast15StatHistoryPort1Entry
	MAX-ACCESS not-accessible
	STATUS current
	DESCRIPTION
        "
        List of pmc2002PerfTelecomClientPast15StatHistory
        Article
        "
	::= { pmc2002MonClient 24 }


pmc2002PerfTelecomClientPast15StatHistoryPort1Entry OBJECT-TYPE
	SYNTAX Pmc2002PerfTelecomClientPast15StatHistoryPort1Entry
	MAX-ACCESS not-accessible
	STATUS current
	DESCRIPTION
        "
        Row definition for the pmc2002PerfTelecomClientPast15StatHistory
        table
        "
	INDEX   { pmc2002PerfTelecomClientPast15StatHistoryPort1Index }
	::= { pmc2002PerfTelecomClientPast15StatHistoryPort1Table 1 }


Pmc2002PerfTelecomClientPast15StatHistoryPort1Entry ::=
	SEQUENCE {
	pmc2002PerfTelecomClientPast15StatHistoryPort1Index
		INTEGER,
	pmc2002PerfTelecomClientPast15StatHistoryInvCvPort1
		EkiOnOff,
	pmc2002PerfTelecomClientPast15StatHistoryCvValuePort1
		Unsigned32,
	pmc2002PerfTelecomClientPast15StatHistoryInvEsPort1
		EkiOnOff,
	pmc2002PerfTelecomClientPast15StatHistoryEsValuePort1
		Unsigned32,
	pmc2002PerfTelecomClientPast15StatHistoryInvSesPort1
		EkiOnOff,
	pmc2002PerfTelecomClientPast15StatHistorySesValuePort1
		Unsigned32,
	pmc2002PerfTelecomClientPast15StatHistoryInvSefsPort1
		EkiOnOff,
	pmc2002PerfTelecomClientPast15StatHistorySefsValuePort1
		Unsigned32,
	pmc2002PerfTelecomClientPast15StatHistoryInvUasPort1
		EkiOnOff,
	pmc2002PerfTelecomClientPast15StatHistoryUasValuePort1
		Unsigned32
	}


pmc2002PerfTelecomClientPast15StatHistoryPort1Index OBJECT-TYPE
	SYNTAX  INTEGER(0..128)
	MAX-ACCESS  read-only
	STATUS current
	DESCRIPTION
        "
        Index definition for the pmc2002PerfTelecomClientPast15StatHistory
        table
        "
	::= { pmc2002PerfTelecomClientPast15StatHistoryPort1Entry 1 }


pmc2002PerfTelecomClientPast15StatHistoryInvCvPort1 OBJECT-TYPE
	SYNTAX  EkiOnOff
	MAX-ACCESS read-only
	STATUS current
	DESCRIPTION
        "
        Previous 15-min CV counter inv.
        :This OID indicates that the previous
        15-min Coding Violation counter
        is invalid
        "
	::= { pmc2002PerfTelecomClientPast15StatHistoryPort1Entry 2 }


pmc2002PerfTelecomClientPast15StatHistoryCvValuePort1 OBJECT-TYPE
	SYNTAX  Unsigned32
	MAX-ACCESS read-only
	STATUS current
	DESCRIPTION
        "
        Previous 15-min CV counter :This
        OID gives the previous 15-min Coding
        Violation counter value
        "
	::= { pmc2002PerfTelecomClientPast15StatHistoryPort1Entry 3 }


pmc2002PerfTelecomClientPast15StatHistoryInvEsPort1 OBJECT-TYPE
	SYNTAX  EkiOnOff
	MAX-ACCESS read-only
	STATUS current
	DESCRIPTION
        "
        Previous 15-min ES counter inv.
        :This OID indicates that the previous
        15-min Errored Second counter is
        invalid
        "
	::= { pmc2002PerfTelecomClientPast15StatHistoryPort1Entry 4 }


pmc2002PerfTelecomClientPast15StatHistoryEsValuePort1 OBJECT-TYPE
	SYNTAX  Unsigned32
	MAX-ACCESS read-only
	STATUS current
	DESCRIPTION
        "
        Previous 15-min ES counter :This
        OID gives the previous 15-min Errored
        Second counter value
        "
	::= { pmc2002PerfTelecomClientPast15StatHistoryPort1Entry 5 }


pmc2002PerfTelecomClientPast15StatHistoryInvSesPort1 OBJECT-TYPE
	SYNTAX  EkiOnOff
	MAX-ACCESS read-only
	STATUS current
	DESCRIPTION
        "
        Previous 15-min SES counter inv.
        :This OID indicates that the previous
        15-min severely Errored Second
         counter is invalid
        "
	::= { pmc2002PerfTelecomClientPast15StatHistoryPort1Entry 6 }


pmc2002PerfTelecomClientPast15StatHistorySesValuePort1 OBJECT-TYPE
	SYNTAX  Unsigned32
	MAX-ACCESS read-only
	STATUS current
	DESCRIPTION
        "
        Previous 15-min SES counter :This
        OID gives the previous 15-min severely
        Errored Second counter value
        "
	::= { pmc2002PerfTelecomClientPast15StatHistoryPort1Entry 7 }


pmc2002PerfTelecomClientPast15StatHistoryInvSefsPort1 OBJECT-TYPE
	SYNTAX  EkiOnOff
	MAX-ACCESS read-only
	STATUS current
	DESCRIPTION
        "
        Previous 15-min SEFS counter inv.
        :This OID indicates that the previous
        15-min severely Errored Framing
        Second counter is invalid
        "
	::= { pmc2002PerfTelecomClientPast15StatHistoryPort1Entry 8 }


pmc2002PerfTelecomClientPast15StatHistorySefsValuePort1 OBJECT-TYPE
	SYNTAX  Unsigned32
	MAX-ACCESS read-only
	STATUS current
	DESCRIPTION
        "
        Previous 15-min SEFS counter :This
        OID gives the previous 15-min severely
        Errored Framing Second counter
         value
        "
	::= { pmc2002PerfTelecomClientPast15StatHistoryPort1Entry 9 }


pmc2002PerfTelecomClientPast15StatHistoryInvUasPort1 OBJECT-TYPE
	SYNTAX  EkiOnOff
	MAX-ACCESS read-only
	STATUS current
	DESCRIPTION
        "
        Previous 15-min UAS counter inv.
        :This OID indicates that the previous
        15-min UnAvailable Second counter
        is invalid
        "
	::= { pmc2002PerfTelecomClientPast15StatHistoryPort1Entry 10 }


pmc2002PerfTelecomClientPast15StatHistoryUasValuePort1 OBJECT-TYPE
	SYNTAX  Unsigned32
	MAX-ACCESS read-only
	STATUS current
	DESCRIPTION
        "
        Previous 15-min UAS counter :This
        OID gives the previous 15-min UnAvailable
        Second counter value
        "
	::= { pmc2002PerfTelecomClientPast15StatHistoryPort1Entry 11 }


--- *****************************************************
---     Leaf of the telecomClientCurrent24Stat
--- *****************************************************
--- *********************************************************
---     TABLE for the pmc2002PerfTelecomClientCurrent24Stat articles
--- *********************************************************

pmc2002PerfTelecomClientCurrent24StatTable OBJECT-TYPE
	SYNTAX  SEQUENCE OF Pmc2002PerfTelecomClientCurrent24StatEntry
	MAX-ACCESS not-accessible
	STATUS current
	DESCRIPTION
        "
        List of pmc2002PerfTelecomClientCurrent24Stat
        Article
        "
	::= { pmc2002MonClient 32 }


pmc2002PerfTelecomClientCurrent24StatEntry OBJECT-TYPE
	SYNTAX Pmc2002PerfTelecomClientCurrent24StatEntry
	MAX-ACCESS not-accessible
	STATUS current
	DESCRIPTION
        "
        Row definition for the pmc2002PerfTelecomClientCurrent24Stat
        table
        "
	INDEX   { pmc2002PerfTelecomClientCurrent24StatIndex }
	::= { pmc2002PerfTelecomClientCurrent24StatTable 1 }


Pmc2002PerfTelecomClientCurrent24StatEntry ::=
	SEQUENCE {
	pmc2002PerfTelecomClientCurrent24StatIndex
		INTEGER,
	pmc2002PerfTelecomClientCurrent24StatInvCvPortn
		EkiOnOff,
	pmc2002PerfTelecomClientCurrent24StatCvValuePortn
		Unsigned32,
	pmc2002PerfTelecomClientCurrent24StatInvEsPortn
		EkiOnOff,
	pmc2002PerfTelecomClientCurrent24StatEsValuePortn
		Unsigned32,
	pmc2002PerfTelecomClientCurrent24StatInvSesPortn
		EkiOnOff,
	pmc2002PerfTelecomClientCurrent24StatSesValuePortn
		Unsigned32,
	pmc2002PerfTelecomClientCurrent24StatInvSefsPortn
		EkiOnOff,
	pmc2002PerfTelecomClientCurrent24StatSefsValuePortn
		Unsigned32,
	pmc2002PerfTelecomClientCurrent24StatInvUasPortn
		EkiOnOff,
	pmc2002PerfTelecomClientCurrent24StatUasValuePortn
		Unsigned32
	}


pmc2002PerfTelecomClientCurrent24StatIndex OBJECT-TYPE
	SYNTAX  INTEGER(0..128)
	MAX-ACCESS  read-only
	STATUS current
	DESCRIPTION
        "
        Index definition for the pmc2002PerfTelecomClientCurrent24Stat
        table
        "
	::= { pmc2002PerfTelecomClientCurrent24StatEntry 1 }


pmc2002PerfTelecomClientCurrent24StatInvCvPortn OBJECT-TYPE
	SYNTAX  EkiOnOff
	MAX-ACCESS read-only
	STATUS current
	DESCRIPTION
        "
        Current 24-hours CV counter inv.
        :This OID indicates that the current
        24-hours Coding Violation counter
        is invalid
        "
	::= { pmc2002PerfTelecomClientCurrent24StatEntry 2 }


pmc2002PerfTelecomClientCurrent24StatCvValuePortn OBJECT-TYPE
	SYNTAX  Unsigned32
	MAX-ACCESS read-only
	STATUS current
	DESCRIPTION
        "
        Current 24-hours CV counter :This
        OID gives the current 24-hours
         Coding Violation counter value
        "
	::= { pmc2002PerfTelecomClientCurrent24StatEntry 3 }


pmc2002PerfTelecomClientCurrent24StatInvEsPortn OBJECT-TYPE
	SYNTAX  EkiOnOff
	MAX-ACCESS read-only
	STATUS current
	DESCRIPTION
        "
        Current 24-hours ES counter inv.
        :This OID indicates that the current
        24-hours Errored Second counter
        is invalid
        "
	::= { pmc2002PerfTelecomClientCurrent24StatEntry 4 }


pmc2002PerfTelecomClientCurrent24StatEsValuePortn OBJECT-TYPE
	SYNTAX  Unsigned32
	MAX-ACCESS read-only
	STATUS current
	DESCRIPTION
        "
        Current 24-hours ES counter :This
        OID gives the current 24-hours
         Errored Second counter value
        "
	::= { pmc2002PerfTelecomClientCurrent24StatEntry 5 }


pmc2002PerfTelecomClientCurrent24StatInvSesPortn OBJECT-TYPE
	SYNTAX  EkiOnOff
	MAX-ACCESS read-only
	STATUS current
	DESCRIPTION
        "
        Current 24-hours SES counter inv.
        :This OID indicates that the current
        24-hours severely Errored Second
        counter is invalid
        "
	::= { pmc2002PerfTelecomClientCurrent24StatEntry 6 }


pmc2002PerfTelecomClientCurrent24StatSesValuePortn OBJECT-TYPE
	SYNTAX  Unsigned32
	MAX-ACCESS read-only
	STATUS current
	DESCRIPTION
        "
        Current 24-hours SES counter :This
        OID gives the current 24-hours
         severely Errored Second counter
        value
        "
	::= { pmc2002PerfTelecomClientCurrent24StatEntry 7 }


pmc2002PerfTelecomClientCurrent24StatInvSefsPortn OBJECT-TYPE
	SYNTAX  EkiOnOff
	MAX-ACCESS read-only
	STATUS current
	DESCRIPTION
        "
        Current 24-hours SEFS counter
         inv. :This OID indicates that
         the current 24-hours severely
         Errored Framing Second counter
        is invalid
        "
	::= { pmc2002PerfTelecomClientCurrent24StatEntry 8 }


pmc2002PerfTelecomClientCurrent24StatSefsValuePortn OBJECT-TYPE
	SYNTAX  Unsigned32
	MAX-ACCESS read-only
	STATUS current
	DESCRIPTION
        "
        Current 24-hours SEFS counter
         :This OID gives the current 24-hours
        severely Errored Framing Second
        counter value
        "
	::= { pmc2002PerfTelecomClientCurrent24StatEntry 9 }


pmc2002PerfTelecomClientCurrent24StatInvUasPortn OBJECT-TYPE
	SYNTAX  EkiOnOff
	MAX-ACCESS read-only
	STATUS current
	DESCRIPTION
        "
        Current 24-hours UAS counter inv.
        :This OID indicates that the current
        24-hours UnAvailable Second counter
        is invalid
        "
	::= { pmc2002PerfTelecomClientCurrent24StatEntry 10 }


pmc2002PerfTelecomClientCurrent24StatUasValuePortn OBJECT-TYPE
	SYNTAX  Unsigned32
	MAX-ACCESS read-only
	STATUS current
	DESCRIPTION
        "
        Current 24-hours UAS counter :This
        OID gives the current 24-hours
         UnAvailable Second counter value
        "
	::= { pmc2002PerfTelecomClientCurrent24StatEntry 11 }


--- *****************************************************
---     Leaf of the telecomClientPast24Stat
--- *****************************************************
--- *********************************************************
---     TABLE for the pmc2002PerfTelecomClientPast24StatHistory articles
--- *********************************************************

pmc2002PerfTelecomClientPast24StatHistoryPort1Table OBJECT-TYPE
	SYNTAX  SEQUENCE OF Pmc2002PerfTelecomClientPast24StatHistoryPort1Entry
	MAX-ACCESS not-accessible
	STATUS current
	DESCRIPTION
        "
        List of pmc2002PerfTelecomClientPast24StatHistory
        Article
        "
	::= { pmc2002MonClient 40 }


pmc2002PerfTelecomClientPast24StatHistoryPort1Entry OBJECT-TYPE
	SYNTAX Pmc2002PerfTelecomClientPast24StatHistoryPort1Entry
	MAX-ACCESS not-accessible
	STATUS current
	DESCRIPTION
        "
        Row definition for the pmc2002PerfTelecomClientPast24StatHistory
        table
        "
	INDEX   { pmc2002PerfTelecomClientPast24StatHistoryPort1Index }
	::= { pmc2002PerfTelecomClientPast24StatHistoryPort1Table 1 }


Pmc2002PerfTelecomClientPast24StatHistoryPort1Entry ::=
	SEQUENCE {
	pmc2002PerfTelecomClientPast24StatHistoryPort1Index
		INTEGER,
	pmc2002PerfTelecomClientPast24StatHistoryInvCvPort1
		EkiOnOff,
	pmc2002PerfTelecomClientPast24StatHistoryCvValuePort1
		Unsigned32,
	pmc2002PerfTelecomClientPast24StatHistoryInvEsPort1
		EkiOnOff,
	pmc2002PerfTelecomClientPast24StatHistoryEsValuePort1
		Unsigned32,
	pmc2002PerfTelecomClientPast24StatHistoryInvSesPort1
		EkiOnOff,
	pmc2002PerfTelecomClientPast24StatHistorySesValuePort1
		Unsigned32,
	pmc2002PerfTelecomClientPast24StatHistoryInvSefsPort1
		EkiOnOff,
	pmc2002PerfTelecomClientPast24StatHistorySefsValuePort1
		Unsigned32,
	pmc2002PerfTelecomClientPast24StatHistoryInvUasPort1
		EkiOnOff,
	pmc2002PerfTelecomClientPast24StatHistoryUasValuePort1
		Unsigned32
	}


pmc2002PerfTelecomClientPast24StatHistoryPort1Index OBJECT-TYPE
	SYNTAX  INTEGER(0..128)
	MAX-ACCESS  read-only
	STATUS current
	DESCRIPTION
        "
        Index definition for the pmc2002PerfTelecomClientPast24StatHistory
        table
        "
	::= { pmc2002PerfTelecomClientPast24StatHistoryPort1Entry 1 }


pmc2002PerfTelecomClientPast24StatHistoryInvCvPort1 OBJECT-TYPE
	SYNTAX  EkiOnOff
	MAX-ACCESS read-only
	STATUS current
	DESCRIPTION
        "
        Previous 24-hours CV counter inv.
        :This OID indicates that the previous
        24-hours Coding Violation counter
        is invalid
        "
	::= { pmc2002PerfTelecomClientPast24StatHistoryPort1Entry 2 }


pmc2002PerfTelecomClientPast24StatHistoryCvValuePort1 OBJECT-TYPE
	SYNTAX  Unsigned32
	MAX-ACCESS read-only
	STATUS current
	DESCRIPTION
        "
        Previous 24-hours CV counter :This
        OID gives the previous 24-hours
        Coding Violation counter value
        "
	::= { pmc2002PerfTelecomClientPast24StatHistoryPort1Entry 3 }


pmc2002PerfTelecomClientPast24StatHistoryInvEsPort1 OBJECT-TYPE
	SYNTAX  EkiOnOff
	MAX-ACCESS read-only
	STATUS current
	DESCRIPTION
        "
        Previous 24-hours ES counter inv.
        :This OID indicates that the previous
        24-hours Errored Second counter
        is invalid
        "
	::= { pmc2002PerfTelecomClientPast24StatHistoryPort1Entry 4 }


pmc2002PerfTelecomClientPast24StatHistoryEsValuePort1 OBJECT-TYPE
	SYNTAX  Unsigned32
	MAX-ACCESS read-only
	STATUS current
	DESCRIPTION
        "
        Previous 24-hours ES counter :This
        OID gives the previous 24-hours
        Errored Second counter value
        "
	::= { pmc2002PerfTelecomClientPast24StatHistoryPort1Entry 5 }


pmc2002PerfTelecomClientPast24StatHistoryInvSesPort1 OBJECT-TYPE
	SYNTAX  EkiOnOff
	MAX-ACCESS read-only
	STATUS current
	DESCRIPTION
        "
        Previous 24-hours SES counter
         inv. :This OID indicates that
         the previous 24-hours severely
        Errored Second counter is invalid
        "
	::= { pmc2002PerfTelecomClientPast24StatHistoryPort1Entry 6 }


pmc2002PerfTelecomClientPast24StatHistorySesValuePort1 OBJECT-TYPE
	SYNTAX  Unsigned32
	MAX-ACCESS read-only
	STATUS current
	DESCRIPTION
        "
        Previous 24-hours SES counter
         :This OID gives the previous 24-hours
        severely Errored Second counter
        value
        "
	::= { pmc2002PerfTelecomClientPast24StatHistoryPort1Entry 7 }


pmc2002PerfTelecomClientPast24StatHistoryInvSefsPort1 OBJECT-TYPE
	SYNTAX  EkiOnOff
	MAX-ACCESS read-only
	STATUS current
	DESCRIPTION
        "
        Previous 24-hours SEFS counter
        inv. :This OID indicates that the
        previous 24-hours severely Errored
        Framing Second counter is invalid
        "
	::= { pmc2002PerfTelecomClientPast24StatHistoryPort1Entry 8 }


pmc2002PerfTelecomClientPast24StatHistorySefsValuePort1 OBJECT-TYPE
	SYNTAX  Unsigned32
	MAX-ACCESS read-only
	STATUS current
	DESCRIPTION
        "
        Previous 24-hours SEFS counter
        :This OID gives the previous 24-hours
        severely Errored Framing Second
        counter value
        "
	::= { pmc2002PerfTelecomClientPast24StatHistoryPort1Entry 9 }


pmc2002PerfTelecomClientPast24StatHistoryInvUasPort1 OBJECT-TYPE
	SYNTAX  EkiOnOff
	MAX-ACCESS read-only
	STATUS current
	DESCRIPTION
        "
        Previous 24-hours UAS counter
         inv. :This OID indicates that
         the previous 24-hours UnAvailable
        Second counter is invalid
        "
	::= { pmc2002PerfTelecomClientPast24StatHistoryPort1Entry 10 }


pmc2002PerfTelecomClientPast24StatHistoryUasValuePort1 OBJECT-TYPE
	SYNTAX  Unsigned32
	MAX-ACCESS read-only
	STATUS current
	DESCRIPTION
        "
        Previous 24-hours UAS counter
         :This OID gives the previous 24-hours
        UnAvailable Second counter value
        "
	::= { pmc2002PerfTelecomClientPast24StatHistoryPort1Entry 11 }


--- *****************************************************
---     Leaf of the telecomLineCurrent15Stat
--- *****************************************************
--- *********************************************************
---     TABLE for the pmc2002PerfTelecomLineCurrent15Stat articles
--- *********************************************************

pmc2002PerfTelecomLineCurrent15StatTable OBJECT-TYPE
	SYNTAX  SEQUENCE OF Pmc2002PerfTelecomLineCurrent15StatEntry
	MAX-ACCESS not-accessible
	STATUS current
	DESCRIPTION
        "
        List of pmc2002PerfTelecomLineCurrent15Stat
        Article
        "
	::= { pmc2002MonLine 128 }


pmc2002PerfTelecomLineCurrent15StatEntry OBJECT-TYPE
	SYNTAX Pmc2002PerfTelecomLineCurrent15StatEntry
	MAX-ACCESS not-accessible
	STATUS current
	DESCRIPTION
        "
        Row definition for the pmc2002PerfTelecomLineCurrent15Stat
        table
        "
	INDEX   { pmc2002PerfTelecomLineCurrent15StatIndex }
	::= { pmc2002PerfTelecomLineCurrent15StatTable 1 }


Pmc2002PerfTelecomLineCurrent15StatEntry ::=
	SEQUENCE {
	pmc2002PerfTelecomLineCurrent15StatIndex
		INTEGER,
	pmc2002PerfTelecomLineCurrent15StatInvCvPortn
		EkiOnOff,
	pmc2002PerfTelecomLineCurrent15StatCvValuePortn
		Unsigned32,
	pmc2002PerfTelecomLineCurrent15StatInvEsPortn
		EkiOnOff,
	pmc2002PerfTelecomLineCurrent15StatEsValuePortn
		Unsigned32,
	pmc2002PerfTelecomLineCurrent15StatInvSesPortn
		EkiOnOff,
	pmc2002PerfTelecomLineCurrent15StatSesValuePortn
		Unsigned32,
	pmc2002PerfTelecomLineCurrent15StatInvSefsPortn
		EkiOnOff,
	pmc2002PerfTelecomLineCurrent15StatSefsValuePortn
		Unsigned32,
	pmc2002PerfTelecomLineCurrent15StatInvUasPortn
		EkiOnOff,
	pmc2002PerfTelecomLineCurrent15StatUasValuePortn
		Unsigned32
	}


pmc2002PerfTelecomLineCurrent15StatIndex OBJECT-TYPE
	SYNTAX  INTEGER(0..128)
	MAX-ACCESS  read-only
	STATUS current
	DESCRIPTION
        "
        Index definition for the pmc2002PerfTelecomLineCurrent15Stat
        table
        "
	::= { pmc2002PerfTelecomLineCurrent15StatEntry 1 }


pmc2002PerfTelecomLineCurrent15StatInvCvPortn OBJECT-TYPE
	SYNTAX  EkiOnOff
	MAX-ACCESS read-only
	STATUS current
	DESCRIPTION
        "
        Current 15-min CV counter inv.
        :This OID indicates that the current
        15-min Coding Violation counter
        is invalid
        "
	::= { pmc2002PerfTelecomLineCurrent15StatEntry 2 }


pmc2002PerfTelecomLineCurrent15StatCvValuePortn OBJECT-TYPE
	SYNTAX  Unsigned32
	MAX-ACCESS read-only
	STATUS current
	DESCRIPTION
        "
        Current 15-min CV counter :This
        OID gives the current 15-min Coding
        Violation counter value
        "
	::= { pmc2002PerfTelecomLineCurrent15StatEntry 3 }


pmc2002PerfTelecomLineCurrent15StatInvEsPortn OBJECT-TYPE
	SYNTAX  EkiOnOff
	MAX-ACCESS read-only
	STATUS current
	DESCRIPTION
        "
        Current 15-min ES counter inv.
        :This OID indicates that the current
        15-min Errored Second counter is
        invalid
        "
	::= { pmc2002PerfTelecomLineCurrent15StatEntry 4 }


pmc2002PerfTelecomLineCurrent15StatEsValuePortn OBJECT-TYPE
	SYNTAX  Unsigned32
	MAX-ACCESS read-only
	STATUS current
	DESCRIPTION
        "
        Current 15-min ES counter :This
        OID gives the current 15-min Errored
        Second counter value
        "
	::= { pmc2002PerfTelecomLineCurrent15StatEntry 5 }


pmc2002PerfTelecomLineCurrent15StatInvSesPortn OBJECT-TYPE
	SYNTAX  EkiOnOff
	MAX-ACCESS read-only
	STATUS current
	DESCRIPTION
        "
        Current 15-min SES counter inv.
        :This OID indicates that the current
        15-min severely Errored Second
         counter is invalid
        "
	::= { pmc2002PerfTelecomLineCurrent15StatEntry 6 }


pmc2002PerfTelecomLineCurrent15StatSesValuePortn OBJECT-TYPE
	SYNTAX  Unsigned32
	MAX-ACCESS read-only
	STATUS current
	DESCRIPTION
        "
        Current 15-min SES counter :This
        OID gives the current 15-min severely
        Errored Second counter value
        "
	::= { pmc2002PerfTelecomLineCurrent15StatEntry 7 }


pmc2002PerfTelecomLineCurrent15StatInvSefsPortn OBJECT-TYPE
	SYNTAX  EkiOnOff
	MAX-ACCESS read-only
	STATUS current
	DESCRIPTION
        "
        Current 15-min SEFS counter inv.
        :This OID indicates that the current
        15-min severely Errored Framing
        Second counter is invalid
        "
	::= { pmc2002PerfTelecomLineCurrent15StatEntry 8 }


pmc2002PerfTelecomLineCurrent15StatSefsValuePortn OBJECT-TYPE
	SYNTAX  Unsigned32
	MAX-ACCESS read-only
	STATUS current
	DESCRIPTION
        "
        Current 15-min SEFS counter :This
        OID gives the current 15-min severely
        Errored Framing Second counter
         value
        "
	::= { pmc2002PerfTelecomLineCurrent15StatEntry 9 }


pmc2002PerfTelecomLineCurrent15StatInvUasPortn OBJECT-TYPE
	SYNTAX  EkiOnOff
	MAX-ACCESS read-only
	STATUS current
	DESCRIPTION
        "
        Current 15-min UAS counter inv.
        :This OID indicates that the current
        15-min UnAvailable Second counter
        is invalid
        "
	::= { pmc2002PerfTelecomLineCurrent15StatEntry 10 }


pmc2002PerfTelecomLineCurrent15StatUasValuePortn OBJECT-TYPE
	SYNTAX  Unsigned32
	MAX-ACCESS read-only
	STATUS current
	DESCRIPTION
        "
        Current 15-min UAS counter :This
        OID gives the current 15-min UnAvailable
        Second counter value
        "
	::= { pmc2002PerfTelecomLineCurrent15StatEntry 11 }


--- *****************************************************
---     Leaf of the telecomLinePast15Stat
--- *****************************************************
--- *********************************************************
---     TABLE for the pmc2002PerfTelecomLinePast15StatHistory articles
--- *********************************************************

pmc2002PerfTelecomLinePast15StatHistoryPort1Table OBJECT-TYPE
	SYNTAX  SEQUENCE OF Pmc2002PerfTelecomLinePast15StatHistoryPort1Entry
	MAX-ACCESS not-accessible
	STATUS current
	DESCRIPTION
        "
        List of pmc2002PerfTelecomLinePast15StatHistory
        Article
        "
	::= { pmc2002MonLine 129 }


pmc2002PerfTelecomLinePast15StatHistoryPort1Entry OBJECT-TYPE
	SYNTAX Pmc2002PerfTelecomLinePast15StatHistoryPort1Entry
	MAX-ACCESS not-accessible
	STATUS current
	DESCRIPTION
        "
        Row definition for the pmc2002PerfTelecomLinePast15StatHistory
        table
        "
	INDEX   { pmc2002PerfTelecomLinePast15StatHistoryPort1Index }
	::= { pmc2002PerfTelecomLinePast15StatHistoryPort1Table 1 }


Pmc2002PerfTelecomLinePast15StatHistoryPort1Entry ::=
	SEQUENCE {
	pmc2002PerfTelecomLinePast15StatHistoryPort1Index
		INTEGER,
	pmc2002PerfTelecomLinePast15StatHistoryInvCvPort1
		EkiOnOff,
	pmc2002PerfTelecomLinePast15StatHistoryCvValuePort1
		Unsigned32,
	pmc2002PerfTelecomLinePast15StatHistoryInvEsPort1
		EkiOnOff,
	pmc2002PerfTelecomLinePast15StatHistoryEsValuePort1
		Unsigned32,
	pmc2002PerfTelecomLinePast15StatHistoryInvSesPort1
		EkiOnOff,
	pmc2002PerfTelecomLinePast15StatHistorySesValuePort1
		Unsigned32,
	pmc2002PerfTelecomLinePast15StatHistoryInvSefsPort1
		EkiOnOff,
	pmc2002PerfTelecomLinePast15StatHistorySefsValuePort1
		Unsigned32,
	pmc2002PerfTelecomLinePast15StatHistoryInvUasPort1
		EkiOnOff,
	pmc2002PerfTelecomLinePast15StatHistoryUasValuePort1
		Unsigned32
	}


pmc2002PerfTelecomLinePast15StatHistoryPort1Index OBJECT-TYPE
	SYNTAX  INTEGER(0..128)
	MAX-ACCESS  read-only
	STATUS current
	DESCRIPTION
        "
        Index definition for the pmc2002PerfTelecomLinePast15StatHistory
        table
        "
	::= { pmc2002PerfTelecomLinePast15StatHistoryPort1Entry 1 }


pmc2002PerfTelecomLinePast15StatHistoryInvCvPort1 OBJECT-TYPE
	SYNTAX  EkiOnOff
	MAX-ACCESS read-only
	STATUS current
	DESCRIPTION
        "
        Previous 15-min CV counter inv.
        :This OID indicates that the previous
        15-min Coding Violation counter
        is invalid
        "
	::= { pmc2002PerfTelecomLinePast15StatHistoryPort1Entry 2 }


pmc2002PerfTelecomLinePast15StatHistoryCvValuePort1 OBJECT-TYPE
	SYNTAX  Unsigned32
	MAX-ACCESS read-only
	STATUS current
	DESCRIPTION
        "
        Previous 15-min CV counter :This
        OID gives the previous 15-min Coding
        Violation counter value
        "
	::= { pmc2002PerfTelecomLinePast15StatHistoryPort1Entry 3 }


pmc2002PerfTelecomLinePast15StatHistoryInvEsPort1 OBJECT-TYPE
	SYNTAX  EkiOnOff
	MAX-ACCESS read-only
	STATUS current
	DESCRIPTION
        "
        Previous 15-min ES counter inv.
        :This OID indicates that the previous
        15-min Errored Second counter is
        invalid
        "
	::= { pmc2002PerfTelecomLinePast15StatHistoryPort1Entry 4 }


pmc2002PerfTelecomLinePast15StatHistoryEsValuePort1 OBJECT-TYPE
	SYNTAX  Unsigned32
	MAX-ACCESS read-only
	STATUS current
	DESCRIPTION
        "
        Previous 15-min ES counter :This
        OID gives the previous 15-min Errored
        Second counter value
        "
	::= { pmc2002PerfTelecomLinePast15StatHistoryPort1Entry 5 }


pmc2002PerfTelecomLinePast15StatHistoryInvSesPort1 OBJECT-TYPE
	SYNTAX  EkiOnOff
	MAX-ACCESS read-only
	STATUS current
	DESCRIPTION
        "
        Previous 15-min SES counter inv.
        :This OID indicates that the previous
        15-min severely Errored Second
         counter is invalid
        "
	::= { pmc2002PerfTelecomLinePast15StatHistoryPort1Entry 6 }


pmc2002PerfTelecomLinePast15StatHistorySesValuePort1 OBJECT-TYPE
	SYNTAX  Unsigned32
	MAX-ACCESS read-only
	STATUS current
	DESCRIPTION
        "
        Previous 15-min SES counter :This
        OID gives the previous 15-min severely
        Errored Second counter value
        "
	::= { pmc2002PerfTelecomLinePast15StatHistoryPort1Entry 7 }


pmc2002PerfTelecomLinePast15StatHistoryInvSefsPort1 OBJECT-TYPE
	SYNTAX  EkiOnOff
	MAX-ACCESS read-only
	STATUS current
	DESCRIPTION
        "
        Previous 15-min SEFS counter inv.
        :This OID indicates that the previous
        15-min severely Errored Framing
        Second counter is invalid
        "
	::= { pmc2002PerfTelecomLinePast15StatHistoryPort1Entry 8 }


pmc2002PerfTelecomLinePast15StatHistorySefsValuePort1 OBJECT-TYPE
	SYNTAX  Unsigned32
	MAX-ACCESS read-only
	STATUS current
	DESCRIPTION
        "
        Previous 15-min SEFS counter :This
        OID gives the previous 15-min severely
        Errored Framing Second counter
         value
        "
	::= { pmc2002PerfTelecomLinePast15StatHistoryPort1Entry 9 }


pmc2002PerfTelecomLinePast15StatHistoryInvUasPort1 OBJECT-TYPE
	SYNTAX  EkiOnOff
	MAX-ACCESS read-only
	STATUS current
	DESCRIPTION
        "
        Previous 15-min UAS counter inv.
        :This OID indicates that the previous
        15-min UnAvailable Second counter
        is invalid
        "
	::= { pmc2002PerfTelecomLinePast15StatHistoryPort1Entry 10 }


pmc2002PerfTelecomLinePast15StatHistoryUasValuePort1 OBJECT-TYPE
	SYNTAX  Unsigned32
	MAX-ACCESS read-only
	STATUS current
	DESCRIPTION
        "
        Previous 15-min UAS counter :This
        OID gives the previous 15-min UnAvailable
        Second counter value
        "
	::= { pmc2002PerfTelecomLinePast15StatHistoryPort1Entry 11 }


--- *****************************************************
---     Leaf of the telecomLineCurrent24Stat
--- *****************************************************
--- *********************************************************
---     TABLE for the pmc2002PerfTelecomLineCurrent24Stat articles
--- *********************************************************

pmc2002PerfTelecomLineCurrent24StatTable OBJECT-TYPE
	SYNTAX  SEQUENCE OF Pmc2002PerfTelecomLineCurrent24StatEntry
	MAX-ACCESS not-accessible
	STATUS current
	DESCRIPTION
        "
        List of pmc2002PerfTelecomLineCurrent24Stat
        Article
        "
	::= { pmc2002MonLine 130 }


pmc2002PerfTelecomLineCurrent24StatEntry OBJECT-TYPE
	SYNTAX Pmc2002PerfTelecomLineCurrent24StatEntry
	MAX-ACCESS not-accessible
	STATUS current
	DESCRIPTION
        "
        Row definition for the pmc2002PerfTelecomLineCurrent24Stat
        table
        "
	INDEX   { pmc2002PerfTelecomLineCurrent24StatIndex }
	::= { pmc2002PerfTelecomLineCurrent24StatTable 1 }


Pmc2002PerfTelecomLineCurrent24StatEntry ::=
	SEQUENCE {
	pmc2002PerfTelecomLineCurrent24StatIndex
		INTEGER,
	pmc2002PerfTelecomLineCurrent24StatInvCvPortn
		EkiOnOff,
	pmc2002PerfTelecomLineCurrent24StatCvValuePortn
		Unsigned32,
	pmc2002PerfTelecomLineCurrent24StatInvEsPortn
		EkiOnOff,
	pmc2002PerfTelecomLineCurrent24StatEsValuePortn
		Unsigned32,
	pmc2002PerfTelecomLineCurrent24StatInvSesPortn
		EkiOnOff,
	pmc2002PerfTelecomLineCurrent24StatSesValuePortn
		Unsigned32,
	pmc2002PerfTelecomLineCurrent24StatInvSefsPortn
		EkiOnOff,
	pmc2002PerfTelecomLineCurrent24StatSefsValuePortn
		Unsigned32,
	pmc2002PerfTelecomLineCurrent24StatInvUasPortn
		EkiOnOff,
	pmc2002PerfTelecomLineCurrent24StatUasValuePortn
		Unsigned32
	}


pmc2002PerfTelecomLineCurrent24StatIndex OBJECT-TYPE
	SYNTAX  INTEGER(0..128)
	MAX-ACCESS  read-only
	STATUS current
	DESCRIPTION
        "
        Index definition for the pmc2002PerfTelecomLineCurrent24Stat
        table
        "
	::= { pmc2002PerfTelecomLineCurrent24StatEntry 1 }


pmc2002PerfTelecomLineCurrent24StatInvCvPortn OBJECT-TYPE
	SYNTAX  EkiOnOff
	MAX-ACCESS read-only
	STATUS current
	DESCRIPTION
        "
        Current 24-hours CV counter inv.
        :This OID indicates that the current
        24-hours Coding Violation counter
        is invalid
        "
	::= { pmc2002PerfTelecomLineCurrent24StatEntry 2 }


pmc2002PerfTelecomLineCurrent24StatCvValuePortn OBJECT-TYPE
	SYNTAX  Unsigned32
	MAX-ACCESS read-only
	STATUS current
	DESCRIPTION
        "
        Current 24-hours CV counter :This
        OID gives the current 24-hours
         Coding Violation counter value
        "
	::= { pmc2002PerfTelecomLineCurrent24StatEntry 3 }


pmc2002PerfTelecomLineCurrent24StatInvEsPortn OBJECT-TYPE
	SYNTAX  EkiOnOff
	MAX-ACCESS read-only
	STATUS current
	DESCRIPTION
        "
        Current 24-hours ES counter inv.
        :This OID indicates that the current
        24-hours Errored Second counter
        is invalid
        "
	::= { pmc2002PerfTelecomLineCurrent24StatEntry 4 }


pmc2002PerfTelecomLineCurrent24StatEsValuePortn OBJECT-TYPE
	SYNTAX  Unsigned32
	MAX-ACCESS read-only
	STATUS current
	DESCRIPTION
        "
        Current 24-hours ES counter :This
        OID gives the current 24-hours
         Errored Second counter value
        "
	::= { pmc2002PerfTelecomLineCurrent24StatEntry 5 }


pmc2002PerfTelecomLineCurrent24StatInvSesPortn OBJECT-TYPE
	SYNTAX  EkiOnOff
	MAX-ACCESS read-only
	STATUS current
	DESCRIPTION
        "
        Current 24-hours SES counter inv.
        :This OID indicates that the current
        24-hours severely Errored Second
        counter is invalid
        "
	::= { pmc2002PerfTelecomLineCurrent24StatEntry 6 }


pmc2002PerfTelecomLineCurrent24StatSesValuePortn OBJECT-TYPE
	SYNTAX  Unsigned32
	MAX-ACCESS read-only
	STATUS current
	DESCRIPTION
        "
        Current 24-hours SES counter :This
        OID gives the current 24-hours
         severely Errored Second counter
        value
        "
	::= { pmc2002PerfTelecomLineCurrent24StatEntry 7 }


pmc2002PerfTelecomLineCurrent24StatInvSefsPortn OBJECT-TYPE
	SYNTAX  EkiOnOff
	MAX-ACCESS read-only
	STATUS current
	DESCRIPTION
        "
        Current 24-hours SEFS counter
         inv. :This OID indicates that
         the current 24-hours severely
         Errored Framing Second counter
        is invalid
        "
	::= { pmc2002PerfTelecomLineCurrent24StatEntry 8 }


pmc2002PerfTelecomLineCurrent24StatSefsValuePortn OBJECT-TYPE
	SYNTAX  Unsigned32
	MAX-ACCESS read-only
	STATUS current
	DESCRIPTION
        "
        Current 24-hours SEFS counter
         :This OID gives the current 24-hours
        severely Errored Framing Second
        counter value
        "
	::= { pmc2002PerfTelecomLineCurrent24StatEntry 9 }


pmc2002PerfTelecomLineCurrent24StatInvUasPortn OBJECT-TYPE
	SYNTAX  EkiOnOff
	MAX-ACCESS read-only
	STATUS current
	DESCRIPTION
        "
        Current 24-hours UAS counter inv.
        :This OID indicates that the current
        24-hours UnAvailable Second counter
        is invalid
        "
	::= { pmc2002PerfTelecomLineCurrent24StatEntry 10 }


pmc2002PerfTelecomLineCurrent24StatUasValuePortn OBJECT-TYPE
	SYNTAX  Unsigned32
	MAX-ACCESS read-only
	STATUS current
	DESCRIPTION
        "
        Current 24-hours UAS counter :This
        OID gives the current 24-hours
         UnAvailable Second counter value
        "
	::= { pmc2002PerfTelecomLineCurrent24StatEntry 11 }


--- *****************************************************
---     Leaf of the telecomLinePast24Stat
--- *****************************************************
--- *********************************************************
---     TABLE for the pmc2002PerfTelecomLinePast24StatHistory articles
--- *********************************************************

pmc2002PerfTelecomLinePast24StatHistoryPort1Table OBJECT-TYPE
	SYNTAX  SEQUENCE OF Pmc2002PerfTelecomLinePast24StatHistoryPort1Entry
	MAX-ACCESS not-accessible
	STATUS current
	DESCRIPTION
        "
        List of pmc2002PerfTelecomLinePast24StatHistory
        Article
        "
	::= { pmc2002MonLine 131 }


pmc2002PerfTelecomLinePast24StatHistoryPort1Entry OBJECT-TYPE
	SYNTAX Pmc2002PerfTelecomLinePast24StatHistoryPort1Entry
	MAX-ACCESS not-accessible
	STATUS current
	DESCRIPTION
        "
        Row definition for the pmc2002PerfTelecomLinePast24StatHistory
        table
        "
	INDEX   { pmc2002PerfTelecomLinePast24StatHistoryPort1Index }
	::= { pmc2002PerfTelecomLinePast24StatHistoryPort1Table 1 }


Pmc2002PerfTelecomLinePast24StatHistoryPort1Entry ::=
	SEQUENCE {
	pmc2002PerfTelecomLinePast24StatHistoryPort1Index
		INTEGER,
	pmc2002PerfTelecomLinePast24StatHistoryInvCvPort1
		EkiOnOff,
	pmc2002PerfTelecomLinePast24StatHistoryCvValuePort1
		Unsigned32,
	pmc2002PerfTelecomLinePast24StatHistoryInvEsPort1
		EkiOnOff,
	pmc2002PerfTelecomLinePast24StatHistoryEsValuePort1
		Unsigned32,
	pmc2002PerfTelecomLinePast24StatHistoryInvSesPort1
		EkiOnOff,
	pmc2002PerfTelecomLinePast24StatHistorySesValuePort1
		Unsigned32,
	pmc2002PerfTelecomLinePast24StatHistoryInvSefsPort1
		EkiOnOff,
	pmc2002PerfTelecomLinePast24StatHistorySefsValuePort1
		Unsigned32,
	pmc2002PerfTelecomLinePast24StatHistoryInvUasPort1
		EkiOnOff,
	pmc2002PerfTelecomLinePast24StatHistoryUasValuePort1
		Unsigned32
	}


pmc2002PerfTelecomLinePast24StatHistoryPort1Index OBJECT-TYPE
	SYNTAX  INTEGER(0..128)
	MAX-ACCESS  read-only
	STATUS current
	DESCRIPTION
        "
        Index definition for the pmc2002PerfTelecomLinePast24StatHistory
        table
        "
	::= { pmc2002PerfTelecomLinePast24StatHistoryPort1Entry 1 }


pmc2002PerfTelecomLinePast24StatHistoryInvCvPort1 OBJECT-TYPE
	SYNTAX  EkiOnOff
	MAX-ACCESS read-only
	STATUS current
	DESCRIPTION
        "
        Previous 24-hours CV counter inv.
        :This OID indicates that the previous
        24-hours Coding Violation counter
        is invalid
        "
	::= { pmc2002PerfTelecomLinePast24StatHistoryPort1Entry 2 }


pmc2002PerfTelecomLinePast24StatHistoryCvValuePort1 OBJECT-TYPE
	SYNTAX  Unsigned32
	MAX-ACCESS read-only
	STATUS current
	DESCRIPTION
        "
        Previous 24-hours CV counter :This
        OID gives the previous 24-hours
        Coding Violation counter value
        "
	::= { pmc2002PerfTelecomLinePast24StatHistoryPort1Entry 3 }


pmc2002PerfTelecomLinePast24StatHistoryInvEsPort1 OBJECT-TYPE
	SYNTAX  EkiOnOff
	MAX-ACCESS read-only
	STATUS current
	DESCRIPTION
        "
        Previous 24-hours ES counter inv.
        :This OID indicates that the previous
        24-hours Errored Second counter
        is invalid
        "
	::= { pmc2002PerfTelecomLinePast24StatHistoryPort1Entry 4 }


pmc2002PerfTelecomLinePast24StatHistoryEsValuePort1 OBJECT-TYPE
	SYNTAX  Unsigned32
	MAX-ACCESS read-only
	STATUS current
	DESCRIPTION
        "
        Previous 24-hours ES counter :This
        OID gives the previous 24-hours
        Errored Second counter value
        "
	::= { pmc2002PerfTelecomLinePast24StatHistoryPort1Entry 5 }


pmc2002PerfTelecomLinePast24StatHistoryInvSesPort1 OBJECT-TYPE
	SYNTAX  EkiOnOff
	MAX-ACCESS read-only
	STATUS current
	DESCRIPTION
        "
        Previous 24-hours SES counter
         inv. :This OID indicates that
         the previous 24-hours severely
        Errored Second counter is invalid
        "
	::= { pmc2002PerfTelecomLinePast24StatHistoryPort1Entry 6 }


pmc2002PerfTelecomLinePast24StatHistorySesValuePort1 OBJECT-TYPE
	SYNTAX  Unsigned32
	MAX-ACCESS read-only
	STATUS current
	DESCRIPTION
        "
        Previous 24-hours SES counter
         :This OID gives the previous 24-hours
        severely Errored Second counter
        value
        "
	::= { pmc2002PerfTelecomLinePast24StatHistoryPort1Entry 7 }


pmc2002PerfTelecomLinePast24StatHistoryInvSefsPort1 OBJECT-TYPE
	SYNTAX  EkiOnOff
	MAX-ACCESS read-only
	STATUS current
	DESCRIPTION
        "
        Previous 24-hours SEFS counter
        inv. :This OID indicates that the
        previous 24-hours severely Errored
        Framing Second counter is invalid
        "
	::= { pmc2002PerfTelecomLinePast24StatHistoryPort1Entry 8 }


pmc2002PerfTelecomLinePast24StatHistorySefsValuePort1 OBJECT-TYPE
	SYNTAX  Unsigned32
	MAX-ACCESS read-only
	STATUS current
	DESCRIPTION
        "
        Previous 24-hours SEFS counter
        :This OID gives the previous 24-hours
        severely Errored Framing Second
        counter value
        "
	::= { pmc2002PerfTelecomLinePast24StatHistoryPort1Entry 9 }


pmc2002PerfTelecomLinePast24StatHistoryInvUasPort1 OBJECT-TYPE
	SYNTAX  EkiOnOff
	MAX-ACCESS read-only
	STATUS current
	DESCRIPTION
        "
        Previous 24-hours UAS counter
         inv. :This OID indicates that
         the previous 24-hours UnAvailable
        Second counter is invalid
        "
	::= { pmc2002PerfTelecomLinePast24StatHistoryPort1Entry 10 }


pmc2002PerfTelecomLinePast24StatHistoryUasValuePort1 OBJECT-TYPE
	SYNTAX  Unsigned32
	MAX-ACCESS read-only
	STATUS current
	DESCRIPTION
        "
        Previous 24-hours UAS counter
         :This OID gives the previous 24-hours
        UnAvailable Second counter value
        "
	::= { pmc2002PerfTelecomLinePast24StatHistoryPort1Entry 11 }


--- *****************************************************
---     Leaf of the datacomClientCurrent15Stat
--- *****************************************************
--- *********************************************************
---     TABLE for the pmc2002PerfDatacomClientCurrent15Stat articles
--- *********************************************************

pmc2002PerfDatacomClientCurrent15StatTable OBJECT-TYPE
	SYNTAX  SEQUENCE OF Pmc2002PerfDatacomClientCurrent15StatEntry
	MAX-ACCESS not-accessible
	STATUS current
	DESCRIPTION
        "
        List of pmc2002PerfDatacomClientCurrent15Stat
        Article
        "
	::= { pmc2002MonClient 256 }


pmc2002PerfDatacomClientCurrent15StatEntry OBJECT-TYPE
	SYNTAX Pmc2002PerfDatacomClientCurrent15StatEntry
	MAX-ACCESS not-accessible
	STATUS current
	DESCRIPTION
        "
        Row definition for the pmc2002PerfDatacomClientCurrent15Stat
        table
        "
	INDEX   { pmc2002PerfDatacomClientCurrent15StatIndex }
	::= { pmc2002PerfDatacomClientCurrent15StatTable 1 }


Pmc2002PerfDatacomClientCurrent15StatEntry ::=
	SEQUENCE {
	pmc2002PerfDatacomClientCurrent15StatIndex
		INTEGER,
	pmc2002perfdatacomclientCurrent15StatOutNonunicastCountInvPortn
		EkiOnOff,
	pmc2002perfdatacomclientCurrent15StatOutNonunicastCountPortn
		Counter64,
	pmc2002perfdatacomclientCurrent15StatOutUnicastCountInvPortn
		EkiOnOff,
	pmc2002perfdatacomclientCurrent15StatOutUnicastCountPortn
		Counter64,
	pmc2002perfdatacomclientCurrent15StatOutMulticastCountInvPortn
		EkiOnOff,
	pmc2002perfdatacomclientCurrent15StatOutMulticastCountPortn
		Counter64,
	pmc2002perfdatacomclientCurrent15StatOutBroadcastCountInvPortn
		EkiOnOff,
	pmc2002perfdatacomclientCurrent15StatOutBroadcastCountPortn
		Counter64,
	pmc2002perfdatacomclientCurrent15StatOutBytesCountInvPortn
		EkiOnOff,
	pmc2002perfdatacomclientCurrent15StatOutBytesCountPortn
		Counter64,
	pmc2002perfdatacomclientCurrent15StatInNonunicastCountInvPortn
		EkiOnOff,
	pmc2002perfdatacomclientCurrent15StatInNonunicastCountPortn
		Counter64,
	pmc2002perfdatacomclientCurrent15StatInUnicastCountInvPortn
		EkiOnOff,
	pmc2002perfdatacomclientCurrent15StatInUnicastCountPortn
		Counter64,
	pmc2002perfdatacomclientCurrent15StatInMulticastCountInvPortn
		EkiOnOff,
	pmc2002perfdatacomclientCurrent15StatInMulticastCountPortn
		Counter64,
	pmc2002perfdatacomclientCurrent15StatInBroadcastCountInvPortn
		EkiOnOff,
	pmc2002perfdatacomclientCurrent15StatInBroadcastCountPortn
		Counter64,
	pmc2002perfdatacomclientCurrent15StatInCrcCountInvPortn
		EkiOnOff,
	pmc2002perfdatacomclientCurrent15StatInCrcCountPortn
		Counter64,
	pmc2002perfdatacomclientCurrent15StatInBytesCountInvPortn
		EkiOnOff,
	pmc2002perfdatacomclientCurrent15StatInBytesCountPortn
		Counter64
	}


pmc2002PerfDatacomClientCurrent15StatIndex OBJECT-TYPE
	SYNTAX  INTEGER(0..128)
	MAX-ACCESS  read-only
	STATUS current
	DESCRIPTION
        "
        Index definition for the pmc2002PerfDatacomClientCurrent15Stat
        table
        "
	::= { pmc2002PerfDatacomClientCurrent15StatEntry 1 }


pmc2002perfdatacomclientCurrent15StatOutNonunicastCountInvPortn OBJECT-TYPE
	SYNTAX  EkiOnOff
	MAX-ACCESS read-only
	STATUS current
	DESCRIPTION
        "
        Client Current 15-min Output Non
        Unicast counter inv. :This OID
         indicates that the current 15-min
        Non Unicast counter is invalid
        "
	::= { pmc2002PerfDatacomClientCurrent15StatEntry 44 }


pmc2002perfdatacomclientCurrent15StatOutNonunicastCountPortn OBJECT-TYPE
	SYNTAX  Counter64
	MAX-ACCESS read-only
	STATUS current
	DESCRIPTION
        "
        Client Current 15-min Output Non
        Unicast counter :This OID gives
        the current 15-min Non Unicast
         counter value
        "
	::= { pmc2002PerfDatacomClientCurrent15StatEntry 45 }


pmc2002perfdatacomclientCurrent15StatOutUnicastCountInvPortn OBJECT-TYPE
	SYNTAX  EkiOnOff
	MAX-ACCESS read-only
	STATUS current
	DESCRIPTION
        "
        Client Current 15-min Output Unicast
        counter inv. :This OID indicates
        that the current 15-min Unicast
        counter is invalid
        "
	::= { pmc2002PerfDatacomClientCurrent15StatEntry 42 }


pmc2002perfdatacomclientCurrent15StatOutUnicastCountPortn OBJECT-TYPE
	SYNTAX  Counter64
	MAX-ACCESS read-only
	STATUS current
	DESCRIPTION
        "
        Client Current 15-min Output Unicast
        counter :This OID gives the current
        15-min Unicast counter value
        "
	::= { pmc2002PerfDatacomClientCurrent15StatEntry 43 }


pmc2002perfdatacomclientCurrent15StatOutMulticastCountInvPortn OBJECT-TYPE
	SYNTAX  EkiOnOff
	MAX-ACCESS read-only
	STATUS current
	DESCRIPTION
        "
        Client Current 15-min Output Multicast
        counter inv. :This OID indicates
        that the current 15-min Multicast
        counter is invalid
        "
	::= { pmc2002PerfDatacomClientCurrent15StatEntry 34 }


pmc2002perfdatacomclientCurrent15StatOutMulticastCountPortn OBJECT-TYPE
	SYNTAX  Counter64
	MAX-ACCESS read-only
	STATUS current
	DESCRIPTION
        "
        Client Current 15-min Output Multicast
        counter :This OID gives the current
        15-min Multicast counter value
        "
	::= { pmc2002PerfDatacomClientCurrent15StatEntry 35 }


pmc2002perfdatacomclientCurrent15StatOutBroadcastCountInvPortn OBJECT-TYPE
	SYNTAX  EkiOnOff
	MAX-ACCESS read-only
	STATUS current
	DESCRIPTION
        "
        Client Current 15-min Output Broadcast
        counter inv. :This OID indicates
        that the current 15-min Broadcast
        counter is invalid
        "
	::= { pmc2002PerfDatacomClientCurrent15StatEntry 32 }


pmc2002perfdatacomclientCurrent15StatOutBroadcastCountPortn OBJECT-TYPE
	SYNTAX  Counter64
	MAX-ACCESS read-only
	STATUS current
	DESCRIPTION
        "
        Client Current 15-min Output Broadcast
        counter :This OID gives the current
        15-min Broadcast counter value
        "
	::= { pmc2002PerfDatacomClientCurrent15StatEntry 33 }


pmc2002perfdatacomclientCurrent15StatOutBytesCountInvPortn OBJECT-TYPE
	SYNTAX  EkiOnOff
	MAX-ACCESS read-only
	STATUS current
	DESCRIPTION
        "
        Client Current 15-min Output Bytes
        counter inv. :This OID indicates
        that the current 15-min Bytes counter
        is invalid
        "
	::= { pmc2002PerfDatacomClientCurrent15StatEntry 26 }


pmc2002perfdatacomclientCurrent15StatOutBytesCountPortn OBJECT-TYPE
	SYNTAX  Counter64
	MAX-ACCESS read-only
	STATUS current
	DESCRIPTION
        "
        Client Current 15-min Output Bytes
        counter :This OID gives the current
        15-min Bytes counter value
        "
	::= { pmc2002PerfDatacomClientCurrent15StatEntry 27 }


pmc2002perfdatacomclientCurrent15StatInNonunicastCountInvPortn OBJECT-TYPE
	SYNTAX  EkiOnOff
	MAX-ACCESS read-only
	STATUS current
	DESCRIPTION
        "
        Client Current 15-min Input Non
        Unicast counter inv. :This OID
         indicates that the current 15-min
        Non unicast counter is invalid
        "
	::= { pmc2002PerfDatacomClientCurrent15StatEntry 22 }


pmc2002perfdatacomclientCurrent15StatInNonunicastCountPortn OBJECT-TYPE
	SYNTAX  Counter64
	MAX-ACCESS read-only
	STATUS current
	DESCRIPTION
        "
        Client Current 15-min Input Non
        Unicast counter :This OID gives
        the current 15-min Non Unicast
         counter value
        "
	::= { pmc2002PerfDatacomClientCurrent15StatEntry 23 }


pmc2002perfdatacomclientCurrent15StatInUnicastCountInvPortn OBJECT-TYPE
	SYNTAX  EkiOnOff
	MAX-ACCESS read-only
	STATUS current
	DESCRIPTION
        "
        Client Current 15-min Input Unicast
        counter inv. :This OID indicates
        that the current 15-min Unicast
        counter is invalid
        "
	::= { pmc2002PerfDatacomClientCurrent15StatEntry 20 }


pmc2002perfdatacomclientCurrent15StatInUnicastCountPortn OBJECT-TYPE
	SYNTAX  Counter64
	MAX-ACCESS read-only
	STATUS current
	DESCRIPTION
        "
        Client Current 15-min Input Unicast
        counter :This OID gives the current
        15-min Unicast counter value
        "
	::= { pmc2002PerfDatacomClientCurrent15StatEntry 21 }


pmc2002perfdatacomclientCurrent15StatInMulticastCountInvPortn OBJECT-TYPE
	SYNTAX  EkiOnOff
	MAX-ACCESS read-only
	STATUS current
	DESCRIPTION
        "
        Client Current 15-min Input Multicast
        counter inv. :This OID indicates
        that the current 15-min Multicast
        counter is invalid
        "
	::= { pmc2002PerfDatacomClientCurrent15StatEntry 10 }


pmc2002perfdatacomclientCurrent15StatInMulticastCountPortn OBJECT-TYPE
	SYNTAX  Counter64
	MAX-ACCESS read-only
	STATUS current
	DESCRIPTION
        "
        Client Current 15-min Input Multicast
        counter :This OID gives the current
        15-min Multicast counter value
        "
	::= { pmc2002PerfDatacomClientCurrent15StatEntry 11 }


pmc2002perfdatacomclientCurrent15StatInBroadcastCountInvPortn OBJECT-TYPE
	SYNTAX  EkiOnOff
	MAX-ACCESS read-only
	STATUS current
	DESCRIPTION
        "
        Client Current 15-min Input Broadcast
        counter inv. :This OID indicates
        that the current 15-min Broadcast
        counter is invalid
        "
	::= { pmc2002PerfDatacomClientCurrent15StatEntry 8 }


pmc2002perfdatacomclientCurrent15StatInBroadcastCountPortn OBJECT-TYPE
	SYNTAX  Counter64
	MAX-ACCESS read-only
	STATUS current
	DESCRIPTION
        "
        Client Current 15-min Input Broadcast
        counter :This OID gives the current
        15-min Broadcast counter value
        "
	::= { pmc2002PerfDatacomClientCurrent15StatEntry 9 }


pmc2002perfdatacomclientCurrent15StatInCrcCountInvPortn OBJECT-TYPE
	SYNTAX  EkiOnOff
	MAX-ACCESS read-only
	STATUS current
	DESCRIPTION
        "
        Client Current 15-min Input CRC
        counter inv. :This OID indicates
        that the current 15-min CRC counter
        is invalid
        "
	::= { pmc2002PerfDatacomClientCurrent15StatEntry 4 }


pmc2002perfdatacomclientCurrent15StatInCrcCountPortn OBJECT-TYPE
	SYNTAX  Counter64
	MAX-ACCESS read-only
	STATUS current
	DESCRIPTION
        "
        Client Current 15-min Input CRC
        counter :This OID gives the current
        15-min CRC counter value
        "
	::= { pmc2002PerfDatacomClientCurrent15StatEntry 5 }


pmc2002perfdatacomclientCurrent15StatInBytesCountInvPortn OBJECT-TYPE
	SYNTAX  EkiOnOff
	MAX-ACCESS read-only
	STATUS current
	DESCRIPTION
        "
        Client Current 15-min Input Bytes
        counter inv. :This OID indicates
        that the current 15-min Bytes counter
        is invalid
        "
	::= { pmc2002PerfDatacomClientCurrent15StatEntry 2 }


pmc2002perfdatacomclientCurrent15StatInBytesCountPortn OBJECT-TYPE
	SYNTAX  Counter64
	MAX-ACCESS read-only
	STATUS current
	DESCRIPTION
        "
        Client Current 15-min Input Bytes
        counter :This OID gives the current
        15-min Bytes counter value
        "
	::= { pmc2002PerfDatacomClientCurrent15StatEntry 3 }


--- *****************************************************
---     Leaf of the datacomClientPast15Stat
--- *****************************************************
--- *********************************************************
---     TABLE for the pmc2002PerfDatacomClientPast15StatHistory articles
--- *********************************************************

pmc2002PerfDatacomClientPast15StatHistoryPort1Table OBJECT-TYPE
	SYNTAX  SEQUENCE OF Pmc2002PerfDatacomClientPast15StatHistoryPort1Entry
	MAX-ACCESS not-accessible
	STATUS current
	DESCRIPTION
        "
        List of pmc2002PerfDatacomClientPast15StatHistory
        Article
        "
	::= { pmc2002MonClient 264 }


pmc2002PerfDatacomClientPast15StatHistoryPort1Entry OBJECT-TYPE
	SYNTAX Pmc2002PerfDatacomClientPast15StatHistoryPort1Entry
	MAX-ACCESS not-accessible
	STATUS current
	DESCRIPTION
        "
        Row definition for the pmc2002PerfDatacomClientPast15StatHistory
        table
        "
	INDEX   { pmc2002PerfDatacomClientPast15StatHistoryPort1Index }
	::= { pmc2002PerfDatacomClientPast15StatHistoryPort1Table 1 }


Pmc2002PerfDatacomClientPast15StatHistoryPort1Entry ::=
	SEQUENCE {
	pmc2002PerfDatacomClientPast15StatHistoryPort1Index
		INTEGER,
	pmc2002perfdatacomclientPast15StatOutNonunicastCountInvPort1
		EkiOnOff,
	pmc2002perfdatacomclientPast15StatOutNonunicastCountPort1
		Counter64,
	pmc2002perfdatacomclientPast15StatOutUnicastCountInvPort1
		EkiOnOff,
	pmc2002perfdatacomclientPast15StatOutUnicastCountPort1
		Counter64,
	pmc2002perfdatacomclientPast15StatOutMulticastCountInvPort1
		EkiOnOff,
	pmc2002perfdatacomclientPast15StatOutMulticastCountPort1
		Counter64,
	pmc2002perfdatacomclientPast15StatOutBroadcastCountInvPort1
		EkiOnOff,
	pmc2002perfdatacomclientPast15StatOutBroadcastCountPort1
		Counter64,
	pmc2002perfdatacomclientPast15StatOutBytesCountInvPort1
		EkiOnOff,
	pmc2002perfdatacomclientPast15StatOutBytesCountPort1
		Counter64,
	pmc2002perfdatacomclientPast15StatInNonunicastCountInvPort1
		EkiOnOff,
	pmc2002perfdatacomclientPast15StatInNonunicastCountPort1
		Counter64,
	pmc2002perfdatacomclientPast15StatInUnicastCountInvPort1
		EkiOnOff,
	pmc2002perfdatacomclientPast15StatInUnicastCountPort1
		Counter64,
	pmc2002perfdatacomclientPast15StatInMulticastCountInvPort1
		EkiOnOff,
	pmc2002perfdatacomclientPast15StatInMulticastCountPort1
		Counter64,
	pmc2002perfdatacomclientPast15StatInBroadcastCountInvPort1
		EkiOnOff,
	pmc2002perfdatacomclientPast15StatInBroadcastCountPort1
		Counter64,
	pmc2002perfdatacomclientPast15StatInCrcCountInvPort1
		EkiOnOff,
	pmc2002perfdatacomclientPast15StatInCrcCountPort1
		Counter64,
	pmc2002perfdatacomclientPast15StatInBytesCountInvPort1
		EkiOnOff,
	pmc2002perfdatacomclientPast15StatInBytesCountPort1
		Counter64
	}


pmc2002PerfDatacomClientPast15StatHistoryPort1Index OBJECT-TYPE
	SYNTAX  INTEGER(0..128)
	MAX-ACCESS  read-only
	STATUS current
	DESCRIPTION
        "
        Index definition for the pmc2002PerfDatacomClientPast15StatHistory
        table
        "
	::= { pmc2002PerfDatacomClientPast15StatHistoryPort1Entry 1 }


pmc2002perfdatacomclientPast15StatOutNonunicastCountInvPort1 OBJECT-TYPE
	SYNTAX  EkiOnOff
	MAX-ACCESS read-only
	STATUS current
	DESCRIPTION
        "
        Client Past 15-min Output Non
         Unicast counter inv. :This OID
        indicates that the past 15-min
         Non Unicast counter is invalid
        "
	::= { pmc2002PerfDatacomClientPast15StatHistoryPort1Entry 44 }


pmc2002perfdatacomclientPast15StatOutNonunicastCountPort1 OBJECT-TYPE
	SYNTAX  Counter64
	MAX-ACCESS read-only
	STATUS current
	DESCRIPTION
        "
        Client Past 15-min Output Non
         Unicast counter :This OID gives
        the past 15-min Non Unicast counter
        value
        "
	::= { pmc2002PerfDatacomClientPast15StatHistoryPort1Entry 45 }


pmc2002perfdatacomclientPast15StatOutUnicastCountInvPort1 OBJECT-TYPE
	SYNTAX  EkiOnOff
	MAX-ACCESS read-only
	STATUS current
	DESCRIPTION
        "
        Client Past 15-min Output Unicast
        counter inv. :This OID indicates
        that the past 15-min Unicast counter
        is invalid
        "
	::= { pmc2002PerfDatacomClientPast15StatHistoryPort1Entry 42 }


pmc2002perfdatacomclientPast15StatOutUnicastCountPort1 OBJECT-TYPE
	SYNTAX  Counter64
	MAX-ACCESS read-only
	STATUS current
	DESCRIPTION
        "
        Client Past 15-min Output Unicast
        counter :This OID gives the past
        15-min Unicast counter value
        "
	::= { pmc2002PerfDatacomClientPast15StatHistoryPort1Entry 43 }


pmc2002perfdatacomclientPast15StatOutMulticastCountInvPort1 OBJECT-TYPE
	SYNTAX  EkiOnOff
	MAX-ACCESS read-only
	STATUS current
	DESCRIPTION
        "
        Client Past 15-min Output Multicast
        counter inv. :This OID indicates
        that the past 15-min Multicast
         counter is invalid
        "
	::= { pmc2002PerfDatacomClientPast15StatHistoryPort1Entry 34 }


pmc2002perfdatacomclientPast15StatOutMulticastCountPort1 OBJECT-TYPE
	SYNTAX  Counter64
	MAX-ACCESS read-only
	STATUS current
	DESCRIPTION
        "
        Client Past 15-min Output Multicast
        counter :This OID gives the past
        15-min Multicast counter value
        "
	::= { pmc2002PerfDatacomClientPast15StatHistoryPort1Entry 35 }


pmc2002perfdatacomclientPast15StatOutBroadcastCountInvPort1 OBJECT-TYPE
	SYNTAX  EkiOnOff
	MAX-ACCESS read-only
	STATUS current
	DESCRIPTION
        "
        Client Past 15-min Output Broadcast
        counter inv. :This OID indicates
        that the past 15-min Broadcast
         counter is invalid
        "
	::= { pmc2002PerfDatacomClientPast15StatHistoryPort1Entry 32 }


pmc2002perfdatacomclientPast15StatOutBroadcastCountPort1 OBJECT-TYPE
	SYNTAX  Counter64
	MAX-ACCESS read-only
	STATUS current
	DESCRIPTION
        "
        Client Past 15-min Output Broadcast
        counter :This OID gives the past
        15-min Broadcast counter value
        "
	::= { pmc2002PerfDatacomClientPast15StatHistoryPort1Entry 33 }


pmc2002perfdatacomclientPast15StatOutBytesCountInvPort1 OBJECT-TYPE
	SYNTAX  EkiOnOff
	MAX-ACCESS read-only
	STATUS current
	DESCRIPTION
        "
        Client Past 15-min Output Bytes
        counter inv. :This OID indicates
        that the past 15-min Bytes counter
        is invalid
        "
	::= { pmc2002PerfDatacomClientPast15StatHistoryPort1Entry 26 }


pmc2002perfdatacomclientPast15StatOutBytesCountPort1 OBJECT-TYPE
	SYNTAX  Counter64
	MAX-ACCESS read-only
	STATUS current
	DESCRIPTION
        "
        Client Past 15-min Output Bytes
        counter :This OID gives the past
        15-min Bytes counter value
        "
	::= { pmc2002PerfDatacomClientPast15StatHistoryPort1Entry 27 }


pmc2002perfdatacomclientPast15StatInNonunicastCountInvPort1 OBJECT-TYPE
	SYNTAX  EkiOnOff
	MAX-ACCESS read-only
	STATUS current
	DESCRIPTION
        "
        Client Past 15-min Input Non Unicast
        counter inv. :This OID indicates
        that the past 15-min Non unicast
        counter is invalid
        "
	::= { pmc2002PerfDatacomClientPast15StatHistoryPort1Entry 22 }


pmc2002perfdatacomclientPast15StatInNonunicastCountPort1 OBJECT-TYPE
	SYNTAX  Counter64
	MAX-ACCESS read-only
	STATUS current
	DESCRIPTION
        "
        Client Past 15-min Input Non Unicast
        counter :This OID gives the past
        15-min Non Unicast counter value
        "
	::= { pmc2002PerfDatacomClientPast15StatHistoryPort1Entry 23 }


pmc2002perfdatacomclientPast15StatInUnicastCountInvPort1 OBJECT-TYPE
	SYNTAX  EkiOnOff
	MAX-ACCESS read-only
	STATUS current
	DESCRIPTION
        "
        Client Past 15-min Input Unicast
        counter inv. :This OID indicates
        that the past 15-min Unicast counter
        is invalid
        "
	::= { pmc2002PerfDatacomClientPast15StatHistoryPort1Entry 20 }


pmc2002perfdatacomclientPast15StatInUnicastCountPort1 OBJECT-TYPE
	SYNTAX  Counter64
	MAX-ACCESS read-only
	STATUS current
	DESCRIPTION
        "
        Client Past 15-min Input Unicast
        counter :This OID gives the past
        15-min Unicast counter value
        "
	::= { pmc2002PerfDatacomClientPast15StatHistoryPort1Entry 21 }


pmc2002perfdatacomclientPast15StatInMulticastCountInvPort1 OBJECT-TYPE
	SYNTAX  EkiOnOff
	MAX-ACCESS read-only
	STATUS current
	DESCRIPTION
        "
        Client Past 15-min Input Multicast
        counter inv. :This OID indicates
        that the past 15-min Multicast
         counter is invalid
        "
	::= { pmc2002PerfDatacomClientPast15StatHistoryPort1Entry 10 }


pmc2002perfdatacomclientPast15StatInMulticastCountPort1 OBJECT-TYPE
	SYNTAX  Counter64
	MAX-ACCESS read-only
	STATUS current
	DESCRIPTION
        "
        Client Past 15-min Input Multicast
        counter :This OID gives the past
        15-min Multicast counter value
        "
	::= { pmc2002PerfDatacomClientPast15StatHistoryPort1Entry 11 }


pmc2002perfdatacomclientPast15StatInBroadcastCountInvPort1 OBJECT-TYPE
	SYNTAX  EkiOnOff
	MAX-ACCESS read-only
	STATUS current
	DESCRIPTION
        "
        Client Past 15-min Input Broadcast
        counter inv. :This OID indicates
        that the past 15-min Broadcast
         counter is invalid
        "
	::= { pmc2002PerfDatacomClientPast15StatHistoryPort1Entry 8 }


pmc2002perfdatacomclientPast15StatInBroadcastCountPort1 OBJECT-TYPE
	SYNTAX  Counter64
	MAX-ACCESS read-only
	STATUS current
	DESCRIPTION
        "
        Client Past 15-min Input Broadcast
        counter :This OID gives the past
        15-min Broadcast counter value
        "
	::= { pmc2002PerfDatacomClientPast15StatHistoryPort1Entry 9 }


pmc2002perfdatacomclientPast15StatInCrcCountInvPort1 OBJECT-TYPE
	SYNTAX  EkiOnOff
	MAX-ACCESS read-only
	STATUS current
	DESCRIPTION
        "
        Client Past 15-min Input CRC counter
        inv. :This OID indicates that the
        past 15-min CRC counter is invalid
        "
	::= { pmc2002PerfDatacomClientPast15StatHistoryPort1Entry 4 }


pmc2002perfdatacomclientPast15StatInCrcCountPort1 OBJECT-TYPE
	SYNTAX  Counter64
	MAX-ACCESS read-only
	STATUS current
	DESCRIPTION
        "
        Client Past 15-min Input CRC counter
        :This OID gives the past 15-min
        CRC counter value
        "
	::= { pmc2002PerfDatacomClientPast15StatHistoryPort1Entry 5 }


pmc2002perfdatacomclientPast15StatInBytesCountInvPort1 OBJECT-TYPE
	SYNTAX  EkiOnOff
	MAX-ACCESS read-only
	STATUS current
	DESCRIPTION
        "
        Client Past 15-min Input Bytes
        counter inv. :This OID indicates
        that the past 15-min Bytes counter
        is invalid
        "
	::= { pmc2002PerfDatacomClientPast15StatHistoryPort1Entry 2 }


pmc2002perfdatacomclientPast15StatInBytesCountPort1 OBJECT-TYPE
	SYNTAX  Counter64
	MAX-ACCESS read-only
	STATUS current
	DESCRIPTION
        "
        Client Past 15-min Input Bytes
        counter :This OID gives the past
        15-min Bytes counter value
        "
	::= { pmc2002PerfDatacomClientPast15StatHistoryPort1Entry 3 }


--- *****************************************************
---     Leaf of the datacomClientCurrent24Stat
--- *****************************************************
--- *********************************************************
---     TABLE for the pmc2002PerfDatacomClientCurrent24Stat articles
--- *********************************************************

pmc2002PerfDatacomClientCurrent24StatTable OBJECT-TYPE
	SYNTAX  SEQUENCE OF Pmc2002PerfDatacomClientCurrent24StatEntry
	MAX-ACCESS not-accessible
	STATUS current
	DESCRIPTION
        "
        List of pmc2002PerfDatacomClientCurrent24Stat
        Article
        "
	::= { pmc2002MonClient 272 }


pmc2002PerfDatacomClientCurrent24StatEntry OBJECT-TYPE
	SYNTAX Pmc2002PerfDatacomClientCurrent24StatEntry
	MAX-ACCESS not-accessible
	STATUS current
	DESCRIPTION
        "
        Row definition for the pmc2002PerfDatacomClientCurrent24Stat
        table
        "
	INDEX   { pmc2002PerfDatacomClientCurrent24StatIndex }
	::= { pmc2002PerfDatacomClientCurrent24StatTable 1 }


Pmc2002PerfDatacomClientCurrent24StatEntry ::=
	SEQUENCE {
	pmc2002PerfDatacomClientCurrent24StatIndex
		INTEGER,
	pmc2002perfdatacomclientCurrent24StatOutNonunicastCountInvPortn
		EkiOnOff,
	pmc2002perfdatacomclientCurrent24StatOutNonunicastCountPortn
		Counter64,
	pmc2002perfdatacomclientCurrent24StatOutUnicastCountInvPortn
		EkiOnOff,
	pmc2002perfdatacomclientCurrent24StatOutUnicastCountPortn
		Counter64,
	pmc2002perfdatacomclientCurrent24StatOutMulticastCountInvPortn
		EkiOnOff,
	pmc2002perfdatacomclientCurrent24StatOutMulticastCountPortn
		Counter64,
	pmc2002perfdatacomclientCurrent24StatOutBroadcastCountInvPortn
		EkiOnOff,
	pmc2002perfdatacomclientCurrent24StatOutBroadcastCountPortn
		Counter64,
	pmc2002perfdatacomclientCurrent24StatOutBytesCountInvPortn
		EkiOnOff,
	pmc2002perfdatacomclientCurrent24StatOutBytesCountPortn
		Counter64,
	pmc2002perfdatacomclientCurrent24StatInNonunicastCountInvPortn
		EkiOnOff,
	pmc2002perfdatacomclientCurrent24StatInNonunicastCountPortn
		Counter64,
	pmc2002perfdatacomclientCurrent24StatInUnicastCountInvPortn
		EkiOnOff,
	pmc2002perfdatacomclientCurrent24StatInUnicastCountPortn
		Counter64,
	pmc2002perfdatacomclientCurrent24StatInMulticastCountInvPortn
		EkiOnOff,
	pmc2002perfdatacomclientCurrent24StatInMulticastCountPortn
		Counter64,
	pmc2002perfdatacomclientCurrent24StatInBroadcastCountInvPortn
		EkiOnOff,
	pmc2002perfdatacomclientCurrent24StatInBroadcastCountPortn
		Counter64,
	pmc2002perfdatacomclientCurrent24StatInCrcCountInvPortn
		EkiOnOff,
	pmc2002perfdatacomclientCurrent24StatInCrcCountPortn
		Counter64,
	pmc2002perfdatacomclientCurrent24StatInBytesCountInvPortn
		EkiOnOff,
	pmc2002perfdatacomclientCurrent24StatInBytesCountPortn
		Counter64
	}


pmc2002PerfDatacomClientCurrent24StatIndex OBJECT-TYPE
	SYNTAX  INTEGER(0..128)
	MAX-ACCESS  read-only
	STATUS current
	DESCRIPTION
        "
        Index definition for the pmc2002PerfDatacomClientCurrent24Stat
        table
        "
	::= { pmc2002PerfDatacomClientCurrent24StatEntry 1 }


pmc2002perfdatacomclientCurrent24StatOutNonunicastCountInvPortn OBJECT-TYPE
	SYNTAX  EkiOnOff
	MAX-ACCESS read-only
	STATUS current
	DESCRIPTION
        "
        Client Current 24-hours Output
        Non Unicast counter inv. :This
         OID indicates that the current
        24-hours Non Unicast counter is
        invalid
        "
	::= { pmc2002PerfDatacomClientCurrent24StatEntry 44 }


pmc2002perfdatacomclientCurrent24StatOutNonunicastCountPortn OBJECT-TYPE
	SYNTAX  Counter64
	MAX-ACCESS read-only
	STATUS current
	DESCRIPTION
        "
        Client Current 24-hours Output
        Non Unicast counter :This OID gives
        the current 24-hours Non Unicast
        counter value
        "
	::= { pmc2002PerfDatacomClientCurrent24StatEntry 45 }


pmc2002perfdatacomclientCurrent24StatOutUnicastCountInvPortn OBJECT-TYPE
	SYNTAX  EkiOnOff
	MAX-ACCESS read-only
	STATUS current
	DESCRIPTION
        "
        Client Current 24-hours Output
        Unicast counter inv. :This OID
         indicates that the current 24-hours
        Unicast counter is invalid
        "
	::= { pmc2002PerfDatacomClientCurrent24StatEntry 42 }


pmc2002perfdatacomclientCurrent24StatOutUnicastCountPortn OBJECT-TYPE
	SYNTAX  Counter64
	MAX-ACCESS read-only
	STATUS current
	DESCRIPTION
        "
        Client Current 24-hours Output
        Unicast counter :This OID gives
        the current 24-hours Unicast counter
        value
        "
	::= { pmc2002PerfDatacomClientCurrent24StatEntry 43 }


pmc2002perfdatacomclientCurrent24StatOutMulticastCountInvPortn OBJECT-TYPE
	SYNTAX  EkiOnOff
	MAX-ACCESS read-only
	STATUS current
	DESCRIPTION
        "
        Client Current 24-hours Output
        Multicast counter inv. :This OID
        indicates that the current 24-hours
        Multicast counter is invalid
        "
	::= { pmc2002PerfDatacomClientCurrent24StatEntry 34 }


pmc2002perfdatacomclientCurrent24StatOutMulticastCountPortn OBJECT-TYPE
	SYNTAX  Counter64
	MAX-ACCESS read-only
	STATUS current
	DESCRIPTION
        "
        Client Current 24-hours Output
        Multicast counter :This OID gives
        the current 24-hours Multicast
         counter value
        "
	::= { pmc2002PerfDatacomClientCurrent24StatEntry 35 }


pmc2002perfdatacomclientCurrent24StatOutBroadcastCountInvPortn OBJECT-TYPE
	SYNTAX  EkiOnOff
	MAX-ACCESS read-only
	STATUS current
	DESCRIPTION
        "
        Client Current 24-hours Output
        Broadcast counter inv. :This OID
        indicates that the current 24-hours
        Broadcast counter is invalid
        "
	::= { pmc2002PerfDatacomClientCurrent24StatEntry 32 }


pmc2002perfdatacomclientCurrent24StatOutBroadcastCountPortn OBJECT-TYPE
	SYNTAX  Counter64
	MAX-ACCESS read-only
	STATUS current
	DESCRIPTION
        "
        Client Current 24-hours Output
        Broadcast counter :This OID gives
        the current 24-hours Broadcast
         counter value
        "
	::= { pmc2002PerfDatacomClientCurrent24StatEntry 33 }


pmc2002perfdatacomclientCurrent24StatOutBytesCountInvPortn OBJECT-TYPE
	SYNTAX  EkiOnOff
	MAX-ACCESS read-only
	STATUS current
	DESCRIPTION
        "
        Client Current 24-hours Output
        Bytes counter inv. :This OID indicates
        that the current 24-hours Bytes
        counter is invalid
        "
	::= { pmc2002PerfDatacomClientCurrent24StatEntry 26 }


pmc2002perfdatacomclientCurrent24StatOutBytesCountPortn OBJECT-TYPE
	SYNTAX  Counter64
	MAX-ACCESS read-only
	STATUS current
	DESCRIPTION
        "
        Client Current 24-hours Output
        Bytes counter :This OID gives the
        current 24-hours Bytes counter
         value
        "
	::= { pmc2002PerfDatacomClientCurrent24StatEntry 27 }


pmc2002perfdatacomclientCurrent24StatInNonunicastCountInvPortn OBJECT-TYPE
	SYNTAX  EkiOnOff
	MAX-ACCESS read-only
	STATUS current
	DESCRIPTION
        "
        Client Current 24-hours Input
         Non Unicast counter inv. :This
        OID indicates that the current
         24-hours Non unicast counter is
        invalid
        "
	::= { pmc2002PerfDatacomClientCurrent24StatEntry 22 }


pmc2002perfdatacomclientCurrent24StatInNonunicastCountPortn OBJECT-TYPE
	SYNTAX  Counter64
	MAX-ACCESS read-only
	STATUS current
	DESCRIPTION
        "
        Client Current 24-hours Input
         Non Unicast counter :This OID
         gives the current 24-hours Non
        Unicast counter value
        "
	::= { pmc2002PerfDatacomClientCurrent24StatEntry 23 }


pmc2002perfdatacomclientCurrent24StatInUnicastCountInvPortn OBJECT-TYPE
	SYNTAX  EkiOnOff
	MAX-ACCESS read-only
	STATUS current
	DESCRIPTION
        "
        Client Current 24-hours Input
         Unicast counter inv. :This OID
        indicates that the current 24-hours
        Unicast counter is invalid
        "
	::= { pmc2002PerfDatacomClientCurrent24StatEntry 20 }


pmc2002perfdatacomclientCurrent24StatInUnicastCountPortn OBJECT-TYPE
	SYNTAX  Counter64
	MAX-ACCESS read-only
	STATUS current
	DESCRIPTION
        "
        Client Current 24-hours Input
         Unicast counter :This OID gives
        the current 24-hours Unicast counter
        value
        "
	::= { pmc2002PerfDatacomClientCurrent24StatEntry 21 }


pmc2002perfdatacomclientCurrent24StatInMulticastCountInvPortn OBJECT-TYPE
	SYNTAX  EkiOnOff
	MAX-ACCESS read-only
	STATUS current
	DESCRIPTION
        "
        Client Current 24-hours Input
         Multicast counter inv. :This OID
        indicates that the current 24-hours
        Multicast counter is invalid
        "
	::= { pmc2002PerfDatacomClientCurrent24StatEntry 10 }


pmc2002perfdatacomclientCurrent24StatInMulticastCountPortn OBJECT-TYPE
	SYNTAX  Counter64
	MAX-ACCESS read-only
	STATUS current
	DESCRIPTION
        "
        Client Current 24-hours Input
         Multicast counter :This OID gives
        the current 24-hours Multicast
         counter value
        "
	::= { pmc2002PerfDatacomClientCurrent24StatEntry 11 }


pmc2002perfdatacomclientCurrent24StatInBroadcastCountInvPortn OBJECT-TYPE
	SYNTAX  EkiOnOff
	MAX-ACCESS read-only
	STATUS current
	DESCRIPTION
        "
        Client Current 24-hours Input
         Broadcast counter inv. :This OID
        indicates that the current 24-hours
        Broadcast counter is invalid
        "
	::= { pmc2002PerfDatacomClientCurrent24StatEntry 8 }


pmc2002perfdatacomclientCurrent24StatInBroadcastCountPortn OBJECT-TYPE
	SYNTAX  Counter64
	MAX-ACCESS read-only
	STATUS current
	DESCRIPTION
        "
        Client Current 24-hours Input
         Broadcast counter :This OID gives
        the current 24-hours Broadcast
         counter value
        "
	::= { pmc2002PerfDatacomClientCurrent24StatEntry 9 }


pmc2002perfdatacomclientCurrent24StatInCrcCountInvPortn OBJECT-TYPE
	SYNTAX  EkiOnOff
	MAX-ACCESS read-only
	STATUS current
	DESCRIPTION
        "
        Client Current 24-hours Input
         CRC counter inv. :This OID indicates
        that the current 24-hours CRC counter
        is invalid
        "
	::= { pmc2002PerfDatacomClientCurrent24StatEntry 4 }


pmc2002perfdatacomclientCurrent24StatInCrcCountPortn OBJECT-TYPE
	SYNTAX  Counter64
	MAX-ACCESS read-only
	STATUS current
	DESCRIPTION
        "
        Client Current 24-hours Input
         CRC counter :This OID gives the
        current 24-hours CRC counter value
        "
	::= { pmc2002PerfDatacomClientCurrent24StatEntry 5 }


pmc2002perfdatacomclientCurrent24StatInBytesCountInvPortn OBJECT-TYPE
	SYNTAX  EkiOnOff
	MAX-ACCESS read-only
	STATUS current
	DESCRIPTION
        "
        Client Current 24-hours Input
         Bytes counter inv. :This OID indicates
        that the current 24-hours Bytes
        counter is invalid
        "
	::= { pmc2002PerfDatacomClientCurrent24StatEntry 2 }


pmc2002perfdatacomclientCurrent24StatInBytesCountPortn OBJECT-TYPE
	SYNTAX  Counter64
	MAX-ACCESS read-only
	STATUS current
	DESCRIPTION
        "
        Client Current 24-hours Input
         Bytes counter :This OID gives
         the current 24-hours Bytes counter
        value
        "
	::= { pmc2002PerfDatacomClientCurrent24StatEntry 3 }


--- *****************************************************
---     Leaf of the datacomClientPast24Stat
--- *****************************************************
--- *********************************************************
---     TABLE for the pmc2002PerfDatacomClientPast24StatHistory articles
--- *********************************************************

pmc2002PerfDatacomClientPast24StatHistoryPort1Table OBJECT-TYPE
	SYNTAX  SEQUENCE OF Pmc2002PerfDatacomClientPast24StatHistoryPort1Entry
	MAX-ACCESS not-accessible
	STATUS current
	DESCRIPTION
        "
        List of pmc2002PerfDatacomClientPast24StatHistory
        Article
        "
	::= { pmc2002MonClient 280 }


pmc2002PerfDatacomClientPast24StatHistoryPort1Entry OBJECT-TYPE
	SYNTAX Pmc2002PerfDatacomClientPast24StatHistoryPort1Entry
	MAX-ACCESS not-accessible
	STATUS current
	DESCRIPTION
        "
        Row definition for the pmc2002PerfDatacomClientPast24StatHistory
        table
        "
	INDEX   { pmc2002PerfDatacomClientPast24StatHistoryPort1Index }
	::= { pmc2002PerfDatacomClientPast24StatHistoryPort1Table 1 }


Pmc2002PerfDatacomClientPast24StatHistoryPort1Entry ::=
	SEQUENCE {
	pmc2002PerfDatacomClientPast24StatHistoryPort1Index
		INTEGER,
	pmc2002perfdatacomclientPast24StatOutNonunicastCountInvPort1
		EkiOnOff,
	pmc2002perfdatacomclientPast24StatOutNonunicastCountPort1
		Counter64,
	pmc2002perfdatacomclientPast24StatOutUnicastCountInvPort1
		EkiOnOff,
	pmc2002perfdatacomclientPast24StatOutUnicastCountPort1
		Counter64,
	pmc2002perfdatacomclientPast24StatOutMulticastCountInvPort1
		EkiOnOff,
	pmc2002perfdatacomclientPast24StatOutMulticastCountPort1
		Counter64,
	pmc2002perfdatacomclientPast24StatOutBroadcastCountInvPort1
		EkiOnOff,
	pmc2002perfdatacomclientPast24StatOutBroadcastCountPort1
		Counter64,
	pmc2002perfdatacomclientPast24StatOutBytesCountInvPort1
		EkiOnOff,
	pmc2002perfdatacomclientPast24StatOutBytesCountPort1
		Counter64,
	pmc2002perfdatacomclientPast24StatInNonunicastCountInvPort1
		EkiOnOff,
	pmc2002perfdatacomclientPast24StatInNonunicastCountPort1
		Counter64,
	pmc2002perfdatacomclientPast24StatInUnicastCountInvPort1
		EkiOnOff,
	pmc2002perfdatacomclientPast24StatInUnicastCountPort1
		Counter64,
	pmc2002perfdatacomclientPast24StatInMulticastCountInvPort1
		EkiOnOff,
	pmc2002perfdatacomclientPast24StatInMulticastCountPort1
		Counter64,
	pmc2002perfdatacomclientPast24StatInBroadcastCountInvPort1
		EkiOnOff,
	pmc2002perfdatacomclientPast24StatInBroadcastCountPort1
		Counter64,
	pmc2002perfdatacomclientPast24StatInCrcCountInvPort1
		EkiOnOff,
	pmc2002perfdatacomclientPast24StatInCrcCountPort1
		Counter64,
	pmc2002perfdatacomclientPast24StatInBytesCountInvPort1
		EkiOnOff,
	pmc2002perfdatacomclientPast24StatInBytesCountPort1
		Counter64
	}


pmc2002PerfDatacomClientPast24StatHistoryPort1Index OBJECT-TYPE
	SYNTAX  INTEGER(0..128)
	MAX-ACCESS  read-only
	STATUS current
	DESCRIPTION
        "
        Index definition for the pmc2002PerfDatacomClientPast24StatHistory
        table
        "
	::= { pmc2002PerfDatacomClientPast24StatHistoryPort1Entry 1 }


pmc2002perfdatacomclientPast24StatOutNonunicastCountInvPort1 OBJECT-TYPE
	SYNTAX  EkiOnOff
	MAX-ACCESS read-only
	STATUS current
	DESCRIPTION
        "
        Client Past 24-hours Output Non
        Unicast counter inv. :This OID
         indicates that the past 24-hours
        Non Unicast counter is invalid
        "
	::= { pmc2002PerfDatacomClientPast24StatHistoryPort1Entry 44 }


pmc2002perfdatacomclientPast24StatOutNonunicastCountPort1 OBJECT-TYPE
	SYNTAX  Counter64
	MAX-ACCESS read-only
	STATUS current
	DESCRIPTION
        "
        Client Past 24-hours Output Non
        Unicast counter :This OID gives
        the past 24-hours Non Unicast counter
        value
        "
	::= { pmc2002PerfDatacomClientPast24StatHistoryPort1Entry 45 }


pmc2002perfdatacomclientPast24StatOutUnicastCountInvPort1 OBJECT-TYPE
	SYNTAX  EkiOnOff
	MAX-ACCESS read-only
	STATUS current
	DESCRIPTION
        "
        Client Past 24-hours Output Unicast
        counter inv. :This OID indicates
        that the past 24-hours Unicast
         counter is invalid
        "
	::= { pmc2002PerfDatacomClientPast24StatHistoryPort1Entry 42 }


pmc2002perfdatacomclientPast24StatOutUnicastCountPort1 OBJECT-TYPE
	SYNTAX  Counter64
	MAX-ACCESS read-only
	STATUS current
	DESCRIPTION
        "
        Client Past 24-hours Output Unicast
        counter :This OID gives the past
        24-hours Unicast counter value
        "
	::= { pmc2002PerfDatacomClientPast24StatHistoryPort1Entry 43 }


pmc2002perfdatacomclientPast24StatOutMulticastCountInvPort1 OBJECT-TYPE
	SYNTAX  EkiOnOff
	MAX-ACCESS read-only
	STATUS current
	DESCRIPTION
        "
        Client Past 24-hours Output Multicast
        counter inv. :This OID indicates
        that the past 24-hours Multicast
        counter is invalid
        "
	::= { pmc2002PerfDatacomClientPast24StatHistoryPort1Entry 34 }


pmc2002perfdatacomclientPast24StatOutMulticastCountPort1 OBJECT-TYPE
	SYNTAX  Counter64
	MAX-ACCESS read-only
	STATUS current
	DESCRIPTION
        "
        Client Past 24-hours Output Multicast
        counter :This OID gives the past
        24-hours Multicast counter value
        "
	::= { pmc2002PerfDatacomClientPast24StatHistoryPort1Entry 35 }


pmc2002perfdatacomclientPast24StatOutBroadcastCountInvPort1 OBJECT-TYPE
	SYNTAX  EkiOnOff
	MAX-ACCESS read-only
	STATUS current
	DESCRIPTION
        "
        Client Past 24-hours Output Broadcast
        counter inv. :This OID indicates
        that the past 24-hours Broadcast
        counter is invalid
        "
	::= { pmc2002PerfDatacomClientPast24StatHistoryPort1Entry 32 }


pmc2002perfdatacomclientPast24StatOutBroadcastCountPort1 OBJECT-TYPE
	SYNTAX  Counter64
	MAX-ACCESS read-only
	STATUS current
	DESCRIPTION
        "
        Client Past 24-hours Output Broadcast
        counter :This OID gives the past
        24-hours Broadcast counter value
        "
	::= { pmc2002PerfDatacomClientPast24StatHistoryPort1Entry 33 }


pmc2002perfdatacomclientPast24StatOutBytesCountInvPort1 OBJECT-TYPE
	SYNTAX  EkiOnOff
	MAX-ACCESS read-only
	STATUS current
	DESCRIPTION
        "
        Client Past 24-hours Output Bytes
        counter inv. :This OID indicates
        that the past 24-hours Bytes counter
        is invalid
        "
	::= { pmc2002PerfDatacomClientPast24StatHistoryPort1Entry 26 }


pmc2002perfdatacomclientPast24StatOutBytesCountPort1 OBJECT-TYPE
	SYNTAX  Counter64
	MAX-ACCESS read-only
	STATUS current
	DESCRIPTION
        "
        Client Past 24-hours Output Bytes
        counter :This OID gives the past
        24-hours Bytes counter value
        "
	::= { pmc2002PerfDatacomClientPast24StatHistoryPort1Entry 27 }


pmc2002perfdatacomclientPast24StatInNonunicastCountInvPort1 OBJECT-TYPE
	SYNTAX  EkiOnOff
	MAX-ACCESS read-only
	STATUS current
	DESCRIPTION
        "
        Client Past 24-hours Input Non
        Unicast counter inv. :This OID
         indicates that the past 24-hours
        Non unicast counter is invalid
        "
	::= { pmc2002PerfDatacomClientPast24StatHistoryPort1Entry 22 }


pmc2002perfdatacomclientPast24StatInNonunicastCountPort1 OBJECT-TYPE
	SYNTAX  Counter64
	MAX-ACCESS read-only
	STATUS current
	DESCRIPTION
        "
        Client Past 24-hours Input Non
        Unicast counter :This OID gives
        the past 24-hours Non Unicast counter
        value
        "
	::= { pmc2002PerfDatacomClientPast24StatHistoryPort1Entry 23 }


pmc2002perfdatacomclientPast24StatInUnicastCountInvPort1 OBJECT-TYPE
	SYNTAX  EkiOnOff
	MAX-ACCESS read-only
	STATUS current
	DESCRIPTION
        "
        Client Past 24-hours Input Unicast
        counter inv. :This OID indicates
        that the past 24-hours Unicast
         counter is invalid
        "
	::= { pmc2002PerfDatacomClientPast24StatHistoryPort1Entry 20 }


pmc2002perfdatacomclientPast24StatInUnicastCountPort1 OBJECT-TYPE
	SYNTAX  Counter64
	MAX-ACCESS read-only
	STATUS current
	DESCRIPTION
        "
        Client Past 24-hours Input Unicast
        counter :This OID gives the past
        24-hours Unicast counter value
        "
	::= { pmc2002PerfDatacomClientPast24StatHistoryPort1Entry 21 }


pmc2002perfdatacomclientPast24StatInMulticastCountInvPort1 OBJECT-TYPE
	SYNTAX  EkiOnOff
	MAX-ACCESS read-only
	STATUS current
	DESCRIPTION
        "
        Client Past 24-hours Input Multicast
        counter inv. :This OID indicates
        that the past 24-hours Multicast
        counter is invalid
        "
	::= { pmc2002PerfDatacomClientPast24StatHistoryPort1Entry 10 }


pmc2002perfdatacomclientPast24StatInMulticastCountPort1 OBJECT-TYPE
	SYNTAX  Counter64
	MAX-ACCESS read-only
	STATUS current
	DESCRIPTION
        "
        Client Past 24-hours Input Multicast
        counter :This OID gives the past
        24-hours Multicast counter value
        "
	::= { pmc2002PerfDatacomClientPast24StatHistoryPort1Entry 11 }


pmc2002perfdatacomclientPast24StatInBroadcastCountInvPort1 OBJECT-TYPE
	SYNTAX  EkiOnOff
	MAX-ACCESS read-only
	STATUS current
	DESCRIPTION
        "
        Client Past 24-hours Input Broadcast
        counter inv. :This OID indicates
        that the past 24-hours Broadcast
        counter is invalid
        "
	::= { pmc2002PerfDatacomClientPast24StatHistoryPort1Entry 8 }


pmc2002perfdatacomclientPast24StatInBroadcastCountPort1 OBJECT-TYPE
	SYNTAX  Counter64
	MAX-ACCESS read-only
	STATUS current
	DESCRIPTION
        "
        Client Past 24-hours Input Broadcast
        counter :This OID gives the past
        24-hours Broadcast counter value
        "
	::= { pmc2002PerfDatacomClientPast24StatHistoryPort1Entry 9 }


pmc2002perfdatacomclientPast24StatInCrcCountInvPort1 OBJECT-TYPE
	SYNTAX  EkiOnOff
	MAX-ACCESS read-only
	STATUS current
	DESCRIPTION
        "
        Client Past 24-hours Input CRC
        counter inv. :This OID indicates
        that the past 24-hours CRC counter
        is invalid
        "
	::= { pmc2002PerfDatacomClientPast24StatHistoryPort1Entry 4 }


pmc2002perfdatacomclientPast24StatInCrcCountPort1 OBJECT-TYPE
	SYNTAX  Counter64
	MAX-ACCESS read-only
	STATUS current
	DESCRIPTION
        "
        Client Past 24-hours Input CRC
        counter :This OID gives the past
        24-hours CRC counter value
        "
	::= { pmc2002PerfDatacomClientPast24StatHistoryPort1Entry 5 }


pmc2002perfdatacomclientPast24StatInBytesCountInvPort1 OBJECT-TYPE
	SYNTAX  EkiOnOff
	MAX-ACCESS read-only
	STATUS current
	DESCRIPTION
        "
        Client Past 24-hours Input Bytes
        counter inv. :This OID indicates
        that the past 24-hours Bytes counter
        is invalid
        "
	::= { pmc2002PerfDatacomClientPast24StatHistoryPort1Entry 2 }


pmc2002perfdatacomclientPast24StatInBytesCountPort1 OBJECT-TYPE
	SYNTAX  Counter64
	MAX-ACCESS read-only
	STATUS current
	DESCRIPTION
        "
        Client Past 24-hours Input Bytes
        counter :This OID gives the past
        24-hours Bytes counter value
        "
	::= { pmc2002PerfDatacomClientPast24StatHistoryPort1Entry 3 }



pmc2002PerfEnable OBJECT-TYPE
	SYNTAX EkiOnOff
	MAX-ACCESS read-write
	STATUS current
	DESCRIPTION
        "
        Perf. Mon. Enable :This OID enables
        the Performance Monitoring application
        "
	::= { pmc2002MonSync 257 }


pmc2002Perf15minSync OBJECT-TYPE
	SYNTAX EkiOnOff
	MAX-ACCESS read-write
	STATUS current
	DESCRIPTION
        "
        Perf. Mon. 15-min sync. :This
         OID must be used in external synchronisation
        mode only to send a 15-min synchronisation
        command
        "
	::= { pmc2002MonSync 259 }


pmc2002Perf24hSync OBJECT-TYPE
	SYNTAX EkiOnOff
	MAX-ACCESS read-write
	STATUS current
	DESCRIPTION
        "
        Perf. Mon. 24-hours sync. :This
        OID must be used in external synchronisation
        mode only to send a 24-hours synchronisation
        command
        "
	::= { pmc2002MonSync 260 }


pmc2002Perf15MinShort OBJECT-TYPE
	SYNTAX EkiOnOff
	MAX-ACCESS read-write
	STATUS current
	DESCRIPTION
        "
        15-min period is short :This OID
        indicates that the 15-min period
        lasts less than 890 seconds
        "
	::= { pmc2002MonTimeStamp 1 }


pmc2002Perf15MinLong OBJECT-TYPE
	SYNTAX EkiOnOff
	MAX-ACCESS read-write
	STATUS current
	DESCRIPTION
        "
        15-min period is long :This OID
        indicates that the 15-min period
        lasts more than 910 seconds
        "
	::= { pmc2002MonTimeStamp 2 }


pmc2002Perf24HoursShort OBJECT-TYPE
	SYNTAX Counter32
	MAX-ACCESS read-write
	STATUS current
	DESCRIPTION
        "
        24-hours period is short :This
        OID indicates that 24-hours period
        lasts less than 86390 seconds
        "
	::= { pmc2002MonTimeStamp 5 }


pmc2002Perf24HoursLong OBJECT-TYPE
	SYNTAX Counter32
	MAX-ACCESS read-write
	STATUS current
	DESCRIPTION
        "
        24-hours period is long :This
         OID indicates that 24-hours period
        lasts more than 86410 seconds
        "
	::= { pmc2002MonTimeStamp 6 }


pmc2002PerfCurrent15MinElapsedTime OBJECT-TYPE
	SYNTAX Counter32
	MAX-ACCESS read-write
	STATUS current
	DESCRIPTION
        "
        Current 15min period Elapsed Time
         :This OID gives the number of
         seconds elapsed in the current
        15-minutes period
        "
	::= { pmc2002MonTimeStamp 7 }


pmc2002PerfCurrent24HoursElapsedTime OBJECT-TYPE
	SYNTAX Counter32
	MAX-ACCESS read-write
	STATUS current
	DESCRIPTION
        "
        Current 24hours period Elapsed
        Time :This OID gives the number
        of seconds elapsed in the current
        24-hours period
        "
	::= { pmc2002MonTimeStamp 8 }






--- *****************************************************
--- $$$$$$$$$$$$$$$$$$$$$$$$$$$$$$$$$$$$$$$$$$$$$$$$$$$$$
---     DOWNLOAD
--- $$$$$$$$$$$$$$$$$$$$$$$$$$$$$$$$$$$$$$$$$$$$$$$$$$$$$
--- *****************************************************



--- *****************************************************
---     LEAF for the restartProcess article
--- *****************************************************
pmc2002DwlrestartProcess OBJECT IDENTIFIER ::= { pmc2002DwlOther 0 }




pmc2002DwlColdRestartProcessed OBJECT-TYPE
	  SYNTAX EkiOnOff
	  MAX-ACCESS read-only
	  STATUS current
	  DESCRIPTION
        "
        Cold Restart :This OID indicates
        that the module last restart was
        a Cold RESTART
        "
	  ::= { pmc2002DwlrestartProcess 2 }



pmc2002DwlWarmRestartProcessed OBJECT-TYPE
	  SYNTAX EkiOnOff
	  MAX-ACCESS read-only
	  STATUS current
	  DESCRIPTION
        "
        Warm Restart :This OID indicates
        that the module last restart was
        a Warm RESTART
        "
	  ::= { pmc2002DwlrestartProcess 1 }



--- *****************************************************
---     LEAF for the swBanksUsed article
--- *****************************************************
pmc2002DwlswBanksUsed OBJECT IDENTIFIER ::= { pmc2002DwlOther 1 }




pmc2002DwlSwBank2Notempty OBJECT-TYPE
	  SYNTAX EkiOnOff
	  MAX-ACCESS read-only
	  STATUS current
	  DESCRIPTION
        "
        SW bank 2 loaded  :This OID indicates
        a software is loaded in SW bank
        2  <Help>  This status indicates
        if the SW bank 2 contains SW package
        "
	  ::= { pmc2002DwlswBanksUsed 6 }



pmc2002DwlSwBank1Notempty OBJECT-TYPE
	  SYNTAX EkiOnOff
	  MAX-ACCESS read-only
	  STATUS current
	  DESCRIPTION
        "
        SW bank 1 loaded  :This OID indicates
        a software is loaded in SW bank
        1  <Help>  This status indicates
        if the SW bank 1 contains SW package
        "
	  ::= { pmc2002DwlswBanksUsed 5 }



pmc2002DwlSwBank2Used OBJECT-TYPE
	  SYNTAX EkiOnOff
	  MAX-ACCESS read-only
	  STATUS current
	  DESCRIPTION
        "
        SW bank 2 active  :This OID indicates
        the module is working on SW bank
        2  <Help>  This status indicates
        if the SW bank 2 is active or standby
        "
	  ::= { pmc2002DwlswBanksUsed 2 }



pmc2002DwlSwBank1Used OBJECT-TYPE
	  SYNTAX EkiOnOff
	  MAX-ACCESS read-only
	  STATUS current
	  DESCRIPTION
        "
        SW bank 1 active  :This OID indicates
        the module is working on SW bank
        1  <Help>  This status indicates
        if the SW bank 1 is active or standby
        "
	  ::= { pmc2002DwlswBanksUsed 1 }



--- *****************************************************
---     LEAF for the gwBanksUsed article
--- *****************************************************
pmc2002DwlgwBanksUsed OBJECT IDENTIFIER ::= { pmc2002DwlOther 2 }




pmc2002DwlGwBank4Notempty OBJECT-TYPE
	  SYNTAX EkiOnOff
	  MAX-ACCESS read-only
	  STATUS deprecated
	  DESCRIPTION
        "
        GW bank 4 loaded  :This OID indicates
        a gateware is loaded in GW bank
        4
        "
	  ::= { pmc2002DwlgwBanksUsed 8 }



pmc2002DwlGwBank3Notempty OBJECT-TYPE
	  SYNTAX EkiOnOff
	  MAX-ACCESS read-only
	  STATUS current
	  DESCRIPTION
        "
        GW bank 3 loaded  :This OID indicates
        a gateware is loaded in GW bank
        3  <Help>  This status indicates
        if the GW bank 3 contains GW package
        "
	  ::= { pmc2002DwlgwBanksUsed 7 }



pmc2002DwlGwBank2Notempty OBJECT-TYPE
	  SYNTAX EkiOnOff
	  MAX-ACCESS read-only
	  STATUS deprecated
	  DESCRIPTION
        "
        GW bank 2 loaded  :This OID indicates
        a gateware is loaded in GW bank
        2
        "
	  ::= { pmc2002DwlgwBanksUsed 6 }



pmc2002DwlGwBank1Notempty OBJECT-TYPE
	  SYNTAX EkiOnOff
	  MAX-ACCESS read-only
	  STATUS current
	  DESCRIPTION
        "
        GW bank 1 loaded  :This OID indicates
        a gateware is loaded in GW bank
        1  <Help>  This status indicates
        if the GW bank 1 contains GW package
        "
	  ::= { pmc2002DwlgwBanksUsed 5 }



pmc2002DwlGwBank4Used OBJECT-TYPE
	  SYNTAX EkiOnOff
	  MAX-ACCESS read-only
	  STATUS deprecated
	  DESCRIPTION
        "
        GW bank 4 active  :This OID indicates
        the module is working on GW bank
        4
        "
	  ::= { pmc2002DwlgwBanksUsed 4 }



pmc2002DwlGwBank3Used OBJECT-TYPE
	  SYNTAX EkiOnOff
	  MAX-ACCESS read-only
	  STATUS current
	  DESCRIPTION
        "
        GW bank 3 active  :This OID indicates
        the module is working on GW bank
        3  <Help>  This status indicates
        if the GW bank 3 is active or standby
        "
	  ::= { pmc2002DwlgwBanksUsed 3 }



pmc2002DwlGwBank2Used OBJECT-TYPE
	  SYNTAX EkiOnOff
	  MAX-ACCESS read-only
	  STATUS deprecated
	  DESCRIPTION
        "
        GW bank 2 active  :This OID indicates
        the module is working on GW bank
        2
        "
	  ::= { pmc2002DwlgwBanksUsed 2 }



pmc2002DwlGwBank1Used OBJECT-TYPE
	  SYNTAX EkiOnOff
	  MAX-ACCESS read-only
	  STATUS current
	  DESCRIPTION
        "
        GW bank 1 active  :This OID indicates
        the module is working on GW bank
        1  <Help>  This status indicates
        if the GW bank 1 is active or standby
        "
	  ::= { pmc2002DwlgwBanksUsed 1 }








--- *****************************************************
--- $$$$$$$$$$$$$$$$$$$$$$$$$$$$$$$$$$$$$$$$$$$$$$$$$$$$$
---     CONFIG
--- $$$$$$$$$$$$$$$$$$$$$$$$$$$$$$$$$$$$$$$$$$$$$$$$$$$$$
--- *****************************************************



--- *****************************************************
---     LEAF for the table Group accessCAisCsf
--- *****************************************************

pmc2002CfgAccessCAisCsf OBJECT IDENTIFIER ::= { pmc2002Config 1 }



--- *****************************************************
---     LEAF for the table 0012
--- *****************************************************

pmc2002CfgClientcaiscsfTable OBJECT-TYPE
	SYNTAX  SEQUENCE OF Pmc2002CfgClientcaiscsfEntry
	MAX-ACCESS not-accessible
	STATUS current
	DESCRIPTION
        "
        List of  Article
        "
	::= { pmc2002CfgAccessCAisCsf 1 }


pmc2002CfgClientcaiscsfEntry OBJECT-TYPE
	SYNTAX Pmc2002CfgClientcaiscsfEntry
	MAX-ACCESS not-accessible
	STATUS current
	DESCRIPTION
        "
        Row definition for the accessCAisCsf
        table
        "
	INDEX   { pmc2002CfgClientcaiscsfIndex }
	::= { pmc2002CfgClientcaiscsfTable 1 }


Pmc2002CfgClientcaiscsfEntry ::=
	SEQUENCE {
	pmc2002CfgClientcaiscsfIndex
		INTEGER,
	pmc2002CfgCAisModePortn
		Unsigned32,
	pmc2002CfgUpAccessioAlmPortn
		Unsigned32,
	pmc2002CfgUpMapperDeAlmPortn
		Unsigned32,
	pmc2002CfgDownAccessioAlmPortn
		Unsigned32,
	pmc2002CfgDownMapperDeAlmPortn
		Unsigned32,
	pmc2002CfgDownDfrmAlmPortn
		Unsigned32,
	pmc2002CfgDownLineSyncAlarmsPortn
		Unsigned32
	}


pmc2002CfgClientcaiscsfIndex OBJECT-TYPE
	SYNTAX  INTEGER(0..128)
	MAX-ACCESS  read-only
	STATUS current
	DESCRIPTION
        "
        Index definition for the clientcaiscsf
        table
        "
	::= { pmc2002CfgClientcaiscsfEntry 1 }


pmc2002CfgCAisModePortn OBJECT-TYPE
	SYNTAX  Unsigned32 (0..65536)
	MAX-ACCESS read-write
	STATUS current
	DESCRIPTION
        "
        CAIS mode  on Client Port :This
        register enables/disables port
          laser shutdown on CAIS insertion
        condition
        "
	::= { pmc2002CfgClientcaiscsfEntry 3 }


pmc2002CfgUpAccessioAlmPortn OBJECT-TYPE
	SYNTAX  Unsigned32 (0..65536)
	MAX-ACCESS read-write
	STATUS current
	DESCRIPTION
        "
        CSF contributors on Client Port
        :This register configures the contributors
        to upstream CSF insertion on the
        port.
        "
	::= { pmc2002CfgClientcaiscsfEntry 9 }


pmc2002CfgUpMapperDeAlmPortn OBJECT-TYPE
	SYNTAX  Unsigned32 (0..65536)
	MAX-ACCESS read-write
	STATUS current
	DESCRIPTION
        "
        CSF contributors on Client Port
        :This register configures the contributors
        to upstream CSF insertion on the
        port.
        "
	::= { pmc2002CfgClientcaiscsfEntry 10 }


pmc2002CfgDownAccessioAlmPortn OBJECT-TYPE
	SYNTAX  Unsigned32 (0..65536)
	MAX-ACCESS read-write
	STATUS current
	DESCRIPTION
        "
        CAIS contributors on Client Port
        :This register configures the contributors
        to downstream CAIS insertion on
         port.
        "
	::= { pmc2002CfgClientcaiscsfEntry 17 }


pmc2002CfgDownMapperDeAlmPortn OBJECT-TYPE
	SYNTAX  Unsigned32 (0..65536)
	MAX-ACCESS read-write
	STATUS current
	DESCRIPTION
        "
        CAIS contributors on Client Port
        :This register configures the contributors
        to downstream CAIS insertion on
         port.
        "
	::= { pmc2002CfgClientcaiscsfEntry 18 }


pmc2002CfgDownDfrmAlmPortn OBJECT-TYPE
	SYNTAX  Unsigned32 (0..65536)
	MAX-ACCESS read-write
	STATUS current
	DESCRIPTION
        "
        CAIS contributors on Client Port
        :This register configures the contributors
        to downstream CAIS insertion on
         port.
        "
	::= { pmc2002CfgClientcaiscsfEntry 19 }


pmc2002CfgDownLineSyncAlarmsPortn OBJECT-TYPE
	SYNTAX  Unsigned32 (0..65536)
	MAX-ACCESS read-write
	STATUS deprecated
	DESCRIPTION
        "
        CAIS contributors on Client Port
        :This register configures the contributors
        to downstream CAIS insertion on
         port.
        "
	::= { pmc2002CfgClientcaiscsfEntry 20 }


--- *****************************************************
---     LEAF for the table Group startup
--- *****************************************************

pmc2002CfgStartup OBJECT IDENTIFIER ::= { pmc2002Config 2 }



--- *****************************************************
---     LEAF for the table 2111
--- *****************************************************

pmc2002CfgClientStartupTable OBJECT-TYPE
	SYNTAX  SEQUENCE OF Pmc2002CfgClientStartupEntry
	MAX-ACCESS not-accessible
	STATUS current
	DESCRIPTION
        "
        List of  Article
        "
	::= { pmc2002CfgStartup 1 }


pmc2002CfgClientStartupEntry OBJECT-TYPE
	SYNTAX Pmc2002CfgClientStartupEntry
	MAX-ACCESS not-accessible
	STATUS current
	DESCRIPTION
        "
        Row definition for the startup
        table
        "
	INDEX   { pmc2002CfgClientStartupIndex }
	::= { pmc2002CfgClientStartupTable 1 }


Pmc2002CfgClientStartupEntry ::=
	SEQUENCE {
	pmc2002CfgClientStartupIndex
		INTEGER,
	pmc2002CfgSystConfPortPortn
		Unsigned32,
	pmc2002CfgNetConfPortPortn
		Unsigned32,
	pmc2002CfgPortsOptionsPortn
		Unsigned32
	}


pmc2002CfgClientStartupIndex OBJECT-TYPE
	SYNTAX  INTEGER(0..128)
	MAX-ACCESS  read-only
	STATUS current
	DESCRIPTION
        "
        Index definition for the clientStartup
        table
        "
	::= { pmc2002CfgClientStartupEntry 1 }


pmc2002CfgSystConfPortPortn OBJECT-TYPE
	SYNTAX  Unsigned32 (0..65536)
	MAX-ACCESS read-write
	STATUS current
	DESCRIPTION
        "
        Default Settings on Client Port
        :This  register configures the
         default initialisation settings
        on the port.
        "
	::= { pmc2002CfgClientStartupEntry 3 }


pmc2002CfgNetConfPortPortn OBJECT-TYPE
	SYNTAX  Unsigned32 (0..65536)
	MAX-ACCESS read-write
	STATUS current
	DESCRIPTION
        "
        Default Protocol on Client Port
        :This register configures the default
        initialisation protocol on the
         port.
        "
	::= { pmc2002CfgClientStartupEntry 4 }


pmc2002CfgPortsOptionsPortn OBJECT-TYPE
	SYNTAX  Unsigned32 (0..65536)
	MAX-ACCESS read-write
	STATUS current
	DESCRIPTION
        "
        Default Options on Client Port
        :This register configures the default
        options on the client port
        "
	::= { pmc2002CfgClientStartupEntry 6 }


--- *****************************************************
---     LEAF for the table 2191
--- *****************************************************

pmc2002tablelineStartup OBJECT IDENTIFIER ::= { pmc2002CfgStartup 2 }



pmc2002CfgsynthTransLine1 OBJECT-TYPE
	  SYNTAX Unsigned32 (0..65536)
	  MAX-ACCESS read-write
	  STATUS current
	  DESCRIPTION
        "
        Default Settings on Line 1 :This
        register configures the default
        initialisation settings on Line
        port 1.
        "
	  ::= { pmc2002tablelineStartup 2 }



pmc2002CfgnetConfMod OBJECT-TYPE
	  SYNTAX Unsigned32 (0..65536)
	  MAX-ACCESS read-write
	  STATUS current
	  DESCRIPTION
        "
        Default Protocol on Module :This
        register configures the default
        initialisation protocol on the
         module.
        "
	  ::= { pmc2002tablelineStartup 3 }



pmc2002CfglineOptions1 OBJECT-TYPE
	  SYNTAX Unsigned32 (0..65536)
	  MAX-ACCESS read-write
	  STATUS current
	  DESCRIPTION
        "
        Default Options on Active Line
        Port :This register configures
         the default options on the active
        line port
        "
	  ::= { pmc2002tablelineStartup 5 }



pmc2002CfgsystTransLine2 OBJECT-TYPE
	  SYNTAX Unsigned32 (0..65536)
	  MAX-ACCESS read-write
	  STATUS current
	  DESCRIPTION
        "
        Default Settings on Line 2 :This
        register configures the default
        initialisation settings on Line
        port 2.
        "
	  ::= { pmc2002tablelineStartup 6 }



pmc2002CfglineSelection OBJECT-TYPE
	  SYNTAX Unsigned32 (0..65536)
	  MAX-ACCESS read-write
	  STATUS current
	  DESCRIPTION
        "
        Default Settings of active line
        :This  register configures the
         start up active line.
        "
	  ::= { pmc2002tablelineStartup 7 }



--- *****************************************************
---     LEAF for the table 21AB
--- *****************************************************

pmc2002CfgXfpTable OBJECT-TYPE
	SYNTAX  SEQUENCE OF Pmc2002CfgXfpEntry
	MAX-ACCESS not-accessible
	STATUS current
	DESCRIPTION
        "
        List of  Article
        "
	::= { pmc2002CfgStartup 3 }


pmc2002CfgXfpEntry OBJECT-TYPE
	SYNTAX Pmc2002CfgXfpEntry
	MAX-ACCESS not-accessible
	STATUS current
	DESCRIPTION
        "
        Row definition for the startup
        table
        "
	INDEX   { pmc2002CfgXfpIndex }
	::= { pmc2002CfgXfpTable 1 }


Pmc2002CfgXfpEntry ::=
	SEQUENCE {
	pmc2002CfgXfpIndex
		INTEGER,
	pmc2002CfgSystConfXfpPortn
		Unsigned32,
	pmc2002CfgDataRateConfXfpPortn
		Unsigned32
	}


pmc2002CfgXfpIndex OBJECT-TYPE
	SYNTAX  INTEGER(0..128)
	MAX-ACCESS  read-only
	STATUS current
	DESCRIPTION
        "
        Index definition for the xfp table
        "
	::= { pmc2002CfgXfpEntry 1 }


pmc2002CfgSystConfXfpPortn OBJECT-TYPE
	SYNTAX  Unsigned32 (0..65536)
	MAX-ACCESS read-write
	STATUS current
	DESCRIPTION
        "
        Default settings on XFP Port :This
        register configures the default
        initialisation settings on XFP
         port.
        "
	::= { pmc2002CfgXfpEntry 3 }


pmc2002CfgDataRateConfXfpPortn OBJECT-TYPE
	SYNTAX  Unsigned32 (0..65536)
	MAX-ACCESS read-write
	STATUS deprecated
	DESCRIPTION
        "
        :Reserved
        "
	::= { pmc2002CfgXfpEntry 4 }


--- *****************************************************
---     LEAF for the table 25AB
--- *****************************************************

pmc2002CfgOtxtlhTable OBJECT-TYPE
	SYNTAX  SEQUENCE OF Pmc2002CfgOtxtlhEntry
	MAX-ACCESS not-accessible
	STATUS current
	DESCRIPTION
        "
        List of  Article
        "
	::= { pmc2002CfgStartup 4 }


pmc2002CfgOtxtlhEntry OBJECT-TYPE
	SYNTAX Pmc2002CfgOtxtlhEntry
	MAX-ACCESS not-accessible
	STATUS current
	DESCRIPTION
        "
        Row definition for the startup
        table
        "
	INDEX   { pmc2002CfgOtxtlhIndex }
	::= { pmc2002CfgOtxtlhTable 1 }


Pmc2002CfgOtxtlhEntry ::=
	SEQUENCE {
	pmc2002CfgOtxtlhIndex
		INTEGER,
	pmc2002CfgLineDitherRatePortn
		Unsigned32,
	pmc2002CfgLineDitherFhzPortn
		Unsigned32,
	pmc2002CfgLinePwrLaserPortn
		Unsigned32,
	pmc2002CfgFPortn
		Unsigned32,
	pmc2002CfgReservedPortn
		Unsigned32,
	pmc2002CfgLinePhotodiodeModePortn
		Unsigned32,
	pmc2002CfgLinePhotodiodeValuePortn
		Unsigned32
	}


pmc2002CfgOtxtlhIndex OBJECT-TYPE
	SYNTAX  INTEGER(0..128)
	MAX-ACCESS  read-only
	STATUS current
	DESCRIPTION
        "
        Index definition for the otxtlh
        table
        "
	::= { pmc2002CfgOtxtlhEntry 1 }


pmc2002CfgLineDitherRatePortn OBJECT-TYPE
	SYNTAX  Unsigned32 (0..65536)
	MAX-ACCESS read-write
	STATUS current
	DESCRIPTION
        "
        Default Line OTX TLH FM amplitude
        :This register configures the start-up
        width of the frequency modulation
        of the Line OTX TLH
        "
	::= { pmc2002CfgOtxtlhEntry 4 }


pmc2002CfgLineDitherFhzPortn OBJECT-TYPE
	SYNTAX  Unsigned32 (0..65536)
	MAX-ACCESS read-write
	STATUS current
	DESCRIPTION
        "
        Default Line OTX TLH FM frequency
        :This register configures the start-up
        frequency of the frequency modulation
        of the Line OTX TLH
        "
	::= { pmc2002CfgOtxtlhEntry 5 }


pmc2002CfgLinePwrLaserPortn OBJECT-TYPE
	SYNTAX  Unsigned32 (0..65536)
	MAX-ACCESS read-write
	STATUS current
	DESCRIPTION
        "
        Defaut Line OTX TLH output Power
        :This register configures the start-up
        output power of the Line OTX TLH
         (Unit = dBm)
        "
	::= { pmc2002CfgOtxtlhEntry 6 }


pmc2002CfgFPortn OBJECT-TYPE
	SYNTAX  Unsigned32 (0..65536)
	MAX-ACCESS read-write
	STATUS current
	DESCRIPTION
        "
        Default Line OTX TLH lowest Freq
        :This register configures the start-up
        lowest frequency supported on the
        Line OTX TLH
        "
	::= { pmc2002CfgOtxtlhEntry 9 }


pmc2002CfgReservedPortn OBJECT-TYPE
	SYNTAX  Unsigned32 (0..65536)
	MAX-ACCESS read-write
	STATUS deprecated
	DESCRIPTION
        "
        :
        "
	::= { pmc2002CfgOtxtlhEntry 10 }


pmc2002CfgLinePhotodiodeModePortn OBJECT-TYPE
	SYNTAX  Unsigned32 (0..65536)
	MAX-ACCESS read-write
	STATUS current
	DESCRIPTION
        "
        Default Line OTX TLH APD mode
         :This register configures the
         start-up APD mode of the Line
         OTX TLH
        "
	::= { pmc2002CfgOtxtlhEntry 11 }


pmc2002CfgLinePhotodiodeValuePortn OBJECT-TYPE
	SYNTAX  Unsigned32 (0..65536)
	MAX-ACCESS read-write
	STATUS current
	DESCRIPTION
        "
        Default Line OTX TLH APD atten.
        :This register configures the start-up
        APD attenuation on the Line OTX
        TLH
        "
	::= { pmc2002CfgOtxtlhEntry 12 }


--- *****************************************************
---     LEAF for the table 25A8
--- *****************************************************

pmc2002CfgOtxtlhCommonTable OBJECT-TYPE
	SYNTAX  SEQUENCE OF Pmc2002CfgOtxtlhCommonEntry
	MAX-ACCESS not-accessible
	STATUS current
	DESCRIPTION
        "
        List of  Article
        "
	::= { pmc2002CfgStartup 5 }


pmc2002CfgOtxtlhCommonEntry OBJECT-TYPE
	SYNTAX Pmc2002CfgOtxtlhCommonEntry
	MAX-ACCESS not-accessible
	STATUS current
	DESCRIPTION
        "
        Row definition for the startup
        table
        "
	INDEX   { pmc2002CfgOtxtlhCommonIndex }
	::= { pmc2002CfgOtxtlhCommonTable 1 }


Pmc2002CfgOtxtlhCommonEntry ::=
	SEQUENCE {
	pmc2002CfgOtxtlhCommonIndex
		INTEGER,
	pmc2002CfgLineFCurrentPortn
		Unsigned32,
	pmc2002CfgLineGridCurrentPortn
		Unsigned32
	}


pmc2002CfgOtxtlhCommonIndex OBJECT-TYPE
	SYNTAX  INTEGER(0..128)
	MAX-ACCESS  read-only
	STATUS current
	DESCRIPTION
        "
        Index definition for the otxtlhCommon
        table
        "
	::= { pmc2002CfgOtxtlhCommonEntry 1 }


pmc2002CfgLineFCurrentPortn OBJECT-TYPE
	SYNTAX  Unsigned32 (0..65536)
	MAX-ACCESS read-write
	STATUS current
	DESCRIPTION
        "
        Default Line OTX TLH Channel :This
        register configures the start-up
        laser channel of the Line OTX TLH
        "
	::= { pmc2002CfgOtxtlhCommonEntry 7 }


pmc2002CfgLineGridCurrentPortn OBJECT-TYPE
	SYNTAX  Unsigned32 (0..65536)
	MAX-ACCESS read-write
	STATUS current
	DESCRIPTION
        "
        Default Line OTX TLH Grid :This
        register configures the start-up
        laser grid of the Line OTX TLH
        "
	::= { pmc2002CfgOtxtlhCommonEntry 8 }


--- *****************************************************
---     LEAF for the table Group labels
--- *****************************************************

pmc2002CfgLabels OBJECT IDENTIFIER ::= { pmc2002Config 3 }



--- *****************************************************
---     LEAF for the table NO_VALUE
--- *****************************************************

pmc2002CfgLabelclientTable OBJECT-TYPE
	SYNTAX  SEQUENCE OF Pmc2002CfgLabelclientEntry
	MAX-ACCESS not-accessible
	STATUS current
	DESCRIPTION
        "
        List of  Article
        "
	::= { pmc2002CfgLabels 1 }


pmc2002CfgLabelclientEntry OBJECT-TYPE
	SYNTAX Pmc2002CfgLabelclientEntry
	MAX-ACCESS not-accessible
	STATUS current
	DESCRIPTION
        "
        Row definition for the labels
         table
        "
	INDEX   { pmc2002CfgLabelclientIndex }
	::= { pmc2002CfgLabelclientTable 1 }


Pmc2002CfgLabelclientEntry ::=
	SEQUENCE {
	pmc2002CfgLabelclientIndex
		INTEGER,
	pmc2002CfgLabelclientPortn
		DisplayString
	}


pmc2002CfgLabelclientIndex OBJECT-TYPE
	SYNTAX  INTEGER(0..128)
	MAX-ACCESS  read-only
	STATUS current
	DESCRIPTION
        "
        Index definition for the labelclient
        table
        "
	::= { pmc2002CfgLabelclientEntry 1 }


pmc2002CfgLabelclientPortn OBJECT-TYPE
	SYNTAX  DisplayString( SIZE(1..16))
	MAX-ACCESS read-write
	STATUS current
	DESCRIPTION
        "
        Default settings on the label
         of the Ports :These registers
         configures the default initialisation
        settings of the labels of the ports.
        "
	::= { pmc2002CfgLabelclientEntry 3 }


--- *****************************************************
---     LEAF for the table NO_VALUE
--- *****************************************************

pmc2002CfgLabellineTable OBJECT-TYPE
	SYNTAX  SEQUENCE OF Pmc2002CfgLabellineEntry
	MAX-ACCESS not-accessible
	STATUS current
	DESCRIPTION
        "
        List of  Article
        "
	::= { pmc2002CfgLabels 2 }


pmc2002CfgLabellineEntry OBJECT-TYPE
	SYNTAX Pmc2002CfgLabellineEntry
	MAX-ACCESS not-accessible
	STATUS current
	DESCRIPTION
        "
        Row definition for the labels
         table
        "
	INDEX   { pmc2002CfgLabellineIndex }
	::= { pmc2002CfgLabellineTable 1 }


Pmc2002CfgLabellineEntry ::=
	SEQUENCE {
	pmc2002CfgLabellineIndex
		INTEGER,
	pmc2002CfgLabellinePortn
		DisplayString
	}


pmc2002CfgLabellineIndex OBJECT-TYPE
	SYNTAX  INTEGER(0..128)
	MAX-ACCESS  read-only
	STATUS current
	DESCRIPTION
        "
        Index definition for the labelline
        table
        "
	::= { pmc2002CfgLabellineEntry 1 }


pmc2002CfgLabellinePortn OBJECT-TYPE
	SYNTAX  DisplayString( SIZE(1..16))
	MAX-ACCESS read-write
	STATUS current
	DESCRIPTION
        "
        Default settings on the label
         of the lines :These registers
         configures the default initialisation
        settings of the labels of the lines.
        "
	::= { pmc2002CfgLabellineEntry 3 }


--- *****************************************************
---     LEAF for the table Group other
--- *****************************************************

pmc2002CfgOther OBJECT IDENTIFIER ::= { pmc2002Config 4 }



--- *****************************************************
---     LEAF for the table 2300
--- *****************************************************

pmc2002tablemoduleOther OBJECT IDENTIFIER ::= { pmc2002CfgOther 1 }



pmc2002Cfgmode OBJECT-TYPE
	  SYNTAX Unsigned32 (0..65536)
	  MAX-ACCESS read-write
	  STATUS current
	  DESCRIPTION
        "
        Default settings on Module :This
        register selects the DCC  configuration
        of the PM
        "
	  ::= { pmc2002tablemoduleOther 2 }



--- *****************************************************
---     LEAF for the table Group startuptablefive
--- *****************************************************

pmc2002CfgStartuptablefive OBJECT IDENTIFIER ::= { pmc2002Config 5 }



--- *****************************************************
---     LEAF for the table 0005
--- *****************************************************

pmc2002CfgOtxtlhcapabilitiesTable OBJECT-TYPE
	SYNTAX  SEQUENCE OF Pmc2002CfgOtxtlhcapabilitiesEntry
	MAX-ACCESS not-accessible
	STATUS current
	DESCRIPTION
        "
        List of  Article
        "
	::= { pmc2002CfgStartuptablefive 1 }


pmc2002CfgOtxtlhcapabilitiesEntry OBJECT-TYPE
	SYNTAX Pmc2002CfgOtxtlhcapabilitiesEntry
	MAX-ACCESS not-accessible
	STATUS current
	DESCRIPTION
        "
        Row definition for the startuptablefive
        table
        "
	INDEX   { pmc2002CfgOtxtlhcapabilitiesIndex }
	::= { pmc2002CfgOtxtlhcapabilitiesTable 1 }


Pmc2002CfgOtxtlhcapabilitiesEntry ::=
	SEQUENCE {
	pmc2002CfgOtxtlhcapabilitiesIndex
		INTEGER,
	pmc2002CfgComponentTypePortn
		Unsigned32,
	pmc2002CfgMiscellaneousPortn
		Unsigned32,
	pmc2002CfgFirstChannelPortn
		Unsigned32,
	pmc2002CfgLastChannelPortn
		Unsigned32,
	pmc2002CfgGridPortn
		Unsigned32
	}


pmc2002CfgOtxtlhcapabilitiesIndex OBJECT-TYPE
	SYNTAX  INTEGER(0..128)
	MAX-ACCESS  read-only
	STATUS current
	DESCRIPTION
        "
        Index definition for the otxtlhcapabilities
        table
        "
	::= { pmc2002CfgOtxtlhcapabilitiesEntry 1 }


pmc2002CfgComponentTypePortn OBJECT-TYPE
	SYNTAX  Unsigned32 (0..65536)
	MAX-ACCESS read-only
	STATUS current
	DESCRIPTION
        "
        Component parameters :This OID
        defines the component parameters
        "
	::= { pmc2002CfgOtxtlhcapabilitiesEntry 3 }


pmc2002CfgMiscellaneousPortn OBJECT-TYPE
	SYNTAX  Unsigned32 (0..65536)
	MAX-ACCESS read-only
	STATUS current
	DESCRIPTION
        "
        Miscellaneous default settings
        :This OID defines the miscellaneous
        parameters
        "
	::= { pmc2002CfgOtxtlhcapabilitiesEntry 4 }


pmc2002CfgFirstChannelPortn OBJECT-TYPE
	SYNTAX  Unsigned32 (0..65536)
	MAX-ACCESS read-only
	STATUS current
	DESCRIPTION
        "
        Number of the first channel of
        the component :This OID defines
        the first channel number of the
        PM
        "
	::= { pmc2002CfgOtxtlhcapabilitiesEntry 5 }


pmc2002CfgLastChannelPortn OBJECT-TYPE
	SYNTAX  Unsigned32 (0..65536)
	MAX-ACCESS read-only
	STATUS current
	DESCRIPTION
        "
        Number of the last channel of
         the component :This OID defines
        the last channel number of the
         PM
        "
	::= { pmc2002CfgOtxtlhcapabilitiesEntry 6 }


pmc2002CfgGridPortn OBJECT-TYPE
	SYNTAX  Unsigned32 (0..65536)
	MAX-ACCESS read-only
	STATUS current
	DESCRIPTION
        "
        Grid value of the component :This
        OID defines the grid of the PM
        "
	::= { pmc2002CfgOtxtlhcapabilitiesEntry 7 }



pmc2002CfgWriteConfiguration  OBJECT-TYPE
	SYNTAX EkiOnOff
	MAX-ACCESS read-write
	STATUS current
	DESCRIPTION
	"Write configuration to module:This OID
	 writes the complete configuration to the module"
	::= { pmc2002Config 257 }






--- *****************************************************
---     TRAP OBJECTS
--- *****************************************************


pmc2002trapBoardNumber OBJECT-TYPE
	SYNTAX INTEGER(1..64)
	MAX-ACCESS read-only
	STATUS current
	DESCRIPTION
	"Last module which generates a trap"
	::= { pmc2002traps 1 }



pmc2002trapClientNumber OBJECT-TYPE
	SYNTAX INTEGER(1..64)
	MAX-ACCESS read-only
	STATUS current
	DESCRIPTION
	"Last module which generates a trap"
	::= { pmc2002traps 2 }



pmc2002trapLineNumber OBJECT-TYPE
	SYNTAX INTEGER(1..64)
	MAX-ACCESS read-only
	STATUS current
	DESCRIPTION
	"Last module which generates a trap"
	::= { pmc2002traps 3 }







--- *****************************************************
---     LINE TRAPS
--- *****************************************************

pmc2002LineTrapNotUrgentGoesOn NOTIFICATION-TYPE
	OBJECTS {pmc2002AlmLineDdmWarningPortn, pmc2002trapLineNumber, pmc2002trapBoardNumber}
	STATUS current
	--&FILTNAME    "PM C2002 Line Not Urgent ON"
	--&ACTIONS     { log, minor }
	--&MATCH       { pmc2002AlmLineDdmWarningPortn "on", pmc2002trapLineNumber "$2", pmc2002trapBoardNumber "$3"}
	--&MESG        "DDM Warning appears on Line Port $2 of PM C2002 in Slot $3 ($A)"
	DESCRIPTION "Not urgent Line default is activated"
	::= { pmc2002traps 30 }

pmc2002LineTrapNotUrgentGoesOff NOTIFICATION-TYPE
	OBJECTS {pmc2002AlmLineDdmWarningPortn, pmc2002trapLineNumber, pmc2002trapBoardNumber}
	STATUS current
	--&FILTNAME    "PM C2002 Line Not Urgent OFF"
	--&ACTIONS     { log, normal }
	--&CLEARS      { "PM C2002 Line Not Urgent ON" }
	--&MATCH       { pmc2002AlmLineDdmWarningPortn "on", pmc2002trapLineNumber "$2", pmc2002trapBoardNumber "$3"}
	--&MESG        "DDM Warning disappears on Line Port $2 of PM C2002 in Slot $3 ($A)"
	DESCRIPTION "Not urgent Line default disappeared"
	::= { pmc2002traps 31 }

pmc2002LineTrapUrgentGoesOn NOTIFICATION-TYPE
	OBJECTS {pmc2002AlmLineDdmAlmPortn, pmc2002trapLineNumber, pmc2002trapBoardNumber}
	STATUS current
	--&FILTNAME    "PM C2002 Line Urgent ON"
	--&ACTIONS     { log, major }
	--&MATCH       { pmc2002AlmLineDdmAlmPortn "on", pmc2002trapLineNumber "$2", pmc2002trapBoardNumber "$3"}
	--&MESG        "DDM Alarm appears on Line Port $2 of PM C2002 in Slot $3 ($A)"
	DESCRIPTION "Urgent Line default is activated"
	::= { pmc2002traps 32 }

pmc2002LineTrapUrgentGoesOff NOTIFICATION-TYPE
	OBJECTS {pmc2002AlmLineDdmAlmPortn, pmc2002trapLineNumber, pmc2002trapBoardNumber}
	STATUS current
	--&FILTNAME    "PM C2002 Line Urgent OFF"
	--&ACTIONS     { log, normal }
	--&CLEARS      { "PM C2002 Line Urgent ON" }
	--&MATCH       { pmc2002AlmLineDdmAlmPortn "on", pmc2002trapLineNumber "$2", pmc2002trapBoardNumber "$3"}
	--&MESG        "DDM Alarm disappears on Line Port $2 of PM C2002 in Slot $3 ($A)"
	DESCRIPTION "Urgent Line default disappeared"
	::= { pmc2002traps 33 }

pmc2002LineTrapCritGoesOn NOTIFICATION-TYPE
	OBJECTS {pmc2002AlmLineFailPortn , pmc2002AlmLineHwFailPortn, pmc2002trapLineNumber, pmc2002trapBoardNumber}
	STATUS current
	--&FILTNAME    "PM C2002 Line Fail ON"
	--&ACTIONS     { log, critical }
	--&MATCH       { pmc2002AlmLineFailPortn "on", pmc2002AlmLineHwFailPortn "*", pmc2002trapLineNumber "$3", pmc2002trapBoardNumber "$4"}
	--&MESG        "Line Port $3 Down on PM C2002 in Slot $4 ($A)"

	--&FILTNAME    "PM C2002 Line HW Fail ON (Hidden)"
	--&ACTIONS     { info }
	--&MATCH       { pmc2002AlmLineFailPortn "*", pmc2002AlmLineHwFailPortn "on", pmc2002trapLineNumber "$3", pmc2002trapBoardNumber "$4"}
	--&MESG        "Line Port $3 Down on PM C2002 in Slot $4 ($A)"
	DESCRIPTION "Critical Line default is activated"
	::= { pmc2002traps 34 }

pmc2002LineTrapCritGoesOff NOTIFICATION-TYPE
	OBJECTS {pmc2002AlmLineFailPortn , pmc2002AlmLineHwFailPortn, pmc2002trapLineNumber, pmc2002trapBoardNumber}
	STATUS current
	--&FILTNAME    "PM C2002 Line Fail OFF"
	--&ACTIONS     { log,  normal }
	--&CLEARS      { "PM C2002 Line Fail ON" }
	--&MATCH       { pmc2002AlmLineFailPortn "on", pmc2002AlmLineHwFailPortn "*", pmc2002trapLineNumber "$3", pmc2002trapBoardNumber "$4"}
	--&MESG        "Line Port $3 Up on PM C2002 in Slot $4 ($A)"

	--&FILTNAME    "PM C2002 Line HW Fail OFF (Hidden)"
	--&ACTIONS     { info }
	--&MATCH       { pmc2002AlmLineFailPortn "*", pmc2002AlmLineHwFailPortn "on", pmc2002trapLineNumber "$3", pmc2002trapBoardNumber "$4"}
	--&MESG        "Line Port $3 Up on PM C2002 in Slot $4 ($A)"
	DESCRIPTION "Critical Line default disappeared"
	::= { pmc2002traps 35 }






--- *****************************************************
---     CLIENT TRAPS
--- *****************************************************

pmc2002ClientTrapNotUrgentGoesOn NOTIFICATION-TYPE
	OBJECTS {pmc2002AlmClientSfpDdmWarningPortn, pmc2002trapClientNumber, pmc2002trapBoardNumber}
	STATUS current
	--&FILTNAME    "PM C2002 Client Not Urgent ON"
	--&ACTIONS     { log, minor }
	--&MATCH       { pmc2002AlmClientSfpDdmWarningPortn "on", pmc2002trapClientNumber "$2", pmc2002trapBoardNumber "$3"}
	--&MESG        "DDM Warning appears on Client Port $2 of PM C2002 in Slot $3 ($A)"
	DESCRIPTION "Not urgent client default is activated"
	::= { pmc2002traps 40 }

pmc2002ClientTrapNotUrgentGoesOff NOTIFICATION-TYPE
	OBJECTS {pmc2002AlmClientSfpDdmWarningPortn, pmc2002trapClientNumber, pmc2002trapBoardNumber}
	STATUS current
	--&FILTNAME    "PM C2002 Client Not Urgent OFF"
	--&ACTIONS     { log, normal }
	--&CLEARS      { "PM C2002 Client Not Urgent ON" }
	--&MATCH       { pmc2002AlmClientSfpDdmWarningPortn "on", pmc2002trapClientNumber "$2", pmc2002trapBoardNumber "$3"}
	--&MESG        "DDM Warning appears on Client Port $2 of PM C2002 in Slot $3 ($A)"
	DESCRIPTION "Not urgent client default disappeared"
	::= { pmc2002traps 41 }

pmc2002ClientTrapUrgentGoesOn NOTIFICATION-TYPE
	OBJECTS {pmc2002AlmClientSfpDdmAlmPortn, pmc2002trapClientNumber, pmc2002trapBoardNumber}
	STATUS current
	--&FILTNAME    "PM C2002 Client Urgent ON"
	--&ACTIONS     { log, major }
	--&MATCH       { pmc2002AlmClientSfpDdmAlmPortn "on", pmc2002trapClientNumber "$2", pmc2002trapBoardNumber "$3"}
	--&MESG        "DDM Alarm appears on Client Port $2 of PM C2002 in Slot $3 ($A)"
	DESCRIPTION "Urgent client default is activated"
	::= { pmc2002traps 42 }

pmc2002ClientTrapUrgentGoesOff NOTIFICATION-TYPE
	OBJECTS {pmc2002AlmClientSfpDdmAlmPortn, pmc2002trapClientNumber, pmc2002trapBoardNumber}
	STATUS current
	--&FILTNAME    "PM C2002 Client Urgent OFF"
	--&ACTIONS     { log, normal }
	--&CLEARS      { "PM C2002 Client Urgent ON" }
	--&MATCH       { pmc2002AlmClientSfpDdmAlmPortn "on", pmc2002trapClientNumber "$2", pmc2002trapBoardNumber "$3"}
	--&MESG        "DDM Alarm disappears on Client Port $2 of PM C2002 in Slot $3 ($A)"
	DESCRIPTION "Urgent client default disappeared"
	::= { pmc2002traps 43 }

pmc2002ClientTrapCritGoesOn NOTIFICATION-TYPE
	OBJECTS {pmc2002AlmClientFailPortn, pmc2002AlmClientHwFailPortn, pmc2002trapClientNumber,pmc2002trapBoardNumber}
	STATUS current
	--&FILTNAME    "PM C2002 Client Fail ON"
	--&ACTIONS     { log, critical }
	--&MATCH       { pmc2002AlmClientFailPortn "on", pmc2002AlmClientHwFailPortn "*", pmc2002trapClientNumber "$3", pmc2002trapBoardNumber "$4"}
	--&MESG        "Client Port $3 Down on PM C2002 in Slot $4 ($A)"

	--&FILTNAME    "PM C2002 Client HW Fail ON (Hidden)"
	--&ACTIONS     { info }
	--&MATCH       { pmc2002AlmClientFailPortn "*", pmc2002AlmClientHwFailPortn "on", pmc2002trapClientNumber "$3", pmc2002trapBoardNumber "$4"}
	--&MESG        "Client Port $3 Down on PM C2002 in Slot $4 ($A)"
	DESCRIPTION "Critical client default is activated"
	::= { pmc2002traps 44 }

pmc2002ClientTrapCritGoesOff NOTIFICATION-TYPE
	OBJECTS {pmc2002AlmClientFailPortn, pmc2002AlmClientHwFailPortn, pmc2002trapClientNumber, pmc2002trapBoardNumber}
	STATUS current
	--&FILTNAME    "PM C2002 Client Fail OFF"
	--&ACTIONS     { log, normal }
	--&CLEARS      { "PM C2002 Client Fail ON" }
	--&MATCH       { pmc2002AlmClientFailPortn "on", pmc2002AlmClientHwFailPortn "*", pmc2002trapClientNumber "$3", pmc2002trapBoardNumber "$4"}
	--&MESG        "Client Port $3 Up on PM C2002 in Slot $4 ($A)"

	--&FILTNAME    "PM C2002 Client HW Fail OFF (Hidden)"
	--&ACTIONS     { info }
	--&MATCH       { pmc2002AlmClientFailPortn "*", pmc2002AlmClientHwFailPortn "on", pmc2002trapClientNumber "$3", pmc2002trapBoardNumber "$4"}
	--&MESG        "Client Port $3 Up on PM C2002 in Slot $4 ($A)"
	DESCRIPTION "Critical client default disappeared"
	::= { pmc2002traps 45 }






--- *****************************************************
---     HW TRAPS
--- *****************************************************

pmc2002PowerTrapUrgentGoesOn NOTIFICATION-TYPE
	OBJECTS {pmc2002AlmDefFuseB, pmc2002AlmDefFuseA , pmc2002trapBoardNumber}
	STATUS current
	--&FILTNAME    "PM C2002 Fuse A Fail ON"
	--&ACTIONS     { log, major }
	--&MATCH       { pmc2002AlmDefFuseB "*", pmc2002AlmDefFuseA "on", pmc2002trapBoardNumber "$3"}
	--&MESG        "Power Input A Fail on PM C2002 in Slot $3 ($A)"

	--&FILTNAME    "PM C2002 Fuse B Fail ON"
	--&ACTIONS     { log, major }
	--&MATCH       { pmc2002AlmDefFuseB "on", pmc2002AlmDefFuseA "*", pmc2002trapBoardNumber "$3"}
	--&MESG        "Power Input B Fail on PM C2002 in Slot $3 ($A)"
	DESCRIPTION "Urgent power supply default is activated"
	::= { pmc2002traps 50 }

pmc2002PowerTrapUrgentGoesOff NOTIFICATION-TYPE
	OBJECTS {pmc2002AlmDefFuseB, pmc2002AlmDefFuseA , pmc2002trapBoardNumber}
	STATUS current
	--&FILTNAME    "PM C2002 Fuse A&B Fail OFF"
	--&ACTIONS     { log, normal}
	--&CLEARS      { "PM C2002 Fuse A Fail ON", "PM C2002 Fuse B Fail ON" }
	--&MATCH       { pmc2002AlmDefFuseB "on", pmc2002AlmDefFuseA "on", pmc2002trapBoardNumber "$3"}
	--&MESG        "Power Inputs A and B Present on PM C2002 in Slot $3 ($A)"

	DESCRIPTION "Urgent power supply default disappeared"
	::= { pmc2002traps 51 }






END
