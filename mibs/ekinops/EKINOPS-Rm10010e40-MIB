-- *****************************************************************
-- EKINOPS-Rm10010e40.TXT:  MIB
--
--MIB Part Number:3MI00029AAAF
--MIB Version:02
--
-- Copyright (c) 2016 by Ekinops
-- All rights reserved.
--
-- *****************************************************************

EKINOPS-Rm10010e40-MIB DEFINITIONS ::= BEGIN

IMPORTS
	ekinops,
	EkiState,
	EkiOnOff,
	EkiMode,
	EkiProtocol,
	EkiApiState,
	EkiSynchroMode,
	EkiMeasureType
			FROM EKINOPS-MIB
        MODULE-IDENTITY,
        OBJECT-TYPE,
        NOTIFICATION-TYPE,
	Unsigned32,
	Integer32,
	Counter32,
	IpAddress
        		FROM SNMPv2-SMI
 	TEXTUAL-CONVENTION,
	DisplayString
                FROM SNMPv2-TC;

moduleRm10010e40 MODULE-IDENTITY
        LAST-UPDATED "201606020000Z"
        ORGANIZATION "Ekinops"
        CONTACT-INFO
         "Ekinops

          3, rue Blaise Pascal
          F-22300 Lannion / FRANCE

          Tel : +33 (0)2 96 05 00 30
          Fax : +33 (0)2 96 48 62 39

          E-mail: support@ekinops.fr"
        DESCRIPTION
          "Creation."

	REVISION "201303040000Z"
	DESCRIPTION
	  "Creation for 100GE40"
	REVISION "201306110000Z"
	DESCRIPTION
	  "Creation for 100GE40"
	REVISION "201401160000Z"
	DESCRIPTION
	  "Add ProbCause on CSF detected"
	REVISION "201404010000Z"
	DESCRIPTION
	  "Probcause,AlarmType - NMS completion"
	REVISION "201410140000Z"
	DESCRIPTION
	  "OSNR help completion"
	REVISION "201501220000Z"
	DESCRIPTION
	  "Labels cosmetic updates"
	REVISION "201510210000Z"
	DESCRIPTION
	  "Add F0 objet"
	REVISION "201605200000Z"
	DESCRIPTION
	  "New AlarmType – synthesisAlarm (12)"
	REVISION "201606020000Z"
	DESCRIPTION
	  "Capabilities objects of Table 5"
        ::= { ekinops 57 }



--- *****************************************************
---     LEAF LEVEL 2
--- *****************************************************


rm10010e40alarms OBJECT IDENTIFIER ::= { moduleRm10010e40 2 }
rm10010e40AlmOther OBJECT IDENTIFIER ::= { rm10010e40alarms 1 }
rm10010e40AlmOtherNurg OBJECT IDENTIFIER ::= { rm10010e40AlmOther 1 }
rm10010e40AlmOtherUrg OBJECT IDENTIFIER ::= { rm10010e40AlmOther 2 }
rm10010e40AlmOtherCrit OBJECT IDENTIFIER ::= { rm10010e40AlmOther 3 }

rm10010e40AlmClient OBJECT IDENTIFIER ::= { rm10010e40alarms 2 }
rm10010e40AlmClientNurg OBJECT IDENTIFIER ::= { rm10010e40AlmClient 1 }
rm10010e40AlmClientUrg OBJECT IDENTIFIER ::= { rm10010e40AlmClient 2 }
rm10010e40AlmClientCrit OBJECT IDENTIFIER ::= { rm10010e40AlmClient 3 }

rm10010e40AlmLine OBJECT IDENTIFIER ::= { rm10010e40alarms 3 }
rm10010e40AlmLineNurg OBJECT IDENTIFIER ::= { rm10010e40AlmLine 1 }
rm10010e40AlmLineUrg OBJECT IDENTIFIER ::= { rm10010e40AlmLine 2 }
rm10010e40AlmLineCrit OBJECT IDENTIFIER ::= { rm10010e40AlmLine 3 }





rm10010e40measures OBJECT IDENTIFIER ::= { moduleRm10010e40 3 }
rm10010e40MesrOther OBJECT IDENTIFIER ::= { rm10010e40measures 1 }
rm10010e40MesrClient OBJECT IDENTIFIER ::= { rm10010e40measures 2 }
rm10010e40MesrLine OBJECT IDENTIFIER ::= { rm10010e40measures 3 }




rm10010e40counters OBJECT IDENTIFIER ::= { moduleRm10010e40 4 }
rm10010e40CntOther OBJECT IDENTIFIER ::= { rm10010e40counters 1 }
rm10010e40CntClient OBJECT IDENTIFIER ::= { rm10010e40counters 2 }
rm10010e40CntLine OBJECT IDENTIFIER ::= { rm10010e40counters 3 }


rm10010e40controlsWrite OBJECT IDENTIFIER ::= { moduleRm10010e40 6 }
rm10010e40CtrlOther OBJECT IDENTIFIER ::= { rm10010e40controlsWrite 1 }
rm10010e40CtrlClient OBJECT IDENTIFIER ::= { rm10010e40controlsWrite 2 }
rm10010e40CtrlLine OBJECT IDENTIFIER ::= { rm10010e40controlsWrite 3 }

rm10010e40ri OBJECT IDENTIFIER ::= { moduleRm10010e40 7 }
rm10010e40riTable OBJECT IDENTIFIER ::= { rm10010e40ri 1 }

rm10010e40download OBJECT IDENTIFIER ::= { moduleRm10010e40 8 }
rm10010e40DwlOther OBJECT IDENTIFIER ::= { rm10010e40download 1 }
rm10010e40DwlClient OBJECT IDENTIFIER ::= { rm10010e40download 2 }
rm10010e40DwlLine OBJECT IDENTIFIER ::= { rm10010e40download 3 }


rm10010e40Config OBJECT IDENTIFIER ::= { moduleRm10010e40 9 }

rm10010e40traps OBJECT IDENTIFIER ::= { moduleRm10010e40 10 }



rm10010e40Monitoring OBJECT IDENTIFIER ::= { moduleRm10010e40 11}

rm10010e40MonOther OBJECT IDENTIFIER ::= { rm10010e40Monitoring 1 }
rm10010e40MonRmon OBJECT IDENTIFIER ::= { rm10010e40MonOther 3 }

rm10010e40MonClient OBJECT IDENTIFIER ::= { rm10010e40Monitoring 2 }
rm10010e40MonClientRmonCounter OBJECT IDENTIFIER ::= { rm10010e40MonClient 4 }


--- *****************************************************
--- $$$$$$$$$$$$$$$$$$$$$$$$$$$$$$$$$$$$$$$$$$$$$$$$$$$$$
---     TEXTUAL-CONVENTION
--- $$$$$$$$$$$$$$$$$$$$$$$$$$$$$$$$$$$$$$$$$$$$$$$$$$$$$
--- *****************************************************

Rm10010e40MultiRate ::= TEXTUAL-CONVENTION
    STATUS      current
    DESCRIPTION "different rate for a client port"
    SYNTAX INTEGER {
		rate100Mhz(0),
		rate250Mhz(1),
		rate500Mhz(2),
		rate1Ghz(3)
           }

Rm10010e40OtxMode ::= TEXTUAL-CONVENTION
    STATUS      current
    DESCRIPTION "Different modes on OTX-TLH on client and line ports"
    SYNTAX INTEGER {
		otx80mode(1),
		otx60mode(2),
		otxadjustmode(4)
           }

Rm10010e40OtxGrid ::= TEXTUAL-CONVENTION
    STATUS      current
    DESCRIPTION "Different grids on OTX-TLH on client and line ports"
    SYNTAX INTEGER {
		otxgrid200(200),
		otxgrid100(100),
		otxgrid50(50)
           }

Rm10010e40AdjustValue ::= TEXTUAL-CONVENTION
    STATUS      current
    DESCRIPTION "Different values in Adjust mode on OTX-TLH on client and line ports"
    SYNTAX INTEGER {
		otxadjustvalue0(0),
		otxadjustvalue1(1),
		otxadjustvalue2(2),
		otxadjustvalue3(3),
		otxadjustvalue4(4),
		otxadjustvalue5(5),
		otxadjustvalue6(6),
		otxadjustvalue7(7),
		otxadjustvalue8(8),
		otxadjustvalue9(9),
		otxadjustvalue10(10)
           }

Rm10010e40ClientProtocol ::= TEXTUAL-CONVENTION
    STATUS      current
    DESCRIPTION "Different values on the protocol on the client ports"
    SYNTAX INTEGER {
		protocolclientvalue0(0),
		protocolclientvalue1(1),
		protocolclientvalue2(2),
		protocolclientvalue3(3),
		protocolclientvalue4(4),
		protocolclientvalue5(5),
		protocolclientvalue6(6),
		protocolclientvalue7(7),
		protocolclientvalue8(8)
           }

Rm10010e40ProtocolMode ::= TEXTUAL-CONVENTION
    STATUS      current
    DESCRIPTION "Different values on the protocol mode"
    SYNTAX INTEGER {
		protocolmodevalue0(0),
		protocolmodevalue1(1),
		protocolmodevalue2(2),
		protocolmodevalue3(3)
           }

Rm10010e40OtxChannel ::= TEXTUAL-CONVENTION
    STATUS      current
    DESCRIPTION "Channel selection on transceiver Tx line ports"
    SYNTAX INTEGER

Rm10010e40OrxChannel ::= TEXTUAL-CONVENTION
    STATUS      current
    DESCRIPTION "Channel selection on transceiver Rx line ports"
    SYNTAX INTEGER

--- *****************************************************
--- $$$$$$$$$$$$$$$$$$$$$$$$$$$$$$$$$$$$$$$$$$$$$$$$$$$$$
---     REMOTE INVENTORY
--- $$$$$$$$$$$$$$$$$$$$$$$$$$$$$$$$$$$$$$$$$$$$$$$$$$$$$
--- *****************************************************

rm10010e40RinvReloadInventory OBJECT-TYPE
  SYNTAX EkiOnOff
  MAX-ACCESS read-write
  STATUS current
  DESCRIPTION
        "Reload the inventory: This OID triggers an
         inventory reload."
  ::= { rm10010e40ri 2 }

rm10010e40RinvHwPlatform OBJECT-TYPE
  SYNTAX DisplayString
  MAX-ACCESS read-only
  STATUS current
  DESCRIPTION
        "HW platform description: This OID contains the
         description of the Hardware platform."
  ::= { rm10010e40ri 3 }

rm10010e40RinvModulePlatform OBJECT-TYPE
  SYNTAX DisplayString
  MAX-ACCESS read-only
  STATUS current
  DESCRIPTION
        "Module platform description: This OID contains the
         description of the Module."
  ::= { rm10010e40ri 4 }

rm10010e40RinvSwPlatform OBJECT-TYPE
  SYNTAX DisplayString
  MAX-ACCESS read-only
  STATUS current
  DESCRIPTION
        "SW platform description: This OID contains the
         description of the Software platform."
  ::= { rm10010e40ri 5 }

rm10010e40RinvGwPlatform OBJECT-TYPE
  SYNTAX DisplayString
  MAX-ACCESS read-only
  STATUS current
  DESCRIPTION
        "GW platform desciption: This OID contains the
         description of the Gateware platform."
  ::= { rm10010e40ri 6 }


rm10010e40RinvSfpTable OBJECT-TYPE
      SYNTAX  SEQUENCE OF Rm10010e40RinvSfpEntry
      MAX-ACCESS  not-accessible
      STATUS  current
      DESCRIPTION
              "List of the SFPs on the selected module"
      ::= { rm10010e40riTable 1 }

rm10010e40RinvSfpEntry OBJECT-TYPE
        SYNTAX  Rm10010e40RinvSfpEntry
        MAX-ACCESS  not-accessible
        STATUS  current
        DESCRIPTION
              "Row definition for the SFP table"
        INDEX   { rm10010e40RinvSfpIndex }
        ::= { rm10010e40RinvSfpTable 1 }



Rm10010e40RinvSfpEntry::=
        SEQUENCE {
          rm10010e40RinvSfpIndex
              Integer32,
          rm10010e40Rinvsfp
              DisplayString
        }


    rm10010e40RinvSfpIndex OBJECT-TYPE
        SYNTAX  Integer32(1..16)
        MAX-ACCESS  read-only
        STATUS  current
        DESCRIPTION
              "Index for SFP table"
        ::= { rm10010e40RinvSfpEntry 1 }


    rm10010e40Rinvsfp OBJECT-TYPE
        SYNTAX  DisplayString
        MAX-ACCESS  read-only
        STATUS  current
        DESCRIPTION
              "Inventory for the SFP: This OID contains the inventory for the SFP"
        ::= { rm10010e40RinvSfpEntry 2 }




rm10010e40RinvLineTable OBJECT-TYPE
      SYNTAX  SEQUENCE OF Rm10010e40RinvLineEntry
      MAX-ACCESS  not-accessible
      STATUS  current
      DESCRIPTION
              "List of the XFPs on the selected module"
      ::= { rm10010e40riTable 2 }

rm10010e40RinvLineEntry OBJECT-TYPE
        SYNTAX  Rm10010e40RinvLineEntry
        MAX-ACCESS  not-accessible
        STATUS  current
        DESCRIPTION
              "Row definition for the XFP table"
        INDEX   { rm10010e40RinvLineIndex }
        ::= { rm10010e40RinvLineTable 1 }



Rm10010e40RinvLineEntry::=
        SEQUENCE {
          rm10010e40RinvLineIndex
              Integer32,
          rm10010e40RinvxfpLine
              DisplayString
        }


    rm10010e40RinvLineIndex OBJECT-TYPE
        SYNTAX  Integer32(1..16)
        MAX-ACCESS  read-only
        STATUS  current
        DESCRIPTION
              "Index for XFP table"
        ::= { rm10010e40RinvLineEntry 1 }


    rm10010e40RinvxfpLine OBJECT-TYPE
        SYNTAX  DisplayString
        MAX-ACCESS  read-only
        STATUS  current
        DESCRIPTION
              "Inventory for the XFP: This OID contains the inventory for the XFP"
        ::= { rm10010e40RinvLineEntry 2 }









--- *****************************************************
--- $$$$$$$$$$$$$$$$$$$$$$$$$$$$$$$$$$$$$$$$$$$$$$$$$$$$$
---     ALARMS
--- $$$$$$$$$$$$$$$$$$$$$$$$$$$$$$$$$$$$$$$$$$$$$$$$$$$$$
--- *****************************************************



--- *****************************************************
---     LEAF for the synthAlm0 article
--- *****************************************************
rm10010e40AlmsynthAlm0 OBJECT IDENTIFIER ::= { rm10010e40AlmOtherCrit 0 }




rm10010e40AlmDefFuseB OBJECT-TYPE
	  SYNTAX EkiOnOff
	  MAX-ACCESS read-only
	  STATUS current
	  DESCRIPTION
        "
        Fuse B Fail :This OID indicates
        that the fuse of the power input
        B is in fail condition <Help> Status
        of the Fuse B <Condtype> DEF_FUSE_B
        <Probcause> powerProblem (36) <Alarmtype>
        equipmentAlarm (5) <Polarity> (2)
        "
	  ::= { rm10010e40AlmsynthAlm0 16 }



rm10010e40AlmDefFuseA OBJECT-TYPE
	  SYNTAX EkiOnOff
	  MAX-ACCESS read-only
	  STATUS current
	  DESCRIPTION
        "
        Fuse A Fail :This OID indicates
        that the fuse of the power input
        A is in fail condition <Help> Status
        of the Fuse A <Condtype> DEF_FUSE_A
        <Probcause> powerProblem (36) <Alarmtype>
        equipmentAlarm (5) <Polarity> (2)
        "
	  ::= { rm10010e40AlmsynthAlm0 15 }



rm10010e40AlmModGlobFail OBJECT-TYPE
	  SYNTAX EkiOnOff
	  MAX-ACCESS read-only
	  STATUS current
	  DESCRIPTION
        "
        Module Failure :This OID is set
        on detection of a failure originating
        from the RM <Help> This alarm is
        set on detection of a failure originating
        from the equipment <Condtype> MOD_GLOB_FAIL
        <Probcause> other (1) <Alarmtype>
        synthesisAlarm (12)  <Polarity>
        (2)
        "
	  ::= { rm10010e40AlmsynthAlm0 9 }



rm10010e40AlmFailFan OBJECT-TYPE
	  SYNTAX EkiOnOff
	  MAX-ACCESS read-only
	  STATUS current
	  DESCRIPTION
        "
        Fan Fail :This OID is at 1 when
        any fail occurs on the fan tray
        <Help> This alarm indicates that
        the Fan tray module is in a failure
        condition <Condtype> FAIL_FAN <Probcause>
        equipmentMalfunction (16) <Alarmtype>
        equipmentAlarm (5) <Polarity> (2)
        "
	  ::= { rm10010e40AlmsynthAlm0 2 }



--- *****************************************************
---     LEAF for the synthAlm2 article
--- *****************************************************
rm10010e40AlmsynthAlm2 OBJECT IDENTIFIER ::= { rm10010e40AlmOtherNurg 2 }




rm10010e40AlmMaintenanceOn OBJECT-TYPE
	  SYNTAX EkiOnOff
	  MAX-ACCESS read-only
	  STATUS current
	  DESCRIPTION
        "
        Maintenance Mode :This OID indicates
        that the RM is in maintenance mode.
        <Help> This alarm indicates that
        the maintenance mode is enabled
        on the PM <Condtype> MAINTENANCE_ON
        <Probcause> informationalStatus(1000)
        <Alarmtype> other (1) <Polarity>
        (2)
        "
	  ::= { rm10010e40AlmsynthAlm2 5 }



rm10010e40AlmCorrelatOff OBJECT-TYPE
	  SYNTAX EkiOnOff
	  MAX-ACCESS read-only
	  STATUS current
	  DESCRIPTION
        "
        Not Used :This OID, when set,
         indicates that alarm correlation
        is not being performed. <Condtype>
        CORRELAT_OFF <Probcause> informationalStatus(1000)
        <Alarmtype> other (1) <Polarity>
        (2)
        "
	  ::= { rm10010e40AlmsynthAlm2 4 }



rm10010e40AlmConfTableLoad OBJECT-TYPE
	  SYNTAX EkiOnOff
	  MAX-ACCESS read-only
	  STATUS current
	  DESCRIPTION
        "
        PM Configuration Load :This OID
         is at 1 during the loading of
         configuration tables in the modules
        RAM. <Condtype> CONF_TABLE_LOAD
        <Probcause> informationalStatus(1000)
        <Alarmtype> other (1) <Polarity>
        (2)
        "
	  ::= { rm10010e40AlmsynthAlm2 3 }



rm10010e40AlmInvUpload OBJECT-TYPE
	  SYNTAX EkiOnOff
	  MAX-ACCESS read-only
	  STATUS current
	  DESCRIPTION
        "
        Inventory Upload :This OID is
         at 1 during the uploading of PM
        inventory information. <Condtype>
        INV_UPLOAD <Probcause> informationalStatus(1000)
        <Alarmtype> other (1) <Polarity>
        (2)
        "
	  ::= { rm10010e40AlmsynthAlm2 2 }



rm10010e40AlmConfTableSave OBJECT-TYPE
	  SYNTAX EkiOnOff
	  MAX-ACCESS read-only
	  STATUS current
	  DESCRIPTION
        "
        PM Configuration Save :This OID
        is at 1 during the saving of a
         new configuration table in the
        module Flash memory. <Condtype>
        CONF_TABLE_SAVE <Probcause> informationalStatus(1000)
        <Alarmtype> other (1) <Polarity>
        (2)
        "
	  ::= { rm10010e40AlmsynthAlm2 1 }



--- *********************************************************
---     TABLE for the rm10010e40AlmsynthAlmPort articles
--- *********************************************************

rm10010e40AlmsynthAlmPortTable OBJECT-TYPE
	SYNTAX  SEQUENCE OF Rm10010e40AlmsynthAlmPortEntry
	MAX-ACCESS not-accessible
	STATUS current
	DESCRIPTION
        "
        List of rm10010e40AlmsynthAlmPort
        Article
        "
	::= { rm10010e40AlmClientCrit 8 }


rm10010e40AlmsynthAlmPortEntry OBJECT-TYPE
	SYNTAX Rm10010e40AlmsynthAlmPortEntry
	MAX-ACCESS not-accessible
	STATUS current
	DESCRIPTION
        "
        Row definition for the rm10010e40AlmsynthAlmPort
        table
        "
	INDEX   { rm10010e40AlmsynthAlmPortIndex }
	::= { rm10010e40AlmsynthAlmPortTable 1 }


Rm10010e40AlmsynthAlmPortEntry ::=
	SEQUENCE {
	rm10010e40AlmsynthAlmPortIndex
		INTEGER,
	rm10010e40AlmUpCsfPortn
		EkiOnOff,
	rm10010e40AlmFailAccPortn
		EkiOnOff,
	rm10010e40AlmSfpDdmAlmPortn
		EkiOnOff,
	rm10010e40AlmSfpDdmWarningPortn
		EkiOnOff,
	rm10010e40AlmDwCaisPortn
		EkiOnOff,
	rm10010e40AlmClientRemoteOosPortn
		EkiOnOff,
	rm10010e40AlmClientLocalOosPortn
		EkiOnOff,
	rm10010e40AlmDwLsdPortn
		EkiOnOff,
	rm10010e40AlmHwFailAccPortn
		EkiOnOff,
	rm10010e40AlmDdmAbsentPortn
		EkiOnOff,
	rm10010e40AlmSfpAbsentPortn
		EkiOnOff
	}


rm10010e40AlmsynthAlmPortIndex OBJECT-TYPE
	SYNTAX  INTEGER(0..128)
	MAX-ACCESS  read-only
	STATUS current
	DESCRIPTION
        "
        Index definition for the rm10010e40AlmsynthAlmPort
        table
        "
	::= { rm10010e40AlmsynthAlmPortEntry 1 }


rm10010e40AlmUpCsfPortn OBJECT-TYPE
	SYNTAX  EkiOnOff
	MAX-ACCESS read-only
	STATUS current
	DESCRIPTION
        "
        Client Signal Fail Inserted :This
        OID indicates a CSF has been inserted
        in the upstream client port. <Help>
        This status indicates if a Client
        Signal Fail is currently inserted
        on the line signal for this client
        port <Condtype> UP_CSF_1 <Probcause>
        informationalStatus(1000) <Alarmtype>
        other (1) <Polarity> (2)
        "
	::= { rm10010e40AlmsynthAlmPortEntry 17 }


rm10010e40AlmFailAccPortn OBJECT-TYPE
	SYNTAX  EkiOnOff
	MAX-ACCESS read-only
	STATUS current
	DESCRIPTION
        "
        Client Access Fail :This OID indicates
        a failure on the Client port <Help>
        This alarm indicates a failure
         on the Client port <Condtype>
         FAIL_ACC_1 <Probcause> equipmentMalfunction
        (16) <Alarmtype> synthesisAlarm
        (12)  <Polarity> (2)
        "
	::= { rm10010e40AlmsynthAlmPortEntry 13 }


rm10010e40AlmSfpDdmAlmPortn OBJECT-TYPE
	SYNTAX  EkiOnOff
	MAX-ACCESS read-only
	STATUS current
	DESCRIPTION
        "
        Alarm On Client Trscv DDM :This
        OID indicates an alarm is being
        received from the Client Transceiver
        DDM <Help> This alarm indicates
        if a DDM Alarm has been detected
        on the client transceiver <Condtype>
        SFP_DDM_ALM_1 <Probcause> inputOutputDeviceError
        (24) <Alarmtype> synthesisAlarm
        (12)  <Polarity> (2)
        "
	::= { rm10010e40AlmsynthAlmPortEntry 11 }


rm10010e40AlmSfpDdmWarningPortn OBJECT-TYPE
	SYNTAX  EkiOnOff
	MAX-ACCESS read-only
	STATUS current
	DESCRIPTION
        "
        Warning On Client Trscv DDM :This
        OID indicates a warning is being
        received from the Client Transceiver
        DDM <Help> This alarm indicates
        if a DDM Warning has been detected
        on the client transceiver <Condtype>
        SFP_DDM_WARNING_1 <Probcause> inputOutputDeviceError
        (24) <Alarmtype> synthesisAlarm
        (12)  <Polarity> (2)
        "
	::= { rm10010e40AlmsynthAlmPortEntry 10 }


rm10010e40AlmDwCaisPortn OBJECT-TYPE
	SYNTAX  EkiOnOff
	MAX-ACCESS read-only
	STATUS current
	DESCRIPTION
        "
        Client AIS Inserted :This OID
         indicates a CAIS has been inserted
        on the output client port. <Help>
        This status indicates if a Client
        Alarm Indication Signal is currently
        inserted on the client interface
        <Condtype> DW_CAIS_1 <Probcause>
        informationalStatus(1000) <Alarmtype>
        other (1) <Polarity> (2)
        "
	::= { rm10010e40AlmsynthAlmPortEntry 9 }


rm10010e40AlmClientRemoteOosPortn OBJECT-TYPE
	SYNTAX  EkiOnOff
	MAX-ACCESS read-only
	STATUS current
	DESCRIPTION
        "
        Remote Client Port In Service
         :This OID indicates that the remote
        Client port is In Service (1) or
        Out of Service (2) <Help> This
         status indicates if the remote
        client port is in service <Condtype>
        CLIENT_REMOTE_OOS <Probcause> informationalStatus(1000)
        <Alarmtype> other (1) <Polarity>
        (2)
        "
	::= { rm10010e40AlmsynthAlmPortEntry 8 }


rm10010e40AlmClientLocalOosPortn OBJECT-TYPE
	SYNTAX  EkiOnOff
	MAX-ACCESS read-only
	STATUS current
	DESCRIPTION
        "
        Local Client Port In Service :This
        OID indicates that the local Client
        port is In Service (1) or Out of
        Service (2) <Help> This status
         indicates if the local client
         port is in service <Condtype>
         CLIENT_LOCAL_OOS <Probcause> informationalStatus(1000)
        <Alarmtype> other (1) <Polarity>
        (2)
        "
	::= { rm10010e40AlmsynthAlmPortEntry 7 }


rm10010e40AlmDwLsdPortn OBJECT-TYPE
	SYNTAX  EkiOnOff
	MAX-ACCESS read-only
	STATUS current
	DESCRIPTION
        "
        Client Trscv Laser Shutdown :This
        OID indicates the Client transceiver
        laser is shutdown <Help> This status
        indicates if the client transceiver
        laser is shutdown <Condtype> DW_LSD_1
        <Probcause> other (1) <Alarmtype>
        equipmentAlarm (5) <Polarity> (2)
        "
	::= { rm10010e40AlmsynthAlmPortEntry 6 }


rm10010e40AlmHwFailAccPortn OBJECT-TYPE
	SYNTAX  EkiOnOff
	MAX-ACCESS read-only
	STATUS current
	DESCRIPTION
        "
        Client HW Fail :This OID indicates
        a failure on client port, most
         probably caused by a HW issue.
        <Help> This alarm indicates a failure
        on client port, most probably caused
        by a HW issue. <Condtype> HW_FAIL_ACC_1
        <Probcause> equipmentMalfunction
        (16) <Alarmtype> synthesisAlarm
        (12)  <Polarity> (2)
        "
	::= { rm10010e40AlmsynthAlmPortEntry 5 }


rm10010e40AlmDdmAbsentPortn OBJECT-TYPE
	SYNTAX  EkiOnOff
	MAX-ACCESS read-only
	STATUS current
	DESCRIPTION
        "
        DDM Supported On Client Trscv
         :This OID indicates that the Client
        transceiver supports the Digital
        Diagnostic Monitoring function
         <Help> This status indicates if
        the client transceiver includes
        the DDM feature <Condtype> DDM_ABSENT_1
        <Probcause> informationalStatus(1000)
        <Alarmtype> other (1) <Polarity>
        (2)
        "
	::= { rm10010e40AlmsynthAlmPortEntry 3 }


rm10010e40AlmSfpAbsentPortn OBJECT-TYPE
	SYNTAX  EkiOnOff
	MAX-ACCESS read-only
	STATUS current
	DESCRIPTION
        "
        Client Optical Module Absent :This
        OID indicates that the Transceiver
        is not present in the client port.
        <Help> This alarm indicates if
         the client transceiver is not
         plugged <Condtype> SFP_ABSENT_1
        <Probcause> inputOutputDeviceError
        (24) <Alarmtype> equipmentAlarm
        (5) <Polarity> (2) <Event> ObjectCDINV
        "
	::= { rm10010e40AlmsynthAlmPortEntry 2 }


--- *********************************************************
---     TABLE for the rm10010e40AlmsynthAlmLine articles
--- *********************************************************

rm10010e40AlmsynthAlmLineTable OBJECT-TYPE
	SYNTAX  SEQUENCE OF Rm10010e40AlmsynthAlmLineEntry
	MAX-ACCESS not-accessible
	STATUS current
	DESCRIPTION
        "
        List of rm10010e40AlmsynthAlmLine
        Article
        "
	::= { rm10010e40AlmLineCrit 24 }


rm10010e40AlmsynthAlmLineEntry OBJECT-TYPE
	SYNTAX Rm10010e40AlmsynthAlmLineEntry
	MAX-ACCESS not-accessible
	STATUS current
	DESCRIPTION
        "
        Row definition for the rm10010e40AlmsynthAlmLine
        table
        "
	INDEX   { rm10010e40AlmsynthAlmLineIndex }
	::= { rm10010e40AlmsynthAlmLineTable 1 }


Rm10010e40AlmsynthAlmLineEntry ::=
	SEQUENCE {
	rm10010e40AlmsynthAlmLineIndex
		INTEGER,
	rm10010e40AlmLineActivePortn
		EkiOnOff,
	rm10010e40AlmLineFailPortn
		EkiOnOff,
	rm10010e40AlmLineDdmAlmPortn
		EkiOnOff,
	rm10010e40AlmLineDdmWarningPortn
		EkiOnOff,
	rm10010e40AlmUpRdiInsPortn
		EkiOnOff,
	rm10010e40AlmLineLocalOosPortn
		EkiOnOff,
	rm10010e40AlmXfpTxOffPortn
		EkiOnOff,
	rm10010e40AlmLineHwFailPortn
		EkiOnOff,
	rm10010e40AlmXfpInitNotComplPortn
		EkiOnOff,
	rm10010e40AlmXfpAbsentPortn
		EkiOnOff
	}


rm10010e40AlmsynthAlmLineIndex OBJECT-TYPE
	SYNTAX  INTEGER(0..128)
	MAX-ACCESS  read-only
	STATUS current
	DESCRIPTION
        "
        Index definition for the rm10010e40AlmsynthAlmLine
        table
        "
	::= { rm10010e40AlmsynthAlmLineEntry 1 }


rm10010e40AlmLineActivePortn OBJECT-TYPE
	SYNTAX  EkiOnOff
	MAX-ACCESS read-only
	STATUS current
	DESCRIPTION
        "
        Line Active :This OID indicates
        whether the line is active or standby.
        <Help> This status indicates whether
        the line is active or standby.
         <Condtype> LINE_ACTIVE <Probcause>
        informationalStatus(1000) <Alarmtype>
        other (1) <Polarity> (2)
        "
	::= { rm10010e40AlmsynthAlmLineEntry 17 }


rm10010e40AlmLineFailPortn OBJECT-TYPE
	SYNTAX  EkiOnOff
	MAX-ACCESS read-only
	STATUS current
	DESCRIPTION
        "
        Line Port Failure :This OID indicates
        a failure on the line port <Help>
        This alarm indicates a failure
         on the line port <Condtype> LINE_FAIL
        <Probcause> equipmentMalfunction
        (16) <Alarmtype> synthesisAlarm
        (12)  <Polarity> (2)
        "
	::= { rm10010e40AlmsynthAlmLineEntry 13 }


rm10010e40AlmLineDdmAlmPortn OBJECT-TYPE
	SYNTAX  EkiOnOff
	MAX-ACCESS read-only
	STATUS current
	DESCRIPTION
        "
        Alarm On Line Optical Module DDM
        :This OID indicates an alarm is
        present coming out of Line transceiver
        DDM <Help> This alarm indicates
        if a DDM Alarm has been detected
        on the line transceiver <Condtype>
        LINE_DDM_ALM <Probcause> inputOutputDeviceError
        (24) <Alarmtype> synthesisAlarm
        (12)  <Polarity> (2)
        "
	::= { rm10010e40AlmsynthAlmLineEntry 11 }


rm10010e40AlmLineDdmWarningPortn OBJECT-TYPE
	SYNTAX  EkiOnOff
	MAX-ACCESS read-only
	STATUS current
	DESCRIPTION
        "
        Warning On Line Optical Module
        DDM :This OID indicates a warning
        is present coming out of Line transceiver
        DDM <Help> This alarm indicates
        if a DDM Warning has been detected
        on the line transceiver <Condtype>
        LINE_DDM_WARNING <Probcause> inputOutputDeviceError
        (24) <Alarmtype> synthesisAlarm
        (12)  <Polarity> (2)
        "
	::= { rm10010e40AlmsynthAlmLineEntry 10 }


rm10010e40AlmUpRdiInsPortn OBJECT-TYPE
	SYNTAX  EkiOnOff
	MAX-ACCESS read-only
	STATUS current
	DESCRIPTION
        "
        MS-RDI/L-RDI Inserted On Line
         :This OID indicates an upstream
        MS-RDI/L-RDI has been inserted
         in the outgoing 10 Gb/s SDH/SONET
        signal. <Help> This status indicates
        if a MS-RDI/L-RDI is currently
         inserted on the line interface.
        <Condtype> UP_RDI_INS <Probcause>
        informationalStatus(1000) <Alarmtype>
        other (1) <Polarity> (2)
        "
	::= { rm10010e40AlmsynthAlmLineEntry 9 }


rm10010e40AlmLineLocalOosPortn OBJECT-TYPE
	SYNTAX  EkiOnOff
	MAX-ACCESS read-only
	STATUS current
	DESCRIPTION
        "
        Line Port In Service :This OID
        indicates that the Line port is
        In Service (1) of Out or Service
        (2) <Help> This status indicates
        if the line port is in service
         <Condtype> LINE_LOCAL_OOS <Probcause>
        informationalStatus(1000) <Alarmtype>
        other (1) <Polarity> (2)
        "
	::= { rm10010e40AlmsynthAlmLineEntry 7 }


rm10010e40AlmXfpTxOffPortn OBJECT-TYPE
	SYNTAX  EkiOnOff
	MAX-ACCESS read-only
	STATUS current
	DESCRIPTION
        "
        Line Trscv Laser Shutdown :This
        OID indicates the Line transceiver
        laser is shutdown <Help> This status
        indicates if the Line transceiver
        laser is shutdown <Condtype> XFP_TX_OFF
        <Probcause> other (1) <Alarmtype>
        equipmentAlarm (5) <Polarity> (2)
        "
	::= { rm10010e40AlmsynthAlmLineEntry 6 }


rm10010e40AlmLineHwFailPortn OBJECT-TYPE
	SYNTAX  EkiOnOff
	MAX-ACCESS read-only
	STATUS current
	DESCRIPTION
        "
        Line Port HW Failure :This OID
        indicates a failure on line port,
        most probably caused by a HW issue
        <Help> This alarm indicates a failure
        on line port, most probably caused
        by a HW issue <Condtype> LINE_HW_FAIL
        <Probcause> equipmentMalfunction
        (16) <Alarmtype> synthesisAlarm
        (12)  <Polarity> (2)
        "
	::= { rm10010e40AlmsynthAlmLineEntry 5 }


rm10010e40AlmXfpInitNotComplPortn OBJECT-TYPE
	SYNTAX  EkiOnOff
	MAX-ACCESS read-only
	STATUS current
	DESCRIPTION
        "
        Line Optical Module Ready :This
        OID indicates that the optical
         interface is not operational.
         <Help> This status indicates if
        the line transceiver has been correctly
        initialized <Condtype> XFP_INIT_NOT_COMPL
        <Probcause> equipmentMalfunction
        (16) <Alarmtype> equipmentAlarm
        (5) <Polarity> (2)
        "
	::= { rm10010e40AlmsynthAlmLineEntry 3 }


rm10010e40AlmXfpAbsentPortn OBJECT-TYPE
	SYNTAX  EkiOnOff
	MAX-ACCESS read-only
	STATUS current
	DESCRIPTION
        "
        Line Optical Module Absent :This
        OID indicates that the line optical
        interface is not present. <Help>
        This alarm indicates if the line
        transceiver is not plugged <Condtype>
        XFP_ABSENT <Probcause> inputOutputDeviceError
        (24) <Alarmtype> equipmentAlarm
        (5) <Polarity> (2)
        "
	::= { rm10010e40AlmsynthAlmLineEntry 2 }


--- *****************************************************
---     LEAF for the clientModuleState article
--- *****************************************************
rm10010e40AlmclientModuleState OBJECT IDENTIFIER ::= { rm10010e40AlmOtherCrit 40 }




rm10010e40AlmCfpHighPowerDown OBJECT-TYPE
	  SYNTAX EkiOnOff
	  MAX-ACCESS read-only
	  STATUS current
	  DESCRIPTION
        "
        Client Trscv High Power Down :This
        OID indicates the Client Trscv
         is entering Low Power state <Help>
        Status indicating the Client Trscv
        is entering Low Power state <Condtype>
        CFP_HIGH_POWER_DOWN <Probcause>
        informationalStatus(1000) <Alarmtype>
        other (1) <Polarity> (2)
        "
	  ::= { rm10010e40AlmclientModuleState 9 }



rm10010e40AlmCfpTxTurnOff OBJECT-TYPE
	  SYNTAX EkiOnOff
	  MAX-ACCESS read-only
	  STATUS current
	  DESCRIPTION
        "
        Client Trscv Laser Turn Off :This
        OID indicates the Client Trscv
         is turning off its laser <Help>
        Status indicating the Client Trscv
        is turning off its laser <Condtype>
        CFP_TX_TURN_OFF <Probcause> informationalStatus(1000)
        <Alarmtype> other (1) <Polarity>
        (2)
        "
	  ::= { rm10010e40AlmclientModuleState 8 }



rm10010e40AlmCfpFault OBJECT-TYPE
	  SYNTAX EkiOnOff
	  MAX-ACCESS read-only
	  STATUS current
	  DESCRIPTION
        "
        Client Trscv Fault :This OID indicates
        the Client Trscv is in Fault state
        <Help> Status indicating the Client
        Trscv is in Fault state <Condtype>
        CFP_FAULT <Probcause> informationalStatus(1000)
        <Alarmtype> other (1) <Polarity>
        (2)
        "
	  ::= { rm10010e40AlmclientModuleState 7 }



rm10010e40AlmCfpReady OBJECT-TYPE
	  SYNTAX EkiOnOff
	  MAX-ACCESS read-only
	  STATUS current
	  DESCRIPTION
        "
        Client Trscv Ready :This OID indicates
        the Client Trscv is ready to operate
        <Help> Status indicating the Client
        Trscv is ready to operate <Condtype>
        CFP_READY <Probcause> informationalStatus(1000)
        <Alarmtype> other (1) <Polarity>
        (2)
        "
	  ::= { rm10010e40AlmclientModuleState 6 }



rm10010e40AlmCfpTxTurnOn OBJECT-TYPE
	  SYNTAX EkiOnOff
	  MAX-ACCESS read-only
	  STATUS current
	  DESCRIPTION
        "
        Client Trscv Laser Turn On :This
        OID indicates the Client Trscv
         is turning on its laser <Help>
        Status indicating the Client Trscv
        is turning on its laser <Condtype>
        CFP_TX_TURN_ON <Probcause> informationalStatus(1000)
        <Alarmtype> other (1) <Polarity>
        (2)
        "
	  ::= { rm10010e40AlmclientModuleState 5 }



rm10010e40AlmCfpTxOff OBJECT-TYPE
	  SYNTAX EkiOnOff
	  MAX-ACCESS read-only
	  STATUS current
	  DESCRIPTION
        "
        Client Trscv Laser Shutdown :This
        OID indicates the Client Trscv
         Laser is OFF <Help> Status indicating
        the Client Trscv Laser is OFF <Condtype>
        CFP_TX_OFF <Probcause> informationalStatus(1000)
        <Alarmtype> other (1) <Polarity>
        (2)
        "
	  ::= { rm10010e40AlmclientModuleState 4 }



rm10010e40AlmCfpHighPowerUp OBJECT-TYPE
	  SYNTAX EkiOnOff
	  MAX-ACCESS read-only
	  STATUS current
	  DESCRIPTION
        "
        Client Trscv High Power Up :This
        OID indicates the Client Trscv
         is leaving Low Power state <Help>
        Status indicating the Client Trscv
        is leaving Low Power state <Condtype>
        CFP_HIGH_POWER_UP <Probcause> informationalStatus(1000)
        <Alarmtype> other (1) <Polarity>
        (2)
        "
	  ::= { rm10010e40AlmclientModuleState 3 }



rm10010e40AlmCfpLowPower OBJECT-TYPE
	  SYNTAX EkiOnOff
	  MAX-ACCESS read-only
	  STATUS current
	  DESCRIPTION
        "
        Client Trscv Low Power :This OID
        indicates the Client Trscv is in
        low power state <Help> Status indicating
        the Client Trscv is in low power
        state <Condtype> CFP_LOW_POWER
         <Probcause> informationalStatus(1000)
        <Alarmtype> other (1) <Polarity>
        (2)
        "
	  ::= { rm10010e40AlmclientModuleState 2 }



rm10010e40AlmCfpInitialize OBJECT-TYPE
	  SYNTAX EkiOnOff
	  MAX-ACCESS read-only
	  STATUS current
	  DESCRIPTION
        "
        Client Trscv Initialize :This
         OID indicates the Client Trscv
        initialization is in progress <Help>
        Status indicating the Client Trscv
        initialization is in progress <Condtype>
        CFP_INITIALIZE <Probcause> informationalStatus(1000)
        <Alarmtype> other (1) <Polarity>
        (2)
        "
	  ::= { rm10010e40AlmclientModuleState 1 }



--- *****************************************************
---     LEAF for the clientModuleGeneralStatus article
--- *****************************************************
rm10010e40AlmclientModuleGeneralStatus OBJECT IDENTIFIER ::= { rm10010e40AlmOtherCrit 41 }




rm10010e40AlmCfpHwInterlock OBJECT-TYPE
	  SYNTAX EkiOnOff
	  MAX-ACCESS read-only
	  STATUS current
	  DESCRIPTION
        "
        Client Trscv Hardware Interlock
        :This OID indicates the Client
         Trscv power is higher than the
        cooling capacity <Help> Alarm indicating
        the Client Trscv power is higher
        than the cooling capacity <Condtype>
        CFP_HW_INTERLOCK <Probcause> temperatureUnacceptable
        (51) <Alarmtype> equipmentAlarm
        (5) <Polarity> (2)
        "
	  ::= { rm10010e40AlmclientModuleGeneralStatus 14 }



rm10010e40AlmCfpLossOfRefclk OBJECT-TYPE
	  SYNTAX EkiOnOff
	  MAX-ACCESS read-only
	  STATUS current
	  DESCRIPTION
        "
        Client Trscv Loss Of Ref Clock
        :This OID indicates a Loss of Reference
        clock is detected on the Client
        Trscv <Help> Alarm indicating a
        Loss of Reference clock is detected
        on the Client Trscv <Condtype>
         CFP_LOSS_OF_REFCLK <Probcause>
        inputOutputDeviceError (24) <Alarmtype>
        equipmentAlarm (5) <Polarity> (2)
        "
	  ::= { rm10010e40AlmclientModuleGeneralStatus 11 }



rm10010e40AlmCfpTxJitterPllLol OBJECT-TYPE
	  SYNTAX EkiOnOff
	  MAX-ACCESS read-only
	  STATUS current
	  DESCRIPTION
        "
        Client Trscv Tx Jitter PLL Loss
        Of Lock :This OID indicates a Tx
        Jitter PLL Loss of Lock is dtected
        on the Client Trscv <Help> Alarm
        indicating a Tx Jitter PLL Loss
        of Lock is dtected on the Client
        Trscv <Condtype> CFP_TX_JITTER_PLL_LOL
        <Probcause> inputOutputDeviceError
        (24) <Alarmtype> equipmentAlarm
        (5) <Polarity> (2)
        "
	  ::= { rm10010e40AlmclientModuleGeneralStatus 10 }



rm10010e40AlmCfpTxCmuLol OBJECT-TYPE
	  SYNTAX EkiOnOff
	  MAX-ACCESS read-only
	  STATUS current
	  DESCRIPTION
        "
        Client Trscv CMU Loss Of Lock
         :This OID indicates a Clock Multiplier
        Unit Loss of Lock is detected on
        the Client Trscv <Help> Alarm indicating
        a Clock Multiplier Unit Loss of
        Lock is detected on the Client
         Trscv <Condtype> CFP_TX_CMU_LOL
        <Probcause> inputOutputDeviceError
        (24) <Alarmtype> equipmentAlarm
        (5) <Polarity> (2)
        "
	  ::= { rm10010e40AlmclientModuleGeneralStatus 9 }



rm10010e40AlmCfpTxLosf OBJECT-TYPE
	  SYNTAX EkiOnOff
	  MAX-ACCESS read-only
	  STATUS current
	  DESCRIPTION
        "
        Client Trscv Loss Of Signal Functionality
        :This OID indicates a Loss of Signal
        functionality is detected on the
        Client Trscv <Help> Alarm indicating
        a Loss of Signal functionality
         is detected on the Client Trscv
        <Condtype> CFP_TX_LOSF <Probcause>
        lossOfSignal (30) <Alarmtype> equipmentAlarm
        (5) <Polarity> (2)
        "
	  ::= { rm10010e40AlmclientModuleGeneralStatus 8 }



rm10010e40AlmCfpTxHostLol OBJECT-TYPE
	  SYNTAX EkiOnOff
	  MAX-ACCESS read-only
	  STATUS current
	  DESCRIPTION
        "
        Client Trscv Tx Host Loss Of Lock
        :This OID indicates of Loss of
         Lock is detected on the Client
        Trscv Tx Host interface <Help>
         Alarm indicating of Loss of Lock
        is detected on the Client Trscv
        Tx Host interface <Condtype> CFP_TX_HOST_LOL
        <Probcause> receiverFailure (42)
        <Alarmtype> equipmentAlarm (5)
         <Polarity> (2)
        "
	  ::= { rm10010e40AlmclientModuleGeneralStatus 7 }



rm10010e40AlmCfpRxLos OBJECT-TYPE
	  SYNTAX EkiOnOff
	  MAX-ACCESS read-only
	  STATUS current
	  DESCRIPTION
        "
        Client Trscv Loss Of Signal :This
        OID indicates a Loss of Signal
         is detected on the Client Trscv
        <Help> Alarm indicating a Loss
         of Signal is detected on the Client
        Trscv <Condtype> CFP_RX_LOS <Probcause>
        lossOfSignal (30) <Alarmtype> equipmentAlarm
        (5) <Polarity> (2)
        "
	  ::= { rm10010e40AlmclientModuleGeneralStatus 6 }



rm10010e40AlmCfpRxNetworkLol OBJECT-TYPE
	  SYNTAX EkiOnOff
	  MAX-ACCESS read-only
	  STATUS current
	  DESCRIPTION
        "
        Client Trscv Rx Network Loss Of
        Lock :This OID indicates of Loss
        of Lock is dected on the Client
        Trscv Rx Network interface <Help>
        Alarm indicating of Loss of Lock
        is dected on the Client Trscv Rx
        Network interface <Condtype> CFP_RX_NETWORK_LOL
        <Probcause> receiverFailure (42)
        <Alarmtype> equipmentAlarm (5)
         <Polarity> (2)
        "
	  ::= { rm10010e40AlmclientModuleGeneralStatus 5 }



rm10010e40AlmCfpOutOfAlignment OBJECT-TYPE
	  SYNTAX EkiOnOff
	  MAX-ACCESS read-only
	  STATUS current
	  DESCRIPTION
        "
        Client Trscv Out Of Alignment
         :This OID indicates an Out of
         alignment on the Client Trscv
         Host Interface <Help> Alarm indicating
        an Out of alignment on the Client
        Trscv Host Interface <Condtype>
        CFP_OUT_OF_ALIGNMENT <Probcause>
        receiverFailure (42) <Alarmtype>
        equipmentAlarm (5) <Polarity> (2)
        "
	  ::= { rm10010e40AlmclientModuleGeneralStatus 4 }



--- *****************************************************
---     LEAF for the clientGlobalAlarmSummary article
--- *****************************************************
rm10010e40AlmclientGlobalAlarmSummary OBJECT IDENTIFIER ::= { rm10010e40AlmOtherCrit 42 }




rm10010e40AlmCfpGlobAlarmAssertion  OBJECT-TYPE
	  SYNTAX EkiOnOff
	  MAX-ACCESS read-only
	  STATUS current
	  DESCRIPTION
        "
        Client Trscv Global Alarm :This
        OID indicates at least one  Fault
        or Status is detected on the Client
        Trscv module <Help> Synthesis alarm
        indicating at least one Alarm,
         Warning, Fault or Status is detected
        on the Client Trscv module <Condtype>
        CFP_GLOB_ALARM_ASSERTION  <Probcause>
        informationalStatus(1000) <Alarmtype>
        other (1) <Polarity> (2)
        "
	  ::= { rm10010e40AlmclientGlobalAlarmSummary 16 }



rm10010e40AlmCfpHostLaneFaultStatus  OBJECT-TYPE
	  SYNTAX EkiOnOff
	  MAX-ACCESS read-only
	  STATUS current
	  DESCRIPTION
        "
        Client Trscv Host Fault And Status
        :This OID indicates at least one
        Fault or Status is detected on
         the Client Trscv Host Interface
        <Help> Synthesis alarm indicating
        at least one Fault or Status is
        detected on the Client Trscv Host
        Interface <Condtype> CFP_HOST_LANE_FAULT_STATUS
         <Probcause> informationalStatus(1000)
        <Alarmtype> other (1) <Polarity>
        (2)
        "
	  ::= { rm10010e40AlmclientGlobalAlarmSummary 15 }



rm10010e40AlmCfpNetworkLaneFaultStatus  OBJECT-TYPE
	  SYNTAX EkiOnOff
	  MAX-ACCESS read-only
	  STATUS current
	  DESCRIPTION
        "
        Client Trscv Network Fault And
        Status :This OID indicates at least
        one Fault or Status is detected
        on the Client Trscv Network Interface
        <Help> Synthesis alarm indicating
        at least one Fault or Status is
        detected on the Client Trscv Network
        Interface <Condtype> CFP_NETWORK_LANE_FAULT_STATUS
         <Probcause> informationalStatus(1000)
        <Alarmtype> other (1) <Polarity>
        (2)
        "
	  ::= { rm10010e40AlmclientGlobalAlarmSummary 14 }



rm10010e40AlmCfpNetworkLaneAlarmWarning1 OBJECT-TYPE
	  SYNTAX EkiOnOff
	  MAX-ACCESS read-only
	  STATUS current
	  DESCRIPTION
        "
        Client Trscv Network Alarm And
        Warning 1 :This OID indicates at
        least one DDM  is detected on the
        Client Trscv Network Interface
         <Help> Synthesis alarm indicating
        at least one DDM Alarm or DDM Warning
        is detected on the Client Trscv
        Network Interface <Condtype> CFP_NETWORK_LANE_ALARM_WARNING_1
        <Probcause> informationalStatus(1000)
        <Alarmtype> other (1) <Polarity>
        (2)
        "
	  ::= { rm10010e40AlmclientGlobalAlarmSummary 13 }



rm10010e40AlmCfpModuleAlarmWarning2 OBJECT-TYPE
	  SYNTAX EkiOnOff
	  MAX-ACCESS read-only
	  STATUS current
	  DESCRIPTION
        "
        Client Trscv Module Alarm And
         Warning 2 :This OID indicates
         at least one DDM is detected on
        the Client Trscv module <Help>
         Synthesis alarm indicating at
         least one DDM Alarm or DDM Warning
        is detected on the Client Trscv
        module <Condtype> CFP_MODULE_ALARM_WARNING_2
        <Probcause> informationalStatus(1000)
        <Alarmtype> other (1) <Polarity>
        (2)
        "
	  ::= { rm10010e40AlmclientGlobalAlarmSummary 12 }



rm10010e40AlmCfpModuleAlarmWarning1  OBJECT-TYPE
	  SYNTAX EkiOnOff
	  MAX-ACCESS read-only
	  STATUS current
	  DESCRIPTION
        "
        Client Trscv Module Alarm And
         Warning 1 :This OID indicates
         at least one DDM  This OID is
         detected on the Client Trscv module
        <Help> Synthesis alarm indicating
        at least one DDM Alarm or DDM Warning
        is detected on the Client Trscv
        module <Condtype> CFP_MODULE_ALARM_WARNING_1
         <Probcause> informationalStatus(1000)
        <Alarmtype> other (1) <Polarity>
        (2)
        "
	  ::= { rm10010e40AlmclientGlobalAlarmSummary 11 }



rm10010e40AlmCfpModuleFault  OBJECT-TYPE
	  SYNTAX EkiOnOff
	  MAX-ACCESS read-only
	  STATUS current
	  DESCRIPTION
        "
        Client Trscv Module Fault :This
        OID indicates at least one Fault
        is detected on the Client Trscv
        module <Help> Synthesis alarm indicating
        at least one Fault is detected
         on the Client Trscv module <Condtype>
        CFP_MODULE_FAULT  <Probcause> informationalStatus(1000)
        <Alarmtype> other (1) <Polarity>
        (2)
        "
	  ::= { rm10010e40AlmclientGlobalAlarmSummary 10 }



rm10010e40AlmCfpModuleGeneralStatus  OBJECT-TYPE
	  SYNTAX EkiOnOff
	  MAX-ACCESS read-only
	  STATUS current
	  DESCRIPTION
        "
        Client Trscv General Status :This
        OID indicates the Client Trscv
         module general status <Help> Synthesis
        alarm indicating the Client Trscv
        module general status <Condtype>
        CFP_MODULE_GENERAL_STATUS  <Probcause>
        informationalStatus(1000) <Alarmtype>
        other (1) <Polarity> (2)
        "
	  ::= { rm10010e40AlmclientGlobalAlarmSummary 9 }



rm10010e40AlmCfpModuleState  OBJECT-TYPE
	  SYNTAX EkiOnOff
	  MAX-ACCESS read-only
	  STATUS current
	  DESCRIPTION
        "
        Client Trscv Module State :This
        OID indicates the Client Trscv
         module state <Help> Synthesis
         alarm indicating the Client Trscv
        module state <Condtype> CFP_MODULE_STATE
         <Probcause> informationalStatus(1000)
        <Alarmtype> other (1) <Polarity>
        (2)
        "
	  ::= { rm10010e40AlmclientGlobalAlarmSummary 8 }



rm10010e40AlmCfpNetworkLaneAlarmWarning2 OBJECT-TYPE
	  SYNTAX EkiOnOff
	  MAX-ACCESS read-only
	  STATUS current
	  DESCRIPTION
        "
        Client Trscv Network Alarm And
        Warning 2 :This OID indicates at
        least one DDM is detected on the
        Client Trscv Network Interface
         <Help> Synthesis alarm indicating
        at least one DDM Alarm or DDM Warning
        is detected on the Client Trscv
        Network Interface <Condtype> CFP_NETWORK_LANE_ALARM_WARNING_2
        <Probcause> informationalStatus(1000)
        <Alarmtype> other (1) <Polarity>
        (2)
        "
	  ::= { rm10010e40AlmclientGlobalAlarmSummary 7 }



rm10010e40AlmCfpSoftGlobAlarmTest  OBJECT-TYPE
	  SYNTAX EkiOnOff
	  MAX-ACCESS read-only
	  STATUS current
	  DESCRIPTION
        "
        Client Trscv Global Alarm SW Test
        :This OID indicates the Client
         Trscv Global Alarm This OID is
        raised by SW request for test purpose
        <Help> Status indicating the Client
        Trscv Global Alarm is raised by
        SW request for test purpose <Condtype>
        CFP_SOFT_GLOB_ALARM_TEST  <Probcause>
        informationalStatus(1000) <Alarmtype>
        other (1) <Polarity> (2)
        "
	  ::= { rm10010e40AlmclientGlobalAlarmSummary 1 }



--- *****************************************************
---     LEAF for the msaModuleState article
--- *****************************************************
rm10010e40AlmmsaModuleState OBJECT IDENTIFIER ::= { rm10010e40AlmOtherCrit 46 }




rm10010e40AlmMsaHighPowerDown OBJECT-TYPE
	  SYNTAX EkiOnOff
	  MAX-ACCESS read-only
	  STATUS current
	  DESCRIPTION
        "
        Line Trscv High Power Down :This
        OID indicates the Line Trscv is
        entering Low Power state <Help>
        Status indicating the Line Trscv
        is entering Low Power state <Condtype>
        MSA_HIGH_POWER_DOWN <Probcause>
        informationalStatus(1000) <Alarmtype>
        other (1) <Polarity> (2)
        "
	  ::= { rm10010e40AlmmsaModuleState 9 }



rm10010e40AlmMsaTxTurnOff OBJECT-TYPE
	  SYNTAX EkiOnOff
	  MAX-ACCESS read-only
	  STATUS current
	  DESCRIPTION
        "
        Line Trscv Laser Turn Off :This
        OID indicates the Line Trscv is
        turning off its laser <Help> Status
        indicating the Line Trscv is turning
        off its laser <Condtype> MSA_TX_TURN_OFF
        <Probcause> informationalStatus(1000)
        <Alarmtype> other (1) <Polarity>
        (2)
        "
	  ::= { rm10010e40AlmmsaModuleState 8 }



rm10010e40AlmMsaFault OBJECT-TYPE
	  SYNTAX EkiOnOff
	  MAX-ACCESS read-only
	  STATUS current
	  DESCRIPTION
        "
        Line Trscv Fault :This OID indicates
        the Line Trscv is in Fault state
        <Help> Status indicating the Line
        Trscv is in Fault state <Condtype>
        MSA_FAULT <Probcause> informationalStatus(1000)
        <Alarmtype> other (1) <Polarity>
        (2)
        "
	  ::= { rm10010e40AlmmsaModuleState 7 }



rm10010e40AlmMsaReady OBJECT-TYPE
	  SYNTAX EkiOnOff
	  MAX-ACCESS read-only
	  STATUS current
	  DESCRIPTION
        "
        Line Trscv Ready :This OID indicates
        the Line Trscv is ready to operate
        <Help> Status indicating the Line
        Trscv is ready to operate <Condtype>
        MSA_READY <Probcause> informationalStatus(1000)
        <Alarmtype> other (1) <Polarity>
        (2)
        "
	  ::= { rm10010e40AlmmsaModuleState 6 }



rm10010e40AlmMsaTxTurnOn OBJECT-TYPE
	  SYNTAX EkiOnOff
	  MAX-ACCESS read-only
	  STATUS current
	  DESCRIPTION
        "
        Line Trscv Laser Turn On :This
        OID indicates the Line Trscv is
        turning on its laser <Help> Status
        indicating the Line Trscv is turning
        on its laser <Condtype> MSA_TX_TURN_ON
        <Probcause> informationalStatus(1000)
        <Alarmtype> other (1) <Polarity>
        (2)
        "
	  ::= { rm10010e40AlmmsaModuleState 5 }



rm10010e40AlmMsaTxOff OBJECT-TYPE
	  SYNTAX EkiOnOff
	  MAX-ACCESS read-only
	  STATUS current
	  DESCRIPTION
        "
        Line Trscv Laser Shutdown :This
        OID indicates the Line Trscv Laser
        is OFF <Help> Status indicating
        the Line Trscv Laser is OFF <Condtype>
        MSA_TX_OFF <Probcause> informationalStatus(1000)
        <Alarmtype> other (1) <Polarity>
        (2)
        "
	  ::= { rm10010e40AlmmsaModuleState 4 }



rm10010e40AlmMsaHighPowerUp OBJECT-TYPE
	  SYNTAX EkiOnOff
	  MAX-ACCESS read-only
	  STATUS current
	  DESCRIPTION
        "
        Line Trscv High Power Up :This
        OID indicates the Line Trscv is
        leaving Low Power state <Help>
         Status indicating the Line Trscv
        is leaving Low Power state <Condtype>
        MSA_HIGH_POWER_UP <Probcause> informationalStatus(1000)
        <Alarmtype> other (1) <Polarity>
        (2)
        "
	  ::= { rm10010e40AlmmsaModuleState 3 }



rm10010e40AlmMsaLowPower OBJECT-TYPE
	  SYNTAX EkiOnOff
	  MAX-ACCESS read-only
	  STATUS current
	  DESCRIPTION
        "
        Line Trscv Low Power :This OID
        indicates the Line Trscv is in
         low power state <Help> Status
         indicating the Line Trscv is in
        low power state <Condtype> MSA_LOW_POWER
        <Probcause> informationalStatus(1000)
        <Alarmtype> other (1) <Polarity>
        (2)
        "
	  ::= { rm10010e40AlmmsaModuleState 2 }



rm10010e40AlmMsaInitialize OBJECT-TYPE
	  SYNTAX EkiOnOff
	  MAX-ACCESS read-only
	  STATUS current
	  DESCRIPTION
        "
        Line Trscv Initialize :This OID
        indicates the Line Trscv initialization
        is in progress <Help> Status indicating
        the Line Trscv initialization is
        in progress <Condtype> MSA_INITIALIZE
        <Probcause> informationalStatus(1000)
        <Alarmtype> other (1) <Polarity>
        (2)
        "
	  ::= { rm10010e40AlmmsaModuleState 1 }



--- *****************************************************
---     LEAF for the msaModuleGeneralStatus article
--- *****************************************************
rm10010e40AlmmsaModuleGeneralStatus OBJECT IDENTIFIER ::= { rm10010e40AlmOtherCrit 47 }




rm10010e40AlmMsaHwInterlock OBJECT-TYPE
	  SYNTAX EkiOnOff
	  MAX-ACCESS read-only
	  STATUS current
	  DESCRIPTION
        "
        Line Trscv Hardware Interlock
         :This OID indicates the Line Trscv
        power is higher than the cooling
        capacity <Help> Alarm indicating
        the Line Trscv power is higher
         than the cooling capacity <Condtype>
        MSA_HW_INTERLOCK <Probcause> temperatureUnacceptable
        (51) <Alarmtype> equipmentAlarm
        (5) <Polarity> (2)
        "
	  ::= { rm10010e40AlmmsaModuleGeneralStatus 14 }



rm10010e40AlmMsaLossOfRefclk OBJECT-TYPE
	  SYNTAX EkiOnOff
	  MAX-ACCESS read-only
	  STATUS current
	  DESCRIPTION
        "
        Line Trscv Loss Of Ref Clock :This
        OID indicates a Loss of Reference
        clock is detected on the Line Trscv
        <Help> Alarm indicating a Loss
         of Reference clock is detected
        on the Line Trscv <Condtype> MSA_LOSS_OF_REFCLK
        <Probcause> inputOutputDeviceError
        (24) <Alarmtype> equipmentAlarm
        (5) <Polarity> (2)
        "
	  ::= { rm10010e40AlmmsaModuleGeneralStatus 11 }



rm10010e40AlmMsaTxJitterPllLol OBJECT-TYPE
	  SYNTAX EkiOnOff
	  MAX-ACCESS read-only
	  STATUS current
	  DESCRIPTION
        "
        Line Trscv Tx Jitter PLL Loss
         Of Lock :This OID indicates a
         Tx Jitter PLL Loss of Lock is
         detected on the Line Trscv <Help>
        Alarm indicating a Tx Jitter PLL
        Loss of Lock is detected on the
        Line Trscv <Condtype> MSA_TX_JITTER_PLL_LOL
        <Probcause> inputOutputDeviceError
        (24) <Alarmtype> equipmentAlarm
        (5) <Polarity> (2)
        "
	  ::= { rm10010e40AlmmsaModuleGeneralStatus 10 }



rm10010e40AlmMsaTxCmuLol OBJECT-TYPE
	  SYNTAX EkiOnOff
	  MAX-ACCESS read-only
	  STATUS current
	  DESCRIPTION
        "
        Line Trscv CMU Loss Of Lock :This
        OID indicates a Clock Multiplier
        Unit Loss of Lock is detected on
        the Line Trscv <Help> Alarm indicating
        a Clock Multiplier Unit Loss of
        Lock is detected on the Line Trscv
        <Condtype> MSA_TX_CMU_LOL <Probcause>
        inputOutputDeviceError (24) <Alarmtype>
        equipmentAlarm (5) <Polarity> (2)
        "
	  ::= { rm10010e40AlmmsaModuleGeneralStatus 9 }



rm10010e40AlmMsaTxLosf OBJECT-TYPE
	  SYNTAX EkiOnOff
	  MAX-ACCESS read-only
	  STATUS current
	  DESCRIPTION
        "
        Line Trscv Loss Of Signal Functionality
        :This OID indicates a Loss of Signal
        functionality is detected on the
        Line Trscv <Help> Alarm indicating
        a Loss of Signal functionality
         is detected on the Line Trscv
         <Condtype> MSA_TX_LOSF <Probcause>
        lossOfSignal (30) <Alarmtype> equipmentAlarm
        (5) <Polarity> (2)
        "
	  ::= { rm10010e40AlmmsaModuleGeneralStatus 8 }



rm10010e40AlmMsaTxHostLol OBJECT-TYPE
	  SYNTAX EkiOnOff
	  MAX-ACCESS read-only
	  STATUS current
	  DESCRIPTION
        "
        Line Trscv Tx Host Loss Of Lock
        :This OID indicates of Loss of
         Lock is detected on the Line Trscv
        Tx Host interface <Help> Alarm
         indicating of Loss of Lock is
         detected on the Line Trscv Tx
         Host interface <Condtype> MSA_TX_HOST_LOL
        <Probcause> receiverFailure (42)
        <Alarmtype> equipmentAlarm (5)
         <Polarity> (2)
        "
	  ::= { rm10010e40AlmmsaModuleGeneralStatus 7 }



rm10010e40AlmMsaRxLos OBJECT-TYPE
	  SYNTAX EkiOnOff
	  MAX-ACCESS read-only
	  STATUS current
	  DESCRIPTION
        "
        Line Trscv Loss Of Signal :This
        OID indicates a Loss of Signal
         is detected on the Line Trscv
         <Help> Alarm indicating a Loss
        of Signal is detected on the Line
        Trscv <Condtype> MSA_RX_LOS <Probcause>
        lossOfSignal (30) <Alarmtype> equipmentAlarm
        (5) <Polarity> (2)
        "
	  ::= { rm10010e40AlmmsaModuleGeneralStatus 6 }



rm10010e40AlmMsaRxNetworkLol OBJECT-TYPE
	  SYNTAX EkiOnOff
	  MAX-ACCESS read-only
	  STATUS current
	  DESCRIPTION
        "
        Line Trscv Rx Network Loss Of
         Lock :This OID indicates of Loss
        of Lock is detected on the Line
        Trscv Rx Network interface <Help>
        Alarm indicating of Loss of Lock
        is detected on the Line Trscv Rx
        Network interface <Condtype> MSA_RX_NETWORK_LOL
        <Probcause> receiverFailure (42)
        <Alarmtype> equipmentAlarm (5)
         <Polarity> (2)
        "
	  ::= { rm10010e40AlmmsaModuleGeneralStatus 5 }



rm10010e40AlmMsaOutOfAlignment OBJECT-TYPE
	  SYNTAX EkiOnOff
	  MAX-ACCESS read-only
	  STATUS current
	  DESCRIPTION
        "
        Line Trscv Out Of Alignment :This
        OID indicates an Out of alignment
        on the Line Trscv Host Interface
        <Help> Alarm indicating an Out
         of alignment on the Line Trscv
        Host Interface <Condtype> MSA_OUT_OF_ALIGNMENT
        <Probcause> receiverFailure (42)
        <Alarmtype> equipmentAlarm (5)
         <Polarity> (2)
        "
	  ::= { rm10010e40AlmmsaModuleGeneralStatus 4 }



--- *****************************************************
---     LEAF for the msaGlobalAlarmSummary article
--- *****************************************************
rm10010e40AlmmsaGlobalAlarmSummary OBJECT IDENTIFIER ::= { rm10010e40AlmOtherCrit 48 }




rm10010e40AlmMsaGlobAlarmAssertion  OBJECT-TYPE
	  SYNTAX EkiOnOff
	  MAX-ACCESS read-only
	  STATUS current
	  DESCRIPTION
        "
        Line Trscv Global Alarm :This
         OID indicates at least one Fault
        or Status is detected on the Line
        Trscv module <Help> Synthesis alarm
        indicating at least one Alarm,
         Warning, Fault or Status is detected
        on the Line Trscv module <Condtype>
        MSA_GLOB_ALARM_ASSERTION  <Probcause>
        informationalStatus(1000) <Alarmtype>
        other (1) <Polarity> (2)
        "
	  ::= { rm10010e40AlmmsaGlobalAlarmSummary 16 }



rm10010e40AlmMsaHostLaneFaultStatus  OBJECT-TYPE
	  SYNTAX EkiOnOff
	  MAX-ACCESS read-only
	  STATUS current
	  DESCRIPTION
        "
        Line Trscv Host Fault And Status
        :This OID indicates at least one
        Fault or Status is detected on
         the Line Trscv Host Interface
         <Help> Synthesis alarm indicating
        at least one Fault or Status is
        detected on the Line Trscv Host
        Interface <Condtype> MSA_HOST_LANE_FAULT_STATUS
         <Probcause> informationalStatus(1000)
        <Alarmtype> other (1) <Polarity>
        (2)
        "
	  ::= { rm10010e40AlmmsaGlobalAlarmSummary 15 }



rm10010e40AlmMsaNetworkLaneFaultStatus  OBJECT-TYPE
	  SYNTAX EkiOnOff
	  MAX-ACCESS read-only
	  STATUS current
	  DESCRIPTION
        "
        Line Trscv Network Fault And Status
        :This OID indicates at least one
        Fault or Status is detected on
         the Line Trscv Network Interface
        <Help> Synthesis alarm indicating
        at least one Fault or Status is
        detected on the Line Trscv Network
        Interface <Condtype> MSA_NETWORK_LANE_FAULT_STATUS
         <Probcause> informationalStatus(1000)
        <Alarmtype> other (1) <Polarity>
        (2)
        "
	  ::= { rm10010e40AlmmsaGlobalAlarmSummary 14 }



rm10010e40AlmMsaNetworkLaneAlarmWarning1 OBJECT-TYPE
	  SYNTAX EkiOnOff
	  MAX-ACCESS read-only
	  STATUS current
	  DESCRIPTION
        "
        Line Trscv Network Alarm And Warning
        1 :This OID indicates at least
         one DDM is detected on the Line
        Trscv Network Interface <Help>
         Synthesis alarm indicating at
         least one DDM Alarm or DDM Warning
        is detected on the Line Trscv Network
        Interface <Condtype> MSA_NETWORK_LANE_ALARM_WARNING_1
        <Probcause> informationalStatus(1000)
        <Alarmtype> other (1) <Polarity>
        (2)
        "
	  ::= { rm10010e40AlmmsaGlobalAlarmSummary 13 }



rm10010e40AlmMsaModuleAlarmWarning2 OBJECT-TYPE
	  SYNTAX EkiOnOff
	  MAX-ACCESS read-only
	  STATUS current
	  DESCRIPTION
        "
        Line Trscv Module Alarm And Warning
        2 :This OID indicates at least
         one DDM is detected on the Line
        Trscv module <Help> Synthesis alarm
        indicating at least one DDM Alarm
        or DDM Warning is detected on the
        Line Trscv module <Condtype> MSA_MODULE_ALARM_WARNING_2
        <Probcause> informationalStatus(1000)
        <Alarmtype> other (1) <Polarity>
        (2)
        "
	  ::= { rm10010e40AlmmsaGlobalAlarmSummary 12 }



rm10010e40AlmMsaModuleAlarmWarning1  OBJECT-TYPE
	  SYNTAX EkiOnOff
	  MAX-ACCESS read-only
	  STATUS current
	  DESCRIPTION
        "
        Line Trscv Module Alarm And Warning
        1 :This OID indicates at least
         one DDM is detected on the Line
        Trscv module <Help> Synthesis alarm
        indicating at least one DDM Alarm
        or DDM Warning is detected on the
        Line Trscv module <Condtype> MSA_MODULE_ALARM_WARNING_1
         <Probcause> informationalStatus(1000)
        <Alarmtype> other (1) <Polarity>
        (2)
        "
	  ::= { rm10010e40AlmmsaGlobalAlarmSummary 11 }



rm10010e40AlmModuleFault  OBJECT-TYPE
	  SYNTAX EkiOnOff
	  MAX-ACCESS read-only
	  STATUS current
	  DESCRIPTION
        "
        Line Trscv Module Fault :This
         OID indicates at least one Fault
        is detected on the Line Trscv module
        <Help> Synthesis alarm indicating
        at least one Fault is detected
         on the Line Trscv module <Condtype>
        MODULE_FAULT  <Probcause> informationalStatus(1000)
        <Alarmtype> other (1) <Polarity>
        (2)
        "
	  ::= { rm10010e40AlmmsaGlobalAlarmSummary 10 }



rm10010e40AlmMsaModuleGeneralStatus  OBJECT-TYPE
	  SYNTAX EkiOnOff
	  MAX-ACCESS read-only
	  STATUS current
	  DESCRIPTION
        "
        Line Trscv General Status :This
        OID indicates the Line Trscv module
        general <Help> Synthesis alarm
         indicating the Line Trscv module
        general status <Condtype> MSA_MODULE_GENERAL_STATUS
         <Probcause> informationalStatus(1000)
        <Alarmtype> other (1) <Polarity>
        (2)
        "
	  ::= { rm10010e40AlmmsaGlobalAlarmSummary 9 }



rm10010e40AlmMsaModuleState  OBJECT-TYPE
	  SYNTAX EkiOnOff
	  MAX-ACCESS read-only
	  STATUS current
	  DESCRIPTION
        "
        Line Trscv Module State :This
         OID indicates the Line Trscv module
        state <Help> Synthesis alarm indicating
        the Line Trscv module state <Condtype>
        MSA_MODULE_STATE  <Probcause> informationalStatus(1000)
        <Alarmtype> other (1) <Polarity>
        (2)
        "
	  ::= { rm10010e40AlmmsaGlobalAlarmSummary 8 }



rm10010e40AlmMsaNetworkLaneAlarmWarning2 OBJECT-TYPE
	  SYNTAX EkiOnOff
	  MAX-ACCESS read-only
	  STATUS current
	  DESCRIPTION
        "
        Line Trscv Network Alarm And Warning
        2 :This OID indicates at least
         one DDM This OID is detected on
        the Line Trscv Network Interface
        <Help> Synthesis alarm indicating
        at least one DDM Alarm or DDM Warning
        is detected on the Line Trscv Network
        Interface <Condtype> MSA_NETWORK_LANE_ALARM_WARNING_2
        <Probcause> informationalStatus(1000)
        <Alarmtype> other (1) <Polarity>
        (2)
        "
	  ::= { rm10010e40AlmmsaGlobalAlarmSummary 7 }



rm10010e40AlmMsaNetworkHostAlarmStatus OBJECT-TYPE
	  SYNTAX EkiOnOff
	  MAX-ACCESS read-only
	  STATUS current
	  DESCRIPTION
        "
        Line Trscv Network/Host Alarm
         Status :This OID indicates the
        state of the Network and Host interface
        of the Line Trscv <Help> Synthesis
        alarm indicating the alarm state
        of the Network and Host interface
        of the Line Trscv <Condtype> MSA_NETWORK_HOST_ALARM_STATUS
        <Probcause> informationalStatus(1000)
        <Alarmtype> other (1) <Polarity>
        (2)
        "
	  ::= { rm10010e40AlmmsaGlobalAlarmSummary 6 }



rm10010e40AlmMsaSoftGlobAlarmTest  OBJECT-TYPE
	  SYNTAX EkiOnOff
	  MAX-ACCESS read-only
	  STATUS current
	  DESCRIPTION
        "
        Line Trscv Global Alarm SW Test
        :This OID indicates the Line Trscv
        Global alarm This OID is raised
        by SW request for test purpose
         <Help> Status indicating the Line
        Trscv Global Alarm is raised by
        SW request for test purpose <Condtype>
        MSA_SOFT_GLOB_ALARM_TEST  <Probcause>
        informationalStatus(1000) <Alarmtype>
        other (1) <Polarity> (2)
        "
	  ::= { rm10010e40AlmmsaGlobalAlarmSummary 1 }



--- *****************************************************
---     LEAF for the msaNetworkTxAlignment article
--- *****************************************************
rm10010e40AlmmsaNetworkTxAlignment OBJECT IDENTIFIER ::= { rm10010e40AlmOtherCrit 49 }




rm10010e40AlmNetTxLossOfAlignment OBJECT-TYPE
	  SYNTAX EkiOnOff
	  MAX-ACCESS read-only
	  STATUS current
	  DESCRIPTION
        "
        Line Trscv Network Tx Loss Of
         Alignment :This OID indicates
         a Tx Loss of Alignment is detected
        on the Line Trscv Network interface
        <Help> Alarm indicating a Tx Loss
        of Alignment is detected on the
        Line Trscv Network interface <Condtype>
        NET_TX_LOSS_OF_ALIGNMENT <Probcause>
        transmitterFailure (56) <Alarmtype>
        equipmentAlarm (5) <Polarity> (2)
        "
	  ::= { rm10010e40AlmmsaNetworkTxAlignment 16 }



rm10010e40AlmNetTxOutOfAlignment OBJECT-TYPE
	  SYNTAX EkiOnOff
	  MAX-ACCESS read-only
	  STATUS current
	  DESCRIPTION
        "
        Line Trscv Network Tx Out Of Alignment
        :This OID indicates a Tx Out of
        Alignment is detected on the Line
        Trscv Network interface <Help>
         Alarm indicating a Tx Out of Alignment
        is detected on the Line Trscv Network
        interface <Condtype> NET_TX_OUT_OF_ALIGNMENT
        <Probcause> transmitterFailure
         (56) <Alarmtype> equipmentAlarm
        (5) <Polarity> (2)
        "
	  ::= { rm10010e40AlmmsaNetworkTxAlignment 15 }



rm10010e40AlmNetTxCmuLockFault OBJECT-TYPE
	  SYNTAX EkiOnOff
	  MAX-ACCESS read-only
	  STATUS current
	  DESCRIPTION
        "
        Line Trscv Network Tx CMU Lock
        Fault :This OID indicates a Tx
         Clock Multiplier Unit Lock Fault
        is detected on the Line Trscv Network
        interface <Help> Alarm indicating
        a Tx Clock Multiplier Unit Lock
        Fault is detected on the Line Trscv
        Network interface <Condtype> NET_TX_CMU_LOCK_FAULT
        <Probcause> transmitterFailure
         (56) <Alarmtype> equipmentAlarm
        (5) <Polarity> (2)
        "
	  ::= { rm10010e40AlmmsaNetworkTxAlignment 14 }



rm10010e40AlmNetTxReferenceClockFault OBJECT-TYPE
	  SYNTAX EkiOnOff
	  MAX-ACCESS read-only
	  STATUS current
	  DESCRIPTION
        "
        Line Trscv Network Tx Ref Clock
        Fault :This OID indicates a Tx
         Reference Clock Fault is detected
        on the Line Trscv Network interface
        <Help> Alarm indicating a Tx Reference
        Clock Fault is detected on the
         Line Trscv Network interface <Condtype>
        NET_TX_REFERENCE_CLOCK_FAULT <Probcause>
        transmitterFailure (56) <Alarmtype>
        equipmentAlarm (5) <Polarity> (2)
        "
	  ::= { rm10010e40AlmmsaNetworkTxAlignment 13 }



rm10010e40AlmNetTxTimingFault OBJECT-TYPE
	  SYNTAX EkiOnOff
	  MAX-ACCESS read-only
	  STATUS current
	  DESCRIPTION
        "
        Line Trscv Network Tx Timing Fault
        :This OID indicates a Tx Timing
        Fault is detected on the Line Trscv
        Network interface <Help> Alarm
         indicating a Tx Timing Fault is
        detected on the Line Trscv Network
        interface <Condtype> NET_TX_TIMING_FAULT
        <Probcause> transmitterFailure
         (56) <Alarmtype> equipmentAlarm
        (5) <Polarity> (2)
        "
	  ::= { rm10010e40AlmmsaNetworkTxAlignment 12 }



--- *****************************************************
---     LEAF for the msaNetworkRxAlignment article
--- *****************************************************
rm10010e40AlmmsaNetworkRxAlignment OBJECT IDENTIFIER ::= { rm10010e40AlmOtherCrit 50 }




rm10010e40AlmNetRxModemSyncDetectFault OBJECT-TYPE
	  SYNTAX EkiOnOff
	  MAX-ACCESS read-only
	  STATUS current
	  DESCRIPTION
        "
        Line Trscv Network Rx Modem Sync
        Detect Fault :This OID indicates
        a Rx Modem Synchronisation Detection
        Fault is detected on the Line Trscv
        Network interface <Help> Alarm
         indicating a Rx Modem Synchronisation
        Detection Fault is detected on
         the Line Trscv Network interface
        <Condtype> NET_RX_MODEM_SYNC_DETECT_FAULT
        <Probcause> receiverFailure (42)
        <Alarmtype> equipmentAlarm (5)
         <Polarity> (2)
        "
	  ::= { rm10010e40AlmmsaNetworkRxAlignment 16 }



rm10010e40AlmNetRxModemLockFault OBJECT-TYPE
	  SYNTAX EkiOnOff
	  MAX-ACCESS read-only
	  STATUS current
	  DESCRIPTION
        "
        Line Trscv Network Rx Modem Lock
        Fault :This OID indicates a Rx
         Modem Lock Fault is detected on
        the Line Trscv Network interface
        <Help> Alarm indicating a Rx Modem
        Lock Fault is detected on the Line
        Trscv Network interface <Condtype>
        NET_RX_MODEM_LOCK_FAULT <Probcause>
        receiverFailure (42) <Alarmtype>
        equipmentAlarm (5) <Polarity> (2)
        "
	  ::= { rm10010e40AlmmsaNetworkRxAlignment 15 }



rm10010e40AlmNetRxLossOfAlignment OBJECT-TYPE
	  SYNTAX EkiOnOff
	  MAX-ACCESS read-only
	  STATUS current
	  DESCRIPTION
        "
        Line Trscv Network Rx Loss Of
         Alignment :This OID indicates
         a Rx Loss of Alignment is detected
        on the Line Trscv Network interface
        <Help> Alarm indicating a Rx Loss
        of Alignment is detected on the
        Line Trscv Network interface <Condtype>
        NET_RX_LOSS_OF_ALIGNMENT <Probcause>
        receiverFailure (42) <Alarmtype>
        equipmentAlarm (5) <Polarity> (2)
        "
	  ::= { rm10010e40AlmmsaNetworkRxAlignment 14 }



rm10010e40AlmNetRxOutOfAlignment OBJECT-TYPE
	  SYNTAX EkiOnOff
	  MAX-ACCESS read-only
	  STATUS current
	  DESCRIPTION
        "
        Line Trscv Network Rx Out Of Alignment
        :This OID indicates a Rx Out of
        Alignment is detected on the Line
        Trscv Network interface <Help>
         Alarm indicating a Rx Out of Alignment
        is detected on the Line Trscv Network
        interface <Condtype> NET_RX_OUT_OF_ALIGNMENT
        <Probcause> receiverFailure (42)
        <Alarmtype> equipmentAlarm (5)
         <Polarity> (2)
        "
	  ::= { rm10010e40AlmmsaNetworkRxAlignment 13 }



rm10010e40AlmNetRxTimingFault OBJECT-TYPE
	  SYNTAX EkiOnOff
	  MAX-ACCESS read-only
	  STATUS current
	  DESCRIPTION
        "
        Line Trscv Network Rx Timing Fault
        :This OID indicates a Rx Timing
        Fault is detected on the Line Trscv
        Network interface <Help> Alarm
         indicating a Rx Timing Fault is
        detected on the Line Trscv Network
        interface <Condtype> NET_RX_TIMING_FAULT
        <Probcause> receiverFailure (42)
        <Alarmtype> equipmentAlarm (5)
         <Polarity> (2)
        "
	  ::= { rm10010e40AlmmsaNetworkRxAlignment 12 }



--- *****************************************************
---     LEAF for the msaNetworkHostNetworkAlarmSummary article
--- *****************************************************
rm10010e40AlmmsaNetworkHostNetworkAlarmSummary OBJECT IDENTIFIER ::= { rm10010e40AlmOtherCrit 51 }




rm10010e40AlmHostTxOtnStatus OBJECT-TYPE
	  SYNTAX EkiOnOff
	  MAX-ACCESS read-only
	  STATUS current
	  DESCRIPTION
        "
        Line Trscv Host Tx OTN :This OID
        indicates a Tx OTN Fault is detected
        on the Line Trscv Host interface
        <Help> Synthesis Alarm indicating
        a Tx OTN Fault is detected on the
        Line Trscv Host interface <Condtype>
        HOST_TX_OTN_STATUS <Probcause>
         informationalStatus(1000) <Alarmtype>
        other (1) <Polarity> (2)
        "
	  ::= { rm10010e40AlmmsaNetworkHostNetworkAlarmSummary 16 }



rm10010e40AlmHostTxAlignment OBJECT-TYPE
	  SYNTAX EkiOnOff
	  MAX-ACCESS read-only
	  STATUS current
	  DESCRIPTION
        "
        Line Trscv Host Tx Alignment :This
        OID indicates a Tx Alignment Fault
        is detected on the Line Trscv Host
        interface <Help> Synthesis Alarm
        indicating a Tx Alignment Fault
        is detected on the Line Trscv Host
        interface <Condtype> HOST_TX_ALIGNMENT
        <Probcause> informationalStatus(1000)
        <Alarmtype> other (1) <Polarity>
        (2)
        "
	  ::= { rm10010e40AlmmsaNetworkHostNetworkAlarmSummary 15 }



rm10010e40AlmHostRxAlignment OBJECT-TYPE
	  SYNTAX EkiOnOff
	  MAX-ACCESS read-only
	  STATUS current
	  DESCRIPTION
        "
        Line Trscv Host Rx Alignment :This
        OID indicates a Rx Alignment Fault
        is detected on the Line Trscv Host
        interface <Help> Synthesis Alarm
        indicating a Rx Alignment Fault
        is detected on the Line Trscv Host
        interface <Condtype> HOST_RX_ALIGNMENT
        <Probcause> informationalStatus(1000)
        <Alarmtype> other (1) <Polarity>
        (2)
        "
	  ::= { rm10010e40AlmmsaNetworkHostNetworkAlarmSummary 14 }



rm10010e40AlmNetworkRxOtn OBJECT-TYPE
	  SYNTAX EkiOnOff
	  MAX-ACCESS read-only
	  STATUS current
	  DESCRIPTION
        "
        Line Trscv Network Rx OTN :This
        OID indicates a Rx OTN Fault is
        detected on the Line Trscv Network
        interface <Help> Synthesis Alarm
        indicating a Rx OTN Fault is detected
        on the Line Trscv Network interface
        <Condtype> NETWORK_RX_OTN <Probcause>
        informationalStatus(1000) <Alarmtype>
        other (1) <Polarity> (2)
        "
	  ::= { rm10010e40AlmmsaNetworkHostNetworkAlarmSummary 13 }



rm10010e40AlmNetworkRxAlignment OBJECT-TYPE
	  SYNTAX EkiOnOff
	  MAX-ACCESS read-only
	  STATUS current
	  DESCRIPTION
        "
        Line Trscv Network Rx Alignment
        :This OID indicates a Rx Alignment
        Fault is detected on the Line Trscv
        Network interface <Help> Synthesis
        Alarm indicating a Rx Alignment
        Fault is detected on the Line Trscv
        Network interface <Condtype> NETWORK_RX_ALIGNMENT
        <Probcause> informationalStatus(1000)
        <Alarmtype> other (1) <Polarity>
        (2)
        "
	  ::= { rm10010e40AlmmsaNetworkHostNetworkAlarmSummary 12 }



rm10010e40AlmNetworkTxAlignment OBJECT-TYPE
	  SYNTAX EkiOnOff
	  MAX-ACCESS read-only
	  STATUS current
	  DESCRIPTION
        "
        Line Trscv Network Tx Alignment
        :This OID indicates a Tx Alignment
        Fault is detected on the Line Trscv
        Network interface <Help> Synthesis
        Alarm indicating a Tx Alignment
        Fault is detected on the Line Trscv
        Network interface <Condtype> NETWORK_TX_ALIGNMENT
        <Probcause> informationalStatus(1000)
        <Alarmtype> other (1) <Polarity>
        (2)
        "
	  ::= { rm10010e40AlmmsaNetworkHostNetworkAlarmSummary 11 }



--- *****************************************************
---     LEAF for the msaHostTxAlignment article
--- *****************************************************
rm10010e40AlmmsaHostTxAlignment OBJECT IDENTIFIER ::= { rm10010e40AlmOtherCrit 52 }




rm10010e40AlmHostTxCdrLockFault OBJECT-TYPE
	  SYNTAX EkiOnOff
	  MAX-ACCESS read-only
	  STATUS current
	  DESCRIPTION
        "
        Line Trscv Host Tx CDR Lock Fault
        :This OID indicates a Tx Clock
         Data Recovery Lock Fault is detected
        on the Line Trscv Host interface
        <Help> Alarm indicating a Tx Clock
        Data Recovery Lock Fault is detected
        on the Line Trscv Host interface
        <Condtype> HOST_TX_CDR_LOCK_FAULT
        <Probcause> receiverFailure (42)
        <Alarmtype> equipmentAlarm (5)
         <Polarity> (2)
        "
	  ::= { rm10010e40AlmmsaHostTxAlignment 16 }



rm10010e40AlmHostTxLossOfAlignment OBJECT-TYPE
	  SYNTAX EkiOnOff
	  MAX-ACCESS read-only
	  STATUS current
	  DESCRIPTION
        "
        Line Trscv Host Tx Loss Of Alignment
        :This OID indicates a Tx Loss of
        Alignment is detected on the Line
        Trscv Host interface <Help> Alarm
        indicating a Tx Loss of Alignment
        is detected on the Line Trscv Host
        interface <Condtype> HOST_TX_LOSS_OF_ALIGNMENT
        <Probcause> receiverFailure (42)
        <Alarmtype> equipmentAlarm (5)
         <Polarity> (2)
        "
	  ::= { rm10010e40AlmmsaHostTxAlignment 15 }



rm10010e40AlmHostTxOutOfAlignment OBJECT-TYPE
	  SYNTAX EkiOnOff
	  MAX-ACCESS read-only
	  STATUS current
	  DESCRIPTION
        "
        Line Trscv Host Tx Out Of Alignment
        :This OID indicates a Tx Out of
        Alignment is detected on the Line
        Trscv Host interface <Help> Alarm
        indicating a Tx Out of Alignment
        is detected on the Line Trscv Host
        interface <Condtype> HOST_TX_OUT_OF_ALIGNMENT
        <Probcause> receiverFailure (42)
        <Alarmtype> equipmentAlarm (5)
         <Polarity> (2)
        "
	  ::= { rm10010e40AlmmsaHostTxAlignment 14 }



rm10010e40AlmHostTxDeskewLockFault OBJECT-TYPE
	  SYNTAX EkiOnOff
	  MAX-ACCESS read-only
	  STATUS current
	  DESCRIPTION
        "
        Line Trscv Host Tx Deskew Lock
        Fault :This OID indicates a Tx
         Deskew Lock Fault is detected
         on  the Line Trscv Host interface
        <Help> Alarm indicating a Tx Deskew
        Lock Fault is detected on  the
         Line Trscv Host interface <Condtype>
        HOST_TX_DESKEW_LOCK_FAULT <Probcause>
        receiverFailure (42) <Alarmtype>
        equipmentAlarm (5) <Polarity> (2)
        "
	  ::= { rm10010e40AlmmsaHostTxAlignment 13 }



--- *****************************************************
---     LEAF for the msaHostRxAlignment article
--- *****************************************************
rm10010e40AlmmsaHostRxAlignment OBJECT IDENTIFIER ::= { rm10010e40AlmOtherCrit 53 }




rm10010e40AlmHostRxLossOfAlignment OBJECT-TYPE
	  SYNTAX EkiOnOff
	  MAX-ACCESS read-only
	  STATUS current
	  DESCRIPTION
        "
        Line Trscv Host Rx Loss Of Alignment
        :This OID indicates a Rx Loss of
        Alignment is detected on the Line
        Trscv Host interface <Help> Alarm
        indicating a Rx Loss of Alignment
        is detected on the Line Trscv Host
        interface <Condtype> HOST_RX_LOSS_OF_ALIGNMENT
        <Probcause> transmitterFailure
         (56) <Alarmtype> equipmentAlarm
        (5) <Polarity> (2)
        "
	  ::= { rm10010e40AlmmsaHostRxAlignment 16 }



rm10010e40AlmHostRxOutOfAlignment OBJECT-TYPE
	  SYNTAX EkiOnOff
	  MAX-ACCESS read-only
	  STATUS current
	  DESCRIPTION
        "
        Line Trscv Host Rx Out Of Alignment
        :This OID indicates a Rx Out of
        Alignment is detected on the Line
        Trscv Host interface <Help> Alarm
        indicating a Rx Out of Alignment
        is detected on the Line Trscv Host
        interface <Condtype> HOST_RX_OUT_OF_ALIGNMENT
        <Probcause> transmitterFailure
         (56) <Alarmtype> equipmentAlarm
        (5) <Polarity> (2)
        "
	  ::= { rm10010e40AlmmsaHostRxAlignment 15 }



rm10010e40AlmHostRxCmuLockFault OBJECT-TYPE
	  SYNTAX EkiOnOff
	  MAX-ACCESS read-only
	  STATUS current
	  DESCRIPTION
        "
        Line Trscv Host Rx CMU Lock Fault
        :This OID indicates a Rx Clock
         Multiplier Unit Lock Fault is
         detected on the Line Trscv Host
        interface <Help> Alarm indicating
        a Rx Clock Multiplier Unit Lock
        Fault is detected on the Line Trscv
        Host interface <Condtype> HOST_RX_CMU_LOCK_FAULT
        <Probcause> transmitterFailure
         (56) <Alarmtype> equipmentAlarm
        (5) <Polarity> (2)
        "
	  ::= { rm10010e40AlmmsaHostRxAlignment 14 }



--- *********************************************************
---     TABLE for the rm10010e40AlmclientNetworkLaneAlarmWarning articles
--- *********************************************************

rm10010e40AlmclientNetworkLaneAlarmWarningTable OBJECT-TYPE
	SYNTAX  SEQUENCE OF Rm10010e40AlmclientNetworkLaneAlarmWarningEntry
	MAX-ACCESS not-accessible
	STATUS current
	DESCRIPTION
        "
        List of rm10010e40AlmclientNetworkLaneAlarmWarning
        Article
        "
	::= { rm10010e40AlmClientNurg 56 }


rm10010e40AlmclientNetworkLaneAlarmWarningEntry OBJECT-TYPE
	SYNTAX Rm10010e40AlmclientNetworkLaneAlarmWarningEntry
	MAX-ACCESS not-accessible
	STATUS current
	DESCRIPTION
        "
        Row definition for the rm10010e40AlmclientNetworkLaneAlarmWarning
        table
        "
	INDEX   { rm10010e40AlmclientNetworkLaneAlarmWarningIndex }
	::= { rm10010e40AlmclientNetworkLaneAlarmWarningTable 1 }


Rm10010e40AlmclientNetworkLaneAlarmWarningEntry ::=
	SEQUENCE {
	rm10010e40AlmclientNetworkLaneAlarmWarningIndex
		INTEGER,
	rm10010e40AlmClientBiasHighAlarmPortn
		EkiOnOff,
	rm10010e40AlmClientBiasHighWarningPortn
		EkiOnOff,
	rm10010e40AlmClientBiasLowWarningPortn
		EkiOnOff,
	rm10010e40AlmClientBiasLowAlarmPortn
		EkiOnOff,
	rm10010e40AlmClientTxPowerHighAlarmPortn
		EkiOnOff,
	rm10010e40AlmClientTxPowerHighWarningPortn
		EkiOnOff,
	rm10010e40AlmClientTxPowerLowWarningPortn
		EkiOnOff,
	rm10010e40AlmClientTxPowerLowAlarmPortn
		EkiOnOff,
	rm10010e40AlmClientLaserTempHighAlarmPortn
		EkiOnOff,
	rm10010e40AlmClientLaserTempHighWarningPortn
		EkiOnOff,
	rm10010e40AlmClientLaserTempLowWarningPortn
		EkiOnOff,
	rm10010e40AlmLaserTempLowAlarmPortn
		EkiOnOff,
	rm10010e40AlmClientRxPowerHighAlarmPortn
		EkiOnOff,
	rm10010e40AlmClientRxPowerHighWarningPortn
		EkiOnOff,
	rm10010e40AlmClientRxPowerLowWarningPortn
		EkiOnOff,
	rm10010e40AlmClientRxPowerLowAlarmPortn
		EkiOnOff
	}


rm10010e40AlmclientNetworkLaneAlarmWarningIndex OBJECT-TYPE
	SYNTAX  INTEGER(0..128)
	MAX-ACCESS  read-only
	STATUS current
	DESCRIPTION
        "
        Index definition for the rm10010e40AlmclientNetworkLaneAlarmWarning
        table
        "
	::= { rm10010e40AlmclientNetworkLaneAlarmWarningEntry 1 }


rm10010e40AlmClientBiasHighAlarmPortn OBJECT-TYPE
	SYNTAX  EkiOnOff
	MAX-ACCESS read-only
	STATUS current
	DESCRIPTION
        "
        Client Trscv Bias High Alarm :This
        OID indicates that the Trscv laser
        bias current is higher than the
        threshold value written in the
         Trscv EEPROM <Help> Alarm indicating
        that the Trscv laser bias current
        is higher than the threshold value
        written in the Trscv EEPROM <Condtype>
        CLIENT_BIAS_HIGH_ALARM <Probcause>
        transmitterFailure (56) <Alarmtype>
        equipmentAlarm (5) <Polarity> (2)
        "
	::= { rm10010e40AlmclientNetworkLaneAlarmWarningEntry 17 }


rm10010e40AlmClientBiasHighWarningPortn OBJECT-TYPE
	SYNTAX  EkiOnOff
	MAX-ACCESS read-only
	STATUS current
	DESCRIPTION
        "
        Client Trscv Bias High Warning
        :This OID indicates that the Trscv
        laser bias current is higher than
        the threshold value written in
         the Trscv EEPROM <Help> Warning
        indicating that the Trscv laser
        bias current is higher than the
        threshold value written in the
         Trscv EEPROM <Condtype> CLIENT_BIAS_HIGH_WARNING
        <Probcause> transmitterFailure
         (56) <Alarmtype> equipmentAlarm
        (5) <Polarity> (2)
        "
	::= { rm10010e40AlmclientNetworkLaneAlarmWarningEntry 16 }


rm10010e40AlmClientBiasLowWarningPortn OBJECT-TYPE
	SYNTAX  EkiOnOff
	MAX-ACCESS read-only
	STATUS current
	DESCRIPTION
        "
        Client Trscv Bias Low Warning
         :This OID indicates that the Trscv
        laser bias current is lower than
        the threshold value written in
         the Trscv EEPROM <Help> Warning
        indicating that the Trscv laser
        bias current is lower than the
         threshold value written in the
        Trscv EEPROM <Condtype> CLIENT_BIAS_LOW_WARNING
        <Probcause> transmitterFailure
         (56) <Alarmtype> equipmentAlarm
        (5) <Polarity> (2)
        "
	::= { rm10010e40AlmclientNetworkLaneAlarmWarningEntry 15 }


rm10010e40AlmClientBiasLowAlarmPortn OBJECT-TYPE
	SYNTAX  EkiOnOff
	MAX-ACCESS read-only
	STATUS current
	DESCRIPTION
        "
        Client Trscv Bias Low Alarm :This
        OID indicates that the Trscv laser
        bias current is lower than the
         threshold value written in the
        Trscv EEPROM <Help> Alarm indicating
        that the Trscv laser bias current
        is lower than the threshold value
        written in the Trscv EEPROM <Condtype>
        CLIENT_BIAS_LOW_ALARM <Probcause>
        transmitterFailure (56) <Alarmtype>
        equipmentAlarm (5) <Polarity> (2)
        "
	::= { rm10010e40AlmclientNetworkLaneAlarmWarningEntry 14 }


rm10010e40AlmClientTxPowerHighAlarmPortn OBJECT-TYPE
	SYNTAX  EkiOnOff
	MAX-ACCESS read-only
	STATUS current
	DESCRIPTION
        "
        Client Trscv Tx Power High Alarm
        :This OID indicates that the Trscv
        output power is higher than the
        threshold value written in the
         Trscv EEPROM <Help> Alarm indicating
        that the Trscv output power is
         higher than the threshold value
        written in the Trscv EEPROM <Condtype>
        CLIENT_TX_POWER_HIGH_ALARM <Probcause>
        transmitterFailure (56) <Alarmtype>
        equipmentAlarm (5) <Polarity> (2)
        "
	::= { rm10010e40AlmclientNetworkLaneAlarmWarningEntry 13 }


rm10010e40AlmClientTxPowerHighWarningPortn OBJECT-TYPE
	SYNTAX  EkiOnOff
	MAX-ACCESS read-only
	STATUS current
	DESCRIPTION
        "
        Client Trscv Tx Power High Warning
        :This OID indicates that the Trscv
        output power is higher than the
        threshold value written in the
         Trscv EEPROM <Help> Warning indicating
        that the Trscv output power is
         higher than the threshold value
        written in the Trscv EEPROM <Condtype>
        CLIENT_TX_POWER_HIGH_WARNING <Probcause>
        transmitterFailure (56) <Alarmtype>
        equipmentAlarm (5) <Polarity> (2)
        "
	::= { rm10010e40AlmclientNetworkLaneAlarmWarningEntry 12 }


rm10010e40AlmClientTxPowerLowWarningPortn OBJECT-TYPE
	SYNTAX  EkiOnOff
	MAX-ACCESS read-only
	STATUS current
	DESCRIPTION
        "
        Client Trscv Tx Power Low Warning
        :This OID indicates that the Trscv
        output power is lower than the
         threshold value written in the
        Trscv EEPROM <Help> Warning indicating
        that the Trscv output power is
         lower than the threshold value
        written in the Trscv EEPROM <Condtype>
        CLIENT_TX_POWER_LOW_WARNING <Probcause>
        transmitterFailure (56) <Alarmtype>
        equipmentAlarm (5) <Polarity> (2)
        "
	::= { rm10010e40AlmclientNetworkLaneAlarmWarningEntry 11 }


rm10010e40AlmClientTxPowerLowAlarmPortn OBJECT-TYPE
	SYNTAX  EkiOnOff
	MAX-ACCESS read-only
	STATUS current
	DESCRIPTION
        "
        Client Trscv Tx Power Low Alarm
        :This OID indicates that the Trscv
        output power is lower than the
         threshold value written in the
        Trscv EEPROM <Help> Alarm indicating
        that the Trscv output power is
         lower than the threshold value
        written in the Trscv EEPROM <Condtype>
        CLIENT_TX_POWER_LOW_ALARM <Probcause>
        transmitterFailure (56) <Alarmtype>
        equipmentAlarm (5) <Polarity> (2)
        "
	::= { rm10010e40AlmclientNetworkLaneAlarmWarningEntry 10 }


rm10010e40AlmClientLaserTempHighAlarmPortn OBJECT-TYPE
	SYNTAX  EkiOnOff
	MAX-ACCESS read-only
	STATUS current
	DESCRIPTION
        "
        Client Trscv Laser Temp High Alarm
        :This OID indicates that the Trscv
        Laser Temperature is higher than
        the threshold value written in
         the Trscv EEPROM <Help> Alarm
         indicating that the Trscv Laser
        Temperature is higher than the
         threshold value written in the
        Trscv EEPROM <Condtype> CLIENT_LASER_TEMP_HIGH_ALARM
        <Probcause> temperatureUnacceptable
        (51) <Alarmtype> equipmentAlarm
        (5) <Polarity> (2)
        "
	::= { rm10010e40AlmclientNetworkLaneAlarmWarningEntry 9 }


rm10010e40AlmClientLaserTempHighWarningPortn OBJECT-TYPE
	SYNTAX  EkiOnOff
	MAX-ACCESS read-only
	STATUS current
	DESCRIPTION
        "
        Client Trscv Laser Temp High Warning
        :This OID indicates that the Trscv
        Laser Temperature is higher than
        the threshold value written in
         the Trscv EEPROM <Help> Warning
        indicating that the Trscv Laser
        Temperature is higher than the
         threshold value written in the
        Trscv EEPROM <Condtype> CLIENT_LASER_TEMP_HIGH_WARNING
        <Probcause> temperatureUnacceptable
        (51) <Alarmtype> equipmentAlarm
        (5) <Polarity> (2)
        "
	::= { rm10010e40AlmclientNetworkLaneAlarmWarningEntry 8 }


rm10010e40AlmClientLaserTempLowWarningPortn OBJECT-TYPE
	SYNTAX  EkiOnOff
	MAX-ACCESS read-only
	STATUS current
	DESCRIPTION
        "
        Client Trscv Laser Temp Low Warning
        :This OID indicates that the Trscv
        Laser Temperature is lower than
        the threshold value written in
         the Trscv EEPROM <Help> Warning
        indicating that the Trscv Laser
        Temperature is lower than the threshold
        value written in the Trscv EEPROM
        <Condtype> CLIENT_LASER_TEMP_LOW_WARNING
        <Probcause> temperatureUnacceptable
        (51) <Alarmtype> equipmentAlarm
        (5) <Polarity> (2)
        "
	::= { rm10010e40AlmclientNetworkLaneAlarmWarningEntry 7 }


rm10010e40AlmLaserTempLowAlarmPortn OBJECT-TYPE
	SYNTAX  EkiOnOff
	MAX-ACCESS read-only
	STATUS current
	DESCRIPTION
        "
        Client Trscv Laser Temp Low Alarm
        :This OID indicates that the Trscv
        Laser Temperature is lower than
        the threshold value written in
         the Trscv EEPROM <Help> Alarm
         indicating that the Trscv Laser
        Temperature is lower than the threshold
        value written in the Trscv EEPROM
        <Condtype> LASER_TEMP_LOW_ALARM
        <Probcause> temperatureUnacceptable
        (51) <Alarmtype> equipmentAlarm
        (5) <Polarity> (2)
        "
	::= { rm10010e40AlmclientNetworkLaneAlarmWarningEntry 6 }


rm10010e40AlmClientRxPowerHighAlarmPortn OBJECT-TYPE
	SYNTAX  EkiOnOff
	MAX-ACCESS read-only
	STATUS current
	DESCRIPTION
        "
        Client Trscv Rx Power High Alarm
        :This OID indicates that the Trscv
        input power is higher than the
         threshold value written in the
        Trscv EEPROM <Help> Alarm indicating
        that the Trscv input power is higher
        than the threshold value written
        in the Trscv EEPROM <Condtype>
         CLIENT_RX_POWER_HIGH_ALARM <Probcause>
        receiveFailure (41) <Alarmtype>
        equipmentAlarm (5) <Polarity> (2)
        "
	::= { rm10010e40AlmclientNetworkLaneAlarmWarningEntry 5 }


rm10010e40AlmClientRxPowerHighWarningPortn OBJECT-TYPE
	SYNTAX  EkiOnOff
	MAX-ACCESS read-only
	STATUS current
	DESCRIPTION
        "
        Client Trscv Rx Power High Warning
        :This OID indicates that the Trscv
        input power is higher than the
         threshold value written in the
        Trscv EEPROM <Help> Warning indicating
        that the Trscv input power is higher
        than the threshold value written
        in the Trscv EEPROM <Condtype>
         CLIENT_RX_POWER_HIGH_WARNING <Probcause>
        receiveFailure (41) <Alarmtype>
        equipmentAlarm (5) <Polarity> (2)
        "
	::= { rm10010e40AlmclientNetworkLaneAlarmWarningEntry 4 }


rm10010e40AlmClientRxPowerLowWarningPortn OBJECT-TYPE
	SYNTAX  EkiOnOff
	MAX-ACCESS read-only
	STATUS current
	DESCRIPTION
        "
        Client Trscv Rx Power Low Warning
        :This OID indicates that the Trscv
        input power is lower than the threshold
        value written in the Trscv EEPROM
        <Help> Warning indicating that
         the Trscv input power is lower
        than the threshold value written
        in the Trscv EEPROM <Condtype>
         CLIENT_RX_POWER_LOW_WARNING <Probcause>
        receiveFailure (41) <Alarmtype>
        equipmentAlarm (5) <Polarity> (2)
        "
	::= { rm10010e40AlmclientNetworkLaneAlarmWarningEntry 3 }


rm10010e40AlmClientRxPowerLowAlarmPortn OBJECT-TYPE
	SYNTAX  EkiOnOff
	MAX-ACCESS read-only
	STATUS current
	DESCRIPTION
        "
        Client Trscv Rx Power Low Alarm
        :This OID indicates that the Trscv
        input power is lower than the threshold
        value written in the Trscv EEPROM
        <Help> Alarm indicating that the
        Trscv input power is lower than
        the threshold value written in
         the Trscv EEPROM <Condtype> CLIENT_RX_POWER_LOW_ALARM
        <Probcause> receiveFailure (41)
        <Alarmtype> equipmentAlarm (5)
         <Polarity> (2)
        "
	::= { rm10010e40AlmclientNetworkLaneAlarmWarningEntry 2 }


--- *********************************************************
---     TABLE for the rm10010e40AlmclientNetworkLaneFault articles
--- *********************************************************

rm10010e40AlmclientNetworkLaneFaultTable OBJECT-TYPE
	SYNTAX  SEQUENCE OF Rm10010e40AlmclientNetworkLaneFaultEntry
	MAX-ACCESS not-accessible
	STATUS current
	DESCRIPTION
        "
        List of rm10010e40AlmclientNetworkLaneFault
        Article
        "
	::= { rm10010e40AlmClientUrg 72 }


rm10010e40AlmclientNetworkLaneFaultEntry OBJECT-TYPE
	SYNTAX Rm10010e40AlmclientNetworkLaneFaultEntry
	MAX-ACCESS not-accessible
	STATUS current
	DESCRIPTION
        "
        Row definition for the rm10010e40AlmclientNetworkLaneFault
        table
        "
	INDEX   { rm10010e40AlmclientNetworkLaneFaultIndex }
	::= { rm10010e40AlmclientNetworkLaneFaultTable 1 }


Rm10010e40AlmclientNetworkLaneFaultEntry ::=
	SEQUENCE {
	rm10010e40AlmclientNetworkLaneFaultIndex
		INTEGER,
	rm10010e40AlmClientLaneTecFaultPortn
		EkiOnOff,
	rm10010e40AlmClientLaneWavelengthUnlockedPortn
		EkiOnOff,
	rm10010e40AlmClientLaneApdPowerSupplyPortn
		EkiOnOff,
	rm10010e40AlmClientLaneTxLosfPortn
		EkiOnOff,
	rm10010e40AlmClientLaneTxLolPortn
		EkiOnOff,
	rm10010e40AlmClientLaneRxLosPortn
		EkiOnOff,
	rm10010e40AlmClientLaneRxLolPortn
		EkiOnOff,
	rm10010e40AlmClientLaneRxFifoErrorPortn
		EkiOnOff
	}


rm10010e40AlmclientNetworkLaneFaultIndex OBJECT-TYPE
	SYNTAX  INTEGER(0..128)
	MAX-ACCESS  read-only
	STATUS current
	DESCRIPTION
        "
        Index definition for the rm10010e40AlmclientNetworkLaneFault
        table
        "
	::= { rm10010e40AlmclientNetworkLaneFaultEntry 1 }


rm10010e40AlmClientLaneTecFaultPortn OBJECT-TYPE
	SYNTAX  EkiOnOff
	MAX-ACCESS read-only
	STATUS current
	DESCRIPTION
        "
        Client Network Lane TEC Fault
         :This OID indicates a TEC Fault
        on the Client Trscv Network Lane
        <Help> Alarm indicating a TEC Fault
        on the Client Trscv Network Lane
        <Condtype> CLIENT_LANE_TEC_FAULT
        <Probcause> transmitterFailure
         (56) <Alarmtype> equipmentAlarm
        (5) <Polarity> (2)
        "
	::= { rm10010e40AlmclientNetworkLaneFaultEntry 17 }


rm10010e40AlmClientLaneWavelengthUnlockedPortn OBJECT-TYPE
	SYNTAX  EkiOnOff
	MAX-ACCESS read-only
	STATUS current
	DESCRIPTION
        "
        Client Network Lane Wavelength
        Unlock :This OID indicates a Wavelength
        unlock on the Client Trscv Network
        Lane <Help> Alarm indicating a
         Wavelength unlock on the Client
        Trscv Network Lane <Condtype> CLIENT_LANE_WAVELENGTH_UNLOCKED
        <Probcause> transmitterFailure
         (56) <Alarmtype> equipmentAlarm
        (5) <Polarity> (2)
        "
	::= { rm10010e40AlmclientNetworkLaneFaultEntry 16 }


rm10010e40AlmClientLaneApdPowerSupplyPortn OBJECT-TYPE
	SYNTAX  EkiOnOff
	MAX-ACCESS read-only
	STATUS current
	DESCRIPTION
        "
        Client Network Lane APD Power
         Supply :This OID indicates an
         APD Power supply failure on the
        Client Trscv Network Lane <Help>
        Alarm indicating an APD Power supply
        failure on the Client Trscv Network
        Lane <Condtype> CLIENT_LANE_APD_POWER_SUPPLY
        <Probcause> transmitterFailure
         (56) <Alarmtype> equipmentAlarm
        (5) <Polarity> (2)
        "
	::= { rm10010e40AlmclientNetworkLaneFaultEntry 15 }


rm10010e40AlmClientLaneTxLosfPortn OBJECT-TYPE
	SYNTAX  EkiOnOff
	MAX-ACCESS read-only
	STATUS current
	DESCRIPTION
        "
        Client Network Lane Tx Loss Of
        Signal Functionality :This OID
         indicates a Tx Loss of Signal
         Functionality on the Client Trscv
        Network Lane <Help> Alarm indicating
        a Tx Loss of Signal Functionality
        on the Client Trscv Network Lane
        <Condtype> CLIENT_LANE_TX_LOSF
         <Probcause> transmitterFailure
        (56) <Alarmtype> equipmentAlarm
        (5) <Polarity> (2)
        "
	::= { rm10010e40AlmclientNetworkLaneFaultEntry 9 }


rm10010e40AlmClientLaneTxLolPortn OBJECT-TYPE
	SYNTAX  EkiOnOff
	MAX-ACCESS read-only
	STATUS current
	DESCRIPTION
        "
        Client Network Lane Tx Loss Of
        Lock :This OID indicates a Tx Loss
        of Lock on the Client Trscv Network
        Lane <Help> Alarm indicating a
         Tx Loss of Lock on the Client
         Trscv Network Lane <Condtype>
         CLIENT_LANE_TX_LOL <Probcause>
        transmitterFailure (56) <Alarmtype>
        equipmentAlarm (5) <Polarity> (2)
        "
	::= { rm10010e40AlmclientNetworkLaneFaultEntry 8 }


rm10010e40AlmClientLaneRxLosPortn OBJECT-TYPE
	SYNTAX  EkiOnOff
	MAX-ACCESS read-only
	STATUS current
	DESCRIPTION
        "
        Client Network Lane Rx Loss Of
        Signal :This OID indicates a Rx
        Loss of Signal on the Client Trscv
        Network Lane <Help> Alarm indicating
        a Rx Loss of Signal on the Client
        Trscv Network Lane <Condtype> CLIENT_LANE_RX_LOS
        <Probcause> receiveFailure (41)
        <Alarmtype> physicalViolation (9)
        <Polarity> (2)
        "
	::= { rm10010e40AlmclientNetworkLaneFaultEntry 6 }


rm10010e40AlmClientLaneRxLolPortn OBJECT-TYPE
	SYNTAX  EkiOnOff
	MAX-ACCESS read-only
	STATUS current
	DESCRIPTION
        "
        Client Network Lane Rx Loss Of
        Lock :This OID indicates a Rx Loss
        of Lock on the Client Trscv Network
        Lane <Help> Alarm indicating a
         Rx Loss of Lock on the Client
         Trscv Network Lane <Condtype>
         CLIENT_LANE_RX_LOL <Probcause>
        receiverFailure (42) <Alarmtype>
        equipmentAlarm (5) <Polarity> (2)
        "
	::= { rm10010e40AlmclientNetworkLaneFaultEntry 5 }


rm10010e40AlmClientLaneRxFifoErrorPortn OBJECT-TYPE
	SYNTAX  EkiOnOff
	MAX-ACCESS read-only
	STATUS current
	DESCRIPTION
        "
        Client Network Lane Rx FIFO Error
        :This OID indicates a Rx FIFO Error
        on the Client Trscv Network Lane
        <Help> Alarm indicating a Rx FIFO
        Error on the Client Trscv Network
        Lane <Condtype> CLIENT_LANE_RX_FIFO_ERROR
        <Probcause> receiverFailure (42)
        <Alarmtype> equipmentAlarm (5)
         <Polarity> (2)
        "
	::= { rm10010e40AlmclientNetworkLaneFaultEntry 4 }


--- *********************************************************
---     TABLE for the rm10010e40AlmclientHostLaneFault articles
--- *********************************************************

rm10010e40AlmclientHostLaneFaultTable OBJECT-TYPE
	SYNTAX  SEQUENCE OF Rm10010e40AlmclientHostLaneFaultEntry
	MAX-ACCESS not-accessible
	STATUS current
	DESCRIPTION
        "
        List of rm10010e40AlmclientHostLaneFault
        Article
        "
	::= { rm10010e40AlmClientUrg 88 }


rm10010e40AlmclientHostLaneFaultEntry OBJECT-TYPE
	SYNTAX Rm10010e40AlmclientHostLaneFaultEntry
	MAX-ACCESS not-accessible
	STATUS current
	DESCRIPTION
        "
        Row definition for the rm10010e40AlmclientHostLaneFault
        table
        "
	INDEX   { rm10010e40AlmclientHostLaneFaultIndex }
	::= { rm10010e40AlmclientHostLaneFaultTable 1 }


Rm10010e40AlmclientHostLaneFaultEntry ::=
	SEQUENCE {
	rm10010e40AlmclientHostLaneFaultIndex
		INTEGER,
	rm10010e40AlmClientLaneTxFifoErrorPortn
		EkiOnOff,
	rm10010e40AlmClientTxHostLolPortn
		EkiOnOff,
	rm10010e40AlmClientCsfDetectedPortn
		EkiOnOff,
	rm10010e40AlmClientLanesNotAlignedPortn
		EkiOnOff,
	rm10010e40AlmClientLanes6466UnlockPortn
		EkiOnOff,
	rm10010e40AlmClientLanesMarkerUnlockPortn
		EkiOnOff,
	rm10010e40AlmClientInputLossOfSigPortn
		EkiOnOff,
	rm10010e40AlmClientLossOfSyncPortn
		EkiOnOff
	}


rm10010e40AlmclientHostLaneFaultIndex OBJECT-TYPE
	SYNTAX  INTEGER(0..128)
	MAX-ACCESS  read-only
	STATUS current
	DESCRIPTION
        "
        Index definition for the rm10010e40AlmclientHostLaneFault
        table
        "
	::= { rm10010e40AlmclientHostLaneFaultEntry 1 }


rm10010e40AlmClientLaneTxFifoErrorPortn OBJECT-TYPE
	SYNTAX  EkiOnOff
	MAX-ACCESS read-only
	STATUS current
	DESCRIPTION
        "
        Client Host Lane Tx FIFO Error
        :This OID indicates a Tx FIFO Error
        on the Client Trscv Host Lane <Help>
        Alarm indicating a Tx FIFO Error
        on the Client Trscv Host Lane <Condtype>
        CLIENT_LANE_TX_FIFO_ERROR <Probcause>
        receiverFailure (42) <Alarmtype>
        equipmentAlarm (5) <Polarity> (2)
        "
	::= { rm10010e40AlmclientHostLaneFaultEntry 11 }


rm10010e40AlmClientTxHostLolPortn OBJECT-TYPE
	SYNTAX  EkiOnOff
	MAX-ACCESS read-only
	STATUS current
	DESCRIPTION
        "
        Client Host Lane Tx Loss Of Lock
        :This OID indicates a Tx Loss of
        Lock on the Client Trscv Host Lane
        <Help> Alarm indicating a Tx Loss
        of Lock on the Client Trscv Host
        Lane <Condtype> CLIENT_TX_HOST_LOL
        <Probcause> receiverFailure (42)
        <Alarmtype> equipmentAlarm (5)
         <Polarity> (2)
        "
	::= { rm10010e40AlmclientHostLaneFaultEntry 10 }


rm10010e40AlmClientCsfDetectedPortn OBJECT-TYPE
	SYNTAX  EkiOnOff
	MAX-ACCESS read-only
	STATUS current
	DESCRIPTION
        "
        Client Signal Fail Detected :This
        OID indicates that a CSF has been
        detected on client port in the
         downstream direction   <Help>
          This alarm indicates if a Client
        Signal Fail has been detected in
        the incoming line frame for this
        client port <Condtype> CLIENT_CSF_DETECTED
        <Probcause> receiveFailure (41)
        <Alarmtype> other(1) <Polarity>
        (2)
        "
	::= { rm10010e40AlmclientHostLaneFaultEntry 7 }


rm10010e40AlmClientLanesNotAlignedPortn OBJECT-TYPE
	SYNTAX  EkiOnOff
	MAX-ACCESS read-only
	STATUS current
	DESCRIPTION
        "
        Client Lanes Not Aligned :This
        OID indicates the Client lanes
         are not aligned <Help> Alarm indicating
        the Client lanes are not aligned
        <Condtype> CLIENT_LANES_NOT_ALIGNED
        <Probcause> receiveFailure (41)
        <Alarmtype> integrityViolation
         (7) <Polarity> (2)
        "
	::= { rm10010e40AlmclientHostLaneFaultEntry 6 }


rm10010e40AlmClientLanes6466UnlockPortn OBJECT-TYPE
	SYNTAX  EkiOnOff
	MAX-ACCESS read-only
	STATUS current
	DESCRIPTION
        "
        Client Lanes 64/66b Unlock :This
        OID indicates the Client 64/66b
        decoder is not lock <Help> Alarm
        indicating the Client 64/66b decoder
        is not lock <Condtype> CLIENT_LANES_64_66_UNLOCK
        <Probcause> receiveFailure (41)
        <Alarmtype> integrityViolation
         (7) <Polarity> (2)
        "
	::= { rm10010e40AlmclientHostLaneFaultEntry 5 }


rm10010e40AlmClientLanesMarkerUnlockPortn OBJECT-TYPE
	SYNTAX  EkiOnOff
	MAX-ACCESS read-only
	STATUS current
	DESCRIPTION
        "
        Client Lanes Marker Unlock :This
        OID indicates the Client lanes
         marker alignment is not lock <Help>
        Alarm indicating the Client lanes
        marker alignment is not lock <Condtype>
        CLIENT_LANES_MARKER_UNLOCK <Probcause>
        receiveFailure (41) <Alarmtype>
        integrityViolation (7) <Polarity>
        (2)
        "
	::= { rm10010e40AlmclientHostLaneFaultEntry 4 }


rm10010e40AlmClientInputLossOfSigPortn OBJECT-TYPE
	SYNTAX  EkiOnOff
	MAX-ACCESS read-only
	STATUS current
	DESCRIPTION
        "
        Client Input Loss Of Signal :This
        OID indicates a Loss of Signal
         is detected on the Client Trscv
        <Help> Alarm indicating a Loss
         of Signal is detected on the Client
        Trscv <Condtype> CLIENT_INPUT_LOSS_OF_SIG
        <Probcause> receiveFailure (41)
        <Alarmtype> physicalViolation (9)
        <Polarity> (2)
        "
	::= { rm10010e40AlmclientHostLaneFaultEntry 3 }


rm10010e40AlmClientLossOfSyncPortn OBJECT-TYPE
	SYNTAX  EkiOnOff
	MAX-ACCESS read-only
	STATUS current
	DESCRIPTION
        "
        Client Frame Alignment Loss :This
        OID indicates the module is not
        aligned with the incoming Client
        signal <Help> Alarm indicating
         the module is not aligned with
        the incoming client signal <Condtype>
        CLIENT_LOSS_OF_SYNC <Probcause>
        receiveFailure (41) <Alarmtype>
        integrityViolation (7) <Polarity>
        (2)
        "
	::= { rm10010e40AlmclientHostLaneFaultEntry 2 }


--- *********************************************************
---     TABLE for the rm10010e40AlmlineNetworkLaneAlarmWarning1 articles
--- *********************************************************

rm10010e40AlmlineNetworkLaneAlarmWarning1Table OBJECT-TYPE
	SYNTAX  SEQUENCE OF Rm10010e40AlmlineNetworkLaneAlarmWarning1Entry
	MAX-ACCESS not-accessible
	STATUS current
	DESCRIPTION
        "
        List of rm10010e40AlmlineNetworkLaneAlarmWarning1
        Article
        "
	::= { rm10010e40AlmLineNurg 104 }


rm10010e40AlmlineNetworkLaneAlarmWarning1Entry OBJECT-TYPE
	SYNTAX Rm10010e40AlmlineNetworkLaneAlarmWarning1Entry
	MAX-ACCESS not-accessible
	STATUS current
	DESCRIPTION
        "
        Row definition for the rm10010e40AlmlineNetworkLaneAlarmWarning1
        table
        "
	INDEX   { rm10010e40AlmlineNetworkLaneAlarmWarning1Index }
	::= { rm10010e40AlmlineNetworkLaneAlarmWarning1Table 1 }


Rm10010e40AlmlineNetworkLaneAlarmWarning1Entry ::=
	SEQUENCE {
	rm10010e40AlmlineNetworkLaneAlarmWarning1Index
		INTEGER,
	rm10010e40AlmLineBiasHighAlarmPortn
		EkiOnOff,
	rm10010e40AlmLineBiasHighWarningPortn
		EkiOnOff,
	rm10010e40AlmLineBiasLowWarningPortn
		EkiOnOff,
	rm10010e40AlmLineBiasLowAlarmPortn
		EkiOnOff,
	rm10010e40AlmLineTxPowerHighAlarmPortn
		EkiOnOff,
	rm10010e40AlmLineTxPowerHighWarningPortn
		EkiOnOff,
	rm10010e40AlmLineTxPowerLowWarningPortn
		EkiOnOff,
	rm10010e40AlmLineTxPowerLowAlarmPortn
		EkiOnOff,
	rm10010e40AlmLineLaserTempHighAlarmPortn
		EkiOnOff,
	rm10010e40AlmLineLaserTempHighWarningPortn
		EkiOnOff,
	rm10010e40AlmLineLaserTempLowWarningPortn
		EkiOnOff,
	rm10010e40AlmLineLaserTempLowAlarmPortn
		EkiOnOff,
	rm10010e40AlmLineRxPowerHighAlarmPortn
		EkiOnOff,
	rm10010e40AlmLineRxPowerHighWarningPortn
		EkiOnOff,
	rm10010e40AlmLineRxPowerLowWarningPortn
		EkiOnOff,
	rm10010e40AlmLineRxPowerLowAlarmPortn
		EkiOnOff
	}


rm10010e40AlmlineNetworkLaneAlarmWarning1Index OBJECT-TYPE
	SYNTAX  INTEGER(0..128)
	MAX-ACCESS  read-only
	STATUS current
	DESCRIPTION
        "
        Index definition for the rm10010e40AlmlineNetworkLaneAlarmWarning1
        table
        "
	::= { rm10010e40AlmlineNetworkLaneAlarmWarning1Entry 1 }


rm10010e40AlmLineBiasHighAlarmPortn OBJECT-TYPE
	SYNTAX  EkiOnOff
	MAX-ACCESS read-only
	STATUS current
	DESCRIPTION
        "
        Line Trscv Tx Bias High Alarm
         :This OID indicates that the Trscv
        laser bias current is higher than
        the threshold value written in
         the Trscv EEPROM <Help> Alarm
         indicating that the Trscv laser
        bias current is higher than the
        threshold value written in the
         Trscv EEPROM <Condtype> LINE_BIAS_HIGH_ALARM
        <Probcause> transmitterFailure
         (56) <Alarmtype> equipmentAlarm
        (5) <Polarity> (2)
        "
	::= { rm10010e40AlmlineNetworkLaneAlarmWarning1Entry 17 }


rm10010e40AlmLineBiasHighWarningPortn OBJECT-TYPE
	SYNTAX  EkiOnOff
	MAX-ACCESS read-only
	STATUS current
	DESCRIPTION
        "
        Line Trscv Tx Bias High Warning
        :This OID indicates that the Trscv
        laser bias current is higher than
        the threshold value written in
         the Trscv EEPROM <Help> Warning
        indicating that the Trscv laser
        bias current is higher than the
        threshold value written in the
         Trscv EEPROM <Condtype> LINE_BIAS_HIGH_WARNING
        <Probcause> transmitterFailure
         (56) <Alarmtype> equipmentAlarm
        (5) <Polarity> (2)
        "
	::= { rm10010e40AlmlineNetworkLaneAlarmWarning1Entry 16 }


rm10010e40AlmLineBiasLowWarningPortn OBJECT-TYPE
	SYNTAX  EkiOnOff
	MAX-ACCESS read-only
	STATUS current
	DESCRIPTION
        "
        Line Trscv Tx Bias Low Warning
        :This OID indicates that the Trscv
        laser bias current is lower than
        the threshold value written in
         the Trscv EEPROM <Help> Warning
        indicating that the Trscv laser
        bias current is lower than the
         threshold value written in the
        Trscv EEPROM <Condtype> LINE_BIAS_LOW_WARNING
        <Probcause> transmitterFailure
         (56) <Alarmtype> equipmentAlarm
        (5) <Polarity> (2)
        "
	::= { rm10010e40AlmlineNetworkLaneAlarmWarning1Entry 15 }


rm10010e40AlmLineBiasLowAlarmPortn OBJECT-TYPE
	SYNTAX  EkiOnOff
	MAX-ACCESS read-only
	STATUS current
	DESCRIPTION
        "
        Line Trscv Tx Bias Low Alarm :This
        OID indicates that the Trscv laser
        bias current is lower than the
         threshold value written in the
        Trscv EEPROM <Help> Alarm indicating
        that the Trscv laser bias current
        is lower than the threshold value
        written in the Trscv EEPROM <Condtype>
        LINE_BIAS_LOW_ALARM <Probcause>
        transmitterFailure (56) <Alarmtype>
        equipmentAlarm (5) <Polarity> (2)
        "
	::= { rm10010e40AlmlineNetworkLaneAlarmWarning1Entry 14 }


rm10010e40AlmLineTxPowerHighAlarmPortn OBJECT-TYPE
	SYNTAX  EkiOnOff
	MAX-ACCESS read-only
	STATUS current
	DESCRIPTION
        "
        Line Trscv Tx Power High Alarm
        :This OID indicates that the Trscv
        output power is higher than the
        threshold value written in the
         Trscv EEPROM <Help> Alarm indicating
        that the Trscv output power is
         higher than the threshold value
        written in the Trscv EEPROM <Condtype>
        LINE_TX_POWER_HIGH_ALARM <Probcause>
        transmitterFailure (56) <Alarmtype>
        equipmentAlarm (5) <Polarity> (2)
        "
	::= { rm10010e40AlmlineNetworkLaneAlarmWarning1Entry 13 }


rm10010e40AlmLineTxPowerHighWarningPortn OBJECT-TYPE
	SYNTAX  EkiOnOff
	MAX-ACCESS read-only
	STATUS current
	DESCRIPTION
        "
        Line Trscv Tx Power High Warning
        :This OID indicates that the Trscv
        output power is higher than the
        threshold value written in the
         Trscv EEPROM <Help> Warning indicating
        that the Trscv output power is
         higher than the threshold value
        written in the Trscv EEPROM <Condtype>
        LINE_TX_POWER_HIGH_WARNING <Probcause>
        transmitterFailure (56) <Alarmtype>
        equipmentAlarm (5) <Polarity> (2)
        "
	::= { rm10010e40AlmlineNetworkLaneAlarmWarning1Entry 12 }


rm10010e40AlmLineTxPowerLowWarningPortn OBJECT-TYPE
	SYNTAX  EkiOnOff
	MAX-ACCESS read-only
	STATUS current
	DESCRIPTION
        "
        Line Trscv Tx Power Low Warning
        :This OID indicates that the Trscv
        output power is lower than the
         threshold value written in the
        Trscv EEPROM <Help> Warning indicating
        that the Trscv output power is
         lower than the threshold value
        written in the Trscv EEPROM <Condtype>
        LINE_TX_POWER_LOW_WARNING <Probcause>
        transmitterFailure (56) <Alarmtype>
        equipmentAlarm (5) <Polarity> (2)
        "
	::= { rm10010e40AlmlineNetworkLaneAlarmWarning1Entry 11 }


rm10010e40AlmLineTxPowerLowAlarmPortn OBJECT-TYPE
	SYNTAX  EkiOnOff
	MAX-ACCESS read-only
	STATUS current
	DESCRIPTION
        "
        Line Trscv Tx Power Low Alarm
         :This OID indicates that the Trscv
        output power is lower than the
         threshold value written in the
        Trscv EEPROM <Help> Alarm indicating
        that the Trscv output power is
         lower than the threshold value
        written in the Trscv EEPROM <Condtype>
        LINE_TX_POWER_LOW_ALARM <Probcause>
        transmitterFailure (56) <Alarmtype>
        equipmentAlarm (5) <Polarity> (2)
        "
	::= { rm10010e40AlmlineNetworkLaneAlarmWarning1Entry 10 }


rm10010e40AlmLineLaserTempHighAlarmPortn OBJECT-TYPE
	SYNTAX  EkiOnOff
	MAX-ACCESS read-only
	STATUS current
	DESCRIPTION
        "
        Line Trscv Tx Laser Temp High
         Alarm :This OID indicates that
        the Trscv Tx Laser Temperature
         is higher than the threshold value
        written in the Trscv EEPROM <Help>
        Alarm indicating that the Trscv
        Tx Laser Temperature is higher
         than the threshold value written
        in the Trscv EEPROM <Condtype>
         LINE_LASER_TEMP_HIGH_ALARM <Probcause>
        temperatureUnacceptable (51) <Alarmtype>
        equipmentAlarm (5) <Polarity> (2)
        "
	::= { rm10010e40AlmlineNetworkLaneAlarmWarning1Entry 9 }


rm10010e40AlmLineLaserTempHighWarningPortn OBJECT-TYPE
	SYNTAX  EkiOnOff
	MAX-ACCESS read-only
	STATUS current
	DESCRIPTION
        "
        Line Trscv Tx Laser Temp High
         Warning :This OID indicates that
        the Trscv Tx Laser Temperature
         is higher than the threshold value
        written in the Trscv EEPROM <Help>
        Warning indicating that the Trscv
        Tx Laser Temperature is higher
         than the threshold value written
        in the Trscv EEPROM <Condtype>
         LINE_LASER_TEMP_HIGH_WARNING <Probcause>
        temperatureUnacceptable (51) <Alarmtype>
        equipmentAlarm (5) <Polarity> (2)
        "
	::= { rm10010e40AlmlineNetworkLaneAlarmWarning1Entry 8 }


rm10010e40AlmLineLaserTempLowWarningPortn OBJECT-TYPE
	SYNTAX  EkiOnOff
	MAX-ACCESS read-only
	STATUS current
	DESCRIPTION
        "
        Line Trscv Tx Laser Temp Low Warning
        :This OID indicates that the Trscv
        Tx Laser Temperature is lower than
        the threshold value written in
         the Trscv EEPROM <Help> Warning
        indicating that the Trscv Tx Laser
        Temperature is lower than the threshold
        value written in the Trscv EEPROM
        <Condtype> LINE_LASER_TEMP_LOW_WARNING
        <Probcause> temperatureUnacceptable
        (51) <Alarmtype> equipmentAlarm
        (5) <Polarity> (2)
        "
	::= { rm10010e40AlmlineNetworkLaneAlarmWarning1Entry 7 }


rm10010e40AlmLineLaserTempLowAlarmPortn OBJECT-TYPE
	SYNTAX  EkiOnOff
	MAX-ACCESS read-only
	STATUS current
	DESCRIPTION
        "
        Line Trscv Tx Laser Temp Low Alarm
        :This OID indicates that the Trscv
        Tx Laser Temperature is lower than
        the threshold value written in
         the Trscv EEPROM <Help> Alarm
         indicating that the Trscv Tx Laser
        Temperature is lower than the threshold
        value written in the Trscv EEPROM
        <Condtype> LINE_LASER_TEMP_LOW_ALARM
        <Probcause> temperatureUnacceptable
        (51) <Alarmtype> equipmentAlarm
        (5) <Polarity> (2)
        "
	::= { rm10010e40AlmlineNetworkLaneAlarmWarning1Entry 6 }


rm10010e40AlmLineRxPowerHighAlarmPortn OBJECT-TYPE
	SYNTAX  EkiOnOff
	MAX-ACCESS read-only
	STATUS current
	DESCRIPTION
        "
        Line Trscv Rx Power High Alarm
        :This OID indicates that the Trscv
        input power is higher than the
         threshold value written in the
        Trscv EEPROM <Help> Alarm indicating
        that the Trscv input power is higher
        than the threshold value written
        in the Trscv EEPROM <Condtype>
         LINE_RX_POWER_HIGH_ALARM <Probcause>
        receiveFailure (41) <Alarmtype>
        equipmentAlarm (5) <Polarity> (2)
        "
	::= { rm10010e40AlmlineNetworkLaneAlarmWarning1Entry 5 }


rm10010e40AlmLineRxPowerHighWarningPortn OBJECT-TYPE
	SYNTAX  EkiOnOff
	MAX-ACCESS read-only
	STATUS current
	DESCRIPTION
        "
        Line Trscv Rx Power High Warning
        :This OID indicates that the Trscv
        input power is higher than the
         threshold value written in the
        Trscv EEPROM <Help> Warning indicating
        that the Trscv input power is higher
        than the threshold value written
        in the Trscv EEPROM <Condtype>
         LINE_RX_POWER_HIGH_WARNING <Probcause>
        receiveFailure (41) <Alarmtype>
        equipmentAlarm (5) <Polarity> (2)
        "
	::= { rm10010e40AlmlineNetworkLaneAlarmWarning1Entry 4 }


rm10010e40AlmLineRxPowerLowWarningPortn OBJECT-TYPE
	SYNTAX  EkiOnOff
	MAX-ACCESS read-only
	STATUS current
	DESCRIPTION
        "
        Line Trscv Rx Power Low Warning
        :This OID indicates that the Trscv
        input power is lower than the threshold
        value written in the Trscv EEPROM
        <Help> Warning indicating that
         the Trscv input power is lower
        than the threshold value written
        in the Trscv EEPROM <Condtype>
         LINE_RX_POWER_LOW_WARNING <Probcause>
        receiveFailure (41) <Alarmtype>
        equipmentAlarm (5) <Polarity> (2)
        "
	::= { rm10010e40AlmlineNetworkLaneAlarmWarning1Entry 3 }


rm10010e40AlmLineRxPowerLowAlarmPortn OBJECT-TYPE
	SYNTAX  EkiOnOff
	MAX-ACCESS read-only
	STATUS current
	DESCRIPTION
        "
        Line Trscv Rx Power Low Alarm
         :This OID indicates that the Trscv
        input power is lower than the threshold
        value written in the Trscv EEPROM
        <Help> Alarm indicating that the
        Trscv input power is lower than
        the threshold value written in
         the Trscv EEPROM <Condtype> LINE_RX_POWER_LOW_ALARM
        <Probcause> receiveFailure (41)
        <Alarmtype> equipmentAlarm (5)
         <Polarity> (2)
        "
	::= { rm10010e40AlmlineNetworkLaneAlarmWarning1Entry 2 }


--- *********************************************************
---     TABLE for the rm10010e40AlmlineNetworkLaneAlarmWarning2 articles
--- *********************************************************

rm10010e40AlmlineNetworkLaneAlarmWarning2Table OBJECT-TYPE
	SYNTAX  SEQUENCE OF Rm10010e40AlmlineNetworkLaneAlarmWarning2Entry
	MAX-ACCESS not-accessible
	STATUS current
	DESCRIPTION
        "
        List of rm10010e40AlmlineNetworkLaneAlarmWarning2
        Article
        "
	::= { rm10010e40AlmLineNurg 120 }


rm10010e40AlmlineNetworkLaneAlarmWarning2Entry OBJECT-TYPE
	SYNTAX Rm10010e40AlmlineNetworkLaneAlarmWarning2Entry
	MAX-ACCESS not-accessible
	STATUS current
	DESCRIPTION
        "
        Row definition for the rm10010e40AlmlineNetworkLaneAlarmWarning2
        table
        "
	INDEX   { rm10010e40AlmlineNetworkLaneAlarmWarning2Index }
	::= { rm10010e40AlmlineNetworkLaneAlarmWarning2Table 1 }


Rm10010e40AlmlineNetworkLaneAlarmWarning2Entry ::=
	SEQUENCE {
	rm10010e40AlmlineNetworkLaneAlarmWarning2Index
		INTEGER,
	rm10010e40AlmRxLaserBiasHighAlarmPortn
		EkiOnOff,
	rm10010e40AlmRxLaserBiasHighWarningPortn
		EkiOnOff,
	rm10010e40AlmRxLaserBiasLowWarningPortn
		EkiOnOff,
	rm10010e40AlmRxLaserBiasLowAlarmPortn
		EkiOnOff,
	rm10010e40AlmRxLaserOutputHighAlarmPortn
		EkiOnOff,
	rm10010e40AlmRxLaserOutputHighWarningPortn
		EkiOnOff,
	rm10010e40AlmRxLaserOutputLowWarningPortn
		EkiOnOff,
	rm10010e40AlmRxLaserOutputLowAlarmPortn
		EkiOnOff,
	rm10010e40AlmRxLaserTempHighAlarmPortn
		EkiOnOff,
	rm10010e40AlmRxLaserTempHighWarningPortn
		EkiOnOff,
	rm10010e40AlmRxLaserTempLowWarningPortn
		EkiOnOff,
	rm10010e40AlmRxLaserTempLowAlarmPortn
		EkiOnOff,
	rm10010e40AlmTxModulatorBiasHighAlarmPortn
		EkiOnOff,
	rm10010e40AlmTxModulatorBiasHighWarningPortn
		EkiOnOff,
	rm10010e40AlmTxModulatorBiasLowWarningPortn
		EkiOnOff,
	rm10010e40AlmTxModulatorBiasLowAlarmPortn
		EkiOnOff
	}


rm10010e40AlmlineNetworkLaneAlarmWarning2Index OBJECT-TYPE
	SYNTAX  INTEGER(0..128)
	MAX-ACCESS  read-only
	STATUS current
	DESCRIPTION
        "
        Index definition for the rm10010e40AlmlineNetworkLaneAlarmWarning2
        table
        "
	::= { rm10010e40AlmlineNetworkLaneAlarmWarning2Entry 1 }


rm10010e40AlmRxLaserBiasHighAlarmPortn OBJECT-TYPE
	SYNTAX  EkiOnOff
	MAX-ACCESS read-only
	STATUS current
	DESCRIPTION
        "
        Line Trscv Rx Bias High Alarm
         :This OID indicates that the Trscv
        Rx laser bias current is higher
        than the threshold value written
        in the Trscv EEPROM <Help> Alarm
        indicating that the Trscv Rx laser
        bias current is higher than the
        threshold value written in the
         Trscv EEPROM <Condtype> RX_LASER_BIAS_HIGH_ALARM
        <Probcause> receiveFailure (41)
        <Alarmtype> equipmentAlarm (5)
         <Polarity> (2)
        "
	::= { rm10010e40AlmlineNetworkLaneAlarmWarning2Entry 17 }


rm10010e40AlmRxLaserBiasHighWarningPortn OBJECT-TYPE
	SYNTAX  EkiOnOff
	MAX-ACCESS read-only
	STATUS current
	DESCRIPTION
        "
        Line Trscv Rx Bias High Warning
        :This OID indicates that the Trscv
        Rx laser bias current is higher
        than the threshold value written
        in the Trscv EEPROM <Help> Warning
        indicating that the Trscv Rx laser
        bias current is higher than the
        threshold value written in the
         Trscv EEPROM <Condtype> RX_LASER_BIAS_HIGH_WARNING
        <Probcause> receiveFailure (41)
        <Alarmtype> equipmentAlarm (5)
         <Polarity> (2)
        "
	::= { rm10010e40AlmlineNetworkLaneAlarmWarning2Entry 16 }


rm10010e40AlmRxLaserBiasLowWarningPortn OBJECT-TYPE
	SYNTAX  EkiOnOff
	MAX-ACCESS read-only
	STATUS current
	DESCRIPTION
        "
        Line Trscv Rx Bias Low Warning
        :This OID indicates that the Trscv
        Rx laser bias current is lower
         than the threshold value written
        in the Trscv EEPROM <Help> Warning
        indicating that the Trscv Rx laser
        bias current is lower than the
         threshold value written in the
        Trscv EEPROM <Condtype> RX_LASER_BIAS_LOW_WARNING
        <Probcause> receiveFailure (41)
        <Alarmtype> equipmentAlarm (5)
         <Polarity> (2)
        "
	::= { rm10010e40AlmlineNetworkLaneAlarmWarning2Entry 15 }


rm10010e40AlmRxLaserBiasLowAlarmPortn OBJECT-TYPE
	SYNTAX  EkiOnOff
	MAX-ACCESS read-only
	STATUS current
	DESCRIPTION
        "
        Line Trscv Rx Bias Low Alarm :This
        OID indicates that the Trscv Rx
        laser bias current is lower than
        the threshold value written in
         the Trscv EEPROM <Help> Alarm
         indicating that the Trscv Rx laser
        bias current is lower than the
         threshold value written in the
        Trscv EEPROM <Condtype> RX_LASER_BIAS_LOW_ALARM
        <Probcause> receiveFailure (41)
        <Alarmtype> equipmentAlarm (5)
         <Polarity> (2)
        "
	::= { rm10010e40AlmlineNetworkLaneAlarmWarning2Entry 14 }


rm10010e40AlmRxLaserOutputHighAlarmPortn OBJECT-TYPE
	SYNTAX  EkiOnOff
	MAX-ACCESS read-only
	STATUS current
	DESCRIPTION
        "
        Line Trscv Rx Output Power High
        Alarm :This OID indicates that
         the Trscv Rx output power is higher
        than the threshold value written
        in the Trscv EEPROM <Help> Alarm
        indicating that the Trscv Rx output
        power is higher than the threshold
        value written in the Trscv EEPROM
        <Condtype> RX_LASER_OUTPUT_HIGH_ALARM
        <Probcause> receiveFailure (41)
        <Alarmtype> equipmentAlarm (5)
         <Polarity> (2)
        "
	::= { rm10010e40AlmlineNetworkLaneAlarmWarning2Entry 13 }


rm10010e40AlmRxLaserOutputHighWarningPortn OBJECT-TYPE
	SYNTAX  EkiOnOff
	MAX-ACCESS read-only
	STATUS current
	DESCRIPTION
        "
        Line Trscv Rx Output Power High
        Warning :This OID indicates that
        the Trscv Rx output power is higher
        than the threshold value written
        in the Trscv EEPROM <Help> Warning
        indicating that the Trscv Rx output
        power is higher than the threshold
        value written in the Trscv EEPROM
        <Condtype> RX_LASER_OUTPUT_HIGH_WARNING
        <Probcause> receiveFailure (41)
        <Alarmtype> equipmentAlarm (5)
         <Polarity> (2)
        "
	::= { rm10010e40AlmlineNetworkLaneAlarmWarning2Entry 12 }


rm10010e40AlmRxLaserOutputLowWarningPortn OBJECT-TYPE
	SYNTAX  EkiOnOff
	MAX-ACCESS read-only
	STATUS current
	DESCRIPTION
        "
        Line Trscv Rx Output Power Low
        Warning :This OID indicates that
        the Trscv Rx output power is lower
        than the threshold value written
        in the Trscv EEPROM <Help> Warning
        indicating that the Trscv Rx output
        power is lower than the threshold
        value written in the Trscv EEPROM
        <Condtype> RX_LASER_OUTPUT_LOW_WARNING
        <Probcause> receiveFailure (41)
        <Alarmtype> equipmentAlarm (5)
         <Polarity> (2)
        "
	::= { rm10010e40AlmlineNetworkLaneAlarmWarning2Entry 11 }


rm10010e40AlmRxLaserOutputLowAlarmPortn OBJECT-TYPE
	SYNTAX  EkiOnOff
	MAX-ACCESS read-only
	STATUS current
	DESCRIPTION
        "
        Line Trscv Rx Output Power Low
        Alarm :This OID indicates that
         the Trscv Rx output power is lower
        than the threshold value written
        in the Trscv EEPROM <Help> Alarm
        indicating that the Trscv Rx output
        power is lower than the threshold
        value written in the Trscv EEPROM
        <Condtype> RX_LASER_OUTPUT_LOW_ALARM
        <Probcause> receiveFailure (41)
        <Alarmtype> equipmentAlarm (5)
         <Polarity> (2)
        "
	::= { rm10010e40AlmlineNetworkLaneAlarmWarning2Entry 10 }


rm10010e40AlmRxLaserTempHighAlarmPortn OBJECT-TYPE
	SYNTAX  EkiOnOff
	MAX-ACCESS read-only
	STATUS current
	DESCRIPTION
        "
        Line Trscv Rx Laser Temp High
         Alarm :This OID indicates that
        the Trscv Rx Laser Temperature
         is higher than the threshold value
        written in the Trscv EEPROM <Help>
        Alarm indicating that the Trscv
        Rx Laser Temperature is higher
         than the threshold value written
        in the Trscv EEPROM <Condtype>
         RX_LASER_TEMP_HIGH_ALARM <Probcause>
        temperatureUnacceptable (51) <Alarmtype>
        equipmentAlarm (5) <Polarity> (2)
        "
	::= { rm10010e40AlmlineNetworkLaneAlarmWarning2Entry 9 }


rm10010e40AlmRxLaserTempHighWarningPortn OBJECT-TYPE
	SYNTAX  EkiOnOff
	MAX-ACCESS read-only
	STATUS current
	DESCRIPTION
        "
        Line Trscv Rx Laser Temp High
         Warning :This OID indicates that
        the Trscv Rx Laser Temperature
         is higher than the threshold value
        written in the Trscv EEPROM <Help>
        Warning indicating that the Trscv
        Rx Laser Temperature is higher
         than the threshold value written
        in the Trscv EEPROM <Condtype>
         RX_LASER_TEMP_HIGH_WARNING <Probcause>
        temperatureUnacceptable (51) <Alarmtype>
        equipmentAlarm (5) <Polarity> (2)
        "
	::= { rm10010e40AlmlineNetworkLaneAlarmWarning2Entry 8 }


rm10010e40AlmRxLaserTempLowWarningPortn OBJECT-TYPE
	SYNTAX  EkiOnOff
	MAX-ACCESS read-only
	STATUS current
	DESCRIPTION
        "
        Line Trscv Rx Laser Temp Low Warning
        :This OID indicates that the Trscv
        Rx Laser Temperature is lower than
        the threshold value written in
         the Trscv EEPROM <Help> Warning
        indicating that the Trscv Rx Laser
        Temperature is lower than the threshold
        value written in the Trscv EEPROM
        <Condtype> RX_LASER_TEMP_LOW_WARNING
        <Probcause> temperatureUnacceptable
        (51) <Alarmtype> equipmentAlarm
        (5) <Polarity> (2)
        "
	::= { rm10010e40AlmlineNetworkLaneAlarmWarning2Entry 7 }


rm10010e40AlmRxLaserTempLowAlarmPortn OBJECT-TYPE
	SYNTAX  EkiOnOff
	MAX-ACCESS read-only
	STATUS current
	DESCRIPTION
        "
        Line Trscv Rx Laser Temp Low Alarm
        :This OID indicates that the Trscv
        Rx Laser Temperature is lower than
        the threshold value written in
         the Trscv EEPROM <Help> Alarm
         indicating that the Trscv Rx Laser
        Temperature is lower than the threshold
        value written in the Trscv EEPROM
        <Condtype> RX_LASER_TEMP_LOW_ALARM
        <Probcause> temperatureUnacceptable
        (51) <Alarmtype> equipmentAlarm
        (5) <Polarity> (2)
        "
	::= { rm10010e40AlmlineNetworkLaneAlarmWarning2Entry 6 }


rm10010e40AlmTxModulatorBiasHighAlarmPortn OBJECT-TYPE
	SYNTAX  EkiOnOff
	MAX-ACCESS read-only
	STATUS current
	DESCRIPTION
        "
        Line Trscv Tx Modulator Bias High
        Alarm :This OID indicates that
         the Trscv Tx modulator bias current
        is higher than the threshold value
        written in the Trscv EEPROM <Help>
        Alarm indicating that the Trscv
        Tx modulator bias current is higher
        than the threshold value written
        in the Trscv EEPROM <Condtype>
         TX_MODULATOR_BIAS_HIGH_ALARM <Probcause>
        transmitterFailure (56) <Alarmtype>
        equipmentAlarm (5) <Polarity> (2)
        "
	::= { rm10010e40AlmlineNetworkLaneAlarmWarning2Entry 5 }


rm10010e40AlmTxModulatorBiasHighWarningPortn OBJECT-TYPE
	SYNTAX  EkiOnOff
	MAX-ACCESS read-only
	STATUS current
	DESCRIPTION
        "
        Line Trscv Tx Modulator Bias High
        Warning :This OID indicates that
        the Trscv Tx modulator bias current
        is higher than the threshold value
        written in the Trscv EEPROM <Help>
        Warning indicating that the Trscv
        Tx modulator bias current is higher
        than the threshold value written
        in the Trscv EEPROM <Condtype>
         TX_MODULATOR_BIAS_HIGH_WARNING
        <Probcause> transmitterFailure
         (56) <Alarmtype> equipmentAlarm
        (5) <Polarity> (2)
        "
	::= { rm10010e40AlmlineNetworkLaneAlarmWarning2Entry 4 }


rm10010e40AlmTxModulatorBiasLowWarningPortn OBJECT-TYPE
	SYNTAX  EkiOnOff
	MAX-ACCESS read-only
	STATUS current
	DESCRIPTION
        "
        Line Trscv Tx Modulator Bias Low
        Warning :This OID indicates that
        the Trscv Tx modulator bias current
        is lower than the threshold value
        written in the Trscv EEPROM <Help>
        Warning indicating that the Trscv
        Tx modulator bias current is lower
        than the threshold value written
        in the Trscv EEPROM <Condtype>
         TX_MODULATOR_BIAS_LOW_WARNING
         <Probcause> transmitterFailure
        (56) <Alarmtype> equipmentAlarm
        (5) <Polarity> (2)
        "
	::= { rm10010e40AlmlineNetworkLaneAlarmWarning2Entry 3 }


rm10010e40AlmTxModulatorBiasLowAlarmPortn OBJECT-TYPE
	SYNTAX  EkiOnOff
	MAX-ACCESS read-only
	STATUS current
	DESCRIPTION
        "
        Line Trscv Tx Modulator Bias Low
        Alarm :This OID indicates that
         the Trscv Tx modulator bias current
        is lower than the threshold value
        written in the Trscv EEPROM <Help>
        Alarm indicating that the Trscv
        Tx modulator bias current is lower
        than the threshold value written
        in the Trscv EEPROM <Condtype>
         TX_MODULATOR_BIAS_LOW_ALARM <Probcause>
        transmitterFailure (56) <Alarmtype>
        equipmentAlarm (5) <Polarity> (2)
        "
	::= { rm10010e40AlmlineNetworkLaneAlarmWarning2Entry 2 }


--- *********************************************************
---     TABLE for the rm10010e40AlmlineNetworkLaneFault articles
--- *********************************************************

rm10010e40AlmlineNetworkLaneFaultTable OBJECT-TYPE
	SYNTAX  SEQUENCE OF Rm10010e40AlmlineNetworkLaneFaultEntry
	MAX-ACCESS not-accessible
	STATUS current
	DESCRIPTION
        "
        List of rm10010e40AlmlineNetworkLaneFault
        Article
        "
	::= { rm10010e40AlmLineUrg 136 }


rm10010e40AlmlineNetworkLaneFaultEntry OBJECT-TYPE
	SYNTAX Rm10010e40AlmlineNetworkLaneFaultEntry
	MAX-ACCESS not-accessible
	STATUS current
	DESCRIPTION
        "
        Row definition for the rm10010e40AlmlineNetworkLaneFault
        table
        "
	INDEX   { rm10010e40AlmlineNetworkLaneFaultIndex }
	::= { rm10010e40AlmlineNetworkLaneFaultTable 1 }


Rm10010e40AlmlineNetworkLaneFaultEntry ::=
	SEQUENCE {
	rm10010e40AlmlineNetworkLaneFaultIndex
		INTEGER,
	rm10010e40AlmLineLaneTecFaultPortn
		EkiOnOff,
	rm10010e40AlmLineLaneWavelengthUnlockedPortn
		EkiOnOff,
	rm10010e40AlmLineLaneApdPowerSupplyPortn
		EkiOnOff,
	rm10010e40AlmLineLaneTxLosfPortn
		EkiOnOff,
	rm10010e40AlmLineLaneTxLolPortn
		EkiOnOff,
	rm10010e40AlmLineLaneRxLosPortn
		EkiOnOff,
	rm10010e40AlmLineLaneRxLolPortn
		EkiOnOff,
	rm10010e40AlmLineLaneRxFifoErrorPortn
		EkiOnOff,
	rm10010e40AlmLineLaneRxTecFaultPortn
		EkiOnOff
	}


rm10010e40AlmlineNetworkLaneFaultIndex OBJECT-TYPE
	SYNTAX  INTEGER(0..128)
	MAX-ACCESS  read-only
	STATUS current
	DESCRIPTION
        "
        Index definition for the rm10010e40AlmlineNetworkLaneFault
        table
        "
	::= { rm10010e40AlmlineNetworkLaneFaultEntry 1 }


rm10010e40AlmLineLaneTecFaultPortn OBJECT-TYPE
	SYNTAX  EkiOnOff
	MAX-ACCESS read-only
	STATUS current
	DESCRIPTION
        "
        Line Network Lane TEC Fault :This
        OID indicates a Tx TEC Fault on
        the Line Trscv Network Lane <Help>
        Alarm indicating a Tx TEC Fault
        on the Line Trscv Network Lane
         <Condtype> LINE_LANE_TEC_FAULT
        <Probcause> transmitterFailure
         (56) <Alarmtype> equipmentAlarm
        (5) <Polarity> (2)
        "
	::= { rm10010e40AlmlineNetworkLaneFaultEntry 17 }


rm10010e40AlmLineLaneWavelengthUnlockedPortn OBJECT-TYPE
	SYNTAX  EkiOnOff
	MAX-ACCESS read-only
	STATUS current
	DESCRIPTION
        "
        Line Network Lane Wavelength Unlock
        :This OID indicates a Wavelength
        unlock on the Line Trscv Network
        Lane <Help> Alarm indicating a
         Wavelength unlock on the Line
         Trscv Network Lane <Condtype>
         LINE_LANE_WAVELENGTH_UNLOCKED
         <Probcause> transmitterFailure
        (56) <Alarmtype> equipmentAlarm
        (5) <Polarity> (2)
        "
	::= { rm10010e40AlmlineNetworkLaneFaultEntry 16 }


rm10010e40AlmLineLaneApdPowerSupplyPortn OBJECT-TYPE
	SYNTAX  EkiOnOff
	MAX-ACCESS read-only
	STATUS current
	DESCRIPTION
        "
        Line Network Lane APD Power Supply
        :This OID indicates an APD Power
        supply failure on the Line Trscv
        Network Lane <Help> Alarm indicating
        an APD Power supply failure on
         the Line Trscv Network Lane <Condtype>
        LINE_LANE_APD_POWER_SUPPLY <Probcause>
        transmitterFailure (56) <Alarmtype>
        equipmentAlarm (5) <Polarity> (2)
        "
	::= { rm10010e40AlmlineNetworkLaneFaultEntry 15 }


rm10010e40AlmLineLaneTxLosfPortn OBJECT-TYPE
	SYNTAX  EkiOnOff
	MAX-ACCESS read-only
	STATUS current
	DESCRIPTION
        "
        Line Network Lane Tx Loss Of Signal
        Functionality :This OID indicates
        a Tx Loss of Signal Functionality
        on the Line Trscv Network Lane
         <Help> Alarm indicating a Tx Loss
        of Signal Functionality on the
         Line Trscv Network Lane <Condtype>
        LINE_LANE_TX_LOSF <Probcause> transmitterFailure
        (56) <Alarmtype> equipmentAlarm
        (5) <Polarity> (2)
        "
	::= { rm10010e40AlmlineNetworkLaneFaultEntry 9 }


rm10010e40AlmLineLaneTxLolPortn OBJECT-TYPE
	SYNTAX  EkiOnOff
	MAX-ACCESS read-only
	STATUS current
	DESCRIPTION
        "
        Line Network Lane Tx Loss Of Lock
        :This OID indicates a Tx Loss of
        Lock on the Line Trscv Network
         Lane <Help> Alarm indicating a
        Tx Loss of Lock on the Line Trscv
        Network Lane <Condtype> LINE_LANE_TX_LOL
        <Probcause> transmitterFailure
         (56) <Alarmtype> equipmentAlarm
        (5) <Polarity> (2)
        "
	::= { rm10010e40AlmlineNetworkLaneFaultEntry 8 }


rm10010e40AlmLineLaneRxLosPortn OBJECT-TYPE
	SYNTAX  EkiOnOff
	MAX-ACCESS read-only
	STATUS current
	DESCRIPTION
        "
        Line Network Lane Rx Loss Of Signal
        :This OID indicates a Rx Loss of
        Signal on the Line Trscv Network
        Lane <Help> Alarm indicating a
         Rx Loss of Signal on the Line
         Trscv Network Lane <Condtype>
         LINE_LANE_RX_LOS <Probcause> receiveFailure
        (41) <Alarmtype> physicalViolation
        (9) <Polarity> (2)
        "
	::= { rm10010e40AlmlineNetworkLaneFaultEntry 6 }


rm10010e40AlmLineLaneRxLolPortn OBJECT-TYPE
	SYNTAX  EkiOnOff
	MAX-ACCESS read-only
	STATUS current
	DESCRIPTION
        "
        Line Network Lane Rx Loss Of Lock
        :This OID indicates a Rx Loss of
        Lock on the Line Trscv Network
         Lane <Help> Alarm indicating a
        Rx Loss of Lock on the Line Trscv
        Network Lane <Condtype> LINE_LANE_RX_LOL
        <Probcause> receiverFailure (42)
        <Alarmtype> equipmentAlarm (5)
         <Polarity> (2)
        "
	::= { rm10010e40AlmlineNetworkLaneFaultEntry 5 }


rm10010e40AlmLineLaneRxFifoErrorPortn OBJECT-TYPE
	SYNTAX  EkiOnOff
	MAX-ACCESS read-only
	STATUS current
	DESCRIPTION
        "
        Line Network Lane Rx FIFO Error
        :This OID indicates a Rx FIFO Error
        on the Line Trscv Network Lane
         <Help> Alarm indicating a Rx FIFO
        Error on the Line Trscv Network
        Lane <Condtype> LINE_LANE_RX_FIFO_ERROR
        <Probcause> receiverFailure (42)
        <Alarmtype> equipmentAlarm (5)
         <Polarity> (2)
        "
	::= { rm10010e40AlmlineNetworkLaneFaultEntry 4 }


rm10010e40AlmLineLaneRxTecFaultPortn OBJECT-TYPE
	SYNTAX  EkiOnOff
	MAX-ACCESS read-only
	STATUS current
	DESCRIPTION
        "
        Line Network Lane Rx TEC Fault
        :This OID indicates a Rx TEC Fault
        on the Line Trscv Network Lane
         <Help> Alarm indicating a Rx TEC
        Fault on the Line Trscv Network
        Lane <Condtype> LINE_LANE_RX_TEC_FAULT
        <Probcause> receiverFailure (42)
        <Alarmtype> equipmentAlarm (5)
         <Polarity> (2)
        "
	::= { rm10010e40AlmlineNetworkLaneFaultEntry 3 }


--- *********************************************************
---     TABLE for the rm10010e40AlmlineHostLaneFault articles
--- *********************************************************

rm10010e40AlmlineHostLaneFaultTable OBJECT-TYPE
	SYNTAX  SEQUENCE OF Rm10010e40AlmlineHostLaneFaultEntry
	MAX-ACCESS not-accessible
	STATUS current
	DESCRIPTION
        "
        List of rm10010e40AlmlineHostLaneFault
        Article
        "
	::= { rm10010e40AlmLineUrg 152 }


rm10010e40AlmlineHostLaneFaultEntry OBJECT-TYPE
	SYNTAX Rm10010e40AlmlineHostLaneFaultEntry
	MAX-ACCESS not-accessible
	STATUS current
	DESCRIPTION
        "
        Row definition for the rm10010e40AlmlineHostLaneFault
        table
        "
	INDEX   { rm10010e40AlmlineHostLaneFaultIndex }
	::= { rm10010e40AlmlineHostLaneFaultTable 1 }


Rm10010e40AlmlineHostLaneFaultEntry ::=
	SEQUENCE {
	rm10010e40AlmlineHostLaneFaultIndex
		INTEGER,
	rm10010e40AlmLineLaneTxFifoErrorPortn
		EkiOnOff,
	rm10010e40AlmLineTxHostLolPortn
		EkiOnOff,
	rm10010e40AlmLineSmIaeDetectedPortn
		EkiOnOff,
	rm10010e40AlmLineSmIaeInsertedPortn
		EkiOnOff,
	rm10010e40AlmLineSmBdiDetectedPortn
		EkiOnOff,
	rm10010e40AlmLineSmBdiInsertedPortn
		EkiOnOff,
	rm10010e40AlmLineLossOfFramePortn
		EkiOnOff,
	rm10010e40AlmLineInputLossOfSignalPortn
		EkiOnOff
	}


rm10010e40AlmlineHostLaneFaultIndex OBJECT-TYPE
	SYNTAX  INTEGER(0..128)
	MAX-ACCESS  read-only
	STATUS current
	DESCRIPTION
        "
        Index definition for the rm10010e40AlmlineHostLaneFault
        table
        "
	::= { rm10010e40AlmlineHostLaneFaultEntry 1 }


rm10010e40AlmLineLaneTxFifoErrorPortn OBJECT-TYPE
	SYNTAX  EkiOnOff
	MAX-ACCESS read-only
	STATUS current
	DESCRIPTION
        "
        Line Host Lane Tx FIFO Error :This
        OID indicates a Tx FIFO Error on
        the Line Trscv Host Lane <Help>
        Alarm indicating a Tx FIFO Error
        on the Line Trscv Host Lane <Condtype>
        LINE_LANE_TX_FIFO_ERROR <Probcause>
        receiverFailure (42) <Alarmtype>
        equipmentAlarm (5) <Polarity> (2)
        "
	::= { rm10010e40AlmlineHostLaneFaultEntry 11 }


rm10010e40AlmLineTxHostLolPortn OBJECT-TYPE
	SYNTAX  EkiOnOff
	MAX-ACCESS read-only
	STATUS current
	DESCRIPTION
        "
        Line Host Lane Tx Loss Of Lock
        :This OID indicates a Tx Loss of
        Lock on the Line Trscv Host Lane
        <Help> Alarm indicating a Tx Loss
        of Lock on the Line Trscv Host
         Lane <Condtype> LINE_TX_HOST_LOL
        <Probcause> receiverFailure (42)
        <Alarmtype> equipmentAlarm (5)
         <Polarity> (2)
        "
	::= { rm10010e40AlmlineHostLaneFaultEntry 10 }


rm10010e40AlmLineSmIaeDetectedPortn OBJECT-TYPE
	SYNTAX  EkiOnOff
	MAX-ACCESS read-only
	STATUS current
	DESCRIPTION
        "
        Line SM IAE Detected :This OID
        indicates a SM Incoming Alignment
        Error is detected on the incoming
        Line signal <Help> Alarm indicating
        a SM Incoming Alignment Error is
        detected on the incoming Line signal
        <Condtype> LINE_SM_IAE_DETECTED
        <Probcause> receiveFailure (41)
        <Alarmtype> integrityViolation
         (7) <Polarity> (2)
        "
	::= { rm10010e40AlmlineHostLaneFaultEntry 7 }


rm10010e40AlmLineSmIaeInsertedPortn OBJECT-TYPE
	SYNTAX  EkiOnOff
	MAX-ACCESS read-only
	STATUS current
	DESCRIPTION
        "
        Line SM IAE Inserted :This OID
        indicates a SM Incoming Alignment
        Error is inserted on the outgoing
        Line signal <Help> Status indicating
        a SM Incoming Alignment Error is
        inserted on the outgoing Line signal
        <Condtype> LINE_SM_IAE_INSERTED
        <Probcause> informationalStatus(1000)
        <Alarmtype> other (1) <Polarity>
        (2)
        "
	::= { rm10010e40AlmlineHostLaneFaultEntry 6 }


rm10010e40AlmLineSmBdiDetectedPortn OBJECT-TYPE
	SYNTAX  EkiOnOff
	MAX-ACCESS read-only
	STATUS current
	DESCRIPTION
        "
        Line SM BDI Detected :This OID
        indicates a SM Backward Defect
         Indication is detected on the
         incoming Line signal <Help> Alarm
        indicating a SM Backward Defect
        Indication is detected on the incoming
        Line signal <Condtype> LINE_SM_BDI_DETECTED
        <Probcause> receiveFailure (41)
        <Alarmtype> integrityViolation
         (7) <Polarity> (2)
        "
	::= { rm10010e40AlmlineHostLaneFaultEntry 5 }


rm10010e40AlmLineSmBdiInsertedPortn OBJECT-TYPE
	SYNTAX  EkiOnOff
	MAX-ACCESS read-only
	STATUS current
	DESCRIPTION
        "
        Line SM BDI Inserted :This OID
        indicates a SM Backward Defect
         Indication is inserted on the
         outgoing Line signal <Help> Status
        indicating a SM Backward Defect
        Indication is inserted on the outgoing
        Line signal <Condtype> LINE_SM_BDI_INSERTED
        <Probcause> informationalStatus(1000)
        <Alarmtype> other (1) <Polarity>
        (2)
        "
	::= { rm10010e40AlmlineHostLaneFaultEntry 4 }


rm10010e40AlmLineLossOfFramePortn OBJECT-TYPE
	SYNTAX  EkiOnOff
	MAX-ACCESS read-only
	STATUS current
	DESCRIPTION
        "
        Line Loss Of Frame :This OID indicates
        the module is not aligned with
         the incoming Line signal <Help>
        Alarm indicating the module is
         not aligned with the incoming
         Line signal <Condtype> LINE_LOSS_OF_FRAME
        <Probcause> receiveFailure (41)
        <Alarmtype> integrityViolation
         (7) <Polarity> (2)
        "
	::= { rm10010e40AlmlineHostLaneFaultEntry 3 }


rm10010e40AlmLineInputLossOfSignalPortn OBJECT-TYPE
	SYNTAX  EkiOnOff
	MAX-ACCESS read-only
	STATUS current
	DESCRIPTION
        "
        Line Input Loss Of Signal :This
        OID indicates a Loss of Signal
         is detected on the Line Trscv
         <Help> Alarm indicating a Loss
        of Signal is detected on the Line
        Trscv <Condtype> LINE_INPUT_LOSS_OF_SIGNAL
        <Probcause> receiveFailure (41)
        <Alarmtype> physicalViolation (9)
        <Polarity> (2)
        "
	::= { rm10010e40AlmlineHostLaneFaultEntry 2 }


--- *********************************************************
---     TABLE for the rm10010e40AlmlineNetworkLaneRxOtn articles
--- *********************************************************

rm10010e40AlmlineNetworkLaneRxOtnTable OBJECT-TYPE
	SYNTAX  SEQUENCE OF Rm10010e40AlmlineNetworkLaneRxOtnEntry
	MAX-ACCESS not-accessible
	STATUS current
	DESCRIPTION
        "
        List of rm10010e40AlmlineNetworkLaneRxOtn
        Article
        "
	::= { rm10010e40AlmLineUrg 168 }


rm10010e40AlmlineNetworkLaneRxOtnEntry OBJECT-TYPE
	SYNTAX Rm10010e40AlmlineNetworkLaneRxOtnEntry
	MAX-ACCESS not-accessible
	STATUS current
	DESCRIPTION
        "
        Row definition for the rm10010e40AlmlineNetworkLaneRxOtn
        table
        "
	INDEX   { rm10010e40AlmlineNetworkLaneRxOtnIndex }
	::= { rm10010e40AlmlineNetworkLaneRxOtnTable 1 }


Rm10010e40AlmlineNetworkLaneRxOtnEntry ::=
	SEQUENCE {
	rm10010e40AlmlineNetworkLaneRxOtnIndex
		INTEGER,
	rm10010e40AlmLineRxOtnLofPortn
		EkiOnOff,
	rm10010e40AlmLineRxOtnOofPortn
		EkiOnOff,
	rm10010e40AlmLineRxOtnLomPortn
		EkiOnOff,
	rm10010e40AlmLineRxOtnOomPortn
		EkiOnOff,
	rm10010e40AlmLineRxOtnIaePortn
		EkiOnOff,
	rm10010e40AlmLineRxSmBdiPortn
		EkiOnOff,
	rm10010e40AlmLineRxOtnOtuAisPortn
		EkiOnOff,
	rm10010e40AlmLineRxOtnOduAisPortn
		EkiOnOff
	}


rm10010e40AlmlineNetworkLaneRxOtnIndex OBJECT-TYPE
	SYNTAX  INTEGER(0..128)
	MAX-ACCESS  read-only
	STATUS current
	DESCRIPTION
        "
        Index definition for the rm10010e40AlmlineNetworkLaneRxOtn
        table
        "
	::= { rm10010e40AlmlineNetworkLaneRxOtnEntry 1 }


rm10010e40AlmLineRxOtnLofPortn OBJECT-TYPE
	SYNTAX  EkiOnOff
	MAX-ACCESS read-only
	STATUS current
	DESCRIPTION
        "
        Line Network Rx LOF :This OID
         indicates a Loss of Frame is detected
        on the Rx Network interface of
         the Line Trscv <Help> Alarm indicating
        a Loss of Frame is detected on
         the Rx Network interface of the
        Line Trscv <Condtype> LINE_RX_OTN_LOF
        <Probcause> receiveFailure (41)
        <Alarmtype> equipmentAlarm (5)
         <Polarity> (2)
        "
	::= { rm10010e40AlmlineNetworkLaneRxOtnEntry 17 }


rm10010e40AlmLineRxOtnOofPortn OBJECT-TYPE
	SYNTAX  EkiOnOff
	MAX-ACCESS read-only
	STATUS current
	DESCRIPTION
        "
        Line Network Rx OOF :This OID
         indicates an Out of Frame is detected
        on the Rx Network interface of
         the Line Trscv <Help> Alarm indicating
        an Out of Frame is detected on
         the Rx Network interface of the
        Line Trscv <Condtype> LINE_RX_OTN_OOF
        <Probcause> receiveFailure (41)
        <Alarmtype> equipmentAlarm (5)
         <Polarity> (2)
        "
	::= { rm10010e40AlmlineNetworkLaneRxOtnEntry 16 }


rm10010e40AlmLineRxOtnLomPortn OBJECT-TYPE
	SYNTAX  EkiOnOff
	MAX-ACCESS read-only
	STATUS current
	DESCRIPTION
        "
        Line Network Rx LOM :This OID
         indicates a Loss of Multiframe
        is detected on the Rx Network interface
        of the Line Trscv <Help> Alarm
         indicating a Loss of Multiframe
        is detected on the Rx Network interface
        of the Line Trscv <Condtype> LINE_RX_OTN_LOM
        <Probcause> receiveFailure (41)
        <Alarmtype> equipmentAlarm (5)
         <Polarity> (2)
        "
	::= { rm10010e40AlmlineNetworkLaneRxOtnEntry 15 }


rm10010e40AlmLineRxOtnOomPortn OBJECT-TYPE
	SYNTAX  EkiOnOff
	MAX-ACCESS read-only
	STATUS current
	DESCRIPTION
        "
        Line Network Rx OOM :This OID
         indicates an Out of Multiframe
        is detected on the Rx Network interface
        of the Line Trscv <Help> Alarm
         indicating an Out of Multiframe
        is detected on the Rx Network interface
        of the Line Trscv <Condtype> LINE_RX_OTN_OOM
        <Probcause> receiveFailure (41)
        <Alarmtype> equipmentAlarm (5)
         <Polarity> (2)
        "
	::= { rm10010e40AlmlineNetworkLaneRxOtnEntry 14 }


rm10010e40AlmLineRxOtnIaePortn OBJECT-TYPE
	SYNTAX  EkiOnOff
	MAX-ACCESS read-only
	STATUS current
	DESCRIPTION
        "
        Line Network Rx IAE :This OID
         indicates an Incoming Alignment
        Error is detected on the Rx Network
        interface of the Line Trscv <Help>
        Alarm indicating an Incoming Alignment
        Error is detected on the Rx Network
        interface of the Line Trscv <Condtype>
        LINE_RX_OTN_IAE <Probcause> receiveFailure
        (41) <Alarmtype> equipmentAlarm
        (5) <Polarity> (2)
        "
	::= { rm10010e40AlmlineNetworkLaneRxOtnEntry 13 }


rm10010e40AlmLineRxSmBdiPortn OBJECT-TYPE
	SYNTAX  EkiOnOff
	MAX-ACCESS read-only
	STATUS current
	DESCRIPTION
        "
        Line Network Rx SM BDI :This OID
        indicates an SM Backward Defect
        Indication is detected on the Rx
        Network interface of the Line Trscv
        <Help> Alarm indicating an SM Backward
        Defect Indication is detected on
        the Rx Network interface of the
        Line Trscv <Condtype> LINE_RX_SM_BDI
        <Probcause> informationalStatus(1000)
        <Alarmtype> other (1) <Polarity>
        (2)
        "
	::= { rm10010e40AlmlineNetworkLaneRxOtnEntry 12 }


rm10010e40AlmLineRxOtnOtuAisPortn OBJECT-TYPE
	SYNTAX  EkiOnOff
	MAX-ACCESS read-only
	STATUS current
	DESCRIPTION
        "
        Line Network Rx OTU AIS :This
         OID indicates an OTU This OID
         Indication Signal is detected
         on the Rx Network interface of
        the Line Trscv <Help> Alarm indicating
        an OTU Alarm Indication Signal
         is detected on the Rx Network
         interface of the Line Trscv <Condtype>
        LINE_RX_OTN_OTU_AIS <Probcause>
        receiveFailure (41) <Alarmtype>
        equipmentAlarm (5) <Polarity> (2)
        "
	::= { rm10010e40AlmlineNetworkLaneRxOtnEntry 11 }


rm10010e40AlmLineRxOtnOduAisPortn OBJECT-TYPE
	SYNTAX  EkiOnOff
	MAX-ACCESS read-only
	STATUS current
	DESCRIPTION
        "
        Line Network Rx ODU AIS :This
         OID indicates an ODU This OID
         Indication Signal is detected
         on the Rx Network interface of
        the Line Trscv <Help> Alarm indicating
        an ODU Alarm Indication Signal
         is detected on the Rx Network
         interface of the Line Trscv <Condtype>
        LINE_RX_OTN_ODU_AIS <Probcause>
        receiveFailure (41) <Alarmtype>
        equipmentAlarm (5) <Polarity> (2)
        "
	::= { rm10010e40AlmlineNetworkLaneRxOtnEntry 10 }


--- *********************************************************
---     TABLE for the rm10010e40AlmlineHostLaneTxOtn articles
--- *********************************************************

rm10010e40AlmlineHostLaneTxOtnTable OBJECT-TYPE
	SYNTAX  SEQUENCE OF Rm10010e40AlmlineHostLaneTxOtnEntry
	MAX-ACCESS not-accessible
	STATUS current
	DESCRIPTION
        "
        List of rm10010e40AlmlineHostLaneTxOtn
        Article
        "
	::= { rm10010e40AlmLineUrg 184 }


rm10010e40AlmlineHostLaneTxOtnEntry OBJECT-TYPE
	SYNTAX Rm10010e40AlmlineHostLaneTxOtnEntry
	MAX-ACCESS not-accessible
	STATUS current
	DESCRIPTION
        "
        Row definition for the rm10010e40AlmlineHostLaneTxOtn
        table
        "
	INDEX   { rm10010e40AlmlineHostLaneTxOtnIndex }
	::= { rm10010e40AlmlineHostLaneTxOtnTable 1 }


Rm10010e40AlmlineHostLaneTxOtnEntry ::=
	SEQUENCE {
	rm10010e40AlmlineHostLaneTxOtnIndex
		INTEGER,
	rm10010e40AlmLineTxOtnLofPortn
		EkiOnOff,
	rm10010e40AlmLineTxOtnOofPortn
		EkiOnOff,
	rm10010e40AlmLineTxOtnLomPortn
		EkiOnOff,
	rm10010e40AlmLineTxOtnOomPortn
		EkiOnOff,
	rm10010e40AlmLineTxOtnIaePortn
		EkiOnOff,
	rm10010e40AlmLineTxSmBdiPortn
		EkiOnOff,
	rm10010e40AlmLineTxOtnOtuAisPortn
		EkiOnOff,
	rm10010e40AlmLineTxOtnOduAisPortn
		EkiOnOff
	}


rm10010e40AlmlineHostLaneTxOtnIndex OBJECT-TYPE
	SYNTAX  INTEGER(0..128)
	MAX-ACCESS  read-only
	STATUS current
	DESCRIPTION
        "
        Index definition for the rm10010e40AlmlineHostLaneTxOtn
        table
        "
	::= { rm10010e40AlmlineHostLaneTxOtnEntry 1 }


rm10010e40AlmLineTxOtnLofPortn OBJECT-TYPE
	SYNTAX  EkiOnOff
	MAX-ACCESS read-only
	STATUS current
	DESCRIPTION
        "
        Line Host Tx LOF :This OID indicates
        a Loss of Frame is detected on
         the Tx Host interface of the Line
        Trscv <Help> Alarm indicating a
        Loss of Frame is detected on the
        Tx Host interface of the Line Trscv
        <Condtype> LINE_TX_OTN_LOF <Probcause>
        receiveFailure (41) <Alarmtype>
        equipmentAlarm (5) <Polarity> (2)
        "
	::= { rm10010e40AlmlineHostLaneTxOtnEntry 17 }


rm10010e40AlmLineTxOtnOofPortn OBJECT-TYPE
	SYNTAX  EkiOnOff
	MAX-ACCESS read-only
	STATUS current
	DESCRIPTION
        "
        Line Host Tx OOF :This OID indicates
        an Out of Frame is detected on
         the Tx Host interface of the Line
        Trscv <Help> Alarm indicating an
        Out of Frame is detected on the
        Tx Host interface of the Line Trscv
        <Condtype> LINE_TX_OTN_OOF <Probcause>
        receiveFailure (41) <Alarmtype>
        equipmentAlarm (5) <Polarity> (2)
        "
	::= { rm10010e40AlmlineHostLaneTxOtnEntry 16 }


rm10010e40AlmLineTxOtnLomPortn OBJECT-TYPE
	SYNTAX  EkiOnOff
	MAX-ACCESS read-only
	STATUS current
	DESCRIPTION
        "
        Line Host Tx LOM :This OID indicates
        a Loss of Multiframe is detected
        on the Tx Host interface of the
        Line Trscv <Help> Alarm indicating
        a Loss of Multiframe is detected
        on the Tx Host interface of the
        Line Trscv <Condtype> LINE_TX_OTN_LOM
        <Probcause> receiveFailure (41)
        <Alarmtype> equipmentAlarm (5)
         <Polarity> (2)
        "
	::= { rm10010e40AlmlineHostLaneTxOtnEntry 15 }


rm10010e40AlmLineTxOtnOomPortn OBJECT-TYPE
	SYNTAX  EkiOnOff
	MAX-ACCESS read-only
	STATUS current
	DESCRIPTION
        "
        Line Host Tx OOM :This OID indicates
        an Out of Multiframe is detected
        on the Tx Host interface of the
        Line Trscv <Help> Alarm indicating
        an Out of Multiframe is detected
        on the Tx Host interface of the
        Line Trscv <Condtype> LINE_TX_OTN_OOM
        <Probcause> receiveFailure (41)
        <Alarmtype> equipmentAlarm (5)
         <Polarity> (2)
        "
	::= { rm10010e40AlmlineHostLaneTxOtnEntry 14 }


rm10010e40AlmLineTxOtnIaePortn OBJECT-TYPE
	SYNTAX  EkiOnOff
	MAX-ACCESS read-only
	STATUS current
	DESCRIPTION
        "
        Line Host Tx IAE :This OID indicates
        an Incoming Alignment Error is
         detected on the Tx Host interface
        of the Line Trscv <Help> Alarm
         indicating an Incoming Alignment
        Error is detected on the Tx Host
        interface of the Line Trscv <Condtype>
        LINE_TX_OTN_IAE <Probcause> receiveFailure
        (41) <Alarmtype> equipmentAlarm
        (5) <Polarity> (2)
        "
	::= { rm10010e40AlmlineHostLaneTxOtnEntry 13 }


rm10010e40AlmLineTxSmBdiPortn OBJECT-TYPE
	SYNTAX  EkiOnOff
	MAX-ACCESS read-only
	STATUS current
	DESCRIPTION
        "
        Line Host Tx SM BDI :This OID
         indicates an SM Backward Defect
        Indication is detected on the Tx
        Host interface of the Line Trscv
        <Help> Alarm indicating an SM Backward
        Defect Indication is detected on
        the Tx Host interface of the Line
        Trscv <Condtype> LINE_TX_SM_BDI
        <Probcause> informationalStatus(1000)
        <Alarmtype> other (1) <Polarity>
        (2)
        "
	::= { rm10010e40AlmlineHostLaneTxOtnEntry 12 }


rm10010e40AlmLineTxOtnOtuAisPortn OBJECT-TYPE
	SYNTAX  EkiOnOff
	MAX-ACCESS read-only
	STATUS current
	DESCRIPTION
        "
        Line Host Tx OTU AIS :This OID
        indicates an OTU This OID Indication
        Signal is detected on the Tx Host
        interface of the Line Trscv <Help>
        Alarm indicating an OTU Alarm Indication
        Signal is detected on the Tx Host
        interface of the Line Trscv <Condtype>
        LINE_TX_OTN_OTU_AIS <Probcause>
        receiveFailure (41) <Alarmtype>
        equipmentAlarm (5) <Polarity> (2)
        "
	::= { rm10010e40AlmlineHostLaneTxOtnEntry 11 }


rm10010e40AlmLineTxOtnOduAisPortn OBJECT-TYPE
	SYNTAX  EkiOnOff
	MAX-ACCESS read-only
	STATUS current
	DESCRIPTION
        "
        Line Host Tx ODU AIS :This OID
        indicates an ODU This OID Indication
        Signal is detected on the Tx Host
        interface of the Line Trscv <Help>
        Alarm indicating an ODU Alarm Indication
        Signal is detected on the Tx Host
        interface of the Line Trscv <Condtype>
        LINE_TX_OTN_ODU_AIS <Probcause>
        receiveFailure (41) <Alarmtype>
        equipmentAlarm (5) <Polarity> (2)
        "
	::= { rm10010e40AlmlineHostLaneTxOtnEntry 10 }


--- *********************************************************
---     TABLE for the rm10010e40AlmclientSfpAlmDdm articles
--- *********************************************************

rm10010e40AlmclientSfpAlmDdmTable OBJECT-TYPE
	SYNTAX  SEQUENCE OF Rm10010e40AlmclientSfpAlmDdmEntry
	MAX-ACCESS not-accessible
	STATUS current
	DESCRIPTION
        "
        List of rm10010e40AlmclientSfpAlmDdm
        Article
        "
	::= { rm10010e40AlmClientUrg 216 }


rm10010e40AlmclientSfpAlmDdmEntry OBJECT-TYPE
	SYNTAX Rm10010e40AlmclientSfpAlmDdmEntry
	MAX-ACCESS not-accessible
	STATUS current
	DESCRIPTION
        "
        Row definition for the rm10010e40AlmclientSfpAlmDdm
        table
        "
	INDEX   { rm10010e40AlmclientSfpAlmDdmIndex }
	::= { rm10010e40AlmclientSfpAlmDdmTable 1 }


Rm10010e40AlmclientSfpAlmDdmEntry ::=
	SEQUENCE {
	rm10010e40AlmclientSfpAlmDdmIndex
		INTEGER,
	rm10010e40AlmRxPwrHighAlaPortn
		EkiOnOff,
	rm10010e40AlmRxPwrLowAlaPortn
		EkiOnOff,
	rm10010e40AlmTempHighAlaPortn
		EkiOnOff,
	rm10010e40AlmTempLowAlaPortn
		EkiOnOff,
	rm10010e40AlmVccHighAlaPortn
		EkiOnOff,
	rm10010e40AlmVccLowAlaPortn
		EkiOnOff,
	rm10010e40AlmTxBiasHighAlaPortn
		EkiOnOff,
	rm10010e40AlmTxBiasLowAlaPortn
		EkiOnOff,
	rm10010e40AlmTxPwrHighAlaPortn
		EkiOnOff,
	rm10010e40AlmTxPwrLowAlaPortn
		EkiOnOff
	}


rm10010e40AlmclientSfpAlmDdmIndex OBJECT-TYPE
	SYNTAX  INTEGER(0..128)
	MAX-ACCESS  read-only
	STATUS current
	DESCRIPTION
        "
        Index definition for the rm10010e40AlmclientSfpAlmDdm
        table
        "
	::= { rm10010e40AlmclientSfpAlmDdmEntry 1 }


rm10010e40AlmRxPwrHighAlaPortn OBJECT-TYPE
	SYNTAX  EkiOnOff
	MAX-ACCESS read-only
	STATUS current
	DESCRIPTION
        "
        Client Trscv Rx Power High :This
        OID indicates that the Trscv input
        power of port is higher than the
        threshold value written in the
         Trscv EEPROM <Help> Alarm indicating
        that the Trscv input power of port
        is higher than the threshold value
        written in the Trscv EEPROM <Condtype>
        RX_PWR_HIGH_ALA_1 <Probcause> receiveFailure
        (41) <Alarmtype> equipmentAlarm
        (5) <Polarity> (2)
        "
	::= { rm10010e40AlmclientSfpAlmDdmEntry 17 }


rm10010e40AlmRxPwrLowAlaPortn OBJECT-TYPE
	SYNTAX  EkiOnOff
	MAX-ACCESS read-only
	STATUS current
	DESCRIPTION
        "
        Client Trscv Rx Power Low :This
        OID indicates that the Trscv input
        power of port is lower than the
        threshold value written in the
         Trscv EEPROM <Help> Alarm indicating
        that the Trscv input power of port
        is lower than the threshold value
        written in the Trscv EEPROM <Condtype>
        RX_PWR_LOW_ALA_1 <Probcause> receiveFailure
        (41) <Alarmtype> equipmentAlarm
        (5) <Polarity> (2)
        "
	::= { rm10010e40AlmclientSfpAlmDdmEntry 16 }


rm10010e40AlmTempHighAlaPortn OBJECT-TYPE
	SYNTAX  EkiOnOff
	MAX-ACCESS read-only
	STATUS current
	DESCRIPTION
        "
        Client Trscv Temp High :This OID
        indicates that the Trscv temperature
        of port is higher than the threshold
        value written in the Trscv EEPROM
        <Help> Alarm indicating that the
        Trscv temperature of port is higher
        than the threshold value written
        in the Trscv EEPROM <Condtype>
         TEMP_HIGH_ALA_1 <Probcause> temperatureUnacceptable
        (51) <Alarmtype> equipmentAlarm
        (5) <Polarity> (2)
        "
	::= { rm10010e40AlmclientSfpAlmDdmEntry 9 }


rm10010e40AlmTempLowAlaPortn OBJECT-TYPE
	SYNTAX  EkiOnOff
	MAX-ACCESS read-only
	STATUS current
	DESCRIPTION
        "
        Client Trscv Temp Low :This OID
        indicates that the Trscv temperature
        of port is lower than the threshold
        value written in the Trscv EEPROM
        <Help> Alarm indicating that the
        Trscv temperature of port is lower
        than the threshold value written
        in the Trscv EEPROM <Condtype>
         TEMP_LOW_ALA_1 <Probcause> temperatureUnacceptable
        (51) <Alarmtype> equipmentAlarm
        (5) <Polarity> (2)
        "
	::= { rm10010e40AlmclientSfpAlmDdmEntry 8 }


rm10010e40AlmVccHighAlaPortn OBJECT-TYPE
	SYNTAX  EkiOnOff
	MAX-ACCESS read-only
	STATUS current
	DESCRIPTION
        "
        Client Trscv Power Supply High
        :This OID indicates that the Trscv
        power supply of port is higher
         than the threshold value written
        in the Trscv EEPROM <Help> Alarm
        indicating that the Trscv power
        supply of port is higher than the
        threshold value written in the
         Trscv EEPROM <Condtype> VCC_HIGH_ALA_1
        <Probcause> powerProblem (36) <Alarmtype>
        equipmentAlarm (5) <Polarity> (2)
        "
	::= { rm10010e40AlmclientSfpAlmDdmEntry 7 }


rm10010e40AlmVccLowAlaPortn OBJECT-TYPE
	SYNTAX  EkiOnOff
	MAX-ACCESS read-only
	STATUS current
	DESCRIPTION
        "
        Client Trscv Power Supply Low
         :This OID indicates that the Trscv
        power supply of port is lower than
        the threshold value written in
         the Trscv EEPROM <Help> Alarm
         indicating that the Trscv power
        supply of port is lower than the
        threshold value written in the
         Trscv EEPROM <Condtype> VCC_LOW_ALA_1
        <Probcause> powerProblem (36) <Alarmtype>
        equipmentAlarm (5) <Polarity> (2)
        "
	::= { rm10010e40AlmclientSfpAlmDdmEntry 6 }


rm10010e40AlmTxBiasHighAlaPortn OBJECT-TYPE
	SYNTAX  EkiOnOff
	MAX-ACCESS read-only
	STATUS current
	DESCRIPTION
        "
        Client Trscv Bias High :This OID
        indicates that the Trscv laser
         bias current of port is higher
        than the threshold value written
        in the Trscv EEPROM <Help> Alarm
        indicating that the Trscv laser
        bias current of port is higher
         than the threshold value written
        in the Trscv EEPROM <Condtype>
         TX_BIAS_HIGH_ALA_1 <Probcause>
        transmitterFailure (56) <Alarmtype>
        equipmentAlarm (5) <Polarity> (2)
        "
	::= { rm10010e40AlmclientSfpAlmDdmEntry 5 }


rm10010e40AlmTxBiasLowAlaPortn OBJECT-TYPE
	SYNTAX  EkiOnOff
	MAX-ACCESS read-only
	STATUS current
	DESCRIPTION
        "
        Client Trscv Bias Low :This OID
        indicates that the Trscv laser
         bias current of port is lower
         than the threshold value written
        in the Trscv EEPROM <Help> Alarm
        indicating that the Trscv laser
        bias current of port is lower than
        the threshold value written in
         the Trscv EEPROM <Condtype> TX_BIAS_LOW_ALA_1
        <Probcause> transmitterFailure
         (56) <Alarmtype> equipmentAlarm
        (5) <Polarity> (2)
        "
	::= { rm10010e40AlmclientSfpAlmDdmEntry 4 }


rm10010e40AlmTxPwrHighAlaPortn OBJECT-TYPE
	SYNTAX  EkiOnOff
	MAX-ACCESS read-only
	STATUS current
	DESCRIPTION
        "
        Client Trscv Tx Power High :This
        OID indicates that the Trscv output
        power of port is higher than the
        threshold value written in the
         Trscv EEPROM <Help> Alarm indicating
        that the Trscv output power of
         port is higher than the threshold
        value written in the Trscv EEPROM
        <Condtype> TX_PWR_HIGH_ALA_1 <Probcause>
        transmitterFailure (56) <Alarmtype>
        equipmentAlarm (5) <Polarity> (2)
        "
	::= { rm10010e40AlmclientSfpAlmDdmEntry 3 }


rm10010e40AlmTxPwrLowAlaPortn OBJECT-TYPE
	SYNTAX  EkiOnOff
	MAX-ACCESS read-only
	STATUS current
	DESCRIPTION
        "
        Client Trscv Tx Power Low :This
        OID indicates that the Trscv output
        power of port is lower than the
        threshold value written in the
         Trscv EEPROM <Help> Alarm indicating
        that the Trscv output power of
         port is lower than the threshold
        value written in the Trscv EEPROM
        <Condtype> TX_PWR_LOW_ALA_1 <Probcause>
        transmitterFailure (56) <Alarmtype>
        equipmentAlarm (5) <Polarity> (2)
        "
	::= { rm10010e40AlmclientSfpAlmDdmEntry 2 }


--- *********************************************************
---     TABLE for the rm10010e40AlmclientSfpWarnDdm articles
--- *********************************************************

rm10010e40AlmclientSfpWarnDdmTable OBJECT-TYPE
	SYNTAX  SEQUENCE OF Rm10010e40AlmclientSfpWarnDdmEntry
	MAX-ACCESS not-accessible
	STATUS current
	DESCRIPTION
        "
        List of rm10010e40AlmclientSfpWarnDdm
        Article
        "
	::= { rm10010e40AlmClientNurg 232 }


rm10010e40AlmclientSfpWarnDdmEntry OBJECT-TYPE
	SYNTAX Rm10010e40AlmclientSfpWarnDdmEntry
	MAX-ACCESS not-accessible
	STATUS current
	DESCRIPTION
        "
        Row definition for the rm10010e40AlmclientSfpWarnDdm
        table
        "
	INDEX   { rm10010e40AlmclientSfpWarnDdmIndex }
	::= { rm10010e40AlmclientSfpWarnDdmTable 1 }


Rm10010e40AlmclientSfpWarnDdmEntry ::=
	SEQUENCE {
	rm10010e40AlmclientSfpWarnDdmIndex
		INTEGER,
	rm10010e40AlmRxPwrHighWngPortn
		EkiOnOff,
	rm10010e40AlmRxPwrLowWngPortn
		EkiOnOff,
	rm10010e40AlmTempHighWngPortn
		EkiOnOff,
	rm10010e40AlmTempLowWngPortn
		EkiOnOff,
	rm10010e40AlmVccHighWngPortn
		EkiOnOff,
	rm10010e40AlmVccLowWngPortn
		EkiOnOff,
	rm10010e40AlmTxBiasHighWngPortn
		EkiOnOff,
	rm10010e40AlmTxBiasLowWngPortn
		EkiOnOff,
	rm10010e40AlmTxPwrHighWngPortn
		EkiOnOff,
	rm10010e40AlmTxPwLowWngPortn
		EkiOnOff
	}


rm10010e40AlmclientSfpWarnDdmIndex OBJECT-TYPE
	SYNTAX  INTEGER(0..128)
	MAX-ACCESS  read-only
	STATUS current
	DESCRIPTION
        "
        Index definition for the rm10010e40AlmclientSfpWarnDdm
        table
        "
	::= { rm10010e40AlmclientSfpWarnDdmEntry 1 }


rm10010e40AlmRxPwrHighWngPortn OBJECT-TYPE
	SYNTAX  EkiOnOff
	MAX-ACCESS read-only
	STATUS current
	DESCRIPTION
        "
        Client Trscv Rx Power High Warning
        :This OID indicates that the Trscv
        input power is higher than the
         threshold value written in the
        Trscv EEPROM <Help> Warning indicating
        that the Trscv input power is higher
        than the threshold value written
        in the Trscv EEPROM <Condtype>
         RX_PWR_HIGH_WNG_1 <Probcause>
         receiveFailure (41) <Alarmtype>
        equipmentAlarm (5) <Polarity> (2)
        "
	::= { rm10010e40AlmclientSfpWarnDdmEntry 17 }


rm10010e40AlmRxPwrLowWngPortn OBJECT-TYPE
	SYNTAX  EkiOnOff
	MAX-ACCESS read-only
	STATUS current
	DESCRIPTION
        "
        Client Trscv Rx Power Low Warning
        :This OID indicates that the Trscv
        input power is lower than the threshold
        value written in the Trscv EEPROM
        <Help> Warning indicating that
         the Trscv input power is lower
        than the threshold value written
        in the Trscv EEPROM <Condtype>
         RX_PWR_LOW_WNG_1 <Probcause> receiveFailure
        (41) <Alarmtype> equipmentAlarm
        (5) <Polarity> (2)
        "
	::= { rm10010e40AlmclientSfpWarnDdmEntry 16 }


rm10010e40AlmTempHighWngPortn OBJECT-TYPE
	SYNTAX  EkiOnOff
	MAX-ACCESS read-only
	STATUS current
	DESCRIPTION
        "
        Client Trscv Temp High Warning
        :This OID indicates that the Trscv
        temperature is higher than the
         threshold value written in the
        Trscv EEPROM <Help> Warning indicating
        that the Trscv temperature is higher
        than the threshold value written
        in the Trscv EEPROM <Condtype>
         TEMP_HIGH_WNG_1 <Probcause> temperatureUnacceptable
        (51) <Alarmtype> equipmentAlarm
        (5) <Polarity> (2)
        "
	::= { rm10010e40AlmclientSfpWarnDdmEntry 9 }


rm10010e40AlmTempLowWngPortn OBJECT-TYPE
	SYNTAX  EkiOnOff
	MAX-ACCESS read-only
	STATUS current
	DESCRIPTION
        "
        Client Trscv Temp Low Warning
         :This OID indicates that the Trscv
        temperature is lower than the threshold
        value written in the Trscv EEPROM
        <Help> Warning indicating that
         the Trscv temperature is lower
        than the threshold value written
        in the Trscv EEPROM <Condtype>
         TEMP_LOW_WNG_1 <Probcause> temperatureUnacceptable
        (51) <Alarmtype> equipmentAlarm
        (5) <Polarity> (2)
        "
	::= { rm10010e40AlmclientSfpWarnDdmEntry 8 }


rm10010e40AlmVccHighWngPortn OBJECT-TYPE
	SYNTAX  EkiOnOff
	MAX-ACCESS read-only
	STATUS current
	DESCRIPTION
        "
        Client Trscv Power Supply High
        Warning :This OID indicates that
        the Trscv power supply is higher
        than the threshold value written
        in the Trscv EEPROM <Help> Warning
        indicating that the Trscv power
        supply is higher than the threshold
        value written in the Trscv EEPROM
        <Condtype> VCC_HIGH_WNG_1 <Probcause>
        powerProblem (36) <Alarmtype> equipmentAlarm
        (5) <Polarity> (2)
        "
	::= { rm10010e40AlmclientSfpWarnDdmEntry 7 }


rm10010e40AlmVccLowWngPortn OBJECT-TYPE
	SYNTAX  EkiOnOff
	MAX-ACCESS read-only
	STATUS current
	DESCRIPTION
        "
        Client Trscv Power Supply Low
         Warning :This OID indicates that
        the Trscv power supply is lower
        than the threshold value written
        in the Trscv EEPROM <Help> Warning
        indicating that the Trscv power
        supply is lower than the threshold
        value written in the Trscv EEPROM
        <Condtype> VCC_LOW_WNG_1 <Probcause>
        powerProblem (36) <Alarmtype> equipmentAlarm
        (5) <Polarity> (2)
        "
	::= { rm10010e40AlmclientSfpWarnDdmEntry 6 }


rm10010e40AlmTxBiasHighWngPortn OBJECT-TYPE
	SYNTAX  EkiOnOff
	MAX-ACCESS read-only
	STATUS current
	DESCRIPTION
        "
        Client Trscv Bias High Warning
        :This OID indicates that the Trscv
        laser bias current is higher than
        the threshold value written in
         the Trscv EEPROM <Help> Warning
        indicating that the Trscv laser
        bias current is higher than the
        threshold value written in the
         Trscv EEPROM <Condtype> TX_BIAS_HIGH_WNG_1
        <Probcause> transmitterFailure
         (56) <Alarmtype> equipmentAlarm
        (5) <Polarity> (2)
        "
	::= { rm10010e40AlmclientSfpWarnDdmEntry 5 }


rm10010e40AlmTxBiasLowWngPortn OBJECT-TYPE
	SYNTAX  EkiOnOff
	MAX-ACCESS read-only
	STATUS current
	DESCRIPTION
        "
        Client Trscv Bias Low Warning
         :This OID indicates that the Trscv
        laser bias current is lower than
        the threshold value written in
         the Trscv EEPROM <Help> Warning
        indicating that the Trscv laser
        bias current is lower than the
         threshold value written in the
        Trscv EEPROM <Condtype> TX_BIAS_LOW_WNG_1
        <Probcause> transmitterFailure
         (56) <Alarmtype> equipmentAlarm
        (5) <Polarity> (2)
        "
	::= { rm10010e40AlmclientSfpWarnDdmEntry 4 }


rm10010e40AlmTxPwrHighWngPortn OBJECT-TYPE
	SYNTAX  EkiOnOff
	MAX-ACCESS read-only
	STATUS current
	DESCRIPTION
        "
        Client Trscv Tx Power High Warning
        :This OID indicates that the Trscv
        output power is higher than the
        threshold value written in the
         Trscv EEPROM <Help> Warning indicating
        that the Trscv output power is
         higher than the threshold value
        written in the Trscv EEPROM <Condtype>
        TX_PWR_HIGH_WNG_1 <Probcause> transmitterFailure
        (56) <Alarmtype> equipmentAlarm
        (5) <Polarity> (2)
        "
	::= { rm10010e40AlmclientSfpWarnDdmEntry 3 }


rm10010e40AlmTxPwLowWngPortn OBJECT-TYPE
	SYNTAX  EkiOnOff
	MAX-ACCESS read-only
	STATUS current
	DESCRIPTION
        "
        Client Trscv Tx Power Low Warning
        :This OID indicates that the Trscv
        output power is lower than the
         threshold value written in the
        Trscv EEPROM <Help> Warning indicating
        that the Trscv output power is
         lower than the threshold value
        written in the Trscv EEPROM <Condtype>
        TX_PW_LOW_WNG_1 <Probcause> transmitterFailure
        (56) <Alarmtype> equipmentAlarm
        (5) <Polarity> (2)
        "
	::= { rm10010e40AlmclientSfpWarnDdmEntry 2 }


--- *****************************************************
---     LEAF for the modFanFail article
--- *****************************************************
rm10010e40AlmmodFanFail OBJECT IDENTIFIER ::= { rm10010e40AlmOtherUrg 248 }




rm10010e40AlmFan4Fail OBJECT-TYPE
	  SYNTAX EkiOnOff
	  MAX-ACCESS read-only
	  STATUS current
	  DESCRIPTION
        "
        Fan Unit N°4 Failed On Fan Module
        :This OID indicates a failure on
        fan 4. Removal of the fan unit
         or no rotation sets the OID.
         <Help>  This alarm indicates if
        the FAN n°4 is in fail condition
        <Condtype> FAN4_FAIL <Probcause>
        heatingVentCoolingSystemProblem
        (22) <Alarmtype> equipmentAlarm
        (5) <Polarity> (2)
        "
	  ::= { rm10010e40AlmmodFanFail 7 }



rm10010e40AlmFan3Fail OBJECT-TYPE
	  SYNTAX EkiOnOff
	  MAX-ACCESS read-only
	  STATUS current
	  DESCRIPTION
        "
        Fan Unit N°3 Failed On Fan Module
        :This OID indicates a failure on
        fan 3. Removal of the fan unit
         or no rotation sets the OID.
         <Help>  This alarm indicates if
        the FAN n°3 is in fail condition
        <Condtype> FAN3_FAIL <Probcause>
        heatingVentCoolingSystemProblem
        (22) <Alarmtype> equipmentAlarm
        (5) <Polarity> (2)
        "
	  ::= { rm10010e40AlmmodFanFail 6 }



rm10010e40AlmFan2Fail OBJECT-TYPE
	  SYNTAX EkiOnOff
	  MAX-ACCESS read-only
	  STATUS current
	  DESCRIPTION
        "
        Fan Unit N°2 Failed On Fan Module
        :This OID indicates a failure on
        fan 2. Removal of the fan unit
         or no rotation sets the OID.
         <Help>  This alarm indicates if
        the FAN n°2 is in fail condition
        <Condtype> FAN2_FAIL <Probcause>
        heatingVentCoolingSystemProblem
        (22) <Alarmtype> equipmentAlarm
        (5) <Polarity> (2)
        "
	  ::= { rm10010e40AlmmodFanFail 5 }



rm10010e40AlmFan1Fail OBJECT-TYPE
	  SYNTAX EkiOnOff
	  MAX-ACCESS read-only
	  STATUS current
	  DESCRIPTION
        "
        Fan Unit N°1 Failed On Fan Module
        :This OID indicates a failure on
        fan 1. Removal of the fan unit
         or no rotation sets the OID.
         <Help>  This alarm indicates if
        the FAN n°1 is in fail condition
        <Condtype> FAN1_FAIL <Probcause>
        heatingVentCoolingSystemProblem
        (22) <Alarmtype> equipmentAlarm
        (5) <Polarity> (2)
        "
	  ::= { rm10010e40AlmmodFanFail 4 }



rm10010e40AlmFansFail OBJECT-TYPE
	  SYNTAX EkiOnOff
	  MAX-ACCESS read-only
	  STATUS current
	  DESCRIPTION
        "
        Fan Module Failure :This OID indicates
        that at least one of the 4 FAN
         unit of the FAN module is in fail
        condition  <Help>  This alarm indicates
        if one the FANs is in a fail condition.
        <Condtype> FANS_FAIL <Probcause>
        heatingVentCoolingSystemProblem
        (22) <Alarmtype> equipmentAlarm
        (5) <Polarity> (2)
        "
	  ::= { rm10010e40AlmmodFanFail 2 }



rm10010e40AlmFanModuleAbsent OBJECT-TYPE
	  SYNTAX EkiOnOff
	  MAX-ACCESS read-only
	  STATUS current
	  DESCRIPTION
        "
        Fan Module Absent :This OID indicates
        the presence of the FAN module
         in the Chassis.  <Help>  This
         alarm indicates if the FAN module
        is detected in the chassis. <Condtype>
        FAN_MODULE_ABSENT <Probcause> heatingVentCoolingSystemProblem
        (22) <Alarmtype> equipmentAlarm
        (5) <Polarity> (2) <Event> ObjectCDINV
        "
	  ::= { rm10010e40AlmmodFanFail 1 }








--- *****************************************************
--- $$$$$$$$$$$$$$$$$$$$$$$$$$$$$$$$$$$$$$$$$$$$$$$$$$$$$
---     CONTROLS
--- $$$$$$$$$$$$$$$$$$$$$$$$$$$$$$$$$$$$$$$$$$$$$$$$$$$$$
--- *****************************************************



--- *****************************************************
---     LEAF for the confMgnt1 article
--- *****************************************************
rm10010e40CtrlconfMgnt1 OBJECT IDENTIFIER ::= { rm10010e40CtrlOther 1 }




rm10010e40CtrlConf2Clear1 OBJECT-TYPE
	  SYNTAX EkiOnOff
	  MAX-ACCESS read-write
	  STATUS current
	  DESCRIPTION
        "
        Clear Configuration Tables :This
        OID clears the configuration tables
        from configuration2 in the flash.
         <Help>  This control restores
         the default configuration of the
        module
        "
	  ::= { rm10010e40CtrlconfMgnt1 14 }



rm10010e40CtrlConf2Flash1 OBJECT-TYPE
	  SYNTAX EkiOnOff
	  MAX-ACCESS read-write
	  STATUS current
	  DESCRIPTION
        "
        Write Configuration Tables :This
        OID saves the current configuration
        of the PM as configuration2 in
         the flash.  <Help>  This control
        saves the customer configuration
        on the module
        "
	  ::= { rm10010e40CtrlconfMgnt1 10 }



rm10010e40CtrlConf2Load1 OBJECT-TYPE
	  SYNTAX EkiOnOff
	  MAX-ACCESS read-write
	  STATUS current
	  DESCRIPTION
        "
        Load Configuration Tables Set
         Nb 2 :When set this OID enables
        loading from flash configuration2
        into the PM.
        "
	  ::= { rm10010e40CtrlconfMgnt1 2 }



rm10010e40CtrlConf1Load1 OBJECT-TYPE
	  SYNTAX EkiOnOff
	  MAX-ACCESS read-write
	  STATUS current
	  DESCRIPTION
        "
        Load Configuration Tables Set
         Nb 1 :When set this OID enables
        loading from flash configuration1
        into the PM.
        "
	  ::= { rm10010e40CtrlconfMgnt1 1 }



--- *****************************************************
---     LEAF for the synth4 article
--- *****************************************************
rm10010e40Ctrlsynth4 OBJECT IDENTIFIER ::= { rm10010e40CtrlOther 4 }




rm10010e40CtrlCorrelatOff OBJECT-TYPE
	  SYNTAX EkiOnOff
	  MAX-ACCESS read-write
	  STATUS current
	  DESCRIPTION
        "
        Disable Alarm Correlation :This
        OID disables the alarm correlation
        in the PM.
        "
	  ::= { rm10010e40Ctrlsynth4 2 }



rm10010e40CtrlCorrelatOn OBJECT-TYPE
	  SYNTAX EkiOnOff
	  MAX-ACCESS read-write
	  STATUS current
	  DESCRIPTION
        "
        Enable Alarm Correlation :This
        OID enables the alarm correlation
        in the PM.
        "
	  ::= { rm10010e40Ctrlsynth4 1 }



--- *****************************************************
---     LEAF for the swMgnt article
--- *****************************************************
rm10010e40CtrlswMgnt OBJECT IDENTIFIER ::= { rm10010e40CtrlOther 5 }




rm10010e40CtrlLoadSwBank2 OBJECT-TYPE
	  SYNTAX EkiOnOff
	  MAX-ACCESS read-write
	  STATUS current
	  DESCRIPTION
        "
        Set Software Nb 2 As Active :This
        OID, when set, loads the SW from
        bank2 into the PM. It must be followed
        by a reset.  <Help>  This controls
        selects the second SW bank as the
        active bank for the next module
        reset
        "
	  ::= { rm10010e40CtrlswMgnt 6 }



rm10010e40CtrlLoadSwBank1 OBJECT-TYPE
	  SYNTAX EkiOnOff
	  MAX-ACCESS read-write
	  STATUS current
	  DESCRIPTION
        "
        Set Software Nb 1 As Active :This
        OID, when set, loads the SW from
        bank1 into the PM. It must be followed
        by a reset.  <Help>  This controls
        selects the first SW bank as the
        active bank for the next module
        reset
        "
	  ::= { rm10010e40CtrlswMgnt 5 }



rm10010e40CtrlWarmReset OBJECT-TYPE
	  SYNTAX EkiOnOff
	  MAX-ACCESS read-write
	  STATUS current
	  DESCRIPTION
        "
        PM Warm Reset :This OID, when
         set, causes a warm reset of the
        PM. This reset is not traffic affecting,
        and the configuration of PM remains
        unchanged.  <Help>  This control
        initiates a warm reset of the module.
        "
	  ::= { rm10010e40CtrlswMgnt 3 }



rm10010e40CtrlColdReset OBJECT-TYPE
	  SYNTAX EkiOnOff
	  MAX-ACCESS read-write
	  STATUS current
	  DESCRIPTION
        "
        PM Cold Reset :This OID, when
         set, causes a cold reset of the
        PM. This reset is traffic affecting,
        and the configuration of PM is
         reloaded on start-up.  <Help>
          This control initiates a cold
        reset of the module.
        "
	  ::= { rm10010e40CtrlswMgnt 2 }



--- *****************************************************
---     LEAF for the gwMgnt article
--- *****************************************************
rm10010e40CtrlgwMgnt OBJECT IDENTIFIER ::= { rm10010e40CtrlOther 6 }




rm10010e40CtrlLoadGwBank4 OBJECT-TYPE
	  SYNTAX EkiOnOff
	  MAX-ACCESS read-write
	  STATUS current
	  DESCRIPTION
        "
        Set Gateware Nb 4 As Active :This
        OID, when set, loads the GW from
        bank4 (Flash) into the PM. It is
        followed by an automatic gateware
        cold reset.
        "
	  ::= { rm10010e40CtrlgwMgnt 8 }



rm10010e40CtrlLoadGwBank3 OBJECT-TYPE
	  SYNTAX EkiOnOff
	  MAX-ACCESS read-write
	  STATUS current
	  DESCRIPTION
        "
        Set Gateware Nb 3 As Active :This
        OID, when set, loads the GW from
        bank3 (Flash) into the PM. It is
        followed by an automatic gateware
        cold reset.  <Help>  This controls
        initiates a cold reset of the module
        and select the third GW bank as
        the active bank
        "
	  ::= { rm10010e40CtrlgwMgnt 7 }



rm10010e40CtrlLoadGwBank2 OBJECT-TYPE
	  SYNTAX EkiOnOff
	  MAX-ACCESS read-write
	  STATUS current
	  DESCRIPTION
        "
        Set Gateware Nb 2 As Active :This
        OID, when set, loads the GW from
        bank2 (Flash) into the PM. It is
        followed by an automatic gateware
        cold reset.
        "
	  ::= { rm10010e40CtrlgwMgnt 6 }



rm10010e40CtrlLoadGwBank1 OBJECT-TYPE
	  SYNTAX EkiOnOff
	  MAX-ACCESS read-write
	  STATUS current
	  DESCRIPTION
        "
        Set Gateware Nb 1 As Active :This
        OID, when set, loads the GW from
        bank1 (Flash) into the PM. It is
        followed by an automatic gateware
        cold reset.  <Help>  This controls
        initiates a cold reset of the module
        and select the first GW bank as
        the active bank
        "
	  ::= { rm10010e40CtrlgwMgnt 5 }



rm10010e40CtrlCurrentGwReset OBJECT-TYPE
	  SYNTAX EkiOnOff
	  MAX-ACCESS read-write
	  STATUS current
	  DESCRIPTION
        "
        Active Gateware Reset :This OID,
        when set, resets the active gateware.
        It is traffic affecting.
        "
	  ::= { rm10010e40CtrlgwMgnt 1 }



--- *********************************************************
---     TABLE for the rm10010e40CtrlaccessLoop articles
--- *********************************************************

rm10010e40CtrlaccessLoopTable OBJECT-TYPE
	SYNTAX  SEQUENCE OF Rm10010e40CtrlaccessLoopEntry
	MAX-ACCESS not-accessible
	STATUS current
	DESCRIPTION
        "
        List of rm10010e40CtrlaccessLoop
        Article
        "
	::= { rm10010e40CtrlClient 16 }


rm10010e40CtrlaccessLoopEntry OBJECT-TYPE
	SYNTAX Rm10010e40CtrlaccessLoopEntry
	MAX-ACCESS not-accessible
	STATUS current
	DESCRIPTION
        "
        Row definition for the rm10010e40CtrlaccessLoop
        table
        "
	INDEX   { rm10010e40CtrlaccessLoopIndex }
	::= { rm10010e40CtrlaccessLoopTable 1 }


Rm10010e40CtrlaccessLoopEntry ::=
	SEQUENCE {
	rm10010e40CtrlaccessLoopIndex
		INTEGER,
	rm10010e40CtrlaccessLoopPortn
		EkiState
	}


rm10010e40CtrlaccessLoopIndex OBJECT-TYPE
	SYNTAX  INTEGER(0..128)
	MAX-ACCESS  read-only
	STATUS current
	DESCRIPTION
        "
        Index definition for the rm10010e40CtrlaccessLoop
        table
        "
	::= { rm10010e40CtrlaccessLoopEntry 1 }


rm10010e40CtrlaccessLoopPortn OBJECT-TYPE
	SYNTAX  EkiState
	MAX-ACCESS read-write
	STATUS current
	DESCRIPTION
        "
        Client Facility Loopback :This
        OID, when set at '1' puts the client
        port in loopback, looping the received
        10 Gb/s signal on the transmit
         10 Gb/s output.  <Help> This control
        enables the Out Loopback on the
        client port, looping the client
        input signal on the client output
        "
	::= { rm10010e40CtrlaccessLoopEntry 2 }


--- *********************************************************
---     TABLE for the rm10010e40CtrlclientLoopToLine articles
--- *********************************************************

rm10010e40CtrlclientLoopToLineTable OBJECT-TYPE
	SYNTAX  SEQUENCE OF Rm10010e40CtrlclientLoopToLineEntry
	MAX-ACCESS not-accessible
	STATUS current
	DESCRIPTION
        "
        List of rm10010e40CtrlclientLoopToLine
        Article
        "
	::= { rm10010e40CtrlClient 17 }


rm10010e40CtrlclientLoopToLineEntry OBJECT-TYPE
	SYNTAX Rm10010e40CtrlclientLoopToLineEntry
	MAX-ACCESS not-accessible
	STATUS current
	DESCRIPTION
        "
        Row definition for the rm10010e40CtrlclientLoopToLine
        table
        "
	INDEX   { rm10010e40CtrlclientLoopToLineIndex }
	::= { rm10010e40CtrlclientLoopToLineTable 1 }


Rm10010e40CtrlclientLoopToLineEntry ::=
	SEQUENCE {
	rm10010e40CtrlclientLoopToLineIndex
		INTEGER,
	rm10010e40CtrlclientLoopToLinePortn
		EkiState
	}


rm10010e40CtrlclientLoopToLineIndex OBJECT-TYPE
	SYNTAX  INTEGER(0..128)
	MAX-ACCESS  read-only
	STATUS current
	DESCRIPTION
        "
        Index definition for the rm10010e40CtrlclientLoopToLine
        table
        "
	::= { rm10010e40CtrlclientLoopToLineEntry 1 }


rm10010e40CtrlclientLoopToLinePortn OBJECT-TYPE
	SYNTAX  EkiState
	MAX-ACCESS read-write
	STATUS current
	DESCRIPTION
        "
        Client Terminal Loopback :This
        OID, when set, puts the client
         port in loop back, looping the
        10 Gb/s output signal on the 10
        Gb/s input.<Help> This control
         enables the In Loopback on the
        client port, looping the client
        output signal on the client input
        "
	::= { rm10010e40CtrlclientLoopToLineEntry 2 }


--- *********************************************************
---     TABLE for the rm10010e40CtrlcsfUpIns articles
--- *********************************************************

rm10010e40CtrlcsfUpInsTable OBJECT-TYPE
	SYNTAX  SEQUENCE OF Rm10010e40CtrlcsfUpInsEntry
	MAX-ACCESS not-accessible
	STATUS current
	DESCRIPTION
        "
        List of rm10010e40CtrlcsfUpIns
        Article
        "
	::= { rm10010e40CtrlClient 21 }


rm10010e40CtrlcsfUpInsEntry OBJECT-TYPE
	SYNTAX Rm10010e40CtrlcsfUpInsEntry
	MAX-ACCESS not-accessible
	STATUS current
	DESCRIPTION
        "
        Row definition for the rm10010e40CtrlcsfUpIns
        table
        "
	INDEX   { rm10010e40CtrlcsfUpInsIndex }
	::= { rm10010e40CtrlcsfUpInsTable 1 }


Rm10010e40CtrlcsfUpInsEntry ::=
	SEQUENCE {
	rm10010e40CtrlcsfUpInsIndex
		INTEGER,
	rm10010e40CtrlcsfUpInsPortn
		EkiState
	}


rm10010e40CtrlcsfUpInsIndex OBJECT-TYPE
	SYNTAX  INTEGER(0..128)
	MAX-ACCESS  read-only
	STATUS current
	DESCRIPTION
        "
        Index definition for the rm10010e40CtrlcsfUpIns
        table
        "
	::= { rm10010e40CtrlcsfUpInsEntry 1 }


rm10010e40CtrlcsfUpInsPortn OBJECT-TYPE
	SYNTAX  EkiState
	MAX-ACCESS read-write
	STATUS current
	DESCRIPTION
        "
        Client Signal Fail Insertion :This
        OID, when set, inserts  a client
        signal fail in the upstream client
        Port.  <Help>  This control inserts
        a Client Signal Fail for the client
        port
        "
	::= { rm10010e40CtrlcsfUpInsEntry 2 }


--- *********************************************************
---     TABLE for the rm10010e40CtrlcaisDwIns articles
--- *********************************************************

rm10010e40CtrlcaisDwInsTable OBJECT-TYPE
	SYNTAX  SEQUENCE OF Rm10010e40CtrlcaisDwInsEntry
	MAX-ACCESS not-accessible
	STATUS current
	DESCRIPTION
        "
        List of rm10010e40CtrlcaisDwIns
        Article
        "
	::= { rm10010e40CtrlClient 22 }


rm10010e40CtrlcaisDwInsEntry OBJECT-TYPE
	SYNTAX Rm10010e40CtrlcaisDwInsEntry
	MAX-ACCESS not-accessible
	STATUS current
	DESCRIPTION
        "
        Row definition for the rm10010e40CtrlcaisDwIns
        table
        "
	INDEX   { rm10010e40CtrlcaisDwInsIndex }
	::= { rm10010e40CtrlcaisDwInsTable 1 }


Rm10010e40CtrlcaisDwInsEntry ::=
	SEQUENCE {
	rm10010e40CtrlcaisDwInsIndex
		INTEGER,
	rm10010e40CtrlcaisDwInsPortn
		EkiState
	}


rm10010e40CtrlcaisDwInsIndex OBJECT-TYPE
	SYNTAX  INTEGER(0..128)
	MAX-ACCESS  read-only
	STATUS current
	DESCRIPTION
        "
        Index definition for the rm10010e40CtrlcaisDwIns
        table
        "
	::= { rm10010e40CtrlcaisDwInsEntry 1 }


rm10010e40CtrlcaisDwInsPortn OBJECT-TYPE
	SYNTAX  EkiState
	MAX-ACCESS read-write
	STATUS current
	DESCRIPTION
        "
        Client AIS Insertion :This OID,
        when set, inserts a client AIS
         on the downstream client Port.
         <Help>  This control inserts a
        Client AIS for the client port
        "
	::= { rm10010e40CtrlcaisDwInsEntry 2 }


--- *********************************************************
---     TABLE for the rm10010e40CtrlcommAccessLoop articles
--- *********************************************************

rm10010e40CtrlcommAccessLoopTable OBJECT-TYPE
	SYNTAX  SEQUENCE OF Rm10010e40CtrlcommAccessLoopEntry
	MAX-ACCESS not-accessible
	STATUS current
	DESCRIPTION
        "
        List of rm10010e40CtrlcommAccessLoop
        Article
        "
	::= { rm10010e40CtrlLine 64 }


rm10010e40CtrlcommAccessLoopEntry OBJECT-TYPE
	SYNTAX Rm10010e40CtrlcommAccessLoopEntry
	MAX-ACCESS not-accessible
	STATUS current
	DESCRIPTION
        "
        Row definition for the rm10010e40CtrlcommAccessLoop
        table
        "
	INDEX   { rm10010e40CtrlcommAccessLoopIndex }
	::= { rm10010e40CtrlcommAccessLoopTable 1 }


Rm10010e40CtrlcommAccessLoopEntry ::=
	SEQUENCE {
	rm10010e40CtrlcommAccessLoopIndex
		INTEGER,
	rm10010e40CtrlcommAccessLoopPortn
		EkiState
	}


rm10010e40CtrlcommAccessLoopIndex OBJECT-TYPE
	SYNTAX  INTEGER(0..128)
	MAX-ACCESS  read-only
	STATUS current
	DESCRIPTION
        "
        Index definition for the rm10010e40CtrlcommAccessLoop
        table
        "
	::= { rm10010e40CtrlcommAccessLoopEntry 1 }


rm10010e40CtrlcommAccessLoopPortn OBJECT-TYPE
	SYNTAX  EkiState
	MAX-ACCESS read-write
	STATUS current
	DESCRIPTION
        "
        Line Terminal Loopback :This OID,
        when set, puts the module in common
        access loop back, looping the 100
        Gb/s output signal on the 100 Gb/s
        input.<Help> This control enables
        the In Loopback on the line port,
        looping the 100 Gb/s output signal
        on the 100 Gb/s input
        "
	::= { rm10010e40CtrlcommAccessLoopEntry 2 }


--- *********************************************************
---     TABLE for the rm10010e40CtrllineLoop articles
--- *********************************************************

rm10010e40CtrllineLoopTable OBJECT-TYPE
	SYNTAX  SEQUENCE OF Rm10010e40CtrllineLoopEntry
	MAX-ACCESS not-accessible
	STATUS current
	DESCRIPTION
        "
        List of rm10010e40CtrllineLoop
        Article
        "
	::= { rm10010e40CtrlLine 66 }


rm10010e40CtrllineLoopEntry OBJECT-TYPE
	SYNTAX Rm10010e40CtrllineLoopEntry
	MAX-ACCESS not-accessible
	STATUS current
	DESCRIPTION
        "
        Row definition for the rm10010e40CtrllineLoop
        table
        "
	INDEX   { rm10010e40CtrllineLoopIndex }
	::= { rm10010e40CtrllineLoopTable 1 }


Rm10010e40CtrllineLoopEntry ::=
	SEQUENCE {
	rm10010e40CtrllineLoopIndex
		INTEGER,
	rm10010e40CtrllineLoopPortn
		EkiState
	}


rm10010e40CtrllineLoopIndex OBJECT-TYPE
	SYNTAX  INTEGER(0..128)
	MAX-ACCESS  read-only
	STATUS current
	DESCRIPTION
        "
        Index definition for the rm10010e40CtrllineLoop
        table
        "
	::= { rm10010e40CtrllineLoopEntry 1 }


rm10010e40CtrllineLoopPortn OBJECT-TYPE
	SYNTAX  EkiState
	MAX-ACCESS read-write
	STATUS current
	DESCRIPTION
        "
        Line Facility Loopback :This OID,
        when set at '1' puts the module
        in line loopback mode, looping
         the received 100 Gb/s signal on
        the transmit 100 Gb/s output. The
        Upstream part of the module is
         timed on the 100 Gb/s recovered
        clock in that case.<Help> This
         control enables the Out Loopback
        on the line port, looping the 100
        Gb/s input signal on the 100 Gb/s
        output
        "
	::= { rm10010e40CtrllineLoopEntry 2 }


--- *********************************************************
---     TABLE for the rm10010e40CtrlfecDisable articles
--- *********************************************************

rm10010e40CtrlfecDisableTable OBJECT-TYPE
	SYNTAX  SEQUENCE OF Rm10010e40CtrlfecDisableEntry
	MAX-ACCESS not-accessible
	STATUS current
	DESCRIPTION
        "
        List of rm10010e40CtrlfecDisable
        Article
        "
	::= { rm10010e40CtrlLine 69 }


rm10010e40CtrlfecDisableEntry OBJECT-TYPE
	SYNTAX Rm10010e40CtrlfecDisableEntry
	MAX-ACCESS not-accessible
	STATUS current
	DESCRIPTION
        "
        Row definition for the rm10010e40CtrlfecDisable
        table
        "
	INDEX   { rm10010e40CtrlfecDisableIndex }
	::= { rm10010e40CtrlfecDisableTable 1 }


Rm10010e40CtrlfecDisableEntry ::=
	SEQUENCE {
	rm10010e40CtrlfecDisableIndex
		INTEGER,
	rm10010e40CtrlfecDisablePortn
		EkiState
	}


rm10010e40CtrlfecDisableIndex OBJECT-TYPE
	SYNTAX  INTEGER(0..128)
	MAX-ACCESS  read-only
	STATUS current
	DESCRIPTION
        "
        Index definition for the rm10010e40CtrlfecDisable
        table
        "
	::= { rm10010e40CtrlfecDisableEntry 1 }


rm10010e40CtrlfecDisablePortn OBJECT-TYPE
	SYNTAX  EkiState
	MAX-ACCESS read-write
	STATUS current
	DESCRIPTION
        "
        Forward Error Correction Inhibition
        :This OID, when set, inhibits the
        Forward Error Correction feature
        on the line input  <Help>  This
        control enables/disables the Forward
        Error Correction on the line interface
        "
	::= { rm10010e40CtrlfecDisableEntry 2 }


--- *****************************************************
---     LEAF for the ledTest article
--- *****************************************************
rm10010e40CtrlledTest OBJECT IDENTIFIER ::= { rm10010e40CtrlOther 192 }




rm10010e40CtrlLedOff OBJECT-TYPE
	  SYNTAX EkiOnOff
	  MAX-ACCESS read-write
	  STATUS current
	  DESCRIPTION
        "
        Leds Off :This OID switches off
        all the Leds as a test feature.
         <Help>  This control initiates
        a test leds turning all the LEDs
        to OFF
        "
	  ::= { rm10010e40CtrlledTest 3 }



rm10010e40CtrlRedLed OBJECT-TYPE
	  SYNTAX EkiOnOff
	  MAX-ACCESS read-write
	  STATUS current
	  DESCRIPTION
        "
        Red Leds Test :This OID switches
        on all the red Leds as a test feature.
         <Help>  This control initiates
        a test leds turning all the LEDs
        to red
        "
	  ::= { rm10010e40CtrlledTest 2 }



rm10010e40CtrlGreenLed OBJECT-TYPE
	  SYNTAX EkiOnOff
	  MAX-ACCESS read-write
	  STATUS current
	  DESCRIPTION
        "
        Green Leds Test :This OID switches
        on all the green Leds as a test
        feature.  <Help>  This control
         initiates a test leds turning
         all the LEDs to green
        "
	  ::= { rm10010e40CtrlledTest 1 }



--- *****************************************************
---     LEAF for the initSwitchMarvell article
--- *****************************************************
rm10010e40CtrlinitSwitchMarvell OBJECT IDENTIFIER ::= { rm10010e40CtrlOther 201 }




rm10010e40CtrlInitSwitchMarvell OBJECT-TYPE
	  SYNTAX EkiOnOff
	  MAX-ACCESS read-write
	  STATUS current
	  DESCRIPTION
        "
        Switch Initialization :This OID
        operates an initialization of the
        switch managed through the module
         <Help>  This control activates
        an initialization of the switch
        managed through the module
        "
	  ::= { rm10010e40CtrlinitSwitchMarvell 1 }



--- *********************************************************
---     TABLE for the rm10010e40CtrlmsaLineLoop articles
--- *********************************************************

rm10010e40CtrlmsaLineLoopTable OBJECT-TYPE
	SYNTAX  SEQUENCE OF Rm10010e40CtrlmsaLineLoopEntry
	MAX-ACCESS not-accessible
	STATUS current
	DESCRIPTION
        "
        List of rm10010e40CtrlmsaLineLoop
        Article
        "
	::= { rm10010e40CtrlLine 209 }


rm10010e40CtrlmsaLineLoopEntry OBJECT-TYPE
	SYNTAX Rm10010e40CtrlmsaLineLoopEntry
	MAX-ACCESS not-accessible
	STATUS current
	DESCRIPTION
        "
        Row definition for the rm10010e40CtrlmsaLineLoop
        table
        "
	INDEX   { rm10010e40CtrlmsaLineLoopIndex }
	::= { rm10010e40CtrlmsaLineLoopTable 1 }


Rm10010e40CtrlmsaLineLoopEntry ::=
	SEQUENCE {
	rm10010e40CtrlmsaLineLoopIndex
		INTEGER,
	rm10010e40CtrlmsaLineLoopPortn
		EkiState
	}


rm10010e40CtrlmsaLineLoopIndex OBJECT-TYPE
	SYNTAX  INTEGER(0..128)
	MAX-ACCESS  read-only
	STATUS current
	DESCRIPTION
        "
        Index definition for the rm10010e40CtrlmsaLineLoop
        table
        "
	::= { rm10010e40CtrlmsaLineLoopEntry 1 }


rm10010e40CtrlmsaLineLoopPortn OBJECT-TYPE
	SYNTAX  EkiState
	MAX-ACCESS read-write
	STATUS current
	DESCRIPTION
        "
        MSA Line Loop :This OID operates
        a line loopback on the MSA Line
         <Help>  This control defines the
        line loop back of the line transceiver
        "
	::= { rm10010e40CtrlmsaLineLoopEntry 2 }


--- *********************************************************
---     TABLE for the rm10010e40CtrlmsaTxReset articles
--- *********************************************************

rm10010e40CtrlmsaTxResetTable OBJECT-TYPE
	SYNTAX  SEQUENCE OF Rm10010e40CtrlmsaTxResetEntry
	MAX-ACCESS not-accessible
	STATUS current
	DESCRIPTION
        "
        List of rm10010e40CtrlmsaTxReset
        Article
        "
	::= { rm10010e40CtrlLine 210 }


rm10010e40CtrlmsaTxResetEntry OBJECT-TYPE
	SYNTAX Rm10010e40CtrlmsaTxResetEntry
	MAX-ACCESS not-accessible
	STATUS current
	DESCRIPTION
        "
        Row definition for the rm10010e40CtrlmsaTxReset
        table
        "
	INDEX   { rm10010e40CtrlmsaTxResetIndex }
	::= { rm10010e40CtrlmsaTxResetTable 1 }


Rm10010e40CtrlmsaTxResetEntry ::=
	SEQUENCE {
	rm10010e40CtrlmsaTxResetIndex
		INTEGER,
	rm10010e40CtrlmsaTxResetPortn
		EkiState
	}


rm10010e40CtrlmsaTxResetIndex OBJECT-TYPE
	SYNTAX  INTEGER(0..128)
	MAX-ACCESS  read-only
	STATUS current
	DESCRIPTION
        "
        Index definition for the rm10010e40CtrlmsaTxReset
        table
        "
	::= { rm10010e40CtrlmsaTxResetEntry 1 }


rm10010e40CtrlmsaTxResetPortn OBJECT-TYPE
	SYNTAX  EkiState
	MAX-ACCESS read-write
	STATUS current
	DESCRIPTION
        "
        Line MSA TX Reset :This OID resets
        the TX portion of the MSA line
         module  <Help > This control
         initiates a reset of the transmitting
        side
        "
	::= { rm10010e40CtrlmsaTxResetEntry 2 }


--- *********************************************************
---     TABLE for the rm10010e40CtrlmsaRxReset articles
--- *********************************************************

rm10010e40CtrlmsaRxResetTable OBJECT-TYPE
	SYNTAX  SEQUENCE OF Rm10010e40CtrlmsaRxResetEntry
	MAX-ACCESS not-accessible
	STATUS current
	DESCRIPTION
        "
        List of rm10010e40CtrlmsaRxReset
        Article
        "
	::= { rm10010e40CtrlLine 211 }


rm10010e40CtrlmsaRxResetEntry OBJECT-TYPE
	SYNTAX Rm10010e40CtrlmsaRxResetEntry
	MAX-ACCESS not-accessible
	STATUS current
	DESCRIPTION
        "
        Row definition for the rm10010e40CtrlmsaRxReset
        table
        "
	INDEX   { rm10010e40CtrlmsaRxResetIndex }
	::= { rm10010e40CtrlmsaRxResetTable 1 }


Rm10010e40CtrlmsaRxResetEntry ::=
	SEQUENCE {
	rm10010e40CtrlmsaRxResetIndex
		INTEGER,
	rm10010e40CtrlmsaRxResetPortn
		EkiState
	}


rm10010e40CtrlmsaRxResetIndex OBJECT-TYPE
	SYNTAX  INTEGER(0..128)
	MAX-ACCESS  read-only
	STATUS current
	DESCRIPTION
        "
        Index definition for the rm10010e40CtrlmsaRxReset
        table
        "
	::= { rm10010e40CtrlmsaRxResetEntry 1 }


rm10010e40CtrlmsaRxResetPortn OBJECT-TYPE
	SYNTAX  EkiState
	MAX-ACCESS read-write
	STATUS current
	DESCRIPTION
        "
        Line MSA RX Reset :This OID resets
        the RX portion of the MSA line
         module  <Help > This control
         initiates a reset of the receiving
        side
        "
	::= { rm10010e40CtrlmsaRxResetEntry 2 }


--- *********************************************************
---     TABLE for the rm10010e40CtrlmsaShutdown articles
--- *********************************************************

rm10010e40CtrlmsaShutdownTable OBJECT-TYPE
	SYNTAX  SEQUENCE OF Rm10010e40CtrlmsaShutdownEntry
	MAX-ACCESS not-accessible
	STATUS current
	DESCRIPTION
        "
        List of rm10010e40CtrlmsaShutdown
        Article
        "
	::= { rm10010e40CtrlLine 212 }


rm10010e40CtrlmsaShutdownEntry OBJECT-TYPE
	SYNTAX Rm10010e40CtrlmsaShutdownEntry
	MAX-ACCESS not-accessible
	STATUS current
	DESCRIPTION
        "
        Row definition for the rm10010e40CtrlmsaShutdown
        table
        "
	INDEX   { rm10010e40CtrlmsaShutdownIndex }
	::= { rm10010e40CtrlmsaShutdownTable 1 }


Rm10010e40CtrlmsaShutdownEntry ::=
	SEQUENCE {
	rm10010e40CtrlmsaShutdownIndex
		INTEGER,
	rm10010e40CtrlmsaShutdownPortn
		EkiState
	}


rm10010e40CtrlmsaShutdownIndex OBJECT-TYPE
	SYNTAX  INTEGER(0..128)
	MAX-ACCESS  read-only
	STATUS current
	DESCRIPTION
        "
        Index definition for the rm10010e40CtrlmsaShutdown
        table
        "
	::= { rm10010e40CtrlmsaShutdownEntry 1 }


rm10010e40CtrlmsaShutdownPortn OBJECT-TYPE
	SYNTAX  EkiState
	MAX-ACCESS read-write
	STATUS current
	DESCRIPTION
        "
        Line MSA Shutdown :This OID enters
        a process to shutdown the MSA line
        module  <Help > This control  initiates
        a shutdown of the module
        "
	::= { rm10010e40CtrlmsaShutdownEntry 2 }


--- *****************************************************
---     LEAF for the resetCount article
--- *****************************************************
rm10010e40CtrlresetCount OBJECT IDENTIFIER ::= { rm10010e40CtrlOther 259 }




rm10010e40CtrlResetcount OBJECT-TYPE
	  SYNTAX EkiOnOff
	  MAX-ACCESS read-write
	  STATUS current
	  DESCRIPTION
        "
        Module Count Global Reset :This
        OID resets all the errors counters
        on the module  <Help > This control
         initiates a reset of the errors
        counters on the module
        "
	  ::= { rm10010e40CtrlresetCount 1 }



--- *****************************************************
---     LEAF for the resetRmon article
--- *****************************************************
rm10010e40CtrlresetRmon OBJECT IDENTIFIER ::= { rm10010e40CtrlOther 260 }




rm10010e40CtrlResetrmon OBJECT-TYPE
	  SYNTAX EkiOnOff
	  MAX-ACCESS read-write
	  STATUS current
	  DESCRIPTION
        "
        Module Rmon Global Reset :This
        OID resets all the Rmon counters
        on the module  <Help > This control
         initiates a reset of the Rmon
         counters on the module
        "
	  ::= { rm10010e40CtrlresetRmon 1 }



--- *****************************************************
---     LEAF for the resetMeasurements article
--- *****************************************************
rm10010e40CtrlresetMeasurements OBJECT IDENTIFIER ::= { rm10010e40CtrlOther 261 }




rm10010e40CtrlResetmeasurements OBJECT-TYPE
	  SYNTAX EkiOnOff
	  MAX-ACCESS read-write
	  STATUS current
	  DESCRIPTION
        "
        Management Meas Global Reset :This
        OID resets some measurements on
        the management  <Help > This control
         initiates a reset of some measurements
        on the management
        "
	  ::= { rm10010e40CtrlresetMeasurements 1 }








--- *****************************************************
--- $$$$$$$$$$$$$$$$$$$$$$$$$$$$$$$$$$$$$$$$$$$$$$$$$$$$$
---     COUNTERS
--- $$$$$$$$$$$$$$$$$$$$$$$$$$$$$$$$$$$$$$$$$$$$$$$$$$$$$
--- *****************************************************



--- *********************************************************
---     TABLE for the rm10010e40CntclientInputErrorCounterLaneOne articles
--- *********************************************************

rm10010e40CntclientInputErrorCounterLaneOneTable OBJECT-TYPE
	SYNTAX  SEQUENCE OF Rm10010e40CntclientInputErrorCounterLaneOneEntry
	MAX-ACCESS not-accessible
	STATUS current
	DESCRIPTION
        "
        List of rm10010e40CntclientInputErrorCounterLaneOne
        Article
        "
	::= { rm10010e40CntClient 16 }


rm10010e40CntclientInputErrorCounterLaneOneEntry OBJECT-TYPE
	SYNTAX Rm10010e40CntclientInputErrorCounterLaneOneEntry
	MAX-ACCESS not-accessible
	STATUS current
	DESCRIPTION
        "
        Row definition for the rm10010e40CntclientInputErrorCounterLaneOne
        table
        "
	INDEX   { rm10010e40CntclientInputErrorCounterLaneOneIndex }
	::= { rm10010e40CntclientInputErrorCounterLaneOneTable 1 }


Rm10010e40CntclientInputErrorCounterLaneOneEntry ::=
	SEQUENCE {
	rm10010e40CntclientInputErrorCounterLaneOneIndex
		INTEGER,
	rm10010e40CntclientInputErrorCounterLaneOneValuePortn
		Counter32,
	rm10010e40CntclientInputErrorCounterLaneOneErrorPortn
		EkiOnOff,
	rm10010e40CntclientInputErrorCounterLaneOneOverloadPortn
		EkiOnOff
	}


rm10010e40CntclientInputErrorCounterLaneOneIndex OBJECT-TYPE
	SYNTAX  INTEGER(0..128)
	MAX-ACCESS  read-only
	STATUS current
	DESCRIPTION
        "
        Index definition for the rm10010e40CntclientInputErrorCounterLaneOne
        table
        "
	::= { rm10010e40CntclientInputErrorCounterLaneOneEntry 1 }


rm10010e40CntclientInputErrorCounterLaneOneValuePortn OBJECT-TYPE
	SYNTAX  Counter32
	MAX-ACCESS read-only
	STATUS current
	DESCRIPTION
        "
        Client_Input_Error_Counter_Lane1
        :This counter is incremented each
        time a coding violation is detected
        on the host lane of the client
         transceiver <Help> This counter
        is incremented each time a coding
        violation is detected on the host
        lane of the client transceiver
        "
	::= { rm10010e40CntclientInputErrorCounterLaneOneEntry 2 }


rm10010e40CntclientInputErrorCounterLaneOneErrorPortn OBJECT-TYPE
	SYNTAX  EkiOnOff
	MAX-ACCESS read-only
	STATUS current
	DESCRIPTION
        "
        Client Input Counter Error :This
        OID when set indicates the rate
        adaptation removal counter value
        is invalid on Port
        "
	::= { rm10010e40CntclientInputErrorCounterLaneOneEntry 3 }


rm10010e40CntclientInputErrorCounterLaneOneOverloadPortn OBJECT-TYPE
	SYNTAX  EkiOnOff
	MAX-ACCESS read-only
	STATUS current
	DESCRIPTION
        "
        Client Input Counter Overload
         :This OID when set indicates a
        rate adaptation removal counter
        overload on Port
        "
	::= { rm10010e40CntclientInputErrorCounterLaneOneEntry 4 }


--- *********************************************************
---     TABLE for the rm10010e40CntclientInputErrorCounterLaneTwo articles
--- *********************************************************

rm10010e40CntclientInputErrorCounterLaneTwoTable OBJECT-TYPE
	SYNTAX  SEQUENCE OF Rm10010e40CntclientInputErrorCounterLaneTwoEntry
	MAX-ACCESS not-accessible
	STATUS current
	DESCRIPTION
        "
        List of rm10010e40CntclientInputErrorCounterLaneTwo
        Article
        "
	::= { rm10010e40CntClient 32 }


rm10010e40CntclientInputErrorCounterLaneTwoEntry OBJECT-TYPE
	SYNTAX Rm10010e40CntclientInputErrorCounterLaneTwoEntry
	MAX-ACCESS not-accessible
	STATUS current
	DESCRIPTION
        "
        Row definition for the rm10010e40CntclientInputErrorCounterLaneTwo
        table
        "
	INDEX   { rm10010e40CntclientInputErrorCounterLaneTwoIndex }
	::= { rm10010e40CntclientInputErrorCounterLaneTwoTable 1 }


Rm10010e40CntclientInputErrorCounterLaneTwoEntry ::=
	SEQUENCE {
	rm10010e40CntclientInputErrorCounterLaneTwoIndex
		INTEGER,
	rm10010e40CntclientInputErrorCounterLaneTwoValuePortn
		Counter32,
	rm10010e40CntclientInputErrorCounterLaneTwoErrorPortn
		EkiOnOff,
	rm10010e40CntclientInputErrorCounterLaneTwoOverloadPortn
		EkiOnOff
	}


rm10010e40CntclientInputErrorCounterLaneTwoIndex OBJECT-TYPE
	SYNTAX  INTEGER(0..128)
	MAX-ACCESS  read-only
	STATUS current
	DESCRIPTION
        "
        Index definition for the rm10010e40CntclientInputErrorCounterLaneTwo
        table
        "
	::= { rm10010e40CntclientInputErrorCounterLaneTwoEntry 1 }


rm10010e40CntclientInputErrorCounterLaneTwoValuePortn OBJECT-TYPE
	SYNTAX  Counter32
	MAX-ACCESS read-only
	STATUS current
	DESCRIPTION
        "
        Client_Input_Error_Counter_Lane2
        :This counter is incremented each
        time a coding violation is detected
        on the host lane of the client
         transceiver <Help> This counter
        is incremented each time a coding
        violation is detected on the host
        lane of the client transceiver
        "
	::= { rm10010e40CntclientInputErrorCounterLaneTwoEntry 2 }


rm10010e40CntclientInputErrorCounterLaneTwoErrorPortn OBJECT-TYPE
	SYNTAX  EkiOnOff
	MAX-ACCESS read-only
	STATUS current
	DESCRIPTION
        "
        Client Input Counter Error :This
        OID when set indicates the client
        error counter value is invalid
         on Port
        "
	::= { rm10010e40CntclientInputErrorCounterLaneTwoEntry 3 }


rm10010e40CntclientInputErrorCounterLaneTwoOverloadPortn OBJECT-TYPE
	SYNTAX  EkiOnOff
	MAX-ACCESS read-only
	STATUS current
	DESCRIPTION
        "
        Client Input Counter Overload
         :This OID when set indicates a
        client input error counter overload
        on Port
        "
	::= { rm10010e40CntclientInputErrorCounterLaneTwoEntry 4 }


--- *********************************************************
---     TABLE for the rm10010e40CntclientInputErrorCounter articles
--- *********************************************************

rm10010e40CntclientInputErrorCounterTable OBJECT-TYPE
	SYNTAX  SEQUENCE OF Rm10010e40CntclientInputErrorCounterEntry
	MAX-ACCESS not-accessible
	STATUS current
	DESCRIPTION
        "
        List of rm10010e40CntclientInputErrorCounter
        Article
        "
	::= { rm10010e40CntClient 80 }


rm10010e40CntclientInputErrorCounterEntry OBJECT-TYPE
	SYNTAX Rm10010e40CntclientInputErrorCounterEntry
	MAX-ACCESS not-accessible
	STATUS current
	DESCRIPTION
        "
        Row definition for the rm10010e40CntclientInputErrorCounter
        table
        "
	INDEX   { rm10010e40CntclientInputErrorCounterIndex }
	::= { rm10010e40CntclientInputErrorCounterTable 1 }


Rm10010e40CntclientInputErrorCounterEntry ::=
	SEQUENCE {
	rm10010e40CntclientInputErrorCounterIndex
		INTEGER,
	rm10010e40CntclientInputErrorCounterValuePortn
		Counter32,
	rm10010e40CntclientInputErrorCounterErrorPortn
		EkiOnOff,
	rm10010e40CntclientInputErrorCounterOverloadPortn
		EkiOnOff
	}


rm10010e40CntclientInputErrorCounterIndex OBJECT-TYPE
	SYNTAX  INTEGER(0..128)
	MAX-ACCESS  read-only
	STATUS current
	DESCRIPTION
        "
        Index definition for the rm10010e40CntclientInputErrorCounter
        table
        "
	::= { rm10010e40CntclientInputErrorCounterEntry 1 }


rm10010e40CntclientInputErrorCounterValuePortn OBJECT-TYPE
	SYNTAX  Counter32
	MAX-ACCESS read-only
	STATUS current
	DESCRIPTION
        "
        Client Input Errors :This counter
        is increased each time a 10b/8b
        running disparity error is detected
        on the Client input stream  <Help>
         This counter gives the number
         of 10b/8b running disparity errors
        on the client port
        "
	::= { rm10010e40CntclientInputErrorCounterEntry 2 }


rm10010e40CntclientInputErrorCounterErrorPortn OBJECT-TYPE
	SYNTAX  EkiOnOff
	MAX-ACCESS read-only
	STATUS current
	DESCRIPTION
        "
        Client Counter Error :This OID
        when set indicates the client error
        counter value is invalid on Port
        "
	::= { rm10010e40CntclientInputErrorCounterEntry 3 }


rm10010e40CntclientInputErrorCounterOverloadPortn OBJECT-TYPE
	SYNTAX  EkiOnOff
	MAX-ACCESS read-only
	STATUS current
	DESCRIPTION
        "
        Client Counter Overload :This
         OID when set indicates a client
        input error counter overload on
        Port
        "
	::= { rm10010e40CntclientInputErrorCounterEntry 4 }


--- *********************************************************
---     TABLE for the rm10010e40CntclientCbipCounter articles
--- *********************************************************

rm10010e40CntclientCbipCounterTable OBJECT-TYPE
	SYNTAX  SEQUENCE OF Rm10010e40CntclientCbipCounterEntry
	MAX-ACCESS not-accessible
	STATUS current
	DESCRIPTION
        "
        List of rm10010e40CntclientCbipCounter
        Article
        "
	::= { rm10010e40CntClient 96 }


rm10010e40CntclientCbipCounterEntry OBJECT-TYPE
	SYNTAX Rm10010e40CntclientCbipCounterEntry
	MAX-ACCESS not-accessible
	STATUS current
	DESCRIPTION
        "
        Row definition for the rm10010e40CntclientCbipCounter
        table
        "
	INDEX   { rm10010e40CntclientCbipCounterIndex }
	::= { rm10010e40CntclientCbipCounterTable 1 }


Rm10010e40CntclientCbipCounterEntry ::=
	SEQUENCE {
	rm10010e40CntclientCbipCounterIndex
		INTEGER,
	rm10010e40CntclientCbipCounterValuePortn
		Counter32,
	rm10010e40CntclientCbipCounterErrorPortn
		EkiOnOff,
	rm10010e40CntclientCbipCounterOverloadPortn
		EkiOnOff
	}


rm10010e40CntclientCbipCounterIndex OBJECT-TYPE
	SYNTAX  INTEGER(0..128)
	MAX-ACCESS  read-only
	STATUS current
	DESCRIPTION
        "
        Index definition for the rm10010e40CntclientCbipCounter
        table
        "
	::= { rm10010e40CntclientCbipCounterEntry 1 }


rm10010e40CntclientCbipCounterValuePortn OBJECT-TYPE
	SYNTAX  Counter32
	MAX-ACCESS read-only
	STATUS current
	DESCRIPTION
        "
        Client Output Errors :This counter
        is incremented each time a CBIP
        parity error is detected on the
        Client output stream  <Help>  This
        counter gives the number of CBIP
        errors on the client port
        "
	::= { rm10010e40CntclientCbipCounterEntry 2 }


rm10010e40CntclientCbipCounterErrorPortn OBJECT-TYPE
	SYNTAX  EkiOnOff
	MAX-ACCESS read-only
	STATUS current
	DESCRIPTION
        "
        Client Counter Error :This OID
        when set indicates the CBIP error
        counter value is invalid on Port
        "
	::= { rm10010e40CntclientCbipCounterEntry 3 }


rm10010e40CntclientCbipCounterOverloadPortn OBJECT-TYPE
	SYNTAX  EkiOnOff
	MAX-ACCESS read-only
	STATUS current
	DESCRIPTION
        "
        Client CBIP Counter Overload :This
        OID when set indicates a CBIP error
        counter overload on Port
        "
	::= { rm10010e40CntclientCbipCounterEntry 4 }


--- *********************************************************
---     TABLE for the rm10010e40CntlocalLineSmBip8ErrorCounter articles
--- *********************************************************

rm10010e40CntlocalLineSmBip8ErrorCounterTable OBJECT-TYPE
	SYNTAX  SEQUENCE OF Rm10010e40CntlocalLineSmBip8ErrorCounterEntry
	MAX-ACCESS not-accessible
	STATUS current
	DESCRIPTION
        "
        List of rm10010e40CntlocalLineSmBip8ErrorCounter
        Article
        "
	::= { rm10010e40CntLine 192 }


rm10010e40CntlocalLineSmBip8ErrorCounterEntry OBJECT-TYPE
	SYNTAX Rm10010e40CntlocalLineSmBip8ErrorCounterEntry
	MAX-ACCESS not-accessible
	STATUS current
	DESCRIPTION
        "
        Row definition for the rm10010e40CntlocalLineSmBip8ErrorCounter
        table
        "
	INDEX   { rm10010e40CntlocalLineSmBip8ErrorCounterIndex }
	::= { rm10010e40CntlocalLineSmBip8ErrorCounterTable 1 }


Rm10010e40CntlocalLineSmBip8ErrorCounterEntry ::=
	SEQUENCE {
	rm10010e40CntlocalLineSmBip8ErrorCounterIndex
		INTEGER,
	rm10010e40CntlocalLineSmBip8ErrorCounterValuePortn
		Counter64,
	rm10010e40CntlocalLineSmBip8ErrorCounterErrorPortn
		EkiOnOff,
	rm10010e40CntlocalLineSmBip8ErrorCounterOverloadPortn
		EkiOnOff
	}


rm10010e40CntlocalLineSmBip8ErrorCounterIndex OBJECT-TYPE
	SYNTAX  INTEGER(0..128)
	MAX-ACCESS  read-only
	STATUS current
	DESCRIPTION
        "
        Index definition for the rm10010e40CntlocalLineSmBip8ErrorCounter
        table
        "
	::= { rm10010e40CntlocalLineSmBip8ErrorCounterEntry 1 }


rm10010e40CntlocalLineSmBip8ErrorCounterValuePortn OBJECT-TYPE
	SYNTAX  Counter64
	MAX-ACCESS read-only
	STATUS current
	DESCRIPTION
        "
        Line Input SM-BIP8 Errors :This
        OID gives the current Bit Error
        Rate (residual SM-BIP8 error) after
        FEC   <Help> This counter gives
        the current Bit Error Rate (residual
        SM-BIP8 error) after FEC
        "
	::= { rm10010e40CntlocalLineSmBip8ErrorCounterEntry 2 }


rm10010e40CntlocalLineSmBip8ErrorCounterErrorPortn OBJECT-TYPE
	SYNTAX  EkiOnOff
	MAX-ACCESS read-only
	STATUS current
	DESCRIPTION
        "
        Line Counter Error :This OID when
        set indicates the B1 error counter
        value is invalid on Port
        "
	::= { rm10010e40CntlocalLineSmBip8ErrorCounterEntry 3 }


rm10010e40CntlocalLineSmBip8ErrorCounterOverloadPortn OBJECT-TYPE
	SYNTAX  EkiOnOff
	MAX-ACCESS read-only
	STATUS current
	DESCRIPTION
        "
        Line Counter Overload :This OID
        when set indicates a B1 error counter
        overload on Port
        "
	::= { rm10010e40CntlocalLineSmBip8ErrorCounterEntry 4 }


--- *********************************************************
---     TABLE for the rm10010e40CntlocalLineFecCorrectedErrorsCounter articles
--- *********************************************************

rm10010e40CntlocalLineFecCorrectedErrorsCounterTable OBJECT-TYPE
	SYNTAX  SEQUENCE OF Rm10010e40CntlocalLineFecCorrectedErrorsCounterEntry
	MAX-ACCESS not-accessible
	STATUS current
	DESCRIPTION
        "
        List of rm10010e40CntlocalLineFecCorrectedErrorsCounter
        Article
        "
	::= { rm10010e40CntLine 193 }


rm10010e40CntlocalLineFecCorrectedErrorsCounterEntry OBJECT-TYPE
	SYNTAX Rm10010e40CntlocalLineFecCorrectedErrorsCounterEntry
	MAX-ACCESS not-accessible
	STATUS current
	DESCRIPTION
        "
        Row definition for the rm10010e40CntlocalLineFecCorrectedErrorsCounter
        table
        "
	INDEX   { rm10010e40CntlocalLineFecCorrectedErrorsCounterIndex }
	::= { rm10010e40CntlocalLineFecCorrectedErrorsCounterTable 1 }


Rm10010e40CntlocalLineFecCorrectedErrorsCounterEntry ::=
	SEQUENCE {
	rm10010e40CntlocalLineFecCorrectedErrorsCounterIndex
		INTEGER,
	rm10010e40CntlocalLineFecCorrectedErrorsCounterValuePortn
		Counter64,
	rm10010e40CntlocalLineFecCorrectedErrorsCounterErrorPortn
		EkiOnOff,
	rm10010e40CntlocalLineFecCorrectedErrorsCounterOverloadPortn
		EkiOnOff
	}


rm10010e40CntlocalLineFecCorrectedErrorsCounterIndex OBJECT-TYPE
	SYNTAX  INTEGER(0..128)
	MAX-ACCESS  read-only
	STATUS current
	DESCRIPTION
        "
        Index definition for the rm10010e40CntlocalLineFecCorrectedErrorsCounter
        table
        "
	::= { rm10010e40CntlocalLineFecCorrectedErrorsCounterEntry 1 }


rm10010e40CntlocalLineFecCorrectedErrorsCounterValuePortn OBJECT-TYPE
	SYNTAX  Counter64
	MAX-ACCESS read-only
	STATUS current
	DESCRIPTION
        "
        Line Input HD FEC Corrected Errors
        :This OID gives the current Bit
        Error Rate before the Hard Decision
        FEC  <Help> This counter gives
         the current Bit Error Rate before
        the Hard Decision FEC
        "
	::= { rm10010e40CntlocalLineFecCorrectedErrorsCounterEntry 2 }


rm10010e40CntlocalLineFecCorrectedErrorsCounterErrorPortn OBJECT-TYPE
	SYNTAX  EkiOnOff
	MAX-ACCESS read-only
	STATUS current
	DESCRIPTION
        "
        FEC Counter Error :This bit when
        set indicates the FEC corrected
        errors counter value is invalid
        on Line
        "
	::= { rm10010e40CntlocalLineFecCorrectedErrorsCounterEntry 3 }


rm10010e40CntlocalLineFecCorrectedErrorsCounterOverloadPortn OBJECT-TYPE
	SYNTAX  EkiOnOff
	MAX-ACCESS read-only
	STATUS current
	DESCRIPTION
        "
        FEC Counter Overload :This bit
        when set indicates a FEC corrected
        errors counter overload on Line
        "
	::= { rm10010e40CntlocalLineFecCorrectedErrorsCounterEntry 4 }


--- *********************************************************
---     TABLE for the rm10010e40CntremoteLineSmBip8ErrorCounter articles
--- *********************************************************

rm10010e40CntremoteLineSmBip8ErrorCounterTable OBJECT-TYPE
	SYNTAX  SEQUENCE OF Rm10010e40CntremoteLineSmBip8ErrorCounterEntry
	MAX-ACCESS not-accessible
	STATUS current
	DESCRIPTION
        "
        List of rm10010e40CntremoteLineSmBip8ErrorCounter
        Article
        "
	::= { rm10010e40CntLine 194 }


rm10010e40CntremoteLineSmBip8ErrorCounterEntry OBJECT-TYPE
	SYNTAX Rm10010e40CntremoteLineSmBip8ErrorCounterEntry
	MAX-ACCESS not-accessible
	STATUS current
	DESCRIPTION
        "
        Row definition for the rm10010e40CntremoteLineSmBip8ErrorCounter
        table
        "
	INDEX   { rm10010e40CntremoteLineSmBip8ErrorCounterIndex }
	::= { rm10010e40CntremoteLineSmBip8ErrorCounterTable 1 }


Rm10010e40CntremoteLineSmBip8ErrorCounterEntry ::=
	SEQUENCE {
	rm10010e40CntremoteLineSmBip8ErrorCounterIndex
		INTEGER,
	rm10010e40CntremoteLineSmBip8ErrorCounterValuePortn
		Counter64,
	rm10010e40CntremoteLineSmBip8ErrorCounterErrorPortn
		EkiOnOff,
	rm10010e40CntremoteLineSmBip8ErrorCounterOverloadPortn
		EkiOnOff
	}


rm10010e40CntremoteLineSmBip8ErrorCounterIndex OBJECT-TYPE
	SYNTAX  INTEGER(0..128)
	MAX-ACCESS  read-only
	STATUS current
	DESCRIPTION
        "
        Index definition for the rm10010e40CntremoteLineSmBip8ErrorCounter
        table
        "
	::= { rm10010e40CntremoteLineSmBip8ErrorCounterEntry 1 }


rm10010e40CntremoteLineSmBip8ErrorCounterValuePortn OBJECT-TYPE
	SYNTAX  Counter64
	MAX-ACCESS read-only
	STATUS current
	DESCRIPTION
        "
        Remote SM BIP8 :This OID gives
        the current Bit Error Rate (residual
        SM-BIP8 error) after FEC on the
        remote side  <Help> This counter
        gives the current Bit Error Rate
        (residual SM-BIP8 error) after
         FEC on the remote side
        "
	::= { rm10010e40CntremoteLineSmBip8ErrorCounterEntry 2 }


rm10010e40CntremoteLineSmBip8ErrorCounterErrorPortn OBJECT-TYPE
	SYNTAX  EkiOnOff
	MAX-ACCESS read-only
	STATUS current
	DESCRIPTION
        "
        Remote Counter Error :
        "
	::= { rm10010e40CntremoteLineSmBip8ErrorCounterEntry 3 }


rm10010e40CntremoteLineSmBip8ErrorCounterOverloadPortn OBJECT-TYPE
	SYNTAX  EkiOnOff
	MAX-ACCESS read-only
	STATUS current
	DESCRIPTION
        "
        Remote Counter Overload :
        "
	::= { rm10010e40CntremoteLineSmBip8ErrorCounterEntry 4 }


--- *********************************************************
---     TABLE for the rm10010e40CntlineDfrmTimCnt articles
--- *********************************************************

rm10010e40CntlineDfrmTimCntTable OBJECT-TYPE
	SYNTAX  SEQUENCE OF Rm10010e40CntlineDfrmTimCntEntry
	MAX-ACCESS not-accessible
	STATUS current
	DESCRIPTION
        "
        List of rm10010e40CntlineDfrmTimCnt
        Article
        "
	::= { rm10010e40CntLine 195 }


rm10010e40CntlineDfrmTimCntEntry OBJECT-TYPE
	SYNTAX Rm10010e40CntlineDfrmTimCntEntry
	MAX-ACCESS not-accessible
	STATUS current
	DESCRIPTION
        "
        Row definition for the rm10010e40CntlineDfrmTimCnt
        table
        "
	INDEX   { rm10010e40CntlineDfrmTimCntIndex }
	::= { rm10010e40CntlineDfrmTimCntTable 1 }


Rm10010e40CntlineDfrmTimCntEntry ::=
	SEQUENCE {
	rm10010e40CntlineDfrmTimCntIndex
		INTEGER,
	rm10010e40CntlineDfrmTimCntValuePortn
		Counter64,
	rm10010e40CntlineDfrmTimCntErrorPortn
		EkiOnOff,
	rm10010e40CntlineDfrmTimCntOverloadPortn
		EkiOnOff
	}


rm10010e40CntlineDfrmTimCntIndex OBJECT-TYPE
	SYNTAX  INTEGER(0..128)
	MAX-ACCESS  read-only
	STATUS current
	DESCRIPTION
        "
        Index definition for the rm10010e40CntlineDfrmTimCnt
        table
        "
	::= { rm10010e40CntlineDfrmTimCntEntry 1 }


rm10010e40CntlineDfrmTimCntValuePortn OBJECT-TYPE
	SYNTAX  Counter64
	MAX-ACCESS read-only
	STATUS current
	DESCRIPTION
        "
        Line Timer Counter :
        "
	::= { rm10010e40CntlineDfrmTimCntEntry 2 }


rm10010e40CntlineDfrmTimCntErrorPortn OBJECT-TYPE
	SYNTAX  EkiOnOff
	MAX-ACCESS read-only
	STATUS current
	DESCRIPTION
        "
        Line Counter Error :This OID when
        set indicates the deframer timer
        counter value is invalid on Port
        "
	::= { rm10010e40CntlineDfrmTimCntEntry 3 }


rm10010e40CntlineDfrmTimCntOverloadPortn OBJECT-TYPE
	SYNTAX  EkiOnOff
	MAX-ACCESS read-only
	STATUS current
	DESCRIPTION
        "
        Line Counter Overload :This OID
        when set indicates a deframer timer
        counter overload on Port
        "
	::= { rm10010e40CntlineDfrmTimCntEntry 4 }


--- *********************************************************
---     TABLE for the rm10010e40CntlocalLineTrscvFecCorrectedErrorCounter articles
--- *********************************************************

rm10010e40CntlocalLineTrscvFecCorrectedErrorCounterTable OBJECT-TYPE
	SYNTAX  SEQUENCE OF Rm10010e40CntlocalLineTrscvFecCorrectedErrorCounterEntry
	MAX-ACCESS not-accessible
	STATUS current
	DESCRIPTION
        "
        List of rm10010e40CntlocalLineTrscvFecCorrectedErrorCounter
        Article
        "
	::= { rm10010e40CntLine 196 }


rm10010e40CntlocalLineTrscvFecCorrectedErrorCounterEntry OBJECT-TYPE
	SYNTAX Rm10010e40CntlocalLineTrscvFecCorrectedErrorCounterEntry
	MAX-ACCESS not-accessible
	STATUS current
	DESCRIPTION
        "
        Row definition for the rm10010e40CntlocalLineTrscvFecCorrectedErrorCounter
        table
        "
	INDEX   { rm10010e40CntlocalLineTrscvFecCorrectedErrorCounterIndex }
	::= { rm10010e40CntlocalLineTrscvFecCorrectedErrorCounterTable 1 }


Rm10010e40CntlocalLineTrscvFecCorrectedErrorCounterEntry ::=
	SEQUENCE {
	rm10010e40CntlocalLineTrscvFecCorrectedErrorCounterIndex
		INTEGER,
	rm10010e40CntlocalLineTrscvFecCorrectedErrorCounterValuePortn
		Counter64,
	rm10010e40CntlocalLineTrscvFecCorrectedErrorCounterErrorPortn
		EkiOnOff,
	rm10010e40CntlocalLineTrscvFecCorrectedErrorCounterOverloadPortn
		EkiOnOff
	}


rm10010e40CntlocalLineTrscvFecCorrectedErrorCounterIndex OBJECT-TYPE
	SYNTAX  INTEGER(0..128)
	MAX-ACCESS  read-only
	STATUS current
	DESCRIPTION
        "
        Index definition for the rm10010e40CntlocalLineTrscvFecCorrectedErrorCounter
        table
        "
	::= { rm10010e40CntlocalLineTrscvFecCorrectedErrorCounterEntry 1 }


rm10010e40CntlocalLineTrscvFecCorrectedErrorCounterValuePortn OBJECT-TYPE
	SYNTAX  Counter64
	MAX-ACCESS read-only
	STATUS current
	DESCRIPTION
        "
        Line Input SD FEC Corrected Errors
        :This OID gives the current Bit
        Error Rate before the Soft Decision
        FEC  <Help> This counter gives
         the current Bit Error Rate before
        the Soft Decision FEC
        "
	::= { rm10010e40CntlocalLineTrscvFecCorrectedErrorCounterEntry 2 }


rm10010e40CntlocalLineTrscvFecCorrectedErrorCounterErrorPortn OBJECT-TYPE
	SYNTAX  EkiOnOff
	MAX-ACCESS read-only
	STATUS current
	DESCRIPTION
        "
        Line Counter Error :This OID when
        set indicates the deframer timer
        counter value is invalid on Port
        "
	::= { rm10010e40CntlocalLineTrscvFecCorrectedErrorCounterEntry 3 }


rm10010e40CntlocalLineTrscvFecCorrectedErrorCounterOverloadPortn OBJECT-TYPE
	SYNTAX  EkiOnOff
	MAX-ACCESS read-only
	STATUS current
	DESCRIPTION
        "
        Line Counter Overload :This OID
        when set indicates a deframer timer
        counter overload on Port
        "
	::= { rm10010e40CntlocalLineTrscvFecCorrectedErrorCounterEntry 4 }


--- *********************************************************
---     TABLE for the rm10010e40CntlocalLineTrscvFecUncorrectedErrorCounter articles
--- *********************************************************

rm10010e40CntlocalLineTrscvFecUncorrectedErrorCounterTable OBJECT-TYPE
	SYNTAX  SEQUENCE OF Rm10010e40CntlocalLineTrscvFecUncorrectedErrorCounterEntry
	MAX-ACCESS not-accessible
	STATUS current
	DESCRIPTION
        "
        List of rm10010e40CntlocalLineTrscvFecUncorrectedErrorCounter
        Article
        "
	::= { rm10010e40CntLine 197 }


rm10010e40CntlocalLineTrscvFecUncorrectedErrorCounterEntry OBJECT-TYPE
	SYNTAX Rm10010e40CntlocalLineTrscvFecUncorrectedErrorCounterEntry
	MAX-ACCESS not-accessible
	STATUS current
	DESCRIPTION
        "
        Row definition for the rm10010e40CntlocalLineTrscvFecUncorrectedErrorCounter
        table
        "
	INDEX   { rm10010e40CntlocalLineTrscvFecUncorrectedErrorCounterIndex }
	::= { rm10010e40CntlocalLineTrscvFecUncorrectedErrorCounterTable 1 }


Rm10010e40CntlocalLineTrscvFecUncorrectedErrorCounterEntry ::=
	SEQUENCE {
	rm10010e40CntlocalLineTrscvFecUncorrectedErrorCounterIndex
		INTEGER,
	rm10010e40CntlocalLineTrscvFecUncorrectedErrorCounterValuePortn
		Counter64,
	rm10010e40CntlocalLineTrscvFecUncorrectedErrorCounterErrorPortn
		EkiOnOff,
	rm10010e40CntlocalLineTrscvFecUncorrectedErrorCounterOverloadPortn
		EkiOnOff
	}


rm10010e40CntlocalLineTrscvFecUncorrectedErrorCounterIndex OBJECT-TYPE
	SYNTAX  INTEGER(0..128)
	MAX-ACCESS  read-only
	STATUS current
	DESCRIPTION
        "
        Index definition for the rm10010e40CntlocalLineTrscvFecUncorrectedErrorCounter
        table
        "
	::= { rm10010e40CntlocalLineTrscvFecUncorrectedErrorCounterEntry 1 }


rm10010e40CntlocalLineTrscvFecUncorrectedErrorCounterValuePortn OBJECT-TYPE
	SYNTAX  Counter64
	MAX-ACCESS read-only
	STATUS current
	DESCRIPTION
        "
        SD Uncorrected :This OID gives
        the current Bit Error Rate after
        the Soft Decision FEC (residual)
         <Help> This counter gives the
         current Bit Error Rate after the
        Soft Decision FEC (residual)
        "
	::= { rm10010e40CntlocalLineTrscvFecUncorrectedErrorCounterEntry 2 }


rm10010e40CntlocalLineTrscvFecUncorrectedErrorCounterErrorPortn OBJECT-TYPE
	SYNTAX  EkiOnOff
	MAX-ACCESS read-only
	STATUS current
	DESCRIPTION
        "
        Line Counter Error :This OID when
        set indicates the deframer timer
        counter value is invalid on Port
        "
	::= { rm10010e40CntlocalLineTrscvFecUncorrectedErrorCounterEntry 3 }


rm10010e40CntlocalLineTrscvFecUncorrectedErrorCounterOverloadPortn OBJECT-TYPE
	SYNTAX  EkiOnOff
	MAX-ACCESS read-only
	STATUS current
	DESCRIPTION
        "
        Line Counter Overload :This OID
        when set indicates a deframer timer
        counter overload on Port
        "
	::= { rm10010e40CntlocalLineTrscvFecUncorrectedErrorCounterEntry 4 }







--- *****************************************************
--- $$$$$$$$$$$$$$$$$$$$$$$$$$$$$$$$$$$$$$$$$$$$$$$$$$$$$
---     RMON
--- $$$$$$$$$$$$$$$$$$$$$$$$$$$$$$$$$$$$$$$$$$$$$$$$$$$$$
--- *****************************************************



--- *********************************************************
---     TABLE for the rm10010e40MonupRmonBytesCounterClientInput articles
--- *********************************************************

rm10010e40MonupRmonBytesCounterClientInputTable OBJECT-TYPE
	SYNTAX  SEQUENCE OF Rm10010e40MonupRmonBytesCounterClientInputEntry
	MAX-ACCESS not-accessible
	STATUS current
	DESCRIPTION
        "
        List of rm10010e40MonupRmonBytesCounterClientInput
        Article
        "
	::= { rm10010e40MonClientRmonCounter 16 }


rm10010e40MonupRmonBytesCounterClientInputEntry OBJECT-TYPE
	SYNTAX Rm10010e40MonupRmonBytesCounterClientInputEntry
	MAX-ACCESS not-accessible
	STATUS current
	DESCRIPTION
        "
        Row definition for the rm10010e40MonupRmonBytesCounterClientInput
        table
        "
	INDEX   { rm10010e40MonupRmonBytesCounterClientInputIndex }
	::= { rm10010e40MonupRmonBytesCounterClientInputTable 1 }


Rm10010e40MonupRmonBytesCounterClientInputEntry ::=
	SEQUENCE {
	rm10010e40MonupRmonBytesCounterClientInputIndex
		INTEGER,
	rm10010e40MonupRmonBytesCounterClientInputValuePortn
		Counter64,
	rm10010e40MonupRmonBytesCounterClientInputErrorPortn
		EkiOnOff,
	rm10010e40MonupRmonBytesCounterClientInputOverloadPortn
		EkiOnOff
	}


rm10010e40MonupRmonBytesCounterClientInputIndex OBJECT-TYPE
	SYNTAX  INTEGER(0..128)
	MAX-ACCESS  read-only
	STATUS current
	DESCRIPTION
        "
        Index definition for the rm10010e40MonupRmonBytesCounterClientInput
        table
        "
	::= { rm10010e40MonupRmonBytesCounterClientInputEntry 1 }


rm10010e40MonupRmonBytesCounterClientInputValuePortn OBJECT-TYPE
	SYNTAX  Counter64
	MAX-ACCESS read-only
	STATUS current
	DESCRIPTION
        "
        Client Input Bytes :This counter
        is increased each time a data byte
        is received on the client port
          <Help>  This counter gives the
        number of bytes received on the
        client port
        "
	::= { rm10010e40MonupRmonBytesCounterClientInputEntry 2 }


rm10010e40MonupRmonBytesCounterClientInputErrorPortn OBJECT-TYPE
	SYNTAX  EkiOnOff
	MAX-ACCESS read-only
	STATUS current
	DESCRIPTION
        "
        Bytes Counter Error :This OID
         when set indicates the Bytes counter
        value is invalid on client port
        "
	::= { rm10010e40MonupRmonBytesCounterClientInputEntry 3 }


rm10010e40MonupRmonBytesCounterClientInputOverloadPortn OBJECT-TYPE
	SYNTAX  EkiOnOff
	MAX-ACCESS read-only
	STATUS current
	DESCRIPTION
        "
        Bytes Counter Overload :This OID
        when set indicates a Bytes counter
        overload on client port
        "
	::= { rm10010e40MonupRmonBytesCounterClientInputEntry 4 }


--- *********************************************************
---     TABLE for the rm10010e40MonupRmonCrcErrorsCounterClientInput articles
--- *********************************************************

rm10010e40MonupRmonCrcErrorsCounterClientInputTable OBJECT-TYPE
	SYNTAX  SEQUENCE OF Rm10010e40MonupRmonCrcErrorsCounterClientInputEntry
	MAX-ACCESS not-accessible
	STATUS current
	DESCRIPTION
        "
        List of rm10010e40MonupRmonCrcErrorsCounterClientInput
        Article
        "
	::= { rm10010e40MonClientRmonCounter 32 }


rm10010e40MonupRmonCrcErrorsCounterClientInputEntry OBJECT-TYPE
	SYNTAX Rm10010e40MonupRmonCrcErrorsCounterClientInputEntry
	MAX-ACCESS not-accessible
	STATUS current
	DESCRIPTION
        "
        Row definition for the rm10010e40MonupRmonCrcErrorsCounterClientInput
        table
        "
	INDEX   { rm10010e40MonupRmonCrcErrorsCounterClientInputIndex }
	::= { rm10010e40MonupRmonCrcErrorsCounterClientInputTable 1 }


Rm10010e40MonupRmonCrcErrorsCounterClientInputEntry ::=
	SEQUENCE {
	rm10010e40MonupRmonCrcErrorsCounterClientInputIndex
		INTEGER,
	rm10010e40MonupRmonCrcErrorsCounterClientInputValuePortn
		Counter64,
	rm10010e40MonupRmonCrcErrorsCounterClientInputErrorPortn
		EkiOnOff,
	rm10010e40MonupRmonCrcErrorsCounterClientInputOverloadPortn
		EkiOnOff
	}


rm10010e40MonupRmonCrcErrorsCounterClientInputIndex OBJECT-TYPE
	SYNTAX  INTEGER(0..128)
	MAX-ACCESS  read-only
	STATUS current
	DESCRIPTION
        "
        Index definition for the rm10010e40MonupRmonCrcErrorsCounterClientInput
        table
        "
	::= { rm10010e40MonupRmonCrcErrorsCounterClientInputEntry 1 }


rm10010e40MonupRmonCrcErrorsCounterClientInputValuePortn OBJECT-TYPE
	SYNTAX  Counter64
	MAX-ACCESS read-only
	STATUS current
	DESCRIPTION
        "
        Client Input CRC Errors :This
         counter is increased each time
        a B1/CRC error is detected on the
        client port  <Help>  This counter
        gives the number of B1/CRC Errors
        received on the client port
        "
	::= { rm10010e40MonupRmonCrcErrorsCounterClientInputEntry 2 }


rm10010e40MonupRmonCrcErrorsCounterClientInputErrorPortn OBJECT-TYPE
	SYNTAX  EkiOnOff
	MAX-ACCESS read-only
	STATUS current
	DESCRIPTION
        "
        CRC Errors Counter Error :This
        OID when set indicates the CRC
         Errors counter value is invalid
        on client port
        "
	::= { rm10010e40MonupRmonCrcErrorsCounterClientInputEntry 3 }


rm10010e40MonupRmonCrcErrorsCounterClientInputOverloadPortn OBJECT-TYPE
	SYNTAX  EkiOnOff
	MAX-ACCESS read-only
	STATUS current
	DESCRIPTION
        "
        CRC Errors Counter Overload :This
        OID when set indicates a CRC Errors
        counter overload on client port
        "
	::= { rm10010e40MonupRmonCrcErrorsCounterClientInputEntry 4 }


--- *********************************************************
---     TABLE for the rm10010e40MonupRmonPacketsCounterClientInput articles
--- *********************************************************

rm10010e40MonupRmonPacketsCounterClientInputTable OBJECT-TYPE
	SYNTAX  SEQUENCE OF Rm10010e40MonupRmonPacketsCounterClientInputEntry
	MAX-ACCESS not-accessible
	STATUS current
	DESCRIPTION
        "
        List of rm10010e40MonupRmonPacketsCounterClientInput
        Article
        "
	::= { rm10010e40MonClientRmonCounter 48 }


rm10010e40MonupRmonPacketsCounterClientInputEntry OBJECT-TYPE
	SYNTAX Rm10010e40MonupRmonPacketsCounterClientInputEntry
	MAX-ACCESS not-accessible
	STATUS current
	DESCRIPTION
        "
        Row definition for the rm10010e40MonupRmonPacketsCounterClientInput
        table
        "
	INDEX   { rm10010e40MonupRmonPacketsCounterClientInputIndex }
	::= { rm10010e40MonupRmonPacketsCounterClientInputTable 1 }


Rm10010e40MonupRmonPacketsCounterClientInputEntry ::=
	SEQUENCE {
	rm10010e40MonupRmonPacketsCounterClientInputIndex
		INTEGER,
	rm10010e40MonupRmonPacketsCounterClientInputValuePortn
		Counter64,
	rm10010e40MonupRmonPacketsCounterClientInputErrorPortn
		EkiOnOff,
	rm10010e40MonupRmonPacketsCounterClientInputOverloadPortn
		EkiOnOff
	}


rm10010e40MonupRmonPacketsCounterClientInputIndex OBJECT-TYPE
	SYNTAX  INTEGER(0..128)
	MAX-ACCESS  read-only
	STATUS current
	DESCRIPTION
        "
        Index definition for the rm10010e40MonupRmonPacketsCounterClientInput
        table
        "
	::= { rm10010e40MonupRmonPacketsCounterClientInputEntry 1 }


rm10010e40MonupRmonPacketsCounterClientInputValuePortn OBJECT-TYPE
	SYNTAX  Counter64
	MAX-ACCESS read-only
	STATUS current
	DESCRIPTION
        "
        Client Input Packets :This counter
        is increased each time a packet
        is received on the client port
          <Help>  This counter gives the
        number of packets received on the
        client port
        "
	::= { rm10010e40MonupRmonPacketsCounterClientInputEntry 2 }


rm10010e40MonupRmonPacketsCounterClientInputErrorPortn OBJECT-TYPE
	SYNTAX  EkiOnOff
	MAX-ACCESS read-only
	STATUS current
	DESCRIPTION
        "
        Packets Counter Error :This OID
        when set indicates the Packets
         counter value is invalid on client
        port
        "
	::= { rm10010e40MonupRmonPacketsCounterClientInputEntry 3 }


rm10010e40MonupRmonPacketsCounterClientInputOverloadPortn OBJECT-TYPE
	SYNTAX  EkiOnOff
	MAX-ACCESS read-only
	STATUS current
	DESCRIPTION
        "
        Packets Counter Overload :This
        OID when set indicates a Packets
        counter overload on client port
        "
	::= { rm10010e40MonupRmonPacketsCounterClientInputEntry 4 }


--- *********************************************************
---     TABLE for the rm10010e40MonupRmonBroadcastCounterClientInput articles
--- *********************************************************

rm10010e40MonupRmonBroadcastCounterClientInputTable OBJECT-TYPE
	SYNTAX  SEQUENCE OF Rm10010e40MonupRmonBroadcastCounterClientInputEntry
	MAX-ACCESS not-accessible
	STATUS current
	DESCRIPTION
        "
        List of rm10010e40MonupRmonBroadcastCounterClientInput
        Article
        "
	::= { rm10010e40MonClientRmonCounter 64 }


rm10010e40MonupRmonBroadcastCounterClientInputEntry OBJECT-TYPE
	SYNTAX Rm10010e40MonupRmonBroadcastCounterClientInputEntry
	MAX-ACCESS not-accessible
	STATUS current
	DESCRIPTION
        "
        Row definition for the rm10010e40MonupRmonBroadcastCounterClientInput
        table
        "
	INDEX   { rm10010e40MonupRmonBroadcastCounterClientInputIndex }
	::= { rm10010e40MonupRmonBroadcastCounterClientInputTable 1 }


Rm10010e40MonupRmonBroadcastCounterClientInputEntry ::=
	SEQUENCE {
	rm10010e40MonupRmonBroadcastCounterClientInputIndex
		INTEGER,
	rm10010e40MonupRmonBroadcastCounterClientInputValuePortn
		Counter64,
	rm10010e40MonupRmonBroadcastCounterClientInputErrorPortn
		EkiOnOff,
	rm10010e40MonupRmonBroadcastCounterClientInputOverloadPortn
		EkiOnOff
	}


rm10010e40MonupRmonBroadcastCounterClientInputIndex OBJECT-TYPE
	SYNTAX  INTEGER(0..128)
	MAX-ACCESS  read-only
	STATUS current
	DESCRIPTION
        "
        Index definition for the rm10010e40MonupRmonBroadcastCounterClientInput
        table
        "
	::= { rm10010e40MonupRmonBroadcastCounterClientInputEntry 1 }


rm10010e40MonupRmonBroadcastCounterClientInputValuePortn OBJECT-TYPE
	SYNTAX  Counter64
	MAX-ACCESS read-only
	STATUS current
	DESCRIPTION
        "
        Client Input Broadcast Packets
        :This counter is increased each
        time a broadcast packet is received
        on the client port  <Help>  This
        counter gives the number of Broadcast
        packets received on the client
         port
        "
	::= { rm10010e40MonupRmonBroadcastCounterClientInputEntry 2 }


rm10010e40MonupRmonBroadcastCounterClientInputErrorPortn OBJECT-TYPE
	SYNTAX  EkiOnOff
	MAX-ACCESS read-only
	STATUS current
	DESCRIPTION
        "
        Broadcast Counter Error :This
         OID when set indicates the Broadcast
        counter value is invalid on client
        port
        "
	::= { rm10010e40MonupRmonBroadcastCounterClientInputEntry 3 }


rm10010e40MonupRmonBroadcastCounterClientInputOverloadPortn OBJECT-TYPE
	SYNTAX  EkiOnOff
	MAX-ACCESS read-only
	STATUS current
	DESCRIPTION
        "
        Broadcast Counter Overload :This
        OID when set indicates a Broadcast
        counter overload on client port
        "
	::= { rm10010e40MonupRmonBroadcastCounterClientInputEntry 4 }


--- *********************************************************
---     TABLE for the rm10010e40MonupRmonMulticastCounterClientInput articles
--- *********************************************************

rm10010e40MonupRmonMulticastCounterClientInputTable OBJECT-TYPE
	SYNTAX  SEQUENCE OF Rm10010e40MonupRmonMulticastCounterClientInputEntry
	MAX-ACCESS not-accessible
	STATUS current
	DESCRIPTION
        "
        List of rm10010e40MonupRmonMulticastCounterClientInput
        Article
        "
	::= { rm10010e40MonClientRmonCounter 80 }


rm10010e40MonupRmonMulticastCounterClientInputEntry OBJECT-TYPE
	SYNTAX Rm10010e40MonupRmonMulticastCounterClientInputEntry
	MAX-ACCESS not-accessible
	STATUS current
	DESCRIPTION
        "
        Row definition for the rm10010e40MonupRmonMulticastCounterClientInput
        table
        "
	INDEX   { rm10010e40MonupRmonMulticastCounterClientInputIndex }
	::= { rm10010e40MonupRmonMulticastCounterClientInputTable 1 }


Rm10010e40MonupRmonMulticastCounterClientInputEntry ::=
	SEQUENCE {
	rm10010e40MonupRmonMulticastCounterClientInputIndex
		INTEGER,
	rm10010e40MonupRmonMulticastCounterClientInputValuePortn
		Counter64,
	rm10010e40MonupRmonMulticastCounterClientInputErrorPortn
		EkiOnOff,
	rm10010e40MonupRmonMulticastCounterClientInputOverloadPortn
		EkiOnOff
	}


rm10010e40MonupRmonMulticastCounterClientInputIndex OBJECT-TYPE
	SYNTAX  INTEGER(0..128)
	MAX-ACCESS  read-only
	STATUS current
	DESCRIPTION
        "
        Index definition for the rm10010e40MonupRmonMulticastCounterClientInput
        table
        "
	::= { rm10010e40MonupRmonMulticastCounterClientInputEntry 1 }


rm10010e40MonupRmonMulticastCounterClientInputValuePortn OBJECT-TYPE
	SYNTAX  Counter64
	MAX-ACCESS read-only
	STATUS current
	DESCRIPTION
        "
        Client Input Multicast Packets
        :This counter is increased each
        time a Multicast packet is received
        on the client port  <Help>  This
        counter gives the number of Multicast
        packets received on the client
         port
        "
	::= { rm10010e40MonupRmonMulticastCounterClientInputEntry 2 }


rm10010e40MonupRmonMulticastCounterClientInputErrorPortn OBJECT-TYPE
	SYNTAX  EkiOnOff
	MAX-ACCESS read-only
	STATUS current
	DESCRIPTION
        "
        Multicast Counter Error :This
         OID when set indicates the Multicast
        counter value is invalid on client
        port
        "
	::= { rm10010e40MonupRmonMulticastCounterClientInputEntry 3 }


rm10010e40MonupRmonMulticastCounterClientInputOverloadPortn OBJECT-TYPE
	SYNTAX  EkiOnOff
	MAX-ACCESS read-only
	STATUS current
	DESCRIPTION
        "
        Multicast Counter Overload :This
        OID when set indicates a Multicast
        counter overload on client port
        "
	::= { rm10010e40MonupRmonMulticastCounterClientInputEntry 4 }


--- *********************************************************
---     TABLE for the rm10010e40MonupRmonPauseFrameCounterClientInput articles
--- *********************************************************

rm10010e40MonupRmonPauseFrameCounterClientInputTable OBJECT-TYPE
	SYNTAX  SEQUENCE OF Rm10010e40MonupRmonPauseFrameCounterClientInputEntry
	MAX-ACCESS not-accessible
	STATUS current
	DESCRIPTION
        "
        List of rm10010e40MonupRmonPauseFrameCounterClientInput
        Article
        "
	::= { rm10010e40MonClientRmonCounter 96 }


rm10010e40MonupRmonPauseFrameCounterClientInputEntry OBJECT-TYPE
	SYNTAX Rm10010e40MonupRmonPauseFrameCounterClientInputEntry
	MAX-ACCESS not-accessible
	STATUS current
	DESCRIPTION
        "
        Row definition for the rm10010e40MonupRmonPauseFrameCounterClientInput
        table
        "
	INDEX   { rm10010e40MonupRmonPauseFrameCounterClientInputIndex }
	::= { rm10010e40MonupRmonPauseFrameCounterClientInputTable 1 }


Rm10010e40MonupRmonPauseFrameCounterClientInputEntry ::=
	SEQUENCE {
	rm10010e40MonupRmonPauseFrameCounterClientInputIndex
		INTEGER,
	rm10010e40MonupRmonPauseFrameCounterClientInputValuePortn
		Counter64,
	rm10010e40MonupRmonPauseFrameCounterClientInputErrorPortn
		EkiOnOff,
	rm10010e40MonupRmonPauseFrameCounterClientInputOverloadPortn
		EkiOnOff
	}


rm10010e40MonupRmonPauseFrameCounterClientInputIndex OBJECT-TYPE
	SYNTAX  INTEGER(0..128)
	MAX-ACCESS  read-only
	STATUS current
	DESCRIPTION
        "
        Index definition for the rm10010e40MonupRmonPauseFrameCounterClientInput
        table
        "
	::= { rm10010e40MonupRmonPauseFrameCounterClientInputEntry 1 }


rm10010e40MonupRmonPauseFrameCounterClientInputValuePortn OBJECT-TYPE
	SYNTAX  Counter64
	MAX-ACCESS read-only
	STATUS current
	DESCRIPTION
        "
        Client Input Pause Frames :This
        counter is increased each time
         a Pause frame is received on the
        client port  <Help>  This counter
        gives the number of Pause frames
        received on the client port
        "
	::= { rm10010e40MonupRmonPauseFrameCounterClientInputEntry 2 }


rm10010e40MonupRmonPauseFrameCounterClientInputErrorPortn OBJECT-TYPE
	SYNTAX  EkiOnOff
	MAX-ACCESS read-only
	STATUS current
	DESCRIPTION
        "
        Pause Counter Error :This OID
         when set indicates the Pause counter
        value is invalid on client port
        "
	::= { rm10010e40MonupRmonPauseFrameCounterClientInputEntry 3 }


rm10010e40MonupRmonPauseFrameCounterClientInputOverloadPortn OBJECT-TYPE
	SYNTAX  EkiOnOff
	MAX-ACCESS read-only
	STATUS current
	DESCRIPTION
        "
        Pause Counter Overload :This OID
        when set indicates a Pause counter
        overload on client port
        "
	::= { rm10010e40MonupRmonPauseFrameCounterClientInputEntry 4 }







--- *****************************************************
--- $$$$$$$$$$$$$$$$$$$$$$$$$$$$$$$$$$$$$$$$$$$$$$$$$$$$$
---     MEASURES
--- $$$$$$$$$$$$$$$$$$$$$$$$$$$$$$$$$$$$$$$$$$$$$$$$$$$$$
--- *****************************************************



rm10010e40Mesrsynth0 OBJECT-TYPE
	  SYNTAX EkiMeasureType
	  MAX-ACCESS read-only
	  STATUS deprecated
	  DESCRIPTION
        "
        Not Used :
        "
	  ::= { rm10010e40MesrOther 0 }



rm10010e40Mesrsynth1 OBJECT-TYPE
	  SYNTAX EkiMeasureType
	  MAX-ACCESS read-only
	  STATUS deprecated
	  DESCRIPTION
        "
        Not Used :
        "
	  ::= { rm10010e40MesrOther 1 }



--- *****************************************************
---     LEAF for the pmIntervalNumber article
--- *****************************************************

rm10010e40MesrpmIntervalNumber OBJECT-TYPE
	  SYNTAX Unsigned32 (0..65535)
	  MAX-ACCESS read-only
	  STATUS current
	  DESCRIPTION
        "
        PM Interval Counter :
        "
	  ::= { rm10010e40MesrOther 7 }



--- *****************************************************
---     LEAF for the clientCfpTemp article
--- *****************************************************

rm10010e40MesrclientCfpTemp OBJECT-TYPE
	  SYNTAX Unsigned32 (0..65535)
	  MAX-ACCESS read-only
	  STATUS current
	  DESCRIPTION
        "
        Client Trscv Temperature :This
        OID gives the temperature value
        of the Client Transceiver, read
        from the DDM (Digital Diagnostic
        Monitoring) (Temperature = AV/256)
        (Unit = C) <Help> This Measure
         gives the temperature value of
        the Client Transceiver
        "
	  ::= { rm10010e40MesrClient 8 }



--- *****************************************************
---     LEAF for the clientCfp3v3Voltage article
--- *****************************************************

rm10010e40MesrclientCfp3v3Voltage OBJECT-TYPE
	  SYNTAX Unsigned32 (0..65535)
	  MAX-ACCESS read-only
	  STATUS current
	  DESCRIPTION
        "
        Client Trscv Voltage :This OID
        gives the 3V3 voltage value of
         the Client Transceiver, read from
        the DDM (Digital Diagnostic Monitoring)
         (Voltage = AV/1000) (Unit = V)
        <Help> This Measure gives the 3V3
        voltage value of the Client Transceiver
        "
	  ::= { rm10010e40MesrClient 9 }



--- *****************************************************
---     LEAF for the clientSoaBiasCurrent article
--- *****************************************************

rm10010e40MesrclientSoaBiasCurrent OBJECT-TYPE
	  SYNTAX Unsigned32 (0..65535)
	  MAX-ACCESS read-only
	  STATUS current
	  DESCRIPTION
        "
        Client Trscv SOA Bias :This OID
        gives the SOA bias value of the
        Client Transceiver, read from the
        DDM (Digital Diagnostic Monitoring)
         (Bias = AV/500) (Unit = mA) <Help>
        This Measure gives the SOA bias
        value of the Client Transceiver
        "
	  ::= { rm10010e40MesrClient 10 }



--- *****************************************************
---     LEAF for the lineMsaTemp article
--- *****************************************************

rm10010e40MesrlineMsaTemp OBJECT-TYPE
	  SYNTAX Unsigned32 (0..65535)
	  MAX-ACCESS read-only
	  STATUS current
	  DESCRIPTION
        "
        Line Trscv Temperature :This OID
        gives the temperature value of
         the Line Transceiver, read from
        the DDM (Digital Diagnostic Monitoring)
         (Temperature = AV/256) (Unit =
        C) <Help> This Measure gives the
        temperature value of the Line Transceiver
        "
	  ::= { rm10010e40MesrLine 12 }



--- *****************************************************
---     LEAF for the lineMsa3v3Voltage article
--- *****************************************************

rm10010e40MesrlineMsa3v3Voltage OBJECT-TYPE
	  SYNTAX Unsigned32 (0..65535)
	  MAX-ACCESS read-only
	  STATUS current
	  DESCRIPTION
        "
        Line Trscv Voltage :This OID gives
        the 3V3 voltage value of the Line
        Transceiver, read from the DDM
         (Digital Diagnostic Monitoring)
        (Voltage = AV/1000) (Unit = V)
         <Help> This Measure gives the
         3V3 voltage value of the Line
         Transceiver
        "
	  ::= { rm10010e40MesrLine 13 }



--- *****************************************************
---     LEAF for the lineSoaBiasCurrent article
--- *****************************************************

rm10010e40MesrlineSoaBiasCurrent OBJECT-TYPE
	  SYNTAX Unsigned32 (0..65535)
	  MAX-ACCESS read-only
	  STATUS current
	  DESCRIPTION
        "
        Line Trscv SOA Bias :This OID
         gives the SOA bias value of the
        Line Transceiver,read from the
         DDM (Digital Diagnostic Monitoring)
         (Bias = AV/500) (Unit = mA) <Help>
        This Measure gives the SOA bias
        value of the Line Transceiver
        "
	  ::= { rm10010e40MesrLine 14 }



--- *********************************************************
---     TABLE for the rm10010e40MesrclientNetTxTemp articles
--- *********************************************************

rm10010e40MesrclientNetTxTempTable OBJECT-TYPE
	SYNTAX  SEQUENCE OF Rm10010e40MesrclientNetTxTempEntry
	MAX-ACCESS not-accessible
	STATUS current
	DESCRIPTION
        "
        List of rm10010e40MesrclientNetTxTemp
        Article
        "
	::= { rm10010e40MesrClient 16 }


rm10010e40MesrclientNetTxTempEntry OBJECT-TYPE
	SYNTAX Rm10010e40MesrclientNetTxTempEntry
	MAX-ACCESS not-accessible
	STATUS current
	DESCRIPTION
        "
        Row definition for the rm10010e40MesrclientNetTxTemp
        table
        "
	INDEX   { rm10010e40MesrclientNetTxTempIndex }
	::= { rm10010e40MesrclientNetTxTempTable 1 }


Rm10010e40MesrclientNetTxTempEntry ::=
	SEQUENCE {
	rm10010e40MesrclientNetTxTempIndex
		INTEGER,
	rm10010e40MesrclientNetTxTempPortn
		INTEGER
	}


rm10010e40MesrclientNetTxTempIndex OBJECT-TYPE
	SYNTAX  INTEGER(0..128)
	MAX-ACCESS  read-only
	STATUS current
	DESCRIPTION
        "
        Index definition for the rm10010e40MesrclientNetTxTemp
        table
        "
	::= { rm10010e40MesrclientNetTxTempEntry 1 }


rm10010e40MesrclientNetTxTempPortn OBJECT-TYPE
	SYNTAX  INTEGER (0..65535)
	MAX-ACCESS read-only
	STATUS current
	DESCRIPTION
        "
        Client Trscv Temperature :This
        OID gives the Laser temperature
        value of the Client Transceiver,
        read from the DDM (Digital Diagnostic
        Monitoring) (Temperature = AV/256)
        (Unit = C) <Help> This Measure
         gives the Laser temperature value
        of the Client Transceiver
        "
	::= { rm10010e40MesrclientNetTxTempEntry 2 }


--- *********************************************************
---     TABLE for the rm10010e40MesrclientNetTxBias articles
--- *********************************************************

rm10010e40MesrclientNetTxBiasTable OBJECT-TYPE
	SYNTAX  SEQUENCE OF Rm10010e40MesrclientNetTxBiasEntry
	MAX-ACCESS not-accessible
	STATUS current
	DESCRIPTION
        "
        List of rm10010e40MesrclientNetTxBias
        Article
        "
	::= { rm10010e40MesrClient 32 }


rm10010e40MesrclientNetTxBiasEntry OBJECT-TYPE
	SYNTAX Rm10010e40MesrclientNetTxBiasEntry
	MAX-ACCESS not-accessible
	STATUS current
	DESCRIPTION
        "
        Row definition for the rm10010e40MesrclientNetTxBias
        table
        "
	INDEX   { rm10010e40MesrclientNetTxBiasIndex }
	::= { rm10010e40MesrclientNetTxBiasTable 1 }


Rm10010e40MesrclientNetTxBiasEntry ::=
	SEQUENCE {
	rm10010e40MesrclientNetTxBiasIndex
		INTEGER,
	rm10010e40MesrclientNetTxBiasPortn
		INTEGER
	}


rm10010e40MesrclientNetTxBiasIndex OBJECT-TYPE
	SYNTAX  INTEGER(0..128)
	MAX-ACCESS  read-only
	STATUS current
	DESCRIPTION
        "
        Index definition for the rm10010e40MesrclientNetTxBias
        table
        "
	::= { rm10010e40MesrclientNetTxBiasEntry 1 }


rm10010e40MesrclientNetTxBiasPortn OBJECT-TYPE
	SYNTAX  INTEGER (0..65535)
	MAX-ACCESS read-only
	STATUS current
	DESCRIPTION
        "
        Client Trscv Laser Bias :This
         OID gives the Laser bias value
        of the Client Transceiver, read
        from the DDM (Digital Diagnostic
        Monitoring) (Bias = AV/500) (Unit
        = mA) <Help> This Measure gives
        the Laser bias value of the Client
        Transceiver
        "
	::= { rm10010e40MesrclientNetTxBiasEntry 2 }


--- *********************************************************
---     TABLE for the rm10010e40MesrclientNetTxPwr articles
--- *********************************************************

rm10010e40MesrclientNetTxPwrTable OBJECT-TYPE
	SYNTAX  SEQUENCE OF Rm10010e40MesrclientNetTxPwrEntry
	MAX-ACCESS not-accessible
	STATUS current
	DESCRIPTION
        "
        List of rm10010e40MesrclientNetTxPwr
        Article
        "
	::= { rm10010e40MesrClient 48 }


rm10010e40MesrclientNetTxPwrEntry OBJECT-TYPE
	SYNTAX Rm10010e40MesrclientNetTxPwrEntry
	MAX-ACCESS not-accessible
	STATUS current
	DESCRIPTION
        "
        Row definition for the rm10010e40MesrclientNetTxPwr
        table
        "
	INDEX   { rm10010e40MesrclientNetTxPwrIndex }
	::= { rm10010e40MesrclientNetTxPwrTable 1 }


Rm10010e40MesrclientNetTxPwrEntry ::=
	SEQUENCE {
	rm10010e40MesrclientNetTxPwrIndex
		INTEGER,
	rm10010e40MesrclientNetTxPwrPortn
		INTEGER
	}


rm10010e40MesrclientNetTxPwrIndex OBJECT-TYPE
	SYNTAX  INTEGER(0..128)
	MAX-ACCESS  read-only
	STATUS current
	DESCRIPTION
        "
        Index definition for the rm10010e40MesrclientNetTxPwr
        table
        "
	::= { rm10010e40MesrclientNetTxPwrEntry 1 }


rm10010e40MesrclientNetTxPwrPortn OBJECT-TYPE
	SYNTAX  INTEGER (0..65535)
	MAX-ACCESS read-only
	STATUS current
	DESCRIPTION
        "
        Client Trscv Tx Power :This OID
        gives the transmit power value
         of the Client Transceiver, read
        from the DDM (Digital Diagnostic
        Monitoring) (Power = 10*log(AV)-40)
        (Unit = dBm) <Help> This Measure
        gives the transmit power value
         of the Client Transceiver
        "
	::= { rm10010e40MesrclientNetTxPwrEntry 2 }


--- *********************************************************
---     TABLE for the rm10010e40MesrclientNetRxPwr articles
--- *********************************************************

rm10010e40MesrclientNetRxPwrTable OBJECT-TYPE
	SYNTAX  SEQUENCE OF Rm10010e40MesrclientNetRxPwrEntry
	MAX-ACCESS not-accessible
	STATUS current
	DESCRIPTION
        "
        List of rm10010e40MesrclientNetRxPwr
        Article
        "
	::= { rm10010e40MesrClient 64 }


rm10010e40MesrclientNetRxPwrEntry OBJECT-TYPE
	SYNTAX Rm10010e40MesrclientNetRxPwrEntry
	MAX-ACCESS not-accessible
	STATUS current
	DESCRIPTION
        "
        Row definition for the rm10010e40MesrclientNetRxPwr
        table
        "
	INDEX   { rm10010e40MesrclientNetRxPwrIndex }
	::= { rm10010e40MesrclientNetRxPwrTable 1 }


Rm10010e40MesrclientNetRxPwrEntry ::=
	SEQUENCE {
	rm10010e40MesrclientNetRxPwrIndex
		INTEGER,
	rm10010e40MesrclientNetRxPwrPortn
		INTEGER
	}


rm10010e40MesrclientNetRxPwrIndex OBJECT-TYPE
	SYNTAX  INTEGER(0..128)
	MAX-ACCESS  read-only
	STATUS current
	DESCRIPTION
        "
        Index definition for the rm10010e40MesrclientNetRxPwr
        table
        "
	::= { rm10010e40MesrclientNetRxPwrEntry 1 }


rm10010e40MesrclientNetRxPwrPortn OBJECT-TYPE
	SYNTAX  INTEGER (0..65535)
	MAX-ACCESS read-only
	STATUS current
	DESCRIPTION
        "
        Client Trscv Rx Power :This OID
        gives the receive power value of
        the Client Transceiver, read in
        the DDM (Digital Diagnostic Monitoring)
        (Power = 10*log(AV)-40) (Unit =
        dBm) <Help> This Measure gives
         the receive power value of the
        Client Transceiver
        "
	::= { rm10010e40MesrclientNetRxPwrEntry 2 }


--- *********************************************************
---     TABLE for the rm10010e40MesrlineNetTxLaserOutputPwr articles
--- *********************************************************

rm10010e40MesrlineNetTxLaserOutputPwrTable OBJECT-TYPE
	SYNTAX  SEQUENCE OF Rm10010e40MesrlineNetTxLaserOutputPwrEntry
	MAX-ACCESS not-accessible
	STATUS current
	DESCRIPTION
        "
        List of rm10010e40MesrlineNetTxLaserOutputPwr
        Article
        "
	::= { rm10010e40MesrLine 80 }


rm10010e40MesrlineNetTxLaserOutputPwrEntry OBJECT-TYPE
	SYNTAX Rm10010e40MesrlineNetTxLaserOutputPwrEntry
	MAX-ACCESS not-accessible
	STATUS current
	DESCRIPTION
        "
        Row definition for the rm10010e40MesrlineNetTxLaserOutputPwr
        table
        "
	INDEX   { rm10010e40MesrlineNetTxLaserOutputPwrIndex }
	::= { rm10010e40MesrlineNetTxLaserOutputPwrTable 1 }


Rm10010e40MesrlineNetTxLaserOutputPwrEntry ::=
	SEQUENCE {
	rm10010e40MesrlineNetTxLaserOutputPwrIndex
		INTEGER,
	rm10010e40MesrlineNetTxLaserOutputPwrPortn
		INTEGER
	}


rm10010e40MesrlineNetTxLaserOutputPwrIndex OBJECT-TYPE
	SYNTAX  INTEGER(0..128)
	MAX-ACCESS  read-only
	STATUS current
	DESCRIPTION
        "
        Index definition for the rm10010e40MesrlineNetTxLaserOutputPwr
        table
        "
	::= { rm10010e40MesrlineNetTxLaserOutputPwrEntry 1 }


rm10010e40MesrlineNetTxLaserOutputPwrPortn OBJECT-TYPE
	SYNTAX  INTEGER (0..65535)
	MAX-ACCESS read-only
	STATUS current
	DESCRIPTION
        "
        Current Line Trscv Tx Power :This
        OID gives the Tx Laser transmit
        power value of the Line Transceiver,
        read in the DDM (Digital Diagnostic
        Monitoring) (Power = AV/100) (Unit
        = dBm) <Help> This Measure gives
        the Tx Laser transmit power value
        of the Line Transceiver
        "
	::= { rm10010e40MesrlineNetTxLaserOutputPwrEntry 2 }


--- *********************************************************
---     TABLE for the rm10010e40MesrlineNetTxLaserTemp articles
--- *********************************************************

rm10010e40MesrlineNetTxLaserTempTable OBJECT-TYPE
	SYNTAX  SEQUENCE OF Rm10010e40MesrlineNetTxLaserTempEntry
	MAX-ACCESS not-accessible
	STATUS current
	DESCRIPTION
        "
        List of rm10010e40MesrlineNetTxLaserTemp
        Article
        "
	::= { rm10010e40MesrLine 96 }


rm10010e40MesrlineNetTxLaserTempEntry OBJECT-TYPE
	SYNTAX Rm10010e40MesrlineNetTxLaserTempEntry
	MAX-ACCESS not-accessible
	STATUS current
	DESCRIPTION
        "
        Row definition for the rm10010e40MesrlineNetTxLaserTemp
        table
        "
	INDEX   { rm10010e40MesrlineNetTxLaserTempIndex }
	::= { rm10010e40MesrlineNetTxLaserTempTable 1 }


Rm10010e40MesrlineNetTxLaserTempEntry ::=
	SEQUENCE {
	rm10010e40MesrlineNetTxLaserTempIndex
		INTEGER,
	rm10010e40MesrlineNetTxLaserTempPortn
		INTEGER
	}


rm10010e40MesrlineNetTxLaserTempIndex OBJECT-TYPE
	SYNTAX  INTEGER(0..128)
	MAX-ACCESS  read-only
	STATUS current
	DESCRIPTION
        "
        Index definition for the rm10010e40MesrlineNetTxLaserTemp
        table
        "
	::= { rm10010e40MesrlineNetTxLaserTempEntry 1 }


rm10010e40MesrlineNetTxLaserTempPortn OBJECT-TYPE
	SYNTAX  INTEGER (0..65535)
	MAX-ACCESS read-only
	STATUS current
	DESCRIPTION
        "
        Current Line Trscv Tx Laser Temperature
        :This OID gives the Tx Laser Temperature
        value of the Line Transceiver,
         read from the DDM (Digital Diagnostic
        Monitoring) (Temperature = AV/256)
        (Unit = C) <Help> This Measure
         gives the Tx Laser Temperature
        value of the Line Transceiver
        "
	::= { rm10010e40MesrlineNetTxLaserTempEntry 2 }


--- *********************************************************
---     TABLE for the rm10010e40MesrlineNetTxBiasCurrent articles
--- *********************************************************

rm10010e40MesrlineNetTxBiasCurrentTable OBJECT-TYPE
	SYNTAX  SEQUENCE OF Rm10010e40MesrlineNetTxBiasCurrentEntry
	MAX-ACCESS not-accessible
	STATUS current
	DESCRIPTION
        "
        List of rm10010e40MesrlineNetTxBiasCurrent
        Article
        "
	::= { rm10010e40MesrLine 112 }


rm10010e40MesrlineNetTxBiasCurrentEntry OBJECT-TYPE
	SYNTAX Rm10010e40MesrlineNetTxBiasCurrentEntry
	MAX-ACCESS not-accessible
	STATUS current
	DESCRIPTION
        "
        Row definition for the rm10010e40MesrlineNetTxBiasCurrent
        table
        "
	INDEX   { rm10010e40MesrlineNetTxBiasCurrentIndex }
	::= { rm10010e40MesrlineNetTxBiasCurrentTable 1 }


Rm10010e40MesrlineNetTxBiasCurrentEntry ::=
	SEQUENCE {
	rm10010e40MesrlineNetTxBiasCurrentIndex
		INTEGER,
	rm10010e40MesrlineNetTxBiasCurrentPortn
		INTEGER
	}


rm10010e40MesrlineNetTxBiasCurrentIndex OBJECT-TYPE
	SYNTAX  INTEGER(0..128)
	MAX-ACCESS  read-only
	STATUS current
	DESCRIPTION
        "
        Index definition for the rm10010e40MesrlineNetTxBiasCurrent
        table
        "
	::= { rm10010e40MesrlineNetTxBiasCurrentEntry 1 }


rm10010e40MesrlineNetTxBiasCurrentPortn OBJECT-TYPE
	SYNTAX  INTEGER (0..65535)
	MAX-ACCESS read-only
	STATUS current
	DESCRIPTION
        "
        Current Line Trscv Tx Laser Bias
        :This OID gives the Tx Laser Bias
        value of the Line Transceiver,
         read from the DDM (Digital Diagnostic
        Monitoring) (Bias = AV/10) (Unit
        = mA) <Help> This Measure gives
        the Tx Laser Bias value of the
         Line Transceiver
        "
	::= { rm10010e40MesrlineNetTxBiasCurrentEntry 2 }


--- *********************************************************
---     TABLE for the rm10010e40MesrlineNetRxInputPwr articles
--- *********************************************************

rm10010e40MesrlineNetRxInputPwrTable OBJECT-TYPE
	SYNTAX  SEQUENCE OF Rm10010e40MesrlineNetRxInputPwrEntry
	MAX-ACCESS not-accessible
	STATUS current
	DESCRIPTION
        "
        List of rm10010e40MesrlineNetRxInputPwr
        Article
        "
	::= { rm10010e40MesrLine 128 }


rm10010e40MesrlineNetRxInputPwrEntry OBJECT-TYPE
	SYNTAX Rm10010e40MesrlineNetRxInputPwrEntry
	MAX-ACCESS not-accessible
	STATUS current
	DESCRIPTION
        "
        Row definition for the rm10010e40MesrlineNetRxInputPwr
        table
        "
	INDEX   { rm10010e40MesrlineNetRxInputPwrIndex }
	::= { rm10010e40MesrlineNetRxInputPwrTable 1 }


Rm10010e40MesrlineNetRxInputPwrEntry ::=
	SEQUENCE {
	rm10010e40MesrlineNetRxInputPwrIndex
		INTEGER,
	rm10010e40MesrlineNetRxInputPwrPortn
		INTEGER
	}


rm10010e40MesrlineNetRxInputPwrIndex OBJECT-TYPE
	SYNTAX  INTEGER(0..128)
	MAX-ACCESS  read-only
	STATUS current
	DESCRIPTION
        "
        Index definition for the rm10010e40MesrlineNetRxInputPwr
        table
        "
	::= { rm10010e40MesrlineNetRxInputPwrEntry 1 }


rm10010e40MesrlineNetRxInputPwrPortn OBJECT-TYPE
	SYNTAX  INTEGER (0..65535)
	MAX-ACCESS read-only
	STATUS current
	DESCRIPTION
        "
        Current Line Trscv Rx Power :This
        OID gives the Receive power value
        of the Line Transceiver, read in
        the DDM (Digital Diagnostic Monitoring)
        (Power = AV/100) (Unit = dBm) <Help>
        This Measure gives the Receive
         power value of the Line Transceiver
        "
	::= { rm10010e40MesrlineNetRxInputPwrEntry 2 }


--- *********************************************************
---     TABLE for the rm10010e40MesrlineResidualChromaticDisp articles
--- *********************************************************

rm10010e40MesrlineResidualChromaticDispTable OBJECT-TYPE
	SYNTAX  SEQUENCE OF Rm10010e40MesrlineResidualChromaticDispEntry
	MAX-ACCESS not-accessible
	STATUS current
	DESCRIPTION
        "
        List of rm10010e40MesrlineResidualChromaticDisp
        Article
        "
	::= { rm10010e40MesrLine 144 }


rm10010e40MesrlineResidualChromaticDispEntry OBJECT-TYPE
	SYNTAX Rm10010e40MesrlineResidualChromaticDispEntry
	MAX-ACCESS not-accessible
	STATUS current
	DESCRIPTION
        "
        Row definition for the rm10010e40MesrlineResidualChromaticDisp
        table
        "
	INDEX   { rm10010e40MesrlineResidualChromaticDispIndex }
	::= { rm10010e40MesrlineResidualChromaticDispTable 1 }


Rm10010e40MesrlineResidualChromaticDispEntry ::=
	SEQUENCE {
	rm10010e40MesrlineResidualChromaticDispIndex
		INTEGER,
	rm10010e40MesrlineResidualChromaticDispPortn
		INTEGER
	}


rm10010e40MesrlineResidualChromaticDispIndex OBJECT-TYPE
	SYNTAX  INTEGER(0..128)
	MAX-ACCESS  read-only
	STATUS current
	DESCRIPTION
        "
        Index definition for the rm10010e40MesrlineResidualChromaticDisp
        table
        "
	::= { rm10010e40MesrlineResidualChromaticDispEntry 1 }


rm10010e40MesrlineResidualChromaticDispPortn OBJECT-TYPE
	SYNTAX  INTEGER (0..65535)
	MAX-ACCESS read-only
	STATUS current
	DESCRIPTION
        "
        Current Residual Chromatic Dispersion
        :This OID gives the current Residual
        Chromatic Dispersion on the Line
        interface  (Unit = ps/nm)<Help>
        This measure gives the current
         Residual Chromatic Dispersion
         on the Line interface.
        "
	::= { rm10010e40MesrlineResidualChromaticDispEntry 2 }


--- *********************************************************
---     TABLE for the rm10010e40MesrlineDiffGroupDelay articles
--- *********************************************************

rm10010e40MesrlineDiffGroupDelayTable OBJECT-TYPE
	SYNTAX  SEQUENCE OF Rm10010e40MesrlineDiffGroupDelayEntry
	MAX-ACCESS not-accessible
	STATUS current
	DESCRIPTION
        "
        List of rm10010e40MesrlineDiffGroupDelay
        Article
        "
	::= { rm10010e40MesrLine 148 }


rm10010e40MesrlineDiffGroupDelayEntry OBJECT-TYPE
	SYNTAX Rm10010e40MesrlineDiffGroupDelayEntry
	MAX-ACCESS not-accessible
	STATUS current
	DESCRIPTION
        "
        Row definition for the rm10010e40MesrlineDiffGroupDelay
        table
        "
	INDEX   { rm10010e40MesrlineDiffGroupDelayIndex }
	::= { rm10010e40MesrlineDiffGroupDelayTable 1 }


Rm10010e40MesrlineDiffGroupDelayEntry ::=
	SEQUENCE {
	rm10010e40MesrlineDiffGroupDelayIndex
		INTEGER,
	rm10010e40MesrlineDiffGroupDelayPortn
		INTEGER
	}


rm10010e40MesrlineDiffGroupDelayIndex OBJECT-TYPE
	SYNTAX  INTEGER(0..128)
	MAX-ACCESS  read-only
	STATUS current
	DESCRIPTION
        "
        Index definition for the rm10010e40MesrlineDiffGroupDelay
        table
        "
	::= { rm10010e40MesrlineDiffGroupDelayEntry 1 }


rm10010e40MesrlineDiffGroupDelayPortn OBJECT-TYPE
	SYNTAX  INTEGER (0..65535)
	MAX-ACCESS read-only
	STATUS current
	DESCRIPTION
        "
        Current Differential Group Delay
        :This OID gives the current Differential
        Group Delay on the Line interface
          (Unit = ps)<Help> This measure
        gives the current Differential
         Group Delay on the Line interface.
        "
	::= { rm10010e40MesrlineDiffGroupDelayEntry 2 }


--- *********************************************************
---     TABLE for the rm10010e40MesrlineQFactor articles
--- *********************************************************

rm10010e40MesrlineQFactorTable OBJECT-TYPE
	SYNTAX  SEQUENCE OF Rm10010e40MesrlineQFactorEntry
	MAX-ACCESS not-accessible
	STATUS current
	DESCRIPTION
        "
        List of rm10010e40MesrlineQFactor
        Article
        "
	::= { rm10010e40MesrLine 152 }


rm10010e40MesrlineQFactorEntry OBJECT-TYPE
	SYNTAX Rm10010e40MesrlineQFactorEntry
	MAX-ACCESS not-accessible
	STATUS current
	DESCRIPTION
        "
        Row definition for the rm10010e40MesrlineQFactor
        table
        "
	INDEX   { rm10010e40MesrlineQFactorIndex }
	::= { rm10010e40MesrlineQFactorTable 1 }


Rm10010e40MesrlineQFactorEntry ::=
	SEQUENCE {
	rm10010e40MesrlineQFactorIndex
		INTEGER,
	rm10010e40MesrlineQFactorPortn
		INTEGER
	}


rm10010e40MesrlineQFactorIndex OBJECT-TYPE
	SYNTAX  INTEGER(0..128)
	MAX-ACCESS  read-only
	STATUS current
	DESCRIPTION
        "
        Index definition for the rm10010e40MesrlineQFactor
        table
        "
	::= { rm10010e40MesrlineQFactorEntry 1 }


rm10010e40MesrlineQFactorPortn OBJECT-TYPE
	SYNTAX  INTEGER (0..65535)
	MAX-ACCESS read-only
	STATUS current
	DESCRIPTION
        "
        Current Q Factor :This OID gives
        the current Q Factor on the Line
        interface   (Unit = dB) <Help>
         This measure gives the current
        Q Factor on the Line interface.
        "
	::= { rm10010e40MesrlineQFactorEntry 2 }


--- *********************************************************
---     TABLE for the rm10010e40MesrlineCarrierFreqOffset articles
--- *********************************************************

rm10010e40MesrlineCarrierFreqOffsetTable OBJECT-TYPE
	SYNTAX  SEQUENCE OF Rm10010e40MesrlineCarrierFreqOffsetEntry
	MAX-ACCESS not-accessible
	STATUS current
	DESCRIPTION
        "
        List of rm10010e40MesrlineCarrierFreqOffset
        Article
        "
	::= { rm10010e40MesrLine 156 }


rm10010e40MesrlineCarrierFreqOffsetEntry OBJECT-TYPE
	SYNTAX Rm10010e40MesrlineCarrierFreqOffsetEntry
	MAX-ACCESS not-accessible
	STATUS current
	DESCRIPTION
        "
        Row definition for the rm10010e40MesrlineCarrierFreqOffset
        table
        "
	INDEX   { rm10010e40MesrlineCarrierFreqOffsetIndex }
	::= { rm10010e40MesrlineCarrierFreqOffsetTable 1 }


Rm10010e40MesrlineCarrierFreqOffsetEntry ::=
	SEQUENCE {
	rm10010e40MesrlineCarrierFreqOffsetIndex
		INTEGER,
	rm10010e40MesrlineCarrierFreqOffsetPortn
		INTEGER
	}


rm10010e40MesrlineCarrierFreqOffsetIndex OBJECT-TYPE
	SYNTAX  INTEGER(0..128)
	MAX-ACCESS  read-only
	STATUS current
	DESCRIPTION
        "
        Index definition for the rm10010e40MesrlineCarrierFreqOffset
        table
        "
	::= { rm10010e40MesrlineCarrierFreqOffsetEntry 1 }


rm10010e40MesrlineCarrierFreqOffsetPortn OBJECT-TYPE
	SYNTAX  INTEGER (0..65535)
	MAX-ACCESS read-only
	STATUS current
	DESCRIPTION
        "
        Current Carrier Frequency Offset
        :This OID gives the current Carrier
        Frequency Offset on the Line interface
          (Unit = Mhz)<Help> This measure
        gives the current Carrier Frequency
        Offset on the Line interface.
        "
	::= { rm10010e40MesrlineCarrierFreqOffsetEntry 2 }


--- *********************************************************
---     TABLE for the rm10010e40MesrlineOsnr articles
--- *********************************************************

rm10010e40MesrlineOsnrTable OBJECT-TYPE
	SYNTAX  SEQUENCE OF Rm10010e40MesrlineOsnrEntry
	MAX-ACCESS not-accessible
	STATUS current
	DESCRIPTION
        "
        List of rm10010e40MesrlineOsnr
        Article
        "
	::= { rm10010e40MesrLine 160 }


rm10010e40MesrlineOsnrEntry OBJECT-TYPE
	SYNTAX Rm10010e40MesrlineOsnrEntry
	MAX-ACCESS not-accessible
	STATUS current
	DESCRIPTION
        "
        Row definition for the rm10010e40MesrlineOsnr
        table
        "
	INDEX   { rm10010e40MesrlineOsnrIndex }
	::= { rm10010e40MesrlineOsnrTable 1 }


Rm10010e40MesrlineOsnrEntry ::=
	SEQUENCE {
	rm10010e40MesrlineOsnrIndex
		INTEGER,
	rm10010e40MesrlineOsnrPortn
		INTEGER
	}


rm10010e40MesrlineOsnrIndex OBJECT-TYPE
	SYNTAX  INTEGER(0..128)
	MAX-ACCESS  read-only
	STATUS current
	DESCRIPTION
        "
        Index definition for the rm10010e40MesrlineOsnr
        table
        "
	::= { rm10010e40MesrlineOsnrEntry 1 }


rm10010e40MesrlineOsnrPortn OBJECT-TYPE
	SYNTAX  INTEGER (0..65535)
	MAX-ACCESS read-only
	STATUS current
	DESCRIPTION
        "
        Current OSNR :This OID gives the
        current OSNR on the Line interface
          (OSNR = AV/10) (Unit = dB) <Help>
        This measure gives the current
         OSNR on the Line interface.
        "
	::= { rm10010e40MesrlineOsnrEntry 2 }


--- *****************************************************
---     LEAF for the lineNetTxLaserOutputPwrAverage article
--- *****************************************************

rm10010e40MesrlineNetTxLaserOutputPwrAverage OBJECT-TYPE
	  SYNTAX Unsigned32 (0..65535)
	  MAX-ACCESS read-only
	  STATUS current
	  DESCRIPTION
        "
        Average Line Trscv Tx Power :This
        OID gives the average Tx Laser
         transmit power value among the
        network lanes of the Line Transceiver,
        read in the DDM (Digital Diagnostic
        Monitoring)  (Power = AV/100) (Unit
        = dBm) (Unit = dBm) <Help> This
        Measure gives the average Tx Laser
        transmit power value among the
         network lanes of the Line Transceiver
        "
	  ::= { rm10010e40MesrOther 180 }



--- *****************************************************
---     LEAF for the lineNetTxLaserTempAverage article
--- *****************************************************

rm10010e40MesrlineNetTxLaserTempAverage OBJECT-TYPE
	  SYNTAX Unsigned32 (0..65535)
	  MAX-ACCESS read-only
	  STATUS current
	  DESCRIPTION
        "
        Average Line Trscv Tx Laser Temperature
        :This OID gives the average Tx
         Laser Temperature value among
         the network lanes of the Line
         Transceiver, read from the DDM
        (Digital Diagnostic Monitoring)
        (Temperature = AV/256) (Unit =
         C) <Help> This Measure gives the
        average Tx Laser Temperature value
        among the network lanes of the
         Line Transceiver
        "
	  ::= { rm10010e40MesrOther 181 }



--- *****************************************************
---     LEAF for the lineNetTxBiasCurrentAverage article
--- *****************************************************

rm10010e40MesrlineNetTxBiasCurrentAverage OBJECT-TYPE
	  SYNTAX Unsigned32 (0..65535)
	  MAX-ACCESS read-only
	  STATUS current
	  DESCRIPTION
        "
        Average Line Trscv Tx Laser Bias
        :This OID gives the average Tx
         Laser Bias value among the network
        lanes of the Line Transceiver,
         read from the DDM (Digital Diagnostic
        Monitoring) (Bias = AV/10) (Unit
        = mA) <Help> This Measure gives
        the average Tx Laser Bias value
        among the network lanes of the
         Line Transceiver
        "
	  ::= { rm10010e40MesrOther 182 }



--- *****************************************************
---     LEAF for the lineNetRxInputPwrAverage article
--- *****************************************************

rm10010e40MesrlineNetRxInputPwrAverage OBJECT-TYPE
	  SYNTAX Unsigned32 (0..65535)
	  MAX-ACCESS read-only
	  STATUS current
	  DESCRIPTION
        "
        Average Line Trscv Rx Power :This
        OID gives the average Receive power
        value among the network lanes of
        the Line Transceiver, read in the
        DDM (Digital Diagnostic Monitoring)
        (Power = AV/100) (Unit = dBm) <Help>
        This Measure gives the average
         Receive power value among the
         network lanes of the Line Transceiver
        "
	  ::= { rm10010e40MesrOther 183 }



--- *****************************************************
---     LEAF for the lineResidualChromaticDispAverage article
--- *****************************************************

rm10010e40MesrlineResidualChromaticDispAverage OBJECT-TYPE
	  SYNTAX Unsigned32 (0..65535)
	  MAX-ACCESS read-only
	  STATUS current
	  DESCRIPTION
        "
        Average Residual Chromatic Dispersion
        :This OID gives the average Residual
        Chromatic Dispersion on the Line
        interface since the last measure
        reset <Help> This measure gives
        the average Residual Chromatic
         Dispersion on the Line interface
        since the last measure reset.
        "
	  ::= { rm10010e40MesrOther 184 }



--- *****************************************************
---     LEAF for the lineDiffGroupDelayAverage article
--- *****************************************************

rm10010e40MesrlineDiffGroupDelayAverage OBJECT-TYPE
	  SYNTAX Unsigned32 (0..65535)
	  MAX-ACCESS read-only
	  STATUS current
	  DESCRIPTION
        "
        Average Differential Group Delay
        :This OID gives the average Group
        Delay on the Line interface since
        the last measure reset <Help> This
        measure gives the average Differential
        Group Delay on the Line interface
        since the last measure reset.
        "
	  ::= { rm10010e40MesrOther 185 }



--- *****************************************************
---     LEAF for the lineQFactorAverage article
--- *****************************************************

rm10010e40MesrlineQFactorAverage OBJECT-TYPE
	  SYNTAX Unsigned32 (0..65535)
	  MAX-ACCESS read-only
	  STATUS current
	  DESCRIPTION
        "
        Average Q Factor :This OID gives
        the average Q Factor on the Line
        interface since the last measure
        reset <Help> This measure gives
        the average Q Factor on the Line
        interface since the last measure
        reset.
        "
	  ::= { rm10010e40MesrOther 186 }



--- *****************************************************
---     LEAF for the lineCarrierFreqOffsetAverage article
--- *****************************************************

rm10010e40MesrlineCarrierFreqOffsetAverage OBJECT-TYPE
	  SYNTAX Unsigned32 (0..65535)
	  MAX-ACCESS read-only
	  STATUS current
	  DESCRIPTION
        "
        Average Carrier Frequency Offset
        :This OID gives the average Carrier
        Frequency Offset on the Line interface
        since the last measure reset <Help>
        This measure gives the average
         Carrier Frequency Offset on the
        Line interface since the last measure
        reset
        "
	  ::= { rm10010e40MesrOther 187 }



--- *****************************************************
---     LEAF for the lineOsnrAverage article
--- *****************************************************

rm10010e40MesrlineOsnrAverage OBJECT-TYPE
	  SYNTAX Unsigned32 (0..65535)
	  MAX-ACCESS read-only
	  STATUS current
	  DESCRIPTION
        "
        Average OSNR :This OID gives the
        average OSNR on the Line interface
        since the last measure reset <Help>
        This measure gives the average
         OSNR on the Line interface since
        the last measure reset.
        "
	  ::= { rm10010e40MesrOther 188 }



--- *****************************************************
---     LEAF for the clientNetTxTempMin article
--- *****************************************************

rm10010e40MesrclientNetTxTempMin OBJECT-TYPE
	  SYNTAX Unsigned32 (0..65535)
	  MAX-ACCESS read-only
	  STATUS current
	  DESCRIPTION
        "
        Min Client Trscv Laser Temperature
        :This OID gives the minimum Laser
        temperature value among the network
        lanes of the Client Transceiver,
        read from the DDM (Digital Diagnostic
        Monitoring) (Temperature = AV/256)
        (Unit = C) <Help> This Measure
         gives the minimum Laser temperature
        value among the network lanes of
        the Client Transceiver
        "
	  ::= { rm10010e40MesrOther 192 }



--- *****************************************************
---     LEAF for the clientNetTxBiasMin article
--- *****************************************************

rm10010e40MesrclientNetTxBiasMin OBJECT-TYPE
	  SYNTAX Unsigned32 (0..65535)
	  MAX-ACCESS read-only
	  STATUS current
	  DESCRIPTION
        "
        Min Client Trscv Laser Bias :This
        OID gives the minimum Laser bias
        value among the network lanes of
        the Client Transceiver, read from
        the DDM (Digital Diagnostic Monitoring)
        (Bias = AV/500) (Unit = mA) <Help>
        This Measure gives the minimum
         Laser bias value among the network
        lanes of the Client Transceiver
        "
	  ::= { rm10010e40MesrOther 193 }



--- *****************************************************
---     LEAF for the clientNetTxPwrMin article
--- *****************************************************

rm10010e40MesrclientNetTxPwrMin OBJECT-TYPE
	  SYNTAX Unsigned32 (0..65535)
	  MAX-ACCESS read-only
	  STATUS current
	  DESCRIPTION
        "
        Min Client Trscv Tx Power :This
        OID gives the minimum transmit
         power value among the network
         lanes of the Client Transceiver,
        read from the DDM (Digital Diagnostic
        Monitoring) (Power = 10*log(AV)-40)
        (Unit = dBm) <Help> This Measure
        gives the minimum transmit power
        value among the network lanes of
        the Client Transceiver
        "
	  ::= { rm10010e40MesrOther 194 }



--- *****************************************************
---     LEAF for the clientNetRxPwrMin article
--- *****************************************************

rm10010e40MesrclientNetRxPwrMin OBJECT-TYPE
	  SYNTAX Unsigned32 (0..65535)
	  MAX-ACCESS read-only
	  STATUS current
	  DESCRIPTION
        "
        Min Client Trscv Rx Power :This
        OID gives the minimum receive power
        value among the network lanes of
        the Client Transceiver, read in
        the DDM (Digital Diagnostic Monitoring)
        (Power = 10*log(AV)-40) (Unit =
        dBm) <Help> This Measure gives
         the minimum receive power value
        among the network lanes of the
         Client Transceiver
        "
	  ::= { rm10010e40MesrOther 195 }



--- *****************************************************
---     LEAF for the lineNetTxLaserOutputPwrMin article
--- *****************************************************

rm10010e40MesrlineNetTxLaserOutputPwrMin OBJECT-TYPE
	  SYNTAX Unsigned32 (0..65535)
	  MAX-ACCESS read-only
	  STATUS current
	  DESCRIPTION
        "
        Min Line Trscv Tx Power :This
         OID gives the minimum Tx Laser
        transmit power value among the
         network lanes of the Line Transceiver,
        read in the DDM (Digital Diagnostic
        Monitoring)  (Power = AV/100) (Unit
        = dBm) (Unit = dBm) <Help> This
        Measure gives the minimum Tx Laser
        transmit power value among the
         network lanes of the Line Transceiver
        "
	  ::= { rm10010e40MesrOther 196 }



--- *****************************************************
---     LEAF for the lineNetTxLaserTempMin article
--- *****************************************************

rm10010e40MesrlineNetTxLaserTempMin OBJECT-TYPE
	  SYNTAX Unsigned32 (0..65535)
	  MAX-ACCESS read-only
	  STATUS current
	  DESCRIPTION
        "
        Min Line Trscv Tx Laser Temperature
        :This OID gives the minimum Tx
         Laser Temperature value among
         the network lanes of the Line
         Transceiver, read from the DDM
        (Digital Diagnostic Monitoring)
        (Temperature = AV/256) (Unit =
         C) <Help> This Measure gives the
        minimum Tx Laser Temperature value
        among the network lanes of the
         Line Transceiver
        "
	  ::= { rm10010e40MesrOther 197 }



--- *****************************************************
---     LEAF for the lineNetTxBiasCurrentMin article
--- *****************************************************

rm10010e40MesrlineNetTxBiasCurrentMin OBJECT-TYPE
	  SYNTAX Unsigned32 (0..65535)
	  MAX-ACCESS read-only
	  STATUS current
	  DESCRIPTION
        "
        Min Line Trscv Tx Laser Bias :This
        OID gives the minimum Tx Laser
         Bias value among the network lanes
        of the Line Transceiver, read from
        the DDM (Digital Diagnostic Monitoring)
        (Bias = AV/10) (Unit = mA) <Help>
        This Measure gives the minimum
         Tx Laser Bias value among the
         network lanes of the Line Transceiver
        "
	  ::= { rm10010e40MesrOther 198 }



--- *****************************************************
---     LEAF for the lineNetRxInputPwrMin article
--- *****************************************************

rm10010e40MesrlineNetRxInputPwrMin OBJECT-TYPE
	  SYNTAX Unsigned32 (0..65535)
	  MAX-ACCESS read-only
	  STATUS current
	  DESCRIPTION
        "
        Min Line Trscv Rx Power :This
         OID gives the minimum Receive
         power value among the network
         lanes of the Line Transceiver,
        read in the DDM (Digital Diagnostic
        Monitoring) (Power = AV/100) (Unit
        = dBm) <Help> This Measure gives
        the minimum Receive power value
        among the network lanes of the
         Line Transceiver
        "
	  ::= { rm10010e40MesrOther 199 }



--- *****************************************************
---     LEAF for the lineResidualChromaticDispMin article
--- *****************************************************

rm10010e40MesrlineResidualChromaticDispMin OBJECT-TYPE
	  SYNTAX Unsigned32 (0..65535)
	  MAX-ACCESS read-only
	  STATUS current
	  DESCRIPTION
        "
        Min Residual Chromatic Dispersion
        :This OID gives the minimum Residual
        Chromatic Dispersion on the Line
        interface since the last measure
        reset  (Unit = ps/nm)<Help> This
        measure gives the minimum Residual
        Chromatic Dispersion on the Line
        interface since the last measure
        reset.
        "
	  ::= { rm10010e40MesrOther 200 }



--- *****************************************************
---     LEAF for the lineDiffGroupDelayMin article
--- *****************************************************

rm10010e40MesrlineDiffGroupDelayMin OBJECT-TYPE
	  SYNTAX Unsigned32 (0..65535)
	  MAX-ACCESS read-only
	  STATUS current
	  DESCRIPTION
        "
        Min Differential Group Delay :This
        OID gives the minimum Differential
        Group Delay  on the Line interface
        since the last measure reset  (Unit
        = ps)<Help> This measure gives
         the minimum Differential Group
        Delay on the Line interface since
        the last measure reset.
        "
	  ::= { rm10010e40MesrOther 201 }



--- *****************************************************
---     LEAF for the lineQFactorMin article
--- *****************************************************

rm10010e40MesrlineQFactorMin OBJECT-TYPE
	  SYNTAX Unsigned32 (0..65535)
	  MAX-ACCESS read-only
	  STATUS current
	  DESCRIPTION
        "
        Min Q Factor :This OID gives the
        minimum Q Factor on the Line interface
        since the last measure reset  (Unit
        = dB)<Help> This measure gives
         the minimum Q Factor on the Line
        interface since the last measure
        reset.
        "
	  ::= { rm10010e40MesrOther 202 }



--- *****************************************************
---     LEAF for the lineCarrierFreqOffsetMin article
--- *****************************************************

rm10010e40MesrlineCarrierFreqOffsetMin OBJECT-TYPE
	  SYNTAX Unsigned32 (0..65535)
	  MAX-ACCESS read-only
	  STATUS current
	  DESCRIPTION
        "
        Min Carrier Frequency Offset :This
        OID gives the minimum Carrier Frequency
        Offset on the Line interface since
        the last measure reset  (Unit =
        Mhz)<Help> This measure gives the
        minimum Carrier Frequency Offset
        on the Line interface since the
        last measure reset
        "
	  ::= { rm10010e40MesrOther 203 }



--- *****************************************************
---     LEAF for the lineOsnrMin article
--- *****************************************************

rm10010e40MesrlineOsnrMin OBJECT-TYPE
	  SYNTAX Unsigned32 (0..65535)
	  MAX-ACCESS read-only
	  STATUS current
	  DESCRIPTION
        "
        Min OSNR :This OID gives the minimum
        OSNR on the Line interface since
        the last measure reset  (OSNR =
        AV/10) (Unit = dB)<Help> This measure
        gives the minimum OSNR on the Line
        interface since the last measure
        reset.
        "
	  ::= { rm10010e40MesrOther 204 }



--- *****************************************************
---     LEAF for the clientNetTxTempMax article
--- *****************************************************

rm10010e40MesrclientNetTxTempMax OBJECT-TYPE
	  SYNTAX Unsigned32 (0..65535)
	  MAX-ACCESS read-only
	  STATUS current
	  DESCRIPTION
        "
        Max Client Trscv Laser Temperature
        :This OID gives the maximum Laser
        temperature value among the network
        lanes of the Client Transceiver,
        read from the DDM (Digital Diagnostic
        Monitoring) (Temperature = AV/256)
        (Unit = C) <Help> This Measure
         gives the maximum Laser temperature
        value among the network lanes of
        the Client Transceiver
        "
	  ::= { rm10010e40MesrOther 208 }



--- *****************************************************
---     LEAF for the clientNetTxBiasMax article
--- *****************************************************

rm10010e40MesrclientNetTxBiasMax OBJECT-TYPE
	  SYNTAX Unsigned32 (0..65535)
	  MAX-ACCESS read-only
	  STATUS current
	  DESCRIPTION
        "
        Max Client Trscv Laser Bias :This
        OID gives the maximum Laser bias
        value among the network lanes of
        the Client Transceiver, read from
        the DDM (Digital Diagnostic Monitoring)
        (Bias = AV/500) (Unit = mA) <Help>
        This Measure gives the maximum
         Laser bias value among the network
        lanes of the Client Transceiver
        "
	  ::= { rm10010e40MesrOther 209 }



--- *****************************************************
---     LEAF for the clientNetTxPwrMax article
--- *****************************************************

rm10010e40MesrclientNetTxPwrMax OBJECT-TYPE
	  SYNTAX Unsigned32 (0..65535)
	  MAX-ACCESS read-only
	  STATUS current
	  DESCRIPTION
        "
        Max Client Trscv Tx Power :This
        OID gives the maximum transmit
         power value among the network
         lanes of the Client Transceiver,
        read from the DDM (Digital Diagnostic
        Monitoring) (Power = 10*log(AV)-40)
        (Unit = dBm) <Help> This Measure
        gives the maximum transmit power
        value among the network lanes of
        the Client Transceiver
        "
	  ::= { rm10010e40MesrOther 210 }



--- *****************************************************
---     LEAF for the clientNetRxPwrMax article
--- *****************************************************

rm10010e40MesrclientNetRxPwrMax OBJECT-TYPE
	  SYNTAX Unsigned32 (0..65535)
	  MAX-ACCESS read-only
	  STATUS current
	  DESCRIPTION
        "
        Max Client Trscv Rx Power :This
        OID gives the maximum receive power
        value among the network lanes of
        the Client Transceiver, read in
        the DDM (Digital Diagnostic Monitoring)
        (Power = 10*log(AV)-40) (Unit =
        dBm) <Help> This Measure gives
         the maximum receive power value
        among the network lanes of the
         Client Transceiver
        "
	  ::= { rm10010e40MesrOther 211 }



--- *****************************************************
---     LEAF for the lineNetTxLaserOutputPwrMax article
--- *****************************************************

rm10010e40MesrlineNetTxLaserOutputPwrMax OBJECT-TYPE
	  SYNTAX Unsigned32 (0..65535)
	  MAX-ACCESS read-only
	  STATUS current
	  DESCRIPTION
        "
        Max Line Trscv Tx Power :This
         OID gives the maximum Tx Laser
        transmit power value among the
         network lanes of the Line Transceiver,
        read in the DDM (Digital Diagnostic
        Monitoring) (Power = 10*log(AV)-40)
        (Unit = dBm) <Help> This Measure
        gives the maximum Tx Laser transmit
        power value among the network lanes
        of the Line Transceiver
        "
	  ::= { rm10010e40MesrOther 212 }



--- *****************************************************
---     LEAF for the lineNetTxLaserTempMax article
--- *****************************************************

rm10010e40MesrlineNetTxLaserTempMax OBJECT-TYPE
	  SYNTAX Unsigned32 (0..65535)
	  MAX-ACCESS read-only
	  STATUS current
	  DESCRIPTION
        "
        Max Line Trscv Tx Laser Temperature
        :This OID gives the maximum Tx
         Laser Temperature value among
         the network lanes of the Line
         Transceiver, read from the DDM
        (Digital Diagnostic Monitoring)
        (Temperature = AV/256) (Unit =
         C) <Help> This Measure gives the
        maximum Tx Laser Temperature value
        among the network lanes of the
         Line Transceiver
        "
	  ::= { rm10010e40MesrOther 213 }



--- *****************************************************
---     LEAF for the lineNetTxBiasCurrentMax article
--- *****************************************************

rm10010e40MesrlineNetTxBiasCurrentMax OBJECT-TYPE
	  SYNTAX Unsigned32 (0..65535)
	  MAX-ACCESS read-only
	  STATUS current
	  DESCRIPTION
        "
        Max Line Trscv Tx Laser Bias :This
        OID gives the maximum Tx Laser
         Bias value among the network lanes
        of the Line Transceiver, read from
        the DDM (Digital Diagnostic Monitoring)
        (Bias = AV/10) (Unit = mA) <Help>
        This Measure gives the maximum
         Tx Laser Bias value among the
         network lanes of the Line Transceiver
        "
	  ::= { rm10010e40MesrOther 214 }



--- *****************************************************
---     LEAF for the lineNetRxInputPwrMax article
--- *****************************************************

rm10010e40MesrlineNetRxInputPwrMax OBJECT-TYPE
	  SYNTAX Unsigned32 (0..65535)
	  MAX-ACCESS read-only
	  STATUS current
	  DESCRIPTION
        "
        Max Line Trscv Rx Power :This
         OID gives the maximum Receive
         power value among the network
         lanes of the Line Transceiver,
        read in the DDM (Digital Diagnostic
        Monitoring) (Power = 10*log(AV)-40)
        (Unit = dBm) <Help> This Measure
        gives the maximum Receive power
        value among the network lanes of
        the Line Transceiver
        "
	  ::= { rm10010e40MesrOther 215 }



--- *****************************************************
---     LEAF for the lineResidualChromaticDispMax article
--- *****************************************************

rm10010e40MesrlineResidualChromaticDispMax OBJECT-TYPE
	  SYNTAX Unsigned32 (0..65535)
	  MAX-ACCESS read-only
	  STATUS current
	  DESCRIPTION
        "
        Max Residual Chromatic Dispersion
        :This OID gives the maximum Residual
        Chromatic Dispersion on the Line
        interface since the last measure
        reset  (Unit = ps/nm)<Help> This
        measure gives the maximum Residual
        Chromatic Dispersion on the Line
        interface since the last measure
        reset.
        "
	  ::= { rm10010e40MesrOther 216 }



--- *****************************************************
---     LEAF for the lineDiffGroupDelayMax article
--- *****************************************************

rm10010e40MesrlineDiffGroupDelayMax OBJECT-TYPE
	  SYNTAX Unsigned32 (0..65535)
	  MAX-ACCESS read-only
	  STATUS current
	  DESCRIPTION
        "
        Max Differential Group Delay :This
        OID gives the maximum Differential
        Group Delay  on the Line interface
        since the last measure reset
         (Unit = ps)<Help> This measure
        gives the maximum Differential
         Group Delay on the Line interface
        since the last measure reset.
        "
	  ::= { rm10010e40MesrOther 217 }



--- *****************************************************
---     LEAF for the lineQFactorMax article
--- *****************************************************

rm10010e40MesrlineQFactorMax OBJECT-TYPE
	  SYNTAX Unsigned32 (0..65535)
	  MAX-ACCESS read-only
	  STATUS current
	  DESCRIPTION
        "
        Max Q Factor :This OID gives the
        maximum Q Factor on the Line interface
        since the last measure reset  (Unit
        = dB)<Help> This measure gives
         the maximum Q Factor on the Line
        interface since the last measure
        reset.
        "
	  ::= { rm10010e40MesrOther 218 }



--- *****************************************************
---     LEAF for the lineCarrierFreqOffsetMax article
--- *****************************************************

rm10010e40MesrlineCarrierFreqOffsetMax OBJECT-TYPE
	  SYNTAX Unsigned32 (0..65535)
	  MAX-ACCESS read-only
	  STATUS current
	  DESCRIPTION
        "
        Max Carrier Frequency Offset :This
        OID gives the maximum Carrier Frequency
        Offset on the Line interface since
        the last measure reset   (Unit
         = Mhz)<Help> This measure gives
        the maximum Carrier Frequency Offset
        on the Line interface since the
        last measure reset.
        "
	  ::= { rm10010e40MesrOther 219 }



--- *****************************************************
---     LEAF for the lineOsnrMax article
--- *****************************************************

rm10010e40MesrlineOsnrMax OBJECT-TYPE
	  SYNTAX Unsigned32 (0..65535)
	  MAX-ACCESS read-only
	  STATUS current
	  DESCRIPTION
        "
        Max OSNR :This OID gives the maximum
        OSNR on the Line interface since
        the last measure reset  (OSNR =
        AV/10) (Unit = dB)<Help> This measure
        gives the maximum OSNR on the Line
        interface since the last measure
        reset
        "
	  ::= { rm10010e40MesrOther 220 }








--- *****************************************************
--- $$$$$$$$$$$$$$$$$$$$$$$$$$$$$$$$$$$$$$$$$$$$$$$$$$$$$
---     DOWNLOAD
--- $$$$$$$$$$$$$$$$$$$$$$$$$$$$$$$$$$$$$$$$$$$$$$$$$$$$$
--- *****************************************************



--- *****************************************************
---     LEAF for the restartProcess article
--- *****************************************************
rm10010e40DwlrestartProcess OBJECT IDENTIFIER ::= { rm10010e40DwlOther 0 }




rm10010e40DwlColdRestartProcessed OBJECT-TYPE
	  SYNTAX EkiOnOff
	  MAX-ACCESS read-only
	  STATUS current
	  DESCRIPTION
        "
        Cold Restart :This OID indicates
        that the module last restart was
        a Cold RESTART
        "
	  ::= { rm10010e40DwlrestartProcess 2 }



rm10010e40DwlWarmRestartProcessed OBJECT-TYPE
	  SYNTAX EkiOnOff
	  MAX-ACCESS read-only
	  STATUS current
	  DESCRIPTION
        "
        Warm Restart :This OID indicates
        that the module last restart was
        a Warm RESTART
        "
	  ::= { rm10010e40DwlrestartProcess 1 }



--- *****************************************************
---     LEAF for the swBanksUsed article
--- *****************************************************
rm10010e40DwlswBanksUsed OBJECT IDENTIFIER ::= { rm10010e40DwlOther 1 }




rm10010e40DwlSwBank2Notempty OBJECT-TYPE
	  SYNTAX EkiOnOff
	  MAX-ACCESS read-only
	  STATUS current
	  DESCRIPTION
        "
        SW bank 2 loaded :This OID indicates
        a software is loaded in SW bank
        2  <Help>  This status indicates
        if the SW bank 2 contains SW package
        "
	  ::= { rm10010e40DwlswBanksUsed 6 }



rm10010e40DwlSwBank1Notempty OBJECT-TYPE
	  SYNTAX EkiOnOff
	  MAX-ACCESS read-only
	  STATUS current
	  DESCRIPTION
        "
        SW bank 1 loaded :This OID indicates
        a software is loaded in SW bank
        1  <Help>  This status indicates
        if the SW bank 1 contains SW package
        "
	  ::= { rm10010e40DwlswBanksUsed 5 }



rm10010e40DwlSwBank2Used OBJECT-TYPE
	  SYNTAX EkiOnOff
	  MAX-ACCESS read-only
	  STATUS current
	  DESCRIPTION
        "
        SW bank 2 active :This OID indicates
        the module is working on SW bank
        2  <Help>  This status indicates
        if the SW bank 2 is active or standby
        "
	  ::= { rm10010e40DwlswBanksUsed 2 }



rm10010e40DwlSwBank1Used OBJECT-TYPE
	  SYNTAX EkiOnOff
	  MAX-ACCESS read-only
	  STATUS current
	  DESCRIPTION
        "
        SW bank 1 active :This OID indicates
        the module is working on SW bank
        1  <Help>  This status indicates
        if the SW bank 1 is active or standby
        "
	  ::= { rm10010e40DwlswBanksUsed 1 }



--- *****************************************************
---     LEAF for the gwBanksUsed article
--- *****************************************************
rm10010e40DwlgwBanksUsed OBJECT IDENTIFIER ::= { rm10010e40DwlOther 2 }




rm10010e40DwlGwBank4Notempty OBJECT-TYPE
	  SYNTAX EkiOnOff
	  MAX-ACCESS read-only
	  STATUS current
	  DESCRIPTION
        "
        GW bank 4 loaded :This OID indicates
        a gateware is loaded in GW bank
        4
        "
	  ::= { rm10010e40DwlgwBanksUsed 8 }



rm10010e40DwlGwBank3Notempty OBJECT-TYPE
	  SYNTAX EkiOnOff
	  MAX-ACCESS read-only
	  STATUS current
	  DESCRIPTION
        "
        GW bank 3 loaded :This OID indicates
        a gateware is loaded in GW bank
        3  <Help>  This status indicates
        if the GW bank 3 contains GW package
        "
	  ::= { rm10010e40DwlgwBanksUsed 7 }



rm10010e40DwlGwBank2Notempty OBJECT-TYPE
	  SYNTAX EkiOnOff
	  MAX-ACCESS read-only
	  STATUS current
	  DESCRIPTION
        "
        GW bank 2 loaded :This OID indicates
        a gateware is loaded in GW bank
        2
        "
	  ::= { rm10010e40DwlgwBanksUsed 6 }



rm10010e40DwlGwBank1Notempty OBJECT-TYPE
	  SYNTAX EkiOnOff
	  MAX-ACCESS read-only
	  STATUS current
	  DESCRIPTION
        "
        GW bank 1 loaded :This OID indicates
        a gateware is loaded in GW bank
        1  <Help>  This status indicates
        if the GW bank 1 contains GW package
        "
	  ::= { rm10010e40DwlgwBanksUsed 5 }



rm10010e40DwlGwBank4Used OBJECT-TYPE
	  SYNTAX EkiOnOff
	  MAX-ACCESS read-only
	  STATUS current
	  DESCRIPTION
        "
        GW bank 4 active :This OID indicates
        the module is working on GW bank
        4
        "
	  ::= { rm10010e40DwlgwBanksUsed 4 }



rm10010e40DwlGwBank3Used OBJECT-TYPE
	  SYNTAX EkiOnOff
	  MAX-ACCESS read-only
	  STATUS current
	  DESCRIPTION
        "
        GW bank 3 active :This OID indicates
        the module is working on GW bank
        3  <Help>  This status indicates
        if the GW bank 3 is active or standby
        "
	  ::= { rm10010e40DwlgwBanksUsed 3 }



rm10010e40DwlGwBank2Used OBJECT-TYPE
	  SYNTAX EkiOnOff
	  MAX-ACCESS read-only
	  STATUS current
	  DESCRIPTION
        "
        GW bank 2 active :This OID indicates
        the module is working on GW bank
        2
        "
	  ::= { rm10010e40DwlgwBanksUsed 2 }



rm10010e40DwlGwBank1Used OBJECT-TYPE
	  SYNTAX EkiOnOff
	  MAX-ACCESS read-only
	  STATUS current
	  DESCRIPTION
        "
        GW bank 1 active :This OID indicates
        the module is working on GW bank
        1  <Help>  This status indicates
        if the GW bank 1 is active or standby
        "
	  ::= { rm10010e40DwlgwBanksUsed 1 }








--- *****************************************************
--- $$$$$$$$$$$$$$$$$$$$$$$$$$$$$$$$$$$$$$$$$$$$$$$$$$$$$
---     CONFIG
--- $$$$$$$$$$$$$$$$$$$$$$$$$$$$$$$$$$$$$$$$$$$$$$$$$$$$$
--- *****************************************************



--- *****************************************************
---     LEAF for the table Group accessCAisCsf
--- *****************************************************

rm10010e40CfgAccessCAisCsf OBJECT IDENTIFIER ::= { rm10010e40Config 1 }



--- *****************************************************
---     LEAF for the table 0012
--- *****************************************************

rm10010e40CfgClientcaiscsfTable OBJECT-TYPE
	SYNTAX  SEQUENCE OF Rm10010e40CfgClientcaiscsfEntry
	MAX-ACCESS not-accessible
	STATUS current
	DESCRIPTION
        "
        List of  Article
        "
	::= { rm10010e40CfgAccessCAisCsf 1 }


rm10010e40CfgClientcaiscsfEntry OBJECT-TYPE
	SYNTAX Rm10010e40CfgClientcaiscsfEntry
	MAX-ACCESS not-accessible
	STATUS current
	DESCRIPTION
        "
        Row definition for the accessCAisCsf
        table
        "
	INDEX   { rm10010e40CfgClientcaiscsfIndex }
	::= { rm10010e40CfgClientcaiscsfTable 1 }


Rm10010e40CfgClientcaiscsfEntry ::=
	SEQUENCE {
	rm10010e40CfgClientcaiscsfIndex
		INTEGER,
	rm10010e40CfgReservePortn
		Unsigned32
	}


rm10010e40CfgClientcaiscsfIndex OBJECT-TYPE
	SYNTAX  INTEGER(0..128)
	MAX-ACCESS  read-only
	STATUS current
	DESCRIPTION
        "
        Index definition for the clientcaiscsf
        table
        "
	::= { rm10010e40CfgClientcaiscsfEntry 1 }


rm10010e40CfgReservePortn OBJECT-TYPE
	SYNTAX  Unsigned32 (0..65536)
	MAX-ACCESS read-write
	STATUS current
	DESCRIPTION
        "
        CAIS mode  on Client Port :This
        register enables/disables port
          laser shutdown on CAIS insertion
        condition
        "
	::= { rm10010e40CfgClientcaiscsfEntry 3 }


--- *****************************************************
---     LEAF for the table Group startup
--- *****************************************************

rm10010e40CfgStartup OBJECT IDENTIFIER ::= { rm10010e40Config 2 }



--- *****************************************************
---     LEAF for the table 2110
--- *****************************************************

rm10010e40CfgClientStartupTable OBJECT-TYPE
	SYNTAX  SEQUENCE OF Rm10010e40CfgClientStartupEntry
	MAX-ACCESS not-accessible
	STATUS current
	DESCRIPTION
        "
        List of  Article
        "
	::= { rm10010e40CfgStartup 1 }


rm10010e40CfgClientStartupEntry OBJECT-TYPE
	SYNTAX Rm10010e40CfgClientStartupEntry
	MAX-ACCESS not-accessible
	STATUS current
	DESCRIPTION
        "
        Row definition for the startup
        table
        "
	INDEX   { rm10010e40CfgClientStartupIndex }
	::= { rm10010e40CfgClientStartupTable 1 }


Rm10010e40CfgClientStartupEntry ::=
	SEQUENCE {
	rm10010e40CfgClientStartupIndex
		INTEGER,
	rm10010e40CfgSystConfPortPortn
		Unsigned32,
	rm10010e40CfgNetConfPortPortn
		Unsigned32,
	rm10010e40CfgOptionsPortPortn
		Unsigned32
	}


rm10010e40CfgClientStartupIndex OBJECT-TYPE
	SYNTAX  INTEGER(0..128)
	MAX-ACCESS  read-only
	STATUS current
	DESCRIPTION
        "
        Index definition for the clientStartup
        table
        "
	::= { rm10010e40CfgClientStartupEntry 1 }


rm10010e40CfgSystConfPortPortn OBJECT-TYPE
	SYNTAX  Unsigned32 (0..65536)
	MAX-ACCESS read-write
	STATUS current
	DESCRIPTION
        "
        Default Settings on Client Port
        :This  register configures the
         default initialisation settings
        on the port.
        "
	::= { rm10010e40CfgClientStartupEntry 3 }


rm10010e40CfgNetConfPortPortn OBJECT-TYPE
	SYNTAX  Unsigned32 (0..65536)
	MAX-ACCESS read-write
	STATUS current
	DESCRIPTION
        "
        Default Settings on Client Port
        :This  register configures the
         default initialisation settings
        on the port.
        "
	::= { rm10010e40CfgClientStartupEntry 4 }


rm10010e40CfgOptionsPortPortn OBJECT-TYPE
	SYNTAX  Unsigned32 (0..65536)
	MAX-ACCESS read-write
	STATUS current
	DESCRIPTION
        "
        Default Options on Client Port
        :This register configures the default
        options on the port.
        "
	::= { rm10010e40CfgClientStartupEntry 14 }


--- *****************************************************
---     LEAF for the table 2190
--- *****************************************************

rm10010e40CfgLineStartupTable OBJECT-TYPE
	SYNTAX  SEQUENCE OF Rm10010e40CfgLineStartupEntry
	MAX-ACCESS not-accessible
	STATUS current
	DESCRIPTION
        "
        List of  Article
        "
	::= { rm10010e40CfgStartup 2 }


rm10010e40CfgLineStartupEntry OBJECT-TYPE
	SYNTAX Rm10010e40CfgLineStartupEntry
	MAX-ACCESS not-accessible
	STATUS current
	DESCRIPTION
        "
        Row definition for the startup
        table
        "
	INDEX   { rm10010e40CfgLineStartupIndex }
	::= { rm10010e40CfgLineStartupTable 1 }


Rm10010e40CfgLineStartupEntry ::=
	SEQUENCE {
	rm10010e40CfgLineStartupIndex
		INTEGER,
	rm10010e40CfgSystConfLinePortn
		Unsigned32,
	rm10010e40CfgOptionsLinePortn
		Unsigned32
	}


rm10010e40CfgLineStartupIndex OBJECT-TYPE
	SYNTAX  INTEGER(0..128)
	MAX-ACCESS  read-only
	STATUS current
	DESCRIPTION
        "
        Index definition for the lineStartup
        table
        "
	::= { rm10010e40CfgLineStartupEntry 1 }


rm10010e40CfgSystConfLinePortn OBJECT-TYPE
	SYNTAX  Unsigned32 (0..65536)
	MAX-ACCESS read-write
	STATUS current
	DESCRIPTION
        "
        Default Settings on Line :This
        register configures the default
        initialisation settings on Line
        "
	::= { rm10010e40CfgLineStartupEntry 3 }


rm10010e40CfgOptionsLinePortn OBJECT-TYPE
	SYNTAX  Unsigned32 (0..65536)
	MAX-ACCESS read-write
	STATUS current
	DESCRIPTION
        "
        Default Options on Line :This
         register configures the default
        options on the line
        "
	::= { rm10010e40CfgLineStartupEntry 14 }


--- *****************************************************
---     LEAF for the table 21AB
--- *****************************************************

rm10010e40CfgXfpTable OBJECT-TYPE
	SYNTAX  SEQUENCE OF Rm10010e40CfgXfpEntry
	MAX-ACCESS not-accessible
	STATUS current
	DESCRIPTION
        "
        List of  Article
        "
	::= { rm10010e40CfgStartup 3 }


rm10010e40CfgXfpEntry OBJECT-TYPE
	SYNTAX Rm10010e40CfgXfpEntry
	MAX-ACCESS not-accessible
	STATUS current
	DESCRIPTION
        "
        Row definition for the startup
        table
        "
	INDEX   { rm10010e40CfgXfpIndex }
	::= { rm10010e40CfgXfpTable 1 }


Rm10010e40CfgXfpEntry ::=
	SEQUENCE {
	rm10010e40CfgXfpIndex
		INTEGER,
	rm10010e40CfgSystConfMsaLinePortn
		Unsigned32
	}


rm10010e40CfgXfpIndex OBJECT-TYPE
	SYNTAX  INTEGER(0..128)
	MAX-ACCESS  read-only
	STATUS current
	DESCRIPTION
        "
        Index definition for the xfp table
        "
	::= { rm10010e40CfgXfpEntry 1 }


rm10010e40CfgSystConfMsaLinePortn OBJECT-TYPE
	SYNTAX  Unsigned32 (0..65536)
	MAX-ACCESS read-write
	STATUS current
	DESCRIPTION
        "
        Default settings on MSA :This
         register configures the default
        initialisation settings on MSA
        "
	::= { rm10010e40CfgXfpEntry 3 }


--- *****************************************************
---     LEAF for the table Group labels
--- *****************************************************

rm10010e40CfgLabels OBJECT IDENTIFIER ::= { rm10010e40Config 3 }



--- *****************************************************
---     LEAF for the table 0003
--- *****************************************************

rm10010e40CfgLabelclientTable OBJECT-TYPE
	SYNTAX  SEQUENCE OF Rm10010e40CfgLabelclientEntry
	MAX-ACCESS not-accessible
	STATUS current
	DESCRIPTION
        "
        List of  Article
        "
	::= { rm10010e40CfgLabels 1 }


rm10010e40CfgLabelclientEntry OBJECT-TYPE
	SYNTAX Rm10010e40CfgLabelclientEntry
	MAX-ACCESS not-accessible
	STATUS current
	DESCRIPTION
        "
        Row definition for the labels
         table
        "
	INDEX   { rm10010e40CfgLabelclientIndex }
	::= { rm10010e40CfgLabelclientTable 1 }


Rm10010e40CfgLabelclientEntry ::=
	SEQUENCE {
	rm10010e40CfgLabelclientIndex
		INTEGER,
	rm10010e40CfgLabelclientPortn
		DisplayString
	}


rm10010e40CfgLabelclientIndex OBJECT-TYPE
	SYNTAX  INTEGER(0..128)
	MAX-ACCESS  read-only
	STATUS current
	DESCRIPTION
        "
        Index definition for the labelclient
        table
        "
	::= { rm10010e40CfgLabelclientEntry 1 }


rm10010e40CfgLabelclientPortn OBJECT-TYPE
	SYNTAX  DisplayString( SIZE(1..16))
	MAX-ACCESS read-write
	STATUS current
	DESCRIPTION
        "
        Default settings on the label
         of the Ports :These registers
         configures the default initialisation
        settings of the labels of the ports.
        "
	::= { rm10010e40CfgLabelclientEntry 3 }


--- *****************************************************
---     LEAF for the table 0004
--- *****************************************************

rm10010e40CfgLabellineTable OBJECT-TYPE
	SYNTAX  SEQUENCE OF Rm10010e40CfgLabellineEntry
	MAX-ACCESS not-accessible
	STATUS current
	DESCRIPTION
        "
        List of  Article
        "
	::= { rm10010e40CfgLabels 2 }


rm10010e40CfgLabellineEntry OBJECT-TYPE
	SYNTAX Rm10010e40CfgLabellineEntry
	MAX-ACCESS not-accessible
	STATUS current
	DESCRIPTION
        "
        Row definition for the labels
         table
        "
	INDEX   { rm10010e40CfgLabellineIndex }
	::= { rm10010e40CfgLabellineTable 1 }


Rm10010e40CfgLabellineEntry ::=
	SEQUENCE {
	rm10010e40CfgLabellineIndex
		INTEGER,
	rm10010e40CfgLabellinePortn
		DisplayString
	}


rm10010e40CfgLabellineIndex OBJECT-TYPE
	SYNTAX  INTEGER(0..128)
	MAX-ACCESS  read-only
	STATUS current
	DESCRIPTION
        "
        Index definition for the labelline
        table
        "
	::= { rm10010e40CfgLabellineEntry 1 }


rm10010e40CfgLabellinePortn OBJECT-TYPE
	SYNTAX  DisplayString( SIZE(1..16))
	MAX-ACCESS read-write
	STATUS current
	DESCRIPTION
        "
        Default settings on the label
         of the lines :These registers
         configures the default initialisation
        settings of the labels of the lines.
        "
	::= { rm10010e40CfgLabellineEntry 3 }


--- *****************************************************
---     LEAF for the table Group startuptlh
--- *****************************************************

rm10010e40CfgStartuptlh OBJECT IDENTIFIER ::= { rm10010e40Config 4 }



--- *****************************************************
---     LEAF for the table 25AB
--- *****************************************************

rm10010e40CfgOtxtlhTable OBJECT-TYPE
	SYNTAX  SEQUENCE OF Rm10010e40CfgOtxtlhEntry
	MAX-ACCESS not-accessible
	STATUS current
	DESCRIPTION
        "
        List of  Article
        "
	::= { rm10010e40CfgStartuptlh 1 }


rm10010e40CfgOtxtlhEntry OBJECT-TYPE
	SYNTAX Rm10010e40CfgOtxtlhEntry
	MAX-ACCESS not-accessible
	STATUS current
	DESCRIPTION
        "
        Row definition for the startuptlh
        table
        "
	INDEX   { rm10010e40CfgOtxtlhIndex }
	::= { rm10010e40CfgOtxtlhTable 1 }


Rm10010e40CfgOtxtlhEntry ::=
	SEQUENCE {
	rm10010e40CfgOtxtlhIndex
		INTEGER,
	rm10010e40CfgLinePwrLaserPortn
		Unsigned32,
	rm10010e40CfgLineFCurrentPortn
		Unsigned32,
	rm10010e40CfgLineGridCurrentPortn
		Unsigned32,
	rm10010e40CfgFPortn
		Unsigned32,
	rm10010e40CfgRxLineFCurrentPortn
		Unsigned32
	}


rm10010e40CfgOtxtlhIndex OBJECT-TYPE
	SYNTAX  INTEGER(0..128)
	MAX-ACCESS  read-only
	STATUS current
	DESCRIPTION
        "
        Index definition for the otxtlh
        table
        "
	::= { rm10010e40CfgOtxtlhEntry 1 }


rm10010e40CfgLinePwrLaserPortn OBJECT-TYPE
	SYNTAX  Unsigned32 (0..65536)
	MAX-ACCESS read-write
	STATUS current
	DESCRIPTION
        "
        Defaut Line output Power :This
        register configures the start-up
        output power of the Line tranceiver
         (Unit = dBm)
        "
	::= { rm10010e40CfgOtxtlhEntry 6 }


rm10010e40CfgLineFCurrentPortn OBJECT-TYPE
	SYNTAX  Unsigned32 (0..65536)
	MAX-ACCESS read-write
	STATUS current
	DESCRIPTION
        "
        Default Line transceiver Tx Channel
        :This register configures the start-up
        laser channel of the Line Tx transceiver
        "
	::= { rm10010e40CfgOtxtlhEntry 7 }


rm10010e40CfgLineGridCurrentPortn OBJECT-TYPE
	SYNTAX  Unsigned32 (0..65536)
	MAX-ACCESS read-write
	STATUS current
	DESCRIPTION
        "
        Default Line transceiver Grid
         :This register configures the
         start-up laser grid of the Line
        transceiver
        "
	::= { rm10010e40CfgOtxtlhEntry 8 }


rm10010e40CfgFPortn OBJECT-TYPE
	SYNTAX  Unsigned32 (0..65536)
	MAX-ACCESS read-write
	STATUS current
	DESCRIPTION
        "
        Default Line TRX lowest Freq :This
        register configures the start-up
        lowest frequency of the Line transceiver
        "
	::= { rm10010e40CfgOtxtlhEntry 9 }


rm10010e40CfgRxLineFCurrentPortn OBJECT-TYPE
	SYNTAX  Unsigned32 (0..65536)
	MAX-ACCESS read-write
	STATUS current
	DESCRIPTION
        "
        Default Line transceiver Rx Channel
        :This register configures the start-up
        laser channel of the Line Rx transceiver
        "
	::= { rm10010e40CfgOtxtlhEntry 10 }


--- *****************************************************
---     LEAF for the table Group other
--- *****************************************************

rm10010e40CfgOther OBJECT IDENTIFIER ::= { rm10010e40Config 5 }



--- *****************************************************
---     LEAF for the table 2300
--- *****************************************************

rm10010e40tablemoduleOther OBJECT IDENTIFIER ::= { rm10010e40CfgOther 1 }



rm10010e40Cfgmode OBJECT-TYPE
	  SYNTAX Unsigned32 (0..65536)
	  MAX-ACCESS read-write
	  STATUS current
	  DESCRIPTION
        "
        Default settings on Module :This
        register selects the configuration
        mode of the module
        "
	  ::= { rm10010e40tablemoduleOther 2 }



rm10010e40CfgfanLowSpeedThreshold OBJECT-TYPE
	  SYNTAX Unsigned32 (0..65536)
	  MAX-ACCESS read-write
	  STATUS current
	  DESCRIPTION
        "
        Default settings on Module :This
        register selects the speed threshold
        of the fan's
        "
	  ::= { rm10010e40tablemoduleOther 3 }



rm10010e40CfgfanHighSpeedThreshold OBJECT-TYPE
	  SYNTAX Unsigned32 (0..65536)
	  MAX-ACCESS read-write
	  STATUS current
	  DESCRIPTION
        "
        Default settings on Module :This
        register selects the speed threshold
        of the fan's
        "
	  ::= { rm10010e40tablemoduleOther 4 }



--- *****************************************************
---     LEAF for the table Group startuptablefive
--- *****************************************************

rm10010e40CfgStartuptablefive OBJECT IDENTIFIER ::= { rm10010e40Config 6 }



--- *****************************************************
---     LEAF for the table 0005
--- *****************************************************

rm10010e40CfgOtxtlhcapabilitiesTable OBJECT-TYPE
	SYNTAX  SEQUENCE OF Rm10010e40CfgOtxtlhcapabilitiesEntry
	MAX-ACCESS not-accessible
	STATUS current
	DESCRIPTION
        "
        List of  Article
        "
	::= { rm10010e40CfgStartuptablefive 1 }


rm10010e40CfgOtxtlhcapabilitiesEntry OBJECT-TYPE
	SYNTAX Rm10010e40CfgOtxtlhcapabilitiesEntry
	MAX-ACCESS not-accessible
	STATUS current
	DESCRIPTION
        "
        Row definition for the startuptablefive
        table
        "
	INDEX   { rm10010e40CfgOtxtlhcapabilitiesIndex }
	::= { rm10010e40CfgOtxtlhcapabilitiesTable 1 }


Rm10010e40CfgOtxtlhcapabilitiesEntry ::=
	SEQUENCE {
	rm10010e40CfgOtxtlhcapabilitiesIndex
		INTEGER,
	rm10010e40CfgComponentTypePortn
		Unsigned32,
	rm10010e40CfgMiscellaneousPortn
		Unsigned32,
	rm10010e40CfgFirstChannelPortn
		Unsigned32,
	rm10010e40CfgLastChannelPortn
		Unsigned32,
	rm10010e40CfgGridPortn
		Unsigned32
	}


rm10010e40CfgOtxtlhcapabilitiesIndex OBJECT-TYPE
	SYNTAX  INTEGER(0..128)
	MAX-ACCESS  read-only
	STATUS current
	DESCRIPTION
        "
        Index definition for the otxtlhcapabilities
        table
        "
	::= { rm10010e40CfgOtxtlhcapabilitiesEntry 1 }


rm10010e40CfgComponentTypePortn OBJECT-TYPE
	SYNTAX  Unsigned32 (0..65536)
	MAX-ACCESS read-only
	STATUS current
	DESCRIPTION
        "
        Component parameters :This OID
        defines the component parameters
        "
	::= { rm10010e40CfgOtxtlhcapabilitiesEntry 3 }


rm10010e40CfgMiscellaneousPortn OBJECT-TYPE
	SYNTAX  Unsigned32 (0..65536)
	MAX-ACCESS read-only
	STATUS current
	DESCRIPTION
        "
        Miscellaneous default settings
        :This OID defines the miscellaneous
        parameters
        "
	::= { rm10010e40CfgOtxtlhcapabilitiesEntry 4 }


rm10010e40CfgFirstChannelPortn OBJECT-TYPE
	SYNTAX  Unsigned32 (0..65536)
	MAX-ACCESS read-only
	STATUS current
	DESCRIPTION
        "
        Number of the first channel of
        the component :This OID defines
        the first channel number of the
        PM
        "
	::= { rm10010e40CfgOtxtlhcapabilitiesEntry 5 }


rm10010e40CfgLastChannelPortn OBJECT-TYPE
	SYNTAX  Unsigned32 (0..65536)
	MAX-ACCESS read-only
	STATUS current
	DESCRIPTION
        "
        Number of the last channel of
         the component :This OID defines
        the last channel number of the
         PM
        "
	::= { rm10010e40CfgOtxtlhcapabilitiesEntry 6 }


rm10010e40CfgGridPortn OBJECT-TYPE
	SYNTAX  Unsigned32 (0..65536)
	MAX-ACCESS read-only
	STATUS current
	DESCRIPTION
        "
        Grid value of the component :This
        OID defines the grid of the PM
        "
	::= { rm10010e40CfgOtxtlhcapabilitiesEntry 7 }



rm10010e40CfgWriteConfiguration  OBJECT-TYPE
	SYNTAX EkiOnOff
	MAX-ACCESS read-write
	STATUS current
	DESCRIPTION
	"Write configuration to module:This OID
	 writes the complete configuration to the module"
	::= { rm10010e40Config 257 }






--- *****************************************************
---     TRAP OBJECTS
--- *****************************************************

rm10010e40trapPortNumber OBJECT-TYPE
	SYNTAX INTEGER(1..64)
	MAX-ACCESS read-only
	STATUS current
	DESCRIPTION
	"Last port which generates a trap"
	::= { rm10010e40traps 2 }

rm10010e40trapLineNumber OBJECT-TYPE
	SYNTAX INTEGER(1..64)
	MAX-ACCESS read-only
	STATUS current
	DESCRIPTION
	"Last Line which generates a trap"
	::= { rm10010e40traps 3 }

rm10010e40trapBoardNumber OBJECT-TYPE
	SYNTAX INTEGER(1..64)
	MAX-ACCESS read-only
	STATUS current
	DESCRIPTION
	"Last module which generates a trap"
	::= { rm10010e40traps 4 }







--- *****************************************************
---     LINE TRAPS
--- *****************************************************

rm10010e40LineTrapNotUrgentGoesOn NOTIFICATION-TYPE
	OBJECTS {rm10010e40AlmLineDdmWarningPortn, rm10010e40trapLineNumber, rm10010e40trapBoardNumber}
	STATUS current
	--&FILTNAME    "RM10010E40 Line Not Urgent ON"
	--&ACTIONS     { log, minor }
	--&MATCH       { rm10010e40AlmLineDdmWarningPortn "on", rm10010e40trapLineNumber "$2", rm10010e40trapBoardNumber "$3"}
	--&MESG        "DDM Warning appears on Line Port $2 of RM10010E40 in Slot $3 ($A)"
	DESCRIPTION "Not urgent Line default is activated"
	::= { rm10010e40traps 30 }

rm10010e40LineTrapNotUrgentGoesOff NOTIFICATION-TYPE
	OBJECTS {rm10010e40AlmLineDdmWarningPortn, rm10010e40trapLineNumber, rm10010e40trapBoardNumber}
	STATUS current
	--&FILTNAME    "RM10010E40 Line Not Urgent OFF"
	--&ACTIONS     { log, normal }
	--&CLEARS      { "RM10010E40 Line Not Urgent ON" }
	--&MATCH       { rm10010e40AlmLineDdmWarningPortn "on", rm10010e40trapLineNumber "$2", rm10010e40trapBoardNumber "$3"}
	--&MESG        "DDM Warning disappears on Line Port $2 of RM10010E40 in Slot $3 ($A)"
	DESCRIPTION "Not urgent Line default disappeared"
	::= { rm10010e40traps 31 }

rm10010e40LineTrapUrgentGoesOn NOTIFICATION-TYPE
	OBJECTS {rm10010e40AlmLineDdmAlmPortn, rm10010e40trapLineNumber, rm10010e40trapBoardNumber}
	STATUS current
	--&FILTNAME    "RM10010E40 Line Urgent ON"
	--&ACTIONS     { log, major }
	--&MATCH       { rm10010e40AlmLineDdmAlE40Portn "on", rm10010e40trapLineNumber "$2", rm10010e40trapBoardNumber "$3"}
	--&MESG        "DDM Alarm appears on Line Port $2 of RM10010E40 in Slot $3 ($A)"
	DESCRIPTION "Urgent Line default is activated"
	::= { rm10010e40traps 32 }

rm10010e40LineTrapUrgentGoesOff NOTIFICATION-TYPE
	OBJECTS {rm10010e40AlmLineDdmAlmPortn, rm10010e40trapLineNumber, rm10010e40trapBoardNumber}
	STATUS current
	--&FILTNAME    "RM10010E40 Line Urgent OFF"
	--&ACTIONS     { log, normal }
	--&CLEARS      { "RM10010E40 Line Urgent ON" }
	--&MATCH       { rm10010e40AlmLineDdmAlE40Portn "on", rm10010e40trapLineNumber "$2", rm10010e40trapBoardNumber "$3"}
	--&MESG        "DDM Alarm disappears on Line Port $2 of RM10010E40 in Slot $3 ($A)"
	DESCRIPTION "Urgent Line default disappeared"
	::= { rm10010e40traps 33 }

rm10010e40LineTrapCritGoesOn NOTIFICATION-TYPE
	OBJECTS {rm10010e40AlmLineFailPortn , rm10010e40AlmLineHwFailPortn , rm10010e40trapLineNumber, rm10010e40trapBoardNumber}
	STATUS current
	--&FILTNAME    "RM10010E40 Line Fail ON"
	--&ACTIONS     { log, critical }
	--&MATCH       { rm10010e40AlmLineFailPortn "on", rm10010e40AlmLineHwFailPortn "*", rm10010e40trapLineNumber "$3", rm10010e40trapBoardNumber "$4"}
	--&MESG        "Line Port $3 Down on RM10010E40 in Slot $4 ($A)"

	--&FILTNAME    "RM10010E40 Line HW Fail ON (Hidden)"
	--&ACTIONS     { info }
	--&MATCH       { rm10010e40AlmLineFailPortn "*", rm10010e40AlmLineHwFailPortn "on", rm10010e40trapLineNumber "$3", rm10010e40trapBoardNumber "$4"}
	--&MESG        "Line Port $3 Down on RM10010E40 in Slot $4 ($A)"
	DESCRIPTION "Critical Line default is activated"
	::= { rm10010e40traps 34 }

rm10010e40LineTrapCritGoesOff NOTIFICATION-TYPE
	OBJECTS {rm10010e40AlmLineFailPortn , rm10010e40AlmLineHwFailPortn , rm10010e40trapLineNumber, rm10010e40trapBoardNumber}
	STATUS current
	--&FILTNAME    "RM10010E40 Line Fail OFF"
	--&ACTIONS     { log,  normal }
	--&CLEARS      { "RM10010E40 Line Fail ON" }
	--&MATCH       { rm10010e40AlmLineFailPortn "on", rm10010e40AlmLineHwFailPortn "*", rm10010e40trapLineNumber "$3", rm10010e40trapBoardNumber "$4"}
	--&MESG        "Line Port $3 Up on RM10010E40 in Slot $4 ($A)"

	--&FILTNAME    "RM10010E40 Line HW Fail OFF (Hidden)"
	--&ACTIONS     { info }
	--&MATCH       { rm10010e40AlmLineFailPortn "*", rm10010e40AlmLineHwFailPortn "on", rm10010e40trapLineNumber "$3", rm10010e40trapBoardNumber "$4"}
	--&MESG        "Line Port $3 Up on RM10010E40 in Slot $4 ($A)"
	DESCRIPTION "Critical Line default disappeared"
	::= { rm10010e40traps 35 }






--- *****************************************************
---     CLIENT TRAPS
--- *****************************************************

rm10010e40ClientTrapNotUrgentGoesOn NOTIFICATION-TYPE
	OBJECTS {rm10010e40AlmSfpDdmWarningPortn, rm10010e40trapPortNumber, rm10010e40trapBoardNumber}
	STATUS current
		--&FILTNAME    "RM10010E40 Client Not Urgent ON"
		--&ACTIONS     { log, minor }
		--&MATCH       { rm10010e40AlmSfpDdmWarningPortn "on", rm10010e40trapPortNumber "$2", rm10010e40trapBoardNumber "$3"}
		--&MESG        "DDM Warning appears on Client Port $2 of RM10010E40 in Slot $3 ($A)"
	DESCRIPTION "Not urgent client default is activated"
	::= { rm10010e40traps 40 }

rm10010e40ClientTrapNotUrgentGoesOff NOTIFICATION-TYPE
	OBJECTS {rm10010e40AlmSfpDdmWarningPortn, rm10010e40trapPortNumber, rm10010e40trapBoardNumber}
	STATUS current
		--&FILTNAME    "RM10010E40 Client Not Urgent OFF"
		--&ACTIONS     { log, normal }
		--&CLEARS      { "RM10010E40 Client Not Urgent ON" }
		--&MATCH       { rm10010e40AlmSfpDdmWarningPortn "on", rm10010e40trapPortNumber "$2", rm10010e40trapBoardNumber "$3"}
		--&MESG        "DDM Warning appears on Client Port $2 of RM10010E40 in Slot $3 ($A)"
	DESCRIPTION "Not urgent client default disappeared"
	::= { rm10010e40traps 41 }

rm10010e40ClientTrapUrgentGoesOn NOTIFICATION-TYPE
	OBJECTS {rm10010e40AlmSfpDdmAlmPortn, rm10010e40trapPortNumber, rm10010e40trapBoardNumber}
	STATUS current
		--&FILTNAME    "RM10010E40 Client Urgent ON"
		--&ACTIONS     { log, major }
		--&MATCH       { rm10010e40AlmSfpDdmAlE40Portn "on", rm10010e40trapPortNumber "$2", rm10010e40trapBoardNumber "$3"}
		--&MESG        "DDM Alarm appears on Client Port $2 of RM10010E40 in Slot $3 ($A)"
	DESCRIPTION "Urgent client default is activated"
	::= { rm10010e40traps 42 }

rm10010e40ClientTrapUrgentGoesOff NOTIFICATION-TYPE
	OBJECTS {rm10010e40AlmSfpDdmAlmPortn, rm10010e40trapPortNumber, rm10010e40trapBoardNumber}
	STATUS current
		--&FILTNAME    "RM10010E40 Client Urgent OFF"
		--&ACTIONS     { log, normal }
		--&CLEARS      { "RM10010E40 Client Urgent ON" }
		--&MATCH       { rm10010e40AlmSfpDdmAlE40Portn "on", rm10010e40trapPortNumber "$2", rm10010e40trapBoardNumber "$3"}
		--&MESG        "DDM Alarm disappears on Client Port $2 of RM10010E40 in Slot $3 ($A)"
	DESCRIPTION "Urgent client default disappeared"
	::= { rm10010e40traps 43 }

rm10010e40ClientTrapCritGoesOn NOTIFICATION-TYPE
	OBJECTS {rm10010e40AlmFailAccPortn, rm10010e40AlmHwFailAccPortn, rm10010e40trapPortNumber, rm10010e40trapBoardNumber}
	STATUS current
		--&FILTNAME    "RM10010E40 Client Fail ON"
		--&ACTIONS     { log, critical }
		--&MATCH       { rm10010e40AlmFailAccPortn "on", rm10010e40AlmHwFailAccPortn "*", rm10010e40trapPortNumber "$3", rm10010e40trapBoardNumber "$4"}
		--&MESG        "Client Port $3 Down on RM10010E40 in Slot $4 ($A)"

		--&FILTNAME    "RM10010E40 Client HW Fail ON (Hidden)"
		--&ACTIONS     { info }
		--&MATCH       { rm10010e40AlmFailAccPortn "*", rm10010e40AlmHwFailAccPortn "on", rm10010e40trapPortNumber "$3", rm10010e40trapBoardNumber "$4"}
		--&MESG        "Client Port $3 Down on RM10010E40 in Slot $4 ($A)"
	DESCRIPTION "Critical client default is activated"
	::= { rm10010e40traps 44 }

rm10010e40ClientTrapCritGoesOff NOTIFICATION-TYPE
	OBJECTS {rm10010e40AlmFailAccPortn, rm10010e40AlmHwFailAccPortn, rm10010e40trapPortNumber, rm10010e40trapBoardNumber}
	STATUS current
		--&FILTNAME    "RM10010E40 Client Fail OFF"
		--&ACTIONS     { log, normal }
		--&CLEARS      { "RM10010E40 Client Fail ON" }
		--&MATCH       { rm10010e40AlmFailAccPortn "on", rm10010e40AlmHwFailAccPortn "*", rm10010e40trapPortNumber "$3", rm10010e40trapBoardNumber "$4"}
		--&MESG        "Client Port $3 Up on RM10010E40 in Slot $4 ($A)"

		--&FILTNAME    "RM10010E40 Client HW Fail OFF (Hidden)"
		--&ACTIONS     { info }
		--&MATCH       { rm10010e40AlmFailAccPortn "*", rm10010e40AlmHwFailAccPortn "on", rm10010e40trapPortNumber "$3", rm10010e40trapBoardNumber "$4"}
		--&MESG        "Client Port $3 Up on RM10010E40 in Slot $4 ($A)"
	DESCRIPTION "Critical client default disappeared"
	::= { rm10010e40traps 45 }






--- *****************************************************
---     HW TRAPS
--- *****************************************************

rm10010e40PowerTrapUrgentGoesOn NOTIFICATION-TYPE
	OBJECTS {rm10010e40AlmDefFuseB, rm10010e40AlmDefFuseA , rm10010e40trapBoardNumber}
	STATUS current
		--&FILTNAME    "RM10010E40 Fuse A Fail ON"
		--&ACTIONS     { log, major }
		--&MATCH       { rm10010e40AlmDefFuseB "*", rm10010e40AlmDefFuseA "on", rm10010e40trapBoardNumber "$3"}
		--&MESG        "Power Input A Fail on RM10010E40 in Slot $3 ($A)"

		--&FILTNAME    "RM10010E40 Fuse B Fail ON"
		--&ACTIONS     { log, major }
		--&MATCH       { rm10010e40AlmDefFuseB "on", rm10010e40AlmDefFuseA "*", rm10010e40trapBoardNumber "$3"}
		--&MESG        "Power Input B Fail on RM10010E40 in Slot $3 ($A)"
	DESCRIPTION "Urgent power supply default is activated"
	::= { rm10010e40traps 50 }

rm10010e40PowerTrapUrgentGoesOff NOTIFICATION-TYPE
	OBJECTS {rm10010e40AlmDefFuseB, rm10010e40AlmDefFuseA , rm10010e40trapBoardNumber}
	STATUS current
		--&FILTNAME    "RM10010E40 Fuse A&B Fail OFF"
		--&ACTIONS     { log, normal}
		--&CLEARS      { "RM10010E40 Fuse A Fail ON", "RM10010E40 Fuse B Fail ON" }
		--&MATCH       { rm10010e40AlmDefFuseB "on", rm10010e40AlmDefFuseA "on", rm10010e40trapBoardNumber "$3"}
		--&MESG        "Power Inputs A and B Present on RM10010E40 in Slot $3 ($A)"
	DESCRIPTION "Urgent power supply default disappeared"
	::= { rm10010e40traps 51 }






END
