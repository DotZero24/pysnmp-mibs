-- *****************************************************************
-- EKINOPS-Pmlma10.TXT:  MIB
--
--MIB Part Number:3MI00034AAAC
--MIB Version:02
--
-- Copyright (c) 2016 by Ekinops
-- All rights reserved.
--
-- *****************************************************************

EKINOPS-Pmlma10-MIB DEFINITIONS ::= BEGIN

IMPORTS
	ekinops,
	EkiState,
	EkiOnOff,
	EkiMode,
	EkiProtocol,
	EkiApiState,
	EkiSynchroMode,
	EkiMeasureType
			FROM EKINOPS-MIB
        MODULE-IDENTITY,
        OBJECT-TYPE,
        NOTIFICATION-TYPE,
	Unsigned32,
	Integer32,
	Counter32,
	IpAddress
	FROM SNMPv2-SMI
	TEXTUAL-CONVENTION,
	DisplayString
                FROM SNMPv2-TC;

modulePmlma10 MODULE-IDENTITY
        LAST-UPDATED "201606020000Z"
        ORGANIZATION "Ekinops"
        CONTACT-INFO
         "Ekinops

          3, rue Blaise Pascal
          F-22300 Lannion / FRANCE

          Tel : +33 (0)2 96 05 00 30
          Fax : +33 (0)2 96 48 62 39

          E-mail: support@ekinops.fr"
        DESCRIPTION
          "Creation."

	REVISION "201410090000Z"
	DESCRIPTION
	  "Creation for PMLMA10"
	REVISION "201501270000Z"
	DESCRIPTION
	  "Creation for PMLMA10"
	REVISION "201510210000Z"
	DESCRIPTION
	  "Add F0 objet"
	REVISION "201605200000Z"
	DESCRIPTION
	  "New AlarmType – synthesisAlarm (12)"
	REVISION "201606020000Z"
	DESCRIPTION
	  "Capabilities objects of Table 5"
        ::= { ekinops 68 }



--- *****************************************************
---     LEAF LEVEL 2
--- *****************************************************


pmlma10alarms OBJECT IDENTIFIER ::= { modulePmlma10 2 }
pmlma10AlmOther OBJECT IDENTIFIER ::= { pmlma10alarms 1 }
pmlma10AlmOtherNurg OBJECT IDENTIFIER ::= { pmlma10AlmOther 1 }
pmlma10AlmOtherUrg OBJECT IDENTIFIER ::= { pmlma10AlmOther 2 }
pmlma10AlmOtherCrit OBJECT IDENTIFIER ::= { pmlma10AlmOther 3 }

pmlma10AlmClient OBJECT IDENTIFIER ::= { pmlma10alarms 2 }
pmlma10AlmClientNurg OBJECT IDENTIFIER ::= { pmlma10AlmClient 1 }
pmlma10AlmClientUrg OBJECT IDENTIFIER ::= { pmlma10AlmClient 2 }
pmlma10AlmClientCrit OBJECT IDENTIFIER ::= { pmlma10AlmClient 3 }

pmlma10AlmLine OBJECT IDENTIFIER ::= { pmlma10alarms 3 }
pmlma10AlmLineNurg OBJECT IDENTIFIER ::= { pmlma10AlmLine 1 }
pmlma10AlmLineUrg OBJECT IDENTIFIER ::= { pmlma10AlmLine 2 }
pmlma10AlmLineCrit OBJECT IDENTIFIER ::= { pmlma10AlmLine 3 }





pmlma10measures OBJECT IDENTIFIER ::= { modulePmlma10 3 }
pmlma10MesrOther OBJECT IDENTIFIER ::= { pmlma10measures 1 }
pmlma10MesrClient OBJECT IDENTIFIER ::= { pmlma10measures 2 }
pmlma10MesrLine OBJECT IDENTIFIER ::= { pmlma10measures 3 }




pmlma10counters OBJECT IDENTIFIER ::= { modulePmlma10 4 }
pmlma10CntOther OBJECT IDENTIFIER ::= { pmlma10counters 1 }
pmlma10CntClient OBJECT IDENTIFIER ::= { pmlma10counters 2 }
pmlma10CntLine OBJECT IDENTIFIER ::= { pmlma10counters 3 }


pmlma10controlsWrite OBJECT IDENTIFIER ::= { modulePmlma10 6 }
pmlma10CtrlOther OBJECT IDENTIFIER ::= { pmlma10controlsWrite 1 }
pmlma10CtrlClient OBJECT IDENTIFIER ::= { pmlma10controlsWrite 2 }
pmlma10CtrlLine OBJECT IDENTIFIER ::= { pmlma10controlsWrite 3 }

pmlma10ri OBJECT IDENTIFIER ::= { modulePmlma10 7 }
pmlma10riTable OBJECT IDENTIFIER ::= { pmlma10ri 1 }

pmlma10download OBJECT IDENTIFIER ::= { modulePmlma10 8 }
pmlma10DwlOther OBJECT IDENTIFIER ::= { pmlma10download 1 }
pmlma10DwlClient OBJECT IDENTIFIER ::= { pmlma10download 2 }
pmlma10DwlLine OBJECT IDENTIFIER ::= { pmlma10download 3 }


pmlma10Config OBJECT IDENTIFIER ::= { modulePmlma10 9 }

pmlma10traps OBJECT IDENTIFIER ::= { modulePmlma10 10 }



pmlma10Monitoring OBJECT IDENTIFIER ::= { modulePmlma10 11}

pmlma10MonOther OBJECT IDENTIFIER ::= { pmlma10Monitoring 1 }
pmlma10MonRmon OBJECT IDENTIFIER ::= { pmlma10MonOther 3 }

pmlma10MonClient OBJECT IDENTIFIER ::= { pmlma10Monitoring 2 }
pmlma10MonClientRmonCounter OBJECT IDENTIFIER ::= { pmlma10MonClient 4 }


--- *****************************************************
--- $$$$$$$$$$$$$$$$$$$$$$$$$$$$$$$$$$$$$$$$$$$$$$$$$$$$$
---     TEXTUAL-CONVENTION
--- $$$$$$$$$$$$$$$$$$$$$$$$$$$$$$$$$$$$$$$$$$$$$$$$$$$$$
--- *****************************************************

Pmlma10MultiRate ::= TEXTUAL-CONVENTION
    STATUS      current
    DESCRIPTION "different rate for a client port"
    SYNTAX INTEGER {
		rate100Mhz(0),
		rate250Mhz(1),
		rate500Mhz(2),
		rate1Ghz(3)
           }

Pmlma10OtxMode ::= TEXTUAL-CONVENTION
    STATUS      current
    DESCRIPTION "Different modes on OTX-TLH on client and line ports"
    SYNTAX INTEGER {
		otx80mode(1),
		otx60mode(2),
		otxadjustmode(4)
           }

Pmlma10OtxGrid ::= TEXTUAL-CONVENTION
    STATUS      current
    DESCRIPTION "Different grids on OTX-TLH on client and line ports"
    SYNTAX INTEGER {
		otxgrid200(200),
		otxgrid100(100),
		otxgrid50(50)
           }

Pmlma10AdjustValue ::= TEXTUAL-CONVENTION
    STATUS      current
    DESCRIPTION "Different values in Adjust mode on OTX-TLH on client and line ports"
    SYNTAX INTEGER {
		otxadjustvalue0(0),
		otxadjustvalue1(1),
		otxadjustvalue2(2),
		otxadjustvalue3(3),
		otxadjustvalue4(4),
		otxadjustvalue5(5),
		otxadjustvalue6(6),
		otxadjustvalue7(7),
		otxadjustvalue8(8),
		otxadjustvalue9(9),
		otxadjustvalue10(10)
           }

Pmlma10ClientProtocol ::= TEXTUAL-CONVENTION
    STATUS      current
    DESCRIPTION "Different values on the protocol on the client ports"
    SYNTAX INTEGER {
		protocolclientvalue0(0),
		protocolclientvalue1(1),
		protocolclientvalue2(2),
		protocolclientvalue3(3),
		protocolclientvalue4(4),
		protocolclientvalue5(5),
		protocolclientvalue6(6),
		protocolclientvalue7(7),
		protocolclientvalue8(8)
           }

Pmlma10ProtocolMode ::= TEXTUAL-CONVENTION
    STATUS      current
    DESCRIPTION "Different values on the protocol mode"
    SYNTAX INTEGER {
		protocolmodevalue0(0),
		protocolmodevalue1(1),
		protocolmodevalue2(2),
		protocolmodevalue3(3)
           }

Pmlma10OtxChannel ::= TEXTUAL-CONVENTION
    STATUS      current
    DESCRIPTION "Channel selection on transceiver Tx line ports"
    SYNTAX INTEGER

Pmlma10OrxChannel ::= TEXTUAL-CONVENTION
    STATUS      current
    DESCRIPTION "Channel selection on transceiver Rx line ports"
    SYNTAX INTEGER

Pmlma10ClientIgnoreTimer ::= TEXTUAL-CONVENTION
    STATUS      current
    DESCRIPTION "Different values on the ignore timer on the client ports"
    SYNTAX INTEGER {
		ignoretimerclientvalue0(0),
		ignoretimerclientvalue1(1),
		ignoretimerclientvalue2(2),
		ignoretimerclientvalue3(3),
		ignoretimerclientvalue4(4),
		ignoretimerclientvalue5(5),
		ignoretimerclientvalue6(6),
		ignoretimerclientvalue7(7),
		ignoretimerclientvalue8(8),
		ignoretimerclientvalue9(9),
		ignoretimerclientvalue10(10)
           }

Pmlma10DccMode ::= TEXTUAL-CONVENTION
    STATUS      current
    DESCRIPTION "Mode for DCC"
    SYNTAX INTEGER {
		dccNo(0),
		dccLine1(1),
		dccLine2(2)
           }

--- *****************************************************
--- $$$$$$$$$$$$$$$$$$$$$$$$$$$$$$$$$$$$$$$$$$$$$$$$$$$$$
---     REMOTE INVENTORY
--- $$$$$$$$$$$$$$$$$$$$$$$$$$$$$$$$$$$$$$$$$$$$$$$$$$$$$
--- *****************************************************

pmlma10RinvReloadInventory OBJECT-TYPE
  SYNTAX EkiOnOff
  MAX-ACCESS read-write
  STATUS current
  DESCRIPTION
        "Reload the inventory: This OID triggers an
         inventory reload."
  ::= { pmlma10ri 2 }

pmlma10RinvHwPlatform OBJECT-TYPE
  SYNTAX DisplayString
  MAX-ACCESS read-only
  STATUS current
  DESCRIPTION
        "HW platform description: This OID contains the
         description of the Hardware platform."
  ::= { pmlma10ri 3 }

pmlma10RinvModulePlatform OBJECT-TYPE
  SYNTAX DisplayString
  MAX-ACCESS read-only
  STATUS current
  DESCRIPTION
        "Module platform description: This OID contains the
         description of the Module."
  ::= { pmlma10ri 4 }

pmlma10RinvSwPlatform OBJECT-TYPE
  SYNTAX DisplayString
  MAX-ACCESS read-only
  STATUS current
  DESCRIPTION
        "SW platform description: This OID contains the
         description of the Software platform."
  ::= { pmlma10ri 5 }

pmlma10RinvGwPlatform OBJECT-TYPE
  SYNTAX DisplayString
  MAX-ACCESS read-only
  STATUS current
  DESCRIPTION
        "GW platform description: This OID contains the
         description of the Gateware platform."
  ::= { pmlma10ri 6 }


pmlma10RinvSfpTable OBJECT-TYPE
      SYNTAX  SEQUENCE OF Pmlma10RinvSfpEntry
      MAX-ACCESS  not-accessible
      STATUS  current
      DESCRIPTION
              "List of the SFPs on the selected module"
      ::= { pmlma10riTable 1 }

pmlma10RinvSfpEntry OBJECT-TYPE
        SYNTAX  Pmlma10RinvSfpEntry
        MAX-ACCESS  not-accessible
        STATUS  current
        DESCRIPTION
              "Row definition for the SFP table"
        INDEX   { pmlma10RinvSfpIndex }
        ::= { pmlma10RinvSfpTable 1 }



Pmlma10RinvSfpEntry::=
        SEQUENCE {
          pmlma10RinvSfpIndex
              Integer32,
          pmlma10Rinvsfp
              DisplayString
        }


    pmlma10RinvSfpIndex OBJECT-TYPE
        SYNTAX  Integer32(1..16)
        MAX-ACCESS  read-only
        STATUS  current
        DESCRIPTION
              "Index for SFP table"
        ::= { pmlma10RinvSfpEntry 1 }


    pmlma10Rinvsfp OBJECT-TYPE
        SYNTAX  DisplayString
        MAX-ACCESS  read-only
        STATUS  current
        DESCRIPTION
              "Inventory for the SFP: This OID contains the inventory for the SFP"
        ::= { pmlma10RinvSfpEntry 2 }




pmlma10RinvLineTable OBJECT-TYPE
      SYNTAX  SEQUENCE OF Pmlma10RinvLineEntry
      MAX-ACCESS  not-accessible
      STATUS  current
      DESCRIPTION
              "List of the XFPs on the selected module"
      ::= { pmlma10riTable 2 }

pmlma10RinvLineEntry OBJECT-TYPE
        SYNTAX  Pmlma10RinvLineEntry
        MAX-ACCESS  not-accessible
        STATUS  current
        DESCRIPTION
              "Row definition for the XFP table"
        INDEX   { pmlma10RinvLineIndex }
        ::= { pmlma10RinvLineTable 1 }



Pmlma10RinvLineEntry::=
        SEQUENCE {
          pmlma10RinvLineIndex
              Integer32,
          pmlma10RinvxfpLine
              DisplayString
        }


    pmlma10RinvLineIndex OBJECT-TYPE
        SYNTAX  Integer32(1..16)
        MAX-ACCESS  read-only
        STATUS  current
        DESCRIPTION
              "Index for XFP table"
        ::= { pmlma10RinvLineEntry 1 }


    pmlma10RinvxfpLine OBJECT-TYPE
        SYNTAX  DisplayString
        MAX-ACCESS  read-only
        STATUS  current
        DESCRIPTION
              "Inventory for the XFP: This OID contains the inventory for the XFP"
        ::= { pmlma10RinvLineEntry 2 }









--- *****************************************************
--- $$$$$$$$$$$$$$$$$$$$$$$$$$$$$$$$$$$$$$$$$$$$$$$$$$$$$
---     ALARMS
--- $$$$$$$$$$$$$$$$$$$$$$$$$$$$$$$$$$$$$$$$$$$$$$$$$$$$$
--- *****************************************************



--- *****************************************************
---     LEAF for the synthAlm0 article
--- *****************************************************
pmlma10AlmsynthAlm0 OBJECT IDENTIFIER ::= { pmlma10AlmOtherCrit 0 }




pmlma10AlmDefFuseB OBJECT-TYPE
	  SYNTAX EkiOnOff
	  MAX-ACCESS read-only
	  STATUS current
	  DESCRIPTION
        "
        Fuse B Fail :This OID indicates
        that the fuse of the power input
        B is in fail condition <Help> Status
        of the Fuse B <Condtype> DEF_FUSE_B
        <Probcause> powerProblem (36) <Alarmtype>
        equipmentAlarm (5) <Polarity> (2)
        "
	  ::= { pmlma10AlmsynthAlm0 16 }



pmlma10AlmDefFuseA OBJECT-TYPE
	  SYNTAX EkiOnOff
	  MAX-ACCESS read-only
	  STATUS current
	  DESCRIPTION
        "
        Fuse A Fail :This OID indicates
        that the fuse of the power input
        A is in fail condition <Help> Status
        of the Fuse A <Condtype> DEF_FUSE_A
        <Probcause> powerProblem (36) <Alarmtype>
        equipmentAlarm (5) <Polarity> (2)
        "
	  ::= { pmlma10AlmsynthAlm0 15 }



pmlma10AlmModGlobFail OBJECT-TYPE
	  SYNTAX EkiOnOff
	  MAX-ACCESS read-only
	  STATUS current
	  DESCRIPTION
        "
        Module Failure :This OID is set
        on detection of a failure originating
        from the RM <Help> This alarm is
        set on detection of a failure originating
        from the equipment <Condtype> MOD_GLOB_FAIL
        <Probcause> other (1) <Alarmtype>
        synthesisAlarm (12)  <Polarity>
        (2)
        "
	  ::= { pmlma10AlmsynthAlm0 9 }



--- *****************************************************
---     LEAF for the synthAlm2 article
--- *****************************************************
pmlma10AlmsynthAlm2 OBJECT IDENTIFIER ::= { pmlma10AlmOtherNurg 2 }




pmlma10AlmCorrelatOff OBJECT-TYPE
	  SYNTAX EkiOnOff
	  MAX-ACCESS read-only
	  STATUS current
	  DESCRIPTION
        "
        Not Used :This OID, when set,
         indicates that alarm correlation
        is not being performed. <Condtype>
        CORRELAT_OFF <Probcause> informationalStatus(1000)
        <Alarmtype> other (1) <Polarity>
        (2)
        "
	  ::= { pmlma10AlmsynthAlm2 4 }



pmlma10AlmConfTableLoad OBJECT-TYPE
	  SYNTAX EkiOnOff
	  MAX-ACCESS read-only
	  STATUS current
	  DESCRIPTION
        "
        PM Configuration Load :This OID
         is at 1 during the loading of
         configuration tables in the modules
        RAM. <Condtype> CONF_TABLE_LOAD
        <Probcause> informationalStatus(1000)
        <Alarmtype> other (1) <Polarity>
        (2)
        "
	  ::= { pmlma10AlmsynthAlm2 3 }



pmlma10AlmInvUpload OBJECT-TYPE
	  SYNTAX EkiOnOff
	  MAX-ACCESS read-only
	  STATUS current
	  DESCRIPTION
        "
        Inventory Upload :This OID is
         at 1 during the uploading of PM
        inventory information. <Condtype>
        INV_UPLOAD <Probcause> informationalStatus(1000)
        <Alarmtype> other (1) <Polarity>
        (2)
        "
	  ::= { pmlma10AlmsynthAlm2 2 }



pmlma10AlmConfTableSave OBJECT-TYPE
	  SYNTAX EkiOnOff
	  MAX-ACCESS read-only
	  STATUS current
	  DESCRIPTION
        "
        PM Configuration Save :This OID
        is at 1 during the saving of a
         new configuration table in the
        module Flash memory. <Condtype>
        CONF_TABLE_SAVE <Probcause> informationalStatus(1000)
        <Alarmtype> other (1) <Polarity>
        (2)
        "
	  ::= { pmlma10AlmsynthAlm2 1 }



--- *********************************************************
---     TABLE for the pmlma10AlmsynthAlmPort articles
--- *********************************************************

pmlma10AlmsynthAlmPortTable OBJECT-TYPE
	SYNTAX  SEQUENCE OF Pmlma10AlmsynthAlmPortEntry
	MAX-ACCESS not-accessible
	STATUS current
	DESCRIPTION
        "
        List of pmlma10AlmsynthAlmPort
        Article
        "
	::= { pmlma10AlmClientCrit 8 }


pmlma10AlmsynthAlmPortEntry OBJECT-TYPE
	SYNTAX Pmlma10AlmsynthAlmPortEntry
	MAX-ACCESS not-accessible
	STATUS current
	DESCRIPTION
        "
        Row definition for the pmlma10AlmsynthAlmPort
        table
        "
	INDEX   { pmlma10AlmsynthAlmPortIndex }
	::= { pmlma10AlmsynthAlmPortTable 1 }


Pmlma10AlmsynthAlmPortEntry ::=
	SEQUENCE {
	pmlma10AlmsynthAlmPortIndex
		INTEGER,
	pmlma10AlmUpCsfPortn
		EkiOnOff,
	pmlma10AlmFailAccPortn
		EkiOnOff,
	pmlma10AlmSfpDdmAlmPortn
		EkiOnOff,
	pmlma10AlmSfpDdmWarningPortn
		EkiOnOff,
	pmlma10AlmDwCaisPortn
		EkiOnOff,
	pmlma10AlmClientRemoteOosPortn
		EkiOnOff,
	pmlma10AlmClientLocalOosPortn
		EkiOnOff,
	pmlma10AlmDwLsdPortn
		EkiOnOff,
	pmlma10AlmHwFailAccPortn
		EkiOnOff,
	pmlma10AlmDdmAbsentPortn
		EkiOnOff,
	pmlma10AlmSfpAbsentPortn
		EkiOnOff
	}


pmlma10AlmsynthAlmPortIndex OBJECT-TYPE
	SYNTAX  INTEGER(0..128)
	MAX-ACCESS  read-only
	STATUS current
	DESCRIPTION
        "
        Index definition for the pmlma10AlmsynthAlmPort
        table
        "
	::= { pmlma10AlmsynthAlmPortEntry 1 }


pmlma10AlmUpCsfPortn OBJECT-TYPE
	SYNTAX  EkiOnOff
	MAX-ACCESS read-only
	STATUS current
	DESCRIPTION
        "
        Client Signal Fail Inserted :This
        OID indicates a CSF has been inserted
        in the upstream client port. <Help>
        This status indicates if a Client
        Signal Fail is currently inserted
        on the line signal for this client
        port <Condtype> UP_CSF_1 <Probcause>
        informationalStatus(1000) <Alarmtype>
        other (1) <Polarity> (2)
        "
	::= { pmlma10AlmsynthAlmPortEntry 17 }


pmlma10AlmFailAccPortn OBJECT-TYPE
	SYNTAX  EkiOnOff
	MAX-ACCESS read-only
	STATUS current
	DESCRIPTION
        "
        Client Access Fail :This OID indicates
        a failure on the Client port <Help>
        This alarm indicates a failure
         on the Client port <Condtype>
         FAIL_ACC_1 <Probcause> equipmentMalfunction
        (16) <Alarmtype> synthesisAlarm
        (12)  <Polarity> (2)
        "
	::= { pmlma10AlmsynthAlmPortEntry 13 }


pmlma10AlmSfpDdmAlmPortn OBJECT-TYPE
	SYNTAX  EkiOnOff
	MAX-ACCESS read-only
	STATUS current
	DESCRIPTION
        "
        Alarm On Client Trscv DDM :This
        OID indicates an alarm is being
        received from the Client Transceiver
        DDM <Help> This alarm indicates
        if a DDM Alarm has been detected
        on the client transceiver <Condtype>
        SFP_DDM_ALM_1 <Probcause> inputOutputDeviceError
        (24) <Alarmtype> synthesisAlarm
        (12)  <Polarity> (2)
        "
	::= { pmlma10AlmsynthAlmPortEntry 11 }


pmlma10AlmSfpDdmWarningPortn OBJECT-TYPE
	SYNTAX  EkiOnOff
	MAX-ACCESS read-only
	STATUS current
	DESCRIPTION
        "
        Warning On Client Trscv DDM :This
        OID indicates a warning is being
        received from the Client Transceiver
        DDM <Help> This alarm indicates
        if a DDM Warning has been detected
        on the client transceiver <Condtype>
        SFP_DDM_WARNING_1 <Probcause> inputOutputDeviceError
        (24) <Alarmtype> synthesisAlarm
        (12)  <Polarity> (2)
        "
	::= { pmlma10AlmsynthAlmPortEntry 10 }


pmlma10AlmDwCaisPortn OBJECT-TYPE
	SYNTAX  EkiOnOff
	MAX-ACCESS read-only
	STATUS current
	DESCRIPTION
        "
        Client AIS Inserted :This OID
         indicates a CAIS has been inserted
        on the output client port. <Help>
        This status indicates if a Client
        Alarm Indication Signal is currently
        inserted on the client interface
        <Condtype> DW_CAIS_1 <Probcause>
        informationalStatus(1000) <Alarmtype>
        other (1) <Polarity> (2)
        "
	::= { pmlma10AlmsynthAlmPortEntry 9 }


pmlma10AlmClientRemoteOosPortn OBJECT-TYPE
	SYNTAX  EkiOnOff
	MAX-ACCESS read-only
	STATUS current
	DESCRIPTION
        "
        Remote Client Port In Service
         :This OID indicates that the remote
        Client port is In Service (1) or
        Out of Service (2) <Help> This
         status indicates if the remote
        client port is in service <Condtype>
        CLIENT_REMOTE_OOS <Probcause> informationalStatus(1000)
        <Alarmtype> other (1) <Polarity>
        (2)
        "
	::= { pmlma10AlmsynthAlmPortEntry 8 }


pmlma10AlmClientLocalOosPortn OBJECT-TYPE
	SYNTAX  EkiOnOff
	MAX-ACCESS read-only
	STATUS current
	DESCRIPTION
        "
        Local Client Port In Service :This
        OID indicates that the local Client
        port is In Service (1) or Out of
        Service (2) <Help> This status
         indicates if the local client
         port is in service <Condtype>
         CLIENT_LOCAL_OOS <Probcause> informationalStatus(1000)
        <Alarmtype> other (1) <Polarity>
        (2)
        "
	::= { pmlma10AlmsynthAlmPortEntry 7 }


pmlma10AlmDwLsdPortn OBJECT-TYPE
	SYNTAX  EkiOnOff
	MAX-ACCESS read-only
	STATUS current
	DESCRIPTION
        "
        Client Trscv Laser Shutdown :This
        OID indicates the Client transceiver
        laser is shutdown <Help> This status
        indicates if the client transceiver
        laser is shutdown <Condtype> DW_LSD_1
        <Probcause> other (1) <Alarmtype>
        equipmentAlarm (5) <Polarity> (2)
        "
	::= { pmlma10AlmsynthAlmPortEntry 6 }


pmlma10AlmHwFailAccPortn OBJECT-TYPE
	SYNTAX  EkiOnOff
	MAX-ACCESS read-only
	STATUS current
	DESCRIPTION
        "
        Client HW Fail :This OID indicates
        a failure on client port, most
         probably caused by a HW issue.
        <Help> This alarm indicates a failure
        on client port, most probably caused
        by a HW issue. <Condtype> HW_FAIL_ACC_1
        <Probcause> equipmentMalfunction
        (16) <Alarmtype> synthesisAlarm
        (12)  <Polarity> (2)
        "
	::= { pmlma10AlmsynthAlmPortEntry 5 }


pmlma10AlmDdmAbsentPortn OBJECT-TYPE
	SYNTAX  EkiOnOff
	MAX-ACCESS read-only
	STATUS current
	DESCRIPTION
        "
        DDM Supported On Client Trscv
         :This OID indicates that the Client
        transceiver supports the Digital
        Diagnostic Monitoring function
         <Help> This status indicates if
        the client transceiver includes
        the DDM feature <Condtype> DDM_ABSENT_1
        <Probcause> informationalStatus(1000)
        <Alarmtype> other (1) <Polarity>
        (2)
        "
	::= { pmlma10AlmsynthAlmPortEntry 3 }


pmlma10AlmSfpAbsentPortn OBJECT-TYPE
	SYNTAX  EkiOnOff
	MAX-ACCESS read-only
	STATUS current
	DESCRIPTION
        "
        Client Optical Module Absent :This
        OID indicates that the Transceiver
        is not present in the client port.
        <Help> This alarm indicates if
         the client transceiver is not
         plugged <Condtype> SFP_ABSENT_1
        <Probcause> inputOutputDeviceError
        (24) <Alarmtype> equipmentAlarm
        (5) <Polarity> (2) <Event> ObjectCDINV
        "
	::= { pmlma10AlmsynthAlmPortEntry 2 }


--- *********************************************************
---     TABLE for the pmlma10AlmsynthAlmLine articles
--- *********************************************************

pmlma10AlmsynthAlmLineTable OBJECT-TYPE
	SYNTAX  SEQUENCE OF Pmlma10AlmsynthAlmLineEntry
	MAX-ACCESS not-accessible
	STATUS current
	DESCRIPTION
        "
        List of pmlma10AlmsynthAlmLine
        Article
        "
	::= { pmlma10AlmLineCrit 24 }


pmlma10AlmsynthAlmLineEntry OBJECT-TYPE
	SYNTAX Pmlma10AlmsynthAlmLineEntry
	MAX-ACCESS not-accessible
	STATUS current
	DESCRIPTION
        "
        Row definition for the pmlma10AlmsynthAlmLine
        table
        "
	INDEX   { pmlma10AlmsynthAlmLineIndex }
	::= { pmlma10AlmsynthAlmLineTable 1 }


Pmlma10AlmsynthAlmLineEntry ::=
	SEQUENCE {
	pmlma10AlmsynthAlmLineIndex
		INTEGER,
	pmlma10AlmLineFailPortn
		EkiOnOff,
	pmlma10AlmLineDdmAlmPortn
		EkiOnOff,
	pmlma10AlmLineDdmWarningPortn
		EkiOnOff,
	pmlma10AlmUpRdiInsPortn
		EkiOnOff,
	pmlma10AlmLineLocalOosPortn
		EkiOnOff,
	pmlma10AlmLineTxOffPortn
		EkiOnOff,
	pmlma10AlmLineHwFailPortn
		EkiOnOff,
	pmlma10AlmLineDdmAbsentPortn
		EkiOnOff,
	pmlma10AlmLineSfpAbsentPortn
		EkiOnOff
	}


pmlma10AlmsynthAlmLineIndex OBJECT-TYPE
	SYNTAX  INTEGER(0..128)
	MAX-ACCESS  read-only
	STATUS current
	DESCRIPTION
        "
        Index definition for the pmlma10AlmsynthAlmLine
        table
        "
	::= { pmlma10AlmsynthAlmLineEntry 1 }


pmlma10AlmLineFailPortn OBJECT-TYPE
	SYNTAX  EkiOnOff
	MAX-ACCESS read-only
	STATUS current
	DESCRIPTION
        "
        Line Port Failure :This OID indicates
        a failure on the line port <Help>
        This alarm indicates a failure
         on the line port <Condtype> LINE_FAIL
        <Probcause> equipmentMalfunction
        (16) <Alarmtype> synthesisAlarm
        (12)  <Polarity> (2)
        "
	::= { pmlma10AlmsynthAlmLineEntry 13 }


pmlma10AlmLineDdmAlmPortn OBJECT-TYPE
	SYNTAX  EkiOnOff
	MAX-ACCESS read-only
	STATUS current
	DESCRIPTION
        "
        Alarm On Line Optical Module DDM
        :This OID indicates an alarm is
        present coming out of Line transceiver
        DDM <Help> This alarm indicates
        if a DDM Alarm has been detected
        on the line transceiver <Condtype>
        LINE_DDM_ALM <Probcause> inputOutputDeviceError
        (24) <Alarmtype> synthesisAlarm
        (12)  <Polarity> (2)
        "
	::= { pmlma10AlmsynthAlmLineEntry 11 }


pmlma10AlmLineDdmWarningPortn OBJECT-TYPE
	SYNTAX  EkiOnOff
	MAX-ACCESS read-only
	STATUS current
	DESCRIPTION
        "
        Warning On Line Optical Module
        DDM :This OID indicates a warning
        is present coming out of Line transceiver
        DDM <Help> This alarm indicates
        if a DDM Warning has been detected
        on the line transceiver <Condtype>
        LINE_DDM_WARNING <Probcause> inputOutputDeviceError
        (24) <Alarmtype> synthesisAlarm
        (12)  <Polarity> (2)
        "
	::= { pmlma10AlmsynthAlmLineEntry 10 }


pmlma10AlmUpRdiInsPortn OBJECT-TYPE
	SYNTAX  EkiOnOff
	MAX-ACCESS read-only
	STATUS current
	DESCRIPTION
        "
        MS-RDI/L-RDI Inserted On Line
         :This OID indicates an upstream
        MS-RDI/L-RDI has been inserted
         in the outgoing 10 Gb/s SDH/SONET
        signal. <Help> This status indicates
        if a MS-RDI/L-RDI is currently
         inserted on the line interface.
        <Condtype> UP_RDI_INS <Probcause>
        informationalStatus(1000) <Alarmtype>
        other (1) <Polarity> (2)
        "
	::= { pmlma10AlmsynthAlmLineEntry 9 }


pmlma10AlmLineLocalOosPortn OBJECT-TYPE
	SYNTAX  EkiOnOff
	MAX-ACCESS read-only
	STATUS current
	DESCRIPTION
        "
        Line Port In Service :This OID
        indicates that the Line port is
        In Service (1) of Out or Service
        (2) <Help> This status indicates
        if the line port is in service
         <Condtype> LINE_LOCAL_OOS <Probcause>
        informationalStatus(1000) <Alarmtype>
        other (1) <Polarity> (2)
        "
	::= { pmlma10AlmsynthAlmLineEntry 7 }


pmlma10AlmLineTxOffPortn OBJECT-TYPE
	SYNTAX  EkiOnOff
	MAX-ACCESS read-only
	STATUS current
	DESCRIPTION
        "
        Line Trscv Laser Shutdown :This
        OID indicates the Line transceiver
        laser is shutdown <Help> This status
        indicates if the Line transceiver
        laser is shutdown <Condtype> LINE_TX_OFF
        <Probcause> other (1) <Alarmtype>
        equipmentAlarm (5) <Polarity> (2)
        "
	::= { pmlma10AlmsynthAlmLineEntry 6 }


pmlma10AlmLineHwFailPortn OBJECT-TYPE
	SYNTAX  EkiOnOff
	MAX-ACCESS read-only
	STATUS current
	DESCRIPTION
        "
        Line Port HW Failure :This OID
        indicates a failure on line port,
        most probably caused by a HW issue
        <Help> This alarm indicates a failure
        on line port, most probably caused
        by a HW issue <Condtype> LINE_HW_FAIL
        <Probcause> equipmentMalfunction
        (16) <Alarmtype> synthesisAlarm
        (12)  <Polarity> (2)
        "
	::= { pmlma10AlmsynthAlmLineEntry 5 }


pmlma10AlmLineDdmAbsentPortn OBJECT-TYPE
	SYNTAX  EkiOnOff
	MAX-ACCESS read-only
	STATUS current
	DESCRIPTION
        "
        Line Optical Module Ready :This
        OID indicates that the optical
         interface is not operational.
         <Help> This status indicates if
        the line transceiver has been correctly
        initialized <Condtype> LINE_DDM_ABSENT_1
        <Probcause> equipmentMalfunction
        (16) <Alarmtype> other (1) <Polarity>
        (2)
        "
	::= { pmlma10AlmsynthAlmLineEntry 3 }


pmlma10AlmLineSfpAbsentPortn OBJECT-TYPE
	SYNTAX  EkiOnOff
	MAX-ACCESS read-only
	STATUS current
	DESCRIPTION
        "
        Line Optical Module Absent :This
        OID indicates that the line optical
        interface is not present. <Help>
        This alarm indicates if the line
        transceiver is not plugged <Condtype>
        LINE_SFP_ABSENT_1 <Probcause> inputOutputDeviceError
        (24) <Alarmtype> equipmentAlarm
        (5) <Polarity> (2) <Event> ObjectCDINV
        "
	::= { pmlma10AlmsynthAlmLineEntry 2 }


--- *********************************************************
---     TABLE for the pmlma10AlmclientHostLaneFault articles
--- *********************************************************

pmlma10AlmclientHostLaneFaultTable OBJECT-TYPE
	SYNTAX  SEQUENCE OF Pmlma10AlmclientHostLaneFaultEntry
	MAX-ACCESS not-accessible
	STATUS current
	DESCRIPTION
        "
        List of pmlma10AlmclientHostLaneFault
        Article
        "
	::= { pmlma10AlmClientUrg 88 }


pmlma10AlmclientHostLaneFaultEntry OBJECT-TYPE
	SYNTAX Pmlma10AlmclientHostLaneFaultEntry
	MAX-ACCESS not-accessible
	STATUS current
	DESCRIPTION
        "
        Row definition for the pmlma10AlmclientHostLaneFault
        table
        "
	INDEX   { pmlma10AlmclientHostLaneFaultIndex }
	::= { pmlma10AlmclientHostLaneFaultTable 1 }


Pmlma10AlmclientHostLaneFaultEntry ::=
	SEQUENCE {
	pmlma10AlmclientHostLaneFaultIndex
		INTEGER,
	pmlma10AlmClientLaneTxFifoErrorPortn
		EkiOnOff,
	pmlma10AlmClientCsfDetectedPortn
		EkiOnOff,
	pmlma10AlmClientInputLossOfSigPortn
		EkiOnOff,
	pmlma10AlmClientLossOfSyncPortn
		EkiOnOff
	}


pmlma10AlmclientHostLaneFaultIndex OBJECT-TYPE
	SYNTAX  INTEGER(0..128)
	MAX-ACCESS  read-only
	STATUS current
	DESCRIPTION
        "
        Index definition for the pmlma10AlmclientHostLaneFault
        table
        "
	::= { pmlma10AlmclientHostLaneFaultEntry 1 }


pmlma10AlmClientLaneTxFifoErrorPortn OBJECT-TYPE
	SYNTAX  EkiOnOff
	MAX-ACCESS read-only
	STATUS current
	DESCRIPTION
        "
        Client Tx FIFO Error :This OID
        indicates a Tx FIFO Error on the
        Client Trscv <Help> Alarm indicating
        a Tx FIFO Error on the Client Trscv
        <Condtype> CLIENT_LANE_TX_FIFO_ERROR
        <Probcause> receiverFailure (42)
        <Alarmtype> equipmentAlarm (5)
         <Polarity> (2)
        "
	::= { pmlma10AlmclientHostLaneFaultEntry 11 }


pmlma10AlmClientCsfDetectedPortn OBJECT-TYPE
	SYNTAX  EkiOnOff
	MAX-ACCESS read-only
	STATUS current
	DESCRIPTION
        "
        Client Signal Fail Detected :This
        OID indicates that a CSF has been
        detected on client port in the
         downstream direction   <Help>
          This alarm indicates if a Client
        Signal Fail has been detected in
        the incoming line frame for this
        client port <Condtype> CLIENT_CSF_DETECTED
        <Probcause> receiveFailure (41)
        <Alarmtype> other(1) <Polarity>
        (2)
        "
	::= { pmlma10AlmclientHostLaneFaultEntry 7 }


pmlma10AlmClientInputLossOfSigPortn OBJECT-TYPE
	SYNTAX  EkiOnOff
	MAX-ACCESS read-only
	STATUS current
	DESCRIPTION
        "
        Client Input Loss Of Signal :This
        OID indicates a Loss of Signal
         is detected on the Client Trscv
        <Help> Alarm indicating a Loss
         of Signal is detected on the Client
        Trscv <Condtype> CLIENT_INPUT_LOSS_OF_SIG
        <Probcause> receiveFailure (41)
        <Alarmtype> physicalViolation (9)
        <Polarity> (2)
        "
	::= { pmlma10AlmclientHostLaneFaultEntry 3 }


pmlma10AlmClientLossOfSyncPortn OBJECT-TYPE
	SYNTAX  EkiOnOff
	MAX-ACCESS read-only
	STATUS current
	DESCRIPTION
        "
        Client Frame Alignment Loss :This
        OID indicates the module is not
        aligned with the incoming Client
        signal <Help> Alarm indicating
         the module is not aligned with
        the incoming client signal <Condtype>
        CLIENT_LOSS_OF_SYNC <Probcause>
        receiveFailure (41) <Alarmtype>
        integrityViolation (7) <Polarity>
        (2)
        "
	::= { pmlma10AlmclientHostLaneFaultEntry 2 }


--- *********************************************************
---     TABLE for the pmlma10AlmlineNetworkLaneAlarmWarning1 articles
--- *********************************************************

pmlma10AlmlineNetworkLaneAlarmWarning1Table OBJECT-TYPE
	SYNTAX  SEQUENCE OF Pmlma10AlmlineNetworkLaneAlarmWarning1Entry
	MAX-ACCESS not-accessible
	STATUS current
	DESCRIPTION
        "
        List of pmlma10AlmlineNetworkLaneAlarmWarning1
        Article
        "
	::= { pmlma10AlmLineUrg 104 }


pmlma10AlmlineNetworkLaneAlarmWarning1Entry OBJECT-TYPE
	SYNTAX Pmlma10AlmlineNetworkLaneAlarmWarning1Entry
	MAX-ACCESS not-accessible
	STATUS current
	DESCRIPTION
        "
        Row definition for the pmlma10AlmlineNetworkLaneAlarmWarning1
        table
        "
	INDEX   { pmlma10AlmlineNetworkLaneAlarmWarning1Index }
	::= { pmlma10AlmlineNetworkLaneAlarmWarning1Table 1 }


Pmlma10AlmlineNetworkLaneAlarmWarning1Entry ::=
	SEQUENCE {
	pmlma10AlmlineNetworkLaneAlarmWarning1Index
		INTEGER,
	pmlma10AlmLineRxPwrHighAlaPortn
		EkiOnOff,
	pmlma10AlmLineRxPwrLowAlaPortn
		EkiOnOff,
	pmlma10AlmLineTempHighAlaPortn
		EkiOnOff,
	pmlma10AlmLineTempLowAlaPortn
		EkiOnOff,
	pmlma10AlmLineVccHighAlaPortn
		EkiOnOff,
	pmlma10AlmLineVccLowAlaPortn
		EkiOnOff,
	pmlma10AlmLineTxBiasHighAlaPortn
		EkiOnOff,
	pmlma10AlmLineTxBiasLowAlaPortn
		EkiOnOff,
	pmlma10AlmLineTxPwrHighAlaPortn
		EkiOnOff,
	pmlma10AlmLineTxPwrLowAlaPortn
		EkiOnOff
	}


pmlma10AlmlineNetworkLaneAlarmWarning1Index OBJECT-TYPE
	SYNTAX  INTEGER(0..128)
	MAX-ACCESS  read-only
	STATUS current
	DESCRIPTION
        "
        Index definition for the pmlma10AlmlineNetworkLaneAlarmWarning1
        table
        "
	::= { pmlma10AlmlineNetworkLaneAlarmWarning1Entry 1 }


pmlma10AlmLineRxPwrHighAlaPortn OBJECT-TYPE
	SYNTAX  EkiOnOff
	MAX-ACCESS read-only
	STATUS current
	DESCRIPTION
        "
        Line Trscv Rx Power High :This
        OID indicates that the Trscv input
        power of port is higher than the
        threshold value written in the
         Trscv EEPROM <Help> Alarm indicating
        that the Trscv input power of port
        is higher than the threshold value
        written in the Trscv EEPROM <Condtype>
        LINE_RX_PWR_HIGH_ALA_1 <Probcause>
        receiveFailure (41) <Alarmtype>
        equipmentAlarm (5) <Polarity> (2)
        "
	::= { pmlma10AlmlineNetworkLaneAlarmWarning1Entry 17 }


pmlma10AlmLineRxPwrLowAlaPortn OBJECT-TYPE
	SYNTAX  EkiOnOff
	MAX-ACCESS read-only
	STATUS current
	DESCRIPTION
        "
        Line Trscv Rx Power Low :This
         OID indicates that the Trscv input
        power of port is lower than the
        threshold value written in the
         Trscv EEPROM <Help> Alarm indicating
        that the Trscv input power of port
        is lower than the threshold value
        written in the Trscv EEPROM <Condtype>
        LINE_RX_PWR_LOW_ALA_1 <Probcause>
        receiveFailure (41) <Alarmtype>
        equipmentAlarm (5) <Polarity> (2)
        "
	::= { pmlma10AlmlineNetworkLaneAlarmWarning1Entry 16 }


pmlma10AlmLineTempHighAlaPortn OBJECT-TYPE
	SYNTAX  EkiOnOff
	MAX-ACCESS read-only
	STATUS current
	DESCRIPTION
        "
        Line Trscv Temp High :This OID
        indicates that the Trscv temperature
        of port is higher than the threshold
        value written in the Trscv EEPROM
        <Help> Alarm indicating that the
        Trscv temperature of port is higher
        than the threshold value written
        in the Trscv EEPROM <Condtype>
         LINE_TEMP_HIGH_ALA_1 <Probcause>
        temperatureUnacceptable (51) <Alarmtype>
        equipmentAlarm (5) <Polarity> (2)
        "
	::= { pmlma10AlmlineNetworkLaneAlarmWarning1Entry 9 }


pmlma10AlmLineTempLowAlaPortn OBJECT-TYPE
	SYNTAX  EkiOnOff
	MAX-ACCESS read-only
	STATUS current
	DESCRIPTION
        "
        Line Trscv Temp Low :This OID
         indicates that the Trscv temperature
        of port is lower than the threshold
        value written in the Trscv EEPROM
        <Help> Alarm indicating that the
        Trscv temperature of port is lower
        than the threshold value written
        in the Trscv EEPROM <Condtype>
         LINE_TEMP_LOW_ALA_1 <Probcause>
        temperatureUnacceptable (51) <Alarmtype>
        equipmentAlarm (5) <Polarity> (2)
        "
	::= { pmlma10AlmlineNetworkLaneAlarmWarning1Entry 8 }


pmlma10AlmLineVccHighAlaPortn OBJECT-TYPE
	SYNTAX  EkiOnOff
	MAX-ACCESS read-only
	STATUS current
	DESCRIPTION
        "
        Line Trscv Power Supply High :This
        OID indicates that the Trscv power
        supply of port is higher than the
        threshold value written in the
         Trscv EEPROM <Help> Alarm indicating
        that the Trscv power supply of
         port is higher than the threshold
        value written in the Trscv EEPROM
        <Condtype> LINE_VCC_HIGH_ALA_1
         <Probcause> powerProblem (36)
         <Alarmtype> equipmentAlarm (5)
        <Polarity> (2)
        "
	::= { pmlma10AlmlineNetworkLaneAlarmWarning1Entry 7 }


pmlma10AlmLineVccLowAlaPortn OBJECT-TYPE
	SYNTAX  EkiOnOff
	MAX-ACCESS read-only
	STATUS current
	DESCRIPTION
        "
        Line Trscv Power Supply Low :This
        OID indicates that the Trscv power
        supply of port is lower than the
        threshold value written in the
         Trscv EEPROM <Help> Alarm indicating
        that the Trscv power supply of
         port is lower than the threshold
        value written in the Trscv EEPROM
        <Condtype> LINE_VCC_LOW_ALA_1 <Probcause>
        powerProblem (36) <Alarmtype> equipmentAlarm
        (5) <Polarity> (2)
        "
	::= { pmlma10AlmlineNetworkLaneAlarmWarning1Entry 6 }


pmlma10AlmLineTxBiasHighAlaPortn OBJECT-TYPE
	SYNTAX  EkiOnOff
	MAX-ACCESS read-only
	STATUS current
	DESCRIPTION
        "
        Line Trscv Bias High :This OID
        indicates that the Trscv laser
         bias current of port is higher
        than the threshold value written
        in the Trscv EEPROM <Help> Alarm
        indicating that the Trscv laser
        bias current of port is higher
         than the threshold value written
        in the Trscv EEPROM <Condtype>
         LINE_TX_BIAS_HIGH_ALA_1 <Probcause>
        transmitterFailure (56) <Alarmtype>
        equipmentAlarm (5) <Polarity> (2)
        "
	::= { pmlma10AlmlineNetworkLaneAlarmWarning1Entry 5 }


pmlma10AlmLineTxBiasLowAlaPortn OBJECT-TYPE
	SYNTAX  EkiOnOff
	MAX-ACCESS read-only
	STATUS current
	DESCRIPTION
        "
        Line Trscv Bias Low :This OID
         indicates that the Trscv laser
        bias current of port is lower than
        the threshold value written in
         the Trscv EEPROM <Help> Alarm
         indicating that the Trscv laser
        bias current of port is lower than
        the threshold value written in
         the Trscv EEPROM <Condtype> LINE_TX_BIAS_LOW_ALA_1
        <Probcause> transmitterFailure
         (56) <Alarmtype> equipmentAlarm
        (5) <Polarity> (2)
        "
	::= { pmlma10AlmlineNetworkLaneAlarmWarning1Entry 4 }


pmlma10AlmLineTxPwrHighAlaPortn OBJECT-TYPE
	SYNTAX  EkiOnOff
	MAX-ACCESS read-only
	STATUS current
	DESCRIPTION
        "
        Line Trscv Tx Power High :This
        OID indicates that the Trscv output
        power of port is higher than the
        threshold value written in the
         Trscv EEPROM <Help> Alarm indicating
        that the Trscv output power of
         port is higher than the threshold
        value written in the Trscv EEPROM
        <Condtype> LINE_TX_PWR_HIGH_ALA_1
        <Probcause> transmitterFailure
         (56) <Alarmtype> equipmentAlarm
        (5) <Polarity> (2)
        "
	::= { pmlma10AlmlineNetworkLaneAlarmWarning1Entry 3 }


pmlma10AlmLineTxPwrLowAlaPortn OBJECT-TYPE
	SYNTAX  EkiOnOff
	MAX-ACCESS read-only
	STATUS current
	DESCRIPTION
        "
        Line Trscv Tx Power Low :This
         OID indicates that the Trscv output
        power of port is lower than the
        threshold value written in the
         Trscv EEPROM <Help> Alarm indicating
        that the Trscv output power of
         port is lower than the threshold
        value written in the Trscv EEPROM
        <Condtype> LINE_TX_PWR_LOW_ALA_1
        <Probcause> transmitterFailure
         (56) <Alarmtype> equipmentAlarm
        (5) <Polarity> (2)
        "
	::= { pmlma10AlmlineNetworkLaneAlarmWarning1Entry 2 }


--- *********************************************************
---     TABLE for the pmlma10AlmlineNetworkLaneAlarmWarning2 articles
--- *********************************************************

pmlma10AlmlineNetworkLaneAlarmWarning2Table OBJECT-TYPE
	SYNTAX  SEQUENCE OF Pmlma10AlmlineNetworkLaneAlarmWarning2Entry
	MAX-ACCESS not-accessible
	STATUS current
	DESCRIPTION
        "
        List of pmlma10AlmlineNetworkLaneAlarmWarning2
        Article
        "
	::= { pmlma10AlmLineUrg 120 }


pmlma10AlmlineNetworkLaneAlarmWarning2Entry OBJECT-TYPE
	SYNTAX Pmlma10AlmlineNetworkLaneAlarmWarning2Entry
	MAX-ACCESS not-accessible
	STATUS current
	DESCRIPTION
        "
        Row definition for the pmlma10AlmlineNetworkLaneAlarmWarning2
        table
        "
	INDEX   { pmlma10AlmlineNetworkLaneAlarmWarning2Index }
	::= { pmlma10AlmlineNetworkLaneAlarmWarning2Table 1 }


Pmlma10AlmlineNetworkLaneAlarmWarning2Entry ::=
	SEQUENCE {
	pmlma10AlmlineNetworkLaneAlarmWarning2Index
		INTEGER,
	pmlma10AlmLineRxPwrHighWngPortn
		EkiOnOff,
	pmlma10AlmLineRxPwrLowWngPortn
		EkiOnOff,
	pmlma10AlmLineTempHighWngPortn
		EkiOnOff,
	pmlma10AlmLineTempLowWngPortn
		EkiOnOff,
	pmlma10AlmLineVccHighWngPortn
		EkiOnOff,
	pmlma10AlmLineVccLowWngPortn
		EkiOnOff,
	pmlma10AlmLineTxBiasHighWngPortn
		EkiOnOff,
	pmlma10AlmLineTxBiasLowWngPortn
		EkiOnOff,
	pmlma10AlmLineTxPwrHighWngPortn
		EkiOnOff,
	pmlma10AlmLineTxPwLowWngPortn
		EkiOnOff
	}


pmlma10AlmlineNetworkLaneAlarmWarning2Index OBJECT-TYPE
	SYNTAX  INTEGER(0..128)
	MAX-ACCESS  read-only
	STATUS current
	DESCRIPTION
        "
        Index definition for the pmlma10AlmlineNetworkLaneAlarmWarning2
        table
        "
	::= { pmlma10AlmlineNetworkLaneAlarmWarning2Entry 1 }


pmlma10AlmLineRxPwrHighWngPortn OBJECT-TYPE
	SYNTAX  EkiOnOff
	MAX-ACCESS read-only
	STATUS current
	DESCRIPTION
        "
        Line Trscv Rx Power High Warning
        :This OID indicates that the Trscv
        input power is higher than the
         threshold value written in the
        Trscv EEPROM <Help> Warning indicating
        that the Trscv input power is higher
        than the threshold value written
        in the Trscv EEPROM <Condtype>
         LINE_RX_PWR_HIGH_WNG_1 <Probcause>
        receiveFailure (41) <Alarmtype>
        equipmentAlarm (5) <Polarity> (2)
        "
	::= { pmlma10AlmlineNetworkLaneAlarmWarning2Entry 17 }


pmlma10AlmLineRxPwrLowWngPortn OBJECT-TYPE
	SYNTAX  EkiOnOff
	MAX-ACCESS read-only
	STATUS current
	DESCRIPTION
        "
        Line Trscv Rx Power Low Warning
        :This OID indicates that the Trscv
        input power is lower than the threshold
        value written in the Trscv EEPROM
        <Help> Warning indicating that
         the Trscv input power is lower
        than the threshold value written
        in the Trscv EEPROM <Condtype>
         LINE_RX_PWR_LOW_WNG_1 <Probcause>
        receiveFailure (41) <Alarmtype>
        equipmentAlarm (5) <Polarity> (2)
        "
	::= { pmlma10AlmlineNetworkLaneAlarmWarning2Entry 16 }


pmlma10AlmLineTempHighWngPortn OBJECT-TYPE
	SYNTAX  EkiOnOff
	MAX-ACCESS read-only
	STATUS current
	DESCRIPTION
        "
        Line Trscv Temp High Warning :This
        OID indicates that the Trscv temperature
        is higher than the threshold value
        written in the Trscv EEPROM <Help>
        Warning indicating that the Trscv
        temperature is higher than the
         threshold value written in the
        Trscv EEPROM <Condtype> LINE_TEMP_HIGH_WNG_1
        <Probcause> temperatureUnacceptable
        (51) <Alarmtype> equipmentAlarm
        (5) <Polarity> (2)
        "
	::= { pmlma10AlmlineNetworkLaneAlarmWarning2Entry 9 }


pmlma10AlmLineTempLowWngPortn OBJECT-TYPE
	SYNTAX  EkiOnOff
	MAX-ACCESS read-only
	STATUS current
	DESCRIPTION
        "
        Line Trscv Temp Low Warning :This
        OID indicates that the Trscv temperature
        is lower than the threshold value
        written in the Trscv EEPROM <Help>
        Warning indicating that the Trscv
        temperature is lower than the threshold
        value written in the Trscv EEPROM
        <Condtype> LINE_TEMP_LOW_WNG_1
         <Probcause> temperatureUnacceptable
        (51) <Alarmtype> equipmentAlarm
        (5) <Polarity> (2)
        "
	::= { pmlma10AlmlineNetworkLaneAlarmWarning2Entry 8 }


pmlma10AlmLineVccHighWngPortn OBJECT-TYPE
	SYNTAX  EkiOnOff
	MAX-ACCESS read-only
	STATUS current
	DESCRIPTION
        "
        Line Trscv Power Supply High Warning
        :This OID indicates that the Trscv
        power supply is higher than the
        threshold value written in the
         Trscv EEPROM <Help> Warning indicating
        that the Trscv power supply is
         higher than the threshold value
        written in the Trscv EEPROM <Condtype>
        LINE_VCC_HIGH_WNG_1 <Probcause>
        powerProblem (36) <Alarmtype> equipmentAlarm
        (5) <Polarity> (2)
        "
	::= { pmlma10AlmlineNetworkLaneAlarmWarning2Entry 7 }


pmlma10AlmLineVccLowWngPortn OBJECT-TYPE
	SYNTAX  EkiOnOff
	MAX-ACCESS read-only
	STATUS current
	DESCRIPTION
        "
        Line Trscv Power Supply Low Warning
        :This OID indicates that the Trscv
        power supply is lower than the
         threshold value written in the
        Trscv EEPROM <Help> Warning indicating
        that the Trscv power supply is
         lower than the threshold value
        written in the Trscv EEPROM <Condtype>
        LINE_VCC_LOW_WNG_1 <Probcause>
         powerProblem (36) <Alarmtype>
         equipmentAlarm (5) <Polarity>
         (2)
        "
	::= { pmlma10AlmlineNetworkLaneAlarmWarning2Entry 6 }


pmlma10AlmLineTxBiasHighWngPortn OBJECT-TYPE
	SYNTAX  EkiOnOff
	MAX-ACCESS read-only
	STATUS current
	DESCRIPTION
        "
        Line Trscv Bias High Warning :This
        OID indicates that the Trscv laser
        bias current is higher than the
        threshold value written in the
         Trscv EEPROM <Help> Warning indicating
        that the Trscv laser bias current
        is higher than the threshold value
        written in the Trscv EEPROM <Condtype>
        LINE_TX_BIAS_HIGH_WNG_1 <Probcause>
        transmitterFailure (56) <Alarmtype>
        equipmentAlarm (5) <Polarity> (2)
        "
	::= { pmlma10AlmlineNetworkLaneAlarmWarning2Entry 5 }


pmlma10AlmLineTxBiasLowWngPortn OBJECT-TYPE
	SYNTAX  EkiOnOff
	MAX-ACCESS read-only
	STATUS current
	DESCRIPTION
        "
        Line Trscv Bias Low Warning :This
        OID indicates that the Trscv laser
        bias current is lower than the
         threshold value written in the
        Trscv EEPROM <Help> Warning indicating
        that the Trscv laser bias current
        is lower than the threshold value
        written in the Trscv EEPROM <Condtype>
        LINE_TX_BIAS_LOW_WNG_1 <Probcause>
        transmitterFailure (56) <Alarmtype>
        equipmentAlarm (5) <Polarity> (2)
        "
	::= { pmlma10AlmlineNetworkLaneAlarmWarning2Entry 4 }


pmlma10AlmLineTxPwrHighWngPortn OBJECT-TYPE
	SYNTAX  EkiOnOff
	MAX-ACCESS read-only
	STATUS current
	DESCRIPTION
        "
        Line Trscv Tx Power High Warning
        :This OID indicates that the Trscv
        output power is higher than the
        threshold value written in the
         Trscv EEPROM <Help> Warning indicating
        that the Trscv output power is
         higher than the threshold value
        written in the Trscv EEPROM <Condtype>
        LINE_TX_PWR_HIGH_WNG_1 <Probcause>
        transmitterFailure (56) <Alarmtype>
        equipmentAlarm (5) <Polarity> (2)
        "
	::= { pmlma10AlmlineNetworkLaneAlarmWarning2Entry 3 }


pmlma10AlmLineTxPwLowWngPortn OBJECT-TYPE
	SYNTAX  EkiOnOff
	MAX-ACCESS read-only
	STATUS current
	DESCRIPTION
        "
        Line Trscv Tx Power Low Warning
        :This OID indicates that the Trscv
        output power is lower than the
         threshold value written in the
        Trscv EEPROM <Help> Warning indicating
        that the Trscv output power is
         lower than the threshold value
        written in the Trscv EEPROM <Condtype>
        LINE_TX_PW_LOW_WNG_1 <Probcause>
        transmitterFailure (56) <Alarmtype>
        equipmentAlarm (5) <Polarity> (2)
        "
	::= { pmlma10AlmlineNetworkLaneAlarmWarning2Entry 2 }


--- *********************************************************
---     TABLE for the pmlma10AlmlineHostLaneFault articles
--- *********************************************************

pmlma10AlmlineHostLaneFaultTable OBJECT-TYPE
	SYNTAX  SEQUENCE OF Pmlma10AlmlineHostLaneFaultEntry
	MAX-ACCESS not-accessible
	STATUS current
	DESCRIPTION
        "
        List of pmlma10AlmlineHostLaneFault
        Article
        "
	::= { pmlma10AlmLineUrg 152 }


pmlma10AlmlineHostLaneFaultEntry OBJECT-TYPE
	SYNTAX Pmlma10AlmlineHostLaneFaultEntry
	MAX-ACCESS not-accessible
	STATUS current
	DESCRIPTION
        "
        Row definition for the pmlma10AlmlineHostLaneFault
        table
        "
	INDEX   { pmlma10AlmlineHostLaneFaultIndex }
	::= { pmlma10AlmlineHostLaneFaultTable 1 }


Pmlma10AlmlineHostLaneFaultEntry ::=
	SEQUENCE {
	pmlma10AlmlineHostLaneFaultIndex
		INTEGER,
	pmlma10AlmLineSmBdiDetectedPortn
		EkiOnOff,
	pmlma10AlmLineSmBdiInsertedPortn
		EkiOnOff,
	pmlma10AlmLineLossOfFramePortn
		EkiOnOff,
	pmlma10AlmLineInputLossOfSignalPortn
		EkiOnOff
	}


pmlma10AlmlineHostLaneFaultIndex OBJECT-TYPE
	SYNTAX  INTEGER(0..128)
	MAX-ACCESS  read-only
	STATUS current
	DESCRIPTION
        "
        Index definition for the pmlma10AlmlineHostLaneFault
        table
        "
	::= { pmlma10AlmlineHostLaneFaultEntry 1 }


pmlma10AlmLineSmBdiDetectedPortn OBJECT-TYPE
	SYNTAX  EkiOnOff
	MAX-ACCESS read-only
	STATUS current
	DESCRIPTION
        "
        Line SM BDI Detected :This OID
        indicates a SM Backward Defect
         Indication is detected on the
         incoming Line signal <Help> Alarm
        indicating a SM Backward Defect
        Indication is detected on the incoming
        Line signal <Condtype> LINE_SM_BDI_DETECTED
        <Probcause> receiveFailure (41)
        <Alarmtype> integrityViolation
         (7) <Polarity> (2)
        "
	::= { pmlma10AlmlineHostLaneFaultEntry 5 }


pmlma10AlmLineSmBdiInsertedPortn OBJECT-TYPE
	SYNTAX  EkiOnOff
	MAX-ACCESS read-only
	STATUS current
	DESCRIPTION
        "
        Line SM BDI Inserted :This OID
        indicates a SM Backward Defect
         Indication is inserted on the
         outgoing Line signal <Help> Status
        indicating a SM Backward Defect
        Indication is inserted on the outgoing
        Line signal <Condtype> LINE_SM_BDI_INSERTED
        <Probcause> informationalStatus(1000)
        <Alarmtype> other (1) <Polarity>
        (2)
        "
	::= { pmlma10AlmlineHostLaneFaultEntry 4 }


pmlma10AlmLineLossOfFramePortn OBJECT-TYPE
	SYNTAX  EkiOnOff
	MAX-ACCESS read-only
	STATUS current
	DESCRIPTION
        "
        Line Loss Of Frame :This OID indicates
        the module is not aligned with
         the incoming Line signal <Help>
        Alarm indicating the module is
         not aligned with the incoming
         Line signal <Condtype> LINE_LOSS_OF_FRAME
        <Probcause> receiveFailure (41)
        <Alarmtype> integrityViolation
         (7) <Polarity> (2)
        "
	::= { pmlma10AlmlineHostLaneFaultEntry 3 }


pmlma10AlmLineInputLossOfSignalPortn OBJECT-TYPE
	SYNTAX  EkiOnOff
	MAX-ACCESS read-only
	STATUS current
	DESCRIPTION
        "
        Line Input Loss Of Signal :This
        OID indicates a Loss of Signal
         is detected on the Line Trscv
         <Help> Alarm indicating a Loss
        of Signal is detected on the Line
        Trscv <Condtype> LINE_INPUT_LOSS_OF_SIGNAL
        <Probcause> receiveFailure (41)
        <Alarmtype> physicalViolation (9)
        <Polarity> (2)
        "
	::= { pmlma10AlmlineHostLaneFaultEntry 2 }


--- *********************************************************
---     TABLE for the pmlma10AlmclientSfpAlmDdm articles
--- *********************************************************

pmlma10AlmclientSfpAlmDdmTable OBJECT-TYPE
	SYNTAX  SEQUENCE OF Pmlma10AlmclientSfpAlmDdmEntry
	MAX-ACCESS not-accessible
	STATUS current
	DESCRIPTION
        "
        List of pmlma10AlmclientSfpAlmDdm
        Article
        "
	::= { pmlma10AlmClientUrg 216 }


pmlma10AlmclientSfpAlmDdmEntry OBJECT-TYPE
	SYNTAX Pmlma10AlmclientSfpAlmDdmEntry
	MAX-ACCESS not-accessible
	STATUS current
	DESCRIPTION
        "
        Row definition for the pmlma10AlmclientSfpAlmDdm
        table
        "
	INDEX   { pmlma10AlmclientSfpAlmDdmIndex }
	::= { pmlma10AlmclientSfpAlmDdmTable 1 }


Pmlma10AlmclientSfpAlmDdmEntry ::=
	SEQUENCE {
	pmlma10AlmclientSfpAlmDdmIndex
		INTEGER,
	pmlma10AlmClientRxPwrHighAlaPortn
		EkiOnOff,
	pmlma10AlmClientRxPwrLowAlaPortn
		EkiOnOff,
	pmlma10AlmClientTempHighAlaPortn
		EkiOnOff,
	pmlma10AlmClientTempLowAlaPortn
		EkiOnOff,
	pmlma10AlmClientVccHighAlaPortn
		EkiOnOff,
	pmlma10AlmClientVccLowAlaPortn
		EkiOnOff,
	pmlma10AlmClientTxBiasHighAlaPortn
		EkiOnOff,
	pmlma10AlmClientTxBiasLowAlaPortn
		EkiOnOff,
	pmlma10AlmClientTxPwrHighAlaPortn
		EkiOnOff,
	pmlma10AlmClientTxPwrLowAlaPortn
		EkiOnOff
	}


pmlma10AlmclientSfpAlmDdmIndex OBJECT-TYPE
	SYNTAX  INTEGER(0..128)
	MAX-ACCESS  read-only
	STATUS current
	DESCRIPTION
        "
        Index definition for the pmlma10AlmclientSfpAlmDdm
        table
        "
	::= { pmlma10AlmclientSfpAlmDdmEntry 1 }


pmlma10AlmClientRxPwrHighAlaPortn OBJECT-TYPE
	SYNTAX  EkiOnOff
	MAX-ACCESS read-only
	STATUS current
	DESCRIPTION
        "
        Client Trscv Rx Power High :This
        OID indicates that the Trscv input
        power of port is higher than the
        threshold value written in the
         Trscv EEPROM <Help> Alarm indicating
        that the Trscv input power of port
        is higher than the threshold value
        written in the Trscv EEPROM <Condtype>
        CLIENT_RX_PWR_HIGH_ALA_1 <Probcause>
        receiveFailure (41) <Alarmtype>
        equipmentAlarm (5) <Polarity> (2)
        "
	::= { pmlma10AlmclientSfpAlmDdmEntry 17 }


pmlma10AlmClientRxPwrLowAlaPortn OBJECT-TYPE
	SYNTAX  EkiOnOff
	MAX-ACCESS read-only
	STATUS current
	DESCRIPTION
        "
        Client Trscv Rx Power Low :This
        OID indicates that the Trscv input
        power of port is lower than the
        threshold value written in the
         Trscv EEPROM <Help> Alarm indicating
        that the Trscv input power of port
        is lower than the threshold value
        written in the Trscv EEPROM <Condtype>
        CLIENT_RX_PWR_LOW_ALA_1 <Probcause>
        receiveFailure (41) <Alarmtype>
        equipmentAlarm (5) <Polarity> (2)
        "
	::= { pmlma10AlmclientSfpAlmDdmEntry 16 }


pmlma10AlmClientTempHighAlaPortn OBJECT-TYPE
	SYNTAX  EkiOnOff
	MAX-ACCESS read-only
	STATUS current
	DESCRIPTION
        "
        Client Trscv Temp High :This OID
        indicates that the Trscv temperature
        of port is higher than the threshold
        value written in the Trscv EEPROM
        <Help> Alarm indicating that the
        Trscv temperature of port is higher
        than the threshold value written
        in the Trscv EEPROM <Condtype>
         CLIENT_TEMP_HIGH_ALA_1 <Probcause>
        temperatureUnacceptable (51) <Alarmtype>
        equipmentAlarm (5) <Polarity> (2)
        "
	::= { pmlma10AlmclientSfpAlmDdmEntry 9 }


pmlma10AlmClientTempLowAlaPortn OBJECT-TYPE
	SYNTAX  EkiOnOff
	MAX-ACCESS read-only
	STATUS current
	DESCRIPTION
        "
        Client Trscv Temp Low :This OID
        indicates that the Trscv temperature
        of port is lower than the threshold
        value written in the Trscv EEPROM
        <Help> Alarm indicating that the
        Trscv temperature of port is lower
        than the threshold value written
        in the Trscv EEPROM <Condtype>
         CLIENT_TEMP_LOW_ALA_1 <Probcause>
        temperatureUnacceptable (51) <Alarmtype>
        equipmentAlarm (5) <Polarity> (2)
        "
	::= { pmlma10AlmclientSfpAlmDdmEntry 8 }


pmlma10AlmClientVccHighAlaPortn OBJECT-TYPE
	SYNTAX  EkiOnOff
	MAX-ACCESS read-only
	STATUS current
	DESCRIPTION
        "
        Client Trscv Power Supply High
        :This OID indicates that the Trscv
        power supply of port is higher
         than the threshold value written
        in the Trscv EEPROM <Help> Alarm
        indicating that the Trscv power
        supply of port is higher than the
        threshold value written in the
         Trscv EEPROM <Condtype> CLIENT_VCC_HIGH_ALA_1
        <Probcause> powerProblem (36) <Alarmtype>
        equipmentAlarm (5) <Polarity> (2)
        "
	::= { pmlma10AlmclientSfpAlmDdmEntry 7 }


pmlma10AlmClientVccLowAlaPortn OBJECT-TYPE
	SYNTAX  EkiOnOff
	MAX-ACCESS read-only
	STATUS current
	DESCRIPTION
        "
        Client Trscv Power Supply Low
         :This OID indicates that the Trscv
        power supply of port is lower than
        the threshold value written in
         the Trscv EEPROM <Help> Alarm
         indicating that the Trscv power
        supply of port is lower than the
        threshold value written in the
         Trscv EEPROM <Condtype> CLIENT_VCC_LOW_ALA_1
        <Probcause> powerProblem (36) <Alarmtype>
        equipmentAlarm (5) <Polarity> (2)
        "
	::= { pmlma10AlmclientSfpAlmDdmEntry 6 }


pmlma10AlmClientTxBiasHighAlaPortn OBJECT-TYPE
	SYNTAX  EkiOnOff
	MAX-ACCESS read-only
	STATUS current
	DESCRIPTION
        "
        Client Trscv Bias High :This OID
        indicates that the Trscv laser
         bias current of port is higher
        than the threshold value written
        in the Trscv EEPROM <Help> Alarm
        indicating that the Trscv laser
        bias current of port is higher
         than the threshold value written
        in the Trscv EEPROM <Condtype>
         CLIENT_TX_BIAS_HIGH_ALA_1 <Probcause>
        transmitterFailure (56) <Alarmtype>
        equipmentAlarm (5) <Polarity> (2)
        "
	::= { pmlma10AlmclientSfpAlmDdmEntry 5 }


pmlma10AlmClientTxBiasLowAlaPortn OBJECT-TYPE
	SYNTAX  EkiOnOff
	MAX-ACCESS read-only
	STATUS current
	DESCRIPTION
        "
        Client Trscv Bias Low :This OID
        indicates that the Trscv laser
         bias current of port is lower
         than the threshold value written
        in the Trscv EEPROM <Help> Alarm
        indicating that the Trscv laser
        bias current of port is lower than
        the threshold value written in
         the Trscv EEPROM <Condtype> CLIENT_TX_BIAS_LOW_ALA_1
        <Probcause> transmitterFailure
         (56) <Alarmtype> equipmentAlarm
        (5) <Polarity> (2)
        "
	::= { pmlma10AlmclientSfpAlmDdmEntry 4 }


pmlma10AlmClientTxPwrHighAlaPortn OBJECT-TYPE
	SYNTAX  EkiOnOff
	MAX-ACCESS read-only
	STATUS current
	DESCRIPTION
        "
        Client Trscv Tx Power High :This
        OID indicates that the Trscv output
        power of port is higher than the
        threshold value written in the
         Trscv EEPROM <Help> Alarm indicating
        that the Trscv output power of
         port is higher than the threshold
        value written in the Trscv EEPROM
        <Condtype> CLIENT_TX_PWR_HIGH_ALA_1
        <Probcause> transmitterFailure
         (56) <Alarmtype> equipmentAlarm
        (5) <Polarity> (2)
        "
	::= { pmlma10AlmclientSfpAlmDdmEntry 3 }


pmlma10AlmClientTxPwrLowAlaPortn OBJECT-TYPE
	SYNTAX  EkiOnOff
	MAX-ACCESS read-only
	STATUS current
	DESCRIPTION
        "
        Client Trscv Tx Power Low :This
        OID indicates that the Trscv output
        power of port is lower than the
        threshold value written in the
         Trscv EEPROM <Help> Alarm indicating
        that the Trscv output power of
         port is lower than the threshold
        value written in the Trscv EEPROM
        <Condtype> CLIENT_TX_PWR_LOW_ALA_1
        <Probcause> transmitterFailure
         (56) <Alarmtype> equipmentAlarm
        (5) <Polarity> (2)
        "
	::= { pmlma10AlmclientSfpAlmDdmEntry 2 }


--- *********************************************************
---     TABLE for the pmlma10AlmclientSfpWarnDdm articles
--- *********************************************************

pmlma10AlmclientSfpWarnDdmTable OBJECT-TYPE
	SYNTAX  SEQUENCE OF Pmlma10AlmclientSfpWarnDdmEntry
	MAX-ACCESS not-accessible
	STATUS current
	DESCRIPTION
        "
        List of pmlma10AlmclientSfpWarnDdm
        Article
        "
	::= { pmlma10AlmClientNurg 232 }


pmlma10AlmclientSfpWarnDdmEntry OBJECT-TYPE
	SYNTAX Pmlma10AlmclientSfpWarnDdmEntry
	MAX-ACCESS not-accessible
	STATUS current
	DESCRIPTION
        "
        Row definition for the pmlma10AlmclientSfpWarnDdm
        table
        "
	INDEX   { pmlma10AlmclientSfpWarnDdmIndex }
	::= { pmlma10AlmclientSfpWarnDdmTable 1 }


Pmlma10AlmclientSfpWarnDdmEntry ::=
	SEQUENCE {
	pmlma10AlmclientSfpWarnDdmIndex
		INTEGER,
	pmlma10AlmClientRxPwrHighWngPortn
		EkiOnOff,
	pmlma10AlmClientRxPwrLowWngPortn
		EkiOnOff,
	pmlma10AlmClientTempHighWngPortn
		EkiOnOff,
	pmlma10AlmClientTempLowWngPortn
		EkiOnOff,
	pmlma10AlmClientVccHighWngPortn
		EkiOnOff,
	pmlma10AlmClientVccLowWngPortn
		EkiOnOff,
	pmlma10AlmClientTxBiasHighWngPortn
		EkiOnOff,
	pmlma10AlmClientTxBiasLowWngPortn
		EkiOnOff,
	pmlma10AlmClientTxPwrHighWngPortn
		EkiOnOff,
	pmlma10AlmClientTxPwLowWngPortn
		EkiOnOff
	}


pmlma10AlmclientSfpWarnDdmIndex OBJECT-TYPE
	SYNTAX  INTEGER(0..128)
	MAX-ACCESS  read-only
	STATUS current
	DESCRIPTION
        "
        Index definition for the pmlma10AlmclientSfpWarnDdm
        table
        "
	::= { pmlma10AlmclientSfpWarnDdmEntry 1 }


pmlma10AlmClientRxPwrHighWngPortn OBJECT-TYPE
	SYNTAX  EkiOnOff
	MAX-ACCESS read-only
	STATUS current
	DESCRIPTION
        "
        Client Trscv Rx Power High Warning
        :This OID indicates that the Trscv
        input power is higher than the
         threshold value written in the
        Trscv EEPROM <Help> Warning indicating
        that the Trscv input power is higher
        than the threshold value written
        in the Trscv EEPROM <Condtype>
         CLIENT_RX_PWR_HIGH_WNG_1 <Probcause>
        receiveFailure (41) <Alarmtype>
        equipmentAlarm (5) <Polarity> (2)
        "
	::= { pmlma10AlmclientSfpWarnDdmEntry 17 }


pmlma10AlmClientRxPwrLowWngPortn OBJECT-TYPE
	SYNTAX  EkiOnOff
	MAX-ACCESS read-only
	STATUS current
	DESCRIPTION
        "
        Client Trscv Rx Power Low Warning
        :This OID indicates that the Trscv
        input power is lower than the threshold
        value written in the Trscv EEPROM
        <Help> Warning indicating that
         the Trscv input power is lower
        than the threshold value written
        in the Trscv EEPROM <Condtype>
         CLIENT_RX_PWR_LOW_WNG_1 <Probcause>
        receiveFailure (41) <Alarmtype>
        equipmentAlarm (5) <Polarity> (2)
        "
	::= { pmlma10AlmclientSfpWarnDdmEntry 16 }


pmlma10AlmClientTempHighWngPortn OBJECT-TYPE
	SYNTAX  EkiOnOff
	MAX-ACCESS read-only
	STATUS current
	DESCRIPTION
        "
        Client Trscv Temp High Warning
        :This OID indicates that the Trscv
        temperature is higher than the
         threshold value written in the
        Trscv EEPROM <Help> Warning indicating
        that the Trscv temperature is higher
        than the threshold value written
        in the Trscv EEPROM <Condtype>
         CLIENT_TEMP_HIGH_WNG_1 <Probcause>
        temperatureUnacceptable (51) <Alarmtype>
        equipmentAlarm (5) <Polarity> (2)
        "
	::= { pmlma10AlmclientSfpWarnDdmEntry 9 }


pmlma10AlmClientTempLowWngPortn OBJECT-TYPE
	SYNTAX  EkiOnOff
	MAX-ACCESS read-only
	STATUS current
	DESCRIPTION
        "
        Client Trscv Temp Low Warning
         :This OID indicates that the Trscv
        temperature is lower than the threshold
        value written in the Trscv EEPROM
        <Help> Warning indicating that
         the Trscv temperature is lower
        than the threshold value written
        in the Trscv EEPROM <Condtype>
         CLIENT_TEMP_LOW_WNG_1 <Probcause>
        temperatureUnacceptable (51) <Alarmtype>
        equipmentAlarm (5) <Polarity> (2)
        "
	::= { pmlma10AlmclientSfpWarnDdmEntry 8 }


pmlma10AlmClientVccHighWngPortn OBJECT-TYPE
	SYNTAX  EkiOnOff
	MAX-ACCESS read-only
	STATUS current
	DESCRIPTION
        "
        Client Trscv Power Supply High
        Warning :This OID indicates that
        the Trscv power supply is higher
        than the threshold value written
        in the Trscv EEPROM <Help> Warning
        indicating that the Trscv power
        supply is higher than the threshold
        value written in the Trscv EEPROM
        <Condtype> CLIENT_VCC_HIGH_WNG_1
        <Probcause> powerProblem (36) <Alarmtype>
        equipmentAlarm (5) <Polarity> (2)
        "
	::= { pmlma10AlmclientSfpWarnDdmEntry 7 }


pmlma10AlmClientVccLowWngPortn OBJECT-TYPE
	SYNTAX  EkiOnOff
	MAX-ACCESS read-only
	STATUS current
	DESCRIPTION
        "
        Client Trscv Power Supply Low
         Warning :This OID indicates that
        the Trscv power supply is lower
        than the threshold value written
        in the Trscv EEPROM <Help> Warning
        indicating that the Trscv power
        supply is lower than the threshold
        value written in the Trscv EEPROM
        <Condtype> CLIENT_VCC_LOW_WNG_1
        <Probcause> powerProblem (36) <Alarmtype>
        equipmentAlarm (5) <Polarity> (2)
        "
	::= { pmlma10AlmclientSfpWarnDdmEntry 6 }


pmlma10AlmClientTxBiasHighWngPortn OBJECT-TYPE
	SYNTAX  EkiOnOff
	MAX-ACCESS read-only
	STATUS current
	DESCRIPTION
        "
        Client Trscv Bias High Warning
        :This OID indicates that the Trscv
        laser bias current is higher than
        the threshold value written in
         the Trscv EEPROM <Help> Warning
        indicating that the Trscv laser
        bias current is higher than the
        threshold value written in the
         Trscv EEPROM <Condtype> CLIENT_TX_BIAS_HIGH_WNG_1
        <Probcause> transmitterFailure
         (56) <Alarmtype> equipmentAlarm
        (5) <Polarity> (2)
        "
	::= { pmlma10AlmclientSfpWarnDdmEntry 5 }


pmlma10AlmClientTxBiasLowWngPortn OBJECT-TYPE
	SYNTAX  EkiOnOff
	MAX-ACCESS read-only
	STATUS current
	DESCRIPTION
        "
        Client Trscv Bias Low Warning
         :This OID indicates that the Trscv
        laser bias current is lower than
        the threshold value written in
         the Trscv EEPROM <Help> Warning
        indicating that the Trscv laser
        bias current is lower than the
         threshold value written in the
        Trscv EEPROM <Condtype> CLIENT_TX_BIAS_LOW_WNG_1
        <Probcause> transmitterFailure
         (56) <Alarmtype> equipmentAlarm
        (5) <Polarity> (2)
        "
	::= { pmlma10AlmclientSfpWarnDdmEntry 4 }


pmlma10AlmClientTxPwrHighWngPortn OBJECT-TYPE
	SYNTAX  EkiOnOff
	MAX-ACCESS read-only
	STATUS current
	DESCRIPTION
        "
        Client Trscv Tx Power High Warning
        :This OID indicates that the Trscv
        output power is higher than the
        threshold value written in the
         Trscv EEPROM <Help> Warning indicating
        that the Trscv output power is
         higher than the threshold value
        written in the Trscv EEPROM <Condtype>
        CLIENT_TX_PWR_HIGH_WNG_1 <Probcause>
        transmitterFailure (56) <Alarmtype>
        equipmentAlarm (5) <Polarity> (2)
        "
	::= { pmlma10AlmclientSfpWarnDdmEntry 3 }


pmlma10AlmClientTxPwLowWngPortn OBJECT-TYPE
	SYNTAX  EkiOnOff
	MAX-ACCESS read-only
	STATUS current
	DESCRIPTION
        "
        Client Trscv Tx Power Low Warning
        :This OID indicates that the Trscv
        output power is lower than the
         threshold value written in the
        Trscv EEPROM <Help> Warning indicating
        that the Trscv output power is
         lower than the threshold value
        written in the Trscv EEPROM <Condtype>
        CLIENT_TX_PW_LOW_WNG_1 <Probcause>
        transmitterFailure (56) <Alarmtype>
        equipmentAlarm (5) <Polarity> (2)
        "
	::= { pmlma10AlmclientSfpWarnDdmEntry 2 }







--- *****************************************************
--- $$$$$$$$$$$$$$$$$$$$$$$$$$$$$$$$$$$$$$$$$$$$$$$$$$$$$
---     CONTROLS
--- $$$$$$$$$$$$$$$$$$$$$$$$$$$$$$$$$$$$$$$$$$$$$$$$$$$$$
--- *****************************************************



--- *****************************************************
---     LEAF for the confMgnt1 article
--- *****************************************************
pmlma10CtrlconfMgnt1 OBJECT IDENTIFIER ::= { pmlma10CtrlOther 1 }




pmlma10CtrlConf2Clear1 OBJECT-TYPE
	  SYNTAX EkiOnOff
	  MAX-ACCESS read-write
	  STATUS current
	  DESCRIPTION
        "
        Clear Configuration Tables :This
        OID clears the configuration tables
        from configuration2 in the flash.
         <Help>  This control restores
         the default configuration of the
        module
        "
	  ::= { pmlma10CtrlconfMgnt1 14 }



pmlma10CtrlConf2Flash1 OBJECT-TYPE
	  SYNTAX EkiOnOff
	  MAX-ACCESS read-write
	  STATUS current
	  DESCRIPTION
        "
        Write Configuration Tables :This
        OID saves the current configuration
        of the PM as configuration2 in
         the flash.  <Help>  This control
        saves the customer configuration
        on the module
        "
	  ::= { pmlma10CtrlconfMgnt1 10 }



pmlma10CtrlConf2Load1 OBJECT-TYPE
	  SYNTAX EkiOnOff
	  MAX-ACCESS read-write
	  STATUS current
	  DESCRIPTION
        "
        Load Configuration Tables Set
         Nb 2 :When set this OID enables
        loading from flash configuration2
        into the PM.
        "
	  ::= { pmlma10CtrlconfMgnt1 2 }



pmlma10CtrlConf1Load1 OBJECT-TYPE
	  SYNTAX EkiOnOff
	  MAX-ACCESS read-write
	  STATUS current
	  DESCRIPTION
        "
        Load Configuration Tables Set
         Nb 1 :When set this OID enables
        loading from flash configuration1
        into the PM.
        "
	  ::= { pmlma10CtrlconfMgnt1 1 }



--- *****************************************************
---     LEAF for the synth4 article
--- *****************************************************
pmlma10Ctrlsynth4 OBJECT IDENTIFIER ::= { pmlma10CtrlOther 4 }




pmlma10CtrlCorrelatOff OBJECT-TYPE
	  SYNTAX EkiOnOff
	  MAX-ACCESS read-write
	  STATUS current
	  DESCRIPTION
        "
        Disable Alarm Correlation :This
        OID disables the alarm correlation
        in the PM.
        "
	  ::= { pmlma10Ctrlsynth4 2 }



pmlma10CtrlCorrelatOn OBJECT-TYPE
	  SYNTAX EkiOnOff
	  MAX-ACCESS read-write
	  STATUS current
	  DESCRIPTION
        "
        Enable Alarm Correlation :This
        OID enables the alarm correlation
        in the PM.
        "
	  ::= { pmlma10Ctrlsynth4 1 }



--- *****************************************************
---     LEAF for the swMgnt article
--- *****************************************************
pmlma10CtrlswMgnt OBJECT IDENTIFIER ::= { pmlma10CtrlOther 5 }




pmlma10CtrlLoadSwBank2 OBJECT-TYPE
	  SYNTAX EkiOnOff
	  MAX-ACCESS read-write
	  STATUS current
	  DESCRIPTION
        "
        Set Software Nb 2 As Active :This
        OID, when set, loads the SW from
        bank2 into the PM. It must be followed
        by a reset.  <Help>  This controls
        selects the second SW bank as the
        active bank for the next module
        reset
        "
	  ::= { pmlma10CtrlswMgnt 6 }



pmlma10CtrlLoadSwBank1 OBJECT-TYPE
	  SYNTAX EkiOnOff
	  MAX-ACCESS read-write
	  STATUS current
	  DESCRIPTION
        "
        Set Software Nb 1 As Active :This
        OID, when set, loads the SW from
        bank1 into the PM. It must be followed
        by a reset.  <Help>  This controls
        selects the first SW bank as the
        active bank for the next module
        reset
        "
	  ::= { pmlma10CtrlswMgnt 5 }



pmlma10CtrlWarmReset OBJECT-TYPE
	  SYNTAX EkiOnOff
	  MAX-ACCESS read-write
	  STATUS current
	  DESCRIPTION
        "
        PM Warm Reset :This OID, when
         set, causes a warm reset of the
        PM. This reset is not traffic affecting,
        and the configuration of PM remains
        unchanged.  <Help>  This control
        initiates a warm reset of the module.
        "
	  ::= { pmlma10CtrlswMgnt 3 }



pmlma10CtrlColdReset OBJECT-TYPE
	  SYNTAX EkiOnOff
	  MAX-ACCESS read-write
	  STATUS current
	  DESCRIPTION
        "
        PM Cold Reset :This OID, when
         set, causes a cold reset of the
        PM. This reset is traffic affecting,
        and the configuration of PM is
         reloaded on start-up.  <Help>
          This control initiates a cold
        reset of the module.
        "
	  ::= { pmlma10CtrlswMgnt 2 }



--- *****************************************************
---     LEAF for the gwMgnt article
--- *****************************************************
pmlma10CtrlgwMgnt OBJECT IDENTIFIER ::= { pmlma10CtrlOther 6 }




pmlma10CtrlLoadGwBank4 OBJECT-TYPE
	  SYNTAX EkiOnOff
	  MAX-ACCESS read-write
	  STATUS current
	  DESCRIPTION
        "
        Set Gateware Nb 4 As Active :This
        OID, when set, loads the GW from
        bank4 (Flash) into the PM. It is
        followed by an automatic gateware
        cold reset.
        "
	  ::= { pmlma10CtrlgwMgnt 8 }



pmlma10CtrlLoadGwBank3 OBJECT-TYPE
	  SYNTAX EkiOnOff
	  MAX-ACCESS read-write
	  STATUS current
	  DESCRIPTION
        "
        Set Gateware Nb 3 As Active :This
        OID, when set, loads the GW from
        bank3 (Flash) into the PM. It is
        followed by an automatic gateware
        cold reset.  <Help>  This controls
        initiates a cold reset of the module
        and select the third GW bank as
        the active bank
        "
	  ::= { pmlma10CtrlgwMgnt 7 }



pmlma10CtrlLoadGwBank2 OBJECT-TYPE
	  SYNTAX EkiOnOff
	  MAX-ACCESS read-write
	  STATUS current
	  DESCRIPTION
        "
        Set Gateware Nb 2 As Active :This
        OID, when set, loads the GW from
        bank2 (Flash) into the PM. It is
        followed by an automatic gateware
        cold reset.
        "
	  ::= { pmlma10CtrlgwMgnt 6 }



pmlma10CtrlLoadGwBank1 OBJECT-TYPE
	  SYNTAX EkiOnOff
	  MAX-ACCESS read-write
	  STATUS current
	  DESCRIPTION
        "
        Set Gateware Nb 1 As Active :This
        OID, when set, loads the GW from
        bank1 (Flash) into the PM. It is
        followed by an automatic gateware
        cold reset.  <Help>  This controls
        initiates a cold reset of the module
        and select the first GW bank as
        the active bank
        "
	  ::= { pmlma10CtrlgwMgnt 5 }



pmlma10CtrlCurrentGwReset OBJECT-TYPE
	  SYNTAX EkiOnOff
	  MAX-ACCESS read-write
	  STATUS current
	  DESCRIPTION
        "
        Active Gateware Reset :This OID,
        when set, resets the active gateware.
        It is traffic affecting.
        "
	  ::= { pmlma10CtrlgwMgnt 1 }



--- *********************************************************
---     TABLE for the pmlma10CtrlaccessLoop articles
--- *********************************************************

pmlma10CtrlaccessLoopTable OBJECT-TYPE
	SYNTAX  SEQUENCE OF Pmlma10CtrlaccessLoopEntry
	MAX-ACCESS not-accessible
	STATUS current
	DESCRIPTION
        "
        List of pmlma10CtrlaccessLoop
         Article
        "
	::= { pmlma10CtrlClient 16 }


pmlma10CtrlaccessLoopEntry OBJECT-TYPE
	SYNTAX Pmlma10CtrlaccessLoopEntry
	MAX-ACCESS not-accessible
	STATUS current
	DESCRIPTION
        "
        Row definition for the pmlma10CtrlaccessLoop
        table
        "
	INDEX   { pmlma10CtrlaccessLoopIndex }
	::= { pmlma10CtrlaccessLoopTable 1 }


Pmlma10CtrlaccessLoopEntry ::=
	SEQUENCE {
	pmlma10CtrlaccessLoopIndex
		INTEGER,
	pmlma10CtrlaccessLoopPortn
		EkiState
	}


pmlma10CtrlaccessLoopIndex OBJECT-TYPE
	SYNTAX  INTEGER(0..128)
	MAX-ACCESS  read-only
	STATUS current
	DESCRIPTION
        "
        Index definition for the pmlma10CtrlaccessLoop
        table
        "
	::= { pmlma10CtrlaccessLoopEntry 1 }


pmlma10CtrlaccessLoopPortn OBJECT-TYPE
	SYNTAX  EkiState
	MAX-ACCESS read-write
	STATUS current
	DESCRIPTION
        "
        Client Facility Loopback :This
        OID, when set at '1' puts the client
        port in loopback, looping the received
        10 Gb/s signal on the transmit
         10 Gb/s output.  <Help> This control
        enables the Out Loopback on the
        client port, looping the client
        input signal on the client output
        "
	::= { pmlma10CtrlaccessLoopEntry 2 }


--- *********************************************************
---     TABLE for the pmlma10CtrlclientLoopToLine articles
--- *********************************************************

pmlma10CtrlclientLoopToLineTable OBJECT-TYPE
	SYNTAX  SEQUENCE OF Pmlma10CtrlclientLoopToLineEntry
	MAX-ACCESS not-accessible
	STATUS current
	DESCRIPTION
        "
        List of pmlma10CtrlclientLoopToLine
        Article
        "
	::= { pmlma10CtrlClient 17 }


pmlma10CtrlclientLoopToLineEntry OBJECT-TYPE
	SYNTAX Pmlma10CtrlclientLoopToLineEntry
	MAX-ACCESS not-accessible
	STATUS current
	DESCRIPTION
        "
        Row definition for the pmlma10CtrlclientLoopToLine
        table
        "
	INDEX   { pmlma10CtrlclientLoopToLineIndex }
	::= { pmlma10CtrlclientLoopToLineTable 1 }


Pmlma10CtrlclientLoopToLineEntry ::=
	SEQUENCE {
	pmlma10CtrlclientLoopToLineIndex
		INTEGER,
	pmlma10CtrlclientLoopToLinePortn
		EkiState
	}


pmlma10CtrlclientLoopToLineIndex OBJECT-TYPE
	SYNTAX  INTEGER(0..128)
	MAX-ACCESS  read-only
	STATUS current
	DESCRIPTION
        "
        Index definition for the pmlma10CtrlclientLoopToLine
        table
        "
	::= { pmlma10CtrlclientLoopToLineEntry 1 }


pmlma10CtrlclientLoopToLinePortn OBJECT-TYPE
	SYNTAX  EkiState
	MAX-ACCESS read-write
	STATUS current
	DESCRIPTION
        "
        Client Terminal Loopback :This
        OID, when set, puts the client
         port in loop back, looping the
        10 Gb/s output signal on the 10
        Gb/s input.<Help> This control
         enables the In Loopback on the
        client port, looping the client
        output signal on the client input
        "
	::= { pmlma10CtrlclientLoopToLineEntry 2 }


--- *********************************************************
---     TABLE for the pmlma10CtrlcsfUpIns articles
--- *********************************************************

pmlma10CtrlcsfUpInsTable OBJECT-TYPE
	SYNTAX  SEQUENCE OF Pmlma10CtrlcsfUpInsEntry
	MAX-ACCESS not-accessible
	STATUS current
	DESCRIPTION
        "
        List of pmlma10CtrlcsfUpIns Article
        "
	::= { pmlma10CtrlClient 21 }


pmlma10CtrlcsfUpInsEntry OBJECT-TYPE
	SYNTAX Pmlma10CtrlcsfUpInsEntry
	MAX-ACCESS not-accessible
	STATUS current
	DESCRIPTION
        "
        Row definition for the pmlma10CtrlcsfUpIns
        table
        "
	INDEX   { pmlma10CtrlcsfUpInsIndex }
	::= { pmlma10CtrlcsfUpInsTable 1 }


Pmlma10CtrlcsfUpInsEntry ::=
	SEQUENCE {
	pmlma10CtrlcsfUpInsIndex
		INTEGER,
	pmlma10CtrlcsfUpInsPortn
		EkiState
	}


pmlma10CtrlcsfUpInsIndex OBJECT-TYPE
	SYNTAX  INTEGER(0..128)
	MAX-ACCESS  read-only
	STATUS current
	DESCRIPTION
        "
        Index definition for the pmlma10CtrlcsfUpIns
        table
        "
	::= { pmlma10CtrlcsfUpInsEntry 1 }


pmlma10CtrlcsfUpInsPortn OBJECT-TYPE
	SYNTAX  EkiState
	MAX-ACCESS read-write
	STATUS current
	DESCRIPTION
        "
        Client Signal Fail Insertion :This
        OID, when set, inserts  a client
        signal fail in the upstream client
        Port.  <Help>  This control inserts
        a Client Signal Fail for the client
        port
        "
	::= { pmlma10CtrlcsfUpInsEntry 2 }


--- *********************************************************
---     TABLE for the pmlma10CtrlcaisDwIns articles
--- *********************************************************

pmlma10CtrlcaisDwInsTable OBJECT-TYPE
	SYNTAX  SEQUENCE OF Pmlma10CtrlcaisDwInsEntry
	MAX-ACCESS not-accessible
	STATUS current
	DESCRIPTION
        "
        List of pmlma10CtrlcaisDwIns Article
        "
	::= { pmlma10CtrlClient 22 }


pmlma10CtrlcaisDwInsEntry OBJECT-TYPE
	SYNTAX Pmlma10CtrlcaisDwInsEntry
	MAX-ACCESS not-accessible
	STATUS current
	DESCRIPTION
        "
        Row definition for the pmlma10CtrlcaisDwIns
        table
        "
	INDEX   { pmlma10CtrlcaisDwInsIndex }
	::= { pmlma10CtrlcaisDwInsTable 1 }


Pmlma10CtrlcaisDwInsEntry ::=
	SEQUENCE {
	pmlma10CtrlcaisDwInsIndex
		INTEGER,
	pmlma10CtrlcaisDwInsPortn
		EkiState
	}


pmlma10CtrlcaisDwInsIndex OBJECT-TYPE
	SYNTAX  INTEGER(0..128)
	MAX-ACCESS  read-only
	STATUS current
	DESCRIPTION
        "
        Index definition for the pmlma10CtrlcaisDwIns
        table
        "
	::= { pmlma10CtrlcaisDwInsEntry 1 }


pmlma10CtrlcaisDwInsPortn OBJECT-TYPE
	SYNTAX  EkiState
	MAX-ACCESS read-write
	STATUS current
	DESCRIPTION
        "
        Client AIS Insertion :This OID,
        when set, inserts a client AIS
         on the downstream client Port.
         <Help>  This control inserts a
        Client AIS for the client port
        "
	::= { pmlma10CtrlcaisDwInsEntry 2 }


--- *********************************************************
---     TABLE for the pmlma10CtrlcommAccessLoop articles
--- *********************************************************

pmlma10CtrlcommAccessLoopTable OBJECT-TYPE
	SYNTAX  SEQUENCE OF Pmlma10CtrlcommAccessLoopEntry
	MAX-ACCESS not-accessible
	STATUS current
	DESCRIPTION
        "
        List of pmlma10CtrlcommAccessLoop
        Article
        "
	::= { pmlma10CtrlLine 64 }


pmlma10CtrlcommAccessLoopEntry OBJECT-TYPE
	SYNTAX Pmlma10CtrlcommAccessLoopEntry
	MAX-ACCESS not-accessible
	STATUS current
	DESCRIPTION
        "
        Row definition for the pmlma10CtrlcommAccessLoop
        table
        "
	INDEX   { pmlma10CtrlcommAccessLoopIndex }
	::= { pmlma10CtrlcommAccessLoopTable 1 }


Pmlma10CtrlcommAccessLoopEntry ::=
	SEQUENCE {
	pmlma10CtrlcommAccessLoopIndex
		INTEGER,
	pmlma10CtrlcommAccessLoopPortn
		EkiState
	}


pmlma10CtrlcommAccessLoopIndex OBJECT-TYPE
	SYNTAX  INTEGER(0..128)
	MAX-ACCESS  read-only
	STATUS current
	DESCRIPTION
        "
        Index definition for the pmlma10CtrlcommAccessLoop
        table
        "
	::= { pmlma10CtrlcommAccessLoopEntry 1 }


pmlma10CtrlcommAccessLoopPortn OBJECT-TYPE
	SYNTAX  EkiState
	MAX-ACCESS read-write
	STATUS current
	DESCRIPTION
        "
        Line Terminal Loopback :This OID,
        when set, puts the module in common
        access loop back, looping the 10
        Gb/s output signal on the 10 Gb/s
        input.<Help> This control enables
        the In Loopback on the line port,
        looping the 100 Gb/s output signal
        on the 100 Gb/s input
        "
	::= { pmlma10CtrlcommAccessLoopEntry 2 }


--- *********************************************************
---     TABLE for the pmlma10CtrllineLoop articles
--- *********************************************************

pmlma10CtrllineLoopTable OBJECT-TYPE
	SYNTAX  SEQUENCE OF Pmlma10CtrllineLoopEntry
	MAX-ACCESS not-accessible
	STATUS current
	DESCRIPTION
        "
        List of pmlma10CtrllineLoop Article
        "
	::= { pmlma10CtrlLine 66 }


pmlma10CtrllineLoopEntry OBJECT-TYPE
	SYNTAX Pmlma10CtrllineLoopEntry
	MAX-ACCESS not-accessible
	STATUS current
	DESCRIPTION
        "
        Row definition for the pmlma10CtrllineLoop
        table
        "
	INDEX   { pmlma10CtrllineLoopIndex }
	::= { pmlma10CtrllineLoopTable 1 }


Pmlma10CtrllineLoopEntry ::=
	SEQUENCE {
	pmlma10CtrllineLoopIndex
		INTEGER,
	pmlma10CtrllineLoopPortn
		EkiState
	}


pmlma10CtrllineLoopIndex OBJECT-TYPE
	SYNTAX  INTEGER(0..128)
	MAX-ACCESS  read-only
	STATUS current
	DESCRIPTION
        "
        Index definition for the pmlma10CtrllineLoop
        table
        "
	::= { pmlma10CtrllineLoopEntry 1 }


pmlma10CtrllineLoopPortn OBJECT-TYPE
	SYNTAX  EkiState
	MAX-ACCESS read-write
	STATUS current
	DESCRIPTION
        "
        Line Facility Loopback :This OID,
        when set at '1' puts the module
        in line loopback mode, looping
         the received 10 Gb/s signal on
        the transmit 10 Gb/s output. The
        Upstream part of the module is
         timed on the 10 Gb/s recovered
        clock in that case.<Help> This
         control enables the Out Loopback
        on the line port, looping the 100
        Gb/s input signal on the 100 Gb/s
        output
        "
	::= { pmlma10CtrllineLoopEntry 2 }


--- *********************************************************
---     TABLE for the pmlma10CtrlfecDisable articles
--- *********************************************************

pmlma10CtrlfecDisableTable OBJECT-TYPE
	SYNTAX  SEQUENCE OF Pmlma10CtrlfecDisableEntry
	MAX-ACCESS not-accessible
	STATUS current
	DESCRIPTION
        "
        List of pmlma10CtrlfecDisable
         Article
        "
	::= { pmlma10CtrlLine 69 }


pmlma10CtrlfecDisableEntry OBJECT-TYPE
	SYNTAX Pmlma10CtrlfecDisableEntry
	MAX-ACCESS not-accessible
	STATUS current
	DESCRIPTION
        "
        Row definition for the pmlma10CtrlfecDisable
        table
        "
	INDEX   { pmlma10CtrlfecDisableIndex }
	::= { pmlma10CtrlfecDisableTable 1 }


Pmlma10CtrlfecDisableEntry ::=
	SEQUENCE {
	pmlma10CtrlfecDisableIndex
		INTEGER,
	pmlma10CtrlfecDisablePortn
		EkiState
	}


pmlma10CtrlfecDisableIndex OBJECT-TYPE
	SYNTAX  INTEGER(0..128)
	MAX-ACCESS  read-only
	STATUS current
	DESCRIPTION
        "
        Index definition for the pmlma10CtrlfecDisable
        table
        "
	::= { pmlma10CtrlfecDisableEntry 1 }


pmlma10CtrlfecDisablePortn OBJECT-TYPE
	SYNTAX  EkiState
	MAX-ACCESS read-write
	STATUS current
	DESCRIPTION
        "
        Forward Error Correction Inhibition
        :This OID, when set, inhibits the
        Forward Error Correction feature
        on the line input  <Help>  This
        control enables/disables the Forward
        Error Correction on the line interface
        "
	::= { pmlma10CtrlfecDisableEntry 2 }


--- *****************************************************
---     LEAF for the ledTest article
--- *****************************************************
pmlma10CtrlledTest OBJECT IDENTIFIER ::= { pmlma10CtrlOther 192 }




pmlma10CtrlLedOff OBJECT-TYPE
	  SYNTAX EkiOnOff
	  MAX-ACCESS read-write
	  STATUS current
	  DESCRIPTION
        "
        Leds Off :This OID switches off
        all the Leds as a test feature.
         <Help>  This control initiates
        a test leds turning all the LEDs
        to OFF
        "
	  ::= { pmlma10CtrlledTest 3 }



pmlma10CtrlRedLed OBJECT-TYPE
	  SYNTAX EkiOnOff
	  MAX-ACCESS read-write
	  STATUS current
	  DESCRIPTION
        "
        Red Leds Test :This OID switches
        on all the red Leds as a test feature.
         <Help>  This control initiates
        a test leds turning all the LEDs
        to red
        "
	  ::= { pmlma10CtrlledTest 2 }



pmlma10CtrlGreenLed OBJECT-TYPE
	  SYNTAX EkiOnOff
	  MAX-ACCESS read-write
	  STATUS current
	  DESCRIPTION
        "
        Green Leds Test :This OID switches
        on all the green Leds as a test
        feature.  <Help>  This control
         initiates a test leds turning
         all the LEDs to green
        "
	  ::= { pmlma10CtrlledTest 1 }








--- *****************************************************
--- $$$$$$$$$$$$$$$$$$$$$$$$$$$$$$$$$$$$$$$$$$$$$$$$$$$$$
---     COUNTERS
--- $$$$$$$$$$$$$$$$$$$$$$$$$$$$$$$$$$$$$$$$$$$$$$$$$$$$$
--- *****************************************************



--- *********************************************************
---     TABLE for the pmlma10CntclientCbipCounter articles
--- *********************************************************

pmlma10CntclientCbipCounterTable OBJECT-TYPE
	SYNTAX  SEQUENCE OF Pmlma10CntclientCbipCounterEntry
	MAX-ACCESS not-accessible
	STATUS current
	DESCRIPTION
        "
        List of pmlma10CntclientCbipCounter
        Article
        "
	::= { pmlma10CntClient 96 }


pmlma10CntclientCbipCounterEntry OBJECT-TYPE
	SYNTAX Pmlma10CntclientCbipCounterEntry
	MAX-ACCESS not-accessible
	STATUS current
	DESCRIPTION
        "
        Row definition for the pmlma10CntclientCbipCounter
        table
        "
	INDEX   { pmlma10CntclientCbipCounterIndex }
	::= { pmlma10CntclientCbipCounterTable 1 }


Pmlma10CntclientCbipCounterEntry ::=
	SEQUENCE {
	pmlma10CntclientCbipCounterIndex
		INTEGER,
	pmlma10CntclientCbipCounterValuePortn
		Counter32,
	pmlma10CntclientCbipCounterErrorPortn
		EkiOnOff,
	pmlma10CntclientCbipCounterOverloadPortn
		EkiOnOff
	}


pmlma10CntclientCbipCounterIndex OBJECT-TYPE
	SYNTAX  INTEGER(0..128)
	MAX-ACCESS  read-only
	STATUS current
	DESCRIPTION
        "
        Index definition for the pmlma10CntclientCbipCounter
        table
        "
	::= { pmlma10CntclientCbipCounterEntry 1 }


pmlma10CntclientCbipCounterValuePortn OBJECT-TYPE
	SYNTAX  Counter32
	MAX-ACCESS read-only
	STATUS current
	DESCRIPTION
        "
        Client Output Errors :This counter
        is incremented each time a CBIP
        parity error is detected on the
        Client output stream  <Help>  This
        counter gives the number of CBIP
        errors on the client port
        "
	::= { pmlma10CntclientCbipCounterEntry 2 }


pmlma10CntclientCbipCounterErrorPortn OBJECT-TYPE
	SYNTAX  EkiOnOff
	MAX-ACCESS read-only
	STATUS current
	DESCRIPTION
        "
        Client Counter Error :This OID
        when set indicates the CBIP error
        counter value is invalid on Port
        "
	::= { pmlma10CntclientCbipCounterEntry 3 }


pmlma10CntclientCbipCounterOverloadPortn OBJECT-TYPE
	SYNTAX  EkiOnOff
	MAX-ACCESS read-only
	STATUS current
	DESCRIPTION
        "
        Client CBIP Counter Overload :This
        OID when set indicates a CBIP error
        counter overload on Port
        "
	::= { pmlma10CntclientCbipCounterEntry 4 }


--- *********************************************************
---     TABLE for the pmlma10CntlocalLineSmBip8ErrorCounter articles
--- *********************************************************

pmlma10CntlocalLineSmBip8ErrorCounterTable OBJECT-TYPE
	SYNTAX  SEQUENCE OF Pmlma10CntlocalLineSmBip8ErrorCounterEntry
	MAX-ACCESS not-accessible
	STATUS current
	DESCRIPTION
        "
        List of pmlma10CntlocalLineSmBip8ErrorCounter
        Article
        "
	::= { pmlma10CntLine 192 }


pmlma10CntlocalLineSmBip8ErrorCounterEntry OBJECT-TYPE
	SYNTAX Pmlma10CntlocalLineSmBip8ErrorCounterEntry
	MAX-ACCESS not-accessible
	STATUS current
	DESCRIPTION
        "
        Row definition for the pmlma10CntlocalLineSmBip8ErrorCounter
        table
        "
	INDEX   { pmlma10CntlocalLineSmBip8ErrorCounterIndex }
	::= { pmlma10CntlocalLineSmBip8ErrorCounterTable 1 }


Pmlma10CntlocalLineSmBip8ErrorCounterEntry ::=
	SEQUENCE {
	pmlma10CntlocalLineSmBip8ErrorCounterIndex
		INTEGER,
	pmlma10CntlocalLineSmBip8ErrorCounterValuePortn
		Counter32,
	pmlma10CntlocalLineSmBip8ErrorCounterErrorPortn
		EkiOnOff,
	pmlma10CntlocalLineSmBip8ErrorCounterOverloadPortn
		EkiOnOff
	}


pmlma10CntlocalLineSmBip8ErrorCounterIndex OBJECT-TYPE
	SYNTAX  INTEGER(0..128)
	MAX-ACCESS  read-only
	STATUS current
	DESCRIPTION
        "
        Index definition for the pmlma10CntlocalLineSmBip8ErrorCounter
        table
        "
	::= { pmlma10CntlocalLineSmBip8ErrorCounterEntry 1 }


pmlma10CntlocalLineSmBip8ErrorCounterValuePortn OBJECT-TYPE
	SYNTAX  Counter32
	MAX-ACCESS read-only
	STATUS current
	DESCRIPTION
        "
        Line Input SM-BIP8 Errors :This
        OID gives the current Bit Error
        Rate (residual SM-BIP8 error) after
        FEC   <Help> This counter gives
        the current Bit Error Rate (residual
        SM-BIP8 error) after FEC
        "
	::= { pmlma10CntlocalLineSmBip8ErrorCounterEntry 2 }


pmlma10CntlocalLineSmBip8ErrorCounterErrorPortn OBJECT-TYPE
	SYNTAX  EkiOnOff
	MAX-ACCESS read-only
	STATUS current
	DESCRIPTION
        "
        Line Counter Error :This OID when
        set indicates the B1 error counter
        value is invalid on Port
        "
	::= { pmlma10CntlocalLineSmBip8ErrorCounterEntry 3 }


pmlma10CntlocalLineSmBip8ErrorCounterOverloadPortn OBJECT-TYPE
	SYNTAX  EkiOnOff
	MAX-ACCESS read-only
	STATUS current
	DESCRIPTION
        "
        Line Counter Overload :This OID
        when set indicates a B1 error counter
        overload on Port
        "
	::= { pmlma10CntlocalLineSmBip8ErrorCounterEntry 4 }


--- *********************************************************
---     TABLE for the pmlma10CntlocalLineFecCorrectedErrorsCounter articles
--- *********************************************************

pmlma10CntlocalLineFecCorrectedErrorsCounterTable OBJECT-TYPE
	SYNTAX  SEQUENCE OF Pmlma10CntlocalLineFecCorrectedErrorsCounterEntry
	MAX-ACCESS not-accessible
	STATUS current
	DESCRIPTION
        "
        List of pmlma10CntlocalLineFecCorrectedErrorsCounter
        Article
        "
	::= { pmlma10CntLine 200 }


pmlma10CntlocalLineFecCorrectedErrorsCounterEntry OBJECT-TYPE
	SYNTAX Pmlma10CntlocalLineFecCorrectedErrorsCounterEntry
	MAX-ACCESS not-accessible
	STATUS current
	DESCRIPTION
        "
        Row definition for the pmlma10CntlocalLineFecCorrectedErrorsCounter
        table
        "
	INDEX   { pmlma10CntlocalLineFecCorrectedErrorsCounterIndex }
	::= { pmlma10CntlocalLineFecCorrectedErrorsCounterTable 1 }


Pmlma10CntlocalLineFecCorrectedErrorsCounterEntry ::=
	SEQUENCE {
	pmlma10CntlocalLineFecCorrectedErrorsCounterIndex
		INTEGER,
	pmlma10CntlocalLineFecCorrectedErrorsCounterValuePortn
		Counter32,
	pmlma10CntlocalLineFecCorrectedErrorsCounterErrorPortn
		EkiOnOff,
	pmlma10CntlocalLineFecCorrectedErrorsCounterOverloadPortn
		EkiOnOff
	}


pmlma10CntlocalLineFecCorrectedErrorsCounterIndex OBJECT-TYPE
	SYNTAX  INTEGER(0..128)
	MAX-ACCESS  read-only
	STATUS current
	DESCRIPTION
        "
        Index definition for the pmlma10CntlocalLineFecCorrectedErrorsCounter
        table
        "
	::= { pmlma10CntlocalLineFecCorrectedErrorsCounterEntry 1 }


pmlma10CntlocalLineFecCorrectedErrorsCounterValuePortn OBJECT-TYPE
	SYNTAX  Counter32
	MAX-ACCESS read-only
	STATUS current
	DESCRIPTION
        "
        Line Input HD FEC Corrected Errors
        :This OID gives the current Bit
        Error Rate before the Hard Decision
        FEC  <Help> This counter gives
         the current Bit Error Rate before
        the Hard Decision FEC
        "
	::= { pmlma10CntlocalLineFecCorrectedErrorsCounterEntry 2 }


pmlma10CntlocalLineFecCorrectedErrorsCounterErrorPortn OBJECT-TYPE
	SYNTAX  EkiOnOff
	MAX-ACCESS read-only
	STATUS current
	DESCRIPTION
        "
        FEC Counter Error :This bit when
        set indicates the FEC corrected
        errors counter value is invalid
        on Line
        "
	::= { pmlma10CntlocalLineFecCorrectedErrorsCounterEntry 3 }


pmlma10CntlocalLineFecCorrectedErrorsCounterOverloadPortn OBJECT-TYPE
	SYNTAX  EkiOnOff
	MAX-ACCESS read-only
	STATUS current
	DESCRIPTION
        "
        FEC Counter Overload :This bit
        when set indicates a FEC corrected
        errors counter overload on Line
        "
	::= { pmlma10CntlocalLineFecCorrectedErrorsCounterEntry 4 }


--- *********************************************************
---     TABLE for the pmlma10CntremoteLineSmBip8ErrorCounter articles
--- *********************************************************

pmlma10CntremoteLineSmBip8ErrorCounterTable OBJECT-TYPE
	SYNTAX  SEQUENCE OF Pmlma10CntremoteLineSmBip8ErrorCounterEntry
	MAX-ACCESS not-accessible
	STATUS current
	DESCRIPTION
        "
        List of pmlma10CntremoteLineSmBip8ErrorCounter
        Article
        "
	::= { pmlma10CntLine 208 }


pmlma10CntremoteLineSmBip8ErrorCounterEntry OBJECT-TYPE
	SYNTAX Pmlma10CntremoteLineSmBip8ErrorCounterEntry
	MAX-ACCESS not-accessible
	STATUS current
	DESCRIPTION
        "
        Row definition for the pmlma10CntremoteLineSmBip8ErrorCounter
        table
        "
	INDEX   { pmlma10CntremoteLineSmBip8ErrorCounterIndex }
	::= { pmlma10CntremoteLineSmBip8ErrorCounterTable 1 }


Pmlma10CntremoteLineSmBip8ErrorCounterEntry ::=
	SEQUENCE {
	pmlma10CntremoteLineSmBip8ErrorCounterIndex
		INTEGER,
	pmlma10CntremoteLineSmBip8ErrorCounterValuePortn
		Counter32,
	pmlma10CntremoteLineSmBip8ErrorCounterErrorPortn
		EkiOnOff,
	pmlma10CntremoteLineSmBip8ErrorCounterOverloadPortn
		EkiOnOff
	}


pmlma10CntremoteLineSmBip8ErrorCounterIndex OBJECT-TYPE
	SYNTAX  INTEGER(0..128)
	MAX-ACCESS  read-only
	STATUS current
	DESCRIPTION
        "
        Index definition for the pmlma10CntremoteLineSmBip8ErrorCounter
        table
        "
	::= { pmlma10CntremoteLineSmBip8ErrorCounterEntry 1 }


pmlma10CntremoteLineSmBip8ErrorCounterValuePortn OBJECT-TYPE
	SYNTAX  Counter32
	MAX-ACCESS read-only
	STATUS current
	DESCRIPTION
        "
        Remote SM BIP8 :This OID gives
        the current Bit Error Rate (residual
        SM-BIP8 error) after FEC on the
        remote side  <Help> This counter
        gives the current Bit Error Rate
        (residual SM-BIP8 error) after
         FEC on the remote side
        "
	::= { pmlma10CntremoteLineSmBip8ErrorCounterEntry 2 }


pmlma10CntremoteLineSmBip8ErrorCounterErrorPortn OBJECT-TYPE
	SYNTAX  EkiOnOff
	MAX-ACCESS read-only
	STATUS current
	DESCRIPTION
        "
        Remote Counter Error :
        "
	::= { pmlma10CntremoteLineSmBip8ErrorCounterEntry 3 }


pmlma10CntremoteLineSmBip8ErrorCounterOverloadPortn OBJECT-TYPE
	SYNTAX  EkiOnOff
	MAX-ACCESS read-only
	STATUS current
	DESCRIPTION
        "
        Remote Counter Overload :
        "
	::= { pmlma10CntremoteLineSmBip8ErrorCounterEntry 4 }


--- *********************************************************
---     TABLE for the pmlma10CntlineDfrmTimCnt articles
--- *********************************************************

pmlma10CntlineDfrmTimCntTable OBJECT-TYPE
	SYNTAX  SEQUENCE OF Pmlma10CntlineDfrmTimCntEntry
	MAX-ACCESS not-accessible
	STATUS current
	DESCRIPTION
        "
        List of pmlma10CntlineDfrmTimCnt
        Article
        "
	::= { pmlma10CntLine 216 }


pmlma10CntlineDfrmTimCntEntry OBJECT-TYPE
	SYNTAX Pmlma10CntlineDfrmTimCntEntry
	MAX-ACCESS not-accessible
	STATUS current
	DESCRIPTION
        "
        Row definition for the pmlma10CntlineDfrmTimCnt
        table
        "
	INDEX   { pmlma10CntlineDfrmTimCntIndex }
	::= { pmlma10CntlineDfrmTimCntTable 1 }


Pmlma10CntlineDfrmTimCntEntry ::=
	SEQUENCE {
	pmlma10CntlineDfrmTimCntIndex
		INTEGER,
	pmlma10CntlineDfrmTimCntValuePortn
		Counter32,
	pmlma10CntlineDfrmTimCntErrorPortn
		EkiOnOff,
	pmlma10CntlineDfrmTimCntOverloadPortn
		EkiOnOff
	}


pmlma10CntlineDfrmTimCntIndex OBJECT-TYPE
	SYNTAX  INTEGER(0..128)
	MAX-ACCESS  read-only
	STATUS current
	DESCRIPTION
        "
        Index definition for the pmlma10CntlineDfrmTimCnt
        table
        "
	::= { pmlma10CntlineDfrmTimCntEntry 1 }


pmlma10CntlineDfrmTimCntValuePortn OBJECT-TYPE
	SYNTAX  Counter32
	MAX-ACCESS read-only
	STATUS current
	DESCRIPTION
        "
        Line Timer Counter :
        "
	::= { pmlma10CntlineDfrmTimCntEntry 2 }


pmlma10CntlineDfrmTimCntErrorPortn OBJECT-TYPE
	SYNTAX  EkiOnOff
	MAX-ACCESS read-only
	STATUS current
	DESCRIPTION
        "
        Line Counter Error :This OID when
        set indicates the deframer timer
        counter value is invalid on Port
        "
	::= { pmlma10CntlineDfrmTimCntEntry 3 }


pmlma10CntlineDfrmTimCntOverloadPortn OBJECT-TYPE
	SYNTAX  EkiOnOff
	MAX-ACCESS read-only
	STATUS current
	DESCRIPTION
        "
        Line Counter Overload :This OID
        when set indicates a deframer timer
        counter overload on Port
        "
	::= { pmlma10CntlineDfrmTimCntEntry 4 }


pmlma10CntCountersReset  OBJECT-TYPE
	SYNTAX EkiOnOff
	MAX-ACCESS read-write
	STATUS current
	DESCRIPTION
	"Counters Reset:This OID resets and restarts all the counters"
	::= { pmlma10counters  259 }

pmlma10CntCountersStop  OBJECT-TYPE
	SYNTAX EkiOnOff
	MAX-ACCESS read-write
	STATUS current
	DESCRIPTION
	"Counters stop:This OID stops all the counters"
	::= { pmlma10counters 260 }






--- *****************************************************
--- $$$$$$$$$$$$$$$$$$$$$$$$$$$$$$$$$$$$$$$$$$$$$$$$$$$$$
---     RMON
--- $$$$$$$$$$$$$$$$$$$$$$$$$$$$$$$$$$$$$$$$$$$$$$$$$$$$$
--- *****************************************************



--- *********************************************************
---     TABLE for the pmlma10MonupRmonBytesCounterClientInput articles
--- *********************************************************

pmlma10MonupRmonBytesCounterClientInputTable OBJECT-TYPE
	SYNTAX  SEQUENCE OF Pmlma10MonupRmonBytesCounterClientInputEntry
	MAX-ACCESS not-accessible
	STATUS current
	DESCRIPTION
        "
        List of pmlma10MonupRmonBytesCounterClientInput
        Article
        "
	::= { pmlma10MonClientRmonCounter 16 }


pmlma10MonupRmonBytesCounterClientInputEntry OBJECT-TYPE
	SYNTAX Pmlma10MonupRmonBytesCounterClientInputEntry
	MAX-ACCESS not-accessible
	STATUS current
	DESCRIPTION
        "
        Row definition for the pmlma10MonupRmonBytesCounterClientInput
        table
        "
	INDEX   { pmlma10MonupRmonBytesCounterClientInputIndex }
	::= { pmlma10MonupRmonBytesCounterClientInputTable 1 }


Pmlma10MonupRmonBytesCounterClientInputEntry ::=
	SEQUENCE {
	pmlma10MonupRmonBytesCounterClientInputIndex
		INTEGER,
	pmlma10MonupRmonBytesCounterClientInputValuePortn
		Counter64,
	pmlma10MonupRmonBytesCounterClientInputErrorPortn
		EkiOnOff,
	pmlma10MonupRmonBytesCounterClientInputOverloadPortn
		EkiOnOff
	}


pmlma10MonupRmonBytesCounterClientInputIndex OBJECT-TYPE
	SYNTAX  INTEGER(0..128)
	MAX-ACCESS  read-only
	STATUS current
	DESCRIPTION
        "
        Index definition for the pmlma10MonupRmonBytesCounterClientInput
        table
        "
	::= { pmlma10MonupRmonBytesCounterClientInputEntry 1 }


pmlma10MonupRmonBytesCounterClientInputValuePortn OBJECT-TYPE
	SYNTAX  Counter64
	MAX-ACCESS read-only
	STATUS current
	DESCRIPTION
        "
        Client Input Bytes :This counter
        is increased each time a data byte
        is received on the client port
          <Help>  This counter gives the
        number of bytes received on the
        client port
        "
	::= { pmlma10MonupRmonBytesCounterClientInputEntry 2 }


pmlma10MonupRmonBytesCounterClientInputErrorPortn OBJECT-TYPE
	SYNTAX  EkiOnOff
	MAX-ACCESS read-only
	STATUS current
	DESCRIPTION
        "
        Bytes Counter Error :This OID
         when set indicates the Bytes counter
        value is invalid on client port
        "
	::= { pmlma10MonupRmonBytesCounterClientInputEntry 3 }


pmlma10MonupRmonBytesCounterClientInputOverloadPortn OBJECT-TYPE
	SYNTAX  EkiOnOff
	MAX-ACCESS read-only
	STATUS current
	DESCRIPTION
        "
        Bytes Counter Overload :This OID
        when set indicates a Bytes counter
        overload on client port
        "
	::= { pmlma10MonupRmonBytesCounterClientInputEntry 4 }


--- *********************************************************
---     TABLE for the pmlma10MonupRmonCrcErrorsCounterClientInput articles
--- *********************************************************

pmlma10MonupRmonCrcErrorsCounterClientInputTable OBJECT-TYPE
	SYNTAX  SEQUENCE OF Pmlma10MonupRmonCrcErrorsCounterClientInputEntry
	MAX-ACCESS not-accessible
	STATUS current
	DESCRIPTION
        "
        List of pmlma10MonupRmonCrcErrorsCounterClientInput
        Article
        "
	::= { pmlma10MonClientRmonCounter 32 }


pmlma10MonupRmonCrcErrorsCounterClientInputEntry OBJECT-TYPE
	SYNTAX Pmlma10MonupRmonCrcErrorsCounterClientInputEntry
	MAX-ACCESS not-accessible
	STATUS current
	DESCRIPTION
        "
        Row definition for the pmlma10MonupRmonCrcErrorsCounterClientInput
        table
        "
	INDEX   { pmlma10MonupRmonCrcErrorsCounterClientInputIndex }
	::= { pmlma10MonupRmonCrcErrorsCounterClientInputTable 1 }


Pmlma10MonupRmonCrcErrorsCounterClientInputEntry ::=
	SEQUENCE {
	pmlma10MonupRmonCrcErrorsCounterClientInputIndex
		INTEGER,
	pmlma10MonupRmonCrcErrorsCounterClientInputValuePortn
		Counter64,
	pmlma10MonupRmonCrcErrorsCounterClientInputErrorPortn
		EkiOnOff,
	pmlma10MonupRmonCrcErrorsCounterClientInputOverloadPortn
		EkiOnOff
	}


pmlma10MonupRmonCrcErrorsCounterClientInputIndex OBJECT-TYPE
	SYNTAX  INTEGER(0..128)
	MAX-ACCESS  read-only
	STATUS current
	DESCRIPTION
        "
        Index definition for the pmlma10MonupRmonCrcErrorsCounterClientInput
        table
        "
	::= { pmlma10MonupRmonCrcErrorsCounterClientInputEntry 1 }


pmlma10MonupRmonCrcErrorsCounterClientInputValuePortn OBJECT-TYPE
	SYNTAX  Counter64
	MAX-ACCESS read-only
	STATUS current
	DESCRIPTION
        "
        Client Input B1/CRC Errors :This
        counter is increased each time
         a B1/FCS error is detected on
         the client port  <Help>  This
         counter gives the number of B1/FCS
        Errors received on the client port
        "
	::= { pmlma10MonupRmonCrcErrorsCounterClientInputEntry 2 }


pmlma10MonupRmonCrcErrorsCounterClientInputErrorPortn OBJECT-TYPE
	SYNTAX  EkiOnOff
	MAX-ACCESS read-only
	STATUS current
	DESCRIPTION
        "
        B1/FCS Errors Counter Error :This
        OID when set indicates the B1/FCS
        Errors counter value is invalid
        on client port
        "
	::= { pmlma10MonupRmonCrcErrorsCounterClientInputEntry 3 }


pmlma10MonupRmonCrcErrorsCounterClientInputOverloadPortn OBJECT-TYPE
	SYNTAX  EkiOnOff
	MAX-ACCESS read-only
	STATUS current
	DESCRIPTION
        "
        B1/FCS Errors Counter Overload
        :This OID when set indicates a
         B1/FCS Errors counter overload
        on client port
        "
	::= { pmlma10MonupRmonCrcErrorsCounterClientInputEntry 4 }


--- *********************************************************
---     TABLE for the pmlma10MonupRmonPacketsCounterClientInput articles
--- *********************************************************

pmlma10MonupRmonPacketsCounterClientInputTable OBJECT-TYPE
	SYNTAX  SEQUENCE OF Pmlma10MonupRmonPacketsCounterClientInputEntry
	MAX-ACCESS not-accessible
	STATUS current
	DESCRIPTION
        "
        List of pmlma10MonupRmonPacketsCounterClientInput
        Article
        "
	::= { pmlma10MonClientRmonCounter 48 }


pmlma10MonupRmonPacketsCounterClientInputEntry OBJECT-TYPE
	SYNTAX Pmlma10MonupRmonPacketsCounterClientInputEntry
	MAX-ACCESS not-accessible
	STATUS current
	DESCRIPTION
        "
        Row definition for the pmlma10MonupRmonPacketsCounterClientInput
        table
        "
	INDEX   { pmlma10MonupRmonPacketsCounterClientInputIndex }
	::= { pmlma10MonupRmonPacketsCounterClientInputTable 1 }


Pmlma10MonupRmonPacketsCounterClientInputEntry ::=
	SEQUENCE {
	pmlma10MonupRmonPacketsCounterClientInputIndex
		INTEGER,
	pmlma10MonupRmonPacketsCounterClientInputValuePortn
		Counter64,
	pmlma10MonupRmonPacketsCounterClientInputErrorPortn
		EkiOnOff,
	pmlma10MonupRmonPacketsCounterClientInputOverloadPortn
		EkiOnOff
	}


pmlma10MonupRmonPacketsCounterClientInputIndex OBJECT-TYPE
	SYNTAX  INTEGER(0..128)
	MAX-ACCESS  read-only
	STATUS current
	DESCRIPTION
        "
        Index definition for the pmlma10MonupRmonPacketsCounterClientInput
        table
        "
	::= { pmlma10MonupRmonPacketsCounterClientInputEntry 1 }


pmlma10MonupRmonPacketsCounterClientInputValuePortn OBJECT-TYPE
	SYNTAX  Counter64
	MAX-ACCESS read-only
	STATUS current
	DESCRIPTION
        "
        Client Input Packets :This counter
        is increased each time a packet
        is received on the client port
          <Help>  This counter gives the
        number of packets received on the
        client port
        "
	::= { pmlma10MonupRmonPacketsCounterClientInputEntry 2 }


pmlma10MonupRmonPacketsCounterClientInputErrorPortn OBJECT-TYPE
	SYNTAX  EkiOnOff
	MAX-ACCESS read-only
	STATUS current
	DESCRIPTION
        "
        Packets Counter Error :This OID
        when set indicates the Packets
         counter value is invalid on client
        port
        "
	::= { pmlma10MonupRmonPacketsCounterClientInputEntry 3 }


pmlma10MonupRmonPacketsCounterClientInputOverloadPortn OBJECT-TYPE
	SYNTAX  EkiOnOff
	MAX-ACCESS read-only
	STATUS current
	DESCRIPTION
        "
        Packets Counter Overload :This
        OID when set indicates a Packets
        counter overload on client port
        "
	::= { pmlma10MonupRmonPacketsCounterClientInputEntry 4 }


--- *********************************************************
---     TABLE for the pmlma10MonupRmonBroadcastCounterClientInput articles
--- *********************************************************

pmlma10MonupRmonBroadcastCounterClientInputTable OBJECT-TYPE
	SYNTAX  SEQUENCE OF Pmlma10MonupRmonBroadcastCounterClientInputEntry
	MAX-ACCESS not-accessible
	STATUS current
	DESCRIPTION
        "
        List of pmlma10MonupRmonBroadcastCounterClientInput
        Article
        "
	::= { pmlma10MonClientRmonCounter 64 }


pmlma10MonupRmonBroadcastCounterClientInputEntry OBJECT-TYPE
	SYNTAX Pmlma10MonupRmonBroadcastCounterClientInputEntry
	MAX-ACCESS not-accessible
	STATUS current
	DESCRIPTION
        "
        Row definition for the pmlma10MonupRmonBroadcastCounterClientInput
        table
        "
	INDEX   { pmlma10MonupRmonBroadcastCounterClientInputIndex }
	::= { pmlma10MonupRmonBroadcastCounterClientInputTable 1 }


Pmlma10MonupRmonBroadcastCounterClientInputEntry ::=
	SEQUENCE {
	pmlma10MonupRmonBroadcastCounterClientInputIndex
		INTEGER,
	pmlma10MonupRmonBroadcastCounterClientInputValuePortn
		Counter64,
	pmlma10MonupRmonBroadcastCounterClientInputErrorPortn
		EkiOnOff,
	pmlma10MonupRmonBroadcastCounterClientInputOverloadPortn
		EkiOnOff
	}


pmlma10MonupRmonBroadcastCounterClientInputIndex OBJECT-TYPE
	SYNTAX  INTEGER(0..128)
	MAX-ACCESS  read-only
	STATUS current
	DESCRIPTION
        "
        Index definition for the pmlma10MonupRmonBroadcastCounterClientInput
        table
        "
	::= { pmlma10MonupRmonBroadcastCounterClientInputEntry 1 }


pmlma10MonupRmonBroadcastCounterClientInputValuePortn OBJECT-TYPE
	SYNTAX  Counter64
	MAX-ACCESS read-only
	STATUS current
	DESCRIPTION
        "
        Client Input Broadcast Packets
        :This counter is increased each
        time a broadcast packet is received
        on the client port  <Help>  This
        counter gives the number of Broadcast
        packets received on the client
         port
        "
	::= { pmlma10MonupRmonBroadcastCounterClientInputEntry 2 }


pmlma10MonupRmonBroadcastCounterClientInputErrorPortn OBJECT-TYPE
	SYNTAX  EkiOnOff
	MAX-ACCESS read-only
	STATUS current
	DESCRIPTION
        "
        Broadcast Counter Error :This
         OID when set indicates the Broadcast
        counter value is invalid on client
        port
        "
	::= { pmlma10MonupRmonBroadcastCounterClientInputEntry 3 }


pmlma10MonupRmonBroadcastCounterClientInputOverloadPortn OBJECT-TYPE
	SYNTAX  EkiOnOff
	MAX-ACCESS read-only
	STATUS current
	DESCRIPTION
        "
        Broadcast Counter Overload :This
        OID when set indicates a Broadcast
        counter overload on client port
        "
	::= { pmlma10MonupRmonBroadcastCounterClientInputEntry 4 }


--- *********************************************************
---     TABLE for the pmlma10MonupRmonMulticastCounterClientInput articles
--- *********************************************************

pmlma10MonupRmonMulticastCounterClientInputTable OBJECT-TYPE
	SYNTAX  SEQUENCE OF Pmlma10MonupRmonMulticastCounterClientInputEntry
	MAX-ACCESS not-accessible
	STATUS current
	DESCRIPTION
        "
        List of pmlma10MonupRmonMulticastCounterClientInput
        Article
        "
	::= { pmlma10MonClientRmonCounter 80 }


pmlma10MonupRmonMulticastCounterClientInputEntry OBJECT-TYPE
	SYNTAX Pmlma10MonupRmonMulticastCounterClientInputEntry
	MAX-ACCESS not-accessible
	STATUS current
	DESCRIPTION
        "
        Row definition for the pmlma10MonupRmonMulticastCounterClientInput
        table
        "
	INDEX   { pmlma10MonupRmonMulticastCounterClientInputIndex }
	::= { pmlma10MonupRmonMulticastCounterClientInputTable 1 }


Pmlma10MonupRmonMulticastCounterClientInputEntry ::=
	SEQUENCE {
	pmlma10MonupRmonMulticastCounterClientInputIndex
		INTEGER,
	pmlma10MonupRmonMulticastCounterClientInputValuePortn
		Counter64,
	pmlma10MonupRmonMulticastCounterClientInputErrorPortn
		EkiOnOff,
	pmlma10MonupRmonMulticastCounterClientInputOverloadPortn
		EkiOnOff
	}


pmlma10MonupRmonMulticastCounterClientInputIndex OBJECT-TYPE
	SYNTAX  INTEGER(0..128)
	MAX-ACCESS  read-only
	STATUS current
	DESCRIPTION
        "
        Index definition for the pmlma10MonupRmonMulticastCounterClientInput
        table
        "
	::= { pmlma10MonupRmonMulticastCounterClientInputEntry 1 }


pmlma10MonupRmonMulticastCounterClientInputValuePortn OBJECT-TYPE
	SYNTAX  Counter64
	MAX-ACCESS read-only
	STATUS current
	DESCRIPTION
        "
        Client Input Multicast Packets
        :This counter is increased each
        time a Multicast packet is received
        on the client port  <Help>  This
        counter gives the number of Multicast
        packets received on the client
         port
        "
	::= { pmlma10MonupRmonMulticastCounterClientInputEntry 2 }


pmlma10MonupRmonMulticastCounterClientInputErrorPortn OBJECT-TYPE
	SYNTAX  EkiOnOff
	MAX-ACCESS read-only
	STATUS current
	DESCRIPTION
        "
        Multicast Counter Error :This
         OID when set indicates the Multicast
        counter value is invalid on client
        port
        "
	::= { pmlma10MonupRmonMulticastCounterClientInputEntry 3 }


pmlma10MonupRmonMulticastCounterClientInputOverloadPortn OBJECT-TYPE
	SYNTAX  EkiOnOff
	MAX-ACCESS read-only
	STATUS current
	DESCRIPTION
        "
        Multicast Counter Overload :This
        OID when set indicates a Multicast
        counter overload on client port
        "
	::= { pmlma10MonupRmonMulticastCounterClientInputEntry 4 }


--- *********************************************************
---     TABLE for the pmlma10MonupRmonPauseFrameCounterClientInput articles
--- *********************************************************

pmlma10MonupRmonPauseFrameCounterClientInputTable OBJECT-TYPE
	SYNTAX  SEQUENCE OF Pmlma10MonupRmonPauseFrameCounterClientInputEntry
	MAX-ACCESS not-accessible
	STATUS current
	DESCRIPTION
        "
        List of pmlma10MonupRmonPauseFrameCounterClientInput
        Article
        "
	::= { pmlma10MonClientRmonCounter 96 }


pmlma10MonupRmonPauseFrameCounterClientInputEntry OBJECT-TYPE
	SYNTAX Pmlma10MonupRmonPauseFrameCounterClientInputEntry
	MAX-ACCESS not-accessible
	STATUS current
	DESCRIPTION
        "
        Row definition for the pmlma10MonupRmonPauseFrameCounterClientInput
        table
        "
	INDEX   { pmlma10MonupRmonPauseFrameCounterClientInputIndex }
	::= { pmlma10MonupRmonPauseFrameCounterClientInputTable 1 }


Pmlma10MonupRmonPauseFrameCounterClientInputEntry ::=
	SEQUENCE {
	pmlma10MonupRmonPauseFrameCounterClientInputIndex
		INTEGER,
	pmlma10MonupRmonPauseFrameCounterClientInputValuePortn
		Counter64,
	pmlma10MonupRmonPauseFrameCounterClientInputErrorPortn
		EkiOnOff,
	pmlma10MonupRmonPauseFrameCounterClientInputOverloadPortn
		EkiOnOff
	}


pmlma10MonupRmonPauseFrameCounterClientInputIndex OBJECT-TYPE
	SYNTAX  INTEGER(0..128)
	MAX-ACCESS  read-only
	STATUS current
	DESCRIPTION
        "
        Index definition for the pmlma10MonupRmonPauseFrameCounterClientInput
        table
        "
	::= { pmlma10MonupRmonPauseFrameCounterClientInputEntry 1 }


pmlma10MonupRmonPauseFrameCounterClientInputValuePortn OBJECT-TYPE
	SYNTAX  Counter64
	MAX-ACCESS read-only
	STATUS current
	DESCRIPTION
        "
        Client Input Pause Frames :This
        counter is increased each time
         a Pause frame is received on the
        client port  <Help>  This counter
        gives the number of Pause frames
        received on the client port
        "
	::= { pmlma10MonupRmonPauseFrameCounterClientInputEntry 2 }


pmlma10MonupRmonPauseFrameCounterClientInputErrorPortn OBJECT-TYPE
	SYNTAX  EkiOnOff
	MAX-ACCESS read-only
	STATUS current
	DESCRIPTION
        "
        Pause Counter Error :This OID
         when set indicates the Pause counter
        value is invalid on client port
        "
	::= { pmlma10MonupRmonPauseFrameCounterClientInputEntry 3 }


pmlma10MonupRmonPauseFrameCounterClientInputOverloadPortn OBJECT-TYPE
	SYNTAX  EkiOnOff
	MAX-ACCESS read-only
	STATUS current
	DESCRIPTION
        "
        Pause Counter Overload :This OID
        when set indicates a Pause counter
        overload on client port
        "
	::= { pmlma10MonupRmonPauseFrameCounterClientInputEntry 4 }


--- *********************************************************
---     TABLE for the pmlma10MondwRmonCrcErrorsCounterClientInput articles
--- *********************************************************

pmlma10MondwRmonCrcErrorsCounterClientInputTable OBJECT-TYPE
	SYNTAX  SEQUENCE OF Pmlma10MondwRmonCrcErrorsCounterClientInputEntry
	MAX-ACCESS not-accessible
	STATUS current
	DESCRIPTION
        "
        List of pmlma10MondwRmonCrcErrorsCounterClientInput
        Article
        "
	::= { pmlma10MonClientRmonCounter 224 }


pmlma10MondwRmonCrcErrorsCounterClientInputEntry OBJECT-TYPE
	SYNTAX Pmlma10MondwRmonCrcErrorsCounterClientInputEntry
	MAX-ACCESS not-accessible
	STATUS current
	DESCRIPTION
        "
        Row definition for the pmlma10MondwRmonCrcErrorsCounterClientInput
        table
        "
	INDEX   { pmlma10MondwRmonCrcErrorsCounterClientInputIndex }
	::= { pmlma10MondwRmonCrcErrorsCounterClientInputTable 1 }


Pmlma10MondwRmonCrcErrorsCounterClientInputEntry ::=
	SEQUENCE {
	pmlma10MondwRmonCrcErrorsCounterClientInputIndex
		INTEGER,
	pmlma10MondwRmonCrcErrorsCounterClientInputValuePortn
		Counter64,
	pmlma10MondwRmonCrcErrorsCounterClientInputErrorPortn
		EkiOnOff,
	pmlma10MondwRmonCrcErrorsCounterClientInputOverloadPortn
		EkiOnOff
	}


pmlma10MondwRmonCrcErrorsCounterClientInputIndex OBJECT-TYPE
	SYNTAX  INTEGER(0..128)
	MAX-ACCESS  read-only
	STATUS current
	DESCRIPTION
        "
        Index definition for the pmlma10MondwRmonCrcErrorsCounterClientInput
        table
        "
	::= { pmlma10MondwRmonCrcErrorsCounterClientInputEntry 1 }


pmlma10MondwRmonCrcErrorsCounterClientInputValuePortn OBJECT-TYPE
	SYNTAX  Counter64
	MAX-ACCESS read-only
	STATUS current
	DESCRIPTION
        "
        Client Output B1/CRC Errors :This
        counter is increased each time
         a B1/FCS error is detected on
         the output client port  <Help>
         This counter gives the number
         of B1/CRC Errors detected on the
        client port
        "
	::= { pmlma10MondwRmonCrcErrorsCounterClientInputEntry 2 }


pmlma10MondwRmonCrcErrorsCounterClientInputErrorPortn OBJECT-TYPE
	SYNTAX  EkiOnOff
	MAX-ACCESS read-only
	STATUS current
	DESCRIPTION
        "
        Output B1/FCS Errors Counter Error
        :This OID when set indicates the
        output B1/FCS Errors counter value
        is invalid on client port
        "
	::= { pmlma10MondwRmonCrcErrorsCounterClientInputEntry 3 }


pmlma10MondwRmonCrcErrorsCounterClientInputOverloadPortn OBJECT-TYPE
	SYNTAX  EkiOnOff
	MAX-ACCESS read-only
	STATUS current
	DESCRIPTION
        "
        Output B1/FCS Errors Counter Overload
        :This OID when set indicates an
        output B1/FCS Errors counter overload
        on client port
        "
	::= { pmlma10MondwRmonCrcErrorsCounterClientInputEntry 4 }


--- *********************************************************
---     TABLE for the pmlma10MondwRmonPacketsCounterClientInput articles
--- *********************************************************

pmlma10MondwRmonPacketsCounterClientInputTable OBJECT-TYPE
	SYNTAX  SEQUENCE OF Pmlma10MondwRmonPacketsCounterClientInputEntry
	MAX-ACCESS not-accessible
	STATUS current
	DESCRIPTION
        "
        List of pmlma10MondwRmonPacketsCounterClientInput
        Article
        "
	::= { pmlma10MonClientRmonCounter 240 }


pmlma10MondwRmonPacketsCounterClientInputEntry OBJECT-TYPE
	SYNTAX Pmlma10MondwRmonPacketsCounterClientInputEntry
	MAX-ACCESS not-accessible
	STATUS current
	DESCRIPTION
        "
        Row definition for the pmlma10MondwRmonPacketsCounterClientInput
        table
        "
	INDEX   { pmlma10MondwRmonPacketsCounterClientInputIndex }
	::= { pmlma10MondwRmonPacketsCounterClientInputTable 1 }


Pmlma10MondwRmonPacketsCounterClientInputEntry ::=
	SEQUENCE {
	pmlma10MondwRmonPacketsCounterClientInputIndex
		INTEGER,
	pmlma10MondwRmonPacketsCounterClientInputValuePortn
		Counter64,
	pmlma10MondwRmonPacketsCounterClientInputErrorPortn
		EkiOnOff,
	pmlma10MondwRmonPacketsCounterClientInputOverloadPortn
		EkiOnOff
	}


pmlma10MondwRmonPacketsCounterClientInputIndex OBJECT-TYPE
	SYNTAX  INTEGER(0..128)
	MAX-ACCESS  read-only
	STATUS current
	DESCRIPTION
        "
        Index definition for the pmlma10MondwRmonPacketsCounterClientInput
        table
        "
	::= { pmlma10MondwRmonPacketsCounterClientInputEntry 1 }


pmlma10MondwRmonPacketsCounterClientInputValuePortn OBJECT-TYPE
	SYNTAX  Counter64
	MAX-ACCESS read-only
	STATUS current
	DESCRIPTION
        "
        Client Output Packets :This counter
        is increased each time a packet
        is transmitted on the client port.
         <Help>  This counter gives the
        number of packets detected on the
        client port
        "
	::= { pmlma10MondwRmonPacketsCounterClientInputEntry 2 }


pmlma10MondwRmonPacketsCounterClientInputErrorPortn OBJECT-TYPE
	SYNTAX  EkiOnOff
	MAX-ACCESS read-only
	STATUS current
	DESCRIPTION
        "
        Output Packets Counter Error :This
        OID when set indicates the output
        Packets counter value is invalid
        on client port
        "
	::= { pmlma10MondwRmonPacketsCounterClientInputEntry 3 }


pmlma10MondwRmonPacketsCounterClientInputOverloadPortn OBJECT-TYPE
	SYNTAX  EkiOnOff
	MAX-ACCESS read-only
	STATUS current
	DESCRIPTION
        "
        Output Packets Counter Overload
        :This OID when set indicates an
        output Packets counter overload
        on client port
        "
	::= { pmlma10MondwRmonPacketsCounterClientInputEntry 4 }


pmlma10MonCountersReset  OBJECT-TYPE
	SYNTAX EkiOnOff
	MAX-ACCESS read-write
	STATUS current
	DESCRIPTION
	"RMON Counters Reset:This OID resets and restarts all the RMON counters"
	::= { pmlma10MonRmon   359 }

pmlma10MonCountersStop  OBJECT-TYPE
	SYNTAX EkiOnOff
	MAX-ACCESS read-write
	STATUS current
	DESCRIPTION
	"RMON Counters stop:This OID stops all the RMON counters"
	::= { pmlma10MonRmon  360 }






--- *****************************************************
--- $$$$$$$$$$$$$$$$$$$$$$$$$$$$$$$$$$$$$$$$$$$$$$$$$$$$$
---     MEASURES
--- $$$$$$$$$$$$$$$$$$$$$$$$$$$$$$$$$$$$$$$$$$$$$$$$$$$$$
--- *****************************************************



--- *********************************************************
---     TABLE for the pmlma10MesrclientTemp articles
--- *********************************************************

pmlma10MesrclientTempTable OBJECT-TYPE
	SYNTAX  SEQUENCE OF Pmlma10MesrclientTempEntry
	MAX-ACCESS not-accessible
	STATUS current
	DESCRIPTION
        "
        List of pmlma10MesrclientTemp
         Article
        "
	::= { pmlma10MesrClient 16 }


pmlma10MesrclientTempEntry OBJECT-TYPE
	SYNTAX Pmlma10MesrclientTempEntry
	MAX-ACCESS not-accessible
	STATUS current
	DESCRIPTION
        "
        Row definition for the pmlma10MesrclientTemp
        table
        "
	INDEX   { pmlma10MesrclientTempIndex }
	::= { pmlma10MesrclientTempTable 1 }


Pmlma10MesrclientTempEntry ::=
	SEQUENCE {
	pmlma10MesrclientTempIndex
		INTEGER,
	pmlma10MesrclientTempPortn
		INTEGER
	}


pmlma10MesrclientTempIndex OBJECT-TYPE
	SYNTAX  INTEGER(0..128)
	MAX-ACCESS  read-only
	STATUS current
	DESCRIPTION
        "
        Index definition for the pmlma10MesrclientTemp
        table
        "
	::= { pmlma10MesrclientTempEntry 1 }


pmlma10MesrclientTempPortn OBJECT-TYPE
	SYNTAX  INTEGER (0..65535)
	MAX-ACCESS read-only
	STATUS current
	DESCRIPTION
        "
        Client Optical Module Temperature
        :This OID gives the Laser temperature
        value of the Client Transceiver,
        read from the DDM (Digital Diagnostic
        Monitoring) (Temperature = AV/256)
        (Unit = C) <Help> This Measure
         gives the Laser temperature value
        of the Client Transceiver
        "
	::= { pmlma10MesrclientTempEntry 2 }


--- *********************************************************
---     TABLE for the pmlma10MesrclientTxBias articles
--- *********************************************************

pmlma10MesrclientTxBiasTable OBJECT-TYPE
	SYNTAX  SEQUENCE OF Pmlma10MesrclientTxBiasEntry
	MAX-ACCESS not-accessible
	STATUS current
	DESCRIPTION
        "
        List of pmlma10MesrclientTxBias
        Article
        "
	::= { pmlma10MesrClient 32 }


pmlma10MesrclientTxBiasEntry OBJECT-TYPE
	SYNTAX Pmlma10MesrclientTxBiasEntry
	MAX-ACCESS not-accessible
	STATUS current
	DESCRIPTION
        "
        Row definition for the pmlma10MesrclientTxBias
        table
        "
	INDEX   { pmlma10MesrclientTxBiasIndex }
	::= { pmlma10MesrclientTxBiasTable 1 }


Pmlma10MesrclientTxBiasEntry ::=
	SEQUENCE {
	pmlma10MesrclientTxBiasIndex
		INTEGER,
	pmlma10MesrclientTxBiasPortn
		INTEGER
	}


pmlma10MesrclientTxBiasIndex OBJECT-TYPE
	SYNTAX  INTEGER(0..128)
	MAX-ACCESS  read-only
	STATUS current
	DESCRIPTION
        "
        Index definition for the pmlma10MesrclientTxBias
        table
        "
	::= { pmlma10MesrclientTxBiasEntry 1 }


pmlma10MesrclientTxBiasPortn OBJECT-TYPE
	SYNTAX  INTEGER (0..65535)
	MAX-ACCESS read-only
	STATUS current
	DESCRIPTION
        "
        Client Optical Module Bias :This
        OID gives the Laser bias value
         of the Client Transceiver, read
        from the DDM (Digital Diagnostic
        Monitoring) (Bias = AV/500) (Unit
        = mA) <Help> This Measure gives
        the Laser bias value of the Client
        Transceiver
        "
	::= { pmlma10MesrclientTxBiasEntry 2 }


--- *********************************************************
---     TABLE for the pmlma10MesrclientTxPwr articles
--- *********************************************************

pmlma10MesrclientTxPwrTable OBJECT-TYPE
	SYNTAX  SEQUENCE OF Pmlma10MesrclientTxPwrEntry
	MAX-ACCESS not-accessible
	STATUS current
	DESCRIPTION
        "
        List of pmlma10MesrclientTxPwr
        Article
        "
	::= { pmlma10MesrClient 48 }


pmlma10MesrclientTxPwrEntry OBJECT-TYPE
	SYNTAX Pmlma10MesrclientTxPwrEntry
	MAX-ACCESS not-accessible
	STATUS current
	DESCRIPTION
        "
        Row definition for the pmlma10MesrclientTxPwr
        table
        "
	INDEX   { pmlma10MesrclientTxPwrIndex }
	::= { pmlma10MesrclientTxPwrTable 1 }


Pmlma10MesrclientTxPwrEntry ::=
	SEQUENCE {
	pmlma10MesrclientTxPwrIndex
		INTEGER,
	pmlma10MesrclientTxPwrPortn
		INTEGER
	}


pmlma10MesrclientTxPwrIndex OBJECT-TYPE
	SYNTAX  INTEGER(0..128)
	MAX-ACCESS  read-only
	STATUS current
	DESCRIPTION
        "
        Index definition for the pmlma10MesrclientTxPwr
        table
        "
	::= { pmlma10MesrclientTxPwrEntry 1 }


pmlma10MesrclientTxPwrPortn OBJECT-TYPE
	SYNTAX  INTEGER (0..65535)
	MAX-ACCESS read-only
	STATUS current
	DESCRIPTION
        "
        Client Optical Module Tx Power
        :This OID gives the transmit power
        value of the Client Transceiver,
        read from the DDM (Digital Diagnostic
        Monitoring) (Power = 10*log(AV)-40)
        (Unit = dBm) <Help> This Measure
        gives the transmit power value
         of the Client Transceiver
        "
	::= { pmlma10MesrclientTxPwrEntry 2 }


--- *********************************************************
---     TABLE for the pmlma10MesrclientRxPwr articles
--- *********************************************************

pmlma10MesrclientRxPwrTable OBJECT-TYPE
	SYNTAX  SEQUENCE OF Pmlma10MesrclientRxPwrEntry
	MAX-ACCESS not-accessible
	STATUS current
	DESCRIPTION
        "
        List of pmlma10MesrclientRxPwr
        Article
        "
	::= { pmlma10MesrClient 64 }


pmlma10MesrclientRxPwrEntry OBJECT-TYPE
	SYNTAX Pmlma10MesrclientRxPwrEntry
	MAX-ACCESS not-accessible
	STATUS current
	DESCRIPTION
        "
        Row definition for the pmlma10MesrclientRxPwr
        table
        "
	INDEX   { pmlma10MesrclientRxPwrIndex }
	::= { pmlma10MesrclientRxPwrTable 1 }


Pmlma10MesrclientRxPwrEntry ::=
	SEQUENCE {
	pmlma10MesrclientRxPwrIndex
		INTEGER,
	pmlma10MesrclientRxPwrPortn
		INTEGER
	}


pmlma10MesrclientRxPwrIndex OBJECT-TYPE
	SYNTAX  INTEGER(0..128)
	MAX-ACCESS  read-only
	STATUS current
	DESCRIPTION
        "
        Index definition for the pmlma10MesrclientRxPwr
        table
        "
	::= { pmlma10MesrclientRxPwrEntry 1 }


pmlma10MesrclientRxPwrPortn OBJECT-TYPE
	SYNTAX  INTEGER (0..65535)
	MAX-ACCESS read-only
	STATUS current
	DESCRIPTION
        "
        Client Optical Module Rx Power
        :This OID gives the receive power
        value of the Client Transceiver,
        read in the DDM (Digital Diagnostic
        Monitoring) (Power = 10*log(AV)-40)
        (Unit = dBm) <Help> This Measure
        gives the receive power value of
        the Client Transceiver
        "
	::= { pmlma10MesrclientRxPwrEntry 2 }


--- *********************************************************
---     TABLE for the pmlma10MesrlineTxPwr articles
--- *********************************************************

pmlma10MesrlineTxPwrTable OBJECT-TYPE
	SYNTAX  SEQUENCE OF Pmlma10MesrlineTxPwrEntry
	MAX-ACCESS not-accessible
	STATUS current
	DESCRIPTION
        "
        List of pmlma10MesrlineTxPwr Article
        "
	::= { pmlma10MesrLine 80 }


pmlma10MesrlineTxPwrEntry OBJECT-TYPE
	SYNTAX Pmlma10MesrlineTxPwrEntry
	MAX-ACCESS not-accessible
	STATUS current
	DESCRIPTION
        "
        Row definition for the pmlma10MesrlineTxPwr
        table
        "
	INDEX   { pmlma10MesrlineTxPwrIndex }
	::= { pmlma10MesrlineTxPwrTable 1 }


Pmlma10MesrlineTxPwrEntry ::=
	SEQUENCE {
	pmlma10MesrlineTxPwrIndex
		INTEGER,
	pmlma10MesrlineTxPwrPortn
		INTEGER
	}


pmlma10MesrlineTxPwrIndex OBJECT-TYPE
	SYNTAX  INTEGER(0..128)
	MAX-ACCESS  read-only
	STATUS current
	DESCRIPTION
        "
        Index definition for the pmlma10MesrlineTxPwr
        table
        "
	::= { pmlma10MesrlineTxPwrEntry 1 }


pmlma10MesrlineTxPwrPortn OBJECT-TYPE
	SYNTAX  INTEGER (0..65535)
	MAX-ACCESS read-only
	STATUS current
	DESCRIPTION
        "
        Line Optical Module Tx Power :This
        OID gives the Tx Laser transmit
        power value of the Line Transceiver,
        read in the DDM (Digital Diagnostic
        Monitoring) (Power = 10*log(AV)-40)
        (Unit = dBm) <Help> This Measure
        gives the Tx Laser transmit power
        value of the Line Transceiver
        "
	::= { pmlma10MesrlineTxPwrEntry 2 }


--- *********************************************************
---     TABLE for the pmlma10MesrlineTemp articles
--- *********************************************************

pmlma10MesrlineTempTable OBJECT-TYPE
	SYNTAX  SEQUENCE OF Pmlma10MesrlineTempEntry
	MAX-ACCESS not-accessible
	STATUS current
	DESCRIPTION
        "
        List of pmlma10MesrlineTemp Article
        "
	::= { pmlma10MesrLine 96 }


pmlma10MesrlineTempEntry OBJECT-TYPE
	SYNTAX Pmlma10MesrlineTempEntry
	MAX-ACCESS not-accessible
	STATUS current
	DESCRIPTION
        "
        Row definition for the pmlma10MesrlineTemp
        table
        "
	INDEX   { pmlma10MesrlineTempIndex }
	::= { pmlma10MesrlineTempTable 1 }


Pmlma10MesrlineTempEntry ::=
	SEQUENCE {
	pmlma10MesrlineTempIndex
		INTEGER,
	pmlma10MesrlineTempPortn
		INTEGER
	}


pmlma10MesrlineTempIndex OBJECT-TYPE
	SYNTAX  INTEGER(0..128)
	MAX-ACCESS  read-only
	STATUS current
	DESCRIPTION
        "
        Index definition for the pmlma10MesrlineTemp
        table
        "
	::= { pmlma10MesrlineTempEntry 1 }


pmlma10MesrlineTempPortn OBJECT-TYPE
	SYNTAX  INTEGER (0..65535)
	MAX-ACCESS read-only
	STATUS current
	DESCRIPTION
        "
        Line Optical Module Temperature
        :This OID gives the Tx Laser Temperature
        value of the Line Transceiver,
         read from the DDM (Digital Diagnostic
        Monitoring) (Temperature = AV/256)
        (Unit = C) <Help> This Measure
         gives the Tx Laser Temperature
        value of the Line Transceiver
        "
	::= { pmlma10MesrlineTempEntry 2 }


--- *********************************************************
---     TABLE for the pmlma10MesrlineTxBias articles
--- *********************************************************

pmlma10MesrlineTxBiasTable OBJECT-TYPE
	SYNTAX  SEQUENCE OF Pmlma10MesrlineTxBiasEntry
	MAX-ACCESS not-accessible
	STATUS current
	DESCRIPTION
        "
        List of pmlma10MesrlineTxBias
         Article
        "
	::= { pmlma10MesrLine 112 }


pmlma10MesrlineTxBiasEntry OBJECT-TYPE
	SYNTAX Pmlma10MesrlineTxBiasEntry
	MAX-ACCESS not-accessible
	STATUS current
	DESCRIPTION
        "
        Row definition for the pmlma10MesrlineTxBias
        table
        "
	INDEX   { pmlma10MesrlineTxBiasIndex }
	::= { pmlma10MesrlineTxBiasTable 1 }


Pmlma10MesrlineTxBiasEntry ::=
	SEQUENCE {
	pmlma10MesrlineTxBiasIndex
		INTEGER,
	pmlma10MesrlineTxBiasPortn
		INTEGER
	}


pmlma10MesrlineTxBiasIndex OBJECT-TYPE
	SYNTAX  INTEGER(0..128)
	MAX-ACCESS  read-only
	STATUS current
	DESCRIPTION
        "
        Index definition for the pmlma10MesrlineTxBias
        table
        "
	::= { pmlma10MesrlineTxBiasEntry 1 }


pmlma10MesrlineTxBiasPortn OBJECT-TYPE
	SYNTAX  INTEGER (0..65535)
	MAX-ACCESS read-only
	STATUS current
	DESCRIPTION
        "
        Line Optical Module Laser Bias
        :This OID gives the Tx Laser Bias
        value of the Line Transceiver,
         read from the DDM (Digital Diagnostic
        Monitoring) (Bias = AV/500) (Unit
        = mA) <Help> This Measure gives
        the Tx Laser Bias value of the
         Line Transceiver
        "
	::= { pmlma10MesrlineTxBiasEntry 2 }


--- *********************************************************
---     TABLE for the pmlma10MesrlineRxPwr articles
--- *********************************************************

pmlma10MesrlineRxPwrTable OBJECT-TYPE
	SYNTAX  SEQUENCE OF Pmlma10MesrlineRxPwrEntry
	MAX-ACCESS not-accessible
	STATUS current
	DESCRIPTION
        "
        List of pmlma10MesrlineRxPwr Article
        "
	::= { pmlma10MesrLine 128 }


pmlma10MesrlineRxPwrEntry OBJECT-TYPE
	SYNTAX Pmlma10MesrlineRxPwrEntry
	MAX-ACCESS not-accessible
	STATUS current
	DESCRIPTION
        "
        Row definition for the pmlma10MesrlineRxPwr
        table
        "
	INDEX   { pmlma10MesrlineRxPwrIndex }
	::= { pmlma10MesrlineRxPwrTable 1 }


Pmlma10MesrlineRxPwrEntry ::=
	SEQUENCE {
	pmlma10MesrlineRxPwrIndex
		INTEGER,
	pmlma10MesrlineRxPwrPortn
		INTEGER
	}


pmlma10MesrlineRxPwrIndex OBJECT-TYPE
	SYNTAX  INTEGER(0..128)
	MAX-ACCESS  read-only
	STATUS current
	DESCRIPTION
        "
        Index definition for the pmlma10MesrlineRxPwr
        table
        "
	::= { pmlma10MesrlineRxPwrEntry 1 }


pmlma10MesrlineRxPwrPortn OBJECT-TYPE
	SYNTAX  INTEGER (0..65535)
	MAX-ACCESS read-only
	STATUS current
	DESCRIPTION
        "
        Line Optical Module Rx Power :This
        OID gives the Receive power value
        of the Line Transceiver, read in
        the DDM (Digital Diagnostic Monitoring)
        (Power = 10*log(AV)-40) (Unit =
        dBm) <Help> This Measure gives
         the Receive power value of the
        Line Transceiver
        "
	::= { pmlma10MesrlineRxPwrEntry 2 }







--- *****************************************************
--- $$$$$$$$$$$$$$$$$$$$$$$$$$$$$$$$$$$$$$$$$$$$$$$$$$$$$
---     DOWNLOAD
--- $$$$$$$$$$$$$$$$$$$$$$$$$$$$$$$$$$$$$$$$$$$$$$$$$$$$$
--- *****************************************************



--- *****************************************************
---     LEAF for the restartProcess article
--- *****************************************************
pmlma10DwlrestartProcess OBJECT IDENTIFIER ::= { pmlma10DwlOther 0 }




pmlma10DwlColdRestartProcessed OBJECT-TYPE
	  SYNTAX EkiOnOff
	  MAX-ACCESS read-only
	  STATUS current
	  DESCRIPTION
        "
        Cold Restart :This OID indicates
        that the module last restart was
        a Cold RESTART
        "
	  ::= { pmlma10DwlrestartProcess 2 }



pmlma10DwlWarmRestartProcessed OBJECT-TYPE
	  SYNTAX EkiOnOff
	  MAX-ACCESS read-only
	  STATUS current
	  DESCRIPTION
        "
        Warm Restart :This OID indicates
        that the module last restart was
        a Warm RESTART
        "
	  ::= { pmlma10DwlrestartProcess 1 }



--- *****************************************************
---     LEAF for the swBanksUsed article
--- *****************************************************
pmlma10DwlswBanksUsed OBJECT IDENTIFIER ::= { pmlma10DwlOther 1 }




pmlma10DwlSwBank2Notempty OBJECT-TYPE
	  SYNTAX EkiOnOff
	  MAX-ACCESS read-only
	  STATUS current
	  DESCRIPTION
        "
        SW bank 2 loaded :This OID indicates
        a software is loaded in SW bank
        2  <Help>  This status indicates
        if the SW bank 2 contains SW package
        "
	  ::= { pmlma10DwlswBanksUsed 6 }



pmlma10DwlSwBank1Notempty OBJECT-TYPE
	  SYNTAX EkiOnOff
	  MAX-ACCESS read-only
	  STATUS current
	  DESCRIPTION
        "
        SW bank 1 loaded :This OID indicates
        a software is loaded in SW bank
        1  <Help>  This status indicates
        if the SW bank 1 contains SW package
        "
	  ::= { pmlma10DwlswBanksUsed 5 }



pmlma10DwlSwBank2Used OBJECT-TYPE
	  SYNTAX EkiOnOff
	  MAX-ACCESS read-only
	  STATUS current
	  DESCRIPTION
        "
        SW bank 2 active :This OID indicates
        the module is working on SW bank
        2  <Help>  This status indicates
        if the SW bank 2 is active or standby
        "
	  ::= { pmlma10DwlswBanksUsed 2 }



pmlma10DwlSwBank1Used OBJECT-TYPE
	  SYNTAX EkiOnOff
	  MAX-ACCESS read-only
	  STATUS current
	  DESCRIPTION
        "
        SW bank 1 active :This OID indicates
        the module is working on SW bank
        1  <Help>  This status indicates
        if the SW bank 1 is active or standby
        "
	  ::= { pmlma10DwlswBanksUsed 1 }



--- *****************************************************
---     LEAF for the gwBanksUsed article
--- *****************************************************
pmlma10DwlgwBanksUsed OBJECT IDENTIFIER ::= { pmlma10DwlOther 2 }




pmlma10DwlGwBank4Notempty OBJECT-TYPE
	  SYNTAX EkiOnOff
	  MAX-ACCESS read-only
	  STATUS current
	  DESCRIPTION
        "
        GW bank 4 loaded :This OID indicates
        a gateware is loaded in GW bank
        4
        "
	  ::= { pmlma10DwlgwBanksUsed 8 }



pmlma10DwlGwBank3Notempty OBJECT-TYPE
	  SYNTAX EkiOnOff
	  MAX-ACCESS read-only
	  STATUS current
	  DESCRIPTION
        "
        GW bank 3 loaded :This OID indicates
        a gateware is loaded in GW bank
        3  <Help>  This status indicates
        if the GW bank 3 contains GW package
        "
	  ::= { pmlma10DwlgwBanksUsed 7 }



pmlma10DwlGwBank2Notempty OBJECT-TYPE
	  SYNTAX EkiOnOff
	  MAX-ACCESS read-only
	  STATUS current
	  DESCRIPTION
        "
        GW bank 2 loaded :This OID indicates
        a gateware is loaded in GW bank
        2
        "
	  ::= { pmlma10DwlgwBanksUsed 6 }



pmlma10DwlGwBank1Notempty OBJECT-TYPE
	  SYNTAX EkiOnOff
	  MAX-ACCESS read-only
	  STATUS current
	  DESCRIPTION
        "
        GW bank 1 loaded :This OID indicates
        a gateware is loaded in GW bank
        1  <Help>  This status indicates
        if the GW bank 1 contains GW package
        "
	  ::= { pmlma10DwlgwBanksUsed 5 }



pmlma10DwlGwBank4Used OBJECT-TYPE
	  SYNTAX EkiOnOff
	  MAX-ACCESS read-only
	  STATUS current
	  DESCRIPTION
        "
        GW bank 4 active :This OID indicates
        the module is working on GW bank
        4
        "
	  ::= { pmlma10DwlgwBanksUsed 4 }



pmlma10DwlGwBank3Used OBJECT-TYPE
	  SYNTAX EkiOnOff
	  MAX-ACCESS read-only
	  STATUS current
	  DESCRIPTION
        "
        GW bank 3 active :This OID indicates
        the module is working on GW bank
        3  <Help>  This status indicates
        if the GW bank 3 is active or standby
        "
	  ::= { pmlma10DwlgwBanksUsed 3 }



pmlma10DwlGwBank2Used OBJECT-TYPE
	  SYNTAX EkiOnOff
	  MAX-ACCESS read-only
	  STATUS current
	  DESCRIPTION
        "
        GW bank 2 active :This OID indicates
        the module is working on GW bank
        2
        "
	  ::= { pmlma10DwlgwBanksUsed 2 }



pmlma10DwlGwBank1Used OBJECT-TYPE
	  SYNTAX EkiOnOff
	  MAX-ACCESS read-only
	  STATUS current
	  DESCRIPTION
        "
        GW bank 1 active :This OID indicates
        the module is working on GW bank
        1  <Help>  This status indicates
        if the GW bank 1 is active or standby
        "
	  ::= { pmlma10DwlgwBanksUsed 1 }








--- *****************************************************
--- $$$$$$$$$$$$$$$$$$$$$$$$$$$$$$$$$$$$$$$$$$$$$$$$$$$$$
---     CONFIG
--- $$$$$$$$$$$$$$$$$$$$$$$$$$$$$$$$$$$$$$$$$$$$$$$$$$$$$
--- *****************************************************



--- *****************************************************
---     LEAF for the table Group accessCAisCsf
--- *****************************************************

pmlma10CfgAccessCAisCsf OBJECT IDENTIFIER ::= { pmlma10Config 1 }



--- *****************************************************
---     LEAF for the table 0012
--- *****************************************************

pmlma10CfgClientcaiscsfTable OBJECT-TYPE
	SYNTAX  SEQUENCE OF Pmlma10CfgClientcaiscsfEntry
	MAX-ACCESS not-accessible
	STATUS current
	DESCRIPTION
        "
        List of  Article
        "
	::= { pmlma10CfgAccessCAisCsf 1 }


pmlma10CfgClientcaiscsfEntry OBJECT-TYPE
	SYNTAX Pmlma10CfgClientcaiscsfEntry
	MAX-ACCESS not-accessible
	STATUS current
	DESCRIPTION
        "
        Row definition for the accessCAisCsf
        table
        "
	INDEX   { pmlma10CfgClientcaiscsfIndex }
	::= { pmlma10CfgClientcaiscsfTable 1 }


Pmlma10CfgClientcaiscsfEntry ::=
	SEQUENCE {
	pmlma10CfgClientcaiscsfIndex
		INTEGER,
	pmlma10CfgReservePortn
		Unsigned32
	}


pmlma10CfgClientcaiscsfIndex OBJECT-TYPE
	SYNTAX  INTEGER(0..128)
	MAX-ACCESS  read-only
	STATUS current
	DESCRIPTION
        "
        Index definition for the clientcaiscsf
        table
        "
	::= { pmlma10CfgClientcaiscsfEntry 1 }


pmlma10CfgReservePortn OBJECT-TYPE
	SYNTAX  Unsigned32 (0..65536)
	MAX-ACCESS read-write
	STATUS current
	DESCRIPTION
        "
        CAIS mode  on Client Port :This
        register enables/disables port
          laser shutdown on CAIS insertion
        condition
        "
	::= { pmlma10CfgClientcaiscsfEntry 3 }


--- *****************************************************
---     LEAF for the table Group startup
--- *****************************************************

pmlma10CfgStartup OBJECT IDENTIFIER ::= { pmlma10Config 2 }



--- *****************************************************
---     LEAF for the table 2110
--- *****************************************************

pmlma10CfgClientStartupTable OBJECT-TYPE
	SYNTAX  SEQUENCE OF Pmlma10CfgClientStartupEntry
	MAX-ACCESS not-accessible
	STATUS current
	DESCRIPTION
        "
        List of  Article
        "
	::= { pmlma10CfgStartup 1 }


pmlma10CfgClientStartupEntry OBJECT-TYPE
	SYNTAX Pmlma10CfgClientStartupEntry
	MAX-ACCESS not-accessible
	STATUS current
	DESCRIPTION
        "
        Row definition for the startup
        table
        "
	INDEX   { pmlma10CfgClientStartupIndex }
	::= { pmlma10CfgClientStartupTable 1 }


Pmlma10CfgClientStartupEntry ::=
	SEQUENCE {
	pmlma10CfgClientStartupIndex
		INTEGER,
	pmlma10CfgSystConfPortPortn
		Unsigned32,
	pmlma10CfgNetConfPortPortn
		Unsigned32,
	pmlma10CfgOptionsPortPortn
		Unsigned32
	}


pmlma10CfgClientStartupIndex OBJECT-TYPE
	SYNTAX  INTEGER(0..128)
	MAX-ACCESS  read-only
	STATUS current
	DESCRIPTION
        "
        Index definition for the clientStartup
        table
        "
	::= { pmlma10CfgClientStartupEntry 1 }


pmlma10CfgSystConfPortPortn OBJECT-TYPE
	SYNTAX  Unsigned32 (0..65536)
	MAX-ACCESS read-write
	STATUS current
	DESCRIPTION
        "
        Default Settings on Client Port
        :This  register configures the
         default initialisation settings
        on the port.
        "
	::= { pmlma10CfgClientStartupEntry 3 }


pmlma10CfgNetConfPortPortn OBJECT-TYPE
	SYNTAX  Unsigned32 (0..65536)
	MAX-ACCESS read-write
	STATUS current
	DESCRIPTION
        "
        Default Settings on Client Port
        :This  register configures the
         default initialisation settings
        on the port.
        "
	::= { pmlma10CfgClientStartupEntry 4 }


pmlma10CfgOptionsPortPortn OBJECT-TYPE
	SYNTAX  Unsigned32 (0..65536)
	MAX-ACCESS read-write
	STATUS current
	DESCRIPTION
        "
        Default Options on Client Port
        :This register configures the default
        options on the port.
        "
	::= { pmlma10CfgClientStartupEntry 14 }


--- *****************************************************
---     LEAF for the table 2190
--- *****************************************************

pmlma10CfgLinexr1StartupTable OBJECT-TYPE
	SYNTAX  SEQUENCE OF Pmlma10CfgLinexr1StartupEntry
	MAX-ACCESS not-accessible
	STATUS current
	DESCRIPTION
        "
        List of  Article
        "
	::= { pmlma10CfgStartup 2 }


pmlma10CfgLinexr1StartupEntry OBJECT-TYPE
	SYNTAX Pmlma10CfgLinexr1StartupEntry
	MAX-ACCESS not-accessible
	STATUS current
	DESCRIPTION
        "
        Row definition for the startup
        table
        "
	INDEX   { pmlma10CfgLinexr1StartupIndex }
	::= { pmlma10CfgLinexr1StartupTable 1 }


Pmlma10CfgLinexr1StartupEntry ::=
	SEQUENCE {
	pmlma10CfgLinexr1StartupIndex
		INTEGER,
	pmlma10CfgSystConfLinePortn
		Unsigned32,
	pmlma10CfgOptionsLinePortn
		Unsigned32
	}


pmlma10CfgLinexr1StartupIndex OBJECT-TYPE
	SYNTAX  INTEGER(0..128)
	MAX-ACCESS  read-only
	STATUS current
	DESCRIPTION
        "
        Index definition for the linexr1Startup
        table
        "
	::= { pmlma10CfgLinexr1StartupEntry 1 }


pmlma10CfgSystConfLinePortn OBJECT-TYPE
	SYNTAX  Unsigned32 (0..65536)
	MAX-ACCESS read-write
	STATUS current
	DESCRIPTION
        "
        Default Settings on Line :This
        register configures the default
        initialisation settings on Line
        "
	::= { pmlma10CfgLinexr1StartupEntry 3 }


pmlma10CfgOptionsLinePortn OBJECT-TYPE
	SYNTAX  Unsigned32 (0..65536)
	MAX-ACCESS read-write
	STATUS current
	DESCRIPTION
        "
        Default Options on Line :This
         register configures the default
        options on the line
        "
	::= { pmlma10CfgLinexr1StartupEntry 14 }


--- *****************************************************
---     LEAF for the table 21AB
--- *****************************************************

pmlma10CfgEmptyTable OBJECT-TYPE
	SYNTAX  SEQUENCE OF Pmlma10CfgEmptyEntry
	MAX-ACCESS not-accessible
	STATUS current
	DESCRIPTION
        "
        List of  Article
        "
	::= { pmlma10CfgStartup 3 }


pmlma10CfgEmptyEntry OBJECT-TYPE
	SYNTAX Pmlma10CfgEmptyEntry
	MAX-ACCESS not-accessible
	STATUS current
	DESCRIPTION
        "
        Row definition for the startup
        table
        "
	INDEX   { pmlma10CfgEmptyIndex }
	::= { pmlma10CfgEmptyTable 1 }


Pmlma10CfgEmptyEntry ::=
	SEQUENCE {
	pmlma10CfgEmptyIndex
		INTEGER,
	pmlma10CfgSystConfMsaLinePortn
		Unsigned32
	}


pmlma10CfgEmptyIndex OBJECT-TYPE
	SYNTAX  INTEGER(0..128)
	MAX-ACCESS  read-only
	STATUS current
	DESCRIPTION
        "
        Index definition for the empty
        table
        "
	::= { pmlma10CfgEmptyEntry 1 }


pmlma10CfgSystConfMsaLinePortn OBJECT-TYPE
	SYNTAX  Unsigned32 (0..65536)
	MAX-ACCESS read-write
	STATUS current
	DESCRIPTION
        "
        Default settings on MSA :This
         register configures the default
        initialisation settings on MSA
        "
	::= { pmlma10CfgEmptyEntry 3 }


--- *****************************************************
---     LEAF for the table Group labels
--- *****************************************************

pmlma10CfgLabels OBJECT IDENTIFIER ::= { pmlma10Config 3 }



--- *****************************************************
---     LEAF for the table 0003
--- *****************************************************

pmlma10CfgLabelclientTable OBJECT-TYPE
	SYNTAX  SEQUENCE OF Pmlma10CfgLabelclientEntry
	MAX-ACCESS not-accessible
	STATUS current
	DESCRIPTION
        "
        List of  Article
        "
	::= { pmlma10CfgLabels 1 }


pmlma10CfgLabelclientEntry OBJECT-TYPE
	SYNTAX Pmlma10CfgLabelclientEntry
	MAX-ACCESS not-accessible
	STATUS current
	DESCRIPTION
        "
        Row definition for the labels
         table
        "
	INDEX   { pmlma10CfgLabelclientIndex }
	::= { pmlma10CfgLabelclientTable 1 }


Pmlma10CfgLabelclientEntry ::=
	SEQUENCE {
	pmlma10CfgLabelclientIndex
		INTEGER,
	pmlma10CfgLabelclientPortn
		DisplayString
	}


pmlma10CfgLabelclientIndex OBJECT-TYPE
	SYNTAX  INTEGER(0..128)
	MAX-ACCESS  read-only
	STATUS current
	DESCRIPTION
        "
        Index definition for the labelclient
        table
        "
	::= { pmlma10CfgLabelclientEntry 1 }


pmlma10CfgLabelclientPortn OBJECT-TYPE
	SYNTAX  DisplayString( SIZE(1..16))
	MAX-ACCESS read-write
	STATUS current
	DESCRIPTION
        "
        Default settings on the label
         of the Ports :These registers
         configures the default initialisation
        settings of the labels of the ports.
        "
	::= { pmlma10CfgLabelclientEntry 3 }


--- *****************************************************
---     LEAF for the table 0004
--- *****************************************************

pmlma10CfgLabellineTable OBJECT-TYPE
	SYNTAX  SEQUENCE OF Pmlma10CfgLabellineEntry
	MAX-ACCESS not-accessible
	STATUS current
	DESCRIPTION
        "
        List of  Article
        "
	::= { pmlma10CfgLabels 2 }


pmlma10CfgLabellineEntry OBJECT-TYPE
	SYNTAX Pmlma10CfgLabellineEntry
	MAX-ACCESS not-accessible
	STATUS current
	DESCRIPTION
        "
        Row definition for the labels
         table
        "
	INDEX   { pmlma10CfgLabellineIndex }
	::= { pmlma10CfgLabellineTable 1 }


Pmlma10CfgLabellineEntry ::=
	SEQUENCE {
	pmlma10CfgLabellineIndex
		INTEGER,
	pmlma10CfgLabellinePortn
		DisplayString
	}


pmlma10CfgLabellineIndex OBJECT-TYPE
	SYNTAX  INTEGER(0..128)
	MAX-ACCESS  read-only
	STATUS current
	DESCRIPTION
        "
        Index definition for the labelline
        table
        "
	::= { pmlma10CfgLabellineEntry 1 }


pmlma10CfgLabellinePortn OBJECT-TYPE
	SYNTAX  DisplayString( SIZE(1..16))
	MAX-ACCESS read-write
	STATUS current
	DESCRIPTION
        "
        Default settings on the label
         of the lines :These registers
         configures the default initialisation
        settings of the labels of the lines.
        "
	::= { pmlma10CfgLabellineEntry 3 }


--- *****************************************************
---     LEAF for the table Group startuptlh
--- *****************************************************

pmlma10CfgStartuptlh OBJECT IDENTIFIER ::= { pmlma10Config 4 }



--- *****************************************************
---     LEAF for the table 2710
--- *****************************************************

pmlma10CfgOtxtlhTable OBJECT-TYPE
	SYNTAX  SEQUENCE OF Pmlma10CfgOtxtlhEntry
	MAX-ACCESS not-accessible
	STATUS current
	DESCRIPTION
        "
        List of  Article
        "
	::= { pmlma10CfgStartuptlh 1 }


pmlma10CfgOtxtlhEntry OBJECT-TYPE
	SYNTAX Pmlma10CfgOtxtlhEntry
	MAX-ACCESS not-accessible
	STATUS current
	DESCRIPTION
        "
        Row definition for the startuptlh
        table
        "
	INDEX   { pmlma10CfgOtxtlhIndex }
	::= { pmlma10CfgOtxtlhTable 1 }


Pmlma10CfgOtxtlhEntry ::=
	SEQUENCE {
	pmlma10CfgOtxtlhIndex
		INTEGER,
	pmlma10CfgLinePwrLaserPortn
		Unsigned32,
	pmlma10CfgLineFCurrentPortn
		Unsigned32,
	pmlma10CfgLineGridCurrentPortn
		Unsigned32,
	pmlma10CfgFPortn
		Unsigned32,
	pmlma10CfgRxLineFCurrentPortn
		Unsigned32
	}


pmlma10CfgOtxtlhIndex OBJECT-TYPE
	SYNTAX  INTEGER(0..128)
	MAX-ACCESS  read-only
	STATUS current
	DESCRIPTION
        "
        Index definition for the otxtlh
        table
        "
	::= { pmlma10CfgOtxtlhEntry 1 }


pmlma10CfgLinePwrLaserPortn OBJECT-TYPE
	SYNTAX  Unsigned32 (0..65536)
	MAX-ACCESS read-write
	STATUS current
	DESCRIPTION
        "
        Defaut Line output Power :This
        register configures the start-up
        output power of the Line tranceiver
         (Unit = dBm)
        "
	::= { pmlma10CfgOtxtlhEntry 6 }


pmlma10CfgLineFCurrentPortn OBJECT-TYPE
	SYNTAX  Unsigned32 (0..65536)
	MAX-ACCESS read-write
	STATUS current
	DESCRIPTION
        "
        Default Line transceiver Tx Channel
        :This register configures the start-up
        laser channel of the Line Tx transceiver
        "
	::= { pmlma10CfgOtxtlhEntry 7 }


pmlma10CfgLineGridCurrentPortn OBJECT-TYPE
	SYNTAX  Unsigned32 (0..65536)
	MAX-ACCESS read-write
	STATUS current
	DESCRIPTION
        "
        Default Line transceiver Grid
         :This register configures the
         start-up laser grid of the Line
        transceiver
        "
	::= { pmlma10CfgOtxtlhEntry 8 }


pmlma10CfgFPortn OBJECT-TYPE
	SYNTAX  Unsigned32 (0..65536)
	MAX-ACCESS read-write
	STATUS current
	DESCRIPTION
        "
        Default Line TRX lowest Freq :This
        register configures the start-up
        lowest frequency of the Line transceiver
        "
	::= { pmlma10CfgOtxtlhEntry 9 }


pmlma10CfgRxLineFCurrentPortn OBJECT-TYPE
	SYNTAX  Unsigned32 (0..65536)
	MAX-ACCESS read-write
	STATUS current
	DESCRIPTION
        "
        Default Line transceiver Rx Channel
        :This register configures the start-up
        laser channel of the Line Rx transceiver
        "
	::= { pmlma10CfgOtxtlhEntry 10 }


--- *****************************************************
---     LEAF for the table Group other
--- *****************************************************

pmlma10CfgOther OBJECT IDENTIFIER ::= { pmlma10Config 5 }



--- *****************************************************
---     LEAF for the table 2300
--- *****************************************************

pmlma10tablemoduleOther OBJECT IDENTIFIER ::= { pmlma10CfgOther 1 }



pmlma10Cfgmode OBJECT-TYPE
	  SYNTAX Unsigned32 (0..65536)
	  MAX-ACCESS read-write
	  STATUS current
	  DESCRIPTION
        "
        Default settings on Module :This
        register selects the configuration
        mode of the module
        "
	  ::= { pmlma10tablemoduleOther 2 }



--- *****************************************************
---     LEAF for the table Group startuptablefive
--- *****************************************************

pmlma10CfgStartuptablefive OBJECT IDENTIFIER ::= { pmlma10Config 6 }



--- *****************************************************
---     LEAF for the table 0005
--- *****************************************************

pmlma10CfgOtxtlhcapabilitiesTable OBJECT-TYPE
	SYNTAX  SEQUENCE OF Pmlma10CfgOtxtlhcapabilitiesEntry
	MAX-ACCESS not-accessible
	STATUS current
	DESCRIPTION
        "
        List of  Article
        "
	::= { pmlma10CfgStartuptablefive 1 }


pmlma10CfgOtxtlhcapabilitiesEntry OBJECT-TYPE
	SYNTAX Pmlma10CfgOtxtlhcapabilitiesEntry
	MAX-ACCESS not-accessible
	STATUS current
	DESCRIPTION
        "
        Row definition for the startuptablefive
        table
        "
	INDEX   { pmlma10CfgOtxtlhcapabilitiesIndex }
	::= { pmlma10CfgOtxtlhcapabilitiesTable 1 }


Pmlma10CfgOtxtlhcapabilitiesEntry ::=
	SEQUENCE {
	pmlma10CfgOtxtlhcapabilitiesIndex
		INTEGER,
	pmlma10CfgComponentTypePortn
		Unsigned32,
	pmlma10CfgMiscellaneousPortn
		Unsigned32,
	pmlma10CfgFirstChannelPortn
		Unsigned32,
	pmlma10CfgLastChannelPortn
		Unsigned32,
	pmlma10CfgGridPortn
		Unsigned32
	}


pmlma10CfgOtxtlhcapabilitiesIndex OBJECT-TYPE
	SYNTAX  INTEGER(0..128)
	MAX-ACCESS  read-only
	STATUS current
	DESCRIPTION
        "
        Index definition for the otxtlhcapabilities
        table
        "
	::= { pmlma10CfgOtxtlhcapabilitiesEntry 1 }


pmlma10CfgComponentTypePortn OBJECT-TYPE
	SYNTAX  Unsigned32 (0..65536)
	MAX-ACCESS read-only
	STATUS current
	DESCRIPTION
        "
        Component parameters :This OID
        defines the component parameters
        "
	::= { pmlma10CfgOtxtlhcapabilitiesEntry 3 }


pmlma10CfgMiscellaneousPortn OBJECT-TYPE
	SYNTAX  Unsigned32 (0..65536)
	MAX-ACCESS read-only
	STATUS current
	DESCRIPTION
        "
        Miscellaneous default settings
        :This OID defines the miscellaneous
        parameters
        "
	::= { pmlma10CfgOtxtlhcapabilitiesEntry 4 }


pmlma10CfgFirstChannelPortn OBJECT-TYPE
	SYNTAX  Unsigned32 (0..65536)
	MAX-ACCESS read-only
	STATUS current
	DESCRIPTION
        "
        Number of the first channel of
        the component :This OID defines
        the first channel number of the
        PM
        "
	::= { pmlma10CfgOtxtlhcapabilitiesEntry 5 }


pmlma10CfgLastChannelPortn OBJECT-TYPE
	SYNTAX  Unsigned32 (0..65536)
	MAX-ACCESS read-only
	STATUS current
	DESCRIPTION
        "
        Number of the last channel of
         the component :This OID defines
        the last channel number of the
         PM
        "
	::= { pmlma10CfgOtxtlhcapabilitiesEntry 6 }


pmlma10CfgGridPortn OBJECT-TYPE
	SYNTAX  Unsigned32 (0..65536)
	MAX-ACCESS read-only
	STATUS current
	DESCRIPTION
        "
        Grid value of the component :This
        OID defines the grid of the PM
        "
	::= { pmlma10CfgOtxtlhcapabilitiesEntry 7 }



pmlma10CfgWriteConfiguration  OBJECT-TYPE
	SYNTAX EkiOnOff
	MAX-ACCESS read-write
	STATUS current
	DESCRIPTION
	"Write configuration to module:This OID
	 writes the complete configuration to the module"
	::= { pmlma10Config 257 }






--- *****************************************************
---     TRAP OBJECTS
--- *****************************************************

pmlma10trapPortNumber OBJECT-TYPE
	SYNTAX INTEGER(1..64)
	MAX-ACCESS read-only
	STATUS current
	DESCRIPTION
	"Last port which generates a trap"
	::= { pmlma10traps 2 }

pmlma10trapLineNumber OBJECT-TYPE
	SYNTAX INTEGER(1..64)
	MAX-ACCESS read-only
	STATUS current
	DESCRIPTION
	"Last Line which generates a trap"
	::= { pmlma10traps 3 }

pmlma10trapBoardNumber OBJECT-TYPE
	SYNTAX INTEGER(1..64)
	MAX-ACCESS read-only
	STATUS current
	DESCRIPTION
	"Last module which generates a trap"
	::= { pmlma10traps 4 }







--- *****************************************************
---     LINE TRAPS
--- *****************************************************

pmlma10LineTrapNotUrgentGoesOn NOTIFICATION-TYPE
	OBJECTS {pmlma10AlmLineDdmWarningPortn, pmlma10trapLineNumber, pmlma10trapBoardNumber}
	STATUS current
	--&FILTNAME    "PMLMA10 Line Not Urgent ON"
	--&ACTIONS     { log, minor }
	--&MATCH       { pmlma10AlmLineDdmWarningPortn "on", pmlma10trapLineNumber "$2", pmlma10trapBoardNumber "$3"}
	--&MESG        "DDM Warning appears on Line Port $2 of PMLMA10 in Slot $3 ($A)"
	DESCRIPTION "Not urgent Line default is activated"
	::= { pmlma10traps 30 }

pmlma10LineTrapNotUrgentGoesOff NOTIFICATION-TYPE
	OBJECTS {pmlma10AlmLineDdmWarningPortn, pmlma10trapLineNumber, pmlma10trapBoardNumber}
	STATUS current
	--&FILTNAME    "PMLMA10 Line Not Urgent OFF"
	--&ACTIONS     { log, normal }
	--&CLEARS      { "PMLMA10 Line Not Urgent ON" }
	--&MATCH       { pmlma10AlmLineDdmWarningPortn "on", pmlma10trapLineNumber "$2", pmlma10trapBoardNumber "$3"}
	--&MESG        "DDM Warning disappears on Line Port $2 of PMLMA10 in Slot $3 ($A)"
	DESCRIPTION "Not urgent Line default disappeared"
	::= { pmlma10traps 31 }

pmlma10LineTrapUrgentGoesOn NOTIFICATION-TYPE
	OBJECTS {pmlma10AlmLineDdmAlmPortn, pmlma10trapLineNumber, pmlma10trapBoardNumber}
	STATUS current
	--&FILTNAME    "PMLMA10 Line Urgent ON"
	--&ACTIONS     { log, major }
	--&MATCH       { pmlma10AlmLineDdmAlmPortn "on", pmlma10trapLineNumber "$2", pmlma10trapBoardNumber "$3"}
	--&MESG        "DDM Alarm appears on Line Port $2 of PMLMA10 in Slot $3 ($A)"
	DESCRIPTION "Urgent Line default is activated"
	::= { pmlma10traps 32 }

pmlma10LineTrapUrgentGoesOff NOTIFICATION-TYPE
	OBJECTS {pmlma10AlmLineDdmAlmPortn, pmlma10trapLineNumber, pmlma10trapBoardNumber}
	STATUS current
	--&FILTNAME    "PMLMA10 Line Urgent OFF"
	--&ACTIONS     { log, normal }
	--&CLEARS      { "PMLMA10 Line Urgent ON" }
	--&MATCH       { pmlma10AlmLineDdmAlmPortn "on", pmlma10trapLineNumber "$2", pmlma10trapBoardNumber "$3"}
	--&MESG        "DDM Alarm disappears on Line Port $2 of PMLMA10 in Slot $3 ($A)"
	DESCRIPTION "Urgent Line default disappeared"
	::= { pmlma10traps 33 }

pmlma10LineTrapCritGoesOn NOTIFICATION-TYPE
	OBJECTS {pmlma10AlmLineFailPortn , pmlma10AlmLineHwFailPortn , pmlma10trapLineNumber, pmlma10trapBoardNumber}
	STATUS current
	--&FILTNAME    "PMLMA10 Line Fail ON"
	--&ACTIONS     { log, critical }
	--&MATCH       { pmlma10AlmLineFailPortn "on", pmlma10AlmLineHwFailPortn "*", pmlma10trapLineNumber "$3", pmlma10trapBoardNumber "$4"}
	--&MESG        "Line Port $3 Down on PMLMA10 in Slot $4 ($A)"

	--&FILTNAME    "PMLMA10 Line HW Fail ON (Hidden)"
	--&ACTIONS     { info }
	--&MATCH       { pmlma10AlmLineFailPortn "*", pmlma10AlmLineHwFailPortn "on", pmlma10trapLineNumber "$3", pmlma10trapBoardNumber "$4"}
	--&MESG        "Line Port $3 Down on PMLMA10 in Slot $4 ($A)"
	DESCRIPTION "Critical Line default is activated"
	::= { pmlma10traps 34 }

pmlma10LineTrapCritGoesOff NOTIFICATION-TYPE
	OBJECTS {pmlma10AlmLineFailPortn , pmlma10AlmLineHwFailPortn , pmlma10trapLineNumber, pmlma10trapBoardNumber}
	STATUS current
	--&FILTNAME    "PMLMA10 Line Fail OFF"
	--&ACTIONS     { log,  normal }
	--&CLEARS      { "PMLMA10 Line Fail ON" }
	--&MATCH       { pmlma10AlmLineFailPortn "on", pmlma10AlmLineHwFailPortn "*", pmlma10trapLineNumber "$3", pmlma10trapBoardNumber "$4"}
	--&MESG        "Line Port $3 Up on PMLMA10 in Slot $4 ($A)"

	--&FILTNAME    "PMLMA10 Line HW Fail OFF (Hidden)"
	--&ACTIONS     { info }
	--&MATCH       { pmlma10AlmLineFailPortn "*", pmlma10AlmLineHwFailPortn "on", pmlma10trapLineNumber "$3", pmlma10trapBoardNumber "$4"}
	--&MESG        "Line Port $3 Up on PMLMA10 in Slot $4 ($A)"
	DESCRIPTION "Critical Line default disappeared"
	::= { pmlma10traps 35 }






--- *****************************************************
---     CLIENT TRAPS
--- *****************************************************

pmlma10ClientTrapNotUrgentGoesOn NOTIFICATION-TYPE
	OBJECTS {pmlma10AlmSfpDdmWarningPortn, pmlma10trapPortNumber, pmlma10trapBoardNumber}
	STATUS current
		--&FILTNAME    "PMLMA10 Client Not Urgent ON"
		--&ACTIONS     { log, minor }
		--&MATCH       { pmlma10AlmSfpDdmWarningPortn "on", pmlma10trapPortNumber "$2", pmlma10trapBoardNumber "$3"}
		--&MESG        "DDM Warning appears on Client Port $2 of PMLMA10 in Slot $3 ($A)"
	DESCRIPTION "Not urgent client default is activated"
	::= { pmlma10traps 40 }

pmlma10ClientTrapNotUrgentGoesOff NOTIFICATION-TYPE
	OBJECTS {pmlma10AlmSfpDdmWarningPortn, pmlma10trapPortNumber, pmlma10trapBoardNumber}
	STATUS current
		--&FILTNAME    "PMLMA10 Client Not Urgent OFF"
		--&ACTIONS     { log, normal }
		--&CLEARS      { "PMLMA10 Client Not Urgent ON" }
		--&MATCH       { pmlma10AlmSfpDdmWarningPortn "on", pmlma10trapPortNumber "$2", pmlma10trapBoardNumber "$3"}
		--&MESG        "DDM Warning appears on Client Port $2 of PMLMA10 in Slot $3 ($A)"
	DESCRIPTION "Not urgent client default disappeared"
	::= { pmlma10traps 41 }

pmlma10ClientTrapUrgentGoesOn NOTIFICATION-TYPE
	OBJECTS {pmlma10AlmSfpDdmAlmPortn, pmlma10trapPortNumber, pmlma10trapBoardNumber}
	STATUS current
		--&FILTNAME    "PMLMA10 Client Urgent ON"
		--&ACTIONS     { log, major }
		--&MATCH       { pmlma10AlmSfpDdmAlmPortn "on", pmlma10trapPortNumber "$2", pmlma10trapBoardNumber "$3"}
		--&MESG        "DDM Alarm appears on Client Port $2 of PMLMA10 in Slot $3 ($A)"
	DESCRIPTION "Urgent client default is activated"
	::= { pmlma10traps 42 }

pmlma10ClientTrapUrgentGoesOff NOTIFICATION-TYPE
	OBJECTS {pmlma10AlmSfpDdmAlmPortn, pmlma10trapPortNumber, pmlma10trapBoardNumber}
	STATUS current
		--&FILTNAME    "PMLMA10 Client Urgent OFF"
		--&ACTIONS     { log, normal }
		--&CLEARS      { "PMLMA10 Client Urgent ON" }
		--&MATCH       { pmlma10AlmSfpDdmAlmPortn "on", pmlma10trapPortNumber "$2", pmlma10trapBoardNumber "$3"}
		--&MESG        "DDM Alarm disappears on Client Port $2 of PMLMA10 in Slot $3 ($A)"
	DESCRIPTION "Urgent client default disappeared"
	::= { pmlma10traps 43 }

pmlma10ClientTrapCritGoesOn NOTIFICATION-TYPE
	OBJECTS {pmlma10AlmFailAccPortn, pmlma10AlmHwFailAccPortn, pmlma10trapPortNumber, pmlma10trapBoardNumber}
	STATUS current
		--&FILTNAME    "PMLMA10 Client Fail ON"
		--&ACTIONS     { log, critical }
		--&MATCH       { pmlma10AlmFailAccPortn "on", pmlma10AlmHwFailAccPortn "*", pmlma10trapPortNumber "$3", pmlma10trapBoardNumber "$4"}
		--&MESG        "Client Port $3 Down on PMLMA10 in Slot $4 ($A)"

		--&FILTNAME    "PMLMA10 Client HW Fail ON (Hidden)"
		--&ACTIONS     { info }
		--&MATCH       { pmlma10AlmFailAccPortn "*", pmlma10AlmHwFailAccPortn "on", pmlma10trapPortNumber "$3", pmlma10trapBoardNumber "$4"}
		--&MESG        "Client Port $3 Down on PMLMA10 in Slot $4 ($A)"
	DESCRIPTION "Critical client default is activated"
	::= { pmlma10traps 44 }

pmlma10ClientTrapCritGoesOff NOTIFICATION-TYPE
	OBJECTS {pmlma10AlmFailAccPortn, pmlma10AlmHwFailAccPortn, pmlma10trapPortNumber, pmlma10trapBoardNumber}
	STATUS current
		--&FILTNAME    "PMLMA10 Client Fail OFF"
		--&ACTIONS     { log, normal }
		--&CLEARS      { "PMLMA10 Client Fail ON" }
		--&MATCH       { pmlma10AlmFailAccPortn "on", pmlma10AlmHwFailAccPortn "*", pmlma10trapPortNumber "$3", pmlma10trapBoardNumber "$4"}
		--&MESG        "Client Port $3 Up on PMLMA10 in Slot $4 ($A)"

		--&FILTNAME    "PMLMA10 Client HW Fail OFF (Hidden)"
		--&ACTIONS     { info }
		--&MATCH       { pmlma10AlmFailAccPortn "*", pmlma10AlmHwFailAccPortn "on", pmlma10trapPortNumber "$3", pmlma10trapBoardNumber "$4"}
		--&MESG        "Client Port $3 Up on PMLMA10 in Slot $4 ($A)"
	DESCRIPTION "Critical client default disappeared"
	::= { pmlma10traps 45 }






--- *****************************************************
---     HW TRAPS
--- *****************************************************

pmlma10PowerTrapUrgentGoesOn NOTIFICATION-TYPE
	OBJECTS {pmlma10AlmDefFuseB, pmlma10AlmDefFuseA , pmlma10trapBoardNumber}
	STATUS current
		--&FILTNAME    "PMLMA10 Fuse A Fail ON"
		--&ACTIONS     { log, major }
		--&MATCH       { pmlma10AlmDefFuseB "*", pmlma10AlmDefFuseA "on", pmlma10trapBoardNumber "$3"}
		--&MESG        "Power Input A Fail on PMLMA10 in Slot $3 ($A)"

		--&FILTNAME    "PMLMA10 Fuse B Fail ON"
		--&ACTIONS     { log, major }
		--&MATCH       { pmlma10AlmDefFuseB "on", pmlma10AlmDefFuseA "*", pmlma10trapBoardNumber "$3"}
		--&MESG        "Power Input B Fail on PMLMA10 in Slot $3 ($A)"
	DESCRIPTION "Urgent power supply default is activated"
	::= { pmlma10traps 50 }

pmlma10PowerTrapUrgentGoesOff NOTIFICATION-TYPE
	OBJECTS {pmlma10AlmDefFuseB, pmlma10AlmDefFuseA , pmlma10trapBoardNumber}
	STATUS current
		--&FILTNAME    "PMLMA10 Fuse A&B Fail OFF"
		--&ACTIONS     { log, normal}
		--&CLEARS      { "PMLMA10 Fuse A Fail ON", "PMLMA10 Fuse B Fail ON" }
		--&MATCH       { pmlma10AlmDefFuseB "on", pmlma10AlmDefFuseA "on", pmlma10trapBoardNumber "$3"}
		--&MESG        "Power Inputs A and B Present on PMLMA10 in Slot $3 ($A)"
	DESCRIPTION "Urgent power supply default disappeared"
	::= { pmlma10traps 51 }






END
