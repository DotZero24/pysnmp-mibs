-- *****************************************************************
-- EKINOPS-Pm1004V.TXT:  MIB
--
--MIB Part Number:3MI00017AHAD
--MIB Version:02
--
-- Copyright (c) 2016 by Ekinops
-- All rights reserved.
--
-- *****************************************************************

EKINOPS-Pm1004V-MIB DEFINITIONS ::= BEGIN

IMPORTS
	ekinops,
	EkiState,
	EkiOnOff,
	EkiMode,
	EkiProtocol,
	EkiApiState,
	EkiSynchroMode,
	EkiMeasureType
			FROM EKINOPS-MIB
        MODULE-IDENTITY,
        OBJECT-TYPE,
        NOTIFICATION-TYPE,
	Unsigned32,
	Integer32,
	Counter32,
	IpAddress
        		FROM SNMPv2-SMI
 	TEXTUAL-CONVENTION,
	DisplayString
                FROM SNMPv2-TC;

modulePm1004v MODULE-IDENTITY
        LAST-UPDATED "201606020000Z"
        ORGANIZATION "Ekinops"
        CONTACT-INFO
         "Ekinops

          11, rue Louis de Broglie
          F-22300 Lannion / FRANCE

          Tel : +33 (0)2 96 05 00 30
          Fax : +33 (0)2 96 48 62 39

          E-mail: support@ekinops.net"
        DESCRIPTION
          "MIB for managing Ekinops modules with PM1004V software"
	REVISION "200803110000Z"
	DESCRIPTION
	  "Initial Version."
	REVISION "200808180000Z"
	DESCRIPTION
	  "Labels modifications."
	REVISION "200812020000Z"
	DESCRIPTION
	  "DCC Storm suppress"
	REVISION "200812080000Z"
	DESCRIPTION
	  "Client Signal Shutdown label"
	REVISION "200905260000Z"
	DESCRIPTION
	  "Client OOS TX and RX insertion"
	REVISION "200907220000Z"
	DESCRIPTION
	  "Add DCC and MAINTENANCE control"
	REVISION "200909020000Z"
	DESCRIPTION
	  "Some Labels updates"
	REVISION "200910270000Z"
	DESCRIPTION
	  "Add LossOfSync as alarm Line"
	REVISION "201003030000Z"
	DESCRIPTION
	  "Probcause,AlarmType - NMS"
	REVISION "201102040000Z"
	DESCRIPTION
	  "Formulas in comments and Event on XFP init"
	REVISION "201104290000Z"
	DESCRIPTION
	  "OTX-TLH features insertion"
	REVISION "201207030000Z"
	DESCRIPTION
	  "Minor cosmetic updates"
	REVISION "201403280000Z"
	DESCRIPTION
	  "Probcause,AlarmType - NMS completion"
	REVISION "201412230000Z"
	DESCRIPTION
	  "Labels cosmetic updates"
	REVISION "201605200000Z"
	DESCRIPTION
	  "New AlarmType – synthesisAlarm (12)"
	REVISION "201606020000Z"
	DESCRIPTION
	  "Capabilities objects of Table 5"
        ::= { ekinops 32 }



--- *****************************************************
---     LEAF LEVEL 2
--- *****************************************************


pm1004valarms OBJECT IDENTIFIER ::= { modulePm1004v 2 }
pm1004vAlmOther OBJECT IDENTIFIER ::= { pm1004valarms 1 }
pm1004vAlmOtherNurg OBJECT IDENTIFIER ::= { pm1004vAlmOther 1 }
pm1004vAlmOtherUrg OBJECT IDENTIFIER ::= { pm1004vAlmOther 2 }
pm1004vAlmOtherCrit OBJECT IDENTIFIER ::= { pm1004vAlmOther 3 }

pm1004vAlmClient OBJECT IDENTIFIER ::= { pm1004valarms 2 }
pm1004vAlmClientNurg OBJECT IDENTIFIER ::= { pm1004vAlmClient 1 }
pm1004vAlmClientUrg OBJECT IDENTIFIER ::= { pm1004vAlmClient 2 }
pm1004vAlmClientCrit OBJECT IDENTIFIER ::= { pm1004vAlmClient 3 }

pm1004vAlmLine OBJECT IDENTIFIER ::= { pm1004valarms 3 }
pm1004vAlmLineNurg OBJECT IDENTIFIER ::= { pm1004vAlmLine 1 }
pm1004vAlmLineUrg OBJECT IDENTIFIER ::= { pm1004vAlmLine 2 }
pm1004vAlmLineCrit OBJECT IDENTIFIER ::= { pm1004vAlmLine 3 }





pm1004vmeasures OBJECT IDENTIFIER ::= { modulePm1004v 3 }
pm1004vMesrOther OBJECT IDENTIFIER ::= { pm1004vmeasures 1 }
pm1004vMesrClient OBJECT IDENTIFIER ::= { pm1004vmeasures 2 }
pm1004vMesrLine OBJECT IDENTIFIER ::= { pm1004vmeasures 3 }




pm1004vcounters OBJECT IDENTIFIER ::= { modulePm1004v 4 }
pm1004vCntOther OBJECT IDENTIFIER ::= { pm1004vcounters 1 }
pm1004vCntClient OBJECT IDENTIFIER ::= { pm1004vcounters 2 }
pm1004vCntLine OBJECT IDENTIFIER ::= { pm1004vcounters 3 }


pm1004vcontrolsWrite OBJECT IDENTIFIER ::= { modulePm1004v 6 }
pm1004vCtrlOther OBJECT IDENTIFIER ::= { pm1004vcontrolsWrite 1 }
pm1004vCtrlClient OBJECT IDENTIFIER ::= { pm1004vcontrolsWrite 2 }
pm1004vCtrlLine OBJECT IDENTIFIER ::= { pm1004vcontrolsWrite 3 }

pm1004vri OBJECT IDENTIFIER ::= { modulePm1004v 7 }
pm1004vriTable OBJECT IDENTIFIER ::= { pm1004vri 1 }

pm1004vdownload OBJECT IDENTIFIER ::= { modulePm1004v 8 }
pm1004vDwlOther OBJECT IDENTIFIER ::= { pm1004vdownload 1 }
pm1004vDwlClient OBJECT IDENTIFIER ::= { pm1004vdownload 2 }
pm1004vDwlLine OBJECT IDENTIFIER ::= { pm1004vdownload 3 }


pm1004vConfig OBJECT IDENTIFIER ::= { modulePm1004v 9 }

pm1004vtraps OBJECT IDENTIFIER ::= { modulePm1004v 10 }



pm1004vMonitoring OBJECT IDENTIFIER ::= { modulePm1004v 11}

pm1004vMonOther OBJECT IDENTIFIER ::= { pm1004vMonitoring 1 }
pm1004vMonRmon OBJECT IDENTIFIER ::= { pm1004vMonOther 3 }

pm1004vMonClient OBJECT IDENTIFIER ::= { pm1004vMonitoring 2 }
pm1004vMonClientRmonCounter OBJECT IDENTIFIER ::= { pm1004vMonClient 4 }
pm1004vMonLine OBJECT IDENTIFIER ::= { pm1004vMonitoring 3 }
pm1004vMonLineRmonCounter OBJECT IDENTIFIER ::= { pm1004vMonLine 4 }


--- *****************************************************
--- $$$$$$$$$$$$$$$$$$$$$$$$$$$$$$$$$$$$$$$$$$$$$$$$$$$$$
---     TEXTUAL-CONVENTION
--- $$$$$$$$$$$$$$$$$$$$$$$$$$$$$$$$$$$$$$$$$$$$$$$$$$$$$
--- *****************************************************

Pm1004vModeTimeSlot ::= TEXTUAL-CONVENTION
    STATUS      current
    DESCRIPTION "different mode for time slot"
    SYNTAX INTEGER {
		singleSplitSelect(256)
           }


Pm1004vModeAddDrop ::= TEXTUAL-CONVENTION
    STATUS      current
    DESCRIPTION "different mode for client"
    SYNTAX INTEGER {
		singleSplitSelect(256)
           }


Pm1004vProtectionTimeSlot ::= TEXTUAL-CONVENTION
    STATUS      current
    DESCRIPTION "protection for control"
    SYNTAX INTEGER {
		auto(0),
		manualX2Line2(257),
		manualX1Line1(513)
           }

Pm1004vProtectionStartUp ::= TEXTUAL-CONVENTION
    STATUS      current
    DESCRIPTION "protection for startup"
    SYNTAX INTEGER {
		auto(2),
		manualX2Line2(0),
		manualX1Line1(1)
           }


Pm1004vDccMode ::= TEXTUAL-CONVENTION
    STATUS      current
    DESCRIPTION "Mode for DCC"
    SYNTAX INTEGER {
		dccNo(0),
		dcctermLine1(1),
		dcctermLine2(2),
		dcctermLines12(3),
		dccmaster(4),
		dccslaveLine12(7)
           }

Pm1004vClientOosMode ::= TEXTUAL-CONVENTION
    STATUS      current
    DESCRIPTION "Mode for OOS on client ports"
    SYNTAX INTEGER {
		clientportis(0),
		clienttxoos(1),
		clientrxoos(2),
		clientportoos(3)
           }


Pm1004vOtxMode ::= TEXTUAL-CONVENTION
    STATUS      current
    DESCRIPTION "Different modes on OTX-TLH on client and line ports"
    SYNTAX INTEGER {
		otx80mode(1),
		otx60mode(2),
		otxadjustmode(4)
           }

Pm1004vOtxGrid ::= TEXTUAL-CONVENTION
    STATUS      current
    DESCRIPTION "Different grids on OTX-TLH on client and line ports"
    SYNTAX INTEGER {
		otxgrid200(200),
		otxgrid100(100),
		otxgrid50(50)
           }

Pm1004vAdjustValue ::= TEXTUAL-CONVENTION
    STATUS      current
    DESCRIPTION "Different values in Adjust mode on OTX-TLH on client and line ports"
    SYNTAX INTEGER {
		otxadjustvalue0(0),
		otxadjustvalue1(1),
		otxadjustvalue2(2),
		otxadjustvalue3(3),
		otxadjustvalue4(4),
		otxadjustvalue5(5),
		otxadjustvalue6(6),
		otxadjustvalue7(7),
		otxadjustvalue8(8),
		otxadjustvalue9(9),
		otxadjustvalue10(10)
           }

Pm1004vOtxChannel ::= TEXTUAL-CONVENTION
    STATUS      current
    DESCRIPTION "Channel selection on OTX-TLH on client and line ports"
    SYNTAX INTEGER


--- *****************************************************
--- $$$$$$$$$$$$$$$$$$$$$$$$$$$$$$$$$$$$$$$$$$$$$$$$$$$$$
---     REMOTE INVENTORY
--- $$$$$$$$$$$$$$$$$$$$$$$$$$$$$$$$$$$$$$$$$$$$$$$$$$$$$
--- *****************************************************

pm1004vRinvReloadInventory OBJECT-TYPE
  SYNTAX EkiOnOff
  MAX-ACCESS read-write
  STATUS current
  DESCRIPTION
        "Reload the inventory: This OID triggers an
         inventory reload."
  ::= { pm1004vri 2 }

pm1004vRinvHwPlatform OBJECT-TYPE
  SYNTAX DisplayString
  MAX-ACCESS read-only
  STATUS current
  DESCRIPTION
        "HW platform description: This OID contains the
         description of the Hardware platform."
  ::= { pm1004vri 3 }

pm1004vRinvModulePlatform OBJECT-TYPE
  SYNTAX DisplayString
  MAX-ACCESS read-only
  STATUS current
  DESCRIPTION
        "Module platform description: This OID contains the
         description of the Module."
  ::= { pm1004vri 4 }

pm1004vRinvSwPlatform OBJECT-TYPE
  SYNTAX DisplayString
  MAX-ACCESS read-only
  STATUS current
  DESCRIPTION
        "SW platform description: This OID contains the
         description of the Software platform."
  ::= { pm1004vri 5 }

pm1004vRinvGwPlatform OBJECT-TYPE
  SYNTAX DisplayString
  MAX-ACCESS read-only
  STATUS current
  DESCRIPTION
        "GW platform desciption: This OID contains the
         description of the Gateware platform."
  ::= { pm1004vri 6 }


pm1004vRinvSfpTable OBJECT-TYPE
      SYNTAX  SEQUENCE OF Pm1004vRinvSfpEntry
      MAX-ACCESS  not-accessible
      STATUS  current
      DESCRIPTION
              "List of the SFPs on the selected module"
      ::= { pm1004vriTable 1 }

pm1004vRinvSfpEntry OBJECT-TYPE
        SYNTAX  Pm1004vRinvSfpEntry
        MAX-ACCESS  not-accessible
        STATUS  current
        DESCRIPTION
              "Row definition for the SFP table"
        INDEX   { pm1004vRinvSfpIndex }
        ::= { pm1004vRinvSfpTable 1 }



Pm1004vRinvSfpEntry::=
        SEQUENCE {
          pm1004vRinvSfpIndex
              Integer32,
          pm1004vRinvsfp
              DisplayString
        }


    pm1004vRinvSfpIndex OBJECT-TYPE
        SYNTAX  Integer32(1..16)
        MAX-ACCESS  read-only
        STATUS  current
        DESCRIPTION
              "Index for SFP table"
        ::= { pm1004vRinvSfpEntry 1 }


    pm1004vRinvsfp OBJECT-TYPE
        SYNTAX  DisplayString
        MAX-ACCESS  read-only
        STATUS  current
        DESCRIPTION
              "Inventory for the SFP: This OID contains the inventory for the SFP"
        ::= { pm1004vRinvSfpEntry 2 }




pm1004vRinvLineTable OBJECT-TYPE
      SYNTAX  SEQUENCE OF Pm1004vRinvLineEntry
      MAX-ACCESS  not-accessible
      STATUS  current
      DESCRIPTION
              "List of the XFPs on the selected module"
      ::= { pm1004vriTable 2 }

pm1004vRinvLineEntry OBJECT-TYPE
        SYNTAX  Pm1004vRinvLineEntry
        MAX-ACCESS  not-accessible
        STATUS  current
        DESCRIPTION
              "Row definition for the XFP table"
        INDEX   { pm1004vRinvLineIndex }
        ::= { pm1004vRinvLineTable 1 }



Pm1004vRinvLineEntry::=
        SEQUENCE {
          pm1004vRinvLineIndex
              Integer32,
          pm1004vRinvxfpLine
              DisplayString
        }


    pm1004vRinvLineIndex OBJECT-TYPE
        SYNTAX  Integer32(1..16)
        MAX-ACCESS  read-only
        STATUS  current
        DESCRIPTION
              "Index for XFP table"
        ::= { pm1004vRinvLineEntry 1 }


    pm1004vRinvxfpLine OBJECT-TYPE
        SYNTAX  DisplayString
        MAX-ACCESS  read-only
        STATUS  current
        DESCRIPTION
              "Inventory for the XFP: This OID contains the inventory for the XFP"
        ::= { pm1004vRinvLineEntry 2 }









--- *****************************************************
--- $$$$$$$$$$$$$$$$$$$$$$$$$$$$$$$$$$$$$$$$$$$$$$$$$$$$$
---     ALARMS
--- $$$$$$$$$$$$$$$$$$$$$$$$$$$$$$$$$$$$$$$$$$$$$$$$$$$$$
--- *****************************************************



--- *****************************************************
---     LEAF for the synthAlm0 article
--- *****************************************************
pm1004vAlmsynthAlm0 OBJECT IDENTIFIER ::= { pm1004vAlmOtherCrit 0 }




pm1004vAlmDefFuseB OBJECT-TYPE
	  SYNTAX EkiOnOff
	  MAX-ACCESS read-only
	  STATUS current
	  DESCRIPTION
        "
        Fuse B Fail :This OID indicates
        that the fuse of the power input
        B is in fail condition  <Help>
          Status of the Fuse B <Condtype>
        DEF_FUSE_B <Probcause> powerProblem
        (36) <Alarmtype> equipmentAlarm
        (5) <Polarity> (2)
        "
	  ::= { pm1004vAlmsynthAlm0 16 }



pm1004vAlmDefFuseA OBJECT-TYPE
	  SYNTAX EkiOnOff
	  MAX-ACCESS read-only
	  STATUS current
	  DESCRIPTION
        "
        Fuse A Fail :This OID indicates
        that the fuse of the power input
        A is in fail condition  <Help>
          Status of the Fuse A <Condtype>
        DEF_FUSE_A <Probcause> powerProblem
        (36) <Alarmtype> equipmentAlarm
        (5) <Polarity> (2)
        "
	  ::= { pm1004vAlmsynthAlm0 15 }



pm1004vAlmModGlobFail OBJECT-TYPE
	  SYNTAX EkiOnOff
	  MAX-ACCESS read-only
	  STATUS current
	  DESCRIPTION
        "
        Module Failure :This OID is set
        on detection of a failure originating
        from the PM <Condtype> MOD_GLOB_FAIL
        <Probcause> equipmentMalfunction
        (16) <Alarmtype> synthesisAlarm
        (12)  <Polarity> (2)
        "
	  ::= { pm1004vAlmsynthAlm0 9 }



--- *****************************************************
---     LEAF for the synthAlm2 article
--- *****************************************************
pm1004vAlmsynthAlm2 OBJECT IDENTIFIER ::= { pm1004vAlmOtherNurg 2 }




pm1004vAlmMaintenanceOn OBJECT-TYPE
	  SYNTAX EkiOnOff
	  MAX-ACCESS read-only
	  STATUS current
	  DESCRIPTION
        "
        Maintenance Mode :This OID indicates
        that the PM is in maintenance mode.
         <Help>  This alarm indicates that
        the maintenance mode is enabled
        on the PM <Condtype> MAINTENANCE_ON
        <Probcause> other (1) <Alarmtype>
        other (1) <Polarity> (2)
        "
	  ::= { pm1004vAlmsynthAlm2 5 }



pm1004vAlmCorrelatOff OBJECT-TYPE
	  SYNTAX EkiOnOff
	  MAX-ACCESS read-only
	  STATUS current
	  DESCRIPTION
        "
        Not Used :This OID, when set,
         indicates that alarm correlation
        is not being performed. <Condtype>
        CORRELAT_OFF <Probcause> other
         (1) <Alarmtype> other (1) <Polarity>
        (2)
        "
	  ::= { pm1004vAlmsynthAlm2 4 }



pm1004vAlmConfTableLoad OBJECT-TYPE
	  SYNTAX EkiOnOff
	  MAX-ACCESS read-only
	  STATUS current
	  DESCRIPTION
        "
        PM Configuration Load :This OID
         is at 1 during the loading of
         configuration tables in the modules
        RAM. <Condtype> CONF_TABLE_LOAD
        <Probcause> other (1) <Alarmtype>
        other (1) <Polarity> (2)
        "
	  ::= { pm1004vAlmsynthAlm2 3 }



pm1004vAlmInvUpload OBJECT-TYPE
	  SYNTAX EkiOnOff
	  MAX-ACCESS read-only
	  STATUS current
	  DESCRIPTION
        "
        Inventory Upload :This OID is
         at 1 during the uploading of PM
        inventory information. <Condtype>
        INV_UPLOAD <Probcause> other (1)
        <Alarmtype> other (1) <Polarity>
        (2)
        "
	  ::= { pm1004vAlmsynthAlm2 2 }



pm1004vAlmConfTableSave OBJECT-TYPE
	  SYNTAX EkiOnOff
	  MAX-ACCESS read-only
	  STATUS current
	  DESCRIPTION
        "
        PM Configuration Save :This OID
        is at 1 during the saving of a
         new configuration table in the
        module Flash memory. <Condtype>
        CONF_TABLE_SAVE <Probcause> other
        (1) <Alarmtype> other (1) <Polarity>
        (2)
        "
	  ::= { pm1004vAlmsynthAlm2 1 }



--- *********************************************************
---     TABLE for the pm1004vAlmsynthAlmLine articles
--- *********************************************************

pm1004vAlmsynthAlmLineTable OBJECT-TYPE
	SYNTAX  SEQUENCE OF Pm1004vAlmsynthAlmLineEntry
	MAX-ACCESS not-accessible
	STATUS current
	DESCRIPTION
        "
        List of pm1004vAlmsynthAlmLine
        Article
        "
	::= { pm1004vAlmLineCrit 7 }


pm1004vAlmsynthAlmLineEntry OBJECT-TYPE
	SYNTAX Pm1004vAlmsynthAlmLineEntry
	MAX-ACCESS not-accessible
	STATUS current
	DESCRIPTION
        "
        Row definition for the pm1004vAlmsynthAlmLine
        table
        "
	INDEX   { pm1004vAlmsynthAlmLineIndex }
	::= { pm1004vAlmsynthAlmLineTable 1 }


Pm1004vAlmsynthAlmLineEntry ::=
	SEQUENCE {
	pm1004vAlmsynthAlmLineIndex
		INTEGER,
	pm1004vAlmLineActivePortn
		EkiOnOff,
	pm1004vAlmLineFailPortn
		EkiOnOff,
	pm1004vAlmLineDdmCritPortn
		EkiOnOff,
	pm1004vAlmLineDdmAlmPortn
		EkiOnOff,
	pm1004vAlmLineDdmWarningPortn
		EkiOnOff,
	pm1004vAlmLineLocalOosPortn
		EkiOnOff,
	pm1004vAlmXfpTxOffPortn
		EkiOnOff,
	pm1004vAlmLineHwFailPortn
		EkiOnOff,
	pm1004vAlmXfpInitNotComplPortn
		EkiOnOff,
	pm1004vAlmXfpAbsentPortn
		EkiOnOff
	}


pm1004vAlmsynthAlmLineIndex OBJECT-TYPE
	SYNTAX  INTEGER(0..128)
	MAX-ACCESS  read-only
	STATUS current
	DESCRIPTION
        "
        Index definition for the pm1004vAlmsynthAlmLine
        table
        "
	::= { pm1004vAlmsynthAlmLineEntry 1 }


pm1004vAlmLineActivePortn OBJECT-TYPE
	SYNTAX  EkiOnOff
	MAX-ACCESS read-only
	STATUS current
	DESCRIPTION
        "
        Line Active :This bit indicates
        the line #n is active on receive
        side  <Help>  This status indicates
        whether the line is active or standby.
        <Condtype> LINE_ACTIVE <Probcause>
        informationalStatus(1000) <Alarmtype>
        other (1) <Polarity> (2)
        "
	::= { pm1004vAlmsynthAlmLineEntry 17 }


pm1004vAlmLineFailPortn OBJECT-TYPE
	SYNTAX  EkiOnOff
	MAX-ACCESS read-only
	STATUS current
	DESCRIPTION
        "
        Line Port Failure :This OID indicates
        a failure on the line port <Condtype>
        LINE_FAIL <Probcause> equipmentMalfunction
        (16) <Alarmtype> synthesisAlarm
        (12)  <Polarity> (2)
        "
	::= { pm1004vAlmsynthAlmLineEntry 13 }


pm1004vAlmLineDdmCritPortn OBJECT-TYPE
	SYNTAX  EkiOnOff
	MAX-ACCESS read-only
	STATUS current
	DESCRIPTION
        "
        Custom Alarm On Line XFP/OTX DDM
        :This OID indicates a Custom alarm
        is present coming out of Line optical
        interface DDM    <Help>   This
         alarm indicates if a DDM Custom
        Alarm has been detected on the
         line transceiver <Condtype> LINE_DDM_CRIT
        <Probcause> equipmentMalfunction
        (16) <Alarmtype> synthesisAlarm
        (12)  <Polarity> (2)
        "
	::= { pm1004vAlmsynthAlmLineEntry 12 }


pm1004vAlmLineDdmAlmPortn OBJECT-TYPE
	SYNTAX  EkiOnOff
	MAX-ACCESS read-only
	STATUS current
	DESCRIPTION
        "
        Alarm On Line Optical Module DDM
        :This OID indicates an alarm is
        present coming out of Line optical
        interface DDM  <Help>  This alarm
        indicates if a DDM Alarm has been
        detected on the line transceiver
        <Condtype> LINE_DDM_ALM <Probcause>
        equipmentMalfunction (16) <Alarmtype>
        synthesisAlarm (12)  <Polarity>
        (2)
        "
	::= { pm1004vAlmsynthAlmLineEntry 11 }


pm1004vAlmLineDdmWarningPortn OBJECT-TYPE
	SYNTAX  EkiOnOff
	MAX-ACCESS read-only
	STATUS current
	DESCRIPTION
        "
        Warning On Line Optical Module
        DDM :This OID indicates a warning
        is present coming out of Line optical
        interface DDM  <Help>  This alarm
        indicates if a DDM Warning has
         been detected on the line transceiver
        <Condtype> LINE_DDM_WARNING <Probcause>
        equipmentMalfunction (16) <Alarmtype>
        synthesisAlarm (12)  <Polarity>
        (2)
        "
	::= { pm1004vAlmsynthAlmLineEntry 10 }


pm1004vAlmLineLocalOosPortn OBJECT-TYPE
	SYNTAX  EkiOnOff
	MAX-ACCESS read-only
	STATUS current
	DESCRIPTION
        "
        Line Port In Service :This OID
        indicates that the Line port is
        In Service (1) of Out or Service
        (2)  <Help>  This status indicates
        if the line port is in service
         <Condtype> LINE_LOCAL_OOS <Probcause>
        informationalStatus(1000) <Alarmtype>
        other (1) <Polarity> (2)
        "
	::= { pm1004vAlmsynthAlmLineEntry 7 }


pm1004vAlmXfpTxOffPortn OBJECT-TYPE
	SYNTAX  EkiOnOff
	MAX-ACCESS read-only
	STATUS current
	DESCRIPTION
        "
        Line Optical Module Laser Shutdown
        :This OID indicates the line optical
        output power is on  <Help>  This
        status indicates if the line transceiver
        laser is ON or OFF <Condtype> XFP_TX_OFF
        <Probcause> other (1) <Alarmtype>
        equipmentAlarm (5) <Polarity> (2)
        "
	::= { pm1004vAlmsynthAlmLineEntry 6 }


pm1004vAlmLineHwFailPortn OBJECT-TYPE
	SYNTAX  EkiOnOff
	MAX-ACCESS read-only
	STATUS current
	DESCRIPTION
        "
        Line Port HW Failure :This OID
        indicates a failure on line port,
        most probably caused by a HW issue
        <Condtype> LINE_HW_FAIL <Probcause>
        equipmentMalfunction (16) <Alarmtype>
        synthesisAlarm (12)  <Polarity>
        (2)
        "
	::= { pm1004vAlmsynthAlmLineEntry 5 }


pm1004vAlmXfpInitNotComplPortn OBJECT-TYPE
	SYNTAX  EkiOnOff
	MAX-ACCESS read-only
	STATUS current
	DESCRIPTION
        "
        Line Optical Module Ready :This
        OID indicates that the optical
         interface (XFP or OTX) is not
         operational.  <Help>  This status
        indicates if the line transceiver
        has been correctly initialized
         <Condtype> XFP_INIT_NOT_COMPL
         <Probcause> equipmentMalfunction
        (16) <Alarmtype> equipmentAlarm
        (5) <Polarity> (2) <Event> ObjectCDINV
        "
	::= { pm1004vAlmsynthAlmLineEntry 3 }


pm1004vAlmXfpAbsentPortn OBJECT-TYPE
	SYNTAX  EkiOnOff
	MAX-ACCESS read-only
	STATUS current
	DESCRIPTION
        "
        Line Optical Module Absent :This
        OID indicates that the line optical
        interface (XFP or OTX) is not plugged
        in.  <Help>  This alarm indicates
        if the line transceiver is present.
        <Condtype> XFP_ABSENT <Probcause>
        inputOutputDeviceError (24) <Alarmtype>
        equipmentAlarm (5) <Polarity> (2)
        <Event> ObjectCDINV
        "
	::= { pm1004vAlmsynthAlmLineEntry 2 }


--- *********************************************************
---     TABLE for the pm1004vAlmsynthAlmPort articles
--- *********************************************************

pm1004vAlmsynthAlmPortTable OBJECT-TYPE
	SYNTAX  SEQUENCE OF Pm1004vAlmsynthAlmPortEntry
	MAX-ACCESS not-accessible
	STATUS current
	DESCRIPTION
        "
        List of pm1004vAlmsynthAlmPort
        Article
        "
	::= { pm1004vAlmClientCrit 8 }


pm1004vAlmsynthAlmPortEntry OBJECT-TYPE
	SYNTAX Pm1004vAlmsynthAlmPortEntry
	MAX-ACCESS not-accessible
	STATUS current
	DESCRIPTION
        "
        Row definition for the pm1004vAlmsynthAlmPort
        table
        "
	INDEX   { pm1004vAlmsynthAlmPortIndex }
	::= { pm1004vAlmsynthAlmPortTable 1 }


Pm1004vAlmsynthAlmPortEntry ::=
	SEQUENCE {
	pm1004vAlmsynthAlmPortIndex
		INTEGER,
	pm1004vAlmUpCsfPortn
		EkiOnOff,
	pm1004vAlmClientActivePortn
		EkiOnOff,
	pm1004vAlmFailAccPortn
		EkiOnOff,
	pm1004vAlmSfpDdmCritPortn
		EkiOnOff,
	pm1004vAlmSfpDdmAlmPortn
		EkiOnOff,
	pm1004vAlmSfpDdmWarningPortn
		EkiOnOff,
	pm1004vAlmDwCaisPortn
		EkiOnOff,
	pm1004vAlmClientLocalOosRxPortn
		EkiOnOff,
	pm1004vAlmClientLocalOosTxPortn
		EkiOnOff,
	pm1004vAlmDwLsdPortn
		EkiOnOff,
	pm1004vAlmHwFailAccPortn
		EkiOnOff,
	pm1004vAlmDdmAbsentPortn
		EkiOnOff,
	pm1004vAlmSfpAbsentPortn
		EkiOnOff
	}


pm1004vAlmsynthAlmPortIndex OBJECT-TYPE
	SYNTAX  INTEGER(0..128)
	MAX-ACCESS  read-only
	STATUS current
	DESCRIPTION
        "
        Index definition for the pm1004vAlmsynthAlmPort
        table
        "
	::= { pm1004vAlmsynthAlmPortEntry 1 }


pm1004vAlmUpCsfPortn OBJECT-TYPE
	SYNTAX  EkiOnOff
	MAX-ACCESS read-only
	STATUS current
	DESCRIPTION
        "
        Client Signal Fail Inserted :This
        OID indicates a CSF has been inserted
        in the upstream client port.  <Help>
         This status indicates if a Client
        Signal Fail is currently inserted
        on the line signal for this client
        port <Condtype> UP_CSF_1 <Probcause>
        other (1) <Alarmtype> other (1)
        <Polarity> (2)
        "
	::= { pm1004vAlmsynthAlmPortEntry 17 }


pm1004vAlmClientActivePortn OBJECT-TYPE
	SYNTAX  EkiOnOff
	MAX-ACCESS read-only
	STATUS current
	DESCRIPTION
        "
        Client Sink (Line1 Or Line2) :This
        bit indicates the Client #n is
         active on receive side  <Help>
         This status indicates whether
         the Client is extracted from Line
        1 or Line 2. <Condtype> CLIENT_ACTIVE
        <Probcause> other (1) <Alarmtype>
        other (1) <Polarity> (2)
        "
	::= { pm1004vAlmsynthAlmPortEntry 16 }


pm1004vAlmFailAccPortn OBJECT-TYPE
	SYNTAX  EkiOnOff
	MAX-ACCESS read-only
	STATUS current
	DESCRIPTION
        "
        Client Access Fail :This OID indicates
        a failure on the Client port <Condtype>
        FAIL_ACC_1 <Probcause> equipmentMalfunction
        (16) <Alarmtype> synthesisAlarm
        (12)  <Polarity> (2)
        "
	::= { pm1004vAlmsynthAlmPortEntry 13 }


pm1004vAlmSfpDdmCritPortn OBJECT-TYPE
	SYNTAX  EkiOnOff
	MAX-ACCESS read-only
	STATUS current
	DESCRIPTION
        "
        Custom Alarm On Client SFP DDM
        :This OID indicates a Custom alarm
        is being received from the Client
        SFP DDM  <Help>   This alarm indicates
        if a DDM Custom Alarm has been
         detected on the client transceiver


        <Condtype> SFP_DDM_CRIT_1 <Probcause>
        equipmentMalfunction (16) <Alarmtype>
        synthesisAlarm (12)  <Polarity>
        (2)
        "
	::= { pm1004vAlmsynthAlmPortEntry 12 }


pm1004vAlmSfpDdmAlmPortn OBJECT-TYPE
	SYNTAX  EkiOnOff
	MAX-ACCESS read-only
	STATUS current
	DESCRIPTION
        "
        Alarm On Client SFP DDM :This
         OID indicates an alarm is being
        received from the Client SFP DDM
        (only significant on Client6-GbE
        port)   <Help>   This alarm indicates
        if a DDM Alarm has been detected
        on the client transceiver (only
        significant on Client6-GbE port)
        <Condtype> SFP_DDM_ALM_1 <Probcause>
        equipmentMalfunction (16) <Alarmtype>
        synthesisAlarm (12)  <Polarity>
        (2)
        "
	::= { pm1004vAlmsynthAlmPortEntry 11 }


pm1004vAlmSfpDdmWarningPortn OBJECT-TYPE
	SYNTAX  EkiOnOff
	MAX-ACCESS read-only
	STATUS current
	DESCRIPTION
        "
        Warning On Client SFP DDM :This
        OID indicates a warning is being
        received from the Client SFP DDM
        (only significant on Client6-GbE
        port)   <Help>   This alarm indicates
        if a DDM Warning has been detected
        on the client transceiver (only
        significant on Client6-GbE port)
        <Condtype> SFP_DDM_WARNING_1 <Probcause>
        equipmentMalfunction (16) <Alarmtype>
        synthesisAlarm (12)  <Polarity>
        (2)
        "
	::= { pm1004vAlmsynthAlmPortEntry 10 }


pm1004vAlmDwCaisPortn OBJECT-TYPE
	SYNTAX  EkiOnOff
	MAX-ACCESS read-only
	STATUS current
	DESCRIPTION
        "
        Client AIS Inserted :This OID
         indicates a CAIS has been inserted
        on the output client port.  <Help>
          This status indictaes if a Client
        Alarm Indication Signal is currently
        inserted on the client interface
        <Condtype> DW_CAIS_1 <Probcause>
        informationalStatus(1000) <Alarmtype>
        other (1) <Polarity> (2)
        "
	::= { pm1004vAlmsynthAlmPortEntry 9 }


pm1004vAlmClientLocalOosRxPortn OBJECT-TYPE
	SYNTAX  EkiOnOff
	MAX-ACCESS read-only
	STATUS current
	DESCRIPTION
        "
        Rx Client Port In Service :This
        OID indicates that the local Rx
        Client port is In Service (1) or
        Out of Service (2)  <Help>   This
        status indicates if the local Rx
        client port is in service <Condtype>
        CLIENT_LOCAL_OOS_RX <Probcause>
        informationalStatus(1000) <Alarmtype>
        other (1) <Polarity> (2)
        "
	::= { pm1004vAlmsynthAlmPortEntry 8 }


pm1004vAlmClientLocalOosTxPortn OBJECT-TYPE
	SYNTAX  EkiOnOff
	MAX-ACCESS read-only
	STATUS current
	DESCRIPTION
        "
        Tx Client Port In Service :This
        OID indicates that the local Tx
        Client port is In Service (1) or
        Out of Service (2)  <Help>   This
        status indicates if the local Tx
        client port is in service
 <Condtype>
        CLIENT_LOCAL_OOS_TX <Probcause>
        informationalStatus(1000) <Alarmtype>
        other (1) <Polarity> (2)
        "
	::= { pm1004vAlmsynthAlmPortEntry 7 }


pm1004vAlmDwLsdPortn OBJECT-TYPE
	SYNTAX  EkiOnOff
	MAX-ACCESS read-only
	STATUS current
	DESCRIPTION
        "
        Client Signal Shutdown :This OID
        indicates the Client SFP transmitter
        output is ON.   <Help>   This status
        indicates if the client transceiver
         is ON or OFF <Condtype> DW_LSD_1
        <Probcause> other (1) <Alarmtype>
        equipmentAlarm (5) <Polarity> (2)
        "
	::= { pm1004vAlmsynthAlmPortEntry 6 }


pm1004vAlmHwFailAccPortn OBJECT-TYPE
	SYNTAX  EkiOnOff
	MAX-ACCESS read-only
	STATUS current
	DESCRIPTION
        "
        Client HW Fail :This OID indicates
        a failure on client port, most
         probably caused by a HW issue.
        <Condtype> HW_FAIL_ACC_1 <Probcause>
        equipmentMalfunction (16) <Alarmtype>
        synthesisAlarm (12)  <Polarity>
        (2)
        "
	::= { pm1004vAlmsynthAlmPortEntry 5 }


pm1004vAlmDdmAbsentPortn OBJECT-TYPE
	SYNTAX  EkiOnOff
	MAX-ACCESS read-only
	STATUS current
	DESCRIPTION
        "
        DDM Supported On Client SFP :This
        OID indicates that the Client SFP
        module supports the Digital Diagnostic
        Monitoring function (only significant
        on Client6-GbE port)   <Help>
          This status indicates if the
         client transceiver includes the
        DDM feature (only significant on
        Client6-GbE port) <Condtype> DDM_ABSENT_1
        <Probcause> equipmentMalfunction
        (16) <Alarmtype> other (1) <Polarity>
        (2)
        "
	::= { pm1004vAlmsynthAlmPortEntry 3 }


pm1004vAlmSfpAbsentPortn OBJECT-TYPE
	SYNTAX  EkiOnOff
	MAX-ACCESS read-only
	STATUS current
	DESCRIPTION
        "
        Client SFP Absent :This OID indicates
        that the SFP module is not present
        in the client port (only significant
        on Client6-GbE port).   <Help>
           This alarm indicates if the
         client transceiver is present
         (only significant on Client6-GbE
        port) <Condtype> SFP_ABSENT_1 <Probcause>
        inputOutputDeviceError (24) <Alarmtype>
        equipmentAlarm (5) <Polarity> (2)
        <Event> ObjectCDINV
        "
	::= { pm1004vAlmsynthAlmPortEntry 2 }


--- *********************************************************
---     TABLE for the pm1004vAlmaccessioAlm articles
--- *********************************************************

pm1004vAlmaccessioAlmTable OBJECT-TYPE
	SYNTAX  SEQUENCE OF Pm1004vAlmaccessioAlmEntry
	MAX-ACCESS not-accessible
	STATUS current
	DESCRIPTION
        "
        List of pm1004vAlmaccessioAlm
         Article
        "
	::= { pm1004vAlmClientCrit 16 }


pm1004vAlmaccessioAlmEntry OBJECT-TYPE
	SYNTAX Pm1004vAlmaccessioAlmEntry
	MAX-ACCESS not-accessible
	STATUS current
	DESCRIPTION
        "
        Row definition for the pm1004vAlmaccessioAlm
        table
        "
	INDEX   { pm1004vAlmaccessioAlmIndex }
	::= { pm1004vAlmaccessioAlmTable 1 }


Pm1004vAlmaccessioAlmEntry ::=
	SEQUENCE {
	pm1004vAlmaccessioAlmIndex
		INTEGER,
	pm1004vAlmUpLosPortn
		EkiOnOff,
	pm1004vAlmDwLasFailPortn
		EkiOnOff
	}


pm1004vAlmaccessioAlmIndex OBJECT-TYPE
	SYNTAX  INTEGER(0..128)
	MAX-ACCESS  read-only
	STATUS current
	DESCRIPTION
        "
        Index definition for the pm1004vAlmaccessioAlm
        table
        "
	::= { pm1004vAlmaccessioAlmEntry 1 }


pm1004vAlmUpLosPortn OBJECT-TYPE
	SYNTAX  EkiOnOff
	MAX-ACCESS read-only
	STATUS current
	DESCRIPTION
        "
        Client Input Loss Of Signal :This
        OID indicates that no signal is
        present on the client port  <Help>
          This alarm indicates if a signal
        is detected on the client input
        <Condtype> UP_LOS_1 <Probcause>
        receiveFailure (41) <Alarmtype>
        physicalViolation (9) <Polarity>
        (2)
        "
	::= { pm1004vAlmaccessioAlmEntry 5 }


pm1004vAlmDwLasFailPortn OBJECT-TYPE
	SYNTAX  EkiOnOff
	MAX-ACCESS read-only
	STATUS current
	DESCRIPTION
        "
        Client SFP Tx Failed :This OID
        indicates that the transmitter
         fails for the SFP plugged into
        the client port. This alarm reports
        the transmitter failure alarm generated
        by the SFPs.  <Help>   This alarm
        indicates if the laser of the client
        transceiver is in fail condition
        <Condtype> DW_LAS_FAIL_1 <Probcause>
        transmitterFailure (56) <Alarmtype>
        equipmentAlarm (5) <Polarity> (2)
        "
	::= { pm1004vAlmaccessioAlmEntry 2 }


--- *********************************************************
---     TABLE for the pm1004vAlmsfpAlmDdm articles
--- *********************************************************

pm1004vAlmsfpAlmDdmTable OBJECT-TYPE
	SYNTAX  SEQUENCE OF Pm1004vAlmsfpAlmDdmEntry
	MAX-ACCESS not-accessible
	STATUS current
	DESCRIPTION
        "
        List of pm1004vAlmsfpAlmDdm Article
        "
	::= { pm1004vAlmClientUrg 32 }


pm1004vAlmsfpAlmDdmEntry OBJECT-TYPE
	SYNTAX Pm1004vAlmsfpAlmDdmEntry
	MAX-ACCESS not-accessible
	STATUS current
	DESCRIPTION
        "
        Row definition for the pm1004vAlmsfpAlmDdm
        table
        "
	INDEX   { pm1004vAlmsfpAlmDdmIndex }
	::= { pm1004vAlmsfpAlmDdmTable 1 }


Pm1004vAlmsfpAlmDdmEntry ::=
	SEQUENCE {
	pm1004vAlmsfpAlmDdmIndex
		INTEGER,
	pm1004vAlmRxPwrHighAlaPortn
		EkiOnOff,
	pm1004vAlmRxPwrLowAlaPortn
		EkiOnOff,
	pm1004vAlmTempHighAlaPortn
		EkiOnOff,
	pm1004vAlmTempLowAlaPortn
		EkiOnOff,
	pm1004vAlmVccHighAlaPortn
		EkiOnOff,
	pm1004vAlmVccLowAlaPortn
		EkiOnOff,
	pm1004vAlmTxBiasHighAlaPortn
		EkiOnOff,
	pm1004vAlmTxBiasLowAlaPortn
		EkiOnOff,
	pm1004vAlmTxPwrHighAlaPortn
		EkiOnOff,
	pm1004vAlmTxPwrLowAlaPortn
		EkiOnOff
	}


pm1004vAlmsfpAlmDdmIndex OBJECT-TYPE
	SYNTAX  INTEGER(0..128)
	MAX-ACCESS  read-only
	STATUS current
	DESCRIPTION
        "
        Index definition for the pm1004vAlmsfpAlmDdm
        table
        "
	::= { pm1004vAlmsfpAlmDdmEntry 1 }


pm1004vAlmRxPwrHighAlaPortn OBJECT-TYPE
	SYNTAX  EkiOnOff
	MAX-ACCESS read-only
	STATUS current
	DESCRIPTION
        "
        Client SFP Rx Power High :Alarm
        indicating that the SFP input power
        of port is higher than the threshold
        value written in the SFP EEPROM
        <Condtype> RX_PWR_HIGH_ALA_1 <Probcause>
        receiveFailure (41) <Alarmtype>
        equipmentAlarm (5) <Polarity> (2)
        "
	::= { pm1004vAlmsfpAlmDdmEntry 17 }


pm1004vAlmRxPwrLowAlaPortn OBJECT-TYPE
	SYNTAX  EkiOnOff
	MAX-ACCESS read-only
	STATUS current
	DESCRIPTION
        "
        Client SFP Rx Power Low :Alarm
        indicating that the SFP input power
        of port is lower than the threshold
        value written in the SFP EEPROM
        <Condtype> RX_PWR_LOW_ALA_1 <Probcause>
        receiveFailure (41) <Alarmtype>
        equipmentAlarm (5) <Polarity> (2)
        "
	::= { pm1004vAlmsfpAlmDdmEntry 16 }


pm1004vAlmTempHighAlaPortn OBJECT-TYPE
	SYNTAX  EkiOnOff
	MAX-ACCESS read-only
	STATUS current
	DESCRIPTION
        "
        Client SFP Temp High :Alarm indicating
        that the SFP temperature of port
        is higher than the threshold value
        written in the SFP EEPROM <Condtype>
        TEMP_HIGH_ALA_1 <Probcause> temperatureUnacceptable
        (51) <Alarmtype> equipmentAlarm
        (5) <Polarity> (2)
        "
	::= { pm1004vAlmsfpAlmDdmEntry 9 }


pm1004vAlmTempLowAlaPortn OBJECT-TYPE
	SYNTAX  EkiOnOff
	MAX-ACCESS read-only
	STATUS current
	DESCRIPTION
        "
        Client SFP Temp Low :Alarm indicating
        that the SFP temperature of port
        is lower than the threshold value
        written in the SFP EEPROM <Condtype>
        TEMP_LOW_ALA_1 <Probcause> temperatureUnacceptable
        (51) <Alarmtype> equipmentAlarm
        (5) <Polarity> (2)
        "
	::= { pm1004vAlmsfpAlmDdmEntry 8 }


pm1004vAlmVccHighAlaPortn OBJECT-TYPE
	SYNTAX  EkiOnOff
	MAX-ACCESS read-only
	STATUS current
	DESCRIPTION
        "
        Client SFP Power Supply High :Alarm
        indicating that the SFP power supply
        of port is higher than the threshold
        value written in the SFP EEPROM
         <Condtype> VCC_HIGH_ALA_1 <Probcause>
        powerProblem (36) <Alarmtype> equipmentAlarm
        (5) <Polarity> (2)
        "
	::= { pm1004vAlmsfpAlmDdmEntry 7 }


pm1004vAlmVccLowAlaPortn OBJECT-TYPE
	SYNTAX  EkiOnOff
	MAX-ACCESS read-only
	STATUS current
	DESCRIPTION
        "
        Client SFP Power Supply Low :Alarm
        indicating that the SFP power supply
        of port is lower than the threshold
        value written in the SFP EEPROM
         <Condtype> VCC_LOW_ALA_1 <Probcause>
        powerProblem (36) <Alarmtype> equipmentAlarm
        (5) <Polarity> (2)
        "
	::= { pm1004vAlmsfpAlmDdmEntry 6 }


pm1004vAlmTxBiasHighAlaPortn OBJECT-TYPE
	SYNTAX  EkiOnOff
	MAX-ACCESS read-only
	STATUS current
	DESCRIPTION
        "
        Client SFP Bias High :Alarm indicating
        that the SFP laser bias current
        of port is higher than the threshold
        value written in the SFP EEPROM
        <Condtype> TX_BIAS_HIGH_ALA_1 <Probcause>
        transmitterFailure (56) <Alarmtype>
        equipmentAlarm (5) <Polarity> (2)
        "
	::= { pm1004vAlmsfpAlmDdmEntry 5 }


pm1004vAlmTxBiasLowAlaPortn OBJECT-TYPE
	SYNTAX  EkiOnOff
	MAX-ACCESS read-only
	STATUS current
	DESCRIPTION
        "
        Client SFP Bias Low :Alarm indicating
        that the SFP laser bias current
        of port is lower than the threshold
        value written in the SFP EEPROM
        <Condtype> TX_BIAS_LOW_ALA_1 <Probcause>
        transmitterFailure (56) <Alarmtype>
        equipmentAlarm (5) <Polarity> (2)
        "
	::= { pm1004vAlmsfpAlmDdmEntry 4 }


pm1004vAlmTxPwrHighAlaPortn OBJECT-TYPE
	SYNTAX  EkiOnOff
	MAX-ACCESS read-only
	STATUS current
	DESCRIPTION
        "
        Client SFP Tx Power High :Alarm
        indicating that the SFP output
         power of port is higher than the
        threshold value written in the
         SFP EEPROM <Condtype> TX_PWR_HIGH_ALA_1
        <Probcause> transmitterFailure
         (56) <Alarmtype> equipmentAlarm
        (5) <Polarity> (2)
        "
	::= { pm1004vAlmsfpAlmDdmEntry 3 }


pm1004vAlmTxPwrLowAlaPortn OBJECT-TYPE
	SYNTAX  EkiOnOff
	MAX-ACCESS read-only
	STATUS current
	DESCRIPTION
        "
        Client SFP Tx Power Low :Alarm
        indicating that the SFP output
         power of port is lower than the
        threshold value written in the
         SFP EEPROM <Condtype> TX_PWR_LOW_ALA_1
        <Probcause> transmitterFailure
         (56) <Alarmtype> equipmentAlarm
        (5) <Polarity> (2)
        "
	::= { pm1004vAlmsfpAlmDdmEntry 2 }


--- *********************************************************
---     TABLE for the pm1004vAlmsfpWarnDdm articles
--- *********************************************************

pm1004vAlmsfpWarnDdmTable OBJECT-TYPE
	SYNTAX  SEQUENCE OF Pm1004vAlmsfpWarnDdmEntry
	MAX-ACCESS not-accessible
	STATUS current
	DESCRIPTION
        "
        List of pm1004vAlmsfpWarnDdm Article
        "
	::= { pm1004vAlmClientNurg 48 }


pm1004vAlmsfpWarnDdmEntry OBJECT-TYPE
	SYNTAX Pm1004vAlmsfpWarnDdmEntry
	MAX-ACCESS not-accessible
	STATUS current
	DESCRIPTION
        "
        Row definition for the pm1004vAlmsfpWarnDdm
        table
        "
	INDEX   { pm1004vAlmsfpWarnDdmIndex }
	::= { pm1004vAlmsfpWarnDdmTable 1 }


Pm1004vAlmsfpWarnDdmEntry ::=
	SEQUENCE {
	pm1004vAlmsfpWarnDdmIndex
		INTEGER,
	pm1004vAlmRxPwrHighWngPortn
		EkiOnOff,
	pm1004vAlmRxPwrLowWngPortn
		EkiOnOff,
	pm1004vAlmTempHighWngPortn
		EkiOnOff,
	pm1004vAlmTempLowWngPortn
		EkiOnOff,
	pm1004vAlmVccHighWngPortn
		EkiOnOff,
	pm1004vAlmVccLowWngPortn
		EkiOnOff,
	pm1004vAlmTxBiasHighWngPortn
		EkiOnOff,
	pm1004vAlmTxBiasLowWngPortn
		EkiOnOff,
	pm1004vAlmTxPwrHighWngPortn
		EkiOnOff,
	pm1004vAlmTxPwLowWngPortn
		EkiOnOff
	}


pm1004vAlmsfpWarnDdmIndex OBJECT-TYPE
	SYNTAX  INTEGER(0..128)
	MAX-ACCESS  read-only
	STATUS current
	DESCRIPTION
        "
        Index definition for the pm1004vAlmsfpWarnDdm
        table
        "
	::= { pm1004vAlmsfpWarnDdmEntry 1 }


pm1004vAlmRxPwrHighWngPortn OBJECT-TYPE
	SYNTAX  EkiOnOff
	MAX-ACCESS read-only
	STATUS current
	DESCRIPTION
        "
        Client SFP Rx Power High Warning
        :Warning indicating that the SFP
        input power of port is higher than
        the threshold value written in
         the SFP EEPROM <Condtype> RX_PWR_HIGH_WNG_1
        <Probcause> receiveFailure (41)
        <Alarmtype> equipmentAlarm (5)
         <Polarity> (2)
        "
	::= { pm1004vAlmsfpWarnDdmEntry 17 }


pm1004vAlmRxPwrLowWngPortn OBJECT-TYPE
	SYNTAX  EkiOnOff
	MAX-ACCESS read-only
	STATUS current
	DESCRIPTION
        "
        Client SFP Rx Power Low Warning
        :Warning indicating that the SFP
        input power of port is lower than
        the threshold value written in
         the SFP EEPROM <Condtype> RX_PWR_LOW_WNG_1
        <Probcause> receiveFailure (41)
        <Alarmtype> equipmentAlarm (5)
         <Polarity> (2)
        "
	::= { pm1004vAlmsfpWarnDdmEntry 16 }


pm1004vAlmTempHighWngPortn OBJECT-TYPE
	SYNTAX  EkiOnOff
	MAX-ACCESS read-only
	STATUS current
	DESCRIPTION
        "
        Client SFP Temp High Warning :Warning
        indicating that the SFP temperature
        of port is higher than the threshold
        value written in the SFP EEPROM
        <Condtype> TEMP_HIGH_WNG_1 <Probcause>
        temperatureUnacceptable (51) <Alarmtype>
        equipmentAlarm (5) <Polarity> (2)
        "
	::= { pm1004vAlmsfpWarnDdmEntry 9 }


pm1004vAlmTempLowWngPortn OBJECT-TYPE
	SYNTAX  EkiOnOff
	MAX-ACCESS read-only
	STATUS current
	DESCRIPTION
        "
        Client SFP Temp Low Warning :Warning
        indicating that the SFP temperature
        of port is lower than the threshold
        value written in the SFP EEPROM
        <Condtype> TEMP_LOW_WNG_1 <Probcause>
        temperatureUnacceptable (51) <Alarmtype>
        equipmentAlarm (5) <Polarity> (2)
        "
	::= { pm1004vAlmsfpWarnDdmEntry 8 }


pm1004vAlmVccHighWngPortn OBJECT-TYPE
	SYNTAX  EkiOnOff
	MAX-ACCESS read-only
	STATUS current
	DESCRIPTION
        "
        Client SFP Power Supply High Warning
        :Warning indicating that the SFP
        power supply of port is higher
         than the threshold value written
        in the SFP EEPROM  <Condtype> VCC_HIGH_WNG_1
        <Probcause> powerProblem (36) <Alarmtype>
        equipmentAlarm (5) <Polarity> (2)
        "
	::= { pm1004vAlmsfpWarnDdmEntry 7 }


pm1004vAlmVccLowWngPortn OBJECT-TYPE
	SYNTAX  EkiOnOff
	MAX-ACCESS read-only
	STATUS current
	DESCRIPTION
        "
        Client SFP Power Supply Low Warning
        :Warning indicating that the SFP
        power supply of port is lower than
        the threshold value written in
         the SFP EEPROM  <Condtype> VCC_LOW_WNG_1
        <Probcause> powerProblem (36) <Alarmtype>
        equipmentAlarm (5) <Polarity> (2)
        "
	::= { pm1004vAlmsfpWarnDdmEntry 6 }


pm1004vAlmTxBiasHighWngPortn OBJECT-TYPE
	SYNTAX  EkiOnOff
	MAX-ACCESS read-only
	STATUS current
	DESCRIPTION
        "
        Client SFP Bias High Warning :Warning
        indicating that the SFP laser bias
        current of port is higher than
         the threshold value written in
        the SFP EEPROM <Condtype> TX_BIAS_HIGH_WNG_1
        <Probcause> transmitterFailure
         (56) <Alarmtype> equipmentAlarm
        (5) <Polarity> (2)
        "
	::= { pm1004vAlmsfpWarnDdmEntry 5 }


pm1004vAlmTxBiasLowWngPortn OBJECT-TYPE
	SYNTAX  EkiOnOff
	MAX-ACCESS read-only
	STATUS current
	DESCRIPTION
        "
        Client SFP Bias Low Warning :Warning
        indicating that the SFP laser bias
        current of port is lower than the
        threshold value written in the
         SFP EEPROM <Condtype> TX_BIAS_LOW_WNG_1
        <Probcause> transmitterFailure
         (56) <Alarmtype> equipmentAlarm
        (5) <Polarity> (2)
        "
	::= { pm1004vAlmsfpWarnDdmEntry 4 }


pm1004vAlmTxPwrHighWngPortn OBJECT-TYPE
	SYNTAX  EkiOnOff
	MAX-ACCESS read-only
	STATUS current
	DESCRIPTION
        "
        Client SFP Tx Power High Warning
        :Warning indicating that the SFP
        output power of port is higher
         than the threshold value written
        in the SFP EEPROM <Condtype> TX_PWR_HIGH_WNG_1
        <Probcause> transmitterFailure
         (56) <Alarmtype> equipmentAlarm
        (5) <Polarity> (2)
        "
	::= { pm1004vAlmsfpWarnDdmEntry 3 }


pm1004vAlmTxPwLowWngPortn OBJECT-TYPE
	SYNTAX  EkiOnOff
	MAX-ACCESS read-only
	STATUS current
	DESCRIPTION
        "
        Client SFP Tx Power Low Warning
        :Warning indicating that the SFP
        output power of port is lower than
        the threshold value written in
         the SFP EEPROM <Condtype> TX_PW_LOW_WNG_1
        <Probcause> transmitterFailure
         (56) <Alarmtype> equipmentAlarm
        (5) <Polarity> (2)
        "
	::= { pm1004vAlmsfpWarnDdmEntry 2 }


--- *********************************************************
---     TABLE for the pm1004vAlmsfpCritDdm articles
--- *********************************************************

pm1004vAlmsfpCritDdmTable OBJECT-TYPE
	SYNTAX  SEQUENCE OF Pm1004vAlmsfpCritDdmEntry
	MAX-ACCESS not-accessible
	STATUS current
	DESCRIPTION
        "
        List of pm1004vAlmsfpCritDdm Article
        "
	::= { pm1004vAlmClientNurg 56 }


pm1004vAlmsfpCritDdmEntry OBJECT-TYPE
	SYNTAX Pm1004vAlmsfpCritDdmEntry
	MAX-ACCESS not-accessible
	STATUS current
	DESCRIPTION
        "
        Row definition for the pm1004vAlmsfpCritDdm
        table
        "
	INDEX   { pm1004vAlmsfpCritDdmIndex }
	::= { pm1004vAlmsfpCritDdmTable 1 }


Pm1004vAlmsfpCritDdmEntry ::=
	SEQUENCE {
	pm1004vAlmsfpCritDdmIndex
		INTEGER,
	pm1004vAlmRxPwrHighCritPortn
		EkiOnOff,
	pm1004vAlmRxPwrLowCritPortn
		EkiOnOff,
	pm1004vAlmTxPwrHighCritPortn
		EkiOnOff,
	pm1004vAlmTxPwrLowCritPortn
		EkiOnOff
	}


pm1004vAlmsfpCritDdmIndex OBJECT-TYPE
	SYNTAX  INTEGER(0..128)
	MAX-ACCESS  read-only
	STATUS current
	DESCRIPTION
        "
        Index definition for the pm1004vAlmsfpCritDdm
        table
        "
	::= { pm1004vAlmsfpCritDdmEntry 1 }


pm1004vAlmRxPwrHighCritPortn OBJECT-TYPE
	SYNTAX  EkiOnOff
	MAX-ACCESS read-only
	STATUS current
	DESCRIPTION
        "
        Client SFP Custom Rx Power High
        :Custom Alarm indicating that the
        SFP input power of port is higher
        than the custom threshold defined
        in configuration  <Help>  Custom
        Alarm indicating that the SFP input
        power of port is higher than the
        custom threshold defined in custom
        configuration <Condtype> RX_PWR_HIGH_CRIT_1
        <Probcause> receiveFailure (41)
        <Alarmtype> equipmentAlarm (5)
         <Polarity> (2)
        "
	::= { pm1004vAlmsfpCritDdmEntry 17 }


pm1004vAlmRxPwrLowCritPortn OBJECT-TYPE
	SYNTAX  EkiOnOff
	MAX-ACCESS read-only
	STATUS current
	DESCRIPTION
        "
        Client SFP Custom Rx Power Low
        :Custom Alarm indicating that the
        SFP input power of port is lower
        than the custom threshold defined
        in configuration  <Help>  Custom
        Alarm indicating that the SFP input
        power of port is lower than the
        custom threshold defined in custom
        configuration <Condtype> RX_PWR_LOW_CRIT_1
        <Probcause> receiveFailure (41)
        <Alarmtype> equipmentAlarm (5)
         <Polarity> (2)
        "
	::= { pm1004vAlmsfpCritDdmEntry 16 }


pm1004vAlmTxPwrHighCritPortn OBJECT-TYPE
	SYNTAX  EkiOnOff
	MAX-ACCESS read-only
	STATUS current
	DESCRIPTION
        "
        Client SFP Custom Tx Power High
        :Custom Alarm indicating that the
        SFP output power of port is higher
        than the custom threshold defined
        in configuration  <Help>  Custom
        Alarm indicating that the SFP output
        power of port is higher than the
        custom threshold defined in custom
        configuration <Condtype> TX_PWR_HIGH_CRIT_1
        <Probcause> transmitterFailure
         (56) <Alarmtype> equipmentAlarm
        (5) <Polarity> (2)
        "
	::= { pm1004vAlmsfpCritDdmEntry 3 }


pm1004vAlmTxPwrLowCritPortn OBJECT-TYPE
	SYNTAX  EkiOnOff
	MAX-ACCESS read-only
	STATUS current
	DESCRIPTION
        "
        Client SFP Custom Tx Power Low
        :Custom Alarm indicating that the
        SFP output power of port is lower
        than the custom threshold defined
        in configuration  <Help>  Custom
        Alarm indicating that the SFP output
        power of port is lower than the
        custom threshold defined in custom
        configuration <Condtype> TX_PWR_LOW_CRIT_1
        <Probcause> transmitterFailure
         (56) <Alarmtype> equipmentAlarm
        (5) <Polarity> (2)
        "
	::= { pm1004vAlmsfpCritDdmEntry 2 }


--- *********************************************************
---     TABLE for the pm1004vAlmmapperDeAlm articles
--- *********************************************************

pm1004vAlmmapperDeAlmTable OBJECT-TYPE
	SYNTAX  SEQUENCE OF Pm1004vAlmmapperDeAlmEntry
	MAX-ACCESS not-accessible
	STATUS current
	DESCRIPTION
        "
        List of pm1004vAlmmapperDeAlm
         Article
        "
	::= { pm1004vAlmClientCrit 72 }


pm1004vAlmmapperDeAlmEntry OBJECT-TYPE
	SYNTAX Pm1004vAlmmapperDeAlmEntry
	MAX-ACCESS not-accessible
	STATUS current
	DESCRIPTION
        "
        Row definition for the pm1004vAlmmapperDeAlm
        table
        "
	INDEX   { pm1004vAlmmapperDeAlmIndex }
	::= { pm1004vAlmmapperDeAlmTable 1 }


Pm1004vAlmmapperDeAlmEntry ::=
	SEQUENCE {
	pm1004vAlmmapperDeAlmIndex
		INTEGER,
	pm1004vAlmDwBufferOvlPortn
		EkiOnOff,
	pm1004vAlmDwCsfDetPortn
		EkiOnOff,
	pm1004vAlmUpBufferOvlPortn
		EkiOnOff,
	pm1004vAlmUpAccOosPortn
		EkiOnOff
	}


pm1004vAlmmapperDeAlmIndex OBJECT-TYPE
	SYNTAX  INTEGER(0..128)
	MAX-ACCESS  read-only
	STATUS current
	DESCRIPTION
        "
        Index definition for the pm1004vAlmmapperDeAlm
        table
        "
	::= { pm1004vAlmmapperDeAlmEntry 1 }


pm1004vAlmDwBufferOvlPortn OBJECT-TYPE
	SYNTAX  EkiOnOff
	MAX-ACCESS read-only
	STATUS current
	DESCRIPTION
        "
        Client Downstream Buffer Overload
        :This OID indicates that the de-mapper
        buffer for client port is in overload.
         <Help>  This alarm indicates if
        there is a downstream FIFO overload
        for this client port <Condtype>
        DW_BUFFER_OVL_1 <Probcause> equipmentMalfunction
        (16) <Alarmtype> equipmentAlarm
        (5) <Polarity> (2)
        "
	::= { pm1004vAlmmapperDeAlmEntry 15 }


pm1004vAlmDwCsfDetPortn OBJECT-TYPE
	SYNTAX  EkiOnOff
	MAX-ACCESS read-only
	STATUS current
	DESCRIPTION
        "
        Client Signal Fail Detected :This
        OID indicates that a CSF has been
        detected on client port in the
         downstream direction   <Help>
          This alarm indicates if a Client
        Signal Fail has been detected in
        the incoming line frame for this
        client port <Condtype> DW_CSF_DET_1
        <Probcause> receiveFailure (41)
        <Alarmtype> equipmentAlarm (5)
         <Polarity> (2)
        "
	::= { pm1004vAlmmapperDeAlmEntry 12 }


pm1004vAlmUpBufferOvlPortn OBJECT-TYPE
	SYNTAX  EkiOnOff
	MAX-ACCESS read-only
	STATUS current
	DESCRIPTION
        "
        Client Upstream Buffer Overload
        :This OID indicates that the rate
        adaptation buffer for client port
        is in overload.  <Help>  This alarm
        indicates if there is a upstream
        FIFO overload for this client port
        <Condtype> UP_BUFFER_OVL_1 <Probcause>
        receiveFailure (41) <Alarmtype>
        integrityViolation (7) <Polarity>
        (2)
        "
	::= { pm1004vAlmmapperDeAlmEntry 11 }


pm1004vAlmUpAccOosPortn OBJECT-TYPE
	SYNTAX  EkiOnOff
	MAX-ACCESS read-only
	STATUS current
	DESCRIPTION
        "
        Client Loss Of Synchro :This OID
        indicates the upstream client input
        port has lost synchronization on
        its decoder   <Help>   This alarms
        indicates if the input client signal
        is correctly synchronized with
         the decoder <Condtype> UP_ACC_OOS_1
        <Probcause> receiveFailure (41)
        <Alarmtype> integrityViolation
         (7) <Polarity> (2)
        "
	::= { pm1004vAlmmapperDeAlmEntry 2 }


--- *********************************************************
---     TABLE for the pm1004vAlmvideoProtocolStatus articles
--- *********************************************************

pm1004vAlmvideoProtocolStatusTable OBJECT-TYPE
	SYNTAX  SEQUENCE OF Pm1004vAlmvideoProtocolStatusEntry
	MAX-ACCESS not-accessible
	STATUS current
	DESCRIPTION
        "
        List of pm1004vAlmvideoProtocolStatus
        Article
        "
	::= { pm1004vAlmClientCrit 112 }


pm1004vAlmvideoProtocolStatusEntry OBJECT-TYPE
	SYNTAX Pm1004vAlmvideoProtocolStatusEntry
	MAX-ACCESS not-accessible
	STATUS current
	DESCRIPTION
        "
        Row definition for the pm1004vAlmvideoProtocolStatus
        table
        "
	INDEX   { pm1004vAlmvideoProtocolStatusIndex }
	::= { pm1004vAlmvideoProtocolStatusTable 1 }


Pm1004vAlmvideoProtocolStatusEntry ::=
	SEQUENCE {
	pm1004vAlmvideoProtocolStatusIndex
		INTEGER,
	pm1004vAlmGbeRxPortn
		EkiOnOff,
	pm1004vAlmFastEtherRxPortn
		EkiOnOff,
	pm1004vAlmDvbAsiRxPortn
		EkiOnOff,
	pm1004vAlmHdSdiNtscRxPortn
		EkiOnOff,
	pm1004vAlmHdSdiPalRxPortn
		EkiOnOff,
	pm1004vAlmSdiRxPortn
		EkiOnOff,
	pm1004vAlmGbeTxPortn
		EkiOnOff,
	pm1004vAlmFastEtherTxPortn
		EkiOnOff,
	pm1004vAlmDvbAsiTxPortn
		EkiOnOff,
	pm1004vAlmHdSdiNtscTxPortn
		EkiOnOff,
	pm1004vAlmHdSdiPalTxPortn
		EkiOnOff,
	pm1004vAlmSdiTxPortn
		EkiOnOff
	}


pm1004vAlmvideoProtocolStatusIndex OBJECT-TYPE
	SYNTAX  INTEGER(0..128)
	MAX-ACCESS  read-only
	STATUS current
	DESCRIPTION
        "
        Index definition for the pm1004vAlmvideoProtocolStatus
        table
        "
	::= { pm1004vAlmvideoProtocolStatusEntry 1 }


pm1004vAlmGbeRxPortn OBJECT-TYPE
	SYNTAX  EkiOnOff
	MAX-ACCESS read-only
	STATUS current
	DESCRIPTION
        "
        Gigabit Ethernet Detected On Rx

 :This OID indicates that the
         Gigabit Ethernet protocol has
         been detected on the port (only
        significant on Client6-GbE port)

         <Help>   This status indicates
        that the Gigabit Ethernet protocol
        has been detected on the port (only
        significant on Client6-GbE port)
        <Condtype> GBE_RX_1 <Probcause>
        informationalStatus(1000) <Alarmtype>
        other (1) <Polarity> (2)
        "
	::= { pm1004vAlmvideoProtocolStatusEntry 15 }


pm1004vAlmFastEtherRxPortn OBJECT-TYPE
	SYNTAX  EkiOnOff
	MAX-ACCESS read-only
	STATUS current
	DESCRIPTION
        "
        Fast Ethernet Detected On Rx :This
        OID indicates that the Fast Ethernet
        protocol has been detected on the
        port (only significant on Client1-RJ45
        port)
  <Help>   This status indicates
        that the Fast Ethernet protocol
        has been detected on the port (only
        significant on Client1-RJ45 port)
        <Condtype> FAST_ETHER_RX_1 <Probcause>
        informationalStatus(1000) <Alarmtype>
        other (1) <Polarity> (2)
        "
	::= { pm1004vAlmvideoProtocolStatusEntry 14 }


pm1004vAlmDvbAsiRxPortn OBJECT-TYPE
	SYNTAX  EkiOnOff
	MAX-ACCESS read-only
	STATUS current
	DESCRIPTION
        "
        DVB-ASI Detected On Rx :This OID
        indicates that the DVB-ASI protocol
        has been detected on the receive
        side of the port (only significant
        on Video2 to Video 5 ports)  <Help>
          This status indicates that the
        DVB-ASI protocol has been detected
        on the receive side of the port
        (only significant on Video2 to
         Video 5 ports) <Condtype> DVB_ASI_RX_1
        <Probcause> informationalStatus(1000)
        <Alarmtype> other (1) <Polarity>
        (2)
        "
	::= { pm1004vAlmvideoProtocolStatusEntry 13 }


pm1004vAlmHdSdiNtscRxPortn OBJECT-TYPE
	SYNTAX  EkiOnOff
	MAX-ACCESS read-only
	STATUS current
	DESCRIPTION
        "
        HD-SDI-NTSC Detected On Rx :This
        OID indicates that the HD-SDI-NTSC
        protocol has been detected on the
        receive side of the port (only
         significant on Video2 to Video
        5 ports)
  <Help>   This status
        indicates that the HD-SDI-NTSC
         protocol has been detected on
         the receive side of the port (only
        significant on Video2 to Video
         5 ports) <Condtype> HD_SDI_NTSC_RX_1
        <Probcause> informationalStatus(1000)
        <Alarmtype> other (1) <Polarity>
        (2)
        "
	::= { pm1004vAlmvideoProtocolStatusEntry 12 }


pm1004vAlmHdSdiPalRxPortn OBJECT-TYPE
	SYNTAX  EkiOnOff
	MAX-ACCESS read-only
	STATUS current
	DESCRIPTION
        "
        HD-SDI-PAL Detected On Rx :This
        OID indicates that the HD-SDI-PAL
        protocol has been detected on the
        receive side of the port (only
         significant on Video2 to Video
        5 ports)
  <Help>   This status
        indicates that the HD-SDI-PAL protocol
        has been detected on the receive
        side of the port (only significant
        on Video2 to Video 5 ports) <Condtype>
        HD_SDI_PAL_RX_1 <Probcause> informationalStatus(1000)
        <Alarmtype> other (1) <Polarity>
        (2)
        "
	::= { pm1004vAlmvideoProtocolStatusEntry 11 }


pm1004vAlmSdiRxPortn OBJECT-TYPE
	SYNTAX  EkiOnOff
	MAX-ACCESS read-only
	STATUS current
	DESCRIPTION
        "
        SDI Detected On Rx :This OID indicates
        that the SDI protocol has been
         detected on the receive side of
        the port (only significant on Video2
        to Video 5 ports)
  <Help>   This
        status indicates that the SDI protocol
        has been detected on the receive
        side of the port (only significant
        on Video2 to Video 5 ports) <Condtype>
        SDI_RX_1 <Probcause> informationalStatus(1000)
        <Alarmtype> other (1) <Polarity>
        (2)
        "
	::= { pm1004vAlmvideoProtocolStatusEntry 10 }


pm1004vAlmGbeTxPortn OBJECT-TYPE
	SYNTAX  EkiOnOff
	MAX-ACCESS read-only
	STATUS current
	DESCRIPTION
        "
        Gigabit Ethernet Detected On Tx

 :This OID indicates that the
         Gigabit Ethernet protocol has
         been detected on the port (only
        significant on Client6-GbE port)

         <Help>   This status indicates
        that the Gigabit Ethernet protocol
        has been detected on the port (only
        significant on Client6-GbE port)
        <Condtype> GBE_TX_1 <Probcause>
        informationalStatus(1000) <Alarmtype>
        other (1) <Polarity> (2)
        "
	::= { pm1004vAlmvideoProtocolStatusEntry 7 }


pm1004vAlmFastEtherTxPortn OBJECT-TYPE
	SYNTAX  EkiOnOff
	MAX-ACCESS read-only
	STATUS current
	DESCRIPTION
        "
        Fast Ethernet Detected On Tx :This
        OID indicates that the Fast Ethernet
        protocol has been detected on the
        port (only significant on Client1-RJ45
        port)
  <Help>   This status indicates
        that the Fast Ethernet protocol
        has been detected on the port (only
        significant on Client1-RJ45 port)
        <Condtype> FAST_ETHER_TX_1 <Probcause>
        informationalStatus(1000) <Alarmtype>
        other (1) <Polarity> (2)
        "
	::= { pm1004vAlmvideoProtocolStatusEntry 6 }


pm1004vAlmDvbAsiTxPortn OBJECT-TYPE
	SYNTAX  EkiOnOff
	MAX-ACCESS read-only
	STATUS current
	DESCRIPTION
        "
        DVB-ASI Detected On Tx :This OID
        indicates that the DVB-ASI protocol
        has been detected on the transmit
        side of the port (only significant
        on Video2 to Video 5 ports)
  <Help>
          This status indicates that the
        DVB-ASI protocol has been detected
        on the transmit side of the port
        (only significant on Video2 to
         Video 5 ports) <Condtype> DVB_ASI_TX_1
        <Probcause> informationalStatus(1000)
        <Alarmtype> other (1) <Polarity>
        (2)
        "
	::= { pm1004vAlmvideoProtocolStatusEntry 5 }


pm1004vAlmHdSdiNtscTxPortn OBJECT-TYPE
	SYNTAX  EkiOnOff
	MAX-ACCESS read-only
	STATUS current
	DESCRIPTION
        "
        HD-SDI-NTSC Detected On Tx :This
        OID indicates that the HD-SDI-NTSC
        protocol has been detected on the
        transmit side of the port (only
        significant on Video2 to Video
         5 ports)
  <Help>   This status
        indicates that the HD-SDI-NTSC
         protocol has been detected on
         the transmit side of the port
         (only significant on Video2 to
        Video 5 ports) <Condtype> HD_SDI_NTSC_TX_1
        <Probcause> informationalStatus(1000)
        <Alarmtype> other (1) <Polarity>
        (2)
        "
	::= { pm1004vAlmvideoProtocolStatusEntry 4 }


pm1004vAlmHdSdiPalTxPortn OBJECT-TYPE
	SYNTAX  EkiOnOff
	MAX-ACCESS read-only
	STATUS current
	DESCRIPTION
        "
        HD-SDI-PAL Detected On Tx :This
        OID indicates that the HD-SDI-PAL
        protocol has been detected on the
        transmit side of the port (only
        significant on Video2 to Video
         5 ports)  <Help>   This status
        indicates that the HD-SDI-PAL protocol
        has been detected on the transmit
        side of the port (only significant
        on Video2 to Video 5 ports) <Condtype>
        HD_SDI_PAL_TX_1 <Probcause> informationalStatus(1000)
        <Alarmtype> other (1) <Polarity>
        (2)
        "
	::= { pm1004vAlmvideoProtocolStatusEntry 3 }


pm1004vAlmSdiTxPortn OBJECT-TYPE
	SYNTAX  EkiOnOff
	MAX-ACCESS read-only
	STATUS current
	DESCRIPTION
        "
        SDI Detected On Tx :This OID indicates
        that the SDI protocol has been
         detected on the transmit side
         of the port (only significant
         on Video2 to Video 5 ports)
         <Help>   This status indicates
        that the SDI protocol has been
         detected on the transmit side
         of the port (only significant
         on Video2 to Video 5 ports) <Condtype>
        SDI_TX_1 <Probcause> informationalStatus(1000)
        <Alarmtype> other (1) <Polarity>
        (2)
        "
	::= { pm1004vAlmvideoProtocolStatusEntry 2 }


--- *********************************************************
---     TABLE for the pm1004vAlmdfrmAlm articles
--- *********************************************************

pm1004vAlmdfrmAlmTable OBJECT-TYPE
	SYNTAX  SEQUENCE OF Pm1004vAlmdfrmAlmEntry
	MAX-ACCESS not-accessible
	STATUS current
	DESCRIPTION
        "
        List of pm1004vAlmdfrmAlm Article
        "
	::= { pm1004vAlmLineCrit 128 }


pm1004vAlmdfrmAlmEntry OBJECT-TYPE
	SYNTAX Pm1004vAlmdfrmAlmEntry
	MAX-ACCESS not-accessible
	STATUS current
	DESCRIPTION
        "
        Row definition for the pm1004vAlmdfrmAlm
        table
        "
	INDEX   { pm1004vAlmdfrmAlmIndex }
	::= { pm1004vAlmdfrmAlmTable 1 }


Pm1004vAlmdfrmAlmEntry ::=
	SEQUENCE {
	pm1004vAlmdfrmAlmIndex
		INTEGER,
	pm1004vAlmDwLossofsyncPortn
		EkiOnOff
	}


pm1004vAlmdfrmAlmIndex OBJECT-TYPE
	SYNTAX  INTEGER(0..128)
	MAX-ACCESS  read-only
	STATUS current
	DESCRIPTION
        "
        Index definition for the pm1004vAlmdfrmAlm
        table
        "
	::= { pm1004vAlmdfrmAlmEntry 1 }


pm1004vAlmDwLossofsyncPortn OBJECT-TYPE
	SYNTAX  EkiOnOff
	MAX-ACCESS read-only
	STATUS current
	DESCRIPTION
        "
        Loss Of Synchronisation :This
         OID indicates the upstream line
        input port is in Loss of Synchronization.
         <Help>  This alarms indicates
         if the input signal is correctly
        synchronized <Condtype> DW_LOSSOFSYNC_1
        <Probcause> receiveFailure (41)
        <Alarmtype>  physicalViolation
         (9) <Polarity> (2)
        "
	::= { pm1004vAlmdfrmAlmEntry 5 }


--- *********************************************************
---     TABLE for the pm1004vAlmlineSyncAlarms articles
--- *********************************************************

pm1004vAlmlineSyncAlarmsTable OBJECT-TYPE
	SYNTAX  SEQUENCE OF Pm1004vAlmlineSyncAlarmsEntry
	MAX-ACCESS not-accessible
	STATUS current
	DESCRIPTION
        "
        List of pm1004vAlmlineSyncAlarms
        Article
        "
	::= { pm1004vAlmLineCrit 133 }


pm1004vAlmlineSyncAlarmsEntry OBJECT-TYPE
	SYNTAX Pm1004vAlmlineSyncAlarmsEntry
	MAX-ACCESS not-accessible
	STATUS current
	DESCRIPTION
        "
        Row definition for the pm1004vAlmlineSyncAlarms
        table
        "
	INDEX   { pm1004vAlmlineSyncAlarmsIndex }
	::= { pm1004vAlmlineSyncAlarmsTable 1 }


Pm1004vAlmlineSyncAlarmsEntry ::=
	SEQUENCE {
	pm1004vAlmlineSyncAlarmsIndex
		INTEGER,
	pm1004vAlmDwLosPortn
		EkiOnOff,
	pm1004vAlmUpLockerrPortn
		EkiOnOff,
	pm1004vAlmDwLockerrPortn
		EkiOnOff
	}


pm1004vAlmlineSyncAlarmsIndex OBJECT-TYPE
	SYNTAX  INTEGER(0..128)
	MAX-ACCESS  read-only
	STATUS current
	DESCRIPTION
        "
        Index definition for the pm1004vAlmlineSyncAlarms
        table
        "
	::= { pm1004vAlmlineSyncAlarmsEntry 1 }


pm1004vAlmDwLosPortn OBJECT-TYPE
	SYNTAX  EkiOnOff
	MAX-ACCESS read-only
	STATUS current
	DESCRIPTION
        "
        Line Input Loss Of Signal :This
        OID indicates a loss of signal
         on the 10 Gb/s input.  <Help>
          This alarm indicates if an optical
        signal is detected on the line
         transceiver input <Condtype> DW_LOS
        <Probcause> receiveFailure (41)
        <Alarmtype> physicalViolation (9)
        <Polarity> (2)
        "
	::= { pm1004vAlmlineSyncAlarmsEntry 17 }


pm1004vAlmUpLockerrPortn OBJECT-TYPE
	SYNTAX  EkiOnOff
	MAX-ACCESS read-only
	STATUS current
	DESCRIPTION
        "
        Upstream Clock Lock Error :This
        OID indicates that the serializer
        output 10 Gb/s clock multiplier
        unit is not locked. <Condtype>
         UP_LOCKERR <Probcause> receiveFailure
        (41) <Alarmtype> equipmentAlarm
        (5) <Polarity> (2)
        "
	::= { pm1004vAlmlineSyncAlarmsEntry 14 }


pm1004vAlmDwLockerrPortn OBJECT-TYPE
	SYNTAX  EkiOnOff
	MAX-ACCESS read-only
	STATUS current
	DESCRIPTION
        "
        Downstream Clock Lock Error :This
        OID indicates that the deserializer
        input 10 Gb/s clock recovery is
        not locked. <Condtype> DW_LOCKERR
        <Probcause> receiveFailure (41)
        <Alarmtype> equipmentAlarm (5)
         <Polarity> (2)
        "
	::= { pm1004vAlmlineSyncAlarmsEntry 13 }


--- *****************************************************
---     LEAF for the modInitFailLevel2 article
--- *****************************************************
pm1004vAlmmodInitFailLevel2 OBJECT IDENTIFIER ::= { pm1004vAlmOtherUrg 194 }




pm1004vAlmSwInitFail OBJECT-TYPE
	  SYNTAX EkiOnOff
	  MAX-ACCESS read-only
	  STATUS current
	  DESCRIPTION
        "
        SW Init Fail :This OID indicates
        that the SW intialization has caused
        unknown intial conditions  <Help>
         This alarm indicates if the SW
        module is correctly initialized
        <Condtype> SW_INIT_FAIL <Probcause>
        softwareError (47) <Alarmtype>
         processingErrorAlarm (4) <Polarity>
        (2)
        "
	  ::= { pm1004vAlmmodInitFailLevel2 5 }



pm1004vAlmResetHwInitFail OBJECT-TYPE
	  SYNTAX EkiOnOff
	  MAX-ACCESS read-only
	  STATUS current
	  DESCRIPTION
        "
        Reset HW Init Fail :This OID indicates
        that the HW intialization has caused
        unknown intial conditions  <Help>
         This alarm indicates if the HW
        has been correctly initialized
         <Condtype> RESET_HW_INIT_FAIL
         <Probcause> softwareError (47)
        <Alarmtype> processingErrorAlarm
        (4) <Polarity> (2)
        "
	  ::= { pm1004vAlmmodInitFailLevel2 4 }



pm1004vAlmBootUndone OBJECT-TYPE
	  SYNTAX EkiOnOff
	  MAX-ACCESS read-only
	  STATUS current
	  DESCRIPTION
        "
        Boot Undone :This OID indicates
        that the boot has not been correctly
        achieved  <Help>  This alarm indicates
        if the module has correctly boot
        <Condtype> BOOT_UNDONE <Probcause>
        softwareError (47) <Alarmtype>
         processingErrorAlarm (4) <Polarity>
        (2)
        "
	  ::= { pm1004vAlmmodInitFailLevel2 3 }



pm1004vAlmNextColdBootForced OBJECT-TYPE
	  SYNTAX EkiOnOff
	  MAX-ACCESS read-only
	  STATUS current
	  DESCRIPTION
        "
        Next Cold Boot Forced :This OID
        indicates that the next Reset will
        be forced Cold  <Help>  This alarm
        indicates that the next reset of
        the module will be forced to cold
        reset <Condtype> NEXT_COLD_BOOT_FORCED
        <Probcause> informationalStatus(1000)
        <Alarmtype> other (1) <Polarity>
        (2)
        "
	  ::= { pm1004vAlmmodInitFailLevel2 2 }



pm1004vAlmLedFail OBJECT-TYPE
	  SYNTAX EkiOnOff
	  MAX-ACCESS read-only
	  STATUS current
	  DESCRIPTION
        "
        Led Fail :This OID indicates that
        Led register has not been correctly
        initalized  <Help>  This alarm
         indicates if the module LEDs are
        correctly initialized <Condtype>
        LED_FAIL <Probcause> softwareError
        (47) <Alarmtype> processingErrorAlarm
        (4) <Polarity> (2)
        "
	  ::= { pm1004vAlmmodInitFailLevel2 1 }



--- *****************************************************
---     LEAF for the modInitFailLevel3 article
--- *****************************************************
pm1004vAlmmodInitFailLevel3 OBJECT IDENTIFIER ::= { pm1004vAlmOtherUrg 195 }




pm1004vAlmClient6InitFail OBJECT-TYPE
	  SYNTAX EkiOnOff
	  MAX-ACCESS read-only
	  STATUS current
	  DESCRIPTION
        "
        Client6 Init Fail :This OID indicates
        that Client 6 registers subset
         has not been correctly initialized
         <Help>  This alarm indicates if
        the client port 6 is correctly
         initialized <Condtype> CLIENT6_INIT_FAIL
        <Probcause> softwareError (47)
         <Alarmtype> processingErrorAlarm
        (4) <Polarity> (2)
        "
	  ::= { pm1004vAlmmodInitFailLevel3 14 }



pm1004vAlmClient5InitFail OBJECT-TYPE
	  SYNTAX EkiOnOff
	  MAX-ACCESS read-only
	  STATUS current
	  DESCRIPTION
        "
        Client5 Init Fail :This OID indicates
        that Client 5 registers subset
         has not been correctly initialized
         <Help>  This alarm indicates if
        the client port 5 is correctly
         initialized <Condtype> CLIENT5_INIT_FAIL
        <Probcause> softwareError (47)
         <Alarmtype> processingErrorAlarm
        (4) <Polarity> (2)
        "
	  ::= { pm1004vAlmmodInitFailLevel3 13 }



pm1004vAlmClient4InitFail OBJECT-TYPE
	  SYNTAX EkiOnOff
	  MAX-ACCESS read-only
	  STATUS current
	  DESCRIPTION
        "
        Client4 Init Fail :This OID indicates
        that Client 4 registers subset
         has not been correctly initialized
         <Help>  This alarm indicates if
        the client port 4 is correctly
         initialized <Condtype> CLIENT4_INIT_FAIL
        <Probcause> softwareError (47)
         <Alarmtype> processingErrorAlarm
        (4) <Polarity> (2)
        "
	  ::= { pm1004vAlmmodInitFailLevel3 12 }



pm1004vAlmClient3InitFail OBJECT-TYPE
	  SYNTAX EkiOnOff
	  MAX-ACCESS read-only
	  STATUS current
	  DESCRIPTION
        "
        Client3 Init Fail :This OID indicates
        that Client 3 registers subset
         has not been correctly initialized
         <Help>  This alarm indicates if
        the client port 3 is correctly
         initialized <Condtype> CLIENT3_INIT_FAIL
        <Probcause> softwareError (47)
         <Alarmtype> processingErrorAlarm
        (4) <Polarity> (2)
        "
	  ::= { pm1004vAlmmodInitFailLevel3 11 }



pm1004vAlmClient2InitFail OBJECT-TYPE
	  SYNTAX EkiOnOff
	  MAX-ACCESS read-only
	  STATUS current
	  DESCRIPTION
        "
        Client2 Init Fail :This OID indicates
        that Client 2 registers subset
         has not been correctly initialized
         <Help>  This alarm indicates if
        the client port 2 is correctly
         initialized <Condtype> CLIENT2_INIT_FAIL
        <Probcause> softwareError (47)
         <Alarmtype> processingErrorAlarm
        (4) <Polarity> (2)
        "
	  ::= { pm1004vAlmmodInitFailLevel3 10 }



pm1004vAlmClient1InitFail OBJECT-TYPE
	  SYNTAX EkiOnOff
	  MAX-ACCESS read-only
	  STATUS current
	  DESCRIPTION
        "
        Client1 Init Fail :This OID indicates
        that Client 1 registers subset
         has not been correctly initialized
         <Help>  This alarm indicates if
        the client port 1 is correctly
         initialized <Condtype> CLIENT1_INIT_FAIL
        <Probcause> softwareError (47)
         <Alarmtype> processingErrorAlarm
        (4) <Polarity> (2)
        "
	  ::= { pm1004vAlmmodInitFailLevel3 9 }



pm1004vAlmLine2InitFail OBJECT-TYPE
	  SYNTAX EkiOnOff
	  MAX-ACCESS read-only
	  STATUS current
	  DESCRIPTION
        "
        Line2 Init Fail :This OID indicates
        that the Line register subset has
        not been correctly initialized
          <Help>  This alarm indicates
         if the line port 2 is correctly
        initialized <Condtype> LINE2_INIT_FAIL
        <Probcause> softwareError (47)
         <Alarmtype> processingErrorAlarm
        (4) <Polarity> (2)
        "
	  ::= { pm1004vAlmmodInitFailLevel3 8 }



pm1004vAlmLine1InitFail OBJECT-TYPE
	  SYNTAX EkiOnOff
	  MAX-ACCESS read-only
	  STATUS current
	  DESCRIPTION
        "
        Line1 Init Fail :This OID indicates
        that the Line registersvsubset
         has not been correctly initialized
         <Help>  This alarm indicates if
        the line port 1 is correctly initialized
        <Condtype> LINE1_INIT_FAIL <Probcause>
        softwareError (47) <Alarmtype>
         processingErrorAlarm (4) <Polarity>
        (2)
        "
	  ::= { pm1004vAlmmodInitFailLevel3 7 }



pm1004vAlmXfp2InitFail OBJECT-TYPE
	  SYNTAX EkiOnOff
	  MAX-ACCESS read-only
	  STATUS current
	  DESCRIPTION
        "
        XFP2 Init Fail :This OID indicates
        that the XFP has not been correctly
        initialized  <Help>  This alarm
        indicates if the line transceiver
        2 is correctly initialized <Condtype>
        XFP2_INIT_FAIL <Probcause> softwareError
        (47) <Alarmtype> processingErrorAlarm
        (4) <Polarity> (2)
        "
	  ::= { pm1004vAlmmodInitFailLevel3 6 }



pm1004vAlmXfp1InitFail OBJECT-TYPE
	  SYNTAX EkiOnOff
	  MAX-ACCESS read-only
	  STATUS current
	  DESCRIPTION
        "
        XFP1 Init Fail :This OID indicates
        that the XFP has not been correctly
        initialized  <Help>  This alarm
        indicates if the line transceiver
        1 is correctly initialized <Condtype>
        XFP1_INIT_FAIL <Probcause> softwareError
        (47) <Alarmtype> processingErrorAlarm
        (4) <Polarity> (2)
        "
	  ::= { pm1004vAlmmodInitFailLevel3 5 }



pm1004vAlmInitModuleFail OBJECT-TYPE
	  SYNTAX EkiOnOff
	  MAX-ACCESS read-only
	  STATUS current
	  DESCRIPTION
        "
        Init Module Fail :This OID indicates
        that the Module has not been correctly
        initialized  <Help>  This alarm
        indicates if the SW module is correctly
        initialized <Condtype> INIT_MODULE_FAIL
        <Probcause> softwareError (47)
         <Alarmtype> processingErrorAlarm
        (4) <Polarity> (2)
        "
	  ::= { pm1004vAlmmodInitFailLevel3 3 }



pm1004vAlmObmTypeReadFail OBJECT-TYPE
	  SYNTAX EkiOnOff
	  MAX-ACCESS read-only
	  STATUS current
	  DESCRIPTION
        "
        OBM Type Read Fail :This OID indicates
        that OBM type has not been recognized
         <Help>  This alarm indicates if
        the OBM board has been correctly
        identified <Condtype> OBM_TYPE_READ_FAIL
        <Probcause> softwareError (47)
         <Alarmtype> processingErrorAlarm
        (4) <Polarity> (2)
        "
	  ::= { pm1004vAlmmodInitFailLevel3 2 }



pm1004vAlmGwIdentFail OBJECT-TYPE
	  SYNTAX EkiOnOff
	  MAX-ACCESS read-only
	  STATUS current
	  DESCRIPTION
        "
        GW Ident Fail :This OID indicates
        that GW identification has not
         been read  <Help>  This alarm
         indicates if the GW has been correctly
        identified <Condtype> GW_IDENT_FAIL
        <Probcause> softwareError (47)
         <Alarmtype> processingErrorAlarm
        (4) <Polarity> (2)
        "
	  ::= { pm1004vAlmmodInitFailLevel3 1 }



--- *****************************************************
---     LEAF for the clientRxProt article
--- *****************************************************
pm1004vAlmclientRxProt OBJECT IDENTIFIER ::= { pm1004vAlmOtherUrg 198 }




pm1004vAlmAdddropClient6East OBJECT-TYPE
	  SYNTAX EkiOnOff
	  MAX-ACCESS read-only
	  STATUS current
	  DESCRIPTION
        "
        Client East Rx Side Active :This
        OID indicates the Client is active
        on East receiving side <Condtype>
        ADDDROP_CLIENT6_EAST <Probcause>
        other (1) <Alarmtype> other (1)
        <Polarity> (2)
        "
	  ::= { pm1004vAlmclientRxProt 14 }



pm1004vAlmAdddropClient5East OBJECT-TYPE
	  SYNTAX EkiOnOff
	  MAX-ACCESS read-only
	  STATUS current
	  DESCRIPTION
        "
        Client East Rx Side Active :This
        OID indicates the Client is active
        on East receiving side <Condtype>
        ADDDROP_CLIENT5_EAST <Probcause>
        other (1) <Alarmtype> other (1)
        <Polarity> (2)
        "
	  ::= { pm1004vAlmclientRxProt 13 }



pm1004vAlmAdddropClient4East OBJECT-TYPE
	  SYNTAX EkiOnOff
	  MAX-ACCESS read-only
	  STATUS current
	  DESCRIPTION
        "
        Client East Rx Side Active :This
        OID indicates the Client is active
        on East receiving side <Condtype>
        ADDDROP_CLIENT4_EAST <Probcause>
        other (1) <Alarmtype> other (1)
        <Polarity> (2)
        "
	  ::= { pm1004vAlmclientRxProt 12 }



pm1004vAlmAdddropClient3East OBJECT-TYPE
	  SYNTAX EkiOnOff
	  MAX-ACCESS read-only
	  STATUS current
	  DESCRIPTION
        "
        Client East Rx Side Active :This
        OID indicates the Client is active
        on East receiving side <Condtype>
        ADDDROP_CLIENT3_EAST <Probcause>
        other (1) <Alarmtype> other (1)
        <Polarity> (2)
        "
	  ::= { pm1004vAlmclientRxProt 11 }



pm1004vAlmAdddropClient2East OBJECT-TYPE
	  SYNTAX EkiOnOff
	  MAX-ACCESS read-only
	  STATUS current
	  DESCRIPTION
        "
        Client East Rx Side Active :This
        OID indicates the Client is active
        on East receiving side <Condtype>
        ADDDROP_CLIENT2_EAST <Probcause>
        other (1) <Alarmtype> other (1)
        <Polarity> (2)
        "
	  ::= { pm1004vAlmclientRxProt 10 }



pm1004vAlmAdddropClient1East OBJECT-TYPE
	  SYNTAX EkiOnOff
	  MAX-ACCESS read-only
	  STATUS current
	  DESCRIPTION
        "
        Client East Rx Side Active :This
        OID indicates the Client is active
        on East receiving side <Condtype>
        ADDDROP_CLIENT1_EAST <Probcause>
        other (1) <Alarmtype> other (1)
        <Polarity> (2)
        "
	  ::= { pm1004vAlmclientRxProt 9 }



pm1004vAlmAdddropClient6West OBJECT-TYPE
	  SYNTAX EkiOnOff
	  MAX-ACCESS read-only
	  STATUS current
	  DESCRIPTION
        "
        Client West Rx Side Active :This
        OID indicates the Client is active
        on West receiving side <Condtype>
        ADDDROP_CLIENT6_WEST <Probcause>
        other (1) <Alarmtype> other (1)
        <Polarity> (2)
        "
	  ::= { pm1004vAlmclientRxProt 6 }



pm1004vAlmAdddropClient5West OBJECT-TYPE
	  SYNTAX EkiOnOff
	  MAX-ACCESS read-only
	  STATUS current
	  DESCRIPTION
        "
        Client West Rx Side Active :This
        OID indicates the Client is active
        on West receiving side <Condtype>
        ADDDROP_CLIENT5_WEST <Probcause>
        other (1) <Alarmtype> other (1)
        <Polarity> (2)
        "
	  ::= { pm1004vAlmclientRxProt 5 }



pm1004vAlmAdddropClient4West OBJECT-TYPE
	  SYNTAX EkiOnOff
	  MAX-ACCESS read-only
	  STATUS current
	  DESCRIPTION
        "
        Client West Rx Side Active :This
        OID indicates the Client is active
        on West receiving side <Condtype>
        ADDDROP_CLIENT4_WEST <Probcause>
        other (1) <Alarmtype> other (1)
        <Polarity> (2)
        "
	  ::= { pm1004vAlmclientRxProt 4 }



pm1004vAlmAdddropClient3West OBJECT-TYPE
	  SYNTAX EkiOnOff
	  MAX-ACCESS read-only
	  STATUS current
	  DESCRIPTION
        "
        Client West Rx Side Active :This
        OID indicates the Client is active
        on West receiving side <Condtype>
        ADDDROP_CLIENT3_WEST <Probcause>
        other (1) <Alarmtype> other (1)
        <Polarity> (2)
        "
	  ::= { pm1004vAlmclientRxProt 3 }



pm1004vAlmAdddropClient2West OBJECT-TYPE
	  SYNTAX EkiOnOff
	  MAX-ACCESS read-only
	  STATUS current
	  DESCRIPTION
        "
        Client West Rx Side Active :This
        OID indicates the Client is active
        on West receiving side <Condtype>
        ADDDROP_CLIENT2_WEST <Probcause>
        other (1) <Alarmtype> other (1)
        <Polarity> (2)
        "
	  ::= { pm1004vAlmclientRxProt 2 }



pm1004vAlmAdddropClient1West OBJECT-TYPE
	  SYNTAX EkiOnOff
	  MAX-ACCESS read-only
	  STATUS current
	  DESCRIPTION
        "
        Client West Rx Side Active :This
        OID indicates the Client is active
        on West receiving side <Condtype>
        ADDDROP_CLIENT1_WEST <Probcause>
        other (1) <Alarmtype> other (1)
        <Polarity> (2)
        "
	  ::= { pm1004vAlmclientRxProt 1 }



--- *********************************************************
---     TABLE for the pm1004vAlmlineXfp1Alarm articles
--- *********************************************************

pm1004vAlmlineXfp1AlarmTable OBJECT-TYPE
	SYNTAX  SEQUENCE OF Pm1004vAlmlineXfp1AlarmEntry
	MAX-ACCESS not-accessible
	STATUS current
	DESCRIPTION
        "
        List of pm1004vAlmlineXfp1Alarm
        Article
        "
	::= { pm1004vAlmLineUrg 208 }


pm1004vAlmlineXfp1AlarmEntry OBJECT-TYPE
	SYNTAX Pm1004vAlmlineXfp1AlarmEntry
	MAX-ACCESS not-accessible
	STATUS current
	DESCRIPTION
        "
        Row definition for the pm1004vAlmlineXfp1Alarm
        table
        "
	INDEX   { pm1004vAlmlineXfp1AlarmIndex }
	::= { pm1004vAlmlineXfp1AlarmTable 1 }


Pm1004vAlmlineXfp1AlarmEntry ::=
	SEQUENCE {
	pm1004vAlmlineXfp1AlarmIndex
		INTEGER,
	pm1004vAlmRxPowerHighAlarmPortn
		EkiOnOff,
	pm1004vAlmRxPowerLowAlarmPortn
		EkiOnOff,
	pm1004vAlmTempHighAlarmPortn
		EkiOnOff,
	pm1004vAlmTempLowAlarmPortn
		EkiOnOff,
	pm1004vAlmTxBiasHighAlarmPortn
		EkiOnOff,
	pm1004vAlmTxBiasLowAlarmPortn
		EkiOnOff,
	pm1004vAlmTxPowerHighAlarmPortn
		EkiOnOff,
	pm1004vAlmTxPowerLowAlarmPortn
		EkiOnOff
	}


pm1004vAlmlineXfp1AlarmIndex OBJECT-TYPE
	SYNTAX  INTEGER(0..128)
	MAX-ACCESS  read-only
	STATUS current
	DESCRIPTION
        "
        Index definition for the pm1004vAlmlineXfp1Alarm
        table
        "
	::= { pm1004vAlmlineXfp1AlarmEntry 1 }


pm1004vAlmRxPowerHighAlarmPortn OBJECT-TYPE
	SYNTAX  EkiOnOff
	MAX-ACCESS read-only
	STATUS current
	DESCRIPTION
        "
        Line Optical Rx Power High :Alarm
        indicating that the XFP received
        optical power is higher than the
        threshold value written in the
         XFP EEPROM <Condtype> RX_POWER_HIGH_ALARM_1
        <Probcause> receiveFailure (41)
        <Alarmtype> equipmentAlarm (5)
         <Polarity> (2)
        "
	::= { pm1004vAlmlineXfp1AlarmEntry 17 }


pm1004vAlmRxPowerLowAlarmPortn OBJECT-TYPE
	SYNTAX  EkiOnOff
	MAX-ACCESS read-only
	STATUS current
	DESCRIPTION
        "
        Line Optical Rx Power Low :Alarm
        indicating that the XFP received
        optical power is lower than the
        threshold value written in the
         XFP EEPROM  <Condtype> RX_POWER_LOW_ALARM_1
        <Probcause> receiveFailure (41)
        <Alarmtype> equipmentAlarm (5)
         <Polarity> (2)
        "
	::= { pm1004vAlmlineXfp1AlarmEntry 16 }


pm1004vAlmTempHighAlarmPortn OBJECT-TYPE
	SYNTAX  EkiOnOff
	MAX-ACCESS read-only
	STATUS current
	DESCRIPTION
        "
        Line Transceiver Temp High :Alarm
        indicating that the XFP/OTX temperature
        is higher than the threshold value
        written in the XFP EEPROM <Condtype>
        TEMP_HIGH_ALARM_1 <Probcause> temperatureUnacceptable
        (51) <Alarmtype> equipmentAlarm
        (5) <Polarity> (2)
        "
	::= { pm1004vAlmlineXfp1AlarmEntry 9 }


pm1004vAlmTempLowAlarmPortn OBJECT-TYPE
	SYNTAX  EkiOnOff
	MAX-ACCESS read-only
	STATUS current
	DESCRIPTION
        "
        Line Transceiver Temp Low :Alarm
        indicating that the XFP/OTX temperature
        is lower than the threshold value
        written in the XFP/OTX EEPROM <Condtype>
        TEMP_LOW_ALARM_1 <Probcause> temperatureUnacceptable
        (51) <Alarmtype> equipmentAlarm
        (5) <Polarity> (2)
        "
	::= { pm1004vAlmlineXfp1AlarmEntry 8 }


pm1004vAlmTxBiasHighAlarmPortn OBJECT-TYPE
	SYNTAX  EkiOnOff
	MAX-ACCESS read-only
	STATUS current
	DESCRIPTION
        "
        Line Transceiver Bias High :Alarm
        indicating that the XFP/OTX transmitter
        laser bias current is higher than
        the threshold value written in
         the XFP EEPROM <Condtype> TX_BIAS_HIGH_ALARM_1
        <Probcause> transmitterFailure
         (56) <Alarmtype> equipmentAlarm
        (5) <Polarity> (2)
        "
	::= { pm1004vAlmlineXfp1AlarmEntry 5 }


pm1004vAlmTxBiasLowAlarmPortn OBJECT-TYPE
	SYNTAX  EkiOnOff
	MAX-ACCESS read-only
	STATUS current
	DESCRIPTION
        "
        Line Transceiver Bias Low :Alarm
        indicating that the XFP/OTX transmitter
        laser bias current is lower than
        the threshold value written in
         the XFP/OTX EEPROM <Condtype>
         TX_BIAS_LOW_ALARM_1 <Probcause>
        transmitterFailure (56) <Alarmtype>
        equipmentAlarm (5) <Polarity> (2)
        "
	::= { pm1004vAlmlineXfp1AlarmEntry 4 }


pm1004vAlmTxPowerHighAlarmPortn OBJECT-TYPE
	SYNTAX  EkiOnOff
	MAX-ACCESS read-only
	STATUS current
	DESCRIPTION
        "
        Line Optical Tx Power High :Alarm
        indicating that the XFP/OTX transmitter
        transmitter output power is higher
        than the threshold value written
        in the XFP EEPROM <Condtype> TX_POWER_HIGH_ALARM_1
        <Probcause> transmitterFailure
         (56) <Alarmtype> equipmentAlarm
        (5) <Polarity> (2)
        "
	::= { pm1004vAlmlineXfp1AlarmEntry 3 }


pm1004vAlmTxPowerLowAlarmPortn OBJECT-TYPE
	SYNTAX  EkiOnOff
	MAX-ACCESS read-only
	STATUS current
	DESCRIPTION
        "
        Line Optical Tx Power Low :Alarm
        indicating that the XFP/OTX transmitter
        transmitter output power is lower
        than the threshold value written
        in the XFP/OTX EEPROM <Condtype>
        TX_POWER_LOW_ALARM_1 <Probcause>
        transmitterFailure (56) <Alarmtype>
        equipmentAlarm (5) <Polarity> (2)
        "
	::= { pm1004vAlmlineXfp1AlarmEntry 2 }


--- *********************************************************
---     TABLE for the pm1004vAlmlineXfp1Warnings articles
--- *********************************************************

pm1004vAlmlineXfp1WarningsTable OBJECT-TYPE
	SYNTAX  SEQUENCE OF Pm1004vAlmlineXfp1WarningsEntry
	MAX-ACCESS not-accessible
	STATUS current
	DESCRIPTION
        "
        List of pm1004vAlmlineXfp1Warnings
        Article
        "
	::= { pm1004vAlmLineNurg 209 }


pm1004vAlmlineXfp1WarningsEntry OBJECT-TYPE
	SYNTAX Pm1004vAlmlineXfp1WarningsEntry
	MAX-ACCESS not-accessible
	STATUS current
	DESCRIPTION
        "
        Row definition for the pm1004vAlmlineXfp1Warnings
        table
        "
	INDEX   { pm1004vAlmlineXfp1WarningsIndex }
	::= { pm1004vAlmlineXfp1WarningsTable 1 }


Pm1004vAlmlineXfp1WarningsEntry ::=
	SEQUENCE {
	pm1004vAlmlineXfp1WarningsIndex
		INTEGER,
	pm1004vAlmRxPowerHighWarningPortn
		EkiOnOff,
	pm1004vAlmRxPowerLowWarningPortn
		EkiOnOff,
	pm1004vAlmTempHighWarningPortn
		EkiOnOff,
	pm1004vAlmTempLowWarningPortn
		EkiOnOff,
	pm1004vAlmTxBiasHighWarningPortn
		EkiOnOff,
	pm1004vAlmTxBiasLowWarningPortn
		EkiOnOff,
	pm1004vAlmTxPowerHighWarningPortn
		EkiOnOff,
	pm1004vAlmTxPowerLowWarningPortn
		EkiOnOff
	}


pm1004vAlmlineXfp1WarningsIndex OBJECT-TYPE
	SYNTAX  INTEGER(0..128)
	MAX-ACCESS  read-only
	STATUS current
	DESCRIPTION
        "
        Index definition for the pm1004vAlmlineXfp1Warnings
        table
        "
	::= { pm1004vAlmlineXfp1WarningsEntry 1 }


pm1004vAlmRxPowerHighWarningPortn OBJECT-TYPE
	SYNTAX  EkiOnOff
	MAX-ACCESS read-only
	STATUS current
	DESCRIPTION
        "
        Line Optical Rx Power High Warning
        :Warning indicating that the XFP
        received optical power is higher
        than the threshold value written
        in the XFP EEPROM <Condtype> RX_POWER_HIGH_WARNING_1
        <Probcause> receiveFailure (41)
        <Alarmtype> equipmentAlarm (5)
         <Polarity> (2)
        "
	::= { pm1004vAlmlineXfp1WarningsEntry 17 }


pm1004vAlmRxPowerLowWarningPortn OBJECT-TYPE
	SYNTAX  EkiOnOff
	MAX-ACCESS read-only
	STATUS current
	DESCRIPTION
        "
        Line Optical Rx Power Low Warning
        :Warning indicating that the XFP
        received optical power is lower
        than the threshold value written
        in the XFP EEPROM  <Condtype> RX_POWER_LOW_WARNING_1
        <Probcause> receiveFailure (41)
        <Alarmtype> equipmentAlarm (5)
         <Polarity> (2)
        "
	::= { pm1004vAlmlineXfp1WarningsEntry 16 }


pm1004vAlmTempHighWarningPortn OBJECT-TYPE
	SYNTAX  EkiOnOff
	MAX-ACCESS read-only
	STATUS current
	DESCRIPTION
        "
        Line Transceiver Temp High Warning
        :Warning indicating that the XFP/OTX
        temperature is higher than the
         threshold value written in the
        XFP EEPROM <Condtype> TEMP_HIGH_WARNING_1
        <Probcause> temperatureUnacceptable
        (51) <Alarmtype> equipmentAlarm
        (5) <Polarity> (2)
        "
	::= { pm1004vAlmlineXfp1WarningsEntry 9 }


pm1004vAlmTempLowWarningPortn OBJECT-TYPE
	SYNTAX  EkiOnOff
	MAX-ACCESS read-only
	STATUS current
	DESCRIPTION
        "
        Line Transceiver Temp Low Warning
        :Warning indicating that the XFP/OTX
        temperature is lower than the threshold
        value written in the XFP/OTX EEPROM
        <Condtype> TEMP_LOW_WARNING_1 <Probcause>
        temperatureUnacceptable (51) <Alarmtype>
        equipmentAlarm (5) <Polarity> (2)
        "
	::= { pm1004vAlmlineXfp1WarningsEntry 8 }


pm1004vAlmTxBiasHighWarningPortn OBJECT-TYPE
	SYNTAX  EkiOnOff
	MAX-ACCESS read-only
	STATUS current
	DESCRIPTION
        "
        Line Transceiver Bias High Warning
        :Warning indicating that the XFP/OTX
        transmitter laser bias current
         is higher than the threshold value
        written in the XFP EEPROM <Condtype>
        TX_BIAS_HIGH_WARNING_1 <Probcause>
        transmitterFailure (56) <Alarmtype>
        equipmentAlarm (5) <Polarity> (2)
        "
	::= { pm1004vAlmlineXfp1WarningsEntry 5 }


pm1004vAlmTxBiasLowWarningPortn OBJECT-TYPE
	SYNTAX  EkiOnOff
	MAX-ACCESS read-only
	STATUS current
	DESCRIPTION
        "
        Line Transceiver Bias Low Warning
        :Warning indicating that the XFP/OTX
        transmitter laser bias current
         is lower than the threshold value
        written in the XFP/OTX EEPROM <Condtype>
        TX_BIAS_LOW_WARNING_1 <Probcause>
        transmitterFailure (56) <Alarmtype>
        equipmentAlarm (5) <Polarity> (2)
        "
	::= { pm1004vAlmlineXfp1WarningsEntry 4 }


pm1004vAlmTxPowerHighWarningPortn OBJECT-TYPE
	SYNTAX  EkiOnOff
	MAX-ACCESS read-only
	STATUS current
	DESCRIPTION
        "
        Line Optical Tx Power High Warning
        :Warning indicating that the XFP/OTX
        transmitter transmitter output
         power is higher than the threshold
        value written in the XFP EEPROM
        <Condtype> TX_POWER_HIGH_WARNING_1
        <Probcause> transmitterFailure
         (56) <Alarmtype> equipmentAlarm
        (5) <Polarity> (2)
        "
	::= { pm1004vAlmlineXfp1WarningsEntry 3 }


pm1004vAlmTxPowerLowWarningPortn OBJECT-TYPE
	SYNTAX  EkiOnOff
	MAX-ACCESS read-only
	STATUS current
	DESCRIPTION
        "
        Line Optical Tx Power Low Warning
        :Warning indicating that the XFP/OTX
        transmitter transmitter output
         power is lower than the threshold
        value written in the XFP/OTX EEPROM
        <Condtype> TX_POWER_LOW_WARNING_1
        <Probcause> transmitterFailure
         (56) <Alarmtype> equipmentAlarm
        (5) <Polarity> (2)
        "
	::= { pm1004vAlmlineXfp1WarningsEntry 2 }


--- *********************************************************
---     TABLE for the pm1004vAlmlineXfp1Crit articles
--- *********************************************************

pm1004vAlmlineXfp1CritTable OBJECT-TYPE
	SYNTAX  SEQUENCE OF Pm1004vAlmlineXfp1CritEntry
	MAX-ACCESS not-accessible
	STATUS current
	DESCRIPTION
        "
        List of pm1004vAlmlineXfp1Crit
        Article
        "
	::= { pm1004vAlmLineUrg 210 }


pm1004vAlmlineXfp1CritEntry OBJECT-TYPE
	SYNTAX Pm1004vAlmlineXfp1CritEntry
	MAX-ACCESS not-accessible
	STATUS current
	DESCRIPTION
        "
        Row definition for the pm1004vAlmlineXfp1Crit
        table
        "
	INDEX   { pm1004vAlmlineXfp1CritIndex }
	::= { pm1004vAlmlineXfp1CritTable 1 }


Pm1004vAlmlineXfp1CritEntry ::=
	SEQUENCE {
	pm1004vAlmlineXfp1CritIndex
		INTEGER,
	pm1004vAlmRxPowerHighCritPortn
		EkiOnOff,
	pm1004vAlmRxPowerLowCritPortn
		EkiOnOff,
	pm1004vAlmTxPowerHighCritPortn
		EkiOnOff,
	pm1004vAlmTxPowerLowCritPortn
		EkiOnOff
	}


pm1004vAlmlineXfp1CritIndex OBJECT-TYPE
	SYNTAX  INTEGER(0..128)
	MAX-ACCESS  read-only
	STATUS current
	DESCRIPTION
        "
        Index definition for the pm1004vAlmlineXfp1Crit
        table
        "
	::= { pm1004vAlmlineXfp1CritEntry 1 }


pm1004vAlmRxPowerHighCritPortn OBJECT-TYPE
	SYNTAX  EkiOnOff
	MAX-ACCESS read-only
	STATUS current
	DESCRIPTION
        "
        Line Custom Rx Power High :Custom
        Alarm indicating that the XFP/OTX
        input power of port is higher than
        the custom threshold defined in
        configuration  <Help>  Custom Alarm
        indicating that the XFP/OTX input
        power of port is higher than the
        custom threshold defined in custom
        configuration <Condtype> RX_POWER_HIGH_CRIT_1
        <Probcause> receiveFailure (41)
        <Alarmtype> equipmentAlarm (5)
         <Polarity> (2)
        "
	::= { pm1004vAlmlineXfp1CritEntry 17 }


pm1004vAlmRxPowerLowCritPortn OBJECT-TYPE
	SYNTAX  EkiOnOff
	MAX-ACCESS read-only
	STATUS current
	DESCRIPTION
        "
        Line Custom Rx Power Low :Custom
        Alarm indicating that the XFP/OTX
        input power of port is lower than
        the custom threshold defined in
        configuration  <Help>  Custom Alarm
        indicating that the XFP/OTX input
        power of port is lower than the
        custom threshold defined in custom
        configuration <Condtype> RX_POWER_LOW_CRIT_1
        <Probcause> receiveFailure (41)
        <Alarmtype> equipmentAlarm (5)
         <Polarity> (2)
        "
	::= { pm1004vAlmlineXfp1CritEntry 16 }


pm1004vAlmTxPowerHighCritPortn OBJECT-TYPE
	SYNTAX  EkiOnOff
	MAX-ACCESS read-only
	STATUS current
	DESCRIPTION
        "
        Line Custom Tx Power High :Custom
        Alarm indicating that the XFP/OTX
        output power of port is higher
         than the custom threshold defined
        in configuration  <Help>  Custom
        Alarm indicating that the XFP/OTX
        output power of port is higher
         than the custom threshold defined
        in custom configuration <Condtype>
        TX_POWER_HIGH_CRIT_1 <Probcause>
        transmitterFailure (56) <Alarmtype>
        equipmentAlarm (5) <Polarity> (2)
        "
	::= { pm1004vAlmlineXfp1CritEntry 3 }


pm1004vAlmTxPowerLowCritPortn OBJECT-TYPE
	SYNTAX  EkiOnOff
	MAX-ACCESS read-only
	STATUS current
	DESCRIPTION
        "
        Line Custom Tx Power Low :Custom
        Alarm indicating that the XFP/OTX
        output power of port is lower than
        the custom threshold defined in
        configuration  <Help>  Custom Alarm
        indicating that the XFP/OTX output
        power of port is lower than the
        custom threshold defined in custom
        configuration <Condtype> TX_POWER_LOW_CRIT_1
        <Probcause> transmitterFailure
         (56) <Alarmtype> equipmentAlarm
        (5) <Polarity> (2)
        "
	::= { pm1004vAlmlineXfp1CritEntry 2 }


--- *********************************************************
---     TABLE for the pm1004vAlmlineXfp1Alarms articles
--- *********************************************************

pm1004vAlmlineXfp1AlarmsTable OBJECT-TYPE
	SYNTAX  SEQUENCE OF Pm1004vAlmlineXfp1AlarmsEntry
	MAX-ACCESS not-accessible
	STATUS current
	DESCRIPTION
        "
        List of pm1004vAlmlineXfp1Alarms
        Article
        "
	::= { pm1004vAlmLineCrit 211 }


pm1004vAlmlineXfp1AlarmsEntry OBJECT-TYPE
	SYNTAX Pm1004vAlmlineXfp1AlarmsEntry
	MAX-ACCESS not-accessible
	STATUS current
	DESCRIPTION
        "
        Row definition for the pm1004vAlmlineXfp1Alarms
        table
        "
	INDEX   { pm1004vAlmlineXfp1AlarmsIndex }
	::= { pm1004vAlmlineXfp1AlarmsTable 1 }


Pm1004vAlmlineXfp1AlarmsEntry ::=
	SEQUENCE {
	pm1004vAlmlineXfp1AlarmsIndex
		INTEGER,
	pm1004vAlmApdSupplyFaultPortn
		EkiOnOff,
	pm1004vAlmTecFaultPortn
		EkiOnOff,
	pm1004vAlmWavelengthUnlockedPortn
		EkiOnOff,
	pm1004vAlmTxNrPortn
		EkiOnOff,
	pm1004vAlmTxFaultPortn
		EkiOnOff,
	pm1004vAlmTxCdrNotLockedPortn
		EkiOnOff,
	pm1004vAlmRxNrPortn
		EkiOnOff,
	pm1004vAlmRxCdrNotLockedPortn
		EkiOnOff,
	pm1004vAlmModNrPortn
		EkiOnOff
	}


pm1004vAlmlineXfp1AlarmsIndex OBJECT-TYPE
	SYNTAX  INTEGER(0..128)
	MAX-ACCESS  read-only
	STATUS current
	DESCRIPTION
        "
        Index definition for the pm1004vAlmlineXfp1Alarms
        table
        "
	::= { pm1004vAlmlineXfp1AlarmsEntry 1 }


pm1004vAlmApdSupplyFaultPortn OBJECT-TYPE
	SYNTAX  EkiOnOff
	MAX-ACCESS read-only
	STATUS current
	DESCRIPTION
        "
        Line Rx Photodiode Power Failed
        :This OID indicates a failure on
        the APD power supply  <Help>  This
        alarm indicates if the APD power
        supply is in fail condition <Condtype>
        APD_SUPPLY_FAULT_1 <Probcause>
         receiverFailure (42) <Alarmtype>
        equipmentAlarm (5) <Polarity> (2)
        "
	::= { pm1004vAlmlineXfp1AlarmsEntry 17 }


pm1004vAlmTecFaultPortn OBJECT-TYPE
	SYNTAX  EkiOnOff
	MAX-ACCESS read-only
	STATUS current
	DESCRIPTION
        "
        Line Optical Tx Temp Regul Failed
        :This OID indicates a failure on
        the TEC module  <Help>  This alarm
        indicates if the TEC of the line
        transceiver is in fail condition
        <Condtype> TEC_FAULT_1 <Probcause>
        transmitterFailure (56) <Alarmtype>
        equipmentAlarm (5) <Polarity> (2)
        "
	::= { pm1004vAlmlineXfp1AlarmsEntry 16 }


pm1004vAlmWavelengthUnlockedPortn OBJECT-TYPE
	SYNTAX  EkiOnOff
	MAX-ACCESS read-only
	STATUS current
	DESCRIPTION
        "
        Line Optical Tx Wavelength Unlocked
        :This OID indicates that the wavelength
        error is exceeding the manufacturer
        tolerance  <Help>  This alarm indicates
        if the wavelenght of the line transceiver
        is locked <Condtype> WAVELENGTH_UNLOCKED_1
        <Probcause> transmitterFailure
         (56) <Alarmtype> equipmentAlarm
        (5) <Polarity> (2)
        "
	::= { pm1004vAlmlineXfp1AlarmsEntry 15 }


pm1004vAlmTxNrPortn OBJECT-TYPE
	SYNTAX  EkiOnOff
	MAX-ACCESS read-only
	STATUS current
	DESCRIPTION
        "
        Line Optical Tx Not Ready :This
        OID indicates a condition has arisen
        leading to invalid data on the
         transmitting side  <Help>  This
        alarm indicates if the Tx part
         of the line transceiver is ready
        <Condtype> TX_NR_1 <Probcause>
         transmitterFailure (56) <Alarmtype>
        equipmentAlarm (5) <Polarity> (2)
        "
	::= { pm1004vAlmlineXfp1AlarmsEntry 9 }


pm1004vAlmTxFaultPortn OBJECT-TYPE
	SYNTAX  EkiOnOff
	MAX-ACCESS read-only
	STATUS current
	DESCRIPTION
        "
        Line Optical Tx Failure :This
         OID indicates a fault condition
        on the laser detected by the safety
        syste  <Help>  This alarm indicates
        if the laser of the line transceiver
        is in fail condition <Condtype>
        TX_FAULT_1 <Probcause> transmitterFailure
        (56) <Alarmtype> equipmentAlarm
        (5) <Polarity> (2)
        "
	::= { pm1004vAlmlineXfp1AlarmsEntry 8 }


pm1004vAlmTxCdrNotLockedPortn OBJECT-TYPE
	SYNTAX  EkiOnOff
	MAX-ACCESS read-only
	STATUS current
	DESCRIPTION
        "
        Line Optical Tx CDR Unlocked :This
        OID indicates a loss of lock on
        the transmitting side CDR has been
        detected.  <Help>  This alarm indicates
        if the Tx CDR is locked in the
         line transceiver <Condtype> TX_CDR_NOT_LOCKED1_1
        <Probcause> transmitterFailure
         (56) <Alarmtype> equipmentAlarm
        (5) <Polarity> (2)
        "
	::= { pm1004vAlmlineXfp1AlarmsEntry 7 }


pm1004vAlmRxNrPortn OBJECT-TYPE
	SYNTAX  EkiOnOff
	MAX-ACCESS read-only
	STATUS current
	DESCRIPTION
        "
        Line Optical Rx Not Ready :This
        OID indicates that a condition
         has arisen leading to invalid
         data on the receiving side.  <Help>
         This alarm indicates if the Rx
        part of the line transceiver is
        ready <Condtype> RX_NR_1 <Probcause>
        receiveFailure (41) <Alarmtype>
        equipmentAlarm (5) <Polarity> (2)
        "
	::= { pm1004vAlmlineXfp1AlarmsEntry 6 }


pm1004vAlmRxCdrNotLockedPortn OBJECT-TYPE
	SYNTAX  EkiOnOff
	MAX-ACCESS read-only
	STATUS current
	DESCRIPTION
        "
        Line Optical Rx CDR Unlocked :This
        OID indicates that a loss of lock
        on the receiving side CDR has been
        detected  <Help>  This alarm indicates
        if the Rx CDR is locked in the
         line transceiver <Condtype> RX_CDR_NOT_LOCKED1_1
        <Probcause> receiveFailure (41)
        <Alarmtype> equipmentAlarm (5)
         <Polarity> (2)
        "
	::= { pm1004vAlmlineXfp1AlarmsEntry 4 }


pm1004vAlmModNrPortn OBJECT-TYPE
	SYNTAX  EkiOnOff
	MAX-ACCESS read-only
	STATUS current
	DESCRIPTION
        "
        Line Optical Module Not Ready
         :This OID indicates that the module
        is unable to determine correct
         data.  <Help>  This alarm indicates
        if the line transceiver is ready
        <Condtype> MOD_NR_1 <Probcause>
        receiveFailure (41) <Alarmtype>
        equipmentAlarm (5) <Polarity> (2)
        "
	::= { pm1004vAlmlineXfp1AlarmsEntry 3 }


--- *********************************************************
---     TABLE for the pm1004vAlmlineXfp1SupplyAlarm articles
--- *********************************************************

pm1004vAlmlineXfp1SupplyAlarmTable OBJECT-TYPE
	SYNTAX  SEQUENCE OF Pm1004vAlmlineXfp1SupplyAlarmEntry
	MAX-ACCESS not-accessible
	STATUS current
	DESCRIPTION
        "
        List of pm1004vAlmlineXfp1SupplyAlarm
        Article
        "
	::= { pm1004vAlmLineUrg 212 }


pm1004vAlmlineXfp1SupplyAlarmEntry OBJECT-TYPE
	SYNTAX Pm1004vAlmlineXfp1SupplyAlarmEntry
	MAX-ACCESS not-accessible
	STATUS current
	DESCRIPTION
        "
        Row definition for the pm1004vAlmlineXfp1SupplyAlarm
        table
        "
	INDEX   { pm1004vAlmlineXfp1SupplyAlarmIndex }
	::= { pm1004vAlmlineXfp1SupplyAlarmTable 1 }


Pm1004vAlmlineXfp1SupplyAlarmEntry ::=
	SEQUENCE {
	pm1004vAlmlineXfp1SupplyAlarmIndex
		INTEGER,
	pm1004vAlmVcc5HighWarningPortn
		EkiOnOff,
	pm1004vAlmVcc5LowWarningPortn
		EkiOnOff,
	pm1004vAlmVcc3HighWarningPortn
		EkiOnOff,
	pm1004vAlmVcc3LowWarningPortn
		EkiOnOff,
	pm1004vAlmVcc2HighWarningPortn
		EkiOnOff,
	pm1004vAlmVcc2LowWarningPortn
		EkiOnOff,
	pm1004vAlmVee5HighWarningPortn
		EkiOnOff,
	pm1004vAlmVee5LowWarningPortn
		EkiOnOff,
	pm1004vAlmVcc5HighAlarmPortn
		EkiOnOff,
	pm1004vAlmVcc5LowAlarmPortn
		EkiOnOff,
	pm1004vAlmVcc3HighAlarmPortn
		EkiOnOff,
	pm1004vAlmVcc3LowAlarmPortn
		EkiOnOff,
	pm1004vAlmVcc2HighAlarmPortn
		EkiOnOff,
	pm1004vAlmVcc2LowAlarmPortn
		EkiOnOff,
	pm1004vAlmVee5HighAlarmPortn
		EkiOnOff,
	pm1004vAlmVee5LowAlarmPortn
		EkiOnOff
	}


pm1004vAlmlineXfp1SupplyAlarmIndex OBJECT-TYPE
	SYNTAX  INTEGER(0..128)
	MAX-ACCESS  read-only
	STATUS current
	DESCRIPTION
        "
        Index definition for the pm1004vAlmlineXfp1SupplyAlarm
        table
        "
	::= { pm1004vAlmlineXfp1SupplyAlarmEntry 1 }


pm1004vAlmVcc5HighWarningPortn OBJECT-TYPE
	SYNTAX  EkiOnOff
	MAX-ACCESS read-only
	STATUS current
	DESCRIPTION
        "
        VCC5 Power Supply High Warning
        :Warning indicating the XFP/OTX
        VCC5 power supply is higher than
        the threshold written in the EEPROM
        <Condtype> VCC5_HIGH_WARNING_1
         <Probcause> powerProblem (36)
         <Alarmtype> equipmentAlarm (5)
        <Polarity> (2)
        "
	::= { pm1004vAlmlineXfp1SupplyAlarmEntry 17 }


pm1004vAlmVcc5LowWarningPortn OBJECT-TYPE
	SYNTAX  EkiOnOff
	MAX-ACCESS read-only
	STATUS current
	DESCRIPTION
        "
        VCC5 Power Supply Low Warning
         :Warning indicating the XFP/OTX
        VCC5 power supply is lower than
        the threshold written in the EEPROM
        <Condtype> VCC5_LOW_WARNING_1 <Probcause>
        powerProblem (36) <Alarmtype> equipmentAlarm
        (5) <Polarity> (2)
        "
	::= { pm1004vAlmlineXfp1SupplyAlarmEntry 16 }


pm1004vAlmVcc3HighWarningPortn OBJECT-TYPE
	SYNTAX  EkiOnOff
	MAX-ACCESS read-only
	STATUS current
	DESCRIPTION
        "
        VCC3 Power Supply High Warning
        :Warning indicating the XFP/OTX
        VCC3 power supply is higher than
        the threshold written in the EEPROM
        <Condtype> VCC3_HIGH_WARNING_1
         <Probcause> powerProblem (36)
         <Alarmtype> equipmentAlarm (5)
        <Polarity> (2)
        "
	::= { pm1004vAlmlineXfp1SupplyAlarmEntry 15 }


pm1004vAlmVcc3LowWarningPortn OBJECT-TYPE
	SYNTAX  EkiOnOff
	MAX-ACCESS read-only
	STATUS current
	DESCRIPTION
        "
        VCC3 Power Supply Low Warning
         :Warning indicating the XFP/OTX
        VCC3 power supply is lower than
        the threshold written in the EEPROM
        <Condtype> VCC3_LOW_WARNING_1 <Probcause>
        powerProblem (36) <Alarmtype> equipmentAlarm
        (5) <Polarity> (2)
        "
	::= { pm1004vAlmlineXfp1SupplyAlarmEntry 14 }


pm1004vAlmVcc2HighWarningPortn OBJECT-TYPE
	SYNTAX  EkiOnOff
	MAX-ACCESS read-only
	STATUS current
	DESCRIPTION
        "
        VCC2 Power Supply High Warning
        :Warning indicating the XFP/OTX
        VCC2 power supply is higher than
        the threshold written in the EEPROM
        <Condtype> VCC2_HIGH_WARNING_1
         <Probcause> powerProblem (36)
         <Alarmtype> equipmentAlarm (5)
        <Polarity> (2)
        "
	::= { pm1004vAlmlineXfp1SupplyAlarmEntry 13 }


pm1004vAlmVcc2LowWarningPortn OBJECT-TYPE
	SYNTAX  EkiOnOff
	MAX-ACCESS read-only
	STATUS current
	DESCRIPTION
        "
        VCC2 Power Supply Low Warning
         :Warning indicating the XFP/OTX
        VCC2 power supply is lower than
        the threshold written in the EEPROM
        <Condtype> VCC2_LOW_WARNING_1 <Probcause>
        powerProblem (36) <Alarmtype> equipmentAlarm
        (5) <Polarity> (2)
        "
	::= { pm1004vAlmlineXfp1SupplyAlarmEntry 12 }


pm1004vAlmVee5HighWarningPortn OBJECT-TYPE
	SYNTAX  EkiOnOff
	MAX-ACCESS read-only
	STATUS current
	DESCRIPTION
        "
        VEE5 Power Supply High Warning
        :Warning indicating the XFP/OTX
        VEE5 power supply is higher than
        the threshold written in the EEPROM
        <Condtype> VEE5_HIGH_WARNING_1
         <Probcause> powerProblem (36)
         <Alarmtype> equipmentAlarm (5)
        <Polarity> (2)
        "
	::= { pm1004vAlmlineXfp1SupplyAlarmEntry 11 }


pm1004vAlmVee5LowWarningPortn OBJECT-TYPE
	SYNTAX  EkiOnOff
	MAX-ACCESS read-only
	STATUS current
	DESCRIPTION
        "
        VEE5 Power Supply Low Warning
         :Warning indicating the XFP/OTX
        VEE5 power supply is lower than
        the threshold written in the EEPROM
        <Condtype> VEE5_LOW_WARNING_1 <Probcause>
        powerProblem (36) <Alarmtype> equipmentAlarm
        (5) <Polarity> (2)
        "
	::= { pm1004vAlmlineXfp1SupplyAlarmEntry 10 }


pm1004vAlmVcc5HighAlarmPortn OBJECT-TYPE
	SYNTAX  EkiOnOff
	MAX-ACCESS read-only
	STATUS current
	DESCRIPTION
        "
        VCC5 Power Supply High :Alarm
         indicating the XFP/OTX VCC5 power
        supply is higher than the threshold
        written in the EEPROM <Condtype>
        VCC5_HIGH_ALARM_1 <Probcause> powerProblem
        (36) <Alarmtype> equipmentAlarm
        (5) <Polarity> (2)
        "
	::= { pm1004vAlmlineXfp1SupplyAlarmEntry 9 }


pm1004vAlmVcc5LowAlarmPortn OBJECT-TYPE
	SYNTAX  EkiOnOff
	MAX-ACCESS read-only
	STATUS current
	DESCRIPTION
        "
        VCC5 Power Supply Low :Alarm indicating
        the XFP/OTX VCC5 power supply is
        lower than the threshold written
        in the EEPROM <Condtype> VCC5_LOW_ALARM_1
        <Probcause> powerProblem (36) <Alarmtype>
        equipmentAlarm (5) <Polarity> (2)
        "
	::= { pm1004vAlmlineXfp1SupplyAlarmEntry 8 }


pm1004vAlmVcc3HighAlarmPortn OBJECT-TYPE
	SYNTAX  EkiOnOff
	MAX-ACCESS read-only
	STATUS current
	DESCRIPTION
        "
        VCC3 Power Supply High :Alarm
         indicating the XFP/OTX VCC3 power
        supply is higher than the threshold
        written in the EEPROM <Condtype>
        VCC3_HIGH_ALARM_1 <Probcause> powerProblem
        (36) <Alarmtype> equipmentAlarm
        (5) <Polarity> (2)
        "
	::= { pm1004vAlmlineXfp1SupplyAlarmEntry 7 }


pm1004vAlmVcc3LowAlarmPortn OBJECT-TYPE
	SYNTAX  EkiOnOff
	MAX-ACCESS read-only
	STATUS current
	DESCRIPTION
        "
        VCC3 Power Supply Low :Alarm indicating
        the XFP/OTX VCC3 power supply is
        lower than the threshold written
        in the EEPROM <Condtype> VCC3_LOW_ALARM_1
        <Probcause> powerProblem (36) <Alarmtype>
        equipmentAlarm (5) <Polarity> (2)
        "
	::= { pm1004vAlmlineXfp1SupplyAlarmEntry 6 }


pm1004vAlmVcc2HighAlarmPortn OBJECT-TYPE
	SYNTAX  EkiOnOff
	MAX-ACCESS read-only
	STATUS current
	DESCRIPTION
        "
        VCC2 Power Supply High :Alarm
         indicating the XFP/OTX VCC2 power
        supply is higher than the threshold
        written in the EEPROM <Condtype>
        VCC2_HIGH_ALARM_1 <Probcause> powerProblem
        (36) <Alarmtype> equipmentAlarm
        (5) <Polarity> (2)
        "
	::= { pm1004vAlmlineXfp1SupplyAlarmEntry 5 }


pm1004vAlmVcc2LowAlarmPortn OBJECT-TYPE
	SYNTAX  EkiOnOff
	MAX-ACCESS read-only
	STATUS current
	DESCRIPTION
        "
        VCC2 Power Supply Low :Alarm indicating
        the XFP/OTX VCC2 power supply is
        lower than the threshold written
        in the EEPROM <Condtype> VCC2_LOW_ALARM_1
        <Probcause> powerProblem (36) <Alarmtype>
        equipmentAlarm (5) <Polarity> (2)
        "
	::= { pm1004vAlmlineXfp1SupplyAlarmEntry 4 }


pm1004vAlmVee5HighAlarmPortn OBJECT-TYPE
	SYNTAX  EkiOnOff
	MAX-ACCESS read-only
	STATUS current
	DESCRIPTION
        "
        VEE5 Power Supply High :Alarm
         indicating the XFP/OTX VEE5 power
        supply is higher than the threshold
        written in the EEPROM <Condtype>
        VEE5_HIGH_ALARM_1 <Probcause> powerProblem
        (36) <Alarmtype> equipmentAlarm
        (5) <Polarity> (2)
        "
	::= { pm1004vAlmlineXfp1SupplyAlarmEntry 3 }


pm1004vAlmVee5LowAlarmPortn OBJECT-TYPE
	SYNTAX  EkiOnOff
	MAX-ACCESS read-only
	STATUS current
	DESCRIPTION
        "
        VEE5 Power Supply Low :Alarm indicating
        the XFP/OTX VEE5 power supply is
        lower than the threshold written
        in the EEPROM <Condtype> VEE5_LOW_ALARM_1
        <Probcause> powerProblem (36) <Alarmtype>
        equipmentAlarm (5) <Polarity> (2)
        "
	::= { pm1004vAlmlineXfp1SupplyAlarmEntry 2 }


--- *********************************************************
---     TABLE for the pm1004vAlmlineOtx1TlhAlarms articles
--- *********************************************************

pm1004vAlmlineOtx1TlhAlarmsTable OBJECT-TYPE
	SYNTAX  SEQUENCE OF Pm1004vAlmlineOtx1TlhAlarmsEntry
	MAX-ACCESS not-accessible
	STATUS current
	DESCRIPTION
        "
        List of pm1004vAlmlineOtx1TlhAlarms
        Article
        "
	::= { pm1004vAlmLineUrg 224 }


pm1004vAlmlineOtx1TlhAlarmsEntry OBJECT-TYPE
	SYNTAX Pm1004vAlmlineOtx1TlhAlarmsEntry
	MAX-ACCESS not-accessible
	STATUS current
	DESCRIPTION
        "
        Row definition for the pm1004vAlmlineOtx1TlhAlarms
        table
        "
	INDEX   { pm1004vAlmlineOtx1TlhAlarmsIndex }
	::= { pm1004vAlmlineOtx1TlhAlarmsTable 1 }


Pm1004vAlmlineOtx1TlhAlarmsEntry ::=
	SEQUENCE {
	pm1004vAlmlineOtx1TlhAlarmsIndex
		INTEGER,
	pm1004vAlmLineLaserTempHighAlaPortn
		EkiOnOff,
	pm1004vAlmLineFreqDevHighAlaPortn
		EkiOnOff,
	pm1004vAlmLineAgingHighAlaPortn
		EkiOnOff,
	pm1004vAlmLineModulatorAgingHighAlaPortn
		EkiOnOff
	}


pm1004vAlmlineOtx1TlhAlarmsIndex OBJECT-TYPE
	SYNTAX  INTEGER(0..128)
	MAX-ACCESS  read-only
	STATUS current
	DESCRIPTION
        "
        Index definition for the pm1004vAlmlineOtx1TlhAlarms
        table
        "
	::= { pm1004vAlmlineOtx1TlhAlarmsEntry 1 }


pm1004vAlmLineLaserTempHighAlaPortn OBJECT-TYPE
	SYNTAX  EkiOnOff
	MAX-ACCESS read-only
	STATUS current
	DESCRIPTION
        "
        Line Laser Temp. High Alarm :Alarm
        indicating the Line OTX TLH laser
        temperature is higher than the
         threshold written in the EEPROM
        <Condtype> LINE_LASER_TEMP_HIGH_ALA_1
        <Probcause> temperatureUnacceptable
        (51) <Alarmtype> equipmentAlarm
        (5) <Polarity> (2)
        "
	::= { pm1004vAlmlineOtx1TlhAlarmsEntry 15 }


pm1004vAlmLineFreqDevHighAlaPortn OBJECT-TYPE
	SYNTAX  EkiOnOff
	MAX-ACCESS read-only
	STATUS current
	DESCRIPTION
        "
        Line Freq. Deviation High Alarm
        :Alarm indicating the Line OTX
         TLH frequency deviation is higher
        than the threshold written in the
        EEPROM <Condtype> LINE_FREQ_DEV_HIGH_ALA_1
        <Probcause> transmitterFailure
         (56) <Alarmtype> equipmentAlarm
        (5) <Polarity> (2)
        "
	::= { pm1004vAlmlineOtx1TlhAlarmsEntry 13 }


pm1004vAlmLineAgingHighAlaPortn OBJECT-TYPE
	SYNTAX  EkiOnOff
	MAX-ACCESS read-only
	STATUS current
	DESCRIPTION
        "
        Line OTX TLH Aging High Alarm
         :Alarm indicating the Line OTX
        TLH aging is higher than the threshold
        written in the EEPROM <Condtype>
        LINE_AGING_HIGH_ALA_1 <Probcause>
        transmitterFailure (56) <Alarmtype>
        equipmentAlarm (5) <Polarity> (2)
        "
	::= { pm1004vAlmlineOtx1TlhAlarmsEntry 7 }


pm1004vAlmLineModulatorAgingHighAlaPortn OBJECT-TYPE
	SYNTAX  EkiOnOff
	MAX-ACCESS read-only
	STATUS current
	DESCRIPTION
        "
        Line Modulator Aging High Alarm
        :Alarm indicating the Line OTX
         TLH modulator aging is higher
         than the threshold written in
         the EEPROM <Condtype> LINE_MODULATOR_AGING_HIGH_ALA_1
        <Probcause> transmitterFailure
         (56) <Alarmtype> equipmentAlarm
        (5) <Polarity> (2)
        "
	::= { pm1004vAlmlineOtx1TlhAlarmsEntry 6 }


--- *********************************************************
---     TABLE for the pm1004vAlmlineOtx1TlhWarnings articles
--- *********************************************************

pm1004vAlmlineOtx1TlhWarningsTable OBJECT-TYPE
	SYNTAX  SEQUENCE OF Pm1004vAlmlineOtx1TlhWarningsEntry
	MAX-ACCESS not-accessible
	STATUS current
	DESCRIPTION
        "
        List of pm1004vAlmlineOtx1TlhWarnings
        Article
        "
	::= { pm1004vAlmLineNurg 225 }


pm1004vAlmlineOtx1TlhWarningsEntry OBJECT-TYPE
	SYNTAX Pm1004vAlmlineOtx1TlhWarningsEntry
	MAX-ACCESS not-accessible
	STATUS current
	DESCRIPTION
        "
        Row definition for the pm1004vAlmlineOtx1TlhWarnings
        table
        "
	INDEX   { pm1004vAlmlineOtx1TlhWarningsIndex }
	::= { pm1004vAlmlineOtx1TlhWarningsTable 1 }


Pm1004vAlmlineOtx1TlhWarningsEntry ::=
	SEQUENCE {
	pm1004vAlmlineOtx1TlhWarningsIndex
		INTEGER,
	pm1004vAlmLineLaserTempHighWarningPortn
		EkiOnOff,
	pm1004vAlmLineFreqDevHighWarningPortn
		EkiOnOff,
	pm1004vAlmLineAgingHighWarningPortn
		EkiOnOff,
	pm1004vAlmLineModulatorAgingHighWarningPortn
		EkiOnOff
	}


pm1004vAlmlineOtx1TlhWarningsIndex OBJECT-TYPE
	SYNTAX  INTEGER(0..128)
	MAX-ACCESS  read-only
	STATUS current
	DESCRIPTION
        "
        Index definition for the pm1004vAlmlineOtx1TlhWarnings
        table
        "
	::= { pm1004vAlmlineOtx1TlhWarningsEntry 1 }


pm1004vAlmLineLaserTempHighWarningPortn OBJECT-TYPE
	SYNTAX  EkiOnOff
	MAX-ACCESS read-only
	STATUS current
	DESCRIPTION
        "
        Line Laser Temp. High Warning
         :Warning indicating the Line OTX
        TLH laser temperature is higher
        than the threshold written in the
        EEPROM <Condtype> LINE_LASER_TEMP_HIGH_WARNING_1
        <Probcause> temperatureUnacceptable
        (51) <Alarmtype> equipmentAlarm
        (5) <Polarity> (2)
        "
	::= { pm1004vAlmlineOtx1TlhWarningsEntry 15 }


pm1004vAlmLineFreqDevHighWarningPortn OBJECT-TYPE
	SYNTAX  EkiOnOff
	MAX-ACCESS read-only
	STATUS current
	DESCRIPTION
        "
        Line Freq. Deviation High Warning
        :Warning indicating the Line OTX
        TLH frequency deviation is higher
        than the threshold written in the
        EEPROM <Condtype> LINE_FREQ_DEV_HIGH_WARNING_1
        <Probcause> transmitterFailure
         (56) <Alarmtype> equipmentAlarm
        (5) <Polarity> (2)
        "
	::= { pm1004vAlmlineOtx1TlhWarningsEntry 13 }


pm1004vAlmLineAgingHighWarningPortn OBJECT-TYPE
	SYNTAX  EkiOnOff
	MAX-ACCESS read-only
	STATUS current
	DESCRIPTION
        "
        Line OTX TLH Aging High Warning
        :Warning indicating the Line OTX
        TLH aging is higher than the threshold
        written in the EEPROM <Condtype>
        LINE_AGING_HIGH_WARNING_1 <Probcause>
        transmitterFailure (56) <Alarmtype>
        equipmentAlarm (5) <Polarity> (2)
        "
	::= { pm1004vAlmlineOtx1TlhWarningsEntry 7 }


pm1004vAlmLineModulatorAgingHighWarningPortn OBJECT-TYPE
	SYNTAX  EkiOnOff
	MAX-ACCESS read-only
	STATUS current
	DESCRIPTION
        "
        Line Modulator Aging High Warning
        :Warning indicating the Line OTX
        TLH modulator aging is higher than
        the threshold written in the EEPROM
        <Condtype> LINE_MODULATOR_AGING_HIGH_WARNING_1
        <Probcause> transmitterFailure
         (56) <Alarmtype> equipmentAlarm
        (5) <Polarity> (2)
        "
	::= { pm1004vAlmlineOtx1TlhWarningsEntry 6 }







--- *****************************************************
--- $$$$$$$$$$$$$$$$$$$$$$$$$$$$$$$$$$$$$$$$$$$$$$$$$$$$$
---     CONTROLS
--- $$$$$$$$$$$$$$$$$$$$$$$$$$$$$$$$$$$$$$$$$$$$$$$$$$$$$
--- *****************************************************



--- *****************************************************
---     LEAF for the confMgnt1 article
--- *****************************************************
pm1004vCtrlconfMgnt1 OBJECT IDENTIFIER ::= { pm1004vCtrlOther 1 }




pm1004vCtrlConf2Clear1 OBJECT-TYPE
	  SYNTAX EkiOnOff
	  MAX-ACCESS read-write
	  STATUS current
	  DESCRIPTION
        "
        Clear Configuration Tables :This
        OID clears the configuration tables
        from configuration2 in the flash.
         <Help>  This control restores
         the default configuration of the
        module
        "
	  ::= { pm1004vCtrlconfMgnt1 14 }



pm1004vCtrlConf2Flash1 OBJECT-TYPE
	  SYNTAX EkiOnOff
	  MAX-ACCESS read-write
	  STATUS current
	  DESCRIPTION
        "
        Write Configuration Tables :This
        OID saves the current configuration
        of the PM as configuration2 in
         the flash.  <Help>  This control
        saves the customer configuration
        on the module
        "
	  ::= { pm1004vCtrlconfMgnt1 10 }



pm1004vCtrlConf2Load1 OBJECT-TYPE
	  SYNTAX EkiOnOff
	  MAX-ACCESS read-write
	  STATUS current
	  DESCRIPTION
        "
        Load Configuration Tables Set
         Nb 2 :When set this OID enables
        loading from flash configuration2
        into the PM.
        "
	  ::= { pm1004vCtrlconfMgnt1 2 }



pm1004vCtrlConf1Load1 OBJECT-TYPE
	  SYNTAX EkiOnOff
	  MAX-ACCESS read-write
	  STATUS current
	  DESCRIPTION
        "
        Load Configuration Tables Set
         Nb 1 :When set this OID enables
        loading from flash configuration1
        into the PM.
        "
	  ::= { pm1004vCtrlconfMgnt1 1 }



--- *****************************************************
---     LEAF for the synth4 article
--- *****************************************************
pm1004vCtrlsynth4 OBJECT IDENTIFIER ::= { pm1004vCtrlOther 4 }




pm1004vCtrlCorrelatOff OBJECT-TYPE
	  SYNTAX EkiOnOff
	  MAX-ACCESS read-write
	  STATUS current
	  DESCRIPTION
        "
        Disable Alarm Correlation :This
        OID disables the alarm correlation
        in the PM.
        "
	  ::= { pm1004vCtrlsynth4 2 }



pm1004vCtrlCorrelatOn OBJECT-TYPE
	  SYNTAX EkiOnOff
	  MAX-ACCESS read-write
	  STATUS current
	  DESCRIPTION
        "
        Enable Alarm Correlation :This
        OID enables the alarm correlation
        in the PM.
        "
	  ::= { pm1004vCtrlsynth4 1 }



--- *****************************************************
---     LEAF for the swMgnt article
--- *****************************************************
pm1004vCtrlswMgnt OBJECT IDENTIFIER ::= { pm1004vCtrlOther 5 }




pm1004vCtrlLoadSwBank2 OBJECT-TYPE
	  SYNTAX EkiOnOff
	  MAX-ACCESS read-write
	  STATUS current
	  DESCRIPTION
        "
        Set Software Nb 2 As Active :This
        OID, when set, loads the SW from
        bank2 into the PM. It must be followed
        by a reset.  <Help>  This controls
        selects the second SW bank as the
        active bank for the next module
        reset
        "
	  ::= { pm1004vCtrlswMgnt 6 }



pm1004vCtrlLoadSwBank1 OBJECT-TYPE
	  SYNTAX EkiOnOff
	  MAX-ACCESS read-write
	  STATUS current
	  DESCRIPTION
        "
        Set Software Nb 1 As Active :This
        OID, when set, loads the SW from
        bank1 into the PM. It must be followed
        by a reset.  <Help>  This controls
        selects the first SW bank as the
        active bank for the next module
        reset
        "
	  ::= { pm1004vCtrlswMgnt 5 }



pm1004vCtrlWarmReset OBJECT-TYPE
	  SYNTAX EkiOnOff
	  MAX-ACCESS read-write
	  STATUS current
	  DESCRIPTION
        "
        PM Warm Reset :This OID, when
         set, causes a warm reset of the
        PM. This reset is not traffic affecting,
        and the configuration of PM remains
        unchanged.  <Help>  This control
        initiates a warm reset of the module.
        "
	  ::= { pm1004vCtrlswMgnt 3 }



pm1004vCtrlColdReset OBJECT-TYPE
	  SYNTAX EkiOnOff
	  MAX-ACCESS read-write
	  STATUS current
	  DESCRIPTION
        "
        PM Cold Reset :This OID, when
         set, causes a cold reset of the
        PM. This reset is traffic affecting,
        and the configuration of PM is
         reloaded on start-up.  <Help>
          This control initiates a cold
        reset of the module.
        "
	  ::= { pm1004vCtrlswMgnt 2 }



--- *****************************************************
---     LEAF for the gwMgnt article
--- *****************************************************
pm1004vCtrlgwMgnt OBJECT IDENTIFIER ::= { pm1004vCtrlOther 6 }




pm1004vCtrlLoadGwBank4 OBJECT-TYPE
	  SYNTAX EkiOnOff
	  MAX-ACCESS read-write
	  STATUS current
	  DESCRIPTION
        "
        Set Gateware Nb 4 As Active :This
        OID, when set, loads the GW from
        bank4 (Flash) into the PM. It is
        followed by an automatic gateware
        cold reset.
        "
	  ::= { pm1004vCtrlgwMgnt 8 }



pm1004vCtrlLoadGwBank3 OBJECT-TYPE
	  SYNTAX EkiOnOff
	  MAX-ACCESS read-write
	  STATUS current
	  DESCRIPTION
        "
        Set Gateware Nb 3 As Active :This
        OID, when set, loads the GW from
        bank3 (Flash) into the PM. It is
        followed by an automatic gateware
        cold reset.  <Help>  This controls
        initiates a cold reset of the module
        and select the third GW bank as
        the active bank
        "
	  ::= { pm1004vCtrlgwMgnt 7 }



pm1004vCtrlLoadGwBank2 OBJECT-TYPE
	  SYNTAX EkiOnOff
	  MAX-ACCESS read-write
	  STATUS current
	  DESCRIPTION
        "
        Set Gateware Nb 2 As Active :This
        OID, when set, loads the GW from
        bank2 (Flash) into the PM. It is
        followed by an automatic gateware
        cold reset.
        "
	  ::= { pm1004vCtrlgwMgnt 6 }



pm1004vCtrlLoadGwBank1 OBJECT-TYPE
	  SYNTAX EkiOnOff
	  MAX-ACCESS read-write
	  STATUS current
	  DESCRIPTION
        "
        Set Gateware Nb 1 As Active :This
        OID, when set, loads the GW from
        bank1 (Flash) into the PM. It is
        followed by an automatic gateware
        cold reset.  <Help>  This controls
        initiates a cold reset of the module
        and select the first GW bank as
        the active bank
        "
	  ::= { pm1004vCtrlgwMgnt 5 }



pm1004vCtrlCurrentGwReset OBJECT-TYPE
	  SYNTAX EkiOnOff
	  MAX-ACCESS read-write
	  STATUS current
	  DESCRIPTION
        "
        Active Gateware Reset :This OID,
        when set, resets the active gateware.
        It is traffic affecting.
        "
	  ::= { pm1004vCtrlgwMgnt 1 }



--- *********************************************************
---     TABLE for the pm1004vCtrlaccessLoop articles
--- *********************************************************

pm1004vCtrlaccessLoopTable OBJECT-TYPE
	SYNTAX  SEQUENCE OF Pm1004vCtrlaccessLoopEntry
	MAX-ACCESS not-accessible
	STATUS current
	DESCRIPTION
        "
        List of pm1004vCtrlaccessLoop
         Article
        "
	::= { pm1004vCtrlClient 16 }


pm1004vCtrlaccessLoopEntry OBJECT-TYPE
	SYNTAX Pm1004vCtrlaccessLoopEntry
	MAX-ACCESS not-accessible
	STATUS current
	DESCRIPTION
        "
        Row definition for the pm1004vCtrlaccessLoop
        table
        "
	INDEX   { pm1004vCtrlaccessLoopIndex }
	::= { pm1004vCtrlaccessLoopTable 1 }


Pm1004vCtrlaccessLoopEntry ::=
	SEQUENCE {
	pm1004vCtrlaccessLoopIndex
		INTEGER,
	pm1004vCtrlaccessLoopPortn
		EkiState
	}


pm1004vCtrlaccessLoopIndex OBJECT-TYPE
	SYNTAX  INTEGER(0..128)
	MAX-ACCESS  read-only
	STATUS current
	DESCRIPTION
        "
        Index definition for the pm1004vCtrlaccessLoop
        table
        "
	::= { pm1004vCtrlaccessLoopEntry 1 }


pm1004vCtrlaccessLoopPortn OBJECT-TYPE
	SYNTAX  EkiState
	MAX-ACCESS read-write
	STATUS current
	DESCRIPTION
        "
        Client Facility Loopback :This
        OID operates a Client Facility
         Loopback, looping client input
        signal on the client output port.
        The loop is located on the client
        transceiver  <Help> This maintenance
        parameter operates a Client Facility
        Loopback, looping client input
         signal on the client output port.
        The loop is located on the client
        transceiver
        "
	::= { pm1004vCtrlaccessLoopEntry 2 }


--- *********************************************************
---     TABLE for the pm1004vCtrlportOosMode articles
--- *********************************************************

pm1004vCtrlportOosModeTable OBJECT-TYPE
	SYNTAX  SEQUENCE OF Pm1004vCtrlportOosModeEntry
	MAX-ACCESS not-accessible
	STATUS current
	DESCRIPTION
        "
        List of pm1004vCtrlportOosMode
        Article
        "
	::= { pm1004vCtrlClient 18 }


pm1004vCtrlportOosModeEntry OBJECT-TYPE
	SYNTAX Pm1004vCtrlportOosModeEntry
	MAX-ACCESS not-accessible
	STATUS current
	DESCRIPTION
        "
        Row definition for the pm1004vCtrlportOosMode
        table
        "
	INDEX   { pm1004vCtrlportOosModeIndex }
	::= { pm1004vCtrlportOosModeTable 1 }


Pm1004vCtrlportOosModeEntry ::=
	SEQUENCE {
	pm1004vCtrlportOosModeIndex
		INTEGER,
	pm1004vCtrlportOosModePortn
		Pm1004vClientOosMode
	}


pm1004vCtrlportOosModeIndex OBJECT-TYPE
	SYNTAX  INTEGER(0..128)
	MAX-ACCESS  read-only
	STATUS current
	DESCRIPTION
        "
        Index definition for the pm1004vCtrlportOosMode
        table
        "
	::= { pm1004vCtrlportOosModeEntry 1 }


pm1004vCtrlportOosModePortn OBJECT-TYPE
	SYNTAX  Pm1004vClientOosMode
	MAX-ACCESS read-write
	STATUS current
	DESCRIPTION
        "
        Client Out Of Service :This OID
        sets the Service state of the client
        port (In Service, Tx Out of Service,
        Rx Out of Service or Port (Rx and
        Tx) Out of Service)  <Help>  This
        controls defines the service state
        of the client port (In Service,
        Tx Out of Service, Rx Out of Service
         or Port (Rx and Tx) Out of Service)
        "
	::= { pm1004vCtrlportOosModeEntry 2 }


--- *********************************************************
---     TABLE for the pm1004vCtrlsfpOffCtrl articles
--- *********************************************************

pm1004vCtrlsfpOffCtrlTable OBJECT-TYPE
	SYNTAX  SEQUENCE OF Pm1004vCtrlsfpOffCtrlEntry
	MAX-ACCESS not-accessible
	STATUS current
	DESCRIPTION
        "
        List of pm1004vCtrlsfpOffCtrl
         Article
        "
	::= { pm1004vCtrlClient 20 }


pm1004vCtrlsfpOffCtrlEntry OBJECT-TYPE
	SYNTAX Pm1004vCtrlsfpOffCtrlEntry
	MAX-ACCESS not-accessible
	STATUS current
	DESCRIPTION
        "
        Row definition for the pm1004vCtrlsfpOffCtrl
        table
        "
	INDEX   { pm1004vCtrlsfpOffCtrlIndex }
	::= { pm1004vCtrlsfpOffCtrlTable 1 }


Pm1004vCtrlsfpOffCtrlEntry ::=
	SEQUENCE {
	pm1004vCtrlsfpOffCtrlIndex
		INTEGER,
	pm1004vCtrlsfpOffCtrlPortn
		EkiState
	}


pm1004vCtrlsfpOffCtrlIndex OBJECT-TYPE
	SYNTAX  INTEGER(0..128)
	MAX-ACCESS  read-only
	STATUS current
	DESCRIPTION
        "
        Index definition for the pm1004vCtrlsfpOffCtrl
        table
        "
	::= { pm1004vCtrlsfpOffCtrlEntry 1 }


pm1004vCtrlsfpOffCtrlPortn OBJECT-TYPE
	SYNTAX  EkiState
	MAX-ACCESS read-write
	STATUS current
	DESCRIPTION
        "
        Client Signal Shutdown :This OID
        switches off the SFP.  <Help>
          This control defines the laser
        state of the client transceiver
        "
	::= { pm1004vCtrlsfpOffCtrlEntry 2 }


--- *********************************************************
---     TABLE for the pm1004vCtrlcsfUpIns articles
--- *********************************************************

pm1004vCtrlcsfUpInsTable OBJECT-TYPE
	SYNTAX  SEQUENCE OF Pm1004vCtrlcsfUpInsEntry
	MAX-ACCESS not-accessible
	STATUS current
	DESCRIPTION
        "
        List of pm1004vCtrlcsfUpIns Article
        "
	::= { pm1004vCtrlClient 21 }


pm1004vCtrlcsfUpInsEntry OBJECT-TYPE
	SYNTAX Pm1004vCtrlcsfUpInsEntry
	MAX-ACCESS not-accessible
	STATUS current
	DESCRIPTION
        "
        Row definition for the pm1004vCtrlcsfUpIns
        table
        "
	INDEX   { pm1004vCtrlcsfUpInsIndex }
	::= { pm1004vCtrlcsfUpInsTable 1 }


Pm1004vCtrlcsfUpInsEntry ::=
	SEQUENCE {
	pm1004vCtrlcsfUpInsIndex
		INTEGER,
	pm1004vCtrlcsfUpInsPortn
		EkiState
	}


pm1004vCtrlcsfUpInsIndex OBJECT-TYPE
	SYNTAX  INTEGER(0..128)
	MAX-ACCESS  read-only
	STATUS current
	DESCRIPTION
        "
        Index definition for the pm1004vCtrlcsfUpIns
        table
        "
	::= { pm1004vCtrlcsfUpInsEntry 1 }


pm1004vCtrlcsfUpInsPortn OBJECT-TYPE
	SYNTAX  EkiState
	MAX-ACCESS read-write
	STATUS current
	DESCRIPTION
        "
        Client Signal Fail Insertion :This
        OID, when set, inserts  a client
        signal fail in the upstream client
        Port.  <Help>  This control inserts
        a Client Signal Fail for the client
        port
        "
	::= { pm1004vCtrlcsfUpInsEntry 2 }


--- *********************************************************
---     TABLE for the pm1004vCtrlcaisDwIns articles
--- *********************************************************

pm1004vCtrlcaisDwInsTable OBJECT-TYPE
	SYNTAX  SEQUENCE OF Pm1004vCtrlcaisDwInsEntry
	MAX-ACCESS not-accessible
	STATUS current
	DESCRIPTION
        "
        List of pm1004vCtrlcaisDwIns Article
        "
	::= { pm1004vCtrlClient 22 }


pm1004vCtrlcaisDwInsEntry OBJECT-TYPE
	SYNTAX Pm1004vCtrlcaisDwInsEntry
	MAX-ACCESS not-accessible
	STATUS current
	DESCRIPTION
        "
        Row definition for the pm1004vCtrlcaisDwIns
        table
        "
	INDEX   { pm1004vCtrlcaisDwInsIndex }
	::= { pm1004vCtrlcaisDwInsTable 1 }


Pm1004vCtrlcaisDwInsEntry ::=
	SEQUENCE {
	pm1004vCtrlcaisDwInsIndex
		INTEGER,
	pm1004vCtrlcaisDwInsPortn
		EkiState
	}


pm1004vCtrlcaisDwInsIndex OBJECT-TYPE
	SYNTAX  INTEGER(0..128)
	MAX-ACCESS  read-only
	STATUS current
	DESCRIPTION
        "
        Index definition for the pm1004vCtrlcaisDwIns
        table
        "
	::= { pm1004vCtrlcaisDwInsEntry 1 }


pm1004vCtrlcaisDwInsPortn OBJECT-TYPE
	SYNTAX  EkiState
	MAX-ACCESS read-write
	STATUS current
	DESCRIPTION
        "
        Client AIS Insertion :This OID,
        when set, inserts a client AIS
         on the downstream client Port.
         <Help>  This control inserts a
        Client AIS for the client port
        "
	::= { pm1004vCtrlcaisDwInsEntry 2 }


--- *********************************************************
---     TABLE for the pm1004vCtrlclientAccessTermLoop articles
--- *********************************************************

pm1004vCtrlclientAccessTermLoopTable OBJECT-TYPE
	SYNTAX  SEQUENCE OF Pm1004vCtrlclientAccessTermLoopEntry
	MAX-ACCESS not-accessible
	STATUS current
	DESCRIPTION
        "
        List of pm1004vCtrlclientAccessTermLoop
        Article
        "
	::= { pm1004vCtrlClient 26 }


pm1004vCtrlclientAccessTermLoopEntry OBJECT-TYPE
	SYNTAX Pm1004vCtrlclientAccessTermLoopEntry
	MAX-ACCESS not-accessible
	STATUS current
	DESCRIPTION
        "
        Row definition for the pm1004vCtrlclientAccessTermLoop
        table
        "
	INDEX   { pm1004vCtrlclientAccessTermLoopIndex }
	::= { pm1004vCtrlclientAccessTermLoopTable 1 }


Pm1004vCtrlclientAccessTermLoopEntry ::=
	SEQUENCE {
	pm1004vCtrlclientAccessTermLoopIndex
		INTEGER,
	pm1004vCtrlclientAccessTermLoopPortn
		EkiState
	}


pm1004vCtrlclientAccessTermLoopIndex OBJECT-TYPE
	SYNTAX  INTEGER(0..128)
	MAX-ACCESS  read-only
	STATUS current
	DESCRIPTION
        "
        Index definition for the pm1004vCtrlclientAccessTermLoop
        table
        "
	::= { pm1004vCtrlclientAccessTermLoopEntry 1 }


pm1004vCtrlclientAccessTermLoopPortn OBJECT-TYPE
	SYNTAX  EkiState
	MAX-ACCESS read-write
	STATUS current
	DESCRIPTION
        "
        Client Terminal Loopback :This
        OID operates a Client Terminal
         Loopback, looping client input
        signal on the client output port.
        The loop is located on the line
        transceiver  <Help> This maintenance
        parameter operates a Client Terminal
        Loopback, looping client input
         signal on the client output port.
        The loop is located on the line
        transceiver
        "
	::= { pm1004vCtrlclientAccessTermLoopEntry 2 }


--- *********************************************************
---     TABLE for the pm1004vCtrlrxVideoProtocol articles
--- *********************************************************

pm1004vCtrlrxVideoProtocolTable OBJECT-TYPE
	SYNTAX  SEQUENCE OF Pm1004vCtrlrxVideoProtocolEntry
	MAX-ACCESS not-accessible
	STATUS current
	DESCRIPTION
        "
        List of pm1004vCtrlrxVideoProtocol
        Article
        "
	::= { pm1004vCtrlClient 43 }


pm1004vCtrlrxVideoProtocolEntry OBJECT-TYPE
	SYNTAX Pm1004vCtrlrxVideoProtocolEntry
	MAX-ACCESS not-accessible
	STATUS current
	DESCRIPTION
        "
        Row definition for the pm1004vCtrlrxVideoProtocol
        table
        "
	INDEX   { pm1004vCtrlrxVideoProtocolIndex }
	::= { pm1004vCtrlrxVideoProtocolTable 1 }


Pm1004vCtrlrxVideoProtocolEntry ::=
	SEQUENCE {
	pm1004vCtrlrxVideoProtocolIndex
		INTEGER,
	pm1004vCtrlrxVideoProtocolPortn
		EkiState
	}


pm1004vCtrlrxVideoProtocolIndex OBJECT-TYPE
	SYNTAX  INTEGER(0..128)
	MAX-ACCESS  read-only
	STATUS current
	DESCRIPTION
        "
        Index definition for the pm1004vCtrlrxVideoProtocol
        table
        "
	::= { pm1004vCtrlrxVideoProtocolEntry 1 }


pm1004vCtrlrxVideoProtocolPortn OBJECT-TYPE
	SYNTAX  EkiState
	MAX-ACCESS read-write
	STATUS current
	DESCRIPTION
        "
        Force DVB ASI On RX Side
 :This
        OID selects the DVB ASI protocol
        on the client port and disable
         the auto-sensing feature
  <Help>
         This control selects the DVB ASI
        protocol on the client port and
        disable the auto-sensing feature

        "
	::= { pm1004vCtrlrxVideoProtocolEntry 2 }


--- *****************************************************
---     LEAF for the commAccessLoop article
--- *****************************************************
pm1004vCtrlcommAccessLoop OBJECT IDENTIFIER ::= { pm1004vCtrlLine 64 }




pm1004vCtrlCommAccessloop OBJECT-TYPE
	  SYNTAX EkiOnOff
	  MAX-ACCESS read-write
	  STATUS deprecated
	  DESCRIPTION
        "
        PM Full Access Loop Mode :This
        OID, when set, puts the module
         in common access loop back, looping
        the 10 Gb/s output signal on the
        10 Gb/s input.
        "
	  ::= { pm1004vCtrlcommAccessLoop 1 }



--- *****************************************************
---     LEAF for the lineLoop article
--- *****************************************************
pm1004vCtrllineLoop OBJECT IDENTIFIER ::= { pm1004vCtrlLine 66 }




pm1004vCtrlLineLoop OBJECT-TYPE
	  SYNTAX EkiOnOff
	  MAX-ACCESS read-write
	  STATUS deprecated
	  DESCRIPTION
        "
        PM Line Loop Mode :This OID, when
        set at '1' puts the module in line
        loopback mode, looping the received
        10 Gb/s signal on the transmit
         10 Gb/s output. The Upstream part
        of the module is timed on the 10
        Gb/s recovered clock in that case.
        "
	  ::= { pm1004vCtrllineLoop 1 }



--- *****************************************************
---     LEAF for the protMgnt article
--- *****************************************************
pm1004vCtrlProtMgnt OBJECT IDENTIFIER ::= { pm1004vCtrlLine 73 }




pm1004vCtrlLineNumber OBJECT-TYPE
	  SYNTAX Unsigned32 (0..3)
	  MAX-ACCESS read-write
	  STATUS current
	  DESCRIPTION
        "
        Active Line Number : This OID
         sets the active line number
        "
	  ::= { pm1004vCtrlProtMgnt 1 }



pm1004vCtrlProtMode OBJECT-TYPE
	  SYNTAX EkiMode
	  MAX-ACCESS read-write
	  STATUS current
	  DESCRIPTION
        "
        Line Switch Mode (Auto Or Manual)
        :This bit selects the manual (1)
        or automatic (0) switch method
          <Help>  This control defines
         the protection switch mode on
         the line interface
        "
	  ::= { pm1004vCtrlProtMgnt 2 }



--- *********************************************************
---     TABLE for the pm1004vCtrllineOosMode articles
--- *********************************************************

pm1004vCtrllineOosModeTable OBJECT-TYPE
	SYNTAX  SEQUENCE OF Pm1004vCtrllineOosModeEntry
	MAX-ACCESS not-accessible
	STATUS current
	DESCRIPTION
        "
        List of pm1004vCtrllineOosMode
        Article
        "
	::= { pm1004vCtrlLine 74 }


pm1004vCtrllineOosModeEntry OBJECT-TYPE
	SYNTAX Pm1004vCtrllineOosModeEntry
	MAX-ACCESS not-accessible
	STATUS current
	DESCRIPTION
        "
        Row definition for the pm1004vCtrllineOosMode
        table
        "
	INDEX   { pm1004vCtrllineOosModeIndex }
	::= { pm1004vCtrllineOosModeTable 1 }


Pm1004vCtrllineOosModeEntry ::=
	SEQUENCE {
	pm1004vCtrllineOosModeIndex
		INTEGER,
	pm1004vCtrllineOosModePortn
		EkiState
	}


pm1004vCtrllineOosModeIndex OBJECT-TYPE
	SYNTAX  INTEGER(0..128)
	MAX-ACCESS  read-only
	STATUS current
	DESCRIPTION
        "
        Index definition for the pm1004vCtrllineOosMode
        table
        "
	::= { pm1004vCtrllineOosModeEntry 1 }


pm1004vCtrllineOosModePortn OBJECT-TYPE
	SYNTAX  EkiState
	MAX-ACCESS read-write
	STATUS current
	DESCRIPTION
        "
        Line Out Of Service (!Laser OFF!)
        :This OID sets the line port Out
        Of Service  <Help>  This control
        defines the service state of the
        line port
        "
	::= { pm1004vCtrllineOosModeEntry 2 }


--- *********************************************************
---     TABLE for the pm1004vCtrladddropClientRxProtect articles
--- *********************************************************

pm1004vCtrladddropClientRxProtectTable OBJECT-TYPE
	SYNTAX  SEQUENCE OF Pm1004vCtrladddropClientRxProtectEntry
	MAX-ACCESS not-accessible
	STATUS current
	DESCRIPTION
        "
        List of pm1004vCtrladddropClientRxProtect
        Article
        "
	::= { pm1004vCtrlClient 128 }


pm1004vCtrladddropClientRxProtectEntry OBJECT-TYPE
	SYNTAX Pm1004vCtrladddropClientRxProtectEntry
	MAX-ACCESS not-accessible
	STATUS current
	DESCRIPTION
        "
        Row definition for the pm1004vCtrladddropClientRxProtect
        table
        "
	INDEX   { pm1004vCtrladddropClientRxProtectIndex }
	::= { pm1004vCtrladddropClientRxProtectTable 1 }


Pm1004vCtrladddropClientRxProtectEntry ::=
	SEQUENCE {
	pm1004vCtrladddropClientRxProtectIndex
		INTEGER,
	pm1004vCtrladddropClientRxProtectPortn
		Pm1004vProtectionTimeSlot
	}


pm1004vCtrladddropClientRxProtectIndex OBJECT-TYPE
	SYNTAX  INTEGER(0..128)
	MAX-ACCESS  read-only
	STATUS current
	DESCRIPTION
        "
        Index definition for the pm1004vCtrladddropClientRxProtect
        table
        "
	::= { pm1004vCtrladddropClientRxProtectEntry 1 }


pm1004vCtrladddropClientRxProtectPortn OBJECT-TYPE
	SYNTAX  Pm1004vProtectionTimeSlot
	MAX-ACCESS read-write
	STATUS current
	DESCRIPTION
        "
        Client Switch Mode :This bit selects
        the manual (1) or automatic (0)
        switch method  <Help>  This control
        defines the protection switch mode
        on the client interface
        "
	::= { pm1004vCtrladddropClientRxProtectEntry 2 }


--- *********************************************************
---     TABLE for the pm1004vCtrladddropTsClientMode articles
--- *********************************************************

pm1004vCtrladddropTsClientModeTable OBJECT-TYPE
	SYNTAX  SEQUENCE OF Pm1004vCtrladddropTsClientModeEntry
	MAX-ACCESS not-accessible
	STATUS current
	DESCRIPTION
        "
        List of pm1004vCtrladddropTsClientMode
        Article
        "
	::= { pm1004vCtrlClient 136 }


pm1004vCtrladddropTsClientModeEntry OBJECT-TYPE
	SYNTAX Pm1004vCtrladddropTsClientModeEntry
	MAX-ACCESS not-accessible
	STATUS current
	DESCRIPTION
        "
        Row definition for the pm1004vCtrladddropTsClientMode
        table
        "
	INDEX   { pm1004vCtrladddropTsClientModeIndex }
	::= { pm1004vCtrladddropTsClientModeTable 1 }


Pm1004vCtrladddropTsClientModeEntry ::=
	SEQUENCE {
	pm1004vCtrladddropTsClientModeIndex
		INTEGER,
	pm1004vCtrladddropTsClientModePortn
		Pm1004vModeTimeSlot
	}


pm1004vCtrladddropTsClientModeIndex OBJECT-TYPE
	SYNTAX  INTEGER(0..128)
	MAX-ACCESS  read-only
	STATUS current
	DESCRIPTION
        "
        Index definition for the pm1004vCtrladddropTsClientMode
        table
        "
	::= { pm1004vCtrladddropTsClientModeEntry 1 }


pm1004vCtrladddropTsClientModePortn OBJECT-TYPE
	SYNTAX  Pm1004vModeTimeSlot
	MAX-ACCESS read-write
	STATUS current
	DESCRIPTION
        "
        Client Mode :This OID selects
         the mode on the client  <Help>
          This control defines the mode
        (Add/Drop or Split&Select) of the
        Client
        "
	::= { pm1004vCtrladddropTsClientModeEntry 2 }


--- *****************************************************
---     LEAF for the ledTest article
--- *****************************************************
pm1004vCtrlledTest OBJECT IDENTIFIER ::= { pm1004vCtrlOther 192 }




pm1004vCtrlLedOff OBJECT-TYPE
	  SYNTAX EkiOnOff
	  MAX-ACCESS read-write
	  STATUS current
	  DESCRIPTION
        "
        Leds Off :This OID switches off
        all the Leds as a test feature.
         <Help>  This control initiates
        a test leds turning all the LEDs
        to OFF
        "
	  ::= { pm1004vCtrlledTest 3 }



pm1004vCtrlRedLed OBJECT-TYPE
	  SYNTAX EkiOnOff
	  MAX-ACCESS read-write
	  STATUS current
	  DESCRIPTION
        "
        Red Leds Test :This OID switches
        on all the red Leds as a test feature.
         <Help>  This control initiates
        a test leds turning all the LEDs
        to red
        "
	  ::= { pm1004vCtrlledTest 2 }



pm1004vCtrlGreenLed OBJECT-TYPE
	  SYNTAX EkiOnOff
	  MAX-ACCESS read-write
	  STATUS current
	  DESCRIPTION
        "
        Green Leds Test :This OID switches
        on all the green Leds as a test
        feature.  <Help>  This control
         initiates a test leds turning
         all the LEDs to green
        "
	  ::= { pm1004vCtrlledTest 1 }



--- *****************************************************
---     LEAF for the moduleOosMode article
--- *****************************************************
pm1004vCtrlmoduleOosMode OBJECT IDENTIFIER ::= { pm1004vCtrlOther 193 }




pm1004vCtrlModuleOosMode OBJECT-TYPE
	  SYNTAX EkiOnOff
	  MAX-ACCESS read-write
	  STATUS current
	  DESCRIPTION
        "
        PM Out Of Service :This OID sets
        the PM Out Of Service  <Help>
         This control defines the service
        state of the complete module
        "
	  ::= { pm1004vCtrlmoduleOosMode 1 }



--- *****************************************************
---     LEAF for the maintenanceMode article
--- *****************************************************
pm1004vCtrlmaintenanceMode OBJECT IDENTIFIER ::= { pm1004vCtrlOther 197 }




pm1004vCtrlMaintenanceMode OBJECT-TYPE
	  SYNTAX EkiOnOff
	  MAX-ACCESS read-write
	  STATUS current
	  DESCRIPTION
        "
        Module Maintenance Mode :This
         OID enables the maintenance mode
        on the PM.  <Help>  This control
        enables the maintenance mode on
        the PM.
        "
	  ::= { pm1004vCtrlmaintenanceMode 1 }



--- *********************************************************
---     TABLE for the pm1004vCtrldccEnable articles
--- *********************************************************

pm1004vCtrldccEnableTable OBJECT-TYPE
	SYNTAX  SEQUENCE OF Pm1004vCtrldccEnableEntry
	MAX-ACCESS not-accessible
	STATUS current
	DESCRIPTION
        "
        List of pm1004vCtrldccEnable Article
        "
	::= { pm1004vCtrlLine 198 }


pm1004vCtrldccEnableEntry OBJECT-TYPE
	SYNTAX Pm1004vCtrldccEnableEntry
	MAX-ACCESS not-accessible
	STATUS current
	DESCRIPTION
        "
        Row definition for the pm1004vCtrldccEnable
        table
        "
	INDEX   { pm1004vCtrldccEnableIndex }
	::= { pm1004vCtrldccEnableTable 1 }


Pm1004vCtrldccEnableEntry ::=
	SEQUENCE {
	pm1004vCtrldccEnableIndex
		INTEGER,
	pm1004vCtrldccEnablePortn
		EkiState
	}


pm1004vCtrldccEnableIndex OBJECT-TYPE
	SYNTAX  INTEGER(0..128)
	MAX-ACCESS  read-only
	STATUS current
	DESCRIPTION
        "
        Index definition for the pm1004vCtrldccEnable
        table
        "
	::= { pm1004vCtrldccEnableEntry 1 }


pm1004vCtrldccEnablePortn OBJECT-TYPE
	SYNTAX  EkiState
	MAX-ACCESS read-write
	STATUS current
	DESCRIPTION
        "
        DCC Enable : This OID enables
         the DCC mode on the PM  <Help>
          This control enables the DCC
         mode on the PM
        "
	::= { pm1004vCtrldccEnableEntry 2 }


--- *********************************************************
---     TABLE for the pm1004vCtrlxfpOnoff articles
--- *********************************************************

pm1004vCtrlxfpOnoffTable OBJECT-TYPE
	SYNTAX  SEQUENCE OF Pm1004vCtrlxfpOnoffEntry
	MAX-ACCESS not-accessible
	STATUS current
	DESCRIPTION
        "
        List of pm1004vCtrlxfpOnoff Article
        "
	::= { pm1004vCtrlLine 208 }


pm1004vCtrlxfpOnoffEntry OBJECT-TYPE
	SYNTAX Pm1004vCtrlxfpOnoffEntry
	MAX-ACCESS not-accessible
	STATUS current
	DESCRIPTION
        "
        Row definition for the pm1004vCtrlxfpOnoff
        table
        "
	INDEX   { pm1004vCtrlxfpOnoffIndex }
	::= { pm1004vCtrlxfpOnoffTable 1 }


Pm1004vCtrlxfpOnoffEntry ::=
	SEQUENCE {
	pm1004vCtrlxfpOnoffIndex
		INTEGER,
	pm1004vCtrlxfpOnoffPortn
		EkiState
	}


pm1004vCtrlxfpOnoffIndex OBJECT-TYPE
	SYNTAX  INTEGER(0..128)
	MAX-ACCESS  read-only
	STATUS current
	DESCRIPTION
        "
        Index definition for the pm1004vCtrlxfpOnoff
        table
        "
	::= { pm1004vCtrlxfpOnoffEntry 1 }


pm1004vCtrlxfpOnoffPortn OBJECT-TYPE
	SYNTAX  EkiState
	MAX-ACCESS read-write
	STATUS current
	DESCRIPTION
        "
        Line Optical Module Laser Shutdown
        :This OID switches off the XFP
         or the OTX  <Help>  This control
        defines the laser state of the
         line transceiver
        "
	::= { pm1004vCtrlxfpOnoffEntry 2 }


--- *********************************************************
---     TABLE for the pm1004vCtrlxfpLineLoop articles
--- *********************************************************

pm1004vCtrlxfpLineLoopTable OBJECT-TYPE
	SYNTAX  SEQUENCE OF Pm1004vCtrlxfpLineLoopEntry
	MAX-ACCESS not-accessible
	STATUS current
	DESCRIPTION
        "
        List of pm1004vCtrlxfpLineLoop
        Article
        "
	::= { pm1004vCtrlLine 209 }


pm1004vCtrlxfpLineLoopEntry OBJECT-TYPE
	SYNTAX Pm1004vCtrlxfpLineLoopEntry
	MAX-ACCESS not-accessible
	STATUS current
	DESCRIPTION
        "
        Row definition for the pm1004vCtrlxfpLineLoop
        table
        "
	INDEX   { pm1004vCtrlxfpLineLoopIndex }
	::= { pm1004vCtrlxfpLineLoopTable 1 }


Pm1004vCtrlxfpLineLoopEntry ::=
	SEQUENCE {
	pm1004vCtrlxfpLineLoopIndex
		INTEGER,
	pm1004vCtrlxfpLineLoopPortn
		EkiState
	}


pm1004vCtrlxfpLineLoopIndex OBJECT-TYPE
	SYNTAX  INTEGER(0..128)
	MAX-ACCESS  read-only
	STATUS current
	DESCRIPTION
        "
        Index definition for the pm1004vCtrlxfpLineLoop
        table
        "
	::= { pm1004vCtrlxfpLineLoopEntry 1 }


pm1004vCtrlxfpLineLoopPortn OBJECT-TYPE
	SYNTAX  EkiState
	MAX-ACCESS read-write
	STATUS current
	DESCRIPTION
        "
        Line Facility Loopback :This OID
        operates a Line Facility Loopback,
        looping line input signal on the
        line output port. The loop is located
        on the line transceiver. If the
        Line signal carries DCC, the management
        network is impacted  <Help> This
        maintenance parameter operates
         a Line Facility Loopback, looping
        line input signal on the line output
        port. The loop is located on the
        line transceiver. If the Line signal
        carries DCC, the management network
        is impacted
        "
	::= { pm1004vCtrlxfpLineLoopEntry 2 }


--- *********************************************************
---     TABLE for the pm1004vCtrlxfpXfiLoop articles
--- *********************************************************

pm1004vCtrlxfpXfiLoopTable OBJECT-TYPE
	SYNTAX  SEQUENCE OF Pm1004vCtrlxfpXfiLoopEntry
	MAX-ACCESS not-accessible
	STATUS current
	DESCRIPTION
        "
        List of pm1004vCtrlxfpXfiLoop
         Article
        "
	::= { pm1004vCtrlLine 210 }


pm1004vCtrlxfpXfiLoopEntry OBJECT-TYPE
	SYNTAX Pm1004vCtrlxfpXfiLoopEntry
	MAX-ACCESS not-accessible
	STATUS current
	DESCRIPTION
        "
        Row definition for the pm1004vCtrlxfpXfiLoop
        table
        "
	INDEX   { pm1004vCtrlxfpXfiLoopIndex }
	::= { pm1004vCtrlxfpXfiLoopTable 1 }


Pm1004vCtrlxfpXfiLoopEntry ::=
	SEQUENCE {
	pm1004vCtrlxfpXfiLoopIndex
		INTEGER,
	pm1004vCtrlxfpXfiLoopPortn
		EkiState
	}


pm1004vCtrlxfpXfiLoopIndex OBJECT-TYPE
	SYNTAX  INTEGER(0..128)
	MAX-ACCESS  read-only
	STATUS current
	DESCRIPTION
        "
        Index definition for the pm1004vCtrlxfpXfiLoop
        table
        "
	::= { pm1004vCtrlxfpXfiLoopEntry 1 }


pm1004vCtrlxfpXfiLoopPortn OBJECT-TYPE
	SYNTAX  EkiState
	MAX-ACCESS read-write
	STATUS current
	DESCRIPTION
        "
        Line Terminal Loopback :This OID
        operates a Line Terminal Loopback,
        looping line input signal on the
        line output port. The loop is located
        on all client transceivers  <Help>
        This maintenance parameter operates
        a Line Terminal Loopback, looping
        line input signal on the line output
        port. The loop is located on all
        client transceivers.
        "
	::= { pm1004vCtrlxfpXfiLoopEntry 2 }







--- *****************************************************
--- $$$$$$$$$$$$$$$$$$$$$$$$$$$$$$$$$$$$$$$$$$$$$$$$$$$$$
---     COUNTERS
--- $$$$$$$$$$$$$$$$$$$$$$$$$$$$$$$$$$$$$$$$$$$$$$$$$$$$$
--- *****************************************************



--- *********************************************************
---     TABLE for the pm1004vCntdfrmB1ErrCnt articles
--- *********************************************************

pm1004vCntdfrmB1ErrCntTable OBJECT-TYPE
	SYNTAX  SEQUENCE OF Pm1004vCntdfrmB1ErrCntEntry
	MAX-ACCESS not-accessible
	STATUS current
	DESCRIPTION
        "
        List of pm1004vCntdfrmB1ErrCnt
        Article
        "
	::= { pm1004vCntLine 152 }


pm1004vCntdfrmB1ErrCntEntry OBJECT-TYPE
	SYNTAX Pm1004vCntdfrmB1ErrCntEntry
	MAX-ACCESS not-accessible
	STATUS current
	DESCRIPTION
        "
        Row definition for the pm1004vCntdfrmB1ErrCnt
        table
        "
	INDEX   { pm1004vCntdfrmB1ErrCntIndex }
	::= { pm1004vCntdfrmB1ErrCntTable 1 }


Pm1004vCntdfrmB1ErrCntEntry ::=
	SEQUENCE {
	pm1004vCntdfrmB1ErrCntIndex
		INTEGER,
	pm1004vCntdfrmB1ErrCntValuePortn
		Counter32,
	pm1004vCntdfrmB1ErrCntErrorPortn
		EkiOnOff,
	pm1004vCntdfrmB1ErrCntOverloadPortn
		EkiOnOff
	}


pm1004vCntdfrmB1ErrCntIndex OBJECT-TYPE
	SYNTAX  INTEGER(0..128)
	MAX-ACCESS  read-only
	STATUS current
	DESCRIPTION
        "
        Index definition for the pm1004vCntdfrmB1ErrCnt
        table
        "
	::= { pm1004vCntdfrmB1ErrCntEntry 1 }


pm1004vCntdfrmB1ErrCntValuePortn OBJECT-TYPE
	SYNTAX  Counter32
	MAX-ACCESS read-only
	STATUS current
	DESCRIPTION
        "
        Line Input CRC Errors :This counter
        is incremented each time a B1 error
        is detected on the Deframer input
        stream.  <Help>  This counter gives
        the number of B1 errors on the
         line port
        "
	::= { pm1004vCntdfrmB1ErrCntEntry 2 }


pm1004vCntdfrmB1ErrCntErrorPortn OBJECT-TYPE
	SYNTAX  EkiOnOff
	MAX-ACCESS read-only
	STATUS current
	DESCRIPTION
        "
        Line Counter Error :This OID when
        set indicates the B1 error counter
        value is invalid on Port
        "
	::= { pm1004vCntdfrmB1ErrCntEntry 3 }


pm1004vCntdfrmB1ErrCntOverloadPortn OBJECT-TYPE
	SYNTAX  EkiOnOff
	MAX-ACCESS read-only
	STATUS current
	DESCRIPTION
        "
        Line Counter Overload :This OID
        when set indicates a B1 error counter
        overload on Port
        "
	::= { pm1004vCntdfrmB1ErrCntEntry 4 }


--- *********************************************************
---     TABLE for the pm1004vCntdfrmTimCnt articles
--- *********************************************************

pm1004vCntdfrmTimCntTable OBJECT-TYPE
	SYNTAX  SEQUENCE OF Pm1004vCntdfrmTimCntEntry
	MAX-ACCESS not-accessible
	STATUS current
	DESCRIPTION
        "
        List of pm1004vCntdfrmTimCnt Article
        "
	::= { pm1004vCntLine 153 }


pm1004vCntdfrmTimCntEntry OBJECT-TYPE
	SYNTAX Pm1004vCntdfrmTimCntEntry
	MAX-ACCESS not-accessible
	STATUS current
	DESCRIPTION
        "
        Row definition for the pm1004vCntdfrmTimCnt
        table
        "
	INDEX   { pm1004vCntdfrmTimCntIndex }
	::= { pm1004vCntdfrmTimCntTable 1 }


Pm1004vCntdfrmTimCntEntry ::=
	SEQUENCE {
	pm1004vCntdfrmTimCntIndex
		INTEGER,
	pm1004vCntdfrmTimCntValuePortn
		Counter32,
	pm1004vCntdfrmTimCntErrorPortn
		EkiOnOff,
	pm1004vCntdfrmTimCntOverloadPortn
		EkiOnOff
	}


pm1004vCntdfrmTimCntIndex OBJECT-TYPE
	SYNTAX  INTEGER(0..128)
	MAX-ACCESS  read-only
	STATUS current
	DESCRIPTION
        "
        Index definition for the pm1004vCntdfrmTimCnt
        table
        "
	::= { pm1004vCntdfrmTimCntEntry 1 }


pm1004vCntdfrmTimCntValuePortn OBJECT-TYPE
	SYNTAX  Counter32
	MAX-ACCESS read-only
	STATUS current
	DESCRIPTION
        "
        Line Timer Counter :This is the
        timing counter dedicated to the
        downstream deframer counters. It
        is incremented every 125 us.
        "
	::= { pm1004vCntdfrmTimCntEntry 2 }


pm1004vCntdfrmTimCntErrorPortn OBJECT-TYPE
	SYNTAX  EkiOnOff
	MAX-ACCESS read-only
	STATUS current
	DESCRIPTION
        "
        Line Counter Error :This OID when
        set indicates the deframer timer
        counter value is invalid on Port
        "
	::= { pm1004vCntdfrmTimCntEntry 3 }


pm1004vCntdfrmTimCntOverloadPortn OBJECT-TYPE
	SYNTAX  EkiOnOff
	MAX-ACCESS read-only
	STATUS current
	DESCRIPTION
        "
        Line Counter Overload :This OID
        when set indicates a deframer timer
        counter overload on Port
        "
	::= { pm1004vCntdfrmTimCntEntry 4 }


pm1004vCntCountersReset  OBJECT-TYPE
	SYNTAX EkiOnOff
	MAX-ACCESS read-write
	STATUS current
	DESCRIPTION
	"Counters Reset:This OID resets and restarts all the counters"
	::= { pm1004vcounters  259 }

pm1004vCntCountersStop  OBJECT-TYPE
	SYNTAX EkiOnOff
	MAX-ACCESS read-write
	STATUS current
	DESCRIPTION
	"Counters stop:This OID stops all the counters"
	::= { pm1004vcounters 260 }






--- *****************************************************
--- $$$$$$$$$$$$$$$$$$$$$$$$$$$$$$$$$$$$$$$$$$$$$$$$$$$$$
---     RMON
--- $$$$$$$$$$$$$$$$$$$$$$$$$$$$$$$$$$$$$$$$$$$$$$$$$$$$$
--- *****************************************************



--- *********************************************************
---     TABLE for the pm1004vMonupRmonByteCnt articles
--- *********************************************************

pm1004vMonupRmonByteCntTable OBJECT-TYPE
	SYNTAX  SEQUENCE OF Pm1004vMonupRmonByteCntEntry
	MAX-ACCESS not-accessible
	STATUS current
	DESCRIPTION
        "
        List of pm1004vMonupRmonByteCnt
        Article
        "
	::= { pm1004vMonClientRmonCounter 16 }


pm1004vMonupRmonByteCntEntry OBJECT-TYPE
	SYNTAX Pm1004vMonupRmonByteCntEntry
	MAX-ACCESS not-accessible
	STATUS current
	DESCRIPTION
        "
        Row definition for the pm1004vMonupRmonByteCnt
        table
        "
	INDEX   { pm1004vMonupRmonByteCntIndex }
	::= { pm1004vMonupRmonByteCntTable 1 }


Pm1004vMonupRmonByteCntEntry ::=
	SEQUENCE {
	pm1004vMonupRmonByteCntIndex
		INTEGER,
	pm1004vMonupRmonByteCntValuePortn
		Counter64,
	pm1004vMonupRmonByteCntErrorPortn
		EkiOnOff,
	pm1004vMonupRmonByteCntOverloadPortn
		EkiOnOff
	}


pm1004vMonupRmonByteCntIndex OBJECT-TYPE
	SYNTAX  INTEGER(0..128)
	MAX-ACCESS  read-only
	STATUS current
	DESCRIPTION
        "
        Index definition for the pm1004vMonupRmonByteCnt
        table
        "
	::= { pm1004vMonupRmonByteCntEntry 1 }


pm1004vMonupRmonByteCntValuePortn OBJECT-TYPE
	SYNTAX  Counter64
	MAX-ACCESS read-only
	STATUS current
	DESCRIPTION
        "
        Client Input Bytes :This counter
        is increased each time a data byte
        is received on the client port
          <Help>  This counter gives the
        number of bytes received on the
        client port
        "
	::= { pm1004vMonupRmonByteCntEntry 2 }


pm1004vMonupRmonByteCntErrorPortn OBJECT-TYPE
	SYNTAX  EkiOnOff
	MAX-ACCESS read-only
	STATUS current
	DESCRIPTION
        "
        Bytes Counter Error :This OID
         when set indicates the Bytes counter
        value is invalid on clinet port
        "
	::= { pm1004vMonupRmonByteCntEntry 3 }


pm1004vMonupRmonByteCntOverloadPortn OBJECT-TYPE
	SYNTAX  EkiOnOff
	MAX-ACCESS read-only
	STATUS current
	DESCRIPTION
        "
        Bytes Counter Overload :This OID
        when set indicates a Bytes counter
        overload on client port
        "
	::= { pm1004vMonupRmonByteCntEntry 4 }


--- *********************************************************
---     TABLE for the pm1004vMonupRmonCrcErrorCnt articles
--- *********************************************************

pm1004vMonupRmonCrcErrorCntTable OBJECT-TYPE
	SYNTAX  SEQUENCE OF Pm1004vMonupRmonCrcErrorCntEntry
	MAX-ACCESS not-accessible
	STATUS current
	DESCRIPTION
        "
        List of pm1004vMonupRmonCrcErrorCnt
        Article
        "
	::= { pm1004vMonClientRmonCounter 24 }


pm1004vMonupRmonCrcErrorCntEntry OBJECT-TYPE
	SYNTAX Pm1004vMonupRmonCrcErrorCntEntry
	MAX-ACCESS not-accessible
	STATUS current
	DESCRIPTION
        "
        Row definition for the pm1004vMonupRmonCrcErrorCnt
        table
        "
	INDEX   { pm1004vMonupRmonCrcErrorCntIndex }
	::= { pm1004vMonupRmonCrcErrorCntTable 1 }


Pm1004vMonupRmonCrcErrorCntEntry ::=
	SEQUENCE {
	pm1004vMonupRmonCrcErrorCntIndex
		INTEGER,
	pm1004vMonupRmonCrcErrorCntValuePortn
		Counter64,
	pm1004vMonupRmonCrcErrorCntErrorPortn
		EkiOnOff,
	pm1004vMonupRmonCrcErrorCntOverloadPortn
		EkiOnOff
	}


pm1004vMonupRmonCrcErrorCntIndex OBJECT-TYPE
	SYNTAX  INTEGER(0..128)
	MAX-ACCESS  read-only
	STATUS current
	DESCRIPTION
        "
        Index definition for the pm1004vMonupRmonCrcErrorCnt
        table
        "
	::= { pm1004vMonupRmonCrcErrorCntEntry 1 }


pm1004vMonupRmonCrcErrorCntValuePortn OBJECT-TYPE
	SYNTAX  Counter64
	MAX-ACCESS read-only
	STATUS current
	DESCRIPTION
        "
        Client Input CRC Errors :This
         counter is increased each time
        a CRC error is detected on the
         client port  <Help>  This counter
        gives the number of CRC Errors
         received on the client port
        "
	::= { pm1004vMonupRmonCrcErrorCntEntry 2 }


pm1004vMonupRmonCrcErrorCntErrorPortn OBJECT-TYPE
	SYNTAX  EkiOnOff
	MAX-ACCESS read-only
	STATUS current
	DESCRIPTION
        "
        CRC Errors Counter Error :This
        OID when set indicates the CRC
         Errors counter value is invalid
        on clinet port
        "
	::= { pm1004vMonupRmonCrcErrorCntEntry 3 }


pm1004vMonupRmonCrcErrorCntOverloadPortn OBJECT-TYPE
	SYNTAX  EkiOnOff
	MAX-ACCESS read-only
	STATUS current
	DESCRIPTION
        "
        CRC Errors Counter Overload :This
        OID when set indicates a CRC Errors
        counter overload on client port
        "
	::= { pm1004vMonupRmonCrcErrorCntEntry 4 }


--- *********************************************************
---     TABLE for the pm1004vMonupRmonPacketsCnt articles
--- *********************************************************

pm1004vMonupRmonPacketsCntTable OBJECT-TYPE
	SYNTAX  SEQUENCE OF Pm1004vMonupRmonPacketsCntEntry
	MAX-ACCESS not-accessible
	STATUS current
	DESCRIPTION
        "
        List of pm1004vMonupRmonPacketsCnt
        Article
        "
	::= { pm1004vMonClientRmonCounter 32 }


pm1004vMonupRmonPacketsCntEntry OBJECT-TYPE
	SYNTAX Pm1004vMonupRmonPacketsCntEntry
	MAX-ACCESS not-accessible
	STATUS current
	DESCRIPTION
        "
        Row definition for the pm1004vMonupRmonPacketsCnt
        table
        "
	INDEX   { pm1004vMonupRmonPacketsCntIndex }
	::= { pm1004vMonupRmonPacketsCntTable 1 }


Pm1004vMonupRmonPacketsCntEntry ::=
	SEQUENCE {
	pm1004vMonupRmonPacketsCntIndex
		INTEGER,
	pm1004vMonupRmonPacketsCntValuePortn
		Counter64,
	pm1004vMonupRmonPacketsCntErrorPortn
		EkiOnOff,
	pm1004vMonupRmonPacketsCntOverloadPortn
		EkiOnOff
	}


pm1004vMonupRmonPacketsCntIndex OBJECT-TYPE
	SYNTAX  INTEGER(0..128)
	MAX-ACCESS  read-only
	STATUS current
	DESCRIPTION
        "
        Index definition for the pm1004vMonupRmonPacketsCnt
        table
        "
	::= { pm1004vMonupRmonPacketsCntEntry 1 }


pm1004vMonupRmonPacketsCntValuePortn OBJECT-TYPE
	SYNTAX  Counter64
	MAX-ACCESS read-only
	STATUS current
	DESCRIPTION
        "
        Client Input Packets :This counter
        is increased each time a packet
        is received on the client port
          <Help>  This counter gives the
        number of packets received on the
        client port
        "
	::= { pm1004vMonupRmonPacketsCntEntry 2 }


pm1004vMonupRmonPacketsCntErrorPortn OBJECT-TYPE
	SYNTAX  EkiOnOff
	MAX-ACCESS read-only
	STATUS current
	DESCRIPTION
        "
        Packets Counter Error :This OID
        when set indicates the Packets
         counter value is invalid on clinet
        port
        "
	::= { pm1004vMonupRmonPacketsCntEntry 3 }


pm1004vMonupRmonPacketsCntOverloadPortn OBJECT-TYPE
	SYNTAX  EkiOnOff
	MAX-ACCESS read-only
	STATUS current
	DESCRIPTION
        "
        Packets Counter Overload :This
        OID when set indicates a Packets
        counter overload on client port
        "
	::= { pm1004vMonupRmonPacketsCntEntry 4 }


--- *********************************************************
---     TABLE for the pm1004vMonupRmonBroadcastCnt articles
--- *********************************************************

pm1004vMonupRmonBroadcastCntTable OBJECT-TYPE
	SYNTAX  SEQUENCE OF Pm1004vMonupRmonBroadcastCntEntry
	MAX-ACCESS not-accessible
	STATUS current
	DESCRIPTION
        "
        List of pm1004vMonupRmonBroadcastCnt
        Article
        "
	::= { pm1004vMonClientRmonCounter 40 }


pm1004vMonupRmonBroadcastCntEntry OBJECT-TYPE
	SYNTAX Pm1004vMonupRmonBroadcastCntEntry
	MAX-ACCESS not-accessible
	STATUS current
	DESCRIPTION
        "
        Row definition for the pm1004vMonupRmonBroadcastCnt
        table
        "
	INDEX   { pm1004vMonupRmonBroadcastCntIndex }
	::= { pm1004vMonupRmonBroadcastCntTable 1 }


Pm1004vMonupRmonBroadcastCntEntry ::=
	SEQUENCE {
	pm1004vMonupRmonBroadcastCntIndex
		INTEGER,
	pm1004vMonupRmonBroadcastCntValuePortn
		Counter64,
	pm1004vMonupRmonBroadcastCntErrorPortn
		EkiOnOff,
	pm1004vMonupRmonBroadcastCntOverloadPortn
		EkiOnOff
	}


pm1004vMonupRmonBroadcastCntIndex OBJECT-TYPE
	SYNTAX  INTEGER(0..128)
	MAX-ACCESS  read-only
	STATUS current
	DESCRIPTION
        "
        Index definition for the pm1004vMonupRmonBroadcastCnt
        table
        "
	::= { pm1004vMonupRmonBroadcastCntEntry 1 }


pm1004vMonupRmonBroadcastCntValuePortn OBJECT-TYPE
	SYNTAX  Counter64
	MAX-ACCESS read-only
	STATUS current
	DESCRIPTION
        "
        Client Input Broadcast Packets
        :This counter is increased each
        time a broadcast packet is received
        on the client port  <Help>  This
        counter gives the number of Broadcast
        packets received on the client
         port
        "
	::= { pm1004vMonupRmonBroadcastCntEntry 2 }


pm1004vMonupRmonBroadcastCntErrorPortn OBJECT-TYPE
	SYNTAX  EkiOnOff
	MAX-ACCESS read-only
	STATUS current
	DESCRIPTION
        "
        Broadcast Counter Error :This
         OID when set indicates the Broadcast
        counter value is invalid on clinet
        port
        "
	::= { pm1004vMonupRmonBroadcastCntEntry 3 }


pm1004vMonupRmonBroadcastCntOverloadPortn OBJECT-TYPE
	SYNTAX  EkiOnOff
	MAX-ACCESS read-only
	STATUS current
	DESCRIPTION
        "
        Broadcast Counter Overload :This
        OID when set indicates a Broadcast
        counter overload on client port
        "
	::= { pm1004vMonupRmonBroadcastCntEntry 4 }


--- *********************************************************
---     TABLE for the pm1004vMonupRmonMulticastCnt articles
--- *********************************************************

pm1004vMonupRmonMulticastCntTable OBJECT-TYPE
	SYNTAX  SEQUENCE OF Pm1004vMonupRmonMulticastCntEntry
	MAX-ACCESS not-accessible
	STATUS current
	DESCRIPTION
        "
        List of pm1004vMonupRmonMulticastCnt
        Article
        "
	::= { pm1004vMonClientRmonCounter 48 }


pm1004vMonupRmonMulticastCntEntry OBJECT-TYPE
	SYNTAX Pm1004vMonupRmonMulticastCntEntry
	MAX-ACCESS not-accessible
	STATUS current
	DESCRIPTION
        "
        Row definition for the pm1004vMonupRmonMulticastCnt
        table
        "
	INDEX   { pm1004vMonupRmonMulticastCntIndex }
	::= { pm1004vMonupRmonMulticastCntTable 1 }


Pm1004vMonupRmonMulticastCntEntry ::=
	SEQUENCE {
	pm1004vMonupRmonMulticastCntIndex
		INTEGER,
	pm1004vMonupRmonMulticastCntValuePortn
		Counter64,
	pm1004vMonupRmonMulticastCntErrorPortn
		EkiOnOff,
	pm1004vMonupRmonMulticastCntOverloadPortn
		EkiOnOff
	}


pm1004vMonupRmonMulticastCntIndex OBJECT-TYPE
	SYNTAX  INTEGER(0..128)
	MAX-ACCESS  read-only
	STATUS current
	DESCRIPTION
        "
        Index definition for the pm1004vMonupRmonMulticastCnt
        table
        "
	::= { pm1004vMonupRmonMulticastCntEntry 1 }


pm1004vMonupRmonMulticastCntValuePortn OBJECT-TYPE
	SYNTAX  Counter64
	MAX-ACCESS read-only
	STATUS current
	DESCRIPTION
        "
        Client Input Multicast Packets
        :This counter is increased each
        time a Multicast packet is received
        on the client port  <Help>  This
        counter gives the number of Multicast
        packets received on the client
         port
        "
	::= { pm1004vMonupRmonMulticastCntEntry 2 }


pm1004vMonupRmonMulticastCntErrorPortn OBJECT-TYPE
	SYNTAX  EkiOnOff
	MAX-ACCESS read-only
	STATUS current
	DESCRIPTION
        "
        Multicast Counter Error :This
         OID when set indicates the Multicast
        counter value is invalid on clinet
        port
        "
	::= { pm1004vMonupRmonMulticastCntEntry 3 }


pm1004vMonupRmonMulticastCntOverloadPortn OBJECT-TYPE
	SYNTAX  EkiOnOff
	MAX-ACCESS read-only
	STATUS current
	DESCRIPTION
        "
        Multicast Counter Overload :This
        OID when set indicates a Multicast
        counter overload on client port
        "
	::= { pm1004vMonupRmonMulticastCntEntry 4 }


--- *********************************************************
---     TABLE for the pm1004vMonupLineRmonByteCnt articles
--- *********************************************************

pm1004vMonupLineRmonByteCntTable OBJECT-TYPE
	SYNTAX  SEQUENCE OF Pm1004vMonupLineRmonByteCntEntry
	MAX-ACCESS not-accessible
	STATUS current
	DESCRIPTION
        "
        List of pm1004vMonupLineRmonByteCnt
        Article
        "
	::= { pm1004vMonClientRmonCounter 208 }


pm1004vMonupLineRmonByteCntEntry OBJECT-TYPE
	SYNTAX Pm1004vMonupLineRmonByteCntEntry
	MAX-ACCESS not-accessible
	STATUS current
	DESCRIPTION
        "
        Row definition for the pm1004vMonupLineRmonByteCnt
        table
        "
	INDEX   { pm1004vMonupLineRmonByteCntIndex }
	::= { pm1004vMonupLineRmonByteCntTable 1 }


Pm1004vMonupLineRmonByteCntEntry ::=
	SEQUENCE {
	pm1004vMonupLineRmonByteCntIndex
		INTEGER,
	pm1004vMonupLineRmonByteCntValuePortn
		Counter64,
	pm1004vMonupLineRmonByteCntErrorPortn
		EkiOnOff,
	pm1004vMonupLineRmonByteCntOverloadPortn
		EkiOnOff
	}


pm1004vMonupLineRmonByteCntIndex OBJECT-TYPE
	SYNTAX  INTEGER(0..128)
	MAX-ACCESS  read-only
	STATUS current
	DESCRIPTION
        "
        Index definition for the pm1004vMonupLineRmonByteCnt
        table
        "
	::= { pm1004vMonupLineRmonByteCntEntry 1 }


pm1004vMonupLineRmonByteCntValuePortn OBJECT-TYPE
	SYNTAX  Counter64
	MAX-ACCESS read-only
	STATUS current
	DESCRIPTION
        "
        Line Input Bytes :This counter
        is increased each time a data byte
        is received on the Line port  <Help>
         This counter gives the number
         of bytes received on the Line
         port
        "
	::= { pm1004vMonupLineRmonByteCntEntry 2 }


pm1004vMonupLineRmonByteCntErrorPortn OBJECT-TYPE
	SYNTAX  EkiOnOff
	MAX-ACCESS read-only
	STATUS current
	DESCRIPTION
        "
        Bytes Counter Error :This OID
         when set indicates the Bytes counter
        value is invalid on line port
        "
	::= { pm1004vMonupLineRmonByteCntEntry 3 }


pm1004vMonupLineRmonByteCntOverloadPortn OBJECT-TYPE
	SYNTAX  EkiOnOff
	MAX-ACCESS read-only
	STATUS current
	DESCRIPTION
        "
        Bytes Counter Overload :This OID
        when set indicates a Bytes counter
        overload on line port
        "
	::= { pm1004vMonupLineRmonByteCntEntry 4 }


--- *********************************************************
---     TABLE for the pm1004vMonupLineRmonCrcErrorCnt articles
--- *********************************************************

pm1004vMonupLineRmonCrcErrorCntTable OBJECT-TYPE
	SYNTAX  SEQUENCE OF Pm1004vMonupLineRmonCrcErrorCntEntry
	MAX-ACCESS not-accessible
	STATUS current
	DESCRIPTION
        "
        List of pm1004vMonupLineRmonCrcErrorCnt
        Article
        "
	::= { pm1004vMonClientRmonCounter 209 }


pm1004vMonupLineRmonCrcErrorCntEntry OBJECT-TYPE
	SYNTAX Pm1004vMonupLineRmonCrcErrorCntEntry
	MAX-ACCESS not-accessible
	STATUS current
	DESCRIPTION
        "
        Row definition for the pm1004vMonupLineRmonCrcErrorCnt
        table
        "
	INDEX   { pm1004vMonupLineRmonCrcErrorCntIndex }
	::= { pm1004vMonupLineRmonCrcErrorCntTable 1 }


Pm1004vMonupLineRmonCrcErrorCntEntry ::=
	SEQUENCE {
	pm1004vMonupLineRmonCrcErrorCntIndex
		INTEGER,
	pm1004vMonupLineRmonCrcErrorCntValuePortn
		Counter64,
	pm1004vMonupLineRmonCrcErrorCntErrorPortn
		EkiOnOff,
	pm1004vMonupLineRmonCrcErrorCntOverloadPortn
		EkiOnOff
	}


pm1004vMonupLineRmonCrcErrorCntIndex OBJECT-TYPE
	SYNTAX  INTEGER(0..128)
	MAX-ACCESS  read-only
	STATUS current
	DESCRIPTION
        "
        Index definition for the pm1004vMonupLineRmonCrcErrorCnt
        table
        "
	::= { pm1004vMonupLineRmonCrcErrorCntEntry 1 }


pm1004vMonupLineRmonCrcErrorCntValuePortn OBJECT-TYPE
	SYNTAX  Counter64
	MAX-ACCESS read-only
	STATUS current
	DESCRIPTION
        "
        Line Input CRC Errors :This counter
        is increased each time a CRC error
        is detected on the Line port  <Help>
         This counter gives the number
         of CRC Errors received on the
         Line port
        "
	::= { pm1004vMonupLineRmonCrcErrorCntEntry 2 }


pm1004vMonupLineRmonCrcErrorCntErrorPortn OBJECT-TYPE
	SYNTAX  EkiOnOff
	MAX-ACCESS read-only
	STATUS current
	DESCRIPTION
        "
        CRC Errors Counter Error :This
        OID when set indicates the CRC
         Errors counter value is invalid
        on line port
        "
	::= { pm1004vMonupLineRmonCrcErrorCntEntry 3 }


pm1004vMonupLineRmonCrcErrorCntOverloadPortn OBJECT-TYPE
	SYNTAX  EkiOnOff
	MAX-ACCESS read-only
	STATUS current
	DESCRIPTION
        "
        CRC Errors Counter Overload :This
        OID when set indicates a CRC Errors
        counter overload on line port
        "
	::= { pm1004vMonupLineRmonCrcErrorCntEntry 4 }


--- *********************************************************
---     TABLE for the pm1004vMonupLineRmonPacketsCnt articles
--- *********************************************************

pm1004vMonupLineRmonPacketsCntTable OBJECT-TYPE
	SYNTAX  SEQUENCE OF Pm1004vMonupLineRmonPacketsCntEntry
	MAX-ACCESS not-accessible
	STATUS current
	DESCRIPTION
        "
        List of pm1004vMonupLineRmonPacketsCnt
        Article
        "
	::= { pm1004vMonClientRmonCounter 210 }


pm1004vMonupLineRmonPacketsCntEntry OBJECT-TYPE
	SYNTAX Pm1004vMonupLineRmonPacketsCntEntry
	MAX-ACCESS not-accessible
	STATUS current
	DESCRIPTION
        "
        Row definition for the pm1004vMonupLineRmonPacketsCnt
        table
        "
	INDEX   { pm1004vMonupLineRmonPacketsCntIndex }
	::= { pm1004vMonupLineRmonPacketsCntTable 1 }


Pm1004vMonupLineRmonPacketsCntEntry ::=
	SEQUENCE {
	pm1004vMonupLineRmonPacketsCntIndex
		INTEGER,
	pm1004vMonupLineRmonPacketsCntValuePortn
		Counter64,
	pm1004vMonupLineRmonPacketsCntErrorPortn
		EkiOnOff,
	pm1004vMonupLineRmonPacketsCntOverloadPortn
		EkiOnOff
	}


pm1004vMonupLineRmonPacketsCntIndex OBJECT-TYPE
	SYNTAX  INTEGER(0..128)
	MAX-ACCESS  read-only
	STATUS current
	DESCRIPTION
        "
        Index definition for the pm1004vMonupLineRmonPacketsCnt
        table
        "
	::= { pm1004vMonupLineRmonPacketsCntEntry 1 }


pm1004vMonupLineRmonPacketsCntValuePortn OBJECT-TYPE
	SYNTAX  Counter64
	MAX-ACCESS read-only
	STATUS current
	DESCRIPTION
        "
        Line Input Packets :This counter
        is increased each time a packet
        is received on the Line port  <Help>
         This counter gives the number
         of packets received on the Line
        port
        "
	::= { pm1004vMonupLineRmonPacketsCntEntry 2 }


pm1004vMonupLineRmonPacketsCntErrorPortn OBJECT-TYPE
	SYNTAX  EkiOnOff
	MAX-ACCESS read-only
	STATUS current
	DESCRIPTION
        "
        Packets Counter Error :This OID
        when set indicates the Packets
         counter value is invalid on client
        port
        "
	::= { pm1004vMonupLineRmonPacketsCntEntry 3 }


pm1004vMonupLineRmonPacketsCntOverloadPortn OBJECT-TYPE
	SYNTAX  EkiOnOff
	MAX-ACCESS read-only
	STATUS current
	DESCRIPTION
        "
        Packets Counter Overload :This
        OID when set indicates a Packets
        counter overload on line port
        "
	::= { pm1004vMonupLineRmonPacketsCntEntry 4 }


pm1004vMonCountersReset  OBJECT-TYPE
	SYNTAX EkiOnOff
	MAX-ACCESS read-write
	STATUS current
	DESCRIPTION
	"RMON Counters Reset:This OID resets and restarts all the RMON counters"
	::= { pm1004vMonRmon   359 }

pm1004vMonCountersStop  OBJECT-TYPE
	SYNTAX EkiOnOff
	MAX-ACCESS read-write
	STATUS current
	DESCRIPTION
	"RMON Counters stop:This OID stops all the RMON counters"
	::= { pm1004vMonRmon  360 }






--- *****************************************************
--- $$$$$$$$$$$$$$$$$$$$$$$$$$$$$$$$$$$$$$$$$$$$$$$$$$$$$
---     MEASURES
--- $$$$$$$$$$$$$$$$$$$$$$$$$$$$$$$$$$$$$$$$$$$$$$$$$$$$$
--- *****************************************************



pm1004vMesrsynth0 OBJECT-TYPE
	  SYNTAX EkiMeasureType
	  MAX-ACCESS read-only
	  STATUS deprecated
	  DESCRIPTION
        "
        Not Used :This OID gives the unit
        used on AUX1 measurement of XFP#1
         (Unit = )
        "
	  ::= { pm1004vMesrOther 0 }



pm1004vMesrsynth1 OBJECT-TYPE
	  SYNTAX EkiMeasureType
	  MAX-ACCESS read-only
	  STATUS deprecated
	  DESCRIPTION
        "
        Not Used :This OID gives the unit
        used on AUX2 measurement of XFP#1
         (Unit = )
        "
	  ::= { pm1004vMesrOther 1 }



--- *********************************************************
---     TABLE for the pm1004vMesrtempMeas articles
--- *********************************************************

pm1004vMesrtempMeasTable OBJECT-TYPE
	SYNTAX  SEQUENCE OF Pm1004vMesrtempMeasEntry
	MAX-ACCESS not-accessible
	STATUS current
	DESCRIPTION
        "
        List of pm1004vMesrtempMeas Article
        "
	::= { pm1004vMesrClient 16 }


pm1004vMesrtempMeasEntry OBJECT-TYPE
	SYNTAX Pm1004vMesrtempMeasEntry
	MAX-ACCESS not-accessible
	STATUS current
	DESCRIPTION
        "
        Row definition for the pm1004vMesrtempMeas
        table
        "
	INDEX   { pm1004vMesrtempMeasIndex }
	::= { pm1004vMesrtempMeasTable 1 }


Pm1004vMesrtempMeasEntry ::=
	SEQUENCE {
	pm1004vMesrtempMeasIndex
		INTEGER,
	pm1004vMesrtempMeasPortn
		INTEGER
	}


pm1004vMesrtempMeasIndex OBJECT-TYPE
	SYNTAX  INTEGER(0..128)
	MAX-ACCESS  read-only
	STATUS current
	DESCRIPTION
        "
        Index definition for the pm1004vMesrtempMeas
        table
        "
	::= { pm1004vMesrtempMeasEntry 1 }


pm1004vMesrtempMeasPortn OBJECT-TYPE
	SYNTAX  INTEGER (0..65535)
	MAX-ACCESS read-only
	STATUS current
	DESCRIPTION
        "
        Client SFP Temperature :This OID
        gives the temperature value of
         the SFP plugged in port, read
         from the DDM (Digital Diagnostic
        Monitoring) (Temperature = AV/256)
        (Unit = C)  <Help>  This measure
        gives the temperature of the client
        transceiver
        "
	::= { pm1004vMesrtempMeasEntry 2 }


--- *********************************************************
---     TABLE for the pm1004vMesrvoltMeas articles
--- *********************************************************

pm1004vMesrvoltMeasTable OBJECT-TYPE
	SYNTAX  SEQUENCE OF Pm1004vMesrvoltMeasEntry
	MAX-ACCESS not-accessible
	STATUS current
	DESCRIPTION
        "
        List of pm1004vMesrvoltMeas Article
        "
	::= { pm1004vMesrClient 24 }


pm1004vMesrvoltMeasEntry OBJECT-TYPE
	SYNTAX Pm1004vMesrvoltMeasEntry
	MAX-ACCESS not-accessible
	STATUS current
	DESCRIPTION
        "
        Row definition for the pm1004vMesrvoltMeas
        table
        "
	INDEX   { pm1004vMesrvoltMeasIndex }
	::= { pm1004vMesrvoltMeasTable 1 }


Pm1004vMesrvoltMeasEntry ::=
	SEQUENCE {
	pm1004vMesrvoltMeasIndex
		INTEGER,
	pm1004vMesrvoltMeasPortn
		INTEGER
	}


pm1004vMesrvoltMeasIndex OBJECT-TYPE
	SYNTAX  INTEGER(0..128)
	MAX-ACCESS  read-only
	STATUS current
	DESCRIPTION
        "
        Index definition for the pm1004vMesrvoltMeas
        table
        "
	::= { pm1004vMesrvoltMeasEntry 1 }


pm1004vMesrvoltMeasPortn OBJECT-TYPE
	SYNTAX  INTEGER (0..65535)
	MAX-ACCESS read-only
	STATUS current
	DESCRIPTION
        "
        Client SFP Power Supply :This
         OID gives the 3V3 voltage value
        of the SFP plugged into port, read
        from the DDM (Digital Diagnostic
        Monitoring) (Voltage = AV/10000)
        (Unit = V)  <Help>  This measure
        gives the 3V3 voltage of the client
        transceiver
        "
	::= { pm1004vMesrvoltMeasEntry 2 }


--- *********************************************************
---     TABLE for the pm1004vMesrbiasMeas articles
--- *********************************************************

pm1004vMesrbiasMeasTable OBJECT-TYPE
	SYNTAX  SEQUENCE OF Pm1004vMesrbiasMeasEntry
	MAX-ACCESS not-accessible
	STATUS current
	DESCRIPTION
        "
        List of pm1004vMesrbiasMeas Article
        "
	::= { pm1004vMesrClient 32 }


pm1004vMesrbiasMeasEntry OBJECT-TYPE
	SYNTAX Pm1004vMesrbiasMeasEntry
	MAX-ACCESS not-accessible
	STATUS current
	DESCRIPTION
        "
        Row definition for the pm1004vMesrbiasMeas
        table
        "
	INDEX   { pm1004vMesrbiasMeasIndex }
	::= { pm1004vMesrbiasMeasTable 1 }


Pm1004vMesrbiasMeasEntry ::=
	SEQUENCE {
	pm1004vMesrbiasMeasIndex
		INTEGER,
	pm1004vMesrbiasMeasPortn
		INTEGER
	}


pm1004vMesrbiasMeasIndex OBJECT-TYPE
	SYNTAX  INTEGER(0..128)
	MAX-ACCESS  read-only
	STATUS current
	DESCRIPTION
        "
        Index definition for the pm1004vMesrbiasMeas
        table
        "
	::= { pm1004vMesrbiasMeasEntry 1 }


pm1004vMesrbiasMeasPortn OBJECT-TYPE
	SYNTAX  INTEGER (0..65535)
	MAX-ACCESS read-only
	STATUS current
	DESCRIPTION
        "
        Client SFP Laser Bias :This OID
        gives the bias value of the SFP
        plugged into port, read from the
        DDM (Digital Diagnostic Monitoring)
        (Bias = AV/500)  (Unit = mA)  <Help>
         This measure gives the bias of
        the client transceiver
        "
	::= { pm1004vMesrbiasMeasEntry 2 }


--- *********************************************************
---     TABLE for the pm1004vMesrtxpwrMeas articles
--- *********************************************************

pm1004vMesrtxpwrMeasTable OBJECT-TYPE
	SYNTAX  SEQUENCE OF Pm1004vMesrtxpwrMeasEntry
	MAX-ACCESS not-accessible
	STATUS current
	DESCRIPTION
        "
        List of pm1004vMesrtxpwrMeas Article
        "
	::= { pm1004vMesrClient 40 }


pm1004vMesrtxpwrMeasEntry OBJECT-TYPE
	SYNTAX Pm1004vMesrtxpwrMeasEntry
	MAX-ACCESS not-accessible
	STATUS current
	DESCRIPTION
        "
        Row definition for the pm1004vMesrtxpwrMeas
        table
        "
	INDEX   { pm1004vMesrtxpwrMeasIndex }
	::= { pm1004vMesrtxpwrMeasTable 1 }


Pm1004vMesrtxpwrMeasEntry ::=
	SEQUENCE {
	pm1004vMesrtxpwrMeasIndex
		INTEGER,
	pm1004vMesrtxpwrMeasPortn
		INTEGER
	}


pm1004vMesrtxpwrMeasIndex OBJECT-TYPE
	SYNTAX  INTEGER(0..128)
	MAX-ACCESS  read-only
	STATUS current
	DESCRIPTION
        "
        Index definition for the pm1004vMesrtxpwrMeas
        table
        "
	::= { pm1004vMesrtxpwrMeasEntry 1 }


pm1004vMesrtxpwrMeasPortn OBJECT-TYPE
	SYNTAX  INTEGER (0..65535)
	MAX-ACCESS read-only
	STATUS current
	DESCRIPTION
        "
        Client SFP Tx Power :This OID
         gives the transmit power value
        of the SFP plugged into port, read
        from the DDM (Digital Diagnostic
        Monitoring) (Power = 10*log(AV)-40)
        (Unit = dBm)  <Help>  This measure
        gives the Tx optical power of the
        client transceiver
        "
	::= { pm1004vMesrtxpwrMeasEntry 2 }


--- *********************************************************
---     TABLE for the pm1004vMesrrxpwrMeas articles
--- *********************************************************

pm1004vMesrrxpwrMeasTable OBJECT-TYPE
	SYNTAX  SEQUENCE OF Pm1004vMesrrxpwrMeasEntry
	MAX-ACCESS not-accessible
	STATUS current
	DESCRIPTION
        "
        List of pm1004vMesrrxpwrMeas Article
        "
	::= { pm1004vMesrClient 48 }


pm1004vMesrrxpwrMeasEntry OBJECT-TYPE
	SYNTAX Pm1004vMesrrxpwrMeasEntry
	MAX-ACCESS not-accessible
	STATUS current
	DESCRIPTION
        "
        Row definition for the pm1004vMesrrxpwrMeas
        table
        "
	INDEX   { pm1004vMesrrxpwrMeasIndex }
	::= { pm1004vMesrrxpwrMeasTable 1 }


Pm1004vMesrrxpwrMeasEntry ::=
	SEQUENCE {
	pm1004vMesrrxpwrMeasIndex
		INTEGER,
	pm1004vMesrrxpwrMeasPortn
		INTEGER
	}


pm1004vMesrrxpwrMeasIndex OBJECT-TYPE
	SYNTAX  INTEGER(0..128)
	MAX-ACCESS  read-only
	STATUS current
	DESCRIPTION
        "
        Index definition for the pm1004vMesrrxpwrMeas
        table
        "
	::= { pm1004vMesrrxpwrMeasEntry 1 }


pm1004vMesrrxpwrMeasPortn OBJECT-TYPE
	SYNTAX  INTEGER (0..65535)
	MAX-ACCESS read-only
	STATUS current
	DESCRIPTION
        "
        Client SFP Rx Power :This OID
         gives the receive power value
         of the SFP plugged into port,
         read in the DDM (Digital Diagnostic
        Monitoring) (Power = 10*log(AV)-40)
        (Unit = dBm)  <Help>  This measure
        gives the Rx optical power of the
        client transceiver
        "
	::= { pm1004vMesrrxpwrMeasEntry 2 }


--- *********************************************************
---     TABLE for the pm1004vMesrxfp1LxModTempMeas articles
--- *********************************************************

pm1004vMesrxfp1LxModTempMeasTable OBJECT-TYPE
	SYNTAX  SEQUENCE OF Pm1004vMesrxfp1LxModTempMeasEntry
	MAX-ACCESS not-accessible
	STATUS current
	DESCRIPTION
        "
        List of pm1004vMesrxfp1LxModTempMeas
        Article
        "
	::= { pm1004vMesrLine 208 }


pm1004vMesrxfp1LxModTempMeasEntry OBJECT-TYPE
	SYNTAX Pm1004vMesrxfp1LxModTempMeasEntry
	MAX-ACCESS not-accessible
	STATUS current
	DESCRIPTION
        "
        Row definition for the pm1004vMesrxfp1LxModTempMeas
        table
        "
	INDEX   { pm1004vMesrxfp1LxModTempMeasIndex }
	::= { pm1004vMesrxfp1LxModTempMeasTable 1 }


Pm1004vMesrxfp1LxModTempMeasEntry ::=
	SEQUENCE {
	pm1004vMesrxfp1LxModTempMeasIndex
		INTEGER,
	pm1004vMesrxfp1LxModTempMeasPortn
		INTEGER
	}


pm1004vMesrxfp1LxModTempMeasIndex OBJECT-TYPE
	SYNTAX  INTEGER(0..128)
	MAX-ACCESS  read-only
	STATUS current
	DESCRIPTION
        "
        Index definition for the pm1004vMesrxfp1LxModTempMeas
        table
        "
	::= { pm1004vMesrxfp1LxModTempMeasEntry 1 }


pm1004vMesrxfp1LxModTempMeasPortn OBJECT-TYPE
	SYNTAX  INTEGER (0..65535)
	MAX-ACCESS read-only
	STATUS current
	DESCRIPTION
        "
        Line Optical Module Temperature
        :This OID gives the temperature
        of the XFP or OTX plugged in line#n,
        read from the DDM (Digital Diagnostic
        Monitoring) (Temperature = AV/256)
        (Unit = C)  <Help>  This measure
        gives the temperature of the line
        transceiver
        "
	::= { pm1004vMesrxfp1LxModTempMeasEntry 2 }


--- *********************************************************
---     TABLE for the pm1004vMesrxfp1Reserved articles
--- *********************************************************

pm1004vMesrxfp1ReservedTable OBJECT-TYPE
	SYNTAX  SEQUENCE OF Pm1004vMesrxfp1ReservedEntry
	MAX-ACCESS not-accessible
	STATUS deprecated
	DESCRIPTION
        "
        List of pm1004vMesrxfp1Reserved
        Article
        "
	::= { pm1004vMesrLine 209 }


pm1004vMesrxfp1ReservedEntry OBJECT-TYPE
	SYNTAX Pm1004vMesrxfp1ReservedEntry
	MAX-ACCESS not-accessible
	STATUS deprecated
	DESCRIPTION
        "
        Row definition for the pm1004vMesrxfp1Reserved
        table
        "
	INDEX   { pm1004vMesrxfp1ReservedIndex }
	::= { pm1004vMesrxfp1ReservedTable 1 }


Pm1004vMesrxfp1ReservedEntry ::=
	SEQUENCE {
	pm1004vMesrxfp1ReservedIndex
		INTEGER,
	pm1004vMesrxfp1ReservedPortn
		INTEGER
	}


pm1004vMesrxfp1ReservedIndex OBJECT-TYPE
	SYNTAX  INTEGER(0..128)
	MAX-ACCESS  read-only
	STATUS deprecated
	DESCRIPTION
        "
        Index definition for the pm1004vMesrxfp1Reserved
        table
        "
	::= { pm1004vMesrxfp1ReservedEntry 1 }


pm1004vMesrxfp1ReservedPortn OBJECT-TYPE
	SYNTAX  INTEGER (0..65535)
	MAX-ACCESS read-only
	STATUS deprecated
	DESCRIPTION
        "
        Not Used :Reserved
        "
	::= { pm1004vMesrxfp1ReservedEntry 2 }


--- *********************************************************
---     TABLE for the pm1004vMesrxfp1LoBiasCurrentMeas articles
--- *********************************************************

pm1004vMesrxfp1LoBiasCurrentMeasTable OBJECT-TYPE
	SYNTAX  SEQUENCE OF Pm1004vMesrxfp1LoBiasCurrentMeasEntry
	MAX-ACCESS not-accessible
	STATUS current
	DESCRIPTION
        "
        List of pm1004vMesrxfp1LoBiasCurrentMeas
        Article
        "
	::= { pm1004vMesrLine 210 }


pm1004vMesrxfp1LoBiasCurrentMeasEntry OBJECT-TYPE
	SYNTAX Pm1004vMesrxfp1LoBiasCurrentMeasEntry
	MAX-ACCESS not-accessible
	STATUS current
	DESCRIPTION
        "
        Row definition for the pm1004vMesrxfp1LoBiasCurrentMeas
        table
        "
	INDEX   { pm1004vMesrxfp1LoBiasCurrentMeasIndex }
	::= { pm1004vMesrxfp1LoBiasCurrentMeasTable 1 }


Pm1004vMesrxfp1LoBiasCurrentMeasEntry ::=
	SEQUENCE {
	pm1004vMesrxfp1LoBiasCurrentMeasIndex
		INTEGER,
	pm1004vMesrxfp1LoBiasCurrentMeasPortn
		INTEGER
	}


pm1004vMesrxfp1LoBiasCurrentMeasIndex OBJECT-TYPE
	SYNTAX  INTEGER(0..128)
	MAX-ACCESS  read-only
	STATUS current
	DESCRIPTION
        "
        Index definition for the pm1004vMesrxfp1LoBiasCurrentMeas
        table
        "
	::= { pm1004vMesrxfp1LoBiasCurrentMeasEntry 1 }


pm1004vMesrxfp1LoBiasCurrentMeasPortn OBJECT-TYPE
	SYNTAX  INTEGER (0..65535)
	MAX-ACCESS read-only
	STATUS current
	DESCRIPTION
        "
        Line Optical Module Laser Bias
        :This OID gives the bias value
         of the XFP or OTX plugged in line
        #n, read from the DDM (Digital
         Diagnostic Monitoring) (Bias =
        AV/500) (Unit = mA)  <Help>  This
        measure gives the bias of the line
        transceiver
        "
	::= { pm1004vMesrxfp1LoBiasCurrentMeasEntry 2 }


--- *********************************************************
---     TABLE for the pm1004vMesrxfp1LoTxPowerMeas articles
--- *********************************************************

pm1004vMesrxfp1LoTxPowerMeasTable OBJECT-TYPE
	SYNTAX  SEQUENCE OF Pm1004vMesrxfp1LoTxPowerMeasEntry
	MAX-ACCESS not-accessible
	STATUS current
	DESCRIPTION
        "
        List of pm1004vMesrxfp1LoTxPowerMeas
        Article
        "
	::= { pm1004vMesrLine 211 }


pm1004vMesrxfp1LoTxPowerMeasEntry OBJECT-TYPE
	SYNTAX Pm1004vMesrxfp1LoTxPowerMeasEntry
	MAX-ACCESS not-accessible
	STATUS current
	DESCRIPTION
        "
        Row definition for the pm1004vMesrxfp1LoTxPowerMeas
        table
        "
	INDEX   { pm1004vMesrxfp1LoTxPowerMeasIndex }
	::= { pm1004vMesrxfp1LoTxPowerMeasTable 1 }


Pm1004vMesrxfp1LoTxPowerMeasEntry ::=
	SEQUENCE {
	pm1004vMesrxfp1LoTxPowerMeasIndex
		INTEGER,
	pm1004vMesrxfp1LoTxPowerMeasPortn
		INTEGER
	}


pm1004vMesrxfp1LoTxPowerMeasIndex OBJECT-TYPE
	SYNTAX  INTEGER(0..128)
	MAX-ACCESS  read-only
	STATUS current
	DESCRIPTION
        "
        Index definition for the pm1004vMesrxfp1LoTxPowerMeas
        table
        "
	::= { pm1004vMesrxfp1LoTxPowerMeasEntry 1 }


pm1004vMesrxfp1LoTxPowerMeasPortn OBJECT-TYPE
	SYNTAX  INTEGER (0..65535)
	MAX-ACCESS read-only
	STATUS current
	DESCRIPTION
        "
        Line Optical Module Tx Power :This
        OID gives the transmit power value
        of the XFP or OTX plugged in line
        #n, read from the DDM (Digital
           Diagnostic Monitoring) (Power
        = 10*log(AV)-40) (Unit = dBm)
         <Help>  This measure gives the
        Tx optical power of the line transceiver
        "
	::= { pm1004vMesrxfp1LoTxPowerMeasEntry 2 }


--- *********************************************************
---     TABLE for the pm1004vMesrxfp1LiRxPowerMeas articles
--- *********************************************************

pm1004vMesrxfp1LiRxPowerMeasTable OBJECT-TYPE
	SYNTAX  SEQUENCE OF Pm1004vMesrxfp1LiRxPowerMeasEntry
	MAX-ACCESS not-accessible
	STATUS current
	DESCRIPTION
        "
        List of pm1004vMesrxfp1LiRxPowerMeas
        Article
        "
	::= { pm1004vMesrLine 212 }


pm1004vMesrxfp1LiRxPowerMeasEntry OBJECT-TYPE
	SYNTAX Pm1004vMesrxfp1LiRxPowerMeasEntry
	MAX-ACCESS not-accessible
	STATUS current
	DESCRIPTION
        "
        Row definition for the pm1004vMesrxfp1LiRxPowerMeas
        table
        "
	INDEX   { pm1004vMesrxfp1LiRxPowerMeasIndex }
	::= { pm1004vMesrxfp1LiRxPowerMeasTable 1 }


Pm1004vMesrxfp1LiRxPowerMeasEntry ::=
	SEQUENCE {
	pm1004vMesrxfp1LiRxPowerMeasIndex
		INTEGER,
	pm1004vMesrxfp1LiRxPowerMeasPortn
		INTEGER
	}


pm1004vMesrxfp1LiRxPowerMeasIndex OBJECT-TYPE
	SYNTAX  INTEGER(0..128)
	MAX-ACCESS  read-only
	STATUS current
	DESCRIPTION
        "
        Index definition for the pm1004vMesrxfp1LiRxPowerMeas
        table
        "
	::= { pm1004vMesrxfp1LiRxPowerMeasEntry 1 }


pm1004vMesrxfp1LiRxPowerMeasPortn OBJECT-TYPE
	SYNTAX  INTEGER (0..65535)
	MAX-ACCESS read-only
	STATUS current
	DESCRIPTION
        "
        Line Optical Module Rx Power :This
        OID gives the receive power value
        of the XFP or OTX plugged in line
        #n, read from the DDM (Digital
         Diagnostic Monitoring) (Power
         = 10*log(AV)-40)  (Unit = dBm)
         <Help>  This measure gives the
        Rx optical power of the line transceiver
        "
	::= { pm1004vMesrxfp1LiRxPowerMeasEntry 2 }


--- *********************************************************
---     TABLE for the pm1004vMesrxfp1LxAux1Meas articles
--- *********************************************************

pm1004vMesrxfp1LxAux1MeasTable OBJECT-TYPE
	SYNTAX  SEQUENCE OF Pm1004vMesrxfp1LxAux1MeasEntry
	MAX-ACCESS not-accessible
	STATUS deprecated
	DESCRIPTION
        "
        List of pm1004vMesrxfp1LxAux1Meas
        Article
        "
	::= { pm1004vMesrLine 213 }


pm1004vMesrxfp1LxAux1MeasEntry OBJECT-TYPE
	SYNTAX Pm1004vMesrxfp1LxAux1MeasEntry
	MAX-ACCESS not-accessible
	STATUS deprecated
	DESCRIPTION
        "
        Row definition for the pm1004vMesrxfp1LxAux1Meas
        table
        "
	INDEX   { pm1004vMesrxfp1LxAux1MeasIndex }
	::= { pm1004vMesrxfp1LxAux1MeasTable 1 }


Pm1004vMesrxfp1LxAux1MeasEntry ::=
	SEQUENCE {
	pm1004vMesrxfp1LxAux1MeasIndex
		INTEGER,
	pm1004vMesrxfp1LxAux1MeasPortn
		INTEGER
	}


pm1004vMesrxfp1LxAux1MeasIndex OBJECT-TYPE
	SYNTAX  INTEGER(0..128)
	MAX-ACCESS  read-only
	STATUS deprecated
	DESCRIPTION
        "
        Index definition for the pm1004vMesrxfp1LxAux1Meas
        table
        "
	::= { pm1004vMesrxfp1LxAux1MeasEntry 1 }


pm1004vMesrxfp1LxAux1MeasPortn OBJECT-TYPE
	SYNTAX  INTEGER (0..65535)
	MAX-ACCESS read-only
	STATUS deprecated
	DESCRIPTION
        "
        Not Used :This OID gives the receive
        power value read in the DDM (Digital
        Diagnostic Monitoring) of the XFP
        or OTX plugged in line #n (Unit
        = ?)
        "
	::= { pm1004vMesrxfp1LxAux1MeasEntry 2 }


--- *********************************************************
---     TABLE for the pm1004vMesrxfp1LxAux2Meas articles
--- *********************************************************

pm1004vMesrxfp1LxAux2MeasTable OBJECT-TYPE
	SYNTAX  SEQUENCE OF Pm1004vMesrxfp1LxAux2MeasEntry
	MAX-ACCESS not-accessible
	STATUS deprecated
	DESCRIPTION
        "
        List of pm1004vMesrxfp1LxAux2Meas
        Article
        "
	::= { pm1004vMesrLine 214 }


pm1004vMesrxfp1LxAux2MeasEntry OBJECT-TYPE
	SYNTAX Pm1004vMesrxfp1LxAux2MeasEntry
	MAX-ACCESS not-accessible
	STATUS deprecated
	DESCRIPTION
        "
        Row definition for the pm1004vMesrxfp1LxAux2Meas
        table
        "
	INDEX   { pm1004vMesrxfp1LxAux2MeasIndex }
	::= { pm1004vMesrxfp1LxAux2MeasTable 1 }


Pm1004vMesrxfp1LxAux2MeasEntry ::=
	SEQUENCE {
	pm1004vMesrxfp1LxAux2MeasIndex
		INTEGER,
	pm1004vMesrxfp1LxAux2MeasPortn
		INTEGER
	}


pm1004vMesrxfp1LxAux2MeasIndex OBJECT-TYPE
	SYNTAX  INTEGER(0..128)
	MAX-ACCESS  read-only
	STATUS deprecated
	DESCRIPTION
        "
        Index definition for the pm1004vMesrxfp1LxAux2Meas
        table
        "
	::= { pm1004vMesrxfp1LxAux2MeasEntry 1 }


pm1004vMesrxfp1LxAux2MeasPortn OBJECT-TYPE
	SYNTAX  INTEGER (0..65535)
	MAX-ACCESS read-only
	STATUS deprecated
	DESCRIPTION
        "
        Not Used :This OID gives the receive
        power value read in the DDM (Digital
        Diagnostic Monitoring) of the XFP
        or OTX plugged in line #n (Unit
        = ?)
        "
	::= { pm1004vMesrxfp1LxAux2MeasEntry 2 }


--- *********************************************************
---     TABLE for the pm1004vMesrotx1Aging articles
--- *********************************************************

pm1004vMesrotx1AgingTable OBJECT-TYPE
	SYNTAX  SEQUENCE OF Pm1004vMesrotx1AgingEntry
	MAX-ACCESS not-accessible
	STATUS current
	DESCRIPTION
        "
        List of pm1004vMesrotx1Aging Article
        "
	::= { pm1004vMesrLine 224 }


pm1004vMesrotx1AgingEntry OBJECT-TYPE
	SYNTAX Pm1004vMesrotx1AgingEntry
	MAX-ACCESS not-accessible
	STATUS current
	DESCRIPTION
        "
        Row definition for the pm1004vMesrotx1Aging
        table
        "
	INDEX   { pm1004vMesrotx1AgingIndex }
	::= { pm1004vMesrotx1AgingTable 1 }


Pm1004vMesrotx1AgingEntry ::=
	SEQUENCE {
	pm1004vMesrotx1AgingIndex
		INTEGER,
	pm1004vMesrotx1AgingPortn
		INTEGER
	}


pm1004vMesrotx1AgingIndex OBJECT-TYPE
	SYNTAX  INTEGER(0..128)
	MAX-ACCESS  read-only
	STATUS current
	DESCRIPTION
        "
        Index definition for the pm1004vMesrotx1Aging
        table
        "
	::= { pm1004vMesrotx1AgingEntry 1 }


pm1004vMesrotx1AgingPortn OBJECT-TYPE
	SYNTAX  INTEGER (0..65535)
	MAX-ACCESS read-only
	STATUS current
	DESCRIPTION
        "
        Line OTX TLH Aging :This OID gives
        the aging of the Line OTX TLH,
         read from the DDM (Digital Diagnostic
        Monitoring)   (Aging = AV) (Unit
        = %)  <Help>  This measure gives
        the aging of the Line OTX TLH
        "
	::= { pm1004vMesrotx1AgingEntry 2 }


--- *********************************************************
---     TABLE for the pm1004vMesrotx1LaserTemperature articles
--- *********************************************************

pm1004vMesrotx1LaserTemperatureTable OBJECT-TYPE
	SYNTAX  SEQUENCE OF Pm1004vMesrotx1LaserTemperatureEntry
	MAX-ACCESS not-accessible
	STATUS deprecated
	DESCRIPTION
        "
        List of pm1004vMesrotx1LaserTemperature
        Article
        "
	::= { pm1004vMesrLine 225 }


pm1004vMesrotx1LaserTemperatureEntry OBJECT-TYPE
	SYNTAX Pm1004vMesrotx1LaserTemperatureEntry
	MAX-ACCESS not-accessible
	STATUS deprecated
	DESCRIPTION
        "
        Row definition for the pm1004vMesrotx1LaserTemperature
        table
        "
	INDEX   { pm1004vMesrotx1LaserTemperatureIndex }
	::= { pm1004vMesrotx1LaserTemperatureTable 1 }


Pm1004vMesrotx1LaserTemperatureEntry ::=
	SEQUENCE {
	pm1004vMesrotx1LaserTemperatureIndex
		INTEGER,
	pm1004vMesrotx1LaserTemperaturePortn
		INTEGER
	}


pm1004vMesrotx1LaserTemperatureIndex OBJECT-TYPE
	SYNTAX  INTEGER(0..128)
	MAX-ACCESS  read-only
	STATUS deprecated
	DESCRIPTION
        "
        Index definition for the pm1004vMesrotx1LaserTemperature
        table
        "
	::= { pm1004vMesrotx1LaserTemperatureEntry 1 }


pm1004vMesrotx1LaserTemperaturePortn OBJECT-TYPE
	SYNTAX  INTEGER (0..65535)
	MAX-ACCESS read-only
	STATUS deprecated
	DESCRIPTION
        "
        Line OTX TLH Laser Temperature
        :This OID gives the laser temperature
        of the Line OTX TLH, read from
         the DDM (Digital Diagnostic Monitoring)
        (Temperature = AV/256) (Unit =
         C)  <Help>  This measure gives
        the laser temperature of the Line
        OTX TLH
        "
	::= { pm1004vMesrotx1LaserTemperatureEntry 2 }


--- *********************************************************
---     TABLE for the pm1004vMesrotx1FreqDeviation articles
--- *********************************************************

pm1004vMesrotx1FreqDeviationTable OBJECT-TYPE
	SYNTAX  SEQUENCE OF Pm1004vMesrotx1FreqDeviationEntry
	MAX-ACCESS not-accessible
	STATUS current
	DESCRIPTION
        "
        List of pm1004vMesrotx1FreqDeviation
        Article
        "
	::= { pm1004vMesrLine 226 }


pm1004vMesrotx1FreqDeviationEntry OBJECT-TYPE
	SYNTAX Pm1004vMesrotx1FreqDeviationEntry
	MAX-ACCESS not-accessible
	STATUS current
	DESCRIPTION
        "
        Row definition for the pm1004vMesrotx1FreqDeviation
        table
        "
	INDEX   { pm1004vMesrotx1FreqDeviationIndex }
	::= { pm1004vMesrotx1FreqDeviationTable 1 }


Pm1004vMesrotx1FreqDeviationEntry ::=
	SEQUENCE {
	pm1004vMesrotx1FreqDeviationIndex
		INTEGER,
	pm1004vMesrotx1FreqDeviationPortn
		INTEGER
	}


pm1004vMesrotx1FreqDeviationIndex OBJECT-TYPE
	SYNTAX  INTEGER(0..128)
	MAX-ACCESS  read-only
	STATUS current
	DESCRIPTION
        "
        Index definition for the pm1004vMesrotx1FreqDeviation
        table
        "
	::= { pm1004vMesrotx1FreqDeviationEntry 1 }


pm1004vMesrotx1FreqDeviationPortn OBJECT-TYPE
	SYNTAX  INTEGER (0..65535)
	MAX-ACCESS read-only
	STATUS current
	DESCRIPTION
        "
        Line OTX TLH Frequency Deviation
        :This OID gives the frequency deviation
        of the Line OTX TLH, read from
         the DDM (Digital Diagnostic Monitoring)
         (Deviation = (AV-32768)*100) (Unit
        = MHz)  <Help>  This measure gives
        the frequency deviation of the
         Line OTX TLH
        "
	::= { pm1004vMesrotx1FreqDeviationEntry 2 }


--- *********************************************************
---     TABLE for the pm1004vMesrotx1LaserWvlength articles
--- *********************************************************

pm1004vMesrotx1LaserWvlengthTable OBJECT-TYPE
	SYNTAX  SEQUENCE OF Pm1004vMesrotx1LaserWvlengthEntry
	MAX-ACCESS not-accessible
	STATUS current
	DESCRIPTION
        "
        List of pm1004vMesrotx1LaserWvlength
        Article
        "
	::= { pm1004vMesrLine 227 }


pm1004vMesrotx1LaserWvlengthEntry OBJECT-TYPE
	SYNTAX Pm1004vMesrotx1LaserWvlengthEntry
	MAX-ACCESS not-accessible
	STATUS current
	DESCRIPTION
        "
        Row definition for the pm1004vMesrotx1LaserWvlength
        table
        "
	INDEX   { pm1004vMesrotx1LaserWvlengthIndex }
	::= { pm1004vMesrotx1LaserWvlengthTable 1 }


Pm1004vMesrotx1LaserWvlengthEntry ::=
	SEQUENCE {
	pm1004vMesrotx1LaserWvlengthIndex
		INTEGER,
	pm1004vMesrotx1LaserWvlengthPortn
		INTEGER
	}


pm1004vMesrotx1LaserWvlengthIndex OBJECT-TYPE
	SYNTAX  INTEGER(0..128)
	MAX-ACCESS  read-only
	STATUS current
	DESCRIPTION
        "
        Index definition for the pm1004vMesrotx1LaserWvlength
        table
        "
	::= { pm1004vMesrotx1LaserWvlengthEntry 1 }


pm1004vMesrotx1LaserWvlengthPortn OBJECT-TYPE
	SYNTAX  INTEGER (0..65535)
	MAX-ACCESS read-only
	STATUS current
	DESCRIPTION
        "
        Line Optical Module Wavelength
        :This OID gives the laser wavelength
        of the Line OTX TLH, read from
         the DDM (Digital Diagnostic Monitoring)
        (Wavelength=299792458/((193,100+(AV-32768
        )*12,5)*10 3)) (Unit = nm)  <Help>
         This measure gives the laser wavelength
        of the Line OTX TLH
        "
	::= { pm1004vMesrotx1LaserWvlengthEntry 2 }







--- *****************************************************
--- $$$$$$$$$$$$$$$$$$$$$$$$$$$$$$$$$$$$$$$$$$$$$$$$$$$$$
---     DOWNLOAD
--- $$$$$$$$$$$$$$$$$$$$$$$$$$$$$$$$$$$$$$$$$$$$$$$$$$$$$
--- *****************************************************



--- *****************************************************
---     LEAF for the restartProcess article
--- *****************************************************
pm1004vDwlrestartProcess OBJECT IDENTIFIER ::= { pm1004vDwlOther 0 }




pm1004vDwlColdRestartProcessed OBJECT-TYPE
	  SYNTAX EkiOnOff
	  MAX-ACCESS read-only
	  STATUS current
	  DESCRIPTION
        "
        Cold Restart :This OID indicates
        that the module last restart was
        a Cold RESTART
        "
	  ::= { pm1004vDwlrestartProcess 2 }



pm1004vDwlWarmRestartProcessed OBJECT-TYPE
	  SYNTAX EkiOnOff
	  MAX-ACCESS read-only
	  STATUS current
	  DESCRIPTION
        "
        Warm Restart :This OID indicates
        that the module last restart was
        a Warm RESTART
        "
	  ::= { pm1004vDwlrestartProcess 1 }



--- *****************************************************
---     LEAF for the swBanksUsed article
--- *****************************************************
pm1004vDwlswBanksUsed OBJECT IDENTIFIER ::= { pm1004vDwlOther 1 }




pm1004vDwlSwBank2Notempty OBJECT-TYPE
	  SYNTAX EkiOnOff
	  MAX-ACCESS read-only
	  STATUS current
	  DESCRIPTION
        "
        SW bank 2 loaded :This OID indicates
        a software is loaded in SW bank
        2  <Help>  This status indicates
        if the SW bank 2 contains SW package
        "
	  ::= { pm1004vDwlswBanksUsed 6 }



pm1004vDwlSwBank1Notempty OBJECT-TYPE
	  SYNTAX EkiOnOff
	  MAX-ACCESS read-only
	  STATUS current
	  DESCRIPTION
        "
        SW bank 1 loaded :This OID indicates
        a software is loaded in SW bank
        1  <Help>  This status indicates
        if the SW bank 1 contains SW package
        "
	  ::= { pm1004vDwlswBanksUsed 5 }



pm1004vDwlSwBank2Used OBJECT-TYPE
	  SYNTAX EkiOnOff
	  MAX-ACCESS read-only
	  STATUS current
	  DESCRIPTION
        "
        SW bank 2 active :This OID indicates
        the module is working on SW bank
        2  <Help>  This status indicates
        if the SW bank 2 is active or standby
        "
	  ::= { pm1004vDwlswBanksUsed 2 }



pm1004vDwlSwBank1Used OBJECT-TYPE
	  SYNTAX EkiOnOff
	  MAX-ACCESS read-only
	  STATUS current
	  DESCRIPTION
        "
        SW bank 1 active :This OID indicates
        the module is working on SW bank
        1  <Help>  This status indicates
        if the SW bank 1 is active or standby
        "
	  ::= { pm1004vDwlswBanksUsed 1 }



--- *****************************************************
---     LEAF for the gwBanksUsed article
--- *****************************************************
pm1004vDwlgwBanksUsed OBJECT IDENTIFIER ::= { pm1004vDwlOther 2 }




pm1004vDwlGwBank4Notempty OBJECT-TYPE
	  SYNTAX EkiOnOff
	  MAX-ACCESS read-only
	  STATUS current
	  DESCRIPTION
        "
        GW bank 4 loaded :This OID indicates
        a gateware is loaded in GW bank
        4
        "
	  ::= { pm1004vDwlgwBanksUsed 8 }



pm1004vDwlGwBank3Notempty OBJECT-TYPE
	  SYNTAX EkiOnOff
	  MAX-ACCESS read-only
	  STATUS current
	  DESCRIPTION
        "
        GW bank 3 loaded :This OID indicates
        a gateware is loaded in GW bank
        3  <Help>  This status indicates
        if the GW bank 3 contains GW package
        "
	  ::= { pm1004vDwlgwBanksUsed 7 }



pm1004vDwlGwBank2Notempty OBJECT-TYPE
	  SYNTAX EkiOnOff
	  MAX-ACCESS read-only
	  STATUS current
	  DESCRIPTION
        "
        GW bank 2 loaded :This OID indicates
        a gateware is loaded in GW bank
        2
        "
	  ::= { pm1004vDwlgwBanksUsed 6 }



pm1004vDwlGwBank1Notempty OBJECT-TYPE
	  SYNTAX EkiOnOff
	  MAX-ACCESS read-only
	  STATUS current
	  DESCRIPTION
        "
        GW bank 1 loaded  :This OID indicates
        a gateware is loaded in GW bank
        1  <Help>  This status indicates
        if the GW bank 1 contains GW package
        "
	  ::= { pm1004vDwlgwBanksUsed 5 }



pm1004vDwlGwBank4Used OBJECT-TYPE
	  SYNTAX EkiOnOff
	  MAX-ACCESS read-only
	  STATUS current
	  DESCRIPTION
        "
        GW bank 4 active  :This OID indicates
        the module is working on GW bank
        4
        "
	  ::= { pm1004vDwlgwBanksUsed 4 }



pm1004vDwlGwBank3Used OBJECT-TYPE
	  SYNTAX EkiOnOff
	  MAX-ACCESS read-only
	  STATUS current
	  DESCRIPTION
        "
        GW bank 3 active :This OID indicates
        the module is working on GW bank
        3  <Help>  This status indicates
        if the GW bank 3 is active or standby
        "
	  ::= { pm1004vDwlgwBanksUsed 3 }



pm1004vDwlGwBank2Used OBJECT-TYPE
	  SYNTAX EkiOnOff
	  MAX-ACCESS read-only
	  STATUS current
	  DESCRIPTION
        "
        GW bank 2 active :This OID indicates
        the module is working on GW bank
        2
        "
	  ::= { pm1004vDwlgwBanksUsed 2 }



pm1004vDwlGwBank1Used OBJECT-TYPE
	  SYNTAX EkiOnOff
	  MAX-ACCESS read-only
	  STATUS current
	  DESCRIPTION
        "
        GW bank 1 active  :This OID indicates
        the module is working on GW bank
        1  <Help>  This status indicates
        if the GW bank 1 is active or standby
        "
	  ::= { pm1004vDwlgwBanksUsed 1 }








--- *****************************************************
--- $$$$$$$$$$$$$$$$$$$$$$$$$$$$$$$$$$$$$$$$$$$$$$$$$$$$$
---     CONFIG
--- $$$$$$$$$$$$$$$$$$$$$$$$$$$$$$$$$$$$$$$$$$$$$$$$$$$$$
--- *****************************************************



--- *****************************************************
---     LEAF for the table Group accessCAisCsf
--- *****************************************************

pm1004vCfgAccessCAisCsf OBJECT IDENTIFIER ::= { pm1004vConfig 1 }



--- *****************************************************
---     LEAF for the table 0012
--- *****************************************************

pm1004vCfgClientcaiscsfTable OBJECT-TYPE
	SYNTAX  SEQUENCE OF Pm1004vCfgClientcaiscsfEntry
	MAX-ACCESS not-accessible
	STATUS current
	DESCRIPTION
        "
        List of  Article
        "
	::= { pm1004vCfgAccessCAisCsf 1 }


pm1004vCfgClientcaiscsfEntry OBJECT-TYPE
	SYNTAX Pm1004vCfgClientcaiscsfEntry
	MAX-ACCESS not-accessible
	STATUS current
	DESCRIPTION
        "
        Row definition for the accessCAisCsf
        table
        "
	INDEX   { pm1004vCfgClientcaiscsfIndex }
	::= { pm1004vCfgClientcaiscsfTable 1 }


Pm1004vCfgClientcaiscsfEntry ::=
	SEQUENCE {
	pm1004vCfgClientcaiscsfIndex
		INTEGER,
	pm1004vCfgCAisModePortn
		Unsigned32,
	pm1004vCfgUpAccessioAlmPortn
		Unsigned32,
	pm1004vCfgUpMapperDeAlmPortn
		Unsigned32,
	pm1004vCfgDownAccessioAlmPortn
		Unsigned32,
	pm1004vCfgDownMapperDeAlmPortn
		Unsigned32,
	pm1004vCfgDownDfrmAlmPortn
		Unsigned32,
	pm1004vCfgDownLineSyncAlarmsPortn
		Unsigned32
	}


pm1004vCfgClientcaiscsfIndex OBJECT-TYPE
	SYNTAX  INTEGER(0..128)
	MAX-ACCESS  read-only
	STATUS current
	DESCRIPTION
        "
        Index definition for the clientcaiscsf
        table
        "
	::= { pm1004vCfgClientcaiscsfEntry 1 }


pm1004vCfgCAisModePortn OBJECT-TYPE
	SYNTAX  Unsigned32 (0..65536)
	MAX-ACCESS read-write
	STATUS current
	DESCRIPTION
        "
        CAIS mode  on Client Port :This
        register enables/disables port
          laser shutdown on CAIS insertion
        condition
        "
	::= { pm1004vCfgClientcaiscsfEntry 3 }


pm1004vCfgUpAccessioAlmPortn OBJECT-TYPE
	SYNTAX  Unsigned32 (0..65536)
	MAX-ACCESS read-write
	STATUS current
	DESCRIPTION
        "
        CSF contributors on Client Port
        :This register configures the contributors
        to upstream CSF insertion on the
        port.
        "
	::= { pm1004vCfgClientcaiscsfEntry 9 }


pm1004vCfgUpMapperDeAlmPortn OBJECT-TYPE
	SYNTAX  Unsigned32 (0..65536)
	MAX-ACCESS read-write
	STATUS current
	DESCRIPTION
        "
        CSF contributors on Client Port
        :This register configures the contributors
        to upstream CSF insertion on the
        port.
        "
	::= { pm1004vCfgClientcaiscsfEntry 10 }


pm1004vCfgDownAccessioAlmPortn OBJECT-TYPE
	SYNTAX  Unsigned32 (0..65536)
	MAX-ACCESS read-write
	STATUS current
	DESCRIPTION
        "
        CAIS contributors on Client Port
        :This register configures the contributors
        to downstream CAIS insertion on
         port.
        "
	::= { pm1004vCfgClientcaiscsfEntry 17 }


pm1004vCfgDownMapperDeAlmPortn OBJECT-TYPE
	SYNTAX  Unsigned32 (0..65536)
	MAX-ACCESS read-write
	STATUS current
	DESCRIPTION
        "
        CAIS contributors on Client Port
        :This register configures the contributors
        to downstream CAIS insertion on
         port.
        "
	::= { pm1004vCfgClientcaiscsfEntry 18 }


pm1004vCfgDownDfrmAlmPortn OBJECT-TYPE
	SYNTAX  Unsigned32 (0..65536)
	MAX-ACCESS read-write
	STATUS current
	DESCRIPTION
        "
        CAIS contributors on Client Port
        :This register configures the contributors
        to downstream CAIS insertion on
         port.
        "
	::= { pm1004vCfgClientcaiscsfEntry 19 }


pm1004vCfgDownLineSyncAlarmsPortn OBJECT-TYPE
	SYNTAX  Unsigned32 (0..65536)
	MAX-ACCESS read-write
	STATUS deprecated
	DESCRIPTION
        "
        CAIS contributors on Client Port
        :This register configures the contributors
        to downstream CAIS insertion on
         port.
        "
	::= { pm1004vCfgClientcaiscsfEntry 20 }


--- *****************************************************
---     LEAF for the table Group startup
--- *****************************************************

pm1004vCfgStartup OBJECT IDENTIFIER ::= { pm1004vConfig 2 }



--- *****************************************************
---     LEAF for the table 2111
--- *****************************************************

pm1004vCfgClientStartupTable OBJECT-TYPE
	SYNTAX  SEQUENCE OF Pm1004vCfgClientStartupEntry
	MAX-ACCESS not-accessible
	STATUS current
	DESCRIPTION
        "
        List of  Article
        "
	::= { pm1004vCfgStartup 1 }


pm1004vCfgClientStartupEntry OBJECT-TYPE
	SYNTAX Pm1004vCfgClientStartupEntry
	MAX-ACCESS not-accessible
	STATUS current
	DESCRIPTION
        "
        Row definition for the startup
        table
        "
	INDEX   { pm1004vCfgClientStartupIndex }
	::= { pm1004vCfgClientStartupTable 1 }


Pm1004vCfgClientStartupEntry ::=
	SEQUENCE {
	pm1004vCfgClientStartupIndex
		INTEGER,
	pm1004vCfgSystConfPortPortn
		Unsigned32,
	pm1004vCfgNetConfPortPortn
		Unsigned32,
	pm1004vCfgAdddropConfPortPortn
		Unsigned32
	}


pm1004vCfgClientStartupIndex OBJECT-TYPE
	SYNTAX  INTEGER(0..128)
	MAX-ACCESS  read-only
	STATUS current
	DESCRIPTION
        "
        Index definition for the clientStartup
        table
        "
	::= { pm1004vCfgClientStartupEntry 1 }


pm1004vCfgSystConfPortPortn OBJECT-TYPE
	SYNTAX  Unsigned32 (0..65536)
	MAX-ACCESS read-write
	STATUS current
	DESCRIPTION
        "
        Default Settings on Client Port
        :This  register configures the
         default initialisation settings
        on the port.
        "
	::= { pm1004vCfgClientStartupEntry 3 }


pm1004vCfgNetConfPortPortn OBJECT-TYPE
	SYNTAX  Unsigned32 (0..65536)
	MAX-ACCESS read-write
	STATUS current
	DESCRIPTION
        "
        Default Protocol on Client Port
        :This register configures the default
        initialisation protocol on the
         port.
        "
	::= { pm1004vCfgClientStartupEntry 4 }


pm1004vCfgAdddropConfPortPortn OBJECT-TYPE
	SYNTAX  Unsigned32 (0..65536)
	MAX-ACCESS read-write
	STATUS deprecated
	DESCRIPTION
        "
        Default Add&Drop mode on Client
        Port :This register configures
         the default Add&Drop mode on the
        port.
        "
	::= { pm1004vCfgClientStartupEntry 5 }


--- *****************************************************
---     LEAF for the table 2191
--- *****************************************************

pm1004vtablelineStartup OBJECT IDENTIFIER ::= { pm1004vCfgStartup 2 }



pm1004vCfgsystConfLine1 OBJECT-TYPE
	  SYNTAX Unsigned32 (0..65536)
	  MAX-ACCESS read-write
	  STATUS current
	  DESCRIPTION
        "
        Default Settings on Line 1 :This
        register configures the default
        initialisation settings on Line
        port 1.
        "
	  ::= { pm1004vtablelineStartup 2 }



pm1004vCfglineOptions1 OBJECT-TYPE
	  SYNTAX Unsigned32 (0..65536)
	  MAX-ACCESS read-write
	  STATUS current
	  DESCRIPTION
        "
        Default Options on Active Line
        Port :This register configures
         the default options on the active
        line port
        "
	  ::= { pm1004vtablelineStartup 5 }



pm1004vCfgsystConfLine2 OBJECT-TYPE
	  SYNTAX Unsigned32 (0..65536)
	  MAX-ACCESS read-write
	  STATUS current
	  DESCRIPTION
        "
        Default Settings on Line 2 :This
        register configures the default
        initialisation settings on Line
        port 2.
        "
	  ::= { pm1004vtablelineStartup 6 }



pm1004vCfglineSelection OBJECT-TYPE
	  SYNTAX Unsigned32 (0..65536)
	  MAX-ACCESS read-write
	  STATUS current
	  DESCRIPTION
        "
        Default Settings of active line
        :This  register configures the
         start up active line.
        "
	  ::= { pm1004vtablelineStartup 7 }



pm1004vCfglineOptions2 OBJECT-TYPE
	  SYNTAX Unsigned32 (0..65536)
	  MAX-ACCESS read-write
	  STATUS current
	  DESCRIPTION
        "
        Default Options on Active Line
        Port :This register configures
         the default options on the active
        line port
        "
	  ::= { pm1004vtablelineStartup 9 }



--- *****************************************************
---     LEAF for the table 21AB
--- *****************************************************

pm1004vCfgXfpTable OBJECT-TYPE
	SYNTAX  SEQUENCE OF Pm1004vCfgXfpEntry
	MAX-ACCESS not-accessible
	STATUS current
	DESCRIPTION
        "
        List of  Article
        "
	::= { pm1004vCfgStartup 3 }


pm1004vCfgXfpEntry OBJECT-TYPE
	SYNTAX Pm1004vCfgXfpEntry
	MAX-ACCESS not-accessible
	STATUS current
	DESCRIPTION
        "
        Row definition for the startup
        table
        "
	INDEX   { pm1004vCfgXfpIndex }
	::= { pm1004vCfgXfpTable 1 }


Pm1004vCfgXfpEntry ::=
	SEQUENCE {
	pm1004vCfgXfpIndex
		INTEGER,
	pm1004vCfgSystConfXfpPortn
		Unsigned32,
	pm1004vCfgDataRateConfXfpPortn
		Unsigned32
	}


pm1004vCfgXfpIndex OBJECT-TYPE
	SYNTAX  INTEGER(0..128)
	MAX-ACCESS  read-only
	STATUS current
	DESCRIPTION
        "
        Index definition for the xfp table
        "
	::= { pm1004vCfgXfpEntry 1 }


pm1004vCfgSystConfXfpPortn OBJECT-TYPE
	SYNTAX  Unsigned32 (0..65536)
	MAX-ACCESS read-write
	STATUS current
	DESCRIPTION
        "
        Default settings on XFP Port :This
        register configures the default
        initialisation settings on XFP
         port.
        "
	::= { pm1004vCfgXfpEntry 3 }


pm1004vCfgDataRateConfXfpPortn OBJECT-TYPE
	SYNTAX  Unsigned32 (0..65536)
	MAX-ACCESS read-write
	STATUS deprecated
	DESCRIPTION
        "
        :
        "
	::= { pm1004vCfgXfpEntry 4 }


--- *****************************************************
---     LEAF for the table Group labels
--- *****************************************************

pm1004vCfgLabels OBJECT IDENTIFIER ::= { pm1004vConfig 3 }



--- *****************************************************
---     LEAF for the table NO_VALUE
--- *****************************************************

pm1004vCfgLabelclientTable OBJECT-TYPE
	SYNTAX  SEQUENCE OF Pm1004vCfgLabelclientEntry
	MAX-ACCESS not-accessible
	STATUS current
	DESCRIPTION
        "
        List of  Article
        "
	::= { pm1004vCfgLabels 1 }


pm1004vCfgLabelclientEntry OBJECT-TYPE
	SYNTAX Pm1004vCfgLabelclientEntry
	MAX-ACCESS not-accessible
	STATUS current
	DESCRIPTION
        "
        Row definition for the labels
         table
        "
	INDEX   { pm1004vCfgLabelclientIndex }
	::= { pm1004vCfgLabelclientTable 1 }


Pm1004vCfgLabelclientEntry ::=
	SEQUENCE {
	pm1004vCfgLabelclientIndex
		INTEGER,
	pm1004vCfgLabelclientPortn
		DisplayString
	}


pm1004vCfgLabelclientIndex OBJECT-TYPE
	SYNTAX  INTEGER(0..128)
	MAX-ACCESS  read-only
	STATUS current
	DESCRIPTION
        "
        Index definition for the labelclient
        table
        "
	::= { pm1004vCfgLabelclientEntry 1 }


pm1004vCfgLabelclientPortn OBJECT-TYPE
	SYNTAX  DisplayString( SIZE(1..16))
	MAX-ACCESS read-write
	STATUS current
	DESCRIPTION
        "
        Default settings on the label
         of the Ports :These registers
         configures the default initialisation
        settings of the labels of the ports.
        "
	::= { pm1004vCfgLabelclientEntry 3 }


--- *****************************************************
---     LEAF for the table NO_VALUE
--- *****************************************************

pm1004vCfgLabellineTable OBJECT-TYPE
	SYNTAX  SEQUENCE OF Pm1004vCfgLabellineEntry
	MAX-ACCESS not-accessible
	STATUS current
	DESCRIPTION
        "
        List of  Article
        "
	::= { pm1004vCfgLabels 2 }


pm1004vCfgLabellineEntry OBJECT-TYPE
	SYNTAX Pm1004vCfgLabellineEntry
	MAX-ACCESS not-accessible
	STATUS current
	DESCRIPTION
        "
        Row definition for the labels
         table
        "
	INDEX   { pm1004vCfgLabellineIndex }
	::= { pm1004vCfgLabellineTable 1 }


Pm1004vCfgLabellineEntry ::=
	SEQUENCE {
	pm1004vCfgLabellineIndex
		INTEGER,
	pm1004vCfgLabellinePortn
		DisplayString
	}


pm1004vCfgLabellineIndex OBJECT-TYPE
	SYNTAX  INTEGER(0..128)
	MAX-ACCESS  read-only
	STATUS current
	DESCRIPTION
        "
        Index definition for the labelline
        table
        "
	::= { pm1004vCfgLabellineEntry 1 }


pm1004vCfgLabellinePortn OBJECT-TYPE
	SYNTAX  DisplayString( SIZE(1..16))
	MAX-ACCESS read-write
	STATUS current
	DESCRIPTION
        "
        Default settings on the label
         of the lines :These registers
         configures the default initialisation
        settings of the labels of the lines.
        "
	::= { pm1004vCfgLabellineEntry 3 }


--- *****************************************************
---     LEAF for the table Group startupthresholds
--- *****************************************************

pm1004vCfgStartupthresholds OBJECT IDENTIFIER ::= { pm1004vConfig 4 }



--- *****************************************************
---     LEAF for the table 5012
--- *****************************************************

pm1004vCfgClientStartupThreshTable OBJECT-TYPE
	SYNTAX  SEQUENCE OF Pm1004vCfgClientStartupThreshEntry
	MAX-ACCESS not-accessible
	STATUS current
	DESCRIPTION
        "
        List of  Article
        "
	::= { pm1004vCfgStartupthresholds 1 }


pm1004vCfgClientStartupThreshEntry OBJECT-TYPE
	SYNTAX Pm1004vCfgClientStartupThreshEntry
	MAX-ACCESS not-accessible
	STATUS current
	DESCRIPTION
        "
        Row definition for the startupthresholds
        table
        "
	INDEX   { pm1004vCfgClientStartupThreshIndex }
	::= { pm1004vCfgClientStartupThreshTable 1 }


Pm1004vCfgClientStartupThreshEntry ::=
	SEQUENCE {
	pm1004vCfgClientStartupThreshIndex
		INTEGER,
	pm1004vCfgClientThreshtxpowhighPortn
		Unsigned32,
	pm1004vCfgClientThreshtxpowlowPortn
		Unsigned32,
	pm1004vCfgClientThreshrxpowhighPortn
		Unsigned32,
	pm1004vCfgClientThreshrxpowlowPortn
		Unsigned32
	}


pm1004vCfgClientStartupThreshIndex OBJECT-TYPE
	SYNTAX  INTEGER(0..128)
	MAX-ACCESS  read-only
	STATUS current
	DESCRIPTION
        "
        Index definition for the clientStartupThresh
        table
        "
	::= { pm1004vCfgClientStartupThreshEntry 1 }


pm1004vCfgClientThreshtxpowhighPortn OBJECT-TYPE
	SYNTAX  Unsigned32 (0..65536)
	MAX-ACCESS read-write
	STATUS current
	DESCRIPTION
        "
        Default Setting on Tx Power high
        threshold :This register configures
        the default initialisation of the
        high threshold of the Transmit
         power on the port.
        "
	::= { pm1004vCfgClientStartupThreshEntry 15 }


pm1004vCfgClientThreshtxpowlowPortn OBJECT-TYPE
	SYNTAX  Unsigned32 (0..65536)
	MAX-ACCESS read-write
	STATUS current
	DESCRIPTION
        "
        Default Setting on Tx Power low
        threshold :This register configures
        the default initialisation of the
        low threshold of the Transmit power
        on the port.
        "
	::= { pm1004vCfgClientStartupThreshEntry 16 }


pm1004vCfgClientThreshrxpowhighPortn OBJECT-TYPE
	SYNTAX  Unsigned32 (0..65536)
	MAX-ACCESS read-write
	STATUS current
	DESCRIPTION
        "
        Default Setting on Rx Power high
        threshold :This register configures
        the default initialisation of the
        high threshold of the received
         power on the port.
        "
	::= { pm1004vCfgClientStartupThreshEntry 19 }


pm1004vCfgClientThreshrxpowlowPortn OBJECT-TYPE
	SYNTAX  Unsigned32 (0..65536)
	MAX-ACCESS read-write
	STATUS current
	DESCRIPTION
        "
        Default Setting on Rx Power low
        threshold :This register configures
        the default initialisation of the
        low threshold of the received power
        on the port.
        "
	::= { pm1004vCfgClientStartupThreshEntry 20 }


--- *****************************************************
---     LEAF for the table 50A1
--- *****************************************************

pm1004vCfgLineStartupThreshTable OBJECT-TYPE
	SYNTAX  SEQUENCE OF Pm1004vCfgLineStartupThreshEntry
	MAX-ACCESS not-accessible
	STATUS current
	DESCRIPTION
        "
        List of  Article
        "
	::= { pm1004vCfgStartupthresholds 2 }


pm1004vCfgLineStartupThreshEntry OBJECT-TYPE
	SYNTAX Pm1004vCfgLineStartupThreshEntry
	MAX-ACCESS not-accessible
	STATUS current
	DESCRIPTION
        "
        Row definition for the startupthresholds
        table
        "
	INDEX   { pm1004vCfgLineStartupThreshIndex }
	::= { pm1004vCfgLineStartupThreshTable 1 }


Pm1004vCfgLineStartupThreshEntry ::=
	SEQUENCE {
	pm1004vCfgLineStartupThreshIndex
		INTEGER,
	pm1004vCfgLineThreshtxpowhighPortn
		Unsigned32,
	pm1004vCfgLineThreshtxpowlowPortn
		Unsigned32,
	pm1004vCfgLineThreshrxpowhighPortn
		Unsigned32,
	pm1004vCfgLineThreshrxpowlowPortn
		Unsigned32
	}


pm1004vCfgLineStartupThreshIndex OBJECT-TYPE
	SYNTAX  INTEGER(0..128)
	MAX-ACCESS  read-only
	STATUS current
	DESCRIPTION
        "
        Index definition for the lineStartupThresh
        table
        "
	::= { pm1004vCfgLineStartupThreshEntry 1 }


pm1004vCfgLineThreshtxpowhighPortn OBJECT-TYPE
	SYNTAX  Unsigned32 (0..65536)
	MAX-ACCESS read-write
	STATUS current
	DESCRIPTION
        "
        Default Setting on Tx Power high
        threshold :This register configures
        the default initialisation of the
        high threshold of the Transmit
         power on the line.
        "
	::= { pm1004vCfgLineStartupThreshEntry 15 }


pm1004vCfgLineThreshtxpowlowPortn OBJECT-TYPE
	SYNTAX  Unsigned32 (0..65536)
	MAX-ACCESS read-write
	STATUS current
	DESCRIPTION
        "
        Default Setting on Tx Power low
        threshold :This register configures
        the default initialisation of the
        low threshold of the Transmit power
        on the line.
        "
	::= { pm1004vCfgLineStartupThreshEntry 16 }


pm1004vCfgLineThreshrxpowhighPortn OBJECT-TYPE
	SYNTAX  Unsigned32 (0..65536)
	MAX-ACCESS read-write
	STATUS current
	DESCRIPTION
        "
        Default Setting on Rx Power high
        threshold :This register configures
        the default initialisation of the
        high threshold of the received
         power on the line.
        "
	::= { pm1004vCfgLineStartupThreshEntry 19 }


pm1004vCfgLineThreshrxpowlowPortn OBJECT-TYPE
	SYNTAX  Unsigned32 (0..65536)
	MAX-ACCESS read-write
	STATUS current
	DESCRIPTION
        "
        Default Setting on Rx Power low
        threshold :This register configures
        the default initialisation of the
        low threshold of the received power
        on the line.
        "
	::= { pm1004vCfgLineStartupThreshEntry 20 }


--- *****************************************************
---     LEAF for the table Group startuptlh
--- *****************************************************

pm1004vCfgStartuptlh OBJECT IDENTIFIER ::= { pm1004vConfig 5 }



--- *****************************************************
---     LEAF for the table 25A8
--- *****************************************************

pm1004vCfgOtxtlhTable OBJECT-TYPE
	SYNTAX  SEQUENCE OF Pm1004vCfgOtxtlhEntry
	MAX-ACCESS not-accessible
	STATUS current
	DESCRIPTION
        "
        List of  Article
        "
	::= { pm1004vCfgStartuptlh 1 }


pm1004vCfgOtxtlhEntry OBJECT-TYPE
	SYNTAX Pm1004vCfgOtxtlhEntry
	MAX-ACCESS not-accessible
	STATUS current
	DESCRIPTION
        "
        Row definition for the startuptlh
        table
        "
	INDEX   { pm1004vCfgOtxtlhIndex }
	::= { pm1004vCfgOtxtlhTable 1 }


Pm1004vCfgOtxtlhEntry ::=
	SEQUENCE {
	pm1004vCfgOtxtlhIndex
		INTEGER,
	pm1004vCfgNuPortn
		Unsigned32,
	pm1004vCfgLineDitherRatePortn
		Unsigned32,
	pm1004vCfgLineDitherFhzPortn
		Unsigned32,
	pm1004vCfgLinePwrLaserPortn
		Unsigned32,
	pm1004vCfgLineFCurrentPortn
		Unsigned32,
	pm1004vCfgLineGridCurrentPortn
		Unsigned32,
	pm1004vCfgFPortn
		Unsigned32,
	pm1004vCfgReservedPortn
		Unsigned32,
	pm1004vCfgLinePhotodiodeModePortn
		Unsigned32,
	pm1004vCfgLinePhotodiodeValuePortn
		Unsigned32
	}


pm1004vCfgOtxtlhIndex OBJECT-TYPE
	SYNTAX  INTEGER(0..128)
	MAX-ACCESS  read-only
	STATUS current
	DESCRIPTION
        "
        Index definition for the otxtlh
        table
        "
	::= { pm1004vCfgOtxtlhEntry 1 }


pm1004vCfgNuPortn OBJECT-TYPE
	SYNTAX  Unsigned32 (0..65536)
	MAX-ACCESS read-write
	STATUS deprecated
	DESCRIPTION
        "
        :
        "
	::= { pm1004vCfgOtxtlhEntry 3 }


pm1004vCfgLineDitherRatePortn OBJECT-TYPE
	SYNTAX  Unsigned32 (0..65536)
	MAX-ACCESS read-write
	STATUS current
	DESCRIPTION
        "
        Default Line OTX TLH FM amplitude
        :This register configures the start-up
        width of the frequency modulation
        of the Line OTX TLH
        "
	::= { pm1004vCfgOtxtlhEntry 4 }


pm1004vCfgLineDitherFhzPortn OBJECT-TYPE
	SYNTAX  Unsigned32 (0..65536)
	MAX-ACCESS read-write
	STATUS current
	DESCRIPTION
        "
        Default Line OTX TLH FM frequency
        :This register configures the start-up
        frequency of the frequency modulation
        of the Line OTX TLH
        "
	::= { pm1004vCfgOtxtlhEntry 5 }


pm1004vCfgLinePwrLaserPortn OBJECT-TYPE
	SYNTAX  Unsigned32 (0..65536)
	MAX-ACCESS read-write
	STATUS current
	DESCRIPTION
        "
        Defaut Line OTX TLH output Power
        :This register configures the start-up
        output power of the Line OTX TLH
         (Unit = dBm)
        "
	::= { pm1004vCfgOtxtlhEntry 6 }


pm1004vCfgLineFCurrentPortn OBJECT-TYPE
	SYNTAX  Unsigned32 (0..65536)
	MAX-ACCESS read-write
	STATUS current
	DESCRIPTION
        "
        Default Line OTX TLH Channel :This
        register configures the start-up
        laser channel of the Line OTX TLH
        "
	::= { pm1004vCfgOtxtlhEntry 7 }


pm1004vCfgLineGridCurrentPortn OBJECT-TYPE
	SYNTAX  Unsigned32 (0..65536)
	MAX-ACCESS read-write
	STATUS current
	DESCRIPTION
        "
        Default Line OTX TLH Grid :This
        register configures the start-up
        laser grid of the Line OTX TLH
        "
	::= { pm1004vCfgOtxtlhEntry 8 }


pm1004vCfgFPortn OBJECT-TYPE
	SYNTAX  Unsigned32 (0..65536)
	MAX-ACCESS read-write
	STATUS current
	DESCRIPTION
        "
        Default Line OTX TLH lowest Freq
        :This register configures the start-up
        lowest frequency supported on the
        Line OTX TLH
        "
	::= { pm1004vCfgOtxtlhEntry 9 }


pm1004vCfgReservedPortn OBJECT-TYPE
	SYNTAX  Unsigned32 (0..65536)
	MAX-ACCESS read-write
	STATUS deprecated
	DESCRIPTION
        "
        :
        "
	::= { pm1004vCfgOtxtlhEntry 10 }


pm1004vCfgLinePhotodiodeModePortn OBJECT-TYPE
	SYNTAX  Unsigned32 (0..65536)
	MAX-ACCESS read-write
	STATUS current
	DESCRIPTION
        "
        Default Line OTX TLH APD mode
         :This register configures the
         start-up APD mode of the Line
         OTX TLH
        "
	::= { pm1004vCfgOtxtlhEntry 11 }


pm1004vCfgLinePhotodiodeValuePortn OBJECT-TYPE
	SYNTAX  Unsigned32 (0..65536)
	MAX-ACCESS read-write
	STATUS current
	DESCRIPTION
        "
        Default Line OTX TLH APD atten.
        :This register configures the start-up
        APD attenuation on the Line OTX
        TLH
        "
	::= { pm1004vCfgOtxtlhEntry 12 }


--- *****************************************************
---     LEAF for the table Group startuptablefive
--- *****************************************************

pm1004vCfgStartuptablefive OBJECT IDENTIFIER ::= { pm1004vConfig 6 }



--- *****************************************************
---     LEAF for the table 0005
--- *****************************************************

pm1004vCfgOtxtlhcapabilitiesTable OBJECT-TYPE
	SYNTAX  SEQUENCE OF Pm1004vCfgOtxtlhcapabilitiesEntry
	MAX-ACCESS not-accessible
	STATUS current
	DESCRIPTION
        "
        List of  Article
        "
	::= { pm1004vCfgStartuptablefive 1 }


pm1004vCfgOtxtlhcapabilitiesEntry OBJECT-TYPE
	SYNTAX Pm1004vCfgOtxtlhcapabilitiesEntry
	MAX-ACCESS not-accessible
	STATUS current
	DESCRIPTION
        "
        Row definition for the startuptablefive
        table
        "
	INDEX   { pm1004vCfgOtxtlhcapabilitiesIndex }
	::= { pm1004vCfgOtxtlhcapabilitiesTable 1 }


Pm1004vCfgOtxtlhcapabilitiesEntry ::=
	SEQUENCE {
	pm1004vCfgOtxtlhcapabilitiesIndex
		INTEGER,
	pm1004vCfgComponentTypePortn
		Unsigned32,
	pm1004vCfgMiscellaneousPortn
		Unsigned32,
	pm1004vCfgFirstChannelPortn
		Unsigned32,
	pm1004vCfgLastChannelPortn
		Unsigned32,
	pm1004vCfgGridPortn
		Unsigned32
	}


pm1004vCfgOtxtlhcapabilitiesIndex OBJECT-TYPE
	SYNTAX  INTEGER(0..128)
	MAX-ACCESS  read-only
	STATUS current
	DESCRIPTION
        "
        Index definition for the otxtlhcapabilities
        table
        "
	::= { pm1004vCfgOtxtlhcapabilitiesEntry 1 }


pm1004vCfgComponentTypePortn OBJECT-TYPE
	SYNTAX  Unsigned32 (0..65536)
	MAX-ACCESS read-only
	STATUS current
	DESCRIPTION
        "
        Component parameters :This OID
        defines the component parameters
        "
	::= { pm1004vCfgOtxtlhcapabilitiesEntry 3 }


pm1004vCfgMiscellaneousPortn OBJECT-TYPE
	SYNTAX  Unsigned32 (0..65536)
	MAX-ACCESS read-only
	STATUS current
	DESCRIPTION
        "
        Miscellaneous default settings
        :This OID defines the miscellaneous
        parameters
        "
	::= { pm1004vCfgOtxtlhcapabilitiesEntry 4 }


pm1004vCfgFirstChannelPortn OBJECT-TYPE
	SYNTAX  Unsigned32 (0..65536)
	MAX-ACCESS read-only
	STATUS current
	DESCRIPTION
        "
        Number of the first channel of
        the component :This OID defines
        the first channel number of the
        PM
        "
	::= { pm1004vCfgOtxtlhcapabilitiesEntry 5 }


pm1004vCfgLastChannelPortn OBJECT-TYPE
	SYNTAX  Unsigned32 (0..65536)
	MAX-ACCESS read-only
	STATUS current
	DESCRIPTION
        "
        Number of the last channel of
         the component :This OID defines
        the last channel number of the
         PM
        "
	::= { pm1004vCfgOtxtlhcapabilitiesEntry 6 }


pm1004vCfgGridPortn OBJECT-TYPE
	SYNTAX  Unsigned32 (0..65536)
	MAX-ACCESS read-only
	STATUS current
	DESCRIPTION
        "
        Grid value of the component :This
        OID defines the grid of the PM
        "
	::= { pm1004vCfgOtxtlhcapabilitiesEntry 7 }



pm1004vCfgWriteConfiguration  OBJECT-TYPE
	SYNTAX EkiOnOff
	MAX-ACCESS read-write
	STATUS current
	DESCRIPTION
	"Write configuration to module:This OID
	 writes the complete configuration to the module"
	::= { pm1004vConfig 257 }






--- *****************************************************
---     TRAP OBJECTS
--- *****************************************************

pm1004vtrapPortNumber OBJECT-TYPE
	SYNTAX INTEGER(1..64)
	MAX-ACCESS read-only
	STATUS current
	DESCRIPTION
	"Last port which generates a trap"
	::= { pm1004vtraps 2 }

pm1004vtrapLineNumber OBJECT-TYPE
	SYNTAX INTEGER(1..64)
	MAX-ACCESS read-only
	STATUS current
	DESCRIPTION
	"Last Line which generates a trap"
	::= { pm1004vtraps 3 }

pm1004vtrapBoardNumber OBJECT-TYPE
	SYNTAX INTEGER(1..64)
	MAX-ACCESS read-only
	STATUS current
	DESCRIPTION
	"Last module which generates a trap"
	::= { pm1004vtraps 4 }







--- *****************************************************
---     LINE TRAPS
--- *****************************************************

pm1004vLineTrapNotUrgentGoesOn NOTIFICATION-TYPE
	OBJECTS {pm1004vAlmLineDdmWarningPortn, pm1004vtrapLineNumber, pm1004vtrapBoardNumber}
	STATUS current
	--&FILTNAME    "PM1004V Line Not Urgent ON"
	--&ACTIONS     { log, minor }
	--&MATCH       { pm1004vAlmLineDdmWarningPortn "on", pm1004vtrapLineNumber "$2", pm1004vtrapBoardNumber "$3"}
	--&MESG        "DDM Warning appears on Line Port $2 of PM1004V(LH) in Slot $3 ($A)"
	DESCRIPTION "Not urgent Line default is activated"
	::= { pm1004vtraps 30 }

pm1004vLineTrapNotUrgentGoesOff NOTIFICATION-TYPE
	OBJECTS {pm1004vAlmLineDdmWarningPortn, pm1004vtrapLineNumber, pm1004vtrapBoardNumber}
	STATUS current
	--&FILTNAME    "PM1004V Line Not Urgent OFF"
	--&ACTIONS     { log, normal }
	--&CLEARS      { "PM1004V Line Not Urgent ON" }
	--&MATCH       { pm1004vAlmLineDdmWarningPortn "on", pm1004vtrapLineNumber "$2", pm1004vtrapBoardNumber "$3"}
	--&MESG        "DDM Warning disappears on Line Port $2 of PM1004V in Slot $3 ($A)"
	DESCRIPTION "Not urgent Line default disappeared"
	::= { pm1004vtraps 31 }

pm1004vLineTrapUrgentGoesOn NOTIFICATION-TYPE
	OBJECTS {pm1004vAlmLineDdmAlmPortn, pm1004vtrapLineNumber, pm1004vtrapBoardNumber}
	STATUS current
	--&FILTNAME    "PM1004V Line Urgent ON"
	--&ACTIONS     { log, major }
	--&MATCH       { pm1004vAlmLineDdmAlmPortn "on", pm1004vtrapLineNumber "$2", pm1004vtrapBoardNumber "$3"}
	--&MESG        "DDM Alarm appears on Line Port $2 of PM1004V in Slot $3 ($A)"
	DESCRIPTION "Urgent Line default is activated"
	::= { pm1004vtraps 32 }

pm1004vLineTrapUrgentGoesOff NOTIFICATION-TYPE
	OBJECTS {pm1004vAlmLineDdmAlmPortn, pm1004vtrapLineNumber, pm1004vtrapBoardNumber}
	STATUS current
	--&FILTNAME    "PM1004V Line Urgent OFF"
	--&ACTIONS     { log, normal }
	--&CLEARS      { "PM1004V Line Urgent ON" }
	--&MATCH       { pm1004vAlmLineDdmAlmPortn "on", pm1004vtrapLineNumber "$2", pm1004vtrapBoardNumber "$3"}
	--&MESG        "DDM Alarm disappears on Line Port $2 of PM1004V in Slot $3 ($A)"
	DESCRIPTION "Urgent Line default disappeared"
	::= { pm1004vtraps 33 }

pm1004vLineTrapCritGoesOn NOTIFICATION-TYPE
	OBJECTS {pm1004vAlmLineFailPortn , pm1004vAlmLineHwFailPortn , pm1004vtrapLineNumber, pm1004vtrapBoardNumber}
	STATUS current
	--&FILTNAME    "PM1004V Line Fail ON"
	--&ACTIONS     { log, critical }
	--&MATCH       { pm1004vAlmLineFailPortn "on", pm1004vAlmLineHwFailPortn "*", pm1004vtrapLineNumber "$3", pm1004vtrapBoardNumber "$4"}
	--&MESG        "Line Port $3 Down on PM1004V in Slot $4 ($A)"

	--&FILTNAME    "PM1004V Line HW Fail ON (Hidden)"
	--&ACTIONS     { info }
	--&MATCH       { pm1004vAlmLineFailPortn "*", pm1004vAlmLineHwFailPortn "on", pm1004vtrapLineNumber "$3", pm1004vtrapBoardNumber "$4"}
	--&MESG        "Line Port $3 Down on PM1004V in Slot $4 ($A)"
	DESCRIPTION "Critical Line default is activated"
	::= { pm1004vtraps 34 }

pm1004vLineTrapCritGoesOff NOTIFICATION-TYPE
	OBJECTS {pm1004vAlmLineFailPortn , pm1004vAlmLineHwFailPortn , pm1004vtrapLineNumber, pm1004vtrapBoardNumber}
	STATUS current
	--&FILTNAME    "PM1004V Line Fail OFF"
	--&ACTIONS     { log,  normal }
	--&CLEARS      { "PM1004V Line Fail ON" }
	--&MATCH       { pm1004vAlmLineFailPortn "on", pm1004vAlmLineHwFailPortn "*", pm1004vtrapLineNumber "$3", pm1004vtrapBoardNumber "$4"}
	--&MESG        "Line Port $3 Up on PM1004V in Slot $4 ($A)"

	--&FILTNAME    "PM1004V Line HW Fail OFF (Hidden)"
	--&ACTIONS     { info }
	--&MATCH       { pm1004vAlmLineFailPortn "*", pm1004vAlmLineHwFailPortn "on", pm1004vtrapLineNumber "$3", pm1004vtrapBoardNumber "$4"}
	--&MESG        "Line Port $3 Up on PM1004V in Slot $4 ($A)"
	DESCRIPTION "Critical Line default disappeared"
	::= { pm1004vtraps 35 }






--- *****************************************************
---     CLIENT TRAPS
--- *****************************************************

pm1004vClientTrapNotUrgentGoesOn NOTIFICATION-TYPE
	OBJECTS {pm1004vAlmSfpDdmWarningPortn, pm1004vtrapPortNumber, pm1004vtrapBoardNumber}
	STATUS current
	--&FILTNAME    "PM1004V Client Not Urgent ON"
	--&ACTIONS     { log, minor }
	--&MATCH       { pm1004vAlmSfpDdmWarningPortn "on", pm1004vtrapPortNumber "$2", pm1004vtrapBoardNumber "$3"}
	--&MESG        "DDM Warning appears on Client Port $2 of PM1004V in Slot $3 ($A)"
	DESCRIPTION "Not urgent client default is activated"
	::= { pm1004vtraps 40 }

pm1004vClientTrapNotUrgentGoesOff NOTIFICATION-TYPE
	OBJECTS {pm1004vAlmSfpDdmWarningPortn, pm1004vtrapPortNumber, pm1004vtrapBoardNumber}
	STATUS current
	--&FILTNAME    "PM1004V Client Not Urgent OFF"
	--&ACTIONS     { log, normal }
	--&CLEARS      { "PM1004V Client Not Urgent ON" }
	--&MATCH       { pm1004vAlmSfpDdmWarningPortn "on", pm1004vtrapPortNumber "$2", pm1004vtrapBoardNumber "$3"}
	--&MESG        "DDM Warning appears on Client Port $2 of PM1004V in Slot $3 ($A)"
	DESCRIPTION "Not urgent client default disappeared"
	::= { pm1004vtraps 41 }

pm1004vClientTrapUrgentGoesOn NOTIFICATION-TYPE
	OBJECTS {pm1004vAlmSfpDdmAlmPortn, pm1004vtrapPortNumber, pm1004vtrapBoardNumber}
	STATUS current
	--&FILTNAME    "PM1004V Client Urgent ON"
	--&ACTIONS     { log, major }
	--&MATCH       { pm1004vAlmSfpDdmAlmPortn "on", pm1004vtrapPortNumber "$2", pm1004vtrapBoardNumber "$3"}
	--&MESG        "DDM Alarm appears on Client Port $2 of PM1004V in Slot $3 ($A)"
	DESCRIPTION "Urgent client default is activated"
	::= { pm1004vtraps 42 }

pm1004vClientTrapUrgentGoesOff NOTIFICATION-TYPE
	OBJECTS {pm1004vAlmSfpDdmAlmPortn, pm1004vtrapPortNumber, pm1004vtrapBoardNumber}
	STATUS current
	--&FILTNAME    "PM1004V Client Urgent OFF"
	--&ACTIONS     { log, normal }
	--&CLEARS      { "PM1004V Client Urgent ON" }
	--&MATCH       { pm1004vAlmSfpDdmAlmPortn "on", pm1004vtrapPortNumber "$2", pm1004vtrapBoardNumber "$3"}
	--&MESG        "DDM Alarm disappears on Client Port $2 of PM1004V in Slot $3 ($A)"
	DESCRIPTION "Urgent client default disappeared"
	::= { pm1004vtraps 43 }

pm1004vClientTrapCritGoesOn NOTIFICATION-TYPE
	OBJECTS {pm1004vAlmFailAccPortn, pm1004vAlmHwFailAccPortn, pm1004vtrapPortNumber, pm1004vtrapBoardNumber}
	STATUS current
	--&FILTNAME    "PM1004V Client Fail ON"
	--&ACTIONS     { log, critical }
	--&MATCH       { pm1004vAlmFailAccPortn "on", pm1004vAlmHwFailAccPortn "*", pm1004vtrapPortNumber "$3", pm1004vtrapBoardNumber "$4"}
	--&MESG        "Client Port $3 Down on PM1004V in Slot $4 ($A)"

	--&FILTNAME    "PM1004V Client HW Fail ON (Hidden)"
	--&ACTIONS     { info }
	--&MATCH       { pm1004vAlmFailAccPortn "*", pm1004vAlmHwFailAccPortn "on", pm1004vtrapPortNumber "$3", pm1004vtrapBoardNumber "$4"}
	--&MESG        "Client Port $3 Down on PM1004V in Slot $4 ($A)"
	DESCRIPTION "Critical client default is activated"
	::= { pm1004vtraps 44 }

pm1004vClientTrapCritGoesOff NOTIFICATION-TYPE
	OBJECTS {pm1004vAlmFailAccPortn, pm1004vAlmHwFailAccPortn, pm1004vtrapPortNumber, pm1004vtrapBoardNumber}
	STATUS current
	--&FILTNAME    "PM1004V Client Fail OFF"
	--&ACTIONS     { log, normal }
	--&CLEARS      { "PM1004V Client Fail ON" }
	--&MATCH       { pm1004vAlmFailAccPortn "on", pm1004vAlmHwFailAccPortn "*", pm1004vtrapPortNumber "$3", pm1004vtrapBoardNumber "$4"}
	--&MESG        "Client Port $3 Up on PM1004V in Slot $4 ($A)"

	--&FILTNAME    "PM1004V Client HW Fail OFF (Hidden)"
	--&ACTIONS     { info }
	--&MATCH       { pm1004vAlmFailAccPortn "*", pm1004vAlmHwFailAccPortn "on", pm1004vtrapPortNumber "$3", pm1004vtrapBoardNumber "$4"}
	--&MESG        "Client Port $3 Up on PM1004V in Slot $4 ($A)"
	DESCRIPTION "Critical client default disappeared"
	::= { pm1004vtraps 45 }






--- *****************************************************
---     HW TRAPS
--- *****************************************************

pm1004vPowerTrapUrgentGoesOn NOTIFICATION-TYPE
	OBJECTS {pm1004vAlmDefFuseB, pm1004vAlmDefFuseA , pm1004vtrapBoardNumber}
	STATUS current
	--&FILTNAME    "PM1004V Fuse A Fail ON"
	--&ACTIONS     { log, major }
	--&MATCH       { pm1004vAlmDefFuseB "*", pm1004vAlmDefFuseA "on", pm1004vtrapBoardNumber "$3"}
	--&MESG        "Power Input A Fail on PM1004V in Slot $3 ($A)"

	--&FILTNAME    "PM1004V Fuse B Fail ON"
	--&ACTIONS     { log, major }
	--&MATCH       { pm1004vAlmDefFuseB "on", pm1004vAlmDefFuseA "*", pm1004vtrapBoardNumber "$3"}
	--&MESG        "Power Input B Fail on PM1004V in Slot $3 ($A)"
	DESCRIPTION "Urgent power supply default is activated"
	::= { pm1004vtraps 50 }

pm1004vPowerTrapUrgentGoesOff NOTIFICATION-TYPE
	OBJECTS {pm1004vAlmDefFuseB, pm1004vAlmDefFuseA , pm1004vtrapBoardNumber}
	STATUS current
	--&FILTNAME    "PM1004V Fuse A&B Fail OFF"
	--&ACTIONS     { log, normal}
	--&CLEARS      { "PM1004V Fuse A Fail ON", "PM1004V Fuse B Fail ON" }
	--&MATCH       { pm1004vAlmDefFuseB "on", pm1004vAlmDefFuseA "on", pm1004vtrapBoardNumber "$3"}
	--&MESG        "Power Inputs A and B Present on PM1004V in Slot $3 ($A)"
	DESCRIPTION "Urgent power supply default disappeared"
	::= { pm1004vtraps 51 }






END
