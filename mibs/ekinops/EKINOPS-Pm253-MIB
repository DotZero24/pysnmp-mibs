-- *****************************************************************
-- EKINOPS-Pm253.TXT:  MIB
--
--MIB Part Number:3MI00006AKAE
--MIB Version:01
--
-- Copyright (c) 2016 by Ekinops
-- All rights reserved.
--
-- *****************************************************************

EKINOPS-Pm253-MIB DEFINITIONS ::= BEGIN

IMPORTS
	ekinops,
	EkiState,
	EkiOnOff,
	EkiMode,
	EkiProtocol,
	EkiApiState,
	EkiMeasureType,
	EkiSynchroMode
			FROM EKINOPS-MIB
        MODULE-IDENTITY,
        OBJECT-TYPE,
        NOTIFICATION-TYPE,
	Unsigned32,
	Integer32,
	Counter32,
	IpAddress
        		FROM SNMPv2-SMI
 	TEXTUAL-CONVENTION,
	DisplayString
                FROM SNMPv2-TC;

modulePm253 MODULE-IDENTITY
        LAST-UPDATED "201605200000Z"
        ORGANIZATION "Ekinops"
        CONTACT-INFO
         "Ekinops

          3, rue Blaise Pascal
          F-22300 Lannion / FRANCE

          Tel : +33 (0)2 96 05 00 30
          Fax : +33 (0)2 96 48 62 39

          E-mail: support@ekinops.net"
        DESCRIPTION
          "MIB for managing Ekinops modules with PM253 software"
	REVISION "200603170000Z"
	DESCRIPTION
	  "Initial Version."
	REVISION "200605220000Z"
	DESCRIPTION
	  "Adding the RMON objects."
	REVISION "200608180000Z"
	DESCRIPTION
	  "Adding the APS objects."
	REVISION "200707060000Z"
	DESCRIPTION
	  "°C changed to C, Add DCC alarms"
	REVISION "200711300000Z"
	DESCRIPTION
	  "Update Ekinops Address,Helps on objects, Ports Label"
	REVISION "200810270000Z"
	DESCRIPTION
	  "New RMON counters and PERF"
	REVISION "200811250000Z"
	DESCRIPTION
	  "DCC Storm suppress"
	REVISION "200904090000Z"
	DESCRIPTION
	  "Add DCC ans MAINTENANCE control"
	REVISION "200908250000Z"
	DESCRIPTION
	  "CondType parameters insertion"
	REVISION "201002180000Z"
	DESCRIPTION
	  "Probcause,AlarmType - NMS"
	REVISION "201011050000Z"
	DESCRIPTION
	  "Formulas in comments"
	REVISION "201207020000Z"
	DESCRIPTION
	  "Minor cosmetic updates"
	REVISION "201403270000Z"
	DESCRIPTION
	  "Probcause,AlarmType - NMS completion"
	REVISION "201501140000Z"
	DESCRIPTION
	  "Add Loopback objects"
	REVISION "201501140000Z"
	DESCRIPTION
	  "Labels cosmetic updates"
	REVISION "201605200000Z"
	DESCRIPTION
	  "New AlarmType – synthesisAlarm (12)"
        ::= { ekinops 13 }






--- *****************************************************
---     LEAF LEVEL 2
--- *****************************************************


pm253alarms OBJECT IDENTIFIER ::= { modulePm253 2 }
pm253AlmOther OBJECT IDENTIFIER ::= { pm253alarms 1 }
pm253AlmOtherNurg OBJECT IDENTIFIER ::= { pm253AlmOther 1 }
pm253AlmOtherUrg OBJECT IDENTIFIER ::= { pm253AlmOther 2 }
pm253AlmOtherCrit OBJECT IDENTIFIER ::= { pm253AlmOther 3 }

pm253AlmPort OBJECT IDENTIFIER ::= { pm253alarms 2 }
pm253AlmPortNurg OBJECT IDENTIFIER ::= { pm253AlmPort 1 }
pm253AlmPortUrg OBJECT IDENTIFIER ::= { pm253AlmPort 2 }
pm253AlmPortCrit OBJECT IDENTIFIER ::= { pm253AlmPort 3 }

pm253AlmLine OBJECT IDENTIFIER ::= { pm253alarms 3 }
pm253AlmLineNurg OBJECT IDENTIFIER ::= { pm253AlmLine 1 }
pm253AlmLineUrg OBJECT IDENTIFIER ::= { pm253AlmLine 2 }
pm253AlmLineCrit OBJECT IDENTIFIER ::= { pm253AlmLine 3 }





pm253measures OBJECT IDENTIFIER ::= { modulePm253 3 }
pm253MesrOther OBJECT IDENTIFIER ::= { pm253measures 1 }
pm253MesrPort OBJECT IDENTIFIER ::= { pm253measures 2 }
pm253MesrLine OBJECT IDENTIFIER ::= { pm253measures 3 }




pm253counters OBJECT IDENTIFIER ::= { modulePm253 4 }
pm253CntOther OBJECT IDENTIFIER ::= { pm253counters 1 }
pm253CntPort OBJECT IDENTIFIER ::= { pm253counters 2 }
pm253CntLine OBJECT IDENTIFIER ::= { pm253counters 3 }


pm253controlsWrite OBJECT IDENTIFIER ::= { modulePm253 6 }
pm253CtrlOther OBJECT IDENTIFIER ::= { pm253controlsWrite 1 }
pm253CtrlPort OBJECT IDENTIFIER ::= { pm253controlsWrite 2 }
pm253CtrlLine OBJECT IDENTIFIER ::= { pm253controlsWrite 3 }

pm253ri OBJECT IDENTIFIER ::= { modulePm253 7 }
pm253riTable OBJECT IDENTIFIER ::= { pm253ri 1 }

pm253download OBJECT IDENTIFIER ::= { modulePm253 8 }
pm253DwlOther OBJECT IDENTIFIER ::= { pm253download 1 }
pm253DwlPort OBJECT IDENTIFIER ::= { pm253download 2 }
pm253DwlLine OBJECT IDENTIFIER ::= { pm253download 3 }


pm253Config OBJECT IDENTIFIER ::= { modulePm253 9 }

pm253traps OBJECT IDENTIFIER ::= { modulePm253 10 }

pm253Monitoring OBJECT IDENTIFIER ::= { modulePm253 11}

pm253MonOther OBJECT IDENTIFIER ::= { pm253Monitoring 1 }
pm253MonRmon OBJECT IDENTIFIER ::= { pm253MonOther 3 }
pm253MonSync OBJECT IDENTIFIER ::= { pm253MonOther 1 }
pm253MonTimeStamp OBJECT IDENTIFIER ::= { pm253MonOther 2 }

pm253MonLine OBJECT IDENTIFIER ::= { pm253Monitoring 3 }

pm253MonClient OBJECT IDENTIFIER ::= { pm253Monitoring 2 }
pm253MonClientRmonCounter OBJECT IDENTIFIER ::= { pm253MonClient 4 }



--- *****************************************************
--- $$$$$$$$$$$$$$$$$$$$$$$$$$$$$$$$$$$$$$$$$$$$$$$$$$$$$
---     REMOTE INVENTORY
--- $$$$$$$$$$$$$$$$$$$$$$$$$$$$$$$$$$$$$$$$$$$$$$$$$$$$$
--- *****************************************************

pm253RinvReloadInventory OBJECT-TYPE
  SYNTAX INTEGER(0..1)
  MAX-ACCESS read-write
  STATUS current
  DESCRIPTION
        "Reload the inventory: This OID triggers an
         inventory reload."
  ::= { pm253ri 2 }

pm253RinvHwPlatform OBJECT-TYPE
  SYNTAX DisplayString
  MAX-ACCESS read-only
  STATUS current
  DESCRIPTION
        "HW platform description: This OID contains the
         description of the Hardware platform."
  ::= { pm253ri 3 }

pm253RinvModulePlatform OBJECT-TYPE
  SYNTAX DisplayString
  MAX-ACCESS read-only
  STATUS current
  DESCRIPTION
        "Module platform description: This OID contains the
         description of the Module."
  ::= { pm253ri 4 }

pm253RinvSwPlatform OBJECT-TYPE
  SYNTAX DisplayString
  MAX-ACCESS read-only
  STATUS current
  DESCRIPTION
        "SW platform description: This OID contains the
         description of the Software platform."
  ::= { pm253ri 5 }

pm253RinvGwPlatform OBJECT-TYPE
  SYNTAX DisplayString
  MAX-ACCESS read-only
  STATUS current
  DESCRIPTION
        "GW platform desciption: This OID contains the
         description of the Gateware platform."
  ::= { pm253ri 6 }



pm253RinvClientTable OBJECT-TYPE
      SYNTAX  SEQUENCE OF Pm253RinvClientEntry
      MAX-ACCESS  not-accessible
      STATUS  current
      DESCRIPTION
              "List of the SFPs on the selected module"
      ::= { pm253riTable 1 }

pm253RinvClientEntry OBJECT-TYPE
        SYNTAX  Pm253RinvClientEntry
        MAX-ACCESS  not-accessible
        STATUS  current
        DESCRIPTION
              "Row definition for the Client SFP table"
        INDEX   { pm253RinvClientIndex }
        ::= { pm253RinvClientTable 1 }



Pm253RinvClientEntry::=
        SEQUENCE {
          pm253RinvClientIndex
              Integer32,
          pm253RinvSfpClient
              DisplayString
        }


    pm253RinvClientIndex OBJECT-TYPE
        SYNTAX  Integer32(1..16)
        MAX-ACCESS  read-only
        STATUS  current
        DESCRIPTION
              "Index for Client SFP table"
        ::= { pm253RinvClientEntry 1 }


    pm253RinvSfpClient OBJECT-TYPE
        SYNTAX  DisplayString
        MAX-ACCESS  read-only
        STATUS  current
        DESCRIPTION
              "Inventory for the SFP: This OID contains the inventory for the Client SFP"
        ::= { pm253RinvClientEntry 2 }





pm253RinvLineTable OBJECT-TYPE
      SYNTAX  SEQUENCE OF Pm253RinvLineEntry
      MAX-ACCESS  not-accessible
      STATUS  current
      DESCRIPTION
              "List of the SFPs on the selected module"
      ::= { pm253riTable 2 }

pm253RinvLineEntry OBJECT-TYPE
        SYNTAX  Pm253RinvLineEntry
        MAX-ACCESS  not-accessible
        STATUS  current
        DESCRIPTION
              "Row definition for the SFP table"
        INDEX   { pm253RinvLineIndex }
        ::= { pm253RinvLineTable 1 }



Pm253RinvLineEntry::=
        SEQUENCE {
          pm253RinvLineIndex
              Integer32,
          pm253RinvsfpLine
              DisplayString
        }


    pm253RinvLineIndex OBJECT-TYPE
        SYNTAX  Integer32(1..16)
        MAX-ACCESS  read-only
        STATUS  current
        DESCRIPTION
              "Index for SFP table"
        ::= { pm253RinvLineEntry 1 }


    pm253RinvsfpLine OBJECT-TYPE
        SYNTAX  DisplayString
        MAX-ACCESS  read-only
        STATUS  current
        DESCRIPTION
              "Inventory for the SFP: This OID contains the inventory for the SFP"
        ::= { pm253RinvLineEntry 2 }










--- *****************************************************
--- $$$$$$$$$$$$$$$$$$$$$$$$$$$$$$$$$$$$$$$$$$$$$$$$$$$$$
---     ALARMS
--- $$$$$$$$$$$$$$$$$$$$$$$$$$$$$$$$$$$$$$$$$$$$$$$$$$$$$
--- *****************************************************



--- *****************************************************
---     LEAF for the synthAlm0 article
--- *****************************************************
pm253AlmsynthAlm0 OBJECT IDENTIFIER ::= { pm253AlmOtherNurg 0 }




pm253AlmDefFuseB OBJECT-TYPE
	  SYNTAX EkiOnOff
	  MAX-ACCESS read-only
	  STATUS current
	  DESCRIPTION
        "
        Fuse B Fail :This OID indicates
        that the fuse of the power input
        B is in fail condition  <Help>
          Status of the Fuse B <Condtype>
        DEF_FUSE_B <Probcause> powerProblem
        (36) <Alarmtype> equipmentAlarm
        (5) <Polarity> (2)
        "
	  ::= { pm253AlmsynthAlm0 16 }



pm253AlmDefFuseA OBJECT-TYPE
	  SYNTAX EkiOnOff
	  MAX-ACCESS read-only
	  STATUS current
	  DESCRIPTION
        "
        Fuse A Fail :This OID indicates
        that the fuse of the power input
        A is in fail condition  <Help>
          Status of the Fuse A <Condtype>
        DEF_FUSE_A <Probcause> powerProblem
        (36) <Alarmtype> equipmentAlarm
        (5) <Polarity> (2)
        "
	  ::= { pm253AlmsynthAlm0 15 }



pm253AlmModGlobFail OBJECT-TYPE
	  SYNTAX EkiOnOff
	  MAX-ACCESS read-only
	  STATUS current
	  DESCRIPTION
        "
        Module Failure :This OID is set
        on detection of a failure originating
        from the PM <Condtype> MOD_GLOB_FAIL
        <Probcause> equipmentMalfunction
        (16) <Alarmtype> synthesisAlarm
        (12)  <Polarity> (2)
        "
	  ::= { pm253AlmsynthAlm0 9 }



--- *****************************************************
---     LEAF for the synthAlm2 article
--- *****************************************************
pm253AlmsynthAlm2 OBJECT IDENTIFIER ::= { pm253AlmOtherNurg 2 }




pm253AlmMaintenanceOn OBJECT-TYPE
	  SYNTAX EkiOnOff
	  MAX-ACCESS read-only
	  STATUS current
	  DESCRIPTION
        "
        Maintenance Mode :This OID indicates
        that the PM is in maintenance mode.
         <Help>  This alarm indicates that
        the maintenance mode is enabled
        on the PM <Condtype> MAINTENANCE_ON
        <Probcause> other (1) <Alarmtype>
        other (1) <Polarity> (2)
        "
	  ::= { pm253AlmsynthAlm2 5 }



pm253AlmCorrelatOff OBJECT-TYPE
	  SYNTAX EkiOnOff
	  MAX-ACCESS read-only
	  STATUS current
	  DESCRIPTION
        "
        Not Used :This OID, when set,
         indicates that alarm correlation
        is not being performed. <Condtype>
        CORRELAT_OFF <Probcause> other
         (1) <Alarmtype> other (1) <Polarity>
        (2)
        "
	  ::= { pm253AlmsynthAlm2 4 }



pm253AlmConfTableLoad OBJECT-TYPE
	  SYNTAX EkiOnOff
	  MAX-ACCESS read-only
	  STATUS current
	  DESCRIPTION
        "
        PM Configuration Load :This OID
         is set during the loading of configuration
        tables in the PMs RAM. <Condtype>
        CONF_TABLE_LOAD <Probcause> other
        (1) <Alarmtype> other (1) <Polarity>
        (2)
        "
	  ::= { pm253AlmsynthAlm2 3 }



pm253AlmInvUpload OBJECT-TYPE
	  SYNTAX EkiOnOff
	  MAX-ACCESS read-only
	  STATUS current
	  DESCRIPTION
        "
        Inventory Upload :This OID is
         set during the uploading of PM
        inventory information. <Condtype>
        INV_UPLOAD <Probcause> other (1)
        <Alarmtype> other (1) <Polarity>
        (2)
        "
	  ::= { pm253AlmsynthAlm2 2 }



pm253AlmConfTableSave OBJECT-TYPE
	  SYNTAX EkiOnOff
	  MAX-ACCESS read-only
	  STATUS current
	  DESCRIPTION
        "
        PM Configuration Save :This OID
        is set during the saving of a new
        configuration table in the PM Flash
        memory. <Condtype> CONF_TABLE_SAVE
        <Probcause> other (1) <Alarmtype>
        other (1) <Polarity> (2)
        "
	  ::= { pm253AlmsynthAlm2 1 }



--- *********************************************************
---     TABLE for the pm253AlmsynthAlmLine articles
--- *********************************************************

pm253AlmsynthAlmLineTable OBJECT-TYPE
	SYNTAX  SEQUENCE OF Pm253AlmsynthAlmLineEntry
	MAX-ACCESS not-accessible
	STATUS current
	DESCRIPTION
        "
        List of pm253AlmsynthAlmLine Article
        "
	::= { pm253AlmLineCrit 4 }


pm253AlmsynthAlmLineEntry OBJECT-TYPE
	SYNTAX Pm253AlmsynthAlmLineEntry
	MAX-ACCESS not-accessible
	STATUS current
	DESCRIPTION
        "
        Row definition for the pm253AlmsynthAlmLine
        table
        "
	INDEX   { pm253AlmsynthAlmLineIndex }
	::= { pm253AlmsynthAlmLineTable 1 }


Pm253AlmsynthAlmLineEntry ::=
	SEQUENCE {
	pm253AlmsynthAlmLineIndex
		INTEGER,
	pm253AlmLineActivePortn
		EkiOnOff,
	pm253AlmLineFailPortn
		EkiOnOff,
	pm253AlmLineDdmAlmPortn
		EkiOnOff,
	pm253AlmLineDdmWarningPortn
		EkiOnOff,
	pm253AlmLineUpRdiInsPortn
		EkiOnOff,
	pm253AlmLineLocalOosPortn
		EkiOnOff,
	pm253AlmLineLsdPortn
		EkiOnOff,
	pm253AlmLineHwFailPortn
		EkiOnOff,
	pm253AlmLineDdmAbsentPortn
		EkiOnOff,
	pm253AlmLineSfpAbsentPortn
		EkiOnOff
	}


pm253AlmsynthAlmLineIndex OBJECT-TYPE
	SYNTAX  INTEGER(0..128)
	MAX-ACCESS  read-only
	STATUS current
	DESCRIPTION
        "
        Index definition for the pm253AlmsynthAlmLine
        table
        "
	::= { pm253AlmsynthAlmLineEntry 1 }


pm253AlmLineActivePortn OBJECT-TYPE
	SYNTAX  EkiOnOff
	MAX-ACCESS read-only
	STATUS current
	DESCRIPTION
        "
        Line Active :This OID indicates
        the line is active on receive side
         <Help>  This status indicates
         whether the line is active or
         standby. <Condtype> LINE_ACTIVE
        <Probcause> informationalStatus(1000)
        <Alarmtype> other (1) <Polarity>
        (2)
        "
	::= { pm253AlmsynthAlmLineEntry 17 }


pm253AlmLineFailPortn OBJECT-TYPE
	SYNTAX  EkiOnOff
	MAX-ACCESS read-only
	STATUS current
	DESCRIPTION
        "
        Line Fail :This OID indicates
         a failure condition on the Line.
        <Condtype> LINE_FAIL_2 <Probcause>
        equipmentMalfunction (16) <Alarmtype>
        synthesisAlarm (12)  <Polarity>
        (2)
        "
	::= { pm253AlmsynthAlmLineEntry 13 }


pm253AlmLineDdmAlmPortn OBJECT-TYPE
	SYNTAX  EkiOnOff
	MAX-ACCESS read-only
	STATUS current
	DESCRIPTION
        "
        Alarm On Line SFP DDM :This OID
        indicates an alarm is present coming
        out of Line optical interface DDM
         <Help>  This alarm indicates if
        a DDM Alarm has been detected on
        the client transceiver <Condtype>
        LINE_DDM_ALM_2 <Probcause> equipmentMalfunction
        (16) <Alarmtype> synthesisAlarm
        (12) ) <Polarity> (2)
        "
	::= { pm253AlmsynthAlmLineEntry 11 }


pm253AlmLineDdmWarningPortn OBJECT-TYPE
	SYNTAX  EkiOnOff
	MAX-ACCESS read-only
	STATUS current
	DESCRIPTION
        "
        Warning On Line SFP DDM :This
         OID indicates a warning is present
        coming out of Line optical interface
        DDM  <Help>  This alarm indicates
        if a DDM Warning has been detected
        on the client transceiver <Condtype>
        LINE_DDM_WARNING_2 <Probcause>
         equipmentMalfunction (16) <Alarmtype>
        synthesisAlarm (12)  <Polarity>
        (2)
        "
	::= { pm253AlmsynthAlmLineEntry 10 }


pm253AlmLineUpRdiInsPortn OBJECT-TYPE
	SYNTAX  EkiOnOff
	MAX-ACCESS read-only
	STATUS current
	DESCRIPTION
        "
        MS-RDI/L-RDI Inserted On Line
         :This OID indicates an upstream
        MS-RDI/L-RDI has been inserted
         on the outgoing 2.5 Gb/s SDH/SONET
        signal.  <Help>  This status indicates
        if a MS-RDI/L-RDI is currently
         inserted on the line interface.
        <Condtype> LINE_UP_RDI_INS_2 <Probcause>
        informationalStatus(1000) <Alarmtype>
        other (1) <Polarity> (2)
        "
	::= { pm253AlmsynthAlmLineEntry 9 }


pm253AlmLineLocalOosPortn OBJECT-TYPE
	SYNTAX  EkiOnOff
	MAX-ACCESS read-only
	STATUS current
	DESCRIPTION
        "
        Line Port In Service :This OID
        indicates that the Line port is
        In Service (1) of Out or Service
        (2)  <Help>  This status indicates
        if the line port is in service
         <Condtype> LINE_LOCAL_OOS_2 <Probcause>
        informationalStatus(1000) <Alarmtype>
        other (1) <Polarity> (2)
        "
	::= { pm253AlmsynthAlmLineEntry 7 }


pm253AlmLineLsdPortn OBJECT-TYPE
	SYNTAX  EkiOnOff
	MAX-ACCESS read-only
	STATUS current
	DESCRIPTION
        "
        Line SFP Laser Shutdown :This
         OID indicates the SFP transmitter
        line output is shut down.  <Help>
         This status indicates if the line
        transceiver laser is ON or OFF
         <Condtype> LINE_LSD_2 <Probcause>
        other (1) <Alarmtype> equipmentAlarm
        (5) <Polarity> (2)
        "
	::= { pm253AlmsynthAlmLineEntry 6 }


pm253AlmLineHwFailPortn OBJECT-TYPE
	SYNTAX  EkiOnOff
	MAX-ACCESS read-only
	STATUS current
	DESCRIPTION
        "
        Line HW Fail :This OID indicates
        a failure condition on the Line
        port, the most probable cause being
        a HW issue <Condtype> LINE_HW_FAIL_2
        <Probcause> equipmentMalfunction
        (16) <Alarmtype> synthesisAlarm
        (12)  <Polarity> (2)
        "
	::= { pm253AlmsynthAlmLineEntry 5 }


pm253AlmLineDdmAbsentPortn OBJECT-TYPE
	SYNTAX  EkiOnOff
	MAX-ACCESS read-only
	STATUS current
	DESCRIPTION
        "
        DDM Supported On Line SFP :This
        OID indicates that the SFP module
        on line port does not support Digital
        Diagnostic Monitoring Functions
         <Help>  This status indicates
         if the client transceiver includes
        the DDM feature <Condtype> LINE_DDM_ABSENT_2
        <Probcause> equipmentMalfunction
        (16) <Alarmtype> equipmentAlarm
        (5) <Polarity> (2)
        "
	::= { pm253AlmsynthAlmLineEntry 3 }


pm253AlmLineSfpAbsentPortn OBJECT-TYPE
	SYNTAX  EkiOnOff
	MAX-ACCESS read-only
	STATUS current
	DESCRIPTION
        "
        Line SFP Absent :This OID indicates
        that the SFP module is not present
        in the line port.  <Help>  This
        alarm indicates if the line transceiver
        is present. <Condtype> LINE_SFP_ABSENT_2
        <Probcause> inputOutputDeviceError
        (24) <Alarmtype> equipmentAlarm
        (5) <Polarity> (2) <Event> ObjectCDINV
        "
	::= { pm253AlmsynthAlmLineEntry 2 }


--- *********************************************************
---     TABLE for the pm253AlmsynthAlmClient articles
--- *********************************************************

pm253AlmsynthAlmClientTable OBJECT-TYPE
	SYNTAX  SEQUENCE OF Pm253AlmsynthAlmClientEntry
	MAX-ACCESS not-accessible
	STATUS current
	DESCRIPTION
        "
        List of pm253AlmsynthAlmClient
        Article
        "
	::= { pm253AlmPortCrit 8 }


pm253AlmsynthAlmClientEntry OBJECT-TYPE
	SYNTAX Pm253AlmsynthAlmClientEntry
	MAX-ACCESS not-accessible
	STATUS current
	DESCRIPTION
        "
        Row definition for the pm253AlmsynthAlmClient
        table
        "
	INDEX   { pm253AlmsynthAlmClientIndex }
	::= { pm253AlmsynthAlmClientTable 1 }


Pm253AlmsynthAlmClientEntry ::=
	SEQUENCE {
	pm253AlmsynthAlmClientIndex
		INTEGER,
	pm253AlmClientUpCsfPortn
		EkiOnOff,
	pm253AlmClientFailAccPortn
		EkiOnOff,
	pm253AlmClientSfpDdmAlmPortn
		EkiOnOff,
	pm253AlmClientSfpDdmWarningPortn
		EkiOnOff,
	pm253AlmClientDwCaisPortn
		EkiOnOff,
	pm253AlmClientRemoteOosPortn
		EkiOnOff,
	pm253AlmClientLocalOosPortn
		EkiOnOff,
	pm253AlmClientLsdPortn
		EkiOnOff,
	pm253AlmClientHwFailAccPortn
		EkiOnOff,
	pm253AlmClientDdmAbsentPortn
		EkiOnOff,
	pm253AlmClientSfpAbsentPortn
		EkiOnOff
	}


pm253AlmsynthAlmClientIndex OBJECT-TYPE
	SYNTAX  INTEGER(0..128)
	MAX-ACCESS  read-only
	STATUS current
	DESCRIPTION
        "
        Index definition for the pm253AlmsynthAlmClient
        table
        "
	::= { pm253AlmsynthAlmClientEntry 1 }


pm253AlmClientUpCsfPortn OBJECT-TYPE
	SYNTAX  EkiOnOff
	MAX-ACCESS read-only
	STATUS current
	DESCRIPTION
        "
        Client Signal Fail Inserted :This
        OID indicates a CSF has been inserted
        in the upstream client port.  <Help>
         This status indicates if a Client
        Signal Fail is currently inserted
        on the line signal for this client
        port <Condtype> CLIENT_UP_CSF_1
        <Probcause> other (1) <Alarmtype>
        other (1) <Polarity> (2)
        "
	::= { pm253AlmsynthAlmClientEntry 17 }


pm253AlmClientFailAccPortn OBJECT-TYPE
	SYNTAX  EkiOnOff
	MAX-ACCESS read-only
	STATUS current
	DESCRIPTION
        "
        Client Access Fail :This OID indicates
        a failure on the Client port <Condtype>
        CLIENT_FAIL_ACC_1 <Probcause> equipmentMalfunction
        (16) <Alarmtype> synthesisAlarm
        (12)  <Polarity> (2)
        "
	::= { pm253AlmsynthAlmClientEntry 13 }


pm253AlmClientSfpDdmAlmPortn OBJECT-TYPE
	SYNTAX  EkiOnOff
	MAX-ACCESS read-only
	STATUS current
	DESCRIPTION
        "
        Alarm On Client SFP DDM :This
         OID indicates an alarm is being
        received from the Client SFP DDM
         <Help>  This alarm indicates if
        a DDM Alarm has been detected on
        the client transceiver <Condtype>
        CLIENT_SFP_DDM_ALM_1 <Probcause>
        equipmentMalfunction (16) <Alarmtype>
        synthesisAlarm (12)  <Polarity>
        (2)
        "
	::= { pm253AlmsynthAlmClientEntry 11 }


pm253AlmClientSfpDdmWarningPortn OBJECT-TYPE
	SYNTAX  EkiOnOff
	MAX-ACCESS read-only
	STATUS current
	DESCRIPTION
        "
        Warning On Client SFP DDM :This
        OID indicates a warning is being
        received from the Client SFP DDM
         <Help>  This alarm indicates if
        a DDM Warning has been detected
        on the client transceiver <Condtype>
        CLIENT_SFP_DDM_WARNING_1 <Probcause>
        equipmentMalfunction (16) <Alarmtype>
        synthesisAlarm (12)  <Polarity>
        (2)
        "
	::= { pm253AlmsynthAlmClientEntry 10 }


pm253AlmClientDwCaisPortn OBJECT-TYPE
	SYNTAX  EkiOnOff
	MAX-ACCESS read-only
	STATUS current
	DESCRIPTION
        "
        Client AIS Inserted :This OID
         indicates a CAIS has been inserted
        on the output client port.  <Help>
         This status indicates if a Client
        Alarm Indication Signal is currently
        inserted on the client interface
        <Condtype> CLIENT_DW_CAIS_1 <Probcause>
        informationalStatus(1000) <Alarmtype>
        other (1) <Polarity> (2)
        "
	::= { pm253AlmsynthAlmClientEntry 9 }


pm253AlmClientRemoteOosPortn OBJECT-TYPE
	SYNTAX  EkiOnOff
	MAX-ACCESS read-only
	STATUS current
	DESCRIPTION
        "
        Remote Client Port In Service
         :This OID indicates that the remote
        Client port is In Service (1) or
        Out of Service (2)  <Help>  This
        status indicates if the remote
         client port is in service <Condtype>
        CLIENT_REMOTE_OOS_1 <Probcause>
        informationalStatus(1000) <Alarmtype>
        other (1) <Polarity> (2)
        "
	::= { pm253AlmsynthAlmClientEntry 8 }


pm253AlmClientLocalOosPortn OBJECT-TYPE
	SYNTAX  EkiOnOff
	MAX-ACCESS read-only
	STATUS current
	DESCRIPTION
        "
        Local Client Port In Service :This
        OID indicates that the local Client
        port is In Service (1) or Out of
        Service (2)  <Help>  This status
        indicates if the local client port
        is in service <Condtype> CLIENT_LOCAL_OOS_1
        <Probcause> informationalStatus(1000)
        <Alarmtype> other (1) <Polarity>
        (2)
        "
	::= { pm253AlmsynthAlmClientEntry 7 }


pm253AlmClientLsdPortn OBJECT-TYPE
	SYNTAX  EkiOnOff
	MAX-ACCESS read-only
	STATUS current
	DESCRIPTION
        "
        Client SFP Laser Shutdown :This
        OID indicates the Client SFP transmitter
        output has shut down.   <Help>
          This status indicates if the
         client transceiver laser is ON
        or OFF <Condtype> CLIENT_LSD_1
         <Probcause> other (1) <Alarmtype>
        equipmentAlarm (5) <Polarity> (2)
        "
	::= { pm253AlmsynthAlmClientEntry 6 }


pm253AlmClientHwFailAccPortn OBJECT-TYPE
	SYNTAX  EkiOnOff
	MAX-ACCESS read-only
	STATUS current
	DESCRIPTION
        "
        Client HW Fail :This OID indicates
        a failure on client port, most
         probably caused by a HW issue.
        <Condtype> CLIENT_HW_FAIL_ACC_1
        <Probcause> equipmentMalfunction
        (16) <Alarmtype> synthesisAlarm
        (12)  <Polarity> (2)
        "
	::= { pm253AlmsynthAlmClientEntry 5 }


pm253AlmClientDdmAbsentPortn OBJECT-TYPE
	SYNTAX  EkiOnOff
	MAX-ACCESS read-only
	STATUS current
	DESCRIPTION
        "
        DDM Supported On Client SFP :This
        OID indicates that the Client SFP
        module does not support the Digital
        Diagnostic Monitoring function
          <Help>  This status indicates
        if the client transceiver includes
        the DDM feature <Condtype> CLIENT_DDM_ABSENT_1
        <Probcause> informationalStatus(1000)
        <Alarmtype> other (1) <Polarity>
        (2)
        "
	::= { pm253AlmsynthAlmClientEntry 3 }


pm253AlmClientSfpAbsentPortn OBJECT-TYPE
	SYNTAX  EkiOnOff
	MAX-ACCESS read-only
	STATUS current
	DESCRIPTION
        "
        Client SFP Absent :This OID indicates
        that the SFP module is not present
        in the client port.  <Help>  This
        alarm indicates if the client transceiver
        is present. <Condtype> CLIENT_SFP_ABSENT_1
        <Probcause> inputOutputDeviceError
        (24) <Alarmtype> equipmentAlarm
        (5) <Polarity> (2) <Event> ObjectCDINV
        "
	::= { pm253AlmsynthAlmClientEntry 2 }


--- *********************************************************
---     TABLE for the pm253AlmaccessioAlm articles
--- *********************************************************

pm253AlmaccessioAlmTable OBJECT-TYPE
	SYNTAX  SEQUENCE OF Pm253AlmaccessioAlmEntry
	MAX-ACCESS not-accessible
	STATUS current
	DESCRIPTION
        "
        List of pm253AlmaccessioAlm Article
        "
	::= { pm253AlmPortCrit 16 }


pm253AlmaccessioAlmEntry OBJECT-TYPE
	SYNTAX Pm253AlmaccessioAlmEntry
	MAX-ACCESS not-accessible
	STATUS current
	DESCRIPTION
        "
        Row definition for the pm253AlmaccessioAlm
        table
        "
	INDEX   { pm253AlmaccessioAlmIndex }
	::= { pm253AlmaccessioAlmTable 1 }


Pm253AlmaccessioAlmEntry ::=
	SEQUENCE {
	pm253AlmaccessioAlmIndex
		INTEGER,
	pm253AlmClientUpLosPortn
		EkiOnOff,
	pm253AlmClientDwLasFailPortn
		EkiOnOff
	}


pm253AlmaccessioAlmIndex OBJECT-TYPE
	SYNTAX  INTEGER(0..128)
	MAX-ACCESS  read-only
	STATUS current
	DESCRIPTION
        "
        Index definition for the pm253AlmaccessioAlm
        table
        "
	::= { pm253AlmaccessioAlmEntry 1 }


pm253AlmClientUpLosPortn OBJECT-TYPE
	SYNTAX  EkiOnOff
	MAX-ACCESS read-only
	STATUS current
	DESCRIPTION
        "
        Client Input Loss Of Signal :This
        OID indicates that no signal is
        present on the SFP of the client
        port  <Help>  This alarm indicates
        if an optical signal is detected
        on the client transceiver input
        <Condtype> CLIENT_UP_LOS_1 <Probcause>
        receiveFailure (41) <Alarmtype>
        physicalViolation (9) <Polarity>
        (2)
        "
	::= { pm253AlmaccessioAlmEntry 5 }


pm253AlmClientDwLasFailPortn OBJECT-TYPE
	SYNTAX  EkiOnOff
	MAX-ACCESS read-only
	STATUS current
	DESCRIPTION
        "
        Client SFP Tx Failed :This OID
        indicates that the transmitter
         fails for the SFP plugged into
        the client port (this alarm reports
        the transmitter failure alarm generated
        by the SFPs)  <Help>  This alarm
        indicates if the laser of the client
        transceiver is in fail condition
        <Condtype> CLIENT_DW_LAS_FAIL_1
        <Probcause> transmitterFailure
         (56) <Alarmtype> equipmentAlarm
        (5) <Polarity> (2)
        "
	::= { pm253AlmaccessioAlmEntry 2 }


--- *********************************************************
---     TABLE for the pm253AlmclientSfpAlmDdm articles
--- *********************************************************

pm253AlmclientSfpAlmDdmTable OBJECT-TYPE
	SYNTAX  SEQUENCE OF Pm253AlmclientSfpAlmDdmEntry
	MAX-ACCESS not-accessible
	STATUS current
	DESCRIPTION
        "
        List of pm253AlmclientSfpAlmDdm
        Article
        "
	::= { pm253AlmPortUrg 32 }


pm253AlmclientSfpAlmDdmEntry OBJECT-TYPE
	SYNTAX Pm253AlmclientSfpAlmDdmEntry
	MAX-ACCESS not-accessible
	STATUS current
	DESCRIPTION
        "
        Row definition for the pm253AlmclientSfpAlmDdm
        table
        "
	INDEX   { pm253AlmclientSfpAlmDdmIndex }
	::= { pm253AlmclientSfpAlmDdmTable 1 }


Pm253AlmclientSfpAlmDdmEntry ::=
	SEQUENCE {
	pm253AlmclientSfpAlmDdmIndex
		INTEGER,
	pm253AlmClientRxPwrHighAlaPortn
		EkiOnOff,
	pm253AlmClientRxPwrLowAlaPortn
		EkiOnOff,
	pm253AlmClientTempHighAlaPortn
		EkiOnOff,
	pm253AlmClientTempLowAlaPortn
		EkiOnOff,
	pm253AlmClientVccHighAlaPortn
		EkiOnOff,
	pm253AlmClientVccLowAlaPortn
		EkiOnOff,
	pm253AlmClientTxBiasHighAlaPortn
		EkiOnOff,
	pm253AlmClientTxBiasLowAlaPortn
		EkiOnOff,
	pm253AlmClientTxPwrHighAlaPortn
		EkiOnOff,
	pm253AlmClientTxPwrLowAlaPortn
		EkiOnOff
	}


pm253AlmclientSfpAlmDdmIndex OBJECT-TYPE
	SYNTAX  INTEGER(0..128)
	MAX-ACCESS  read-only
	STATUS current
	DESCRIPTION
        "
        Index definition for the pm253AlmclientSfpAlmDdm
        table
        "
	::= { pm253AlmclientSfpAlmDdmEntry 1 }


pm253AlmClientRxPwrHighAlaPortn OBJECT-TYPE
	SYNTAX  EkiOnOff
	MAX-ACCESS read-only
	STATUS current
	DESCRIPTION
        "
        Client SFP Rx Power High :Alarm
        indicating that the SFP input power
        of port is higher than the threshold
        value written in the SFP EEPROM
        <Condtype> CLIENT_RX_PWR_HIGH_ALA_1
        <Probcause> receiveFailure (41)
        <Alarmtype> equipmentAlarm (5)
         <Polarity> (2)
        "
	::= { pm253AlmclientSfpAlmDdmEntry 17 }


pm253AlmClientRxPwrLowAlaPortn OBJECT-TYPE
	SYNTAX  EkiOnOff
	MAX-ACCESS read-only
	STATUS current
	DESCRIPTION
        "
        Client SFP Rx Power Low :Alarm
        indicating that the SFP input power
        of port is lower than the threshold
        value written in the SFP EEPROM
        <Condtype> CLIENT_RX_PWR_LOW_ALA_1
        <Probcause> receiveFailure (41)
        <Alarmtype> equipmentAlarm (5)
         <Polarity> (2)
        "
	::= { pm253AlmclientSfpAlmDdmEntry 16 }


pm253AlmClientTempHighAlaPortn OBJECT-TYPE
	SYNTAX  EkiOnOff
	MAX-ACCESS read-only
	STATUS current
	DESCRIPTION
        "
        Client SFP Temp High :Alarm indicating
        that the SFP temperature of port
        is higher than the threshold value
        written in the SFP EEPROM <Condtype>
        CLIENT_TEMP_HIGH_ALA_1 <Probcause>
        temperatureUnacceptable (51) <Alarmtype>
        equipmentAlarm (5) <Polarity> (2)
        "
	::= { pm253AlmclientSfpAlmDdmEntry 9 }


pm253AlmClientTempLowAlaPortn OBJECT-TYPE
	SYNTAX  EkiOnOff
	MAX-ACCESS read-only
	STATUS current
	DESCRIPTION
        "
        Client SFP Temp Low :Alarm indicating
        that the SFP temperature of port
        is lower than the threshold value
        written in the SFP EEPROM <Condtype>
        CLIENT_TEMP_LOW_ALA_1 <Probcause>
        temperatureUnacceptable (51) <Alarmtype>
        equipmentAlarm (5) <Polarity> (2)
        "
	::= { pm253AlmclientSfpAlmDdmEntry 8 }


pm253AlmClientVccHighAlaPortn OBJECT-TYPE
	SYNTAX  EkiOnOff
	MAX-ACCESS read-only
	STATUS current
	DESCRIPTION
        "
        Client SFP Power Supply High :Alarm
        indicating that the SFP power supply
        of port is higher than the threshold
        value written in the SFP EEPROM
         <Condtype> CLIENT_VCC_HIGH_ALA_1
        <Probcause> powerProblem (36) <Alarmtype>
        equipmentAlarm (5) <Polarity> (2)
        "
	::= { pm253AlmclientSfpAlmDdmEntry 7 }


pm253AlmClientVccLowAlaPortn OBJECT-TYPE
	SYNTAX  EkiOnOff
	MAX-ACCESS read-only
	STATUS current
	DESCRIPTION
        "
        Client SFP Power Supply Low :Alarm
        indicating that the SFP power supply
        of port is lower than the threshold
        value written in the SFP EEPROM
         <Condtype> CLIENT_VCC_LOW_ALA_1
        <Probcause> powerProblem (36) <Alarmtype>
        equipmentAlarm (5) <Polarity> (2)
        "
	::= { pm253AlmclientSfpAlmDdmEntry 6 }


pm253AlmClientTxBiasHighAlaPortn OBJECT-TYPE
	SYNTAX  EkiOnOff
	MAX-ACCESS read-only
	STATUS current
	DESCRIPTION
        "
        Client SFP Bias High :Alarm indicating
        that the SFP laser bias current
        of port is higher than the threshold
        value written in the SFP EEPROM
        <Condtype> CLIENT_TX_BIAS_HIGH_ALA_1
        <Probcause> transmitterFailure
         (56) <Alarmtype> equipmentAlarm
        (5) <Polarity> (2)
        "
	::= { pm253AlmclientSfpAlmDdmEntry 5 }


pm253AlmClientTxBiasLowAlaPortn OBJECT-TYPE
	SYNTAX  EkiOnOff
	MAX-ACCESS read-only
	STATUS current
	DESCRIPTION
        "
        Client SFP Bias Low :Alarm indicating
        that the SFP laser bias current
        of port is lower than the threshold
        value written in the SFP EEPROM
        <Condtype> CLIENT_TX_BIAS_LOW_ALA_1
        <Probcause> transmitterFailure
         (56) <Alarmtype> equipmentAlarm
        (5) <Polarity> (2)
        "
	::= { pm253AlmclientSfpAlmDdmEntry 4 }


pm253AlmClientTxPwrHighAlaPortn OBJECT-TYPE
	SYNTAX  EkiOnOff
	MAX-ACCESS read-only
	STATUS current
	DESCRIPTION
        "
        Client SFP Tx Power High :Alarm
        indicating that the SFP output
         power of port is higher than the
        threshold value written in the
         SFP EEPROM <Condtype> CLIENT_TX_PWR_HIGH_ALA_1
        <Probcause> transmitterFailure
         (56) <Alarmtype> equipmentAlarm
        (5) <Polarity> (2)
        "
	::= { pm253AlmclientSfpAlmDdmEntry 3 }


pm253AlmClientTxPwrLowAlaPortn OBJECT-TYPE
	SYNTAX  EkiOnOff
	MAX-ACCESS read-only
	STATUS current
	DESCRIPTION
        "
        Client SFP Tx Power Low :Alarm
        indicating that the SFP output
         power of port is lower than the
        threshold value written in the
         SFP EEPROM <Condtype> CLIENT_TX_PWR_LOW_ALA_1
        <Probcause> transmitterFailure
         (56) <Alarmtype> equipmentAlarm
        (5) <Polarity> (2)
        "
	::= { pm253AlmclientSfpAlmDdmEntry 2 }


--- *********************************************************
---     TABLE for the pm253AlmclientSfpWarnDdm articles
--- *********************************************************

pm253AlmclientSfpWarnDdmTable OBJECT-TYPE
	SYNTAX  SEQUENCE OF Pm253AlmclientSfpWarnDdmEntry
	MAX-ACCESS not-accessible
	STATUS current
	DESCRIPTION
        "
        List of pm253AlmclientSfpWarnDdm
        Article
        "
	::= { pm253AlmPortNurg 48 }


pm253AlmclientSfpWarnDdmEntry OBJECT-TYPE
	SYNTAX Pm253AlmclientSfpWarnDdmEntry
	MAX-ACCESS not-accessible
	STATUS current
	DESCRIPTION
        "
        Row definition for the pm253AlmclientSfpWarnDdm
        table
        "
	INDEX   { pm253AlmclientSfpWarnDdmIndex }
	::= { pm253AlmclientSfpWarnDdmTable 1 }


Pm253AlmclientSfpWarnDdmEntry ::=
	SEQUENCE {
	pm253AlmclientSfpWarnDdmIndex
		INTEGER,
	pm253AlmClientRxPwrHighWngPortn
		EkiOnOff,
	pm253AlmClientRxPwrLowWngPortn
		EkiOnOff,
	pm253AlmClientTempHighWngPortn
		EkiOnOff,
	pm253AlmClientTempLowWngPortn
		EkiOnOff,
	pm253AlmClientVccHighWngPortn
		EkiOnOff,
	pm253AlmClientVccLowWngPortn
		EkiOnOff,
	pm253AlmClientTxBiasHighWngPortn
		EkiOnOff,
	pm253AlmClientTxBiasLowWngPortn
		EkiOnOff,
	pm253AlmClientTxPwrHighWngPortn
		EkiOnOff,
	pm253AlmClientTxPwLowWngPortn
		EkiOnOff
	}


pm253AlmclientSfpWarnDdmIndex OBJECT-TYPE
	SYNTAX  INTEGER(0..128)
	MAX-ACCESS  read-only
	STATUS current
	DESCRIPTION
        "
        Index definition for the pm253AlmclientSfpWarnDdm
        table
        "
	::= { pm253AlmclientSfpWarnDdmEntry 1 }


pm253AlmClientRxPwrHighWngPortn OBJECT-TYPE
	SYNTAX  EkiOnOff
	MAX-ACCESS read-only
	STATUS current
	DESCRIPTION
        "
        Client SFP Rx Power High Warning
        :Warning indicating that the SFP
        input power of port is higher than
        the threshold value written in
         the SFP EEPROM <Condtype> CLIENT_RX_PWR_HIGH_WNG_1
        <Probcause> receiveFailure (41)
        <Alarmtype> equipmentAlarm (5)
         <Polarity> (2)
        "
	::= { pm253AlmclientSfpWarnDdmEntry 17 }


pm253AlmClientRxPwrLowWngPortn OBJECT-TYPE
	SYNTAX  EkiOnOff
	MAX-ACCESS read-only
	STATUS current
	DESCRIPTION
        "
        Client SFP Rx Power Low Warning
        :Warning indicating that the SFP
        input power of port is lower than
        the threshold value written in
         the SFP EEPROM <Condtype> CLIENT_RX_PWR_LOW_WNG_1
        <Probcause> receiveFailure (41)
        <Alarmtype> equipmentAlarm (5)
         <Polarity> (2)
        "
	::= { pm253AlmclientSfpWarnDdmEntry 16 }


pm253AlmClientTempHighWngPortn OBJECT-TYPE
	SYNTAX  EkiOnOff
	MAX-ACCESS read-only
	STATUS current
	DESCRIPTION
        "
        Client SFP Temp High Warning :Warning
        indicating that the SFP temperature
        of port is higher than the threshold
        value written in the SFP EEPROM
        <Condtype> CLIENT_TEMP_HIGH_WNG_1
        <Probcause> temperatureUnacceptable
        (51) <Alarmtype> equipmentAlarm
        (5) <Polarity> (2)
        "
	::= { pm253AlmclientSfpWarnDdmEntry 9 }


pm253AlmClientTempLowWngPortn OBJECT-TYPE
	SYNTAX  EkiOnOff
	MAX-ACCESS read-only
	STATUS current
	DESCRIPTION
        "
        Client SFP Temp Low Warning :Warning
        indicating that the SFP temperature
        of port is lower than the threshold
        value written in the SFP EEPROM
        <Condtype> CLIENT_TEMP_LOW_WNG_1
        <Probcause> temperatureUnacceptable
        (51) <Alarmtype> equipmentAlarm
        (5) <Polarity> (2)
        "
	::= { pm253AlmclientSfpWarnDdmEntry 8 }


pm253AlmClientVccHighWngPortn OBJECT-TYPE
	SYNTAX  EkiOnOff
	MAX-ACCESS read-only
	STATUS current
	DESCRIPTION
        "
        Client SFP Power Supply High Warning
        :Warning indicating that the SFP
        power supply of port is higher
         than the threshold value written
        in the SFP EEPROM  <Condtype> CLIENT_VCC_HIGH_WNG_1
        <Probcause> powerProblem (36) <Alarmtype>
        equipmentAlarm (5) <Polarity> (2)
        "
	::= { pm253AlmclientSfpWarnDdmEntry 7 }


pm253AlmClientVccLowWngPortn OBJECT-TYPE
	SYNTAX  EkiOnOff
	MAX-ACCESS read-only
	STATUS current
	DESCRIPTION
        "
        Client SFP Power Supply Low Warning
        :Warning indicating that the SFP
        power supply of port is lower than
        the threshold value written in
         the SFP EEPROM  <Condtype> CLIENT_VCC_LOW_WNG_1
        <Probcause> powerProblem (36) <Alarmtype>
        equipmentAlarm (5) <Polarity> (2)
        "
	::= { pm253AlmclientSfpWarnDdmEntry 6 }


pm253AlmClientTxBiasHighWngPortn OBJECT-TYPE
	SYNTAX  EkiOnOff
	MAX-ACCESS read-only
	STATUS current
	DESCRIPTION
        "
        Client SFP Bias High Warning :Warning
        indicating that the SFP laser bias
        current of port is higher than
         the threshold value written in
        the SFP EEPROM <Condtype> CLIENT_TX_BIAS_HIGH_WNG_1
        <Probcause> transmitterFailure
         (56) <Alarmtype> equipmentAlarm
        (5) <Polarity> (2)
        "
	::= { pm253AlmclientSfpWarnDdmEntry 5 }


pm253AlmClientTxBiasLowWngPortn OBJECT-TYPE
	SYNTAX  EkiOnOff
	MAX-ACCESS read-only
	STATUS current
	DESCRIPTION
        "
        Client SFP Bias Low Warning :Warning
        indicating that the SFP laser bias
        current of port is lower than the
        threshold value written in the
         SFP EEPROM <Condtype> CLIENT_TX_BIAS_LOW_WNG_1
        <Probcause> transmitterFailure
         (56) <Alarmtype> equipmentAlarm
        (5) <Polarity> (2)
        "
	::= { pm253AlmclientSfpWarnDdmEntry 4 }


pm253AlmClientTxPwrHighWngPortn OBJECT-TYPE
	SYNTAX  EkiOnOff
	MAX-ACCESS read-only
	STATUS current
	DESCRIPTION
        "
        Client SFP Tx Power High Warning
        :Warning indicating that the SFP
        output power of port is higher
         than the threshold value written
        in the SFP EEPROM <Condtype> CLIENT_TX_PWR_HIGH_WNG_1
        <Probcause> transmitterFailure
         (56) <Alarmtype> equipmentAlarm
        (5) <Polarity> (2)
        "
	::= { pm253AlmclientSfpWarnDdmEntry 3 }


pm253AlmClientTxPwLowWngPortn OBJECT-TYPE
	SYNTAX  EkiOnOff
	MAX-ACCESS read-only
	STATUS current
	DESCRIPTION
        "
        Client SFP Tx Power Low Warning
        :Warning indicating that the SFP
        output power of port is lower than
        the threshold value written in
         the SFP EEPROM <Condtype> CLIENT_TX_PW_LOW_WNG_1
        <Probcause> transmitterFailure
         (56) <Alarmtype> equipmentAlarm
        (5) <Polarity> (2)
        "
	::= { pm253AlmclientSfpWarnDdmEntry 2 }


--- *********************************************************
---     TABLE for the pm253AlmclientMapperDeAlm articles
--- *********************************************************

pm253AlmclientMapperDeAlmTable OBJECT-TYPE
	SYNTAX  SEQUENCE OF Pm253AlmclientMapperDeAlmEntry
	MAX-ACCESS not-accessible
	STATUS current
	DESCRIPTION
        "
        List of pm253AlmclientMapperDeAlm
        Article
        "
	::= { pm253AlmPortCrit 72 }


pm253AlmclientMapperDeAlmEntry OBJECT-TYPE
	SYNTAX Pm253AlmclientMapperDeAlmEntry
	MAX-ACCESS not-accessible
	STATUS current
	DESCRIPTION
        "
        Row definition for the pm253AlmclientMapperDeAlm
        table
        "
	INDEX   { pm253AlmclientMapperDeAlmIndex }
	::= { pm253AlmclientMapperDeAlmTable 1 }


Pm253AlmclientMapperDeAlmEntry ::=
	SEQUENCE {
	pm253AlmclientMapperDeAlmIndex
		INTEGER,
	pm253AlmClientLoopAccFifoFailPortn
		EkiOnOff,
	pm253AlmClientDwBufferOvlPortn
		EkiOnOff,
	pm253AlmClientDwCsfDetPortn
		EkiOnOff,
	pm253AlmClientUpBufferOvlPortn
		EkiOnOff,
	pm253AlmClientUpAccOosPortn
		EkiOnOff
	}


pm253AlmclientMapperDeAlmIndex OBJECT-TYPE
	SYNTAX  INTEGER(0..128)
	MAX-ACCESS  read-only
	STATUS current
	DESCRIPTION
        "
        Index definition for the pm253AlmclientMapperDeAlm
        table
        "
	::= { pm253AlmclientMapperDeAlmEntry 1 }


pm253AlmClientLoopAccFifoFailPortn OBJECT-TYPE
	SYNTAX  EkiOnOff
	MAX-ACCESS read-only
	STATUS deprecated
	DESCRIPTION
        "
        Client Port Loop FIFO Failure
         :active only in client loopback
        mode. <Condtype> CLIENT_LOOP_ACC_FIFO_FAIL_1
        <Probcause> equipmentMalfunction
        (16) <Alarmtype> equipmentAlarm
        (5) <Polarity> (2)
        "
	::= { pm253AlmclientMapperDeAlmEntry 16 }


pm253AlmClientDwBufferOvlPortn OBJECT-TYPE
	SYNTAX  EkiOnOff
	MAX-ACCESS read-only
	STATUS current
	DESCRIPTION
        "
        Client Downstream Buffer Overload
        :This OID indicates that the de-mapper
        buffer for client port is in overload.
         <Help>  This alarm indicates if
        there is a downstream FIFO overload
        for this client port <Condtype>
        CLIENT_DW_BUFFER_OVL_1 <Probcause>
        equipmentMalfunction (16) <Alarmtype>
        equipmentAlarm (5) <Polarity> (2)
        "
	::= { pm253AlmclientMapperDeAlmEntry 15 }


pm253AlmClientDwCsfDetPortn OBJECT-TYPE
	SYNTAX  EkiOnOff
	MAX-ACCESS read-only
	STATUS current
	DESCRIPTION
        "
        Client Signal Fail Detected :This
        OID indicates that a CSF has been
        detected on client port in the
         downstream direction   <Help>
          This alarm indicates if a Client
        Signal Fail has been detected in
        the incoming line frame for this
        client port <Condtype> CLIENT_DW_CSF_DET_1
        <Probcause> receiveFailure (41)
        <Alarmtype> integrityViolation
         (7) <Polarity> (2)
        "
	::= { pm253AlmclientMapperDeAlmEntry 12 }


pm253AlmClientUpBufferOvlPortn OBJECT-TYPE
	SYNTAX  EkiOnOff
	MAX-ACCESS read-only
	STATUS current
	DESCRIPTION
        "
        Client Upstream Buffer Overload
        :This OID indicates that the rate
        adaptation buffer for client port
        is in overload.  <Help>  This alarm
        indicates if there is a upstream
        FIFO overload for this client port
        <Condtype> CLIENT_UP_BUFFER_OVL_1
        <Probcause> receiveFailure (41)
        <Alarmtype> integrityViolation
         (7) <Polarity> (2)
        "
	::= { pm253AlmclientMapperDeAlmEntry 11 }


pm253AlmClientUpAccOosPortn OBJECT-TYPE
	SYNTAX  EkiOnOff
	MAX-ACCESS read-only
	STATUS current
	DESCRIPTION
        "
        Client Loss Of 10b/8b Synchro
         :This OID indicates the upstream
        client input port has lost synchronization
        on its 10B/8B decoder  <Help>
         This alarms indicates if the input
        client signal is correctly synchronized
        with the 10b/8b decoder <Condtype>
        CLIENT_UP_ACC_OOS_1 <Probcause>
        receiveFailure (41) <Alarmtype>
        integrityViolation (7) <Polarity>
        (2)
        "
	::= { pm253AlmclientMapperDeAlmEntry 2 }


--- *********************************************************
---     TABLE for the pm253AlmaccessioSdhAlarm articles
--- *********************************************************

pm253AlmaccessioSdhAlarmTable OBJECT-TYPE
	SYNTAX  SEQUENCE OF Pm253AlmaccessioSdhAlarmEntry
	MAX-ACCESS not-accessible
	STATUS current
	DESCRIPTION
        "
        List of pm253AlmaccessioSdhAlarm
        Article
        "
	::= { pm253AlmPortCrit 104 }


pm253AlmaccessioSdhAlarmEntry OBJECT-TYPE
	SYNTAX Pm253AlmaccessioSdhAlarmEntry
	MAX-ACCESS not-accessible
	STATUS current
	DESCRIPTION
        "
        Row definition for the pm253AlmaccessioSdhAlarm
        table
        "
	INDEX   { pm253AlmaccessioSdhAlarmIndex }
	::= { pm253AlmaccessioSdhAlarmTable 1 }


Pm253AlmaccessioSdhAlarmEntry ::=
	SEQUENCE {
	pm253AlmaccessioSdhAlarmIndex
		INTEGER,
	pm253AlmClientOofPortn
		EkiOnOff,
	pm253AlmClientRdiDetPortn
		EkiOnOff,
	pm253AlmClientAisDetPortn
		EkiOnOff,
	pm253AlmTxLossOfLockPortn
		EkiOnOff,
	pm253AlmRxLossOfLockPortn
		EkiOnOff,
	pm253AlmFifoErrPortn
		EkiOnOff,
	pm253AlmLosTrscPortn
		EkiOnOff
	}


pm253AlmaccessioSdhAlarmIndex OBJECT-TYPE
	SYNTAX  INTEGER(0..128)
	MAX-ACCESS  read-only
	STATUS current
	DESCRIPTION
        "
        Index definition for the pm253AlmaccessioSdhAlarm
        table
        "
	::= { pm253AlmaccessioSdhAlarmEntry 1 }


pm253AlmClientOofPortn OBJECT-TYPE
	SYNTAX  EkiOnOff
	MAX-ACCESS read-only
	STATUS current
	DESCRIPTION
        "
        Client Rx Out Of Frame :This OID
        indicates that an Out Of Frame
         condition has been detected on
        the client input stream   <Help>
         This alarm indicates if there
         is a Out of Frame is detected
         on the client input signal <Condtype>
        CLIENT_OOF_1 <Probcause> receiveFailure
        (41) <Alarmtype> integrityViolation
        (7) <Polarity> (2)
        "
	::= { pm253AlmaccessioSdhAlarmEntry 8 }


pm253AlmClientRdiDetPortn OBJECT-TYPE
	SYNTAX  EkiOnOff
	MAX-ACCESS read-only
	STATUS current
	DESCRIPTION
        "
        MS-RDI Detected On Client Input
        :This OID indicates that a MS-RDI
        has been detected on the client
        input stream  <Help>  This alarm
        indicates if there is a MS-RDI/L-RDI
        is detected on the client input
        signal <Condtype> CLIENT_RDI_DET_1
        <Probcause> other (1) <Alarmtype>
        other (1) <Polarity> (2)
        "
	::= { pm253AlmaccessioSdhAlarmEntry 7 }


pm253AlmClientAisDetPortn OBJECT-TYPE
	SYNTAX  EkiOnOff
	MAX-ACCESS read-only
	STATUS current
	DESCRIPTION
        "
        MS-AIS Detected On Client Input
        :This OID indicates that a MS-AIS
        has been detected on the client
        input stream  <Help>  This alarm
        indicates if there is a MS-AIS/L-AIS
        is detected on the client input
        signal <Condtype> CLIENT_AIS_DET_1
        <Probcause> other (1) <Alarmtype>
        other (1) <Polarity> (2)
        "
	::= { pm253AlmaccessioSdhAlarmEntry 6 }


pm253AlmTxLossOfLockPortn OBJECT-TYPE
	SYNTAX  EkiOnOff
	MAX-ACCESS read-only
	STATUS current
	DESCRIPTION
        "
        Client Tx Clock Lock Error :This
        OID indicates that the transmit
        clock of the client transceiver
        is not locked <Condtype> TX_LOSS_OF_LOCK_1
        <Probcause> transmitterFailure
         (56) <Alarmtype> equipmentAlarm
        (5) <Polarity> (2)
        "
	::= { pm253AlmaccessioSdhAlarmEntry 5 }


pm253AlmRxLossOfLockPortn OBJECT-TYPE
	SYNTAX  EkiOnOff
	MAX-ACCESS read-only
	STATUS current
	DESCRIPTION
        "
        Client Rx Clock Lock Error :This
        OID indicates the recovered receive
        clock of the client transceiver
        is not locked <Condtype> RX_LOSS_OF_LOCK_1
        <Probcause> receiveFailure (41)
        <Alarmtype> equipmentAlarm (5)
         <Polarity> (2)
        "
	::= { pm253AlmaccessioSdhAlarmEntry 4 }


pm253AlmFifoErrPortn OBJECT-TYPE
	SYNTAX  EkiOnOff
	MAX-ACCESS read-only
	STATUS current
	DESCRIPTION
        "
        Client Transceiver Fifo Error
         :This OID indicates that an error
        has been detected in the FIFO of
        the client transceiver <Condtype>
        FIFO_ERR_1 <Probcause> receiveFailure
        (41) <Alarmtype> equipmentAlarm
        (5) <Polarity> (2)
        "
	::= { pm253AlmaccessioSdhAlarmEntry 3 }


pm253AlmLosTrscPortn OBJECT-TYPE
	SYNTAX  EkiOnOff
	MAX-ACCESS read-only
	STATUS current
	DESCRIPTION
        "
        Client Transceiver Loss Of Signal
        :This OID indicates that a Loss
        of Signal condition has been detected
        on the client input transceiver
        <Condtype> LOS_TRSC_1 <Probcause>
        receiveFailure (41) <Alarmtype>
        equipmentAlarm (5) <Polarity> (2)
        "
	::= { pm253AlmaccessioSdhAlarmEntry 2 }


--- *********************************************************
---     TABLE for the pm253AlmlineDfrmAlm articles
--- *********************************************************

pm253AlmlineDfrmAlmTable OBJECT-TYPE
	SYNTAX  SEQUENCE OF Pm253AlmlineDfrmAlmEntry
	MAX-ACCESS not-accessible
	STATUS current
	DESCRIPTION
        "
        List of pm253AlmlineDfrmAlm Article
        "
	::= { pm253AlmLineCrit 128 }


pm253AlmlineDfrmAlmEntry OBJECT-TYPE
	SYNTAX Pm253AlmlineDfrmAlmEntry
	MAX-ACCESS not-accessible
	STATUS current
	DESCRIPTION
        "
        Row definition for the pm253AlmlineDfrmAlm
        table
        "
	INDEX   { pm253AlmlineDfrmAlmIndex }
	::= { pm253AlmlineDfrmAlmTable 1 }


Pm253AlmlineDfrmAlmEntry ::=
	SEQUENCE {
	pm253AlmlineDfrmAlmIndex
		INTEGER,
	pm253AlmDwAuAisSecondPortn
		EkiOnOff,
	pm253AlmDwLopSecondPortn
		EkiOnOff,
	pm253AlmDwAuAisFirstPortn
		EkiOnOff,
	pm253AlmDwLopFirstPortn
		EkiOnOff,
	pm253AlmLineDwLofPortn
		EkiOnOff,
	pm253AlmLineDwOofPortn
		EkiOnOff,
	pm253AlmLineDwRdiDetPortn
		EkiOnOff,
	pm253AlmLineDwAisDetPortn
		EkiOnOff
	}


pm253AlmlineDfrmAlmIndex OBJECT-TYPE
	SYNTAX  INTEGER(0..128)
	MAX-ACCESS  read-only
	STATUS current
	DESCRIPTION
        "
        Index definition for the pm253AlmlineDfrmAlm
        table
        "
	::= { pm253AlmlineDfrmAlmEntry 1 }


pm253AlmDwAuAisSecondPortn OBJECT-TYPE
	SYNTAX  EkiOnOff
	MAX-ACCESS read-only
	STATUS current
	DESCRIPTION
        "
        P-AIS On The 2nd STS24c :This
         OID indicates that an AU-AIS/AIS-P
        has been detected on second incoming
        STS-24c input signal  <Help>  This
        alarm indicates if a Path AIS is
        detected on the second STS-24c
         <Condtype> DW_AU_AIS_SECOND_1
         <Probcause> receiveFailure (41)
        <Alarmtype> operationalViolation
        (8) <Polarity> (2)
        "
	::= { pm253AlmlineDfrmAlmEntry 13 }


pm253AlmDwLopSecondPortn OBJECT-TYPE
	SYNTAX  EkiOnOff
	MAX-ACCESS read-only
	STATUS current
	DESCRIPTION
        "
        P-LOP On The 2nd STS24c :This
         OID indicates that a Loss Of Pointer
        has been detected on second incoming
        STS-24c input signal  <Help>  This
        alarm indicates if Loss of Pointer
        is detected on the second STS-24c
        <Condtype> DW_LOP_SECOND_1 <Probcause>
        receiveFailure (41) <Alarmtype>
        integrityViolation (7) <Polarity>
        (2)
        "
	::= { pm253AlmlineDfrmAlmEntry 12 }


pm253AlmDwAuAisFirstPortn OBJECT-TYPE
	SYNTAX  EkiOnOff
	MAX-ACCESS read-only
	STATUS current
	DESCRIPTION
        "
        P-AIS On STS48c Or 1st STS24c
         :This OID indicates that an AU-AIS/AIS-P
        has been detected on incoming STS-48c
         (or first STS-24c) input signal
         <Help>  This alarm indicates if
        a Path AIS is detected on the STS-48c
        or first STS-24c <Condtype> DW_AU_AIS_FIRST_1
        <Probcause> receiveFailure (41)
        <Alarmtype> operationalViolation
        (8) <Polarity> (2)
        "
	::= { pm253AlmlineDfrmAlmEntry 11 }


pm253AlmDwLopFirstPortn OBJECT-TYPE
	SYNTAX  EkiOnOff
	MAX-ACCESS read-only
	STATUS current
	DESCRIPTION
        "
        P-LOP On STS48c Or 1st STS24c
         :This OID indicates that a Loss
        Of Pointer has been detected on
        incoming STS-48c (or first STS-24c)
        input signal  <Help>  This alarm
        indicates if Loss of Pointer is
        detected on the STS-48c or first
        STS-24c <Condtype> DW_LOP_FIRST_1
        <Probcause> receiveFailure (41)
        <Alarmtype> integrityViolation
         (7) <Polarity> (2)
        "
	::= { pm253AlmlineDfrmAlmEntry 10 }


pm253AlmLineDwLofPortn OBJECT-TYPE
	SYNTAX  EkiOnOff
	MAX-ACCESS read-only
	STATUS current
	DESCRIPTION
        "
        SONET/SDH Line Loss Of Frame :This
        OID indicates that a Loss Of Frame
        has been detected on incoming
         OC-48c/STM-16c input signal  <Help>
         This alarm indicates if there
         is a Loss of Frame is detected
        on the line input signal <Condtype>
        LINE_DW_LOF_1 <Probcause> receiveFailure
        (41) <Alarmtype> integrityViolation
        (7) <Polarity> (2)
        "
	::= { pm253AlmlineDfrmAlmEntry 5 }


pm253AlmLineDwOofPortn OBJECT-TYPE
	SYNTAX  EkiOnOff
	MAX-ACCESS read-only
	STATUS current
	DESCRIPTION
        "
        SONET/SDH Line Out Of Frame :This
        OID indicates that an Out Of Frame
        has been detected on incoming
         OC-48c/STM-16c input signal  <Help>
         This alarm indicates if there
         is a Out of Frame is detected
         on the line input signal <Condtype>
        LINE_DW_OOF_1 <Probcause> receiveFailure
        (41) <Alarmtype> integrityViolation
        (7) <Polarity> (2)
        "
	::= { pm253AlmlineDfrmAlmEntry 4 }


pm253AlmLineDwRdiDetPortn OBJECT-TYPE
	SYNTAX  EkiOnOff
	MAX-ACCESS read-only
	STATUS current
	DESCRIPTION
        "
        MS-RDI/L-RDI Detected On Line
         Input :This OID indicates that
        an MS-RDI has been detected on
         incoming  OC-48c/STM-16c input
        signal  <Help>  This alarm indicates
        if there is a MS-RDI/L-RDI is detected
        on the line input signal <Condtype>
        LINE_DW_RDI_DET_1 <Probcause> remoteNodeTransmissionError
        (43) <Alarmtype> other (1) <Polarity>
        (2)
        "
	::= { pm253AlmlineDfrmAlmEntry 3 }


pm253AlmLineDwAisDetPortn OBJECT-TYPE
	SYNTAX  EkiOnOff
	MAX-ACCESS read-only
	STATUS current
	DESCRIPTION
        "
        MS-AIS/L-AIS Detected On Line
         Input :This OID indicates that
        an MS-AIS has been detected on
         incoming  OC-48c/STM-16c input
        signal  <Help>  This alarm indicates
        if there is a MS-AIS/L-AIS is detected
        on the line input signal <Condtype>
        LINE_DW_AIS_DET_1 <Probcause> receiveFailure
        (41) <Alarmtype> operationalViolation
        (8) <Polarity> (2)
        "
	::= { pm253AlmlineDfrmAlmEntry 2 }


--- *********************************************************
---     TABLE for the pm253AlmlineDownS1 articles
--- *********************************************************

pm253AlmlineDownS1Table OBJECT-TYPE
	SYNTAX  SEQUENCE OF Pm253AlmlineDownS1Entry
	MAX-ACCESS not-accessible
	STATUS current
	DESCRIPTION
        "
        List of pm253AlmlineDownS1 Article
        "
	::= { pm253AlmLineNurg 130 }


pm253AlmlineDownS1Entry OBJECT-TYPE
	SYNTAX Pm253AlmlineDownS1Entry
	MAX-ACCESS not-accessible
	STATUS current
	DESCRIPTION
        "
        Row definition for the pm253AlmlineDownS1
        table
        "
	INDEX   { pm253AlmlineDownS1Index }
	::= { pm253AlmlineDownS1Table 1 }


Pm253AlmlineDownS1Entry ::=
	SEQUENCE {
	pm253AlmlineDownS1Index
		INTEGER,
	pm253AlmlineDownS1Portn
		INTEGER
	}


pm253AlmlineDownS1Index OBJECT-TYPE
	SYNTAX  INTEGER(0..128)
	MAX-ACCESS  read-only
	STATUS current
	DESCRIPTION
        "
        Index definition for the pm253AlmlineDownS1
        table
        "
	::= { pm253AlmlineDownS1Entry 1 }


pm253AlmlineDownS1Portn OBJECT-TYPE
	SYNTAX  INTEGER (0..255)
	MAX-ACCESS read-only
	STATUS current
	DESCRIPTION
        "
        Line 1 S1 Extracted Value :This
        gives the value of S1 extracted
        from the overhead of the received
        OC-48c/STM-16c signal on the line
        1 <Condtype> LINE_DW_S1_8_1 <Probcause>
        other (1) <Alarmtype> other (1)
        <Polarity> (2)
        "
	::= { pm253AlmlineDownS1Entry 2 }


--- *********************************************************
---     TABLE for the pm253AlmlineDownK1 articles
--- *********************************************************

pm253AlmlineDownK1Table OBJECT-TYPE
	SYNTAX  SEQUENCE OF Pm253AlmlineDownK1Entry
	MAX-ACCESS not-accessible
	STATUS current
	DESCRIPTION
        "
        List of pm253AlmlineDownK1 Article
        "
	::= { pm253AlmLineNurg 131 }


pm253AlmlineDownK1Entry OBJECT-TYPE
	SYNTAX Pm253AlmlineDownK1Entry
	MAX-ACCESS not-accessible
	STATUS current
	DESCRIPTION
        "
        Row definition for the pm253AlmlineDownK1
        table
        "
	INDEX   { pm253AlmlineDownK1Index }
	::= { pm253AlmlineDownK1Table 1 }


Pm253AlmlineDownK1Entry ::=
	SEQUENCE {
	pm253AlmlineDownK1Index
		INTEGER,
	pm253AlmlineDownK1Portn
		INTEGER
	}


pm253AlmlineDownK1Index OBJECT-TYPE
	SYNTAX  INTEGER(0..128)
	MAX-ACCESS  read-only
	STATUS current
	DESCRIPTION
        "
        Index definition for the pm253AlmlineDownK1
        table
        "
	::= { pm253AlmlineDownK1Entry 1 }


pm253AlmlineDownK1Portn OBJECT-TYPE
	SYNTAX  INTEGER (0..255)
	MAX-ACCESS read-only
	STATUS current
	DESCRIPTION
        "
        Line 1 K1 Extracted Value :This
        gives the value of K1 extracted
        from the overhead of the received
        OC-48c/STM-16c signal on the line
        1 <Condtype> LINE_DW_K1_8_1 <Probcause>
        other (1) <Alarmtype> other (1)
        <Polarity> (2)
        "
	::= { pm253AlmlineDownK1Entry 2 }


--- *********************************************************
---     TABLE for the pm253AlmlineDownK2 articles
--- *********************************************************

pm253AlmlineDownK2Table OBJECT-TYPE
	SYNTAX  SEQUENCE OF Pm253AlmlineDownK2Entry
	MAX-ACCESS not-accessible
	STATUS current
	DESCRIPTION
        "
        List of pm253AlmlineDownK2 Article
        "
	::= { pm253AlmLineNurg 132 }


pm253AlmlineDownK2Entry OBJECT-TYPE
	SYNTAX Pm253AlmlineDownK2Entry
	MAX-ACCESS not-accessible
	STATUS current
	DESCRIPTION
        "
        Row definition for the pm253AlmlineDownK2
        table
        "
	INDEX   { pm253AlmlineDownK2Index }
	::= { pm253AlmlineDownK2Table 1 }


Pm253AlmlineDownK2Entry ::=
	SEQUENCE {
	pm253AlmlineDownK2Index
		INTEGER,
	pm253AlmlineDownK2Portn
		INTEGER
	}


pm253AlmlineDownK2Index OBJECT-TYPE
	SYNTAX  INTEGER(0..128)
	MAX-ACCESS  read-only
	STATUS current
	DESCRIPTION
        "
        Index definition for the pm253AlmlineDownK2
        table
        "
	::= { pm253AlmlineDownK2Entry 1 }


pm253AlmlineDownK2Portn OBJECT-TYPE
	SYNTAX  INTEGER (0..255)
	MAX-ACCESS read-only
	STATUS current
	DESCRIPTION
        "
        Line 1 K2 Extracted Value :This
        gives the value of K2 extracted
        from the overhead of the received
        OC-48c/STM-16c signal on the line
        1 <Condtype> LINE_DW_K2_8_1 <Probcause>
        other (1) <Alarmtype> other (1)
        <Polarity> (2)
        "
	::= { pm253AlmlineDownK2Entry 2 }


--- *********************************************************
---     TABLE for the pm253AlmlineIoAlm articles
--- *********************************************************

pm253AlmlineIoAlmTable OBJECT-TYPE
	SYNTAX  SEQUENCE OF Pm253AlmlineIoAlmEntry
	MAX-ACCESS not-accessible
	STATUS current
	DESCRIPTION
        "
        List of pm253AlmlineIoAlm Article
        "
	::= { pm253AlmLineCrit 160 }


pm253AlmlineIoAlmEntry OBJECT-TYPE
	SYNTAX Pm253AlmlineIoAlmEntry
	MAX-ACCESS not-accessible
	STATUS current
	DESCRIPTION
        "
        Row definition for the pm253AlmlineIoAlm
        table
        "
	INDEX   { pm253AlmlineIoAlmIndex }
	::= { pm253AlmlineIoAlmTable 1 }


Pm253AlmlineIoAlmEntry ::=
	SEQUENCE {
	pm253AlmlineIoAlmIndex
		INTEGER,
	pm253AlmLineDwLosPortn
		EkiOnOff,
	pm253AlmLineUpLasFailPortn
		EkiOnOff
	}


pm253AlmlineIoAlmIndex OBJECT-TYPE
	SYNTAX  INTEGER(0..128)
	MAX-ACCESS  read-only
	STATUS current
	DESCRIPTION
        "
        Index definition for the pm253AlmlineIoAlm
        table
        "
	::= { pm253AlmlineIoAlmEntry 1 }


pm253AlmLineDwLosPortn OBJECT-TYPE
	SYNTAX  EkiOnOff
	MAX-ACCESS read-only
	STATUS current
	DESCRIPTION
        "
        Line Input Loss Of Signal :This
        OID indicates that no signal is
        present on the SFP of the line
         port #n  <Help>  This alarm indicates
        if an optical signal is detected
        on the line transceiver input <Condtype>
        LINE_DW_LOS_1 <Probcause> receiveFailure
        (41) <Alarmtype> physicalViolation
        (9) <Polarity> (2)
        "
	::= { pm253AlmlineIoAlmEntry 5 }


pm253AlmLineUpLasFailPortn OBJECT-TYPE
	SYNTAX  EkiOnOff
	MAX-ACCESS read-only
	STATUS current
	DESCRIPTION
        "
        Line SFP Tx Failed :This OID indicates
        that the transmitter fails for
         the SFP plugged into the line
         port #n (this alarm reports the
        transmitter failure alarm generated
        by the SFPs)  <Help>  This alarm
        indicates if the laser of the client
        transceiver is in fail condition
        <Condtype> LINE_UP_LAS_FAIL_1 <Probcause>
        transmitterFailure (56) <Alarmtype>
        equipmentAlarm (5) <Polarity> (2)
        "
	::= { pm253AlmlineIoAlmEntry 2 }


--- *********************************************************
---     TABLE for the pm253AlmlineSfpAlaDdm articles
--- *********************************************************

pm253AlmlineSfpAlaDdmTable OBJECT-TYPE
	SYNTAX  SEQUENCE OF Pm253AlmlineSfpAlaDdmEntry
	MAX-ACCESS not-accessible
	STATUS current
	DESCRIPTION
        "
        List of pm253AlmlineSfpAlaDdm
         Article
        "
	::= { pm253AlmLineUrg 162 }


pm253AlmlineSfpAlaDdmEntry OBJECT-TYPE
	SYNTAX Pm253AlmlineSfpAlaDdmEntry
	MAX-ACCESS not-accessible
	STATUS current
	DESCRIPTION
        "
        Row definition for the pm253AlmlineSfpAlaDdm
        table
        "
	INDEX   { pm253AlmlineSfpAlaDdmIndex }
	::= { pm253AlmlineSfpAlaDdmTable 1 }


Pm253AlmlineSfpAlaDdmEntry ::=
	SEQUENCE {
	pm253AlmlineSfpAlaDdmIndex
		INTEGER,
	pm253AlmLineRxPwrHighAlaPortn
		EkiOnOff,
	pm253AlmLineRxPwrLowAlaPortn
		EkiOnOff,
	pm253AlmLineTempHighAlaPortn
		EkiOnOff,
	pm253AlmLineTempLowAlaPortn
		EkiOnOff,
	pm253AlmLineVccHighAlaPortn
		EkiOnOff,
	pm253AlmLineVccLowAlaPortn
		EkiOnOff,
	pm253AlmLineTxBiasHighAlaPortn
		EkiOnOff,
	pm253AlmLineTxBiasLowAlaPortn
		EkiOnOff,
	pm253AlmLineTxPwrHighAlaPortn
		EkiOnOff,
	pm253AlmLineTxPwrLowAlaPortn
		EkiOnOff
	}


pm253AlmlineSfpAlaDdmIndex OBJECT-TYPE
	SYNTAX  INTEGER(0..128)
	MAX-ACCESS  read-only
	STATUS current
	DESCRIPTION
        "
        Index definition for the pm253AlmlineSfpAlaDdm
        table
        "
	::= { pm253AlmlineSfpAlaDdmEntry 1 }


pm253AlmLineRxPwrHighAlaPortn OBJECT-TYPE
	SYNTAX  EkiOnOff
	MAX-ACCESS read-only
	STATUS current
	DESCRIPTION
        "
        Line SFP Rx Power High :Alarm
         indicating that the SFP input
         power of Line is higher than the
        threshold value written in the
         SFP EEPROM <Condtype> LINE_RX_PWR_HIGH_ALA_1
        <Probcause> receiveFailure (41)
        <Alarmtype> equipmentAlarm (5)
         <Polarity> (2)
        "
	::= { pm253AlmlineSfpAlaDdmEntry 17 }


pm253AlmLineRxPwrLowAlaPortn OBJECT-TYPE
	SYNTAX  EkiOnOff
	MAX-ACCESS read-only
	STATUS current
	DESCRIPTION
        "
        Line SFP Rx Power Low :Alarm indicating
        that the SFP input power of Line
        is lower than the threshold value
        written in the SFP EEPROM <Condtype>
        LINE_RX_PWR_LOW_ALA_1 <Probcause>
        receiveFailure (41) <Alarmtype>
        equipmentAlarm (5) <Polarity> (2)
        "
	::= { pm253AlmlineSfpAlaDdmEntry 16 }


pm253AlmLineTempHighAlaPortn OBJECT-TYPE
	SYNTAX  EkiOnOff
	MAX-ACCESS read-only
	STATUS current
	DESCRIPTION
        "
        Line SFP Temp High :Alarm indicating
        that the SFP temperature of Line
        is higher than the threshold value
        written in the SFP EEPROM <Condtype>
        LINE_TEMP_HIGH_ALA_1 <Probcause>
        temperatureUnacceptable (51) <Alarmtype>
        equipmentAlarm (5) <Polarity> (2)
        "
	::= { pm253AlmlineSfpAlaDdmEntry 9 }


pm253AlmLineTempLowAlaPortn OBJECT-TYPE
	SYNTAX  EkiOnOff
	MAX-ACCESS read-only
	STATUS current
	DESCRIPTION
        "
        Line SFP Temp Low :Alarm indicating
        that the SFP temperature of Line
        is lower than the threshold value
        written in the SFP EEPROM <Condtype>
        LINE_TEMP_LOW_ALA_1 <Probcause>
        temperatureUnacceptable (51) <Alarmtype>
        equipmentAlarm (5) <Polarity> (2)
        "
	::= { pm253AlmlineSfpAlaDdmEntry 8 }


pm253AlmLineVccHighAlaPortn OBJECT-TYPE
	SYNTAX  EkiOnOff
	MAX-ACCESS read-only
	STATUS current
	DESCRIPTION
        "
        Line SFP Power Supply High :Alarm
        indicating that the SFP power supply
        of Line is higher than the threshold
        value written in the SFP EEPROM
         <Condtype> LINE_VCC_HIGH_ALA_1
        <Probcause> powerProblem (36) <Alarmtype>
        equipmentAlarm (5) <Polarity> (2)
        "
	::= { pm253AlmlineSfpAlaDdmEntry 7 }


pm253AlmLineVccLowAlaPortn OBJECT-TYPE
	SYNTAX  EkiOnOff
	MAX-ACCESS read-only
	STATUS current
	DESCRIPTION
        "
        Line SFP Power Supply Low :Alarm
        indicating that the SFP power supply
        of Line is lower than the threshold
        value written in the SFP EEPROM
         <Condtype> LINE_VCC_LOW_ALA_1
         <Probcause> powerProblem (36)
         <Alarmtype> equipmentAlarm (5)
        <Polarity> (2)
        "
	::= { pm253AlmlineSfpAlaDdmEntry 6 }


pm253AlmLineTxBiasHighAlaPortn OBJECT-TYPE
	SYNTAX  EkiOnOff
	MAX-ACCESS read-only
	STATUS current
	DESCRIPTION
        "
        Line SFP Bias High :Alarm indicating
        that the SFP laser bias current
        of Line is higher than the threshold
        value written in the SFP EEPROM
        <Condtype> LINE_TX_BIAS_HIGH_ALA_1
        <Probcause> transmitterFailure
         (56) <Alarmtype> equipmentAlarm
        (5) <Polarity> (2)
        "
	::= { pm253AlmlineSfpAlaDdmEntry 5 }


pm253AlmLineTxBiasLowAlaPortn OBJECT-TYPE
	SYNTAX  EkiOnOff
	MAX-ACCESS read-only
	STATUS current
	DESCRIPTION
        "
        Line SFP Bias Low :Alarm indicating
        that the SFP laser bias current
        of Line is lower than the threshold
        value written in the SFP EEPROM
        <Condtype> LINE_TX_BIAS_LOW_ALA_1
        <Probcause> transmitterFailure
         (56) <Alarmtype> equipmentAlarm
        (5) <Polarity> (2)
        "
	::= { pm253AlmlineSfpAlaDdmEntry 4 }


pm253AlmLineTxPwrHighAlaPortn OBJECT-TYPE
	SYNTAX  EkiOnOff
	MAX-ACCESS read-only
	STATUS current
	DESCRIPTION
        "
        Line SFP Tx Power High :Alarm
         indicating that the SFP output
        power of Line is higher than the
        threshold value written in the
         SFP EEPROM <Condtype> LINE_TX_PWR_HIGH_ALA_1
        <Probcause> transmitterFailure
         (56) <Alarmtype> equipmentAlarm
        (5) <Polarity> (2)
        "
	::= { pm253AlmlineSfpAlaDdmEntry 3 }


pm253AlmLineTxPwrLowAlaPortn OBJECT-TYPE
	SYNTAX  EkiOnOff
	MAX-ACCESS read-only
	STATUS current
	DESCRIPTION
        "
        Line SFP Tx Power Low :Alarm indicating
        that the SFP output power of Line
        is lower than the threshold value
        written in the SFP EEPROM <Condtype>
        LINE_TX_PWR_LOW_ALA_1 <Probcause>
        transmitterFailure (56) <Alarmtype>
        equipmentAlarm (5) <Polarity> (2)
        "
	::= { pm253AlmlineSfpAlaDdmEntry 2 }


--- *********************************************************
---     TABLE for the pm253AlmlineSfpWarnDdm articles
--- *********************************************************

pm253AlmlineSfpWarnDdmTable OBJECT-TYPE
	SYNTAX  SEQUENCE OF Pm253AlmlineSfpWarnDdmEntry
	MAX-ACCESS not-accessible
	STATUS current
	DESCRIPTION
        "
        List of pm253AlmlineSfpWarnDdm
        Article
        "
	::= { pm253AlmLineNurg 164 }


pm253AlmlineSfpWarnDdmEntry OBJECT-TYPE
	SYNTAX Pm253AlmlineSfpWarnDdmEntry
	MAX-ACCESS not-accessible
	STATUS current
	DESCRIPTION
        "
        Row definition for the pm253AlmlineSfpWarnDdm
        table
        "
	INDEX   { pm253AlmlineSfpWarnDdmIndex }
	::= { pm253AlmlineSfpWarnDdmTable 1 }


Pm253AlmlineSfpWarnDdmEntry ::=
	SEQUENCE {
	pm253AlmlineSfpWarnDdmIndex
		INTEGER,
	pm253AlmLineRxPwrHighWngPortn
		EkiOnOff,
	pm253AlmLineRxPwrLowWngPortn
		EkiOnOff,
	pm253AlmLineTempHighWngPortn
		EkiOnOff,
	pm253AlmLineTempLowWngPortn
		EkiOnOff,
	pm253AlmLineVccHighWngPortn
		EkiOnOff,
	pm253AlmLineVccLowWngPortn
		EkiOnOff,
	pm253AlmLineTxBiasHighWngPortn
		EkiOnOff,
	pm253AlmLineTxBiasLowWngPortn
		EkiOnOff,
	pm253AlmLineTxPwrHighWngPortn
		EkiOnOff,
	pm253AlmLineTxPwLowWngPortn
		EkiOnOff
	}


pm253AlmlineSfpWarnDdmIndex OBJECT-TYPE
	SYNTAX  INTEGER(0..128)
	MAX-ACCESS  read-only
	STATUS current
	DESCRIPTION
        "
        Index definition for the pm253AlmlineSfpWarnDdm
        table
        "
	::= { pm253AlmlineSfpWarnDdmEntry 1 }


pm253AlmLineRxPwrHighWngPortn OBJECT-TYPE
	SYNTAX  EkiOnOff
	MAX-ACCESS read-only
	STATUS current
	DESCRIPTION
        "
        Line SFP Rx Power High Warning
        :Warning indicating that the SFP
        input power of Line is higher than
        the threshold value written in
         the SFP EEPROM <Condtype> LINE_RX_PWR_HIGH_WNG_1
        <Probcause> receiveFailure (41)
        <Alarmtype> equipmentAlarm (5)
         <Polarity> (2)
        "
	::= { pm253AlmlineSfpWarnDdmEntry 17 }


pm253AlmLineRxPwrLowWngPortn OBJECT-TYPE
	SYNTAX  EkiOnOff
	MAX-ACCESS read-only
	STATUS current
	DESCRIPTION
        "
        Line SFP Rx Power Low Warning
         :Warning indicating that the SFP
        input power of Line is lower than
        the threshold value written in
         the SFP EEPROM <Condtype> LINE_RX_PWR_LOW_WNG_1
        <Probcause> receiveFailure (41)
        <Alarmtype> equipmentAlarm (5)
         <Polarity> (2)
        "
	::= { pm253AlmlineSfpWarnDdmEntry 16 }


pm253AlmLineTempHighWngPortn OBJECT-TYPE
	SYNTAX  EkiOnOff
	MAX-ACCESS read-only
	STATUS current
	DESCRIPTION
        "
        Line SFP Temp High Warning :Warning
        indicating that the SFP temperature
        of Line is higher than the threshold
        value written in the SFP EEPROM
        <Condtype> LINE_TEMP_HIGH_WNG_1
        <Probcause> temperatureUnacceptable
        (51) <Alarmtype> equipmentAlarm
        (5) <Polarity> (2)
        "
	::= { pm253AlmlineSfpWarnDdmEntry 9 }


pm253AlmLineTempLowWngPortn OBJECT-TYPE
	SYNTAX  EkiOnOff
	MAX-ACCESS read-only
	STATUS current
	DESCRIPTION
        "
        Line SFP Temp Low Warning :Warning
        indicating that the SFP temperature
        of Line is lower than the threshold
        value written in the SFP EEPROM
        <Condtype> LINE_TEMP_LOW_WNG_1
         <Probcause> temperatureUnacceptable
        (51) <Alarmtype> equipmentAlarm
        (5) <Polarity> (2)
        "
	::= { pm253AlmlineSfpWarnDdmEntry 8 }


pm253AlmLineVccHighWngPortn OBJECT-TYPE
	SYNTAX  EkiOnOff
	MAX-ACCESS read-only
	STATUS current
	DESCRIPTION
        "
        Line SFP Power Supply High Warning
        :Warning indicating that the SFP
        power supply of Line is higher
         than the threshold value written
        in the SFP EEPROM  <Condtype> LINE_VCC_HIGH_WNG_1
        <Probcause> powerProblem (36) <Alarmtype>
        equipmentAlarm (5) <Polarity> (2)
        "
	::= { pm253AlmlineSfpWarnDdmEntry 7 }


pm253AlmLineVccLowWngPortn OBJECT-TYPE
	SYNTAX  EkiOnOff
	MAX-ACCESS read-only
	STATUS current
	DESCRIPTION
        "
        Line SFP Power Supply Low Warning
        :Warning indicating that the SFP
        power supply of Line is lower than
        the threshold value written in
         the SFP EEPROM  <Condtype> LINE_VCC_LOW_WNG_1
        <Probcause> powerProblem (36) <Alarmtype>
        equipmentAlarm (5) <Polarity> (2)
        "
	::= { pm253AlmlineSfpWarnDdmEntry 6 }


pm253AlmLineTxBiasHighWngPortn OBJECT-TYPE
	SYNTAX  EkiOnOff
	MAX-ACCESS read-only
	STATUS current
	DESCRIPTION
        "
        Line SFP Bias High Warning :Warning
        indicating that the SFP laser bias
        current of Line is higher than
         the threshold value written in
        the SFP EEPROM <Condtype> LINE_TX_BIAS_HIGH_WNG_1
        <Probcause> transmitterFailure
         (56) <Alarmtype> equipmentAlarm
        (5) <Polarity> (2)
        "
	::= { pm253AlmlineSfpWarnDdmEntry 5 }


pm253AlmLineTxBiasLowWngPortn OBJECT-TYPE
	SYNTAX  EkiOnOff
	MAX-ACCESS read-only
	STATUS current
	DESCRIPTION
        "
        Line SFP Bias Low Warning :Warning
        indicating that the SFP laser bias
        current of Line is lower than the
        threshold value written in the
         SFP EEPROM <Condtype> LINE_TX_BIAS_LOW_WNG_1
        <Probcause> transmitterFailure
         (56) <Alarmtype> equipmentAlarm
        (5) <Polarity> (2)
        "
	::= { pm253AlmlineSfpWarnDdmEntry 4 }


pm253AlmLineTxPwrHighWngPortn OBJECT-TYPE
	SYNTAX  EkiOnOff
	MAX-ACCESS read-only
	STATUS current
	DESCRIPTION
        "
        Line SFP Tx Power High Warning
        :Warning indicating that the SFP
        output power of Line is higher
         than the threshold value written
        in the SFP EEPROM <Condtype> LINE_TX_PWR_HIGH_WNG_1
        <Probcause> transmitterFailure
         (56) <Alarmtype> equipmentAlarm
        (5) <Polarity> (2)
        "
	::= { pm253AlmlineSfpWarnDdmEntry 3 }


pm253AlmLineTxPwLowWngPortn OBJECT-TYPE
	SYNTAX  EkiOnOff
	MAX-ACCESS read-only
	STATUS current
	DESCRIPTION
        "
        Line SFP Tx Power Low Warning
         :Warning indicating that the SFP
        output power of Line is lower than
        the threshold value written in
         the SFP EEPROM <Condtype> LINE_TX_PW_LOW_WNG_1
        <Probcause> transmitterFailure
         (56) <Alarmtype> equipmentAlarm
        (5) <Polarity> (2)
        "
	::= { pm253AlmlineSfpWarnDdmEntry 2 }


--- *****************************************************
---     LEAF for the modInitFailLevel2 article
--- *****************************************************
pm253AlmmodInitFailLevel2 OBJECT IDENTIFIER ::= { pm253AlmOtherUrg 194 }




pm253AlmSwInitFail OBJECT-TYPE
	  SYNTAX EkiOnOff
	  MAX-ACCESS read-only
	  STATUS current
	  DESCRIPTION
        "
        SW Init Fail :This OID indicates
        that the SW intialization has caused
        unknown intial conditions  <Help>
         This alarm indicates if the SW
        module is correctly initialized
        <Condtype> SW_INIT_FAIL <Probcause>
        softwareError (47) <Alarmtype>
         processingErrorAlarm (4) <Polarity>
        (2)
        "
	  ::= { pm253AlmmodInitFailLevel2 5 }



pm253AlmResetHwInitFail OBJECT-TYPE
	  SYNTAX EkiOnOff
	  MAX-ACCESS read-only
	  STATUS current
	  DESCRIPTION
        "
        Reset HW Init Fail :This OID indicates
        that the HW intialization has caused
        unknown intial conditions  <Help>
         This alarm indicates if the HW
        has been correctly initialized
         <Condtype> RESET_HW_INIT_FAIL
         <Probcause> softwareError (47)
        <Alarmtype> processingErrorAlarm
        (4) <Polarity> (2)
        "
	  ::= { pm253AlmmodInitFailLevel2 4 }



pm253AlmBootUndone OBJECT-TYPE
	  SYNTAX EkiOnOff
	  MAX-ACCESS read-only
	  STATUS current
	  DESCRIPTION
        "
        Boot Undone :This OID indicates
        that the boot has not been correctly
        achieved  <Help>  This alarm indicates
        if the module has correctly boot
        <Condtype> BOOT_UNDONE <Probcause>
        softwareError (47) <Alarmtype>
         processingErrorAlarm (4) <Polarity>
        (2)
        "
	  ::= { pm253AlmmodInitFailLevel2 3 }



pm253AlmNextColdBootForced OBJECT-TYPE
	  SYNTAX EkiOnOff
	  MAX-ACCESS read-only
	  STATUS current
	  DESCRIPTION
        "
        Next Cold Boot Forced :This OID
        indicates that the next Reset will
        be forced Cold  <Help>  This alarm
        indicates that the next reset of
        the module will be forced to cold
        reset <Condtype> NEXT_COLD_BOOT_FORCED
        <Probcause> informationalStatus(1000)
        <Alarmtype> other (1) <Polarity>
        (2)
        "
	  ::= { pm253AlmmodInitFailLevel2 2 }



pm253AlmLedFail OBJECT-TYPE
	  SYNTAX EkiOnOff
	  MAX-ACCESS read-only
	  STATUS current
	  DESCRIPTION
        "
        Led Fail :This OID indicates that
        Led register has not been correctly
        initalized  <Help>  This alarm
         indicates if the module LEDs are
        correctly initialized <Condtype>
        LED_FAIL <Probcause> softwareError
        (47) <Alarmtype> processingErrorAlarm
        (4) <Polarity> (2)
        "
	  ::= { pm253AlmmodInitFailLevel2 1 }



--- *****************************************************
---     LEAF for the modInitFailLevel3 article
--- *****************************************************
pm253AlmmodInitFailLevel3 OBJECT IDENTIFIER ::= { pm253AlmOtherUrg 195 }




pm253AlmClient3InitFail OBJECT-TYPE
	  SYNTAX EkiOnOff
	  MAX-ACCESS read-only
	  STATUS current
	  DESCRIPTION
        "
        Client3 Init Fail :This OID indicates
        that Client 3 registers subset
         has not been correctly initialized
         <Help>  This alarm indicates if
        the client port 3 is correctly
         initialized <Condtype> CLIENT3_INIT_FAIL
        <Probcause> softwareError (47)
         <Alarmtype> processingErrorAlarm
        (4) <Polarity> (2)
        "
	  ::= { pm253AlmmodInitFailLevel3 11 }



pm253AlmClient2InitFail OBJECT-TYPE
	  SYNTAX EkiOnOff
	  MAX-ACCESS read-only
	  STATUS current
	  DESCRIPTION
        "
        Client2 Init Fail :This OID indicates
        that Client 2 registers subset
         has not been correctly initialized
         <Help>  This alarm indicates if
        the client port 2 is correctly
         initialized <Condtype> CLIENT2_INIT_FAIL
        <Probcause> softwareError (47)
         <Alarmtype> processingErrorAlarm
        (4) <Polarity> (2)
        "
	  ::= { pm253AlmmodInitFailLevel3 10 }



pm253AlmClient1InitFail OBJECT-TYPE
	  SYNTAX EkiOnOff
	  MAX-ACCESS read-only
	  STATUS current
	  DESCRIPTION
        "
        Client1 Init Fail :This OID indicates
        that Client 1 registers subset
         has not been correctly initialized
         <Help>  This alarm indicates if
        the client port 1 is correctly
         initialized <Condtype> CLIENT1_INIT_FAIL
        <Probcause> softwareError (47)
         <Alarmtype> processingErrorAlarm
        (4) <Polarity> (2)
        "
	  ::= { pm253AlmmodInitFailLevel3 9 }



pm253AlmLine2InitFail OBJECT-TYPE
	  SYNTAX EkiOnOff
	  MAX-ACCESS read-only
	  STATUS current
	  DESCRIPTION
        "
        Line2 Init Fail :This OID indicates
        that the Line register subset has
        not been correctly initialized
          <Help>  This alarm indicates
         if the line port 2 is correctly
        initialized <Condtype> LINE2_INIT_FAIL
        <Probcause> softwareError (47)
         <Alarmtype> processingErrorAlarm
        (4) <Polarity> (2)
        "
	  ::= { pm253AlmmodInitFailLevel3 8 }



pm253AlmLine1InitFail OBJECT-TYPE
	  SYNTAX EkiOnOff
	  MAX-ACCESS read-only
	  STATUS current
	  DESCRIPTION
        "
        Line1 Init Fail :This OID indicates
        that the Line registersvsubset
         has not been correctly initialized
         <Help>  This alarm indicates if
        the line port 1 is correctly initialized
        <Condtype> LINE1_INIT_FAIL <Probcause>
        softwareError (47) <Alarmtype>
         processingErrorAlarm (4) <Polarity>
        (2)
        "
	  ::= { pm253AlmmodInitFailLevel3 7 }



pm253AlmSfp2InitFail OBJECT-TYPE
	  SYNTAX EkiOnOff
	  MAX-ACCESS read-only
	  STATUS current
	  DESCRIPTION
        "
        SFP2 Init Fail :This OID indicates
        that the SFP has not been correctly
        initialized  <Help>  This alarm
        indicates if the line transceiver
        2 is correctly initialized <Condtype>
        SFP2_INIT_FAIL <Probcause> softwareError
        (47) <Alarmtype> processingErrorAlarm
        (4) <Polarity> (2)
        "
	  ::= { pm253AlmmodInitFailLevel3 6 }



pm253AlmSfp1InitFail OBJECT-TYPE
	  SYNTAX EkiOnOff
	  MAX-ACCESS read-only
	  STATUS current
	  DESCRIPTION
        "
        SFP1 Init Fail :This OID indicates
        that the SFP has not been correctly
        initialized  <Help>  This alarm
        indicates if the line transceiver
        1 is correctly initialized <Condtype>
        SFP1_INIT_FAIL <Probcause> softwareError
        (47) <Alarmtype> processingErrorAlarm
        (4) <Polarity> (2)
        "
	  ::= { pm253AlmmodInitFailLevel3 5 }



pm253AlmInitModuleFail OBJECT-TYPE
	  SYNTAX EkiOnOff
	  MAX-ACCESS read-only
	  STATUS current
	  DESCRIPTION
        "
        Init Module Fail :This OID indicates
        that the Module has not been correctly
        initialized  <Help>  This alarm
        indicates if the SW module is correctly
        initialized <Condtype> INIT_MODULE_FAIL
        <Probcause> softwareError (47)
         <Alarmtype> processingErrorAlarm
        (4) <Polarity> (2)
        "
	  ::= { pm253AlmmodInitFailLevel3 3 }



pm253AlmObmTypeReadFail OBJECT-TYPE
	  SYNTAX EkiOnOff
	  MAX-ACCESS read-only
	  STATUS current
	  DESCRIPTION
        "
        OBM Type Read Fail :This OID indicates
        that OBM type has not been recognized
         <Help>  This alarm indicates if
        the OBM board has been correctly
        identified <Condtype> OBM_TYPE_READ_FAIL
        <Probcause> softwareError (47)
         <Alarmtype> processingErrorAlarm
        (4) <Polarity> (2)
        "
	  ::= { pm253AlmmodInitFailLevel3 2 }



pm253AlmGwIdentFail OBJECT-TYPE
	  SYNTAX EkiOnOff
	  MAX-ACCESS read-only
	  STATUS current
	  DESCRIPTION
        "
        GW Ident Fail :This OID indicates
        that GW identification has not
         been read  <Help>  This alarm
         indicates if the GW has been correctly
        identified <Condtype> GW_IDENT_FAIL
        <Probcause> softwareError (47)
         <Alarmtype> processingErrorAlarm
        (4) <Polarity> (2)
        "
	  ::= { pm253AlmmodInitFailLevel3 1 }








--- *****************************************************
--- $$$$$$$$$$$$$$$$$$$$$$$$$$$$$$$$$$$$$$$$$$$$$$$$$$$$$
---     CONTROLS
--- $$$$$$$$$$$$$$$$$$$$$$$$$$$$$$$$$$$$$$$$$$$$$$$$$$$$$
--- *****************************************************



--- *****************************************************
---     LEAF for the confMgnt1 article
--- *****************************************************
pm253CtrlconfMgnt1 OBJECT IDENTIFIER ::= { pm253CtrlOther 1 }




pm253CtrlConf2Clear1 OBJECT-TYPE
	  SYNTAX EkiOnOff
	  MAX-ACCESS read-write
	  STATUS current
	  DESCRIPTION
        "
        Clear Configuration Tables :This
        OID clears the configuration tables
        from configuration2 in the flash.
         <Help>  This control restores
         the default configuration of the
        module
        "
	  ::= { pm253CtrlconfMgnt1 14 }



pm253CtrlConf2Flash1 OBJECT-TYPE
	  SYNTAX EkiOnOff
	  MAX-ACCESS read-write
	  STATUS current
	  DESCRIPTION
        "
        Write Configuration Tables :This
        OID saves the current configuration
        of the PM as configuration2 in
         the flash.  <Help>  This control
        saves the customer configuration
        on the module
        "
	  ::= { pm253CtrlconfMgnt1 10 }



pm253CtrlConf2Load1 OBJECT-TYPE
	  SYNTAX EkiOnOff
	  MAX-ACCESS read-write
	  STATUS current
	  DESCRIPTION
        "
        Load Configuration Tables Set
         N°2 :When set this OID enables
        loading from flash configuration2
        into the PM.
        "
	  ::= { pm253CtrlconfMgnt1 2 }



pm253CtrlConf1Load1 OBJECT-TYPE
	  SYNTAX EkiOnOff
	  MAX-ACCESS read-write
	  STATUS current
	  DESCRIPTION
        "
        Load Configuration Tables Set
         N°1 :When set this OID enables
        loading from flash configuration1
        into the PM.
        "
	  ::= { pm253CtrlconfMgnt1 1 }



--- *****************************************************
---     LEAF for the synth4 article
--- *****************************************************
pm253Ctrlsynth4 OBJECT IDENTIFIER ::= { pm253CtrlOther 4 }




pm253CtrlCorrelatOff OBJECT-TYPE
	  SYNTAX EkiOnOff
	  MAX-ACCESS read-write
	  STATUS current
	  DESCRIPTION
        "
        Disable Alarm Correlation :This
        OID disables the alarm correlation
        in the PM.
        "
	  ::= { pm253Ctrlsynth4 2 }



pm253CtrlCorrelatOn OBJECT-TYPE
	  SYNTAX EkiOnOff
	  MAX-ACCESS read-write
	  STATUS current
	  DESCRIPTION
        "
        Enable Alarm Correlation :This
        OID enables the alarm correlation
        in the PM.
        "
	  ::= { pm253Ctrlsynth4 1 }



--- *****************************************************
---     LEAF for the swMgnt article
--- *****************************************************
pm253CtrlswMgnt OBJECT IDENTIFIER ::= { pm253CtrlOther 5 }




pm253CtrlLoadSwBank2 OBJECT-TYPE
	  SYNTAX EkiOnOff
	  MAX-ACCESS read-write
	  STATUS current
	  DESCRIPTION
        "
        Set Software Nb 2 As Active :This
        OID, when set, loads the SW from
        bank2 into the PM. It must be followed
        by a reset.  <Help>  This controls
        selects the second SW bank as the
        active bank for the next module
        reset
        "
	  ::= { pm253CtrlswMgnt 6 }



pm253CtrlLoadSwBank1 OBJECT-TYPE
	  SYNTAX EkiOnOff
	  MAX-ACCESS read-write
	  STATUS current
	  DESCRIPTION
        "
        Set Software Nb 1 As Active :This
        OID, when set, loads the SW from
        bank1 into the PM. It must be followed
        by a reset.  <Help>  This controls
        selects the first SW bank as the
        active bank for the next module
        reset
        "
	  ::= { pm253CtrlswMgnt 5 }



pm253CtrlWarmReset OBJECT-TYPE
	  SYNTAX EkiOnOff
	  MAX-ACCESS read-write
	  STATUS current
	  DESCRIPTION
        "
        PM Warm Reset :This OID, when
         set, causes a warm reset of the
        PM. This reset is not traffic affecting,
        and the configuration of PM remains
        unchanged.  <Help>  This control
        initiates a warm reset of the module.
        "
	  ::= { pm253CtrlswMgnt 3 }



pm253CtrlColdReset OBJECT-TYPE
	  SYNTAX EkiOnOff
	  MAX-ACCESS read-write
	  STATUS current
	  DESCRIPTION
        "
        PM Cold Reset :This OID, when
         set, causes a cold reset of the
        PM. This reset is traffic affecting,
        and the configuration of PM is
         reloaded on start-up.  <Help>
          This control initiates a cold
        reset of the module.
        "
	  ::= { pm253CtrlswMgnt 2 }



--- *****************************************************
---     LEAF for the gwMgnt article
--- *****************************************************
pm253CtrlgwMgnt OBJECT IDENTIFIER ::= { pm253CtrlOther 6 }




pm253CtrlLoadGwBank4 OBJECT-TYPE
	  SYNTAX EkiOnOff
	  MAX-ACCESS read-write
	  STATUS current
	  DESCRIPTION
        "
        Set Gateware Nb 4 As Active :This
        OID, when set, loads the GW from
        bank4 (Flash) into the PM. It is
        followed by an automatic gateware
        cold reset.
        "
	  ::= { pm253CtrlgwMgnt 8 }



pm253CtrlLoadGwBank3 OBJECT-TYPE
	  SYNTAX EkiOnOff
	  MAX-ACCESS read-write
	  STATUS current
	  DESCRIPTION
        "
        Set Gateware Nb 3 As Active :This
        OID, when set, loads the GW from
        bank3 (Flash) into the PM. It is
        followed by an automatic gateware
        cold reset.  <Help>  This controls
        initiates a cold reset of the module
        and select the third GW bank as
        the active bank
        "
	  ::= { pm253CtrlgwMgnt 7 }



pm253CtrlLoadGwBank2 OBJECT-TYPE
	  SYNTAX EkiOnOff
	  MAX-ACCESS read-write
	  STATUS current
	  DESCRIPTION
        "
        Set Gateware Nb 2 As Active :This
        OID, when set, loads the GW from
        bank2 (Flash) into the PM. It is
        followed by an automatic gateware
        cold reset.
        "
	  ::= { pm253CtrlgwMgnt 6 }



pm253CtrlLoadGwBank1 OBJECT-TYPE
	  SYNTAX EkiOnOff
	  MAX-ACCESS read-write
	  STATUS current
	  DESCRIPTION
        "
        Set Gateware Nb 1 As Active :This
        OID, when set, loads the GW from
        bank1 (Flash) into the PM. It is
        followed by an automatic gateware
        cold reset.  <Help>  This controls
        initiates a cold reset of the module
        and select the first GW bank as
        the active bank
        "
	  ::= { pm253CtrlgwMgnt 5 }



pm253CtrlCurrentGwReset OBJECT-TYPE
	  SYNTAX EkiOnOff
	  MAX-ACCESS read-write
	  STATUS current
	  DESCRIPTION
        "
        Active Gateware Reset :This OID,
        when set, resets the active gateware.
        It is traffic affecting.
        "
	  ::= { pm253CtrlgwMgnt 1 }



--- *********************************************************
---     TABLE for the pm253CtrlclientAccessLoop articles
--- *********************************************************

pm253CtrlclientAccessLoopTable OBJECT-TYPE
	SYNTAX  SEQUENCE OF Pm253CtrlclientAccessLoopEntry
	MAX-ACCESS not-accessible
	STATUS current
	DESCRIPTION
        "
        List of pm253CtrlclientAccessLoop
        Article
        "
	::= { pm253CtrlPort 16 }


pm253CtrlclientAccessLoopEntry OBJECT-TYPE
	SYNTAX Pm253CtrlclientAccessLoopEntry
	MAX-ACCESS not-accessible
	STATUS current
	DESCRIPTION
        "
        Row definition for the pm253CtrlclientAccessLoop
        table
        "
	INDEX   { pm253CtrlclientAccessLoopIndex }
	::= { pm253CtrlclientAccessLoopTable 1 }


Pm253CtrlclientAccessLoopEntry ::=
	SEQUENCE {
	pm253CtrlclientAccessLoopIndex
		INTEGER,
	pm253CtrlclientAccessLoopPortn
		EkiState
	}


pm253CtrlclientAccessLoopIndex OBJECT-TYPE
	SYNTAX  INTEGER(0..128)
	MAX-ACCESS  read-only
	STATUS current
	DESCRIPTION
        "
        Index definition for the pm253CtrlclientAccessLoop
        table
        "
	::= { pm253CtrlclientAccessLoopEntry 1 }


pm253CtrlclientAccessLoopPortn OBJECT-TYPE
	SYNTAX  EkiState
	MAX-ACCESS read-write
	STATUS current
	DESCRIPTION
        "
        Client Facility Loopback :This
        OID operates a Client Facility
         Loopback, looping client input
        signal on the client output port.
        The loop is located on the client
        transceiver  <Help> This maintenance
        parameter operates a Client Facility
        Loopback, looping client input
         signal on the client output port.
        The loop is located on the client
        transceiver
        "
	::= { pm253CtrlclientAccessLoopEntry 2 }


--- *********************************************************
---     TABLE for the pm253CtrlclientOosMode articles
--- *********************************************************

pm253CtrlclientOosModeTable OBJECT-TYPE
	SYNTAX  SEQUENCE OF Pm253CtrlclientOosModeEntry
	MAX-ACCESS not-accessible
	STATUS current
	DESCRIPTION
        "
        List of pm253CtrlclientOosMode
        Article
        "
	::= { pm253CtrlPort 18 }


pm253CtrlclientOosModeEntry OBJECT-TYPE
	SYNTAX Pm253CtrlclientOosModeEntry
	MAX-ACCESS not-accessible
	STATUS current
	DESCRIPTION
        "
        Row definition for the pm253CtrlclientOosMode
        table
        "
	INDEX   { pm253CtrlclientOosModeIndex }
	::= { pm253CtrlclientOosModeTable 1 }


Pm253CtrlclientOosModeEntry ::=
	SEQUENCE {
	pm253CtrlclientOosModeIndex
		INTEGER,
	pm253CtrlclientOosModePortn
		EkiState
	}


pm253CtrlclientOosModeIndex OBJECT-TYPE
	SYNTAX  INTEGER(0..128)
	MAX-ACCESS  read-only
	STATUS current
	DESCRIPTION
        "
        Index definition for the pm253CtrlclientOosMode
        table
        "
	::= { pm253CtrlclientOosModeEntry 1 }


pm253CtrlclientOosModePortn OBJECT-TYPE
	SYNTAX  EkiState
	MAX-ACCESS read-write
	STATUS current
	DESCRIPTION
        "
        Client Port Out Of Service :This
        OID sets the client port Out Of
        Service  <Help>  This controls
         defines the service state of the
        client port
        "
	::= { pm253CtrlclientOosModeEntry 2 }


--- *********************************************************
---     TABLE for the pm253CtrlclientSfpOnOffCtrl articles
--- *********************************************************

pm253CtrlclientSfpOnOffCtrlTable OBJECT-TYPE
	SYNTAX  SEQUENCE OF Pm253CtrlclientSfpOnOffCtrlEntry
	MAX-ACCESS not-accessible
	STATUS current
	DESCRIPTION
        "
        List of pm253CtrlclientSfpOnOffCtrl
        Article
        "
	::= { pm253CtrlPort 20 }


pm253CtrlclientSfpOnOffCtrlEntry OBJECT-TYPE
	SYNTAX Pm253CtrlclientSfpOnOffCtrlEntry
	MAX-ACCESS not-accessible
	STATUS current
	DESCRIPTION
        "
        Row definition for the pm253CtrlclientSfpOnOffCtrl
        table
        "
	INDEX   { pm253CtrlclientSfpOnOffCtrlIndex }
	::= { pm253CtrlclientSfpOnOffCtrlTable 1 }


Pm253CtrlclientSfpOnOffCtrlEntry ::=
	SEQUENCE {
	pm253CtrlclientSfpOnOffCtrlIndex
		INTEGER,
	pm253CtrlclientSfpOnOffCtrlPortn
		EkiState
	}


pm253CtrlclientSfpOnOffCtrlIndex OBJECT-TYPE
	SYNTAX  INTEGER(0..128)
	MAX-ACCESS  read-only
	STATUS current
	DESCRIPTION
        "
        Index definition for the pm253CtrlclientSfpOnOffCtrl
        table
        "
	::= { pm253CtrlclientSfpOnOffCtrlEntry 1 }


pm253CtrlclientSfpOnOffCtrlPortn OBJECT-TYPE
	SYNTAX  EkiState
	MAX-ACCESS read-write
	STATUS current
	DESCRIPTION
        "
        Client SFP Laser Shutdown :This
        OID switches off the Client SFP.
         <Help>  This control defines the
        laser state of the client transceiver
        "
	::= { pm253CtrlclientSfpOnOffCtrlEntry 2 }


--- *********************************************************
---     TABLE for the pm253CtrlclientCsfUpIns articles
--- *********************************************************

pm253CtrlclientCsfUpInsTable OBJECT-TYPE
	SYNTAX  SEQUENCE OF Pm253CtrlclientCsfUpInsEntry
	MAX-ACCESS not-accessible
	STATUS current
	DESCRIPTION
        "
        List of pm253CtrlclientCsfUpIns
        Article
        "
	::= { pm253CtrlPort 21 }


pm253CtrlclientCsfUpInsEntry OBJECT-TYPE
	SYNTAX Pm253CtrlclientCsfUpInsEntry
	MAX-ACCESS not-accessible
	STATUS current
	DESCRIPTION
        "
        Row definition for the pm253CtrlclientCsfUpIns
        table
        "
	INDEX   { pm253CtrlclientCsfUpInsIndex }
	::= { pm253CtrlclientCsfUpInsTable 1 }


Pm253CtrlclientCsfUpInsEntry ::=
	SEQUENCE {
	pm253CtrlclientCsfUpInsIndex
		INTEGER,
	pm253CtrlclientCsfUpInsPortn
		EkiState
	}


pm253CtrlclientCsfUpInsIndex OBJECT-TYPE
	SYNTAX  INTEGER(0..128)
	MAX-ACCESS  read-only
	STATUS current
	DESCRIPTION
        "
        Index definition for the pm253CtrlclientCsfUpIns
        table
        "
	::= { pm253CtrlclientCsfUpInsEntry 1 }


pm253CtrlclientCsfUpInsPortn OBJECT-TYPE
	SYNTAX  EkiState
	MAX-ACCESS read-write
	STATUS current
	DESCRIPTION
        "
        Client Signal Fail Insertion :This
        OID, when set, inserts  a client
        signal fail in the upstream client
        Port.  <Help>  This control inserts
        a Client Signal Fail for the client
        port
        "
	::= { pm253CtrlclientCsfUpInsEntry 2 }


--- *********************************************************
---     TABLE for the pm253CtrlclientCaisDwIns articles
--- *********************************************************

pm253CtrlclientCaisDwInsTable OBJECT-TYPE
	SYNTAX  SEQUENCE OF Pm253CtrlclientCaisDwInsEntry
	MAX-ACCESS not-accessible
	STATUS current
	DESCRIPTION
        "
        List of pm253CtrlclientCaisDwIns
        Article
        "
	::= { pm253CtrlPort 22 }


pm253CtrlclientCaisDwInsEntry OBJECT-TYPE
	SYNTAX Pm253CtrlclientCaisDwInsEntry
	MAX-ACCESS not-accessible
	STATUS current
	DESCRIPTION
        "
        Row definition for the pm253CtrlclientCaisDwIns
        table
        "
	INDEX   { pm253CtrlclientCaisDwInsIndex }
	::= { pm253CtrlclientCaisDwInsTable 1 }


Pm253CtrlclientCaisDwInsEntry ::=
	SEQUENCE {
	pm253CtrlclientCaisDwInsIndex
		INTEGER,
	pm253CtrlclientCaisDwInsPortn
		EkiState
	}


pm253CtrlclientCaisDwInsIndex OBJECT-TYPE
	SYNTAX  INTEGER(0..128)
	MAX-ACCESS  read-only
	STATUS current
	DESCRIPTION
        "
        Index definition for the pm253CtrlclientCaisDwIns
        table
        "
	::= { pm253CtrlclientCaisDwInsEntry 1 }


pm253CtrlclientCaisDwInsPortn OBJECT-TYPE
	SYNTAX  EkiState
	MAX-ACCESS read-write
	STATUS current
	DESCRIPTION
        "
        Client AIS Insertion :This OID,
        when set, inserts a client AIS
         on the downstream client Port.
         <Help>  This control inserts a
        Client AIS for the client port
        "
	::= { pm253CtrlclientCaisDwInsEntry 2 }


--- *********************************************************
---     TABLE for the pm253CtrlclientAccessTermLoop articles
--- *********************************************************

pm253CtrlclientAccessTermLoopTable OBJECT-TYPE
	SYNTAX  SEQUENCE OF Pm253CtrlclientAccessTermLoopEntry
	MAX-ACCESS not-accessible
	STATUS current
	DESCRIPTION
        "
        List of pm253CtrlclientAccessTermLoop
        Article
        "
	::= { pm253CtrlPort 26 }


pm253CtrlclientAccessTermLoopEntry OBJECT-TYPE
	SYNTAX Pm253CtrlclientAccessTermLoopEntry
	MAX-ACCESS not-accessible
	STATUS current
	DESCRIPTION
        "
        Row definition for the pm253CtrlclientAccessTermLoop
        table
        "
	INDEX   { pm253CtrlclientAccessTermLoopIndex }
	::= { pm253CtrlclientAccessTermLoopTable 1 }


Pm253CtrlclientAccessTermLoopEntry ::=
	SEQUENCE {
	pm253CtrlclientAccessTermLoopIndex
		INTEGER,
	pm253CtrlclientAccessTermLoopPortn
		EkiState
	}


pm253CtrlclientAccessTermLoopIndex OBJECT-TYPE
	SYNTAX  INTEGER(0..128)
	MAX-ACCESS  read-only
	STATUS current
	DESCRIPTION
        "
        Index definition for the pm253CtrlclientAccessTermLoop
        table
        "
	::= { pm253CtrlclientAccessTermLoopEntry 1 }


pm253CtrlclientAccessTermLoopPortn OBJECT-TYPE
	SYNTAX  EkiState
	MAX-ACCESS read-write
	STATUS current
	DESCRIPTION
        "
        Client Terminal Loopback :This
        OID operates a Client Terminal
         Loopback, looping client input
        signal on the client output port.
        The loop is located on the line
        transceiver  <Help> This maintenance
        parameter operates a Client Terminal
        Loopback, looping client input
         signal on the client output port.
        The loop is located on the line
        transceiver
        "
	::= { pm253CtrlclientAccessTermLoopEntry 2 }


--- *********************************************************
---     TABLE for the pm253CtrlProtocol articles
--- *********************************************************

pm253CtrlProtocolTable OBJECT-TYPE
	SYNTAX  SEQUENCE OF Pm253CtrlProtocolEntry
	MAX-ACCESS not-accessible
	STATUS current
	DESCRIPTION
        "
        List of pm253CtrlProtocol Article
        "
	::= { pm253CtrlPort 48 }


pm253CtrlProtocolEntry OBJECT-TYPE
	SYNTAX Pm253CtrlProtocolEntry
	MAX-ACCESS not-accessible
	STATUS current
	DESCRIPTION
        "
        Row definition for the pm253CtrlProtocol
        table
        "
	INDEX   { pm253CtrlProtocolIndex }
	::= { pm253CtrlProtocolTable 1 }


Pm253CtrlProtocolEntry ::=
	SEQUENCE {
	pm253CtrlProtocolIndex
		INTEGER,
	pm253CtrlProtocolPortn
		EkiProtocol
	}


pm253CtrlProtocolIndex OBJECT-TYPE
	SYNTAX  INTEGER(0..128)
	MAX-ACCESS  read-only
	STATUS current
	DESCRIPTION
        "
        Index definition for the pm253CtrlProtocol
        table
        "
	::= { pm253CtrlProtocolEntry 1 }


pm253CtrlProtocolPortn OBJECT-TYPE
	SYNTAX  EkiProtocol
	MAX-ACCESS read-write
	STATUS current
	DESCRIPTION
        "
        Client Protocol: This OID sets
        the protocol of the Client port.
        "
	::= { pm253CtrlProtocolEntry 2 }


--- *****************************************************
---     LEAF for the sts48c24c article
--- *****************************************************
pm253Ctrlsts48c24c OBJECT IDENTIFIER ::= { pm253CtrlLine 65 }




pm253CtrlSts24cMode OBJECT-TYPE
	  SYNTAX EkiOnOff
	  MAX-ACCESS read-write
	  STATUS current
	  DESCRIPTION
        "
        STS24c (check) - STS48c (uncheck)
        :This OID defines the STM16/OC48
        lines format. 1xSTS48c (0) or 2xSTS24c
        (1).  <Help>  This control defines
        the payload mapping of the line
        (2xSTS-24c or 1xSTS48c).
        "
	  ::= { pm253Ctrlsts48c24c 1 }



--- *****************************************************
---     LEAF for the lineMsAis article
--- *****************************************************
pm253CtrllineMsAis OBJECT IDENTIFIER ::= { pm253CtrlLine 67 }




pm253CtrlLineMsAis OBJECT-TYPE
	  SYNTAX EkiOnOff
	  MAX-ACCESS read-write
	  STATUS current
	  DESCRIPTION
        "
        Insert MS-AIS/L-AIS On Lines Output
        :This OID, when set, inserts an
        MS-AIS/L-AIS in the two outgoing
        STM-16/OC-48 signals.
        "
	  ::= { pm253CtrllineMsAis 1 }



--- *********************************************************
---     TABLE for the pm253CtrllineUpS1 articles
--- *********************************************************

pm253CtrllineUpS1Table OBJECT-TYPE
	SYNTAX  SEQUENCE OF Pm253CtrllineUpS1Entry
	MAX-ACCESS not-accessible
	STATUS current
	DESCRIPTION
        "
        List of pm253CtrllineUpS1 Article
        "
	::= { pm253CtrlLine 70 }


pm253CtrllineUpS1Entry OBJECT-TYPE
	SYNTAX Pm253CtrllineUpS1Entry
	MAX-ACCESS not-accessible
	STATUS current
	DESCRIPTION
        "
        Row definition for the pm253CtrllineUpS1
        table
        "
	INDEX   { pm253CtrllineUpS1Index }
	::= { pm253CtrllineUpS1Table 1 }


Pm253CtrllineUpS1Entry ::=
	SEQUENCE {
	pm253CtrllineUpS1Index
		INTEGER,
	pm253CtrllineUpS1Portn
		INTEGER
	}


pm253CtrllineUpS1Index OBJECT-TYPE
	SYNTAX  INTEGER(0..128)
	MAX-ACCESS  read-only
	STATUS current
	DESCRIPTION
        "
        Index definition for the pm253CtrllineUpS1
        table
        "
	::= { pm253CtrllineUpS1Entry 1 }


pm253CtrllineUpS1Portn OBJECT-TYPE
	SYNTAX  INTEGER (0..1)
	MAX-ACCESS read-write
	STATUS current
	DESCRIPTION
        "
        S1 Value Inserted On Lines Output
        :The value to be written in the
        S1 byte of the two upstream OC-48c/STM-16c
        signals is accessible through the
        present OID
        "
	::= { pm253CtrllineUpS1Entry 2 }


--- *********************************************************
---     TABLE for the pm253CtrllineUpK1 articles
--- *********************************************************

pm253CtrllineUpK1Table OBJECT-TYPE
	SYNTAX  SEQUENCE OF Pm253CtrllineUpK1Entry
	MAX-ACCESS not-accessible
	STATUS current
	DESCRIPTION
        "
        List of pm253CtrllineUpK1 Article
        "
	::= { pm253CtrlLine 71 }


pm253CtrllineUpK1Entry OBJECT-TYPE
	SYNTAX Pm253CtrllineUpK1Entry
	MAX-ACCESS not-accessible
	STATUS current
	DESCRIPTION
        "
        Row definition for the pm253CtrllineUpK1
        table
        "
	INDEX   { pm253CtrllineUpK1Index }
	::= { pm253CtrllineUpK1Table 1 }


Pm253CtrllineUpK1Entry ::=
	SEQUENCE {
	pm253CtrllineUpK1Index
		INTEGER,
	pm253CtrllineUpK1Portn
		INTEGER
	}


pm253CtrllineUpK1Index OBJECT-TYPE
	SYNTAX  INTEGER(0..128)
	MAX-ACCESS  read-only
	STATUS current
	DESCRIPTION
        "
        Index definition for the pm253CtrllineUpK1
        table
        "
	::= { pm253CtrllineUpK1Entry 1 }


pm253CtrllineUpK1Portn OBJECT-TYPE
	SYNTAX  INTEGER (0..1)
	MAX-ACCESS read-write
	STATUS current
	DESCRIPTION
        "
        K1 Value Inserted On Lines Output
        :The value to be written in the
        K1 byte of the two upstream OC-48c/STM-16c
        signals is accessible through the
        present OID
        "
	::= { pm253CtrllineUpK1Entry 2 }


--- *********************************************************
---     TABLE for the pm253CtrllineUpK2 articles
--- *********************************************************

pm253CtrllineUpK2Table OBJECT-TYPE
	SYNTAX  SEQUENCE OF Pm253CtrllineUpK2Entry
	MAX-ACCESS not-accessible
	STATUS current
	DESCRIPTION
        "
        List of pm253CtrllineUpK2 Article
        "
	::= { pm253CtrlLine 72 }


pm253CtrllineUpK2Entry OBJECT-TYPE
	SYNTAX Pm253CtrllineUpK2Entry
	MAX-ACCESS not-accessible
	STATUS current
	DESCRIPTION
        "
        Row definition for the pm253CtrllineUpK2
        table
        "
	INDEX   { pm253CtrllineUpK2Index }
	::= { pm253CtrllineUpK2Table 1 }


Pm253CtrllineUpK2Entry ::=
	SEQUENCE {
	pm253CtrllineUpK2Index
		INTEGER,
	pm253CtrllineUpK2Portn
		INTEGER
	}


pm253CtrllineUpK2Index OBJECT-TYPE
	SYNTAX  INTEGER(0..128)
	MAX-ACCESS  read-only
	STATUS current
	DESCRIPTION
        "
        Index definition for the pm253CtrllineUpK2
        table
        "
	::= { pm253CtrllineUpK2Entry 1 }


pm253CtrllineUpK2Portn OBJECT-TYPE
	SYNTAX  INTEGER (0..1)
	MAX-ACCESS read-write
	STATUS current
	DESCRIPTION
        "
        K2 Value Inserted On Lines Output
        :The value to be written in the
        K2 byte of the two upstream OC-48c/STM-16c
        signals is accessible through the
        present OID
        "
	::= { pm253CtrllineUpK2Entry 2 }


--- *****************************************************
---     LEAF for the protMgnt article
--- *****************************************************
pm253CtrlProtMgnt OBJECT IDENTIFIER ::= { pm253CtrlLine 73 }




pm253CtrlLineNumber OBJECT-TYPE
	  SYNTAX Unsigned32 (0..3)
	  MAX-ACCESS read-write
	  STATUS current
	  DESCRIPTION
        "
        Switch to Line Port : This OID
        sets the active line number
        "
	  ::= { pm253CtrlProtMgnt 1 }



pm253CtrlProtMode OBJECT-TYPE
	  SYNTAX EkiMode
	  MAX-ACCESS read-write
	  STATUS current
	  DESCRIPTION
        "
        Line Switch Mode (Auto Or Manual)
        :This OID selects the manual (1)
        or automatic (0) switch method
        "
	  ::= { pm253CtrlProtMgnt 2 }



--- *********************************************************
---     TABLE for the pm253CtrllineOosMode articles
--- *********************************************************

pm253CtrllineOosModeTable OBJECT-TYPE
	SYNTAX  SEQUENCE OF Pm253CtrllineOosModeEntry
	MAX-ACCESS not-accessible
	STATUS current
	DESCRIPTION
        "
        List of pm253CtrllineOosMode Article
        "
	::= { pm253CtrlLine 74 }


pm253CtrllineOosModeEntry OBJECT-TYPE
	SYNTAX Pm253CtrllineOosModeEntry
	MAX-ACCESS not-accessible
	STATUS current
	DESCRIPTION
        "
        Row definition for the pm253CtrllineOosMode
        table
        "
	INDEX   { pm253CtrllineOosModeIndex }
	::= { pm253CtrllineOosModeTable 1 }


Pm253CtrllineOosModeEntry ::=
	SEQUENCE {
	pm253CtrllineOosModeIndex
		INTEGER,
	pm253CtrllineOosModePortn
		EkiState
	}


pm253CtrllineOosModeIndex OBJECT-TYPE
	SYNTAX  INTEGER(0..128)
	MAX-ACCESS  read-only
	STATUS current
	DESCRIPTION
        "
        Index definition for the pm253CtrllineOosMode
        table
        "
	::= { pm253CtrllineOosModeEntry 1 }


pm253CtrllineOosModePortn OBJECT-TYPE
	SYNTAX  EkiState
	MAX-ACCESS read-write
	STATUS current
	DESCRIPTION
        "
        Line Port Out Of Service :This
        OID sets the line port Out Of Service
         <Help>  This control defines the
        service state of the line port
        "
	::= { pm253CtrllineOosModeEntry 2 }


--- *****************************************************
---     LEAF for the k1K2Mgnt article
--- *****************************************************
pm253Ctrlk1K2Mgnt OBJECT IDENTIFIER ::= { pm253CtrlLine 75 }




pm253CtrlK1K2Transparent OBJECT-TYPE
	  SYNTAX EkiOnOff
	  MAX-ACCESS read-write
	  STATUS current
	  DESCRIPTION
        "
        Transparent Client Mode (OC48
         Mode) :This OID enables the transparent
        transport of the OC48 client port.
        When not sets, the value of S1,
        K1 and K2 bytes are adapted. This
        OID is active when the automatic
        protection switch is disabled
         <Help>  This control is valid
         only in OC48 regenerator mode
         and disables the modification
         of K1, K2 and S1 bytes in the
         OC48 frame (for protection and
        synchro purpose)
        "
	  ::= { pm253Ctrlk1K2Mgnt 1 }



--- *****************************************************
---     LEAF for the apsForceMode article
--- *****************************************************
pm253CtrlApsForceMode OBJECT IDENTIFIER ::= { pm253CtrlLine 90 }




pm253CtrlApsForceModeLine1 OBJECT-TYPE
	  SYNTAX EkiOnOff
	  MAX-ACCESS read-write
	  STATUS current
	  DESCRIPTION
        "
        Force Switch To Line 1 (protect)
        :This OID performs a forced switch
        to the line 1 (protect line)
        "
	  ::= { pm253CtrlApsForceMode 1 }



pm253CtrlApsForceModeLine2 OBJECT-TYPE
	  SYNTAX EkiOnOff
	  MAX-ACCESS read-write
	  STATUS current
	  DESCRIPTION
        "
        Force Switch To Line 2 (working)
        :This OID performs a forced switch
        to the line 2 (working line)
        "
	  ::= { pm253CtrlApsForceMode 2 }



--- *****************************************************
---     LEAF for the apsManualMode article
--- *****************************************************
pm253CtrlApsManualMode OBJECT IDENTIFIER ::= { pm253CtrlLine 91 }




pm253CtrlApsManualModeLine1 OBJECT-TYPE
	  SYNTAX EkiOnOff
	  MAX-ACCESS read-write
	  STATUS current
	  DESCRIPTION
        "
        Manual Switch To Line 1 (protect)
        :This OID performs a manual switch
        to the line 1 (protect line)
        "
	  ::= { pm253CtrlApsManualMode 1 }



pm253CtrlApsManualModeLine2 OBJECT-TYPE
	  SYNTAX EkiOnOff
	  MAX-ACCESS read-write
	  STATUS current
	  DESCRIPTION
        "
        Manual Switch To Line 2 (working)
        :This OID performs a manual switch
        to the line 2 (working line)
        "
	  ::= { pm253CtrlApsManualMode 2 }



--- *****************************************************
---     LEAF for the apsOtherModes article
--- *****************************************************
pm253CtrlapsOtherModes OBJECT IDENTIFIER ::= { pm253CtrlLine 92 }




pm253CtrlClear OBJECT-TYPE
	  SYNTAX EkiOnOff
	  MAX-ACCESS read-write
	  STATUS current
	  DESCRIPTION
        "
        APS Clear :This OID clears any
        APS command previously set  <Help>
         This control sets the APS mode
        to Clear.
        "
	  ::= { pm253CtrlapsOtherModes 2 }



pm253CtrlLockout OBJECT-TYPE
	  SYNTAX EkiOnOff
	  MAX-ACCESS read-write
	  STATUS current
	  DESCRIPTION
        "
        Lockout From Protection :This
         OID sets the APS in 'Lockout from
        protection' mode  <Help>  This
         control sets the APS mode to Lockout
        from Protection
        "
	  ::= { pm253CtrlapsOtherModes 1 }



--- *********************************************************
---     TABLE for the pm253CtrllineAccessLoop articles
--- *********************************************************

pm253CtrllineAccessLoopTable OBJECT-TYPE
	SYNTAX  SEQUENCE OF Pm253CtrllineAccessLoopEntry
	MAX-ACCESS not-accessible
	STATUS current
	DESCRIPTION
        "
        List of pm253CtrllineAccessLoop
        Article
        "
	::= { pm253CtrlLine 160 }


pm253CtrllineAccessLoopEntry OBJECT-TYPE
	SYNTAX Pm253CtrllineAccessLoopEntry
	MAX-ACCESS not-accessible
	STATUS current
	DESCRIPTION
        "
        Row definition for the pm253CtrllineAccessLoop
        table
        "
	INDEX   { pm253CtrllineAccessLoopIndex }
	::= { pm253CtrllineAccessLoopTable 1 }


Pm253CtrllineAccessLoopEntry ::=
	SEQUENCE {
	pm253CtrllineAccessLoopIndex
		INTEGER,
	pm253CtrllineAccessLoopPortn
		EkiState
	}


pm253CtrllineAccessLoopIndex OBJECT-TYPE
	SYNTAX  INTEGER(0..128)
	MAX-ACCESS  read-only
	STATUS current
	DESCRIPTION
        "
        Index definition for the pm253CtrllineAccessLoop
        table
        "
	::= { pm253CtrllineAccessLoopEntry 1 }


pm253CtrllineAccessLoopPortn OBJECT-TYPE
	SYNTAX  EkiState
	MAX-ACCESS read-write
	STATUS current
	DESCRIPTION
        "
        Line Facility Loopback :This OID
        operates a Line Facility Loopback,
        looping line input signal on the
        line output port. The loop is located
        on the line transceiver. If the
        Line signal carries DCC, the management
        network is impacted  <Help> This
        maintenance parameter operates
         a Line Facility Loopback, looping
        line input signal on the line output
        port. The loop is located on the
        line transceiver. If the Line signal
        carries DCC, the management network
        is impacted
        "
	::= { pm253CtrllineAccessLoopEntry 2 }


--- *********************************************************
---     TABLE for the pm253CtrllineLoopTransceiver articles
--- *********************************************************

pm253CtrllineLoopTransceiverTable OBJECT-TYPE
	SYNTAX  SEQUENCE OF Pm253CtrllineLoopTransceiverEntry
	MAX-ACCESS not-accessible
	STATUS current
	DESCRIPTION
        "
        List of pm253CtrllineLoopTransceiver
        Article
        "
	::= { pm253CtrlLine 161 }


pm253CtrllineLoopTransceiverEntry OBJECT-TYPE
	SYNTAX Pm253CtrllineLoopTransceiverEntry
	MAX-ACCESS not-accessible
	STATUS current
	DESCRIPTION
        "
        Row definition for the pm253CtrllineLoopTransceiver
        table
        "
	INDEX   { pm253CtrllineLoopTransceiverIndex }
	::= { pm253CtrllineLoopTransceiverTable 1 }


Pm253CtrllineLoopTransceiverEntry ::=
	SEQUENCE {
	pm253CtrllineLoopTransceiverIndex
		INTEGER,
	pm253CtrllineLoopTransceiverPortn
		EkiState
	}


pm253CtrllineLoopTransceiverIndex OBJECT-TYPE
	SYNTAX  INTEGER(0..128)
	MAX-ACCESS  read-only
	STATUS current
	DESCRIPTION
        "
        Index definition for the pm253CtrllineLoopTransceiver
        table
        "
	::= { pm253CtrllineLoopTransceiverEntry 1 }


pm253CtrllineLoopTransceiverPortn OBJECT-TYPE
	SYNTAX  EkiState
	MAX-ACCESS read-write
	STATUS current
	DESCRIPTION
        "
        Line Terminal Loopback :This OID
        operates a Line Terminal Loopback,
        looping line input signal on the
        line output port. The loop is located
        on all client transceivers  <Help>
        This maintenance parameter operates
        a Line Terminal Loopback, looping
        line input signal on the line output
        port. The loop is located on all
        client transceivers.
        "
	::= { pm253CtrllineLoopTransceiverEntry 2 }


--- *********************************************************
---     TABLE for the pm253CtrllineSfpOnOffCtrl articles
--- *********************************************************

pm253CtrllineSfpOnOffCtrlTable OBJECT-TYPE
	SYNTAX  SEQUENCE OF Pm253CtrllineSfpOnOffCtrlEntry
	MAX-ACCESS not-accessible
	STATUS current
	DESCRIPTION
        "
        List of pm253CtrllineSfpOnOffCtrl
        Article
        "
	::= { pm253CtrlLine 162 }


pm253CtrllineSfpOnOffCtrlEntry OBJECT-TYPE
	SYNTAX Pm253CtrllineSfpOnOffCtrlEntry
	MAX-ACCESS not-accessible
	STATUS current
	DESCRIPTION
        "
        Row definition for the pm253CtrllineSfpOnOffCtrl
        table
        "
	INDEX   { pm253CtrllineSfpOnOffCtrlIndex }
	::= { pm253CtrllineSfpOnOffCtrlTable 1 }


Pm253CtrllineSfpOnOffCtrlEntry ::=
	SEQUENCE {
	pm253CtrllineSfpOnOffCtrlIndex
		INTEGER,
	pm253CtrllineSfpOnOffCtrlPortn
		EkiState
	}


pm253CtrllineSfpOnOffCtrlIndex OBJECT-TYPE
	SYNTAX  INTEGER(0..128)
	MAX-ACCESS  read-only
	STATUS current
	DESCRIPTION
        "
        Index definition for the pm253CtrllineSfpOnOffCtrl
        table
        "
	::= { pm253CtrllineSfpOnOffCtrlEntry 1 }


pm253CtrllineSfpOnOffCtrlPortn OBJECT-TYPE
	SYNTAX  EkiState
	MAX-ACCESS read-write
	STATUS current
	DESCRIPTION
        "
        Line SFP Laser Shutdown :This
         OID switches off the Line SFP.
         <Help>  This control defines the
        laser state of the line transceiver
        "
	::= { pm253CtrllineSfpOnOffCtrlEntry 2 }


--- *****************************************************
---     LEAF for the ledTest article
--- *****************************************************
pm253CtrlledTest OBJECT IDENTIFIER ::= { pm253CtrlOther 192 }




pm253CtrlLedOff OBJECT-TYPE
	  SYNTAX EkiOnOff
	  MAX-ACCESS read-write
	  STATUS current
	  DESCRIPTION
        "
        Leds Off :This OID switches off
        all the Leds as a test feature.
         <Help>  This control initiates
        a test leds turning all the LEDs
        to OFF
        "
	  ::= { pm253CtrlledTest 3 }



pm253CtrlRedLed OBJECT-TYPE
	  SYNTAX EkiOnOff
	  MAX-ACCESS read-write
	  STATUS current
	  DESCRIPTION
        "
        Red Leds Test :This OID switches
        on all the red Leds as a test feature.
         <Help>  This control initiates
        a test leds turning all the LEDs
        to red
        "
	  ::= { pm253CtrlledTest 2 }



pm253CtrlGreenLed OBJECT-TYPE
	  SYNTAX EkiOnOff
	  MAX-ACCESS read-write
	  STATUS current
	  DESCRIPTION
        "
        Green Leds Test :This OID switches
        on all the green Leds as a test
        feature.  <Help>  This control
         initiates a test leds turning
         all the LEDs to green
        "
	  ::= { pm253CtrlledTest 1 }



--- *****************************************************
---     LEAF for the moduleOosMode article
--- *****************************************************
pm253CtrlmoduleOosMode OBJECT IDENTIFIER ::= { pm253CtrlOther 193 }




pm253CtrlModuleOosMode OBJECT-TYPE
	  SYNTAX EkiOnOff
	  MAX-ACCESS read-write
	  STATUS current
	  DESCRIPTION
        "
        PM Out Of Service :This OID sets
        the PM253 Out Of Service  <Help>
         This control defines the service
        state of the complete module
        "
	  ::= { pm253CtrlmoduleOosMode 1 }



--- *****************************************************
---     LEAF for the clientPortMode article
--- *****************************************************
pm253CtrlclientPortMode OBJECT IDENTIFIER ::= { pm253CtrlOther 194 }




pm253CtrlClientPortMode OBJECT-TYPE
	  SYNTAX EkiOnOff
	  MAX-ACCESS read-write
	  STATUS current
	  DESCRIPTION
        "
        OC48 (check) - GbE (uncheck) Mode
        :This OID sets the client port
         in 2xGbE/GFC mode (1) or 1xOC748/STM16
        mode (2)  <Help>  This control
         defines the working mode of the
        PM253 (OC48 regenerator or 2xGbE
        aggregator)
        "
	  ::= { pm253CtrlclientPortMode 1 }



--- *****************************************************
---     LEAF for the maintenanceMode article
--- *****************************************************
pm253CtrlmaintenanceMode OBJECT IDENTIFIER ::= { pm253CtrlOther 197 }




pm253CtrlMaintenanceMode OBJECT-TYPE
	  SYNTAX EkiOnOff
	  MAX-ACCESS read-write
	  STATUS current
	  DESCRIPTION
        "
        Module Maintenance Mode :This
         OID enables the maintenance mode
        on the PM.  <Help>   This control
        enables the maintenance mode on
        the PM.
        "
	  ::= { pm253CtrlmaintenanceMode 1 }



--- *****************************************************
---     LEAF for the dccEnable article
--- *****************************************************
pm253CtrldccEnable OBJECT IDENTIFIER ::= { pm253CtrlOther 198 }




pm253CtrlDccEnable OBJECT-TYPE
	  SYNTAX EkiOnOff
	  MAX-ACCESS read-write
	  STATUS current
	  DESCRIPTION
        "
        DCC Enable :This OID enables the
        DCC mode on the PM   <Help>   This
        control enables the DCC mode on
        the PM
        "
	  ::= { pm253CtrldccEnable 1 }



--- *********************************************************
---     TABLE for the pm253CtrlclientResetAllCount articles
--- *********************************************************

pm253CtrlclientResetAllCountTable OBJECT-TYPE
	SYNTAX  SEQUENCE OF Pm253CtrlclientResetAllCountEntry
	MAX-ACCESS not-accessible
	STATUS current
	DESCRIPTION
        "
        List of pm253CtrlclientResetAllCount
        Article
        "
	::= { pm253CtrlPort 271 }


pm253CtrlclientResetAllCountEntry OBJECT-TYPE
	SYNTAX Pm253CtrlclientResetAllCountEntry
	MAX-ACCESS not-accessible
	STATUS current
	DESCRIPTION
        "
        Row definition for the pm253CtrlclientResetAllCount
        table
        "
	INDEX   { pm253CtrlclientResetAllCountIndex }
	::= { pm253CtrlclientResetAllCountTable 1 }


Pm253CtrlclientResetAllCountEntry ::=
	SEQUENCE {
	pm253CtrlclientResetAllCountIndex
		INTEGER,
	pm253CtrlclientResetAllCountsPortn
		EkiState
	}


pm253CtrlclientResetAllCountIndex OBJECT-TYPE
	SYNTAX  INTEGER(0..128)
	MAX-ACCESS  read-only
	STATUS current
	DESCRIPTION
        "
        Index definition for the pm253CtrlclientResetAllCount
        table
        "
	::= { pm253CtrlclientResetAllCountEntry 1 }


pm253CtrlclientResetAllCountsPortn OBJECT-TYPE
	SYNTAX  EkiState
	MAX-ACCESS read-write
	STATUS deprecated
	DESCRIPTION
        "
        Client Counters Reset :This OID
        resets every counter on the client
        port  <Help>   This control operates
        a reset on the statistics current
        ,previous and history client port
        counters
        "
	::= { pm253CtrlclientResetAllCountEntry 2 }


--- *********************************************************
---     TABLE for the pm253CtrllineResetAllCount articles
--- *********************************************************

pm253CtrllineResetAllCountTable OBJECT-TYPE
	SYNTAX  SEQUENCE OF Pm253CtrllineResetAllCountEntry
	MAX-ACCESS not-accessible
	STATUS current
	DESCRIPTION
        "
        List of pm253CtrllineResetAllCount
        Article
        "
	::= { pm253CtrlLine 335 }


pm253CtrllineResetAllCountEntry OBJECT-TYPE
	SYNTAX Pm253CtrllineResetAllCountEntry
	MAX-ACCESS not-accessible
	STATUS current
	DESCRIPTION
        "
        Row definition for the pm253CtrllineResetAllCount
        table
        "
	INDEX   { pm253CtrllineResetAllCountIndex }
	::= { pm253CtrllineResetAllCountTable 1 }


Pm253CtrllineResetAllCountEntry ::=
	SEQUENCE {
	pm253CtrllineResetAllCountIndex
		INTEGER,
	pm253CtrllineResetAllCountsPortn
		EkiState
	}


pm253CtrllineResetAllCountIndex OBJECT-TYPE
	SYNTAX  INTEGER(0..128)
	MAX-ACCESS  read-only
	STATUS current
	DESCRIPTION
        "
        Index definition for the pm253CtrllineResetAllCount
        table
        "
	::= { pm253CtrllineResetAllCountEntry 1 }


pm253CtrllineResetAllCountsPortn OBJECT-TYPE
	SYNTAX  EkiState
	MAX-ACCESS read-write
	STATUS deprecated
	DESCRIPTION
        "
        Line Counters Reset :This OID
         resets every counter on the line
        port  <Help>   This control operates
        a reset on the statistics current
        ,previous and history line port
        counters
        "
	::= { pm253CtrllineResetAllCountEntry 2 }







--- *****************************************************
--- $$$$$$$$$$$$$$$$$$$$$$$$$$$$$$$$$$$$$$$$$$$$$$$$$$$$$
---     COUNTERS
--- $$$$$$$$$$$$$$$$$$$$$$$$$$$$$$$$$$$$$$$$$$$$$$$$$$$$$
--- *****************************************************



--- *********************************************************
---     TABLE for the pm253CntclientUpRaRemCnt articles
--- *********************************************************

pm253CntclientUpRaRemCntTable OBJECT-TYPE
	SYNTAX  SEQUENCE OF Pm253CntclientUpRaRemCntEntry
	MAX-ACCESS not-accessible
	STATUS current
	DESCRIPTION
        "
        List of pm253CntclientUpRaRemCnt
        Article
        "
	::= { pm253CntPort 16 }


pm253CntclientUpRaRemCntEntry OBJECT-TYPE
	SYNTAX Pm253CntclientUpRaRemCntEntry
	MAX-ACCESS not-accessible
	STATUS current
	DESCRIPTION
        "
        Row definition for the pm253CntclientUpRaRemCnt
        table
        "
	INDEX   { pm253CntclientUpRaRemCntIndex }
	::= { pm253CntclientUpRaRemCntTable 1 }


Pm253CntclientUpRaRemCntEntry ::=
	SEQUENCE {
	pm253CntclientUpRaRemCntIndex
		INTEGER,
	pm253CntclientUpRaRemCntValuePortn
		Counter32,
	pm253CntclientUpRaRemCntErrorPortn
		EkiOnOff,
	pm253CntclientUpRaRemCntOverloadPortn
		EkiOnOff
	}


pm253CntclientUpRaRemCntIndex OBJECT-TYPE
	SYNTAX  INTEGER(0..128)
	MAX-ACCESS  read-only
	STATUS current
	DESCRIPTION
        "
        Index definition for the pm253CntclientUpRaRemCnt
        table
        "
	::= { pm253CntclientUpRaRemCntEntry 1 }


pm253CntclientUpRaRemCntValuePortn OBJECT-TYPE
	SYNTAX  Counter32
	MAX-ACCESS read-only
	STATUS current
	DESCRIPTION
        "
        Client Rate Adapt. Words Removal
        :This counter is incremented each
        time a rate adaptation 10B word
        is removed from the Client input
        stream
        "
	::= { pm253CntclientUpRaRemCntEntry 2 }


pm253CntclientUpRaRemCntErrorPortn OBJECT-TYPE
	SYNTAX  EkiOnOff
	MAX-ACCESS read-only
	STATUS current
	DESCRIPTION
        "
        Client Counter Error :This OID
        when set indicates the rate adaptation
        removal counter value is invalid
        on Port
        "
	::= { pm253CntclientUpRaRemCntEntry 3 }


pm253CntclientUpRaRemCntOverloadPortn OBJECT-TYPE
	SYNTAX  EkiOnOff
	MAX-ACCESS read-only
	STATUS current
	DESCRIPTION
        "
        Client Counter Overload :This
         OID when set indicates a rate
         adaptation removal counter overload
        on Port
        "
	::= { pm253CntclientUpRaRemCntEntry 4 }


--- *********************************************************
---     TABLE for the pm253CntclientUpRaInsCnt articles
--- *********************************************************

pm253CntclientUpRaInsCntTable OBJECT-TYPE
	SYNTAX  SEQUENCE OF Pm253CntclientUpRaInsCntEntry
	MAX-ACCESS not-accessible
	STATUS current
	DESCRIPTION
        "
        List of pm253CntclientUpRaInsCnt
        Article
        "
	::= { pm253CntPort 24 }


pm253CntclientUpRaInsCntEntry OBJECT-TYPE
	SYNTAX Pm253CntclientUpRaInsCntEntry
	MAX-ACCESS not-accessible
	STATUS current
	DESCRIPTION
        "
        Row definition for the pm253CntclientUpRaInsCnt
        table
        "
	INDEX   { pm253CntclientUpRaInsCntIndex }
	::= { pm253CntclientUpRaInsCntTable 1 }


Pm253CntclientUpRaInsCntEntry ::=
	SEQUENCE {
	pm253CntclientUpRaInsCntIndex
		INTEGER,
	pm253CntclientUpRaInsCntValuePortn
		Counter32,
	pm253CntclientUpRaInsCntErrorPortn
		EkiOnOff,
	pm253CntclientUpRaInsCntOverloadPortn
		EkiOnOff
	}


pm253CntclientUpRaInsCntIndex OBJECT-TYPE
	SYNTAX  INTEGER(0..128)
	MAX-ACCESS  read-only
	STATUS current
	DESCRIPTION
        "
        Index definition for the pm253CntclientUpRaInsCnt
        table
        "
	::= { pm253CntclientUpRaInsCntEntry 1 }


pm253CntclientUpRaInsCntValuePortn OBJECT-TYPE
	SYNTAX  Counter32
	MAX-ACCESS read-only
	STATUS current
	DESCRIPTION
        "
        Client Rate Adapt. Words Insertion
        :This counter is incremented each
        time a rate adaptation 10B word
        is inserted in the Client input
        stream
        "
	::= { pm253CntclientUpRaInsCntEntry 2 }


pm253CntclientUpRaInsCntErrorPortn OBJECT-TYPE
	SYNTAX  EkiOnOff
	MAX-ACCESS read-only
	STATUS current
	DESCRIPTION
        "
        Client Counter Error :This OID
        when set indicates the rate adaptation
        insertion counter value is invalid
        on Port
        "
	::= { pm253CntclientUpRaInsCntEntry 3 }


pm253CntclientUpRaInsCntOverloadPortn OBJECT-TYPE
	SYNTAX  EkiOnOff
	MAX-ACCESS read-only
	STATUS current
	DESCRIPTION
        "
        Client Counter Overload :This
         OID when set indicates a rate
         adaptation insertion counter overload
        on Port
        "
	::= { pm253CntclientUpRaInsCntEntry 4 }


--- *********************************************************
---     TABLE for the pm253CntclientUpDispErrCnt articles
--- *********************************************************

pm253CntclientUpDispErrCntTable OBJECT-TYPE
	SYNTAX  SEQUENCE OF Pm253CntclientUpDispErrCntEntry
	MAX-ACCESS not-accessible
	STATUS current
	DESCRIPTION
        "
        List of pm253CntclientUpDispErrCnt
        Article
        "
	::= { pm253CntPort 32 }


pm253CntclientUpDispErrCntEntry OBJECT-TYPE
	SYNTAX Pm253CntclientUpDispErrCntEntry
	MAX-ACCESS not-accessible
	STATUS current
	DESCRIPTION
        "
        Row definition for the pm253CntclientUpDispErrCnt
        table
        "
	INDEX   { pm253CntclientUpDispErrCntIndex }
	::= { pm253CntclientUpDispErrCntTable 1 }


Pm253CntclientUpDispErrCntEntry ::=
	SEQUENCE {
	pm253CntclientUpDispErrCntIndex
		INTEGER,
	pm253CntclientUpDispErrCntValuePortn
		Counter32,
	pm253CntclientUpDispErrCntErrorPortn
		EkiOnOff,
	pm253CntclientUpDispErrCntOverloadPortn
		EkiOnOff
	}


pm253CntclientUpDispErrCntIndex OBJECT-TYPE
	SYNTAX  INTEGER(0..128)
	MAX-ACCESS  read-only
	STATUS current
	DESCRIPTION
        "
        Index definition for the pm253CntclientUpDispErrCnt
        table
        "
	::= { pm253CntclientUpDispErrCntEntry 1 }


pm253CntclientUpDispErrCntValuePortn OBJECT-TYPE
	SYNTAX  Counter32
	MAX-ACCESS read-only
	STATUS current
	DESCRIPTION
        "
        Client Input Errors :This counter
        is incremented each time a running
        disparity error or a 10b/8b decoding
        violation is detected on the Client
        input stream  <Help>  This counter
        gives the number of 10b/8b running
        disparity errors on the client
         port
        "
	::= { pm253CntclientUpDispErrCntEntry 2 }


pm253CntclientUpDispErrCntErrorPortn OBJECT-TYPE
	SYNTAX  EkiOnOff
	MAX-ACCESS read-only
	STATUS current
	DESCRIPTION
        "
        Client Counter Error :This OID
        when set indicates the 10B/8B decoding
        violations counter value is invalid
        on Port
        "
	::= { pm253CntclientUpDispErrCntEntry 3 }


pm253CntclientUpDispErrCntOverloadPortn OBJECT-TYPE
	SYNTAX  EkiOnOff
	MAX-ACCESS read-only
	STATUS current
	DESCRIPTION
        "
        Client Counter Overload :This
         OID when set indicates a 10B/8B
        decoding violations counter overload
        on Port
        "
	::= { pm253CntclientUpDispErrCntEntry 4 }


--- *********************************************************
---     TABLE for the pm253CntclientUpTimCnt articles
--- *********************************************************

pm253CntclientUpTimCntTable OBJECT-TYPE
	SYNTAX  SEQUENCE OF Pm253CntclientUpTimCntEntry
	MAX-ACCESS not-accessible
	STATUS current
	DESCRIPTION
        "
        List of pm253CntclientUpTimCnt
        Article
        "
	::= { pm253CntPort 40 }


pm253CntclientUpTimCntEntry OBJECT-TYPE
	SYNTAX Pm253CntclientUpTimCntEntry
	MAX-ACCESS not-accessible
	STATUS current
	DESCRIPTION
        "
        Row definition for the pm253CntclientUpTimCnt
        table
        "
	INDEX   { pm253CntclientUpTimCntIndex }
	::= { pm253CntclientUpTimCntTable 1 }


Pm253CntclientUpTimCntEntry ::=
	SEQUENCE {
	pm253CntclientUpTimCntIndex
		INTEGER,
	pm253CntclientUpTimCntValuePortn
		Counter32,
	pm253CntclientUpTimCntErrorPortn
		EkiOnOff,
	pm253CntclientUpTimCntOverloadPortn
		EkiOnOff
	}


pm253CntclientUpTimCntIndex OBJECT-TYPE
	SYNTAX  INTEGER(0..128)
	MAX-ACCESS  read-only
	STATUS current
	DESCRIPTION
        "
        Index definition for the pm253CntclientUpTimCnt
        table
        "
	::= { pm253CntclientUpTimCntEntry 1 }


pm253CntclientUpTimCntValuePortn OBJECT-TYPE
	SYNTAX  Counter32
	MAX-ACCESS read-only
	STATUS current
	DESCRIPTION
        "
        Client Upstream Timer Counter
         :This is the timing counter dedicated
        to the upstream access counters.
        It is incremented every 125 us.
        "
	::= { pm253CntclientUpTimCntEntry 2 }


pm253CntclientUpTimCntErrorPortn OBJECT-TYPE
	SYNTAX  EkiOnOff
	MAX-ACCESS read-only
	STATUS current
	DESCRIPTION
        "
        Client Counter Error :This OID
        when set indicates the upstream
        timing counter value is invalid
        on Port
        "
	::= { pm253CntclientUpTimCntEntry 3 }


pm253CntclientUpTimCntOverloadPortn OBJECT-TYPE
	SYNTAX  EkiOnOff
	MAX-ACCESS read-only
	STATUS current
	DESCRIPTION
        "
        Client Counter Overload :This
         OID when set indicates a upstream
        timing counter overload on Port
        "
	::= { pm253CntclientUpTimCntEntry 4 }


--- *********************************************************
---     TABLE for the pm253CntclientDwCbipCnt articles
--- *********************************************************

pm253CntclientDwCbipCntTable OBJECT-TYPE
	SYNTAX  SEQUENCE OF Pm253CntclientDwCbipCntEntry
	MAX-ACCESS not-accessible
	STATUS current
	DESCRIPTION
        "
        List of pm253CntclientDwCbipCnt
        Article
        "
	::= { pm253CntPort 64 }


pm253CntclientDwCbipCntEntry OBJECT-TYPE
	SYNTAX Pm253CntclientDwCbipCntEntry
	MAX-ACCESS not-accessible
	STATUS current
	DESCRIPTION
        "
        Row definition for the pm253CntclientDwCbipCnt
        table
        "
	INDEX   { pm253CntclientDwCbipCntIndex }
	::= { pm253CntclientDwCbipCntTable 1 }


Pm253CntclientDwCbipCntEntry ::=
	SEQUENCE {
	pm253CntclientDwCbipCntIndex
		INTEGER,
	pm253CntclientDwCbipCntValuePortn
		Counter32,
	pm253CntclientDwCbipCntErrorPortn
		EkiOnOff,
	pm253CntclientDwCbipCntOverloadPortn
		EkiOnOff
	}


pm253CntclientDwCbipCntIndex OBJECT-TYPE
	SYNTAX  INTEGER(0..128)
	MAX-ACCESS  read-only
	STATUS current
	DESCRIPTION
        "
        Index definition for the pm253CntclientDwCbipCnt
        table
        "
	::= { pm253CntclientDwCbipCntEntry 1 }


pm253CntclientDwCbipCntValuePortn OBJECT-TYPE
	SYNTAX  Counter32
	MAX-ACCESS read-only
	STATUS current
	DESCRIPTION
        "
        Client CBIP Errors :This counter
        is incremented each time a CBIP
        parity error is detected on the
        Client output stream  <Help>  This
        counter gives the number of CBIP
        errors on the client port
        "
	::= { pm253CntclientDwCbipCntEntry 2 }


pm253CntclientDwCbipCntErrorPortn OBJECT-TYPE
	SYNTAX  EkiOnOff
	MAX-ACCESS read-only
	STATUS current
	DESCRIPTION
        "
        Client Counter Error :This OID
        when set indicates the CBIP error
        counter value is invalid on Port
        "
	::= { pm253CntclientDwCbipCntEntry 3 }


pm253CntclientDwCbipCntOverloadPortn OBJECT-TYPE
	SYNTAX  EkiOnOff
	MAX-ACCESS read-only
	STATUS current
	DESCRIPTION
        "
        Client CBIP Counter Overload :This
        OID when set indicates a CBIP error
        counter overload on Port
        "
	::= { pm253CntclientDwCbipCntEntry 4 }


--- *********************************************************
---     TABLE for the pm253CntclientDwTimCnt articles
--- *********************************************************

pm253CntclientDwTimCntTable OBJECT-TYPE
	SYNTAX  SEQUENCE OF Pm253CntclientDwTimCntEntry
	MAX-ACCESS not-accessible
	STATUS current
	DESCRIPTION
        "
        List of pm253CntclientDwTimCnt
        Article
        "
	::= { pm253CntPort 72 }


pm253CntclientDwTimCntEntry OBJECT-TYPE
	SYNTAX Pm253CntclientDwTimCntEntry
	MAX-ACCESS not-accessible
	STATUS current
	DESCRIPTION
        "
        Row definition for the pm253CntclientDwTimCnt
        table
        "
	INDEX   { pm253CntclientDwTimCntIndex }
	::= { pm253CntclientDwTimCntTable 1 }


Pm253CntclientDwTimCntEntry ::=
	SEQUENCE {
	pm253CntclientDwTimCntIndex
		INTEGER,
	pm253CntclientDwTimCntValuePortn
		Counter32,
	pm253CntclientDwTimCntErrorPortn
		EkiOnOff,
	pm253CntclientDwTimCntOverloadPortn
		EkiOnOff
	}


pm253CntclientDwTimCntIndex OBJECT-TYPE
	SYNTAX  INTEGER(0..128)
	MAX-ACCESS  read-only
	STATUS current
	DESCRIPTION
        "
        Index definition for the pm253CntclientDwTimCnt
        table
        "
	::= { pm253CntclientDwTimCntEntry 1 }


pm253CntclientDwTimCntValuePortn OBJECT-TYPE
	SYNTAX  Counter32
	MAX-ACCESS read-only
	STATUS current
	DESCRIPTION
        "
        Client Downstream Timer Counter
        :This is the timing counter dedicated
        to the downstream access counters.
        It is incremented every 125 us.
        "
	::= { pm253CntclientDwTimCntEntry 2 }


pm253CntclientDwTimCntErrorPortn OBJECT-TYPE
	SYNTAX  EkiOnOff
	MAX-ACCESS read-only
	STATUS current
	DESCRIPTION
        "
        Client Counter Error :This OID
        when set indicates the downstream
        timer counter value is invalid
         on Port
        "
	::= { pm253CntclientDwTimCntEntry 3 }


pm253CntclientDwTimCntOverloadPortn OBJECT-TYPE
	SYNTAX  EkiOnOff
	MAX-ACCESS read-only
	STATUS current
	DESCRIPTION
        "
        Client Counter Overload :This
         OID when set indicates a downstream
        timer counter overload on Port
        "
	::= { pm253CntclientDwTimCntEntry 4 }


--- *********************************************************
---     TABLE for the pm253CntlineDfrmB1ErrCnt articles
--- *********************************************************

pm253CntlineDfrmB1ErrCntTable OBJECT-TYPE
	SYNTAX  SEQUENCE OF Pm253CntlineDfrmB1ErrCntEntry
	MAX-ACCESS not-accessible
	STATUS current
	DESCRIPTION
        "
        List of pm253CntlineDfrmB1ErrCnt
        Article
        "
	::= { pm253CntLine 152 }


pm253CntlineDfrmB1ErrCntEntry OBJECT-TYPE
	SYNTAX Pm253CntlineDfrmB1ErrCntEntry
	MAX-ACCESS not-accessible
	STATUS current
	DESCRIPTION
        "
        Row definition for the pm253CntlineDfrmB1ErrCnt
        table
        "
	INDEX   { pm253CntlineDfrmB1ErrCntIndex }
	::= { pm253CntlineDfrmB1ErrCntTable 1 }


Pm253CntlineDfrmB1ErrCntEntry ::=
	SEQUENCE {
	pm253CntlineDfrmB1ErrCntIndex
		INTEGER,
	pm253CntlineDfrmB1ErrCntValuePortn
		Counter32,
	pm253CntlineDfrmB1ErrCntErrorPortn
		EkiOnOff,
	pm253CntlineDfrmB1ErrCntOverloadPortn
		EkiOnOff
	}


pm253CntlineDfrmB1ErrCntIndex OBJECT-TYPE
	SYNTAX  INTEGER(0..128)
	MAX-ACCESS  read-only
	STATUS current
	DESCRIPTION
        "
        Index definition for the pm253CntlineDfrmB1ErrCnt
        table
        "
	::= { pm253CntlineDfrmB1ErrCntEntry 1 }


pm253CntlineDfrmB1ErrCntValuePortn OBJECT-TYPE
	SYNTAX  Counter32
	MAX-ACCESS read-only
	STATUS current
	DESCRIPTION
        "
        Line B1 Errors :This counter is
        incremented each time a B1 error
        is detected on the Deframer input
        stream.  <Help>  This counter gives
        the number of B1 errors on the
         line port
        "
	::= { pm253CntlineDfrmB1ErrCntEntry 2 }


pm253CntlineDfrmB1ErrCntErrorPortn OBJECT-TYPE
	SYNTAX  EkiOnOff
	MAX-ACCESS read-only
	STATUS current
	DESCRIPTION
        "
        Line Counter Error :This OID when
        set indicates the B1 error counter
        value is invalid on Port
        "
	::= { pm253CntlineDfrmB1ErrCntEntry 3 }


pm253CntlineDfrmB1ErrCntOverloadPortn OBJECT-TYPE
	SYNTAX  EkiOnOff
	MAX-ACCESS read-only
	STATUS current
	DESCRIPTION
        "
        Line Counter Overload :This OID
        when set indicates a B1 error counter
        overload on Port
        "
	::= { pm253CntlineDfrmB1ErrCntEntry 4 }


--- *********************************************************
---     TABLE for the pm253CntlineDfrmTimCnt articles
--- *********************************************************

pm253CntlineDfrmTimCntTable OBJECT-TYPE
	SYNTAX  SEQUENCE OF Pm253CntlineDfrmTimCntEntry
	MAX-ACCESS not-accessible
	STATUS current
	DESCRIPTION
        "
        List of pm253CntlineDfrmTimCnt
        Article
        "
	::= { pm253CntLine 153 }


pm253CntlineDfrmTimCntEntry OBJECT-TYPE
	SYNTAX Pm253CntlineDfrmTimCntEntry
	MAX-ACCESS not-accessible
	STATUS current
	DESCRIPTION
        "
        Row definition for the pm253CntlineDfrmTimCnt
        table
        "
	INDEX   { pm253CntlineDfrmTimCntIndex }
	::= { pm253CntlineDfrmTimCntTable 1 }


Pm253CntlineDfrmTimCntEntry ::=
	SEQUENCE {
	pm253CntlineDfrmTimCntIndex
		INTEGER,
	pm253CntlineDfrmTimCntValuePortn
		Counter32,
	pm253CntlineDfrmTimCntErrorPortn
		EkiOnOff,
	pm253CntlineDfrmTimCntOverloadPortn
		EkiOnOff
	}


pm253CntlineDfrmTimCntIndex OBJECT-TYPE
	SYNTAX  INTEGER(0..128)
	MAX-ACCESS  read-only
	STATUS current
	DESCRIPTION
        "
        Index definition for the pm253CntlineDfrmTimCnt
        table
        "
	::= { pm253CntlineDfrmTimCntEntry 1 }


pm253CntlineDfrmTimCntValuePortn OBJECT-TYPE
	SYNTAX  Counter32
	MAX-ACCESS read-only
	STATUS current
	DESCRIPTION
        "
        Line Timer Counter :This is the
        timing counter dedicated to the
        downstream deframer counters. It
        is incremented every 125 us.
        "
	::= { pm253CntlineDfrmTimCntEntry 2 }


pm253CntlineDfrmTimCntErrorPortn OBJECT-TYPE
	SYNTAX  EkiOnOff
	MAX-ACCESS read-only
	STATUS current
	DESCRIPTION
        "
        Line Counter Error :This OID when
        set indicates the deframer timer
        counter value is invalid on Port
        "
	::= { pm253CntlineDfrmTimCntEntry 3 }


pm253CntlineDfrmTimCntOverloadPortn OBJECT-TYPE
	SYNTAX  EkiOnOff
	MAX-ACCESS read-only
	STATUS current
	DESCRIPTION
        "
        Line Counter Overload :This OID
        when set indicates a deframer timer
        counter overload on Port
        "
	::= { pm253CntlineDfrmTimCntEntry 4 }


pm253CntCountersReset  OBJECT-TYPE
	SYNTAX EkiOnOff
	MAX-ACCESS read-write
	STATUS current
	DESCRIPTION
	"Counters Reset : This OID resets and restarts all the counters"
	::= { pm253counters  259 }

pm253CntCountersStop  OBJECT-TYPE
	SYNTAX EkiOnOff
	MAX-ACCESS read-write
	STATUS current
	DESCRIPTION
	"Counters stop : This OID stops all the counters"
	::= { pm253counters 260 }






--- *****************************************************
--- $$$$$$$$$$$$$$$$$$$$$$$$$$$$$$$$$$$$$$$$$$$$$$$$$$$$$
---     RMON
--- $$$$$$$$$$$$$$$$$$$$$$$$$$$$$$$$$$$$$$$$$$$$$$$$$$$$$
--- *****************************************************



--- *********************************************************
---     TABLE for the pm253MonupRmonByteCnt articles
--- *********************************************************

pm253MonupRmonByteCntTable OBJECT-TYPE
	SYNTAX  SEQUENCE OF Pm253MonupRmonByteCntEntry
	MAX-ACCESS not-accessible
	STATUS current
	DESCRIPTION
        "
        List of pm253MonupRmonByteCnt
         Article
        "
	::= { pm253MonClientRmonCounter 16 }


pm253MonupRmonByteCntEntry OBJECT-TYPE
	SYNTAX Pm253MonupRmonByteCntEntry
	MAX-ACCESS not-accessible
	STATUS current
	DESCRIPTION
        "
        Row definition for the pm253MonupRmonByteCnt
        table
        "
	INDEX   { pm253MonupRmonByteCntIndex }
	::= { pm253MonupRmonByteCntTable 1 }


Pm253MonupRmonByteCntEntry ::=
	SEQUENCE {
	pm253MonupRmonByteCntIndex
		INTEGER,
	pm253MonupRmonByteCntValuePortn
		Counter64,
	pm253MonupRmonByteCntErrorPortn
		EkiOnOff,
	pm253MonupRmonByteCntOverloadPortn
		EkiOnOff
	}


pm253MonupRmonByteCntIndex OBJECT-TYPE
	SYNTAX  INTEGER(0..128)
	MAX-ACCESS  read-only
	STATUS current
	DESCRIPTION
        "
        Index definition for the pm253MonupRmonByteCnt
        table
        "
	::= { pm253MonupRmonByteCntEntry 1 }


pm253MonupRmonByteCntValuePortn OBJECT-TYPE
	SYNTAX  Counter64
	MAX-ACCESS read-only
	STATUS current
	DESCRIPTION
        "
        Client Input Bytes :This counter
        is increased each time a data byte
        is received on the client port
          <Help>  This counter gives the
        number of bytes received on the
        client port
        "
	::= { pm253MonupRmonByteCntEntry 2 }


pm253MonupRmonByteCntErrorPortn OBJECT-TYPE
	SYNTAX  EkiOnOff
	MAX-ACCESS read-only
	STATUS current
	DESCRIPTION
        "
        Input Bytes Counter Error :This
        OID when set indicates the input
        Bytes counter value is invalid
         on client port
        "
	::= { pm253MonupRmonByteCntEntry 3 }


pm253MonupRmonByteCntOverloadPortn OBJECT-TYPE
	SYNTAX  EkiOnOff
	MAX-ACCESS read-only
	STATUS current
	DESCRIPTION
        "
        Input Bytes Counter Overload :This
        OID when set indicates an input
        Bytes counter overload on client
        port
        "
	::= { pm253MonupRmonByteCntEntry 4 }


--- *********************************************************
---     TABLE for the pm253MonupRmonCrcErrorCnt articles
--- *********************************************************

pm253MonupRmonCrcErrorCntTable OBJECT-TYPE
	SYNTAX  SEQUENCE OF Pm253MonupRmonCrcErrorCntEntry
	MAX-ACCESS not-accessible
	STATUS current
	DESCRIPTION
        "
        List of pm253MonupRmonCrcErrorCnt
        Article
        "
	::= { pm253MonClientRmonCounter 24 }


pm253MonupRmonCrcErrorCntEntry OBJECT-TYPE
	SYNTAX Pm253MonupRmonCrcErrorCntEntry
	MAX-ACCESS not-accessible
	STATUS current
	DESCRIPTION
        "
        Row definition for the pm253MonupRmonCrcErrorCnt
        table
        "
	INDEX   { pm253MonupRmonCrcErrorCntIndex }
	::= { pm253MonupRmonCrcErrorCntTable 1 }


Pm253MonupRmonCrcErrorCntEntry ::=
	SEQUENCE {
	pm253MonupRmonCrcErrorCntIndex
		INTEGER,
	pm253MonupRmonCrcErrorCntValuePortn
		Counter64,
	pm253MonupRmonCrcErrorCntErrorPortn
		EkiOnOff,
	pm253MonupRmonCrcErrorCntOverloadPortn
		EkiOnOff
	}


pm253MonupRmonCrcErrorCntIndex OBJECT-TYPE
	SYNTAX  INTEGER(0..128)
	MAX-ACCESS  read-only
	STATUS current
	DESCRIPTION
        "
        Index definition for the pm253MonupRmonCrcErrorCnt
        table
        "
	::= { pm253MonupRmonCrcErrorCntEntry 1 }


pm253MonupRmonCrcErrorCntValuePortn OBJECT-TYPE
	SYNTAX  Counter64
	MAX-ACCESS read-only
	STATUS current
	DESCRIPTION
        "
        Client Input CRC Errors :This
         counter is increased each time
        a CRC error is detected on the
         client port.   <Help>  This counter
        gives the number of CRC Errors
         received on the client port
        "
	::= { pm253MonupRmonCrcErrorCntEntry 2 }


pm253MonupRmonCrcErrorCntErrorPortn OBJECT-TYPE
	SYNTAX  EkiOnOff
	MAX-ACCESS read-only
	STATUS current
	DESCRIPTION
        "
        Input CRC Errors Counter Error
        :This OID when set indicates the
        input CRC Errors counter value
         is invalid on client port
        "
	::= { pm253MonupRmonCrcErrorCntEntry 3 }


pm253MonupRmonCrcErrorCntOverloadPortn OBJECT-TYPE
	SYNTAX  EkiOnOff
	MAX-ACCESS read-only
	STATUS current
	DESCRIPTION
        "
        Input CRC Errors Counter Overload
        :This OID when set indicates an
        input CRC Errors counter overload
        on client port
        "
	::= { pm253MonupRmonCrcErrorCntEntry 4 }


--- *********************************************************
---     TABLE for the pm253MonupRmonPacketsCnt articles
--- *********************************************************

pm253MonupRmonPacketsCntTable OBJECT-TYPE
	SYNTAX  SEQUENCE OF Pm253MonupRmonPacketsCntEntry
	MAX-ACCESS not-accessible
	STATUS current
	DESCRIPTION
        "
        List of pm253MonupRmonPacketsCnt
        Article
        "
	::= { pm253MonClientRmonCounter 32 }


pm253MonupRmonPacketsCntEntry OBJECT-TYPE
	SYNTAX Pm253MonupRmonPacketsCntEntry
	MAX-ACCESS not-accessible
	STATUS current
	DESCRIPTION
        "
        Row definition for the pm253MonupRmonPacketsCnt
        table
        "
	INDEX   { pm253MonupRmonPacketsCntIndex }
	::= { pm253MonupRmonPacketsCntTable 1 }


Pm253MonupRmonPacketsCntEntry ::=
	SEQUENCE {
	pm253MonupRmonPacketsCntIndex
		INTEGER,
	pm253MonupRmonPacketsCntValuePortn
		Counter64,
	pm253MonupRmonPacketsCntErrorPortn
		EkiOnOff,
	pm253MonupRmonPacketsCntOverloadPortn
		EkiOnOff
	}


pm253MonupRmonPacketsCntIndex OBJECT-TYPE
	SYNTAX  INTEGER(0..128)
	MAX-ACCESS  read-only
	STATUS current
	DESCRIPTION
        "
        Index definition for the pm253MonupRmonPacketsCnt
        table
        "
	::= { pm253MonupRmonPacketsCntEntry 1 }


pm253MonupRmonPacketsCntValuePortn OBJECT-TYPE
	SYNTAX  Counter64
	MAX-ACCESS read-only
	STATUS current
	DESCRIPTION
        "
        Packets Counter On Client Input
        :This counter is increased each
        time a packet is received on the
        client port  <Help>  This counter
        gives the number of packets received
        on the client port
        "
	::= { pm253MonupRmonPacketsCntEntry 2 }


pm253MonupRmonPacketsCntErrorPortn OBJECT-TYPE
	SYNTAX  EkiOnOff
	MAX-ACCESS read-only
	STATUS current
	DESCRIPTION
        "
        Input Packets Counter Error :This
        OID when set indicates the input
        Packets counter value is invalid
        on client port
        "
	::= { pm253MonupRmonPacketsCntEntry 3 }


pm253MonupRmonPacketsCntOverloadPortn OBJECT-TYPE
	SYNTAX  EkiOnOff
	MAX-ACCESS read-only
	STATUS current
	DESCRIPTION
        "
        Input Packets Counter Overload
        :This OID when set indicates an
        input Packets counter overload
         on client port
        "
	::= { pm253MonupRmonPacketsCntEntry 4 }


--- *********************************************************
---     TABLE for the pm253MonupRmonBroadcastCnt articles
--- *********************************************************

pm253MonupRmonBroadcastCntTable OBJECT-TYPE
	SYNTAX  SEQUENCE OF Pm253MonupRmonBroadcastCntEntry
	MAX-ACCESS not-accessible
	STATUS current
	DESCRIPTION
        "
        List of pm253MonupRmonBroadcastCnt
        Article
        "
	::= { pm253MonClientRmonCounter 40 }


pm253MonupRmonBroadcastCntEntry OBJECT-TYPE
	SYNTAX Pm253MonupRmonBroadcastCntEntry
	MAX-ACCESS not-accessible
	STATUS current
	DESCRIPTION
        "
        Row definition for the pm253MonupRmonBroadcastCnt
        table
        "
	INDEX   { pm253MonupRmonBroadcastCntIndex }
	::= { pm253MonupRmonBroadcastCntTable 1 }


Pm253MonupRmonBroadcastCntEntry ::=
	SEQUENCE {
	pm253MonupRmonBroadcastCntIndex
		INTEGER,
	pm253MonupRmonBroadcastCntValuePortn
		Counter64,
	pm253MonupRmonBroadcastCntErrorPortn
		EkiOnOff,
	pm253MonupRmonBroadcastCntOverloadPortn
		EkiOnOff
	}


pm253MonupRmonBroadcastCntIndex OBJECT-TYPE
	SYNTAX  INTEGER(0..128)
	MAX-ACCESS  read-only
	STATUS current
	DESCRIPTION
        "
        Index definition for the pm253MonupRmonBroadcastCnt
        table
        "
	::= { pm253MonupRmonBroadcastCntEntry 1 }


pm253MonupRmonBroadcastCntValuePortn OBJECT-TYPE
	SYNTAX  Counter64
	MAX-ACCESS read-only
	STATUS current
	DESCRIPTION
        "
        Client Input Broadcast Packets
        :This counter is increased each
        time a broadcast packet is received
        on the client port.   <Help>  This
        counter gives the number of Broadcast
        packets received on the client
         port
        "
	::= { pm253MonupRmonBroadcastCntEntry 2 }


pm253MonupRmonBroadcastCntErrorPortn OBJECT-TYPE
	SYNTAX  EkiOnOff
	MAX-ACCESS read-only
	STATUS current
	DESCRIPTION
        "
        Input Broadcast Counter Error
         :This OID when set indicates the
        input Broadcast counter value is
        invalid on client port
        "
	::= { pm253MonupRmonBroadcastCntEntry 3 }


pm253MonupRmonBroadcastCntOverloadPortn OBJECT-TYPE
	SYNTAX  EkiOnOff
	MAX-ACCESS read-only
	STATUS current
	DESCRIPTION
        "
        Input Broadcast Counter Overload
        :This OID when set indicates an
        input Broadcast counter overload
        on client port
        "
	::= { pm253MonupRmonBroadcastCntEntry 4 }


--- *********************************************************
---     TABLE for the pm253MonupRmonMulticastCnt articles
--- *********************************************************

pm253MonupRmonMulticastCntTable OBJECT-TYPE
	SYNTAX  SEQUENCE OF Pm253MonupRmonMulticastCntEntry
	MAX-ACCESS not-accessible
	STATUS current
	DESCRIPTION
        "
        List of pm253MonupRmonMulticastCnt
        Article
        "
	::= { pm253MonClientRmonCounter 48 }


pm253MonupRmonMulticastCntEntry OBJECT-TYPE
	SYNTAX Pm253MonupRmonMulticastCntEntry
	MAX-ACCESS not-accessible
	STATUS current
	DESCRIPTION
        "
        Row definition for the pm253MonupRmonMulticastCnt
        table
        "
	INDEX   { pm253MonupRmonMulticastCntIndex }
	::= { pm253MonupRmonMulticastCntTable 1 }


Pm253MonupRmonMulticastCntEntry ::=
	SEQUENCE {
	pm253MonupRmonMulticastCntIndex
		INTEGER,
	pm253MonupRmonMulticastCntValuePortn
		Counter64,
	pm253MonupRmonMulticastCntErrorPortn
		EkiOnOff,
	pm253MonupRmonMulticastCntOverloadPortn
		EkiOnOff
	}


pm253MonupRmonMulticastCntIndex OBJECT-TYPE
	SYNTAX  INTEGER(0..128)
	MAX-ACCESS  read-only
	STATUS current
	DESCRIPTION
        "
        Index definition for the pm253MonupRmonMulticastCnt
        table
        "
	::= { pm253MonupRmonMulticastCntEntry 1 }


pm253MonupRmonMulticastCntValuePortn OBJECT-TYPE
	SYNTAX  Counter64
	MAX-ACCESS read-only
	STATUS current
	DESCRIPTION
        "
        Client Input Multicast Packets
        :This counter is increased each
        time a Multicast packet is received
        on the client port.  <Help>  This
        counter gives the number of Multicast
        packets received on the client
         port
        "
	::= { pm253MonupRmonMulticastCntEntry 2 }


pm253MonupRmonMulticastCntErrorPortn OBJECT-TYPE
	SYNTAX  EkiOnOff
	MAX-ACCESS read-only
	STATUS current
	DESCRIPTION
        "
        Input Multicast Counter Error
         :This OID when set indicates the
        input Multicast counter value is
        invalid on client port
        "
	::= { pm253MonupRmonMulticastCntEntry 3 }


pm253MonupRmonMulticastCntOverloadPortn OBJECT-TYPE
	SYNTAX  EkiOnOff
	MAX-ACCESS read-only
	STATUS current
	DESCRIPTION
        "
        Input Multicast Counter Overload
        :This OID when set indicates an
        input Multicast counter overload
        on client port
        "
	::= { pm253MonupRmonMulticastCntEntry 4 }


--- *********************************************************
---     TABLE for the pm253MonupRmonTimerCnt articles
--- *********************************************************

pm253MonupRmonTimerCntTable OBJECT-TYPE
	SYNTAX  SEQUENCE OF Pm253MonupRmonTimerCntEntry
	MAX-ACCESS not-accessible
	STATUS current
	DESCRIPTION
        "
        List of pm253MonupRmonTimerCnt
        Article
        "
	::= { pm253MonClientRmonCounter 56 }


pm253MonupRmonTimerCntEntry OBJECT-TYPE
	SYNTAX Pm253MonupRmonTimerCntEntry
	MAX-ACCESS not-accessible
	STATUS current
	DESCRIPTION
        "
        Row definition for the pm253MonupRmonTimerCnt
        table
        "
	INDEX   { pm253MonupRmonTimerCntIndex }
	::= { pm253MonupRmonTimerCntTable 1 }


Pm253MonupRmonTimerCntEntry ::=
	SEQUENCE {
	pm253MonupRmonTimerCntIndex
		INTEGER,
	pm253MonupRmonTimerCntValuePortn
		Counter64,
	pm253MonupRmonTimerCntErrorPortn
		EkiOnOff,
	pm253MonupRmonTimerCntOverloadPortn
		EkiOnOff
	}


pm253MonupRmonTimerCntIndex OBJECT-TYPE
	SYNTAX  INTEGER(0..128)
	MAX-ACCESS  read-only
	STATUS current
	DESCRIPTION
        "
        Index definition for the pm253MonupRmonTimerCnt
        table
        "
	::= { pm253MonupRmonTimerCntEntry 1 }


pm253MonupRmonTimerCntValuePortn OBJECT-TYPE
	SYNTAX  Counter64
	MAX-ACCESS read-only
	STATUS current
	DESCRIPTION
        "
        RMON Timer On Client Input :This
        is the timing counter dedicated
        to the upstream RMON counters.
         It is incremented every 125 us.
        "
	::= { pm253MonupRmonTimerCntEntry 2 }


pm253MonupRmonTimerCntErrorPortn OBJECT-TYPE
	SYNTAX  EkiOnOff
	MAX-ACCESS read-only
	STATUS current
	DESCRIPTION
        "
        Input RMON Timer Error :This OID
        when set indicates the input RMON
        timer is invalid on client port
        "
	::= { pm253MonupRmonTimerCntEntry 3 }


pm253MonupRmonTimerCntOverloadPortn OBJECT-TYPE
	SYNTAX  EkiOnOff
	MAX-ACCESS read-only
	STATUS current
	DESCRIPTION
        "
        Input RMON Timer Overload :This
        OID when set indicates an input
        RMON timer overload on client port
        "
	::= { pm253MonupRmonTimerCntEntry 4 }


--- *********************************************************
---     TABLE for the pm253MonupRmonPauseFrameCnt articles
--- *********************************************************

pm253MonupRmonPauseFrameCntTable OBJECT-TYPE
	SYNTAX  SEQUENCE OF Pm253MonupRmonPauseFrameCntEntry
	MAX-ACCESS not-accessible
	STATUS current
	DESCRIPTION
        "
        List of pm253MonupRmonPauseFrameCnt
        Article
        "
	::= { pm253MonClientRmonCounter 64 }


pm253MonupRmonPauseFrameCntEntry OBJECT-TYPE
	SYNTAX Pm253MonupRmonPauseFrameCntEntry
	MAX-ACCESS not-accessible
	STATUS current
	DESCRIPTION
        "
        Row definition for the pm253MonupRmonPauseFrameCnt
        table
        "
	INDEX   { pm253MonupRmonPauseFrameCntIndex }
	::= { pm253MonupRmonPauseFrameCntTable 1 }


Pm253MonupRmonPauseFrameCntEntry ::=
	SEQUENCE {
	pm253MonupRmonPauseFrameCntIndex
		INTEGER,
	pm253MonupRmonPauseFrameCntValuePortn
		Counter64,
	pm253MonupRmonPauseFrameCntErrorPortn
		EkiOnOff,
	pm253MonupRmonPauseFrameCntOverloadPortn
		EkiOnOff
	}


pm253MonupRmonPauseFrameCntIndex OBJECT-TYPE
	SYNTAX  INTEGER(0..128)
	MAX-ACCESS  read-only
	STATUS current
	DESCRIPTION
        "
        Index definition for the pm253MonupRmonPauseFrameCnt
        table
        "
	::= { pm253MonupRmonPauseFrameCntEntry 1 }


pm253MonupRmonPauseFrameCntValuePortn OBJECT-TYPE
	SYNTAX  Counter64
	MAX-ACCESS read-only
	STATUS current
	DESCRIPTION
        "
        Pause Counter On Client Input
         :This counter is increased each
        time a Pause frame is received
         on the client port
        "
	::= { pm253MonupRmonPauseFrameCntEntry 2 }


pm253MonupRmonPauseFrameCntErrorPortn OBJECT-TYPE
	SYNTAX  EkiOnOff
	MAX-ACCESS read-only
	STATUS current
	DESCRIPTION
        "
        Input Pause Counter Error :This
        OID when set indicates the input
        Pause counter value is invalid
         on client port
        "
	::= { pm253MonupRmonPauseFrameCntEntry 3 }


pm253MonupRmonPauseFrameCntOverloadPortn OBJECT-TYPE
	SYNTAX  EkiOnOff
	MAX-ACCESS read-only
	STATUS current
	DESCRIPTION
        "
        Input Pause Counter Overload :This
        OID when set indicates an input
        Pause counter overload on client
        port
        "
	::= { pm253MonupRmonPauseFrameCntEntry 4 }


--- *********************************************************
---     TABLE for the pm253MonupRmonDropFrameCnt articles
--- *********************************************************

pm253MonupRmonDropFrameCntTable OBJECT-TYPE
	SYNTAX  SEQUENCE OF Pm253MonupRmonDropFrameCntEntry
	MAX-ACCESS not-accessible
	STATUS current
	DESCRIPTION
        "
        List of pm253MonupRmonDropFrameCnt
        Article
        "
	::= { pm253MonClientRmonCounter 72 }


pm253MonupRmonDropFrameCntEntry OBJECT-TYPE
	SYNTAX Pm253MonupRmonDropFrameCntEntry
	MAX-ACCESS not-accessible
	STATUS current
	DESCRIPTION
        "
        Row definition for the pm253MonupRmonDropFrameCnt
        table
        "
	INDEX   { pm253MonupRmonDropFrameCntIndex }
	::= { pm253MonupRmonDropFrameCntTable 1 }


Pm253MonupRmonDropFrameCntEntry ::=
	SEQUENCE {
	pm253MonupRmonDropFrameCntIndex
		INTEGER,
	pm253MonupRmonDropFrameCntValuePortn
		Counter64,
	pm253MonupRmonDropFrameCntErrorPortn
		EkiOnOff,
	pm253MonupRmonDropFrameCntOverloadPortn
		EkiOnOff
	}


pm253MonupRmonDropFrameCntIndex OBJECT-TYPE
	SYNTAX  INTEGER(0..128)
	MAX-ACCESS  read-only
	STATUS current
	DESCRIPTION
        "
        Index definition for the pm253MonupRmonDropFrameCnt
        table
        "
	::= { pm253MonupRmonDropFrameCntEntry 1 }


pm253MonupRmonDropFrameCntValuePortn OBJECT-TYPE
	SYNTAX  Counter64
	MAX-ACCESS read-only
	STATUS current
	DESCRIPTION
        "
        Drop Counter On Client Input :This
        counter is increased each time
         a Frame is dropped on the input
        client port
        "
	::= { pm253MonupRmonDropFrameCntEntry 2 }


pm253MonupRmonDropFrameCntErrorPortn OBJECT-TYPE
	SYNTAX  EkiOnOff
	MAX-ACCESS read-only
	STATUS current
	DESCRIPTION
        "
        Input Drop Counter Error :This
        OID when set indicates the input
        Drop counter value is invalid on
        client port
        "
	::= { pm253MonupRmonDropFrameCntEntry 3 }


pm253MonupRmonDropFrameCntOverloadPortn OBJECT-TYPE
	SYNTAX  EkiOnOff
	MAX-ACCESS read-only
	STATUS current
	DESCRIPTION
        "
        Input Drop Counter Overload :This
        OID when set indicates an input
        Drop counter overload on client
        port
        "
	::= { pm253MonupRmonDropFrameCntEntry 4 }


--- *********************************************************
---     TABLE for the pm253MonupRmonBitsCnt articles
--- *********************************************************

pm253MonupRmonBitsCntTable OBJECT-TYPE
	SYNTAX  SEQUENCE OF Pm253MonupRmonBitsCntEntry
	MAX-ACCESS not-accessible
	STATUS current
	DESCRIPTION
        "
        List of pm253MonupRmonBitsCnt
         Article
        "
	::= { pm253MonClientRmonCounter 80 }


pm253MonupRmonBitsCntEntry OBJECT-TYPE
	SYNTAX Pm253MonupRmonBitsCntEntry
	MAX-ACCESS not-accessible
	STATUS current
	DESCRIPTION
        "
        Row definition for the pm253MonupRmonBitsCnt
        table
        "
	INDEX   { pm253MonupRmonBitsCntIndex }
	::= { pm253MonupRmonBitsCntTable 1 }


Pm253MonupRmonBitsCntEntry ::=
	SEQUENCE {
	pm253MonupRmonBitsCntIndex
		INTEGER,
	pm253MonupRmonBitsCntValuePortn
		Counter64,
	pm253MonupRmonBitsCntErrorPortn
		EkiOnOff,
	pm253MonupRmonBitsCntOverloadPortn
		EkiOnOff
	}


pm253MonupRmonBitsCntIndex OBJECT-TYPE
	SYNTAX  INTEGER(0..128)
	MAX-ACCESS  read-only
	STATUS current
	DESCRIPTION
        "
        Index definition for the pm253MonupRmonBitsCnt
        table
        "
	::= { pm253MonupRmonBitsCntEntry 1 }


pm253MonupRmonBitsCntValuePortn OBJECT-TYPE
	SYNTAX  Counter64
	MAX-ACCESS read-only
	STATUS current
	DESCRIPTION
        "
        Bits Counter On Client Input :This
        counter is increased each time
         a bit is received on the input
        client port
        "
	::= { pm253MonupRmonBitsCntEntry 2 }


pm253MonupRmonBitsCntErrorPortn OBJECT-TYPE
	SYNTAX  EkiOnOff
	MAX-ACCESS read-only
	STATUS current
	DESCRIPTION
        "
        Input Bits Counter Error :This
        OID when set indicates the input
        Bits counter value is invalid on
        client port
        "
	::= { pm253MonupRmonBitsCntEntry 3 }


pm253MonupRmonBitsCntOverloadPortn OBJECT-TYPE
	SYNTAX  EkiOnOff
	MAX-ACCESS read-only
	STATUS current
	DESCRIPTION
        "
        Input Bits Counter Overload :This
        OID when set indicates an input
        Bits counter overload on client
        port
        "
	::= { pm253MonupRmonBitsCntEntry 4 }


--- *********************************************************
---     TABLE for the pm253MonupRmonUnicastCnt articles
--- *********************************************************

pm253MonupRmonUnicastCntTable OBJECT-TYPE
	SYNTAX  SEQUENCE OF Pm253MonupRmonUnicastCntEntry
	MAX-ACCESS not-accessible
	STATUS current
	DESCRIPTION
        "
        List of pm253MonupRmonUnicastCnt
        Article
        "
	::= { pm253MonClientRmonCounter 88 }


pm253MonupRmonUnicastCntEntry OBJECT-TYPE
	SYNTAX Pm253MonupRmonUnicastCntEntry
	MAX-ACCESS not-accessible
	STATUS current
	DESCRIPTION
        "
        Row definition for the pm253MonupRmonUnicastCnt
        table
        "
	INDEX   { pm253MonupRmonUnicastCntIndex }
	::= { pm253MonupRmonUnicastCntTable 1 }


Pm253MonupRmonUnicastCntEntry ::=
	SEQUENCE {
	pm253MonupRmonUnicastCntIndex
		INTEGER,
	pm253MonupRmonUnicastCntValuePortn
		Counter64,
	pm253MonupRmonUnicastCntErrorPortn
		EkiOnOff,
	pm253MonupRmonUnicastCntOverloadPortn
		EkiOnOff
	}


pm253MonupRmonUnicastCntIndex OBJECT-TYPE
	SYNTAX  INTEGER(0..128)
	MAX-ACCESS  read-only
	STATUS current
	DESCRIPTION
        "
        Index definition for the pm253MonupRmonUnicastCnt
        table
        "
	::= { pm253MonupRmonUnicastCntEntry 1 }


pm253MonupRmonUnicastCntValuePortn OBJECT-TYPE
	SYNTAX  Counter64
	MAX-ACCESS read-only
	STATUS current
	DESCRIPTION
        "
        Client Input Unicast Packets :This
        counter is increased each time
         a Unicast packet is received on
        client input  <Help>  This counter
        gives the number of Unicast packets
        received on the client input port
        "
	::= { pm253MonupRmonUnicastCntEntry 2 }


pm253MonupRmonUnicastCntErrorPortn OBJECT-TYPE
	SYNTAX  EkiOnOff
	MAX-ACCESS read-only
	STATUS current
	DESCRIPTION
        "
        Input Unicast Counter Error :This
        OID when set indicates the input
        Drop counter value is invalid on
        client port
        "
	::= { pm253MonupRmonUnicastCntEntry 3 }


pm253MonupRmonUnicastCntOverloadPortn OBJECT-TYPE
	SYNTAX  EkiOnOff
	MAX-ACCESS read-only
	STATUS current
	DESCRIPTION
        "
        Input Unicast Counter Overload
        :This OID when set indicates an
        input Drop counter overload on
         client port
        "
	::= { pm253MonupRmonUnicastCntEntry 4 }


--- *********************************************************
---     TABLE for the pm253MonupRmonNonUnicastCnt articles
--- *********************************************************

pm253MonupRmonNonUnicastCntTable OBJECT-TYPE
	SYNTAX  SEQUENCE OF Pm253MonupRmonNonUnicastCntEntry
	MAX-ACCESS not-accessible
	STATUS current
	DESCRIPTION
        "
        List of pm253MonupRmonNonUnicastCnt
        Article
        "
	::= { pm253MonClientRmonCounter 96 }


pm253MonupRmonNonUnicastCntEntry OBJECT-TYPE
	SYNTAX Pm253MonupRmonNonUnicastCntEntry
	MAX-ACCESS not-accessible
	STATUS current
	DESCRIPTION
        "
        Row definition for the pm253MonupRmonNonUnicastCnt
        table
        "
	INDEX   { pm253MonupRmonNonUnicastCntIndex }
	::= { pm253MonupRmonNonUnicastCntTable 1 }


Pm253MonupRmonNonUnicastCntEntry ::=
	SEQUENCE {
	pm253MonupRmonNonUnicastCntIndex
		INTEGER,
	pm253MonupRmonNonUnicastCntValuePortn
		Counter64,
	pm253MonupRmonNonUnicastCntErrorPortn
		EkiOnOff,
	pm253MonupRmonNonUnicastCntOverloadPortn
		EkiOnOff
	}


pm253MonupRmonNonUnicastCntIndex OBJECT-TYPE
	SYNTAX  INTEGER(0..128)
	MAX-ACCESS  read-only
	STATUS current
	DESCRIPTION
        "
        Index definition for the pm253MonupRmonNonUnicastCnt
        table
        "
	::= { pm253MonupRmonNonUnicastCntEntry 1 }


pm253MonupRmonNonUnicastCntValuePortn OBJECT-TYPE
	SYNTAX  Counter64
	MAX-ACCESS read-only
	STATUS current
	DESCRIPTION
        "
        Client Input Not Unicast Packets
        :This counter is increased each
        time a Non Unicast packet is received
        on client input    <Help>  This
        counter gives the number of Non
        Unicast packets received on the
        client input port
        "
	::= { pm253MonupRmonNonUnicastCntEntry 2 }


pm253MonupRmonNonUnicastCntErrorPortn OBJECT-TYPE
	SYNTAX  EkiOnOff
	MAX-ACCESS read-only
	STATUS current
	DESCRIPTION
        "
        Input Non Unicast Counter Error
        :This OID when set indicates the
        input Bits counter value is invalid
        on client port
        "
	::= { pm253MonupRmonNonUnicastCntEntry 3 }


pm253MonupRmonNonUnicastCntOverloadPortn OBJECT-TYPE
	SYNTAX  EkiOnOff
	MAX-ACCESS read-only
	STATUS current
	DESCRIPTION
        "
        Input Non Unicast Counter Overload
        :This OID when set indicates an
        input Bits counter overload on
         client port
        "
	::= { pm253MonupRmonNonUnicastCntEntry 4 }


--- *********************************************************
---     TABLE for the pm253MondwRmonByteCnt articles
--- *********************************************************

pm253MondwRmonByteCntTable OBJECT-TYPE
	SYNTAX  SEQUENCE OF Pm253MondwRmonByteCntEntry
	MAX-ACCESS not-accessible
	STATUS current
	DESCRIPTION
        "
        List of pm253MondwRmonByteCnt
         Article
        "
	::= { pm253MonClientRmonCounter 112 }


pm253MondwRmonByteCntEntry OBJECT-TYPE
	SYNTAX Pm253MondwRmonByteCntEntry
	MAX-ACCESS not-accessible
	STATUS current
	DESCRIPTION
        "
        Row definition for the pm253MondwRmonByteCnt
        table
        "
	INDEX   { pm253MondwRmonByteCntIndex }
	::= { pm253MondwRmonByteCntTable 1 }


Pm253MondwRmonByteCntEntry ::=
	SEQUENCE {
	pm253MondwRmonByteCntIndex
		INTEGER,
	pm253MondwRmonByteCntValuePortn
		Counter64,
	pm253MondwRmonByteCntErrorPortn
		EkiOnOff,
	pm253MondwRmonByteCntOverloadPortn
		EkiOnOff
	}


pm253MondwRmonByteCntIndex OBJECT-TYPE
	SYNTAX  INTEGER(0..128)
	MAX-ACCESS  read-only
	STATUS current
	DESCRIPTION
        "
        Index definition for the pm253MondwRmonByteCnt
        table
        "
	::= { pm253MondwRmonByteCntEntry 1 }


pm253MondwRmonByteCntValuePortn OBJECT-TYPE
	SYNTAX  Counter64
	MAX-ACCESS read-only
	STATUS current
	DESCRIPTION
        "
        Client Output Bytes :This counter
        is increased each time a data byte
        is transmitted on the client port.
         <Help>  This counter gives the
        number of bytes transmitted on
         the client port
        "
	::= { pm253MondwRmonByteCntEntry 2 }


pm253MondwRmonByteCntErrorPortn OBJECT-TYPE
	SYNTAX  EkiOnOff
	MAX-ACCESS read-only
	STATUS current
	DESCRIPTION
        "
        Output Bytes Counter Error :This
        OID when set indicates the output
        Bytes counter value is invalid
         on client port
        "
	::= { pm253MondwRmonByteCntEntry 3 }


pm253MondwRmonByteCntOverloadPortn OBJECT-TYPE
	SYNTAX  EkiOnOff
	MAX-ACCESS read-only
	STATUS current
	DESCRIPTION
        "
        Output Bytes Counter Overload
         :This OID when set indicates an
        output Bytes counter overload on
        client port
        "
	::= { pm253MondwRmonByteCntEntry 4 }


--- *********************************************************
---     TABLE for the pm253MondwRmonCrcErrorCnt articles
--- *********************************************************

pm253MondwRmonCrcErrorCntTable OBJECT-TYPE
	SYNTAX  SEQUENCE OF Pm253MondwRmonCrcErrorCntEntry
	MAX-ACCESS not-accessible
	STATUS current
	DESCRIPTION
        "
        List of pm253MondwRmonCrcErrorCnt
        Article
        "
	::= { pm253MonClientRmonCounter 120 }


pm253MondwRmonCrcErrorCntEntry OBJECT-TYPE
	SYNTAX Pm253MondwRmonCrcErrorCntEntry
	MAX-ACCESS not-accessible
	STATUS current
	DESCRIPTION
        "
        Row definition for the pm253MondwRmonCrcErrorCnt
        table
        "
	INDEX   { pm253MondwRmonCrcErrorCntIndex }
	::= { pm253MondwRmonCrcErrorCntTable 1 }


Pm253MondwRmonCrcErrorCntEntry ::=
	SEQUENCE {
	pm253MondwRmonCrcErrorCntIndex
		INTEGER,
	pm253MondwRmonCrcErrorCntValuePortn
		Counter64,
	pm253MondwRmonCrcErrorCntErrorPortn
		EkiOnOff,
	pm253MondwRmonCrcErrorCntOverloadPortn
		EkiOnOff
	}


pm253MondwRmonCrcErrorCntIndex OBJECT-TYPE
	SYNTAX  INTEGER(0..128)
	MAX-ACCESS  read-only
	STATUS current
	DESCRIPTION
        "
        Index definition for the pm253MondwRmonCrcErrorCnt
        table
        "
	::= { pm253MondwRmonCrcErrorCntEntry 1 }


pm253MondwRmonCrcErrorCntValuePortn OBJECT-TYPE
	SYNTAX  Counter64
	MAX-ACCESS read-only
	STATUS current
	DESCRIPTION
        "
        CRC Errors Counter On Client Output
        :This counter is increased each
        time a CRC error is detected on
        the output client port  <Help>
          This counter gives the number
        of CRC Errors transmitted on the
        client port
        "
	::= { pm253MondwRmonCrcErrorCntEntry 2 }


pm253MondwRmonCrcErrorCntErrorPortn OBJECT-TYPE
	SYNTAX  EkiOnOff
	MAX-ACCESS read-only
	STATUS current
	DESCRIPTION
        "
        Output CRC Errors Counter Error
        :This OID when set indicates the
        output CRC Errors counter value
        is invalid on client port
        "
	::= { pm253MondwRmonCrcErrorCntEntry 3 }


pm253MondwRmonCrcErrorCntOverloadPortn OBJECT-TYPE
	SYNTAX  EkiOnOff
	MAX-ACCESS read-only
	STATUS current
	DESCRIPTION
        "
        Output CRC Errors Counter Overload
        :This OID when set indicates an
        output CRC Errors counter overload
        on client port
        "
	::= { pm253MondwRmonCrcErrorCntEntry 4 }


--- *********************************************************
---     TABLE for the pm253MondwRmonPacketsCnt articles
--- *********************************************************

pm253MondwRmonPacketsCntTable OBJECT-TYPE
	SYNTAX  SEQUENCE OF Pm253MondwRmonPacketsCntEntry
	MAX-ACCESS not-accessible
	STATUS current
	DESCRIPTION
        "
        List of pm253MondwRmonPacketsCnt
        Article
        "
	::= { pm253MonClientRmonCounter 128 }


pm253MondwRmonPacketsCntEntry OBJECT-TYPE
	SYNTAX Pm253MondwRmonPacketsCntEntry
	MAX-ACCESS not-accessible
	STATUS current
	DESCRIPTION
        "
        Row definition for the pm253MondwRmonPacketsCnt
        table
        "
	INDEX   { pm253MondwRmonPacketsCntIndex }
	::= { pm253MondwRmonPacketsCntTable 1 }


Pm253MondwRmonPacketsCntEntry ::=
	SEQUENCE {
	pm253MondwRmonPacketsCntIndex
		INTEGER,
	pm253MondwRmonPacketsCntValuePortn
		Counter64,
	pm253MondwRmonPacketsCntErrorPortn
		EkiOnOff,
	pm253MondwRmonPacketsCntOverloadPortn
		EkiOnOff
	}


pm253MondwRmonPacketsCntIndex OBJECT-TYPE
	SYNTAX  INTEGER(0..128)
	MAX-ACCESS  read-only
	STATUS current
	DESCRIPTION
        "
        Index definition for the pm253MondwRmonPacketsCnt
        table
        "
	::= { pm253MondwRmonPacketsCntEntry 1 }


pm253MondwRmonPacketsCntValuePortn OBJECT-TYPE
	SYNTAX  Counter64
	MAX-ACCESS read-only
	STATUS current
	DESCRIPTION
        "
        Packets Counter On Client Output
        :This counter is increased each
        time a packet is transmitted on
        the client port.  <Help>  This
         counter gives the number of packets
        transmitted on the client port
        "
	::= { pm253MondwRmonPacketsCntEntry 2 }


pm253MondwRmonPacketsCntErrorPortn OBJECT-TYPE
	SYNTAX  EkiOnOff
	MAX-ACCESS read-only
	STATUS current
	DESCRIPTION
        "
        Output Packets Counter Error :This
        OID when set indicates the output
        Packets counter value is invalid
        on client port
        "
	::= { pm253MondwRmonPacketsCntEntry 3 }


pm253MondwRmonPacketsCntOverloadPortn OBJECT-TYPE
	SYNTAX  EkiOnOff
	MAX-ACCESS read-only
	STATUS current
	DESCRIPTION
        "
        Output Packets Counter Overload
        :This OID when set indicates an
        output Packets counter overload
        on client port
        "
	::= { pm253MondwRmonPacketsCntEntry 4 }


--- *********************************************************
---     TABLE for the pm253MondwRmonBroadcastCnt articles
--- *********************************************************

pm253MondwRmonBroadcastCntTable OBJECT-TYPE
	SYNTAX  SEQUENCE OF Pm253MondwRmonBroadcastCntEntry
	MAX-ACCESS not-accessible
	STATUS current
	DESCRIPTION
        "
        List of pm253MondwRmonBroadcastCnt
        Article
        "
	::= { pm253MonClientRmonCounter 136 }


pm253MondwRmonBroadcastCntEntry OBJECT-TYPE
	SYNTAX Pm253MondwRmonBroadcastCntEntry
	MAX-ACCESS not-accessible
	STATUS current
	DESCRIPTION
        "
        Row definition for the pm253MondwRmonBroadcastCnt
        table
        "
	INDEX   { pm253MondwRmonBroadcastCntIndex }
	::= { pm253MondwRmonBroadcastCntTable 1 }


Pm253MondwRmonBroadcastCntEntry ::=
	SEQUENCE {
	pm253MondwRmonBroadcastCntIndex
		INTEGER,
	pm253MondwRmonBroadcastCntValuePortn
		Counter64,
	pm253MondwRmonBroadcastCntErrorPortn
		EkiOnOff,
	pm253MondwRmonBroadcastCntOverloadPortn
		EkiOnOff
	}


pm253MondwRmonBroadcastCntIndex OBJECT-TYPE
	SYNTAX  INTEGER(0..128)
	MAX-ACCESS  read-only
	STATUS current
	DESCRIPTION
        "
        Index definition for the pm253MondwRmonBroadcastCnt
        table
        "
	::= { pm253MondwRmonBroadcastCntEntry 1 }


pm253MondwRmonBroadcastCntValuePortn OBJECT-TYPE
	SYNTAX  Counter64
	MAX-ACCESS read-only
	STATUS current
	DESCRIPTION
        "
        Client Output Broadcast Packets
        :This counter is increased each
        time a broadcast packet is transmitted
        on the client port.  <Help>  This
        counter gives the number of Broadcast
        packets transmitted on the client
        port
        "
	::= { pm253MondwRmonBroadcastCntEntry 2 }


pm253MondwRmonBroadcastCntErrorPortn OBJECT-TYPE
	SYNTAX  EkiOnOff
	MAX-ACCESS read-only
	STATUS current
	DESCRIPTION
        "
        Output Broadcast Counter Error
        :This OID when set indicates the
        output Broadcast counter value
         is invalid on client port
        "
	::= { pm253MondwRmonBroadcastCntEntry 3 }


pm253MondwRmonBroadcastCntOverloadPortn OBJECT-TYPE
	SYNTAX  EkiOnOff
	MAX-ACCESS read-only
	STATUS current
	DESCRIPTION
        "
        Output Broadcast Counter Overload
        :This OID when set indicates an
        output Broadcast counter overload
        on client port
        "
	::= { pm253MondwRmonBroadcastCntEntry 4 }


--- *********************************************************
---     TABLE for the pm253MondwRmonMulticastCnt articles
--- *********************************************************

pm253MondwRmonMulticastCntTable OBJECT-TYPE
	SYNTAX  SEQUENCE OF Pm253MondwRmonMulticastCntEntry
	MAX-ACCESS not-accessible
	STATUS current
	DESCRIPTION
        "
        List of pm253MondwRmonMulticastCnt
        Article
        "
	::= { pm253MonClientRmonCounter 144 }


pm253MondwRmonMulticastCntEntry OBJECT-TYPE
	SYNTAX Pm253MondwRmonMulticastCntEntry
	MAX-ACCESS not-accessible
	STATUS current
	DESCRIPTION
        "
        Row definition for the pm253MondwRmonMulticastCnt
        table
        "
	INDEX   { pm253MondwRmonMulticastCntIndex }
	::= { pm253MondwRmonMulticastCntTable 1 }


Pm253MondwRmonMulticastCntEntry ::=
	SEQUENCE {
	pm253MondwRmonMulticastCntIndex
		INTEGER,
	pm253MondwRmonMulticastCntValuePortn
		Counter64,
	pm253MondwRmonMulticastCntErrorPortn
		EkiOnOff,
	pm253MondwRmonMulticastCntOverloadPortn
		EkiOnOff
	}


pm253MondwRmonMulticastCntIndex OBJECT-TYPE
	SYNTAX  INTEGER(0..128)
	MAX-ACCESS  read-only
	STATUS current
	DESCRIPTION
        "
        Index definition for the pm253MondwRmonMulticastCnt
        table
        "
	::= { pm253MondwRmonMulticastCntEntry 1 }


pm253MondwRmonMulticastCntValuePortn OBJECT-TYPE
	SYNTAX  Counter64
	MAX-ACCESS read-only
	STATUS current
	DESCRIPTION
        "
        Client Output Multicast Packets
        :This counter is increased each
        time a Multicast packet is tra,smitted
        on the client port.  <Help>  This
        counter gives the number of Multicast
        packets transmitted on the client
        port
        "
	::= { pm253MondwRmonMulticastCntEntry 2 }


pm253MondwRmonMulticastCntErrorPortn OBJECT-TYPE
	SYNTAX  EkiOnOff
	MAX-ACCESS read-only
	STATUS current
	DESCRIPTION
        "
        Output Multicast Counter Error
        :This OID when set indicates the
        output Multicast counter value
         is invalid on client port
        "
	::= { pm253MondwRmonMulticastCntEntry 3 }


pm253MondwRmonMulticastCntOverloadPortn OBJECT-TYPE
	SYNTAX  EkiOnOff
	MAX-ACCESS read-only
	STATUS current
	DESCRIPTION
        "
        Output Multicast Counter Overload
        :This OID when set indicates an
        output Multicast counter overload
        on client port
        "
	::= { pm253MondwRmonMulticastCntEntry 4 }


--- *********************************************************
---     TABLE for the pm253MondwRmonPauseFrameCnt articles
--- *********************************************************

pm253MondwRmonPauseFrameCntTable OBJECT-TYPE
	SYNTAX  SEQUENCE OF Pm253MondwRmonPauseFrameCntEntry
	MAX-ACCESS not-accessible
	STATUS current
	DESCRIPTION
        "
        List of pm253MondwRmonPauseFrameCnt
        Article
        "
	::= { pm253MonClientRmonCounter 152 }


pm253MondwRmonPauseFrameCntEntry OBJECT-TYPE
	SYNTAX Pm253MondwRmonPauseFrameCntEntry
	MAX-ACCESS not-accessible
	STATUS current
	DESCRIPTION
        "
        Row definition for the pm253MondwRmonPauseFrameCnt
        table
        "
	INDEX   { pm253MondwRmonPauseFrameCntIndex }
	::= { pm253MondwRmonPauseFrameCntTable 1 }


Pm253MondwRmonPauseFrameCntEntry ::=
	SEQUENCE {
	pm253MondwRmonPauseFrameCntIndex
		INTEGER,
	pm253MondwRmonPauseFrameCntValuePortn
		Counter64,
	pm253MondwRmonPauseFrameCntErrorPortn
		EkiOnOff,
	pm253MondwRmonPauseFrameCntOverloadPortn
		EkiOnOff
	}


pm253MondwRmonPauseFrameCntIndex OBJECT-TYPE
	SYNTAX  INTEGER(0..128)
	MAX-ACCESS  read-only
	STATUS current
	DESCRIPTION
        "
        Index definition for the pm253MondwRmonPauseFrameCnt
        table
        "
	::= { pm253MondwRmonPauseFrameCntEntry 1 }


pm253MondwRmonPauseFrameCntValuePortn OBJECT-TYPE
	SYNTAX  Counter64
	MAX-ACCESS read-only
	STATUS current
	DESCRIPTION
        "
        Pause Counter On Client Output
        :This counter is increased each
        time a Pause frame is generated
        by the PM on the client port
        "
	::= { pm253MondwRmonPauseFrameCntEntry 2 }


pm253MondwRmonPauseFrameCntErrorPortn OBJECT-TYPE
	SYNTAX  EkiOnOff
	MAX-ACCESS read-only
	STATUS current
	DESCRIPTION
        "
        Output Pause Counter Error :This
        OID when set indicates the output
        Pause counter value is invalid
         on client port
        "
	::= { pm253MondwRmonPauseFrameCntEntry 3 }


pm253MondwRmonPauseFrameCntOverloadPortn OBJECT-TYPE
	SYNTAX  EkiOnOff
	MAX-ACCESS read-only
	STATUS current
	DESCRIPTION
        "
        Output Pause Counter Overload
         :This OID when set indicates an
        output Pause counter overload on
        client port
        "
	::= { pm253MondwRmonPauseFrameCntEntry 4 }


--- *********************************************************
---     TABLE for the pm253MondwRmonTimerCnt articles
--- *********************************************************

pm253MondwRmonTimerCntTable OBJECT-TYPE
	SYNTAX  SEQUENCE OF Pm253MondwRmonTimerCntEntry
	MAX-ACCESS not-accessible
	STATUS current
	DESCRIPTION
        "
        List of pm253MondwRmonTimerCnt
        Article
        "
	::= { pm253MonClientRmonCounter 160 }


pm253MondwRmonTimerCntEntry OBJECT-TYPE
	SYNTAX Pm253MondwRmonTimerCntEntry
	MAX-ACCESS not-accessible
	STATUS current
	DESCRIPTION
        "
        Row definition for the pm253MondwRmonTimerCnt
        table
        "
	INDEX   { pm253MondwRmonTimerCntIndex }
	::= { pm253MondwRmonTimerCntTable 1 }


Pm253MondwRmonTimerCntEntry ::=
	SEQUENCE {
	pm253MondwRmonTimerCntIndex
		INTEGER,
	pm253MondwRmonTimerCntValuePortn
		Counter64,
	pm253MondwRmonTimerCntErrorPortn
		EkiOnOff,
	pm253MondwRmonTimerCntOverloadPortn
		EkiOnOff
	}


pm253MondwRmonTimerCntIndex OBJECT-TYPE
	SYNTAX  INTEGER(0..128)
	MAX-ACCESS  read-only
	STATUS current
	DESCRIPTION
        "
        Index definition for the pm253MondwRmonTimerCnt
        table
        "
	::= { pm253MondwRmonTimerCntEntry 1 }


pm253MondwRmonTimerCntValuePortn OBJECT-TYPE
	SYNTAX  Counter64
	MAX-ACCESS read-only
	STATUS current
	DESCRIPTION
        "
        RMON Timer On Client Output :This
        is the timing counter dedicated
        to the downstream RMON counters.
        It is incremented every 125 us.
        "
	::= { pm253MondwRmonTimerCntEntry 2 }


pm253MondwRmonTimerCntErrorPortn OBJECT-TYPE
	SYNTAX  EkiOnOff
	MAX-ACCESS read-only
	STATUS current
	DESCRIPTION
        "
        Output RMON Timer Error :This
         OID when set indicates the output
        RMON timer is invalid on client
        port
        "
	::= { pm253MondwRmonTimerCntEntry 3 }


pm253MondwRmonTimerCntOverloadPortn OBJECT-TYPE
	SYNTAX  EkiOnOff
	MAX-ACCESS read-only
	STATUS current
	DESCRIPTION
        "
        Output RMON Timer Overload :This
        OID when set indicates an output
        RMON timer overload on client port
        "
	::= { pm253MondwRmonTimerCntEntry 4 }


--- *********************************************************
---     TABLE for the pm253MondwRmonBitsCnt articles
--- *********************************************************

pm253MondwRmonBitsCntTable OBJECT-TYPE
	SYNTAX  SEQUENCE OF Pm253MondwRmonBitsCntEntry
	MAX-ACCESS not-accessible
	STATUS current
	DESCRIPTION
        "
        List of pm253MondwRmonBitsCnt
         Article
        "
	::= { pm253MonClientRmonCounter 168 }


pm253MondwRmonBitsCntEntry OBJECT-TYPE
	SYNTAX Pm253MondwRmonBitsCntEntry
	MAX-ACCESS not-accessible
	STATUS current
	DESCRIPTION
        "
        Row definition for the pm253MondwRmonBitsCnt
        table
        "
	INDEX   { pm253MondwRmonBitsCntIndex }
	::= { pm253MondwRmonBitsCntTable 1 }


Pm253MondwRmonBitsCntEntry ::=
	SEQUENCE {
	pm253MondwRmonBitsCntIndex
		INTEGER,
	pm253MondwRmonBitsCntValuePortn
		Counter64,
	pm253MondwRmonBitsCntErrorPortn
		EkiOnOff,
	pm253MondwRmonBitsCntOverloadPortn
		EkiOnOff
	}


pm253MondwRmonBitsCntIndex OBJECT-TYPE
	SYNTAX  INTEGER(0..128)
	MAX-ACCESS  read-only
	STATUS current
	DESCRIPTION
        "
        Index definition for the pm253MondwRmonBitsCnt
        table
        "
	::= { pm253MondwRmonBitsCntEntry 1 }


pm253MondwRmonBitsCntValuePortn OBJECT-TYPE
	SYNTAX  Counter64
	MAX-ACCESS read-only
	STATUS current
	DESCRIPTION
        "
        Bits Counter On Client Output
         :This counter is increased each
        time a bit is received on the Output
        client port
        "
	::= { pm253MondwRmonBitsCntEntry 2 }


pm253MondwRmonBitsCntErrorPortn OBJECT-TYPE
	SYNTAX  EkiOnOff
	MAX-ACCESS read-only
	STATUS current
	DESCRIPTION
        "
        Output Bits Counter Error :This
        OID when set indicates the output
        Bits counter value is invalid on
        client port
        "
	::= { pm253MondwRmonBitsCntEntry 3 }


pm253MondwRmonBitsCntOverloadPortn OBJECT-TYPE
	SYNTAX  EkiOnOff
	MAX-ACCESS read-only
	STATUS current
	DESCRIPTION
        "
        Output Bits Counter Overload :This
        OID when set indicates an output
        Bits counter overload on client
        port
        "
	::= { pm253MondwRmonBitsCntEntry 4 }


--- *********************************************************
---     TABLE for the pm253MondwRmonUnicastCnt articles
--- *********************************************************

pm253MondwRmonUnicastCntTable OBJECT-TYPE
	SYNTAX  SEQUENCE OF Pm253MondwRmonUnicastCntEntry
	MAX-ACCESS not-accessible
	STATUS current
	DESCRIPTION
        "
        List of pm253MondwRmonUnicastCnt
        Article
        "
	::= { pm253MonClientRmonCounter 176 }


pm253MondwRmonUnicastCntEntry OBJECT-TYPE
	SYNTAX Pm253MondwRmonUnicastCntEntry
	MAX-ACCESS not-accessible
	STATUS current
	DESCRIPTION
        "
        Row definition for the pm253MondwRmonUnicastCnt
        table
        "
	INDEX   { pm253MondwRmonUnicastCntIndex }
	::= { pm253MondwRmonUnicastCntTable 1 }


Pm253MondwRmonUnicastCntEntry ::=
	SEQUENCE {
	pm253MondwRmonUnicastCntIndex
		INTEGER,
	pm253MondwRmonUnicastCntValuePortn
		Counter64,
	pm253MondwRmonUnicastCntErrorPortn
		EkiOnOff,
	pm253MondwRmonUnicastCntOverloadPortn
		EkiOnOff
	}


pm253MondwRmonUnicastCntIndex OBJECT-TYPE
	SYNTAX  INTEGER(0..128)
	MAX-ACCESS  read-only
	STATUS current
	DESCRIPTION
        "
        Index definition for the pm253MondwRmonUnicastCnt
        table
        "
	::= { pm253MondwRmonUnicastCntEntry 1 }


pm253MondwRmonUnicastCntValuePortn OBJECT-TYPE
	SYNTAX  Counter64
	MAX-ACCESS read-only
	STATUS current
	DESCRIPTION
        "
        Client Output Unicast Packets
         :This counter is increased each
        time a Unicast packet is transmitted
        on client port   <Help>  This counter
        gives the number of Unicast packets
        transmitted on the client output
        port
        "
	::= { pm253MondwRmonUnicastCntEntry 2 }


pm253MondwRmonUnicastCntErrorPortn OBJECT-TYPE
	SYNTAX  EkiOnOff
	MAX-ACCESS read-only
	STATUS current
	DESCRIPTION
        "
        Output Unicast Counter Error :This
        OID when set indicates the output
        RMON timer is invalid on client
        port
        "
	::= { pm253MondwRmonUnicastCntEntry 3 }


pm253MondwRmonUnicastCntOverloadPortn OBJECT-TYPE
	SYNTAX  EkiOnOff
	MAX-ACCESS read-only
	STATUS current
	DESCRIPTION
        "
        Output Unicast Counter Overload
        :This OID when set indicates an
        output RMON timer overload on client
        port
        "
	::= { pm253MondwRmonUnicastCntEntry 4 }


--- *********************************************************
---     TABLE for the pm253MondwRmonNonUnicastCnt articles
--- *********************************************************

pm253MondwRmonNonUnicastCntTable OBJECT-TYPE
	SYNTAX  SEQUENCE OF Pm253MondwRmonNonUnicastCntEntry
	MAX-ACCESS not-accessible
	STATUS current
	DESCRIPTION
        "
        List of pm253MondwRmonNonUnicastCnt
        Article
        "
	::= { pm253MonClientRmonCounter 184 }


pm253MondwRmonNonUnicastCntEntry OBJECT-TYPE
	SYNTAX Pm253MondwRmonNonUnicastCntEntry
	MAX-ACCESS not-accessible
	STATUS current
	DESCRIPTION
        "
        Row definition for the pm253MondwRmonNonUnicastCnt
        table
        "
	INDEX   { pm253MondwRmonNonUnicastCntIndex }
	::= { pm253MondwRmonNonUnicastCntTable 1 }


Pm253MondwRmonNonUnicastCntEntry ::=
	SEQUENCE {
	pm253MondwRmonNonUnicastCntIndex
		INTEGER,
	pm253MondwRmonNonUnicastCntValuePortn
		Counter64,
	pm253MondwRmonNonUnicastCntErrorPortn
		EkiOnOff,
	pm253MondwRmonNonUnicastCntOverloadPortn
		EkiOnOff
	}


pm253MondwRmonNonUnicastCntIndex OBJECT-TYPE
	SYNTAX  INTEGER(0..128)
	MAX-ACCESS  read-only
	STATUS current
	DESCRIPTION
        "
        Index definition for the pm253MondwRmonNonUnicastCnt
        table
        "
	::= { pm253MondwRmonNonUnicastCntEntry 1 }


pm253MondwRmonNonUnicastCntValuePortn OBJECT-TYPE
	SYNTAX  Counter64
	MAX-ACCESS read-only
	STATUS current
	DESCRIPTION
        "
        Client Output Not Unicast Packets
        :This counter is increased each
        time a Non Unicast packet is transmitted
        on client port   <Help>  This counter
        gives the number of Non Unicast
        packets transmitted on the client
        output port
        "
	::= { pm253MondwRmonNonUnicastCntEntry 2 }


pm253MondwRmonNonUnicastCntErrorPortn OBJECT-TYPE
	SYNTAX  EkiOnOff
	MAX-ACCESS read-only
	STATUS current
	DESCRIPTION
        "
        Output Non Unicast Counter Error
        :This OID when set indicates the
        output Bits counter value is invalid
        on client port
        "
	::= { pm253MondwRmonNonUnicastCntEntry 3 }


pm253MondwRmonNonUnicastCntOverloadPortn OBJECT-TYPE
	SYNTAX  EkiOnOff
	MAX-ACCESS read-only
	STATUS current
	DESCRIPTION
        "
        Output Non Unicast Counter Overload
        :This OID when set indicates an
        output Bits counter overload on
        client port
        "
	::= { pm253MondwRmonNonUnicastCntEntry 4 }


pm253MonCountersReset  OBJECT-TYPE
	SYNTAX EkiOnOff
	MAX-ACCESS read-write
	STATUS current
	DESCRIPTION
	"RMON Counters Reset:This OID resets and restarts all the RMON counters"
	::= { pm253MonRmon 359 }

pm253MonCountersStop  OBJECT-TYPE
	SYNTAX EkiOnOff
	MAX-ACCESS read-write
	STATUS current
	DESCRIPTION
	"RMON Counters stop:This OID stops all the RMON counters"
	::= { pm253MonRmon 360 }






--- *****************************************************
--- $$$$$$$$$$$$$$$$$$$$$$$$$$$$$$$$$$$$$$$$$$$$$$$$$$$$$
---     MEASURES
--- $$$$$$$$$$$$$$$$$$$$$$$$$$$$$$$$$$$$$$$$$$$$$$$$$$$$$
--- *****************************************************



--- *********************************************************
---     TABLE for the pm253MesrclientTempMeas articles
--- *********************************************************

pm253MesrclientTempMeasTable OBJECT-TYPE
	SYNTAX  SEQUENCE OF Pm253MesrclientTempMeasEntry
	MAX-ACCESS not-accessible
	STATUS current
	DESCRIPTION
        "
        List of pm253MesrclientTempMeas
        Article
        "
	::= { pm253MesrPort 16 }


pm253MesrclientTempMeasEntry OBJECT-TYPE
	SYNTAX Pm253MesrclientTempMeasEntry
	MAX-ACCESS not-accessible
	STATUS current
	DESCRIPTION
        "
        Row definition for the pm253MesrclientTempMeas
        table
        "
	INDEX   { pm253MesrclientTempMeasIndex }
	::= { pm253MesrclientTempMeasTable 1 }


Pm253MesrclientTempMeasEntry ::=
	SEQUENCE {
	pm253MesrclientTempMeasIndex
		INTEGER,
	pm253MesrclientTempMeasPortn
		INTEGER
	}


pm253MesrclientTempMeasIndex OBJECT-TYPE
	SYNTAX  INTEGER(0..128)
	MAX-ACCESS  read-only
	STATUS current
	DESCRIPTION
        "
        Index definition for the pm253MesrclientTempMeas
        table
        "
	::= { pm253MesrclientTempMeasEntry 1 }


pm253MesrclientTempMeasPortn OBJECT-TYPE
	SYNTAX  INTEGER (0..65535)
	MAX-ACCESS read-only
	STATUS current
	DESCRIPTION
        "
        Client SFP Temperature :This OID
        gives the temperature value of
         the client SFP, read from the
         DDM (Digital Diagnostic Monitoring)
        (Temperature = AV/256) (Unit =
         C)  <Help>  This measure gives
        the temperature of the client transceiver
        "
	::= { pm253MesrclientTempMeasEntry 2 }


--- *********************************************************
---     TABLE for the pm253MesrclientVoltMeas articles
--- *********************************************************

pm253MesrclientVoltMeasTable OBJECT-TYPE
	SYNTAX  SEQUENCE OF Pm253MesrclientVoltMeasEntry
	MAX-ACCESS not-accessible
	STATUS current
	DESCRIPTION
        "
        List of pm253MesrclientVoltMeas
        Article
        "
	::= { pm253MesrPort 24 }


pm253MesrclientVoltMeasEntry OBJECT-TYPE
	SYNTAX Pm253MesrclientVoltMeasEntry
	MAX-ACCESS not-accessible
	STATUS current
	DESCRIPTION
        "
        Row definition for the pm253MesrclientVoltMeas
        table
        "
	INDEX   { pm253MesrclientVoltMeasIndex }
	::= { pm253MesrclientVoltMeasTable 1 }


Pm253MesrclientVoltMeasEntry ::=
	SEQUENCE {
	pm253MesrclientVoltMeasIndex
		INTEGER,
	pm253MesrclientVoltMeasPortn
		INTEGER
	}


pm253MesrclientVoltMeasIndex OBJECT-TYPE
	SYNTAX  INTEGER(0..128)
	MAX-ACCESS  read-only
	STATUS current
	DESCRIPTION
        "
        Index definition for the pm253MesrclientVoltMeas
        table
        "
	::= { pm253MesrclientVoltMeasEntry 1 }


pm253MesrclientVoltMeasPortn OBJECT-TYPE
	SYNTAX  INTEGER (0..65535)
	MAX-ACCESS read-only
	STATUS current
	DESCRIPTION
        "
        Client SFP Power Supply :This
         OID gives the 3V3 voltage value
        of the client SFP, read from the
        DDM (Digital Diagnostic Monitoring)
        (Voltage = AV/10000) (Unit = V)
         <Help>  This measure gives the
        3V3 voltage of the client transceiver
        "
	::= { pm253MesrclientVoltMeasEntry 2 }


--- *********************************************************
---     TABLE for the pm253MesrclientBiasMeas articles
--- *********************************************************

pm253MesrclientBiasMeasTable OBJECT-TYPE
	SYNTAX  SEQUENCE OF Pm253MesrclientBiasMeasEntry
	MAX-ACCESS not-accessible
	STATUS current
	DESCRIPTION
        "
        List of pm253MesrclientBiasMeas
        Article
        "
	::= { pm253MesrPort 32 }


pm253MesrclientBiasMeasEntry OBJECT-TYPE
	SYNTAX Pm253MesrclientBiasMeasEntry
	MAX-ACCESS not-accessible
	STATUS current
	DESCRIPTION
        "
        Row definition for the pm253MesrclientBiasMeas
        table
        "
	INDEX   { pm253MesrclientBiasMeasIndex }
	::= { pm253MesrclientBiasMeasTable 1 }


Pm253MesrclientBiasMeasEntry ::=
	SEQUENCE {
	pm253MesrclientBiasMeasIndex
		INTEGER,
	pm253MesrclientBiasMeasPortn
		INTEGER
	}


pm253MesrclientBiasMeasIndex OBJECT-TYPE
	SYNTAX  INTEGER(0..128)
	MAX-ACCESS  read-only
	STATUS current
	DESCRIPTION
        "
        Index definition for the pm253MesrclientBiasMeas
        table
        "
	::= { pm253MesrclientBiasMeasEntry 1 }


pm253MesrclientBiasMeasPortn OBJECT-TYPE
	SYNTAX  INTEGER (0..65535)
	MAX-ACCESS read-only
	STATUS current
	DESCRIPTION
        "
        Client SFP Laser Bias :This OID
        gives the bias value of the Client
        SFP, read from the DDM (Digital
        Diagnostic Monitoring)  (Bias =
        AV/500) (Unit = mA)  <Help>  This
        measure gives the bias of the client
        transceiver
        "
	::= { pm253MesrclientBiasMeasEntry 2 }


--- *********************************************************
---     TABLE for the pm253MesrclientTxpwrMeas articles
--- *********************************************************

pm253MesrclientTxpwrMeasTable OBJECT-TYPE
	SYNTAX  SEQUENCE OF Pm253MesrclientTxpwrMeasEntry
	MAX-ACCESS not-accessible
	STATUS current
	DESCRIPTION
        "
        List of pm253MesrclientTxpwrMeas
        Article
        "
	::= { pm253MesrPort 40 }


pm253MesrclientTxpwrMeasEntry OBJECT-TYPE
	SYNTAX Pm253MesrclientTxpwrMeasEntry
	MAX-ACCESS not-accessible
	STATUS current
	DESCRIPTION
        "
        Row definition for the pm253MesrclientTxpwrMeas
        table
        "
	INDEX   { pm253MesrclientTxpwrMeasIndex }
	::= { pm253MesrclientTxpwrMeasTable 1 }


Pm253MesrclientTxpwrMeasEntry ::=
	SEQUENCE {
	pm253MesrclientTxpwrMeasIndex
		INTEGER,
	pm253MesrclientTxpwrMeasPortn
		INTEGER
	}


pm253MesrclientTxpwrMeasIndex OBJECT-TYPE
	SYNTAX  INTEGER(0..128)
	MAX-ACCESS  read-only
	STATUS current
	DESCRIPTION
        "
        Index definition for the pm253MesrclientTxpwrMeas
        table
        "
	::= { pm253MesrclientTxpwrMeasEntry 1 }


pm253MesrclientTxpwrMeasPortn OBJECT-TYPE
	SYNTAX  INTEGER (0..65535)
	MAX-ACCESS read-only
	STATUS current
	DESCRIPTION
        "
        Client SFP Tx Power :This OID
         gives the transmit power value
        of the Client SFP, read from the
        DDM (Digital Diagnostic Monitoring)
        (Power = 10*log(AV)-40) (Unit =
        dBm)  <Help>  This measure gives
        the Tx optical power of the client
        transceiver
        "
	::= { pm253MesrclientTxpwrMeasEntry 2 }


--- *********************************************************
---     TABLE for the pm253MesrclientRxpwrMeas articles
--- *********************************************************

pm253MesrclientRxpwrMeasTable OBJECT-TYPE
	SYNTAX  SEQUENCE OF Pm253MesrclientRxpwrMeasEntry
	MAX-ACCESS not-accessible
	STATUS current
	DESCRIPTION
        "
        List of pm253MesrclientRxpwrMeas
        Article
        "
	::= { pm253MesrPort 48 }


pm253MesrclientRxpwrMeasEntry OBJECT-TYPE
	SYNTAX Pm253MesrclientRxpwrMeasEntry
	MAX-ACCESS not-accessible
	STATUS current
	DESCRIPTION
        "
        Row definition for the pm253MesrclientRxpwrMeas
        table
        "
	INDEX   { pm253MesrclientRxpwrMeasIndex }
	::= { pm253MesrclientRxpwrMeasTable 1 }


Pm253MesrclientRxpwrMeasEntry ::=
	SEQUENCE {
	pm253MesrclientRxpwrMeasIndex
		INTEGER,
	pm253MesrclientRxpwrMeasPortn
		INTEGER
	}


pm253MesrclientRxpwrMeasIndex OBJECT-TYPE
	SYNTAX  INTEGER(0..128)
	MAX-ACCESS  read-only
	STATUS current
	DESCRIPTION
        "
        Index definition for the pm253MesrclientRxpwrMeas
        table
        "
	::= { pm253MesrclientRxpwrMeasEntry 1 }


pm253MesrclientRxpwrMeasPortn OBJECT-TYPE
	SYNTAX  INTEGER (0..65535)
	MAX-ACCESS read-only
	STATUS current
	DESCRIPTION
        "
        Client SFP Rx Power :This OID
         gives the receive power value
         of the Client SFP, read in the
        DDM (Digital Diagnostic Monitoring)
        (Power = 10*log(AV)-40) (Unit =
        dBm)  <Help>  This measure gives
        the Rx optical power of the client
        transceiver
        "
	::= { pm253MesrclientRxpwrMeasEntry 2 }


--- *********************************************************
---     TABLE for the pm253MesrlineTempMeas articles
--- *********************************************************

pm253MesrlineTempMeasTable OBJECT-TYPE
	SYNTAX  SEQUENCE OF Pm253MesrlineTempMeasEntry
	MAX-ACCESS not-accessible
	STATUS current
	DESCRIPTION
        "
        List of pm253MesrlineTempMeas
         Article
        "
	::= { pm253MesrLine 160 }


pm253MesrlineTempMeasEntry OBJECT-TYPE
	SYNTAX Pm253MesrlineTempMeasEntry
	MAX-ACCESS not-accessible
	STATUS current
	DESCRIPTION
        "
        Row definition for the pm253MesrlineTempMeas
        table
        "
	INDEX   { pm253MesrlineTempMeasIndex }
	::= { pm253MesrlineTempMeasTable 1 }


Pm253MesrlineTempMeasEntry ::=
	SEQUENCE {
	pm253MesrlineTempMeasIndex
		INTEGER,
	pm253MesrlineTempMeasPortn
		INTEGER
	}


pm253MesrlineTempMeasIndex OBJECT-TYPE
	SYNTAX  INTEGER(0..128)
	MAX-ACCESS  read-only
	STATUS current
	DESCRIPTION
        "
        Index definition for the pm253MesrlineTempMeas
        table
        "
	::= { pm253MesrlineTempMeasEntry 1 }


pm253MesrlineTempMeasPortn OBJECT-TYPE
	SYNTAX  INTEGER (0..65535)
	MAX-ACCESS read-only
	STATUS current
	DESCRIPTION
        "
        Line SFP Temperature :This OID
        gives the temperature value of
         the Line SFP, read from the DDM
        (Digital Diagnostic Monitoring)

(Temperature = AV/256) (Unit =
        C)  <Help>  This measure gives
         the temperature of the line transceiver
        "
	::= { pm253MesrlineTempMeasEntry 2 }


--- *********************************************************
---     TABLE for the pm253MesrlineVoltMeas articles
--- *********************************************************

pm253MesrlineVoltMeasTable OBJECT-TYPE
	SYNTAX  SEQUENCE OF Pm253MesrlineVoltMeasEntry
	MAX-ACCESS not-accessible
	STATUS current
	DESCRIPTION
        "
        List of pm253MesrlineVoltMeas
         Article
        "
	::= { pm253MesrLine 161 }


pm253MesrlineVoltMeasEntry OBJECT-TYPE
	SYNTAX Pm253MesrlineVoltMeasEntry
	MAX-ACCESS not-accessible
	STATUS current
	DESCRIPTION
        "
        Row definition for the pm253MesrlineVoltMeas
        table
        "
	INDEX   { pm253MesrlineVoltMeasIndex }
	::= { pm253MesrlineVoltMeasTable 1 }


Pm253MesrlineVoltMeasEntry ::=
	SEQUENCE {
	pm253MesrlineVoltMeasIndex
		INTEGER,
	pm253MesrlineVoltMeasPortn
		INTEGER
	}


pm253MesrlineVoltMeasIndex OBJECT-TYPE
	SYNTAX  INTEGER(0..128)
	MAX-ACCESS  read-only
	STATUS current
	DESCRIPTION
        "
        Index definition for the pm253MesrlineVoltMeas
        table
        "
	::= { pm253MesrlineVoltMeasEntry 1 }


pm253MesrlineVoltMeasPortn OBJECT-TYPE
	SYNTAX  INTEGER (0..65535)
	MAX-ACCESS read-only
	STATUS current
	DESCRIPTION
        "
        Line SFP Power Supply :This OID
        gives the 3V3 voltage value of
         the Line SFP, read from the DDM
        (Digital Diagnostic Monitoring)
        (Voltage = AV/10000) (Unit = V)
         <Help>  This measure gives the
        3V3 voltage of the line transceiver
        "
	::= { pm253MesrlineVoltMeasEntry 2 }


--- *********************************************************
---     TABLE for the pm253MesrlineBiasMeas articles
--- *********************************************************

pm253MesrlineBiasMeasTable OBJECT-TYPE
	SYNTAX  SEQUENCE OF Pm253MesrlineBiasMeasEntry
	MAX-ACCESS not-accessible
	STATUS current
	DESCRIPTION
        "
        List of pm253MesrlineBiasMeas
         Article
        "
	::= { pm253MesrLine 162 }


pm253MesrlineBiasMeasEntry OBJECT-TYPE
	SYNTAX Pm253MesrlineBiasMeasEntry
	MAX-ACCESS not-accessible
	STATUS current
	DESCRIPTION
        "
        Row definition for the pm253MesrlineBiasMeas
        table
        "
	INDEX   { pm253MesrlineBiasMeasIndex }
	::= { pm253MesrlineBiasMeasTable 1 }


Pm253MesrlineBiasMeasEntry ::=
	SEQUENCE {
	pm253MesrlineBiasMeasIndex
		INTEGER,
	pm253MesrlineBiasMeasPortn
		INTEGER
	}


pm253MesrlineBiasMeasIndex OBJECT-TYPE
	SYNTAX  INTEGER(0..128)
	MAX-ACCESS  read-only
	STATUS current
	DESCRIPTION
        "
        Index definition for the pm253MesrlineBiasMeas
        table
        "
	::= { pm253MesrlineBiasMeasEntry 1 }


pm253MesrlineBiasMeasPortn OBJECT-TYPE
	SYNTAX  INTEGER (0..65535)
	MAX-ACCESS read-only
	STATUS current
	DESCRIPTION
        "
        Line SFP Laser Bias :This OID
         gives the bias value of the Line
        SFP, read from the DDM (Digital
        Diagnostic Monitoring) (Bias =
         AV/500)  (Unit = mA)  <Help>
         This measure gives the bias of
        the line transceiver
        "
	::= { pm253MesrlineBiasMeasEntry 2 }


--- *********************************************************
---     TABLE for the pm253MesrlineTxpwrMeas articles
--- *********************************************************

pm253MesrlineTxpwrMeasTable OBJECT-TYPE
	SYNTAX  SEQUENCE OF Pm253MesrlineTxpwrMeasEntry
	MAX-ACCESS not-accessible
	STATUS current
	DESCRIPTION
        "
        List of pm253MesrlineTxpwrMeas
        Article
        "
	::= { pm253MesrLine 163 }


pm253MesrlineTxpwrMeasEntry OBJECT-TYPE
	SYNTAX Pm253MesrlineTxpwrMeasEntry
	MAX-ACCESS not-accessible
	STATUS current
	DESCRIPTION
        "
        Row definition for the pm253MesrlineTxpwrMeas
        table
        "
	INDEX   { pm253MesrlineTxpwrMeasIndex }
	::= { pm253MesrlineTxpwrMeasTable 1 }


Pm253MesrlineTxpwrMeasEntry ::=
	SEQUENCE {
	pm253MesrlineTxpwrMeasIndex
		INTEGER,
	pm253MesrlineTxpwrMeasPortn
		INTEGER
	}


pm253MesrlineTxpwrMeasIndex OBJECT-TYPE
	SYNTAX  INTEGER(0..128)
	MAX-ACCESS  read-only
	STATUS current
	DESCRIPTION
        "
        Index definition for the pm253MesrlineTxpwrMeas
        table
        "
	::= { pm253MesrlineTxpwrMeasEntry 1 }


pm253MesrlineTxpwrMeasPortn OBJECT-TYPE
	SYNTAX  INTEGER (0..65535)
	MAX-ACCESS read-only
	STATUS current
	DESCRIPTION
        "
        Line SFP Tx Power :This OID gives
        the transmit power value of the
        Line SFP, read from the DDM (Digital
        Diagnostic Monitoring) (Power =
        10*log(AV)-40) (Unit = dBm)  <Help>
         This measure gives the Tx optical
        power of the line transceiver
        "
	::= { pm253MesrlineTxpwrMeasEntry 2 }


--- *********************************************************
---     TABLE for the pm253MesrlineRxpwrMeas articles
--- *********************************************************

pm253MesrlineRxpwrMeasTable OBJECT-TYPE
	SYNTAX  SEQUENCE OF Pm253MesrlineRxpwrMeasEntry
	MAX-ACCESS not-accessible
	STATUS current
	DESCRIPTION
        "
        List of pm253MesrlineRxpwrMeas
        Article
        "
	::= { pm253MesrLine 164 }


pm253MesrlineRxpwrMeasEntry OBJECT-TYPE
	SYNTAX Pm253MesrlineRxpwrMeasEntry
	MAX-ACCESS not-accessible
	STATUS current
	DESCRIPTION
        "
        Row definition for the pm253MesrlineRxpwrMeas
        table
        "
	INDEX   { pm253MesrlineRxpwrMeasIndex }
	::= { pm253MesrlineRxpwrMeasTable 1 }


Pm253MesrlineRxpwrMeasEntry ::=
	SEQUENCE {
	pm253MesrlineRxpwrMeasIndex
		INTEGER,
	pm253MesrlineRxpwrMeasPortn
		INTEGER
	}


pm253MesrlineRxpwrMeasIndex OBJECT-TYPE
	SYNTAX  INTEGER(0..128)
	MAX-ACCESS  read-only
	STATUS current
	DESCRIPTION
        "
        Index definition for the pm253MesrlineRxpwrMeas
        table
        "
	::= { pm253MesrlineRxpwrMeasEntry 1 }


pm253MesrlineRxpwrMeasPortn OBJECT-TYPE
	SYNTAX  INTEGER (0..65535)
	MAX-ACCESS read-only
	STATUS current
	DESCRIPTION
        "
        Line SFP Rx Power :This OID gives
        the receive power value of the
         Line SFP, read in the DDM (Digital
        Diagnostic Monitoring) (Power =
        10*log(AV)-40) (Unit = dBm)  <Help>
         This measure gives the Rx optical
        power of the line transceiver
        "
	::= { pm253MesrlineRxpwrMeasEntry 2 }







--- *****************************************************
--- $$$$$$$$$$$$$$$$$$$$$$$$$$$$$$$$$$$$$$$$$$$$$$$$$$$$$
---     PERFORMANCE
--- $$$$$$$$$$$$$$$$$$$$$$$$$$$$$$$$$$$$$$$$$$$$$$$$$$$$$
--- *****************************************************



--- *****************************************************
---     Leaf of the telecomClientCurrent15Stat
--- *****************************************************
--- *********************************************************
---     TABLE for the pm253PerfTelecomClientCurrent15Stat articles
--- *********************************************************

pm253PerfTelecomClientCurrent15StatTable OBJECT-TYPE
	SYNTAX  SEQUENCE OF Pm253PerfTelecomClientCurrent15StatEntry
	MAX-ACCESS not-accessible
	STATUS current
	DESCRIPTION
        "
        List of pm253PerfTelecomClientCurrent15Stat
        Article
        "
	::= { pm253MonClient 16 }


pm253PerfTelecomClientCurrent15StatEntry OBJECT-TYPE
	SYNTAX Pm253PerfTelecomClientCurrent15StatEntry
	MAX-ACCESS not-accessible
	STATUS current
	DESCRIPTION
        "
        Row definition for the pm253PerfTelecomClientCurrent15Stat
        table
        "
	INDEX   { pm253PerfTelecomClientCurrent15StatIndex }
	::= { pm253PerfTelecomClientCurrent15StatTable 1 }


Pm253PerfTelecomClientCurrent15StatEntry ::=
	SEQUENCE {
	pm253PerfTelecomClientCurrent15StatIndex
		INTEGER,
	pm253PerfTelecomClientCurrent15StatInvCvPortn
		EkiOnOff,
	pm253PerfTelecomClientCurrent15StatCvValuePortn
		Unsigned32,
	pm253PerfTelecomClientCurrent15StatInvEsPortn
		EkiOnOff,
	pm253PerfTelecomClientCurrent15StatEsValuePortn
		Unsigned32,
	pm253PerfTelecomClientCurrent15StatInvSesPortn
		EkiOnOff,
	pm253PerfTelecomClientCurrent15StatSesValuePortn
		Unsigned32,
	pm253PerfTelecomClientCurrent15StatInvSefsPortn
		EkiOnOff,
	pm253PerfTelecomClientCurrent15StatSefsValuePortn
		Unsigned32,
	pm253PerfTelecomClientCurrent15StatInvUasPortn
		EkiOnOff,
	pm253PerfTelecomClientCurrent15StatUasValuePortn
		Unsigned32
	}


pm253PerfTelecomClientCurrent15StatIndex OBJECT-TYPE
	SYNTAX  INTEGER(0..128)
	MAX-ACCESS  read-only
	STATUS current
	DESCRIPTION
        "
        Index definition for the pm253PerfTelecomClientCurrent15Stat
        table
        "
	::= { pm253PerfTelecomClientCurrent15StatEntry 1 }


pm253PerfTelecomClientCurrent15StatInvCvPortn OBJECT-TYPE
	SYNTAX  EkiOnOff
	MAX-ACCESS read-only
	STATUS current
	DESCRIPTION
        "
        Current 15-min CV counter inv.
        :This OID indicates that the current
        15-min Coding Violation counter
        is invalid
        "
	::= { pm253PerfTelecomClientCurrent15StatEntry 2 }


pm253PerfTelecomClientCurrent15StatCvValuePortn OBJECT-TYPE
	SYNTAX  Unsigned32
	MAX-ACCESS read-only
	STATUS current
	DESCRIPTION
        "
        Current 15-min CV counter :This
        OID gives the current 15-min Coding
        Violation counter value
        "
	::= { pm253PerfTelecomClientCurrent15StatEntry 3 }


pm253PerfTelecomClientCurrent15StatInvEsPortn OBJECT-TYPE
	SYNTAX  EkiOnOff
	MAX-ACCESS read-only
	STATUS current
	DESCRIPTION
        "
        Current 15-min ES counter inv.
        :This OID indicates that the current
        15-min Errored Second counter is
        invalid
        "
	::= { pm253PerfTelecomClientCurrent15StatEntry 4 }


pm253PerfTelecomClientCurrent15StatEsValuePortn OBJECT-TYPE
	SYNTAX  Unsigned32
	MAX-ACCESS read-only
	STATUS current
	DESCRIPTION
        "
        Current 15-min ES counter :This
        OID gives the current 15-min Errored
        Second counter value
        "
	::= { pm253PerfTelecomClientCurrent15StatEntry 5 }


pm253PerfTelecomClientCurrent15StatInvSesPortn OBJECT-TYPE
	SYNTAX  EkiOnOff
	MAX-ACCESS read-only
	STATUS current
	DESCRIPTION
        "
        Current 15-min SES counter inv.
        :This OID indicates that the current
        15-min severely Errored Second
         counter is invalid
        "
	::= { pm253PerfTelecomClientCurrent15StatEntry 6 }


pm253PerfTelecomClientCurrent15StatSesValuePortn OBJECT-TYPE
	SYNTAX  Unsigned32
	MAX-ACCESS read-only
	STATUS current
	DESCRIPTION
        "
        Current 15-min SES counter :This
        OID gives the current 15-min severely
        Errored Second counter value
        "
	::= { pm253PerfTelecomClientCurrent15StatEntry 7 }


pm253PerfTelecomClientCurrent15StatInvSefsPortn OBJECT-TYPE
	SYNTAX  EkiOnOff
	MAX-ACCESS read-only
	STATUS current
	DESCRIPTION
        "
        Current 15-min SEFS counter inv.
        :This OID indicates that the current
        15-min severely Errored Framing
        Second counter is invalid
        "
	::= { pm253PerfTelecomClientCurrent15StatEntry 8 }


pm253PerfTelecomClientCurrent15StatSefsValuePortn OBJECT-TYPE
	SYNTAX  Unsigned32
	MAX-ACCESS read-only
	STATUS current
	DESCRIPTION
        "
        Current 15-min SEFS counter :This
        OID gives the current 15-min severely
        Errored Framing Second counter
         value
        "
	::= { pm253PerfTelecomClientCurrent15StatEntry 9 }


pm253PerfTelecomClientCurrent15StatInvUasPortn OBJECT-TYPE
	SYNTAX  EkiOnOff
	MAX-ACCESS read-only
	STATUS current
	DESCRIPTION
        "
        Current 15-min UAS counter inv.
        :This OID indicates that the current
        15-min UnAvailable Second counter
        is invalid
        "
	::= { pm253PerfTelecomClientCurrent15StatEntry 10 }


pm253PerfTelecomClientCurrent15StatUasValuePortn OBJECT-TYPE
	SYNTAX  Unsigned32
	MAX-ACCESS read-only
	STATUS current
	DESCRIPTION
        "
        Current 15-min UAS counter :This
        OID gives the current 15-min UnAvailable
        Second counter value
        "
	::= { pm253PerfTelecomClientCurrent15StatEntry 11 }


--- *****************************************************
---     Leaf of the telecomClientPast15Stat
--- *****************************************************
--- *********************************************************
---     TABLE for the pm253PerfTelecomClientPast15StatHistory articles
--- *********************************************************

pm253PerfTelecomClientPast15StatHistoryPort1Table OBJECT-TYPE
	SYNTAX  SEQUENCE OF Pm253PerfTelecomClientPast15StatHistoryPort1Entry
	MAX-ACCESS not-accessible
	STATUS current
	DESCRIPTION
        "
        List of pm253PerfTelecomClientPast15StatHistory
        Article
        "
	::= { pm253MonClient 24 }


pm253PerfTelecomClientPast15StatHistoryPort1Entry OBJECT-TYPE
	SYNTAX Pm253PerfTelecomClientPast15StatHistoryPort1Entry
	MAX-ACCESS not-accessible
	STATUS current
	DESCRIPTION
        "
        Row definition for the pm253PerfTelecomClientPast15StatHistory
        table
        "
	INDEX   { pm253PerfTelecomClientPast15StatHistoryPort1Index }
	::= { pm253PerfTelecomClientPast15StatHistoryPort1Table 1 }


Pm253PerfTelecomClientPast15StatHistoryPort1Entry ::=
	SEQUENCE {
	pm253PerfTelecomClientPast15StatHistoryPort1Index
		INTEGER,
	pm253PerfTelecomClientPast15StatHistoryInvCvPort1
		EkiOnOff,
	pm253PerfTelecomClientPast15StatHistoryCvValuePort1
		Unsigned32,
	pm253PerfTelecomClientPast15StatHistoryInvEsPort1
		EkiOnOff,
	pm253PerfTelecomClientPast15StatHistoryEsValuePort1
		Unsigned32,
	pm253PerfTelecomClientPast15StatHistoryInvSesPort1
		EkiOnOff,
	pm253PerfTelecomClientPast15StatHistorySesValuePort1
		Unsigned32,
	pm253PerfTelecomClientPast15StatHistoryInvSefsPort1
		EkiOnOff,
	pm253PerfTelecomClientPast15StatHistorySefsValuePort1
		Unsigned32,
	pm253PerfTelecomClientPast15StatHistoryInvUasPort1
		EkiOnOff,
	pm253PerfTelecomClientPast15StatHistoryUasValuePort1
		Unsigned32
	}


pm253PerfTelecomClientPast15StatHistoryPort1Index OBJECT-TYPE
	SYNTAX  INTEGER(0..128)
	MAX-ACCESS  read-only
	STATUS current
	DESCRIPTION
        "
        Index definition for the pm253PerfTelecomClientPast15StatHistory
        table
        "
	::= { pm253PerfTelecomClientPast15StatHistoryPort1Entry 1 }


pm253PerfTelecomClientPast15StatHistoryInvCvPort1 OBJECT-TYPE
	SYNTAX  EkiOnOff
	MAX-ACCESS read-only
	STATUS current
	DESCRIPTION
        "
        Previous 15-min CV counter inv.
        :This OID indicates that the previous
        15-min Coding Violation counter
        is invalid
        "
	::= { pm253PerfTelecomClientPast15StatHistoryPort1Entry 2 }


pm253PerfTelecomClientPast15StatHistoryCvValuePort1 OBJECT-TYPE
	SYNTAX  Unsigned32
	MAX-ACCESS read-only
	STATUS current
	DESCRIPTION
        "
        Previous 15-min CV counter :This
        OID gives the previous 15-min Coding
        Violation counter value
        "
	::= { pm253PerfTelecomClientPast15StatHistoryPort1Entry 3 }


pm253PerfTelecomClientPast15StatHistoryInvEsPort1 OBJECT-TYPE
	SYNTAX  EkiOnOff
	MAX-ACCESS read-only
	STATUS current
	DESCRIPTION
        "
        Previous 15-min ES counter inv.
        :This OID indicates that the previous
        15-min Errored Second counter is
        invalid
        "
	::= { pm253PerfTelecomClientPast15StatHistoryPort1Entry 4 }


pm253PerfTelecomClientPast15StatHistoryEsValuePort1 OBJECT-TYPE
	SYNTAX  Unsigned32
	MAX-ACCESS read-only
	STATUS current
	DESCRIPTION
        "
        Previous 15-min ES counter :This
        OID gives the previous 15-min Errored
        Second counter value
        "
	::= { pm253PerfTelecomClientPast15StatHistoryPort1Entry 5 }


pm253PerfTelecomClientPast15StatHistoryInvSesPort1 OBJECT-TYPE
	SYNTAX  EkiOnOff
	MAX-ACCESS read-only
	STATUS current
	DESCRIPTION
        "
        Previous 15-min SES counter inv.
        :This OID indicates that the previous
        15-min severely Errored Second
         counter is invalid
        "
	::= { pm253PerfTelecomClientPast15StatHistoryPort1Entry 6 }


pm253PerfTelecomClientPast15StatHistorySesValuePort1 OBJECT-TYPE
	SYNTAX  Unsigned32
	MAX-ACCESS read-only
	STATUS current
	DESCRIPTION
        "
        Previous 15-min SES counter :This
        OID gives the previous 15-min severely
        Errored Second counter value
        "
	::= { pm253PerfTelecomClientPast15StatHistoryPort1Entry 7 }


pm253PerfTelecomClientPast15StatHistoryInvSefsPort1 OBJECT-TYPE
	SYNTAX  EkiOnOff
	MAX-ACCESS read-only
	STATUS current
	DESCRIPTION
        "
        Previous 15-min SEFS counter inv.
        :This OID indicates that the previous
        15-min severely Errored Framing
        Second counter is invalid
        "
	::= { pm253PerfTelecomClientPast15StatHistoryPort1Entry 8 }


pm253PerfTelecomClientPast15StatHistorySefsValuePort1 OBJECT-TYPE
	SYNTAX  Unsigned32
	MAX-ACCESS read-only
	STATUS current
	DESCRIPTION
        "
        Previous 15-min SEFS counter :This
        OID gives the previous 15-min severely
        Errored Framing Second counter
         value
        "
	::= { pm253PerfTelecomClientPast15StatHistoryPort1Entry 9 }


pm253PerfTelecomClientPast15StatHistoryInvUasPort1 OBJECT-TYPE
	SYNTAX  EkiOnOff
	MAX-ACCESS read-only
	STATUS current
	DESCRIPTION
        "
        Previous 15-min UAS counter inv.
        :This OID indicates that the previous
        15-min UnAvailable Second counter
        is invalid
        "
	::= { pm253PerfTelecomClientPast15StatHistoryPort1Entry 10 }


pm253PerfTelecomClientPast15StatHistoryUasValuePort1 OBJECT-TYPE
	SYNTAX  Unsigned32
	MAX-ACCESS read-only
	STATUS current
	DESCRIPTION
        "
        Previous 15-min UAS counter :This
        OID gives the previous 15-min UnAvailable
        Second counter value
        "
	::= { pm253PerfTelecomClientPast15StatHistoryPort1Entry 11 }


--- *********************************************************
---     TABLE for the pm253PerfTelecomClientPast15StatHistory articles
--- *********************************************************

pm253PerfTelecomClientPast15StatHistoryPort2Table OBJECT-TYPE
	SYNTAX  SEQUENCE OF Pm253PerfTelecomClientPast15StatHistoryPort2Entry
	MAX-ACCESS not-accessible
	STATUS current
	DESCRIPTION
        "
        List of pm253PerfTelecomClientPast15StatHistory
        Article
        "
	::= { pm253MonClient 25 }


pm253PerfTelecomClientPast15StatHistoryPort2Entry OBJECT-TYPE
	SYNTAX Pm253PerfTelecomClientPast15StatHistoryPort2Entry
	MAX-ACCESS not-accessible
	STATUS current
	DESCRIPTION
        "
        Row definition for the pm253PerfTelecomClientPast15StatHistory
        table
        "
	INDEX   { pm253PerfTelecomClientPast15StatHistoryPort2Index }
	::= { pm253PerfTelecomClientPast15StatHistoryPort2Table 1 }


Pm253PerfTelecomClientPast15StatHistoryPort2Entry ::=
	SEQUENCE {
	pm253PerfTelecomClientPast15StatHistoryPort2Index
		INTEGER,
	pm253PerfTelecomClientPast15StatHistoryInvCvPort2
		EkiOnOff,
	pm253PerfTelecomClientPast15StatHistoryCvValuePort2
		Unsigned32,
	pm253PerfTelecomClientPast15StatHistoryInvEsPort2
		EkiOnOff,
	pm253PerfTelecomClientPast15StatHistoryEsValuePort2
		Unsigned32,
	pm253PerfTelecomClientPast15StatHistoryInvSesPort2
		EkiOnOff,
	pm253PerfTelecomClientPast15StatHistorySesValuePort2
		Unsigned32,
	pm253PerfTelecomClientPast15StatHistoryInvSefsPort2
		EkiOnOff,
	pm253PerfTelecomClientPast15StatHistorySefsValuePort2
		Unsigned32,
	pm253PerfTelecomClientPast15StatHistoryInvUasPort2
		EkiOnOff,
	pm253PerfTelecomClientPast15StatHistoryUasValuePort2
		Unsigned32
	}


pm253PerfTelecomClientPast15StatHistoryPort2Index OBJECT-TYPE
	SYNTAX  INTEGER(0..128)
	MAX-ACCESS  read-only
	STATUS current
	DESCRIPTION
        "
        Index definition for the pm253PerfTelecomClientPast15StatHistory
        table
        "
	::= { pm253PerfTelecomClientPast15StatHistoryPort2Entry 1 }


pm253PerfTelecomClientPast15StatHistoryInvCvPort2 OBJECT-TYPE
	SYNTAX  EkiOnOff
	MAX-ACCESS read-only
	STATUS current
	DESCRIPTION
        "
        Previous 15-min CV counter inv.
        :This OID indicates that the previous
        15-min Coding Violation counter
        is invalid
        "
	::= { pm253PerfTelecomClientPast15StatHistoryPort2Entry 2 }


pm253PerfTelecomClientPast15StatHistoryCvValuePort2 OBJECT-TYPE
	SYNTAX  Unsigned32
	MAX-ACCESS read-only
	STATUS current
	DESCRIPTION
        "
        Previous 15-min CV counter :This
        OID gives the previous 15-min Coding
        Violation counter value
        "
	::= { pm253PerfTelecomClientPast15StatHistoryPort2Entry 3 }


pm253PerfTelecomClientPast15StatHistoryInvEsPort2 OBJECT-TYPE
	SYNTAX  EkiOnOff
	MAX-ACCESS read-only
	STATUS current
	DESCRIPTION
        "
        Previous 15-min ES counter inv.
        :This OID indicates that the previous
        15-min Errored Second counter is
        invalid
        "
	::= { pm253PerfTelecomClientPast15StatHistoryPort2Entry 4 }


pm253PerfTelecomClientPast15StatHistoryEsValuePort2 OBJECT-TYPE
	SYNTAX  Unsigned32
	MAX-ACCESS read-only
	STATUS current
	DESCRIPTION
        "
        Previous 15-min ES counter :This
        OID gives the previous 15-min Errored
        Second counter value
        "
	::= { pm253PerfTelecomClientPast15StatHistoryPort2Entry 5 }


pm253PerfTelecomClientPast15StatHistoryInvSesPort2 OBJECT-TYPE
	SYNTAX  EkiOnOff
	MAX-ACCESS read-only
	STATUS current
	DESCRIPTION
        "
        Previous 15-min SES counter inv.
        :This OID indicates that the previous
        15-min severely Errored Second
         counter is invalid
        "
	::= { pm253PerfTelecomClientPast15StatHistoryPort2Entry 6 }


pm253PerfTelecomClientPast15StatHistorySesValuePort2 OBJECT-TYPE
	SYNTAX  Unsigned32
	MAX-ACCESS read-only
	STATUS current
	DESCRIPTION
        "
        Previous 15-min SES counter :This
        OID gives the previous 15-min severely
        Errored Second counter value
        "
	::= { pm253PerfTelecomClientPast15StatHistoryPort2Entry 7 }


pm253PerfTelecomClientPast15StatHistoryInvSefsPort2 OBJECT-TYPE
	SYNTAX  EkiOnOff
	MAX-ACCESS read-only
	STATUS current
	DESCRIPTION
        "
        Previous 15-min SEFS counter inv.
        :This OID indicates that the previous
        15-min severely Errored Framing
        Second counter is invalid
        "
	::= { pm253PerfTelecomClientPast15StatHistoryPort2Entry 8 }


pm253PerfTelecomClientPast15StatHistorySefsValuePort2 OBJECT-TYPE
	SYNTAX  Unsigned32
	MAX-ACCESS read-only
	STATUS current
	DESCRIPTION
        "
        Previous 15-min SEFS counter :This
        OID gives the previous 15-min severely
        Errored Framing Second counter
         value
        "
	::= { pm253PerfTelecomClientPast15StatHistoryPort2Entry 9 }


pm253PerfTelecomClientPast15StatHistoryInvUasPort2 OBJECT-TYPE
	SYNTAX  EkiOnOff
	MAX-ACCESS read-only
	STATUS current
	DESCRIPTION
        "
        Previous 15-min UAS counter inv.
        :This OID indicates that the previous
        15-min UnAvailable Second counter
        is invalid
        "
	::= { pm253PerfTelecomClientPast15StatHistoryPort2Entry 10 }


pm253PerfTelecomClientPast15StatHistoryUasValuePort2 OBJECT-TYPE
	SYNTAX  Unsigned32
	MAX-ACCESS read-only
	STATUS current
	DESCRIPTION
        "
        Previous 15-min UAS counter :This
        OID gives the previous 15-min UnAvailable
        Second counter value
        "
	::= { pm253PerfTelecomClientPast15StatHistoryPort2Entry 11 }


--- *********************************************************
---     TABLE for the pm253PerfTelecomClientPast15StatHistory articles
--- *********************************************************

pm253PerfTelecomClientPast15StatHistoryPort3Table OBJECT-TYPE
	SYNTAX  SEQUENCE OF Pm253PerfTelecomClientPast15StatHistoryPort3Entry
	MAX-ACCESS not-accessible
	STATUS current
	DESCRIPTION
        "
        List of pm253PerfTelecomClientPast15StatHistory
        Article
        "
	::= { pm253MonClient 26 }


pm253PerfTelecomClientPast15StatHistoryPort3Entry OBJECT-TYPE
	SYNTAX Pm253PerfTelecomClientPast15StatHistoryPort3Entry
	MAX-ACCESS not-accessible
	STATUS current
	DESCRIPTION
        "
        Row definition for the pm253PerfTelecomClientPast15StatHistory
        table
        "
	INDEX   { pm253PerfTelecomClientPast15StatHistoryPort3Index }
	::= { pm253PerfTelecomClientPast15StatHistoryPort3Table 1 }


Pm253PerfTelecomClientPast15StatHistoryPort3Entry ::=
	SEQUENCE {
	pm253PerfTelecomClientPast15StatHistoryPort3Index
		INTEGER,
	pm253PerfTelecomClientPast15StatHistoryInvCvPort3
		EkiOnOff,
	pm253PerfTelecomClientPast15StatHistoryCvValuePort3
		Unsigned32,
	pm253PerfTelecomClientPast15StatHistoryInvEsPort3
		EkiOnOff,
	pm253PerfTelecomClientPast15StatHistoryEsValuePort3
		Unsigned32,
	pm253PerfTelecomClientPast15StatHistoryInvSesPort3
		EkiOnOff,
	pm253PerfTelecomClientPast15StatHistorySesValuePort3
		Unsigned32,
	pm253PerfTelecomClientPast15StatHistoryInvSefsPort3
		EkiOnOff,
	pm253PerfTelecomClientPast15StatHistorySefsValuePort3
		Unsigned32,
	pm253PerfTelecomClientPast15StatHistoryInvUasPort3
		EkiOnOff,
	pm253PerfTelecomClientPast15StatHistoryUasValuePort3
		Unsigned32
	}


pm253PerfTelecomClientPast15StatHistoryPort3Index OBJECT-TYPE
	SYNTAX  INTEGER(0..128)
	MAX-ACCESS  read-only
	STATUS current
	DESCRIPTION
        "
        Index definition for the pm253PerfTelecomClientPast15StatHistory
        table
        "
	::= { pm253PerfTelecomClientPast15StatHistoryPort3Entry 1 }


pm253PerfTelecomClientPast15StatHistoryInvCvPort3 OBJECT-TYPE
	SYNTAX  EkiOnOff
	MAX-ACCESS read-only
	STATUS current
	DESCRIPTION
        "
        Previous 15-min CV counter inv.
        :This OID indicates that the previous
        15-min Coding Violation counter
        is invalid
        "
	::= { pm253PerfTelecomClientPast15StatHistoryPort3Entry 2 }


pm253PerfTelecomClientPast15StatHistoryCvValuePort3 OBJECT-TYPE
	SYNTAX  Unsigned32
	MAX-ACCESS read-only
	STATUS current
	DESCRIPTION
        "
        Previous 15-min CV counter :This
        OID gives the previous 15-min Coding
        Violation counter value
        "
	::= { pm253PerfTelecomClientPast15StatHistoryPort3Entry 3 }


pm253PerfTelecomClientPast15StatHistoryInvEsPort3 OBJECT-TYPE
	SYNTAX  EkiOnOff
	MAX-ACCESS read-only
	STATUS current
	DESCRIPTION
        "
        Previous 15-min ES counter inv.
        :This OID indicates that the previous
        15-min Errored Second counter is
        invalid
        "
	::= { pm253PerfTelecomClientPast15StatHistoryPort3Entry 4 }


pm253PerfTelecomClientPast15StatHistoryEsValuePort3 OBJECT-TYPE
	SYNTAX  Unsigned32
	MAX-ACCESS read-only
	STATUS current
	DESCRIPTION
        "
        Previous 15-min ES counter :This
        OID gives the previous 15-min Errored
        Second counter value
        "
	::= { pm253PerfTelecomClientPast15StatHistoryPort3Entry 5 }


pm253PerfTelecomClientPast15StatHistoryInvSesPort3 OBJECT-TYPE
	SYNTAX  EkiOnOff
	MAX-ACCESS read-only
	STATUS current
	DESCRIPTION
        "
        Previous 15-min SES counter inv.
        :This OID indicates that the previous
        15-min severely Errored Second
         counter is invalid
        "
	::= { pm253PerfTelecomClientPast15StatHistoryPort3Entry 6 }


pm253PerfTelecomClientPast15StatHistorySesValuePort3 OBJECT-TYPE
	SYNTAX  Unsigned32
	MAX-ACCESS read-only
	STATUS current
	DESCRIPTION
        "
        Previous 15-min SES counter :This
        OID gives the previous 15-min severely
        Errored Second counter value
        "
	::= { pm253PerfTelecomClientPast15StatHistoryPort3Entry 7 }


pm253PerfTelecomClientPast15StatHistoryInvSefsPort3 OBJECT-TYPE
	SYNTAX  EkiOnOff
	MAX-ACCESS read-only
	STATUS current
	DESCRIPTION
        "
        Previous 15-min SEFS counter inv.
        :This OID indicates that the previous
        15-min severely Errored Framing
        Second counter is invalid
        "
	::= { pm253PerfTelecomClientPast15StatHistoryPort3Entry 8 }


pm253PerfTelecomClientPast15StatHistorySefsValuePort3 OBJECT-TYPE
	SYNTAX  Unsigned32
	MAX-ACCESS read-only
	STATUS current
	DESCRIPTION
        "
        Previous 15-min SEFS counter :This
        OID gives the previous 15-min severely
        Errored Framing Second counter
         value
        "
	::= { pm253PerfTelecomClientPast15StatHistoryPort3Entry 9 }


pm253PerfTelecomClientPast15StatHistoryInvUasPort3 OBJECT-TYPE
	SYNTAX  EkiOnOff
	MAX-ACCESS read-only
	STATUS current
	DESCRIPTION
        "
        Previous 15-min UAS counter inv.
        :This OID indicates that the previous
        15-min UnAvailable Second counter
        is invalid
        "
	::= { pm253PerfTelecomClientPast15StatHistoryPort3Entry 10 }


pm253PerfTelecomClientPast15StatHistoryUasValuePort3 OBJECT-TYPE
	SYNTAX  Unsigned32
	MAX-ACCESS read-only
	STATUS current
	DESCRIPTION
        "
        Previous 15-min UAS counter :This
        OID gives the previous 15-min UnAvailable
        Second counter value
        "
	::= { pm253PerfTelecomClientPast15StatHistoryPort3Entry 11 }


--- *****************************************************
---     Leaf of the telecomClientCurrent24Stat
--- *****************************************************
--- *********************************************************
---     TABLE for the pm253PerfTelecomClientCurrent24Stat articles
--- *********************************************************

pm253PerfTelecomClientCurrent24StatTable OBJECT-TYPE
	SYNTAX  SEQUENCE OF Pm253PerfTelecomClientCurrent24StatEntry
	MAX-ACCESS not-accessible
	STATUS current
	DESCRIPTION
        "
        List of pm253PerfTelecomClientCurrent24Stat
        Article
        "
	::= { pm253MonClient 32 }


pm253PerfTelecomClientCurrent24StatEntry OBJECT-TYPE
	SYNTAX Pm253PerfTelecomClientCurrent24StatEntry
	MAX-ACCESS not-accessible
	STATUS current
	DESCRIPTION
        "
        Row definition for the pm253PerfTelecomClientCurrent24Stat
        table
        "
	INDEX   { pm253PerfTelecomClientCurrent24StatIndex }
	::= { pm253PerfTelecomClientCurrent24StatTable 1 }


Pm253PerfTelecomClientCurrent24StatEntry ::=
	SEQUENCE {
	pm253PerfTelecomClientCurrent24StatIndex
		INTEGER,
	pm253PerfTelecomClientCurrent24StatInvCvPortn
		EkiOnOff,
	pm253PerfTelecomClientCurrent24StatCvValuePortn
		Unsigned32,
	pm253PerfTelecomClientCurrent24StatInvEsPortn
		EkiOnOff,
	pm253PerfTelecomClientCurrent24StatEsValuePortn
		Unsigned32,
	pm253PerfTelecomClientCurrent24StatInvSesPortn
		EkiOnOff,
	pm253PerfTelecomClientCurrent24StatSesValuePortn
		Unsigned32,
	pm253PerfTelecomClientCurrent24StatInvSefsPortn
		EkiOnOff,
	pm253PerfTelecomClientCurrent24StatSefsValuePortn
		Unsigned32,
	pm253PerfTelecomClientCurrent24StatInvUasPortn
		EkiOnOff,
	pm253PerfTelecomClientCurrent24StatUasValuePortn
		Unsigned32
	}


pm253PerfTelecomClientCurrent24StatIndex OBJECT-TYPE
	SYNTAX  INTEGER(0..128)
	MAX-ACCESS  read-only
	STATUS current
	DESCRIPTION
        "
        Index definition for the pm253PerfTelecomClientCurrent24Stat
        table
        "
	::= { pm253PerfTelecomClientCurrent24StatEntry 1 }


pm253PerfTelecomClientCurrent24StatInvCvPortn OBJECT-TYPE
	SYNTAX  EkiOnOff
	MAX-ACCESS read-only
	STATUS current
	DESCRIPTION
        "
        Current 24-hours CV counter inv.
        :This OID indicates that the current
        24-hours Coding Violation counter
        is invalid
        "
	::= { pm253PerfTelecomClientCurrent24StatEntry 2 }


pm253PerfTelecomClientCurrent24StatCvValuePortn OBJECT-TYPE
	SYNTAX  Unsigned32
	MAX-ACCESS read-only
	STATUS current
	DESCRIPTION
        "
        Current 24-hours CV counter :This
        OID gives the current 24-hours
         Coding Violation counter value
        "
	::= { pm253PerfTelecomClientCurrent24StatEntry 3 }


pm253PerfTelecomClientCurrent24StatInvEsPortn OBJECT-TYPE
	SYNTAX  EkiOnOff
	MAX-ACCESS read-only
	STATUS current
	DESCRIPTION
        "
        Current 24-hours ES counter inv.
        :This OID indicates that the current
        24-hours Errored Second counter
        is invalid
        "
	::= { pm253PerfTelecomClientCurrent24StatEntry 4 }


pm253PerfTelecomClientCurrent24StatEsValuePortn OBJECT-TYPE
	SYNTAX  Unsigned32
	MAX-ACCESS read-only
	STATUS current
	DESCRIPTION
        "
        Current 24-hours ES counter :This
        OID gives the current 24-hours
         Errored Second counter value
        "
	::= { pm253PerfTelecomClientCurrent24StatEntry 5 }


pm253PerfTelecomClientCurrent24StatInvSesPortn OBJECT-TYPE
	SYNTAX  EkiOnOff
	MAX-ACCESS read-only
	STATUS current
	DESCRIPTION
        "
        Current 24-hours SES counter inv.
        :This OID indicates that the current
        24-hours severely Errored Second
        counter is invalid
        "
	::= { pm253PerfTelecomClientCurrent24StatEntry 6 }


pm253PerfTelecomClientCurrent24StatSesValuePortn OBJECT-TYPE
	SYNTAX  Unsigned32
	MAX-ACCESS read-only
	STATUS current
	DESCRIPTION
        "
        Current 24-hours SES counter :This
        OID gives the current 24-hours
         severely Errored Second counter
        value
        "
	::= { pm253PerfTelecomClientCurrent24StatEntry 7 }


pm253PerfTelecomClientCurrent24StatInvSefsPortn OBJECT-TYPE
	SYNTAX  EkiOnOff
	MAX-ACCESS read-only
	STATUS current
	DESCRIPTION
        "
        Current 24-hours SEFS counter
         inv. :This OID indicates that
         the current 24-hours severely
         Errored Framing Second counter
        is invalid
        "
	::= { pm253PerfTelecomClientCurrent24StatEntry 8 }


pm253PerfTelecomClientCurrent24StatSefsValuePortn OBJECT-TYPE
	SYNTAX  Unsigned32
	MAX-ACCESS read-only
	STATUS current
	DESCRIPTION
        "
        Current 24-hours SEFS counter
         :This OID gives the current 24-hours
        severely Errored Framing Second
        counter value
        "
	::= { pm253PerfTelecomClientCurrent24StatEntry 9 }


pm253PerfTelecomClientCurrent24StatInvUasPortn OBJECT-TYPE
	SYNTAX  EkiOnOff
	MAX-ACCESS read-only
	STATUS current
	DESCRIPTION
        "
        Current 24-hours UAS counter inv.
        :This OID indicates that the current
        24-hours UnAvailable Second counter
        is invalid
        "
	::= { pm253PerfTelecomClientCurrent24StatEntry 10 }


pm253PerfTelecomClientCurrent24StatUasValuePortn OBJECT-TYPE
	SYNTAX  Unsigned32
	MAX-ACCESS read-only
	STATUS current
	DESCRIPTION
        "
        Current 24-hours UAS counter :This
        OID gives the current 24-hours
         UnAvailable Second counter value
        "
	::= { pm253PerfTelecomClientCurrent24StatEntry 11 }


--- *****************************************************
---     Leaf of the telecomClientPast24Stat
--- *****************************************************
--- *********************************************************
---     TABLE for the pm253PerfTelecomClientPast24StatHistory articles
--- *********************************************************

pm253PerfTelecomClientPast24StatHistoryPort1Table OBJECT-TYPE
	SYNTAX  SEQUENCE OF Pm253PerfTelecomClientPast24StatHistoryPort1Entry
	MAX-ACCESS not-accessible
	STATUS current
	DESCRIPTION
        "
        List of pm253PerfTelecomClientPast24StatHistory
        Article
        "
	::= { pm253MonClient 40 }


pm253PerfTelecomClientPast24StatHistoryPort1Entry OBJECT-TYPE
	SYNTAX Pm253PerfTelecomClientPast24StatHistoryPort1Entry
	MAX-ACCESS not-accessible
	STATUS current
	DESCRIPTION
        "
        Row definition for the pm253PerfTelecomClientPast24StatHistory
        table
        "
	INDEX   { pm253PerfTelecomClientPast24StatHistoryPort1Index }
	::= { pm253PerfTelecomClientPast24StatHistoryPort1Table 1 }


Pm253PerfTelecomClientPast24StatHistoryPort1Entry ::=
	SEQUENCE {
	pm253PerfTelecomClientPast24StatHistoryPort1Index
		INTEGER,
	pm253PerfTelecomClientPast24StatHistoryInvCvPort1
		EkiOnOff,
	pm253PerfTelecomClientPast24StatHistoryCvValuePort1
		Unsigned32,
	pm253PerfTelecomClientPast24StatHistoryInvEsPort1
		EkiOnOff,
	pm253PerfTelecomClientPast24StatHistoryEsValuePort1
		Unsigned32,
	pm253PerfTelecomClientPast24StatHistoryInvSesPort1
		EkiOnOff,
	pm253PerfTelecomClientPast24StatHistorySesValuePort1
		Unsigned32,
	pm253PerfTelecomClientPast24StatHistoryInvSefsPort1
		EkiOnOff,
	pm253PerfTelecomClientPast24StatHistorySefsValuePort1
		Unsigned32,
	pm253PerfTelecomClientPast24StatHistoryInvUasPort1
		EkiOnOff,
	pm253PerfTelecomClientPast24StatHistoryUasValuePort1
		Unsigned32
	}


pm253PerfTelecomClientPast24StatHistoryPort1Index OBJECT-TYPE
	SYNTAX  INTEGER(0..128)
	MAX-ACCESS  read-only
	STATUS current
	DESCRIPTION
        "
        Index definition for the pm253PerfTelecomClientPast24StatHistory
        table
        "
	::= { pm253PerfTelecomClientPast24StatHistoryPort1Entry 1 }


pm253PerfTelecomClientPast24StatHistoryInvCvPort1 OBJECT-TYPE
	SYNTAX  EkiOnOff
	MAX-ACCESS read-only
	STATUS current
	DESCRIPTION
        "
        Previous 24-hours CV counter inv.
        :This OID indicates that the previous
        24-hours Coding Violation counter
        is invalid
        "
	::= { pm253PerfTelecomClientPast24StatHistoryPort1Entry 2 }


pm253PerfTelecomClientPast24StatHistoryCvValuePort1 OBJECT-TYPE
	SYNTAX  Unsigned32
	MAX-ACCESS read-only
	STATUS current
	DESCRIPTION
        "
        Previous 24-hours CV counter :This
        OID gives the previous 24-hours
        Coding Violation counter value
        "
	::= { pm253PerfTelecomClientPast24StatHistoryPort1Entry 3 }


pm253PerfTelecomClientPast24StatHistoryInvEsPort1 OBJECT-TYPE
	SYNTAX  EkiOnOff
	MAX-ACCESS read-only
	STATUS current
	DESCRIPTION
        "
        Previous 24-hours ES counter inv.
        :This OID indicates that the previous
        24-hours Errored Second counter
        is invalid
        "
	::= { pm253PerfTelecomClientPast24StatHistoryPort1Entry 4 }


pm253PerfTelecomClientPast24StatHistoryEsValuePort1 OBJECT-TYPE
	SYNTAX  Unsigned32
	MAX-ACCESS read-only
	STATUS current
	DESCRIPTION
        "
        Previous 24-hours ES counter :This
        OID gives the previous 24-hours
        Errored Second counter value
        "
	::= { pm253PerfTelecomClientPast24StatHistoryPort1Entry 5 }


pm253PerfTelecomClientPast24StatHistoryInvSesPort1 OBJECT-TYPE
	SYNTAX  EkiOnOff
	MAX-ACCESS read-only
	STATUS current
	DESCRIPTION
        "
        Previous 24-hours SES counter
         inv. :This OID indicates that
         the previous 24-hours severely
        Errored Second counter is invalid
        "
	::= { pm253PerfTelecomClientPast24StatHistoryPort1Entry 6 }


pm253PerfTelecomClientPast24StatHistorySesValuePort1 OBJECT-TYPE
	SYNTAX  Unsigned32
	MAX-ACCESS read-only
	STATUS current
	DESCRIPTION
        "
        Previous 24-hours SES counter
         :This OID gives the previous 24-hours
        severely Errored Second counter
        value
        "
	::= { pm253PerfTelecomClientPast24StatHistoryPort1Entry 7 }


pm253PerfTelecomClientPast24StatHistoryInvSefsPort1 OBJECT-TYPE
	SYNTAX  EkiOnOff
	MAX-ACCESS read-only
	STATUS current
	DESCRIPTION
        "
        Previous 24-hours SEFS counter
        inv. :This OID indicates that the
        previous 24-hours severely Errored
        Framing Second counter is invalid
        "
	::= { pm253PerfTelecomClientPast24StatHistoryPort1Entry 8 }


pm253PerfTelecomClientPast24StatHistorySefsValuePort1 OBJECT-TYPE
	SYNTAX  Unsigned32
	MAX-ACCESS read-only
	STATUS current
	DESCRIPTION
        "
        Previous 24-hours SEFS counter
        :This OID gives the previous 24-hours
        severely Errored Framing Second
        counter value
        "
	::= { pm253PerfTelecomClientPast24StatHistoryPort1Entry 9 }


pm253PerfTelecomClientPast24StatHistoryInvUasPort1 OBJECT-TYPE
	SYNTAX  EkiOnOff
	MAX-ACCESS read-only
	STATUS current
	DESCRIPTION
        "
        Previous 24-hours UAS counter
         inv. :This OID indicates that
         the previous 24-hours UnAvailable
        Second counter is invalid
        "
	::= { pm253PerfTelecomClientPast24StatHistoryPort1Entry 10 }


pm253PerfTelecomClientPast24StatHistoryUasValuePort1 OBJECT-TYPE
	SYNTAX  Unsigned32
	MAX-ACCESS read-only
	STATUS current
	DESCRIPTION
        "
        Previous 24-hours UAS counter
         :This OID gives the previous 24-hours
        UnAvailable Second counter value
        "
	::= { pm253PerfTelecomClientPast24StatHistoryPort1Entry 11 }


--- *********************************************************
---     TABLE for the pm253PerfTelecomClientPast24StatHistory articles
--- *********************************************************

pm253PerfTelecomClientPast24StatHistoryPort2Table OBJECT-TYPE
	SYNTAX  SEQUENCE OF Pm253PerfTelecomClientPast24StatHistoryPort2Entry
	MAX-ACCESS not-accessible
	STATUS current
	DESCRIPTION
        "
        List of pm253PerfTelecomClientPast24StatHistory
        Article
        "
	::= { pm253MonClient 41 }


pm253PerfTelecomClientPast24StatHistoryPort2Entry OBJECT-TYPE
	SYNTAX Pm253PerfTelecomClientPast24StatHistoryPort2Entry
	MAX-ACCESS not-accessible
	STATUS current
	DESCRIPTION
        "
        Row definition for the pm253PerfTelecomClientPast24StatHistory
        table
        "
	INDEX   { pm253PerfTelecomClientPast24StatHistoryPort2Index }
	::= { pm253PerfTelecomClientPast24StatHistoryPort2Table 1 }


Pm253PerfTelecomClientPast24StatHistoryPort2Entry ::=
	SEQUENCE {
	pm253PerfTelecomClientPast24StatHistoryPort2Index
		INTEGER,
	pm253PerfTelecomClientPast24StatHistoryInvCvPort2
		EkiOnOff,
	pm253PerfTelecomClientPast24StatHistoryCvValuePort2
		Unsigned32,
	pm253PerfTelecomClientPast24StatHistoryInvEsPort2
		EkiOnOff,
	pm253PerfTelecomClientPast24StatHistoryEsValuePort2
		Unsigned32,
	pm253PerfTelecomClientPast24StatHistoryInvSesPort2
		EkiOnOff,
	pm253PerfTelecomClientPast24StatHistorySesValuePort2
		Unsigned32,
	pm253PerfTelecomClientPast24StatHistoryInvSefsPort2
		EkiOnOff,
	pm253PerfTelecomClientPast24StatHistorySefsValuePort2
		Unsigned32,
	pm253PerfTelecomClientPast24StatHistoryInvUasPort2
		EkiOnOff,
	pm253PerfTelecomClientPast24StatHistoryUasValuePort2
		Unsigned32
	}


pm253PerfTelecomClientPast24StatHistoryPort2Index OBJECT-TYPE
	SYNTAX  INTEGER(0..128)
	MAX-ACCESS  read-only
	STATUS current
	DESCRIPTION
        "
        Index definition for the pm253PerfTelecomClientPast24StatHistory
        table
        "
	::= { pm253PerfTelecomClientPast24StatHistoryPort2Entry 1 }


pm253PerfTelecomClientPast24StatHistoryInvCvPort2 OBJECT-TYPE
	SYNTAX  EkiOnOff
	MAX-ACCESS read-only
	STATUS current
	DESCRIPTION
        "
        Previous 24-hours CV counter inv.
        :This OID indicates that the previous
        24-hours Coding Violation counter
        is invalid
        "
	::= { pm253PerfTelecomClientPast24StatHistoryPort2Entry 2 }


pm253PerfTelecomClientPast24StatHistoryCvValuePort2 OBJECT-TYPE
	SYNTAX  Unsigned32
	MAX-ACCESS read-only
	STATUS current
	DESCRIPTION
        "
        Previous 24-hours CV counter :This
        OID gives the previous 24-hours
        Coding Violation counter value
        "
	::= { pm253PerfTelecomClientPast24StatHistoryPort2Entry 3 }


pm253PerfTelecomClientPast24StatHistoryInvEsPort2 OBJECT-TYPE
	SYNTAX  EkiOnOff
	MAX-ACCESS read-only
	STATUS current
	DESCRIPTION
        "
        Previous 24-hours ES counter inv.
        :This OID indicates that the previous
        24-hours Errored Second counter
        is invalid
        "
	::= { pm253PerfTelecomClientPast24StatHistoryPort2Entry 4 }


pm253PerfTelecomClientPast24StatHistoryEsValuePort2 OBJECT-TYPE
	SYNTAX  Unsigned32
	MAX-ACCESS read-only
	STATUS current
	DESCRIPTION
        "
        Previous 24-hours ES counter :This
        OID gives the previous 24-hours
        Errored Second counter value
        "
	::= { pm253PerfTelecomClientPast24StatHistoryPort2Entry 5 }


pm253PerfTelecomClientPast24StatHistoryInvSesPort2 OBJECT-TYPE
	SYNTAX  EkiOnOff
	MAX-ACCESS read-only
	STATUS current
	DESCRIPTION
        "
        Previous 24-hours SES counter
         inv. :This OID indicates that
         the previous 24-hours severely
        Errored Second counter is invalid
        "
	::= { pm253PerfTelecomClientPast24StatHistoryPort2Entry 6 }


pm253PerfTelecomClientPast24StatHistorySesValuePort2 OBJECT-TYPE
	SYNTAX  Unsigned32
	MAX-ACCESS read-only
	STATUS current
	DESCRIPTION
        "
        Previous 24-hours SES counter
         :This OID gives the previous 24-hours
        severely Errored Second counter
        value
        "
	::= { pm253PerfTelecomClientPast24StatHistoryPort2Entry 7 }


pm253PerfTelecomClientPast24StatHistoryInvSefsPort2 OBJECT-TYPE
	SYNTAX  EkiOnOff
	MAX-ACCESS read-only
	STATUS current
	DESCRIPTION
        "
        Previous 24-hours SEFS counter
        inv. :This OID indicates that the
        previous 24-hours severely Errored
        Framing Second counter is invalid
        "
	::= { pm253PerfTelecomClientPast24StatHistoryPort2Entry 8 }


pm253PerfTelecomClientPast24StatHistorySefsValuePort2 OBJECT-TYPE
	SYNTAX  Unsigned32
	MAX-ACCESS read-only
	STATUS current
	DESCRIPTION
        "
        Previous 24-hours SEFS counter
        :This OID gives the previous 24-hours
        severely Errored Framing Second
        counter value
        "
	::= { pm253PerfTelecomClientPast24StatHistoryPort2Entry 9 }


pm253PerfTelecomClientPast24StatHistoryInvUasPort2 OBJECT-TYPE
	SYNTAX  EkiOnOff
	MAX-ACCESS read-only
	STATUS current
	DESCRIPTION
        "
        Previous 24-hours UAS counter
         inv. :This OID indicates that
         the previous 24-hours UnAvailable
        Second counter is invalid
        "
	::= { pm253PerfTelecomClientPast24StatHistoryPort2Entry 10 }


pm253PerfTelecomClientPast24StatHistoryUasValuePort2 OBJECT-TYPE
	SYNTAX  Unsigned32
	MAX-ACCESS read-only
	STATUS current
	DESCRIPTION
        "
        Previous 24-hours UAS counter
         :This OID gives the previous 24-hours
        UnAvailable Second counter value
        "
	::= { pm253PerfTelecomClientPast24StatHistoryPort2Entry 11 }


--- *********************************************************
---     TABLE for the pm253PerfTelecomClientPast24StatHistory articles
--- *********************************************************

pm253PerfTelecomClientPast24StatHistoryPort3Table OBJECT-TYPE
	SYNTAX  SEQUENCE OF Pm253PerfTelecomClientPast24StatHistoryPort3Entry
	MAX-ACCESS not-accessible
	STATUS current
	DESCRIPTION
        "
        List of pm253PerfTelecomClientPast24StatHistory
        Article
        "
	::= { pm253MonClient 42 }


pm253PerfTelecomClientPast24StatHistoryPort3Entry OBJECT-TYPE
	SYNTAX Pm253PerfTelecomClientPast24StatHistoryPort3Entry
	MAX-ACCESS not-accessible
	STATUS current
	DESCRIPTION
        "
        Row definition for the pm253PerfTelecomClientPast24StatHistory
        table
        "
	INDEX   { pm253PerfTelecomClientPast24StatHistoryPort3Index }
	::= { pm253PerfTelecomClientPast24StatHistoryPort3Table 1 }


Pm253PerfTelecomClientPast24StatHistoryPort3Entry ::=
	SEQUENCE {
	pm253PerfTelecomClientPast24StatHistoryPort3Index
		INTEGER,
	pm253PerfTelecomClientPast24StatHistoryInvCvPort3
		EkiOnOff,
	pm253PerfTelecomClientPast24StatHistoryCvValuePort3
		Unsigned32,
	pm253PerfTelecomClientPast24StatHistoryInvEsPort3
		EkiOnOff,
	pm253PerfTelecomClientPast24StatHistoryEsValuePort3
		Unsigned32,
	pm253PerfTelecomClientPast24StatHistoryInvSesPort3
		EkiOnOff,
	pm253PerfTelecomClientPast24StatHistorySesValuePort3
		Unsigned32,
	pm253PerfTelecomClientPast24StatHistoryInvSefsPort3
		EkiOnOff,
	pm253PerfTelecomClientPast24StatHistorySefsValuePort3
		Unsigned32,
	pm253PerfTelecomClientPast24StatHistoryInvUasPort3
		EkiOnOff,
	pm253PerfTelecomClientPast24StatHistoryUasValuePort3
		Unsigned32
	}


pm253PerfTelecomClientPast24StatHistoryPort3Index OBJECT-TYPE
	SYNTAX  INTEGER(0..128)
	MAX-ACCESS  read-only
	STATUS current
	DESCRIPTION
        "
        Index definition for the pm253PerfTelecomClientPast24StatHistory
        table
        "
	::= { pm253PerfTelecomClientPast24StatHistoryPort3Entry 1 }


pm253PerfTelecomClientPast24StatHistoryInvCvPort3 OBJECT-TYPE
	SYNTAX  EkiOnOff
	MAX-ACCESS read-only
	STATUS current
	DESCRIPTION
        "
        Previous 24-hours CV counter inv.
        :This OID indicates that the previous
        24-hours Coding Violation counter
        is invalid
        "
	::= { pm253PerfTelecomClientPast24StatHistoryPort3Entry 2 }


pm253PerfTelecomClientPast24StatHistoryCvValuePort3 OBJECT-TYPE
	SYNTAX  Unsigned32
	MAX-ACCESS read-only
	STATUS current
	DESCRIPTION
        "
        Previous 24-hours CV counter :This
        OID gives the previous 24-hours
        Coding Violation counter value
        "
	::= { pm253PerfTelecomClientPast24StatHistoryPort3Entry 3 }


pm253PerfTelecomClientPast24StatHistoryInvEsPort3 OBJECT-TYPE
	SYNTAX  EkiOnOff
	MAX-ACCESS read-only
	STATUS current
	DESCRIPTION
        "
        Previous 24-hours ES counter inv.
        :This OID indicates that the previous
        24-hours Errored Second counter
        is invalid
        "
	::= { pm253PerfTelecomClientPast24StatHistoryPort3Entry 4 }


pm253PerfTelecomClientPast24StatHistoryEsValuePort3 OBJECT-TYPE
	SYNTAX  Unsigned32
	MAX-ACCESS read-only
	STATUS current
	DESCRIPTION
        "
        Previous 24-hours ES counter :This
        OID gives the previous 24-hours
        Errored Second counter value
        "
	::= { pm253PerfTelecomClientPast24StatHistoryPort3Entry 5 }


pm253PerfTelecomClientPast24StatHistoryInvSesPort3 OBJECT-TYPE
	SYNTAX  EkiOnOff
	MAX-ACCESS read-only
	STATUS current
	DESCRIPTION
        "
        Previous 24-hours SES counter
         inv. :This OID indicates that
         the previous 24-hours severely
        Errored Second counter is invalid
        "
	::= { pm253PerfTelecomClientPast24StatHistoryPort3Entry 6 }


pm253PerfTelecomClientPast24StatHistorySesValuePort3 OBJECT-TYPE
	SYNTAX  Unsigned32
	MAX-ACCESS read-only
	STATUS current
	DESCRIPTION
        "
        Previous 24-hours SES counter
         :This OID gives the previous 24-hours
        severely Errored Second counter
        value
        "
	::= { pm253PerfTelecomClientPast24StatHistoryPort3Entry 7 }


pm253PerfTelecomClientPast24StatHistoryInvSefsPort3 OBJECT-TYPE
	SYNTAX  EkiOnOff
	MAX-ACCESS read-only
	STATUS current
	DESCRIPTION
        "
        Previous 24-hours SEFS counter
        inv. :This OID indicates that the
        previous 24-hours severely Errored
        Framing Second counter is invalid
        "
	::= { pm253PerfTelecomClientPast24StatHistoryPort3Entry 8 }


pm253PerfTelecomClientPast24StatHistorySefsValuePort3 OBJECT-TYPE
	SYNTAX  Unsigned32
	MAX-ACCESS read-only
	STATUS current
	DESCRIPTION
        "
        Previous 24-hours SEFS counter
        :This OID gives the previous 24-hours
        severely Errored Framing Second
        counter value
        "
	::= { pm253PerfTelecomClientPast24StatHistoryPort3Entry 9 }


pm253PerfTelecomClientPast24StatHistoryInvUasPort3 OBJECT-TYPE
	SYNTAX  EkiOnOff
	MAX-ACCESS read-only
	STATUS current
	DESCRIPTION
        "
        Previous 24-hours UAS counter
         inv. :This OID indicates that
         the previous 24-hours UnAvailable
        Second counter is invalid
        "
	::= { pm253PerfTelecomClientPast24StatHistoryPort3Entry 10 }


pm253PerfTelecomClientPast24StatHistoryUasValuePort3 OBJECT-TYPE
	SYNTAX  Unsigned32
	MAX-ACCESS read-only
	STATUS current
	DESCRIPTION
        "
        Previous 24-hours UAS counter
         :This OID gives the previous 24-hours
        UnAvailable Second counter value
        "
	::= { pm253PerfTelecomClientPast24StatHistoryPort3Entry 11 }


--- *****************************************************
---     Leaf of the telecomLineCurrent15Stat
--- *****************************************************
--- *********************************************************
---     TABLE for the pm253PerfTelecomLineCurrent15Stat articles
--- *********************************************************

pm253PerfTelecomLineCurrent15StatTable OBJECT-TYPE
	SYNTAX  SEQUENCE OF Pm253PerfTelecomLineCurrent15StatEntry
	MAX-ACCESS not-accessible
	STATUS current
	DESCRIPTION
        "
        List of pm253PerfTelecomLineCurrent15Stat
        Article
        "
	::= { pm253MonLine 128 }


pm253PerfTelecomLineCurrent15StatEntry OBJECT-TYPE
	SYNTAX Pm253PerfTelecomLineCurrent15StatEntry
	MAX-ACCESS not-accessible
	STATUS current
	DESCRIPTION
        "
        Row definition for the pm253PerfTelecomLineCurrent15Stat
        table
        "
	INDEX   { pm253PerfTelecomLineCurrent15StatIndex }
	::= { pm253PerfTelecomLineCurrent15StatTable 1 }


Pm253PerfTelecomLineCurrent15StatEntry ::=
	SEQUENCE {
	pm253PerfTelecomLineCurrent15StatIndex
		INTEGER,
	pm253PerfTelecomLineCurrent15StatInvCvPortn
		EkiOnOff,
	pm253PerfTelecomLineCurrent15StatCvValuePortn
		Unsigned32,
	pm253PerfTelecomLineCurrent15StatInvEsPortn
		EkiOnOff,
	pm253PerfTelecomLineCurrent15StatEsValuePortn
		Unsigned32,
	pm253PerfTelecomLineCurrent15StatInvSesPortn
		EkiOnOff,
	pm253PerfTelecomLineCurrent15StatSesValuePortn
		Unsigned32,
	pm253PerfTelecomLineCurrent15StatInvSefsPortn
		EkiOnOff,
	pm253PerfTelecomLineCurrent15StatSefsValuePortn
		Unsigned32,
	pm253PerfTelecomLineCurrent15StatInvUasPortn
		EkiOnOff,
	pm253PerfTelecomLineCurrent15StatUasValuePortn
		Unsigned32
	}


pm253PerfTelecomLineCurrent15StatIndex OBJECT-TYPE
	SYNTAX  INTEGER(0..128)
	MAX-ACCESS  read-only
	STATUS current
	DESCRIPTION
        "
        Index definition for the pm253PerfTelecomLineCurrent15Stat
        table
        "
	::= { pm253PerfTelecomLineCurrent15StatEntry 1 }


pm253PerfTelecomLineCurrent15StatInvCvPortn OBJECT-TYPE
	SYNTAX  EkiOnOff
	MAX-ACCESS read-only
	STATUS current
	DESCRIPTION
        "
        Current 15-min CV counter inv.
        :This OID indicates that the current
        15-min Coding Violation counter
        is invalid
        "
	::= { pm253PerfTelecomLineCurrent15StatEntry 2 }


pm253PerfTelecomLineCurrent15StatCvValuePortn OBJECT-TYPE
	SYNTAX  Unsigned32
	MAX-ACCESS read-only
	STATUS current
	DESCRIPTION
        "
        Current 15-min CV counter :This
        OID gives the current 15-min Coding
        Violation counter value
        "
	::= { pm253PerfTelecomLineCurrent15StatEntry 3 }


pm253PerfTelecomLineCurrent15StatInvEsPortn OBJECT-TYPE
	SYNTAX  EkiOnOff
	MAX-ACCESS read-only
	STATUS current
	DESCRIPTION
        "
        Current 15-min ES counter inv.
        :This OID indicates that the current
        15-min Errored Second counter is
        invalid
        "
	::= { pm253PerfTelecomLineCurrent15StatEntry 4 }


pm253PerfTelecomLineCurrent15StatEsValuePortn OBJECT-TYPE
	SYNTAX  Unsigned32
	MAX-ACCESS read-only
	STATUS current
	DESCRIPTION
        "
        Current 15-min ES counter :This
        OID gives the current 15-min Errored
        Second counter value
        "
	::= { pm253PerfTelecomLineCurrent15StatEntry 5 }


pm253PerfTelecomLineCurrent15StatInvSesPortn OBJECT-TYPE
	SYNTAX  EkiOnOff
	MAX-ACCESS read-only
	STATUS current
	DESCRIPTION
        "
        Current 15-min SES counter inv.
        :This OID indicates that the current
        15-min severely Errored Second
         counter is invalid
        "
	::= { pm253PerfTelecomLineCurrent15StatEntry 6 }


pm253PerfTelecomLineCurrent15StatSesValuePortn OBJECT-TYPE
	SYNTAX  Unsigned32
	MAX-ACCESS read-only
	STATUS current
	DESCRIPTION
        "
        Current 15-min SES counter :This
        OID gives the current 15-min severely
        Errored Second counter value
        "
	::= { pm253PerfTelecomLineCurrent15StatEntry 7 }


pm253PerfTelecomLineCurrent15StatInvSefsPortn OBJECT-TYPE
	SYNTAX  EkiOnOff
	MAX-ACCESS read-only
	STATUS current
	DESCRIPTION
        "
        Current 15-min SEFS counter inv.
        :This OID indicates that the current
        15-min severely Errored Framing
        Second counter is invalid
        "
	::= { pm253PerfTelecomLineCurrent15StatEntry 8 }


pm253PerfTelecomLineCurrent15StatSefsValuePortn OBJECT-TYPE
	SYNTAX  Unsigned32
	MAX-ACCESS read-only
	STATUS current
	DESCRIPTION
        "
        Current 15-min SEFS counter :This
        OID gives the current 15-min severely
        Errored Framing Second counter
         value
        "
	::= { pm253PerfTelecomLineCurrent15StatEntry 9 }


pm253PerfTelecomLineCurrent15StatInvUasPortn OBJECT-TYPE
	SYNTAX  EkiOnOff
	MAX-ACCESS read-only
	STATUS current
	DESCRIPTION
        "
        Current 15-min UAS counter inv.
        :This OID indicates that the current
        15-min UnAvailable Second counter
        is invalid
        "
	::= { pm253PerfTelecomLineCurrent15StatEntry 10 }


pm253PerfTelecomLineCurrent15StatUasValuePortn OBJECT-TYPE
	SYNTAX  Unsigned32
	MAX-ACCESS read-only
	STATUS current
	DESCRIPTION
        "
        Current 15-min UAS counter :This
        OID gives the current 15-min UnAvailable
        Second counter value
        "
	::= { pm253PerfTelecomLineCurrent15StatEntry 11 }


--- *****************************************************
---     Leaf of the telecomLinePast15Stat
--- *****************************************************
--- *********************************************************
---     TABLE for the pm253PerfTelecomLinePast15StatHistory articles
--- *********************************************************

pm253PerfTelecomLinePast15StatHistoryPort1Table OBJECT-TYPE
	SYNTAX  SEQUENCE OF Pm253PerfTelecomLinePast15StatHistoryPort1Entry
	MAX-ACCESS not-accessible
	STATUS current
	DESCRIPTION
        "
        List of pm253PerfTelecomLinePast15StatHistory
        Article
        "
	::= { pm253MonLine 129 }


pm253PerfTelecomLinePast15StatHistoryPort1Entry OBJECT-TYPE
	SYNTAX Pm253PerfTelecomLinePast15StatHistoryPort1Entry
	MAX-ACCESS not-accessible
	STATUS current
	DESCRIPTION
        "
        Row definition for the pm253PerfTelecomLinePast15StatHistory
        table
        "
	INDEX   { pm253PerfTelecomLinePast15StatHistoryPort1Index }
	::= { pm253PerfTelecomLinePast15StatHistoryPort1Table 1 }


Pm253PerfTelecomLinePast15StatHistoryPort1Entry ::=
	SEQUENCE {
	pm253PerfTelecomLinePast15StatHistoryPort1Index
		INTEGER,
	pm253PerfTelecomLinePast15StatHistoryInvCvPort1
		EkiOnOff,
	pm253PerfTelecomLinePast15StatHistoryCvValuePort1
		Unsigned32,
	pm253PerfTelecomLinePast15StatHistoryInvEsPort1
		EkiOnOff,
	pm253PerfTelecomLinePast15StatHistoryEsValuePort1
		Unsigned32,
	pm253PerfTelecomLinePast15StatHistoryInvSesPort1
		EkiOnOff,
	pm253PerfTelecomLinePast15StatHistorySesValuePort1
		Unsigned32,
	pm253PerfTelecomLinePast15StatHistoryInvSefsPort1
		EkiOnOff,
	pm253PerfTelecomLinePast15StatHistorySefsValuePort1
		Unsigned32,
	pm253PerfTelecomLinePast15StatHistoryInvUasPort1
		EkiOnOff,
	pm253PerfTelecomLinePast15StatHistoryUasValuePort1
		Unsigned32
	}


pm253PerfTelecomLinePast15StatHistoryPort1Index OBJECT-TYPE
	SYNTAX  INTEGER(0..128)
	MAX-ACCESS  read-only
	STATUS current
	DESCRIPTION
        "
        Index definition for the pm253PerfTelecomLinePast15StatHistory
        table
        "
	::= { pm253PerfTelecomLinePast15StatHistoryPort1Entry 1 }


pm253PerfTelecomLinePast15StatHistoryInvCvPort1 OBJECT-TYPE
	SYNTAX  EkiOnOff
	MAX-ACCESS read-only
	STATUS current
	DESCRIPTION
        "
        Previous 15-min CV counter inv.
        :This OID indicates that the previous
        15-min Coding Violation counter
        is invalid
        "
	::= { pm253PerfTelecomLinePast15StatHistoryPort1Entry 2 }


pm253PerfTelecomLinePast15StatHistoryCvValuePort1 OBJECT-TYPE
	SYNTAX  Unsigned32
	MAX-ACCESS read-only
	STATUS current
	DESCRIPTION
        "
        Previous 15-min CV counter :This
        OID gives the previous 15-min Coding
        Violation counter value
        "
	::= { pm253PerfTelecomLinePast15StatHistoryPort1Entry 3 }


pm253PerfTelecomLinePast15StatHistoryInvEsPort1 OBJECT-TYPE
	SYNTAX  EkiOnOff
	MAX-ACCESS read-only
	STATUS current
	DESCRIPTION
        "
        Previous 15-min ES counter inv.
        :This OID indicates that the previous
        15-min Errored Second counter is
        invalid
        "
	::= { pm253PerfTelecomLinePast15StatHistoryPort1Entry 4 }


pm253PerfTelecomLinePast15StatHistoryEsValuePort1 OBJECT-TYPE
	SYNTAX  Unsigned32
	MAX-ACCESS read-only
	STATUS current
	DESCRIPTION
        "
        Previous 15-min ES counter :This
        OID gives the previous 15-min Errored
        Second counter value
        "
	::= { pm253PerfTelecomLinePast15StatHistoryPort1Entry 5 }


pm253PerfTelecomLinePast15StatHistoryInvSesPort1 OBJECT-TYPE
	SYNTAX  EkiOnOff
	MAX-ACCESS read-only
	STATUS current
	DESCRIPTION
        "
        Previous 15-min SES counter inv.
        :This OID indicates that the previous
        15-min severely Errored Second
         counter is invalid
        "
	::= { pm253PerfTelecomLinePast15StatHistoryPort1Entry 6 }


pm253PerfTelecomLinePast15StatHistorySesValuePort1 OBJECT-TYPE
	SYNTAX  Unsigned32
	MAX-ACCESS read-only
	STATUS current
	DESCRIPTION
        "
        Previous 15-min SES counter :This
        OID gives the previous 15-min severely
        Errored Second counter value
        "
	::= { pm253PerfTelecomLinePast15StatHistoryPort1Entry 7 }


pm253PerfTelecomLinePast15StatHistoryInvSefsPort1 OBJECT-TYPE
	SYNTAX  EkiOnOff
	MAX-ACCESS read-only
	STATUS current
	DESCRIPTION
        "
        Previous 15-min SEFS counter inv.
        :This OID indicates that the previous
        15-min severely Errored Framing
        Second counter is invalid
        "
	::= { pm253PerfTelecomLinePast15StatHistoryPort1Entry 8 }


pm253PerfTelecomLinePast15StatHistorySefsValuePort1 OBJECT-TYPE
	SYNTAX  Unsigned32
	MAX-ACCESS read-only
	STATUS current
	DESCRIPTION
        "
        Previous 15-min SEFS counter :This
        OID gives the previous 15-min severely
        Errored Framing Second counter
         value
        "
	::= { pm253PerfTelecomLinePast15StatHistoryPort1Entry 9 }


pm253PerfTelecomLinePast15StatHistoryInvUasPort1 OBJECT-TYPE
	SYNTAX  EkiOnOff
	MAX-ACCESS read-only
	STATUS current
	DESCRIPTION
        "
        Previous 15-min UAS counter inv.
        :This OID indicates that the previous
        15-min UnAvailable Second counter
        is invalid
        "
	::= { pm253PerfTelecomLinePast15StatHistoryPort1Entry 10 }


pm253PerfTelecomLinePast15StatHistoryUasValuePort1 OBJECT-TYPE
	SYNTAX  Unsigned32
	MAX-ACCESS read-only
	STATUS current
	DESCRIPTION
        "
        Previous 15-min UAS counter :This
        OID gives the previous 15-min UnAvailable
        Second counter value
        "
	::= { pm253PerfTelecomLinePast15StatHistoryPort1Entry 11 }


--- *********************************************************
---     TABLE for the pm253PerfTelecomLinePast15StatHistory articles
--- *********************************************************

pm253PerfTelecomLinePast15StatHistoryPort2Table OBJECT-TYPE
	SYNTAX  SEQUENCE OF Pm253PerfTelecomLinePast15StatHistoryPort2Entry
	MAX-ACCESS not-accessible
	STATUS current
	DESCRIPTION
        "
        List of pm253PerfTelecomLinePast15StatHistory
        Article
        "
	::= { pm253MonLine 145 }


pm253PerfTelecomLinePast15StatHistoryPort2Entry OBJECT-TYPE
	SYNTAX Pm253PerfTelecomLinePast15StatHistoryPort2Entry
	MAX-ACCESS not-accessible
	STATUS current
	DESCRIPTION
        "
        Row definition for the pm253PerfTelecomLinePast15StatHistory
        table
        "
	INDEX   { pm253PerfTelecomLinePast15StatHistoryPort2Index }
	::= { pm253PerfTelecomLinePast15StatHistoryPort2Table 1 }


Pm253PerfTelecomLinePast15StatHistoryPort2Entry ::=
	SEQUENCE {
	pm253PerfTelecomLinePast15StatHistoryPort2Index
		INTEGER,
	pm253PerfTelecomLinePast15StatHistoryInvCvPort2
		EkiOnOff,
	pm253PerfTelecomLinePast15StatHistoryCvValuePort2
		Unsigned32,
	pm253PerfTelecomLinePast15StatHistoryInvEsPort2
		EkiOnOff,
	pm253PerfTelecomLinePast15StatHistoryEsValuePort2
		Unsigned32,
	pm253PerfTelecomLinePast15StatHistoryInvSesPort2
		EkiOnOff,
	pm253PerfTelecomLinePast15StatHistorySesValuePort2
		Unsigned32,
	pm253PerfTelecomLinePast15StatHistoryInvSefsPort2
		EkiOnOff,
	pm253PerfTelecomLinePast15StatHistorySefsValuePort2
		Unsigned32,
	pm253PerfTelecomLinePast15StatHistoryInvUasPort2
		EkiOnOff,
	pm253PerfTelecomLinePast15StatHistoryUasValuePort2
		Unsigned32
	}


pm253PerfTelecomLinePast15StatHistoryPort2Index OBJECT-TYPE
	SYNTAX  INTEGER(0..128)
	MAX-ACCESS  read-only
	STATUS current
	DESCRIPTION
        "
        Index definition for the pm253PerfTelecomLinePast15StatHistory
        table
        "
	::= { pm253PerfTelecomLinePast15StatHistoryPort2Entry 1 }


pm253PerfTelecomLinePast15StatHistoryInvCvPort2 OBJECT-TYPE
	SYNTAX  EkiOnOff
	MAX-ACCESS read-only
	STATUS current
	DESCRIPTION
        "
        Previous 15-min CV counter inv.
        :This OID indicates that the previous
        15-min Coding Violation counter
        is invalid
        "
	::= { pm253PerfTelecomLinePast15StatHistoryPort2Entry 2 }


pm253PerfTelecomLinePast15StatHistoryCvValuePort2 OBJECT-TYPE
	SYNTAX  Unsigned32
	MAX-ACCESS read-only
	STATUS current
	DESCRIPTION
        "
        Previous 15-min CV counter :This
        OID gives the previous 15-min Coding
        Violation counter value
        "
	::= { pm253PerfTelecomLinePast15StatHistoryPort2Entry 3 }


pm253PerfTelecomLinePast15StatHistoryInvEsPort2 OBJECT-TYPE
	SYNTAX  EkiOnOff
	MAX-ACCESS read-only
	STATUS current
	DESCRIPTION
        "
        Previous 15-min ES counter inv.
        :This OID indicates that the previous
        15-min Errored Second counter is
        invalid
        "
	::= { pm253PerfTelecomLinePast15StatHistoryPort2Entry 4 }


pm253PerfTelecomLinePast15StatHistoryEsValuePort2 OBJECT-TYPE
	SYNTAX  Unsigned32
	MAX-ACCESS read-only
	STATUS current
	DESCRIPTION
        "
        Previous 15-min ES counter :This
        OID gives the previous 15-min Errored
        Second counter value
        "
	::= { pm253PerfTelecomLinePast15StatHistoryPort2Entry 5 }


pm253PerfTelecomLinePast15StatHistoryInvSesPort2 OBJECT-TYPE
	SYNTAX  EkiOnOff
	MAX-ACCESS read-only
	STATUS current
	DESCRIPTION
        "
        Previous 15-min SES counter inv.
        :This OID indicates that the previous
        15-min severely Errored Second
         counter is invalid
        "
	::= { pm253PerfTelecomLinePast15StatHistoryPort2Entry 6 }


pm253PerfTelecomLinePast15StatHistorySesValuePort2 OBJECT-TYPE
	SYNTAX  Unsigned32
	MAX-ACCESS read-only
	STATUS current
	DESCRIPTION
        "
        Previous 15-min SES counter :This
        OID gives the previous 15-min severely
        Errored Second counter value
        "
	::= { pm253PerfTelecomLinePast15StatHistoryPort2Entry 7 }


pm253PerfTelecomLinePast15StatHistoryInvSefsPort2 OBJECT-TYPE
	SYNTAX  EkiOnOff
	MAX-ACCESS read-only
	STATUS current
	DESCRIPTION
        "
        Previous 15-min SEFS counter inv.
        :This OID indicates that the previous
        15-min severely Errored Framing
        Second counter is invalid
        "
	::= { pm253PerfTelecomLinePast15StatHistoryPort2Entry 8 }


pm253PerfTelecomLinePast15StatHistorySefsValuePort2 OBJECT-TYPE
	SYNTAX  Unsigned32
	MAX-ACCESS read-only
	STATUS current
	DESCRIPTION
        "
        Previous 15-min SEFS counter :This
        OID gives the previous 15-min severely
        Errored Framing Second counter
         value
        "
	::= { pm253PerfTelecomLinePast15StatHistoryPort2Entry 9 }


pm253PerfTelecomLinePast15StatHistoryInvUasPort2 OBJECT-TYPE
	SYNTAX  EkiOnOff
	MAX-ACCESS read-only
	STATUS current
	DESCRIPTION
        "
        Previous 15-min UAS counter inv.
        :This OID indicates that the previous
        15-min UnAvailable Second counter
        is invalid
        "
	::= { pm253PerfTelecomLinePast15StatHistoryPort2Entry 10 }


pm253PerfTelecomLinePast15StatHistoryUasValuePort2 OBJECT-TYPE
	SYNTAX  Unsigned32
	MAX-ACCESS read-only
	STATUS current
	DESCRIPTION
        "
        Previous 15-min UAS counter :This
        OID gives the previous 15-min UnAvailable
        Second counter value
        "
	::= { pm253PerfTelecomLinePast15StatHistoryPort2Entry 11 }


--- *****************************************************
---     Leaf of the telecomLineCurrent24Stat
--- *****************************************************
--- *********************************************************
---     TABLE for the pm253PerfTelecomLineCurrent24Stat articles
--- *********************************************************

pm253PerfTelecomLineCurrent24StatTable OBJECT-TYPE
	SYNTAX  SEQUENCE OF Pm253PerfTelecomLineCurrent24StatEntry
	MAX-ACCESS not-accessible
	STATUS current
	DESCRIPTION
        "
        List of pm253PerfTelecomLineCurrent24Stat
        Article
        "
	::= { pm253MonLine 130 }


pm253PerfTelecomLineCurrent24StatEntry OBJECT-TYPE
	SYNTAX Pm253PerfTelecomLineCurrent24StatEntry
	MAX-ACCESS not-accessible
	STATUS current
	DESCRIPTION
        "
        Row definition for the pm253PerfTelecomLineCurrent24Stat
        table
        "
	INDEX   { pm253PerfTelecomLineCurrent24StatIndex }
	::= { pm253PerfTelecomLineCurrent24StatTable 1 }


Pm253PerfTelecomLineCurrent24StatEntry ::=
	SEQUENCE {
	pm253PerfTelecomLineCurrent24StatIndex
		INTEGER,
	pm253PerfTelecomLineCurrent24StatInvCvPortn
		EkiOnOff,
	pm253PerfTelecomLineCurrent24StatCvValuePortn
		Unsigned32,
	pm253PerfTelecomLineCurrent24StatInvEsPortn
		EkiOnOff,
	pm253PerfTelecomLineCurrent24StatEsValuePortn
		Unsigned32,
	pm253PerfTelecomLineCurrent24StatInvSesPortn
		EkiOnOff,
	pm253PerfTelecomLineCurrent24StatSesValuePortn
		Unsigned32,
	pm253PerfTelecomLineCurrent24StatInvSefsPortn
		EkiOnOff,
	pm253PerfTelecomLineCurrent24StatSefsValuePortn
		Unsigned32,
	pm253PerfTelecomLineCurrent24StatInvUasPortn
		EkiOnOff,
	pm253PerfTelecomLineCurrent24StatUasValuePortn
		Unsigned32
	}


pm253PerfTelecomLineCurrent24StatIndex OBJECT-TYPE
	SYNTAX  INTEGER(0..128)
	MAX-ACCESS  read-only
	STATUS current
	DESCRIPTION
        "
        Index definition for the pm253PerfTelecomLineCurrent24Stat
        table
        "
	::= { pm253PerfTelecomLineCurrent24StatEntry 1 }


pm253PerfTelecomLineCurrent24StatInvCvPortn OBJECT-TYPE
	SYNTAX  EkiOnOff
	MAX-ACCESS read-only
	STATUS current
	DESCRIPTION
        "
        Current 24-hours CV counter inv.
        :This OID indicates that the current
        24-hours Coding Violation counter
        is invalid
        "
	::= { pm253PerfTelecomLineCurrent24StatEntry 2 }


pm253PerfTelecomLineCurrent24StatCvValuePortn OBJECT-TYPE
	SYNTAX  Unsigned32
	MAX-ACCESS read-only
	STATUS current
	DESCRIPTION
        "
        Current 24-hours CV counter :This
        OID gives the current 24-hours
         Coding Violation counter value
        "
	::= { pm253PerfTelecomLineCurrent24StatEntry 3 }


pm253PerfTelecomLineCurrent24StatInvEsPortn OBJECT-TYPE
	SYNTAX  EkiOnOff
	MAX-ACCESS read-only
	STATUS current
	DESCRIPTION
        "
        Current 24-hours ES counter inv.
        :This OID indicates that the current
        24-hours Errored Second counter
        is invalid
        "
	::= { pm253PerfTelecomLineCurrent24StatEntry 4 }


pm253PerfTelecomLineCurrent24StatEsValuePortn OBJECT-TYPE
	SYNTAX  Unsigned32
	MAX-ACCESS read-only
	STATUS current
	DESCRIPTION
        "
        Current 24-hours ES counter :This
        OID gives the current 24-hours
         Errored Second counter value
        "
	::= { pm253PerfTelecomLineCurrent24StatEntry 5 }


pm253PerfTelecomLineCurrent24StatInvSesPortn OBJECT-TYPE
	SYNTAX  EkiOnOff
	MAX-ACCESS read-only
	STATUS current
	DESCRIPTION
        "
        Current 24-hours SES counter inv.
        :This OID indicates that the current
        24-hours severely Errored Second
        counter is invalid
        "
	::= { pm253PerfTelecomLineCurrent24StatEntry 6 }


pm253PerfTelecomLineCurrent24StatSesValuePortn OBJECT-TYPE
	SYNTAX  Unsigned32
	MAX-ACCESS read-only
	STATUS current
	DESCRIPTION
        "
        Current 24-hours SES counter :This
        OID gives the current 24-hours
         severely Errored Second counter
        value
        "
	::= { pm253PerfTelecomLineCurrent24StatEntry 7 }


pm253PerfTelecomLineCurrent24StatInvSefsPortn OBJECT-TYPE
	SYNTAX  EkiOnOff
	MAX-ACCESS read-only
	STATUS current
	DESCRIPTION
        "
        Current 24-hours SEFS counter
         inv. :This OID indicates that
         the current 24-hours severely
         Errored Framing Second counter
        is invalid
        "
	::= { pm253PerfTelecomLineCurrent24StatEntry 8 }


pm253PerfTelecomLineCurrent24StatSefsValuePortn OBJECT-TYPE
	SYNTAX  Unsigned32
	MAX-ACCESS read-only
	STATUS current
	DESCRIPTION
        "
        Current 24-hours SEFS counter
         :This OID gives the current 24-hours
        severely Errored Framing Second
        counter value
        "
	::= { pm253PerfTelecomLineCurrent24StatEntry 9 }


pm253PerfTelecomLineCurrent24StatInvUasPortn OBJECT-TYPE
	SYNTAX  EkiOnOff
	MAX-ACCESS read-only
	STATUS current
	DESCRIPTION
        "
        Current 24-hours UAS counter inv.
        :This OID indicates that the current
        24-hours UnAvailable Second counter
        is invalid
        "
	::= { pm253PerfTelecomLineCurrent24StatEntry 10 }


pm253PerfTelecomLineCurrent24StatUasValuePortn OBJECT-TYPE
	SYNTAX  Unsigned32
	MAX-ACCESS read-only
	STATUS current
	DESCRIPTION
        "
        Current 24-hours UAS counter :This
        OID gives the current 24-hours
         UnAvailable Second counter value
        "
	::= { pm253PerfTelecomLineCurrent24StatEntry 11 }


--- *****************************************************
---     Leaf of the telecomLinePast24Stat
--- *****************************************************
--- *********************************************************
---     TABLE for the pm253PerfTelecomLinePast24StatHistory articles
--- *********************************************************

pm253PerfTelecomLinePast24StatHistoryPort1Table OBJECT-TYPE
	SYNTAX  SEQUENCE OF Pm253PerfTelecomLinePast24StatHistoryPort1Entry
	MAX-ACCESS not-accessible
	STATUS current
	DESCRIPTION
        "
        List of pm253PerfTelecomLinePast24StatHistory
        Article
        "
	::= { pm253MonLine 131 }


pm253PerfTelecomLinePast24StatHistoryPort1Entry OBJECT-TYPE
	SYNTAX Pm253PerfTelecomLinePast24StatHistoryPort1Entry
	MAX-ACCESS not-accessible
	STATUS current
	DESCRIPTION
        "
        Row definition for the pm253PerfTelecomLinePast24StatHistory
        table
        "
	INDEX   { pm253PerfTelecomLinePast24StatHistoryPort1Index }
	::= { pm253PerfTelecomLinePast24StatHistoryPort1Table 1 }


Pm253PerfTelecomLinePast24StatHistoryPort1Entry ::=
	SEQUENCE {
	pm253PerfTelecomLinePast24StatHistoryPort1Index
		INTEGER,
	pm253PerfTelecomLinePast24StatHistoryInvCvPort1
		EkiOnOff,
	pm253PerfTelecomLinePast24StatHistoryCvValuePort1
		Unsigned32,
	pm253PerfTelecomLinePast24StatHistoryInvEsPort1
		EkiOnOff,
	pm253PerfTelecomLinePast24StatHistoryEsValuePort1
		Unsigned32,
	pm253PerfTelecomLinePast24StatHistoryInvSesPort1
		EkiOnOff,
	pm253PerfTelecomLinePast24StatHistorySesValuePort1
		Unsigned32,
	pm253PerfTelecomLinePast24StatHistoryInvSefsPort1
		EkiOnOff,
	pm253PerfTelecomLinePast24StatHistorySefsValuePort1
		Unsigned32,
	pm253PerfTelecomLinePast24StatHistoryInvUasPort1
		EkiOnOff,
	pm253PerfTelecomLinePast24StatHistoryUasValuePort1
		Unsigned32
	}


pm253PerfTelecomLinePast24StatHistoryPort1Index OBJECT-TYPE
	SYNTAX  INTEGER(0..128)
	MAX-ACCESS  read-only
	STATUS current
	DESCRIPTION
        "
        Index definition for the pm253PerfTelecomLinePast24StatHistory
        table
        "
	::= { pm253PerfTelecomLinePast24StatHistoryPort1Entry 1 }


pm253PerfTelecomLinePast24StatHistoryInvCvPort1 OBJECT-TYPE
	SYNTAX  EkiOnOff
	MAX-ACCESS read-only
	STATUS current
	DESCRIPTION
        "
        Previous 24-hours CV counter inv.
        :This OID indicates that the previous
        24-hours Coding Violation counter
        is invalid
        "
	::= { pm253PerfTelecomLinePast24StatHistoryPort1Entry 2 }


pm253PerfTelecomLinePast24StatHistoryCvValuePort1 OBJECT-TYPE
	SYNTAX  Unsigned32
	MAX-ACCESS read-only
	STATUS current
	DESCRIPTION
        "
        Previous 24-hours CV counter :This
        OID gives the previous 24-hours
        Coding Violation counter value
        "
	::= { pm253PerfTelecomLinePast24StatHistoryPort1Entry 3 }


pm253PerfTelecomLinePast24StatHistoryInvEsPort1 OBJECT-TYPE
	SYNTAX  EkiOnOff
	MAX-ACCESS read-only
	STATUS current
	DESCRIPTION
        "
        Previous 24-hours ES counter inv.
        :This OID indicates that the previous
        24-hours Errored Second counter
        is invalid
        "
	::= { pm253PerfTelecomLinePast24StatHistoryPort1Entry 4 }


pm253PerfTelecomLinePast24StatHistoryEsValuePort1 OBJECT-TYPE
	SYNTAX  Unsigned32
	MAX-ACCESS read-only
	STATUS current
	DESCRIPTION
        "
        Previous 24-hours ES counter :This
        OID gives the previous 24-hours
        Errored Second counter value
        "
	::= { pm253PerfTelecomLinePast24StatHistoryPort1Entry 5 }


pm253PerfTelecomLinePast24StatHistoryInvSesPort1 OBJECT-TYPE
	SYNTAX  EkiOnOff
	MAX-ACCESS read-only
	STATUS current
	DESCRIPTION
        "
        Previous 24-hours SES counter
         inv. :This OID indicates that
         the previous 24-hours severely
        Errored Second counter is invalid
        "
	::= { pm253PerfTelecomLinePast24StatHistoryPort1Entry 6 }


pm253PerfTelecomLinePast24StatHistorySesValuePort1 OBJECT-TYPE
	SYNTAX  Unsigned32
	MAX-ACCESS read-only
	STATUS current
	DESCRIPTION
        "
        Previous 24-hours SES counter
         :This OID gives the previous 24-hours
        severely Errored Second counter
        value
        "
	::= { pm253PerfTelecomLinePast24StatHistoryPort1Entry 7 }


pm253PerfTelecomLinePast24StatHistoryInvSefsPort1 OBJECT-TYPE
	SYNTAX  EkiOnOff
	MAX-ACCESS read-only
	STATUS current
	DESCRIPTION
        "
        Previous 24-hours SEFS counter
        inv. :This OID indicates that the
        previous 24-hours severely Errored
        Framing Second counter is invalid
        "
	::= { pm253PerfTelecomLinePast24StatHistoryPort1Entry 8 }


pm253PerfTelecomLinePast24StatHistorySefsValuePort1 OBJECT-TYPE
	SYNTAX  Unsigned32
	MAX-ACCESS read-only
	STATUS current
	DESCRIPTION
        "
        Previous 24-hours SEFS counter
        :This OID gives the previous 24-hours
        severely Errored Framing Second
        counter value
        "
	::= { pm253PerfTelecomLinePast24StatHistoryPort1Entry 9 }


pm253PerfTelecomLinePast24StatHistoryInvUasPort1 OBJECT-TYPE
	SYNTAX  EkiOnOff
	MAX-ACCESS read-only
	STATUS current
	DESCRIPTION
        "
        Previous 24-hours UAS counter
         inv. :This OID indicates that
         the previous 24-hours UnAvailable
        Second counter is invalid
        "
	::= { pm253PerfTelecomLinePast24StatHistoryPort1Entry 10 }


pm253PerfTelecomLinePast24StatHistoryUasValuePort1 OBJECT-TYPE
	SYNTAX  Unsigned32
	MAX-ACCESS read-only
	STATUS current
	DESCRIPTION
        "
        Previous 24-hours UAS counter
         :This OID gives the previous 24-hours
        UnAvailable Second counter value
        "
	::= { pm253PerfTelecomLinePast24StatHistoryPort1Entry 11 }


--- *********************************************************
---     TABLE for the pm253PerfTelecomLinePast24StatHistory articles
--- *********************************************************

pm253PerfTelecomLinePast24StatHistoryPort2Table OBJECT-TYPE
	SYNTAX  SEQUENCE OF Pm253PerfTelecomLinePast24StatHistoryPort2Entry
	MAX-ACCESS not-accessible
	STATUS current
	DESCRIPTION
        "
        List of pm253PerfTelecomLinePast24StatHistory
        Article
        "
	::= { pm253MonLine 147 }


pm253PerfTelecomLinePast24StatHistoryPort2Entry OBJECT-TYPE
	SYNTAX Pm253PerfTelecomLinePast24StatHistoryPort2Entry
	MAX-ACCESS not-accessible
	STATUS current
	DESCRIPTION
        "
        Row definition for the pm253PerfTelecomLinePast24StatHistory
        table
        "
	INDEX   { pm253PerfTelecomLinePast24StatHistoryPort2Index }
	::= { pm253PerfTelecomLinePast24StatHistoryPort2Table 1 }


Pm253PerfTelecomLinePast24StatHistoryPort2Entry ::=
	SEQUENCE {
	pm253PerfTelecomLinePast24StatHistoryPort2Index
		INTEGER,
	pm253PerfTelecomLinePast24StatHistoryInvCvPort2
		EkiOnOff,
	pm253PerfTelecomLinePast24StatHistoryCvValuePort2
		Unsigned32,
	pm253PerfTelecomLinePast24StatHistoryInvEsPort2
		EkiOnOff,
	pm253PerfTelecomLinePast24StatHistoryEsValuePort2
		Unsigned32,
	pm253PerfTelecomLinePast24StatHistoryInvSesPort2
		EkiOnOff,
	pm253PerfTelecomLinePast24StatHistorySesValuePort2
		Unsigned32,
	pm253PerfTelecomLinePast24StatHistoryInvSefsPort2
		EkiOnOff,
	pm253PerfTelecomLinePast24StatHistorySefsValuePort2
		Unsigned32,
	pm253PerfTelecomLinePast24StatHistoryInvUasPort2
		EkiOnOff,
	pm253PerfTelecomLinePast24StatHistoryUasValuePort2
		Unsigned32
	}


pm253PerfTelecomLinePast24StatHistoryPort2Index OBJECT-TYPE
	SYNTAX  INTEGER(0..128)
	MAX-ACCESS  read-only
	STATUS current
	DESCRIPTION
        "
        Index definition for the pm253PerfTelecomLinePast24StatHistory
        table
        "
	::= { pm253PerfTelecomLinePast24StatHistoryPort2Entry 1 }


pm253PerfTelecomLinePast24StatHistoryInvCvPort2 OBJECT-TYPE
	SYNTAX  EkiOnOff
	MAX-ACCESS read-only
	STATUS current
	DESCRIPTION
        "
        Previous 24-hours CV counter inv.
        :This OID indicates that the previous
        24-hours Coding Violation counter
        is invalid
        "
	::= { pm253PerfTelecomLinePast24StatHistoryPort2Entry 2 }


pm253PerfTelecomLinePast24StatHistoryCvValuePort2 OBJECT-TYPE
	SYNTAX  Unsigned32
	MAX-ACCESS read-only
	STATUS current
	DESCRIPTION
        "
        Previous 24-hours CV counter :This
        OID gives the previous 24-hours
        Coding Violation counter value
        "
	::= { pm253PerfTelecomLinePast24StatHistoryPort2Entry 3 }


pm253PerfTelecomLinePast24StatHistoryInvEsPort2 OBJECT-TYPE
	SYNTAX  EkiOnOff
	MAX-ACCESS read-only
	STATUS current
	DESCRIPTION
        "
        Previous 24-hours ES counter inv.
        :This OID indicates that the previous
        24-hours Errored Second counter
        is invalid
        "
	::= { pm253PerfTelecomLinePast24StatHistoryPort2Entry 4 }


pm253PerfTelecomLinePast24StatHistoryEsValuePort2 OBJECT-TYPE
	SYNTAX  Unsigned32
	MAX-ACCESS read-only
	STATUS current
	DESCRIPTION
        "
        Previous 24-hours ES counter :This
        OID gives the previous 24-hours
        Errored Second counter value
        "
	::= { pm253PerfTelecomLinePast24StatHistoryPort2Entry 5 }


pm253PerfTelecomLinePast24StatHistoryInvSesPort2 OBJECT-TYPE
	SYNTAX  EkiOnOff
	MAX-ACCESS read-only
	STATUS current
	DESCRIPTION
        "
        Previous 24-hours SES counter
         inv. :This OID indicates that
         the previous 24-hours severely
        Errored Second counter is invalid
        "
	::= { pm253PerfTelecomLinePast24StatHistoryPort2Entry 6 }


pm253PerfTelecomLinePast24StatHistorySesValuePort2 OBJECT-TYPE
	SYNTAX  Unsigned32
	MAX-ACCESS read-only
	STATUS current
	DESCRIPTION
        "
        Previous 24-hours SES counter
         :This OID gives the previous 24-hours
        severely Errored Second counter
        value
        "
	::= { pm253PerfTelecomLinePast24StatHistoryPort2Entry 7 }


pm253PerfTelecomLinePast24StatHistoryInvSefsPort2 OBJECT-TYPE
	SYNTAX  EkiOnOff
	MAX-ACCESS read-only
	STATUS current
	DESCRIPTION
        "
        Previous 24-hours SEFS counter
        inv. :This OID indicates that the
        previous 24-hours severely Errored
        Framing Second counter is invalid
        "
	::= { pm253PerfTelecomLinePast24StatHistoryPort2Entry 8 }


pm253PerfTelecomLinePast24StatHistorySefsValuePort2 OBJECT-TYPE
	SYNTAX  Unsigned32
	MAX-ACCESS read-only
	STATUS current
	DESCRIPTION
        "
        Previous 24-hours SEFS counter
        :This OID gives the previous 24-hours
        severely Errored Framing Second
        counter value
        "
	::= { pm253PerfTelecomLinePast24StatHistoryPort2Entry 9 }


pm253PerfTelecomLinePast24StatHistoryInvUasPort2 OBJECT-TYPE
	SYNTAX  EkiOnOff
	MAX-ACCESS read-only
	STATUS current
	DESCRIPTION
        "
        Previous 24-hours UAS counter
         inv. :This OID indicates that
         the previous 24-hours UnAvailable
        Second counter is invalid
        "
	::= { pm253PerfTelecomLinePast24StatHistoryPort2Entry 10 }


pm253PerfTelecomLinePast24StatHistoryUasValuePort2 OBJECT-TYPE
	SYNTAX  Unsigned32
	MAX-ACCESS read-only
	STATUS current
	DESCRIPTION
        "
        Previous 24-hours UAS counter
         :This OID gives the previous 24-hours
        UnAvailable Second counter value
        "
	::= { pm253PerfTelecomLinePast24StatHistoryPort2Entry 11 }


--- *****************************************************
---     Leaf of the datacomClientCurrent15Stat
--- *****************************************************
--- *********************************************************
---     TABLE for the pm253PerfDatacomClientCurrent15Stat articles
--- *********************************************************

pm253PerfDatacomClientCurrent15StatTable OBJECT-TYPE
	SYNTAX  SEQUENCE OF Pm253PerfDatacomClientCurrent15StatEntry
	MAX-ACCESS not-accessible
	STATUS current
	DESCRIPTION
        "
        List of pm253PerfDatacomClientCurrent15Stat
        Article
        "
	::= { pm253MonClient 256 }


pm253PerfDatacomClientCurrent15StatEntry OBJECT-TYPE
	SYNTAX Pm253PerfDatacomClientCurrent15StatEntry
	MAX-ACCESS not-accessible
	STATUS current
	DESCRIPTION
        "
        Row definition for the pm253PerfDatacomClientCurrent15Stat
        table
        "
	INDEX   { pm253PerfDatacomClientCurrent15StatIndex }
	::= { pm253PerfDatacomClientCurrent15StatTable 1 }


Pm253PerfDatacomClientCurrent15StatEntry ::=
	SEQUENCE {
	pm253PerfDatacomClientCurrent15StatIndex
		INTEGER,
	pm253perfdatacomclientCurrent15StatOutNonunicastCountInvPortn
		EkiOnOff,
	pm253perfdatacomclientCurrent15StatOutNonunicastCountPortn
		Counter64,
	pm253perfdatacomclientCurrent15StatOutUnicastCountInvPortn
		EkiOnOff,
	pm253perfdatacomclientCurrent15StatOutUnicastCountPortn
		Counter64,
	pm253perfdatacomclientCurrent15StatOutMulticastCountInvPortn
		EkiOnOff,
	pm253perfdatacomclientCurrent15StatOutMulticastCountPortn
		Counter64,
	pm253perfdatacomclientCurrent15StatOutBroadcastCountInvPortn
		EkiOnOff,
	pm253perfdatacomclientCurrent15StatOutBroadcastCountPortn
		Counter64,
	pm253perfdatacomclientCurrent15StatOutBytesCountInvPortn
		EkiOnOff,
	pm253perfdatacomclientCurrent15StatOutBytesCountPortn
		Counter64,
	pm253perfdatacomclientCurrent15StatInNonunicastCountInvPortn
		EkiOnOff,
	pm253perfdatacomclientCurrent15StatInNonunicastCountPortn
		Counter64,
	pm253perfdatacomclientCurrent15StatInUnicastCountInvPortn
		EkiOnOff,
	pm253perfdatacomclientCurrent15StatInUnicastCountPortn
		Counter64,
	pm253perfdatacomclientCurrent15StatInMulticastCountInvPortn
		EkiOnOff,
	pm253perfdatacomclientCurrent15StatInMulticastCountPortn
		Counter64,
	pm253perfdatacomclientCurrent15StatInBroadcastCountInvPortn
		EkiOnOff,
	pm253perfdatacomclientCurrent15StatInBroadcastCountPortn
		Counter64,
	pm253perfdatacomclientCurrent15StatInCrcCountInvPortn
		EkiOnOff,
	pm253perfdatacomclientCurrent15StatInCrcCountPortn
		Counter64,
	pm253perfdatacomclientCurrent15StatInBytesCountInvPortn
		EkiOnOff,
	pm253perfdatacomclientCurrent15StatInBytesCountPortn
		Counter64
	}


pm253PerfDatacomClientCurrent15StatIndex OBJECT-TYPE
	SYNTAX  INTEGER(0..128)
	MAX-ACCESS  read-only
	STATUS current
	DESCRIPTION
        "
        Index definition for the pm253PerfDatacomClientCurrent15Stat
        table
        "
	::= { pm253PerfDatacomClientCurrent15StatEntry 1 }


pm253perfdatacomclientCurrent15StatOutNonunicastCountInvPortn OBJECT-TYPE
	SYNTAX  EkiOnOff
	MAX-ACCESS read-only
	STATUS current
	DESCRIPTION
        "
        Client Current 15-min Output Non
        Unicast counter inv. :This OID
         indicates that the current 15-min
        Non Unicast counter is invalid
        "
	::= { pm253PerfDatacomClientCurrent15StatEntry 44 }


pm253perfdatacomclientCurrent15StatOutNonunicastCountPortn OBJECT-TYPE
	SYNTAX  Counter64
	MAX-ACCESS read-only
	STATUS current
	DESCRIPTION
        "
        Client Current 15-min Output Non
        Unicast counter :This OID gives
        the current 15-min Non Unicast
         counter value
        "
	::= { pm253PerfDatacomClientCurrent15StatEntry 45 }


pm253perfdatacomclientCurrent15StatOutUnicastCountInvPortn OBJECT-TYPE
	SYNTAX  EkiOnOff
	MAX-ACCESS read-only
	STATUS current
	DESCRIPTION
        "
        Client Current 15-min Output Unicast
        counter inv. :This OID indicates
        that the current 15-min Unicast
        counter is invalid
        "
	::= { pm253PerfDatacomClientCurrent15StatEntry 42 }


pm253perfdatacomclientCurrent15StatOutUnicastCountPortn OBJECT-TYPE
	SYNTAX  Counter64
	MAX-ACCESS read-only
	STATUS current
	DESCRIPTION
        "
        Client Current 15-min Output Unicast
        counter :This OID gives the current
        15-min Unicast counter value
        "
	::= { pm253PerfDatacomClientCurrent15StatEntry 43 }


pm253perfdatacomclientCurrent15StatOutMulticastCountInvPortn OBJECT-TYPE
	SYNTAX  EkiOnOff
	MAX-ACCESS read-only
	STATUS current
	DESCRIPTION
        "
        Client Current 15-min Output Multicast
        counter inv. :This OID indicates
        that the current 15-min Multicast
        counter is invalid
        "
	::= { pm253PerfDatacomClientCurrent15StatEntry 34 }


pm253perfdatacomclientCurrent15StatOutMulticastCountPortn OBJECT-TYPE
	SYNTAX  Counter64
	MAX-ACCESS read-only
	STATUS current
	DESCRIPTION
        "
        Client Current 15-min Output Multicast
        counter :This OID gives the current
        15-min Multicast counter value
        "
	::= { pm253PerfDatacomClientCurrent15StatEntry 35 }


pm253perfdatacomclientCurrent15StatOutBroadcastCountInvPortn OBJECT-TYPE
	SYNTAX  EkiOnOff
	MAX-ACCESS read-only
	STATUS current
	DESCRIPTION
        "
        Client Current 15-min Output Broadcast
        counter inv. :This OID indicates
        that the current 15-min Broadcast
        counter is invalid
        "
	::= { pm253PerfDatacomClientCurrent15StatEntry 32 }


pm253perfdatacomclientCurrent15StatOutBroadcastCountPortn OBJECT-TYPE
	SYNTAX  Counter64
	MAX-ACCESS read-only
	STATUS current
	DESCRIPTION
        "
        Client Current 15-min Output Broadcast
        counter :This OID gives the current
        15-min Broadcast counter value
        "
	::= { pm253PerfDatacomClientCurrent15StatEntry 33 }


pm253perfdatacomclientCurrent15StatOutBytesCountInvPortn OBJECT-TYPE
	SYNTAX  EkiOnOff
	MAX-ACCESS read-only
	STATUS current
	DESCRIPTION
        "
        Client Current 15-min Output Bytes
        counter inv. :This OID indicates
        that the current 15-min Bytes counter
        is invalid
        "
	::= { pm253PerfDatacomClientCurrent15StatEntry 26 }


pm253perfdatacomclientCurrent15StatOutBytesCountPortn OBJECT-TYPE
	SYNTAX  Counter64
	MAX-ACCESS read-only
	STATUS current
	DESCRIPTION
        "
        Client Current 15-min Output Bytes
        counter :This OID gives the current
        15-min Bytes counter value
        "
	::= { pm253PerfDatacomClientCurrent15StatEntry 27 }


pm253perfdatacomclientCurrent15StatInNonunicastCountInvPortn OBJECT-TYPE
	SYNTAX  EkiOnOff
	MAX-ACCESS read-only
	STATUS current
	DESCRIPTION
        "
        Client Current 15-min Input Non
        Unicast counter inv. :This OID
         indicates that the current 15-min
        Non unicast counter is invalid
        "
	::= { pm253PerfDatacomClientCurrent15StatEntry 22 }


pm253perfdatacomclientCurrent15StatInNonunicastCountPortn OBJECT-TYPE
	SYNTAX  Counter64
	MAX-ACCESS read-only
	STATUS current
	DESCRIPTION
        "
        Client Current 15-min Input Non
        Unicast counter :This OID gives
        the current 15-min Non Unicast
         counter value
        "
	::= { pm253PerfDatacomClientCurrent15StatEntry 23 }


pm253perfdatacomclientCurrent15StatInUnicastCountInvPortn OBJECT-TYPE
	SYNTAX  EkiOnOff
	MAX-ACCESS read-only
	STATUS current
	DESCRIPTION
        "
        Client Current 15-min Input Unicast
        counter inv. :This OID indicates
        that the current 15-min Unicast
        counter is invalid
        "
	::= { pm253PerfDatacomClientCurrent15StatEntry 20 }


pm253perfdatacomclientCurrent15StatInUnicastCountPortn OBJECT-TYPE
	SYNTAX  Counter64
	MAX-ACCESS read-only
	STATUS current
	DESCRIPTION
        "
        Client Current 15-min Input Unicast
        counter :This OID gives the current
        15-min Unicast counter value
        "
	::= { pm253PerfDatacomClientCurrent15StatEntry 21 }


pm253perfdatacomclientCurrent15StatInMulticastCountInvPortn OBJECT-TYPE
	SYNTAX  EkiOnOff
	MAX-ACCESS read-only
	STATUS current
	DESCRIPTION
        "
        Client Current 15-min Input Multicast
        counter inv. :This OID indicates
        that the current 15-min Multicast
        counter is invalid
        "
	::= { pm253PerfDatacomClientCurrent15StatEntry 10 }


pm253perfdatacomclientCurrent15StatInMulticastCountPortn OBJECT-TYPE
	SYNTAX  Counter64
	MAX-ACCESS read-only
	STATUS current
	DESCRIPTION
        "
        Client Current 15-min Input Multicast
        counter :This OID gives the current
        15-min Multicast counter value
        "
	::= { pm253PerfDatacomClientCurrent15StatEntry 11 }


pm253perfdatacomclientCurrent15StatInBroadcastCountInvPortn OBJECT-TYPE
	SYNTAX  EkiOnOff
	MAX-ACCESS read-only
	STATUS current
	DESCRIPTION
        "
        Client Current 15-min Input Broadcast
        counter inv. :This OID indicates
        that the current 15-min Broadcast
        counter is invalid
        "
	::= { pm253PerfDatacomClientCurrent15StatEntry 8 }


pm253perfdatacomclientCurrent15StatInBroadcastCountPortn OBJECT-TYPE
	SYNTAX  Counter64
	MAX-ACCESS read-only
	STATUS current
	DESCRIPTION
        "
        Client Current 15-min Input Broadcast
        counter :This OID gives the current
        15-min Broadcast counter value
        "
	::= { pm253PerfDatacomClientCurrent15StatEntry 9 }


pm253perfdatacomclientCurrent15StatInCrcCountInvPortn OBJECT-TYPE
	SYNTAX  EkiOnOff
	MAX-ACCESS read-only
	STATUS current
	DESCRIPTION
        "
        Client Current 15-min Input CRC
        counter inv. :This OID indicates
        that the current 15-min CRC counter
        is invalid
        "
	::= { pm253PerfDatacomClientCurrent15StatEntry 4 }


pm253perfdatacomclientCurrent15StatInCrcCountPortn OBJECT-TYPE
	SYNTAX  Counter64
	MAX-ACCESS read-only
	STATUS current
	DESCRIPTION
        "
        Client Current 15-min Input CRC
        counter :This OID gives the current
        15-min CRC counter value
        "
	::= { pm253PerfDatacomClientCurrent15StatEntry 5 }


pm253perfdatacomclientCurrent15StatInBytesCountInvPortn OBJECT-TYPE
	SYNTAX  EkiOnOff
	MAX-ACCESS read-only
	STATUS current
	DESCRIPTION
        "
        Client Current 15-min Input Bytes
        counter inv. :This OID indicates
        that the current 15-min Bytes counter
        is invalid
        "
	::= { pm253PerfDatacomClientCurrent15StatEntry 2 }


pm253perfdatacomclientCurrent15StatInBytesCountPortn OBJECT-TYPE
	SYNTAX  Counter64
	MAX-ACCESS read-only
	STATUS current
	DESCRIPTION
        "
        Client Current 15-min Input Bytes
        counter :This OID gives the current
        15-min Bytes counter value
        "
	::= { pm253PerfDatacomClientCurrent15StatEntry 3 }


--- *****************************************************
---     Leaf of the datacomClientPast15Stat
--- *****************************************************
--- *********************************************************
---     TABLE for the pm253PerfDatacomClientPast15StatHistory articles
--- *********************************************************

pm253PerfDatacomClientPast15StatHistoryPort1Table OBJECT-TYPE
	SYNTAX  SEQUENCE OF Pm253PerfDatacomClientPast15StatHistoryPort1Entry
	MAX-ACCESS not-accessible
	STATUS current
	DESCRIPTION
        "
        List of pm253PerfDatacomClientPast15StatHistory
        Article
        "
	::= { pm253MonClient 264 }


pm253PerfDatacomClientPast15StatHistoryPort1Entry OBJECT-TYPE
	SYNTAX Pm253PerfDatacomClientPast15StatHistoryPort1Entry
	MAX-ACCESS not-accessible
	STATUS current
	DESCRIPTION
        "
        Row definition for the pm253PerfDatacomClientPast15StatHistory
        table
        "
	INDEX   { pm253PerfDatacomClientPast15StatHistoryPort1Index }
	::= { pm253PerfDatacomClientPast15StatHistoryPort1Table 1 }


Pm253PerfDatacomClientPast15StatHistoryPort1Entry ::=
	SEQUENCE {
	pm253PerfDatacomClientPast15StatHistoryPort1Index
		INTEGER,
	pm253perfdatacomclientPast15StatOutNonunicastCountInvPort1
		EkiOnOff,
	pm253perfdatacomclientPast15StatOutNonunicastCountPort1
		Counter64,
	pm253perfdatacomclientPast15StatOutUnicastCountInvPort1
		EkiOnOff,
	pm253perfdatacomclientPast15StatOutUnicastCountPort1
		Counter64,
	pm253perfdatacomclientPast15StatOutMulticastCountInvPort1
		EkiOnOff,
	pm253perfdatacomclientPast15StatOutMulticastCountPort1
		Counter64,
	pm253perfdatacomclientPast15StatOutBroadcastCountInvPort1
		EkiOnOff,
	pm253perfdatacomclientPast15StatOutBroadcastCountPort1
		Counter64,
	pm253perfdatacomclientPast15StatOutBytesCountInvPort1
		EkiOnOff,
	pm253perfdatacomclientPast15StatOutBytesCountPort1
		Counter64,
	pm253perfdatacomclientPast15StatInNonunicastCountInvPort1
		EkiOnOff,
	pm253perfdatacomclientPast15StatInNonunicastCountPort1
		Counter64,
	pm253perfdatacomclientPast15StatInUnicastCountInvPort1
		EkiOnOff,
	pm253perfdatacomclientPast15StatInUnicastCountPort1
		Counter64,
	pm253perfdatacomclientPast15StatInMulticastCountInvPort1
		EkiOnOff,
	pm253perfdatacomclientPast15StatInMulticastCountPort1
		Counter64,
	pm253perfdatacomclientPast15StatInBroadcastCountInvPort1
		EkiOnOff,
	pm253perfdatacomclientPast15StatInBroadcastCountPort1
		Counter64,
	pm253perfdatacomclientPast15StatInCrcCountInvPort1
		EkiOnOff,
	pm253perfdatacomclientPast15StatInCrcCountPort1
		Counter64,
	pm253perfdatacomclientPast15StatInBytesCountInvPort1
		EkiOnOff,
	pm253perfdatacomclientPast15StatInBytesCountPort1
		Counter64
	}


pm253PerfDatacomClientPast15StatHistoryPort1Index OBJECT-TYPE
	SYNTAX  INTEGER(0..128)
	MAX-ACCESS  read-only
	STATUS current
	DESCRIPTION
        "
        Index definition for the pm253PerfDatacomClientPast15StatHistory
        table
        "
	::= { pm253PerfDatacomClientPast15StatHistoryPort1Entry 1 }


pm253perfdatacomclientPast15StatOutNonunicastCountInvPort1 OBJECT-TYPE
	SYNTAX  EkiOnOff
	MAX-ACCESS read-only
	STATUS current
	DESCRIPTION
        "
        Client Past 15-min Output Non
         Unicast counter inv. :This OID
        indicates that the past 15-min
         Non Unicast counter is invalid
        "
	::= { pm253PerfDatacomClientPast15StatHistoryPort1Entry 44 }


pm253perfdatacomclientPast15StatOutNonunicastCountPort1 OBJECT-TYPE
	SYNTAX  Counter64
	MAX-ACCESS read-only
	STATUS current
	DESCRIPTION
        "
        Client Past 15-min Output Non
         Unicast counter :This OID gives
        the past 15-min Non Unicast counter
        value
        "
	::= { pm253PerfDatacomClientPast15StatHistoryPort1Entry 45 }


pm253perfdatacomclientPast15StatOutUnicastCountInvPort1 OBJECT-TYPE
	SYNTAX  EkiOnOff
	MAX-ACCESS read-only
	STATUS current
	DESCRIPTION
        "
        Client Past 15-min Output Unicast
        counter inv. :This OID indicates
        that the past 15-min Unicast counter
        is invalid
        "
	::= { pm253PerfDatacomClientPast15StatHistoryPort1Entry 42 }


pm253perfdatacomclientPast15StatOutUnicastCountPort1 OBJECT-TYPE
	SYNTAX  Counter64
	MAX-ACCESS read-only
	STATUS current
	DESCRIPTION
        "
        Client Past 15-min Output Unicast
        counter :This OID gives the past
        15-min Unicast counter value
        "
	::= { pm253PerfDatacomClientPast15StatHistoryPort1Entry 43 }


pm253perfdatacomclientPast15StatOutMulticastCountInvPort1 OBJECT-TYPE
	SYNTAX  EkiOnOff
	MAX-ACCESS read-only
	STATUS current
	DESCRIPTION
        "
        Client Past 15-min Output Multicast
        counter inv. :This OID indicates
        that the past 15-min Multicast
         counter is invalid
        "
	::= { pm253PerfDatacomClientPast15StatHistoryPort1Entry 34 }


pm253perfdatacomclientPast15StatOutMulticastCountPort1 OBJECT-TYPE
	SYNTAX  Counter64
	MAX-ACCESS read-only
	STATUS current
	DESCRIPTION
        "
        Client Past 15-min Output Multicast
        counter :This OID gives the past
        15-min Multicast counter value
        "
	::= { pm253PerfDatacomClientPast15StatHistoryPort1Entry 35 }


pm253perfdatacomclientPast15StatOutBroadcastCountInvPort1 OBJECT-TYPE
	SYNTAX  EkiOnOff
	MAX-ACCESS read-only
	STATUS current
	DESCRIPTION
        "
        Client Past 15-min Output Broadcast
        counter inv. :This OID indicates
        that the past 15-min Broadcast
         counter is invalid
        "
	::= { pm253PerfDatacomClientPast15StatHistoryPort1Entry 32 }


pm253perfdatacomclientPast15StatOutBroadcastCountPort1 OBJECT-TYPE
	SYNTAX  Counter64
	MAX-ACCESS read-only
	STATUS current
	DESCRIPTION
        "
        Client Past 15-min Output Broadcast
        counter :This OID gives the past
        15-min Broadcast counter value
        "
	::= { pm253PerfDatacomClientPast15StatHistoryPort1Entry 33 }


pm253perfdatacomclientPast15StatOutBytesCountInvPort1 OBJECT-TYPE
	SYNTAX  EkiOnOff
	MAX-ACCESS read-only
	STATUS current
	DESCRIPTION
        "
        Client Past 15-min Output Bytes
        counter inv. :This OID indicates
        that the past 15-min Bytes counter
        is invalid
        "
	::= { pm253PerfDatacomClientPast15StatHistoryPort1Entry 26 }


pm253perfdatacomclientPast15StatOutBytesCountPort1 OBJECT-TYPE
	SYNTAX  Counter64
	MAX-ACCESS read-only
	STATUS current
	DESCRIPTION
        "
        Client Past 15-min Output Bytes
        counter :This OID gives the past
        15-min Bytes counter value
        "
	::= { pm253PerfDatacomClientPast15StatHistoryPort1Entry 27 }


pm253perfdatacomclientPast15StatInNonunicastCountInvPort1 OBJECT-TYPE
	SYNTAX  EkiOnOff
	MAX-ACCESS read-only
	STATUS current
	DESCRIPTION
        "
        Client Past 15-min Input Non Unicast
        counter inv. :This OID indicates
        that the past 15-min Non unicast
        counter is invalid
        "
	::= { pm253PerfDatacomClientPast15StatHistoryPort1Entry 22 }


pm253perfdatacomclientPast15StatInNonunicastCountPort1 OBJECT-TYPE
	SYNTAX  Counter64
	MAX-ACCESS read-only
	STATUS current
	DESCRIPTION
        "
        Client Past 15-min Input Non Unicast
        counter :This OID gives the past
        15-min Non Unicast counter value
        "
	::= { pm253PerfDatacomClientPast15StatHistoryPort1Entry 23 }


pm253perfdatacomclientPast15StatInUnicastCountInvPort1 OBJECT-TYPE
	SYNTAX  EkiOnOff
	MAX-ACCESS read-only
	STATUS current
	DESCRIPTION
        "
        Client Past 15-min Input Unicast
        counter inv. :This OID indicates
        that the past 15-min Unicast counter
        is invalid
        "
	::= { pm253PerfDatacomClientPast15StatHistoryPort1Entry 20 }


pm253perfdatacomclientPast15StatInUnicastCountPort1 OBJECT-TYPE
	SYNTAX  Counter64
	MAX-ACCESS read-only
	STATUS current
	DESCRIPTION
        "
        Client Past 15-min Input Unicast
        counter :This OID gives the past
        15-min Unicast counter value
        "
	::= { pm253PerfDatacomClientPast15StatHistoryPort1Entry 21 }


pm253perfdatacomclientPast15StatInMulticastCountInvPort1 OBJECT-TYPE
	SYNTAX  EkiOnOff
	MAX-ACCESS read-only
	STATUS current
	DESCRIPTION
        "
        Client Past 15-min Input Multicast
        counter inv. :This OID indicates
        that the past 15-min Multicast
         counter is invalid
        "
	::= { pm253PerfDatacomClientPast15StatHistoryPort1Entry 10 }


pm253perfdatacomclientPast15StatInMulticastCountPort1 OBJECT-TYPE
	SYNTAX  Counter64
	MAX-ACCESS read-only
	STATUS current
	DESCRIPTION
        "
        Client Past 15-min Input Multicast
        counter :This OID gives the past
        15-min Multicast counter value
        "
	::= { pm253PerfDatacomClientPast15StatHistoryPort1Entry 11 }


pm253perfdatacomclientPast15StatInBroadcastCountInvPort1 OBJECT-TYPE
	SYNTAX  EkiOnOff
	MAX-ACCESS read-only
	STATUS current
	DESCRIPTION
        "
        Client Past 15-min Input Broadcast
        counter inv. :This OID indicates
        that the past 15-min Broadcast
         counter is invalid
        "
	::= { pm253PerfDatacomClientPast15StatHistoryPort1Entry 8 }


pm253perfdatacomclientPast15StatInBroadcastCountPort1 OBJECT-TYPE
	SYNTAX  Counter64
	MAX-ACCESS read-only
	STATUS current
	DESCRIPTION
        "
        Client Past 15-min Input Broadcast
        counter :This OID gives the past
        15-min Broadcast counter value
        "
	::= { pm253PerfDatacomClientPast15StatHistoryPort1Entry 9 }


pm253perfdatacomclientPast15StatInCrcCountInvPort1 OBJECT-TYPE
	SYNTAX  EkiOnOff
	MAX-ACCESS read-only
	STATUS current
	DESCRIPTION
        "
        Client Past 15-min Input CRC counter
        inv. :This OID indicates that the
        past 15-min CRC counter is invalid
        "
	::= { pm253PerfDatacomClientPast15StatHistoryPort1Entry 4 }


pm253perfdatacomclientPast15StatInCrcCountPort1 OBJECT-TYPE
	SYNTAX  Counter64
	MAX-ACCESS read-only
	STATUS current
	DESCRIPTION
        "
        Client Past 15-min Input CRC counter
        :This OID gives the past 15-min
        CRC counter value
        "
	::= { pm253PerfDatacomClientPast15StatHistoryPort1Entry 5 }


pm253perfdatacomclientPast15StatInBytesCountInvPort1 OBJECT-TYPE
	SYNTAX  EkiOnOff
	MAX-ACCESS read-only
	STATUS current
	DESCRIPTION
        "
        Client Past 15-min Input Bytes
        counter inv. :This OID indicates
        that the past 15-min Bytes counter
        is invalid
        "
	::= { pm253PerfDatacomClientPast15StatHistoryPort1Entry 2 }


pm253perfdatacomclientPast15StatInBytesCountPort1 OBJECT-TYPE
	SYNTAX  Counter64
	MAX-ACCESS read-only
	STATUS current
	DESCRIPTION
        "
        Client Past 15-min Input Bytes
        counter :This OID gives the past
        15-min Bytes counter value
        "
	::= { pm253PerfDatacomClientPast15StatHistoryPort1Entry 3 }


--- *********************************************************
---     TABLE for the pm253PerfDatacomClientPast15StatHistory articles
--- *********************************************************

pm253PerfDatacomClientPast15StatHistoryPort2Table OBJECT-TYPE
	SYNTAX  SEQUENCE OF Pm253PerfDatacomClientPast15StatHistoryPort2Entry
	MAX-ACCESS not-accessible
	STATUS current
	DESCRIPTION
        "
        List of pm253PerfDatacomClientPast15StatHistory
        Article
        "
	::= { pm253MonClient 265 }


pm253PerfDatacomClientPast15StatHistoryPort2Entry OBJECT-TYPE
	SYNTAX Pm253PerfDatacomClientPast15StatHistoryPort2Entry
	MAX-ACCESS not-accessible
	STATUS current
	DESCRIPTION
        "
        Row definition for the pm253PerfDatacomClientPast15StatHistory
        table
        "
	INDEX   { pm253PerfDatacomClientPast15StatHistoryPort2Index }
	::= { pm253PerfDatacomClientPast15StatHistoryPort2Table 1 }


Pm253PerfDatacomClientPast15StatHistoryPort2Entry ::=
	SEQUENCE {
	pm253PerfDatacomClientPast15StatHistoryPort2Index
		INTEGER,
	pm253perfdatacomclientPast15StatOutNonunicastCountInvPort2
		EkiOnOff,
	pm253perfdatacomclientPast15StatOutNonunicastCountPort2
		Counter64,
	pm253perfdatacomclientPast15StatOutUnicastCountInvPort2
		EkiOnOff,
	pm253perfdatacomclientPast15StatOutUnicastCountPort2
		Counter64,
	pm253perfdatacomclientPast15StatOutMulticastCountInvPort2
		EkiOnOff,
	pm253perfdatacomclientPast15StatOutMulticastCountPort2
		Counter64,
	pm253perfdatacomclientPast15StatOutBroadcastCountInvPort2
		EkiOnOff,
	pm253perfdatacomclientPast15StatOutBroadcastCountPort2
		Counter64,
	pm253perfdatacomclientPast15StatOutBytesCountInvPort2
		EkiOnOff,
	pm253perfdatacomclientPast15StatOutBytesCountPort2
		Counter64,
	pm253perfdatacomclientPast15StatInNonunicastCountInvPort2
		EkiOnOff,
	pm253perfdatacomclientPast15StatInNonunicastCountPort2
		Counter64,
	pm253perfdatacomclientPast15StatInUnicastCountInvPort2
		EkiOnOff,
	pm253perfdatacomclientPast15StatInUnicastCountPort2
		Counter64,
	pm253perfdatacomclientPast15StatInMulticastCountInvPort2
		EkiOnOff,
	pm253perfdatacomclientPast15StatInMulticastCountPort2
		Counter64,
	pm253perfdatacomclientPast15StatInBroadcastCountInvPort2
		EkiOnOff,
	pm253perfdatacomclientPast15StatInBroadcastCountPort2
		Counter64,
	pm253perfdatacomclientPast15StatInCrcCountInvPort2
		EkiOnOff,
	pm253perfdatacomclientPast15StatInCrcCountPort2
		Counter64,
	pm253perfdatacomclientPast15StatInBytesCountInvPort2
		EkiOnOff,
	pm253perfdatacomclientPast15StatInBytesCountPort2
		Counter64
	}


pm253PerfDatacomClientPast15StatHistoryPort2Index OBJECT-TYPE
	SYNTAX  INTEGER(0..128)
	MAX-ACCESS  read-only
	STATUS current
	DESCRIPTION
        "
        Index definition for the pm253PerfDatacomClientPast15StatHistory
        table
        "
	::= { pm253PerfDatacomClientPast15StatHistoryPort2Entry 1 }


pm253perfdatacomclientPast15StatOutNonunicastCountInvPort2 OBJECT-TYPE
	SYNTAX  EkiOnOff
	MAX-ACCESS read-only
	STATUS current
	DESCRIPTION
        "
        Client Past 15-min Output Non
         Unicast counter inv. :This OID
        indicates that the past 15-min
         Non Unicast counter is invalid
        "
	::= { pm253PerfDatacomClientPast15StatHistoryPort2Entry 44 }


pm253perfdatacomclientPast15StatOutNonunicastCountPort2 OBJECT-TYPE
	SYNTAX  Counter64
	MAX-ACCESS read-only
	STATUS current
	DESCRIPTION
        "
        Client Past 15-min Output Non
         Unicast counter :This OID gives
        the past 15-min Non Unicast counter
        value
        "
	::= { pm253PerfDatacomClientPast15StatHistoryPort2Entry 45 }


pm253perfdatacomclientPast15StatOutUnicastCountInvPort2 OBJECT-TYPE
	SYNTAX  EkiOnOff
	MAX-ACCESS read-only
	STATUS current
	DESCRIPTION
        "
        Client Past 15-min Output Unicast
        counter inv. :This OID indicates
        that the past 15-min Unicast counter
        is invalid
        "
	::= { pm253PerfDatacomClientPast15StatHistoryPort2Entry 42 }


pm253perfdatacomclientPast15StatOutUnicastCountPort2 OBJECT-TYPE
	SYNTAX  Counter64
	MAX-ACCESS read-only
	STATUS current
	DESCRIPTION
        "
        Client Past 15-min Output Unicast
        counter :This OID gives the past
        15-min Unicast counter value
        "
	::= { pm253PerfDatacomClientPast15StatHistoryPort2Entry 43 }


pm253perfdatacomclientPast15StatOutMulticastCountInvPort2 OBJECT-TYPE
	SYNTAX  EkiOnOff
	MAX-ACCESS read-only
	STATUS current
	DESCRIPTION
        "
        Client Past 15-min Output Multicast
        counter inv. :This OID indicates
        that the past 15-min Multicast
         counter is invalid
        "
	::= { pm253PerfDatacomClientPast15StatHistoryPort2Entry 34 }


pm253perfdatacomclientPast15StatOutMulticastCountPort2 OBJECT-TYPE
	SYNTAX  Counter64
	MAX-ACCESS read-only
	STATUS current
	DESCRIPTION
        "
        Client Past 15-min Output Multicast
        counter :This OID gives the past
        15-min Multicast counter value
        "
	::= { pm253PerfDatacomClientPast15StatHistoryPort2Entry 35 }


pm253perfdatacomclientPast15StatOutBroadcastCountInvPort2 OBJECT-TYPE
	SYNTAX  EkiOnOff
	MAX-ACCESS read-only
	STATUS current
	DESCRIPTION
        "
        Client Past 15-min Output Broadcast
        counter inv. :This OID indicates
        that the past 15-min Broadcast
         counter is invalid
        "
	::= { pm253PerfDatacomClientPast15StatHistoryPort2Entry 32 }


pm253perfdatacomclientPast15StatOutBroadcastCountPort2 OBJECT-TYPE
	SYNTAX  Counter64
	MAX-ACCESS read-only
	STATUS current
	DESCRIPTION
        "
        Client Past 15-min Output Broadcast
        counter :This OID gives the past
        15-min Broadcast counter value
        "
	::= { pm253PerfDatacomClientPast15StatHistoryPort2Entry 33 }


pm253perfdatacomclientPast15StatOutBytesCountInvPort2 OBJECT-TYPE
	SYNTAX  EkiOnOff
	MAX-ACCESS read-only
	STATUS current
	DESCRIPTION
        "
        Client Past 15-min Output Bytes
        counter inv. :This OID indicates
        that the past 15-min Bytes counter
        is invalid
        "
	::= { pm253PerfDatacomClientPast15StatHistoryPort2Entry 26 }


pm253perfdatacomclientPast15StatOutBytesCountPort2 OBJECT-TYPE
	SYNTAX  Counter64
	MAX-ACCESS read-only
	STATUS current
	DESCRIPTION
        "
        Client Past 15-min Output Bytes
        counter :This OID gives the past
        15-min Bytes counter value
        "
	::= { pm253PerfDatacomClientPast15StatHistoryPort2Entry 27 }


pm253perfdatacomclientPast15StatInNonunicastCountInvPort2 OBJECT-TYPE
	SYNTAX  EkiOnOff
	MAX-ACCESS read-only
	STATUS current
	DESCRIPTION
        "
        Client Past 15-min Input Non Unicast
        counter inv. :This OID indicates
        that the past 15-min Non unicast
        counter is invalid
        "
	::= { pm253PerfDatacomClientPast15StatHistoryPort2Entry 22 }


pm253perfdatacomclientPast15StatInNonunicastCountPort2 OBJECT-TYPE
	SYNTAX  Counter64
	MAX-ACCESS read-only
	STATUS current
	DESCRIPTION
        "
        Client Past 15-min Input Non Unicast
        counter :This OID gives the past
        15-min Non Unicast counter value
        "
	::= { pm253PerfDatacomClientPast15StatHistoryPort2Entry 23 }


pm253perfdatacomclientPast15StatInUnicastCountInvPort2 OBJECT-TYPE
	SYNTAX  EkiOnOff
	MAX-ACCESS read-only
	STATUS current
	DESCRIPTION
        "
        Client Past 15-min Input Unicast
        counter inv. :This OID indicates
        that the past 15-min Unicast counter
        is invalid
        "
	::= { pm253PerfDatacomClientPast15StatHistoryPort2Entry 20 }


pm253perfdatacomclientPast15StatInUnicastCountPort2 OBJECT-TYPE
	SYNTAX  Counter64
	MAX-ACCESS read-only
	STATUS current
	DESCRIPTION
        "
        Client Past 15-min Input Unicast
        counter :This OID gives the past
        15-min Unicast counter value
        "
	::= { pm253PerfDatacomClientPast15StatHistoryPort2Entry 21 }


pm253perfdatacomclientPast15StatInMulticastCountInvPort2 OBJECT-TYPE
	SYNTAX  EkiOnOff
	MAX-ACCESS read-only
	STATUS current
	DESCRIPTION
        "
        Client Past 15-min Input Multicast
        counter inv. :This OID indicates
        that the past 15-min Multicast
         counter is invalid
        "
	::= { pm253PerfDatacomClientPast15StatHistoryPort2Entry 10 }


pm253perfdatacomclientPast15StatInMulticastCountPort2 OBJECT-TYPE
	SYNTAX  Counter64
	MAX-ACCESS read-only
	STATUS current
	DESCRIPTION
        "
        Client Past 15-min Input Multicast
        counter :This OID gives the past
        15-min Multicast counter value
        "
	::= { pm253PerfDatacomClientPast15StatHistoryPort2Entry 11 }


pm253perfdatacomclientPast15StatInBroadcastCountInvPort2 OBJECT-TYPE
	SYNTAX  EkiOnOff
	MAX-ACCESS read-only
	STATUS current
	DESCRIPTION
        "
        Client Past 15-min Input Broadcast
        counter inv. :This OID indicates
        that the past 15-min Broadcast
         counter is invalid
        "
	::= { pm253PerfDatacomClientPast15StatHistoryPort2Entry 8 }


pm253perfdatacomclientPast15StatInBroadcastCountPort2 OBJECT-TYPE
	SYNTAX  Counter64
	MAX-ACCESS read-only
	STATUS current
	DESCRIPTION
        "
        Client Past 15-min Input Broadcast
        counter :This OID gives the past
        15-min Broadcast counter value
        "
	::= { pm253PerfDatacomClientPast15StatHistoryPort2Entry 9 }


pm253perfdatacomclientPast15StatInCrcCountInvPort2 OBJECT-TYPE
	SYNTAX  EkiOnOff
	MAX-ACCESS read-only
	STATUS current
	DESCRIPTION
        "
        Client Past 15-min Input CRC counter
        inv. :This OID indicates that the
        past 15-min CRC counter is invalid
        "
	::= { pm253PerfDatacomClientPast15StatHistoryPort2Entry 4 }


pm253perfdatacomclientPast15StatInCrcCountPort2 OBJECT-TYPE
	SYNTAX  Counter64
	MAX-ACCESS read-only
	STATUS current
	DESCRIPTION
        "
        Client Past 15-min Input CRC counter
        :This OID gives the past 15-min
        CRC counter value
        "
	::= { pm253PerfDatacomClientPast15StatHistoryPort2Entry 5 }


pm253perfdatacomclientPast15StatInBytesCountInvPort2 OBJECT-TYPE
	SYNTAX  EkiOnOff
	MAX-ACCESS read-only
	STATUS current
	DESCRIPTION
        "
        Client Past 15-min Input Bytes
        counter inv. :This OID indicates
        that the past 15-min Bytes counter
        is invalid
        "
	::= { pm253PerfDatacomClientPast15StatHistoryPort2Entry 2 }


pm253perfdatacomclientPast15StatInBytesCountPort2 OBJECT-TYPE
	SYNTAX  Counter64
	MAX-ACCESS read-only
	STATUS current
	DESCRIPTION
        "
        Client Past 15-min Input Bytes
        counter :This OID gives the past
        15-min Bytes counter value
        "
	::= { pm253PerfDatacomClientPast15StatHistoryPort2Entry 3 }


--- *********************************************************
---     TABLE for the pm253PerfDatacomClientPast15StatHistory articles
--- *********************************************************

pm253PerfDatacomClientPast15StatHistoryPort3Table OBJECT-TYPE
	SYNTAX  SEQUENCE OF Pm253PerfDatacomClientPast15StatHistoryPort3Entry
	MAX-ACCESS not-accessible
	STATUS current
	DESCRIPTION
        "
        List of pm253PerfDatacomClientPast15StatHistory
        Article
        "
	::= { pm253MonClient 266 }


pm253PerfDatacomClientPast15StatHistoryPort3Entry OBJECT-TYPE
	SYNTAX Pm253PerfDatacomClientPast15StatHistoryPort3Entry
	MAX-ACCESS not-accessible
	STATUS current
	DESCRIPTION
        "
        Row definition for the pm253PerfDatacomClientPast15StatHistory
        table
        "
	INDEX   { pm253PerfDatacomClientPast15StatHistoryPort3Index }
	::= { pm253PerfDatacomClientPast15StatHistoryPort3Table 1 }


Pm253PerfDatacomClientPast15StatHistoryPort3Entry ::=
	SEQUENCE {
	pm253PerfDatacomClientPast15StatHistoryPort3Index
		INTEGER,
	pm253perfdatacomclientPast15StatOutNonunicastCountInvPort3
		EkiOnOff,
	pm253perfdatacomclientPast15StatOutNonunicastCountPort3
		Counter64,
	pm253perfdatacomclientPast15StatOutUnicastCountInvPort3
		EkiOnOff,
	pm253perfdatacomclientPast15StatOutUnicastCountPort3
		Counter64,
	pm253perfdatacomclientPast15StatOutMulticastCountInvPort3
		EkiOnOff,
	pm253perfdatacomclientPast15StatOutMulticastCountPort3
		Counter64,
	pm253perfdatacomclientPast15StatOutBroadcastCountInvPort3
		EkiOnOff,
	pm253perfdatacomclientPast15StatOutBroadcastCountPort3
		Counter64,
	pm253perfdatacomclientPast15StatOutBytesCountInvPort3
		EkiOnOff,
	pm253perfdatacomclientPast15StatOutBytesCountPort3
		Counter64,
	pm253perfdatacomclientPast15StatInNonunicastCountInvPort3
		EkiOnOff,
	pm253perfdatacomclientPast15StatInNonunicastCountPort3
		Counter64,
	pm253perfdatacomclientPast15StatInUnicastCountInvPort3
		EkiOnOff,
	pm253perfdatacomclientPast15StatInUnicastCountPort3
		Counter64,
	pm253perfdatacomclientPast15StatInMulticastCountInvPort3
		EkiOnOff,
	pm253perfdatacomclientPast15StatInMulticastCountPort3
		Counter64,
	pm253perfdatacomclientPast15StatInBroadcastCountInvPort3
		EkiOnOff,
	pm253perfdatacomclientPast15StatInBroadcastCountPort3
		Counter64,
	pm253perfdatacomclientPast15StatInCrcCountInvPort3
		EkiOnOff,
	pm253perfdatacomclientPast15StatInCrcCountPort3
		Counter64,
	pm253perfdatacomclientPast15StatInBytesCountInvPort3
		EkiOnOff,
	pm253perfdatacomclientPast15StatInBytesCountPort3
		Counter64
	}


pm253PerfDatacomClientPast15StatHistoryPort3Index OBJECT-TYPE
	SYNTAX  INTEGER(0..128)
	MAX-ACCESS  read-only
	STATUS current
	DESCRIPTION
        "
        Index definition for the pm253PerfDatacomClientPast15StatHistory
        table
        "
	::= { pm253PerfDatacomClientPast15StatHistoryPort3Entry 1 }


pm253perfdatacomclientPast15StatOutNonunicastCountInvPort3 OBJECT-TYPE
	SYNTAX  EkiOnOff
	MAX-ACCESS read-only
	STATUS current
	DESCRIPTION
        "
        Client Past 15-min Output Non
         Unicast counter inv. :This OID
        indicates that the past 15-min
         Non Unicast counter is invalid
        "
	::= { pm253PerfDatacomClientPast15StatHistoryPort3Entry 44 }


pm253perfdatacomclientPast15StatOutNonunicastCountPort3 OBJECT-TYPE
	SYNTAX  Counter64
	MAX-ACCESS read-only
	STATUS current
	DESCRIPTION
        "
        Client Past 15-min Output Non
         Unicast counter :This OID gives
        the past 15-min Non Unicast counter
        value
        "
	::= { pm253PerfDatacomClientPast15StatHistoryPort3Entry 45 }


pm253perfdatacomclientPast15StatOutUnicastCountInvPort3 OBJECT-TYPE
	SYNTAX  EkiOnOff
	MAX-ACCESS read-only
	STATUS current
	DESCRIPTION
        "
        Client Past 15-min Output Unicast
        counter inv. :This OID indicates
        that the past 15-min Unicast counter
        is invalid
        "
	::= { pm253PerfDatacomClientPast15StatHistoryPort3Entry 42 }


pm253perfdatacomclientPast15StatOutUnicastCountPort3 OBJECT-TYPE
	SYNTAX  Counter64
	MAX-ACCESS read-only
	STATUS current
	DESCRIPTION
        "
        Client Past 15-min Output Unicast
        counter :This OID gives the past
        15-min Unicast counter value
        "
	::= { pm253PerfDatacomClientPast15StatHistoryPort3Entry 43 }


pm253perfdatacomclientPast15StatOutMulticastCountInvPort3 OBJECT-TYPE
	SYNTAX  EkiOnOff
	MAX-ACCESS read-only
	STATUS current
	DESCRIPTION
        "
        Client Past 15-min Output Multicast
        counter inv. :This OID indicates
        that the past 15-min Multicast
         counter is invalid
        "
	::= { pm253PerfDatacomClientPast15StatHistoryPort3Entry 34 }


pm253perfdatacomclientPast15StatOutMulticastCountPort3 OBJECT-TYPE
	SYNTAX  Counter64
	MAX-ACCESS read-only
	STATUS current
	DESCRIPTION
        "
        Client Past 15-min Output Multicast
        counter :This OID gives the past
        15-min Multicast counter value
        "
	::= { pm253PerfDatacomClientPast15StatHistoryPort3Entry 35 }


pm253perfdatacomclientPast15StatOutBroadcastCountInvPort3 OBJECT-TYPE
	SYNTAX  EkiOnOff
	MAX-ACCESS read-only
	STATUS current
	DESCRIPTION
        "
        Client Past 15-min Output Broadcast
        counter inv. :This OID indicates
        that the past 15-min Broadcast
         counter is invalid
        "
	::= { pm253PerfDatacomClientPast15StatHistoryPort3Entry 32 }


pm253perfdatacomclientPast15StatOutBroadcastCountPort3 OBJECT-TYPE
	SYNTAX  Counter64
	MAX-ACCESS read-only
	STATUS current
	DESCRIPTION
        "
        Client Past 15-min Output Broadcast
        counter :This OID gives the past
        15-min Broadcast counter value
        "
	::= { pm253PerfDatacomClientPast15StatHistoryPort3Entry 33 }


pm253perfdatacomclientPast15StatOutBytesCountInvPort3 OBJECT-TYPE
	SYNTAX  EkiOnOff
	MAX-ACCESS read-only
	STATUS current
	DESCRIPTION
        "
        Client Past 15-min Output Bytes
        counter inv. :This OID indicates
        that the past 15-min Bytes counter
        is invalid
        "
	::= { pm253PerfDatacomClientPast15StatHistoryPort3Entry 26 }


pm253perfdatacomclientPast15StatOutBytesCountPort3 OBJECT-TYPE
	SYNTAX  Counter64
	MAX-ACCESS read-only
	STATUS current
	DESCRIPTION
        "
        Client Past 15-min Output Bytes
        counter :This OID gives the past
        15-min Bytes counter value
        "
	::= { pm253PerfDatacomClientPast15StatHistoryPort3Entry 27 }


pm253perfdatacomclientPast15StatInNonunicastCountInvPort3 OBJECT-TYPE
	SYNTAX  EkiOnOff
	MAX-ACCESS read-only
	STATUS current
	DESCRIPTION
        "
        Client Past 15-min Input Non Unicast
        counter inv. :This OID indicates
        that the past 15-min Non unicast
        counter is invalid
        "
	::= { pm253PerfDatacomClientPast15StatHistoryPort3Entry 22 }


pm253perfdatacomclientPast15StatInNonunicastCountPort3 OBJECT-TYPE
	SYNTAX  Counter64
	MAX-ACCESS read-only
	STATUS current
	DESCRIPTION
        "
        Client Past 15-min Input Non Unicast
        counter :This OID gives the past
        15-min Non Unicast counter value
        "
	::= { pm253PerfDatacomClientPast15StatHistoryPort3Entry 23 }


pm253perfdatacomclientPast15StatInUnicastCountInvPort3 OBJECT-TYPE
	SYNTAX  EkiOnOff
	MAX-ACCESS read-only
	STATUS current
	DESCRIPTION
        "
        Client Past 15-min Input Unicast
        counter inv. :This OID indicates
        that the past 15-min Unicast counter
        is invalid
        "
	::= { pm253PerfDatacomClientPast15StatHistoryPort3Entry 20 }


pm253perfdatacomclientPast15StatInUnicastCountPort3 OBJECT-TYPE
	SYNTAX  Counter64
	MAX-ACCESS read-only
	STATUS current
	DESCRIPTION
        "
        Client Past 15-min Input Unicast
        counter :This OID gives the past
        15-min Unicast counter value
        "
	::= { pm253PerfDatacomClientPast15StatHistoryPort3Entry 21 }


pm253perfdatacomclientPast15StatInMulticastCountInvPort3 OBJECT-TYPE
	SYNTAX  EkiOnOff
	MAX-ACCESS read-only
	STATUS current
	DESCRIPTION
        "
        Client Past 15-min Input Multicast
        counter inv. :This OID indicates
        that the past 15-min Multicast
         counter is invalid
        "
	::= { pm253PerfDatacomClientPast15StatHistoryPort3Entry 10 }


pm253perfdatacomclientPast15StatInMulticastCountPort3 OBJECT-TYPE
	SYNTAX  Counter64
	MAX-ACCESS read-only
	STATUS current
	DESCRIPTION
        "
        Client Past 15-min Input Multicast
        counter :This OID gives the past
        15-min Multicast counter value
        "
	::= { pm253PerfDatacomClientPast15StatHistoryPort3Entry 11 }


pm253perfdatacomclientPast15StatInBroadcastCountInvPort3 OBJECT-TYPE
	SYNTAX  EkiOnOff
	MAX-ACCESS read-only
	STATUS current
	DESCRIPTION
        "
        Client Past 15-min Input Broadcast
        counter inv. :This OID indicates
        that the past 15-min Broadcast
         counter is invalid
        "
	::= { pm253PerfDatacomClientPast15StatHistoryPort3Entry 8 }


pm253perfdatacomclientPast15StatInBroadcastCountPort3 OBJECT-TYPE
	SYNTAX  Counter64
	MAX-ACCESS read-only
	STATUS current
	DESCRIPTION
        "
        Client Past 15-min Input Broadcast
        counter :This OID gives the past
        15-min Broadcast counter value
        "
	::= { pm253PerfDatacomClientPast15StatHistoryPort3Entry 9 }


pm253perfdatacomclientPast15StatInCrcCountInvPort3 OBJECT-TYPE
	SYNTAX  EkiOnOff
	MAX-ACCESS read-only
	STATUS current
	DESCRIPTION
        "
        Client Past 15-min Input CRC counter
        inv. :This OID indicates that the
        past 15-min CRC counter is invalid
        "
	::= { pm253PerfDatacomClientPast15StatHistoryPort3Entry 4 }


pm253perfdatacomclientPast15StatInCrcCountPort3 OBJECT-TYPE
	SYNTAX  Counter64
	MAX-ACCESS read-only
	STATUS current
	DESCRIPTION
        "
        Client Past 15-min Input CRC counter
        :This OID gives the past 15-min
        CRC counter value
        "
	::= { pm253PerfDatacomClientPast15StatHistoryPort3Entry 5 }


pm253perfdatacomclientPast15StatInBytesCountInvPort3 OBJECT-TYPE
	SYNTAX  EkiOnOff
	MAX-ACCESS read-only
	STATUS current
	DESCRIPTION
        "
        Client Past 15-min Input Bytes
        counter inv. :This OID indicates
        that the past 15-min Bytes counter
        is invalid
        "
	::= { pm253PerfDatacomClientPast15StatHistoryPort3Entry 2 }


pm253perfdatacomclientPast15StatInBytesCountPort3 OBJECT-TYPE
	SYNTAX  Counter64
	MAX-ACCESS read-only
	STATUS current
	DESCRIPTION
        "
        Client Past 15-min Input Bytes
        counter :This OID gives the past
        15-min Bytes counter value
        "
	::= { pm253PerfDatacomClientPast15StatHistoryPort3Entry 3 }


--- *****************************************************
---     Leaf of the datacomClientCurrent24Stat
--- *****************************************************
--- *********************************************************
---     TABLE for the pm253PerfDatacomClientCurrent24Stat articles
--- *********************************************************

pm253PerfDatacomClientCurrent24StatTable OBJECT-TYPE
	SYNTAX  SEQUENCE OF Pm253PerfDatacomClientCurrent24StatEntry
	MAX-ACCESS not-accessible
	STATUS current
	DESCRIPTION
        "
        List of pm253PerfDatacomClientCurrent24Stat
        Article
        "
	::= { pm253MonClient 272 }


pm253PerfDatacomClientCurrent24StatEntry OBJECT-TYPE
	SYNTAX Pm253PerfDatacomClientCurrent24StatEntry
	MAX-ACCESS not-accessible
	STATUS current
	DESCRIPTION
        "
        Row definition for the pm253PerfDatacomClientCurrent24Stat
        table
        "
	INDEX   { pm253PerfDatacomClientCurrent24StatIndex }
	::= { pm253PerfDatacomClientCurrent24StatTable 1 }


Pm253PerfDatacomClientCurrent24StatEntry ::=
	SEQUENCE {
	pm253PerfDatacomClientCurrent24StatIndex
		INTEGER,
	pm253perfdatacomclientCurrent24StatOutNonunicastCountInvPortn
		EkiOnOff,
	pm253perfdatacomclientCurrent24StatOutNonunicastCountPortn
		Counter64,
	pm253perfdatacomclientCurrent24StatOutUnicastCountInvPortn
		EkiOnOff,
	pm253perfdatacomclientCurrent24StatOutUnicastCountPortn
		Counter64,
	pm253perfdatacomclientCurrent24StatOutMulticastCountInvPortn
		EkiOnOff,
	pm253perfdatacomclientCurrent24StatOutMulticastCountPortn
		Counter64,
	pm253perfdatacomclientCurrent24StatOutBroadcastCountInvPortn
		EkiOnOff,
	pm253perfdatacomclientCurrent24StatOutBroadcastCountPortn
		Counter64,
	pm253perfdatacomclientCurrent24StatOutBytesCountInvPortn
		EkiOnOff,
	pm253perfdatacomclientCurrent24StatOutBytesCountPortn
		Counter64,
	pm253perfdatacomclientCurrent24StatInNonunicastCountInvPortn
		EkiOnOff,
	pm253perfdatacomclientCurrent24StatInNonunicastCountPortn
		Counter64,
	pm253perfdatacomclientCurrent24StatInUnicastCountInvPortn
		EkiOnOff,
	pm253perfdatacomclientCurrent24StatInUnicastCountPortn
		Counter64,
	pm253perfdatacomclientCurrent24StatInMulticastCountInvPortn
		EkiOnOff,
	pm253perfdatacomclientCurrent24StatInMulticastCountPortn
		Counter64,
	pm253perfdatacomclientCurrent24StatInBroadcastCountInvPortn
		EkiOnOff,
	pm253perfdatacomclientCurrent24StatInBroadcastCountPortn
		Counter64,
	pm253perfdatacomclientCurrent24StatInCrcCountInvPortn
		EkiOnOff,
	pm253perfdatacomclientCurrent24StatInCrcCountPortn
		Counter64,
	pm253perfdatacomclientCurrent24StatInBytesCountInvPortn
		EkiOnOff,
	pm253perfdatacomclientCurrent24StatInBytesCountPortn
		Counter64
	}


pm253PerfDatacomClientCurrent24StatIndex OBJECT-TYPE
	SYNTAX  INTEGER(0..128)
	MAX-ACCESS  read-only
	STATUS current
	DESCRIPTION
        "
        Index definition for the pm253PerfDatacomClientCurrent24Stat
        table
        "
	::= { pm253PerfDatacomClientCurrent24StatEntry 1 }


pm253perfdatacomclientCurrent24StatOutNonunicastCountInvPortn OBJECT-TYPE
	SYNTAX  EkiOnOff
	MAX-ACCESS read-only
	STATUS current
	DESCRIPTION
        "
        Client Current 24-hours Output
        Non Unicast counter inv. :This
         OID indicates that the current
        24-hours Non Unicast counter is
        invalid
        "
	::= { pm253PerfDatacomClientCurrent24StatEntry 44 }


pm253perfdatacomclientCurrent24StatOutNonunicastCountPortn OBJECT-TYPE
	SYNTAX  Counter64
	MAX-ACCESS read-only
	STATUS current
	DESCRIPTION
        "
        Client Current 24-hours Output
        Non Unicast counter :This OID gives
        the current 24-hours Non Unicast
        counter value
        "
	::= { pm253PerfDatacomClientCurrent24StatEntry 45 }


pm253perfdatacomclientCurrent24StatOutUnicastCountInvPortn OBJECT-TYPE
	SYNTAX  EkiOnOff
	MAX-ACCESS read-only
	STATUS current
	DESCRIPTION
        "
        Client Current 24-hours Output
        Unicast counter inv. :This OID
         indicates that the current 24-hours
        Unicast counter is invalid
        "
	::= { pm253PerfDatacomClientCurrent24StatEntry 42 }


pm253perfdatacomclientCurrent24StatOutUnicastCountPortn OBJECT-TYPE
	SYNTAX  Counter64
	MAX-ACCESS read-only
	STATUS current
	DESCRIPTION
        "
        Client Current 24-hours Output
        Unicast counter :This OID gives
        the current 24-hours Unicast counter
        value
        "
	::= { pm253PerfDatacomClientCurrent24StatEntry 43 }


pm253perfdatacomclientCurrent24StatOutMulticastCountInvPortn OBJECT-TYPE
	SYNTAX  EkiOnOff
	MAX-ACCESS read-only
	STATUS current
	DESCRIPTION
        "
        Client Current 24-hours Output
        Multicast counter inv. :This OID
        indicates that the current 24-hours
        Multicast counter is invalid
        "
	::= { pm253PerfDatacomClientCurrent24StatEntry 34 }


pm253perfdatacomclientCurrent24StatOutMulticastCountPortn OBJECT-TYPE
	SYNTAX  Counter64
	MAX-ACCESS read-only
	STATUS current
	DESCRIPTION
        "
        Client Current 24-hours Output
        Multicast counter :This OID gives
        the current 24-hours Multicast
         counter value
        "
	::= { pm253PerfDatacomClientCurrent24StatEntry 35 }


pm253perfdatacomclientCurrent24StatOutBroadcastCountInvPortn OBJECT-TYPE
	SYNTAX  EkiOnOff
	MAX-ACCESS read-only
	STATUS current
	DESCRIPTION
        "
        Client Current 24-hours Output
        Broadcast counter inv. :This OID
        indicates that the current 24-hours
        Broadcast counter is invalid
        "
	::= { pm253PerfDatacomClientCurrent24StatEntry 32 }


pm253perfdatacomclientCurrent24StatOutBroadcastCountPortn OBJECT-TYPE
	SYNTAX  Counter64
	MAX-ACCESS read-only
	STATUS current
	DESCRIPTION
        "
        Client Current 24-hours Output
        Broadcast counter :This OID gives
        the current 24-hours Broadcast
         counter value
        "
	::= { pm253PerfDatacomClientCurrent24StatEntry 33 }


pm253perfdatacomclientCurrent24StatOutBytesCountInvPortn OBJECT-TYPE
	SYNTAX  EkiOnOff
	MAX-ACCESS read-only
	STATUS current
	DESCRIPTION
        "
        Client Current 24-hours Output
        Bytes counter inv. :This OID indicates
        that the current 24-hours Bytes
        counter is invalid
        "
	::= { pm253PerfDatacomClientCurrent24StatEntry 26 }


pm253perfdatacomclientCurrent24StatOutBytesCountPortn OBJECT-TYPE
	SYNTAX  Counter64
	MAX-ACCESS read-only
	STATUS current
	DESCRIPTION
        "
        Client Current 24-hours Output
        Bytes counter :This OID gives the
        current 24-hours Bytes counter
         value
        "
	::= { pm253PerfDatacomClientCurrent24StatEntry 27 }


pm253perfdatacomclientCurrent24StatInNonunicastCountInvPortn OBJECT-TYPE
	SYNTAX  EkiOnOff
	MAX-ACCESS read-only
	STATUS current
	DESCRIPTION
        "
        Client Current 24-hours Input
         Non Unicast counter inv. :This
        OID indicates that the current
         24-hours Non unicast counter is
        invalid
        "
	::= { pm253PerfDatacomClientCurrent24StatEntry 22 }


pm253perfdatacomclientCurrent24StatInNonunicastCountPortn OBJECT-TYPE
	SYNTAX  Counter64
	MAX-ACCESS read-only
	STATUS current
	DESCRIPTION
        "
        Client Current 24-hours Input
         Non Unicast counter :This OID
         gives the current 24-hours Non
        Unicast counter value
        "
	::= { pm253PerfDatacomClientCurrent24StatEntry 23 }


pm253perfdatacomclientCurrent24StatInUnicastCountInvPortn OBJECT-TYPE
	SYNTAX  EkiOnOff
	MAX-ACCESS read-only
	STATUS current
	DESCRIPTION
        "
        Client Current 24-hours Input
         Unicast counter inv. :This OID
        indicates that the current 24-hours
        Unicast counter is invalid
        "
	::= { pm253PerfDatacomClientCurrent24StatEntry 20 }


pm253perfdatacomclientCurrent24StatInUnicastCountPortn OBJECT-TYPE
	SYNTAX  Counter64
	MAX-ACCESS read-only
	STATUS current
	DESCRIPTION
        "
        Client Current 24-hours Input
         Unicast counter :This OID gives
        the current 24-hours Unicast counter
        value
        "
	::= { pm253PerfDatacomClientCurrent24StatEntry 21 }


pm253perfdatacomclientCurrent24StatInMulticastCountInvPortn OBJECT-TYPE
	SYNTAX  EkiOnOff
	MAX-ACCESS read-only
	STATUS current
	DESCRIPTION
        "
        Client Current 24-hours Input
         Multicast counter inv. :This OID
        indicates that the current 24-hours
        Multicast counter is invalid
        "
	::= { pm253PerfDatacomClientCurrent24StatEntry 10 }


pm253perfdatacomclientCurrent24StatInMulticastCountPortn OBJECT-TYPE
	SYNTAX  Counter64
	MAX-ACCESS read-only
	STATUS current
	DESCRIPTION
        "
        Client Current 24-hours Input
         Multicast counter :This OID gives
        the current 24-hours Multicast
         counter value
        "
	::= { pm253PerfDatacomClientCurrent24StatEntry 11 }


pm253perfdatacomclientCurrent24StatInBroadcastCountInvPortn OBJECT-TYPE
	SYNTAX  EkiOnOff
	MAX-ACCESS read-only
	STATUS current
	DESCRIPTION
        "
        Client Current 24-hours Input
         Broadcast counter inv. :This OID
        indicates that the current 24-hours
        Broadcast counter is invalid
        "
	::= { pm253PerfDatacomClientCurrent24StatEntry 8 }


pm253perfdatacomclientCurrent24StatInBroadcastCountPortn OBJECT-TYPE
	SYNTAX  Counter64
	MAX-ACCESS read-only
	STATUS current
	DESCRIPTION
        "
        Client Current 24-hours Input
         Broadcast counter :This OID gives
        the current 24-hours Broadcast
         counter value
        "
	::= { pm253PerfDatacomClientCurrent24StatEntry 9 }


pm253perfdatacomclientCurrent24StatInCrcCountInvPortn OBJECT-TYPE
	SYNTAX  EkiOnOff
	MAX-ACCESS read-only
	STATUS current
	DESCRIPTION
        "
        Client Current 24-hours Input
         CRC counter inv. :This OID indicates
        that the current 24-hours CRC counter
        is invalid
        "
	::= { pm253PerfDatacomClientCurrent24StatEntry 4 }


pm253perfdatacomclientCurrent24StatInCrcCountPortn OBJECT-TYPE
	SYNTAX  Counter64
	MAX-ACCESS read-only
	STATUS current
	DESCRIPTION
        "
        Client Current 24-hours Input
         CRC counter :This OID gives the
        current 24-hours CRC counter value
        "
	::= { pm253PerfDatacomClientCurrent24StatEntry 5 }


pm253perfdatacomclientCurrent24StatInBytesCountInvPortn OBJECT-TYPE
	SYNTAX  EkiOnOff
	MAX-ACCESS read-only
	STATUS current
	DESCRIPTION
        "
        Client Current 24-hours Input
         Bytes counter inv. :This OID indicates
        that the current 24-hours Bytes
        counter is invalid
        "
	::= { pm253PerfDatacomClientCurrent24StatEntry 2 }


pm253perfdatacomclientCurrent24StatInBytesCountPortn OBJECT-TYPE
	SYNTAX  Counter64
	MAX-ACCESS read-only
	STATUS current
	DESCRIPTION
        "
        Client Current 24-hours Input
         Bytes counter :This OID gives
         the current 24-hours Bytes counter
        value
        "
	::= { pm253PerfDatacomClientCurrent24StatEntry 3 }


--- *****************************************************
---     Leaf of the datacomClientPast24Stat
--- *****************************************************
--- *********************************************************
---     TABLE for the pm253PerfDatacomClientPast24StatHistory articles
--- *********************************************************

pm253PerfDatacomClientPast24StatHistoryPort1Table OBJECT-TYPE
	SYNTAX  SEQUENCE OF Pm253PerfDatacomClientPast24StatHistoryPort1Entry
	MAX-ACCESS not-accessible
	STATUS current
	DESCRIPTION
        "
        List of pm253PerfDatacomClientPast24StatHistory
        Article
        "
	::= { pm253MonClient 280 }


pm253PerfDatacomClientPast24StatHistoryPort1Entry OBJECT-TYPE
	SYNTAX Pm253PerfDatacomClientPast24StatHistoryPort1Entry
	MAX-ACCESS not-accessible
	STATUS current
	DESCRIPTION
        "
        Row definition for the pm253PerfDatacomClientPast24StatHistory
        table
        "
	INDEX   { pm253PerfDatacomClientPast24StatHistoryPort1Index }
	::= { pm253PerfDatacomClientPast24StatHistoryPort1Table 1 }


Pm253PerfDatacomClientPast24StatHistoryPort1Entry ::=
	SEQUENCE {
	pm253PerfDatacomClientPast24StatHistoryPort1Index
		INTEGER,
	pm253perfdatacomclientPast24StatOutNonunicastCountInvPort1
		EkiOnOff,
	pm253perfdatacomclientPast24StatOutNonunicastCountPort1
		Counter64,
	pm253perfdatacomclientPast24StatOutUnicastCountInvPort1
		EkiOnOff,
	pm253perfdatacomclientPast24StatOutUnicastCountPort1
		Counter64,
	pm253perfdatacomclientPast24StatOutMulticastCountInvPort1
		EkiOnOff,
	pm253perfdatacomclientPast24StatOutMulticastCountPort1
		Counter64,
	pm253perfdatacomclientPast24StatOutBroadcastCountInvPort1
		EkiOnOff,
	pm253perfdatacomclientPast24StatOutBroadcastCountPort1
		Counter64,
	pm253perfdatacomclientPast24StatOutBytesCountInvPort1
		EkiOnOff,
	pm253perfdatacomclientPast24StatOutBytesCountPort1
		Counter64,
	pm253perfdatacomclientPast24StatInNonunicastCountInvPort1
		EkiOnOff,
	pm253perfdatacomclientPast24StatInNonunicastCountPort1
		Counter64,
	pm253perfdatacomclientPast24StatInUnicastCountInvPort1
		EkiOnOff,
	pm253perfdatacomclientPast24StatInUnicastCountPort1
		Counter64,
	pm253perfdatacomclientPast24StatInMulticastCountInvPort1
		EkiOnOff,
	pm253perfdatacomclientPast24StatInMulticastCountPort1
		Counter64,
	pm253perfdatacomclientPast24StatInBroadcastCountInvPort1
		EkiOnOff,
	pm253perfdatacomclientPast24StatInBroadcastCountPort1
		Counter64,
	pm253perfdatacomclientPast24StatInCrcCountInvPort1
		EkiOnOff,
	pm253perfdatacomclientPast24StatInCrcCountPort1
		Counter64,
	pm253perfdatacomclientPast24StatInBytesCountInvPort1
		EkiOnOff,
	pm253perfdatacomclientPast24StatInBytesCountPort1
		Counter64
	}


pm253PerfDatacomClientPast24StatHistoryPort1Index OBJECT-TYPE
	SYNTAX  INTEGER(0..128)
	MAX-ACCESS  read-only
	STATUS current
	DESCRIPTION
        "
        Index definition for the pm253PerfDatacomClientPast24StatHistory
        table
        "
	::= { pm253PerfDatacomClientPast24StatHistoryPort1Entry 1 }


pm253perfdatacomclientPast24StatOutNonunicastCountInvPort1 OBJECT-TYPE
	SYNTAX  EkiOnOff
	MAX-ACCESS read-only
	STATUS current
	DESCRIPTION
        "
        Client Past 24-hours Output Non
        Unicast counter inv. :This OID
         indicates that the past 24-hours
        Non Unicast counter is invalid
        "
	::= { pm253PerfDatacomClientPast24StatHistoryPort1Entry 44 }


pm253perfdatacomclientPast24StatOutNonunicastCountPort1 OBJECT-TYPE
	SYNTAX  Counter64
	MAX-ACCESS read-only
	STATUS current
	DESCRIPTION
        "
        Client Past 24-hours Output Non
        Unicast counter :This OID gives
        the past 24-hours Non Unicast counter
        value
        "
	::= { pm253PerfDatacomClientPast24StatHistoryPort1Entry 45 }


pm253perfdatacomclientPast24StatOutUnicastCountInvPort1 OBJECT-TYPE
	SYNTAX  EkiOnOff
	MAX-ACCESS read-only
	STATUS current
	DESCRIPTION
        "
        Client Past 24-hours Output Unicast
        counter inv. :This OID indicates
        that the past 24-hours Unicast
         counter is invalid
        "
	::= { pm253PerfDatacomClientPast24StatHistoryPort1Entry 42 }


pm253perfdatacomclientPast24StatOutUnicastCountPort1 OBJECT-TYPE
	SYNTAX  Counter64
	MAX-ACCESS read-only
	STATUS current
	DESCRIPTION
        "
        Client Past 24-hours Output Unicast
        counter :This OID gives the past
        24-hours Unicast counter value
        "
	::= { pm253PerfDatacomClientPast24StatHistoryPort1Entry 43 }


pm253perfdatacomclientPast24StatOutMulticastCountInvPort1 OBJECT-TYPE
	SYNTAX  EkiOnOff
	MAX-ACCESS read-only
	STATUS current
	DESCRIPTION
        "
        Client Past 24-hours Output Multicast
        counter inv. :This OID indicates
        that the past 24-hours Multicast
        counter is invalid
        "
	::= { pm253PerfDatacomClientPast24StatHistoryPort1Entry 34 }


pm253perfdatacomclientPast24StatOutMulticastCountPort1 OBJECT-TYPE
	SYNTAX  Counter64
	MAX-ACCESS read-only
	STATUS current
	DESCRIPTION
        "
        Client Past 24-hours Output Multicast
        counter :This OID gives the past
        24-hours Multicast counter value
        "
	::= { pm253PerfDatacomClientPast24StatHistoryPort1Entry 35 }


pm253perfdatacomclientPast24StatOutBroadcastCountInvPort1 OBJECT-TYPE
	SYNTAX  EkiOnOff
	MAX-ACCESS read-only
	STATUS current
	DESCRIPTION
        "
        Client Past 24-hours Output Broadcast
        counter inv. :This OID indicates
        that the past 24-hours Broadcast
        counter is invalid
        "
	::= { pm253PerfDatacomClientPast24StatHistoryPort1Entry 32 }


pm253perfdatacomclientPast24StatOutBroadcastCountPort1 OBJECT-TYPE
	SYNTAX  Counter64
	MAX-ACCESS read-only
	STATUS current
	DESCRIPTION
        "
        Client Past 24-hours Output Broadcast
        counter :This OID gives the past
        24-hours Broadcast counter value
        "
	::= { pm253PerfDatacomClientPast24StatHistoryPort1Entry 33 }


pm253perfdatacomclientPast24StatOutBytesCountInvPort1 OBJECT-TYPE
	SYNTAX  EkiOnOff
	MAX-ACCESS read-only
	STATUS current
	DESCRIPTION
        "
        Client Past 24-hours Output Bytes
        counter inv. :This OID indicates
        that the past 24-hours Bytes counter
        is invalid
        "
	::= { pm253PerfDatacomClientPast24StatHistoryPort1Entry 26 }


pm253perfdatacomclientPast24StatOutBytesCountPort1 OBJECT-TYPE
	SYNTAX  Counter64
	MAX-ACCESS read-only
	STATUS current
	DESCRIPTION
        "
        Client Past 24-hours Output Bytes
        counter :This OID gives the past
        24-hours Bytes counter value
        "
	::= { pm253PerfDatacomClientPast24StatHistoryPort1Entry 27 }


pm253perfdatacomclientPast24StatInNonunicastCountInvPort1 OBJECT-TYPE
	SYNTAX  EkiOnOff
	MAX-ACCESS read-only
	STATUS current
	DESCRIPTION
        "
        Client Past 24-hours Input Non
        Unicast counter inv. :This OID
         indicates that the past 24-hours
        Non unicast counter is invalid
        "
	::= { pm253PerfDatacomClientPast24StatHistoryPort1Entry 22 }


pm253perfdatacomclientPast24StatInNonunicastCountPort1 OBJECT-TYPE
	SYNTAX  Counter64
	MAX-ACCESS read-only
	STATUS current
	DESCRIPTION
        "
        Client Past 24-hours Input Non
        Unicast counter :This OID gives
        the past 24-hours Non Unicast counter
        value
        "
	::= { pm253PerfDatacomClientPast24StatHistoryPort1Entry 23 }


pm253perfdatacomclientPast24StatInUnicastCountInvPort1 OBJECT-TYPE
	SYNTAX  EkiOnOff
	MAX-ACCESS read-only
	STATUS current
	DESCRIPTION
        "
        Client Past 24-hours Input Unicast
        counter inv. :This OID indicates
        that the past 24-hours Unicast
         counter is invalid
        "
	::= { pm253PerfDatacomClientPast24StatHistoryPort1Entry 20 }


pm253perfdatacomclientPast24StatInUnicastCountPort1 OBJECT-TYPE
	SYNTAX  Counter64
	MAX-ACCESS read-only
	STATUS current
	DESCRIPTION
        "
        Client Past 24-hours Input Unicast
        counter :This OID gives the past
        24-hours Unicast counter value
        "
	::= { pm253PerfDatacomClientPast24StatHistoryPort1Entry 21 }


pm253perfdatacomclientPast24StatInMulticastCountInvPort1 OBJECT-TYPE
	SYNTAX  EkiOnOff
	MAX-ACCESS read-only
	STATUS current
	DESCRIPTION
        "
        Client Past 24-hours Input Multicast
        counter inv. :This OID indicates
        that the past 24-hours Multicast
        counter is invalid
        "
	::= { pm253PerfDatacomClientPast24StatHistoryPort1Entry 10 }


pm253perfdatacomclientPast24StatInMulticastCountPort1 OBJECT-TYPE
	SYNTAX  Counter64
	MAX-ACCESS read-only
	STATUS current
	DESCRIPTION
        "
        Client Past 24-hours Input Multicast
        counter :This OID gives the past
        24-hours Multicast counter value
        "
	::= { pm253PerfDatacomClientPast24StatHistoryPort1Entry 11 }


pm253perfdatacomclientPast24StatInBroadcastCountInvPort1 OBJECT-TYPE
	SYNTAX  EkiOnOff
	MAX-ACCESS read-only
	STATUS current
	DESCRIPTION
        "
        Client Past 24-hours Input Broadcast
        counter inv. :This OID indicates
        that the past 24-hours Broadcast
        counter is invalid
        "
	::= { pm253PerfDatacomClientPast24StatHistoryPort1Entry 8 }


pm253perfdatacomclientPast24StatInBroadcastCountPort1 OBJECT-TYPE
	SYNTAX  Counter64
	MAX-ACCESS read-only
	STATUS current
	DESCRIPTION
        "
        Client Past 24-hours Input Broadcast
        counter :This OID gives the past
        24-hours Broadcast counter value
        "
	::= { pm253PerfDatacomClientPast24StatHistoryPort1Entry 9 }


pm253perfdatacomclientPast24StatInCrcCountInvPort1 OBJECT-TYPE
	SYNTAX  EkiOnOff
	MAX-ACCESS read-only
	STATUS current
	DESCRIPTION
        "
        Client Past 24-hours Input CRC
        counter inv. :This OID indicates
        that the past 24-hours CRC counter
        is invalid
        "
	::= { pm253PerfDatacomClientPast24StatHistoryPort1Entry 4 }


pm253perfdatacomclientPast24StatInCrcCountPort1 OBJECT-TYPE
	SYNTAX  Counter64
	MAX-ACCESS read-only
	STATUS current
	DESCRIPTION
        "
        Client Past 24-hours Input CRC
        counter :This OID gives the past
        24-hours CRC counter value
        "
	::= { pm253PerfDatacomClientPast24StatHistoryPort1Entry 5 }


pm253perfdatacomclientPast24StatInBytesCountInvPort1 OBJECT-TYPE
	SYNTAX  EkiOnOff
	MAX-ACCESS read-only
	STATUS current
	DESCRIPTION
        "
        Client Past 24-hours Input Bytes
        counter inv. :This OID indicates
        that the past 24-hours Bytes counter
        is invalid
        "
	::= { pm253PerfDatacomClientPast24StatHistoryPort1Entry 2 }


pm253perfdatacomclientPast24StatInBytesCountPort1 OBJECT-TYPE
	SYNTAX  Counter64
	MAX-ACCESS read-only
	STATUS current
	DESCRIPTION
        "
        Client Past 24-hours Input Bytes
        counter :This OID gives the past
        24-hours Bytes counter value
        "
	::= { pm253PerfDatacomClientPast24StatHistoryPort1Entry 3 }


--- *********************************************************
---     TABLE for the pm253PerfDatacomClientPast24StatHistory articles
--- *********************************************************

pm253PerfDatacomClientPast24StatHistoryPort2Table OBJECT-TYPE
	SYNTAX  SEQUENCE OF Pm253PerfDatacomClientPast24StatHistoryPort2Entry
	MAX-ACCESS not-accessible
	STATUS current
	DESCRIPTION
        "
        List of pm253PerfDatacomClientPast24StatHistory
        Article
        "
	::= { pm253MonClient 281 }


pm253PerfDatacomClientPast24StatHistoryPort2Entry OBJECT-TYPE
	SYNTAX Pm253PerfDatacomClientPast24StatHistoryPort2Entry
	MAX-ACCESS not-accessible
	STATUS current
	DESCRIPTION
        "
        Row definition for the pm253PerfDatacomClientPast24StatHistory
        table
        "
	INDEX   { pm253PerfDatacomClientPast24StatHistoryPort2Index }
	::= { pm253PerfDatacomClientPast24StatHistoryPort2Table 1 }


Pm253PerfDatacomClientPast24StatHistoryPort2Entry ::=
	SEQUENCE {
	pm253PerfDatacomClientPast24StatHistoryPort2Index
		INTEGER,
	pm253perfdatacomclientPast24StatOutNonunicastCountInvPort2
		EkiOnOff,
	pm253perfdatacomclientPast24StatOutNonunicastCountPort2
		Counter64,
	pm253perfdatacomclientPast24StatOutUnicastCountInvPort2
		EkiOnOff,
	pm253perfdatacomclientPast24StatOutUnicastCountPort2
		Counter64,
	pm253perfdatacomclientPast24StatOutMulticastCountInvPort2
		EkiOnOff,
	pm253perfdatacomclientPast24StatOutMulticastCountPort2
		Counter64,
	pm253perfdatacomclientPast24StatOutBroadcastCountInvPort2
		EkiOnOff,
	pm253perfdatacomclientPast24StatOutBroadcastCountPort2
		Counter64,
	pm253perfdatacomclientPast24StatOutBytesCountInvPort2
		EkiOnOff,
	pm253perfdatacomclientPast24StatOutBytesCountPort2
		Counter64,
	pm253perfdatacomclientPast24StatInNonunicastCountInvPort2
		EkiOnOff,
	pm253perfdatacomclientPast24StatInNonunicastCountPort2
		Counter64,
	pm253perfdatacomclientPast24StatInUnicastCountInvPort2
		EkiOnOff,
	pm253perfdatacomclientPast24StatInUnicastCountPort2
		Counter64,
	pm253perfdatacomclientPast24StatInMulticastCountInvPort2
		EkiOnOff,
	pm253perfdatacomclientPast24StatInMulticastCountPort2
		Counter64,
	pm253perfdatacomclientPast24StatInBroadcastCountInvPort2
		EkiOnOff,
	pm253perfdatacomclientPast24StatInBroadcastCountPort2
		Counter64,
	pm253perfdatacomclientPast24StatInCrcCountInvPort2
		EkiOnOff,
	pm253perfdatacomclientPast24StatInCrcCountPort2
		Counter64,
	pm253perfdatacomclientPast24StatInBytesCountInvPort2
		EkiOnOff,
	pm253perfdatacomclientPast24StatInBytesCountPort2
		Counter64
	}


pm253PerfDatacomClientPast24StatHistoryPort2Index OBJECT-TYPE
	SYNTAX  INTEGER(0..128)
	MAX-ACCESS  read-only
	STATUS current
	DESCRIPTION
        "
        Index definition for the pm253PerfDatacomClientPast24StatHistory
        table
        "
	::= { pm253PerfDatacomClientPast24StatHistoryPort2Entry 1 }


pm253perfdatacomclientPast24StatOutNonunicastCountInvPort2 OBJECT-TYPE
	SYNTAX  EkiOnOff
	MAX-ACCESS read-only
	STATUS current
	DESCRIPTION
        "
        Client Past 24-hours Output Non
        Unicast counter inv. :This OID
         indicates that the past 24-hours
        Non Unicast counter is invalid
        "
	::= { pm253PerfDatacomClientPast24StatHistoryPort2Entry 44 }


pm253perfdatacomclientPast24StatOutNonunicastCountPort2 OBJECT-TYPE
	SYNTAX  Counter64
	MAX-ACCESS read-only
	STATUS current
	DESCRIPTION
        "
        Client Past 24-hours Output Non
        Unicast counter :This OID gives
        the past 24-hours Non Unicast counter
        value
        "
	::= { pm253PerfDatacomClientPast24StatHistoryPort2Entry 45 }


pm253perfdatacomclientPast24StatOutUnicastCountInvPort2 OBJECT-TYPE
	SYNTAX  EkiOnOff
	MAX-ACCESS read-only
	STATUS current
	DESCRIPTION
        "
        Client Past 24-hours Output Unicast
        counter inv. :This OID indicates
        that the past 24-hours Unicast
         counter is invalid
        "
	::= { pm253PerfDatacomClientPast24StatHistoryPort2Entry 42 }


pm253perfdatacomclientPast24StatOutUnicastCountPort2 OBJECT-TYPE
	SYNTAX  Counter64
	MAX-ACCESS read-only
	STATUS current
	DESCRIPTION
        "
        Client Past 24-hours Output Unicast
        counter :This OID gives the past
        24-hours Unicast counter value
        "
	::= { pm253PerfDatacomClientPast24StatHistoryPort2Entry 43 }


pm253perfdatacomclientPast24StatOutMulticastCountInvPort2 OBJECT-TYPE
	SYNTAX  EkiOnOff
	MAX-ACCESS read-only
	STATUS current
	DESCRIPTION
        "
        Client Past 24-hours Output Multicast
        counter inv. :This OID indicates
        that the past 24-hours Multicast
        counter is invalid
        "
	::= { pm253PerfDatacomClientPast24StatHistoryPort2Entry 34 }


pm253perfdatacomclientPast24StatOutMulticastCountPort2 OBJECT-TYPE
	SYNTAX  Counter64
	MAX-ACCESS read-only
	STATUS current
	DESCRIPTION
        "
        Client Past 24-hours Output Multicast
        counter :This OID gives the past
        24-hours Multicast counter value
        "
	::= { pm253PerfDatacomClientPast24StatHistoryPort2Entry 35 }


pm253perfdatacomclientPast24StatOutBroadcastCountInvPort2 OBJECT-TYPE
	SYNTAX  EkiOnOff
	MAX-ACCESS read-only
	STATUS current
	DESCRIPTION
        "
        Client Past 24-hours Output Broadcast
        counter inv. :This OID indicates
        that the past 24-hours Broadcast
        counter is invalid
        "
	::= { pm253PerfDatacomClientPast24StatHistoryPort2Entry 32 }


pm253perfdatacomclientPast24StatOutBroadcastCountPort2 OBJECT-TYPE
	SYNTAX  Counter64
	MAX-ACCESS read-only
	STATUS current
	DESCRIPTION
        "
        Client Past 24-hours Output Broadcast
        counter :This OID gives the past
        24-hours Broadcast counter value
        "
	::= { pm253PerfDatacomClientPast24StatHistoryPort2Entry 33 }


pm253perfdatacomclientPast24StatOutBytesCountInvPort2 OBJECT-TYPE
	SYNTAX  EkiOnOff
	MAX-ACCESS read-only
	STATUS current
	DESCRIPTION
        "
        Client Past 24-hours Output Bytes
        counter inv. :This OID indicates
        that the past 24-hours Bytes counter
        is invalid
        "
	::= { pm253PerfDatacomClientPast24StatHistoryPort2Entry 26 }


pm253perfdatacomclientPast24StatOutBytesCountPort2 OBJECT-TYPE
	SYNTAX  Counter64
	MAX-ACCESS read-only
	STATUS current
	DESCRIPTION
        "
        Client Past 24-hours Output Bytes
        counter :This OID gives the past
        24-hours Bytes counter value
        "
	::= { pm253PerfDatacomClientPast24StatHistoryPort2Entry 27 }


pm253perfdatacomclientPast24StatInNonunicastCountInvPort2 OBJECT-TYPE
	SYNTAX  EkiOnOff
	MAX-ACCESS read-only
	STATUS current
	DESCRIPTION
        "
        Client Past 24-hours Input Non
        Unicast counter inv. :This OID
         indicates that the past 24-hours
        Non unicast counter is invalid
        "
	::= { pm253PerfDatacomClientPast24StatHistoryPort2Entry 22 }


pm253perfdatacomclientPast24StatInNonunicastCountPort2 OBJECT-TYPE
	SYNTAX  Counter64
	MAX-ACCESS read-only
	STATUS current
	DESCRIPTION
        "
        Client Past 24-hours Input Non
        Unicast counter :This OID gives
        the past 24-hours Non Unicast counter
        value
        "
	::= { pm253PerfDatacomClientPast24StatHistoryPort2Entry 23 }


pm253perfdatacomclientPast24StatInUnicastCountInvPort2 OBJECT-TYPE
	SYNTAX  EkiOnOff
	MAX-ACCESS read-only
	STATUS current
	DESCRIPTION
        "
        Client Past 24-hours Input Unicast
        counter inv. :This OID indicates
        that the past 24-hours Unicast
         counter is invalid
        "
	::= { pm253PerfDatacomClientPast24StatHistoryPort2Entry 20 }


pm253perfdatacomclientPast24StatInUnicastCountPort2 OBJECT-TYPE
	SYNTAX  Counter64
	MAX-ACCESS read-only
	STATUS current
	DESCRIPTION
        "
        Client Past 24-hours Input Unicast
        counter :This OID gives the past
        24-hours Unicast counter value
        "
	::= { pm253PerfDatacomClientPast24StatHistoryPort2Entry 21 }


pm253perfdatacomclientPast24StatInMulticastCountInvPort2 OBJECT-TYPE
	SYNTAX  EkiOnOff
	MAX-ACCESS read-only
	STATUS current
	DESCRIPTION
        "
        Client Past 24-hours Input Multicast
        counter inv. :This OID indicates
        that the past 24-hours Multicast
        counter is invalid
        "
	::= { pm253PerfDatacomClientPast24StatHistoryPort2Entry 10 }


pm253perfdatacomclientPast24StatInMulticastCountPort2 OBJECT-TYPE
	SYNTAX  Counter64
	MAX-ACCESS read-only
	STATUS current
	DESCRIPTION
        "
        Client Past 24-hours Input Multicast
        counter :This OID gives the past
        24-hours Multicast counter value
        "
	::= { pm253PerfDatacomClientPast24StatHistoryPort2Entry 11 }


pm253perfdatacomclientPast24StatInBroadcastCountInvPort2 OBJECT-TYPE
	SYNTAX  EkiOnOff
	MAX-ACCESS read-only
	STATUS current
	DESCRIPTION
        "
        Client Past 24-hours Input Broadcast
        counter inv. :This OID indicates
        that the past 24-hours Broadcast
        counter is invalid
        "
	::= { pm253PerfDatacomClientPast24StatHistoryPort2Entry 8 }


pm253perfdatacomclientPast24StatInBroadcastCountPort2 OBJECT-TYPE
	SYNTAX  Counter64
	MAX-ACCESS read-only
	STATUS current
	DESCRIPTION
        "
        Client Past 24-hours Input Broadcast
        counter :This OID gives the past
        24-hours Broadcast counter value
        "
	::= { pm253PerfDatacomClientPast24StatHistoryPort2Entry 9 }


pm253perfdatacomclientPast24StatInCrcCountInvPort2 OBJECT-TYPE
	SYNTAX  EkiOnOff
	MAX-ACCESS read-only
	STATUS current
	DESCRIPTION
        "
        Client Past 24-hours Input CRC
        counter inv. :This OID indicates
        that the past 24-hours CRC counter
        is invalid
        "
	::= { pm253PerfDatacomClientPast24StatHistoryPort2Entry 4 }


pm253perfdatacomclientPast24StatInCrcCountPort2 OBJECT-TYPE
	SYNTAX  Counter64
	MAX-ACCESS read-only
	STATUS current
	DESCRIPTION
        "
        Client Past 24-hours Input CRC
        counter :This OID gives the past
        24-hours CRC counter value
        "
	::= { pm253PerfDatacomClientPast24StatHistoryPort2Entry 5 }


pm253perfdatacomclientPast24StatInBytesCountInvPort2 OBJECT-TYPE
	SYNTAX  EkiOnOff
	MAX-ACCESS read-only
	STATUS current
	DESCRIPTION
        "
        Client Past 24-hours Input Bytes
        counter inv. :This OID indicates
        that the past 24-hours Bytes counter
        is invalid
        "
	::= { pm253PerfDatacomClientPast24StatHistoryPort2Entry 2 }


pm253perfdatacomclientPast24StatInBytesCountPort2 OBJECT-TYPE
	SYNTAX  Counter64
	MAX-ACCESS read-only
	STATUS current
	DESCRIPTION
        "
        Client Past 24-hours Input Bytes
        counter :This OID gives the past
        24-hours Bytes counter value
        "
	::= { pm253PerfDatacomClientPast24StatHistoryPort2Entry 3 }


--- *********************************************************
---     TABLE for the pm253PerfDatacomClientPast24StatHistory articles
--- *********************************************************

pm253PerfDatacomClientPast24StatHistoryPort3Table OBJECT-TYPE
	SYNTAX  SEQUENCE OF Pm253PerfDatacomClientPast24StatHistoryPort3Entry
	MAX-ACCESS not-accessible
	STATUS current
	DESCRIPTION
        "
        List of pm253PerfDatacomClientPast24StatHistory
        Article
        "
	::= { pm253MonClient 282 }


pm253PerfDatacomClientPast24StatHistoryPort3Entry OBJECT-TYPE
	SYNTAX Pm253PerfDatacomClientPast24StatHistoryPort3Entry
	MAX-ACCESS not-accessible
	STATUS current
	DESCRIPTION
        "
        Row definition for the pm253PerfDatacomClientPast24StatHistory
        table
        "
	INDEX   { pm253PerfDatacomClientPast24StatHistoryPort3Index }
	::= { pm253PerfDatacomClientPast24StatHistoryPort3Table 1 }


Pm253PerfDatacomClientPast24StatHistoryPort3Entry ::=
	SEQUENCE {
	pm253PerfDatacomClientPast24StatHistoryPort3Index
		INTEGER,
	pm253perfdatacomclientPast24StatOutNonunicastCountInvPort3
		EkiOnOff,
	pm253perfdatacomclientPast24StatOutNonunicastCountPort3
		Counter64,
	pm253perfdatacomclientPast24StatOutUnicastCountInvPort3
		EkiOnOff,
	pm253perfdatacomclientPast24StatOutUnicastCountPort3
		Counter64,
	pm253perfdatacomclientPast24StatOutMulticastCountInvPort3
		EkiOnOff,
	pm253perfdatacomclientPast24StatOutMulticastCountPort3
		Counter64,
	pm253perfdatacomclientPast24StatOutBroadcastCountInvPort3
		EkiOnOff,
	pm253perfdatacomclientPast24StatOutBroadcastCountPort3
		Counter64,
	pm253perfdatacomclientPast24StatOutBytesCountInvPort3
		EkiOnOff,
	pm253perfdatacomclientPast24StatOutBytesCountPort3
		Counter64,
	pm253perfdatacomclientPast24StatInNonunicastCountInvPort3
		EkiOnOff,
	pm253perfdatacomclientPast24StatInNonunicastCountPort3
		Counter64,
	pm253perfdatacomclientPast24StatInUnicastCountInvPort3
		EkiOnOff,
	pm253perfdatacomclientPast24StatInUnicastCountPort3
		Counter64,
	pm253perfdatacomclientPast24StatInMulticastCountInvPort3
		EkiOnOff,
	pm253perfdatacomclientPast24StatInMulticastCountPort3
		Counter64,
	pm253perfdatacomclientPast24StatInBroadcastCountInvPort3
		EkiOnOff,
	pm253perfdatacomclientPast24StatInBroadcastCountPort3
		Counter64,
	pm253perfdatacomclientPast24StatInCrcCountInvPort3
		EkiOnOff,
	pm253perfdatacomclientPast24StatInCrcCountPort3
		Counter64,
	pm253perfdatacomclientPast24StatInBytesCountInvPort3
		EkiOnOff,
	pm253perfdatacomclientPast24StatInBytesCountPort3
		Counter64
	}


pm253PerfDatacomClientPast24StatHistoryPort3Index OBJECT-TYPE
	SYNTAX  INTEGER(0..128)
	MAX-ACCESS  read-only
	STATUS current
	DESCRIPTION
        "
        Index definition for the pm253PerfDatacomClientPast24StatHistory
        table
        "
	::= { pm253PerfDatacomClientPast24StatHistoryPort3Entry 1 }


pm253perfdatacomclientPast24StatOutNonunicastCountInvPort3 OBJECT-TYPE
	SYNTAX  EkiOnOff
	MAX-ACCESS read-only
	STATUS current
	DESCRIPTION
        "
        Client Past 24-hours Output Non
        Unicast counter inv. :This OID
         indicates that the past 24-hours
        Non Unicast counter is invalid
        "
	::= { pm253PerfDatacomClientPast24StatHistoryPort3Entry 44 }


pm253perfdatacomclientPast24StatOutNonunicastCountPort3 OBJECT-TYPE
	SYNTAX  Counter64
	MAX-ACCESS read-only
	STATUS current
	DESCRIPTION
        "
        Client Past 24-hours Output Non
        Unicast counter :This OID gives
        the past 24-hours Non Unicast counter
        value
        "
	::= { pm253PerfDatacomClientPast24StatHistoryPort3Entry 45 }


pm253perfdatacomclientPast24StatOutUnicastCountInvPort3 OBJECT-TYPE
	SYNTAX  EkiOnOff
	MAX-ACCESS read-only
	STATUS current
	DESCRIPTION
        "
        Client Past 24-hours Output Unicast
        counter inv. :This OID indicates
        that the past 24-hours Unicast
         counter is invalid
        "
	::= { pm253PerfDatacomClientPast24StatHistoryPort3Entry 42 }


pm253perfdatacomclientPast24StatOutUnicastCountPort3 OBJECT-TYPE
	SYNTAX  Counter64
	MAX-ACCESS read-only
	STATUS current
	DESCRIPTION
        "
        Client Past 24-hours Output Unicast
        counter :This OID gives the past
        24-hours Unicast counter value
        "
	::= { pm253PerfDatacomClientPast24StatHistoryPort3Entry 43 }


pm253perfdatacomclientPast24StatOutMulticastCountInvPort3 OBJECT-TYPE
	SYNTAX  EkiOnOff
	MAX-ACCESS read-only
	STATUS current
	DESCRIPTION
        "
        Client Past 24-hours Output Multicast
        counter inv. :This OID indicates
        that the past 24-hours Multicast
        counter is invalid
        "
	::= { pm253PerfDatacomClientPast24StatHistoryPort3Entry 34 }


pm253perfdatacomclientPast24StatOutMulticastCountPort3 OBJECT-TYPE
	SYNTAX  Counter64
	MAX-ACCESS read-only
	STATUS current
	DESCRIPTION
        "
        Client Past 24-hours Output Multicast
        counter :This OID gives the past
        24-hours Multicast counter value
        "
	::= { pm253PerfDatacomClientPast24StatHistoryPort3Entry 35 }


pm253perfdatacomclientPast24StatOutBroadcastCountInvPort3 OBJECT-TYPE
	SYNTAX  EkiOnOff
	MAX-ACCESS read-only
	STATUS current
	DESCRIPTION
        "
        Client Past 24-hours Output Broadcast
        counter inv. :This OID indicates
        that the past 24-hours Broadcast
        counter is invalid
        "
	::= { pm253PerfDatacomClientPast24StatHistoryPort3Entry 32 }


pm253perfdatacomclientPast24StatOutBroadcastCountPort3 OBJECT-TYPE
	SYNTAX  Counter64
	MAX-ACCESS read-only
	STATUS current
	DESCRIPTION
        "
        Client Past 24-hours Output Broadcast
        counter :This OID gives the past
        24-hours Broadcast counter value
        "
	::= { pm253PerfDatacomClientPast24StatHistoryPort3Entry 33 }


pm253perfdatacomclientPast24StatOutBytesCountInvPort3 OBJECT-TYPE
	SYNTAX  EkiOnOff
	MAX-ACCESS read-only
	STATUS current
	DESCRIPTION
        "
        Client Past 24-hours Output Bytes
        counter inv. :This OID indicates
        that the past 24-hours Bytes counter
        is invalid
        "
	::= { pm253PerfDatacomClientPast24StatHistoryPort3Entry 26 }


pm253perfdatacomclientPast24StatOutBytesCountPort3 OBJECT-TYPE
	SYNTAX  Counter64
	MAX-ACCESS read-only
	STATUS current
	DESCRIPTION
        "
        Client Past 24-hours Output Bytes
        counter :This OID gives the past
        24-hours Bytes counter value
        "
	::= { pm253PerfDatacomClientPast24StatHistoryPort3Entry 27 }


pm253perfdatacomclientPast24StatInNonunicastCountInvPort3 OBJECT-TYPE
	SYNTAX  EkiOnOff
	MAX-ACCESS read-only
	STATUS current
	DESCRIPTION
        "
        Client Past 24-hours Input Non
        Unicast counter inv. :This OID
         indicates that the past 24-hours
        Non unicast counter is invalid
        "
	::= { pm253PerfDatacomClientPast24StatHistoryPort3Entry 22 }


pm253perfdatacomclientPast24StatInNonunicastCountPort3 OBJECT-TYPE
	SYNTAX  Counter64
	MAX-ACCESS read-only
	STATUS current
	DESCRIPTION
        "
        Client Past 24-hours Input Non
        Unicast counter :This OID gives
        the past 24-hours Non Unicast counter
        value
        "
	::= { pm253PerfDatacomClientPast24StatHistoryPort3Entry 23 }


pm253perfdatacomclientPast24StatInUnicastCountInvPort3 OBJECT-TYPE
	SYNTAX  EkiOnOff
	MAX-ACCESS read-only
	STATUS current
	DESCRIPTION
        "
        Client Past 24-hours Input Unicast
        counter inv. :This OID indicates
        that the past 24-hours Unicast
         counter is invalid
        "
	::= { pm253PerfDatacomClientPast24StatHistoryPort3Entry 20 }


pm253perfdatacomclientPast24StatInUnicastCountPort3 OBJECT-TYPE
	SYNTAX  Counter64
	MAX-ACCESS read-only
	STATUS current
	DESCRIPTION
        "
        Client Past 24-hours Input Unicast
        counter :This OID gives the past
        24-hours Unicast counter value
        "
	::= { pm253PerfDatacomClientPast24StatHistoryPort3Entry 21 }


pm253perfdatacomclientPast24StatInMulticastCountInvPort3 OBJECT-TYPE
	SYNTAX  EkiOnOff
	MAX-ACCESS read-only
	STATUS current
	DESCRIPTION
        "
        Client Past 24-hours Input Multicast
        counter inv. :This OID indicates
        that the past 24-hours Multicast
        counter is invalid
        "
	::= { pm253PerfDatacomClientPast24StatHistoryPort3Entry 10 }


pm253perfdatacomclientPast24StatInMulticastCountPort3 OBJECT-TYPE
	SYNTAX  Counter64
	MAX-ACCESS read-only
	STATUS current
	DESCRIPTION
        "
        Client Past 24-hours Input Multicast
        counter :This OID gives the past
        24-hours Multicast counter value
        "
	::= { pm253PerfDatacomClientPast24StatHistoryPort3Entry 11 }


pm253perfdatacomclientPast24StatInBroadcastCountInvPort3 OBJECT-TYPE
	SYNTAX  EkiOnOff
	MAX-ACCESS read-only
	STATUS current
	DESCRIPTION
        "
        Client Past 24-hours Input Broadcast
        counter inv. :This OID indicates
        that the past 24-hours Broadcast
        counter is invalid
        "
	::= { pm253PerfDatacomClientPast24StatHistoryPort3Entry 8 }


pm253perfdatacomclientPast24StatInBroadcastCountPort3 OBJECT-TYPE
	SYNTAX  Counter64
	MAX-ACCESS read-only
	STATUS current
	DESCRIPTION
        "
        Client Past 24-hours Input Broadcast
        counter :This OID gives the past
        24-hours Broadcast counter value
        "
	::= { pm253PerfDatacomClientPast24StatHistoryPort3Entry 9 }


pm253perfdatacomclientPast24StatInCrcCountInvPort3 OBJECT-TYPE
	SYNTAX  EkiOnOff
	MAX-ACCESS read-only
	STATUS current
	DESCRIPTION
        "
        Client Past 24-hours Input CRC
        counter inv. :This OID indicates
        that the past 24-hours CRC counter
        is invalid
        "
	::= { pm253PerfDatacomClientPast24StatHistoryPort3Entry 4 }


pm253perfdatacomclientPast24StatInCrcCountPort3 OBJECT-TYPE
	SYNTAX  Counter64
	MAX-ACCESS read-only
	STATUS current
	DESCRIPTION
        "
        Client Past 24-hours Input CRC
        counter :This OID gives the past
        24-hours CRC counter value
        "
	::= { pm253PerfDatacomClientPast24StatHistoryPort3Entry 5 }


pm253perfdatacomclientPast24StatInBytesCountInvPort3 OBJECT-TYPE
	SYNTAX  EkiOnOff
	MAX-ACCESS read-only
	STATUS current
	DESCRIPTION
        "
        Client Past 24-hours Input Bytes
        counter inv. :This OID indicates
        that the past 24-hours Bytes counter
        is invalid
        "
	::= { pm253PerfDatacomClientPast24StatHistoryPort3Entry 2 }


pm253perfdatacomclientPast24StatInBytesCountPort3 OBJECT-TYPE
	SYNTAX  Counter64
	MAX-ACCESS read-only
	STATUS current
	DESCRIPTION
        "
        Client Past 24-hours Input Bytes
        counter :This OID gives the past
        24-hours Bytes counter value
        "
	::= { pm253PerfDatacomClientPast24StatHistoryPort3Entry 3 }



pm253PerfEnable OBJECT-TYPE
	SYNTAX EkiOnOff
	MAX-ACCESS read-write
	STATUS current
	DESCRIPTION
        "
        Perf. Mon. Enable :This OID enables
        the Performance Monitoring application
        "
	::= { pm253MonSync 257 }


pm253Perf15minSync OBJECT-TYPE
	SYNTAX EkiOnOff
	MAX-ACCESS read-write
	STATUS current
	DESCRIPTION
        "
        Perf. Mon. 15-min sync. :This
         OID must be used in external synchronisation
        mode only to send a 15-min synchronisation
        command
        "
	::= { pm253MonSync 259 }


pm253Perf24hSync OBJECT-TYPE
	SYNTAX EkiOnOff
	MAX-ACCESS read-write
	STATUS current
	DESCRIPTION
        "
        Perf. Mon. 24-hours sync. :This
        OID must be used in external synchronisation
        mode only to send a 24-hours synchronisation
        command
        "
	::= { pm253MonSync 260 }


pm253Perf15MinShort OBJECT-TYPE
	SYNTAX EkiOnOff
	MAX-ACCESS read-write
	STATUS current
	DESCRIPTION
        "
        15-min period is short :This OID
        indicates that the 15-min period
        lasts less than 890 seconds
        "
	::= { pm253MonTimeStamp 1 }


pm253Perf15MinLong OBJECT-TYPE
	SYNTAX EkiOnOff
	MAX-ACCESS read-write
	STATUS current
	DESCRIPTION
        "
        15-min period is long :This OID
        indicates that the 15-min period
        lasts more than 910 seconds
        "
	::= { pm253MonTimeStamp 2 }


pm253Perf24HoursShort OBJECT-TYPE
	SYNTAX Counter32
	MAX-ACCESS read-write
	STATUS current
	DESCRIPTION
        "
        24-hours period is short :This
        OID indicates that 24-hours period
        lasts less than 86390 seconds
        "
	::= { pm253MonTimeStamp 5 }


pm253Perf24HoursLong OBJECT-TYPE
	SYNTAX Counter32
	MAX-ACCESS read-write
	STATUS current
	DESCRIPTION
        "
        24-hours period is long :This
         OID indicates that 24-hours period
        lasts more than 86410 seconds
        "
	::= { pm253MonTimeStamp 6 }


pm253PerfCurrent15MinElapsedTime OBJECT-TYPE
	SYNTAX Counter32
	MAX-ACCESS read-write
	STATUS current
	DESCRIPTION
        "
        Current 15min period Elapsed Time
         :This OID gives the number of
         seconds elapsed in the current
        15-minutes period
        "
	::= { pm253MonTimeStamp 7 }


pm253PerfCurrent24HoursElapsedTime OBJECT-TYPE
	SYNTAX Counter32
	MAX-ACCESS read-write
	STATUS current
	DESCRIPTION
        "
        Current 24hours period Elapsed
        Time :This OID gives the number
        of seconds elapsed in the current
        24-hours period
        "
	::= { pm253MonTimeStamp 8 }






--- *****************************************************
--- $$$$$$$$$$$$$$$$$$$$$$$$$$$$$$$$$$$$$$$$$$$$$$$$$$$$$
---     DOWNLOAD
--- $$$$$$$$$$$$$$$$$$$$$$$$$$$$$$$$$$$$$$$$$$$$$$$$$$$$$
--- *****************************************************



--- *****************************************************
---     LEAF for the restartProcess article
--- *****************************************************
pm253DwlrestartProcess OBJECT IDENTIFIER ::= { pm253DwlOther 0 }




pm253DwlColdRestartProcessed OBJECT-TYPE
	  SYNTAX EkiOnOff
	  MAX-ACCESS read-only
	  STATUS current
	  DESCRIPTION
        "
        Cold Restart :This OID indicates
        that the PM last restart was a
         Cold RESTART
        "
	  ::= { pm253DwlrestartProcess 2 }



pm253DwlWarmRestartProcessed OBJECT-TYPE
	  SYNTAX EkiOnOff
	  MAX-ACCESS read-only
	  STATUS current
	  DESCRIPTION
        "
        Warm Restart :This OID indicates
        that the PM last restart was a
         Warm RESTART
        "
	  ::= { pm253DwlrestartProcess 1 }



--- *****************************************************
---     LEAF for the swBanksUsed article
--- *****************************************************
pm253DwlswBanksUsed OBJECT IDENTIFIER ::= { pm253DwlOther 1 }




pm253DwlSwBank2Notempty OBJECT-TYPE
	  SYNTAX EkiOnOff
	  MAX-ACCESS read-only
	  STATUS current
	  DESCRIPTION
        "
        SW bank 2 loaded   :This OID indicates
        a software is loaded in SW bank2
         <Help>  This status indicates
         if the SW bank 2 contains SW package
        "
	  ::= { pm253DwlswBanksUsed 6 }



pm253DwlSwBank1Notempty OBJECT-TYPE
	  SYNTAX EkiOnOff
	  MAX-ACCESS read-only
	  STATUS current
	  DESCRIPTION
        "
        SW bank 1 loaded   :This OID indicates
        a software is loaded in SW bank1
         <Help>  This status indicates
         if the SW bank 1 contains SW package
        "
	  ::= { pm253DwlswBanksUsed 5 }



pm253DwlSwBank2Used OBJECT-TYPE
	  SYNTAX EkiOnOff
	  MAX-ACCESS read-only
	  STATUS current
	  DESCRIPTION
        "
        SW bank 2 active  :This OID indicates
        the PM is working on SW bank 2
          <Help>  This status indicates
        if the SW bank 2 is active or standby
        "
	  ::= { pm253DwlswBanksUsed 2 }



pm253DwlSwBank1Used OBJECT-TYPE
	  SYNTAX EkiOnOff
	  MAX-ACCESS read-only
	  STATUS current
	  DESCRIPTION
        "
        SW bank 1 active  :This OID indicates
        the PM is working on SW bank 1
          <Help>  This status indicates
        if the SW bank 1 is active or standby
        "
	  ::= { pm253DwlswBanksUsed 1 }



--- *****************************************************
---     LEAF for the gwBanksUsed article
--- *****************************************************
pm253DwlgwBanksUsed OBJECT IDENTIFIER ::= { pm253DwlOther 2 }




pm253DwlGwBank4Notempty OBJECT-TYPE
	  SYNTAX EkiOnOff
	  MAX-ACCESS read-only
	  STATUS current
	  DESCRIPTION
        "
        GW bank 4 loaded  :This OID indicates
        a gateware is loaded in GW bank4
        "
	  ::= { pm253DwlgwBanksUsed 8 }



pm253DwlGwBank3Notempty OBJECT-TYPE
	  SYNTAX EkiOnOff
	  MAX-ACCESS read-only
	  STATUS current
	  DESCRIPTION
        "
        GW bank 3 loaded  :This OID indicates
        a gateware is loaded in GW bank3
         <Help>  This status indicates
         if the GW bank 3 contains GW package
        "
	  ::= { pm253DwlgwBanksUsed 7 }



pm253DwlGwBank2Notempty OBJECT-TYPE
	  SYNTAX EkiOnOff
	  MAX-ACCESS read-only
	  STATUS current
	  DESCRIPTION
        "
        GW bank 2 loaded  :This OID indicates
        a gateware is loaded in GW bank2
        "
	  ::= { pm253DwlgwBanksUsed 6 }



pm253DwlGwBank1Notempty OBJECT-TYPE
	  SYNTAX EkiOnOff
	  MAX-ACCESS read-only
	  STATUS current
	  DESCRIPTION
        "
        GW bank 1 loaded  :This OID indicates
        a gateware is loaded in GW bank1
         <Help>  This status indicates
         if the GW bank 1 contains GW package
        "
	  ::= { pm253DwlgwBanksUsed 5 }



pm253DwlGwBank4Used OBJECT-TYPE
	  SYNTAX EkiOnOff
	  MAX-ACCESS read-only
	  STATUS current
	  DESCRIPTION
        "
        GW bank 4 active  :This OID indicates
        the PM is working on GW bank 4
        "
	  ::= { pm253DwlgwBanksUsed 4 }



pm253DwlGwBank3Used OBJECT-TYPE
	  SYNTAX EkiOnOff
	  MAX-ACCESS read-only
	  STATUS current
	  DESCRIPTION
        "
        GW bank 3 active  :This OID indicates
        the PM is working on GW bank 3
          <Help>  This status indicates
        if the GW bank 3 is active or standby
        "
	  ::= { pm253DwlgwBanksUsed 3 }



pm253DwlGwBank2Used OBJECT-TYPE
	  SYNTAX EkiOnOff
	  MAX-ACCESS read-only
	  STATUS current
	  DESCRIPTION
        "
        GW bank 2 active  :This OID indicates
        the PM is working on GW bank 2
        "
	  ::= { pm253DwlgwBanksUsed 2 }



pm253DwlGwBank1Used OBJECT-TYPE
	  SYNTAX EkiOnOff
	  MAX-ACCESS read-only
	  STATUS current
	  DESCRIPTION
        "
        GW bank 1 active  :This OID indicates
        the PM is working on GW bank 1
          <Help>  This status indicates
        if the GW bank 1 is active or standby
        "
	  ::= { pm253DwlgwBanksUsed 1 }








--- *****************************************************
--- $$$$$$$$$$$$$$$$$$$$$$$$$$$$$$$$$$$$$$$$$$$$$$$$$$$$$
---     CONFIG
--- $$$$$$$$$$$$$$$$$$$$$$$$$$$$$$$$$$$$$$$$$$$$$$$$$$$$$
--- *****************************************************



--- *****************************************************
---     LEAF for the table Group accessCAisCsf
--- *****************************************************

pm253CfgAccessCAisCsf OBJECT IDENTIFIER ::= { pm253Config 1 }



--- *****************************************************
---     LEAF for the table 0012
--- *****************************************************

pm253CfgClientcaiscsfTable OBJECT-TYPE
	SYNTAX  SEQUENCE OF Pm253CfgClientcaiscsfEntry
	MAX-ACCESS not-accessible
	STATUS current
	DESCRIPTION
        "
        List of  Article
        "
	::= { pm253CfgAccessCAisCsf 1 }


pm253CfgClientcaiscsfEntry OBJECT-TYPE
	SYNTAX Pm253CfgClientcaiscsfEntry
	MAX-ACCESS not-accessible
	STATUS current
	DESCRIPTION
        "
        Row definition for the accessCAisCsf
        table
        "
	INDEX   { pm253CfgClientcaiscsfIndex }
	::= { pm253CfgClientcaiscsfTable 1 }


Pm253CfgClientcaiscsfEntry ::=
	SEQUENCE {
	pm253CfgClientcaiscsfIndex
		INTEGER,
	pm253CfgCAisModePortn
		Unsigned32,
	pm253CfgSts24cContribPortn
		Unsigned32,
	pm253CfgUpAccessioAlmPortn
		Unsigned32,
	pm253CfgUpMapperDeAlmPortn
		Unsigned32,
	pm253CfgDownMapperDeAlmPortn
		Unsigned32,
	pm253CfgDownDfrmAlmPortn
		Unsigned32,
	pm253CfgDownLineIoAlmPortn
		Unsigned32
	}


pm253CfgClientcaiscsfIndex OBJECT-TYPE
	SYNTAX  INTEGER(0..128)
	MAX-ACCESS  read-only
	STATUS current
	DESCRIPTION
        "
        Index definition for the clientcaiscsf
        table
        "
	::= { pm253CfgClientcaiscsfEntry 1 }


pm253CfgCAisModePortn OBJECT-TYPE
	SYNTAX  Unsigned32 (0..65536)
	MAX-ACCESS read-write
	STATUS current
	DESCRIPTION
        "
        CAIS mode  on Client Port :This
        register enables/disables Client
        Port  laser shutdown on CAIS insertion
        condition
        "
	::= { pm253CfgClientcaiscsfEntry 3 }


pm253CfgSts24cContribPortn OBJECT-TYPE
	SYNTAX  Unsigned32 (0..65536)
	MAX-ACCESS read-write
	STATUS current
	DESCRIPTION
        "
        Sts24c contributors on Client
         Port :This register selects the
        contributors of STS24c to downstream
        CAIS/CSF on Port
        "
	::= { pm253CfgClientcaiscsfEntry 4 }


pm253CfgUpAccessioAlmPortn OBJECT-TYPE
	SYNTAX  Unsigned32 (0..65536)
	MAX-ACCESS read-write
	STATUS current
	DESCRIPTION
        "
        CSF contributors on Client Port
        :This register configures the contributors
        to upstream CSF insertion on the
        Client Port.
        "
	::= { pm253CfgClientcaiscsfEntry 9 }


pm253CfgUpMapperDeAlmPortn OBJECT-TYPE
	SYNTAX  Unsigned32 (0..65536)
	MAX-ACCESS read-write
	STATUS current
	DESCRIPTION
        "
        CSF contributors on Client Port
        :This register configures the contributors
        to upstream CSF insertion on the
        Client Port.
        "
	::= { pm253CfgClientcaiscsfEntry 10 }


pm253CfgDownMapperDeAlmPortn OBJECT-TYPE
	SYNTAX  Unsigned32 (0..65536)
	MAX-ACCESS read-write
	STATUS current
	DESCRIPTION
        "
        CAIS contributors on Client Port
        :This register configures the contributors
        to downstream CAIS insertion on
         Client Port.
        "
	::= { pm253CfgClientcaiscsfEntry 18 }


pm253CfgDownDfrmAlmPortn OBJECT-TYPE
	SYNTAX  Unsigned32 (0..65536)
	MAX-ACCESS read-write
	STATUS current
	DESCRIPTION
        "
        CAIS contributors on Client Port
        :This register configures the contributors
        to downstream CAIS insertion on
         Client Port.
        "
	::= { pm253CfgClientcaiscsfEntry 19 }


pm253CfgDownLineIoAlmPortn OBJECT-TYPE
	SYNTAX  Unsigned32 (0..65536)
	MAX-ACCESS read-write
	STATUS deprecated
	DESCRIPTION
        "
        CAIS contributors on Client Port
        :This register configures the contributors
        to downstream CAIS insertion on
         Client Port.
        "
	::= { pm253CfgClientcaiscsfEntry 22 }


--- *****************************************************
---     LEAF for the table Group startup
--- *****************************************************

pm253CfgStartup OBJECT IDENTIFIER ::= { pm253Config 2 }



--- *****************************************************
---     LEAF for the table 2114
--- *****************************************************

pm253CfgClientStartupTable OBJECT-TYPE
	SYNTAX  SEQUENCE OF Pm253CfgClientStartupEntry
	MAX-ACCESS not-accessible
	STATUS current
	DESCRIPTION
        "
        List of  Article
        "
	::= { pm253CfgStartup 1 }


pm253CfgClientStartupEntry OBJECT-TYPE
	SYNTAX Pm253CfgClientStartupEntry
	MAX-ACCESS not-accessible
	STATUS current
	DESCRIPTION
        "
        Row definition for the startup
        table
        "
	INDEX   { pm253CfgClientStartupIndex }
	::= { pm253CfgClientStartupTable 1 }


Pm253CfgClientStartupEntry ::=
	SEQUENCE {
	pm253CfgClientStartupIndex
		INTEGER,
	pm253CfgSystConfPortPortn
		Unsigned32,
	pm253CfgNetConfPortPortn
		Unsigned32,
	pm253CfgPortsOptionsPortn
		Unsigned32
	}


pm253CfgClientStartupIndex OBJECT-TYPE
	SYNTAX  INTEGER(0..128)
	MAX-ACCESS  read-only
	STATUS current
	DESCRIPTION
        "
        Index definition for the clientStartup
        table
        "
	::= { pm253CfgClientStartupEntry 1 }


pm253CfgSystConfPortPortn OBJECT-TYPE
	SYNTAX  Unsigned32 (0..65536)
	MAX-ACCESS read-write
	STATUS current
	DESCRIPTION
        "
        Default Settings on Client Port
        :This  register configures the
         default initialisation settings
        on the client port.
        "
	::= { pm253CfgClientStartupEntry 3 }


pm253CfgNetConfPortPortn OBJECT-TYPE
	SYNTAX  Unsigned32 (0..65536)
	MAX-ACCESS read-write
	STATUS current
	DESCRIPTION
        "
        Default Protocol on Client Port
        :This register configures the default
        initialisation protocol on the
         client port.
        "
	::= { pm253CfgClientStartupEntry 4 }


pm253CfgPortsOptionsPortn OBJECT-TYPE
	SYNTAX  Unsigned32 (0..65536)
	MAX-ACCESS read-write
	STATUS deprecated
	DESCRIPTION
        "
        Default Options on Client Port
        :This register configures the default
        options on the client port
        "
	::= { pm253CfgClientStartupEntry 6 }


--- *****************************************************
---     LEAF for the table 2194
--- *****************************************************

pm253tablelineStartup OBJECT IDENTIFIER ::= { pm253CfgStartup 2 }



pm253CfgsystConfLine1 OBJECT-TYPE
	  SYNTAX Unsigned32 (0..65536)
	  MAX-ACCESS read-write
	  STATUS current
	  DESCRIPTION
        "
        Default Settings on Line 1 :This
        register configures the default
        initialisation settings on Line
        port 1.
        "
	  ::= { pm253tablelineStartup 2 }



pm253CfgsystConfLine2 OBJECT-TYPE
	  SYNTAX Unsigned32 (0..65536)
	  MAX-ACCESS read-write
	  STATUS current
	  DESCRIPTION
        "
        Default Settings on Line 2 :This
        register configures the default
        initialisation settings on Line
        port 2.
        "
	  ::= { pm253tablelineStartup 6 }



pm253CfglineSelection OBJECT-TYPE
	  SYNTAX Unsigned32 (0..65536)
	  MAX-ACCESS read-write
	  STATUS current
	  DESCRIPTION
        "
        Default Settings of active line
        :This  register configures the
         start up active line.
        "
	  ::= { pm253tablelineStartup 7 }



pm253CfglineOptions OBJECT-TYPE
	  SYNTAX Unsigned32 (0..65536)
	  MAX-ACCESS read-write
	  STATUS current
	  DESCRIPTION
        "
        Default Options on Active Line
        Port :This register configures
         the default options on the active
        line port
        "
	  ::= { pm253tablelineStartup 9 }



--- *****************************************************
---     LEAF for the table Group labels
--- *****************************************************

pm253CfgLabels OBJECT IDENTIFIER ::= { pm253Config 3 }



--- *****************************************************
---     LEAF for the table NO_VALUE
--- *****************************************************

pm253CfgLabelclientTable OBJECT-TYPE
	SYNTAX  SEQUENCE OF Pm253CfgLabelclientEntry
	MAX-ACCESS not-accessible
	STATUS current
	DESCRIPTION
        "
        List of  Article
        "
	::= { pm253CfgLabels 1 }


pm253CfgLabelclientEntry OBJECT-TYPE
	SYNTAX Pm253CfgLabelclientEntry
	MAX-ACCESS not-accessible
	STATUS current
	DESCRIPTION
        "
        Row definition for the labels
         table
        "
	INDEX   { pm253CfgLabelclientIndex }
	::= { pm253CfgLabelclientTable 1 }


Pm253CfgLabelclientEntry ::=
	SEQUENCE {
	pm253CfgLabelclientIndex
		INTEGER,
	pm253CfgLabelclientPortn
		DisplayString
	}


pm253CfgLabelclientIndex OBJECT-TYPE
	SYNTAX  INTEGER(0..128)
	MAX-ACCESS  read-only
	STATUS current
	DESCRIPTION
        "
        Index definition for the labelclient
        table
        "
	::= { pm253CfgLabelclientEntry 1 }


pm253CfgLabelclientPortn OBJECT-TYPE
	SYNTAX  DisplayString( SIZE(1..16))
	MAX-ACCESS read-write
	STATUS current
	DESCRIPTION
        "
        Default settings on the label
         of the Ports :These registers
         configures the default initialisation
        settings of the labels of the ports.
        "
	::= { pm253CfgLabelclientEntry 3 }


--- *****************************************************
---     LEAF for the table NO_VALUE
--- *****************************************************

pm253CfgLabellineTable OBJECT-TYPE
	SYNTAX  SEQUENCE OF Pm253CfgLabellineEntry
	MAX-ACCESS not-accessible
	STATUS current
	DESCRIPTION
        "
        List of  Article
        "
	::= { pm253CfgLabels 2 }


pm253CfgLabellineEntry OBJECT-TYPE
	SYNTAX Pm253CfgLabellineEntry
	MAX-ACCESS not-accessible
	STATUS current
	DESCRIPTION
        "
        Row definition for the labels
         table
        "
	INDEX   { pm253CfgLabellineIndex }
	::= { pm253CfgLabellineTable 1 }


Pm253CfgLabellineEntry ::=
	SEQUENCE {
	pm253CfgLabellineIndex
		INTEGER,
	pm253CfgLabellinePortn
		DisplayString
	}


pm253CfgLabellineIndex OBJECT-TYPE
	SYNTAX  INTEGER(0..128)
	MAX-ACCESS  read-only
	STATUS current
	DESCRIPTION
        "
        Index definition for the labelline
        table
        "
	::= { pm253CfgLabellineEntry 1 }


pm253CfgLabellinePortn OBJECT-TYPE
	SYNTAX  DisplayString( SIZE(1..16))
	MAX-ACCESS read-write
	STATUS current
	DESCRIPTION
        "
        Default settings on the label
         of the lines :These registers
         configures the default initialisation
        settings of the labels of the lines.
        "
	::= { pm253CfgLabellineEntry 3 }



pm253CfgWriteConfiguration  OBJECT-TYPE
	SYNTAX EkiOnOff
	MAX-ACCESS read-write
	STATUS current
	DESCRIPTION
	"Write configuration to PM: This OID, when sets,
	 write the complete configuration to the PM."
	::= { pm253Config 257 }






--- *****************************************************
---     TRAP OBJECTS
--- *****************************************************

pm253TrapPortNumber OBJECT-TYPE
	SYNTAX INTEGER(1..64)
	MAX-ACCESS read-only
	STATUS current
	DESCRIPTION
	"Last port which generated a trap"
	::= { pm253traps 2 }

pm253TrapBoardNumber OBJECT-TYPE
	SYNTAX INTEGER(1..64)
	MAX-ACCESS read-only
	STATUS current
	DESCRIPTION
	"Last module which generated a trap"
	::= { pm253traps 3 }

pm253TrapLineNumber OBJECT-TYPE
	SYNTAX INTEGER(1..64)
	MAX-ACCESS read-only
	STATUS current
	DESCRIPTION
	"Last line which generated a trap"
	::= { pm253traps 4 }







--- *****************************************************
---     Line TRAPS
--- *****************************************************

pm253LineTrapNotUrgentGoesOn NOTIFICATION-TYPE
	OBJECTS {pm253AlmLineDdmWarningPortn, pm253TrapLineNumber, pm253TrapBoardNumber}
	STATUS current
	--&FILTNAME    "PM253 Line Not Urgent ON"
	--&ACTIONS     { log, minor }
	--&MATCH       { pm253AlmLineDdmWarningPortn "on", pm253TrapLineNumber "$2", pm253TrapBoardNumber "$3"}
	--&MESG        "DDM Warning appears on Line Port $2 of PM253 in Slot $3 ($A)"
	DESCRIPTION "Not urgent line default is activated"
	::= { pm253traps 30 }

pm253LineTrapNotUrgentGoesOff NOTIFICATION-TYPE
	OBJECTS {pm253AlmLineDdmWarningPortn, pm253TrapLineNumber, pm253TrapBoardNumber}
	STATUS current
	--&FILTNAME    "PM253 Line Not Urgent OFF"
	--&ACTIONS     { log, normal }
	--&CLEARS      { "PM253 Line Not Urgent ON" }
	--&MATCH       { pm253AlmLineDdmWarningPortn "on", pm253TrapLineNumber "$2", pm253TrapBoardNumber "$3"}
	--&MESG        "DDM Warning disappears on Line Port $2 of PM253 in Slot $3 ($A)"
	DESCRIPTION "Not urgent line default disappeared"
	::= { pm253traps 31 }

pm253LineTrapUrgentGoesOn NOTIFICATION-TYPE
	OBJECTS {pm253AlmLineDdmAlmPortn, pm253TrapLineNumber, pm253TrapBoardNumber}
	STATUS current
	--&FILTNAME    "PM253 Line Urgent ON"
	--&ACTIONS     { log, major }
	--&MATCH       { pm253AlmLineDdmAlmPortn "on", pm253TrapLineNumber "$2", pm253TrapBoardNumber "$3"}
	--&MESG        "DDM Alarm appears on Line Port $2 of PM253 in Slot $3 ($A)"
	DESCRIPTION "Urgent line default is activated"
	::= { pm253traps 32 }

pm253LineTrapUrgentGoesOff NOTIFICATION-TYPE
	OBJECTS {pm253AlmLineDdmAlmPortn, pm253TrapLineNumber, pm253TrapBoardNumber}
	STATUS current
	--&FILTNAME    "PM253 Line Urgent OFF"
	--&ACTIONS     { log, normal }
	--&CLEARS      { "PM253 Line Urgent ON" }
	--&MATCH       { pm253AlmLineDdmAlmPortn "on", pm253TrapLineNumber "$2", pm253TrapBoardNumber "$3"}
	--&MESG        "DDM Alarm disappears on Line Port $2 of PM253 in Slot $3 ($A)"
	DESCRIPTION "Urgent line default disappeared"
	::= { pm253traps 33 }

pm253LineTrapCritGoesOn NOTIFICATION-TYPE
	OBJECTS {pm253AlmLineFailPortn, pm253AlmLineHwFailPortn, pm253AlmLineActivePortn, pm253TrapLineNumber, pm253TrapBoardNumber}
	STATUS current
	--&FILTNAME    "PM253 Line Fail ON"
	--&ACTIONS     { log, critical }
	--&MATCH       { pm253AlmLineFailPortn "on", pm253AlmLineHwFailPortn "*", pm253AlmLineActivePortn "$3", pm253TrapLineNumber "$4", pm253TrapBoardNumber "$5"}
	--&MESG        "Line Port $4 Down on PM253 in Slot $5 ($A)"

	--&FILTNAME    "PM253 Line HW Fail ON (Hidden)"
	--&ACTIONS     { info }
	--&MATCH       { pm253AlmLineFailPortn "*", pm253AlmLineHwFailPortn "on", pm253AlmLineActivePortn "$3", pm253TrapLineNumber "$4", pm253TrapBoardNumber "$5"}
	--&MESG        "Line Port $4 Down on PM253 in Slot $5 ($A)"
	DESCRIPTION "Critical line default is activated"
	::= { pm253traps 34 }

pm253LineTrapCritGoesOff NOTIFICATION-TYPE
	OBJECTS {pm253AlmLineFailPortn, pm253AlmLineHwFailPortn, pm253AlmLineActivePortn, pm253TrapLineNumber, pm253TrapBoardNumber}
	STATUS current
	--&FILTNAME    "PM253 Line Fail OFF"
	--&ACTIONS     { log,  normal }
	--&CLEARS      { "PM253 Line Fail ON" }
	--&MATCH       { pm253AlmLineFailPortn "on", pm253AlmLineHwFailPortn "*", pm253AlmLineActivePortn "$3", pm253TrapLineNumber "$4", pm253TrapBoardNumber "$5"}
	--&MESG        "Line Port $4 Up on PM253 in Slot $5 ($A)"

	--&FILTNAME    "PM253 Line HW Fail OFF (Hidden)"
	--&ACTIONS     { info }
	--&MATCH       { pm253AlmLineFailPortn "*", pm253AlmLineHwFailPortn "on", pm253AlmLineActivePortn "$3", pm253TrapLineNumber "$4", pm253TrapBoardNumber "$5"}
	--&MESG        "Line Port $4 Up on PM253 in Slot $5 ($A)"
	DESCRIPTION "Critical line default disappeared"
	::= { pm253traps 35 }






--- *****************************************************
---     PORTS TRAPS
--- *****************************************************

pm253PortnTrapNotUrgentGoesOn NOTIFICATION-TYPE
	OBJECTS {pm253AlmClientSfpDdmWarningPortn, pm253TrapPortNumber, pm253TrapBoardNumber}
	STATUS current
	--&FILTNAME    "PM253 Client Not Urgent ON"
	--&ACTIONS     { log, minor }
	--&MATCH       { pm253AlmClientSfpDdmWarningPortn "on", pm253TrapPortNumber "$2", pm253TrapBoardNumber "$3"}
	--&MESG        "DDM Warning appears on Client Port $2 of PM253 in Slot $3 ($A)"
	DESCRIPTION "Not urgent client default is activated"
	::= { pm253traps 40 }

pm253PortnTrapNotUrgentGoesOff NOTIFICATION-TYPE
	OBJECTS {pm253AlmClientSfpDdmWarningPortn, pm253TrapPortNumber, pm253TrapBoardNumber}
	STATUS current
	--&FILTNAME    "PM253 Client Not Urgent OFF"
	--&ACTIONS     { log, normal }
	--&CLEARS      { "PM253 Client Not Urgent ON" }
	--&MATCH       { pm253AlmClientSfpDdmWarningPortn "on", pm253TrapPortNumber "$2", pm253TrapBoardNumber "$3"}
	--&MESG        "DDM Warning appears on Client Port $2 of PM253 in Slot $3 ($A)"
	DESCRIPTION "Not urgent client default disappeared"
	::= { pm253traps 41 }

pm253PortnTrapUrgentGoesOn NOTIFICATION-TYPE
	OBJECTS {pm253AlmClientSfpDdmAlmPortn, pm253TrapPortNumber, pm253TrapBoardNumber}
	STATUS current
	--&FILTNAME    "PM253 Client Urgent ON"
	--&ACTIONS     { log, major }
	--&MATCH       { pm253AlmClientSfpDdmAlmPortn "on", pm253TrapPortNumber "$2", pm253TrapBoardNumber "$3"}
	--&MESG        "DDM Alarm appears on Client Port $2 of PM253 in Slot $3 ($A)"
	DESCRIPTION "Urgent client default is activated"
	::= { pm253traps 42 }

pm253PortnTrapUrgentGoesOff NOTIFICATION-TYPE
	OBJECTS {pm253AlmClientSfpDdmAlmPortn, pm253TrapPortNumber, pm253TrapBoardNumber}
	STATUS current
	--&FILTNAME    "PM253 Client Urgent OFF"
	--&ACTIONS     { log, normal }
	--&CLEARS      { "PM253 Client Urgent ON" }
	--&MATCH       { pm253AlmClientSfpDdmAlmPortn "on", pm253TrapPortNumber "$2", pm253TrapBoardNumber "$3"}
	--&MESG        "DDM Alarm disappears on Client Port $2 of PM253 in Slot $3 ($A)"
	DESCRIPTION "Urgent client default disappeared"
	::= { pm253traps 43 }

pm253PortnTrapCritGoesOn NOTIFICATION-TYPE
	OBJECTS {pm253AlmClientFailAccPortn, pm253AlmClientHwFailAccPortn, pm253TrapPortNumber, pm253TrapBoardNumber}
	STATUS current
	--&FILTNAME    "PM253 Client Fail ON"
	--&ACTIONS     { log, critical }
	--&MATCH       { pm253AlmClientFailAccPortn "on", pm253AlmClientHwFailAccPortn "*", pm253TrapPortNumber "$3", pm253TrapBoardNumber "$4"}
	--&MESG        "Client Port $3 Down on PM253 in Slot $4 ($A)"

	--&FILTNAME    "PM253 Client HW Fail ON (Hidden)"
	--&ACTIONS     { info }
	--&MATCH       { pm253AlmClientFailAccPortn "*", pm253AlmClientHwFailAccPortn "on", pm253TrapPortNumber "$3", pm253TrapBoardNumber "$4"}
	--&MESG        "Client Port $3 Down on PM253 in Slot $4 ($A)"
	DESCRIPTION "Critical client default is activated"
	::= { pm253traps 44 }

pm253PortnTrapCritGoesOff NOTIFICATION-TYPE
	OBJECTS {pm253AlmClientFailAccPortn, pm253AlmClientHwFailAccPortn, pm253TrapPortNumber, pm253TrapBoardNumber}
	STATUS current
	--&FILTNAME    "PM253 Client Fail OFF"
	--&ACTIONS     { log, normal }
	--&CLEARS      { "PM253 Client Fail ON" }
	--&MATCH       { pm253AlmClientFailAccPortn "on", pm253AlmClientHwFailAccPortn "*", pm253TrapPortNumber "$3", pm253TrapBoardNumber "$4"}
	--&MESG        "Client Port $3 Up on PM253 in Slot $4 ($A)"

	--&FILTNAME    "PM253 Client HW Fail OFF (Hidden)"
	--&ACTIONS     { info }
	--&MATCH       { pm253AlmClientFailAccPortn "*", pm253AlmClientHwFailAccPortn "on", pm253TrapPortNumber "$3", pm253TrapBoardNumber "$4"}
	--&MESG        "Client Port $3 Up on PM253 in Slot $4 ($A)"
	DESCRIPTION "Critical client default disappeared"
	::= { pm253traps 45 }






END
