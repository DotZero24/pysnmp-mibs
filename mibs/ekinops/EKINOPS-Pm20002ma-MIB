-- *****************************************************************
-- EKINOPS-Pm20002ma.TXT:  MIB
--
--MIB Part Number:3MI00037AAAD
--MIB Version:03
--
-- Copyright (c) 2016 by Ekinops
-- All rights reserved.
--
-- *****************************************************************

EKINOPS-Pm20002ma-MIB DEFINITIONS ::= BEGIN

IMPORTS
	ekinops,
	EkiState,
	EkiOnOff,
	EkiMode,
	EkiProtocol,
	EkiApiState,
	EkiSynchroMode,
	EkiMeasureType
			FROM EKINOPS-MIB
        MODULE-IDENTITY,
        OBJECT-TYPE,
        NOTIFICATION-TYPE,
	Unsigned32,
	Integer32,
	Counter32,
	IpAddress
        		FROM SNMPv2-SMI
 	TEXTUAL-CONVENTION,
	DisplayString
                FROM SNMPv2-TC;

modulePm20002ma MODULE-IDENTITY
        LAST-UPDATED "201704130000Z"
        ORGANIZATION "Ekinops"
        CONTACT-INFO
         "Ekinops

          3, rue Blaise Pascal
          F-22300 Lannion / FRANCE

          Tel : +33 (0)2 96 05 00 30
          Fax : +33 (0)2 96 48 62 39

          E-mail: support@ekinops.fr"
        DESCRIPTION
          "Creation."

	REVISION "201511090000Z"
	DESCRIPTION
	  "Creation for PM20002MA"
	REVISION "201604200000Z"
	DESCRIPTION
	  "Label modif on a line counter"
	REVISION "201604290000Z"
	DESCRIPTION
	  "Objects name modification on perf objects"
	REVISION "201605200000Z"
	DESCRIPTION
	  "New AlarmType – synthesisAlarm (12)"
	REVISION "201606020000Z"
	DESCRIPTION
	  "Capabilities objects of Table 5"
	REVISION "201704130000Z"
	DESCRIPTION
	  "Modules Mode"
        ::= { ekinops 73 }



--- *****************************************************
---     LEAF LEVEL 2
--- *****************************************************


pm20002maalarms OBJECT IDENTIFIER ::= { modulePm20002ma 2 }
pm20002maAlmOther OBJECT IDENTIFIER ::= { pm20002maalarms 1 }
pm20002maAlmOtherNurg OBJECT IDENTIFIER ::= { pm20002maAlmOther 1 }
pm20002maAlmOtherUrg OBJECT IDENTIFIER ::= { pm20002maAlmOther 2 }
pm20002maAlmOtherCrit OBJECT IDENTIFIER ::= { pm20002maAlmOther 3 }

pm20002maAlmClient OBJECT IDENTIFIER ::= { pm20002maalarms 2 }
pm20002maAlmClientNurg OBJECT IDENTIFIER ::= { pm20002maAlmClient 1 }
pm20002maAlmClientUrg OBJECT IDENTIFIER ::= { pm20002maAlmClient 2 }
pm20002maAlmClientCrit OBJECT IDENTIFIER ::= { pm20002maAlmClient 3 }

pm20002maAlmLine OBJECT IDENTIFIER ::= { pm20002maalarms 3 }
pm20002maAlmLineNurg OBJECT IDENTIFIER ::= { pm20002maAlmLine 1 }
pm20002maAlmLineUrg OBJECT IDENTIFIER ::= { pm20002maAlmLine 2 }
pm20002maAlmLineCrit OBJECT IDENTIFIER ::= { pm20002maAlmLine 3 }





pm20002mameasures OBJECT IDENTIFIER ::= { modulePm20002ma 3 }
pm20002maMesrOther OBJECT IDENTIFIER ::= { pm20002mameasures 1 }
pm20002maMesrClient OBJECT IDENTIFIER ::= { pm20002mameasures 2 }
pm20002maMesrLine OBJECT IDENTIFIER ::= { pm20002mameasures 3 }




pm20002macounters OBJECT IDENTIFIER ::= { modulePm20002ma 4 }
pm20002maCntOther OBJECT IDENTIFIER ::= { pm20002macounters 1 }
pm20002maCntClient OBJECT IDENTIFIER ::= { pm20002macounters 2 }
pm20002maCntLine OBJECT IDENTIFIER ::= { pm20002macounters 3 }


pm20002macontrolsWrite OBJECT IDENTIFIER ::= { modulePm20002ma 6 }
pm20002maCtrlOther OBJECT IDENTIFIER ::= { pm20002macontrolsWrite 1 }
pm20002maCtrlClient OBJECT IDENTIFIER ::= { pm20002macontrolsWrite 2 }
pm20002maCtrlLine OBJECT IDENTIFIER ::= { pm20002macontrolsWrite 3 }

pm20002mari OBJECT IDENTIFIER ::= { modulePm20002ma 7 }
pm20002mariTable OBJECT IDENTIFIER ::= { pm20002mari 1 }

pm20002madownload OBJECT IDENTIFIER ::= { modulePm20002ma 8 }
pm20002maDwlOther OBJECT IDENTIFIER ::= { pm20002madownload 1 }
pm20002maDwlClient OBJECT IDENTIFIER ::= { pm20002madownload 2 }
pm20002maDwlLine OBJECT IDENTIFIER ::= { pm20002madownload 3 }


pm20002maConfig OBJECT IDENTIFIER ::= { modulePm20002ma 9 }

pm20002matraps OBJECT IDENTIFIER ::= { modulePm20002ma 10 }



pm20002maMonitoring OBJECT IDENTIFIER ::= { modulePm20002ma 11}

pm20002maMonOther OBJECT IDENTIFIER ::= { pm20002maMonitoring 1 }
pm20002maMonRmon OBJECT IDENTIFIER ::= { pm20002maMonOther 3 }

pm20002maMonClient OBJECT IDENTIFIER ::= { pm20002maMonitoring 2 }
pm20002maMonClientRmonCounter OBJECT IDENTIFIER ::= { pm20002maMonClient 4 }


pm20002maMonPerfOther OBJECT IDENTIFIER ::= { pm20002maMonitoring 5 }
pm20002maMonPerfSync OBJECT IDENTIFIER ::= { pm20002maMonPerfOther 1 }
pm20002maMonPerfTimeStamp OBJECT IDENTIFIER ::= { pm20002maMonPerfOther 2 }


pm20002maMonPerfClient OBJECT IDENTIFIER ::= { pm20002maMonitoring 6 }

pm20002maMonPerfLine OBJECT IDENTIFIER ::= { pm20002maMonitoring 7 }



--- *****************************************************
--- $$$$$$$$$$$$$$$$$$$$$$$$$$$$$$$$$$$$$$$$$$$$$$$$$$$$$
---     TEXTUAL-CONVENTION
--- $$$$$$$$$$$$$$$$$$$$$$$$$$$$$$$$$$$$$$$$$$$$$$$$$$$$$
--- *****************************************************

Pm20002maMultiRate ::= TEXTUAL-CONVENTION
    STATUS      current
    DESCRIPTION "different rate for a client port"
    SYNTAX INTEGER {
		rate100Mhz(0),
		rate250Mhz(1),
		rate500Mhz(2),
		rate1Ghz(3)
           }

Pm20002maOtxMode ::= TEXTUAL-CONVENTION
    STATUS      current
    DESCRIPTION "Different modes on OTX-TLH on client and line ports"
    SYNTAX INTEGER {
		otx80mode(1),
		otx60mode(2),
		otxadjustmode(4)
           }

Pm20002maOtxGrid ::= TEXTUAL-CONVENTION
    STATUS      current
    DESCRIPTION "Different grids on OTX-TLH on client and line ports"
    SYNTAX INTEGER {
		otxgrid200(200),
		otxgrid100(100),
		otxgrid50(50)
           }

Pm20002maAdjustValue ::= TEXTUAL-CONVENTION
    STATUS      current
    DESCRIPTION "Different values in Adjust mode on OTX-TLH on client and line ports"
    SYNTAX INTEGER {
		otxadjustvalue0(0),
		otxadjustvalue1(1),
		otxadjustvalue2(2),
		otxadjustvalue3(3),
		otxadjustvalue4(4),
		otxadjustvalue5(5),
		otxadjustvalue6(6),
		otxadjustvalue7(7),
		otxadjustvalue8(8),
		otxadjustvalue9(9),
		otxadjustvalue10(10)
           }

Pm20002maClientProtocol ::= TEXTUAL-CONVENTION
    STATUS      current
    DESCRIPTION "Different values on the protocol on the client ports"
    SYNTAX INTEGER {
		protocolclientvalue0(0),
		protocolclientvalue1(1),
		protocolclientvalue2(2),
		protocolclientvalue3(3),
		protocolclientvalue4(4),
		protocolclientvalue5(5),
		protocolclientvalue6(6),
		protocolclientvalue7(7),
		protocolclientvalue8(8)
           }

Pm20002maProtocolMode ::= TEXTUAL-CONVENTION
    STATUS      current
    DESCRIPTION "Different values on the protocol mode"
    SYNTAX INTEGER {
		protocolmodevalue0(0),
		protocolmodevalue1(1),
		protocolmodevalue2(2),
		protocolmodevalue3(3)
           }

Pm20002maOtxChannel ::= TEXTUAL-CONVENTION
    STATUS      current
    DESCRIPTION "Channel selection on transceiver Tx line ports"
    SYNTAX INTEGER

Pm20002maOrxChannel ::= TEXTUAL-CONVENTION
    STATUS      current
    DESCRIPTION "Channel selection on transceiver Rx line ports"
    SYNTAX INTEGER

Pm20002maDccMode ::= TEXTUAL-CONVENTION
    STATUS      current
    DESCRIPTION "Mode for DCC"
    SYNTAX INTEGER {
		dccNo(0),
		dccLine1(1),
		dccLine2(2)
           }

Pm20002maModuleMode ::= TEXTUAL-CONVENTION
    STATUS      current
    DESCRIPTION "Mode for the  module"
    SYNTAX INTEGER {
		unusedmode(0),
		mode200gma(1),
		mode200gmr(2),
		mode100gulh(3)
           }


--- *****************************************************
--- $$$$$$$$$$$$$$$$$$$$$$$$$$$$$$$$$$$$$$$$$$$$$$$$$$$$$
---     REMOTE INVENTORY
--- $$$$$$$$$$$$$$$$$$$$$$$$$$$$$$$$$$$$$$$$$$$$$$$$$$$$$
--- *****************************************************

pm20002maRinvReloadInventory OBJECT-TYPE
  SYNTAX EkiOnOff
  MAX-ACCESS read-write
  STATUS current
  DESCRIPTION
        "Reload the inventory: This OID triggers an
         inventory reload."
  ::= { pm20002mari 2 }

pm20002maRinvHwPlatform OBJECT-TYPE
  SYNTAX DisplayString
  MAX-ACCESS read-only
  STATUS current
  DESCRIPTION
        "HW platform description: This OID contains the
         description of the Hardware platform."
  ::= { pm20002mari 3 }

pm20002maRinvModulePlatform OBJECT-TYPE
  SYNTAX DisplayString
  MAX-ACCESS read-only
  STATUS current
  DESCRIPTION
        "Module platform description: This OID contains the
         description of the Module."
  ::= { pm20002mari 4 }

pm20002maRinvSwPlatform OBJECT-TYPE
  SYNTAX DisplayString
  MAX-ACCESS read-only
  STATUS current
  DESCRIPTION
        "SW platform description: This OID contains the
         description of the Software platform."
  ::= { pm20002mari 5 }

pm20002maRinvGwPlatform OBJECT-TYPE
  SYNTAX DisplayString
  MAX-ACCESS read-only
  STATUS current
  DESCRIPTION
        "GW platform description: This OID contains the
         description of the Gateware platform."
  ::= { pm20002mari 6 }


pm20002maRinvSfpTable OBJECT-TYPE
      SYNTAX  SEQUENCE OF Pm20002maRinvSfpEntry
      MAX-ACCESS  not-accessible
      STATUS  current
      DESCRIPTION
              "List of the SFPs on the selected module"
      ::= { pm20002mariTable 1 }

pm20002maRinvSfpEntry OBJECT-TYPE
        SYNTAX  Pm20002maRinvSfpEntry
        MAX-ACCESS  not-accessible
        STATUS  current
        DESCRIPTION
              "Row definition for the SFP table"
        INDEX   { pm20002maRinvSfpIndex }
        ::= { pm20002maRinvSfpTable 1 }



Pm20002maRinvSfpEntry::=
        SEQUENCE {
          pm20002maRinvSfpIndex
              Integer32,
          pm20002maRinvsfp
              DisplayString
        }


    pm20002maRinvSfpIndex OBJECT-TYPE
        SYNTAX  Integer32(1..16)
        MAX-ACCESS  read-only
        STATUS  current
        DESCRIPTION
              "Index for SFP table"
        ::= { pm20002maRinvSfpEntry 1 }


    pm20002maRinvsfp OBJECT-TYPE
        SYNTAX  DisplayString
        MAX-ACCESS  read-only
        STATUS  current
        DESCRIPTION
              "Inventory for the SFP: This OID contains the inventory for the SFP"
        ::= { pm20002maRinvSfpEntry 2 }




pm20002maRinvLineTable OBJECT-TYPE
      SYNTAX  SEQUENCE OF Pm20002maRinvLineEntry
      MAX-ACCESS  not-accessible
      STATUS  current
      DESCRIPTION
              "List of the XFPs on the selected module"
      ::= { pm20002mariTable 2 }

pm20002maRinvLineEntry OBJECT-TYPE
        SYNTAX  Pm20002maRinvLineEntry
        MAX-ACCESS  not-accessible
        STATUS  current
        DESCRIPTION
              "Row definition for the XFP table"
        INDEX   { pm20002maRinvLineIndex }
        ::= { pm20002maRinvLineTable 1 }



Pm20002maRinvLineEntry::=
        SEQUENCE {
          pm20002maRinvLineIndex
              Integer32,
          pm20002maRinvxfpLine
              DisplayString
        }


    pm20002maRinvLineIndex OBJECT-TYPE
        SYNTAX  Integer32(1..16)
        MAX-ACCESS  read-only
        STATUS  current
        DESCRIPTION
              "Index for XFP table"
        ::= { pm20002maRinvLineEntry 1 }


    pm20002maRinvxfpLine OBJECT-TYPE
        SYNTAX  DisplayString
        MAX-ACCESS  read-only
        STATUS  current
        DESCRIPTION
              "Inventory for the XFP: This OID contains the inventory for the XFP"
        ::= { pm20002maRinvLineEntry 2 }









--- *****************************************************
--- $$$$$$$$$$$$$$$$$$$$$$$$$$$$$$$$$$$$$$$$$$$$$$$$$$$$$
---     ALARMS
--- $$$$$$$$$$$$$$$$$$$$$$$$$$$$$$$$$$$$$$$$$$$$$$$$$$$$$
--- *****************************************************



--- *****************************************************
---     LEAF for the synthAlm0 article
--- *****************************************************
pm20002maAlmsynthAlm0 OBJECT IDENTIFIER ::= { pm20002maAlmOtherCrit 0 }




pm20002maAlmDefFuseB OBJECT-TYPE
	  SYNTAX EkiOnOff
	  MAX-ACCESS read-only
	  STATUS current
	  DESCRIPTION
        "
        Fuse B Fail :This OID indicates
        that the fuse of the power input
        B is in fail condition <Help> Status
        of the Fuse B <Condtype> DEF_FUSE_B
        <Probcause> powerProblem (36) <Alarmtype>
        equipmentAlarm (5) <Polarity> (2)
        "
	  ::= { pm20002maAlmsynthAlm0 16 }



pm20002maAlmDefFuseA OBJECT-TYPE
	  SYNTAX EkiOnOff
	  MAX-ACCESS read-only
	  STATUS current
	  DESCRIPTION
        "
        Fuse A Fail :This OID indicates
        that the fuse of the power input
        A is in fail condition <Help> Status
        of the Fuse A <Condtype> DEF_FUSE_A
        <Probcause> powerProblem (36) <Alarmtype>
        equipmentAlarm (5) <Polarity> (2)
        "
	  ::= { pm20002maAlmsynthAlm0 15 }



pm20002maAlmModGlobFail OBJECT-TYPE
	  SYNTAX EkiOnOff
	  MAX-ACCESS read-only
	  STATUS current
	  DESCRIPTION
        "
        Module Failure :This OID is set
        on detection of a failure originating
        from the RM <Help> This alarm is
        set on detection of a failure originating
        from the equipment <Condtype> MOD_GLOB_FAIL
        <Probcause> other (1) <Alarmtype>
        synthesisAlarm (12)  <Polarity>
        (2)
        "
	  ::= { pm20002maAlmsynthAlm0 9 }



pm20002maAlmFailFan OBJECT-TYPE
	  SYNTAX EkiOnOff
	  MAX-ACCESS read-only
	  STATUS current
	  DESCRIPTION
        "
        Fan Fail :This OID is at 1 when
        any fail occurs on the fan tray
        <Help> This alarm indicates that
        the Fan tray module is in a failure
        condition <Condtype> FAIL_FAN <Probcause>
        equipmentMalfunction (16) <Alarmtype>
        equipmentAlarm (5) <Polarity> (2)
        "
	  ::= { pm20002maAlmsynthAlm0 2 }



--- *****************************************************
---     LEAF for the synthAlm2 article
--- *****************************************************
pm20002maAlmsynthAlm2 OBJECT IDENTIFIER ::= { pm20002maAlmOtherNurg 2 }




pm20002maAlmMaintenanceOn OBJECT-TYPE
	  SYNTAX EkiOnOff
	  MAX-ACCESS read-only
	  STATUS current
	  DESCRIPTION
        "
        Maintenance Mode :This OID indicates
        that the RM is in maintenance mode.
        <Help> This alarm indicates that
        the maintenance mode is enabled
        on the PM <Condtype> MAINTENANCE_ON
        <Probcause> informationalStatus(1000)
        <Alarmtype> other (1) <Polarity>
        (2)
        "
	  ::= { pm20002maAlmsynthAlm2 5 }



pm20002maAlmCorrelatOff OBJECT-TYPE
	  SYNTAX EkiOnOff
	  MAX-ACCESS read-only
	  STATUS current
	  DESCRIPTION
        "
        Not Used :This OID, when set,
         indicates that alarm correlation
        is not being performed. <Condtype>
        CORRELAT_OFF <Probcause> informationalStatus(1000)
        <Alarmtype> other (1) <Polarity>
        (2)
        "
	  ::= { pm20002maAlmsynthAlm2 4 }



pm20002maAlmConfTableLoad OBJECT-TYPE
	  SYNTAX EkiOnOff
	  MAX-ACCESS read-only
	  STATUS current
	  DESCRIPTION
        "
        PM Configuration Load :This OID
         is at 1 during the loading of
         configuration tables in the modules
        RAM. <Condtype> CONF_TABLE_LOAD
        <Probcause> informationalStatus(1000)
        <Alarmtype> other (1) <Polarity>
        (2)
        "
	  ::= { pm20002maAlmsynthAlm2 3 }



pm20002maAlmInvUpload OBJECT-TYPE
	  SYNTAX EkiOnOff
	  MAX-ACCESS read-only
	  STATUS current
	  DESCRIPTION
        "
        Inventory Upload :This OID is
         at 1 during the uploading of PM
        inventory information. <Condtype>
        INV_UPLOAD <Probcause> informationalStatus(1000)
        <Alarmtype> other (1) <Polarity>
        (2)
        "
	  ::= { pm20002maAlmsynthAlm2 2 }



pm20002maAlmConfTableSave OBJECT-TYPE
	  SYNTAX EkiOnOff
	  MAX-ACCESS read-only
	  STATUS current
	  DESCRIPTION
        "
        PM Configuration Save :This OID
        is at 1 during the saving of a
         new configuration table in the
        module Flash memory. <Condtype>
        CONF_TABLE_SAVE <Probcause> informationalStatus(1000)
        <Alarmtype> other (1) <Polarity>
        (2)
        "
	  ::= { pm20002maAlmsynthAlm2 1 }



--- *********************************************************
---     TABLE for the pm20002maAlmsynthAlmPort articles
--- *********************************************************

pm20002maAlmsynthAlmPortTable OBJECT-TYPE
	SYNTAX  SEQUENCE OF Pm20002maAlmsynthAlmPortEntry
	MAX-ACCESS not-accessible
	STATUS current
	DESCRIPTION
        "
        List of pm20002maAlmsynthAlmPort
        Article
        "
	::= { pm20002maAlmClientCrit 8 }


pm20002maAlmsynthAlmPortEntry OBJECT-TYPE
	SYNTAX Pm20002maAlmsynthAlmPortEntry
	MAX-ACCESS not-accessible
	STATUS current
	DESCRIPTION
        "
        Row definition for the pm20002maAlmsynthAlmPort
        table
        "
	INDEX   { pm20002maAlmsynthAlmPortIndex }
	::= { pm20002maAlmsynthAlmPortTable 1 }


Pm20002maAlmsynthAlmPortEntry ::=
	SEQUENCE {
	pm20002maAlmsynthAlmPortIndex
		INTEGER,
	pm20002maAlmUpCsfPortn
		EkiOnOff,
	pm20002maAlmFailAccPortn
		EkiOnOff,
	pm20002maAlmSfpDdmAlmPortn
		EkiOnOff,
	pm20002maAlmSfpDdmWarningPortn
		EkiOnOff,
	pm20002maAlmDwCaisPortn
		EkiOnOff,
	pm20002maAlmClientRemoteOosPortn
		EkiOnOff,
	pm20002maAlmClientLocalOosPortn
		EkiOnOff,
	pm20002maAlmDwLsdPortn
		EkiOnOff,
	pm20002maAlmHwFailAccPortn
		EkiOnOff,
	pm20002maAlmDdmAbsentPortn
		EkiOnOff,
	pm20002maAlmSfpAbsentPortn
		EkiOnOff
	}


pm20002maAlmsynthAlmPortIndex OBJECT-TYPE
	SYNTAX  INTEGER(0..128)
	MAX-ACCESS  read-only
	STATUS current
	DESCRIPTION
        "
        Index definition for the pm20002maAlmsynthAlmPort
        table
        "
	::= { pm20002maAlmsynthAlmPortEntry 1 }


pm20002maAlmUpCsfPortn OBJECT-TYPE
	SYNTAX  EkiOnOff
	MAX-ACCESS read-only
	STATUS current
	DESCRIPTION
        "
        Client Signal Fail Inserted :This
        OID indicates a CSF has been inserted
        in the upstream client port. <Help>
        This status indicates if a Client
        Signal Fail is currently inserted
        on the line signal for this client
        port <Condtype> UP_CSF_1 <Probcause>
        informationalStatus(1000) <Alarmtype>
        other (1) <Polarity> (2)
        "
	::= { pm20002maAlmsynthAlmPortEntry 17 }


pm20002maAlmFailAccPortn OBJECT-TYPE
	SYNTAX  EkiOnOff
	MAX-ACCESS read-only
	STATUS current
	DESCRIPTION
        "
        Client Access Fail :This OID indicates
        a failure on the Client port <Help>
        This alarm indicates a failure
         on the Client port <Condtype>
         FAIL_ACC_1 <Probcause> equipmentMalfunction
        (16) <Alarmtype> synthesisAlarm
        (12)  <Polarity> (2)
        "
	::= { pm20002maAlmsynthAlmPortEntry 13 }


pm20002maAlmSfpDdmAlmPortn OBJECT-TYPE
	SYNTAX  EkiOnOff
	MAX-ACCESS read-only
	STATUS current
	DESCRIPTION
        "
        Alarm On Client Trscv DDM :This
        OID indicates an alarm is being
        received from the Client Transceiver
        DDM <Help> This alarm indicates
        if a DDM Alarm has been detected
        on the client transceiver <Condtype>
        SFP_DDM_ALM_1 <Probcause> inputOutputDeviceError
        (24) <Alarmtype> synthesisAlarm
        (12)  <Polarity> (2)
        "
	::= { pm20002maAlmsynthAlmPortEntry 11 }


pm20002maAlmSfpDdmWarningPortn OBJECT-TYPE
	SYNTAX  EkiOnOff
	MAX-ACCESS read-only
	STATUS current
	DESCRIPTION
        "
        Warning On Client Trscv DDM :This
        OID indicates a warning is being
        received from the Client Transceiver
        DDM <Help> This alarm indicates
        if a DDM Warning has been detected
        on the client transceiver <Condtype>
        SFP_DDM_WARNING_1 <Probcause> inputOutputDeviceError
        (24) <Alarmtype> synthesisAlarm
        (12)  <Polarity> (2)
        "
	::= { pm20002maAlmsynthAlmPortEntry 10 }


pm20002maAlmDwCaisPortn OBJECT-TYPE
	SYNTAX  EkiOnOff
	MAX-ACCESS read-only
	STATUS current
	DESCRIPTION
        "
        Client AIS Inserted :This OID
         indicates a CAIS has been inserted
        on the output client port. <Help>
        This status indicates if a Client
        Alarm Indication Signal is currently
        inserted on the client interface
        <Condtype> DW_CAIS_1 <Probcause>
        informationalStatus(1000) <Alarmtype>
        other (1) <Polarity> (2)
        "
	::= { pm20002maAlmsynthAlmPortEntry 9 }


pm20002maAlmClientRemoteOosPortn OBJECT-TYPE
	SYNTAX  EkiOnOff
	MAX-ACCESS read-only
	STATUS current
	DESCRIPTION
        "
        Remote Client Port In Service
         :This OID indicates that the remote
        Client port is In Service (1) or
        Out of Service (2) <Help> This
         status indicates if the remote
        client port is in service <Condtype>
        CLIENT_REMOTE_OOS <Probcause> informationalStatus(1000)
        <Alarmtype> other (1) <Polarity>
        (2)
        "
	::= { pm20002maAlmsynthAlmPortEntry 8 }


pm20002maAlmClientLocalOosPortn OBJECT-TYPE
	SYNTAX  EkiOnOff
	MAX-ACCESS read-only
	STATUS current
	DESCRIPTION
        "
        Local Client Port In Service :This
        OID indicates that the local Client
        port is In Service (1) or Out of
        Service (2) <Help> This status
         indicates if the local client
         port is in service <Condtype>
         CLIENT_LOCAL_OOS <Probcause> informationalStatus(1000)
        <Alarmtype> other (1) <Polarity>
        (2)
        "
	::= { pm20002maAlmsynthAlmPortEntry 7 }


pm20002maAlmDwLsdPortn OBJECT-TYPE
	SYNTAX  EkiOnOff
	MAX-ACCESS read-only
	STATUS current
	DESCRIPTION
        "
        Client Trscv Laser Shutdown :This
        OID indicates the Client transceiver
        laser is shutdown <Help> This status
        indicates if the client transceiver
        laser is shutdown <Condtype> DW_LSD_1
        <Probcause> other (1) <Alarmtype>
        equipmentAlarm (5) <Polarity> (2)
        "
	::= { pm20002maAlmsynthAlmPortEntry 6 }


pm20002maAlmHwFailAccPortn OBJECT-TYPE
	SYNTAX  EkiOnOff
	MAX-ACCESS read-only
	STATUS current
	DESCRIPTION
        "
        Client HW Fail :This OID indicates
        a failure on client port, most
         probably caused by a HW issue.
        <Help> This alarm indicates a failure
        on client port, most probably caused
        by a HW issue. <Condtype> HW_FAIL_ACC_1
        <Probcause> equipmentMalfunction
        (16) <Alarmtype> synthesisAlarm
        (12)  <Polarity> (2)
        "
	::= { pm20002maAlmsynthAlmPortEntry 5 }


pm20002maAlmDdmAbsentPortn OBJECT-TYPE
	SYNTAX  EkiOnOff
	MAX-ACCESS read-only
	STATUS current
	DESCRIPTION
        "
        DDM Supported On Client Trscv
         :This OID indicates that the Client
        transceiver supports the Digital
        Diagnostic Monitoring function
         <Help> This status indicates if
        the client transceiver includes
        the DDM feature <Condtype> DDM_ABSENT_1
        <Probcause> informationalStatus(1000)
        <Alarmtype> other (1) <Polarity>
        (2)
        "
	::= { pm20002maAlmsynthAlmPortEntry 3 }


pm20002maAlmSfpAbsentPortn OBJECT-TYPE
	SYNTAX  EkiOnOff
	MAX-ACCESS read-only
	STATUS current
	DESCRIPTION
        "
        Client Optical Module Absent :This
        OID indicates that the Transceiver
        is not present in the client port.
        <Help> This alarm indicates if
         the client transceiver is not
         plugged <Condtype> SFP_ABSENT_1
        <Probcause> inputOutputDeviceError
        (24) <Alarmtype> equipmentAlarm
        (5) <Polarity> (2) <Event> ObjectCDINV
        "
	::= { pm20002maAlmsynthAlmPortEntry 2 }


--- *********************************************************
---     TABLE for the pm20002maAlmsynthAlmLine articles
--- *********************************************************

pm20002maAlmsynthAlmLineTable OBJECT-TYPE
	SYNTAX  SEQUENCE OF Pm20002maAlmsynthAlmLineEntry
	MAX-ACCESS not-accessible
	STATUS current
	DESCRIPTION
        "
        List of pm20002maAlmsynthAlmLine
        Article
        "
	::= { pm20002maAlmLineCrit 40 }


pm20002maAlmsynthAlmLineEntry OBJECT-TYPE
	SYNTAX Pm20002maAlmsynthAlmLineEntry
	MAX-ACCESS not-accessible
	STATUS current
	DESCRIPTION
        "
        Row definition for the pm20002maAlmsynthAlmLine
        table
        "
	INDEX   { pm20002maAlmsynthAlmLineIndex }
	::= { pm20002maAlmsynthAlmLineTable 1 }


Pm20002maAlmsynthAlmLineEntry ::=
	SEQUENCE {
	pm20002maAlmsynthAlmLineIndex
		INTEGER,
	pm20002maAlmLineActivePortn
		EkiOnOff,
	pm20002maAlmLineFailPortn
		EkiOnOff,
	pm20002maAlmLineDdmAlmPortn
		EkiOnOff,
	pm20002maAlmLineDdmWarningPortn
		EkiOnOff,
	pm20002maAlmUpRdiInsPortn
		EkiOnOff,
	pm20002maAlmLineLocalOosPortn
		EkiOnOff,
	pm20002maAlmXfpTxOffPortn
		EkiOnOff,
	pm20002maAlmLineHwFailPortn
		EkiOnOff,
	pm20002maAlmXfpInitNotComplPortn
		EkiOnOff,
	pm20002maAlmXfpAbsentPortn
		EkiOnOff
	}


pm20002maAlmsynthAlmLineIndex OBJECT-TYPE
	SYNTAX  INTEGER(0..128)
	MAX-ACCESS  read-only
	STATUS current
	DESCRIPTION
        "
        Index definition for the pm20002maAlmsynthAlmLine
        table
        "
	::= { pm20002maAlmsynthAlmLineEntry 1 }


pm20002maAlmLineActivePortn OBJECT-TYPE
	SYNTAX  EkiOnOff
	MAX-ACCESS read-only
	STATUS current
	DESCRIPTION
        "
        Line Active :This OID indicates
        whether the line is active or standby.
        <Help> This status indicates whether
        the line is active or standby.
         <Condtype> LINE_ACTIVE <Probcause>
        informationalStatus(1000) <Alarmtype>
        other (1) <Polarity> (2)
        "
	::= { pm20002maAlmsynthAlmLineEntry 17 }


pm20002maAlmLineFailPortn OBJECT-TYPE
	SYNTAX  EkiOnOff
	MAX-ACCESS read-only
	STATUS current
	DESCRIPTION
        "
        Line Port Failure :This OID indicates
        a failure on the line port <Help>
        This alarm indicates a failure
         on the line port <Condtype> LINE_FAIL
        <Probcause> equipmentMalfunction
        (16) <Alarmtype> synthesisAlarm
        (12)  <Polarity> (2)
        "
	::= { pm20002maAlmsynthAlmLineEntry 13 }


pm20002maAlmLineDdmAlmPortn OBJECT-TYPE
	SYNTAX  EkiOnOff
	MAX-ACCESS read-only
	STATUS current
	DESCRIPTION
        "
        Alarm On Line Optical Module DDM
        :This OID indicates an alarm is
        present coming out of Line transceiver
        DDM <Help> This alarm indicates
        if a DDM Alarm has been detected
        on the line transceiver <Condtype>
        LINE_DDM_ALM <Probcause> inputOutputDeviceError
        (24) <Alarmtype> synthesisAlarm
        (12)  <Polarity> (2)
        "
	::= { pm20002maAlmsynthAlmLineEntry 11 }


pm20002maAlmLineDdmWarningPortn OBJECT-TYPE
	SYNTAX  EkiOnOff
	MAX-ACCESS read-only
	STATUS current
	DESCRIPTION
        "
        Warning On Line Optical Module
        DDM :This OID indicates a warning
        is present coming out of Line transceiver
        DDM <Help> This alarm indicates
        if a DDM Warning has been detected
        on the line transceiver <Condtype>
        LINE_DDM_WARNING <Probcause> inputOutputDeviceError
        (24) <Alarmtype> synthesisAlarm
        (12)  <Polarity> (2)
        "
	::= { pm20002maAlmsynthAlmLineEntry 10 }


pm20002maAlmUpRdiInsPortn OBJECT-TYPE
	SYNTAX  EkiOnOff
	MAX-ACCESS read-only
	STATUS current
	DESCRIPTION
        "
        MS-RDI/L-RDI Inserted On Line
         :This OID indicates an upstream
        MS-RDI/L-RDI has been inserted
         in the outgoing 10 Gb/s SDH/SONET
        signal. <Help> This status indicates
        if a MS-RDI/L-RDI is currently
         inserted on the line interface.
        <Condtype> UP_RDI_INS <Probcause>
        informationalStatus(1000) <Alarmtype>
        other (1) <Polarity> (2)
        "
	::= { pm20002maAlmsynthAlmLineEntry 9 }


pm20002maAlmLineLocalOosPortn OBJECT-TYPE
	SYNTAX  EkiOnOff
	MAX-ACCESS read-only
	STATUS current
	DESCRIPTION
        "
        Line Port In Service :This OID
        indicates that the Line port is
        In Service (1) of Out or Service
        (2) <Help> This status indicates
        if the line port is in service
         <Condtype> LINE_LOCAL_OOS <Probcause>
        informationalStatus(1000) <Alarmtype>
        other (1) <Polarity> (2)
        "
	::= { pm20002maAlmsynthAlmLineEntry 7 }


pm20002maAlmXfpTxOffPortn OBJECT-TYPE
	SYNTAX  EkiOnOff
	MAX-ACCESS read-only
	STATUS current
	DESCRIPTION
        "
        Line Trscv Laser Shutdown :This
        OID indicates the Line transceiver
        laser is shutdown <Help> This status
        indicates if the Line transceiver
        laser is shutdown <Condtype> XFP_TX_OFF
        <Probcause> other (1) <Alarmtype>
        equipmentAlarm (5) <Polarity> (2)
        "
	::= { pm20002maAlmsynthAlmLineEntry 6 }


pm20002maAlmLineHwFailPortn OBJECT-TYPE
	SYNTAX  EkiOnOff
	MAX-ACCESS read-only
	STATUS current
	DESCRIPTION
        "
        Line Port HW Failure :This OID
        indicates a failure on line port,
        most probably caused by a HW issue
        <Help> This alarm indicates a failure
        on line port, most probably caused
        by a HW issue <Condtype> LINE_HW_FAIL
        <Probcause> equipmentMalfunction
        (16) <Alarmtype> synthesisAlarm
        (12)  <Polarity> (2)
        "
	::= { pm20002maAlmsynthAlmLineEntry 5 }


pm20002maAlmXfpInitNotComplPortn OBJECT-TYPE
	SYNTAX  EkiOnOff
	MAX-ACCESS read-only
	STATUS current
	DESCRIPTION
        "
        Line Optical Module Ready :This
        OID indicates that the optical
         interface is not operational.
         <Help> This status indicates if
        the line transceiver has been correctly
        initialized <Condtype> XFP_INIT_NOT_COMPL
        <Probcause> equipmentMalfunction
        (16) <Alarmtype> equipmentAlarm
        (5) <Polarity> (2)
        "
	::= { pm20002maAlmsynthAlmLineEntry 3 }


pm20002maAlmXfpAbsentPortn OBJECT-TYPE
	SYNTAX  EkiOnOff
	MAX-ACCESS read-only
	STATUS current
	DESCRIPTION
        "
        Line Optical Module Absent :This
        OID indicates that the line optical
        interface is not present. <Help>
        This alarm indicates if the line
        transceiver is not plugged <Condtype>
        XFP_ABSENT <Probcause> inputOutputDeviceError
        (24) <Alarmtype> equipmentAlarm
        (5) <Polarity> (2)
        "
	::= { pm20002maAlmsynthAlmLineEntry 2 }


--- *****************************************************
---     LEAF for the clientModuleState article
--- *****************************************************
pm20002maAlmclientModuleState OBJECT IDENTIFIER ::= { pm20002maAlmOtherCrit 72 }




pm20002maAlmCfpHighPowerDown OBJECT-TYPE
	  SYNTAX EkiOnOff
	  MAX-ACCESS read-only
	  STATUS current
	  DESCRIPTION
        "
        Client Trscv High Power Down :This
        OID indicates the Client Trscv
         is entering Low Power state <Help>
        Status indicating the Client Trscv
        is entering Low Power state <Condtype>
        CFP_HIGH_POWER_DOWN <Probcause>
        informationalStatus(1000) <Alarmtype>
        other (1) <Polarity> (2)
        "
	  ::= { pm20002maAlmclientModuleState 9 }



pm20002maAlmCfpTxTurnOff OBJECT-TYPE
	  SYNTAX EkiOnOff
	  MAX-ACCESS read-only
	  STATUS current
	  DESCRIPTION
        "
        Client Trscv Laser Turn Off :This
        OID indicates the Client Trscv
         is turning off its laser <Help>
        Status indicating the Client Trscv
        is turning off its laser <Condtype>
        CFP_TX_TURN_OFF <Probcause> informationalStatus(1000)
        <Alarmtype> other (1) <Polarity>
        (2)
        "
	  ::= { pm20002maAlmclientModuleState 8 }



pm20002maAlmCfpFault OBJECT-TYPE
	  SYNTAX EkiOnOff
	  MAX-ACCESS read-only
	  STATUS current
	  DESCRIPTION
        "
        Client Trscv Fault :This OID indicates
        the Client Trscv is in Fault state
        <Help> Status indicating the Client
        Trscv is in Fault state <Condtype>
        CFP_FAULT <Probcause> informationalStatus(1000)
        <Alarmtype> other (1) <Polarity>
        (2)
        "
	  ::= { pm20002maAlmclientModuleState 7 }



pm20002maAlmCfpReady OBJECT-TYPE
	  SYNTAX EkiOnOff
	  MAX-ACCESS read-only
	  STATUS current
	  DESCRIPTION
        "
        Client Trscv Ready :This OID indicates
        the Client Trscv is ready to operate
        <Help> Status indicating the Client
        Trscv is ready to operate <Condtype>
        CFP_READY <Probcause> informationalStatus(1000)
        <Alarmtype> other (1) <Polarity>
        (2)
        "
	  ::= { pm20002maAlmclientModuleState 6 }



pm20002maAlmCfpTxTurnOn OBJECT-TYPE
	  SYNTAX EkiOnOff
	  MAX-ACCESS read-only
	  STATUS current
	  DESCRIPTION
        "
        Client Trscv Laser Turn On :This
        OID indicates the Client Trscv
         is turning on its laser <Help>
        Status indicating the Client Trscv
        is turning on its laser <Condtype>
        CFP_TX_TURN_ON <Probcause> informationalStatus(1000)
        <Alarmtype> other (1) <Polarity>
        (2)
        "
	  ::= { pm20002maAlmclientModuleState 5 }



pm20002maAlmCfpTxOff OBJECT-TYPE
	  SYNTAX EkiOnOff
	  MAX-ACCESS read-only
	  STATUS current
	  DESCRIPTION
        "
        Client Trscv Laser Shutdown :This
        OID indicates the Client Trscv
         Laser is OFF <Help> Status indicating
        the Client Trscv Laser is OFF <Condtype>
        CFP_TX_OFF <Probcause> informationalStatus(1000)
        <Alarmtype> other (1) <Polarity>
        (2)
        "
	  ::= { pm20002maAlmclientModuleState 4 }



pm20002maAlmCfpHighPowerUp OBJECT-TYPE
	  SYNTAX EkiOnOff
	  MAX-ACCESS read-only
	  STATUS current
	  DESCRIPTION
        "
        Client Trscv High Power Up :This
        OID indicates the Client Trscv
         is leaving Low Power state <Help>
        Status indicating the Client Trscv
        is leaving Low Power state <Condtype>
        CFP_HIGH_POWER_UP <Probcause> informationalStatus(1000)
        <Alarmtype> other (1) <Polarity>
        (2)
        "
	  ::= { pm20002maAlmclientModuleState 3 }



pm20002maAlmCfpLowPower OBJECT-TYPE
	  SYNTAX EkiOnOff
	  MAX-ACCESS read-only
	  STATUS current
	  DESCRIPTION
        "
        Client Trscv Low Power :This OID
        indicates the Client Trscv is in
        low power state <Help> Status indicating
        the Client Trscv is in low power
        state <Condtype> CFP_LOW_POWER
         <Probcause> informationalStatus(1000)
        <Alarmtype> other (1) <Polarity>
        (2)
        "
	  ::= { pm20002maAlmclientModuleState 2 }



pm20002maAlmCfpInitialize OBJECT-TYPE
	  SYNTAX EkiOnOff
	  MAX-ACCESS read-only
	  STATUS current
	  DESCRIPTION
        "
        Client Trscv Initialize :This
         OID indicates the Client Trscv
        initialization is in progress <Help>
        Status indicating the Client Trscv
        initialization is in progress <Condtype>
        CFP_INITIALIZE <Probcause> informationalStatus(1000)
        <Alarmtype> other (1) <Polarity>
        (2)
        "
	  ::= { pm20002maAlmclientModuleState 1 }



--- *****************************************************
---     LEAF for the clientModuleGeneralStatus article
--- *****************************************************
pm20002maAlmclientModuleGeneralStatus OBJECT IDENTIFIER ::= { pm20002maAlmOtherCrit 73 }




pm20002maAlmCfpHwInterlock OBJECT-TYPE
	  SYNTAX EkiOnOff
	  MAX-ACCESS read-only
	  STATUS current
	  DESCRIPTION
        "
        Client Trscv Hardware Interlock
        :This OID indicates the Client
         Trscv power is higher than the
        cooling capacity <Help> Alarm indicating
        the Client Trscv power is higher
        than the cooling capacity <Condtype>
        CFP_HW_INTERLOCK <Probcause> temperatureUnacceptable
        (51) <Alarmtype> equipmentAlarm
        (5) <Polarity> (2)
        "
	  ::= { pm20002maAlmclientModuleGeneralStatus 14 }



pm20002maAlmCfpLossOfRefclk OBJECT-TYPE
	  SYNTAX EkiOnOff
	  MAX-ACCESS read-only
	  STATUS current
	  DESCRIPTION
        "
        Client Trscv Loss Of Ref Clock
        :This OID indicates a Loss of Reference
        clock is detected on the Client
        Trscv <Help> Alarm indicating a
        Loss of Reference clock is detected
        on the Client Trscv <Condtype>
         CFP_LOSS_OF_REFCLK <Probcause>
        inputOutputDeviceError (24) <Alarmtype>
        equipmentAlarm (5) <Polarity> (2)
        "
	  ::= { pm20002maAlmclientModuleGeneralStatus 11 }



pm20002maAlmCfpTxJitterPllLol OBJECT-TYPE
	  SYNTAX EkiOnOff
	  MAX-ACCESS read-only
	  STATUS current
	  DESCRIPTION
        "
        Client Trscv Tx Jitter PLL Loss
        Of Lock :This OID indicates a Tx
        Jitter PLL Loss of Lock is dtected
        on the Client Trscv <Help> Alarm
        indicating a Tx Jitter PLL Loss
        of Lock is dtected on the Client
        Trscv <Condtype> CFP_TX_JITTER_PLL_LOL
        <Probcause> inputOutputDeviceError
        (24) <Alarmtype> equipmentAlarm
        (5) <Polarity> (2)
        "
	  ::= { pm20002maAlmclientModuleGeneralStatus 10 }



pm20002maAlmCfpTxCmuLol OBJECT-TYPE
	  SYNTAX EkiOnOff
	  MAX-ACCESS read-only
	  STATUS current
	  DESCRIPTION
        "
        Client Trscv CMU Loss Of Lock
         :This OID indicates a Clock Multiplier
        Unit Loss of Lock is detected on
        the Client Trscv <Help> Alarm indicating
        a Clock Multiplier Unit Loss of
        Lock is detected on the Client
         Trscv <Condtype> CFP_TX_CMU_LOL
        <Probcause> inputOutputDeviceError
        (24) <Alarmtype> equipmentAlarm
        (5) <Polarity> (2)
        "
	  ::= { pm20002maAlmclientModuleGeneralStatus 9 }



pm20002maAlmCfpTxLosf OBJECT-TYPE
	  SYNTAX EkiOnOff
	  MAX-ACCESS read-only
	  STATUS current
	  DESCRIPTION
        "
        Client Trscv Loss Of Signal Functionality
        :This OID indicates a Loss of Signal
        functionality is detected on the
        Client Trscv <Help> Alarm indicating
        a Loss of Signal functionality
         is detected on the Client Trscv
        <Condtype> CFP_TX_LOSF <Probcause>
        lossOfSignal (30) <Alarmtype> equipmentAlarm
        (5) <Polarity> (2)
        "
	  ::= { pm20002maAlmclientModuleGeneralStatus 8 }



pm20002maAlmCfpTxHostLol OBJECT-TYPE
	  SYNTAX EkiOnOff
	  MAX-ACCESS read-only
	  STATUS current
	  DESCRIPTION
        "
        Client Trscv Tx Host Loss Of Lock
        :This OID indicates of Loss of
         Lock is detected on the Client
        Trscv Tx Host interface <Help>
         Alarm indicating of Loss of Lock
        is detected on the Client Trscv
        Tx Host interface <Condtype> CFP_TX_HOST_LOL
        <Probcause> receiverFailure (42)
        <Alarmtype> equipmentAlarm (5)
         <Polarity> (2)
        "
	  ::= { pm20002maAlmclientModuleGeneralStatus 7 }



pm20002maAlmCfpRxLos OBJECT-TYPE
	  SYNTAX EkiOnOff
	  MAX-ACCESS read-only
	  STATUS current
	  DESCRIPTION
        "
        Client Trscv Loss Of Signal :This
        OID indicates a Loss of Signal
         is detected on the Client Trscv
        <Help> Alarm indicating a Loss
         of Signal is detected on the Client
        Trscv <Condtype> CFP_RX_LOS <Probcause>
        lossOfSignal (30) <Alarmtype> equipmentAlarm
        (5) <Polarity> (2)
        "
	  ::= { pm20002maAlmclientModuleGeneralStatus 6 }



pm20002maAlmCfpRxNetworkLol OBJECT-TYPE
	  SYNTAX EkiOnOff
	  MAX-ACCESS read-only
	  STATUS current
	  DESCRIPTION
        "
        Client Trscv Rx Network Loss Of
        Lock :This OID indicates of Loss
        of Lock is dected on the Client
        Trscv Rx Network interface <Help>
        Alarm indicating of Loss of Lock
        is dected on the Client Trscv Rx
        Network interface <Condtype> CFP_RX_NETWORK_LOL
        <Probcause> receiverFailure (42)
        <Alarmtype> equipmentAlarm (5)
         <Polarity> (2)
        "
	  ::= { pm20002maAlmclientModuleGeneralStatus 5 }



pm20002maAlmCfpOutOfAlignment OBJECT-TYPE
	  SYNTAX EkiOnOff
	  MAX-ACCESS read-only
	  STATUS current
	  DESCRIPTION
        "
        Client Trscv Out Of Alignment
         :This OID indicates an Out of
         alignment on the Client Trscv
         Host Interface <Help> Alarm indicating
        an Out of alignment on the Client
        Trscv Host Interface <Condtype>
        CFP_OUT_OF_ALIGNMENT <Probcause>
        receiverFailure (42) <Alarmtype>
        equipmentAlarm (5) <Polarity> (2)
        "
	  ::= { pm20002maAlmclientModuleGeneralStatus 4 }



--- *****************************************************
---     LEAF for the clientGlobalAlarmSummary article
--- *****************************************************
pm20002maAlmclientGlobalAlarmSummary OBJECT IDENTIFIER ::= { pm20002maAlmOtherCrit 74 }




pm20002maAlmCfpGlobAlarmAssertion  OBJECT-TYPE
	  SYNTAX EkiOnOff
	  MAX-ACCESS read-only
	  STATUS current
	  DESCRIPTION
        "
        Client Trscv Global Alarm :This
        OID indicates at least one  Fault
        or Status is detected on the Client
        Trscv module <Help> Synthesis alarm
        indicating at least one Alarm,
         Warning, Fault or Status is detected
        on the Client Trscv module <Condtype>
        CFP_GLOB_ALARM_ASSERTION  <Probcause>
        informationalStatus(1000) <Alarmtype>
        other (1) <Polarity> (2)
        "
	  ::= { pm20002maAlmclientGlobalAlarmSummary 16 }



pm20002maAlmCfpHostLaneFaultStatus  OBJECT-TYPE
	  SYNTAX EkiOnOff
	  MAX-ACCESS read-only
	  STATUS current
	  DESCRIPTION
        "
        Client Trscv Host Fault And Status
        :This OID indicates at least one
        Fault or Status is detected on
         the Client Trscv Host Interface
        <Help> Synthesis alarm indicating
        at least one Fault or Status is
        detected on the Client Trscv Host
        Interface <Condtype> CFP_HOST_LANE_FAULT_STATUS
         <Probcause> informationalStatus(1000)
        <Alarmtype> other (1) <Polarity>
        (2)
        "
	  ::= { pm20002maAlmclientGlobalAlarmSummary 15 }



pm20002maAlmCfpNetworkLaneFaultStatus  OBJECT-TYPE
	  SYNTAX EkiOnOff
	  MAX-ACCESS read-only
	  STATUS current
	  DESCRIPTION
        "
        Client Trscv Network Fault And
        Status :This OID indicates at least
        one Fault or Status is detected
        on the Client Trscv Network Interface
        <Help> Synthesis alarm indicating
        at least one Fault or Status is
        detected on the Client Trscv Network
        Interface <Condtype> CFP_NETWORK_LANE_FAULT_STATUS
         <Probcause> informationalStatus(1000)
        <Alarmtype> other (1) <Polarity>
        (2)
        "
	  ::= { pm20002maAlmclientGlobalAlarmSummary 14 }



pm20002maAlmCfpNetworkLaneAlarmWarning1 OBJECT-TYPE
	  SYNTAX EkiOnOff
	  MAX-ACCESS read-only
	  STATUS current
	  DESCRIPTION
        "
        Client Trscv Network Alarm And
        Warning 1 :This OID indicates at
        least one DDM  is detected on the
        Client Trscv Network Interface
         <Help> Synthesis alarm indicating
        at least one DDM Alarm or DDM Warning
        is detected on the Client Trscv
        Network Interface <Condtype> CFP_NETWORK_LANE_ALARM_WARNING_1
        <Probcause> informationalStatus(1000)
        <Alarmtype> other (1) <Polarity>
        (2)
        "
	  ::= { pm20002maAlmclientGlobalAlarmSummary 13 }



pm20002maAlmCfpModuleAlarmWarning2 OBJECT-TYPE
	  SYNTAX EkiOnOff
	  MAX-ACCESS read-only
	  STATUS current
	  DESCRIPTION
        "
        Client Trscv Module Alarm And
         Warning 2 :This OID indicates
         at least one DDM is detected on
        the Client Trscv module <Help>
         Synthesis alarm indicating at
         least one DDM Alarm or DDM Warning
        is detected on the Client Trscv
        module <Condtype> CFP_MODULE_ALARM_WARNING_2
        <Probcause> informationalStatus(1000)
        <Alarmtype> other (1) <Polarity>
        (2)
        "
	  ::= { pm20002maAlmclientGlobalAlarmSummary 12 }



pm20002maAlmCfpModuleAlarmWarning1  OBJECT-TYPE
	  SYNTAX EkiOnOff
	  MAX-ACCESS read-only
	  STATUS current
	  DESCRIPTION
        "
        Client Trscv Module Alarm And
         Warning 1 :This OID indicates
         at least one DDM  This OID is
         detected on the Client Trscv module
        <Help> Synthesis alarm indicating
        at least one DDM Alarm or DDM Warning
        is detected on the Client Trscv
        module <Condtype> CFP_MODULE_ALARM_WARNING_1
         <Probcause> informationalStatus(1000)
        <Alarmtype> other (1) <Polarity>
        (2)
        "
	  ::= { pm20002maAlmclientGlobalAlarmSummary 11 }



pm20002maAlmCfpModuleFault  OBJECT-TYPE
	  SYNTAX EkiOnOff
	  MAX-ACCESS read-only
	  STATUS current
	  DESCRIPTION
        "
        Client Trscv Module Fault :This
        OID indicates at least one Fault
        is detected on the Client Trscv
        module <Help> Synthesis alarm indicating
        at least one Fault is detected
         on the Client Trscv module <Condtype>
        CFP_MODULE_FAULT  <Probcause> informationalStatus(1000)
        <Alarmtype> other (1) <Polarity>
        (2)
        "
	  ::= { pm20002maAlmclientGlobalAlarmSummary 10 }



pm20002maAlmCfpModuleGeneralStatus  OBJECT-TYPE
	  SYNTAX EkiOnOff
	  MAX-ACCESS read-only
	  STATUS current
	  DESCRIPTION
        "
        Client Trscv General Status :This
        OID indicates the Client Trscv
         module general status <Help> Synthesis
        alarm indicating the Client Trscv
        module general status <Condtype>
        CFP_MODULE_GENERAL_STATUS  <Probcause>
        informationalStatus(1000) <Alarmtype>
        other (1) <Polarity> (2)
        "
	  ::= { pm20002maAlmclientGlobalAlarmSummary 9 }



pm20002maAlmCfpModuleState  OBJECT-TYPE
	  SYNTAX EkiOnOff
	  MAX-ACCESS read-only
	  STATUS current
	  DESCRIPTION
        "
        Client Trscv Module State :This
        OID indicates the Client Trscv
         module state <Help> Synthesis
         alarm indicating the Client Trscv
        module state <Condtype> CFP_MODULE_STATE
         <Probcause> informationalStatus(1000)
        <Alarmtype> other (1) <Polarity>
        (2)
        "
	  ::= { pm20002maAlmclientGlobalAlarmSummary 8 }



pm20002maAlmCfpNetworkLaneAlarmWarning2 OBJECT-TYPE
	  SYNTAX EkiOnOff
	  MAX-ACCESS read-only
	  STATUS current
	  DESCRIPTION
        "
        Client Trscv Network Alarm And
        Warning 2 :This OID indicates at
        least one DDM is detected on the
        Client Trscv Network Interface
         <Help> Synthesis alarm indicating
        at least one DDM Alarm or DDM Warning
        is detected on the Client Trscv
        Network Interface <Condtype> CFP_NETWORK_LANE_ALARM_WARNING_2
        <Probcause> informationalStatus(1000)
        <Alarmtype> other (1) <Polarity>
        (2)
        "
	  ::= { pm20002maAlmclientGlobalAlarmSummary 7 }



pm20002maAlmCfpSoftGlobAlarmTest  OBJECT-TYPE
	  SYNTAX EkiOnOff
	  MAX-ACCESS read-only
	  STATUS current
	  DESCRIPTION
        "
        Client Trscv Global Alarm SW Test
        :This OID indicates the Client
         Trscv Global Alarm This OID is
        raised by SW request for test purpose
        <Help> Status indicating the Client
        Trscv Global Alarm is raised by
        SW request for test purpose <Condtype>
        CFP_SOFT_GLOB_ALARM_TEST  <Probcause>
        informationalStatus(1000) <Alarmtype>
        other (1) <Polarity> (2)
        "
	  ::= { pm20002maAlmclientGlobalAlarmSummary 1 }



--- *****************************************************
---     LEAF for the msaModuleState article
--- *****************************************************
pm20002maAlmmsaModuleState OBJECT IDENTIFIER ::= { pm20002maAlmOtherCrit 78 }




pm20002maAlmMsaHighPowerDown OBJECT-TYPE
	  SYNTAX EkiOnOff
	  MAX-ACCESS read-only
	  STATUS current
	  DESCRIPTION
        "
        Line Trscv High Power Down :This
        OID indicates the Line Trscv is
        entering Low Power state <Help>
        Status indicating the Line Trscv
        is entering Low Power state <Condtype>
        MSA_HIGH_POWER_DOWN <Probcause>
        informationalStatus(1000) <Alarmtype>
        other (1) <Polarity> (2)
        "
	  ::= { pm20002maAlmmsaModuleState 9 }



pm20002maAlmMsaTxTurnOff OBJECT-TYPE
	  SYNTAX EkiOnOff
	  MAX-ACCESS read-only
	  STATUS current
	  DESCRIPTION
        "
        Line Trscv Laser Turn Off :This
        OID indicates the Line Trscv is
        turning off its laser <Help> Status
        indicating the Line Trscv is turning
        off its laser <Condtype> MSA_TX_TURN_OFF
        <Probcause> informationalStatus(1000)
        <Alarmtype> other (1) <Polarity>
        (2)
        "
	  ::= { pm20002maAlmmsaModuleState 8 }



pm20002maAlmMsaFault OBJECT-TYPE
	  SYNTAX EkiOnOff
	  MAX-ACCESS read-only
	  STATUS current
	  DESCRIPTION
        "
        Line Trscv Fault :This OID indicates
        the Line Trscv is in Fault state
        <Help> Status indicating the Line
        Trscv is in Fault state <Condtype>
        MSA_FAULT <Probcause> informationalStatus(1000)
        <Alarmtype> other (1) <Polarity>
        (2)
        "
	  ::= { pm20002maAlmmsaModuleState 7 }



pm20002maAlmMsaReady OBJECT-TYPE
	  SYNTAX EkiOnOff
	  MAX-ACCESS read-only
	  STATUS current
	  DESCRIPTION
        "
        Line Trscv Ready :This OID indicates
        the Line Trscv is ready to operate
        <Help> Status indicating the Line
        Trscv is ready to operate <Condtype>
        MSA_READY <Probcause> informationalStatus(1000)
        <Alarmtype> other (1) <Polarity>
        (2)
        "
	  ::= { pm20002maAlmmsaModuleState 6 }



pm20002maAlmMsaTxTurnOn OBJECT-TYPE
	  SYNTAX EkiOnOff
	  MAX-ACCESS read-only
	  STATUS current
	  DESCRIPTION
        "
        Line Trscv Laser Turn On :This
        OID indicates the Line Trscv is
        turning on its laser <Help> Status
        indicating the Line Trscv is turning
        on its laser <Condtype> MSA_TX_TURN_ON
        <Probcause> informationalStatus(1000)
        <Alarmtype> other (1) <Polarity>
        (2)
        "
	  ::= { pm20002maAlmmsaModuleState 5 }



pm20002maAlmMsaTxOff OBJECT-TYPE
	  SYNTAX EkiOnOff
	  MAX-ACCESS read-only
	  STATUS current
	  DESCRIPTION
        "
        Line Trscv Laser Shutdown :This
        OID indicates the Line Trscv Laser
        is OFF <Help> Status indicating
        the Line Trscv Laser is OFF <Condtype>
        MSA_TX_OFF <Probcause> informationalStatus(1000)
        <Alarmtype> other (1) <Polarity>
        (2)
        "
	  ::= { pm20002maAlmmsaModuleState 4 }



pm20002maAlmMsaHighPowerUp OBJECT-TYPE
	  SYNTAX EkiOnOff
	  MAX-ACCESS read-only
	  STATUS current
	  DESCRIPTION
        "
        Line Trscv High Power Up :This
        OID indicates the Line Trscv is
        leaving Low Power state <Help>
         Status indicating the Line Trscv
        is leaving Low Power state <Condtype>
        MSA_HIGH_POWER_UP <Probcause> informationalStatus(1000)
        <Alarmtype> other (1) <Polarity>
        (2)
        "
	  ::= { pm20002maAlmmsaModuleState 3 }



pm20002maAlmMsaLowPower OBJECT-TYPE
	  SYNTAX EkiOnOff
	  MAX-ACCESS read-only
	  STATUS current
	  DESCRIPTION
        "
        Line Trscv Low Power :This OID
        indicates the Line Trscv is in
         low power state <Help> Status
         indicating the Line Trscv is in
        low power state <Condtype> MSA_LOW_POWER
        <Probcause> informationalStatus(1000)
        <Alarmtype> other (1) <Polarity>
        (2)
        "
	  ::= { pm20002maAlmmsaModuleState 2 }



pm20002maAlmMsaInitialize OBJECT-TYPE
	  SYNTAX EkiOnOff
	  MAX-ACCESS read-only
	  STATUS current
	  DESCRIPTION
        "
        Line Trscv Initialize :This OID
        indicates the Line Trscv initialization
        is in progress <Help> Status indicating
        the Line Trscv initialization is
        in progress <Condtype> MSA_INITIALIZE
        <Probcause> informationalStatus(1000)
        <Alarmtype> other (1) <Polarity>
        (2)
        "
	  ::= { pm20002maAlmmsaModuleState 1 }



--- *****************************************************
---     LEAF for the msaModuleGeneralStatus article
--- *****************************************************
pm20002maAlmmsaModuleGeneralStatus OBJECT IDENTIFIER ::= { pm20002maAlmOtherCrit 79 }




pm20002maAlmMsaHwInterlock OBJECT-TYPE
	  SYNTAX EkiOnOff
	  MAX-ACCESS read-only
	  STATUS current
	  DESCRIPTION
        "
        Line Trscv Hardware Interlock
         :This OID indicates the Line Trscv
        power is higher than the cooling
        capacity <Help> Alarm indicating
        the Line Trscv power is higher
         than the cooling capacity <Condtype>
        MSA_HW_INTERLOCK <Probcause> temperatureUnacceptable
        (51) <Alarmtype> equipmentAlarm
        (5) <Polarity> (2)
        "
	  ::= { pm20002maAlmmsaModuleGeneralStatus 14 }



pm20002maAlmMsaLossOfRefclk OBJECT-TYPE
	  SYNTAX EkiOnOff
	  MAX-ACCESS read-only
	  STATUS current
	  DESCRIPTION
        "
        Line Trscv Loss Of Ref Clock :This
        OID indicates a Loss of Reference
        clock is detected on the Line Trscv
        <Help> Alarm indicating a Loss
         of Reference clock is detected
        on the Line Trscv <Condtype> MSA_LOSS_OF_REFCLK
        <Probcause> inputOutputDeviceError
        (24) <Alarmtype> equipmentAlarm
        (5) <Polarity> (2)
        "
	  ::= { pm20002maAlmmsaModuleGeneralStatus 11 }



pm20002maAlmMsaTxJitterPllLol OBJECT-TYPE
	  SYNTAX EkiOnOff
	  MAX-ACCESS read-only
	  STATUS current
	  DESCRIPTION
        "
        Line Trscv Tx Jitter PLL Loss
         Of Lock :This OID indicates a
         Tx Jitter PLL Loss of Lock is
         detected on the Line Trscv <Help>
        Alarm indicating a Tx Jitter PLL
        Loss of Lock is detected on the
        Line Trscv <Condtype> MSA_TX_JITTER_PLL_LOL
        <Probcause> inputOutputDeviceError
        (24) <Alarmtype> equipmentAlarm
        (5) <Polarity> (2)
        "
	  ::= { pm20002maAlmmsaModuleGeneralStatus 10 }



pm20002maAlmMsaTxCmuLol OBJECT-TYPE
	  SYNTAX EkiOnOff
	  MAX-ACCESS read-only
	  STATUS current
	  DESCRIPTION
        "
        Line Trscv CMU Loss Of Lock :This
        OID indicates a Clock Multiplier
        Unit Loss of Lock is detected on
        the Line Trscv <Help> Alarm indicating
        a Clock Multiplier Unit Loss of
        Lock is detected on the Line Trscv
        <Condtype> MSA_TX_CMU_LOL <Probcause>
        inputOutputDeviceError (24) <Alarmtype>
        equipmentAlarm (5) <Polarity> (2)
        "
	  ::= { pm20002maAlmmsaModuleGeneralStatus 9 }



pm20002maAlmMsaTxLosf OBJECT-TYPE
	  SYNTAX EkiOnOff
	  MAX-ACCESS read-only
	  STATUS current
	  DESCRIPTION
        "
        Line Trscv Loss Of Signal Functionality
        :This OID indicates a Loss of Signal
        functionality is detected on the
        Line Trscv <Help> Alarm indicating
        a Loss of Signal functionality
         is detected on the Line Trscv
         <Condtype> MSA_TX_LOSF <Probcause>
        lossOfSignal (30) <Alarmtype> equipmentAlarm
        (5) <Polarity> (2)
        "
	  ::= { pm20002maAlmmsaModuleGeneralStatus 8 }



pm20002maAlmMsaTxHostLol OBJECT-TYPE
	  SYNTAX EkiOnOff
	  MAX-ACCESS read-only
	  STATUS current
	  DESCRIPTION
        "
        Line Trscv Tx Host Loss Of Lock
        :This OID indicates of Loss of
         Lock is detected on the Line Trscv
        Tx Host interface <Help> Alarm
         indicating of Loss of Lock is
         detected on the Line Trscv Tx
         Host interface <Condtype> MSA_TX_HOST_LOL
        <Probcause> receiverFailure (42)
        <Alarmtype> equipmentAlarm (5)
         <Polarity> (2)
        "
	  ::= { pm20002maAlmmsaModuleGeneralStatus 7 }



pm20002maAlmMsaRxLos OBJECT-TYPE
	  SYNTAX EkiOnOff
	  MAX-ACCESS read-only
	  STATUS current
	  DESCRIPTION
        "
        Line Trscv Loss Of Signal :This
        OID indicates a Loss of Signal
         is detected on the Line Trscv
         <Help> Alarm indicating a Loss
        of Signal is detected on the Line
        Trscv <Condtype> MSA_RX_LOS <Probcause>
        lossOfSignal (30) <Alarmtype> equipmentAlarm
        (5) <Polarity> (2)
        "
	  ::= { pm20002maAlmmsaModuleGeneralStatus 6 }



pm20002maAlmMsaRxNetworkLol OBJECT-TYPE
	  SYNTAX EkiOnOff
	  MAX-ACCESS read-only
	  STATUS current
	  DESCRIPTION
        "
        Line Trscv Rx Network Loss Of
         Lock :This OID indicates of Loss
        of Lock is detected on the Line
        Trscv Rx Network interface <Help>
        Alarm indicating of Loss of Lock
        is detected on the Line Trscv Rx
        Network interface <Condtype> MSA_RX_NETWORK_LOL
        <Probcause> receiverFailure (42)
        <Alarmtype> equipmentAlarm (5)
         <Polarity> (2)
        "
	  ::= { pm20002maAlmmsaModuleGeneralStatus 5 }



pm20002maAlmMsaOutOfAlignment OBJECT-TYPE
	  SYNTAX EkiOnOff
	  MAX-ACCESS read-only
	  STATUS current
	  DESCRIPTION
        "
        Line Trscv Out Of Alignment :This
        OID indicates an Out of alignment
        on the Line Trscv Host Interface
        <Help> Alarm indicating an Out
         of alignment on the Line Trscv
        Host Interface <Condtype> MSA_OUT_OF_ALIGNMENT
        <Probcause> receiverFailure (42)
        <Alarmtype> equipmentAlarm (5)
         <Polarity> (2)
        "
	  ::= { pm20002maAlmmsaModuleGeneralStatus 4 }



--- *****************************************************
---     LEAF for the msaGlobalAlarmSummary article
--- *****************************************************
pm20002maAlmmsaGlobalAlarmSummary OBJECT IDENTIFIER ::= { pm20002maAlmOtherCrit 80 }




pm20002maAlmMsaGlobAlarmAssertion  OBJECT-TYPE
	  SYNTAX EkiOnOff
	  MAX-ACCESS read-only
	  STATUS current
	  DESCRIPTION
        "
        Line Trscv Global Alarm :This
         OID indicates at least one Fault
        or Status is detected on the Line
        Trscv module <Help> Synthesis alarm
        indicating at least one Alarm,
         Warning, Fault or Status is detected
        on the Line Trscv module <Condtype>
        MSA_GLOB_ALARM_ASSERTION  <Probcause>
        informationalStatus(1000) <Alarmtype>
        other (1) <Polarity> (2)
        "
	  ::= { pm20002maAlmmsaGlobalAlarmSummary 16 }



pm20002maAlmMsaHostLaneFaultStatus  OBJECT-TYPE
	  SYNTAX EkiOnOff
	  MAX-ACCESS read-only
	  STATUS current
	  DESCRIPTION
        "
        Line Trscv Host Fault And Status
        :This OID indicates at least one
        Fault or Status is detected on
         the Line Trscv Host Interface
         <Help> Synthesis alarm indicating
        at least one Fault or Status is
        detected on the Line Trscv Host
        Interface <Condtype> MSA_HOST_LANE_FAULT_STATUS
         <Probcause> informationalStatus(1000)
        <Alarmtype> other (1) <Polarity>
        (2)
        "
	  ::= { pm20002maAlmmsaGlobalAlarmSummary 15 }



pm20002maAlmMsaNetworkLaneFaultStatus  OBJECT-TYPE
	  SYNTAX EkiOnOff
	  MAX-ACCESS read-only
	  STATUS current
	  DESCRIPTION
        "
        Line Trscv Network Fault And Status
        :This OID indicates at least one
        Fault or Status is detected on
         the Line Trscv Network Interface
        <Help> Synthesis alarm indicating
        at least one Fault or Status is
        detected on the Line Trscv Network
        Interface <Condtype> MSA_NETWORK_LANE_FAULT_STATUS
         <Probcause> informationalStatus(1000)
        <Alarmtype> other (1) <Polarity>
        (2)
        "
	  ::= { pm20002maAlmmsaGlobalAlarmSummary 14 }



pm20002maAlmMsaNetworkLaneAlarmWarning1 OBJECT-TYPE
	  SYNTAX EkiOnOff
	  MAX-ACCESS read-only
	  STATUS current
	  DESCRIPTION
        "
        Line Trscv Network Alarm And Warning
        1 :This OID indicates at least
         one DDM is detected on the Line
        Trscv Network Interface <Help>
         Synthesis alarm indicating at
         least one DDM Alarm or DDM Warning
        is detected on the Line Trscv Network
        Interface <Condtype> MSA_NETWORK_LANE_ALARM_WARNING_1
        <Probcause> informationalStatus(1000)
        <Alarmtype> other (1) <Polarity>
        (2)
        "
	  ::= { pm20002maAlmmsaGlobalAlarmSummary 13 }



pm20002maAlmMsaModuleAlarmWarning2 OBJECT-TYPE
	  SYNTAX EkiOnOff
	  MAX-ACCESS read-only
	  STATUS current
	  DESCRIPTION
        "
        Line Trscv Module Alarm And Warning
        2 :This OID indicates at least
         one DDM is detected on the Line
        Trscv module <Help> Synthesis alarm
        indicating at least one DDM Alarm
        or DDM Warning is detected on the
        Line Trscv module <Condtype> MSA_MODULE_ALARM_WARNING_2
        <Probcause> informationalStatus(1000)
        <Alarmtype> other (1) <Polarity>
        (2)
        "
	  ::= { pm20002maAlmmsaGlobalAlarmSummary 12 }



pm20002maAlmMsaModuleAlarmWarning1  OBJECT-TYPE
	  SYNTAX EkiOnOff
	  MAX-ACCESS read-only
	  STATUS current
	  DESCRIPTION
        "
        Line Trscv Module Alarm And Warning
        1 :This OID indicates at least
         one DDM is detected on the Line
        Trscv module <Help> Synthesis alarm
        indicating at least one DDM Alarm
        or DDM Warning is detected on the
        Line Trscv module <Condtype> MSA_MODULE_ALARM_WARNING_1
         <Probcause> informationalStatus(1000)
        <Alarmtype> other (1) <Polarity>
        (2)
        "
	  ::= { pm20002maAlmmsaGlobalAlarmSummary 11 }



pm20002maAlmModuleFault  OBJECT-TYPE
	  SYNTAX EkiOnOff
	  MAX-ACCESS read-only
	  STATUS current
	  DESCRIPTION
        "
        Line Trscv Module Fault :This
         OID indicates at least one Fault
        is detected on the Line Trscv module
        <Help> Synthesis alarm indicating
        at least one Fault is detected
         on the Line Trscv module <Condtype>
        MODULE_FAULT  <Probcause> informationalStatus(1000)
        <Alarmtype> other (1) <Polarity>
        (2)
        "
	  ::= { pm20002maAlmmsaGlobalAlarmSummary 10 }



pm20002maAlmMsaModuleGeneralStatus  OBJECT-TYPE
	  SYNTAX EkiOnOff
	  MAX-ACCESS read-only
	  STATUS current
	  DESCRIPTION
        "
        Line Trscv General Status :This
        OID indicates the Line Trscv module
        general <Help> Synthesis alarm
         indicating the Line Trscv module
        general status <Condtype> MSA_MODULE_GENERAL_STATUS
         <Probcause> informationalStatus(1000)
        <Alarmtype> other (1) <Polarity>
        (2)
        "
	  ::= { pm20002maAlmmsaGlobalAlarmSummary 9 }



pm20002maAlmMsaModuleState  OBJECT-TYPE
	  SYNTAX EkiOnOff
	  MAX-ACCESS read-only
	  STATUS current
	  DESCRIPTION
        "
        Line Trscv Module State :This
         OID indicates the Line Trscv module
        state <Help> Synthesis alarm indicating
        the Line Trscv module state <Condtype>
        MSA_MODULE_STATE  <Probcause> informationalStatus(1000)
        <Alarmtype> other (1) <Polarity>
        (2)
        "
	  ::= { pm20002maAlmmsaGlobalAlarmSummary 8 }



pm20002maAlmMsaNetworkLaneAlarmWarning2 OBJECT-TYPE
	  SYNTAX EkiOnOff
	  MAX-ACCESS read-only
	  STATUS current
	  DESCRIPTION
        "
        Line Trscv Network Alarm And Warning
        2 :This OID indicates at least
         one DDM This OID is detected on
        the Line Trscv Network Interface
        <Help> Synthesis alarm indicating
        at least one DDM Alarm or DDM Warning
        is detected on the Line Trscv Network
        Interface <Condtype> MSA_NETWORK_LANE_ALARM_WARNING_2
        <Probcause> informationalStatus(1000)
        <Alarmtype> other (1) <Polarity>
        (2)
        "
	  ::= { pm20002maAlmmsaGlobalAlarmSummary 7 }



pm20002maAlmMsaNetworkHostAlarmStatus OBJECT-TYPE
	  SYNTAX EkiOnOff
	  MAX-ACCESS read-only
	  STATUS current
	  DESCRIPTION
        "
        Line Trscv Network/Host Alarm
         Status :This OID indicates the
        state of the Network and Host interface
        of the Line Trscv <Help> Synthesis
        alarm indicating the alarm state
        of the Network and Host interface
        of the Line Trscv <Condtype> MSA_NETWORK_HOST_ALARM_STATUS
        <Probcause> informationalStatus(1000)
        <Alarmtype> other (1) <Polarity>
        (2)
        "
	  ::= { pm20002maAlmmsaGlobalAlarmSummary 6 }



pm20002maAlmMsaSoftGlobAlarmTest  OBJECT-TYPE
	  SYNTAX EkiOnOff
	  MAX-ACCESS read-only
	  STATUS current
	  DESCRIPTION
        "
        Line Trscv Global Alarm SW Test
        :This OID indicates the Line Trscv
        Global alarm This OID is raised
        by SW request for test purpose
         <Help> Status indicating the Line
        Trscv Global Alarm is raised by
        SW request for test purpose <Condtype>
        MSA_SOFT_GLOB_ALARM_TEST  <Probcause>
        informationalStatus(1000) <Alarmtype>
        other (1) <Polarity> (2)
        "
	  ::= { pm20002maAlmmsaGlobalAlarmSummary 1 }



--- *****************************************************
---     LEAF for the msaNetworkTxAlignment article
--- *****************************************************
pm20002maAlmmsaNetworkTxAlignment OBJECT IDENTIFIER ::= { pm20002maAlmOtherCrit 81 }




pm20002maAlmNetTxLossOfAlignment OBJECT-TYPE
	  SYNTAX EkiOnOff
	  MAX-ACCESS read-only
	  STATUS current
	  DESCRIPTION
        "
        Line Trscv Network Tx Loss Of
         Alignment :This OID indicates
         a Tx Loss of Alignment is detected
        on the Line Trscv Network interface
        <Help> Alarm indicating a Tx Loss
        of Alignment is detected on the
        Line Trscv Network interface <Condtype>
        NET_TX_LOSS_OF_ALIGNMENT <Probcause>
        transmitterFailure (56) <Alarmtype>
        equipmentAlarm (5) <Polarity> (2)
        "
	  ::= { pm20002maAlmmsaNetworkTxAlignment 16 }



pm20002maAlmNetTxOutOfAlignment OBJECT-TYPE
	  SYNTAX EkiOnOff
	  MAX-ACCESS read-only
	  STATUS current
	  DESCRIPTION
        "
        Line Trscv Network Tx Out Of Alignment
        :This OID indicates a Tx Out of
        Alignment is detected on the Line
        Trscv Network interface <Help>
         Alarm indicating a Tx Out of Alignment
        is detected on the Line Trscv Network
        interface <Condtype> NET_TX_OUT_OF_ALIGNMENT
        <Probcause> transmitterFailure
         (56) <Alarmtype> equipmentAlarm
        (5) <Polarity> (2)
        "
	  ::= { pm20002maAlmmsaNetworkTxAlignment 15 }



pm20002maAlmNetTxCmuLockFault OBJECT-TYPE
	  SYNTAX EkiOnOff
	  MAX-ACCESS read-only
	  STATUS current
	  DESCRIPTION
        "
        Line Trscv Network Tx CMU Lock
        Fault :This OID indicates a Tx
         Clock Multiplier Unit Lock Fault
        is detected on the Line Trscv Network
        interface <Help> Alarm indicating
        a Tx Clock Multiplier Unit Lock
        Fault is detected on the Line Trscv
        Network interface <Condtype> NET_TX_CMU_LOCK_FAULT
        <Probcause> transmitterFailure
         (56) <Alarmtype> equipmentAlarm
        (5) <Polarity> (2)
        "
	  ::= { pm20002maAlmmsaNetworkTxAlignment 14 }



pm20002maAlmNetTxReferenceClockFault OBJECT-TYPE
	  SYNTAX EkiOnOff
	  MAX-ACCESS read-only
	  STATUS current
	  DESCRIPTION
        "
        Line Trscv Network Tx Ref Clock
        Fault :This OID indicates a Tx
         Reference Clock Fault is detected
        on the Line Trscv Network interface
        <Help> Alarm indicating a Tx Reference
        Clock Fault is detected on the
         Line Trscv Network interface <Condtype>
        NET_TX_REFERENCE_CLOCK_FAULT <Probcause>
        transmitterFailure (56) <Alarmtype>
        equipmentAlarm (5) <Polarity> (2)
        "
	  ::= { pm20002maAlmmsaNetworkTxAlignment 13 }



pm20002maAlmNetTxTimingFault OBJECT-TYPE
	  SYNTAX EkiOnOff
	  MAX-ACCESS read-only
	  STATUS current
	  DESCRIPTION
        "
        Line Trscv Network Tx Timing Fault
        :This OID indicates a Tx Timing
        Fault is detected on the Line Trscv
        Network interface <Help> Alarm
         indicating a Tx Timing Fault is
        detected on the Line Trscv Network
        interface <Condtype> NET_TX_TIMING_FAULT
        <Probcause> transmitterFailure
         (56) <Alarmtype> equipmentAlarm
        (5) <Polarity> (2)
        "
	  ::= { pm20002maAlmmsaNetworkTxAlignment 12 }



--- *****************************************************
---     LEAF for the msaNetworkRxAlignment article
--- *****************************************************
pm20002maAlmmsaNetworkRxAlignment OBJECT IDENTIFIER ::= { pm20002maAlmOtherCrit 82 }




pm20002maAlmNetRxModemSyncDetectFault OBJECT-TYPE
	  SYNTAX EkiOnOff
	  MAX-ACCESS read-only
	  STATUS current
	  DESCRIPTION
        "
        Line Trscv Network Rx Modem Sync
        Detect Fault :This OID indicates
        a Rx Modem Synchronisation Detection
        Fault is detected on the Line Trscv
        Network interface <Help> Alarm
         indicating a Rx Modem Synchronisation
        Detection Fault is detected on
         the Line Trscv Network interface
        <Condtype> NET_RX_MODEM_SYNC_DETECT_FAULT
        <Probcause> receiverFailure (42)
        <Alarmtype> equipmentAlarm (5)
         <Polarity> (2)
        "
	  ::= { pm20002maAlmmsaNetworkRxAlignment 16 }



pm20002maAlmNetRxModemLockFault OBJECT-TYPE
	  SYNTAX EkiOnOff
	  MAX-ACCESS read-only
	  STATUS current
	  DESCRIPTION
        "
        Line Trscv Network Rx Modem Lock
        Fault :This OID indicates a Rx
         Modem Lock Fault is detected on
        the Line Trscv Network interface
        <Help> Alarm indicating a Rx Modem
        Lock Fault is detected on the Line
        Trscv Network interface <Condtype>
        NET_RX_MODEM_LOCK_FAULT <Probcause>
        receiverFailure (42) <Alarmtype>
        equipmentAlarm (5) <Polarity> (2)
        "
	  ::= { pm20002maAlmmsaNetworkRxAlignment 15 }



pm20002maAlmNetRxLossOfAlignment OBJECT-TYPE
	  SYNTAX EkiOnOff
	  MAX-ACCESS read-only
	  STATUS current
	  DESCRIPTION
        "
        Line Trscv Network Rx Loss Of
         Alignment :This OID indicates
         a Rx Loss of Alignment is detected
        on the Line Trscv Network interface
        <Help> Alarm indicating a Rx Loss
        of Alignment is detected on the
        Line Trscv Network interface <Condtype>
        NET_RX_LOSS_OF_ALIGNMENT <Probcause>
        receiverFailure (42) <Alarmtype>
        equipmentAlarm (5) <Polarity> (2)
        "
	  ::= { pm20002maAlmmsaNetworkRxAlignment 14 }



pm20002maAlmNetRxOutOfAlignment OBJECT-TYPE
	  SYNTAX EkiOnOff
	  MAX-ACCESS read-only
	  STATUS current
	  DESCRIPTION
        "
        Line Trscv Network Rx Out Of Alignment
        :This OID indicates a Rx Out of
        Alignment is detected on the Line
        Trscv Network interface <Help>
         Alarm indicating a Rx Out of Alignment
        is detected on the Line Trscv Network
        interface <Condtype> NET_RX_OUT_OF_ALIGNMENT
        <Probcause> receiverFailure (42)
        <Alarmtype> equipmentAlarm (5)
         <Polarity> (2)
        "
	  ::= { pm20002maAlmmsaNetworkRxAlignment 13 }



pm20002maAlmNetRxTimingFault OBJECT-TYPE
	  SYNTAX EkiOnOff
	  MAX-ACCESS read-only
	  STATUS current
	  DESCRIPTION
        "
        Line Trscv Network Rx Timing Fault
        :This OID indicates a Rx Timing
        Fault is detected on the Line Trscv
        Network interface <Help> Alarm
         indicating a Rx Timing Fault is
        detected on the Line Trscv Network
        interface <Condtype> NET_RX_TIMING_FAULT
        <Probcause> receiverFailure (42)
        <Alarmtype> equipmentAlarm (5)
         <Polarity> (2)
        "
	  ::= { pm20002maAlmmsaNetworkRxAlignment 12 }



--- *****************************************************
---     LEAF for the msaNetworkHostNetworkAlarmSummary article
--- *****************************************************
pm20002maAlmmsaNetworkHostNetworkAlarmSummary OBJECT IDENTIFIER ::= { pm20002maAlmOtherCrit 83 }




pm20002maAlmHostTxOtnStatus OBJECT-TYPE
	  SYNTAX EkiOnOff
	  MAX-ACCESS read-only
	  STATUS current
	  DESCRIPTION
        "
        Line Trscv Host Tx OTN :This OID
        indicates a Tx OTN Fault is detected
        on the Line Trscv Host interface
        <Help> Synthesis Alarm indicating
        a Tx OTN Fault is detected on the
        Line Trscv Host interface <Condtype>
        HOST_TX_OTN_STATUS <Probcause>
         informationalStatus(1000) <Alarmtype>
        other (1) <Polarity> (2)
        "
	  ::= { pm20002maAlmmsaNetworkHostNetworkAlarmSummary 16 }



pm20002maAlmHostTxAlignment OBJECT-TYPE
	  SYNTAX EkiOnOff
	  MAX-ACCESS read-only
	  STATUS current
	  DESCRIPTION
        "
        Line Trscv Host Tx Alignment :This
        OID indicates a Tx Alignment Fault
        is detected on the Line Trscv Host
        interface <Help> Synthesis Alarm
        indicating a Tx Alignment Fault
        is detected on the Line Trscv Host
        interface <Condtype> HOST_TX_ALIGNMENT
        <Probcause> informationalStatus(1000)
        <Alarmtype> other (1) <Polarity>
        (2)
        "
	  ::= { pm20002maAlmmsaNetworkHostNetworkAlarmSummary 15 }



pm20002maAlmHostRxAlignment OBJECT-TYPE
	  SYNTAX EkiOnOff
	  MAX-ACCESS read-only
	  STATUS current
	  DESCRIPTION
        "
        Line Trscv Host Rx Alignment :This
        OID indicates a Rx Alignment Fault
        is detected on the Line Trscv Host
        interface <Help> Synthesis Alarm
        indicating a Rx Alignment Fault
        is detected on the Line Trscv Host
        interface <Condtype> HOST_RX_ALIGNMENT
        <Probcause> informationalStatus(1000)
        <Alarmtype> other (1) <Polarity>
        (2)
        "
	  ::= { pm20002maAlmmsaNetworkHostNetworkAlarmSummary 14 }



pm20002maAlmNetworkRxOtn OBJECT-TYPE
	  SYNTAX EkiOnOff
	  MAX-ACCESS read-only
	  STATUS current
	  DESCRIPTION
        "
        Line Trscv Network Rx OTN :This
        OID indicates a Rx OTN Fault is
        detected on the Line Trscv Network
        interface <Help> Synthesis Alarm
        indicating a Rx OTN Fault is detected
        on the Line Trscv Network interface
        <Condtype> NETWORK_RX_OTN <Probcause>
        informationalStatus(1000) <Alarmtype>
        other (1) <Polarity> (2)
        "
	  ::= { pm20002maAlmmsaNetworkHostNetworkAlarmSummary 13 }



pm20002maAlmNetworkRxAlignment OBJECT-TYPE
	  SYNTAX EkiOnOff
	  MAX-ACCESS read-only
	  STATUS current
	  DESCRIPTION
        "
        Line Trscv Network Rx Alignment
        :This OID indicates a Rx Alignment
        Fault is detected on the Line Trscv
        Network interface <Help> Synthesis
        Alarm indicating a Rx Alignment
        Fault is detected on the Line Trscv
        Network interface <Condtype> NETWORK_RX_ALIGNMENT
        <Probcause> informationalStatus(1000)
        <Alarmtype> other (1) <Polarity>
        (2)
        "
	  ::= { pm20002maAlmmsaNetworkHostNetworkAlarmSummary 12 }



pm20002maAlmNetworkTxAlignment OBJECT-TYPE
	  SYNTAX EkiOnOff
	  MAX-ACCESS read-only
	  STATUS current
	  DESCRIPTION
        "
        Line Trscv Network Tx Alignment
        :This OID indicates a Tx Alignment
        Fault is detected on the Line Trscv
        Network interface <Help> Synthesis
        Alarm indicating a Tx Alignment
        Fault is detected on the Line Trscv
        Network interface <Condtype> NETWORK_TX_ALIGNMENT
        <Probcause> informationalStatus(1000)
        <Alarmtype> other (1) <Polarity>
        (2)
        "
	  ::= { pm20002maAlmmsaNetworkHostNetworkAlarmSummary 11 }



--- *****************************************************
---     LEAF for the msaHostTxAlignment article
--- *****************************************************
pm20002maAlmmsaHostTxAlignment OBJECT IDENTIFIER ::= { pm20002maAlmOtherCrit 84 }




pm20002maAlmHostTxCdrLockFault OBJECT-TYPE
	  SYNTAX EkiOnOff
	  MAX-ACCESS read-only
	  STATUS current
	  DESCRIPTION
        "
        Line Trscv Host Tx CDR Lock Fault
        :This OID indicates a Tx Clock
         Data Recovery Lock Fault is detected
        on the Line Trscv Host interface
        <Help> Alarm indicating a Tx Clock
        Data Recovery Lock Fault is detected
        on the Line Trscv Host interface
        <Condtype> HOST_TX_CDR_LOCK_FAULT
        <Probcause> receiverFailure (42)
        <Alarmtype> equipmentAlarm (5)
         <Polarity> (2)
        "
	  ::= { pm20002maAlmmsaHostTxAlignment 16 }



pm20002maAlmHostTxLossOfAlignment OBJECT-TYPE
	  SYNTAX EkiOnOff
	  MAX-ACCESS read-only
	  STATUS current
	  DESCRIPTION
        "
        Line Trscv Host Tx Loss Of Alignment
        :This OID indicates a Tx Loss of
        Alignment is detected on the Line
        Trscv Host interface <Help> Alarm
        indicating a Tx Loss of Alignment
        is detected on the Line Trscv Host
        interface <Condtype> HOST_TX_LOSS_OF_ALIGNMENT
        <Probcause> receiverFailure (42)
        <Alarmtype> equipmentAlarm (5)
         <Polarity> (2)
        "
	  ::= { pm20002maAlmmsaHostTxAlignment 15 }



pm20002maAlmHostTxOutOfAlignment OBJECT-TYPE
	  SYNTAX EkiOnOff
	  MAX-ACCESS read-only
	  STATUS current
	  DESCRIPTION
        "
        Line Trscv Host Tx Out Of Alignment
        :This OID indicates a Tx Out of
        Alignment is detected on the Line
        Trscv Host interface <Help> Alarm
        indicating a Tx Out of Alignment
        is detected on the Line Trscv Host
        interface <Condtype> HOST_TX_OUT_OF_ALIGNMENT
        <Probcause> receiverFailure (42)
        <Alarmtype> equipmentAlarm (5)
         <Polarity> (2)
        "
	  ::= { pm20002maAlmmsaHostTxAlignment 14 }



pm20002maAlmHostTxDeskewLockFault OBJECT-TYPE
	  SYNTAX EkiOnOff
	  MAX-ACCESS read-only
	  STATUS current
	  DESCRIPTION
        "
        Line Trscv Host Tx Deskew Lock
        Fault :This OID indicates a Tx
         Deskew Lock Fault is detected
         on  the Line Trscv Host interface
        <Help> Alarm indicating a Tx Deskew
        Lock Fault is detected on  the
         Line Trscv Host interface <Condtype>
        HOST_TX_DESKEW_LOCK_FAULT <Probcause>
        receiverFailure (42) <Alarmtype>
        equipmentAlarm (5) <Polarity> (2)
        "
	  ::= { pm20002maAlmmsaHostTxAlignment 13 }



--- *****************************************************
---     LEAF for the msaHostRxAlignment article
--- *****************************************************
pm20002maAlmmsaHostRxAlignment OBJECT IDENTIFIER ::= { pm20002maAlmOtherCrit 85 }




pm20002maAlmHostRxLossOfAlignment OBJECT-TYPE
	  SYNTAX EkiOnOff
	  MAX-ACCESS read-only
	  STATUS current
	  DESCRIPTION
        "
        Line Trscv Host Rx Loss Of Alignment
        :This OID indicates a Rx Loss of
        Alignment is detected on the Line
        Trscv Host interface <Help> Alarm
        indicating a Rx Loss of Alignment
        is detected on the Line Trscv Host
        interface <Condtype> HOST_RX_LOSS_OF_ALIGNMENT
        <Probcause> transmitterFailure
         (56) <Alarmtype> equipmentAlarm
        (5) <Polarity> (2)
        "
	  ::= { pm20002maAlmmsaHostRxAlignment 16 }



pm20002maAlmHostRxOutOfAlignment OBJECT-TYPE
	  SYNTAX EkiOnOff
	  MAX-ACCESS read-only
	  STATUS current
	  DESCRIPTION
        "
        Line Trscv Host Rx Out Of Alignment
        :This OID indicates a Rx Out of
        Alignment is detected on the Line
        Trscv Host interface <Help> Alarm
        indicating a Rx Out of Alignment
        is detected on the Line Trscv Host
        interface <Condtype> HOST_RX_OUT_OF_ALIGNMENT
        <Probcause> transmitterFailure
         (56) <Alarmtype> equipmentAlarm
        (5) <Polarity> (2)
        "
	  ::= { pm20002maAlmmsaHostRxAlignment 15 }



pm20002maAlmHostRxCmuLockFault OBJECT-TYPE
	  SYNTAX EkiOnOff
	  MAX-ACCESS read-only
	  STATUS current
	  DESCRIPTION
        "
        Line Trscv Host Rx CMU Lock Fault
        :This OID indicates a Rx Clock
         Multiplier Unit Lock Fault is
         detected on the Line Trscv Host
        interface <Help> Alarm indicating
        a Rx Clock Multiplier Unit Lock
        Fault is detected on the Line Trscv
        Host interface <Condtype> HOST_RX_CMU_LOCK_FAULT
        <Probcause> transmitterFailure
         (56) <Alarmtype> equipmentAlarm
        (5) <Polarity> (2)
        "
	  ::= { pm20002maAlmmsaHostRxAlignment 14 }



--- *********************************************************
---     TABLE for the pm20002maAlmclientHostLaneFault articles
--- *********************************************************

pm20002maAlmclientHostLaneFaultTable OBJECT-TYPE
	SYNTAX  SEQUENCE OF Pm20002maAlmclientHostLaneFaultEntry
	MAX-ACCESS not-accessible
	STATUS current
	DESCRIPTION
        "
        List of pm20002maAlmclientHostLaneFault
        Article
        "
	::= { pm20002maAlmClientUrg 152 }


pm20002maAlmclientHostLaneFaultEntry OBJECT-TYPE
	SYNTAX Pm20002maAlmclientHostLaneFaultEntry
	MAX-ACCESS not-accessible
	STATUS current
	DESCRIPTION
        "
        Row definition for the pm20002maAlmclientHostLaneFault
        table
        "
	INDEX   { pm20002maAlmclientHostLaneFaultIndex }
	::= { pm20002maAlmclientHostLaneFaultTable 1 }


Pm20002maAlmclientHostLaneFaultEntry ::=
	SEQUENCE {
	pm20002maAlmclientHostLaneFaultIndex
		INTEGER,
	pm20002maAlmClientLaneTxFifoErrorPortn
		EkiOnOff,
	pm20002maAlmClientTxHostLolPortn
		EkiOnOff,
	pm20002maAlmClientCsfDetectedPortn
		EkiOnOff,
	pm20002maAlmClientLanesNotAlignedPortn
		EkiOnOff,
	pm20002maAlmClientLanes6466UnlockPortn
		EkiOnOff,
	pm20002maAlmClientLanesMarkerUnlockPortn
		EkiOnOff,
	pm20002maAlmClientInputLossOfSigPortn
		EkiOnOff,
	pm20002maAlmClientLossOfSyncPortn
		EkiOnOff
	}


pm20002maAlmclientHostLaneFaultIndex OBJECT-TYPE
	SYNTAX  INTEGER(0..128)
	MAX-ACCESS  read-only
	STATUS current
	DESCRIPTION
        "
        Index definition for the pm20002maAlmclientHostLaneFault
        table
        "
	::= { pm20002maAlmclientHostLaneFaultEntry 1 }


pm20002maAlmClientLaneTxFifoErrorPortn OBJECT-TYPE
	SYNTAX  EkiOnOff
	MAX-ACCESS read-only
	STATUS current
	DESCRIPTION
        "
        Client Host Lane Tx FIFO Error
        :This OID indicates a Tx FIFO Error
        on the Client Trscv Host Lane <Help>
        Alarm indicating a Tx FIFO Error
        on the Client Trscv Host Lane <Condtype>
        CLIENT_LANE_TX_FIFO_ERROR <Probcause>
        receiverFailure (42) <Alarmtype>
        equipmentAlarm (5) <Polarity> (2)
        "
	::= { pm20002maAlmclientHostLaneFaultEntry 11 }


pm20002maAlmClientTxHostLolPortn OBJECT-TYPE
	SYNTAX  EkiOnOff
	MAX-ACCESS read-only
	STATUS current
	DESCRIPTION
        "
        Client Host Lane Tx Loss Of Lock
        :This OID indicates a Tx Loss of
        Lock on the Client Trscv Host Lane
        <Help> Alarm indicating a Tx Loss
        of Lock on the Client Trscv Host
        Lane <Condtype> CLIENT_TX_HOST_LOL
        <Probcause> receiverFailure (42)
        <Alarmtype> equipmentAlarm (5)
         <Polarity> (2)
        "
	::= { pm20002maAlmclientHostLaneFaultEntry 10 }


pm20002maAlmClientCsfDetectedPortn OBJECT-TYPE
	SYNTAX  EkiOnOff
	MAX-ACCESS read-only
	STATUS current
	DESCRIPTION
        "
        Client Signal Fail Detected :This
        OID indicates that a CSF has been
        detected on client port in the
         downstream direction   <Help>
          This alarm indicates if a Client
        Signal Fail has been detected in
        the incoming line frame for this
        client port <Condtype> CLIENT_CSF_DETECTED
        <Probcause> receiveFailure (41)
        <Alarmtype> other(1) <Polarity>
        (2)
        "
	::= { pm20002maAlmclientHostLaneFaultEntry 7 }


pm20002maAlmClientLanesNotAlignedPortn OBJECT-TYPE
	SYNTAX  EkiOnOff
	MAX-ACCESS read-only
	STATUS current
	DESCRIPTION
        "
        Client Lanes Not Aligned :This
        OID indicates the Client lanes
         are not aligned <Help> Alarm indicating
        the Client lanes are not aligned
        <Condtype> CLIENT_LANES_NOT_ALIGNED
        <Probcause> receiveFailure (41)
        <Alarmtype> integrityViolation
         (7) <Polarity> (2)
        "
	::= { pm20002maAlmclientHostLaneFaultEntry 6 }


pm20002maAlmClientLanes6466UnlockPortn OBJECT-TYPE
	SYNTAX  EkiOnOff
	MAX-ACCESS read-only
	STATUS current
	DESCRIPTION
        "
        Client Lanes 64/66b Unlock :This
        OID indicates the Client 64/66b
        decoder is not lock <Help> Alarm
        indicating the Client 64/66b decoder
        is not lock <Condtype> CLIENT_LANES_64_66_UNLOCK
        <Probcause> receiveFailure (41)
        <Alarmtype> integrityViolation
         (7) <Polarity> (2)
        "
	::= { pm20002maAlmclientHostLaneFaultEntry 5 }


pm20002maAlmClientLanesMarkerUnlockPortn OBJECT-TYPE
	SYNTAX  EkiOnOff
	MAX-ACCESS read-only
	STATUS current
	DESCRIPTION
        "
        Client Lanes Marker Unlock :This
        OID indicates the Client lanes
         marker alignment is not lock <Help>
        Alarm indicating the Client lanes
        marker alignment is not lock <Condtype>
        CLIENT_LANES_MARKER_UNLOCK <Probcause>
        receiveFailure (41) <Alarmtype>
        integrityViolation (7) <Polarity>
        (2)
        "
	::= { pm20002maAlmclientHostLaneFaultEntry 4 }


pm20002maAlmClientInputLossOfSigPortn OBJECT-TYPE
	SYNTAX  EkiOnOff
	MAX-ACCESS read-only
	STATUS current
	DESCRIPTION
        "
        Client Input Loss Of Signal :This
        OID indicates a Loss of Signal
         is detected on the Client Trscv
        <Help> Alarm indicating a Loss
         of Signal is detected on the Client
        Trscv <Condtype> CLIENT_INPUT_LOSS_OF_SIG
        <Probcause> receiveFailure (41)
        <Alarmtype> physicalViolation (9)
        <Polarity> (2)
        "
	::= { pm20002maAlmclientHostLaneFaultEntry 3 }


pm20002maAlmClientLossOfSyncPortn OBJECT-TYPE
	SYNTAX  EkiOnOff
	MAX-ACCESS read-only
	STATUS current
	DESCRIPTION
        "
        Client Frame Alignment Loss :This
        OID indicates the module is not
        aligned with the incoming Client
        signal <Help> Alarm indicating
         the module is not aligned with
        the incoming client signal <Condtype>
        CLIENT_LOSS_OF_SYNC <Probcause>
        receiveFailure (41) <Alarmtype>
        integrityViolation (7) <Polarity>
        (2)
        "
	::= { pm20002maAlmclientHostLaneFaultEntry 2 }


--- *********************************************************
---     TABLE for the pm20002maAlmlineNetworkLaneAlarmWarning1 articles
--- *********************************************************

pm20002maAlmlineNetworkLaneAlarmWarning1Table OBJECT-TYPE
	SYNTAX  SEQUENCE OF Pm20002maAlmlineNetworkLaneAlarmWarning1Entry
	MAX-ACCESS not-accessible
	STATUS current
	DESCRIPTION
        "
        List of pm20002maAlmlineNetworkLaneAlarmWarning1
        Article
        "
	::= { pm20002maAlmLineNurg 184 }


pm20002maAlmlineNetworkLaneAlarmWarning1Entry OBJECT-TYPE
	SYNTAX Pm20002maAlmlineNetworkLaneAlarmWarning1Entry
	MAX-ACCESS not-accessible
	STATUS current
	DESCRIPTION
        "
        Row definition for the pm20002maAlmlineNetworkLaneAlarmWarning1
        table
        "
	INDEX   { pm20002maAlmlineNetworkLaneAlarmWarning1Index }
	::= { pm20002maAlmlineNetworkLaneAlarmWarning1Table 1 }


Pm20002maAlmlineNetworkLaneAlarmWarning1Entry ::=
	SEQUENCE {
	pm20002maAlmlineNetworkLaneAlarmWarning1Index
		INTEGER,
	pm20002maAlmLineBiasHighAlarmPortn
		EkiOnOff,
	pm20002maAlmLineBiasHighWarningPortn
		EkiOnOff,
	pm20002maAlmLineBiasLowWarningPortn
		EkiOnOff,
	pm20002maAlmLineBiasLowAlarmPortn
		EkiOnOff,
	pm20002maAlmLineTxPowerHighAlarmPortn
		EkiOnOff,
	pm20002maAlmLineTxPowerHighWarningPortn
		EkiOnOff,
	pm20002maAlmLineTxPowerLowWarningPortn
		EkiOnOff,
	pm20002maAlmLineTxPowerLowAlarmPortn
		EkiOnOff,
	pm20002maAlmLineLaserTempHighAlarmPortn
		EkiOnOff,
	pm20002maAlmLineLaserTempHighWarningPortn
		EkiOnOff,
	pm20002maAlmLineLaserTempLowWarningPortn
		EkiOnOff,
	pm20002maAlmLineLaserTempLowAlarmPortn
		EkiOnOff,
	pm20002maAlmLineRxPowerHighAlarmPortn
		EkiOnOff,
	pm20002maAlmLineRxPowerHighWarningPortn
		EkiOnOff,
	pm20002maAlmLineRxPowerLowWarningPortn
		EkiOnOff,
	pm20002maAlmLineRxPowerLowAlarmPortn
		EkiOnOff
	}


pm20002maAlmlineNetworkLaneAlarmWarning1Index OBJECT-TYPE
	SYNTAX  INTEGER(0..128)
	MAX-ACCESS  read-only
	STATUS current
	DESCRIPTION
        "
        Index definition for the pm20002maAlmlineNetworkLaneAlarmWarning1
        table
        "
	::= { pm20002maAlmlineNetworkLaneAlarmWarning1Entry 1 }


pm20002maAlmLineBiasHighAlarmPortn OBJECT-TYPE
	SYNTAX  EkiOnOff
	MAX-ACCESS read-only
	STATUS current
	DESCRIPTION
        "
        Line Trscv Tx Bias High Alarm
         :This OID indicates that the Trscv
        laser bias current is higher than
        the threshold value written in
         the Trscv EEPROM <Help> Alarm
         indicating that the Trscv laser
        bias current is higher than the
        threshold value written in the
         Trscv EEPROM <Condtype> LINE_BIAS_HIGH_ALARM
        <Probcause> transmitterFailure
         (56) <Alarmtype> equipmentAlarm
        (5) <Polarity> (2)
        "
	::= { pm20002maAlmlineNetworkLaneAlarmWarning1Entry 17 }


pm20002maAlmLineBiasHighWarningPortn OBJECT-TYPE
	SYNTAX  EkiOnOff
	MAX-ACCESS read-only
	STATUS current
	DESCRIPTION
        "
        Line Trscv Tx Bias High Warning
        :This OID indicates that the Trscv
        laser bias current is higher than
        the threshold value written in
         the Trscv EEPROM <Help> Warning
        indicating that the Trscv laser
        bias current is higher than the
        threshold value written in the
         Trscv EEPROM <Condtype> LINE_BIAS_HIGH_WARNING
        <Probcause> transmitterFailure
         (56) <Alarmtype> equipmentAlarm
        (5) <Polarity> (2)
        "
	::= { pm20002maAlmlineNetworkLaneAlarmWarning1Entry 16 }


pm20002maAlmLineBiasLowWarningPortn OBJECT-TYPE
	SYNTAX  EkiOnOff
	MAX-ACCESS read-only
	STATUS current
	DESCRIPTION
        "
        Line Trscv Tx Bias Low Warning
        :This OID indicates that the Trscv
        laser bias current is lower than
        the threshold value written in
         the Trscv EEPROM <Help> Warning
        indicating that the Trscv laser
        bias current is lower than the
         threshold value written in the
        Trscv EEPROM <Condtype> LINE_BIAS_LOW_WARNING
        <Probcause> transmitterFailure
         (56) <Alarmtype> equipmentAlarm
        (5) <Polarity> (2)
        "
	::= { pm20002maAlmlineNetworkLaneAlarmWarning1Entry 15 }


pm20002maAlmLineBiasLowAlarmPortn OBJECT-TYPE
	SYNTAX  EkiOnOff
	MAX-ACCESS read-only
	STATUS current
	DESCRIPTION
        "
        Line Trscv Tx Bias Low Alarm :This
        OID indicates that the Trscv laser
        bias current is lower than the
         threshold value written in the
        Trscv EEPROM <Help> Alarm indicating
        that the Trscv laser bias current
        is lower than the threshold value
        written in the Trscv EEPROM <Condtype>
        LINE_BIAS_LOW_ALARM <Probcause>
        transmitterFailure (56) <Alarmtype>
        equipmentAlarm (5) <Polarity> (2)
        "
	::= { pm20002maAlmlineNetworkLaneAlarmWarning1Entry 14 }


pm20002maAlmLineTxPowerHighAlarmPortn OBJECT-TYPE
	SYNTAX  EkiOnOff
	MAX-ACCESS read-only
	STATUS current
	DESCRIPTION
        "
        Line Trscv Tx Power High Alarm
        :This OID indicates that the Trscv
        output power is higher than the
        threshold value written in the
         Trscv EEPROM <Help> Alarm indicating
        that the Trscv output power is
         higher than the threshold value
        written in the Trscv EEPROM <Condtype>
        LINE_TX_POWER_HIGH_ALARM <Probcause>
        transmitterFailure (56) <Alarmtype>
        equipmentAlarm (5) <Polarity> (2)
        "
	::= { pm20002maAlmlineNetworkLaneAlarmWarning1Entry 13 }


pm20002maAlmLineTxPowerHighWarningPortn OBJECT-TYPE
	SYNTAX  EkiOnOff
	MAX-ACCESS read-only
	STATUS current
	DESCRIPTION
        "
        Line Trscv Tx Power High Warning
        :This OID indicates that the Trscv
        output power is higher than the
        threshold value written in the
         Trscv EEPROM <Help> Warning indicating
        that the Trscv output power is
         higher than the threshold value
        written in the Trscv EEPROM <Condtype>
        LINE_TX_POWER_HIGH_WARNING <Probcause>
        transmitterFailure (56) <Alarmtype>
        equipmentAlarm (5) <Polarity> (2)
        "
	::= { pm20002maAlmlineNetworkLaneAlarmWarning1Entry 12 }


pm20002maAlmLineTxPowerLowWarningPortn OBJECT-TYPE
	SYNTAX  EkiOnOff
	MAX-ACCESS read-only
	STATUS current
	DESCRIPTION
        "
        Line Trscv Tx Power Low Warning
        :This OID indicates that the Trscv
        output power is lower than the
         threshold value written in the
        Trscv EEPROM <Help> Warning indicating
        that the Trscv output power is
         lower than the threshold value
        written in the Trscv EEPROM <Condtype>
        LINE_TX_POWER_LOW_WARNING <Probcause>
        transmitterFailure (56) <Alarmtype>
        equipmentAlarm (5) <Polarity> (2)
        "
	::= { pm20002maAlmlineNetworkLaneAlarmWarning1Entry 11 }


pm20002maAlmLineTxPowerLowAlarmPortn OBJECT-TYPE
	SYNTAX  EkiOnOff
	MAX-ACCESS read-only
	STATUS current
	DESCRIPTION
        "
        Line Trscv Tx Power Low Alarm
         :This OID indicates that the Trscv
        output power is lower than the
         threshold value written in the
        Trscv EEPROM <Help> Alarm indicating
        that the Trscv output power is
         lower than the threshold value
        written in the Trscv EEPROM <Condtype>
        LINE_TX_POWER_LOW_ALARM <Probcause>
        transmitterFailure (56) <Alarmtype>
        equipmentAlarm (5) <Polarity> (2)
        "
	::= { pm20002maAlmlineNetworkLaneAlarmWarning1Entry 10 }


pm20002maAlmLineLaserTempHighAlarmPortn OBJECT-TYPE
	SYNTAX  EkiOnOff
	MAX-ACCESS read-only
	STATUS current
	DESCRIPTION
        "
        Line Trscv Tx Laser Temp High
         Alarm :This OID indicates that
        the Trscv Tx Laser Temperature
         is higher than the threshold value
        written in the Trscv EEPROM <Help>
        Alarm indicating that the Trscv
        Tx Laser Temperature is higher
         than the threshold value written
        in the Trscv EEPROM <Condtype>
         LINE_LASER_TEMP_HIGH_ALARM <Probcause>
        temperatureUnacceptable (51) <Alarmtype>
        equipmentAlarm (5) <Polarity> (2)
        "
	::= { pm20002maAlmlineNetworkLaneAlarmWarning1Entry 9 }


pm20002maAlmLineLaserTempHighWarningPortn OBJECT-TYPE
	SYNTAX  EkiOnOff
	MAX-ACCESS read-only
	STATUS current
	DESCRIPTION
        "
        Line Trscv Tx Laser Temp High
         Warning :This OID indicates that
        the Trscv Tx Laser Temperature
         is higher than the threshold value
        written in the Trscv EEPROM <Help>
        Warning indicating that the Trscv
        Tx Laser Temperature is higher
         than the threshold value written
        in the Trscv EEPROM <Condtype>
         LINE_LASER_TEMP_HIGH_WARNING <Probcause>
        temperatureUnacceptable (51) <Alarmtype>
        equipmentAlarm (5) <Polarity> (2)
        "
	::= { pm20002maAlmlineNetworkLaneAlarmWarning1Entry 8 }


pm20002maAlmLineLaserTempLowWarningPortn OBJECT-TYPE
	SYNTAX  EkiOnOff
	MAX-ACCESS read-only
	STATUS current
	DESCRIPTION
        "
        Line Trscv Tx Laser Temp Low Warning
        :This OID indicates that the Trscv
        Tx Laser Temperature is lower than
        the threshold value written in
         the Trscv EEPROM <Help> Warning
        indicating that the Trscv Tx Laser
        Temperature is lower than the threshold
        value written in the Trscv EEPROM
        <Condtype> LINE_LASER_TEMP_LOW_WARNING
        <Probcause> temperatureUnacceptable
        (51) <Alarmtype> equipmentAlarm
        (5) <Polarity> (2)
        "
	::= { pm20002maAlmlineNetworkLaneAlarmWarning1Entry 7 }


pm20002maAlmLineLaserTempLowAlarmPortn OBJECT-TYPE
	SYNTAX  EkiOnOff
	MAX-ACCESS read-only
	STATUS current
	DESCRIPTION
        "
        Line Trscv Tx Laser Temp Low Alarm
        :This OID indicates that the Trscv
        Tx Laser Temperature is lower than
        the threshold value written in
         the Trscv EEPROM <Help> Alarm
         indicating that the Trscv Tx Laser
        Temperature is lower than the threshold
        value written in the Trscv EEPROM
        <Condtype> LINE_LASER_TEMP_LOW_ALARM
        <Probcause> temperatureUnacceptable
        (51) <Alarmtype> equipmentAlarm
        (5) <Polarity> (2)
        "
	::= { pm20002maAlmlineNetworkLaneAlarmWarning1Entry 6 }


pm20002maAlmLineRxPowerHighAlarmPortn OBJECT-TYPE
	SYNTAX  EkiOnOff
	MAX-ACCESS read-only
	STATUS current
	DESCRIPTION
        "
        Line Trscv Rx Power High Alarm
        :This OID indicates that the Trscv
        input power is higher than the
         threshold value written in the
        Trscv EEPROM <Help> Alarm indicating
        that the Trscv input power is higher
        than the threshold value written
        in the Trscv EEPROM <Condtype>
         LINE_RX_POWER_HIGH_ALARM <Probcause>
        receiveFailure (41) <Alarmtype>
        equipmentAlarm (5) <Polarity> (2)
        "
	::= { pm20002maAlmlineNetworkLaneAlarmWarning1Entry 5 }


pm20002maAlmLineRxPowerHighWarningPortn OBJECT-TYPE
	SYNTAX  EkiOnOff
	MAX-ACCESS read-only
	STATUS current
	DESCRIPTION
        "
        Line Trscv Rx Power High Warning
        :This OID indicates that the Trscv
        input power is higher than the
         threshold value written in the
        Trscv EEPROM <Help> Warning indicating
        that the Trscv input power is higher
        than the threshold value written
        in the Trscv EEPROM <Condtype>
         LINE_RX_POWER_HIGH_WARNING <Probcause>
        receiveFailure (41) <Alarmtype>
        equipmentAlarm (5) <Polarity> (2)
        "
	::= { pm20002maAlmlineNetworkLaneAlarmWarning1Entry 4 }


pm20002maAlmLineRxPowerLowWarningPortn OBJECT-TYPE
	SYNTAX  EkiOnOff
	MAX-ACCESS read-only
	STATUS current
	DESCRIPTION
        "
        Line Trscv Rx Power Low Warning
        :This OID indicates that the Trscv
        input power is lower than the threshold
        value written in the Trscv EEPROM
        <Help> Warning indicating that
         the Trscv input power is lower
        than the threshold value written
        in the Trscv EEPROM <Condtype>
         LINE_RX_POWER_LOW_WARNING <Probcause>
        receiveFailure (41) <Alarmtype>
        equipmentAlarm (5) <Polarity> (2)
        "
	::= { pm20002maAlmlineNetworkLaneAlarmWarning1Entry 3 }


pm20002maAlmLineRxPowerLowAlarmPortn OBJECT-TYPE
	SYNTAX  EkiOnOff
	MAX-ACCESS read-only
	STATUS current
	DESCRIPTION
        "
        Line Trscv Rx Power Low Alarm
         :This OID indicates that the Trscv
        input power is lower than the threshold
        value written in the Trscv EEPROM
        <Help> Alarm indicating that the
        Trscv input power is lower than
        the threshold value written in
         the Trscv EEPROM <Condtype> LINE_RX_POWER_LOW_ALARM
        <Probcause> receiveFailure (41)
        <Alarmtype> equipmentAlarm (5)
         <Polarity> (2)
        "
	::= { pm20002maAlmlineNetworkLaneAlarmWarning1Entry 2 }


--- *********************************************************
---     TABLE for the pm20002maAlmlineNetworkLaneAlarmWarning2 articles
--- *********************************************************

pm20002maAlmlineNetworkLaneAlarmWarning2Table OBJECT-TYPE
	SYNTAX  SEQUENCE OF Pm20002maAlmlineNetworkLaneAlarmWarning2Entry
	MAX-ACCESS not-accessible
	STATUS current
	DESCRIPTION
        "
        List of pm20002maAlmlineNetworkLaneAlarmWarning2
        Article
        "
	::= { pm20002maAlmLineNurg 188 }


pm20002maAlmlineNetworkLaneAlarmWarning2Entry OBJECT-TYPE
	SYNTAX Pm20002maAlmlineNetworkLaneAlarmWarning2Entry
	MAX-ACCESS not-accessible
	STATUS current
	DESCRIPTION
        "
        Row definition for the pm20002maAlmlineNetworkLaneAlarmWarning2
        table
        "
	INDEX   { pm20002maAlmlineNetworkLaneAlarmWarning2Index }
	::= { pm20002maAlmlineNetworkLaneAlarmWarning2Table 1 }


Pm20002maAlmlineNetworkLaneAlarmWarning2Entry ::=
	SEQUENCE {
	pm20002maAlmlineNetworkLaneAlarmWarning2Index
		INTEGER,
	pm20002maAlmRxLaserBiasHighAlarmPortn
		EkiOnOff,
	pm20002maAlmRxLaserBiasHighWarningPortn
		EkiOnOff,
	pm20002maAlmRxLaserBiasLowWarningPortn
		EkiOnOff,
	pm20002maAlmRxLaserBiasLowAlarmPortn
		EkiOnOff,
	pm20002maAlmRxLaserOutputHighAlarmPortn
		EkiOnOff,
	pm20002maAlmRxLaserOutputHighWarningPortn
		EkiOnOff,
	pm20002maAlmRxLaserOutputLowWarningPortn
		EkiOnOff,
	pm20002maAlmRxLaserOutputLowAlarmPortn
		EkiOnOff,
	pm20002maAlmRxLaserTempHighAlarmPortn
		EkiOnOff,
	pm20002maAlmRxLaserTempHighWarningPortn
		EkiOnOff,
	pm20002maAlmRxLaserTempLowWarningPortn
		EkiOnOff,
	pm20002maAlmRxLaserTempLowAlarmPortn
		EkiOnOff,
	pm20002maAlmTxModulatorBiasHighAlarmPortn
		EkiOnOff,
	pm20002maAlmTxModulatorBiasHighWarningPortn
		EkiOnOff,
	pm20002maAlmTxModulatorBiasLowWarningPortn
		EkiOnOff,
	pm20002maAlmTxModulatorBiasLowAlarmPortn
		EkiOnOff
	}


pm20002maAlmlineNetworkLaneAlarmWarning2Index OBJECT-TYPE
	SYNTAX  INTEGER(0..128)
	MAX-ACCESS  read-only
	STATUS current
	DESCRIPTION
        "
        Index definition for the pm20002maAlmlineNetworkLaneAlarmWarning2
        table
        "
	::= { pm20002maAlmlineNetworkLaneAlarmWarning2Entry 1 }


pm20002maAlmRxLaserBiasHighAlarmPortn OBJECT-TYPE
	SYNTAX  EkiOnOff
	MAX-ACCESS read-only
	STATUS current
	DESCRIPTION
        "
        Line Trscv Rx Bias High Alarm
         :This OID indicates that the Trscv
        Rx laser bias current is higher
        than the threshold value written
        in the Trscv EEPROM <Help> Alarm
        indicating that the Trscv Rx laser
        bias current is higher than the
        threshold value written in the
         Trscv EEPROM <Condtype> RX_LASER_BIAS_HIGH_ALARM
        <Probcause> receiveFailure (41)
        <Alarmtype> equipmentAlarm (5)
         <Polarity> (2)
        "
	::= { pm20002maAlmlineNetworkLaneAlarmWarning2Entry 17 }


pm20002maAlmRxLaserBiasHighWarningPortn OBJECT-TYPE
	SYNTAX  EkiOnOff
	MAX-ACCESS read-only
	STATUS current
	DESCRIPTION
        "
        Line Trscv Rx Bias High Warning
        :This OID indicates that the Trscv
        Rx laser bias current is higher
        than the threshold value written
        in the Trscv EEPROM <Help> Warning
        indicating that the Trscv Rx laser
        bias current is higher than the
        threshold value written in the
         Trscv EEPROM <Condtype> RX_LASER_BIAS_HIGH_WARNING
        <Probcause> receiveFailure (41)
        <Alarmtype> equipmentAlarm (5)
         <Polarity> (2)
        "
	::= { pm20002maAlmlineNetworkLaneAlarmWarning2Entry 16 }


pm20002maAlmRxLaserBiasLowWarningPortn OBJECT-TYPE
	SYNTAX  EkiOnOff
	MAX-ACCESS read-only
	STATUS current
	DESCRIPTION
        "
        Line Trscv Rx Bias Low Warning
        :This OID indicates that the Trscv
        Rx laser bias current is lower
         than the threshold value written
        in the Trscv EEPROM <Help> Warning
        indicating that the Trscv Rx laser
        bias current is lower than the
         threshold value written in the
        Trscv EEPROM <Condtype> RX_LASER_BIAS_LOW_WARNING
        <Probcause> receiveFailure (41)
        <Alarmtype> equipmentAlarm (5)
         <Polarity> (2)
        "
	::= { pm20002maAlmlineNetworkLaneAlarmWarning2Entry 15 }


pm20002maAlmRxLaserBiasLowAlarmPortn OBJECT-TYPE
	SYNTAX  EkiOnOff
	MAX-ACCESS read-only
	STATUS current
	DESCRIPTION
        "
        Line Trscv Rx Bias Low Alarm :This
        OID indicates that the Trscv Rx
        laser bias current is lower than
        the threshold value written in
         the Trscv EEPROM <Help> Alarm
         indicating that the Trscv Rx laser
        bias current is lower than the
         threshold value written in the
        Trscv EEPROM <Condtype> RX_LASER_BIAS_LOW_ALARM
        <Probcause> receiveFailure (41)
        <Alarmtype> equipmentAlarm (5)
         <Polarity> (2)
        "
	::= { pm20002maAlmlineNetworkLaneAlarmWarning2Entry 14 }


pm20002maAlmRxLaserOutputHighAlarmPortn OBJECT-TYPE
	SYNTAX  EkiOnOff
	MAX-ACCESS read-only
	STATUS current
	DESCRIPTION
        "
        Line Trscv Rx Output Power High
        Alarm :This OID indicates that
         the Trscv Rx output power is higher
        than the threshold value written
        in the Trscv EEPROM <Help> Alarm
        indicating that the Trscv Rx output
        power is higher than the threshold
        value written in the Trscv EEPROM
        <Condtype> RX_LASER_OUTPUT_HIGH_ALARM
        <Probcause> receiveFailure (41)
        <Alarmtype> equipmentAlarm (5)
         <Polarity> (2)
        "
	::= { pm20002maAlmlineNetworkLaneAlarmWarning2Entry 13 }


pm20002maAlmRxLaserOutputHighWarningPortn OBJECT-TYPE
	SYNTAX  EkiOnOff
	MAX-ACCESS read-only
	STATUS current
	DESCRIPTION
        "
        Line Trscv Rx Output Power High
        Warning :This OID indicates that
        the Trscv Rx output power is higher
        than the threshold value written
        in the Trscv EEPROM <Help> Warning
        indicating that the Trscv Rx output
        power is higher than the threshold
        value written in the Trscv EEPROM
        <Condtype> RX_LASER_OUTPUT_HIGH_WARNING
        <Probcause> receiveFailure (41)
        <Alarmtype> equipmentAlarm (5)
         <Polarity> (2)
        "
	::= { pm20002maAlmlineNetworkLaneAlarmWarning2Entry 12 }


pm20002maAlmRxLaserOutputLowWarningPortn OBJECT-TYPE
	SYNTAX  EkiOnOff
	MAX-ACCESS read-only
	STATUS current
	DESCRIPTION
        "
        Line Trscv Rx Output Power Low
        Warning :This OID indicates that
        the Trscv Rx output power is lower
        than the threshold value written
        in the Trscv EEPROM <Help> Warning
        indicating that the Trscv Rx output
        power is lower than the threshold
        value written in the Trscv EEPROM
        <Condtype> RX_LASER_OUTPUT_LOW_WARNING
        <Probcause> receiveFailure (41)
        <Alarmtype> equipmentAlarm (5)
         <Polarity> (2)
        "
	::= { pm20002maAlmlineNetworkLaneAlarmWarning2Entry 11 }


pm20002maAlmRxLaserOutputLowAlarmPortn OBJECT-TYPE
	SYNTAX  EkiOnOff
	MAX-ACCESS read-only
	STATUS current
	DESCRIPTION
        "
        Line Trscv Rx Output Power Low
        Alarm :This OID indicates that
         the Trscv Rx output power is lower
        than the threshold value written
        in the Trscv EEPROM <Help> Alarm
        indicating that the Trscv Rx output
        power is lower than the threshold
        value written in the Trscv EEPROM
        <Condtype> RX_LASER_OUTPUT_LOW_ALARM
        <Probcause> receiveFailure (41)
        <Alarmtype> equipmentAlarm (5)
         <Polarity> (2)
        "
	::= { pm20002maAlmlineNetworkLaneAlarmWarning2Entry 10 }


pm20002maAlmRxLaserTempHighAlarmPortn OBJECT-TYPE
	SYNTAX  EkiOnOff
	MAX-ACCESS read-only
	STATUS current
	DESCRIPTION
        "
        Line Trscv Rx Laser Temp High
         Alarm :This OID indicates that
        the Trscv Rx Laser Temperature
         is higher than the threshold value
        written in the Trscv EEPROM <Help>
        Alarm indicating that the Trscv
        Rx Laser Temperature is higher
         than the threshold value written
        in the Trscv EEPROM <Condtype>
         RX_LASER_TEMP_HIGH_ALARM <Probcause>
        temperatureUnacceptable (51) <Alarmtype>
        equipmentAlarm (5) <Polarity> (2)
        "
	::= { pm20002maAlmlineNetworkLaneAlarmWarning2Entry 9 }


pm20002maAlmRxLaserTempHighWarningPortn OBJECT-TYPE
	SYNTAX  EkiOnOff
	MAX-ACCESS read-only
	STATUS current
	DESCRIPTION
        "
        Line Trscv Rx Laser Temp High
         Warning :This OID indicates that
        the Trscv Rx Laser Temperature
         is higher than the threshold value
        written in the Trscv EEPROM <Help>
        Warning indicating that the Trscv
        Rx Laser Temperature is higher
         than the threshold value written
        in the Trscv EEPROM <Condtype>
         RX_LASER_TEMP_HIGH_WARNING <Probcause>
        temperatureUnacceptable (51) <Alarmtype>
        equipmentAlarm (5) <Polarity> (2)
        "
	::= { pm20002maAlmlineNetworkLaneAlarmWarning2Entry 8 }


pm20002maAlmRxLaserTempLowWarningPortn OBJECT-TYPE
	SYNTAX  EkiOnOff
	MAX-ACCESS read-only
	STATUS current
	DESCRIPTION
        "
        Line Trscv Rx Laser Temp Low Warning
        :This OID indicates that the Trscv
        Rx Laser Temperature is lower than
        the threshold value written in
         the Trscv EEPROM <Help> Warning
        indicating that the Trscv Rx Laser
        Temperature is lower than the threshold
        value written in the Trscv EEPROM
        <Condtype> RX_LASER_TEMP_LOW_WARNING
        <Probcause> temperatureUnacceptable
        (51) <Alarmtype> equipmentAlarm
        (5) <Polarity> (2)
        "
	::= { pm20002maAlmlineNetworkLaneAlarmWarning2Entry 7 }


pm20002maAlmRxLaserTempLowAlarmPortn OBJECT-TYPE
	SYNTAX  EkiOnOff
	MAX-ACCESS read-only
	STATUS current
	DESCRIPTION
        "
        Line Trscv Rx Laser Temp Low Alarm
        :This OID indicates that the Trscv
        Rx Laser Temperature is lower than
        the threshold value written in
         the Trscv EEPROM <Help> Alarm
         indicating that the Trscv Rx Laser
        Temperature is lower than the threshold
        value written in the Trscv EEPROM
        <Condtype> RX_LASER_TEMP_LOW_ALARM
        <Probcause> temperatureUnacceptable
        (51) <Alarmtype> equipmentAlarm
        (5) <Polarity> (2)
        "
	::= { pm20002maAlmlineNetworkLaneAlarmWarning2Entry 6 }


pm20002maAlmTxModulatorBiasHighAlarmPortn OBJECT-TYPE
	SYNTAX  EkiOnOff
	MAX-ACCESS read-only
	STATUS current
	DESCRIPTION
        "
        Line Trscv Tx Modulator Bias High
        Alarm :This OID indicates that
         the Trscv Tx modulator bias current
        is higher than the threshold value
        written in the Trscv EEPROM <Help>
        Alarm indicating that the Trscv
        Tx modulator bias current is higher
        than the threshold value written
        in the Trscv EEPROM <Condtype>
         TX_MODULATOR_BIAS_HIGH_ALARM <Probcause>
        transmitterFailure (56) <Alarmtype>
        equipmentAlarm (5) <Polarity> (2)
        "
	::= { pm20002maAlmlineNetworkLaneAlarmWarning2Entry 5 }


pm20002maAlmTxModulatorBiasHighWarningPortn OBJECT-TYPE
	SYNTAX  EkiOnOff
	MAX-ACCESS read-only
	STATUS current
	DESCRIPTION
        "
        Line Trscv Tx Modulator Bias High
        Warning :This OID indicates that
        the Trscv Tx modulator bias current
        is higher than the threshold value
        written in the Trscv EEPROM <Help>
        Warning indicating that the Trscv
        Tx modulator bias current is higher
        than the threshold value written
        in the Trscv EEPROM <Condtype>
         TX_MODULATOR_BIAS_HIGH_WARNING
        <Probcause> transmitterFailure
         (56) <Alarmtype> equipmentAlarm
        (5) <Polarity> (2)
        "
	::= { pm20002maAlmlineNetworkLaneAlarmWarning2Entry 4 }


pm20002maAlmTxModulatorBiasLowWarningPortn OBJECT-TYPE
	SYNTAX  EkiOnOff
	MAX-ACCESS read-only
	STATUS current
	DESCRIPTION
        "
        Line Trscv Tx Modulator Bias Low
        Warning :This OID indicates that
        the Trscv Tx modulator bias current
        is lower than the threshold value
        written in the Trscv EEPROM <Help>
        Warning indicating that the Trscv
        Tx modulator bias current is lower
        than the threshold value written
        in the Trscv EEPROM <Condtype>
         TX_MODULATOR_BIAS_LOW_WARNING
         <Probcause> transmitterFailure
        (56) <Alarmtype> equipmentAlarm
        (5) <Polarity> (2)
        "
	::= { pm20002maAlmlineNetworkLaneAlarmWarning2Entry 3 }


pm20002maAlmTxModulatorBiasLowAlarmPortn OBJECT-TYPE
	SYNTAX  EkiOnOff
	MAX-ACCESS read-only
	STATUS current
	DESCRIPTION
        "
        Line Trscv Tx Modulator Bias Low
        Alarm :This OID indicates that
         the Trscv Tx modulator bias current
        is lower than the threshold value
        written in the Trscv EEPROM <Help>
        Alarm indicating that the Trscv
        Tx modulator bias current is lower
        than the threshold value written
        in the Trscv EEPROM <Condtype>
         TX_MODULATOR_BIAS_LOW_ALARM <Probcause>
        transmitterFailure (56) <Alarmtype>
        equipmentAlarm (5) <Polarity> (2)
        "
	::= { pm20002maAlmlineNetworkLaneAlarmWarning2Entry 2 }


--- *********************************************************
---     TABLE for the pm20002maAlmlineNetworkLaneFault articles
--- *********************************************************

pm20002maAlmlineNetworkLaneFaultTable OBJECT-TYPE
	SYNTAX  SEQUENCE OF Pm20002maAlmlineNetworkLaneFaultEntry
	MAX-ACCESS not-accessible
	STATUS current
	DESCRIPTION
        "
        List of pm20002maAlmlineNetworkLaneFault
        Article
        "
	::= { pm20002maAlmLineUrg 192 }


pm20002maAlmlineNetworkLaneFaultEntry OBJECT-TYPE
	SYNTAX Pm20002maAlmlineNetworkLaneFaultEntry
	MAX-ACCESS not-accessible
	STATUS current
	DESCRIPTION
        "
        Row definition for the pm20002maAlmlineNetworkLaneFault
        table
        "
	INDEX   { pm20002maAlmlineNetworkLaneFaultIndex }
	::= { pm20002maAlmlineNetworkLaneFaultTable 1 }


Pm20002maAlmlineNetworkLaneFaultEntry ::=
	SEQUENCE {
	pm20002maAlmlineNetworkLaneFaultIndex
		INTEGER,
	pm20002maAlmLineLaneTecFaultPortn
		EkiOnOff,
	pm20002maAlmLineLaneWavelengthUnlockedPortn
		EkiOnOff,
	pm20002maAlmLineLaneApdPowerSupplyPortn
		EkiOnOff,
	pm20002maAlmLineLaneTxLosfPortn
		EkiOnOff,
	pm20002maAlmLineLaneTxLolPortn
		EkiOnOff,
	pm20002maAlmLineLaneRxLosPortn
		EkiOnOff,
	pm20002maAlmLineLaneRxLolPortn
		EkiOnOff,
	pm20002maAlmLineLaneRxFifoErrorPortn
		EkiOnOff,
	pm20002maAlmLineLaneRxTecFaultPortn
		EkiOnOff
	}


pm20002maAlmlineNetworkLaneFaultIndex OBJECT-TYPE
	SYNTAX  INTEGER(0..128)
	MAX-ACCESS  read-only
	STATUS current
	DESCRIPTION
        "
        Index definition for the pm20002maAlmlineNetworkLaneFault
        table
        "
	::= { pm20002maAlmlineNetworkLaneFaultEntry 1 }


pm20002maAlmLineLaneTecFaultPortn OBJECT-TYPE
	SYNTAX  EkiOnOff
	MAX-ACCESS read-only
	STATUS current
	DESCRIPTION
        "
        Line Network Lane TEC Fault :This
        OID indicates a Tx TEC Fault on
        the Line Trscv Network Lane <Help>
        Alarm indicating a Tx TEC Fault
        on the Line Trscv Network Lane
         <Condtype> LINE_LANE_TEC_FAULT
        <Probcause> transmitterFailure
         (56) <Alarmtype> equipmentAlarm
        (5) <Polarity> (2)
        "
	::= { pm20002maAlmlineNetworkLaneFaultEntry 17 }


pm20002maAlmLineLaneWavelengthUnlockedPortn OBJECT-TYPE
	SYNTAX  EkiOnOff
	MAX-ACCESS read-only
	STATUS current
	DESCRIPTION
        "
        Line Network Lane Wavelength Unlock
        :This OID indicates a Wavelength
        unlock on the Line Trscv Network
        Lane <Help> Alarm indicating a
         Wavelength unlock on the Line
         Trscv Network Lane <Condtype>
         LINE_LANE_WAVELENGTH_UNLOCKED
         <Probcause> transmitterFailure
        (56) <Alarmtype> equipmentAlarm
        (5) <Polarity> (2)
        "
	::= { pm20002maAlmlineNetworkLaneFaultEntry 16 }


pm20002maAlmLineLaneApdPowerSupplyPortn OBJECT-TYPE
	SYNTAX  EkiOnOff
	MAX-ACCESS read-only
	STATUS current
	DESCRIPTION
        "
        Line Network Lane APD Power Supply
        :This OID indicates an APD Power
        supply failure on the Line Trscv
        Network Lane <Help> Alarm indicating
        an APD Power supply failure on
         the Line Trscv Network Lane <Condtype>
        LINE_LANE_APD_POWER_SUPPLY <Probcause>
        transmitterFailure (56) <Alarmtype>
        equipmentAlarm (5) <Polarity> (2)
        "
	::= { pm20002maAlmlineNetworkLaneFaultEntry 15 }


pm20002maAlmLineLaneTxLosfPortn OBJECT-TYPE
	SYNTAX  EkiOnOff
	MAX-ACCESS read-only
	STATUS current
	DESCRIPTION
        "
        Line Network Lane Tx Loss Of Signal
        Functionality :This OID indicates
        a Tx Loss of Signal Functionality
        on the Line Trscv Network Lane
         <Help> Alarm indicating a Tx Loss
        of Signal Functionality on the
         Line Trscv Network Lane <Condtype>
        LINE_LANE_TX_LOSF <Probcause> transmitterFailure
        (56) <Alarmtype> equipmentAlarm
        (5) <Polarity> (2)
        "
	::= { pm20002maAlmlineNetworkLaneFaultEntry 9 }


pm20002maAlmLineLaneTxLolPortn OBJECT-TYPE
	SYNTAX  EkiOnOff
	MAX-ACCESS read-only
	STATUS current
	DESCRIPTION
        "
        Line Network Lane Tx Loss Of Lock
        :This OID indicates a Tx Loss of
        Lock on the Line Trscv Network
         Lane <Help> Alarm indicating a
        Tx Loss of Lock on the Line Trscv
        Network Lane <Condtype> LINE_LANE_TX_LOL
        <Probcause> transmitterFailure
         (56) <Alarmtype> equipmentAlarm
        (5) <Polarity> (2)
        "
	::= { pm20002maAlmlineNetworkLaneFaultEntry 8 }


pm20002maAlmLineLaneRxLosPortn OBJECT-TYPE
	SYNTAX  EkiOnOff
	MAX-ACCESS read-only
	STATUS current
	DESCRIPTION
        "
        Line Network Lane Rx Loss Of Signal
        :This OID indicates a Rx Loss of
        Signal on the Line Trscv Network
        Lane <Help> Alarm indicating a
         Rx Loss of Signal on the Line
         Trscv Network Lane <Condtype>
         LINE_LANE_RX_LOS <Probcause> receiveFailure
        (41) <Alarmtype> physicalViolation
        (9) <Polarity> (2)
        "
	::= { pm20002maAlmlineNetworkLaneFaultEntry 6 }


pm20002maAlmLineLaneRxLolPortn OBJECT-TYPE
	SYNTAX  EkiOnOff
	MAX-ACCESS read-only
	STATUS current
	DESCRIPTION
        "
        Line Network Lane Rx Loss Of Lock
        :This OID indicates a Rx Loss of
        Lock on the Line Trscv Network
         Lane <Help> Alarm indicating a
        Rx Loss of Lock on the Line Trscv
        Network Lane <Condtype> LINE_LANE_RX_LOL
        <Probcause> receiverFailure (42)
        <Alarmtype> equipmentAlarm (5)
         <Polarity> (2)
        "
	::= { pm20002maAlmlineNetworkLaneFaultEntry 5 }


pm20002maAlmLineLaneRxFifoErrorPortn OBJECT-TYPE
	SYNTAX  EkiOnOff
	MAX-ACCESS read-only
	STATUS current
	DESCRIPTION
        "
        Line Network Lane Rx FIFO Error
        :This OID indicates a Rx FIFO Error
        on the Line Trscv Network Lane
         <Help> Alarm indicating a Rx FIFO
        Error on the Line Trscv Network
        Lane <Condtype> LINE_LANE_RX_FIFO_ERROR
        <Probcause> receiverFailure (42)
        <Alarmtype> equipmentAlarm (5)
         <Polarity> (2)
        "
	::= { pm20002maAlmlineNetworkLaneFaultEntry 4 }


pm20002maAlmLineLaneRxTecFaultPortn OBJECT-TYPE
	SYNTAX  EkiOnOff
	MAX-ACCESS read-only
	STATUS current
	DESCRIPTION
        "
        Line Network Lane Rx TEC Fault
        :This OID indicates a Rx TEC Fault
        on the Line Trscv Network Lane
         <Help> Alarm indicating a Rx TEC
        Fault on the Line Trscv Network
        Lane <Condtype> LINE_LANE_RX_TEC_FAULT
        <Probcause> receiverFailure (42)
        <Alarmtype> equipmentAlarm (5)
         <Polarity> (2)
        "
	::= { pm20002maAlmlineNetworkLaneFaultEntry 3 }


--- *********************************************************
---     TABLE for the pm20002maAlmlineHostLaneFault articles
--- *********************************************************

pm20002maAlmlineHostLaneFaultTable OBJECT-TYPE
	SYNTAX  SEQUENCE OF Pm20002maAlmlineHostLaneFaultEntry
	MAX-ACCESS not-accessible
	STATUS current
	DESCRIPTION
        "
        List of pm20002maAlmlineHostLaneFault
        Article
        "
	::= { pm20002maAlmLineUrg 196 }


pm20002maAlmlineHostLaneFaultEntry OBJECT-TYPE
	SYNTAX Pm20002maAlmlineHostLaneFaultEntry
	MAX-ACCESS not-accessible
	STATUS current
	DESCRIPTION
        "
        Row definition for the pm20002maAlmlineHostLaneFault
        table
        "
	INDEX   { pm20002maAlmlineHostLaneFaultIndex }
	::= { pm20002maAlmlineHostLaneFaultTable 1 }


Pm20002maAlmlineHostLaneFaultEntry ::=
	SEQUENCE {
	pm20002maAlmlineHostLaneFaultIndex
		INTEGER,
	pm20002maAlmLineLaneTxFifoErrorPortn
		EkiOnOff,
	pm20002maAlmLineTxHostLolPortn
		EkiOnOff,
	pm20002maAlmLineSmIaeDetectedPortn
		EkiOnOff,
	pm20002maAlmLineSmIaeInsertedPortn
		EkiOnOff,
	pm20002maAlmLineSmBdiDetectedPortn
		EkiOnOff,
	pm20002maAlmLineSmBdiInsertedPortn
		EkiOnOff,
	pm20002maAlmLineLossOfFramePortn
		EkiOnOff,
	pm20002maAlmLineInputLossOfSignalPortn
		EkiOnOff
	}


pm20002maAlmlineHostLaneFaultIndex OBJECT-TYPE
	SYNTAX  INTEGER(0..128)
	MAX-ACCESS  read-only
	STATUS current
	DESCRIPTION
        "
        Index definition for the pm20002maAlmlineHostLaneFault
        table
        "
	::= { pm20002maAlmlineHostLaneFaultEntry 1 }


pm20002maAlmLineLaneTxFifoErrorPortn OBJECT-TYPE
	SYNTAX  EkiOnOff
	MAX-ACCESS read-only
	STATUS current
	DESCRIPTION
        "
        Line Host Lane Tx FIFO Error :This
        OID indicates a Tx FIFO Error on
        the Line Trscv Host Lane <Help>
        Alarm indicating a Tx FIFO Error
        on the Line Trscv Host Lane <Condtype>
        LINE_LANE_TX_FIFO_ERROR <Probcause>
        receiverFailure (42) <Alarmtype>
        equipmentAlarm (5) <Polarity> (2)
        "
	::= { pm20002maAlmlineHostLaneFaultEntry 11 }


pm20002maAlmLineTxHostLolPortn OBJECT-TYPE
	SYNTAX  EkiOnOff
	MAX-ACCESS read-only
	STATUS current
	DESCRIPTION
        "
        Line Host Lane Tx Loss Of Lock
        :This OID indicates a Tx Loss of
        Lock on the Line Trscv Host Lane
        <Help> Alarm indicating a Tx Loss
        of Lock on the Line Trscv Host
         Lane <Condtype> LINE_TX_HOST_LOL
        <Probcause> receiverFailure (42)
        <Alarmtype> equipmentAlarm (5)
         <Polarity> (2)
        "
	::= { pm20002maAlmlineHostLaneFaultEntry 10 }


pm20002maAlmLineSmIaeDetectedPortn OBJECT-TYPE
	SYNTAX  EkiOnOff
	MAX-ACCESS read-only
	STATUS current
	DESCRIPTION
        "
        Line SM IAE Detected :This OID
        indicates a SM Incoming Alignment
        Error is detected on the incoming
        Line signal <Help> Alarm indicating
        a SM Incoming Alignment Error is
        detected on the incoming Line signal
        <Condtype> LINE_SM_IAE_DETECTED
        <Probcause> receiveFailure (41)
        <Alarmtype> integrityViolation
         (7) <Polarity> (2)
        "
	::= { pm20002maAlmlineHostLaneFaultEntry 7 }


pm20002maAlmLineSmIaeInsertedPortn OBJECT-TYPE
	SYNTAX  EkiOnOff
	MAX-ACCESS read-only
	STATUS current
	DESCRIPTION
        "
        Line SM IAE Inserted :This OID
        indicates a SM Incoming Alignment
        Error is inserted on the outgoing
        Line signal <Help> Status indicating
        a SM Incoming Alignment Error is
        inserted on the outgoing Line signal
        <Condtype> LINE_SM_IAE_INSERTED
        <Probcause> informationalStatus(1000)
        <Alarmtype> other (1) <Polarity>
        (2)
        "
	::= { pm20002maAlmlineHostLaneFaultEntry 6 }


pm20002maAlmLineSmBdiDetectedPortn OBJECT-TYPE
	SYNTAX  EkiOnOff
	MAX-ACCESS read-only
	STATUS current
	DESCRIPTION
        "
        Line SM BDI Detected :This OID
        indicates a SM Backward Defect
         Indication is detected on the
         incoming Line signal <Help> Alarm
        indicating a SM Backward Defect
        Indication is detected on the incoming
        Line signal <Condtype> LINE_SM_BDI_DETECTED
        <Probcause> receiveFailure (41)
        <Alarmtype> integrityViolation
         (7) <Polarity> (2)
        "
	::= { pm20002maAlmlineHostLaneFaultEntry 5 }


pm20002maAlmLineSmBdiInsertedPortn OBJECT-TYPE
	SYNTAX  EkiOnOff
	MAX-ACCESS read-only
	STATUS current
	DESCRIPTION
        "
        Line SM BDI Inserted :This OID
        indicates a SM Backward Defect
         Indication is inserted on the
         outgoing Line signal <Help> Status
        indicating a SM Backward Defect
        Indication is inserted on the outgoing
        Line signal <Condtype> LINE_SM_BDI_INSERTED
        <Probcause> informationalStatus(1000)
        <Alarmtype> other (1) <Polarity>
        (2)
        "
	::= { pm20002maAlmlineHostLaneFaultEntry 4 }


pm20002maAlmLineLossOfFramePortn OBJECT-TYPE
	SYNTAX  EkiOnOff
	MAX-ACCESS read-only
	STATUS current
	DESCRIPTION
        "
        Line Loss Of Frame :This OID indicates
        the module is not aligned with
         the incoming Line signal <Help>
        Alarm indicating the module is
         not aligned with the incoming
         Line signal <Condtype> LINE_LOSS_OF_FRAME
        <Probcause> receiveFailure (41)
        <Alarmtype> integrityViolation
         (7) <Polarity> (2)
        "
	::= { pm20002maAlmlineHostLaneFaultEntry 3 }


pm20002maAlmLineInputLossOfSignalPortn OBJECT-TYPE
	SYNTAX  EkiOnOff
	MAX-ACCESS read-only
	STATUS current
	DESCRIPTION
        "
        Line Input Loss Of Signal :This
        OID indicates a Loss of Signal
         is detected on the Line Trscv
         <Help> Alarm indicating a Loss
        of Signal is detected on the Line
        Trscv <Condtype> LINE_INPUT_LOSS_OF_SIGNAL
        <Probcause> receiveFailure (41)
        <Alarmtype> physicalViolation (9)
        <Polarity> (2)
        "
	::= { pm20002maAlmlineHostLaneFaultEntry 2 }


--- *********************************************************
---     TABLE for the pm20002maAlmlineNetworkLaneRxOtn articles
--- *********************************************************

pm20002maAlmlineNetworkLaneRxOtnTable OBJECT-TYPE
	SYNTAX  SEQUENCE OF Pm20002maAlmlineNetworkLaneRxOtnEntry
	MAX-ACCESS not-accessible
	STATUS current
	DESCRIPTION
        "
        List of pm20002maAlmlineNetworkLaneRxOtn
        Article
        "
	::= { pm20002maAlmLineUrg 200 }


pm20002maAlmlineNetworkLaneRxOtnEntry OBJECT-TYPE
	SYNTAX Pm20002maAlmlineNetworkLaneRxOtnEntry
	MAX-ACCESS not-accessible
	STATUS current
	DESCRIPTION
        "
        Row definition for the pm20002maAlmlineNetworkLaneRxOtn
        table
        "
	INDEX   { pm20002maAlmlineNetworkLaneRxOtnIndex }
	::= { pm20002maAlmlineNetworkLaneRxOtnTable 1 }


Pm20002maAlmlineNetworkLaneRxOtnEntry ::=
	SEQUENCE {
	pm20002maAlmlineNetworkLaneRxOtnIndex
		INTEGER,
	pm20002maAlmLineRxOtnLofPortn
		EkiOnOff,
	pm20002maAlmLineRxOtnOofPortn
		EkiOnOff,
	pm20002maAlmLineRxOtnLomPortn
		EkiOnOff,
	pm20002maAlmLineRxOtnOomPortn
		EkiOnOff,
	pm20002maAlmLineRxOtnIaePortn
		EkiOnOff,
	pm20002maAlmLineRxSmBdiPortn
		EkiOnOff,
	pm20002maAlmLineRxOtnOtuAisPortn
		EkiOnOff,
	pm20002maAlmLineRxOtnOduAisPortn
		EkiOnOff
	}


pm20002maAlmlineNetworkLaneRxOtnIndex OBJECT-TYPE
	SYNTAX  INTEGER(0..128)
	MAX-ACCESS  read-only
	STATUS current
	DESCRIPTION
        "
        Index definition for the pm20002maAlmlineNetworkLaneRxOtn
        table
        "
	::= { pm20002maAlmlineNetworkLaneRxOtnEntry 1 }


pm20002maAlmLineRxOtnLofPortn OBJECT-TYPE
	SYNTAX  EkiOnOff
	MAX-ACCESS read-only
	STATUS current
	DESCRIPTION
        "
        Line Network Rx LOF :This OID
         indicates a Loss of Frame is detected
        on the Rx Network interface of
         the Line Trscv <Help> Alarm indicating
        a Loss of Frame is detected on
         the Rx Network interface of the
        Line Trscv <Condtype> LINE_RX_OTN_LOF
        <Probcause> receiveFailure (41)
        <Alarmtype> equipmentAlarm (5)
         <Polarity> (2)
        "
	::= { pm20002maAlmlineNetworkLaneRxOtnEntry 17 }


pm20002maAlmLineRxOtnOofPortn OBJECT-TYPE
	SYNTAX  EkiOnOff
	MAX-ACCESS read-only
	STATUS current
	DESCRIPTION
        "
        Line Network Rx OOF :This OID
         indicates an Out of Frame is detected
        on the Rx Network interface of
         the Line Trscv <Help> Alarm indicating
        an Out of Frame is detected on
         the Rx Network interface of the
        Line Trscv <Condtype> LINE_RX_OTN_OOF
        <Probcause> receiveFailure (41)
        <Alarmtype> equipmentAlarm (5)
         <Polarity> (2)
        "
	::= { pm20002maAlmlineNetworkLaneRxOtnEntry 16 }


pm20002maAlmLineRxOtnLomPortn OBJECT-TYPE
	SYNTAX  EkiOnOff
	MAX-ACCESS read-only
	STATUS current
	DESCRIPTION
        "
        Line Network Rx LOM :This OID
         indicates a Loss of Multiframe
        is detected on the Rx Network interface
        of the Line Trscv <Help> Alarm
         indicating a Loss of Multiframe
        is detected on the Rx Network interface
        of the Line Trscv <Condtype> LINE_RX_OTN_LOM
        <Probcause> receiveFailure (41)
        <Alarmtype> equipmentAlarm (5)
         <Polarity> (2)
        "
	::= { pm20002maAlmlineNetworkLaneRxOtnEntry 15 }


pm20002maAlmLineRxOtnOomPortn OBJECT-TYPE
	SYNTAX  EkiOnOff
	MAX-ACCESS read-only
	STATUS current
	DESCRIPTION
        "
        Line Network Rx OOM :This OID
         indicates an Out of Multiframe
        is detected on the Rx Network interface
        of the Line Trscv <Help> Alarm
         indicating an Out of Multiframe
        is detected on the Rx Network interface
        of the Line Trscv <Condtype> LINE_RX_OTN_OOM
        <Probcause> receiveFailure (41)
        <Alarmtype> equipmentAlarm (5)
         <Polarity> (2)
        "
	::= { pm20002maAlmlineNetworkLaneRxOtnEntry 14 }


pm20002maAlmLineRxOtnIaePortn OBJECT-TYPE
	SYNTAX  EkiOnOff
	MAX-ACCESS read-only
	STATUS current
	DESCRIPTION
        "
        Line Network Rx IAE :This OID
         indicates an Incoming Alignment
        Error is detected on the Rx Network
        interface of the Line Trscv <Help>
        Alarm indicating an Incoming Alignment
        Error is detected on the Rx Network
        interface of the Line Trscv <Condtype>
        LINE_RX_OTN_IAE <Probcause> receiveFailure
        (41) <Alarmtype> equipmentAlarm
        (5) <Polarity> (2)
        "
	::= { pm20002maAlmlineNetworkLaneRxOtnEntry 13 }


pm20002maAlmLineRxSmBdiPortn OBJECT-TYPE
	SYNTAX  EkiOnOff
	MAX-ACCESS read-only
	STATUS current
	DESCRIPTION
        "
        Line Network Rx SM BDI :This OID
        indicates an SM Backward Defect
        Indication is detected on the Rx
        Network interface of the Line Trscv
        <Help> Alarm indicating an SM Backward
        Defect Indication is detected on
        the Rx Network interface of the
        Line Trscv <Condtype> LINE_RX_SM_BDI
        <Probcause> informationalStatus(1000)
        <Alarmtype> other (1) <Polarity>
        (2)
        "
	::= { pm20002maAlmlineNetworkLaneRxOtnEntry 12 }


pm20002maAlmLineRxOtnOtuAisPortn OBJECT-TYPE
	SYNTAX  EkiOnOff
	MAX-ACCESS read-only
	STATUS current
	DESCRIPTION
        "
        Line Network Rx OTU AIS :This
         OID indicates an OTU This OID
         Indication Signal is detected
         on the Rx Network interface of
        the Line Trscv <Help> Alarm indicating
        an OTU Alarm Indication Signal
         is detected on the Rx Network
         interface of the Line Trscv <Condtype>
        LINE_RX_OTN_OTU_AIS <Probcause>
        receiveFailure (41) <Alarmtype>
        equipmentAlarm (5) <Polarity> (2)
        "
	::= { pm20002maAlmlineNetworkLaneRxOtnEntry 11 }


pm20002maAlmLineRxOtnOduAisPortn OBJECT-TYPE
	SYNTAX  EkiOnOff
	MAX-ACCESS read-only
	STATUS current
	DESCRIPTION
        "
        Line Network Rx ODU AIS :This
         OID indicates an ODU This OID
         Indication Signal is detected
         on the Rx Network interface of
        the Line Trscv <Help> Alarm indicating
        an ODU Alarm Indication Signal
         is detected on the Rx Network
         interface of the Line Trscv <Condtype>
        LINE_RX_OTN_ODU_AIS <Probcause>
        receiveFailure (41) <Alarmtype>
        equipmentAlarm (5) <Polarity> (2)
        "
	::= { pm20002maAlmlineNetworkLaneRxOtnEntry 10 }


--- *********************************************************
---     TABLE for the pm20002maAlmlineHostLaneTxOtn articles
--- *********************************************************

pm20002maAlmlineHostLaneTxOtnTable OBJECT-TYPE
	SYNTAX  SEQUENCE OF Pm20002maAlmlineHostLaneTxOtnEntry
	MAX-ACCESS not-accessible
	STATUS current
	DESCRIPTION
        "
        List of pm20002maAlmlineHostLaneTxOtn
        Article
        "
	::= { pm20002maAlmLineUrg 204 }


pm20002maAlmlineHostLaneTxOtnEntry OBJECT-TYPE
	SYNTAX Pm20002maAlmlineHostLaneTxOtnEntry
	MAX-ACCESS not-accessible
	STATUS current
	DESCRIPTION
        "
        Row definition for the pm20002maAlmlineHostLaneTxOtn
        table
        "
	INDEX   { pm20002maAlmlineHostLaneTxOtnIndex }
	::= { pm20002maAlmlineHostLaneTxOtnTable 1 }


Pm20002maAlmlineHostLaneTxOtnEntry ::=
	SEQUENCE {
	pm20002maAlmlineHostLaneTxOtnIndex
		INTEGER,
	pm20002maAlmLineTxOtnLofPortn
		EkiOnOff,
	pm20002maAlmLineTxOtnOofPortn
		EkiOnOff,
	pm20002maAlmLineTxOtnLomPortn
		EkiOnOff,
	pm20002maAlmLineTxOtnOomPortn
		EkiOnOff,
	pm20002maAlmLineTxOtnIaePortn
		EkiOnOff,
	pm20002maAlmLineTxSmBdiPortn
		EkiOnOff,
	pm20002maAlmLineTxOtnOtuAisPortn
		EkiOnOff,
	pm20002maAlmLineTxOtnOduAisPortn
		EkiOnOff
	}


pm20002maAlmlineHostLaneTxOtnIndex OBJECT-TYPE
	SYNTAX  INTEGER(0..128)
	MAX-ACCESS  read-only
	STATUS current
	DESCRIPTION
        "
        Index definition for the pm20002maAlmlineHostLaneTxOtn
        table
        "
	::= { pm20002maAlmlineHostLaneTxOtnEntry 1 }


pm20002maAlmLineTxOtnLofPortn OBJECT-TYPE
	SYNTAX  EkiOnOff
	MAX-ACCESS read-only
	STATUS current
	DESCRIPTION
        "
        Line Host Tx LOF :This OID indicates
        a Loss of Frame is detected on
         the Tx Host interface of the Line
        Trscv <Help> Alarm indicating a
        Loss of Frame is detected on the
        Tx Host interface of the Line Trscv
        <Condtype> LINE_TX_OTN_LOF <Probcause>
        receiveFailure (41) <Alarmtype>
        equipmentAlarm (5) <Polarity> (2)
        "
	::= { pm20002maAlmlineHostLaneTxOtnEntry 17 }


pm20002maAlmLineTxOtnOofPortn OBJECT-TYPE
	SYNTAX  EkiOnOff
	MAX-ACCESS read-only
	STATUS current
	DESCRIPTION
        "
        Line Host Tx OOF :This OID indicates
        an Out of Frame is detected on
         the Tx Host interface of the Line
        Trscv <Help> Alarm indicating an
        Out of Frame is detected on the
        Tx Host interface of the Line Trscv
        <Condtype> LINE_TX_OTN_OOF <Probcause>
        receiveFailure (41) <Alarmtype>
        equipmentAlarm (5) <Polarity> (2)
        "
	::= { pm20002maAlmlineHostLaneTxOtnEntry 16 }


pm20002maAlmLineTxOtnLomPortn OBJECT-TYPE
	SYNTAX  EkiOnOff
	MAX-ACCESS read-only
	STATUS current
	DESCRIPTION
        "
        Line Host Tx LOM :This OID indicates
        a Loss of Multiframe is detected
        on the Tx Host interface of the
        Line Trscv <Help> Alarm indicating
        a Loss of Multiframe is detected
        on the Tx Host interface of the
        Line Trscv <Condtype> LINE_TX_OTN_LOM
        <Probcause> receiveFailure (41)
        <Alarmtype> equipmentAlarm (5)
         <Polarity> (2)
        "
	::= { pm20002maAlmlineHostLaneTxOtnEntry 15 }


pm20002maAlmLineTxOtnOomPortn OBJECT-TYPE
	SYNTAX  EkiOnOff
	MAX-ACCESS read-only
	STATUS current
	DESCRIPTION
        "
        Line Host Tx OOM :This OID indicates
        an Out of Multiframe is detected
        on the Tx Host interface of the
        Line Trscv <Help> Alarm indicating
        an Out of Multiframe is detected
        on the Tx Host interface of the
        Line Trscv <Condtype> LINE_TX_OTN_OOM
        <Probcause> receiveFailure (41)
        <Alarmtype> equipmentAlarm (5)
         <Polarity> (2)
        "
	::= { pm20002maAlmlineHostLaneTxOtnEntry 14 }


pm20002maAlmLineTxOtnIaePortn OBJECT-TYPE
	SYNTAX  EkiOnOff
	MAX-ACCESS read-only
	STATUS current
	DESCRIPTION
        "
        Line Host Tx IAE :This OID indicates
        an Incoming Alignment Error is
         detected on the Tx Host interface
        of the Line Trscv <Help> Alarm
         indicating an Incoming Alignment
        Error is detected on the Tx Host
        interface of the Line Trscv <Condtype>
        LINE_TX_OTN_IAE <Probcause> receiveFailure
        (41) <Alarmtype> equipmentAlarm
        (5) <Polarity> (2)
        "
	::= { pm20002maAlmlineHostLaneTxOtnEntry 13 }


pm20002maAlmLineTxSmBdiPortn OBJECT-TYPE
	SYNTAX  EkiOnOff
	MAX-ACCESS read-only
	STATUS current
	DESCRIPTION
        "
        Line Host Tx SM BDI :This OID
         indicates an SM Backward Defect
        Indication is detected on the Tx
        Host interface of the Line Trscv
        <Help> Alarm indicating an SM Backward
        Defect Indication is detected on
        the Tx Host interface of the Line
        Trscv <Condtype> LINE_TX_SM_BDI
        <Probcause> informationalStatus(1000)
        <Alarmtype> other (1) <Polarity>
        (2)
        "
	::= { pm20002maAlmlineHostLaneTxOtnEntry 12 }


pm20002maAlmLineTxOtnOtuAisPortn OBJECT-TYPE
	SYNTAX  EkiOnOff
	MAX-ACCESS read-only
	STATUS current
	DESCRIPTION
        "
        Line Host Tx OTU AIS :This OID
        indicates an OTU This OID Indication
        Signal is detected on the Tx Host
        interface of the Line Trscv <Help>
        Alarm indicating an OTU Alarm Indication
        Signal is detected on the Tx Host
        interface of the Line Trscv <Condtype>
        LINE_TX_OTN_OTU_AIS <Probcause>
        receiveFailure (41) <Alarmtype>
        equipmentAlarm (5) <Polarity> (2)
        "
	::= { pm20002maAlmlineHostLaneTxOtnEntry 11 }


pm20002maAlmLineTxOtnOduAisPortn OBJECT-TYPE
	SYNTAX  EkiOnOff
	MAX-ACCESS read-only
	STATUS current
	DESCRIPTION
        "
        Line Host Tx ODU AIS :This OID
        indicates an ODU This OID Indication
        Signal is detected on the Tx Host
        interface of the Line Trscv <Help>
        Alarm indicating an ODU Alarm Indication
        Signal is detected on the Tx Host
        interface of the Line Trscv <Condtype>
        LINE_TX_OTN_ODU_AIS <Probcause>
        receiveFailure (41) <Alarmtype>
        equipmentAlarm (5) <Polarity> (2)
        "
	::= { pm20002maAlmlineHostLaneTxOtnEntry 10 }


--- *********************************************************
---     TABLE for the pm20002maAlmclientSfpAlmDdm articles
--- *********************************************************

pm20002maAlmclientSfpAlmDdmTable OBJECT-TYPE
	SYNTAX  SEQUENCE OF Pm20002maAlmclientSfpAlmDdmEntry
	MAX-ACCESS not-accessible
	STATUS current
	DESCRIPTION
        "
        List of pm20002maAlmclientSfpAlmDdm
        Article
        "
	::= { pm20002maAlmClientUrg 240 }


pm20002maAlmclientSfpAlmDdmEntry OBJECT-TYPE
	SYNTAX Pm20002maAlmclientSfpAlmDdmEntry
	MAX-ACCESS not-accessible
	STATUS current
	DESCRIPTION
        "
        Row definition for the pm20002maAlmclientSfpAlmDdm
        table
        "
	INDEX   { pm20002maAlmclientSfpAlmDdmIndex }
	::= { pm20002maAlmclientSfpAlmDdmTable 1 }


Pm20002maAlmclientSfpAlmDdmEntry ::=
	SEQUENCE {
	pm20002maAlmclientSfpAlmDdmIndex
		INTEGER,
	pm20002maAlmRxPwrHighAlaPortn
		EkiOnOff,
	pm20002maAlmRxPwrLowAlaPortn
		EkiOnOff,
	pm20002maAlmTxBiasHighAlaPortn
		EkiOnOff,
	pm20002maAlmTxBiasLowAlaPortn
		EkiOnOff,
	pm20002maAlmTxPwrHighAlaPortn
		EkiOnOff,
	pm20002maAlmTxPwrLowAlaPortn
		EkiOnOff
	}


pm20002maAlmclientSfpAlmDdmIndex OBJECT-TYPE
	SYNTAX  INTEGER(0..128)
	MAX-ACCESS  read-only
	STATUS current
	DESCRIPTION
        "
        Index definition for the pm20002maAlmclientSfpAlmDdm
        table
        "
	::= { pm20002maAlmclientSfpAlmDdmEntry 1 }


pm20002maAlmRxPwrHighAlaPortn OBJECT-TYPE
	SYNTAX  EkiOnOff
	MAX-ACCESS read-only
	STATUS current
	DESCRIPTION
        "
        Client Trscv Rx Power High :This
        OID indicates that the Trscv input
        power of port is higher than the
        threshold value written in the
         Trscv EEPROM <Help> Alarm indicating
        that the Trscv input power of port
        is higher than the threshold value
        written in the Trscv EEPROM <Condtype>
        RX_PWR_HIGH_ALA_1 <Probcause> receiveFailure
        (41) <Alarmtype> equipmentAlarm
        (5) <Polarity> (2)
        "
	::= { pm20002maAlmclientSfpAlmDdmEntry 17 }


pm20002maAlmRxPwrLowAlaPortn OBJECT-TYPE
	SYNTAX  EkiOnOff
	MAX-ACCESS read-only
	STATUS current
	DESCRIPTION
        "
        Client Trscv Rx Power Low :This
        OID indicates that the Trscv input
        power of port is lower than the
        threshold value written in the
         Trscv EEPROM <Help> Alarm indicating
        that the Trscv input power of port
        is lower than the threshold value
        written in the Trscv EEPROM <Condtype>
        RX_PWR_LOW_ALA_1 <Probcause> receiveFailure
        (41) <Alarmtype> equipmentAlarm
        (5) <Polarity> (2)
        "
	::= { pm20002maAlmclientSfpAlmDdmEntry 16 }


pm20002maAlmTxBiasHighAlaPortn OBJECT-TYPE
	SYNTAX  EkiOnOff
	MAX-ACCESS read-only
	STATUS current
	DESCRIPTION
        "
        Client Trscv Bias High :This OID
        indicates that the Trscv laser
         bias current of port is higher
        than the threshold value written
        in the Trscv EEPROM <Help> Alarm
        indicating that the Trscv laser
        bias current of port is higher
         than the threshold value written
        in the Trscv EEPROM <Condtype>
         TX_BIAS_HIGH_ALA_1 <Probcause>
        transmitterFailure (56) <Alarmtype>
        equipmentAlarm (5) <Polarity> (2)
        "
	::= { pm20002maAlmclientSfpAlmDdmEntry 5 }


pm20002maAlmTxBiasLowAlaPortn OBJECT-TYPE
	SYNTAX  EkiOnOff
	MAX-ACCESS read-only
	STATUS current
	DESCRIPTION
        "
        Client Trscv Bias Low :This OID
        indicates that the Trscv laser
         bias current of port is lower
         than the threshold value written
        in the Trscv EEPROM <Help> Alarm
        indicating that the Trscv laser
        bias current of port is lower than
        the threshold value written in
         the Trscv EEPROM <Condtype> TX_BIAS_LOW_ALA_1
        <Probcause> transmitterFailure
         (56) <Alarmtype> equipmentAlarm
        (5) <Polarity> (2)
        "
	::= { pm20002maAlmclientSfpAlmDdmEntry 4 }


pm20002maAlmTxPwrHighAlaPortn OBJECT-TYPE
	SYNTAX  EkiOnOff
	MAX-ACCESS read-only
	STATUS current
	DESCRIPTION
        "
        Client Trscv Tx Power High :This
        OID indicates that the Trscv output
        power of port is higher than the
        threshold value written in the
         Trscv EEPROM <Help> Alarm indicating
        that the Trscv output power of
         port is higher than the threshold
        value written in the Trscv EEPROM
        <Condtype> TX_PWR_HIGH_ALA_1 <Probcause>
        transmitterFailure (56) <Alarmtype>
        equipmentAlarm (5) <Polarity> (2)
        "
	::= { pm20002maAlmclientSfpAlmDdmEntry 3 }


pm20002maAlmTxPwrLowAlaPortn OBJECT-TYPE
	SYNTAX  EkiOnOff
	MAX-ACCESS read-only
	STATUS current
	DESCRIPTION
        "
        Client Trscv Tx Power Low :This
        OID indicates that the Trscv output
        power of port is lower than the
        threshold value written in the
         Trscv EEPROM <Help> Alarm indicating
        that the Trscv output power of
         port is lower than the threshold
        value written in the Trscv EEPROM
        <Condtype> TX_PWR_LOW_ALA_1 <Probcause>
        transmitterFailure (56) <Alarmtype>
        equipmentAlarm (5) <Polarity> (2)
        "
	::= { pm20002maAlmclientSfpAlmDdmEntry 2 }


--- *********************************************************
---     TABLE for the pm20002maAlmclientSfpWarnDdm articles
--- *********************************************************

pm20002maAlmclientSfpWarnDdmTable OBJECT-TYPE
	SYNTAX  SEQUENCE OF Pm20002maAlmclientSfpWarnDdmEntry
	MAX-ACCESS not-accessible
	STATUS current
	DESCRIPTION
        "
        List of pm20002maAlmclientSfpWarnDdm
        Article
        "
	::= { pm20002maAlmClientNurg 272 }


pm20002maAlmclientSfpWarnDdmEntry OBJECT-TYPE
	SYNTAX Pm20002maAlmclientSfpWarnDdmEntry
	MAX-ACCESS not-accessible
	STATUS current
	DESCRIPTION
        "
        Row definition for the pm20002maAlmclientSfpWarnDdm
        table
        "
	INDEX   { pm20002maAlmclientSfpWarnDdmIndex }
	::= { pm20002maAlmclientSfpWarnDdmTable 1 }


Pm20002maAlmclientSfpWarnDdmEntry ::=
	SEQUENCE {
	pm20002maAlmclientSfpWarnDdmIndex
		INTEGER,
	pm20002maAlmRxPwrHighWngPortn
		EkiOnOff,
	pm20002maAlmRxPwrLowWngPortn
		EkiOnOff,
	pm20002maAlmTxBiasHighWngPortn
		EkiOnOff,
	pm20002maAlmTxBiasLowWngPortn
		EkiOnOff,
	pm20002maAlmTxPwrHighWngPortn
		EkiOnOff,
	pm20002maAlmTxPwLowWngPortn
		EkiOnOff
	}


pm20002maAlmclientSfpWarnDdmIndex OBJECT-TYPE
	SYNTAX  INTEGER(0..128)
	MAX-ACCESS  read-only
	STATUS current
	DESCRIPTION
        "
        Index definition for the pm20002maAlmclientSfpWarnDdm
        table
        "
	::= { pm20002maAlmclientSfpWarnDdmEntry 1 }


pm20002maAlmRxPwrHighWngPortn OBJECT-TYPE
	SYNTAX  EkiOnOff
	MAX-ACCESS read-only
	STATUS current
	DESCRIPTION
        "
        Client Trscv Rx Power High Warning
        :This OID indicates that the Trscv
        input power is higher than the
         threshold value written in the
        Trscv EEPROM <Help> Warning indicating
        that the Trscv input power is higher
        than the threshold value written
        in the Trscv EEPROM <Condtype>
         RX_PWR_HIGH_WNG_1 <Probcause>
         receiveFailure (41) <Alarmtype>
        equipmentAlarm (5) <Polarity> (2)
        "
	::= { pm20002maAlmclientSfpWarnDdmEntry 17 }


pm20002maAlmRxPwrLowWngPortn OBJECT-TYPE
	SYNTAX  EkiOnOff
	MAX-ACCESS read-only
	STATUS current
	DESCRIPTION
        "
        Client Trscv Rx Power Low Warning
        :This OID indicates that the Trscv
        input power is lower than the threshold
        value written in the Trscv EEPROM
        <Help> Warning indicating that
         the Trscv input power is lower
        than the threshold value written
        in the Trscv EEPROM <Condtype>
         RX_PWR_LOW_WNG_1 <Probcause> receiveFailure
        (41) <Alarmtype> equipmentAlarm
        (5) <Polarity> (2)
        "
	::= { pm20002maAlmclientSfpWarnDdmEntry 16 }


pm20002maAlmTxBiasHighWngPortn OBJECT-TYPE
	SYNTAX  EkiOnOff
	MAX-ACCESS read-only
	STATUS current
	DESCRIPTION
        "
        Client Trscv Bias High Warning
        :This OID indicates that the Trscv
        laser bias current is higher than
        the threshold value written in
         the Trscv EEPROM <Help> Warning
        indicating that the Trscv laser
        bias current is higher than the
        threshold value written in the
         Trscv EEPROM <Condtype> TX_BIAS_HIGH_WNG_1
        <Probcause> transmitterFailure
         (56) <Alarmtype> equipmentAlarm
        (5) <Polarity> (2)
        "
	::= { pm20002maAlmclientSfpWarnDdmEntry 5 }


pm20002maAlmTxBiasLowWngPortn OBJECT-TYPE
	SYNTAX  EkiOnOff
	MAX-ACCESS read-only
	STATUS current
	DESCRIPTION
        "
        Client Trscv Bias Low Warning
         :This OID indicates that the Trscv
        laser bias current is lower than
        the threshold value written in
         the Trscv EEPROM <Help> Warning
        indicating that the Trscv laser
        bias current is lower than the
         threshold value written in the
        Trscv EEPROM <Condtype> TX_BIAS_LOW_WNG_1
        <Probcause> transmitterFailure
         (56) <Alarmtype> equipmentAlarm
        (5) <Polarity> (2)
        "
	::= { pm20002maAlmclientSfpWarnDdmEntry 4 }


pm20002maAlmTxPwrHighWngPortn OBJECT-TYPE
	SYNTAX  EkiOnOff
	MAX-ACCESS read-only
	STATUS current
	DESCRIPTION
        "
        Client Trscv Tx Power High Warning
        :This OID indicates that the Trscv
        output power is higher than the
        threshold value written in the
         Trscv EEPROM <Help> Warning indicating
        that the Trscv output power is
         higher than the threshold value
        written in the Trscv EEPROM <Condtype>
        TX_PWR_HIGH_WNG_1 <Probcause> transmitterFailure
        (56) <Alarmtype> equipmentAlarm
        (5) <Polarity> (2)
        "
	::= { pm20002maAlmclientSfpWarnDdmEntry 3 }


pm20002maAlmTxPwLowWngPortn OBJECT-TYPE
	SYNTAX  EkiOnOff
	MAX-ACCESS read-only
	STATUS current
	DESCRIPTION
        "
        Client Trscv Tx Power Low Warning
        :This OID indicates that the Trscv
        output power is lower than the
         threshold value written in the
        Trscv EEPROM <Help> Warning indicating
        that the Trscv output power is
         lower than the threshold value
        written in the Trscv EEPROM <Condtype>
        TX_PW_LOW_WNG_1 <Probcause> transmitterFailure
        (56) <Alarmtype> equipmentAlarm
        (5) <Polarity> (2)
        "
	::= { pm20002maAlmclientSfpWarnDdmEntry 2 }


--- *****************************************************
---     LEAF for the modFanFail article
--- *****************************************************
pm20002maAlmmodFanFail OBJECT IDENTIFIER ::= { pm20002maAlmOtherUrg 336 }




pm20002maAlmFanHighSpeed OBJECT-TYPE
	  SYNTAX EkiOnOff
	  MAX-ACCESS read-only
	  STATUS current
	  DESCRIPTION
        "
        Fan High Speed :This OID indicates
        the fan is blowing at high speed
        <Help> This alarm indicates the
        fan is blowing at high speed <Condtype>
        FAN_HIGH_SPEED <Probcause> other
        (1) <Alarmtype> other (1) <Polarity>
        (2)
        "
	  ::= { pm20002maAlmmodFanFail 2 }



pm20002maAlmFanFail OBJECT-TYPE
	  SYNTAX EkiOnOff
	  MAX-ACCESS read-only
	  STATUS current
	  DESCRIPTION
        "
        Fan Module Failure :This OID indicates
        that the FAN unit inside the module
        is in fail condition  <Help>  This
        alarm indicates that the FAN is
        in a fail condition. <Condtype>
        FAN_FAIL <Probcause> heatingVentCoolingSystemProblem
        (22) <Alarmtype> equipmentAlarm
        (5) <Polarity> (2)
        "
	  ::= { pm20002maAlmmodFanFail 1 }



--- *****************************************************
---     LEAF for the clientQsfpAlarmDdm article
--- *****************************************************
pm20002maAlmclientQsfpAlarmDdm OBJECT IDENTIFIER ::= { pm20002maAlmOtherUrg 337 }




pm20002maAlmTrscv2TempHighAla1 OBJECT-TYPE
	  SYNTAX EkiOnOff
	  MAX-ACCESS read-only
	  STATUS current
	  DESCRIPTION
        "
        Q2 Trscv Temp High Alarm :This
        OID indicates that the Trscv temperature
        of port is higher than the threshold
        value written in the Trscv EEPROM
        <Help> Alarm indicating that the
        Trscv temperature of port is higher
        than the threshold value written
        in the Trscv EEPROM <Condtype>
         TRSCV2_TEMP_HIGH_ALA_1 <Probcause>
        temperatureUnacceptable (51) <Alarmtype>
        "
	  ::= { pm20002maAlmclientQsfpAlarmDdm 8 }



pm20002maAlmTrscv2TempLowAla1 OBJECT-TYPE
	  SYNTAX EkiOnOff
	  MAX-ACCESS read-only
	  STATUS current
	  DESCRIPTION
        "
        Q2 Trscv Temp Low Alarm :This
         OID indicates that the Trscv temperature
        of port is lower than the threshold
        value written in the Trscv EEPROM
        <Help> Alarm indicating that the
        Trscv temperature of port is lower
        than the threshold value written
        in the Trscv EEPROM <Condtype>
         TRSCV2_TEMP_LOW_ALA_1 <Probcause>
        temperatureUnacceptable (51) <Alarmtype>
        "
	  ::= { pm20002maAlmclientQsfpAlarmDdm 7 }



pm20002maAlmTrscv2VccHighAla1 OBJECT-TYPE
	  SYNTAX EkiOnOff
	  MAX-ACCESS read-only
	  STATUS current
	  DESCRIPTION
        "
        Q2 Trscv Power Supply High Alarm
        :This OID indicates that the Trscv
        power supply of port is higher
         than the threshold value written
        in the Trscv EEPROM <Help> Alarm
        indicating that the Trscv power
        supply of port is higher than the
        threshold value written in the
         Trscv EEPROM <Condtype> TRSCV2_VCC_HIGH_ALA_1
        <Probcause> powerProblem (36) <Alarmtype>
        "
	  ::= { pm20002maAlmclientQsfpAlarmDdm 6 }



pm20002maAlmTrscv2VccLowAla1 OBJECT-TYPE
	  SYNTAX EkiOnOff
	  MAX-ACCESS read-only
	  STATUS current
	  DESCRIPTION
        "
        Q2 Trscv Power Supply Low Alarm
        :This OID indicates that the Trscv
        power supply of port is lower than
        the threshold value written in
         the Trscv EEPROM <Help> Alarm
         indicating that the Trscv power
        supply of port is lower than the
        threshold value written in the
         Trscv EEPROM <Condtype> TRSCV2_VCC_LOW_ALA_1
        <Probcause> powerProblem (36) <Alarmtype>
        "
	  ::= { pm20002maAlmclientQsfpAlarmDdm 5 }



pm20002maAlmTrscv1TempHighAla OBJECT-TYPE
	  SYNTAX EkiOnOff
	  MAX-ACCESS read-only
	  STATUS current
	  DESCRIPTION
        "
        Q1 Trscv Temp High Alarm :This
        OID indicates that the Trscv temperature
        of port is higher than the threshold
        value written in the Trscv EEPROM
        <Help> Alarm indicating that the
        Trscv temperature of port is higher
        than the threshold value written
        in the Trscv EEPROM <Condtype>
         TRSCV1_TEMP_HIGH_ALA <Probcause>
        temperatureUnacceptable (51) <Alarmtype>
        "
	  ::= { pm20002maAlmclientQsfpAlarmDdm 4 }



pm20002maAlmTrscv1TempLowAla1 OBJECT-TYPE
	  SYNTAX EkiOnOff
	  MAX-ACCESS read-only
	  STATUS current
	  DESCRIPTION
        "
        Q1 Trscv Temp Low Alarm :This
         OID indicates that the Trscv temperature
        of port is lower than the threshold
        value written in the Trscv EEPROM
        <Help> Alarm indicating that the
        Trscv temperature of port is lower
        than the threshold value written
        in the Trscv EEPROM <Condtype>
         TRSCV1_TEMP_LOW_ALA_1 <Probcause>
        temperatureUnacceptable (51) <Alarmtype>
        "
	  ::= { pm20002maAlmclientQsfpAlarmDdm 3 }



pm20002maAlmTrscv1VccHighAla1 OBJECT-TYPE
	  SYNTAX EkiOnOff
	  MAX-ACCESS read-only
	  STATUS current
	  DESCRIPTION
        "
        Q1 Trscv Power Supply High Alarm
        :This OID indicates that the Trscv
        power supply of port is higher
         than the threshold value written
        in the Trscv EEPROM <Help> Alarm
        indicating that the Trscv power
        supply of port is higher than the
        threshold value written in the
         Trscv EEPROM <Condtype> TRSCV1_VCC_HIGH_ALA_1
        <Probcause> powerProblem (36) <Alarmtype>
        "
	  ::= { pm20002maAlmclientQsfpAlarmDdm 2 }



pm20002maAlmTrscv1VccLowAla1 OBJECT-TYPE
	  SYNTAX EkiOnOff
	  MAX-ACCESS read-only
	  STATUS current
	  DESCRIPTION
        "
        Q1 Trscv Power Supply Low Alarm
        :This OID indicates that the Trscv
        power supply of port is lower than
        the threshold value written in
         the Trscv EEPROM <Help> Alarm
         indicating that the Trscv power
        supply of port is lower than the
        threshold value written in the
         Trscv EEPROM <Condtype> TRSCV1_VCC_LOW_ALA_1
        <Probcause> powerProblem (36) <Alarmtype>
        "
	  ::= { pm20002maAlmclientQsfpAlarmDdm 1 }



--- *****************************************************
---     LEAF for the clientQsfpWarnDdm article
--- *****************************************************
pm20002maAlmclientQsfpWarnDdm OBJECT IDENTIFIER ::= { pm20002maAlmOtherNurg 338 }




pm20002maAlmTrscv2TempHighWng1 OBJECT-TYPE
	  SYNTAX EkiOnOff
	  MAX-ACCESS read-only
	  STATUS current
	  DESCRIPTION
        "
        Q2 Trscv Temp High Warning :This
        OID indicates that the Trscv temperature
        is higher than the threshold value
        written in the Trscv EEPROM <Help>
        Warning indicating that the Trscv
        temperature is higher than the
         threshold value written in the
        Trscv EEPROM <Condtype> TRSCV2_TEMP_HIGH_WNG_1
        <Probcause> temperatureUnacceptable
        (51) <Alarmtype>
        "
	  ::= { pm20002maAlmclientQsfpWarnDdm 8 }



pm20002maAlmTrscv2TempLowWng1 OBJECT-TYPE
	  SYNTAX EkiOnOff
	  MAX-ACCESS read-only
	  STATUS current
	  DESCRIPTION
        "
        Q2 Trscv Temp Low Warning :This
        OID indicates that the Trscv temperature
        is lower than the threshold value
        written in the Trscv EEPROM <Help>
        Warning indicating that the Trscv
        temperature is lower than the threshold
        value written in the Trscv EEPROM
        <Condtype> TRSCV2_TEMP_LOW_WNG_1
        <Probcause> temperatureUnacceptable
        (51) <Alarmtype>
        "
	  ::= { pm20002maAlmclientQsfpWarnDdm 7 }



pm20002maAlmTrscv2VccHighWng1 OBJECT-TYPE
	  SYNTAX EkiOnOff
	  MAX-ACCESS read-only
	  STATUS current
	  DESCRIPTION
        "
        Q2 Trscv Power Supply High Warning
        :This OID indicates that the Trscv
        power supply is higher than the
        threshold value written in the
         Trscv EEPROM <Help> Warning indicating
        that the Trscv power supply is
         higher than the threshold value
        written in the Trscv EEPROM <Condtype>
        TRSCV2_VCC_HIGH_WNG_1 <Probcause>
        powerProblem (36) <Alarmtype>
        "
	  ::= { pm20002maAlmclientQsfpWarnDdm 6 }



pm20002maAlmTrscv2VccLowWng1 OBJECT-TYPE
	  SYNTAX EkiOnOff
	  MAX-ACCESS read-only
	  STATUS current
	  DESCRIPTION
        "
        Q2 Trscv Power Supply Low Warning
        :This OID indicates that the Trscv
        power supply is lower than the
         threshold value written in the
        Trscv EEPROM <Help> Warning indicating
        that the Trscv power supply is
         lower than the threshold value
        written in the Trscv EEPROM <Condtype>
        TRSCV2_VCC_LOW_WNG_1 <Probcause>
        powerProblem (36) <Alarmtype>
        "
	  ::= { pm20002maAlmclientQsfpWarnDdm 5 }



pm20002maAlmTrscv1TempHighWng1 OBJECT-TYPE
	  SYNTAX EkiOnOff
	  MAX-ACCESS read-only
	  STATUS current
	  DESCRIPTION
        "
        Q1 Trscv Temp High Warning :This
        OID indicates that the Trscv temperature
        is higher than the threshold value
        written in the Trscv EEPROM <Help>
        Warning indicating that the Trscv
        temperature is higher than the
         threshold value written in the
        Trscv EEPROM <Condtype> TRSCV1_TEMP_HIGH_WNG_1
        <Probcause> temperatureUnacceptable
        (51) <Alarmtype>
        "
	  ::= { pm20002maAlmclientQsfpWarnDdm 4 }



pm20002maAlmTrscv1TempLowWng1 OBJECT-TYPE
	  SYNTAX EkiOnOff
	  MAX-ACCESS read-only
	  STATUS current
	  DESCRIPTION
        "
        Q1 Trscv Temp Low Warning :This
        OID indicates that the Trscv temperature
        is lower than the threshold value
        written in the Trscv EEPROM <Help>
        Warning indicating that the Trscv
        temperature is lower than the threshold
        value written in the Trscv EEPROM
        <Condtype> TRSCV1_TEMP_LOW_WNG_1
        <Probcause> temperatureUnacceptable
        (51) <Alarmtype>
        "
	  ::= { pm20002maAlmclientQsfpWarnDdm 3 }



pm20002maAlmTrscv1VccHighWng1 OBJECT-TYPE
	  SYNTAX EkiOnOff
	  MAX-ACCESS read-only
	  STATUS current
	  DESCRIPTION
        "
        Q1 Trscv Power Supply High Warning
        :This OID indicates that the Trscv
        power supply is higher than the
        threshold value written in the
         Trscv EEPROM <Help> Warning indicating
        that the Trscv power supply is
         higher than the threshold value
        written in the Trscv EEPROM <Condtype>
        TRSCV1_VCC_HIGH_WNG_1 <Probcause>
        powerProblem (36) <Alarmtype>
        "
	  ::= { pm20002maAlmclientQsfpWarnDdm 2 }



pm20002maAlmTrscv1VccLowWng1 OBJECT-TYPE
	  SYNTAX EkiOnOff
	  MAX-ACCESS read-only
	  STATUS current
	  DESCRIPTION
        "
        Q1 Trscv Power Supply Low Warning
        :This OID indicates that the Trscv
        power supply is lower than the
         threshold value written in the
        Trscv EEPROM <Help> Warning indicating
        that the Trscv power supply is
         lower than the threshold value
        written in the Trscv EEPROM <Condtype>
        TRSCV1_VCC_LOW_WNG_1 <Probcause>
        powerProblem (36) <Alarmtype>
        "
	  ::= { pm20002maAlmclientQsfpWarnDdm 1 }








--- *****************************************************
--- $$$$$$$$$$$$$$$$$$$$$$$$$$$$$$$$$$$$$$$$$$$$$$$$$$$$$
---     CONTROLS
--- $$$$$$$$$$$$$$$$$$$$$$$$$$$$$$$$$$$$$$$$$$$$$$$$$$$$$
--- *****************************************************



--- *****************************************************
---     LEAF for the confMgnt1 article
--- *****************************************************
pm20002maCtrlconfMgnt1 OBJECT IDENTIFIER ::= { pm20002maCtrlOther 1 }




pm20002maCtrlConf2Clear1 OBJECT-TYPE
	  SYNTAX EkiOnOff
	  MAX-ACCESS read-write
	  STATUS current
	  DESCRIPTION
        "
        Clear Configuration Tables :This
        OID clears the configuration tables
        from configuration2 in the flash.
         <Help>  This control restores
         the default configuration of the
        module
        "
	  ::= { pm20002maCtrlconfMgnt1 14 }



pm20002maCtrlConf2Flash1 OBJECT-TYPE
	  SYNTAX EkiOnOff
	  MAX-ACCESS read-write
	  STATUS current
	  DESCRIPTION
        "
        Write Configuration Tables :This
        OID saves the current configuration
        of the PM as configuration2 in
         the flash.  <Help>  This control
        saves the customer configuration
        on the module
        "
	  ::= { pm20002maCtrlconfMgnt1 10 }



pm20002maCtrlConf2Load1 OBJECT-TYPE
	  SYNTAX EkiOnOff
	  MAX-ACCESS read-write
	  STATUS current
	  DESCRIPTION
        "
        Load Configuration Tables Set
         Nb 2 :When set this OID enables
        loading from flash configuration2
        into the PM.
        "
	  ::= { pm20002maCtrlconfMgnt1 2 }



pm20002maCtrlConf1Load1 OBJECT-TYPE
	  SYNTAX EkiOnOff
	  MAX-ACCESS read-write
	  STATUS current
	  DESCRIPTION
        "
        Load Configuration Tables Set
         Nb 1 :When set this OID enables
        loading from flash configuration1
        into the PM.
        "
	  ::= { pm20002maCtrlconfMgnt1 1 }



--- *****************************************************
---     LEAF for the synth4 article
--- *****************************************************
pm20002maCtrlsynth4 OBJECT IDENTIFIER ::= { pm20002maCtrlOther 4 }




pm20002maCtrlCorrelatOff OBJECT-TYPE
	  SYNTAX EkiOnOff
	  MAX-ACCESS read-write
	  STATUS current
	  DESCRIPTION
        "
        Disable Alarm Correlation :This
        OID disables the alarm correlation
        in the PM.
        "
	  ::= { pm20002maCtrlsynth4 2 }



pm20002maCtrlCorrelatOn OBJECT-TYPE
	  SYNTAX EkiOnOff
	  MAX-ACCESS read-write
	  STATUS current
	  DESCRIPTION
        "
        Enable Alarm Correlation :This
        OID enables the alarm correlation
        in the PM.
        "
	  ::= { pm20002maCtrlsynth4 1 }



--- *****************************************************
---     LEAF for the swMgnt article
--- *****************************************************
pm20002maCtrlswMgnt OBJECT IDENTIFIER ::= { pm20002maCtrlOther 5 }




pm20002maCtrlLoadSwBank2 OBJECT-TYPE
	  SYNTAX EkiOnOff
	  MAX-ACCESS read-write
	  STATUS current
	  DESCRIPTION
        "
        Set Software Nb 2 As Active :This
        OID, when set, loads the SW from
        bank2 into the PM. It must be followed
        by a reset.  <Help>  This controls
        selects the second SW bank as the
        active bank for the next module
        reset
        "
	  ::= { pm20002maCtrlswMgnt 6 }



pm20002maCtrlLoadSwBank1 OBJECT-TYPE
	  SYNTAX EkiOnOff
	  MAX-ACCESS read-write
	  STATUS current
	  DESCRIPTION
        "
        Set Software Nb 1 As Active :This
        OID, when set, loads the SW from
        bank1 into the PM. It must be followed
        by a reset.  <Help>  This controls
        selects the first SW bank as the
        active bank for the next module
        reset
        "
	  ::= { pm20002maCtrlswMgnt 5 }



pm20002maCtrlWarmReset OBJECT-TYPE
	  SYNTAX EkiOnOff
	  MAX-ACCESS read-write
	  STATUS current
	  DESCRIPTION
        "
        PM Warm Reset :This OID, when
         set, causes a warm reset of the
        PM. This reset is not traffic affecting,
        and the configuration of PM remains
        unchanged.  <Help>  This control
        initiates a warm reset of the module.
        "
	  ::= { pm20002maCtrlswMgnt 3 }



pm20002maCtrlColdReset OBJECT-TYPE
	  SYNTAX EkiOnOff
	  MAX-ACCESS read-write
	  STATUS current
	  DESCRIPTION
        "
        PM Cold Reset :This OID, when
         set, causes a cold reset of the
        PM. This reset is traffic affecting,
        and the configuration of PM is
         reloaded on start-up.  <Help>
          This control initiates a cold
        reset of the module.
        "
	  ::= { pm20002maCtrlswMgnt 2 }



--- *****************************************************
---     LEAF for the gwMgnt article
--- *****************************************************
pm20002maCtrlgwMgnt OBJECT IDENTIFIER ::= { pm20002maCtrlOther 6 }




pm20002maCtrlLoadGwBank4 OBJECT-TYPE
	  SYNTAX EkiOnOff
	  MAX-ACCESS read-write
	  STATUS current
	  DESCRIPTION
        "
        Set Gateware Nb 4 As Active :This
        OID, when set, loads the GW from
        bank4 (Flash) into the PM. It is
        followed by an automatic gateware
        cold reset.
        "
	  ::= { pm20002maCtrlgwMgnt 8 }



pm20002maCtrlLoadGwBank3 OBJECT-TYPE
	  SYNTAX EkiOnOff
	  MAX-ACCESS read-write
	  STATUS current
	  DESCRIPTION
        "
        Set Gateware Nb 3 As Active :This
        OID, when set, loads the GW from
        bank3 (Flash) into the PM. It is
        followed by an automatic gateware
        cold reset.  <Help>  This controls
        initiates a cold reset of the module
        and select the third GW bank as
        the active bank
        "
	  ::= { pm20002maCtrlgwMgnt 7 }



pm20002maCtrlLoadGwBank2 OBJECT-TYPE
	  SYNTAX EkiOnOff
	  MAX-ACCESS read-write
	  STATUS current
	  DESCRIPTION
        "
        Set Gateware Nb 2 As Active :This
        OID, when set, loads the GW from
        bank2 (Flash) into the PM. It is
        followed by an automatic gateware
        cold reset.
        "
	  ::= { pm20002maCtrlgwMgnt 6 }



pm20002maCtrlLoadGwBank1 OBJECT-TYPE
	  SYNTAX EkiOnOff
	  MAX-ACCESS read-write
	  STATUS current
	  DESCRIPTION
        "
        Set Gateware Nb 1 As Active :This
        OID, when set, loads the GW from
        bank1 (Flash) into the PM. It is
        followed by an automatic gateware
        cold reset.  <Help>  This controls
        initiates a cold reset of the module
        and select the first GW bank as
        the active bank
        "
	  ::= { pm20002maCtrlgwMgnt 5 }



pm20002maCtrlCurrentGwReset OBJECT-TYPE
	  SYNTAX EkiOnOff
	  MAX-ACCESS read-write
	  STATUS current
	  DESCRIPTION
        "
        Active Gateware Reset :This OID,
        when set, resets the active gateware.
        It is traffic affecting.
        "
	  ::= { pm20002maCtrlgwMgnt 1 }



--- *********************************************************
---     TABLE for the pm20002maCtrlaccessLoop articles
--- *********************************************************

pm20002maCtrlaccessLoopTable OBJECT-TYPE
	SYNTAX  SEQUENCE OF Pm20002maCtrlaccessLoopEntry
	MAX-ACCESS not-accessible
	STATUS current
	DESCRIPTION
        "
        List of pm20002maCtrlaccessLoop
        Article
        "
	::= { pm20002maCtrlClient 16 }


pm20002maCtrlaccessLoopEntry OBJECT-TYPE
	SYNTAX Pm20002maCtrlaccessLoopEntry
	MAX-ACCESS not-accessible
	STATUS current
	DESCRIPTION
        "
        Row definition for the pm20002maCtrlaccessLoop
        table
        "
	INDEX   { pm20002maCtrlaccessLoopIndex }
	::= { pm20002maCtrlaccessLoopTable 1 }


Pm20002maCtrlaccessLoopEntry ::=
	SEQUENCE {
	pm20002maCtrlaccessLoopIndex
		INTEGER,
	pm20002maCtrlaccessLoopPortn
		EkiState
	}


pm20002maCtrlaccessLoopIndex OBJECT-TYPE
	SYNTAX  INTEGER(0..128)
	MAX-ACCESS  read-only
	STATUS current
	DESCRIPTION
        "
        Index definition for the pm20002maCtrlaccessLoop
        table
        "
	::= { pm20002maCtrlaccessLoopEntry 1 }


pm20002maCtrlaccessLoopPortn OBJECT-TYPE
	SYNTAX  EkiState
	MAX-ACCESS read-write
	STATUS current
	DESCRIPTION
        "
        Client Facility Loopback :This
        OID, when set at '1' puts the client
        port in loopback, looping the received
        10 Gb/s signal on the transmit
         10 Gb/s output.  <Help> This control
        enables the Out Loopback on the
        client port, looping the client
        input signal on the client output
        "
	::= { pm20002maCtrlaccessLoopEntry 2 }


--- *********************************************************
---     TABLE for the pm20002maCtrlclientLoopToLine articles
--- *********************************************************

pm20002maCtrlclientLoopToLineTable OBJECT-TYPE
	SYNTAX  SEQUENCE OF Pm20002maCtrlclientLoopToLineEntry
	MAX-ACCESS not-accessible
	STATUS current
	DESCRIPTION
        "
        List of pm20002maCtrlclientLoopToLine
        Article
        "
	::= { pm20002maCtrlClient 17 }


pm20002maCtrlclientLoopToLineEntry OBJECT-TYPE
	SYNTAX Pm20002maCtrlclientLoopToLineEntry
	MAX-ACCESS not-accessible
	STATUS current
	DESCRIPTION
        "
        Row definition for the pm20002maCtrlclientLoopToLine
        table
        "
	INDEX   { pm20002maCtrlclientLoopToLineIndex }
	::= { pm20002maCtrlclientLoopToLineTable 1 }


Pm20002maCtrlclientLoopToLineEntry ::=
	SEQUENCE {
	pm20002maCtrlclientLoopToLineIndex
		INTEGER,
	pm20002maCtrlclientLoopToLinePortn
		EkiState
	}


pm20002maCtrlclientLoopToLineIndex OBJECT-TYPE
	SYNTAX  INTEGER(0..128)
	MAX-ACCESS  read-only
	STATUS current
	DESCRIPTION
        "
        Index definition for the pm20002maCtrlclientLoopToLine
        table
        "
	::= { pm20002maCtrlclientLoopToLineEntry 1 }


pm20002maCtrlclientLoopToLinePortn OBJECT-TYPE
	SYNTAX  EkiState
	MAX-ACCESS read-write
	STATUS current
	DESCRIPTION
        "
        Client Terminal Loopback :This
        OID, when set, puts the client
         port in loop back, looping the
        10 Gb/s output signal on the 10
        Gb/s input.<Help> This control
         enables the In Loopback on the
        client port, looping the client
        output signal on the client input
        "
	::= { pm20002maCtrlclientLoopToLineEntry 2 }


--- *********************************************************
---     TABLE for the pm20002maCtrlcsfUpIns articles
--- *********************************************************

pm20002maCtrlcsfUpInsTable OBJECT-TYPE
	SYNTAX  SEQUENCE OF Pm20002maCtrlcsfUpInsEntry
	MAX-ACCESS not-accessible
	STATUS current
	DESCRIPTION
        "
        List of pm20002maCtrlcsfUpIns
         Article
        "
	::= { pm20002maCtrlClient 21 }


pm20002maCtrlcsfUpInsEntry OBJECT-TYPE
	SYNTAX Pm20002maCtrlcsfUpInsEntry
	MAX-ACCESS not-accessible
	STATUS current
	DESCRIPTION
        "
        Row definition for the pm20002maCtrlcsfUpIns
        table
        "
	INDEX   { pm20002maCtrlcsfUpInsIndex }
	::= { pm20002maCtrlcsfUpInsTable 1 }


Pm20002maCtrlcsfUpInsEntry ::=
	SEQUENCE {
	pm20002maCtrlcsfUpInsIndex
		INTEGER,
	pm20002maCtrlcsfUpInsPortn
		EkiState
	}


pm20002maCtrlcsfUpInsIndex OBJECT-TYPE
	SYNTAX  INTEGER(0..128)
	MAX-ACCESS  read-only
	STATUS current
	DESCRIPTION
        "
        Index definition for the pm20002maCtrlcsfUpIns
        table
        "
	::= { pm20002maCtrlcsfUpInsEntry 1 }


pm20002maCtrlcsfUpInsPortn OBJECT-TYPE
	SYNTAX  EkiState
	MAX-ACCESS read-write
	STATUS current
	DESCRIPTION
        "
        Client Signal Fail Insertion :This
        OID, when set, inserts  a client
        signal fail in the upstream client
        Port.  <Help>  This control inserts
        a Client Signal Fail for the client
        port
        "
	::= { pm20002maCtrlcsfUpInsEntry 2 }


--- *********************************************************
---     TABLE for the pm20002maCtrlcaisDwIns articles
--- *********************************************************

pm20002maCtrlcaisDwInsTable OBJECT-TYPE
	SYNTAX  SEQUENCE OF Pm20002maCtrlcaisDwInsEntry
	MAX-ACCESS not-accessible
	STATUS current
	DESCRIPTION
        "
        List of pm20002maCtrlcaisDwIns
        Article
        "
	::= { pm20002maCtrlClient 22 }


pm20002maCtrlcaisDwInsEntry OBJECT-TYPE
	SYNTAX Pm20002maCtrlcaisDwInsEntry
	MAX-ACCESS not-accessible
	STATUS current
	DESCRIPTION
        "
        Row definition for the pm20002maCtrlcaisDwIns
        table
        "
	INDEX   { pm20002maCtrlcaisDwInsIndex }
	::= { pm20002maCtrlcaisDwInsTable 1 }


Pm20002maCtrlcaisDwInsEntry ::=
	SEQUENCE {
	pm20002maCtrlcaisDwInsIndex
		INTEGER,
	pm20002maCtrlcaisDwInsPortn
		EkiState
	}


pm20002maCtrlcaisDwInsIndex OBJECT-TYPE
	SYNTAX  INTEGER(0..128)
	MAX-ACCESS  read-only
	STATUS current
	DESCRIPTION
        "
        Index definition for the pm20002maCtrlcaisDwIns
        table
        "
	::= { pm20002maCtrlcaisDwInsEntry 1 }


pm20002maCtrlcaisDwInsPortn OBJECT-TYPE
	SYNTAX  EkiState
	MAX-ACCESS read-write
	STATUS current
	DESCRIPTION
        "
        Client AIS Insertion :This OID,
        when set, inserts a client AIS
         on the downstream client Port.
         <Help>  This control inserts a
        Client AIS for the client port
        "
	::= { pm20002maCtrlcaisDwInsEntry 2 }


--- *********************************************************
---     TABLE for the pm20002maCtrlcommAccessLoop articles
--- *********************************************************

pm20002maCtrlcommAccessLoopTable OBJECT-TYPE
	SYNTAX  SEQUENCE OF Pm20002maCtrlcommAccessLoopEntry
	MAX-ACCESS not-accessible
	STATUS current
	DESCRIPTION
        "
        List of pm20002maCtrlcommAccessLoop
        Article
        "
	::= { pm20002maCtrlLine 64 }


pm20002maCtrlcommAccessLoopEntry OBJECT-TYPE
	SYNTAX Pm20002maCtrlcommAccessLoopEntry
	MAX-ACCESS not-accessible
	STATUS current
	DESCRIPTION
        "
        Row definition for the pm20002maCtrlcommAccessLoop
        table
        "
	INDEX   { pm20002maCtrlcommAccessLoopIndex }
	::= { pm20002maCtrlcommAccessLoopTable 1 }


Pm20002maCtrlcommAccessLoopEntry ::=
	SEQUENCE {
	pm20002maCtrlcommAccessLoopIndex
		INTEGER,
	pm20002maCtrlcommAccessLoopPortn
		EkiState
	}


pm20002maCtrlcommAccessLoopIndex OBJECT-TYPE
	SYNTAX  INTEGER(0..128)
	MAX-ACCESS  read-only
	STATUS current
	DESCRIPTION
        "
        Index definition for the pm20002maCtrlcommAccessLoop
        table
        "
	::= { pm20002maCtrlcommAccessLoopEntry 1 }


pm20002maCtrlcommAccessLoopPortn OBJECT-TYPE
	SYNTAX  EkiState
	MAX-ACCESS read-write
	STATUS current
	DESCRIPTION
        "
        Line Terminal Loopback :This OID,
        when set, puts the module in common
        access loop back, looping the 200
        Gb/s output signal on the 200 Gb/s
        input.<Help> This control enables
        the In Loopback on the line port,
        looping the 200 Gb/s output signal
        on the 200 Gb/s input
        "
	::= { pm20002maCtrlcommAccessLoopEntry 2 }


--- *********************************************************
---     TABLE for the pm20002maCtrllineLoop articles
--- *********************************************************

pm20002maCtrllineLoopTable OBJECT-TYPE
	SYNTAX  SEQUENCE OF Pm20002maCtrllineLoopEntry
	MAX-ACCESS not-accessible
	STATUS current
	DESCRIPTION
        "
        List of pm20002maCtrllineLoop
         Article
        "
	::= { pm20002maCtrlLine 66 }


pm20002maCtrllineLoopEntry OBJECT-TYPE
	SYNTAX Pm20002maCtrllineLoopEntry
	MAX-ACCESS not-accessible
	STATUS current
	DESCRIPTION
        "
        Row definition for the pm20002maCtrllineLoop
        table
        "
	INDEX   { pm20002maCtrllineLoopIndex }
	::= { pm20002maCtrllineLoopTable 1 }


Pm20002maCtrllineLoopEntry ::=
	SEQUENCE {
	pm20002maCtrllineLoopIndex
		INTEGER,
	pm20002maCtrllineLoopPortn
		EkiState
	}


pm20002maCtrllineLoopIndex OBJECT-TYPE
	SYNTAX  INTEGER(0..128)
	MAX-ACCESS  read-only
	STATUS current
	DESCRIPTION
        "
        Index definition for the pm20002maCtrllineLoop
        table
        "
	::= { pm20002maCtrllineLoopEntry 1 }


pm20002maCtrllineLoopPortn OBJECT-TYPE
	SYNTAX  EkiState
	MAX-ACCESS read-write
	STATUS current
	DESCRIPTION
        "
        Line Facility Loopback :This OID,
        when set at '1' puts the module
        in line loopback mode, looping
         the received 200 Gb/s signal on
        the transmit 200 Gb/s output. The
        Upstream part of the module is
         timed on the 200 Gb/s recovered
        clock in that case.<Help> This
         control enables the Out Loopback
        on the line port, looping the 200
        Gb/s input signal on the 200 Gb/s
        output
        "
	::= { pm20002maCtrllineLoopEntry 2 }


--- *********************************************************
---     TABLE for the pm20002maCtrlfecDisable articles
--- *********************************************************

pm20002maCtrlfecDisableTable OBJECT-TYPE
	SYNTAX  SEQUENCE OF Pm20002maCtrlfecDisableEntry
	MAX-ACCESS not-accessible
	STATUS current
	DESCRIPTION
        "
        List of pm20002maCtrlfecDisable
        Article
        "
	::= { pm20002maCtrlLine 69 }


pm20002maCtrlfecDisableEntry OBJECT-TYPE
	SYNTAX Pm20002maCtrlfecDisableEntry
	MAX-ACCESS not-accessible
	STATUS current
	DESCRIPTION
        "
        Row definition for the pm20002maCtrlfecDisable
        table
        "
	INDEX   { pm20002maCtrlfecDisableIndex }
	::= { pm20002maCtrlfecDisableTable 1 }


Pm20002maCtrlfecDisableEntry ::=
	SEQUENCE {
	pm20002maCtrlfecDisableIndex
		INTEGER,
	pm20002maCtrlfecDisablePortn
		EkiState
	}


pm20002maCtrlfecDisableIndex OBJECT-TYPE
	SYNTAX  INTEGER(0..128)
	MAX-ACCESS  read-only
	STATUS current
	DESCRIPTION
        "
        Index definition for the pm20002maCtrlfecDisable
        table
        "
	::= { pm20002maCtrlfecDisableEntry 1 }


pm20002maCtrlfecDisablePortn OBJECT-TYPE
	SYNTAX  EkiState
	MAX-ACCESS read-write
	STATUS current
	DESCRIPTION
        "
        Forward Error Correction Inhibition
        :This OID, when set, inhibits the
        Forward Error Correction feature
        on the line input  <Help>  This
        control enables/disables the Forward
        Error Correction on the line interface
        "
	::= { pm20002maCtrlfecDisableEntry 2 }


--- *****************************************************
---     LEAF for the ledTest article
--- *****************************************************
pm20002maCtrlledTest OBJECT IDENTIFIER ::= { pm20002maCtrlOther 192 }




pm20002maCtrlLedOff OBJECT-TYPE
	  SYNTAX EkiOnOff
	  MAX-ACCESS read-write
	  STATUS current
	  DESCRIPTION
        "
        Leds Off :This OID switches off
        all the Leds as a test feature.
         <Help>  This control initiates
        a test leds turning all the LEDs
        to OFF
        "
	  ::= { pm20002maCtrlledTest 3 }



pm20002maCtrlRedLed OBJECT-TYPE
	  SYNTAX EkiOnOff
	  MAX-ACCESS read-write
	  STATUS current
	  DESCRIPTION
        "
        Red Leds Test :This OID switches
        on all the red Leds as a test feature.
         <Help>  This control initiates
        a test leds turning all the LEDs
        to red
        "
	  ::= { pm20002maCtrlledTest 2 }



pm20002maCtrlGreenLed OBJECT-TYPE
	  SYNTAX EkiOnOff
	  MAX-ACCESS read-write
	  STATUS current
	  DESCRIPTION
        "
        Green Leds Test :This OID switches
        on all the green Leds as a test
        feature.  <Help>  This control
         initiates a test leds turning
         all the LEDs to green
        "
	  ::= { pm20002maCtrlledTest 1 }



--- *****************************************************
---     LEAF for the initSwitchMarvell article
--- *****************************************************
pm20002maCtrlinitSwitchMarvell OBJECT IDENTIFIER ::= { pm20002maCtrlOther 201 }




pm20002maCtrlInitSwitchMarvell OBJECT-TYPE
	  SYNTAX EkiOnOff
	  MAX-ACCESS read-write
	  STATUS current
	  DESCRIPTION
        "
        Switch Initialization :This OID
        operates an initialization of the
        switch managed through the module
         <Help>  This control activates
        an initialization of the switch
        managed through the module
        "
	  ::= { pm20002maCtrlinitSwitchMarvell 1 }



--- *********************************************************
---     TABLE for the pm20002maCtrlmsaLineLoop articles
--- *********************************************************

pm20002maCtrlmsaLineLoopTable OBJECT-TYPE
	SYNTAX  SEQUENCE OF Pm20002maCtrlmsaLineLoopEntry
	MAX-ACCESS not-accessible
	STATUS current
	DESCRIPTION
        "
        List of pm20002maCtrlmsaLineLoop
        Article
        "
	::= { pm20002maCtrlLine 209 }


pm20002maCtrlmsaLineLoopEntry OBJECT-TYPE
	SYNTAX Pm20002maCtrlmsaLineLoopEntry
	MAX-ACCESS not-accessible
	STATUS current
	DESCRIPTION
        "
        Row definition for the pm20002maCtrlmsaLineLoop
        table
        "
	INDEX   { pm20002maCtrlmsaLineLoopIndex }
	::= { pm20002maCtrlmsaLineLoopTable 1 }


Pm20002maCtrlmsaLineLoopEntry ::=
	SEQUENCE {
	pm20002maCtrlmsaLineLoopIndex
		INTEGER,
	pm20002maCtrlmsaLineLoopPortn
		EkiState
	}


pm20002maCtrlmsaLineLoopIndex OBJECT-TYPE
	SYNTAX  INTEGER(0..128)
	MAX-ACCESS  read-only
	STATUS current
	DESCRIPTION
        "
        Index definition for the pm20002maCtrlmsaLineLoop
        table
        "
	::= { pm20002maCtrlmsaLineLoopEntry 1 }


pm20002maCtrlmsaLineLoopPortn OBJECT-TYPE
	SYNTAX  EkiState
	MAX-ACCESS read-write
	STATUS current
	DESCRIPTION
        "
        MSA Line Loop :This OID operates
        a line loopback on the MSA Line
         <Help>  This control defines the
        line loop back of the line transceiver
        "
	::= { pm20002maCtrlmsaLineLoopEntry 2 }


--- *********************************************************
---     TABLE for the pm20002maCtrlmsaTxReset articles
--- *********************************************************

pm20002maCtrlmsaTxResetTable OBJECT-TYPE
	SYNTAX  SEQUENCE OF Pm20002maCtrlmsaTxResetEntry
	MAX-ACCESS not-accessible
	STATUS current
	DESCRIPTION
        "
        List of pm20002maCtrlmsaTxReset
        Article
        "
	::= { pm20002maCtrlLine 210 }


pm20002maCtrlmsaTxResetEntry OBJECT-TYPE
	SYNTAX Pm20002maCtrlmsaTxResetEntry
	MAX-ACCESS not-accessible
	STATUS current
	DESCRIPTION
        "
        Row definition for the pm20002maCtrlmsaTxReset
        table
        "
	INDEX   { pm20002maCtrlmsaTxResetIndex }
	::= { pm20002maCtrlmsaTxResetTable 1 }


Pm20002maCtrlmsaTxResetEntry ::=
	SEQUENCE {
	pm20002maCtrlmsaTxResetIndex
		INTEGER,
	pm20002maCtrlmsaTxResetPortn
		EkiState
	}


pm20002maCtrlmsaTxResetIndex OBJECT-TYPE
	SYNTAX  INTEGER(0..128)
	MAX-ACCESS  read-only
	STATUS current
	DESCRIPTION
        "
        Index definition for the pm20002maCtrlmsaTxReset
        table
        "
	::= { pm20002maCtrlmsaTxResetEntry 1 }


pm20002maCtrlmsaTxResetPortn OBJECT-TYPE
	SYNTAX  EkiState
	MAX-ACCESS read-write
	STATUS current
	DESCRIPTION
        "
        Line MSA TX Reset :This OID resets
        the TX portion of the MSA line
         module  <Help > This control
         initiates a reset of the transmitting
        side
        "
	::= { pm20002maCtrlmsaTxResetEntry 2 }


--- *********************************************************
---     TABLE for the pm20002maCtrlmsaRxReset articles
--- *********************************************************

pm20002maCtrlmsaRxResetTable OBJECT-TYPE
	SYNTAX  SEQUENCE OF Pm20002maCtrlmsaRxResetEntry
	MAX-ACCESS not-accessible
	STATUS current
	DESCRIPTION
        "
        List of pm20002maCtrlmsaRxReset
        Article
        "
	::= { pm20002maCtrlLine 211 }


pm20002maCtrlmsaRxResetEntry OBJECT-TYPE
	SYNTAX Pm20002maCtrlmsaRxResetEntry
	MAX-ACCESS not-accessible
	STATUS current
	DESCRIPTION
        "
        Row definition for the pm20002maCtrlmsaRxReset
        table
        "
	INDEX   { pm20002maCtrlmsaRxResetIndex }
	::= { pm20002maCtrlmsaRxResetTable 1 }


Pm20002maCtrlmsaRxResetEntry ::=
	SEQUENCE {
	pm20002maCtrlmsaRxResetIndex
		INTEGER,
	pm20002maCtrlmsaRxResetPortn
		EkiState
	}


pm20002maCtrlmsaRxResetIndex OBJECT-TYPE
	SYNTAX  INTEGER(0..128)
	MAX-ACCESS  read-only
	STATUS current
	DESCRIPTION
        "
        Index definition for the pm20002maCtrlmsaRxReset
        table
        "
	::= { pm20002maCtrlmsaRxResetEntry 1 }


pm20002maCtrlmsaRxResetPortn OBJECT-TYPE
	SYNTAX  EkiState
	MAX-ACCESS read-write
	STATUS current
	DESCRIPTION
        "
        Line MSA RX Reset :This OID resets
        the RX portion of the MSA line
         module  <Help > This control
         initiates a reset of the receiving
        side
        "
	::= { pm20002maCtrlmsaRxResetEntry 2 }


--- *********************************************************
---     TABLE for the pm20002maCtrlmsaShutdown articles
--- *********************************************************

pm20002maCtrlmsaShutdownTable OBJECT-TYPE
	SYNTAX  SEQUENCE OF Pm20002maCtrlmsaShutdownEntry
	MAX-ACCESS not-accessible
	STATUS current
	DESCRIPTION
        "
        List of pm20002maCtrlmsaShutdown
        Article
        "
	::= { pm20002maCtrlLine 212 }


pm20002maCtrlmsaShutdownEntry OBJECT-TYPE
	SYNTAX Pm20002maCtrlmsaShutdownEntry
	MAX-ACCESS not-accessible
	STATUS current
	DESCRIPTION
        "
        Row definition for the pm20002maCtrlmsaShutdown
        table
        "
	INDEX   { pm20002maCtrlmsaShutdownIndex }
	::= { pm20002maCtrlmsaShutdownTable 1 }


Pm20002maCtrlmsaShutdownEntry ::=
	SEQUENCE {
	pm20002maCtrlmsaShutdownIndex
		INTEGER,
	pm20002maCtrlmsaShutdownPortn
		EkiState
	}


pm20002maCtrlmsaShutdownIndex OBJECT-TYPE
	SYNTAX  INTEGER(0..128)
	MAX-ACCESS  read-only
	STATUS current
	DESCRIPTION
        "
        Index definition for the pm20002maCtrlmsaShutdown
        table
        "
	::= { pm20002maCtrlmsaShutdownEntry 1 }


pm20002maCtrlmsaShutdownPortn OBJECT-TYPE
	SYNTAX  EkiState
	MAX-ACCESS read-write
	STATUS current
	DESCRIPTION
        "
        Line MSA Shutdown :This OID enters
        a process to shutdown the MSA line
        module  <Help > This control  initiates
        a shutdown of the module
        "
	::= { pm20002maCtrlmsaShutdownEntry 2 }


--- *****************************************************
---     LEAF for the resetCount article
--- *****************************************************
pm20002maCtrlresetCount OBJECT IDENTIFIER ::= { pm20002maCtrlOther 259 }




pm20002maCtrlResetcount OBJECT-TYPE
	  SYNTAX EkiOnOff
	  MAX-ACCESS read-write
	  STATUS current
	  DESCRIPTION
        "
        Module Count Global Reset :This
        OID resets all the errors counters
        on the module  <Help > This control
         initiates a reset of the errors
        counters on the module
        "
	  ::= { pm20002maCtrlresetCount 1 }



--- *****************************************************
---     LEAF for the resetRmon article
--- *****************************************************
pm20002maCtrlresetRmon OBJECT IDENTIFIER ::= { pm20002maCtrlOther 260 }




pm20002maCtrlResetrmon OBJECT-TYPE
	  SYNTAX EkiOnOff
	  MAX-ACCESS read-write
	  STATUS current
	  DESCRIPTION
        "
        Module Rmon Global Reset :This
        OID resets all the Rmon counters
        on the module  <Help > This control
         initiates a reset of the Rmon
         counters on the module
        "
	  ::= { pm20002maCtrlresetRmon 1 }



--- *****************************************************
---     LEAF for the resetMeasurements article
--- *****************************************************
pm20002maCtrlresetMeasurements OBJECT IDENTIFIER ::= { pm20002maCtrlOther 261 }




pm20002maCtrlResetmeasurements OBJECT-TYPE
	  SYNTAX EkiOnOff
	  MAX-ACCESS read-write
	  STATUS current
	  DESCRIPTION
        "
        Management Meas Global Reset :This
        OID resets some measurements on
        the management  <Help > This control
         initiates a reset of some measurements
        on the management
        "
	  ::= { pm20002maCtrlresetMeasurements 1 }



--- *********************************************************
---     TABLE for the pm20002maCtrlclientResetAllCount articles
--- *********************************************************

pm20002maCtrlclientResetAllCountTable OBJECT-TYPE
	SYNTAX  SEQUENCE OF Pm20002maCtrlclientResetAllCountEntry
	MAX-ACCESS not-accessible
	STATUS current
	DESCRIPTION
        "
        List of pm20002maCtrlclientResetAllCount
        Article
        "
	::= { pm20002maCtrlClient 262 }


pm20002maCtrlclientResetAllCountEntry OBJECT-TYPE
	SYNTAX Pm20002maCtrlclientResetAllCountEntry
	MAX-ACCESS not-accessible
	STATUS current
	DESCRIPTION
        "
        Row definition for the pm20002maCtrlclientResetAllCount
        table
        "
	INDEX   { pm20002maCtrlclientResetAllCountIndex }
	::= { pm20002maCtrlclientResetAllCountTable 1 }


Pm20002maCtrlclientResetAllCountEntry ::=
	SEQUENCE {
	pm20002maCtrlclientResetAllCountIndex
		INTEGER,
	pm20002maCtrlclientResetAllCountsPortn
		EkiState
	}


pm20002maCtrlclientResetAllCountIndex OBJECT-TYPE
	SYNTAX  INTEGER(0..128)
	MAX-ACCESS  read-only
	STATUS current
	DESCRIPTION
        "
        Index definition for the pm20002maCtrlclientResetAllCount
        table
        "
	::= { pm20002maCtrlclientResetAllCountEntry 1 }


pm20002maCtrlclientResetAllCountsPortn OBJECT-TYPE
	SYNTAX  EkiState
	MAX-ACCESS read-write
	STATUS current
	DESCRIPTION
        "
        Client Counters Reset :This OID
        resets every counter on the client
        port  <Help>   This control operates
        a reset on the statistics current
        ,previous and history client port
        counters
        "
	::= { pm20002maCtrlclientResetAllCountEntry 2 }


--- *********************************************************
---     TABLE for the pm20002maCtrllineResetAllCount articles
--- *********************************************************

pm20002maCtrllineResetAllCountTable OBJECT-TYPE
	SYNTAX  SEQUENCE OF Pm20002maCtrllineResetAllCountEntry
	MAX-ACCESS not-accessible
	STATUS current
	DESCRIPTION
        "
        List of pm20002maCtrllineResetAllCount
        Article
        "
	::= { pm20002maCtrlLine 263 }


pm20002maCtrllineResetAllCountEntry OBJECT-TYPE
	SYNTAX Pm20002maCtrllineResetAllCountEntry
	MAX-ACCESS not-accessible
	STATUS current
	DESCRIPTION
        "
        Row definition for the pm20002maCtrllineResetAllCount
        table
        "
	INDEX   { pm20002maCtrllineResetAllCountIndex }
	::= { pm20002maCtrllineResetAllCountTable 1 }


Pm20002maCtrllineResetAllCountEntry ::=
	SEQUENCE {
	pm20002maCtrllineResetAllCountIndex
		INTEGER,
	pm20002maCtrllineResetAllCountsPortn
		EkiState
	}


pm20002maCtrllineResetAllCountIndex OBJECT-TYPE
	SYNTAX  INTEGER(0..128)
	MAX-ACCESS  read-only
	STATUS current
	DESCRIPTION
        "
        Index definition for the pm20002maCtrllineResetAllCount
        table
        "
	::= { pm20002maCtrllineResetAllCountEntry 1 }


pm20002maCtrllineResetAllCountsPortn OBJECT-TYPE
	SYNTAX  EkiState
	MAX-ACCESS read-write
	STATUS current
	DESCRIPTION
        "
        Line Counters Reset :This OID
         resets every counter on the line
        port  <Help>   This control operates
        a reset on the statistics current
        ,previous and history line port
        counters
        "
	::= { pm20002maCtrllineResetAllCountEntry 2 }







--- *****************************************************
--- $$$$$$$$$$$$$$$$$$$$$$$$$$$$$$$$$$$$$$$$$$$$$$$$$$$$$
---     COUNTERS
--- $$$$$$$$$$$$$$$$$$$$$$$$$$$$$$$$$$$$$$$$$$$$$$$$$$$$$
--- *****************************************************



--- *********************************************************
---     TABLE for the pm20002maCntclientInputErrorCounter articles
--- *********************************************************

pm20002maCntclientInputErrorCounterTable OBJECT-TYPE
	SYNTAX  SEQUENCE OF Pm20002maCntclientInputErrorCounterEntry
	MAX-ACCESS not-accessible
	STATUS current
	DESCRIPTION
        "
        List of pm20002maCntclientInputErrorCounter
        Article
        "
	::= { pm20002maCntClient 112 }


pm20002maCntclientInputErrorCounterEntry OBJECT-TYPE
	SYNTAX Pm20002maCntclientInputErrorCounterEntry
	MAX-ACCESS not-accessible
	STATUS current
	DESCRIPTION
        "
        Row definition for the pm20002maCntclientInputErrorCounter
        table
        "
	INDEX   { pm20002maCntclientInputErrorCounterIndex }
	::= { pm20002maCntclientInputErrorCounterTable 1 }


Pm20002maCntclientInputErrorCounterEntry ::=
	SEQUENCE {
	pm20002maCntclientInputErrorCounterIndex
		INTEGER,
	pm20002maCntclientInputErrorCounterValuePortn
		Counter32,
	pm20002maCntclientInputErrorCounterErrorPortn
		EkiOnOff,
	pm20002maCntclientInputErrorCounterOverloadPortn
		EkiOnOff
	}


pm20002maCntclientInputErrorCounterIndex OBJECT-TYPE
	SYNTAX  INTEGER(0..128)
	MAX-ACCESS  read-only
	STATUS current
	DESCRIPTION
        "
        Index definition for the pm20002maCntclientInputErrorCounter
        table
        "
	::= { pm20002maCntclientInputErrorCounterEntry 1 }


pm20002maCntclientInputErrorCounterValuePortn OBJECT-TYPE
	SYNTAX  Counter32
	MAX-ACCESS read-only
	STATUS current
	DESCRIPTION
        "
        Client Input Errors :This counter
        is increased each time a 10b/8b
        running disparity error is detected
        on the Client input stream  <Help>
         This counter gives the number
         of 10b/8b running disparity errors
        on the client port
        "
	::= { pm20002maCntclientInputErrorCounterEntry 2 }


pm20002maCntclientInputErrorCounterErrorPortn OBJECT-TYPE
	SYNTAX  EkiOnOff
	MAX-ACCESS read-only
	STATUS current
	DESCRIPTION
        "
        Client Counter Error :This OID
        when set indicates the client error
        counter value is invalid on Port
        "
	::= { pm20002maCntclientInputErrorCounterEntry 3 }


pm20002maCntclientInputErrorCounterOverloadPortn OBJECT-TYPE
	SYNTAX  EkiOnOff
	MAX-ACCESS read-only
	STATUS current
	DESCRIPTION
        "
        Client Counter Overload :This
         OID when set indicates a client
        input error counter overload on
        Port
        "
	::= { pm20002maCntclientInputErrorCounterEntry 4 }


--- *********************************************************
---     TABLE for the pm20002maCntclientCbipCounter articles
--- *********************************************************

pm20002maCntclientCbipCounterTable OBJECT-TYPE
	SYNTAX  SEQUENCE OF Pm20002maCntclientCbipCounterEntry
	MAX-ACCESS not-accessible
	STATUS current
	DESCRIPTION
        "
        List of pm20002maCntclientCbipCounter
        Article
        "
	::= { pm20002maCntClient 144 }


pm20002maCntclientCbipCounterEntry OBJECT-TYPE
	SYNTAX Pm20002maCntclientCbipCounterEntry
	MAX-ACCESS not-accessible
	STATUS current
	DESCRIPTION
        "
        Row definition for the pm20002maCntclientCbipCounter
        table
        "
	INDEX   { pm20002maCntclientCbipCounterIndex }
	::= { pm20002maCntclientCbipCounterTable 1 }


Pm20002maCntclientCbipCounterEntry ::=
	SEQUENCE {
	pm20002maCntclientCbipCounterIndex
		INTEGER,
	pm20002maCntclientCbipCounterValuePortn
		Counter32,
	pm20002maCntclientCbipCounterErrorPortn
		EkiOnOff,
	pm20002maCntclientCbipCounterOverloadPortn
		EkiOnOff
	}


pm20002maCntclientCbipCounterIndex OBJECT-TYPE
	SYNTAX  INTEGER(0..128)
	MAX-ACCESS  read-only
	STATUS current
	DESCRIPTION
        "
        Index definition for the pm20002maCntclientCbipCounter
        table
        "
	::= { pm20002maCntclientCbipCounterEntry 1 }


pm20002maCntclientCbipCounterValuePortn OBJECT-TYPE
	SYNTAX  Counter32
	MAX-ACCESS read-only
	STATUS current
	DESCRIPTION
        "
        Client Output Errors :This counter
        is incremented each time a CBIP
        parity error is detected on the
        Client output stream  <Help>  This
        counter gives the number of CBIP
        errors on the client port
        "
	::= { pm20002maCntclientCbipCounterEntry 2 }


pm20002maCntclientCbipCounterErrorPortn OBJECT-TYPE
	SYNTAX  EkiOnOff
	MAX-ACCESS read-only
	STATUS current
	DESCRIPTION
        "
        Client Counter Error :This OID
        when set indicates the CBIP error
        counter value is invalid on Port
        "
	::= { pm20002maCntclientCbipCounterEntry 3 }


pm20002maCntclientCbipCounterOverloadPortn OBJECT-TYPE
	SYNTAX  EkiOnOff
	MAX-ACCESS read-only
	STATUS current
	DESCRIPTION
        "
        Client CBIP Counter Overload :This
        OID when set indicates a CBIP error
        counter overload on Port
        "
	::= { pm20002maCntclientCbipCounterEntry 4 }


--- *********************************************************
---     TABLE for the pm20002maCntlocalLineSmBip8ErrorCounter articles
--- *********************************************************

pm20002maCntlocalLineSmBip8ErrorCounterTable OBJECT-TYPE
	SYNTAX  SEQUENCE OF Pm20002maCntlocalLineSmBip8ErrorCounterEntry
	MAX-ACCESS not-accessible
	STATUS current
	DESCRIPTION
        "
        List of pm20002maCntlocalLineSmBip8ErrorCounter
        Article
        "
	::= { pm20002maCntLine 192 }


pm20002maCntlocalLineSmBip8ErrorCounterEntry OBJECT-TYPE
	SYNTAX Pm20002maCntlocalLineSmBip8ErrorCounterEntry
	MAX-ACCESS not-accessible
	STATUS current
	DESCRIPTION
        "
        Row definition for the pm20002maCntlocalLineSmBip8ErrorCounter
        table
        "
	INDEX   { pm20002maCntlocalLineSmBip8ErrorCounterIndex }
	::= { pm20002maCntlocalLineSmBip8ErrorCounterTable 1 }


Pm20002maCntlocalLineSmBip8ErrorCounterEntry ::=
	SEQUENCE {
	pm20002maCntlocalLineSmBip8ErrorCounterIndex
		INTEGER,
	pm20002maCntlocalLineSmBip8ErrorCounterValuePortn
		Counter64,
	pm20002maCntlocalLineSmBip8ErrorCounterErrorPortn
		EkiOnOff,
	pm20002maCntlocalLineSmBip8ErrorCounterOverloadPortn
		EkiOnOff
	}


pm20002maCntlocalLineSmBip8ErrorCounterIndex OBJECT-TYPE
	SYNTAX  INTEGER(0..128)
	MAX-ACCESS  read-only
	STATUS current
	DESCRIPTION
        "
        Index definition for the pm20002maCntlocalLineSmBip8ErrorCounter
        table
        "
	::= { pm20002maCntlocalLineSmBip8ErrorCounterEntry 1 }


pm20002maCntlocalLineSmBip8ErrorCounterValuePortn OBJECT-TYPE
	SYNTAX  Counter64
	MAX-ACCESS read-only
	STATUS current
	DESCRIPTION
        "
        Uncorrected SD FEC Errors :This
        OID gives the current Bit Error
        Rate (residual SM-BIP8 error) after
        FEC   <Help> This counter gives
        the current Bit Error Rate (residual
        SM-BIP8 error) after FEC
        "
	::= { pm20002maCntlocalLineSmBip8ErrorCounterEntry 2 }


pm20002maCntlocalLineSmBip8ErrorCounterErrorPortn OBJECT-TYPE
	SYNTAX  EkiOnOff
	MAX-ACCESS read-only
	STATUS current
	DESCRIPTION
        "
        Line Counter Error :This OID when
        set indicates the B1 error counter
        value is invalid on Port
        "
	::= { pm20002maCntlocalLineSmBip8ErrorCounterEntry 3 }


pm20002maCntlocalLineSmBip8ErrorCounterOverloadPortn OBJECT-TYPE
	SYNTAX  EkiOnOff
	MAX-ACCESS read-only
	STATUS current
	DESCRIPTION
        "
        Line Counter Overload :This OID
        when set indicates a B1 error counter
        overload on Port
        "
	::= { pm20002maCntlocalLineSmBip8ErrorCounterEntry 4 }


--- *********************************************************
---     TABLE for the pm20002maCntlocalLineFecCorrectedErrorsCounter articles
--- *********************************************************

pm20002maCntlocalLineFecCorrectedErrorsCounterTable OBJECT-TYPE
	SYNTAX  SEQUENCE OF Pm20002maCntlocalLineFecCorrectedErrorsCounterEntry
	MAX-ACCESS not-accessible
	STATUS current
	DESCRIPTION
        "
        List of pm20002maCntlocalLineFecCorrectedErrorsCounter
        Article
        "
	::= { pm20002maCntLine 193 }


pm20002maCntlocalLineFecCorrectedErrorsCounterEntry OBJECT-TYPE
	SYNTAX Pm20002maCntlocalLineFecCorrectedErrorsCounterEntry
	MAX-ACCESS not-accessible
	STATUS current
	DESCRIPTION
        "
        Row definition for the pm20002maCntlocalLineFecCorrectedErrorsCounter
        table
        "
	INDEX   { pm20002maCntlocalLineFecCorrectedErrorsCounterIndex }
	::= { pm20002maCntlocalLineFecCorrectedErrorsCounterTable 1 }


Pm20002maCntlocalLineFecCorrectedErrorsCounterEntry ::=
	SEQUENCE {
	pm20002maCntlocalLineFecCorrectedErrorsCounterIndex
		INTEGER,
	pm20002maCntlocalLineFecCorrectedErrorsCounterValuePortn
		Counter64,
	pm20002maCntlocalLineFecCorrectedErrorsCounterErrorPortn
		EkiOnOff,
	pm20002maCntlocalLineFecCorrectedErrorsCounterOverloadPortn
		EkiOnOff
	}


pm20002maCntlocalLineFecCorrectedErrorsCounterIndex OBJECT-TYPE
	SYNTAX  INTEGER(0..128)
	MAX-ACCESS  read-only
	STATUS current
	DESCRIPTION
        "
        Index definition for the pm20002maCntlocalLineFecCorrectedErrorsCounter
        table
        "
	::= { pm20002maCntlocalLineFecCorrectedErrorsCounterEntry 1 }


pm20002maCntlocalLineFecCorrectedErrorsCounterValuePortn OBJECT-TYPE
	SYNTAX  Counter64
	MAX-ACCESS read-only
	STATUS current
	DESCRIPTION
        "
        Line Input HD FEC Corrected Errors
        :This OID gives the current Bit
        Error Rate before the Hard Decision
        FEC  <Help> This counter gives
         the current Bit Error Rate before
        the Hard Decision FEC
        "
	::= { pm20002maCntlocalLineFecCorrectedErrorsCounterEntry 2 }


pm20002maCntlocalLineFecCorrectedErrorsCounterErrorPortn OBJECT-TYPE
	SYNTAX  EkiOnOff
	MAX-ACCESS read-only
	STATUS current
	DESCRIPTION
        "
        FEC Counter Error :This bit when
        set indicates the FEC corrected
        errors counter value is invalid
        on Line
        "
	::= { pm20002maCntlocalLineFecCorrectedErrorsCounterEntry 3 }


pm20002maCntlocalLineFecCorrectedErrorsCounterOverloadPortn OBJECT-TYPE
	SYNTAX  EkiOnOff
	MAX-ACCESS read-only
	STATUS current
	DESCRIPTION
        "
        FEC Counter Overload :This bit
        when set indicates a FEC corrected
        errors counter overload on Line
        "
	::= { pm20002maCntlocalLineFecCorrectedErrorsCounterEntry 4 }


--- *********************************************************
---     TABLE for the pm20002maCntremoteLineSmBip8ErrorCounter articles
--- *********************************************************

pm20002maCntremoteLineSmBip8ErrorCounterTable OBJECT-TYPE
	SYNTAX  SEQUENCE OF Pm20002maCntremoteLineSmBip8ErrorCounterEntry
	MAX-ACCESS not-accessible
	STATUS current
	DESCRIPTION
        "
        List of pm20002maCntremoteLineSmBip8ErrorCounter
        Article
        "
	::= { pm20002maCntLine 194 }


pm20002maCntremoteLineSmBip8ErrorCounterEntry OBJECT-TYPE
	SYNTAX Pm20002maCntremoteLineSmBip8ErrorCounterEntry
	MAX-ACCESS not-accessible
	STATUS current
	DESCRIPTION
        "
        Row definition for the pm20002maCntremoteLineSmBip8ErrorCounter
        table
        "
	INDEX   { pm20002maCntremoteLineSmBip8ErrorCounterIndex }
	::= { pm20002maCntremoteLineSmBip8ErrorCounterTable 1 }


Pm20002maCntremoteLineSmBip8ErrorCounterEntry ::=
	SEQUENCE {
	pm20002maCntremoteLineSmBip8ErrorCounterIndex
		INTEGER,
	pm20002maCntremoteLineSmBip8ErrorCounterValuePortn
		Counter64,
	pm20002maCntremoteLineSmBip8ErrorCounterErrorPortn
		EkiOnOff,
	pm20002maCntremoteLineSmBip8ErrorCounterOverloadPortn
		EkiOnOff
	}


pm20002maCntremoteLineSmBip8ErrorCounterIndex OBJECT-TYPE
	SYNTAX  INTEGER(0..128)
	MAX-ACCESS  read-only
	STATUS current
	DESCRIPTION
        "
        Index definition for the pm20002maCntremoteLineSmBip8ErrorCounter
        table
        "
	::= { pm20002maCntremoteLineSmBip8ErrorCounterEntry 1 }


pm20002maCntremoteLineSmBip8ErrorCounterValuePortn OBJECT-TYPE
	SYNTAX  Counter64
	MAX-ACCESS read-only
	STATUS current
	DESCRIPTION
        "
        Remote SM BIP8 :This OID gives
        the current Bit Error Rate (residual
        SM-BIP8 error) after FEC on the
        remote side  <Help> This counter
        gives the current Bit Error Rate
        (residual SM-BIP8 error) after
         FEC on the remote side
        "
	::= { pm20002maCntremoteLineSmBip8ErrorCounterEntry 2 }


pm20002maCntremoteLineSmBip8ErrorCounterErrorPortn OBJECT-TYPE
	SYNTAX  EkiOnOff
	MAX-ACCESS read-only
	STATUS current
	DESCRIPTION
        "
        Remote Counter Error :
        "
	::= { pm20002maCntremoteLineSmBip8ErrorCounterEntry 3 }


pm20002maCntremoteLineSmBip8ErrorCounterOverloadPortn OBJECT-TYPE
	SYNTAX  EkiOnOff
	MAX-ACCESS read-only
	STATUS current
	DESCRIPTION
        "
        Remote Counter Overload :
        "
	::= { pm20002maCntremoteLineSmBip8ErrorCounterEntry 4 }


--- *********************************************************
---     TABLE for the pm20002maCntlineDfrmTimCnt articles
--- *********************************************************

pm20002maCntlineDfrmTimCntTable OBJECT-TYPE
	SYNTAX  SEQUENCE OF Pm20002maCntlineDfrmTimCntEntry
	MAX-ACCESS not-accessible
	STATUS current
	DESCRIPTION
        "
        List of pm20002maCntlineDfrmTimCnt
        Article
        "
	::= { pm20002maCntLine 195 }


pm20002maCntlineDfrmTimCntEntry OBJECT-TYPE
	SYNTAX Pm20002maCntlineDfrmTimCntEntry
	MAX-ACCESS not-accessible
	STATUS current
	DESCRIPTION
        "
        Row definition for the pm20002maCntlineDfrmTimCnt
        table
        "
	INDEX   { pm20002maCntlineDfrmTimCntIndex }
	::= { pm20002maCntlineDfrmTimCntTable 1 }


Pm20002maCntlineDfrmTimCntEntry ::=
	SEQUENCE {
	pm20002maCntlineDfrmTimCntIndex
		INTEGER,
	pm20002maCntlineDfrmTimCntValuePortn
		Counter64,
	pm20002maCntlineDfrmTimCntErrorPortn
		EkiOnOff,
	pm20002maCntlineDfrmTimCntOverloadPortn
		EkiOnOff
	}


pm20002maCntlineDfrmTimCntIndex OBJECT-TYPE
	SYNTAX  INTEGER(0..128)
	MAX-ACCESS  read-only
	STATUS current
	DESCRIPTION
        "
        Index definition for the pm20002maCntlineDfrmTimCnt
        table
        "
	::= { pm20002maCntlineDfrmTimCntEntry 1 }


pm20002maCntlineDfrmTimCntValuePortn OBJECT-TYPE
	SYNTAX  Counter64
	MAX-ACCESS read-only
	STATUS current
	DESCRIPTION
        "
        Line Timer Counter :
        "
	::= { pm20002maCntlineDfrmTimCntEntry 2 }


pm20002maCntlineDfrmTimCntErrorPortn OBJECT-TYPE
	SYNTAX  EkiOnOff
	MAX-ACCESS read-only
	STATUS current
	DESCRIPTION
        "
        Line Counter Error :This OID when
        set indicates the deframer timer
        counter value is invalid on Port
        "
	::= { pm20002maCntlineDfrmTimCntEntry 3 }


pm20002maCntlineDfrmTimCntOverloadPortn OBJECT-TYPE
	SYNTAX  EkiOnOff
	MAX-ACCESS read-only
	STATUS current
	DESCRIPTION
        "
        Line Counter Overload :This OID
        when set indicates a deframer timer
        counter overload on Port
        "
	::= { pm20002maCntlineDfrmTimCntEntry 4 }


--- *********************************************************
---     TABLE for the pm20002maCntlocalLineTrscvPreSdFecErrorCounter articles
--- *********************************************************

pm20002maCntlocalLineTrscvPreSdFecErrorCounterTable OBJECT-TYPE
	SYNTAX  SEQUENCE OF Pm20002maCntlocalLineTrscvPreSdFecErrorCounterEntry
	MAX-ACCESS not-accessible
	STATUS current
	DESCRIPTION
        "
        List of pm20002maCntlocalLineTrscvPreSdFecErrorCounter
        Article
        "
	::= { pm20002maCntLine 196 }


pm20002maCntlocalLineTrscvPreSdFecErrorCounterEntry OBJECT-TYPE
	SYNTAX Pm20002maCntlocalLineTrscvPreSdFecErrorCounterEntry
	MAX-ACCESS not-accessible
	STATUS current
	DESCRIPTION
        "
        Row definition for the pm20002maCntlocalLineTrscvPreSdFecErrorCounter
        table
        "
	INDEX   { pm20002maCntlocalLineTrscvPreSdFecErrorCounterIndex }
	::= { pm20002maCntlocalLineTrscvPreSdFecErrorCounterTable 1 }


Pm20002maCntlocalLineTrscvPreSdFecErrorCounterEntry ::=
	SEQUENCE {
	pm20002maCntlocalLineTrscvPreSdFecErrorCounterIndex
		INTEGER,
	pm20002maCntlocalLineTrscvPreSdFecErrorCounterValuePortn
		Counter64,
	pm20002maCntlocalLineTrscvPreSdFecErrorCounterErrorPortn
		EkiOnOff,
	pm20002maCntlocalLineTrscvPreSdFecErrorCounterOverloadPortn
		EkiOnOff
	}


pm20002maCntlocalLineTrscvPreSdFecErrorCounterIndex OBJECT-TYPE
	SYNTAX  INTEGER(0..128)
	MAX-ACCESS  read-only
	STATUS current
	DESCRIPTION
        "
        Index definition for the pm20002maCntlocalLineTrscvPreSdFecErrorCounter
        table
        "
	::= { pm20002maCntlocalLineTrscvPreSdFecErrorCounterEntry 1 }


pm20002maCntlocalLineTrscvPreSdFecErrorCounterValuePortn OBJECT-TYPE
	SYNTAX  Counter64
	MAX-ACCESS read-only
	STATUS current
	DESCRIPTION
        "
        Pre-SD FEC Errors :This OID gives
        the current Bit Error Rate before
        the Soft Decision FEC  <Help> This
        counter gives the current Bit Error
        Rate before the Soft Decision FEC
        "
	::= { pm20002maCntlocalLineTrscvPreSdFecErrorCounterEntry 2 }


pm20002maCntlocalLineTrscvPreSdFecErrorCounterErrorPortn OBJECT-TYPE
	SYNTAX  EkiOnOff
	MAX-ACCESS read-only
	STATUS current
	DESCRIPTION
        "
        Line Counter Error :This OID when
        set indicates the deframer timer
        counter value is invalid on Port
        "
	::= { pm20002maCntlocalLineTrscvPreSdFecErrorCounterEntry 3 }


pm20002maCntlocalLineTrscvPreSdFecErrorCounterOverloadPortn OBJECT-TYPE
	SYNTAX  EkiOnOff
	MAX-ACCESS read-only
	STATUS current
	DESCRIPTION
        "
        Line Counter Overload :This OID
        when set indicates a deframer timer
        counter overload on Port
        "
	::= { pm20002maCntlocalLineTrscvPreSdFecErrorCounterEntry 4 }


--- *********************************************************
---     TABLE for the pm20002maCntlocalLineTrscvUncorrectedSdFecErrorCounter articles
--- *********************************************************

pm20002maCntlocalLineTrscvUncorrectedSdFecErrorCounterTable OBJECT-TYPE
	SYNTAX  SEQUENCE OF Pm20002maCntlocalLineTrscvUncorrectedSdFecErrorCounterEntry
	MAX-ACCESS not-accessible
	STATUS current
	DESCRIPTION
        "
        List of pm20002maCntlocalLineTrscvUncorrectedSdFecErrorCounter
        Article
        "
	::= { pm20002maCntLine 197 }


pm20002maCntlocalLineTrscvUncorrectedSdFecErrorCounterEntry OBJECT-TYPE
	SYNTAX Pm20002maCntlocalLineTrscvUncorrectedSdFecErrorCounterEntry
	MAX-ACCESS not-accessible
	STATUS current
	DESCRIPTION
        "
        Row definition for the pm20002maCntlocalLineTrscvUncorrectedSdFecErrorCounter
        table
        "
	INDEX   { pm20002maCntlocalLineTrscvUncorrectedSdFecErrorCounterIndex }
	::= { pm20002maCntlocalLineTrscvUncorrectedSdFecErrorCounterTable 1 }


Pm20002maCntlocalLineTrscvUncorrectedSdFecErrorCounterEntry ::=
	SEQUENCE {
	pm20002maCntlocalLineTrscvUncorrectedSdFecErrorCounterIndex
		INTEGER,
	pm20002maCntlocalLineTrscvUncorrectedSdFecErrorCounterValuePortn
		Counter64,
	pm20002maCntlocalLineTrscvUncorrectedSdFecErrorCounterErrorPortn
		EkiOnOff,
	pm20002maCntlocalLineTrscvUncorrectedSdFecErrorCounterOverloadPortn
		EkiOnOff
	}


pm20002maCntlocalLineTrscvUncorrectedSdFecErrorCounterIndex OBJECT-TYPE
	SYNTAX  INTEGER(0..128)
	MAX-ACCESS  read-only
	STATUS current
	DESCRIPTION
        "
        Index definition for the pm20002maCntlocalLineTrscvUncorrectedSdFecErrorCounter
        table
        "
	::= { pm20002maCntlocalLineTrscvUncorrectedSdFecErrorCounterEntry 1 }


pm20002maCntlocalLineTrscvUncorrectedSdFecErrorCounterValuePortn OBJECT-TYPE
	SYNTAX  Counter64
	MAX-ACCESS read-only
	STATUS current
	DESCRIPTION
        "
        Uncorrected SD FEC Errors :This
        OID gives the current Bit Error
        Rate after the Soft Decision FEC
        (residual)  <Help> This counter
        gives the current Bit Error Rate
        after the Soft Decision FEC (residual)
        "
	::= { pm20002maCntlocalLineTrscvUncorrectedSdFecErrorCounterEntry 2 }


pm20002maCntlocalLineTrscvUncorrectedSdFecErrorCounterErrorPortn OBJECT-TYPE
	SYNTAX  EkiOnOff
	MAX-ACCESS read-only
	STATUS current
	DESCRIPTION
        "
        Line Counter Error :This OID when
        set indicates the deframer timer
        counter value is invalid on Port
        "
	::= { pm20002maCntlocalLineTrscvUncorrectedSdFecErrorCounterEntry 3 }


pm20002maCntlocalLineTrscvUncorrectedSdFecErrorCounterOverloadPortn OBJECT-TYPE
	SYNTAX  EkiOnOff
	MAX-ACCESS read-only
	STATUS current
	DESCRIPTION
        "
        Line Counter Overload :This OID
        when set indicates a deframer timer
        counter overload on Port
        "
	::= { pm20002maCntlocalLineTrscvUncorrectedSdFecErrorCounterEntry 4 }


--- *********************************************************
---     TABLE for the pm20002maCntlocalLineTrscvPreSdFecBitCounter articles
--- *********************************************************

pm20002maCntlocalLineTrscvPreSdFecBitCounterTable OBJECT-TYPE
	SYNTAX  SEQUENCE OF Pm20002maCntlocalLineTrscvPreSdFecBitCounterEntry
	MAX-ACCESS not-accessible
	STATUS current
	DESCRIPTION
        "
        List of pm20002maCntlocalLineTrscvPreSdFecBitCounter
        Article
        "
	::= { pm20002maCntLine 198 }


pm20002maCntlocalLineTrscvPreSdFecBitCounterEntry OBJECT-TYPE
	SYNTAX Pm20002maCntlocalLineTrscvPreSdFecBitCounterEntry
	MAX-ACCESS not-accessible
	STATUS current
	DESCRIPTION
        "
        Row definition for the pm20002maCntlocalLineTrscvPreSdFecBitCounter
        table
        "
	INDEX   { pm20002maCntlocalLineTrscvPreSdFecBitCounterIndex }
	::= { pm20002maCntlocalLineTrscvPreSdFecBitCounterTable 1 }


Pm20002maCntlocalLineTrscvPreSdFecBitCounterEntry ::=
	SEQUENCE {
	pm20002maCntlocalLineTrscvPreSdFecBitCounterIndex
		INTEGER,
	pm20002maCntlocalLineTrscvPreSdFecBitCounterValuePortn
		Counter64,
	pm20002maCntlocalLineTrscvPreSdFecBitCounterErrorPortn
		EkiOnOff,
	pm20002maCntlocalLineTrscvPreSdFecBitCounterOverloadPortn
		EkiOnOff
	}


pm20002maCntlocalLineTrscvPreSdFecBitCounterIndex OBJECT-TYPE
	SYNTAX  INTEGER(0..128)
	MAX-ACCESS  read-only
	STATUS current
	DESCRIPTION
        "
        Index definition for the pm20002maCntlocalLineTrscvPreSdFecBitCounter
        table
        "
	::= { pm20002maCntlocalLineTrscvPreSdFecBitCounterEntry 1 }


pm20002maCntlocalLineTrscvPreSdFecBitCounterValuePortn OBJECT-TYPE
	SYNTAX  Counter64
	MAX-ACCESS read-only
	STATUS current
	DESCRIPTION
        "
        Pre-SD FEC Bit Counter :This OID
        gives the current Bit count before
        the Soft Decision FEC  <Help> This
        counter gives the current Bit Count
        before the Soft Decision FEC
        "
	::= { pm20002maCntlocalLineTrscvPreSdFecBitCounterEntry 2 }


pm20002maCntlocalLineTrscvPreSdFecBitCounterErrorPortn OBJECT-TYPE
	SYNTAX  EkiOnOff
	MAX-ACCESS read-only
	STATUS current
	DESCRIPTION
        "
        Line Counter Error :This OID when
        set indicates the deframer timer
        counter value is invalid on Port
        "
	::= { pm20002maCntlocalLineTrscvPreSdFecBitCounterEntry 3 }


pm20002maCntlocalLineTrscvPreSdFecBitCounterOverloadPortn OBJECT-TYPE
	SYNTAX  EkiOnOff
	MAX-ACCESS read-only
	STATUS current
	DESCRIPTION
        "
        Line Counter Overload :This OID
        when set indicates a deframer timer
        counter overload on Port
        "
	::= { pm20002maCntlocalLineTrscvPreSdFecBitCounterEntry 4 }


--- *********************************************************
---     TABLE for the pm20002maCntlocalLineTrscvUncorrectedSdFecBitCounter articles
--- *********************************************************

pm20002maCntlocalLineTrscvUncorrectedSdFecBitCounterTable OBJECT-TYPE
	SYNTAX  SEQUENCE OF Pm20002maCntlocalLineTrscvUncorrectedSdFecBitCounterEntry
	MAX-ACCESS not-accessible
	STATUS current
	DESCRIPTION
        "
        List of pm20002maCntlocalLineTrscvUncorrectedSdFecBitCounter
        Article
        "
	::= { pm20002maCntLine 199 }


pm20002maCntlocalLineTrscvUncorrectedSdFecBitCounterEntry OBJECT-TYPE
	SYNTAX Pm20002maCntlocalLineTrscvUncorrectedSdFecBitCounterEntry
	MAX-ACCESS not-accessible
	STATUS current
	DESCRIPTION
        "
        Row definition for the pm20002maCntlocalLineTrscvUncorrectedSdFecBitCounter
        table
        "
	INDEX   { pm20002maCntlocalLineTrscvUncorrectedSdFecBitCounterIndex }
	::= { pm20002maCntlocalLineTrscvUncorrectedSdFecBitCounterTable 1 }


Pm20002maCntlocalLineTrscvUncorrectedSdFecBitCounterEntry ::=
	SEQUENCE {
	pm20002maCntlocalLineTrscvUncorrectedSdFecBitCounterIndex
		INTEGER,
	pm20002maCntlocalLineTrscvUncorrectedSdFecBitCounterValuePortn
		Counter64,
	pm20002maCntlocalLineTrscvUncorrectedSdFecBitCounterErrorPortn
		EkiOnOff,
	pm20002maCntlocalLineTrscvUncorrectedSdFecBitCounterOverloadPortn
		EkiOnOff
	}


pm20002maCntlocalLineTrscvUncorrectedSdFecBitCounterIndex OBJECT-TYPE
	SYNTAX  INTEGER(0..128)
	MAX-ACCESS  read-only
	STATUS current
	DESCRIPTION
        "
        Index definition for the pm20002maCntlocalLineTrscvUncorrectedSdFecBitCounter
        table
        "
	::= { pm20002maCntlocalLineTrscvUncorrectedSdFecBitCounterEntry 1 }


pm20002maCntlocalLineTrscvUncorrectedSdFecBitCounterValuePortn OBJECT-TYPE
	SYNTAX  Counter64
	MAX-ACCESS read-only
	STATUS current
	DESCRIPTION
        "
        Uncorrected SD FEC Bit Counter
        :This OID gives the current Bit
        count after the Soft Decision FEC
        (residual)  <Help> This counter
        gives the current Bit Count after
        the Soft Decision FEC (residual)
        "
	::= { pm20002maCntlocalLineTrscvUncorrectedSdFecBitCounterEntry 2 }


pm20002maCntlocalLineTrscvUncorrectedSdFecBitCounterErrorPortn OBJECT-TYPE
	SYNTAX  EkiOnOff
	MAX-ACCESS read-only
	STATUS current
	DESCRIPTION
        "
        Line Counter Error :This OID when
        set indicates the deframer timer
        counter value is invalid on Port
        "
	::= { pm20002maCntlocalLineTrscvUncorrectedSdFecBitCounterEntry 3 }


pm20002maCntlocalLineTrscvUncorrectedSdFecBitCounterOverloadPortn OBJECT-TYPE
	SYNTAX  EkiOnOff
	MAX-ACCESS read-only
	STATUS current
	DESCRIPTION
        "
        Line Counter Overload :This OID
        when set indicates a deframer timer
        counter overload on Port
        "
	::= { pm20002maCntlocalLineTrscvUncorrectedSdFecBitCounterEntry 4 }







--- *****************************************************
--- $$$$$$$$$$$$$$$$$$$$$$$$$$$$$$$$$$$$$$$$$$$$$$$$$$$$$
---     RMON - 64 bits COUNTERS
--- $$$$$$$$$$$$$$$$$$$$$$$$$$$$$$$$$$$$$$$$$$$$$$$$$$$$$
--- *****************************************************



--- *********************************************************
---     TABLE for the pm20002maMonupRmonBytesCounterClientInput articles
--- *********************************************************

pm20002maMonupRmonBytesCounterClientInputTable OBJECT-TYPE
	SYNTAX  SEQUENCE OF Pm20002maMonupRmonBytesCounterClientInputEntry
	MAX-ACCESS not-accessible
	STATUS current
	DESCRIPTION
        "
        List of pm20002maMonupRmonBytesCounterClientInput
        Article
        "
	::= { pm20002maMonClientRmonCounter 16 }


pm20002maMonupRmonBytesCounterClientInputEntry OBJECT-TYPE
	SYNTAX Pm20002maMonupRmonBytesCounterClientInputEntry
	MAX-ACCESS not-accessible
	STATUS current
	DESCRIPTION
        "
        Row definition for the pm20002maMonupRmonBytesCounterClientInput
        table
        "
	INDEX   { pm20002maMonupRmonBytesCounterClientInputIndex }
	::= { pm20002maMonupRmonBytesCounterClientInputTable 1 }


Pm20002maMonupRmonBytesCounterClientInputEntry ::=
	SEQUENCE {
	pm20002maMonupRmonBytesCounterClientInputIndex
		INTEGER,
	pm20002maMonupRmonBytesCounterClientInputValuePortn
		Counter64,
	pm20002maMonupRmonBytesCounterClientInputErrorPortn
		EkiOnOff,
	pm20002maMonupRmonBytesCounterClientInputOverloadPortn
		EkiOnOff
	}


pm20002maMonupRmonBytesCounterClientInputIndex OBJECT-TYPE
	SYNTAX  INTEGER(0..128)
	MAX-ACCESS  read-only
	STATUS current
	DESCRIPTION
        "
        Index definition for the pm20002maMonupRmonBytesCounterClientInput
        table
        "
	::= { pm20002maMonupRmonBytesCounterClientInputEntry 1 }


pm20002maMonupRmonBytesCounterClientInputValuePortn OBJECT-TYPE
	SYNTAX  Counter64
	MAX-ACCESS read-only
	STATUS current
	DESCRIPTION
        "
        Client Input Bytes :This counter
        is increased each time a data byte
        is received on the client port
          <Help>  This counter gives the
        number of bytes received on the
        client port
        "
	::= { pm20002maMonupRmonBytesCounterClientInputEntry 2 }


pm20002maMonupRmonBytesCounterClientInputErrorPortn OBJECT-TYPE
	SYNTAX  EkiOnOff
	MAX-ACCESS read-only
	STATUS current
	DESCRIPTION
        "
        Bytes Counter Error :This OID
         when set indicates the Bytes counter
        value is invalid on client port
        "
	::= { pm20002maMonupRmonBytesCounterClientInputEntry 3 }


pm20002maMonupRmonBytesCounterClientInputOverloadPortn OBJECT-TYPE
	SYNTAX  EkiOnOff
	MAX-ACCESS read-only
	STATUS current
	DESCRIPTION
        "
        Bytes Counter Overload :This OID
        when set indicates a Bytes counter
        overload on client port
        "
	::= { pm20002maMonupRmonBytesCounterClientInputEntry 4 }


--- *********************************************************
---     TABLE for the pm20002maMonupRmonCrcErrorsCounterClientInput articles
--- *********************************************************

pm20002maMonupRmonCrcErrorsCounterClientInputTable OBJECT-TYPE
	SYNTAX  SEQUENCE OF Pm20002maMonupRmonCrcErrorsCounterClientInputEntry
	MAX-ACCESS not-accessible
	STATUS current
	DESCRIPTION
        "
        List of pm20002maMonupRmonCrcErrorsCounterClientInput
        Article
        "
	::= { pm20002maMonClientRmonCounter 48 }


pm20002maMonupRmonCrcErrorsCounterClientInputEntry OBJECT-TYPE
	SYNTAX Pm20002maMonupRmonCrcErrorsCounterClientInputEntry
	MAX-ACCESS not-accessible
	STATUS current
	DESCRIPTION
        "
        Row definition for the pm20002maMonupRmonCrcErrorsCounterClientInput
        table
        "
	INDEX   { pm20002maMonupRmonCrcErrorsCounterClientInputIndex }
	::= { pm20002maMonupRmonCrcErrorsCounterClientInputTable 1 }


Pm20002maMonupRmonCrcErrorsCounterClientInputEntry ::=
	SEQUENCE {
	pm20002maMonupRmonCrcErrorsCounterClientInputIndex
		INTEGER,
	pm20002maMonupRmonCrcErrorsCounterClientInputValuePortn
		Counter64,
	pm20002maMonupRmonCrcErrorsCounterClientInputErrorPortn
		EkiOnOff,
	pm20002maMonupRmonCrcErrorsCounterClientInputOverloadPortn
		EkiOnOff
	}


pm20002maMonupRmonCrcErrorsCounterClientInputIndex OBJECT-TYPE
	SYNTAX  INTEGER(0..128)
	MAX-ACCESS  read-only
	STATUS current
	DESCRIPTION
        "
        Index definition for the pm20002maMonupRmonCrcErrorsCounterClientInput
        table
        "
	::= { pm20002maMonupRmonCrcErrorsCounterClientInputEntry 1 }


pm20002maMonupRmonCrcErrorsCounterClientInputValuePortn OBJECT-TYPE
	SYNTAX  Counter64
	MAX-ACCESS read-only
	STATUS current
	DESCRIPTION
        "
        Client Input CRC Errors :This
         counter is increased each time
        a CRC error is detected on the
         client port<Help>  This counter
        gives the number of CRC Errors
         received on the client port
        "
	::= { pm20002maMonupRmonCrcErrorsCounterClientInputEntry 2 }


pm20002maMonupRmonCrcErrorsCounterClientInputErrorPortn OBJECT-TYPE
	SYNTAX  EkiOnOff
	MAX-ACCESS read-only
	STATUS current
	DESCRIPTION
        "
        CRC Errors Counter Error :This
        OID when set indicates the CRC
         Errors counter value is invalid
        on client port
        "
	::= { pm20002maMonupRmonCrcErrorsCounterClientInputEntry 3 }


pm20002maMonupRmonCrcErrorsCounterClientInputOverloadPortn OBJECT-TYPE
	SYNTAX  EkiOnOff
	MAX-ACCESS read-only
	STATUS current
	DESCRIPTION
        "
        CRC Errors Counter Overload :This
        OID when set indicates a CRC Errors
        counter overload on client port
        "
	::= { pm20002maMonupRmonCrcErrorsCounterClientInputEntry 4 }


--- *********************************************************
---     TABLE for the pm20002maMonupRmonPacketsCounterClientInput articles
--- *********************************************************

pm20002maMonupRmonPacketsCounterClientInputTable OBJECT-TYPE
	SYNTAX  SEQUENCE OF Pm20002maMonupRmonPacketsCounterClientInputEntry
	MAX-ACCESS not-accessible
	STATUS current
	DESCRIPTION
        "
        List of pm20002maMonupRmonPacketsCounterClientInput
        Article
        "
	::= { pm20002maMonClientRmonCounter 80 }


pm20002maMonupRmonPacketsCounterClientInputEntry OBJECT-TYPE
	SYNTAX Pm20002maMonupRmonPacketsCounterClientInputEntry
	MAX-ACCESS not-accessible
	STATUS current
	DESCRIPTION
        "
        Row definition for the pm20002maMonupRmonPacketsCounterClientInput
        table
        "
	INDEX   { pm20002maMonupRmonPacketsCounterClientInputIndex }
	::= { pm20002maMonupRmonPacketsCounterClientInputTable 1 }


Pm20002maMonupRmonPacketsCounterClientInputEntry ::=
	SEQUENCE {
	pm20002maMonupRmonPacketsCounterClientInputIndex
		INTEGER,
	pm20002maMonupRmonPacketsCounterClientInputValuePortn
		Counter64,
	pm20002maMonupRmonPacketsCounterClientInputErrorPortn
		EkiOnOff,
	pm20002maMonupRmonPacketsCounterClientInputOverloadPortn
		EkiOnOff
	}


pm20002maMonupRmonPacketsCounterClientInputIndex OBJECT-TYPE
	SYNTAX  INTEGER(0..128)
	MAX-ACCESS  read-only
	STATUS current
	DESCRIPTION
        "
        Index definition for the pm20002maMonupRmonPacketsCounterClientInput
        table
        "
	::= { pm20002maMonupRmonPacketsCounterClientInputEntry 1 }


pm20002maMonupRmonPacketsCounterClientInputValuePortn OBJECT-TYPE
	SYNTAX  Counter64
	MAX-ACCESS read-only
	STATUS current
	DESCRIPTION
        "
        Client Input Packets :This counter
        is increased each time a packet
        is received on the client port
          <Help>  This counter gives the
        number of packets received on the
        client port
        "
	::= { pm20002maMonupRmonPacketsCounterClientInputEntry 2 }


pm20002maMonupRmonPacketsCounterClientInputErrorPortn OBJECT-TYPE
	SYNTAX  EkiOnOff
	MAX-ACCESS read-only
	STATUS current
	DESCRIPTION
        "
        Packets Counter Error :This OID
        when set indicates the Packets
         counter value is invalid on client
        port
        "
	::= { pm20002maMonupRmonPacketsCounterClientInputEntry 3 }


pm20002maMonupRmonPacketsCounterClientInputOverloadPortn OBJECT-TYPE
	SYNTAX  EkiOnOff
	MAX-ACCESS read-only
	STATUS current
	DESCRIPTION
        "
        Packets Counter Overload :This
        OID when set indicates a Packets
        counter overload on client port
        "
	::= { pm20002maMonupRmonPacketsCounterClientInputEntry 4 }


--- *********************************************************
---     TABLE for the pm20002maMonupRmonBroadcastCounterClientInput articles
--- *********************************************************

pm20002maMonupRmonBroadcastCounterClientInputTable OBJECT-TYPE
	SYNTAX  SEQUENCE OF Pm20002maMonupRmonBroadcastCounterClientInputEntry
	MAX-ACCESS not-accessible
	STATUS current
	DESCRIPTION
        "
        List of pm20002maMonupRmonBroadcastCounterClientInput
        Article
        "
	::= { pm20002maMonClientRmonCounter 112 }


pm20002maMonupRmonBroadcastCounterClientInputEntry OBJECT-TYPE
	SYNTAX Pm20002maMonupRmonBroadcastCounterClientInputEntry
	MAX-ACCESS not-accessible
	STATUS current
	DESCRIPTION
        "
        Row definition for the pm20002maMonupRmonBroadcastCounterClientInput
        table
        "
	INDEX   { pm20002maMonupRmonBroadcastCounterClientInputIndex }
	::= { pm20002maMonupRmonBroadcastCounterClientInputTable 1 }


Pm20002maMonupRmonBroadcastCounterClientInputEntry ::=
	SEQUENCE {
	pm20002maMonupRmonBroadcastCounterClientInputIndex
		INTEGER,
	pm20002maMonupRmonBroadcastCounterClientInputValuePortn
		Counter64,
	pm20002maMonupRmonBroadcastCounterClientInputErrorPortn
		EkiOnOff,
	pm20002maMonupRmonBroadcastCounterClientInputOverloadPortn
		EkiOnOff
	}


pm20002maMonupRmonBroadcastCounterClientInputIndex OBJECT-TYPE
	SYNTAX  INTEGER(0..128)
	MAX-ACCESS  read-only
	STATUS current
	DESCRIPTION
        "
        Index definition for the pm20002maMonupRmonBroadcastCounterClientInput
        table
        "
	::= { pm20002maMonupRmonBroadcastCounterClientInputEntry 1 }


pm20002maMonupRmonBroadcastCounterClientInputValuePortn OBJECT-TYPE
	SYNTAX  Counter64
	MAX-ACCESS read-only
	STATUS current
	DESCRIPTION
        "
        Client Input Broadcast Packets
        :This counter is increased each
        time a broadcast packet is received
        on the client port  <Help>  This
        counter gives the number of Broadcast
        packets received on the client
         port
        "
	::= { pm20002maMonupRmonBroadcastCounterClientInputEntry 2 }


pm20002maMonupRmonBroadcastCounterClientInputErrorPortn OBJECT-TYPE
	SYNTAX  EkiOnOff
	MAX-ACCESS read-only
	STATUS current
	DESCRIPTION
        "
        Broadcast Counter Error :This
         OID when set indicates the Broadcast
        counter value is invalid on client
        port
        "
	::= { pm20002maMonupRmonBroadcastCounterClientInputEntry 3 }


pm20002maMonupRmonBroadcastCounterClientInputOverloadPortn OBJECT-TYPE
	SYNTAX  EkiOnOff
	MAX-ACCESS read-only
	STATUS current
	DESCRIPTION
        "
        Broadcast Counter Overload :This
        OID when set indicates a Broadcast
        counter overload on client port
        "
	::= { pm20002maMonupRmonBroadcastCounterClientInputEntry 4 }


--- *********************************************************
---     TABLE for the pm20002maMonupRmonMulticastCounterClientInput articles
--- *********************************************************

pm20002maMonupRmonMulticastCounterClientInputTable OBJECT-TYPE
	SYNTAX  SEQUENCE OF Pm20002maMonupRmonMulticastCounterClientInputEntry
	MAX-ACCESS not-accessible
	STATUS current
	DESCRIPTION
        "
        List of pm20002maMonupRmonMulticastCounterClientInput
        Article
        "
	::= { pm20002maMonClientRmonCounter 144 }


pm20002maMonupRmonMulticastCounterClientInputEntry OBJECT-TYPE
	SYNTAX Pm20002maMonupRmonMulticastCounterClientInputEntry
	MAX-ACCESS not-accessible
	STATUS current
	DESCRIPTION
        "
        Row definition for the pm20002maMonupRmonMulticastCounterClientInput
        table
        "
	INDEX   { pm20002maMonupRmonMulticastCounterClientInputIndex }
	::= { pm20002maMonupRmonMulticastCounterClientInputTable 1 }


Pm20002maMonupRmonMulticastCounterClientInputEntry ::=
	SEQUENCE {
	pm20002maMonupRmonMulticastCounterClientInputIndex
		INTEGER,
	pm20002maMonupRmonMulticastCounterClientInputValuePortn
		Counter64,
	pm20002maMonupRmonMulticastCounterClientInputErrorPortn
		EkiOnOff,
	pm20002maMonupRmonMulticastCounterClientInputOverloadPortn
		EkiOnOff
	}


pm20002maMonupRmonMulticastCounterClientInputIndex OBJECT-TYPE
	SYNTAX  INTEGER(0..128)
	MAX-ACCESS  read-only
	STATUS current
	DESCRIPTION
        "
        Index definition for the pm20002maMonupRmonMulticastCounterClientInput
        table
        "
	::= { pm20002maMonupRmonMulticastCounterClientInputEntry 1 }


pm20002maMonupRmonMulticastCounterClientInputValuePortn OBJECT-TYPE
	SYNTAX  Counter64
	MAX-ACCESS read-only
	STATUS current
	DESCRIPTION
        "
        Client Input Multicast Packets
        :This counter is increased each
        time a Multicast packet is received
        on the client port  <Help>  This
        counter gives the number of Multicast
        packets received on the client
         port
        "
	::= { pm20002maMonupRmonMulticastCounterClientInputEntry 2 }


pm20002maMonupRmonMulticastCounterClientInputErrorPortn OBJECT-TYPE
	SYNTAX  EkiOnOff
	MAX-ACCESS read-only
	STATUS current
	DESCRIPTION
        "
        Multicast Counter Error :This
         OID when set indicates the Multicast
        counter value is invalid on client
        port
        "
	::= { pm20002maMonupRmonMulticastCounterClientInputEntry 3 }


pm20002maMonupRmonMulticastCounterClientInputOverloadPortn OBJECT-TYPE
	SYNTAX  EkiOnOff
	MAX-ACCESS read-only
	STATUS current
	DESCRIPTION
        "
        Multicast Counter Overload :This
        OID when set indicates a Multicast
        counter overload on client port
        "
	::= { pm20002maMonupRmonMulticastCounterClientInputEntry 4 }


--- *********************************************************
---     TABLE for the pm20002maMonupRmonPauseFrameCounterClientInput articles
--- *********************************************************

pm20002maMonupRmonPauseFrameCounterClientInputTable OBJECT-TYPE
	SYNTAX  SEQUENCE OF Pm20002maMonupRmonPauseFrameCounterClientInputEntry
	MAX-ACCESS not-accessible
	STATUS current
	DESCRIPTION
        "
        List of pm20002maMonupRmonPauseFrameCounterClientInput
        Article
        "
	::= { pm20002maMonClientRmonCounter 176 }


pm20002maMonupRmonPauseFrameCounterClientInputEntry OBJECT-TYPE
	SYNTAX Pm20002maMonupRmonPauseFrameCounterClientInputEntry
	MAX-ACCESS not-accessible
	STATUS current
	DESCRIPTION
        "
        Row definition for the pm20002maMonupRmonPauseFrameCounterClientInput
        table
        "
	INDEX   { pm20002maMonupRmonPauseFrameCounterClientInputIndex }
	::= { pm20002maMonupRmonPauseFrameCounterClientInputTable 1 }


Pm20002maMonupRmonPauseFrameCounterClientInputEntry ::=
	SEQUENCE {
	pm20002maMonupRmonPauseFrameCounterClientInputIndex
		INTEGER,
	pm20002maMonupRmonPauseFrameCounterClientInputValuePortn
		Counter64,
	pm20002maMonupRmonPauseFrameCounterClientInputErrorPortn
		EkiOnOff,
	pm20002maMonupRmonPauseFrameCounterClientInputOverloadPortn
		EkiOnOff
	}


pm20002maMonupRmonPauseFrameCounterClientInputIndex OBJECT-TYPE
	SYNTAX  INTEGER(0..128)
	MAX-ACCESS  read-only
	STATUS current
	DESCRIPTION
        "
        Index definition for the pm20002maMonupRmonPauseFrameCounterClientInput
        table
        "
	::= { pm20002maMonupRmonPauseFrameCounterClientInputEntry 1 }


pm20002maMonupRmonPauseFrameCounterClientInputValuePortn OBJECT-TYPE
	SYNTAX  Counter64
	MAX-ACCESS read-only
	STATUS current
	DESCRIPTION
        "
        Client Input Pause Frames :This
        counter is increased each time
         a Pause frame is received on the
        client port  <Help>  This counter
        gives the number of Pause frames
        received on the client port
        "
	::= { pm20002maMonupRmonPauseFrameCounterClientInputEntry 2 }


pm20002maMonupRmonPauseFrameCounterClientInputErrorPortn OBJECT-TYPE
	SYNTAX  EkiOnOff
	MAX-ACCESS read-only
	STATUS current
	DESCRIPTION
        "
        Pause Counter Error :This OID
         when set indicates the Pause counter
        value is invalid on client port
        "
	::= { pm20002maMonupRmonPauseFrameCounterClientInputEntry 3 }


pm20002maMonupRmonPauseFrameCounterClientInputOverloadPortn OBJECT-TYPE
	SYNTAX  EkiOnOff
	MAX-ACCESS read-only
	STATUS current
	DESCRIPTION
        "
        Pause Counter Overload :This OID
        when set indicates a Pause counter
        overload on client port
        "
	::= { pm20002maMonupRmonPauseFrameCounterClientInputEntry 4 }


--- *********************************************************
---     TABLE for the pm20002maMonupRmonUnicastCounterClientInput articles
--- *********************************************************

pm20002maMonupRmonUnicastCounterClientInputTable OBJECT-TYPE
	SYNTAX  SEQUENCE OF Pm20002maMonupRmonUnicastCounterClientInputEntry
	MAX-ACCESS not-accessible
	STATUS current
	DESCRIPTION
        "
        List of pm20002maMonupRmonUnicastCounterClientInput
        Article
        "
	::= { pm20002maMonClientRmonCounter 304 }


pm20002maMonupRmonUnicastCounterClientInputEntry OBJECT-TYPE
	SYNTAX Pm20002maMonupRmonUnicastCounterClientInputEntry
	MAX-ACCESS not-accessible
	STATUS current
	DESCRIPTION
        "
        Row definition for the pm20002maMonupRmonUnicastCounterClientInput
        table
        "
	INDEX   { pm20002maMonupRmonUnicastCounterClientInputIndex }
	::= { pm20002maMonupRmonUnicastCounterClientInputTable 1 }


Pm20002maMonupRmonUnicastCounterClientInputEntry ::=
	SEQUENCE {
	pm20002maMonupRmonUnicastCounterClientInputIndex
		INTEGER,
	pm20002maMonupRmonUnicastCounterClientInputValuePortn
		Counter64,
	pm20002maMonupRmonUnicastCounterClientInputErrorPortn
		EkiOnOff,
	pm20002maMonupRmonUnicastCounterClientInputOverloadPortn
		EkiOnOff
	}


pm20002maMonupRmonUnicastCounterClientInputIndex OBJECT-TYPE
	SYNTAX  INTEGER(0..128)
	MAX-ACCESS  read-only
	STATUS current
	DESCRIPTION
        "
        Index definition for the pm20002maMonupRmonUnicastCounterClientInput
        table
        "
	::= { pm20002maMonupRmonUnicastCounterClientInputEntry 1 }


pm20002maMonupRmonUnicastCounterClientInputValuePortn OBJECT-TYPE
	SYNTAX  Counter64
	MAX-ACCESS read-only
	STATUS current
	DESCRIPTION
        "
        Client Input Unicast Packets :This
        counter is increased each time
         a Unicast packet is received on
        the client port  <Help>  This counter
        gives the number of Unicast packets
        received on the client port
        "
	::= { pm20002maMonupRmonUnicastCounterClientInputEntry 2 }


pm20002maMonupRmonUnicastCounterClientInputErrorPortn OBJECT-TYPE
	SYNTAX  EkiOnOff
	MAX-ACCESS read-only
	STATUS current
	DESCRIPTION
        "
        Unicast Counter Error :This OID
        when set indicates the Unicast
         counter value is invalid on client
        port
        "
	::= { pm20002maMonupRmonUnicastCounterClientInputEntry 3 }


pm20002maMonupRmonUnicastCounterClientInputOverloadPortn OBJECT-TYPE
	SYNTAX  EkiOnOff
	MAX-ACCESS read-only
	STATUS current
	DESCRIPTION
        "
        Unicast Counter Overload :This
        OID when set indicates a Unicast
        counter overload on client port
        "
	::= { pm20002maMonupRmonUnicastCounterClientInputEntry 4 }


--- *********************************************************
---     TABLE for the pm20002maMonupRmonNonunicastCounterClientInput articles
--- *********************************************************

pm20002maMonupRmonNonunicastCounterClientInputTable OBJECT-TYPE
	SYNTAX  SEQUENCE OF Pm20002maMonupRmonNonunicastCounterClientInputEntry
	MAX-ACCESS not-accessible
	STATUS current
	DESCRIPTION
        "
        List of pm20002maMonupRmonNonunicastCounterClientInput
        Article
        "
	::= { pm20002maMonClientRmonCounter 336 }


pm20002maMonupRmonNonunicastCounterClientInputEntry OBJECT-TYPE
	SYNTAX Pm20002maMonupRmonNonunicastCounterClientInputEntry
	MAX-ACCESS not-accessible
	STATUS current
	DESCRIPTION
        "
        Row definition for the pm20002maMonupRmonNonunicastCounterClientInput
        table
        "
	INDEX   { pm20002maMonupRmonNonunicastCounterClientInputIndex }
	::= { pm20002maMonupRmonNonunicastCounterClientInputTable 1 }


Pm20002maMonupRmonNonunicastCounterClientInputEntry ::=
	SEQUENCE {
	pm20002maMonupRmonNonunicastCounterClientInputIndex
		INTEGER,
	pm20002maMonupRmonNonunicastCounterClientInputValuePortn
		Counter64,
	pm20002maMonupRmonNonunicastCounterClientInputErrorPortn
		EkiOnOff,
	pm20002maMonupRmonNonunicastCounterClientInputOverloadPortn
		EkiOnOff
	}


pm20002maMonupRmonNonunicastCounterClientInputIndex OBJECT-TYPE
	SYNTAX  INTEGER(0..128)
	MAX-ACCESS  read-only
	STATUS current
	DESCRIPTION
        "
        Index definition for the pm20002maMonupRmonNonunicastCounterClientInput
        table
        "
	::= { pm20002maMonupRmonNonunicastCounterClientInputEntry 1 }


pm20002maMonupRmonNonunicastCounterClientInputValuePortn OBJECT-TYPE
	SYNTAX  Counter64
	MAX-ACCESS read-only
	STATUS current
	DESCRIPTION
        "
        Client Input Non Unicast Packets
        :This counter is increased each
        time a Non-Unicast packet is received
        on the client port  <Help>  This
        counter gives the number of Non-Unicast
        packets received on the client
         port
        "
	::= { pm20002maMonupRmonNonunicastCounterClientInputEntry 2 }


pm20002maMonupRmonNonunicastCounterClientInputErrorPortn OBJECT-TYPE
	SYNTAX  EkiOnOff
	MAX-ACCESS read-only
	STATUS current
	DESCRIPTION
        "
        Non Unicast Counter Error :This
        OID when set indicates the Non-Unicast
        counter value is invalid on client
        port
        "
	::= { pm20002maMonupRmonNonunicastCounterClientInputEntry 3 }


pm20002maMonupRmonNonunicastCounterClientInputOverloadPortn OBJECT-TYPE
	SYNTAX  EkiOnOff
	MAX-ACCESS read-only
	STATUS current
	DESCRIPTION
        "
        Non Unicast Counter Overload :This
        OID when set indicates a Non-Unicast
        counter overload on client port
        "
	::= { pm20002maMonupRmonNonunicastCounterClientInputEntry 4 }


--- *********************************************************
---     TABLE for the pm20002maMondownRmonBytesCounterClientOutput articles
--- *********************************************************

pm20002maMondownRmonBytesCounterClientOutputTable OBJECT-TYPE
	SYNTAX  SEQUENCE OF Pm20002maMondownRmonBytesCounterClientOutputEntry
	MAX-ACCESS not-accessible
	STATUS current
	DESCRIPTION
        "
        List of pm20002maMondownRmonBytesCounterClientOutput
        Article
        "
	::= { pm20002maMonClientRmonCounter 400 }


pm20002maMondownRmonBytesCounterClientOutputEntry OBJECT-TYPE
	SYNTAX Pm20002maMondownRmonBytesCounterClientOutputEntry
	MAX-ACCESS not-accessible
	STATUS current
	DESCRIPTION
        "
        Row definition for the pm20002maMondownRmonBytesCounterClientOutput
        table
        "
	INDEX   { pm20002maMondownRmonBytesCounterClientOutputIndex }
	::= { pm20002maMondownRmonBytesCounterClientOutputTable 1 }


Pm20002maMondownRmonBytesCounterClientOutputEntry ::=
	SEQUENCE {
	pm20002maMondownRmonBytesCounterClientOutputIndex
		INTEGER,
	pm20002maMondownRmonBytesCounterClientOutputValuePortn
		Counter64,
	pm20002maMondownRmonBytesCounterClientOutputErrorPortn
		EkiOnOff,
	pm20002maMondownRmonBytesCounterClientOutputOverloadPortn
		EkiOnOff
	}


pm20002maMondownRmonBytesCounterClientOutputIndex OBJECT-TYPE
	SYNTAX  INTEGER(0..128)
	MAX-ACCESS  read-only
	STATUS current
	DESCRIPTION
        "
        Index definition for the pm20002maMondownRmonBytesCounterClientOutput
        table
        "
	::= { pm20002maMondownRmonBytesCounterClientOutputEntry 1 }


pm20002maMondownRmonBytesCounterClientOutputValuePortn OBJECT-TYPE
	SYNTAX  Counter64
	MAX-ACCESS read-only
	STATUS current
	DESCRIPTION
        "
        Client Output Bytes :This counter
        is increased each time a data byte
        is transmitted on the client port
        <Help> This counter gives the number
        of bytes transmitted on the client
        port
        "
	::= { pm20002maMondownRmonBytesCounterClientOutputEntry 2 }


pm20002maMondownRmonBytesCounterClientOutputErrorPortn OBJECT-TYPE
	SYNTAX  EkiOnOff
	MAX-ACCESS read-only
	STATUS current
	DESCRIPTION
        "
        Bytes Counter Error :This OID
         when set indicates the Bytes counter
        value is invalid on client port
        "
	::= { pm20002maMondownRmonBytesCounterClientOutputEntry 3 }


pm20002maMondownRmonBytesCounterClientOutputOverloadPortn OBJECT-TYPE
	SYNTAX  EkiOnOff
	MAX-ACCESS read-only
	STATUS current
	DESCRIPTION
        "
        Bytes Counter Overload :This OID
        when set indicates a Bytes counter
        overload on client port

        "
	::= { pm20002maMondownRmonBytesCounterClientOutputEntry 4 }


--- *********************************************************
---     TABLE for the pm20002maMondownRmonCrcErrorsCounterClientOutput articles
--- *********************************************************

pm20002maMondownRmonCrcErrorsCounterClientOutputTable OBJECT-TYPE
	SYNTAX  SEQUENCE OF Pm20002maMondownRmonCrcErrorsCounterClientOutputEntry
	MAX-ACCESS not-accessible
	STATUS current
	DESCRIPTION
        "
        List of pm20002maMondownRmonCrcErrorsCounterClientOutput
        Article
        "
	::= { pm20002maMonClientRmonCounter 432 }


pm20002maMondownRmonCrcErrorsCounterClientOutputEntry OBJECT-TYPE
	SYNTAX Pm20002maMondownRmonCrcErrorsCounterClientOutputEntry
	MAX-ACCESS not-accessible
	STATUS current
	DESCRIPTION
        "
        Row definition for the pm20002maMondownRmonCrcErrorsCounterClientOutput
        table
        "
	INDEX   { pm20002maMondownRmonCrcErrorsCounterClientOutputIndex }
	::= { pm20002maMondownRmonCrcErrorsCounterClientOutputTable 1 }


Pm20002maMondownRmonCrcErrorsCounterClientOutputEntry ::=
	SEQUENCE {
	pm20002maMondownRmonCrcErrorsCounterClientOutputIndex
		INTEGER,
	pm20002maMondownRmonCrcErrorsCounterClientOutputValuePortn
		Counter64,
	pm20002maMondownRmonCrcErrorsCounterClientOutputErrorPortn
		EkiOnOff,
	pm20002maMondownRmonCrcErrorsCounterClientOutputOverloadPortn
		EkiOnOff
	}


pm20002maMondownRmonCrcErrorsCounterClientOutputIndex OBJECT-TYPE
	SYNTAX  INTEGER(0..128)
	MAX-ACCESS  read-only
	STATUS current
	DESCRIPTION
        "
        Index definition for the pm20002maMondownRmonCrcErrorsCounterClientOutput
        table
        "
	::= { pm20002maMondownRmonCrcErrorsCounterClientOutputEntry 1 }


pm20002maMondownRmonCrcErrorsCounterClientOutputValuePortn OBJECT-TYPE
	SYNTAX  Counter64
	MAX-ACCESS read-only
	STATUS current
	DESCRIPTION
        "
        Client Output CRC Errors :This
        counter is increased each time
         a CRC error is detected on the
        transmit client port  <Help>  This
        counter gives the number of CRC
        Errors transmitted on the client
        port
        "
	::= { pm20002maMondownRmonCrcErrorsCounterClientOutputEntry 2 }


pm20002maMondownRmonCrcErrorsCounterClientOutputErrorPortn OBJECT-TYPE
	SYNTAX  EkiOnOff
	MAX-ACCESS read-only
	STATUS current
	DESCRIPTION
        "
        CRC Errors Counter Error :This
        OID when set indicates the CRC
         Errors counter value is invalid
        on client port
        "
	::= { pm20002maMondownRmonCrcErrorsCounterClientOutputEntry 3 }


pm20002maMondownRmonCrcErrorsCounterClientOutputOverloadPortn OBJECT-TYPE
	SYNTAX  EkiOnOff
	MAX-ACCESS read-only
	STATUS current
	DESCRIPTION
        "
        CRC Errors Counter Overload :This
        OID when set indicates a CRC Errors
        counter overload on client port
        "
	::= { pm20002maMondownRmonCrcErrorsCounterClientOutputEntry 4 }


--- *********************************************************
---     TABLE for the pm20002maMondownRmonPacketsCounterClientOutput articles
--- *********************************************************

pm20002maMondownRmonPacketsCounterClientOutputTable OBJECT-TYPE
	SYNTAX  SEQUENCE OF Pm20002maMondownRmonPacketsCounterClientOutputEntry
	MAX-ACCESS not-accessible
	STATUS current
	DESCRIPTION
        "
        List of pm20002maMondownRmonPacketsCounterClientOutput
        Article
        "
	::= { pm20002maMonClientRmonCounter 464 }


pm20002maMondownRmonPacketsCounterClientOutputEntry OBJECT-TYPE
	SYNTAX Pm20002maMondownRmonPacketsCounterClientOutputEntry
	MAX-ACCESS not-accessible
	STATUS current
	DESCRIPTION
        "
        Row definition for the pm20002maMondownRmonPacketsCounterClientOutput
        table
        "
	INDEX   { pm20002maMondownRmonPacketsCounterClientOutputIndex }
	::= { pm20002maMondownRmonPacketsCounterClientOutputTable 1 }


Pm20002maMondownRmonPacketsCounterClientOutputEntry ::=
	SEQUENCE {
	pm20002maMondownRmonPacketsCounterClientOutputIndex
		INTEGER,
	pm20002maMondownRmonPacketsCounterClientOutputValuePortn
		Counter64,
	pm20002maMondownRmonPacketsCounterClientOutputErrorPortn
		EkiOnOff,
	pm20002maMondownRmonPacketsCounterClientOutputOverloadPortn
		EkiOnOff
	}


pm20002maMondownRmonPacketsCounterClientOutputIndex OBJECT-TYPE
	SYNTAX  INTEGER(0..128)
	MAX-ACCESS  read-only
	STATUS current
	DESCRIPTION
        "
        Index definition for the pm20002maMondownRmonPacketsCounterClientOutput
        table
        "
	::= { pm20002maMondownRmonPacketsCounterClientOutputEntry 1 }


pm20002maMondownRmonPacketsCounterClientOutputValuePortn OBJECT-TYPE
	SYNTAX  Counter64
	MAX-ACCESS read-only
	STATUS current
	DESCRIPTION
        "
        Client Output Packets :This counter
        is increased each time a packet
        is transmitted on the client port
         <Help>  This counter gives the
        number of packets transmitted on
        the client port
        "
	::= { pm20002maMondownRmonPacketsCounterClientOutputEntry 2 }


pm20002maMondownRmonPacketsCounterClientOutputErrorPortn OBJECT-TYPE
	SYNTAX  EkiOnOff
	MAX-ACCESS read-only
	STATUS current
	DESCRIPTION
        "
        Packets Counter Error :This OID
        when set indicates the Packets
         counter value is invalid on client
        port
        "
	::= { pm20002maMondownRmonPacketsCounterClientOutputEntry 3 }


pm20002maMondownRmonPacketsCounterClientOutputOverloadPortn OBJECT-TYPE
	SYNTAX  EkiOnOff
	MAX-ACCESS read-only
	STATUS current
	DESCRIPTION
        "
        Packets Counter Overload :This
        OID when set indicates a Packets
        counter overload on client port
        "
	::= { pm20002maMondownRmonPacketsCounterClientOutputEntry 4 }


--- *********************************************************
---     TABLE for the pm20002maMondownRmonBroadcastCounterClientOutput articles
--- *********************************************************

pm20002maMondownRmonBroadcastCounterClientOutputTable OBJECT-TYPE
	SYNTAX  SEQUENCE OF Pm20002maMondownRmonBroadcastCounterClientOutputEntry
	MAX-ACCESS not-accessible
	STATUS current
	DESCRIPTION
        "
        List of pm20002maMondownRmonBroadcastCounterClientOutput
        Article
        "
	::= { pm20002maMonClientRmonCounter 496 }


pm20002maMondownRmonBroadcastCounterClientOutputEntry OBJECT-TYPE
	SYNTAX Pm20002maMondownRmonBroadcastCounterClientOutputEntry
	MAX-ACCESS not-accessible
	STATUS current
	DESCRIPTION
        "
        Row definition for the pm20002maMondownRmonBroadcastCounterClientOutput
        table
        "
	INDEX   { pm20002maMondownRmonBroadcastCounterClientOutputIndex }
	::= { pm20002maMondownRmonBroadcastCounterClientOutputTable 1 }


Pm20002maMondownRmonBroadcastCounterClientOutputEntry ::=
	SEQUENCE {
	pm20002maMondownRmonBroadcastCounterClientOutputIndex
		INTEGER,
	pm20002maMondownRmonBroadcastCounterClientOutputValuePortn
		Counter64,
	pm20002maMondownRmonBroadcastCounterClientOutputErrorPortn
		EkiOnOff,
	pm20002maMondownRmonBroadcastCounterClientOutputOverloadPortn
		EkiOnOff
	}


pm20002maMondownRmonBroadcastCounterClientOutputIndex OBJECT-TYPE
	SYNTAX  INTEGER(0..128)
	MAX-ACCESS  read-only
	STATUS current
	DESCRIPTION
        "
        Index definition for the pm20002maMondownRmonBroadcastCounterClientOutput
        table
        "
	::= { pm20002maMondownRmonBroadcastCounterClientOutputEntry 1 }


pm20002maMondownRmonBroadcastCounterClientOutputValuePortn OBJECT-TYPE
	SYNTAX  Counter64
	MAX-ACCESS read-only
	STATUS current
	DESCRIPTION
        "
        Client Output Broadcast Packets
        :This counter is increased each
        time a broadcast packet is transmitted
        on the client port  <Help>  This
        counter gives the number of Broadcast
        packets transmitted on the client
        port
        "
	::= { pm20002maMondownRmonBroadcastCounterClientOutputEntry 2 }


pm20002maMondownRmonBroadcastCounterClientOutputErrorPortn OBJECT-TYPE
	SYNTAX  EkiOnOff
	MAX-ACCESS read-only
	STATUS current
	DESCRIPTION
        "
        Broadcast Counter Error :This
         OID when set indicates the Broadcast
        counter value is invalid on client
        port
        "
	::= { pm20002maMondownRmonBroadcastCounterClientOutputEntry 3 }


pm20002maMondownRmonBroadcastCounterClientOutputOverloadPortn OBJECT-TYPE
	SYNTAX  EkiOnOff
	MAX-ACCESS read-only
	STATUS current
	DESCRIPTION
        "
        Broadcast Counter Overload :This
        OID when set indicates a Broadcast
        counter overload on client port
        "
	::= { pm20002maMondownRmonBroadcastCounterClientOutputEntry 4 }


--- *********************************************************
---     TABLE for the pm20002maMondownRmonMulticastCounterClientOutput articles
--- *********************************************************

pm20002maMondownRmonMulticastCounterClientOutputTable OBJECT-TYPE
	SYNTAX  SEQUENCE OF Pm20002maMondownRmonMulticastCounterClientOutputEntry
	MAX-ACCESS not-accessible
	STATUS current
	DESCRIPTION
        "
        List of pm20002maMondownRmonMulticastCounterClientOutput
        Article
        "
	::= { pm20002maMonClientRmonCounter 528 }


pm20002maMondownRmonMulticastCounterClientOutputEntry OBJECT-TYPE
	SYNTAX Pm20002maMondownRmonMulticastCounterClientOutputEntry
	MAX-ACCESS not-accessible
	STATUS current
	DESCRIPTION
        "
        Row definition for the pm20002maMondownRmonMulticastCounterClientOutput
        table
        "
	INDEX   { pm20002maMondownRmonMulticastCounterClientOutputIndex }
	::= { pm20002maMondownRmonMulticastCounterClientOutputTable 1 }


Pm20002maMondownRmonMulticastCounterClientOutputEntry ::=
	SEQUENCE {
	pm20002maMondownRmonMulticastCounterClientOutputIndex
		INTEGER,
	pm20002maMondownRmonMulticastCounterClientOutputValuePortn
		Counter64,
	pm20002maMondownRmonMulticastCounterClientOutputErrorPortn
		EkiOnOff,
	pm20002maMondownRmonMulticastCounterClientOutputOverloadPortn
		EkiOnOff
	}


pm20002maMondownRmonMulticastCounterClientOutputIndex OBJECT-TYPE
	SYNTAX  INTEGER(0..128)
	MAX-ACCESS  read-only
	STATUS current
	DESCRIPTION
        "
        Index definition for the pm20002maMondownRmonMulticastCounterClientOutput
        table
        "
	::= { pm20002maMondownRmonMulticastCounterClientOutputEntry 1 }


pm20002maMondownRmonMulticastCounterClientOutputValuePortn OBJECT-TYPE
	SYNTAX  Counter64
	MAX-ACCESS read-only
	STATUS current
	DESCRIPTION
        "
        Client Output Multicast Packets
        :This counter is increased each
        time a Multicast packet is transmitted
        on the client port  <Help>  This
        counter gives the number of Multicast
        packets transmitted on the client
        port
        "
	::= { pm20002maMondownRmonMulticastCounterClientOutputEntry 2 }


pm20002maMondownRmonMulticastCounterClientOutputErrorPortn OBJECT-TYPE
	SYNTAX  EkiOnOff
	MAX-ACCESS read-only
	STATUS current
	DESCRIPTION
        "
        Multicast Counter Error :This
         OID when set indicates the Multicast
        counter value is invalid on client
        port
        "
	::= { pm20002maMondownRmonMulticastCounterClientOutputEntry 3 }


pm20002maMondownRmonMulticastCounterClientOutputOverloadPortn OBJECT-TYPE
	SYNTAX  EkiOnOff
	MAX-ACCESS read-only
	STATUS current
	DESCRIPTION
        "
        Multicast Counter Overload :This
        OID when set indicates a Multicast
        counter overload on client port
        "
	::= { pm20002maMondownRmonMulticastCounterClientOutputEntry 4 }


--- *********************************************************
---     TABLE for the pm20002maMondownRmonPauseFrameCounterClientOutput articles
--- *********************************************************

pm20002maMondownRmonPauseFrameCounterClientOutputTable OBJECT-TYPE
	SYNTAX  SEQUENCE OF Pm20002maMondownRmonPauseFrameCounterClientOutputEntry
	MAX-ACCESS not-accessible
	STATUS current
	DESCRIPTION
        "
        List of pm20002maMondownRmonPauseFrameCounterClientOutput
        Article
        "
	::= { pm20002maMonClientRmonCounter 560 }


pm20002maMondownRmonPauseFrameCounterClientOutputEntry OBJECT-TYPE
	SYNTAX Pm20002maMondownRmonPauseFrameCounterClientOutputEntry
	MAX-ACCESS not-accessible
	STATUS current
	DESCRIPTION
        "
        Row definition for the pm20002maMondownRmonPauseFrameCounterClientOutput
        table
        "
	INDEX   { pm20002maMondownRmonPauseFrameCounterClientOutputIndex }
	::= { pm20002maMondownRmonPauseFrameCounterClientOutputTable 1 }


Pm20002maMondownRmonPauseFrameCounterClientOutputEntry ::=
	SEQUENCE {
	pm20002maMondownRmonPauseFrameCounterClientOutputIndex
		INTEGER,
	pm20002maMondownRmonPauseFrameCounterClientOutputValuePortn
		Counter64,
	pm20002maMondownRmonPauseFrameCounterClientOutputErrorPortn
		EkiOnOff,
	pm20002maMondownRmonPauseFrameCounterClientOutputOverloadPortn
		EkiOnOff
	}


pm20002maMondownRmonPauseFrameCounterClientOutputIndex OBJECT-TYPE
	SYNTAX  INTEGER(0..128)
	MAX-ACCESS  read-only
	STATUS current
	DESCRIPTION
        "
        Index definition for the pm20002maMondownRmonPauseFrameCounterClientOutput
        table
        "
	::= { pm20002maMondownRmonPauseFrameCounterClientOutputEntry 1 }


pm20002maMondownRmonPauseFrameCounterClientOutputValuePortn OBJECT-TYPE
	SYNTAX  Counter64
	MAX-ACCESS read-only
	STATUS current
	DESCRIPTION
        "
        Client Output Pause Frames :This
        counter is increased each time
         a Pause frame is transmitted on
        the client port  <Help>  This counter
        gives the number of Pause frames
        transmitted on the client port
        "
	::= { pm20002maMondownRmonPauseFrameCounterClientOutputEntry 2 }


pm20002maMondownRmonPauseFrameCounterClientOutputErrorPortn OBJECT-TYPE
	SYNTAX  EkiOnOff
	MAX-ACCESS read-only
	STATUS current
	DESCRIPTION
        "
        Pause Counter Error :This OID
         when set indicates the Pause counter
        value is invalid on client port
        "
	::= { pm20002maMondownRmonPauseFrameCounterClientOutputEntry 3 }


pm20002maMondownRmonPauseFrameCounterClientOutputOverloadPortn OBJECT-TYPE
	SYNTAX  EkiOnOff
	MAX-ACCESS read-only
	STATUS current
	DESCRIPTION
        "
        Pause Counter Overload :This OID
        when set indicates a Pause counter
        overload on client port
        "
	::= { pm20002maMondownRmonPauseFrameCounterClientOutputEntry 4 }


--- *********************************************************
---     TABLE for the pm20002maMondownRmonUnicastCounterClientOutput articles
--- *********************************************************

pm20002maMondownRmonUnicastCounterClientOutputTable OBJECT-TYPE
	SYNTAX  SEQUENCE OF Pm20002maMondownRmonUnicastCounterClientOutputEntry
	MAX-ACCESS not-accessible
	STATUS current
	DESCRIPTION
        "
        List of pm20002maMondownRmonUnicastCounterClientOutput
        Article
        "
	::= { pm20002maMonClientRmonCounter 688 }


pm20002maMondownRmonUnicastCounterClientOutputEntry OBJECT-TYPE
	SYNTAX Pm20002maMondownRmonUnicastCounterClientOutputEntry
	MAX-ACCESS not-accessible
	STATUS current
	DESCRIPTION
        "
        Row definition for the pm20002maMondownRmonUnicastCounterClientOutput
        table
        "
	INDEX   { pm20002maMondownRmonUnicastCounterClientOutputIndex }
	::= { pm20002maMondownRmonUnicastCounterClientOutputTable 1 }


Pm20002maMondownRmonUnicastCounterClientOutputEntry ::=
	SEQUENCE {
	pm20002maMondownRmonUnicastCounterClientOutputIndex
		INTEGER,
	pm20002maMondownRmonUnicastCounterClientOutputValuePortn
		Counter64,
	pm20002maMondownRmonUnicastCounterClientOutputErrorPortn
		EkiOnOff,
	pm20002maMondownRmonUnicastCounterClientOutputOverloadPortn
		EkiOnOff
	}


pm20002maMondownRmonUnicastCounterClientOutputIndex OBJECT-TYPE
	SYNTAX  INTEGER(0..128)
	MAX-ACCESS  read-only
	STATUS current
	DESCRIPTION
        "
        Index definition for the pm20002maMondownRmonUnicastCounterClientOutput
        table
        "
	::= { pm20002maMondownRmonUnicastCounterClientOutputEntry 1 }


pm20002maMondownRmonUnicastCounterClientOutputValuePortn OBJECT-TYPE
	SYNTAX  Counter64
	MAX-ACCESS read-only
	STATUS current
	DESCRIPTION
        "
        Client Output Unicast Packets
         :This counter is increased each
        time a Unicast packet is transmitted
        on the client port  <Help>  This
        counter gives the number of Unicast
        packets transmitted on the client
        port
        "
	::= { pm20002maMondownRmonUnicastCounterClientOutputEntry 2 }


pm20002maMondownRmonUnicastCounterClientOutputErrorPortn OBJECT-TYPE
	SYNTAX  EkiOnOff
	MAX-ACCESS read-only
	STATUS current
	DESCRIPTION
        "
        Unicast Counter Error :This OID
        when set indicates the Unicast
         counter value is invalid on client
        port
        "
	::= { pm20002maMondownRmonUnicastCounterClientOutputEntry 3 }


pm20002maMondownRmonUnicastCounterClientOutputOverloadPortn OBJECT-TYPE
	SYNTAX  EkiOnOff
	MAX-ACCESS read-only
	STATUS current
	DESCRIPTION
        "
        Unicast Counter Overload :This
        OID when set indicates a Unicast
        counter overload on client port
        "
	::= { pm20002maMondownRmonUnicastCounterClientOutputEntry 4 }


--- *********************************************************
---     TABLE for the pm20002maMondownRmonNonunicastCounterClientOutput articles
--- *********************************************************

pm20002maMondownRmonNonunicastCounterClientOutputTable OBJECT-TYPE
	SYNTAX  SEQUENCE OF Pm20002maMondownRmonNonunicastCounterClientOutputEntry
	MAX-ACCESS not-accessible
	STATUS current
	DESCRIPTION
        "
        List of pm20002maMondownRmonNonunicastCounterClientOutput
        Article
        "
	::= { pm20002maMonClientRmonCounter 720 }


pm20002maMondownRmonNonunicastCounterClientOutputEntry OBJECT-TYPE
	SYNTAX Pm20002maMondownRmonNonunicastCounterClientOutputEntry
	MAX-ACCESS not-accessible
	STATUS current
	DESCRIPTION
        "
        Row definition for the pm20002maMondownRmonNonunicastCounterClientOutput
        table
        "
	INDEX   { pm20002maMondownRmonNonunicastCounterClientOutputIndex }
	::= { pm20002maMondownRmonNonunicastCounterClientOutputTable 1 }


Pm20002maMondownRmonNonunicastCounterClientOutputEntry ::=
	SEQUENCE {
	pm20002maMondownRmonNonunicastCounterClientOutputIndex
		INTEGER,
	pm20002maMondownRmonNonunicastCounterClientOutputValuePortn
		Counter64,
	pm20002maMondownRmonNonunicastCounterClientOutputErrorPortn
		EkiOnOff,
	pm20002maMondownRmonNonunicastCounterClientOutputOverloadPortn
		EkiOnOff
	}


pm20002maMondownRmonNonunicastCounterClientOutputIndex OBJECT-TYPE
	SYNTAX  INTEGER(0..128)
	MAX-ACCESS  read-only
	STATUS current
	DESCRIPTION
        "
        Index definition for the pm20002maMondownRmonNonunicastCounterClientOutput
        table
        "
	::= { pm20002maMondownRmonNonunicastCounterClientOutputEntry 1 }


pm20002maMondownRmonNonunicastCounterClientOutputValuePortn OBJECT-TYPE
	SYNTAX  Counter64
	MAX-ACCESS read-only
	STATUS current
	DESCRIPTION
        "
        Client Output Non Unicast Packets
        :This counter is increased each
        time a Non-Unicast packet is transmitted
        on the client port  <Help>  This
        counter gives the number of Non-Unicast
        packets transmitted on the client
        port
        "
	::= { pm20002maMondownRmonNonunicastCounterClientOutputEntry 2 }


pm20002maMondownRmonNonunicastCounterClientOutputErrorPortn OBJECT-TYPE
	SYNTAX  EkiOnOff
	MAX-ACCESS read-only
	STATUS current
	DESCRIPTION
        "
        Non Unicast Counter Error :This
        OID when set indicates the Non-Unicast
        counter value is invalid on client
        port
        "
	::= { pm20002maMondownRmonNonunicastCounterClientOutputEntry 3 }


pm20002maMondownRmonNonunicastCounterClientOutputOverloadPortn OBJECT-TYPE
	SYNTAX  EkiOnOff
	MAX-ACCESS read-only
	STATUS current
	DESCRIPTION
        "
        Non Unicast Counter Overload :This
        OID when set indicates a Non-Unicast
        counter overload on client port
        "
	::= { pm20002maMondownRmonNonunicastCounterClientOutputEntry 4 }







--- *****************************************************
--- $$$$$$$$$$$$$$$$$$$$$$$$$$$$$$$$$$$$$$$$$$$$$$$$$$$$$
---     MEASURES
--- $$$$$$$$$$$$$$$$$$$$$$$$$$$$$$$$$$$$$$$$$$$$$$$$$$$$$
--- *****************************************************



pm20002maMesrsynth0 OBJECT-TYPE
	  SYNTAX EkiMeasureType
	  MAX-ACCESS read-only
	  STATUS deprecated
	  DESCRIPTION
        "
        Not Used :
        "
	  ::= { pm20002maMesrOther 0 }



pm20002maMesrsynth1 OBJECT-TYPE
	  SYNTAX EkiMeasureType
	  MAX-ACCESS read-only
	  STATUS deprecated
	  DESCRIPTION
        "
        Not Used :
        "
	  ::= { pm20002maMesrOther 1 }



--- *****************************************************
---     LEAF for the pmIntervalNumber article
--- *****************************************************

pm20002maMesrpmIntervalNumber OBJECT-TYPE
	  SYNTAX Unsigned32 (0..65535)
	  MAX-ACCESS read-only
	  STATUS current
	  DESCRIPTION
        "
        PM Interval Counter :
        "
	  ::= { pm20002maMesrOther 7 }



--- *****************************************************
---     LEAF for the clientCfpTemp article
--- *****************************************************

pm20002maMesrclientCfpTemp OBJECT-TYPE
	  SYNTAX Unsigned32 (0..65535)
	  MAX-ACCESS read-only
	  STATUS current
	  DESCRIPTION
        "
        Client Trscv Temperature :This
        OID gives the temperature value
        of the Client Transceiver, read
        from the DDM (Digital Diagnostic
        Monitoring) (Temperature = AV/256)
        (Unit = C) <Help> This Measure
         gives the temperature value of
        the Client Transceiver
        "
	  ::= { pm20002maMesrClient 8 }



--- *****************************************************
---     LEAF for the clientCfp3v3Voltage article
--- *****************************************************

pm20002maMesrclientCfp3v3Voltage OBJECT-TYPE
	  SYNTAX Unsigned32 (0..65535)
	  MAX-ACCESS read-only
	  STATUS current
	  DESCRIPTION
        "
        Client Trscv Voltage :This OID
        gives the 3V3 voltage value of
         the Client Transceiver, read from
        the DDM (Digital Diagnostic Monitoring)
         (Voltage = AV/1000) (Unit = V)
        <Help> This Measure gives the 3V3
        voltage value of the Client Transceiver
        "
	  ::= { pm20002maMesrClient 9 }



--- *****************************************************
---     LEAF for the clientSoaBiasCurrent article
--- *****************************************************

pm20002maMesrclientSoaBiasCurrent OBJECT-TYPE
	  SYNTAX Unsigned32 (0..65535)
	  MAX-ACCESS read-only
	  STATUS current
	  DESCRIPTION
        "
        Client Trscv SOA Bias :This OID
        gives the SOA bias value of the
        Client Transceiver, read from the
        DDM (Digital Diagnostic Monitoring)
         (Bias = AV/500) (Unit = mA) <Help>
        This Measure gives the SOA bias
        value of the Client Transceiver
        "
	  ::= { pm20002maMesrClient 10 }



--- *****************************************************
---     LEAF for the lineMsaTemp article
--- *****************************************************

pm20002maMesrlineMsaTemp OBJECT-TYPE
	  SYNTAX Unsigned32 (0..65535)
	  MAX-ACCESS read-only
	  STATUS current
	  DESCRIPTION
        "
        Line Trscv Temperature :This OID
        gives the temperature value of
         the Line Transceiver, read from
        the DDM (Digital Diagnostic Monitoring)
         (Temperature = AV/256) (Unit =
        C) <Help> This Measure gives the
        temperature value of the Line Transceiver.This
        temperature must remain below 95°C
        for proper operation
        "
	  ::= { pm20002maMesrLine 12 }



--- *****************************************************
---     LEAF for the lineMsa3v3Voltage article
--- *****************************************************

pm20002maMesrlineMsa3v3Voltage OBJECT-TYPE
	  SYNTAX Unsigned32 (0..65535)
	  MAX-ACCESS read-only
	  STATUS current
	  DESCRIPTION
        "
        Line Trscv Voltage :This OID gives
        the 3V3 voltage value of the Line
        Transceiver, read from the DDM
         (Digital Diagnostic Monitoring)
        (Voltage = AV/1000) (Unit = V)
         <Help> This Measure gives the
         3V3 voltage value of the Line
         Transceiver
        "
	  ::= { pm20002maMesrLine 13 }



--- *****************************************************
---     LEAF for the lineSoaBiasCurrent article
--- *****************************************************

pm20002maMesrlineSoaBiasCurrent OBJECT-TYPE
	  SYNTAX Unsigned32 (0..65535)
	  MAX-ACCESS read-only
	  STATUS current
	  DESCRIPTION
        "
        Line Trscv SOA Bias :This OID
         gives the SOA bias value of the
        Line Transceiver,read from the
         DDM (Digital Diagnostic Monitoring)
         (Bias = AV/500) (Unit = mA) <Help>
        This Measure gives the SOA bias
        value of the Line Transceiver
        "
	  ::= { pm20002maMesrLine 14 }



--- *********************************************************
---     TABLE for the pm20002maMesrclientTxPwrMin articles
--- *********************************************************

pm20002maMesrclientTxPwrMinTable OBJECT-TYPE
	SYNTAX  SEQUENCE OF Pm20002maMesrclientTxPwrMinEntry
	MAX-ACCESS not-accessible
	STATUS current
	DESCRIPTION
        "
        List of pm20002maMesrclientTxPwrMin
        Article
        "
	::= { pm20002maMesrClient 16 }


pm20002maMesrclientTxPwrMinEntry OBJECT-TYPE
	SYNTAX Pm20002maMesrclientTxPwrMinEntry
	MAX-ACCESS not-accessible
	STATUS current
	DESCRIPTION
        "
        Row definition for the pm20002maMesrclientTxPwrMin
        table
        "
	INDEX   { pm20002maMesrclientTxPwrMinIndex }
	::= { pm20002maMesrclientTxPwrMinTable 1 }


Pm20002maMesrclientTxPwrMinEntry ::=
	SEQUENCE {
	pm20002maMesrclientTxPwrMinIndex
		INTEGER,
	pm20002maMesrclientTxPwrMinPortn
		INTEGER
	}


pm20002maMesrclientTxPwrMinIndex OBJECT-TYPE
	SYNTAX  INTEGER(0..128)
	MAX-ACCESS  read-only
	STATUS current
	DESCRIPTION
        "
        Index definition for the pm20002maMesrclientTxPwrMin
        table
        "
	::= { pm20002maMesrclientTxPwrMinEntry 1 }


pm20002maMesrclientTxPwrMinPortn OBJECT-TYPE
	SYNTAX  INTEGER (0..65535)
	MAX-ACCESS read-only
	STATUS current
	DESCRIPTION
        "
        Min Client Trscv Tx Power :This
        OID gives the minimum transmit
         power value among the network
         lanes of the Client Transceiver,
        read from the DDM (Digital Diagnostic
        Monitoring) (Power = 10*log(AV)-40)
        (Unit = dBm) <Help> This Measure
        gives the minimum transmit power
        value among the network lanes of
        the Client Transceiver
        "
	::= { pm20002maMesrclientTxPwrMinEntry 2 }


--- *********************************************************
---     TABLE for the pm20002maMesrclientRxPwrMin articles
--- *********************************************************

pm20002maMesrclientRxPwrMinTable OBJECT-TYPE
	SYNTAX  SEQUENCE OF Pm20002maMesrclientRxPwrMinEntry
	MAX-ACCESS not-accessible
	STATUS current
	DESCRIPTION
        "
        List of pm20002maMesrclientRxPwrMin
        Article
        "
	::= { pm20002maMesrClient 48 }


pm20002maMesrclientRxPwrMinEntry OBJECT-TYPE
	SYNTAX Pm20002maMesrclientRxPwrMinEntry
	MAX-ACCESS not-accessible
	STATUS current
	DESCRIPTION
        "
        Row definition for the pm20002maMesrclientRxPwrMin
        table
        "
	INDEX   { pm20002maMesrclientRxPwrMinIndex }
	::= { pm20002maMesrclientRxPwrMinTable 1 }


Pm20002maMesrclientRxPwrMinEntry ::=
	SEQUENCE {
	pm20002maMesrclientRxPwrMinIndex
		INTEGER,
	pm20002maMesrclientRxPwrMinPortn
		INTEGER
	}


pm20002maMesrclientRxPwrMinIndex OBJECT-TYPE
	SYNTAX  INTEGER(0..128)
	MAX-ACCESS  read-only
	STATUS current
	DESCRIPTION
        "
        Index definition for the pm20002maMesrclientRxPwrMin
        table
        "
	::= { pm20002maMesrclientRxPwrMinEntry 1 }


pm20002maMesrclientRxPwrMinPortn OBJECT-TYPE
	SYNTAX  INTEGER (0..65535)
	MAX-ACCESS read-only
	STATUS current
	DESCRIPTION
        "
        Min Client Trscv Rx Power :This
        OID gives the minimum receive power
        value among the network lanes of
        the Client Transceiver, read from
        the DDM (Digital Diagnostic Monitoring)
        (Power = 10*log(AV)-40) (Unit =
        dBm) <Help> This Measure gives
         the minimum receive power value
        among the network lanes of the
         Client Transceiver
        "
	::= { pm20002maMesrclientRxPwrMinEntry 2 }


--- *********************************************************
---     TABLE for the pm20002maMesrclientTxPwrMax articles
--- *********************************************************

pm20002maMesrclientTxPwrMaxTable OBJECT-TYPE
	SYNTAX  SEQUENCE OF Pm20002maMesrclientTxPwrMaxEntry
	MAX-ACCESS not-accessible
	STATUS current
	DESCRIPTION
        "
        List of pm20002maMesrclientTxPwrMax
        Article
        "
	::= { pm20002maMesrClient 80 }


pm20002maMesrclientTxPwrMaxEntry OBJECT-TYPE
	SYNTAX Pm20002maMesrclientTxPwrMaxEntry
	MAX-ACCESS not-accessible
	STATUS current
	DESCRIPTION
        "
        Row definition for the pm20002maMesrclientTxPwrMax
        table
        "
	INDEX   { pm20002maMesrclientTxPwrMaxIndex }
	::= { pm20002maMesrclientTxPwrMaxTable 1 }


Pm20002maMesrclientTxPwrMaxEntry ::=
	SEQUENCE {
	pm20002maMesrclientTxPwrMaxIndex
		INTEGER,
	pm20002maMesrclientTxPwrMaxPortn
		INTEGER
	}


pm20002maMesrclientTxPwrMaxIndex OBJECT-TYPE
	SYNTAX  INTEGER(0..128)
	MAX-ACCESS  read-only
	STATUS current
	DESCRIPTION
        "
        Index definition for the pm20002maMesrclientTxPwrMax
        table
        "
	::= { pm20002maMesrclientTxPwrMaxEntry 1 }


pm20002maMesrclientTxPwrMaxPortn OBJECT-TYPE
	SYNTAX  INTEGER (0..65535)
	MAX-ACCESS read-only
	STATUS current
	DESCRIPTION
        "
        Max Client Trscv Tx Power :This
        OID gives the maximum transmit
         power value among the network
         lanes of the Client Transceiver,
        read from the DDM (Digital Diagnostic
        Monitoring) (Power = 10*log(AV)-40)
        (Unit = dBm) <Help> This Measure
        gives the maximum transmit power
        value among the network lanes of
        the Client Transceiver
        "
	::= { pm20002maMesrclientTxPwrMaxEntry 2 }


--- *********************************************************
---     TABLE for the pm20002maMesrclientRxPwrMax articles
--- *********************************************************

pm20002maMesrclientRxPwrMaxTable OBJECT-TYPE
	SYNTAX  SEQUENCE OF Pm20002maMesrclientRxPwrMaxEntry
	MAX-ACCESS not-accessible
	STATUS current
	DESCRIPTION
        "
        List of pm20002maMesrclientRxPwrMax
        Article
        "
	::= { pm20002maMesrClient 112 }


pm20002maMesrclientRxPwrMaxEntry OBJECT-TYPE
	SYNTAX Pm20002maMesrclientRxPwrMaxEntry
	MAX-ACCESS not-accessible
	STATUS current
	DESCRIPTION
        "
        Row definition for the pm20002maMesrclientRxPwrMax
        table
        "
	INDEX   { pm20002maMesrclientRxPwrMaxIndex }
	::= { pm20002maMesrclientRxPwrMaxTable 1 }


Pm20002maMesrclientRxPwrMaxEntry ::=
	SEQUENCE {
	pm20002maMesrclientRxPwrMaxIndex
		INTEGER,
	pm20002maMesrclientRxPwrMaxPortn
		INTEGER
	}


pm20002maMesrclientRxPwrMaxIndex OBJECT-TYPE
	SYNTAX  INTEGER(0..128)
	MAX-ACCESS  read-only
	STATUS current
	DESCRIPTION
        "
        Index definition for the pm20002maMesrclientRxPwrMax
        table
        "
	::= { pm20002maMesrclientRxPwrMaxEntry 1 }


pm20002maMesrclientRxPwrMaxPortn OBJECT-TYPE
	SYNTAX  INTEGER (0..65535)
	MAX-ACCESS read-only
	STATUS current
	DESCRIPTION
        "
        Max Client Trscv Rx Power :This
        OID gives the maximum receive power
        value among the network lanes of
        the Client Transceiver, read in
        the DDM (Digital Diagnostic Monitoring)
        (Power = 10*log(AV)-40) (Unit =
        dBm) <Help> This Measure gives
         the maximum receive power value
        among the network lanes of the
         Client Transceiver
        "
	::= { pm20002maMesrclientRxPwrMaxEntry 2 }


--- *********************************************************
---     TABLE for the pm20002maMesrlineNetTxLaserOutputPwr articles
--- *********************************************************

pm20002maMesrlineNetTxLaserOutputPwrTable OBJECT-TYPE
	SYNTAX  SEQUENCE OF Pm20002maMesrlineNetTxLaserOutputPwrEntry
	MAX-ACCESS not-accessible
	STATUS current
	DESCRIPTION
        "
        List of pm20002maMesrlineNetTxLaserOutputPwr
        Article
        "
	::= { pm20002maMesrLine 144 }


pm20002maMesrlineNetTxLaserOutputPwrEntry OBJECT-TYPE
	SYNTAX Pm20002maMesrlineNetTxLaserOutputPwrEntry
	MAX-ACCESS not-accessible
	STATUS current
	DESCRIPTION
        "
        Row definition for the pm20002maMesrlineNetTxLaserOutputPwr
        table
        "
	INDEX   { pm20002maMesrlineNetTxLaserOutputPwrIndex }
	::= { pm20002maMesrlineNetTxLaserOutputPwrTable 1 }


Pm20002maMesrlineNetTxLaserOutputPwrEntry ::=
	SEQUENCE {
	pm20002maMesrlineNetTxLaserOutputPwrIndex
		INTEGER,
	pm20002maMesrlineNetTxLaserOutputPwrPortn
		INTEGER
	}


pm20002maMesrlineNetTxLaserOutputPwrIndex OBJECT-TYPE
	SYNTAX  INTEGER(0..128)
	MAX-ACCESS  read-only
	STATUS current
	DESCRIPTION
        "
        Index definition for the pm20002maMesrlineNetTxLaserOutputPwr
        table
        "
	::= { pm20002maMesrlineNetTxLaserOutputPwrEntry 1 }


pm20002maMesrlineNetTxLaserOutputPwrPortn OBJECT-TYPE
	SYNTAX  INTEGER (0..65535)
	MAX-ACCESS read-only
	STATUS current
	DESCRIPTION
        "
        Current Line Trscv Tx Power :This
        OID gives the Tx Laser transmit
        power value of the Line Transceiver,
        read in the DDM (Digital Diagnostic
        Monitoring) (Power = AV/100) (Unit
        = dBm) <Help> This Measure gives
        the Tx Laser transmit power value
        of the Line Transceiver
        "
	::= { pm20002maMesrlineNetTxLaserOutputPwrEntry 2 }


--- *********************************************************
---     TABLE for the pm20002maMesrlineNetTxLaserTemp articles
--- *********************************************************

pm20002maMesrlineNetTxLaserTempTable OBJECT-TYPE
	SYNTAX  SEQUENCE OF Pm20002maMesrlineNetTxLaserTempEntry
	MAX-ACCESS not-accessible
	STATUS current
	DESCRIPTION
        "
        List of pm20002maMesrlineNetTxLaserTemp
        Article
        "
	::= { pm20002maMesrLine 148 }


pm20002maMesrlineNetTxLaserTempEntry OBJECT-TYPE
	SYNTAX Pm20002maMesrlineNetTxLaserTempEntry
	MAX-ACCESS not-accessible
	STATUS current
	DESCRIPTION
        "
        Row definition for the pm20002maMesrlineNetTxLaserTemp
        table
        "
	INDEX   { pm20002maMesrlineNetTxLaserTempIndex }
	::= { pm20002maMesrlineNetTxLaserTempTable 1 }


Pm20002maMesrlineNetTxLaserTempEntry ::=
	SEQUENCE {
	pm20002maMesrlineNetTxLaserTempIndex
		INTEGER,
	pm20002maMesrlineNetTxLaserTempPortn
		INTEGER
	}


pm20002maMesrlineNetTxLaserTempIndex OBJECT-TYPE
	SYNTAX  INTEGER(0..128)
	MAX-ACCESS  read-only
	STATUS current
	DESCRIPTION
        "
        Index definition for the pm20002maMesrlineNetTxLaserTemp
        table
        "
	::= { pm20002maMesrlineNetTxLaserTempEntry 1 }


pm20002maMesrlineNetTxLaserTempPortn OBJECT-TYPE
	SYNTAX  INTEGER (0..65535)
	MAX-ACCESS read-only
	STATUS current
	DESCRIPTION
        "
        Current Line Trscv Tx Laser Temperature
        :This OID gives the Tx Laser Temperature
        value of the Line Transceiver,
         read from the DDM (Digital Diagnostic
        Monitoring) (Temperature = AV/256)
        (Unit = C) <Help> This Measure
         gives the Tx Laser Temperature
        value of the Line Transceiver
        "
	::= { pm20002maMesrlineNetTxLaserTempEntry 2 }


--- *********************************************************
---     TABLE for the pm20002maMesrlineNetTxBiasCurrent articles
--- *********************************************************

pm20002maMesrlineNetTxBiasCurrentTable OBJECT-TYPE
	SYNTAX  SEQUENCE OF Pm20002maMesrlineNetTxBiasCurrentEntry
	MAX-ACCESS not-accessible
	STATUS current
	DESCRIPTION
        "
        List of pm20002maMesrlineNetTxBiasCurrent
        Article
        "
	::= { pm20002maMesrLine 152 }


pm20002maMesrlineNetTxBiasCurrentEntry OBJECT-TYPE
	SYNTAX Pm20002maMesrlineNetTxBiasCurrentEntry
	MAX-ACCESS not-accessible
	STATUS current
	DESCRIPTION
        "
        Row definition for the pm20002maMesrlineNetTxBiasCurrent
        table
        "
	INDEX   { pm20002maMesrlineNetTxBiasCurrentIndex }
	::= { pm20002maMesrlineNetTxBiasCurrentTable 1 }


Pm20002maMesrlineNetTxBiasCurrentEntry ::=
	SEQUENCE {
	pm20002maMesrlineNetTxBiasCurrentIndex
		INTEGER,
	pm20002maMesrlineNetTxBiasCurrentPortn
		INTEGER
	}


pm20002maMesrlineNetTxBiasCurrentIndex OBJECT-TYPE
	SYNTAX  INTEGER(0..128)
	MAX-ACCESS  read-only
	STATUS current
	DESCRIPTION
        "
        Index definition for the pm20002maMesrlineNetTxBiasCurrent
        table
        "
	::= { pm20002maMesrlineNetTxBiasCurrentEntry 1 }


pm20002maMesrlineNetTxBiasCurrentPortn OBJECT-TYPE
	SYNTAX  INTEGER (0..65535)
	MAX-ACCESS read-only
	STATUS current
	DESCRIPTION
        "
        Current Line Trscv Tx Laser Bias
        :This OID gives the Tx Laser Bias
        value of the Line Transceiver,
         read from the DDM (Digital Diagnostic
        Monitoring) (Bias = AV/10) (Unit
        = mA) <Help> This Measure gives
        the Tx Laser Bias value of the
         Line Transceiver
        "
	::= { pm20002maMesrlineNetTxBiasCurrentEntry 2 }


--- *********************************************************
---     TABLE for the pm20002maMesrlineNetRxInputPwr articles
--- *********************************************************

pm20002maMesrlineNetRxInputPwrTable OBJECT-TYPE
	SYNTAX  SEQUENCE OF Pm20002maMesrlineNetRxInputPwrEntry
	MAX-ACCESS not-accessible
	STATUS current
	DESCRIPTION
        "
        List of pm20002maMesrlineNetRxInputPwr
        Article
        "
	::= { pm20002maMesrLine 156 }


pm20002maMesrlineNetRxInputPwrEntry OBJECT-TYPE
	SYNTAX Pm20002maMesrlineNetRxInputPwrEntry
	MAX-ACCESS not-accessible
	STATUS current
	DESCRIPTION
        "
        Row definition for the pm20002maMesrlineNetRxInputPwr
        table
        "
	INDEX   { pm20002maMesrlineNetRxInputPwrIndex }
	::= { pm20002maMesrlineNetRxInputPwrTable 1 }


Pm20002maMesrlineNetRxInputPwrEntry ::=
	SEQUENCE {
	pm20002maMesrlineNetRxInputPwrIndex
		INTEGER,
	pm20002maMesrlineNetRxInputPwrPortn
		INTEGER
	}


pm20002maMesrlineNetRxInputPwrIndex OBJECT-TYPE
	SYNTAX  INTEGER(0..128)
	MAX-ACCESS  read-only
	STATUS current
	DESCRIPTION
        "
        Index definition for the pm20002maMesrlineNetRxInputPwr
        table
        "
	::= { pm20002maMesrlineNetRxInputPwrEntry 1 }


pm20002maMesrlineNetRxInputPwrPortn OBJECT-TYPE
	SYNTAX  INTEGER (0..65535)
	MAX-ACCESS read-only
	STATUS current
	DESCRIPTION
        "
        Current Line Trscv Rx Power :This
        OID gives the Receive power value
        of the Line Transceiver, read in
        the DDM (Digital Diagnostic Monitoring)
        (Power = AV/100) (Unit = dBm) <Help>
        This Measure gives the Receive
         power value of the Line Transceiver
        "
	::= { pm20002maMesrlineNetRxInputPwrEntry 2 }


--- *********************************************************
---     TABLE for the pm20002maMesrlineResidualChromaticDisp articles
--- *********************************************************

pm20002maMesrlineResidualChromaticDispTable OBJECT-TYPE
	SYNTAX  SEQUENCE OF Pm20002maMesrlineResidualChromaticDispEntry
	MAX-ACCESS not-accessible
	STATUS current
	DESCRIPTION
        "
        List of pm20002maMesrlineResidualChromaticDisp
        Article
        "
	::= { pm20002maMesrLine 160 }


pm20002maMesrlineResidualChromaticDispEntry OBJECT-TYPE
	SYNTAX Pm20002maMesrlineResidualChromaticDispEntry
	MAX-ACCESS not-accessible
	STATUS current
	DESCRIPTION
        "
        Row definition for the pm20002maMesrlineResidualChromaticDisp
        table
        "
	INDEX   { pm20002maMesrlineResidualChromaticDispIndex }
	::= { pm20002maMesrlineResidualChromaticDispTable 1 }


Pm20002maMesrlineResidualChromaticDispEntry ::=
	SEQUENCE {
	pm20002maMesrlineResidualChromaticDispIndex
		INTEGER,
	pm20002maMesrlineResidualChromaticDispPortn
		INTEGER
	}


pm20002maMesrlineResidualChromaticDispIndex OBJECT-TYPE
	SYNTAX  INTEGER(0..128)
	MAX-ACCESS  read-only
	STATUS current
	DESCRIPTION
        "
        Index definition for the pm20002maMesrlineResidualChromaticDisp
        table
        "
	::= { pm20002maMesrlineResidualChromaticDispEntry 1 }


pm20002maMesrlineResidualChromaticDispPortn OBJECT-TYPE
	SYNTAX  INTEGER (0..65535)
	MAX-ACCESS read-only
	STATUS current
	DESCRIPTION
        "
        Current Residual Chromatic Dispersion
        :This OID gives the current Residual
        Chromatic Dispersion on the Line
        interface  (Unit = ps/nm)<Help>
        This measure gives the current
         Residual Chromatic Dispersion
         on the Line interface.
        "
	::= { pm20002maMesrlineResidualChromaticDispEntry 2 }


--- *********************************************************
---     TABLE for the pm20002maMesrlineDiffGroupDelay articles
--- *********************************************************

pm20002maMesrlineDiffGroupDelayTable OBJECT-TYPE
	SYNTAX  SEQUENCE OF Pm20002maMesrlineDiffGroupDelayEntry
	MAX-ACCESS not-accessible
	STATUS current
	DESCRIPTION
        "
        List of pm20002maMesrlineDiffGroupDelay
        Article
        "
	::= { pm20002maMesrLine 164 }


pm20002maMesrlineDiffGroupDelayEntry OBJECT-TYPE
	SYNTAX Pm20002maMesrlineDiffGroupDelayEntry
	MAX-ACCESS not-accessible
	STATUS current
	DESCRIPTION
        "
        Row definition for the pm20002maMesrlineDiffGroupDelay
        table
        "
	INDEX   { pm20002maMesrlineDiffGroupDelayIndex }
	::= { pm20002maMesrlineDiffGroupDelayTable 1 }


Pm20002maMesrlineDiffGroupDelayEntry ::=
	SEQUENCE {
	pm20002maMesrlineDiffGroupDelayIndex
		INTEGER,
	pm20002maMesrlineDiffGroupDelayPortn
		INTEGER
	}


pm20002maMesrlineDiffGroupDelayIndex OBJECT-TYPE
	SYNTAX  INTEGER(0..128)
	MAX-ACCESS  read-only
	STATUS current
	DESCRIPTION
        "
        Index definition for the pm20002maMesrlineDiffGroupDelay
        table
        "
	::= { pm20002maMesrlineDiffGroupDelayEntry 1 }


pm20002maMesrlineDiffGroupDelayPortn OBJECT-TYPE
	SYNTAX  INTEGER (0..65535)
	MAX-ACCESS read-only
	STATUS current
	DESCRIPTION
        "
        Current Differential Group Delay
        :This OID gives the current Differential
        Group Delay on the Line interface
          (Unit = ps)<Help> This measure
        gives the current Differential
         Group Delay on the Line interface.
        "
	::= { pm20002maMesrlineDiffGroupDelayEntry 2 }


--- *********************************************************
---     TABLE for the pm20002maMesrlineQFactor articles
--- *********************************************************

pm20002maMesrlineQFactorTable OBJECT-TYPE
	SYNTAX  SEQUENCE OF Pm20002maMesrlineQFactorEntry
	MAX-ACCESS not-accessible
	STATUS current
	DESCRIPTION
        "
        List of pm20002maMesrlineQFactor
        Article
        "
	::= { pm20002maMesrLine 168 }


pm20002maMesrlineQFactorEntry OBJECT-TYPE
	SYNTAX Pm20002maMesrlineQFactorEntry
	MAX-ACCESS not-accessible
	STATUS current
	DESCRIPTION
        "
        Row definition for the pm20002maMesrlineQFactor
        table
        "
	INDEX   { pm20002maMesrlineQFactorIndex }
	::= { pm20002maMesrlineQFactorTable 1 }


Pm20002maMesrlineQFactorEntry ::=
	SEQUENCE {
	pm20002maMesrlineQFactorIndex
		INTEGER,
	pm20002maMesrlineQFactorPortn
		INTEGER
	}


pm20002maMesrlineQFactorIndex OBJECT-TYPE
	SYNTAX  INTEGER(0..128)
	MAX-ACCESS  read-only
	STATUS current
	DESCRIPTION
        "
        Index definition for the pm20002maMesrlineQFactor
        table
        "
	::= { pm20002maMesrlineQFactorEntry 1 }


pm20002maMesrlineQFactorPortn OBJECT-TYPE
	SYNTAX  INTEGER (0..65535)
	MAX-ACCESS read-only
	STATUS current
	DESCRIPTION
        "
        Current Q Factor :This OID gives
        the current Q Factor on the Line
        interface   (Unit = dB) <Help>
         This measure gives the current
        Q Factor on the Line interface.
        "
	::= { pm20002maMesrlineQFactorEntry 2 }


--- *********************************************************
---     TABLE for the pm20002maMesrlineCarrierFreqOffset articles
--- *********************************************************

pm20002maMesrlineCarrierFreqOffsetTable OBJECT-TYPE
	SYNTAX  SEQUENCE OF Pm20002maMesrlineCarrierFreqOffsetEntry
	MAX-ACCESS not-accessible
	STATUS current
	DESCRIPTION
        "
        List of pm20002maMesrlineCarrierFreqOffset
        Article
        "
	::= { pm20002maMesrLine 172 }


pm20002maMesrlineCarrierFreqOffsetEntry OBJECT-TYPE
	SYNTAX Pm20002maMesrlineCarrierFreqOffsetEntry
	MAX-ACCESS not-accessible
	STATUS current
	DESCRIPTION
        "
        Row definition for the pm20002maMesrlineCarrierFreqOffset
        table
        "
	INDEX   { pm20002maMesrlineCarrierFreqOffsetIndex }
	::= { pm20002maMesrlineCarrierFreqOffsetTable 1 }


Pm20002maMesrlineCarrierFreqOffsetEntry ::=
	SEQUENCE {
	pm20002maMesrlineCarrierFreqOffsetIndex
		INTEGER,
	pm20002maMesrlineCarrierFreqOffsetPortn
		INTEGER
	}


pm20002maMesrlineCarrierFreqOffsetIndex OBJECT-TYPE
	SYNTAX  INTEGER(0..128)
	MAX-ACCESS  read-only
	STATUS current
	DESCRIPTION
        "
        Index definition for the pm20002maMesrlineCarrierFreqOffset
        table
        "
	::= { pm20002maMesrlineCarrierFreqOffsetEntry 1 }


pm20002maMesrlineCarrierFreqOffsetPortn OBJECT-TYPE
	SYNTAX  INTEGER (0..65535)
	MAX-ACCESS read-only
	STATUS current
	DESCRIPTION
        "
        Current Carrier Frequency Offset
        :This OID gives the current Carrier
        Frequency Offset on the Line interface
          (Unit = Mhz)<Help> This measure
        gives the current Carrier Frequency
        Offset on the Line interface.
        "
	::= { pm20002maMesrlineCarrierFreqOffsetEntry 2 }


--- *********************************************************
---     TABLE for the pm20002maMesrlineOsnr articles
--- *********************************************************

pm20002maMesrlineOsnrTable OBJECT-TYPE
	SYNTAX  SEQUENCE OF Pm20002maMesrlineOsnrEntry
	MAX-ACCESS not-accessible
	STATUS current
	DESCRIPTION
        "
        List of pm20002maMesrlineOsnr
         Article
        "
	::= { pm20002maMesrLine 176 }


pm20002maMesrlineOsnrEntry OBJECT-TYPE
	SYNTAX Pm20002maMesrlineOsnrEntry
	MAX-ACCESS not-accessible
	STATUS current
	DESCRIPTION
        "
        Row definition for the pm20002maMesrlineOsnr
        table
        "
	INDEX   { pm20002maMesrlineOsnrIndex }
	::= { pm20002maMesrlineOsnrTable 1 }


Pm20002maMesrlineOsnrEntry ::=
	SEQUENCE {
	pm20002maMesrlineOsnrIndex
		INTEGER,
	pm20002maMesrlineOsnrPortn
		INTEGER
	}


pm20002maMesrlineOsnrIndex OBJECT-TYPE
	SYNTAX  INTEGER(0..128)
	MAX-ACCESS  read-only
	STATUS current
	DESCRIPTION
        "
        Index definition for the pm20002maMesrlineOsnr
        table
        "
	::= { pm20002maMesrlineOsnrEntry 1 }


pm20002maMesrlineOsnrPortn OBJECT-TYPE
	SYNTAX  INTEGER (0..65535)
	MAX-ACCESS read-only
	STATUS current
	DESCRIPTION
        "
        Current OSNR :This OID gives the
        current OSNR on the Line interface
          (OSNR = AV/10) (Unit = dB)<Help>
        This measure gives the current
         OSNR on the Line interface.
        "
	::= { pm20002maMesrlineOsnrEntry 2 }


--- *****************************************************
---     LEAF for the lineNetTxLaserOutputPwrAverage article
--- *****************************************************

pm20002maMesrlineNetTxLaserOutputPwrAverage OBJECT-TYPE
	  SYNTAX Unsigned32 (0..65535)
	  MAX-ACCESS read-only
	  STATUS current
	  DESCRIPTION
        "
        Average Line Trscv Tx Power :This
        OID gives the average Tx Laser
         transmit power value among the
        network lanes of the Line Transceiver,
        read in the DDM (Digital Diagnostic
        Monitoring)  (Power = AV/100) (Unit
        = dBm) (Unit = dBm) <Help> This
        Measure gives the average Tx Laser
        transmit power value among the
         network lanes of the Line Transceiver
        "
	  ::= { pm20002maMesrOther 196 }



--- *****************************************************
---     LEAF for the lineNetTxLaserTempAverage article
--- *****************************************************

pm20002maMesrlineNetTxLaserTempAverage OBJECT-TYPE
	  SYNTAX Unsigned32 (0..65535)
	  MAX-ACCESS read-only
	  STATUS current
	  DESCRIPTION
        "
        Average Line Trscv Tx Laser Temperature
        :This OID gives the average Tx
         Laser Temperature value among
         the network lanes of the Line
         Transceiver, read from the DDM
        (Digital Diagnostic Monitoring)
        (Temperature = AV/256) (Unit =
         C) <Help> This Measure gives the
        average Tx Laser Temperature value
        among the network lanes of the
         Line Transceiver
        "
	  ::= { pm20002maMesrOther 197 }



--- *****************************************************
---     LEAF for the lineNetTxBiasCurrentAverage article
--- *****************************************************

pm20002maMesrlineNetTxBiasCurrentAverage OBJECT-TYPE
	  SYNTAX Unsigned32 (0..65535)
	  MAX-ACCESS read-only
	  STATUS current
	  DESCRIPTION
        "
        Average Line Trscv Tx Laser Bias
        :This OID gives the average Tx
         Laser Bias value among the network
        lanes of the Line Transceiver,
         read from the DDM (Digital Diagnostic
        Monitoring) (Bias = AV/10) (Unit
        = mA) <Help> This Measure gives
        the average Tx Laser Bias value
        among the network lanes of the
         Line Transceiver
        "
	  ::= { pm20002maMesrOther 198 }



--- *****************************************************
---     LEAF for the lineNetRxInputPwrAverage article
--- *****************************************************

pm20002maMesrlineNetRxInputPwrAverage OBJECT-TYPE
	  SYNTAX Unsigned32 (0..65535)
	  MAX-ACCESS read-only
	  STATUS current
	  DESCRIPTION
        "
        Average Line Trscv Rx Power :This
        OID gives the average Receive power
        value among the network lanes of
        the Line Transceiver, read in the
        DDM (Digital Diagnostic Monitoring)
        (Power = AV/100) (Unit = dBm) <Help>
        This Measure gives the average
         Receive power value among the
         network lanes of the Line Transceiver
        "
	  ::= { pm20002maMesrOther 199 }



--- *****************************************************
---     LEAF for the lineResidualChromaticDispAverage article
--- *****************************************************

pm20002maMesrlineResidualChromaticDispAverage OBJECT-TYPE
	  SYNTAX Unsigned32 (0..65535)
	  MAX-ACCESS read-only
	  STATUS current
	  DESCRIPTION
        "
        Average Residual Chromatic Dispersion
        :This OID gives the average Residual
        Chromatic Dispersion on the Line
        interface since the last measure
        reset <Help> This measure gives
        the average Residual Chromatic
         Dispersion on the Line interface
        since the last measure reset.
        "
	  ::= { pm20002maMesrOther 200 }



--- *****************************************************
---     LEAF for the lineDiffGroupDelayAverage article
--- *****************************************************

pm20002maMesrlineDiffGroupDelayAverage OBJECT-TYPE
	  SYNTAX Unsigned32 (0..65535)
	  MAX-ACCESS read-only
	  STATUS current
	  DESCRIPTION
        "
        Average Differential Group Delay
        :This OID gives the average Group
        Delay on the Line interface since
        the last measure reset <Help> This
        measure gives the average Differential
        Group Delay on the Line interface
        since the last measure reset.
        "
	  ::= { pm20002maMesrOther 201 }



--- *****************************************************
---     LEAF for the lineQFactorAverage article
--- *****************************************************

pm20002maMesrlineQFactorAverage OBJECT-TYPE
	  SYNTAX Unsigned32 (0..65535)
	  MAX-ACCESS read-only
	  STATUS current
	  DESCRIPTION
        "
        Average Q Factor :This OID gives
        the average Q Factor on the Line
        interface since the last measure
        reset <Help> This measure gives
        the average Q Factor on the Line
        interface since the last measure
        reset.
        "
	  ::= { pm20002maMesrOther 202 }



--- *****************************************************
---     LEAF for the lineCarrierFreqOffsetAverage article
--- *****************************************************

pm20002maMesrlineCarrierFreqOffsetAverage OBJECT-TYPE
	  SYNTAX Unsigned32 (0..65535)
	  MAX-ACCESS read-only
	  STATUS current
	  DESCRIPTION
        "
        Average Carrier Frequency Offset
        :This OID gives the average Carrier
        Frequency Offset on the Line interface
        since the last measure reset <Help>
        This measure gives the average
         Carrier Frequency Offset on the
        Line interface since the last measure
        reset
        "
	  ::= { pm20002maMesrOther 203 }



--- *****************************************************
---     LEAF for the lineOsnrAverage article
--- *****************************************************

pm20002maMesrlineOsnrAverage OBJECT-TYPE
	  SYNTAX Unsigned32 (0..65535)
	  MAX-ACCESS read-only
	  STATUS current
	  DESCRIPTION
        "
        Average OSNR :This OID gives the
        average OSNR on the Line interface
        since the last measure reset <Help>
        This measure gives the average
         OSNR on the Line interface since
        the last measure reset.
        "
	  ::= { pm20002maMesrOther 204 }



--- *****************************************************
---     LEAF for the lineNetTxLaserOutputPwrMin article
--- *****************************************************

pm20002maMesrlineNetTxLaserOutputPwrMin OBJECT-TYPE
	  SYNTAX Unsigned32 (0..65535)
	  MAX-ACCESS read-only
	  STATUS current
	  DESCRIPTION
        "
        Min Line Trscv Tx Power :This
         OID gives the minimum Tx Laser
        transmit power value among the
         network lanes of the Line Transceiver,
        read in the DDM (Digital Diagnostic
        Monitoring)  (Power = AV/100) (Unit
        = dBm) (Unit = dBm) <Help> This
        Measure gives the minimum Tx Laser
        transmit power value among the
         network lanes of the Line Transceiver
        "
	  ::= { pm20002maMesrOther 212 }



--- *****************************************************
---     LEAF for the lineNetTxLaserTempMin article
--- *****************************************************

pm20002maMesrlineNetTxLaserTempMin OBJECT-TYPE
	  SYNTAX Unsigned32 (0..65535)
	  MAX-ACCESS read-only
	  STATUS current
	  DESCRIPTION
        "
        Min Line Trscv Tx Laser Temperature
        :This OID gives the minimum Tx
         Laser Temperature value among
         the network lanes of the Line
         Transceiver, read from the DDM
        (Digital Diagnostic Monitoring)
        (Temperature = AV/256) (Unit =
         C) <Help> This Measure gives the
        minimum Tx Laser Temperature value
        among the network lanes of the
         Line Transceiver
        "
	  ::= { pm20002maMesrOther 213 }



--- *****************************************************
---     LEAF for the lineNetTxBiasCurrentMin article
--- *****************************************************

pm20002maMesrlineNetTxBiasCurrentMin OBJECT-TYPE
	  SYNTAX Unsigned32 (0..65535)
	  MAX-ACCESS read-only
	  STATUS current
	  DESCRIPTION
        "
        Min Line Trscv Tx Laser Bias :This
        OID gives the minimum Tx Laser
         Bias value among the network lanes
        of the Line Transceiver, read from
        the DDM (Digital Diagnostic Monitoring)
        (Bias = AV/10) (Unit = mA) <Help>
        This Measure gives the minimum
         Tx Laser Bias value among the
         network lanes of the Line Transceiver
        "
	  ::= { pm20002maMesrOther 214 }



--- *****************************************************
---     LEAF for the lineNetRxInputPwrMin article
--- *****************************************************

pm20002maMesrlineNetRxInputPwrMin OBJECT-TYPE
	  SYNTAX Unsigned32 (0..65535)
	  MAX-ACCESS read-only
	  STATUS current
	  DESCRIPTION
        "
        Min Line Trscv Rx Power :This
         OID gives the minimum Receive
         power value among the network
         lanes of the Line Transceiver,
        read in the DDM (Digital Diagnostic
        Monitoring) (Power = AV/100) (Unit
        = dBm) <Help> This Measure gives
        the minimum Receive power value
        among the network lanes of the
         Line Transceiver
        "
	  ::= { pm20002maMesrOther 215 }



--- *****************************************************
---     LEAF for the lineResidualChromaticDispMin article
--- *****************************************************

pm20002maMesrlineResidualChromaticDispMin OBJECT-TYPE
	  SYNTAX Unsigned32 (0..65535)
	  MAX-ACCESS read-only
	  STATUS current
	  DESCRIPTION
        "
        Min Residual Chromatic Dispersion
        :This OID gives the minimum Residual
        Chromatic Dispersion on the Line
        interface since the last measure
        reset  (Unit = ps/nm)<Help> This
        measure gives the minimum Residual
        Chromatic Dispersion on the Line
        interface since the last measure
        reset.
        "
	  ::= { pm20002maMesrOther 216 }



--- *****************************************************
---     LEAF for the lineDiffGroupDelayMin article
--- *****************************************************

pm20002maMesrlineDiffGroupDelayMin OBJECT-TYPE
	  SYNTAX Unsigned32 (0..65535)
	  MAX-ACCESS read-only
	  STATUS current
	  DESCRIPTION
        "
        Min Differential Group Delay :This
        OID gives the minimum Differential
        Group Delay  on the Line interface
        since the last measure reset  (Unit
        = ps)<Help> This measure gives
         the minimum Differential Group
        Delay on the Line interface since
        the last measure reset.
        "
	  ::= { pm20002maMesrOther 217 }



--- *****************************************************
---     LEAF for the lineQFactorMin article
--- *****************************************************

pm20002maMesrlineQFactorMin OBJECT-TYPE
	  SYNTAX Unsigned32 (0..65535)
	  MAX-ACCESS read-only
	  STATUS current
	  DESCRIPTION
        "
        Min Q Factor :This OID gives the
        minimum Q Factor on the Line interface
        since the last measure reset  (Unit
        = dB)<Help> This measure gives
         the minimum Q Factor on the Line
        interface since the last measure
        reset.
        "
	  ::= { pm20002maMesrOther 218 }



--- *****************************************************
---     LEAF for the lineCarrierFreqOffsetMin article
--- *****************************************************

pm20002maMesrlineCarrierFreqOffsetMin OBJECT-TYPE
	  SYNTAX Unsigned32 (0..65535)
	  MAX-ACCESS read-only
	  STATUS current
	  DESCRIPTION
        "
        Min Carrier Frequency Offset :This
        OID gives the minimum Carrier Frequency
        Offset on the Line interface since
        the last measure reset  (Unit =
        Mhz)<Help> This measure gives the
        minimum Carrier Frequency Offset
        on the Line interface since the
        last measure reset
        "
	  ::= { pm20002maMesrOther 219 }



--- *****************************************************
---     LEAF for the lineOsnrMin article
--- *****************************************************

pm20002maMesrlineOsnrMin OBJECT-TYPE
	  SYNTAX Unsigned32 (0..65535)
	  MAX-ACCESS read-only
	  STATUS current
	  DESCRIPTION
        "
        Min OSNR :This OID gives the minimum
        OSNR on the Line interface since
        the last measure reset  (OSNR =
        AV/10) (Unit = dB)<Help> This measure
        gives the minimum OSNR on the Line
        interface since the last measure
        reset.
        "
	  ::= { pm20002maMesrOther 220 }



--- *****************************************************
---     LEAF for the lineNetTxLaserOutputPwrMax article
--- *****************************************************

pm20002maMesrlineNetTxLaserOutputPwrMax OBJECT-TYPE
	  SYNTAX Unsigned32 (0..65535)
	  MAX-ACCESS read-only
	  STATUS current
	  DESCRIPTION
        "
        Max Line Trscv Tx Power :This
         OID gives the maximum Tx Laser
        transmit power value among the
         network lanes of the Line Transceiver,
        read in the DDM (Digital Diagnostic
        Monitoring) (Power = 10*log(AV)-40)
        (Unit = dBm) <Help> This Measure
        gives the maximum Tx Laser transmit
        power value among the network lanes
        of the Line Transceiver
        "
	  ::= { pm20002maMesrOther 228 }



--- *****************************************************
---     LEAF for the lineNetTxLaserTempMax article
--- *****************************************************

pm20002maMesrlineNetTxLaserTempMax OBJECT-TYPE
	  SYNTAX Unsigned32 (0..65535)
	  MAX-ACCESS read-only
	  STATUS current
	  DESCRIPTION
        "
        Max Line Trscv Tx Laser Temperature
        :This OID gives the maximum Tx
         Laser Temperature value among
         the network lanes of the Line
         Transceiver, read from the DDM
        (Digital Diagnostic Monitoring)
        (Temperature = AV/256) (Unit =
         C) <Help> This Measure gives the
        maximum Tx Laser Temperature value
        among the network lanes of the
         Line Transceiver
        "
	  ::= { pm20002maMesrOther 229 }



--- *****************************************************
---     LEAF for the lineNetTxBiasCurrentMax article
--- *****************************************************

pm20002maMesrlineNetTxBiasCurrentMax OBJECT-TYPE
	  SYNTAX Unsigned32 (0..65535)
	  MAX-ACCESS read-only
	  STATUS current
	  DESCRIPTION
        "
        Max Line Trscv Tx Laser Bias :This
        OID gives the maximum Tx Laser
         Bias value among the network lanes
        of the Line Transceiver, read from
        the DDM (Digital Diagnostic Monitoring)
        (Bias = AV/10) (Unit = mA) <Help>
        This Measure gives the maximum
         Tx Laser Bias value among the
         network lanes of the Line Transceiver
        "
	  ::= { pm20002maMesrOther 230 }



--- *****************************************************
---     LEAF for the lineNetRxInputPwrMax article
--- *****************************************************

pm20002maMesrlineNetRxInputPwrMax OBJECT-TYPE
	  SYNTAX Unsigned32 (0..65535)
	  MAX-ACCESS read-only
	  STATUS current
	  DESCRIPTION
        "
        Max Line Trscv Rx Power :This
         OID gives the maximum Receive
         power value among the network
         lanes of the Line Transceiver,
        read in the DDM (Digital Diagnostic
        Monitoring) (Power = 10*log(AV)-40)
        (Unit = dBm) <Help> This Measure
        gives the maximum Receive power
        value among the network lanes of
        the Line Transceiver
        "
	  ::= { pm20002maMesrOther 231 }



--- *****************************************************
---     LEAF for the lineResidualChromaticDispMax article
--- *****************************************************

pm20002maMesrlineResidualChromaticDispMax OBJECT-TYPE
	  SYNTAX Unsigned32 (0..65535)
	  MAX-ACCESS read-only
	  STATUS current
	  DESCRIPTION
        "
        Max Residual Chromatic Dispersion
        :This OID gives the maximum Residual
        Chromatic Dispersion on the Line
        interface since the last measure
        reset  (Unit = ps/nm)<Help> This
        measure gives the maximum Residual
        Chromatic Dispersion on the Line
        interface since the last measure
        reset.
        "
	  ::= { pm20002maMesrOther 232 }



--- *****************************************************
---     LEAF for the lineDiffGroupDelayMax article
--- *****************************************************

pm20002maMesrlineDiffGroupDelayMax OBJECT-TYPE
	  SYNTAX Unsigned32 (0..65535)
	  MAX-ACCESS read-only
	  STATUS current
	  DESCRIPTION
        "
        Max Differential Group Delay :This
        OID gives the maximum Differential
        Group Delay  on the Line interface
        since the last measure reset
         (Unit = ps)<Help> This measure
        gives the maximum Differential
         Group Delay on the Line interface
        since the last measure reset.
        "
	  ::= { pm20002maMesrOther 233 }



--- *****************************************************
---     LEAF for the lineQFactorMax article
--- *****************************************************

pm20002maMesrlineQFactorMax OBJECT-TYPE
	  SYNTAX Unsigned32 (0..65535)
	  MAX-ACCESS read-only
	  STATUS current
	  DESCRIPTION
        "
        Max Q Factor :This OID gives the
        maximum Q Factor on the Line interface
        since the last measure reset  (Unit
        = dB)<Help> This measure gives
         the maximum Q Factor on the Line
        interface since the last measure
        reset.
        "
	  ::= { pm20002maMesrOther 234 }



--- *****************************************************
---     LEAF for the lineCarrierFreqOffsetMax article
--- *****************************************************

pm20002maMesrlineCarrierFreqOffsetMax OBJECT-TYPE
	  SYNTAX Unsigned32 (0..65535)
	  MAX-ACCESS read-only
	  STATUS current
	  DESCRIPTION
        "
        Max Carrier Frequency Offset :This
        OID gives the maximum Carrier Frequency
        Offset on the Line interface since
        the last measure reset   (Unit
         = Mhz)<Help> This measure gives
        the maximum Carrier Frequency Offset
        on the Line interface since the
        last measure reset.
        "
	  ::= { pm20002maMesrOther 235 }



--- *****************************************************
---     LEAF for the lineOsnrMax article
--- *****************************************************

pm20002maMesrlineOsnrMax OBJECT-TYPE
	  SYNTAX Unsigned32 (0..65535)
	  MAX-ACCESS read-only
	  STATUS current
	  DESCRIPTION
        "
        Max OSNR :This OID gives the maximum
        OSNR on the Line interface since
        the last measure reset  (OSNR =
        AV/10) (Unit = dB) <Help> This
         measure gives the maximum OSNR
        on the Line interface since the
        last measure reset
        "
	  ::= { pm20002maMesrOther 236 }



--- *****************************************************
---     LEAF for the trscv1Temp article
--- *****************************************************

pm20002maMesrtrscv1Temp OBJECT-TYPE
	  SYNTAX Unsigned32 (0..65535)
	  MAX-ACCESS read-only
	  STATUS current
	  DESCRIPTION
        "
        Q1 Trscv Temperature :This OID
        gives the temperature value of
         the Transceiver, read from the
        DDM (Digital Diagnostic Monitoring)
        (Temperature = AV/256) (Unit =
         C) <Help> This Measure gives the
        temperature value of the Transceiver
        "
	  ::= { pm20002maMesrOther 252 }



--- *****************************************************
---     LEAF for the trscv2Temp article
--- *****************************************************

pm20002maMesrtrscv2Temp OBJECT-TYPE
	  SYNTAX Unsigned32 (0..65535)
	  MAX-ACCESS read-only
	  STATUS current
	  DESCRIPTION
        "
        Q2 Trscv Temperature :This OID
        gives the temperature value of
         the Transceiver, read from the
        DDM (Digital Diagnostic Monitoring)
        (Temperature = AV/256) (Unit =
         C) <Help> This Measure gives the
        temperature value of the Transceiver
        "
	  ::= { pm20002maMesrOther 253 }



--- *****************************************************
---     LEAF for the trscv1PowerSupply article
--- *****************************************************

pm20002maMesrtrscv1PowerSupply OBJECT-TYPE
	  SYNTAX Unsigned32 (0..65535)
	  MAX-ACCESS read-only
	  STATUS current
	  DESCRIPTION
        "
        Q1 Trscv Voltage :This OID gives
        the voltage value of the QSFP plugged
        into the port, read from the DDM
        (Digital Diagnostic Monitoring)
        (Voltage = AV/10000) (Unit = V)
         <Help>  This measure gives the
        power supply voltage of the client
        transceiver
        "
	  ::= { pm20002maMesrOther 254 }



--- *****************************************************
---     LEAF for the trscv2PowerSupply article
--- *****************************************************

pm20002maMesrtrscv2PowerSupply OBJECT-TYPE
	  SYNTAX Unsigned32 (0..65535)
	  MAX-ACCESS read-only
	  STATUS current
	  DESCRIPTION
        "
        Q2 Trscv Voltage :This OID gives
        the voltage value of the QSFP plugged
        into the port, read from the DDM
        (Digital Diagnostic Monitoring)
        (Voltage = AV/10000) (Unit = V)
         <Help>  This measure gives the
        power supply voltage of the client
        transceiver
        "
	  ::= { pm20002maMesrOther 255 }








--- *****************************************************
--- $$$$$$$$$$$$$$$$$$$$$$$$$$$$$$$$$$$$$$$$$$$$$$$$$$$$$
---     PERFORMANCE
--- $$$$$$$$$$$$$$$$$$$$$$$$$$$$$$$$$$$$$$$$$$$$$$$$$$$$$
--- *****************************************************



--- *****************************************************
---     Leaf of the telecomInputClientCurrent15Stat
--- *****************************************************
--- *********************************************************
---     TABLE for the pm20002maPerfTelecomInputClientCurrent15Stat articles
--- *********************************************************

pm20002maPerfTelecomInputClientCurrent15StatTable OBJECT-TYPE
	SYNTAX  SEQUENCE OF Pm20002maPerfTelecomInputClientCurrent15StatEntry
	MAX-ACCESS not-accessible
	STATUS current
	DESCRIPTION
        "
        List of pm20002maPerfTelecomInputClientCurrent15Stat
        Article
        "
	::= { pm20002maMonPerfClient 16 }


pm20002maPerfTelecomInputClientCurrent15StatEntry OBJECT-TYPE
	SYNTAX Pm20002maPerfTelecomInputClientCurrent15StatEntry
	MAX-ACCESS not-accessible
	STATUS current
	DESCRIPTION
        "
        Row definition for the pm20002maPerfTelecomInputClientCurrent15Stat
        table
        "
	INDEX   { pm20002maPerfTelecomInputClientCurrent15StatIndex }
	::= { pm20002maPerfTelecomInputClientCurrent15StatTable 1 }


Pm20002maPerfTelecomInputClientCurrent15StatEntry ::=
	SEQUENCE {
	pm20002maPerfTelecomInputClientCurrent15StatIndex
		INTEGER,
	pm20002maPerfTelecomInputClientCurrent15StatInvCvPortn
		EkiOnOff,
	pm20002maPerfTelecomInputClientCurrent15StatCvValuePortn
		Unsigned32,
	pm20002maPerfTelecomInputClientCurrent15StatInvEsPortn
		EkiOnOff,
	pm20002maPerfTelecomInputClientCurrent15StatEsValuePortn
		Unsigned32,
	pm20002maPerfTelecomInputClientCurrent15StatInvSesPortn
		EkiOnOff,
	pm20002maPerfTelecomInputClientCurrent15StatSesValuePortn
		Unsigned32,
	pm20002maPerfTelecomInputClientCurrent15StatInvSefsPortn
		EkiOnOff,
	pm20002maPerfTelecomInputClientCurrent15StatSefsValuePortn
		Unsigned32,
	pm20002maPerfTelecomInputClientCurrent15StatInvUasPortn
		EkiOnOff,
	pm20002maPerfTelecomInputClientCurrent15StatUasValuePortn
		Unsigned32
	}


pm20002maPerfTelecomInputClientCurrent15StatIndex OBJECT-TYPE
	SYNTAX  INTEGER(0..128)
	MAX-ACCESS  read-only
	STATUS current
	DESCRIPTION
        "
        Index definition for the pm20002maPerfTelecomInputClientCurrent15Stat
        table
        "
	::= { pm20002maPerfTelecomInputClientCurrent15StatEntry 1 }


pm20002maPerfTelecomInputClientCurrent15StatInvCvPortn OBJECT-TYPE
	SYNTAX  EkiOnOff
	MAX-ACCESS read-only
	STATUS current
	DESCRIPTION
        "
        Current 15-min EBC counter inv.
        :This OID indicates that the current
        15-min Coding Violation counter
        is invalid
        "
	::= { pm20002maPerfTelecomInputClientCurrent15StatEntry 2 }


pm20002maPerfTelecomInputClientCurrent15StatCvValuePortn OBJECT-TYPE
	SYNTAX  Unsigned32
	MAX-ACCESS read-only
	STATUS current
	DESCRIPTION
        "
        Current 15-min EBC counter :This
        OID gives the current 15-min Coding
        Violation counter value
        "
	::= { pm20002maPerfTelecomInputClientCurrent15StatEntry 3 }


pm20002maPerfTelecomInputClientCurrent15StatInvEsPortn OBJECT-TYPE
	SYNTAX  EkiOnOff
	MAX-ACCESS read-only
	STATUS current
	DESCRIPTION
        "
        Current 15-min ES counter inv.
        :This OID indicates that the current
        15-min Errored Second counter is
        invalid
        "
	::= { pm20002maPerfTelecomInputClientCurrent15StatEntry 4 }


pm20002maPerfTelecomInputClientCurrent15StatEsValuePortn OBJECT-TYPE
	SYNTAX  Unsigned32
	MAX-ACCESS read-only
	STATUS current
	DESCRIPTION
        "
        Current 15-min ES counter :This
        OID gives the current 15-min Errored
        Second counter value
        "
	::= { pm20002maPerfTelecomInputClientCurrent15StatEntry 5 }


pm20002maPerfTelecomInputClientCurrent15StatInvSesPortn OBJECT-TYPE
	SYNTAX  EkiOnOff
	MAX-ACCESS read-only
	STATUS current
	DESCRIPTION
        "
        Current 15-min SES counter inv.
        :This OID indicates that the current
        15-min severely Errored Second
         counter is invalid
        "
	::= { pm20002maPerfTelecomInputClientCurrent15StatEntry 6 }


pm20002maPerfTelecomInputClientCurrent15StatSesValuePortn OBJECT-TYPE
	SYNTAX  Unsigned32
	MAX-ACCESS read-only
	STATUS current
	DESCRIPTION
        "
        Current 15-min SES counter :This
        OID gives the current 15-min severely
        Errored Second counter value
        "
	::= { pm20002maPerfTelecomInputClientCurrent15StatEntry 7 }


pm20002maPerfTelecomInputClientCurrent15StatInvSefsPortn OBJECT-TYPE
	SYNTAX  EkiOnOff
	MAX-ACCESS read-only
	STATUS current
	DESCRIPTION
        "
        Current 15-min SEFS counter inv.
        :This OID indicates that the current
        15-min severely Errored Framing
        Second counter is invalid
        "
	::= { pm20002maPerfTelecomInputClientCurrent15StatEntry 8 }


pm20002maPerfTelecomInputClientCurrent15StatSefsValuePortn OBJECT-TYPE
	SYNTAX  Unsigned32
	MAX-ACCESS read-only
	STATUS current
	DESCRIPTION
        "
        Current 15-min SEFS counter :This
        OID gives the current 15-min severely
        Errored Framing Second counter
         value
        "
	::= { pm20002maPerfTelecomInputClientCurrent15StatEntry 9 }


pm20002maPerfTelecomInputClientCurrent15StatInvUasPortn OBJECT-TYPE
	SYNTAX  EkiOnOff
	MAX-ACCESS read-only
	STATUS current
	DESCRIPTION
        "
        Current 15-min UAS counter inv.
        :This OID indicates that the current
        15-min UnAvailable Second counter
        is invalid
        "
	::= { pm20002maPerfTelecomInputClientCurrent15StatEntry 10 }


pm20002maPerfTelecomInputClientCurrent15StatUasValuePortn OBJECT-TYPE
	SYNTAX  Unsigned32
	MAX-ACCESS read-only
	STATUS current
	DESCRIPTION
        "
        Current 15-min UAS counter :This
        OID gives the current 15-min UnAvailable
        Second counter value
        "
	::= { pm20002maPerfTelecomInputClientCurrent15StatEntry 11 }


--- *****************************************************
---     Leaf of the telecomInputClientPast15Stat
--- *****************************************************
--- *********************************************************
---     TABLE for the pm20002maPerfTelecomInputClientPast15StatHistory articles
--- *********************************************************

pm20002maPerfTelecomInputClientPast15StatHistoryPort1Table OBJECT-TYPE
	SYNTAX  SEQUENCE OF Pm20002maPerfTelecomInputClientPast15StatHistoryPort1Entry
	MAX-ACCESS not-accessible
	STATUS current
	DESCRIPTION
        "
        List of pm20002maPerfTelecomInputClientPast15StatHistory
        Article
        "
	::= { pm20002maMonPerfClient 48 }


pm20002maPerfTelecomInputClientPast15StatHistoryPort1Entry OBJECT-TYPE
	SYNTAX Pm20002maPerfTelecomInputClientPast15StatHistoryPort1Entry
	MAX-ACCESS not-accessible
	STATUS current
	DESCRIPTION
        "
        Row definition for the pm20002maPerfTelecomInputClientPast15StatHistory
        table
        "
	INDEX   { pm20002maPerfTelecomInputClientPast15StatHistoryPort1Index }
	::= { pm20002maPerfTelecomInputClientPast15StatHistoryPort1Table 1 }


Pm20002maPerfTelecomInputClientPast15StatHistoryPort1Entry ::=
	SEQUENCE {
	pm20002maPerfTelecomInputClientPast15StatHistoryPort1Index
		INTEGER,
	pm20002maPerfTelecomInputClientPast15StatHistoryInvCvPort1
		EkiOnOff,
	pm20002maPerfTelecomInputClientPast15StatHistoryCvValuePort1
		Unsigned32,
	pm20002maPerfTelecomInputClientPast15StatHistoryInvEsPort1
		EkiOnOff,
	pm20002maPerfTelecomInputClientPast15StatHistoryEsValuePort1
		Unsigned32,
	pm20002maPerfTelecomInputClientPast15StatHistoryInvSesPort1
		EkiOnOff,
	pm20002maPerfTelecomInputClientPast15StatHistorySesValuePort1
		Unsigned32,
	pm20002maPerfTelecomInputClientPast15StatHistoryInvSefsPort1
		EkiOnOff,
	pm20002maPerfTelecomInputClientPast15StatHistorySefsValuePort1
		Unsigned32,
	pm20002maPerfTelecomInputClientPast15StatHistoryInvUasPort1
		EkiOnOff,
	pm20002maPerfTelecomInputClientPast15StatHistoryUasValuePort1
		Unsigned32
	}


pm20002maPerfTelecomInputClientPast15StatHistoryPort1Index OBJECT-TYPE
	SYNTAX  INTEGER(0..128)
	MAX-ACCESS  read-only
	STATUS current
	DESCRIPTION
        "
        Index definition for the pm20002maPerfTelecomInputClientPast15StatHistory
        table
        "
	::= { pm20002maPerfTelecomInputClientPast15StatHistoryPort1Entry 1 }


pm20002maPerfTelecomInputClientPast15StatHistoryInvCvPort1 OBJECT-TYPE
	SYNTAX  EkiOnOff
	MAX-ACCESS read-only
	STATUS current
	DESCRIPTION
        "
        Previous 15-min EBC counter inv.
        :This OID indicates that the previous
        15-min Coding Violation counter
        is invalid
        "
	::= { pm20002maPerfTelecomInputClientPast15StatHistoryPort1Entry 2 }


pm20002maPerfTelecomInputClientPast15StatHistoryCvValuePort1 OBJECT-TYPE
	SYNTAX  Unsigned32
	MAX-ACCESS read-only
	STATUS current
	DESCRIPTION
        "
        Previous 15-min EBC counter :This
        OID gives the previous 15-min Coding
        Violation counter value
        "
	::= { pm20002maPerfTelecomInputClientPast15StatHistoryPort1Entry 3 }


pm20002maPerfTelecomInputClientPast15StatHistoryInvEsPort1 OBJECT-TYPE
	SYNTAX  EkiOnOff
	MAX-ACCESS read-only
	STATUS current
	DESCRIPTION
        "
        Previous 15-min ES counter inv.
        :This OID indicates that the previous
        15-min Errored Second counter is
        invalid
        "
	::= { pm20002maPerfTelecomInputClientPast15StatHistoryPort1Entry 4 }


pm20002maPerfTelecomInputClientPast15StatHistoryEsValuePort1 OBJECT-TYPE
	SYNTAX  Unsigned32
	MAX-ACCESS read-only
	STATUS current
	DESCRIPTION
        "
        Previous 15-min ES counter :This
        OID gives the previous 15-min Errored
        Second counter value
        "
	::= { pm20002maPerfTelecomInputClientPast15StatHistoryPort1Entry 5 }


pm20002maPerfTelecomInputClientPast15StatHistoryInvSesPort1 OBJECT-TYPE
	SYNTAX  EkiOnOff
	MAX-ACCESS read-only
	STATUS current
	DESCRIPTION
        "
        Previous 15-min SES counter inv.
        :This OID indicates that the previous
        15-min severely Errored Second
         counter is invalid
        "
	::= { pm20002maPerfTelecomInputClientPast15StatHistoryPort1Entry 6 }


pm20002maPerfTelecomInputClientPast15StatHistorySesValuePort1 OBJECT-TYPE
	SYNTAX  Unsigned32
	MAX-ACCESS read-only
	STATUS current
	DESCRIPTION
        "
        Previous 15-min SES counter :This
        OID gives the previous 15-min severely
        Errored Second counter value
        "
	::= { pm20002maPerfTelecomInputClientPast15StatHistoryPort1Entry 7 }


pm20002maPerfTelecomInputClientPast15StatHistoryInvSefsPort1 OBJECT-TYPE
	SYNTAX  EkiOnOff
	MAX-ACCESS read-only
	STATUS current
	DESCRIPTION
        "
        Previous 15-min SEFS counter inv.
        :This OID indicates that the previous
        15-min severely Errored Framing
        Second counter is invalid
        "
	::= { pm20002maPerfTelecomInputClientPast15StatHistoryPort1Entry 8 }


pm20002maPerfTelecomInputClientPast15StatHistorySefsValuePort1 OBJECT-TYPE
	SYNTAX  Unsigned32
	MAX-ACCESS read-only
	STATUS current
	DESCRIPTION
        "
        Previous 15-min SEFS counter :This
        OID gives the previous 15-min severely
        Errored Framing Second counter
         value
        "
	::= { pm20002maPerfTelecomInputClientPast15StatHistoryPort1Entry 9 }


pm20002maPerfTelecomInputClientPast15StatHistoryInvUasPort1 OBJECT-TYPE
	SYNTAX  EkiOnOff
	MAX-ACCESS read-only
	STATUS current
	DESCRIPTION
        "
        Previous 15-min UAS counter inv.
        :This OID indicates that the previous
        15-min UnAvailable Second counter
        is invalid
        "
	::= { pm20002maPerfTelecomInputClientPast15StatHistoryPort1Entry 10 }


pm20002maPerfTelecomInputClientPast15StatHistoryUasValuePort1 OBJECT-TYPE
	SYNTAX  Unsigned32
	MAX-ACCESS read-only
	STATUS current
	DESCRIPTION
        "
        Previous 15-min UAS counter :This
        OID gives the previous 15-min UnAvailable
        Second counter value
        "
	::= { pm20002maPerfTelecomInputClientPast15StatHistoryPort1Entry 11 }


--- *****************************************************
---     Leaf of the telecomInputClientCurrent24Stat
--- *****************************************************
--- *********************************************************
---     TABLE for the pm20002maPerfTelecomInputClientCurrent24Stat articles
--- *********************************************************

pm20002maPerfTelecomInputClientCurrent24StatTable OBJECT-TYPE
	SYNTAX  SEQUENCE OF Pm20002maPerfTelecomInputClientCurrent24StatEntry
	MAX-ACCESS not-accessible
	STATUS current
	DESCRIPTION
        "
        List of pm20002maPerfTelecomInputClientCurrent24Stat
        Article
        "
	::= { pm20002maMonPerfClient 80 }


pm20002maPerfTelecomInputClientCurrent24StatEntry OBJECT-TYPE
	SYNTAX Pm20002maPerfTelecomInputClientCurrent24StatEntry
	MAX-ACCESS not-accessible
	STATUS current
	DESCRIPTION
        "
        Row definition for the pm20002maPerfTelecomInputClientCurrent24Stat
        table
        "
	INDEX   { pm20002maPerfTelecomInputClientCurrent24StatIndex }
	::= { pm20002maPerfTelecomInputClientCurrent24StatTable 1 }


Pm20002maPerfTelecomInputClientCurrent24StatEntry ::=
	SEQUENCE {
	pm20002maPerfTelecomInputClientCurrent24StatIndex
		INTEGER,
	pm20002maPerfTelecomInputClientCurrent24StatInvCvPortn
		EkiOnOff,
	pm20002maPerfTelecomInputClientCurrent24StatCvValuePortn
		Unsigned32,
	pm20002maPerfTelecomInputClientCurrent24StatInvEsPortn
		EkiOnOff,
	pm20002maPerfTelecomInputClientCurrent24StatEsValuePortn
		Unsigned32,
	pm20002maPerfTelecomInputClientCurrent24StatInvSesPortn
		EkiOnOff,
	pm20002maPerfTelecomInputClientCurrent24StatSesValuePortn
		Unsigned32,
	pm20002maPerfTelecomInputClientCurrent24StatInvSefsPortn
		EkiOnOff,
	pm20002maPerfTelecomInputClientCurrent24StatSefsValuePortn
		Unsigned32,
	pm20002maPerfTelecomInputClientCurrent24StatInvUasPortn
		EkiOnOff,
	pm20002maPerfTelecomInputClientCurrent24StatUasValuePortn
		Unsigned32
	}


pm20002maPerfTelecomInputClientCurrent24StatIndex OBJECT-TYPE
	SYNTAX  INTEGER(0..128)
	MAX-ACCESS  read-only
	STATUS current
	DESCRIPTION
        "
        Index definition for the pm20002maPerfTelecomInputClientCurrent24Stat
        table
        "
	::= { pm20002maPerfTelecomInputClientCurrent24StatEntry 1 }


pm20002maPerfTelecomInputClientCurrent24StatInvCvPortn OBJECT-TYPE
	SYNTAX  EkiOnOff
	MAX-ACCESS read-only
	STATUS current
	DESCRIPTION
        "
        Current 24-hours EBC counter inv.
        :This OID indicates that the current
        24-hours Coding Violation counter
        is invalid
        "
	::= { pm20002maPerfTelecomInputClientCurrent24StatEntry 2 }


pm20002maPerfTelecomInputClientCurrent24StatCvValuePortn OBJECT-TYPE
	SYNTAX  Unsigned32
	MAX-ACCESS read-only
	STATUS current
	DESCRIPTION
        "
        Current 24-hours EBC counter :This
        OID gives the current 24-hours
         Coding Violation counter value
        "
	::= { pm20002maPerfTelecomInputClientCurrent24StatEntry 3 }


pm20002maPerfTelecomInputClientCurrent24StatInvEsPortn OBJECT-TYPE
	SYNTAX  EkiOnOff
	MAX-ACCESS read-only
	STATUS current
	DESCRIPTION
        "
        Current 24-hours ES counter inv.
        :This OID indicates that the current
        24-hours Errored Second counter
        is invalid
        "
	::= { pm20002maPerfTelecomInputClientCurrent24StatEntry 4 }


pm20002maPerfTelecomInputClientCurrent24StatEsValuePortn OBJECT-TYPE
	SYNTAX  Unsigned32
	MAX-ACCESS read-only
	STATUS current
	DESCRIPTION
        "
        Current 24-hours ES counter :This
        OID gives the current 24-hours
         Errored Second counter value
        "
	::= { pm20002maPerfTelecomInputClientCurrent24StatEntry 5 }


pm20002maPerfTelecomInputClientCurrent24StatInvSesPortn OBJECT-TYPE
	SYNTAX  EkiOnOff
	MAX-ACCESS read-only
	STATUS current
	DESCRIPTION
        "
        Current 24-hours SES counter inv.
        :This OID indicates that the current
        24-hours severely Errored Second
        counter is invalid
        "
	::= { pm20002maPerfTelecomInputClientCurrent24StatEntry 6 }


pm20002maPerfTelecomInputClientCurrent24StatSesValuePortn OBJECT-TYPE
	SYNTAX  Unsigned32
	MAX-ACCESS read-only
	STATUS current
	DESCRIPTION
        "
        Current 24-hours SES counter :This
        OID gives the current 24-hours
         severely Errored Second counter
        value
        "
	::= { pm20002maPerfTelecomInputClientCurrent24StatEntry 7 }


pm20002maPerfTelecomInputClientCurrent24StatInvSefsPortn OBJECT-TYPE
	SYNTAX  EkiOnOff
	MAX-ACCESS read-only
	STATUS current
	DESCRIPTION
        "
        Current 24-hours SEFS counter
         inv. :This OID indicates that
         the current 24-hours severely
         Errored Framing Second counter
        is invalid
        "
	::= { pm20002maPerfTelecomInputClientCurrent24StatEntry 8 }


pm20002maPerfTelecomInputClientCurrent24StatSefsValuePortn OBJECT-TYPE
	SYNTAX  Unsigned32
	MAX-ACCESS read-only
	STATUS current
	DESCRIPTION
        "
        Current 24-hours SEFS counter
         :This OID gives the current 24-hours
        severely Errored Framing Second
        counter value
        "
	::= { pm20002maPerfTelecomInputClientCurrent24StatEntry 9 }


pm20002maPerfTelecomInputClientCurrent24StatInvUasPortn OBJECT-TYPE
	SYNTAX  EkiOnOff
	MAX-ACCESS read-only
	STATUS current
	DESCRIPTION
        "
        Current 24-hours UAS counter inv.
        :This OID indicates that the current
        24-hours UnAvailable Second counter
        is invalid
        "
	::= { pm20002maPerfTelecomInputClientCurrent24StatEntry 10 }


pm20002maPerfTelecomInputClientCurrent24StatUasValuePortn OBJECT-TYPE
	SYNTAX  Unsigned32
	MAX-ACCESS read-only
	STATUS current
	DESCRIPTION
        "
        Current 24-hours UAS counter :This
        OID gives the current 24-hours
         UnAvailable Second counter value
        "
	::= { pm20002maPerfTelecomInputClientCurrent24StatEntry 11 }


--- *****************************************************
---     Leaf of the telecomInputClientPast24Stat
--- *****************************************************
--- *********************************************************
---     TABLE for the pm20002maPerfTelecomInputClientPast24StatHistory articles
--- *********************************************************

pm20002maPerfTelecomInputClientPast24StatHistoryPort1Table OBJECT-TYPE
	SYNTAX  SEQUENCE OF Pm20002maPerfTelecomInputClientPast24StatHistoryPort1Entry
	MAX-ACCESS not-accessible
	STATUS current
	DESCRIPTION
        "
        List of pm20002maPerfTelecomInputClientPast24StatHistory
        Article
        "
	::= { pm20002maMonPerfClient 112 }


pm20002maPerfTelecomInputClientPast24StatHistoryPort1Entry OBJECT-TYPE
	SYNTAX Pm20002maPerfTelecomInputClientPast24StatHistoryPort1Entry
	MAX-ACCESS not-accessible
	STATUS current
	DESCRIPTION
        "
        Row definition for the pm20002maPerfTelecomInputClientPast24StatHistory
        table
        "
	INDEX   { pm20002maPerfTelecomInputClientPast24StatHistoryPort1Index }
	::= { pm20002maPerfTelecomInputClientPast24StatHistoryPort1Table 1 }


Pm20002maPerfTelecomInputClientPast24StatHistoryPort1Entry ::=
	SEQUENCE {
	pm20002maPerfTelecomInputClientPast24StatHistoryPort1Index
		INTEGER,
	pm20002maPerfTelecomInputClientPast24StatHistoryInvCvPort1
		EkiOnOff,
	pm20002maPerfTelecomInputClientPast24StatHistoryCvValuePort1
		Unsigned32,
	pm20002maPerfTelecomInputClientPast24StatHistoryInvEsPort1
		EkiOnOff,
	pm20002maPerfTelecomInputClientPast24StatHistoryEsValuePort1
		Unsigned32,
	pm20002maPerfTelecomInputClientPast24StatHistoryInvSesPort1
		EkiOnOff,
	pm20002maPerfTelecomInputClientPast24StatHistorySesValuePort1
		Unsigned32,
	pm20002maPerfTelecomInputClientPast24StatHistoryInvSefsPort1
		EkiOnOff,
	pm20002maPerfTelecomInputClientPast24StatHistorySefsValuePort1
		Unsigned32,
	pm20002maPerfTelecomInputClientPast24StatHistoryInvUasPort1
		EkiOnOff,
	pm20002maPerfTelecomInputClientPast24StatHistoryUasValuePort1
		Unsigned32
	}


pm20002maPerfTelecomInputClientPast24StatHistoryPort1Index OBJECT-TYPE
	SYNTAX  INTEGER(0..128)
	MAX-ACCESS  read-only
	STATUS current
	DESCRIPTION
        "
        Index definition for the pm20002maPerfTelecomInputClientPast24StatHistory
        table
        "
	::= { pm20002maPerfTelecomInputClientPast24StatHistoryPort1Entry 1 }


pm20002maPerfTelecomInputClientPast24StatHistoryInvCvPort1 OBJECT-TYPE
	SYNTAX  EkiOnOff
	MAX-ACCESS read-only
	STATUS current
	DESCRIPTION
        "
        Previous 24-hours EBC counter
         inv. :This OID indicates that
         the previous 24-hours Coding Violation
        counter is invalid
        "
	::= { pm20002maPerfTelecomInputClientPast24StatHistoryPort1Entry 2 }


pm20002maPerfTelecomInputClientPast24StatHistoryCvValuePort1 OBJECT-TYPE
	SYNTAX  Unsigned32
	MAX-ACCESS read-only
	STATUS current
	DESCRIPTION
        "
        Previous 24-hours EBC counter
         :This OID gives the previous 24-hours
        Coding Violation counter value
        "
	::= { pm20002maPerfTelecomInputClientPast24StatHistoryPort1Entry 3 }


pm20002maPerfTelecomInputClientPast24StatHistoryInvEsPort1 OBJECT-TYPE
	SYNTAX  EkiOnOff
	MAX-ACCESS read-only
	STATUS current
	DESCRIPTION
        "
        Previous 24-hours ES counter inv.
        :This OID indicates that the previous
        24-hours Errored Second counter
        is invalid
        "
	::= { pm20002maPerfTelecomInputClientPast24StatHistoryPort1Entry 4 }


pm20002maPerfTelecomInputClientPast24StatHistoryEsValuePort1 OBJECT-TYPE
	SYNTAX  Unsigned32
	MAX-ACCESS read-only
	STATUS current
	DESCRIPTION
        "
        Previous 24-hours ES counter :This
        OID gives the previous 24-hours
        Errored Second counter value
        "
	::= { pm20002maPerfTelecomInputClientPast24StatHistoryPort1Entry 5 }


pm20002maPerfTelecomInputClientPast24StatHistoryInvSesPort1 OBJECT-TYPE
	SYNTAX  EkiOnOff
	MAX-ACCESS read-only
	STATUS current
	DESCRIPTION
        "
        Previous 24-hours SES counter
         inv. :This OID indicates that
         the previous 24-hours severely
        Errored Second counter is invalid
        "
	::= { pm20002maPerfTelecomInputClientPast24StatHistoryPort1Entry 6 }


pm20002maPerfTelecomInputClientPast24StatHistorySesValuePort1 OBJECT-TYPE
	SYNTAX  Unsigned32
	MAX-ACCESS read-only
	STATUS current
	DESCRIPTION
        "
        Previous 24-hours SES counter
         :This OID gives the previous 24-hours
        severely Errored Second counter
        value
        "
	::= { pm20002maPerfTelecomInputClientPast24StatHistoryPort1Entry 7 }


pm20002maPerfTelecomInputClientPast24StatHistoryInvSefsPort1 OBJECT-TYPE
	SYNTAX  EkiOnOff
	MAX-ACCESS read-only
	STATUS current
	DESCRIPTION
        "
        Previous 24-hours SEFS counter
        inv. :This OID indicates that the
        previous 24-hours severely Errored
        Framing Second counter is invalid
        "
	::= { pm20002maPerfTelecomInputClientPast24StatHistoryPort1Entry 8 }


pm20002maPerfTelecomInputClientPast24StatHistorySefsValuePort1 OBJECT-TYPE
	SYNTAX  Unsigned32
	MAX-ACCESS read-only
	STATUS current
	DESCRIPTION
        "
        Previous 24-hours SEFS counter
        :This OID gives the previous 24-hours
        severely Errored Framing Second
        counter value
        "
	::= { pm20002maPerfTelecomInputClientPast24StatHistoryPort1Entry 9 }


pm20002maPerfTelecomInputClientPast24StatHistoryInvUasPort1 OBJECT-TYPE
	SYNTAX  EkiOnOff
	MAX-ACCESS read-only
	STATUS current
	DESCRIPTION
        "
        Previous 24-hours UAS counter
         inv. :This OID indicates that
         the previous 24-hours UnAvailable
        Second counter is invalid
        "
	::= { pm20002maPerfTelecomInputClientPast24StatHistoryPort1Entry 10 }


pm20002maPerfTelecomInputClientPast24StatHistoryUasValuePort1 OBJECT-TYPE
	SYNTAX  Unsigned32
	MAX-ACCESS read-only
	STATUS current
	DESCRIPTION
        "
        Previous 24-hours UAS counter
         :This OID gives the previous 24-hours
        UnAvailable Second counter value
        "
	::= { pm20002maPerfTelecomInputClientPast24StatHistoryPort1Entry 11 }


--- *****************************************************
---     Leaf of the telecomOutputClientCurrent15Stat
--- *****************************************************
--- *********************************************************
---     TABLE for the pm20002maPerfTelecomOutputClientCurrent15Stat articles
--- *********************************************************

pm20002maPerfTelecomOutputClientCurrent15StatTable OBJECT-TYPE
	SYNTAX  SEQUENCE OF Pm20002maPerfTelecomOutputClientCurrent15StatEntry
	MAX-ACCESS not-accessible
	STATUS current
	DESCRIPTION
        "
        List of pm20002maPerfTelecomOutputClientCurrent15Stat
        Article
        "
	::= { pm20002maMonPerfClient 144 }


pm20002maPerfTelecomOutputClientCurrent15StatEntry OBJECT-TYPE
	SYNTAX Pm20002maPerfTelecomOutputClientCurrent15StatEntry
	MAX-ACCESS not-accessible
	STATUS current
	DESCRIPTION
        "
        Row definition for the pm20002maPerfTelecomOutputClientCurrent15Stat
        table
        "
	INDEX   { pm20002maPerfTelecomOutputClientCurrent15StatIndex }
	::= { pm20002maPerfTelecomOutputClientCurrent15StatTable 1 }


Pm20002maPerfTelecomOutputClientCurrent15StatEntry ::=
	SEQUENCE {
	pm20002maPerfTelecomOutputClientCurrent15StatIndex
		INTEGER,
	pm20002maPerfTelecomOutputClientCurrent15StatInvCvPortn
		EkiOnOff,
	pm20002maPerfTelecomOutputClientCurrent15StatCvValuePortn
		Unsigned32,
	pm20002maPerfTelecomOutputClientCurrent15StatInvEsPortn
		EkiOnOff,
	pm20002maPerfTelecomOutputClientCurrent15StatEsValuePortn
		Unsigned32,
	pm20002maPerfTelecomOutputClientCurrent15StatInvSesPortn
		EkiOnOff,
	pm20002maPerfTelecomOutputClientCurrent15StatSesValuePortn
		Unsigned32,
	pm20002maPerfTelecomOutputClientCurrent15StatInvSefsPortn
		EkiOnOff,
	pm20002maPerfTelecomOutputClientCurrent15StatSefsValuePortn
		Unsigned32,
	pm20002maPerfTelecomOutputClientCurrent15StatInvUasPortn
		EkiOnOff,
	pm20002maPerfTelecomOutputClientCurrent15StatUasValuePortn
		Unsigned32
	}


pm20002maPerfTelecomOutputClientCurrent15StatIndex OBJECT-TYPE
	SYNTAX  INTEGER(0..128)
	MAX-ACCESS  read-only
	STATUS current
	DESCRIPTION
        "
        Index definition for the pm20002maPerfTelecomOutputClientCurrent15Stat
        table
        "
	::= { pm20002maPerfTelecomOutputClientCurrent15StatEntry 1 }


pm20002maPerfTelecomOutputClientCurrent15StatInvCvPortn OBJECT-TYPE
	SYNTAX  EkiOnOff
	MAX-ACCESS read-only
	STATUS current
	DESCRIPTION
        "
        Current 15-min EBC counter inv.
        :This OID indicates that the current
        15-min Coding Violation counter
        is invalid
        "
	::= { pm20002maPerfTelecomOutputClientCurrent15StatEntry 2 }


pm20002maPerfTelecomOutputClientCurrent15StatCvValuePortn OBJECT-TYPE
	SYNTAX  Unsigned32
	MAX-ACCESS read-only
	STATUS current
	DESCRIPTION
        "
        Current 15-min EBC counter :This
        OID gives the current 15-min Coding
        Violation counter value
        "
	::= { pm20002maPerfTelecomOutputClientCurrent15StatEntry 3 }


pm20002maPerfTelecomOutputClientCurrent15StatInvEsPortn OBJECT-TYPE
	SYNTAX  EkiOnOff
	MAX-ACCESS read-only
	STATUS current
	DESCRIPTION
        "
        Current 15-min ES counter inv.
        :This OID indicates that the current
        15-min Errored Second counter is
        invalid
        "
	::= { pm20002maPerfTelecomOutputClientCurrent15StatEntry 4 }


pm20002maPerfTelecomOutputClientCurrent15StatEsValuePortn OBJECT-TYPE
	SYNTAX  Unsigned32
	MAX-ACCESS read-only
	STATUS current
	DESCRIPTION
        "
        Current 15-min ES counter :This
        OID gives the current 15-min Errored
        Second counter value
        "
	::= { pm20002maPerfTelecomOutputClientCurrent15StatEntry 5 }


pm20002maPerfTelecomOutputClientCurrent15StatInvSesPortn OBJECT-TYPE
	SYNTAX  EkiOnOff
	MAX-ACCESS read-only
	STATUS current
	DESCRIPTION
        "
        Current 15-min SES counter inv.
        :This OID indicates that the current
        15-min severely Errored Second
         counter is invalid
        "
	::= { pm20002maPerfTelecomOutputClientCurrent15StatEntry 6 }


pm20002maPerfTelecomOutputClientCurrent15StatSesValuePortn OBJECT-TYPE
	SYNTAX  Unsigned32
	MAX-ACCESS read-only
	STATUS current
	DESCRIPTION
        "
        Current 15-min SES counter :This
        OID gives the current 15-min severely
        Errored Second counter value
        "
	::= { pm20002maPerfTelecomOutputClientCurrent15StatEntry 7 }


pm20002maPerfTelecomOutputClientCurrent15StatInvSefsPortn OBJECT-TYPE
	SYNTAX  EkiOnOff
	MAX-ACCESS read-only
	STATUS current
	DESCRIPTION
        "
        Current 15-min SEFS counter inv.
        :This OID indicates that the current
        15-min severely Errored Framing
        Second counter is invalid
        "
	::= { pm20002maPerfTelecomOutputClientCurrent15StatEntry 8 }


pm20002maPerfTelecomOutputClientCurrent15StatSefsValuePortn OBJECT-TYPE
	SYNTAX  Unsigned32
	MAX-ACCESS read-only
	STATUS current
	DESCRIPTION
        "
        Current 15-min SEFS counter :This
        OID gives the current 15-min severely
        Errored Framing Second counter
         value
        "
	::= { pm20002maPerfTelecomOutputClientCurrent15StatEntry 9 }


pm20002maPerfTelecomOutputClientCurrent15StatInvUasPortn OBJECT-TYPE
	SYNTAX  EkiOnOff
	MAX-ACCESS read-only
	STATUS current
	DESCRIPTION
        "
        Current 15-min UAS counter inv.
        :This OID indicates that the current
        15-min UnAvailable Second counter
        is invalid
        "
	::= { pm20002maPerfTelecomOutputClientCurrent15StatEntry 10 }


pm20002maPerfTelecomOutputClientCurrent15StatUasValuePortn OBJECT-TYPE
	SYNTAX  Unsigned32
	MAX-ACCESS read-only
	STATUS current
	DESCRIPTION
        "
        Current 15-min UAS counter :This
        OID gives the current 15-min UnAvailable
        Second counter value
        "
	::= { pm20002maPerfTelecomOutputClientCurrent15StatEntry 11 }


--- *****************************************************
---     Leaf of the telecomOutputClientPast15Stat
--- *****************************************************
--- *********************************************************
---     TABLE for the pm20002maPerfTelecomOutputClientPast15StatHistory articles
--- *********************************************************

pm20002maPerfTelecomOutputClientPast15StatHistoryPort1Table OBJECT-TYPE
	SYNTAX  SEQUENCE OF Pm20002maPerfTelecomOutputClientPast15StatHistoryPort1Entry
	MAX-ACCESS not-accessible
	STATUS current
	DESCRIPTION
        "
        List of pm20002maPerfTelecomOutputClientPast15StatHistory
        Article
        "
	::= { pm20002maMonPerfClient 176 }


pm20002maPerfTelecomOutputClientPast15StatHistoryPort1Entry OBJECT-TYPE
	SYNTAX Pm20002maPerfTelecomOutputClientPast15StatHistoryPort1Entry
	MAX-ACCESS not-accessible
	STATUS current
	DESCRIPTION
        "
        Row definition for the pm20002maPerfTelecomOutputClientPast15StatHistory
        table
        "
	INDEX   { pm20002maPerfTelecomOutputClientPast15StatHistoryPort1Index }
	::= { pm20002maPerfTelecomOutputClientPast15StatHistoryPort1Table 1 }


Pm20002maPerfTelecomOutputClientPast15StatHistoryPort1Entry ::=
	SEQUENCE {
	pm20002maPerfTelecomOutputClientPast15StatHistoryPort1Index
		INTEGER,
	pm20002maPerfTelecomOutputClientPast15StatHistoryInvCvPort1
		EkiOnOff,
	pm20002maPerfTelecomOutputClientPast15StatHistoryCvValuePort1
		Unsigned32,
	pm20002maPerfTelecomOutputClientPast15StatHistoryInvEsPort1
		EkiOnOff,
	pm20002maPerfTelecomOutputClientPast15StatHistoryEsValuePort1
		Unsigned32,
	pm20002maPerfTelecomOutputClientPast15StatHistoryInvSesPort1
		EkiOnOff,
	pm20002maPerfTelecomOutputClientPast15StatHistorySesValuePort1
		Unsigned32,
	pm20002maPerfTelecomOutputClientPast15StatHistoryInvSefsPort1
		EkiOnOff,
	pm20002maPerfTelecomOutputClientPast15StatHistorySefsValuePort1
		Unsigned32,
	pm20002maPerfTelecomOutputClientPast15StatHistoryInvUasPort1
		EkiOnOff,
	pm20002maPerfTelecomOutputClientPast15StatHistoryUasValuePort1
		Unsigned32
	}


pm20002maPerfTelecomOutputClientPast15StatHistoryPort1Index OBJECT-TYPE
	SYNTAX  INTEGER(0..128)
	MAX-ACCESS  read-only
	STATUS current
	DESCRIPTION
        "
        Index definition for the pm20002maPerfTelecomOutputClientPast15StatHistory
        table
        "
	::= { pm20002maPerfTelecomOutputClientPast15StatHistoryPort1Entry 1 }


pm20002maPerfTelecomOutputClientPast15StatHistoryInvCvPort1 OBJECT-TYPE
	SYNTAX  EkiOnOff
	MAX-ACCESS read-only
	STATUS current
	DESCRIPTION
        "
        Previous 15-min EBC counter inv.
        :This OID indicates that the previous
        15-min Coding Violation counter
        is invalid
        "
	::= { pm20002maPerfTelecomOutputClientPast15StatHistoryPort1Entry 2 }


pm20002maPerfTelecomOutputClientPast15StatHistoryCvValuePort1 OBJECT-TYPE
	SYNTAX  Unsigned32
	MAX-ACCESS read-only
	STATUS current
	DESCRIPTION
        "
        Previous 15-min EBC counter :This
        OID gives the previous 15-min Coding
        Violation counter value
        "
	::= { pm20002maPerfTelecomOutputClientPast15StatHistoryPort1Entry 3 }


pm20002maPerfTelecomOutputClientPast15StatHistoryInvEsPort1 OBJECT-TYPE
	SYNTAX  EkiOnOff
	MAX-ACCESS read-only
	STATUS current
	DESCRIPTION
        "
        Previous 15-min ES counter inv.
        :This OID indicates that the previous
        15-min Errored Second counter is
        invalid
        "
	::= { pm20002maPerfTelecomOutputClientPast15StatHistoryPort1Entry 4 }


pm20002maPerfTelecomOutputClientPast15StatHistoryEsValuePort1 OBJECT-TYPE
	SYNTAX  Unsigned32
	MAX-ACCESS read-only
	STATUS current
	DESCRIPTION
        "
        Previous 15-min ES counter :This
        OID gives the previous 15-min Errored
        Second counter value
        "
	::= { pm20002maPerfTelecomOutputClientPast15StatHistoryPort1Entry 5 }


pm20002maPerfTelecomOutputClientPast15StatHistoryInvSesPort1 OBJECT-TYPE
	SYNTAX  EkiOnOff
	MAX-ACCESS read-only
	STATUS current
	DESCRIPTION
        "
        Previous 15-min SES counter inv.
        :This OID indicates that the previous
        15-min severely Errored Second
         counter is invalid
        "
	::= { pm20002maPerfTelecomOutputClientPast15StatHistoryPort1Entry 6 }


pm20002maPerfTelecomOutputClientPast15StatHistorySesValuePort1 OBJECT-TYPE
	SYNTAX  Unsigned32
	MAX-ACCESS read-only
	STATUS current
	DESCRIPTION
        "
        Previous 15-min SES counter :This
        OID gives the previous 15-min severely
        Errored Second counter value
        "
	::= { pm20002maPerfTelecomOutputClientPast15StatHistoryPort1Entry 7 }


pm20002maPerfTelecomOutputClientPast15StatHistoryInvSefsPort1 OBJECT-TYPE
	SYNTAX  EkiOnOff
	MAX-ACCESS read-only
	STATUS current
	DESCRIPTION
        "
        Previous 15-min SEFS counter inv.
        :This OID indicates that the previous
        15-min severely Errored Framing
        Second counter is invalid
        "
	::= { pm20002maPerfTelecomOutputClientPast15StatHistoryPort1Entry 8 }


pm20002maPerfTelecomOutputClientPast15StatHistorySefsValuePort1 OBJECT-TYPE
	SYNTAX  Unsigned32
	MAX-ACCESS read-only
	STATUS current
	DESCRIPTION
        "
        Previous 15-min SEFS counter :This
        OID gives the previous 15-min severely
        Errored Framing Second counter
         value
        "
	::= { pm20002maPerfTelecomOutputClientPast15StatHistoryPort1Entry 9 }


pm20002maPerfTelecomOutputClientPast15StatHistoryInvUasPort1 OBJECT-TYPE
	SYNTAX  EkiOnOff
	MAX-ACCESS read-only
	STATUS current
	DESCRIPTION
        "
        Previous 15-min UAS counter inv.
        :This OID indicates that the previous
        15-min UnAvailable Second counter
        is invalid
        "
	::= { pm20002maPerfTelecomOutputClientPast15StatHistoryPort1Entry 10 }


pm20002maPerfTelecomOutputClientPast15StatHistoryUasValuePort1 OBJECT-TYPE
	SYNTAX  Unsigned32
	MAX-ACCESS read-only
	STATUS current
	DESCRIPTION
        "
        Previous 15-min UAS counter :This
        OID gives the previous 15-min UnAvailable
        Second counter value
        "
	::= { pm20002maPerfTelecomOutputClientPast15StatHistoryPort1Entry 11 }


--- *****************************************************
---     Leaf of the telecomOutputClientCurrent24Stat
--- *****************************************************
--- *********************************************************
---     TABLE for the pm20002maPerfTelecomOutputClientCurrent24Stat articles
--- *********************************************************

pm20002maPerfTelecomOutputClientCurrent24StatTable OBJECT-TYPE
	SYNTAX  SEQUENCE OF Pm20002maPerfTelecomOutputClientCurrent24StatEntry
	MAX-ACCESS not-accessible
	STATUS current
	DESCRIPTION
        "
        List of pm20002maPerfTelecomOutputClientCurrent24Stat
        Article
        "
	::= { pm20002maMonPerfClient 208 }


pm20002maPerfTelecomOutputClientCurrent24StatEntry OBJECT-TYPE
	SYNTAX Pm20002maPerfTelecomOutputClientCurrent24StatEntry
	MAX-ACCESS not-accessible
	STATUS current
	DESCRIPTION
        "
        Row definition for the pm20002maPerfTelecomOutputClientCurrent24Stat
        table
        "
	INDEX   { pm20002maPerfTelecomOutputClientCurrent24StatIndex }
	::= { pm20002maPerfTelecomOutputClientCurrent24StatTable 1 }


Pm20002maPerfTelecomOutputClientCurrent24StatEntry ::=
	SEQUENCE {
	pm20002maPerfTelecomOutputClientCurrent24StatIndex
		INTEGER,
	pm20002maPerfTelecomOutputClientCurrent24StatInvCvPortn
		EkiOnOff,
	pm20002maPerfTelecomOutputClientCurrent24StatCvValuePortn
		Unsigned32,
	pm20002maPerfTelecomOutputClientCurrent24StatInvEsPortn
		EkiOnOff,
	pm20002maPerfTelecomOutputClientCurrent24StatEsValuePortn
		Unsigned32,
	pm20002maPerfTelecomOutputClientCurrent24StatInvSesPortn
		EkiOnOff,
	pm20002maPerfTelecomOutputClientCurrent24StatSesValuePortn
		Unsigned32,
	pm20002maPerfTelecomOutputClientCurrent24StatInvSefsPortn
		EkiOnOff,
	pm20002maPerfTelecomOutputClientCurrent24StatSefsValuePortn
		Unsigned32,
	pm20002maPerfTelecomOutputClientCurrent24StatInvUasPortn
		EkiOnOff,
	pm20002maPerfTelecomOutputClientCurrent24StatUasValuePortn
		Unsigned32
	}


pm20002maPerfTelecomOutputClientCurrent24StatIndex OBJECT-TYPE
	SYNTAX  INTEGER(0..128)
	MAX-ACCESS  read-only
	STATUS current
	DESCRIPTION
        "
        Index definition for the pm20002maPerfTelecomOutputClientCurrent24Stat
        table
        "
	::= { pm20002maPerfTelecomOutputClientCurrent24StatEntry 1 }


pm20002maPerfTelecomOutputClientCurrent24StatInvCvPortn OBJECT-TYPE
	SYNTAX  EkiOnOff
	MAX-ACCESS read-only
	STATUS current
	DESCRIPTION
        "
        Current 24-hours EBC counter inv.
        :This OID indicates that the current
        24-hours Coding Violation counter
        is invalid
        "
	::= { pm20002maPerfTelecomOutputClientCurrent24StatEntry 2 }


pm20002maPerfTelecomOutputClientCurrent24StatCvValuePortn OBJECT-TYPE
	SYNTAX  Unsigned32
	MAX-ACCESS read-only
	STATUS current
	DESCRIPTION
        "
        Current 24-hours EBC counter :This
        OID gives the current 24-hours
         Coding Violation counter value
        "
	::= { pm20002maPerfTelecomOutputClientCurrent24StatEntry 3 }


pm20002maPerfTelecomOutputClientCurrent24StatInvEsPortn OBJECT-TYPE
	SYNTAX  EkiOnOff
	MAX-ACCESS read-only
	STATUS current
	DESCRIPTION
        "
        Current 24-hours ES counter inv.
        :This OID indicates that the current
        24-hours Errored Second counter
        is invalid
        "
	::= { pm20002maPerfTelecomOutputClientCurrent24StatEntry 4 }


pm20002maPerfTelecomOutputClientCurrent24StatEsValuePortn OBJECT-TYPE
	SYNTAX  Unsigned32
	MAX-ACCESS read-only
	STATUS current
	DESCRIPTION
        "
        Current 24-hours ES counter :This
        OID gives the current 24-hours
         Errored Second counter value
        "
	::= { pm20002maPerfTelecomOutputClientCurrent24StatEntry 5 }


pm20002maPerfTelecomOutputClientCurrent24StatInvSesPortn OBJECT-TYPE
	SYNTAX  EkiOnOff
	MAX-ACCESS read-only
	STATUS current
	DESCRIPTION
        "
        Current 24-hours SES counter inv.
        :This OID indicates that the current
        24-hours severely Errored Second
        counter is invalid
        "
	::= { pm20002maPerfTelecomOutputClientCurrent24StatEntry 6 }


pm20002maPerfTelecomOutputClientCurrent24StatSesValuePortn OBJECT-TYPE
	SYNTAX  Unsigned32
	MAX-ACCESS read-only
	STATUS current
	DESCRIPTION
        "
        Current 24-hours SES counter :This
        OID gives the current 24-hours
         severely Errored Second counter
        value
        "
	::= { pm20002maPerfTelecomOutputClientCurrent24StatEntry 7 }


pm20002maPerfTelecomOutputClientCurrent24StatInvSefsPortn OBJECT-TYPE
	SYNTAX  EkiOnOff
	MAX-ACCESS read-only
	STATUS current
	DESCRIPTION
        "
        Current 24-hours SEFS counter
         inv. :This OID indicates that
         the current 24-hours severely
         Errored Framing Second counter
        is invalid
        "
	::= { pm20002maPerfTelecomOutputClientCurrent24StatEntry 8 }


pm20002maPerfTelecomOutputClientCurrent24StatSefsValuePortn OBJECT-TYPE
	SYNTAX  Unsigned32
	MAX-ACCESS read-only
	STATUS current
	DESCRIPTION
        "
        Current 24-hours SEFS counter
         :This OID gives the current 24-hours
        severely Errored Framing Second
        counter value
        "
	::= { pm20002maPerfTelecomOutputClientCurrent24StatEntry 9 }


pm20002maPerfTelecomOutputClientCurrent24StatInvUasPortn OBJECT-TYPE
	SYNTAX  EkiOnOff
	MAX-ACCESS read-only
	STATUS current
	DESCRIPTION
        "
        Current 24-hours UAS counter inv.
        :This OID indicates that the current
        24-hours UnAvailable Second counter
        is invalid
        "
	::= { pm20002maPerfTelecomOutputClientCurrent24StatEntry 10 }


pm20002maPerfTelecomOutputClientCurrent24StatUasValuePortn OBJECT-TYPE
	SYNTAX  Unsigned32
	MAX-ACCESS read-only
	STATUS current
	DESCRIPTION
        "
        Current 24-hours UAS counter :This
        OID gives the current 24-hours
         UnAvailable Second counter value
        "
	::= { pm20002maPerfTelecomOutputClientCurrent24StatEntry 11 }


--- *****************************************************
---     Leaf of the telecomOutputClientPast24Stat
--- *****************************************************
--- *********************************************************
---     TABLE for the pm20002maPerfTelecomOutputClientPast24StatHistory articles
--- *********************************************************

pm20002maPerfTelecomOutputClientPast24StatHistoryPort1Table OBJECT-TYPE
	SYNTAX  SEQUENCE OF Pm20002maPerfTelecomOutputClientPast24StatHistoryPort1Entry
	MAX-ACCESS not-accessible
	STATUS current
	DESCRIPTION
        "
        List of pm20002maPerfTelecomOutputClientPast24StatHistory
        Article
        "
	::= { pm20002maMonPerfClient 240 }


pm20002maPerfTelecomOutputClientPast24StatHistoryPort1Entry OBJECT-TYPE
	SYNTAX Pm20002maPerfTelecomOutputClientPast24StatHistoryPort1Entry
	MAX-ACCESS not-accessible
	STATUS current
	DESCRIPTION
        "
        Row definition for the pm20002maPerfTelecomOutputClientPast24StatHistory
        table
        "
	INDEX   { pm20002maPerfTelecomOutputClientPast24StatHistoryPort1Index }
	::= { pm20002maPerfTelecomOutputClientPast24StatHistoryPort1Table 1 }


Pm20002maPerfTelecomOutputClientPast24StatHistoryPort1Entry ::=
	SEQUENCE {
	pm20002maPerfTelecomOutputClientPast24StatHistoryPort1Index
		INTEGER,
	pm20002maPerfTelecomOutputClientPast24StatHistoryInvCvPort1
		EkiOnOff,
	pm20002maPerfTelecomOutputClientPast24StatHistoryCvValuePort1
		Unsigned32,
	pm20002maPerfTelecomOutputClientPast24StatHistoryInvEsPort1
		EkiOnOff,
	pm20002maPerfTelecomOutputClientPast24StatHistoryEsValuePort1
		Unsigned32,
	pm20002maPerfTelecomOutputClientPast24StatHistoryInvSesPort1
		EkiOnOff,
	pm20002maPerfTelecomOutputClientPast24StatHistorySesValuePort1
		Unsigned32,
	pm20002maPerfTelecomOutputClientPast24StatHistoryInvSefsPort1
		EkiOnOff,
	pm20002maPerfTelecomOutputClientPast24StatHistorySefsValuePort1
		Unsigned32,
	pm20002maPerfTelecomOutputClientPast24StatHistoryInvUasPort1
		EkiOnOff,
	pm20002maPerfTelecomOutputClientPast24StatHistoryUasValuePort1
		Unsigned32
	}


pm20002maPerfTelecomOutputClientPast24StatHistoryPort1Index OBJECT-TYPE
	SYNTAX  INTEGER(0..128)
	MAX-ACCESS  read-only
	STATUS current
	DESCRIPTION
        "
        Index definition for the pm20002maPerfTelecomOutputClientPast24StatHistory
        table
        "
	::= { pm20002maPerfTelecomOutputClientPast24StatHistoryPort1Entry 1 }


pm20002maPerfTelecomOutputClientPast24StatHistoryInvCvPort1 OBJECT-TYPE
	SYNTAX  EkiOnOff
	MAX-ACCESS read-only
	STATUS current
	DESCRIPTION
        "
        Previous 24-hours EBC counter
         inv. :This OID indicates that
         the previous 24-hours Coding Violation
        counter is invalid
        "
	::= { pm20002maPerfTelecomOutputClientPast24StatHistoryPort1Entry 2 }


pm20002maPerfTelecomOutputClientPast24StatHistoryCvValuePort1 OBJECT-TYPE
	SYNTAX  Unsigned32
	MAX-ACCESS read-only
	STATUS current
	DESCRIPTION
        "
        Previous 24-hours EBC counter
         :This OID gives the previous 24-hours
        Coding Violation counter value
        "
	::= { pm20002maPerfTelecomOutputClientPast24StatHistoryPort1Entry 3 }


pm20002maPerfTelecomOutputClientPast24StatHistoryInvEsPort1 OBJECT-TYPE
	SYNTAX  EkiOnOff
	MAX-ACCESS read-only
	STATUS current
	DESCRIPTION
        "
        Previous 24-hours ES counter inv.
        :This OID indicates that the previous
        24-hours Errored Second counter
        is invalid
        "
	::= { pm20002maPerfTelecomOutputClientPast24StatHistoryPort1Entry 4 }


pm20002maPerfTelecomOutputClientPast24StatHistoryEsValuePort1 OBJECT-TYPE
	SYNTAX  Unsigned32
	MAX-ACCESS read-only
	STATUS current
	DESCRIPTION
        "
        Previous 24-hours ES counter :This
        OID gives the previous 24-hours
        Errored Second counter value
        "
	::= { pm20002maPerfTelecomOutputClientPast24StatHistoryPort1Entry 5 }


pm20002maPerfTelecomOutputClientPast24StatHistoryInvSesPort1 OBJECT-TYPE
	SYNTAX  EkiOnOff
	MAX-ACCESS read-only
	STATUS current
	DESCRIPTION
        "
        Previous 24-hours SES counter
         inv. :This OID indicates that
         the previous 24-hours severely
        Errored Second counter is invalid
        "
	::= { pm20002maPerfTelecomOutputClientPast24StatHistoryPort1Entry 6 }


pm20002maPerfTelecomOutputClientPast24StatHistorySesValuePort1 OBJECT-TYPE
	SYNTAX  Unsigned32
	MAX-ACCESS read-only
	STATUS current
	DESCRIPTION
        "
        Previous 24-hours SES counter
         :This OID gives the previous 24-hours
        severely Errored Second counter
        value
        "
	::= { pm20002maPerfTelecomOutputClientPast24StatHistoryPort1Entry 7 }


pm20002maPerfTelecomOutputClientPast24StatHistoryInvSefsPort1 OBJECT-TYPE
	SYNTAX  EkiOnOff
	MAX-ACCESS read-only
	STATUS current
	DESCRIPTION
        "
        Previous 24-hours SEFS counter
        inv. :This OID indicates that the
        previous 24-hours severely Errored
        Framing Second counter is invalid
        "
	::= { pm20002maPerfTelecomOutputClientPast24StatHistoryPort1Entry 8 }


pm20002maPerfTelecomOutputClientPast24StatHistorySefsValuePort1 OBJECT-TYPE
	SYNTAX  Unsigned32
	MAX-ACCESS read-only
	STATUS current
	DESCRIPTION
        "
        Previous 24-hours SEFS counter
        :This OID gives the previous 24-hours
        severely Errored Framing Second
        counter value
        "
	::= { pm20002maPerfTelecomOutputClientPast24StatHistoryPort1Entry 9 }


pm20002maPerfTelecomOutputClientPast24StatHistoryInvUasPort1 OBJECT-TYPE
	SYNTAX  EkiOnOff
	MAX-ACCESS read-only
	STATUS current
	DESCRIPTION
        "
        Previous 24-hours UAS counter
         inv. :This OID indicates that
         the previous 24-hours UnAvailable
        Second counter is invalid
        "
	::= { pm20002maPerfTelecomOutputClientPast24StatHistoryPort1Entry 10 }


pm20002maPerfTelecomOutputClientPast24StatHistoryUasValuePort1 OBJECT-TYPE
	SYNTAX  Unsigned32
	MAX-ACCESS read-only
	STATUS current
	DESCRIPTION
        "
        Previous 24-hours UAS counter
         :This OID gives the previous 24-hours
        UnAvailable Second counter value
        "
	::= { pm20002maPerfTelecomOutputClientPast24StatHistoryPort1Entry 11 }


--- *****************************************************
---     Leaf of the telecomLinePostFecCurrent15Stat
--- *****************************************************
--- *********************************************************
---     TABLE for the pm20002maPerfTelecomLinePostFecCurrent15Stat articles
--- *********************************************************

pm20002maPerfTelecomLinePostFecCurrent15StatTable OBJECT-TYPE
	SYNTAX  SEQUENCE OF Pm20002maPerfTelecomLinePostFecCurrent15StatEntry
	MAX-ACCESS not-accessible
	STATUS current
	DESCRIPTION
        "
        List of pm20002maPerfTelecomLinePostFecCurrent15Stat
        Article
        "
	::= { pm20002maMonPerfLine 336 }


pm20002maPerfTelecomLinePostFecCurrent15StatEntry OBJECT-TYPE
	SYNTAX Pm20002maPerfTelecomLinePostFecCurrent15StatEntry
	MAX-ACCESS not-accessible
	STATUS current
	DESCRIPTION
        "
        Row definition for the pm20002maPerfTelecomLinePostFecCurrent15Stat
        table
        "
	INDEX   { pm20002maPerfTelecomLinePostFecCurrent15StatIndex }
	::= { pm20002maPerfTelecomLinePostFecCurrent15StatTable 1 }


Pm20002maPerfTelecomLinePostFecCurrent15StatEntry ::=
	SEQUENCE {
	pm20002maPerfTelecomLinePostFecCurrent15StatIndex
		INTEGER,
	pm20002maPerfTelecomLinePostFecCurrent15StatInvCvPortn
		EkiOnOff,
	pm20002maPerfTelecomLinePostFecCurrent15StatCvValuePortn
		Unsigned32,
	pm20002maPerfTelecomLinePostFecCurrent15StatInvEsPortn
		EkiOnOff,
	pm20002maPerfTelecomLinePostFecCurrent15StatEsValuePortn
		Unsigned32,
	pm20002maPerfTelecomLinePostFecCurrent15StatInvSesPortn
		EkiOnOff,
	pm20002maPerfTelecomLinePostFecCurrent15StatSesValuePortn
		Unsigned32,
	pm20002maPerfTelecomLinePostFecCurrent15StatInvSefsPortn
		EkiOnOff,
	pm20002maPerfTelecomLinePostFecCurrent15StatSefsValuePortn
		Unsigned32,
	pm20002maPerfTelecomLinePostFecCurrent15StatInvUasPortn
		EkiOnOff,
	pm20002maPerfTelecomLinePostFecCurrent15StatUasValuePortn
		Unsigned32
	}


pm20002maPerfTelecomLinePostFecCurrent15StatIndex OBJECT-TYPE
	SYNTAX  INTEGER(0..128)
	MAX-ACCESS  read-only
	STATUS current
	DESCRIPTION
        "
        Index definition for the pm20002maPerfTelecomLinePostFecCurrent15Stat
        table
        "
	::= { pm20002maPerfTelecomLinePostFecCurrent15StatEntry 1 }


pm20002maPerfTelecomLinePostFecCurrent15StatInvCvPortn OBJECT-TYPE
	SYNTAX  EkiOnOff
	MAX-ACCESS read-only
	STATUS current
	DESCRIPTION
        "
        Current 15-min EBC counter inv.
        :This OID indicates that the current
        15-min Coding Violation counter
        is invalid
        "
	::= { pm20002maPerfTelecomLinePostFecCurrent15StatEntry 2 }


pm20002maPerfTelecomLinePostFecCurrent15StatCvValuePortn OBJECT-TYPE
	SYNTAX  Unsigned32
	MAX-ACCESS read-only
	STATUS current
	DESCRIPTION
        "
        Current 15-min EBC counter :This
        OID gives the current 15-min Coding
        Violation counter value
        "
	::= { pm20002maPerfTelecomLinePostFecCurrent15StatEntry 3 }


pm20002maPerfTelecomLinePostFecCurrent15StatInvEsPortn OBJECT-TYPE
	SYNTAX  EkiOnOff
	MAX-ACCESS read-only
	STATUS current
	DESCRIPTION
        "
        Current 15-min ES counter inv.
        :This OID indicates that the current
        15-min Errored Second counter is
        invalid
        "
	::= { pm20002maPerfTelecomLinePostFecCurrent15StatEntry 4 }


pm20002maPerfTelecomLinePostFecCurrent15StatEsValuePortn OBJECT-TYPE
	SYNTAX  Unsigned32
	MAX-ACCESS read-only
	STATUS current
	DESCRIPTION
        "
        Current 15-min ES counter :This
        OID gives the current 15-min Errored
        Second counter value
        "
	::= { pm20002maPerfTelecomLinePostFecCurrent15StatEntry 5 }


pm20002maPerfTelecomLinePostFecCurrent15StatInvSesPortn OBJECT-TYPE
	SYNTAX  EkiOnOff
	MAX-ACCESS read-only
	STATUS current
	DESCRIPTION
        "
        Current 15-min SES counter inv.
        :This OID indicates that the current
        15-min severely Errored Second
         counter is invalid
        "
	::= { pm20002maPerfTelecomLinePostFecCurrent15StatEntry 6 }


pm20002maPerfTelecomLinePostFecCurrent15StatSesValuePortn OBJECT-TYPE
	SYNTAX  Unsigned32
	MAX-ACCESS read-only
	STATUS current
	DESCRIPTION
        "
        Current 15-min SES counter :This
        OID gives the current 15-min severely
        Errored Second counter value
        "
	::= { pm20002maPerfTelecomLinePostFecCurrent15StatEntry 7 }


pm20002maPerfTelecomLinePostFecCurrent15StatInvSefsPortn OBJECT-TYPE
	SYNTAX  EkiOnOff
	MAX-ACCESS read-only
	STATUS current
	DESCRIPTION
        "
        Current 15-min SEFS counter inv.
        :This OID indicates that the current
        15-min severely Errored Framing
        Second counter is invalid
        "
	::= { pm20002maPerfTelecomLinePostFecCurrent15StatEntry 8 }


pm20002maPerfTelecomLinePostFecCurrent15StatSefsValuePortn OBJECT-TYPE
	SYNTAX  Unsigned32
	MAX-ACCESS read-only
	STATUS current
	DESCRIPTION
        "
        Current 15-min SEFS counter :This
        OID gives the current 15-min severely
        Errored Framing Second counter
         value
        "
	::= { pm20002maPerfTelecomLinePostFecCurrent15StatEntry 9 }


pm20002maPerfTelecomLinePostFecCurrent15StatInvUasPortn OBJECT-TYPE
	SYNTAX  EkiOnOff
	MAX-ACCESS read-only
	STATUS current
	DESCRIPTION
        "
        Current 15-min UAS counter inv.
        :This OID indicates that the current
        15-min UnAvailable Second counter
        is invalid
        "
	::= { pm20002maPerfTelecomLinePostFecCurrent15StatEntry 10 }


pm20002maPerfTelecomLinePostFecCurrent15StatUasValuePortn OBJECT-TYPE
	SYNTAX  Unsigned32
	MAX-ACCESS read-only
	STATUS current
	DESCRIPTION
        "
        Current 15-min UAS counter :This
        OID gives the current 15-min UnAvailable
        Second counter value
        "
	::= { pm20002maPerfTelecomLinePostFecCurrent15StatEntry 11 }


--- *****************************************************
---     Leaf of the telecomLinePostFecPast15Stat
--- *****************************************************
--- *********************************************************
---     TABLE for the pm20002maPerfTelecomLinePostFecPast15StatHistory articles
--- *********************************************************

pm20002maPerfTelecomLinePostFecPast15StatHistoryPort1Table OBJECT-TYPE
	SYNTAX  SEQUENCE OF Pm20002maPerfTelecomLinePostFecPast15StatHistoryPort1Entry
	MAX-ACCESS not-accessible
	STATUS current
	DESCRIPTION
        "
        List of pm20002maPerfTelecomLinePostFecPast15StatHistory
        Article
        "
	::= { pm20002maMonPerfLine 337 }


pm20002maPerfTelecomLinePostFecPast15StatHistoryPort1Entry OBJECT-TYPE
	SYNTAX Pm20002maPerfTelecomLinePostFecPast15StatHistoryPort1Entry
	MAX-ACCESS not-accessible
	STATUS current
	DESCRIPTION
        "
        Row definition for the pm20002maPerfTelecomLinePostFecPast15StatHistory
        table
        "
	INDEX   { pm20002maPerfTelecomLinePostFecPast15StatHistoryPort1Index }
	::= { pm20002maPerfTelecomLinePostFecPast15StatHistoryPort1Table 1 }


Pm20002maPerfTelecomLinePostFecPast15StatHistoryPort1Entry ::=
	SEQUENCE {
	pm20002maPerfTelecomLinePostFecPast15StatHistoryPort1Index
		INTEGER,
	pm20002maPerfTelecomLinePostFecPast15StatHistoryInvCvPort1
		EkiOnOff,
	pm20002maPerfTelecomLinePostFecPast15StatHistoryCvValuePort1
		Unsigned32,
	pm20002maPerfTelecomLinePostFecPast15StatHistoryInvEsPort1
		EkiOnOff,
	pm20002maPerfTelecomLinePostFecPast15StatHistoryEsValuePort1
		Unsigned32,
	pm20002maPerfTelecomLinePostFecPast15StatHistoryInvSesPort1
		EkiOnOff,
	pm20002maPerfTelecomLinePostFecPast15StatHistorySesValuePort1
		Unsigned32,
	pm20002maPerfTelecomLinePostFecPast15StatHistoryInvSefsPort1
		EkiOnOff,
	pm20002maPerfTelecomLinePostFecPast15StatHistorySefsValuePort1
		Unsigned32,
	pm20002maPerfTelecomLinePostFecPast15StatHistoryInvUasPort1
		EkiOnOff,
	pm20002maPerfTelecomLinePostFecPast15StatHistoryUasValuePort1
		Unsigned32
	}


pm20002maPerfTelecomLinePostFecPast15StatHistoryPort1Index OBJECT-TYPE
	SYNTAX  INTEGER(0..128)
	MAX-ACCESS  read-only
	STATUS current
	DESCRIPTION
        "
        Index definition for the pm20002maPerfTelecomLinePostFecPast15StatHistory
        table
        "
	::= { pm20002maPerfTelecomLinePostFecPast15StatHistoryPort1Entry 1 }


pm20002maPerfTelecomLinePostFecPast15StatHistoryInvCvPort1 OBJECT-TYPE
	SYNTAX  EkiOnOff
	MAX-ACCESS read-only
	STATUS current
	DESCRIPTION
        "
        Previous 15-min EBC counter inv.
        :This OID indicates that the previous
        15-min Coding Violation counter
        is invalid
        "
	::= { pm20002maPerfTelecomLinePostFecPast15StatHistoryPort1Entry 2 }


pm20002maPerfTelecomLinePostFecPast15StatHistoryCvValuePort1 OBJECT-TYPE
	SYNTAX  Unsigned32
	MAX-ACCESS read-only
	STATUS current
	DESCRIPTION
        "
        Previous 15-min EBC counter :This
        OID gives the previous 15-min Coding
        Violation counter value
        "
	::= { pm20002maPerfTelecomLinePostFecPast15StatHistoryPort1Entry 3 }


pm20002maPerfTelecomLinePostFecPast15StatHistoryInvEsPort1 OBJECT-TYPE
	SYNTAX  EkiOnOff
	MAX-ACCESS read-only
	STATUS current
	DESCRIPTION
        "
        Previous 15-min ES counter inv.
        :This OID indicates that the previous
        15-min Errored Second counter is
        invalid
        "
	::= { pm20002maPerfTelecomLinePostFecPast15StatHistoryPort1Entry 4 }


pm20002maPerfTelecomLinePostFecPast15StatHistoryEsValuePort1 OBJECT-TYPE
	SYNTAX  Unsigned32
	MAX-ACCESS read-only
	STATUS current
	DESCRIPTION
        "
        Previous 15-min ES counter :This
        OID gives the previous 15-min Errored
        Second counter value
        "
	::= { pm20002maPerfTelecomLinePostFecPast15StatHistoryPort1Entry 5 }


pm20002maPerfTelecomLinePostFecPast15StatHistoryInvSesPort1 OBJECT-TYPE
	SYNTAX  EkiOnOff
	MAX-ACCESS read-only
	STATUS current
	DESCRIPTION
        "
        Previous 15-min SES counter inv.
        :This OID indicates that the previous
        15-min severely Errored Second
         counter is invalid
        "
	::= { pm20002maPerfTelecomLinePostFecPast15StatHistoryPort1Entry 6 }


pm20002maPerfTelecomLinePostFecPast15StatHistorySesValuePort1 OBJECT-TYPE
	SYNTAX  Unsigned32
	MAX-ACCESS read-only
	STATUS current
	DESCRIPTION
        "
        Previous 15-min SES counter :This
        OID gives the previous 15-min severely
        Errored Second counter value
        "
	::= { pm20002maPerfTelecomLinePostFecPast15StatHistoryPort1Entry 7 }


pm20002maPerfTelecomLinePostFecPast15StatHistoryInvSefsPort1 OBJECT-TYPE
	SYNTAX  EkiOnOff
	MAX-ACCESS read-only
	STATUS current
	DESCRIPTION
        "
        Previous 15-min SEFS counter inv.
        :This OID indicates that the previous
        15-min severely Errored Framing
        Second counter is invalid
        "
	::= { pm20002maPerfTelecomLinePostFecPast15StatHistoryPort1Entry 8 }


pm20002maPerfTelecomLinePostFecPast15StatHistorySefsValuePort1 OBJECT-TYPE
	SYNTAX  Unsigned32
	MAX-ACCESS read-only
	STATUS current
	DESCRIPTION
        "
        Previous 15-min SEFS counter :This
        OID gives the previous 15-min severely
        Errored Framing Second counter
         value
        "
	::= { pm20002maPerfTelecomLinePostFecPast15StatHistoryPort1Entry 9 }


pm20002maPerfTelecomLinePostFecPast15StatHistoryInvUasPort1 OBJECT-TYPE
	SYNTAX  EkiOnOff
	MAX-ACCESS read-only
	STATUS current
	DESCRIPTION
        "
        Previous 15-min UAS counter inv.
        :This OID indicates that the previous
        15-min UnAvailable Second counter
        is invalid
        "
	::= { pm20002maPerfTelecomLinePostFecPast15StatHistoryPort1Entry 10 }


pm20002maPerfTelecomLinePostFecPast15StatHistoryUasValuePort1 OBJECT-TYPE
	SYNTAX  Unsigned32
	MAX-ACCESS read-only
	STATUS current
	DESCRIPTION
        "
        Previous 15-min UAS counter :This
        OID gives the previous 15-min UnAvailable
        Second counter value
        "
	::= { pm20002maPerfTelecomLinePostFecPast15StatHistoryPort1Entry 11 }


--- *****************************************************
---     Leaf of the telecomLinePostFecCurrent24Stat
--- *****************************************************
--- *********************************************************
---     TABLE for the pm20002maPerfTelecomLinePostFecCurrent24Stat articles
--- *********************************************************

pm20002maPerfTelecomLinePostFecCurrent24StatTable OBJECT-TYPE
	SYNTAX  SEQUENCE OF Pm20002maPerfTelecomLinePostFecCurrent24StatEntry
	MAX-ACCESS not-accessible
	STATUS current
	DESCRIPTION
        "
        List of pm20002maPerfTelecomLinePostFecCurrent24Stat
        Article
        "
	::= { pm20002maMonPerfLine 338 }


pm20002maPerfTelecomLinePostFecCurrent24StatEntry OBJECT-TYPE
	SYNTAX Pm20002maPerfTelecomLinePostFecCurrent24StatEntry
	MAX-ACCESS not-accessible
	STATUS current
	DESCRIPTION
        "
        Row definition for the pm20002maPerfTelecomLinePostFecCurrent24Stat
        table
        "
	INDEX   { pm20002maPerfTelecomLinePostFecCurrent24StatIndex }
	::= { pm20002maPerfTelecomLinePostFecCurrent24StatTable 1 }


Pm20002maPerfTelecomLinePostFecCurrent24StatEntry ::=
	SEQUENCE {
	pm20002maPerfTelecomLinePostFecCurrent24StatIndex
		INTEGER,
	pm20002maPerfTelecomLinePostFecCurrent24StatInvCvPortn
		EkiOnOff,
	pm20002maPerfTelecomLinePostFecCurrent24StatCvValuePortn
		Unsigned32,
	pm20002maPerfTelecomLinePostFecCurrent24StatInvEsPortn
		EkiOnOff,
	pm20002maPerfTelecomLinePostFecCurrent24StatEsValuePortn
		Unsigned32,
	pm20002maPerfTelecomLinePostFecCurrent24StatInvSesPortn
		EkiOnOff,
	pm20002maPerfTelecomLinePostFecCurrent24StatSesValuePortn
		Unsigned32,
	pm20002maPerfTelecomLinePostFecCurrent24StatInvSefsPortn
		EkiOnOff,
	pm20002maPerfTelecomLinePostFecCurrent24StatSefsValuePortn
		Unsigned32,
	pm20002maPerfTelecomLinePostFecCurrent24StatInvUasPortn
		EkiOnOff,
	pm20002maPerfTelecomLinePostFecCurrent24StatUasValuePortn
		Unsigned32
	}


pm20002maPerfTelecomLinePostFecCurrent24StatIndex OBJECT-TYPE
	SYNTAX  INTEGER(0..128)
	MAX-ACCESS  read-only
	STATUS current
	DESCRIPTION
        "
        Index definition for the pm20002maPerfTelecomLinePostFecCurrent24Stat
        table
        "
	::= { pm20002maPerfTelecomLinePostFecCurrent24StatEntry 1 }


pm20002maPerfTelecomLinePostFecCurrent24StatInvCvPortn OBJECT-TYPE
	SYNTAX  EkiOnOff
	MAX-ACCESS read-only
	STATUS current
	DESCRIPTION
        "
        Current 24-hours EBC counter inv.
        :This OID indicates that the current
        24-hours Coding Violation counter
        is invalid
        "
	::= { pm20002maPerfTelecomLinePostFecCurrent24StatEntry 2 }


pm20002maPerfTelecomLinePostFecCurrent24StatCvValuePortn OBJECT-TYPE
	SYNTAX  Unsigned32
	MAX-ACCESS read-only
	STATUS current
	DESCRIPTION
        "
        Current 24-hours EBC counter :This
        OID gives the current 24-hours
         Coding Violation counter value
        "
	::= { pm20002maPerfTelecomLinePostFecCurrent24StatEntry 3 }


pm20002maPerfTelecomLinePostFecCurrent24StatInvEsPortn OBJECT-TYPE
	SYNTAX  EkiOnOff
	MAX-ACCESS read-only
	STATUS current
	DESCRIPTION
        "
        Current 24-hours ES counter inv.
        :This OID indicates that the current
        24-hours Errored Second counter
        is invalid
        "
	::= { pm20002maPerfTelecomLinePostFecCurrent24StatEntry 4 }


pm20002maPerfTelecomLinePostFecCurrent24StatEsValuePortn OBJECT-TYPE
	SYNTAX  Unsigned32
	MAX-ACCESS read-only
	STATUS current
	DESCRIPTION
        "
        Current 24-hours ES counter :This
        OID gives the current 24-hours
         Errored Second counter value
        "
	::= { pm20002maPerfTelecomLinePostFecCurrent24StatEntry 5 }


pm20002maPerfTelecomLinePostFecCurrent24StatInvSesPortn OBJECT-TYPE
	SYNTAX  EkiOnOff
	MAX-ACCESS read-only
	STATUS current
	DESCRIPTION
        "
        Current 24-hours SES counter inv.
        :This OID indicates that the current
        24-hours severely Errored Second
        counter is invalid
        "
	::= { pm20002maPerfTelecomLinePostFecCurrent24StatEntry 6 }


pm20002maPerfTelecomLinePostFecCurrent24StatSesValuePortn OBJECT-TYPE
	SYNTAX  Unsigned32
	MAX-ACCESS read-only
	STATUS current
	DESCRIPTION
        "
        Current 24-hours SES counter :This
        OID gives the current 24-hours
         severely Errored Second counter
        value
        "
	::= { pm20002maPerfTelecomLinePostFecCurrent24StatEntry 7 }


pm20002maPerfTelecomLinePostFecCurrent24StatInvSefsPortn OBJECT-TYPE
	SYNTAX  EkiOnOff
	MAX-ACCESS read-only
	STATUS current
	DESCRIPTION
        "
        Current 24-hours SEFS counter
         inv. :This OID indicates that
         the current 24-hours severely
         Errored Framing Second counter
        is invalid
        "
	::= { pm20002maPerfTelecomLinePostFecCurrent24StatEntry 8 }


pm20002maPerfTelecomLinePostFecCurrent24StatSefsValuePortn OBJECT-TYPE
	SYNTAX  Unsigned32
	MAX-ACCESS read-only
	STATUS current
	DESCRIPTION
        "
        Current 24-hours SEFS counter
         :This OID gives the current 24-hours
        severely Errored Framing Second
        counter value
        "
	::= { pm20002maPerfTelecomLinePostFecCurrent24StatEntry 9 }


pm20002maPerfTelecomLinePostFecCurrent24StatInvUasPortn OBJECT-TYPE
	SYNTAX  EkiOnOff
	MAX-ACCESS read-only
	STATUS current
	DESCRIPTION
        "
        Current 24-hours UAS counter inv.
        :This OID indicates that the current
        24-hours UnAvailable Second counter
        is invalid
        "
	::= { pm20002maPerfTelecomLinePostFecCurrent24StatEntry 10 }


pm20002maPerfTelecomLinePostFecCurrent24StatUasValuePortn OBJECT-TYPE
	SYNTAX  Unsigned32
	MAX-ACCESS read-only
	STATUS current
	DESCRIPTION
        "
        Current 24-hours UAS counter :This
        OID gives the current 24-hours
         UnAvailable Second counter value
        "
	::= { pm20002maPerfTelecomLinePostFecCurrent24StatEntry 11 }


--- *****************************************************
---     Leaf of the telecomLinePostFecPast24Stat
--- *****************************************************
--- *********************************************************
---     TABLE for the pm20002maPerfTelecomLinePostFecPast24StatHistory articles
--- *********************************************************

pm20002maPerfTelecomLinePostFecPast24StatHistoryPort1Table OBJECT-TYPE
	SYNTAX  SEQUENCE OF Pm20002maPerfTelecomLinePostFecPast24StatHistoryPort1Entry
	MAX-ACCESS not-accessible
	STATUS current
	DESCRIPTION
        "
        List of pm20002maPerfTelecomLinePostFecPast24StatHistory
        Article
        "
	::= { pm20002maMonPerfLine 339 }


pm20002maPerfTelecomLinePostFecPast24StatHistoryPort1Entry OBJECT-TYPE
	SYNTAX Pm20002maPerfTelecomLinePostFecPast24StatHistoryPort1Entry
	MAX-ACCESS not-accessible
	STATUS current
	DESCRIPTION
        "
        Row definition for the pm20002maPerfTelecomLinePostFecPast24StatHistory
        table
        "
	INDEX   { pm20002maPerfTelecomLinePostFecPast24StatHistoryPort1Index }
	::= { pm20002maPerfTelecomLinePostFecPast24StatHistoryPort1Table 1 }


Pm20002maPerfTelecomLinePostFecPast24StatHistoryPort1Entry ::=
	SEQUENCE {
	pm20002maPerfTelecomLinePostFecPast24StatHistoryPort1Index
		INTEGER,
	pm20002maPerfTelecomLinePostFecPast24StatHistoryInvCvPort1
		EkiOnOff,
	pm20002maPerfTelecomLinePostFecPast24StatHistoryCvValuePort1
		Unsigned32,
	pm20002maPerfTelecomLinePostFecPast24StatHistoryInvEsPort1
		EkiOnOff,
	pm20002maPerfTelecomLinePostFecPast24StatHistoryEsValuePort1
		Unsigned32,
	pm20002maPerfTelecomLinePostFecPast24StatHistoryInvSesPort1
		EkiOnOff,
	pm20002maPerfTelecomLinePostFecPast24StatHistorySesValuePort1
		Unsigned32,
	pm20002maPerfTelecomLinePostFecPast24StatHistoryInvSefsPort1
		EkiOnOff,
	pm20002maPerfTelecomLinePostFecPast24StatHistorySefsValuePort1
		Unsigned32,
	pm20002maPerfTelecomLinePostFecPast24StatHistoryInvUasPort1
		EkiOnOff,
	pm20002maPerfTelecomLinePostFecPast24StatHistoryUasValuePort1
		Unsigned32
	}


pm20002maPerfTelecomLinePostFecPast24StatHistoryPort1Index OBJECT-TYPE
	SYNTAX  INTEGER(0..128)
	MAX-ACCESS  read-only
	STATUS current
	DESCRIPTION
        "
        Index definition for the pm20002maPerfTelecomLinePostFecPast24StatHistory
        table
        "
	::= { pm20002maPerfTelecomLinePostFecPast24StatHistoryPort1Entry 1 }


pm20002maPerfTelecomLinePostFecPast24StatHistoryInvCvPort1 OBJECT-TYPE
	SYNTAX  EkiOnOff
	MAX-ACCESS read-only
	STATUS current
	DESCRIPTION
        "
        Previous 24-hours EBC counter
         inv. :This OID indicates that
         the previous 24-hours Coding Violation
        counter is invalid
        "
	::= { pm20002maPerfTelecomLinePostFecPast24StatHistoryPort1Entry 2 }


pm20002maPerfTelecomLinePostFecPast24StatHistoryCvValuePort1 OBJECT-TYPE
	SYNTAX  Unsigned32
	MAX-ACCESS read-only
	STATUS current
	DESCRIPTION
        "
        Previous 24-hours EBC counter
         :This OID gives the previous 24-hours
        Coding Violation counter value
        "
	::= { pm20002maPerfTelecomLinePostFecPast24StatHistoryPort1Entry 3 }


pm20002maPerfTelecomLinePostFecPast24StatHistoryInvEsPort1 OBJECT-TYPE
	SYNTAX  EkiOnOff
	MAX-ACCESS read-only
	STATUS current
	DESCRIPTION
        "
        Previous 24-hours ES counter inv.
        :This OID indicates that the previous
        24-hours Errored Second counter
        is invalid
        "
	::= { pm20002maPerfTelecomLinePostFecPast24StatHistoryPort1Entry 4 }


pm20002maPerfTelecomLinePostFecPast24StatHistoryEsValuePort1 OBJECT-TYPE
	SYNTAX  Unsigned32
	MAX-ACCESS read-only
	STATUS current
	DESCRIPTION
        "
        Previous 24-hours ES counter :This
        OID gives the previous 24-hours
        Errored Second counter value
        "
	::= { pm20002maPerfTelecomLinePostFecPast24StatHistoryPort1Entry 5 }


pm20002maPerfTelecomLinePostFecPast24StatHistoryInvSesPort1 OBJECT-TYPE
	SYNTAX  EkiOnOff
	MAX-ACCESS read-only
	STATUS current
	DESCRIPTION
        "
        Previous 24-hours SES counter
         inv. :This OID indicates that
         the previous 24-hours severely
        Errored Second counter is invalid
        "
	::= { pm20002maPerfTelecomLinePostFecPast24StatHistoryPort1Entry 6 }


pm20002maPerfTelecomLinePostFecPast24StatHistorySesValuePort1 OBJECT-TYPE
	SYNTAX  Unsigned32
	MAX-ACCESS read-only
	STATUS current
	DESCRIPTION
        "
        Previous 24-hours SES counter
         :This OID gives the previous 24-hours
        severely Errored Second counter
        value
        "
	::= { pm20002maPerfTelecomLinePostFecPast24StatHistoryPort1Entry 7 }


pm20002maPerfTelecomLinePostFecPast24StatHistoryInvSefsPort1 OBJECT-TYPE
	SYNTAX  EkiOnOff
	MAX-ACCESS read-only
	STATUS current
	DESCRIPTION
        "
        Previous 24-hours SEFS counter
        inv. :This OID indicates that the
        previous 24-hours severely Errored
        Framing Second counter is invalid
        "
	::= { pm20002maPerfTelecomLinePostFecPast24StatHistoryPort1Entry 8 }


pm20002maPerfTelecomLinePostFecPast24StatHistorySefsValuePort1 OBJECT-TYPE
	SYNTAX  Unsigned32
	MAX-ACCESS read-only
	STATUS current
	DESCRIPTION
        "
        Previous 24-hours SEFS counter
        :This OID gives the previous 24-hours
        severely Errored Framing Second
        counter value
        "
	::= { pm20002maPerfTelecomLinePostFecPast24StatHistoryPort1Entry 9 }


pm20002maPerfTelecomLinePostFecPast24StatHistoryInvUasPort1 OBJECT-TYPE
	SYNTAX  EkiOnOff
	MAX-ACCESS read-only
	STATUS current
	DESCRIPTION
        "
        Previous 24-hours UAS counter
         inv. :This OID indicates that
         the previous 24-hours UnAvailable
        Second counter is invalid
        "
	::= { pm20002maPerfTelecomLinePostFecPast24StatHistoryPort1Entry 10 }


pm20002maPerfTelecomLinePostFecPast24StatHistoryUasValuePort1 OBJECT-TYPE
	SYNTAX  Unsigned32
	MAX-ACCESS read-only
	STATUS current
	DESCRIPTION
        "
        Previous 24-hours UAS counter
         :This OID gives the previous 24-hours
        UnAvailable Second counter value
        "
	::= { pm20002maPerfTelecomLinePostFecPast24StatHistoryPort1Entry 11 }


--- *****************************************************
---     Leaf of the telecomBerLinePreFecCurrent15Stat
--- *****************************************************
--- *********************************************************
---     TABLE for the pm20002maPerfTelecomBerLinePreFecCurrent15Stat articles
--- *********************************************************

pm20002maPerfTelecomBerLinePreFecCurrent15StatTable OBJECT-TYPE
	SYNTAX  SEQUENCE OF Pm20002maPerfTelecomBerLinePreFecCurrent15StatEntry
	MAX-ACCESS not-accessible
	STATUS current
	DESCRIPTION
        "
        List of pm20002maPerfTelecomBerLinePreFecCurrent15Stat
        Article
        "
	::= { pm20002maMonPerfLine 352 }


pm20002maPerfTelecomBerLinePreFecCurrent15StatEntry OBJECT-TYPE
	SYNTAX Pm20002maPerfTelecomBerLinePreFecCurrent15StatEntry
	MAX-ACCESS not-accessible
	STATUS current
	DESCRIPTION
        "
        Row definition for the pm20002maPerfTelecomBerLinePreFecCurrent15Stat
        table
        "
	INDEX   { pm20002maPerfTelecomBerLinePreFecCurrent15StatIndex }
	::= { pm20002maPerfTelecomBerLinePreFecCurrent15StatTable 1 }


Pm20002maPerfTelecomBerLinePreFecCurrent15StatEntry ::=
	SEQUENCE {
	pm20002maPerfTelecomBerLinePreFecCurrent15StatIndex
		INTEGER,
	pm20002maPerfTelecomBerLinePreFecCurrent15StatInvBerPortn
		EkiOnOff,
	pm20002maPerfTelecomBerLinePreFecCurrent15StatBerValuePortn
		Unsigned32,
	pm20002maPerfTelecomBerLinePreFecCurrent15StatInvMinBerPortn
		EkiOnOff,
	pm20002maPerfTelecomBerLinePreFecCurrent15StatMinBerValuePortn
		Unsigned32,
	pm20002maPerfTelecomBerLinePreFecCurrent15StatInvMaxBerPortn
		EkiOnOff,
	pm20002maPerfTelecomBerLinePreFecCurrent15StatMaxBerValuePortn
		Unsigned32
	}


pm20002maPerfTelecomBerLinePreFecCurrent15StatIndex OBJECT-TYPE
	SYNTAX  INTEGER(0..128)
	MAX-ACCESS  read-only
	STATUS current
	DESCRIPTION
        "
        Index definition for the pm20002maPerfTelecomBerLinePreFecCurrent15Stat
        table
        "
	::= { pm20002maPerfTelecomBerLinePreFecCurrent15StatEntry 1 }


pm20002maPerfTelecomBerLinePreFecCurrent15StatInvBerPortn OBJECT-TYPE
	SYNTAX  EkiOnOff
	MAX-ACCESS read-only
	STATUS current
	DESCRIPTION
        "
        Current 15-min BER counter inv.
        :This OID indicates that the current
        15-min Coding Violation counter
        is invalid
        "
	::= { pm20002maPerfTelecomBerLinePreFecCurrent15StatEntry 2 }


pm20002maPerfTelecomBerLinePreFecCurrent15StatBerValuePortn OBJECT-TYPE
	SYNTAX  Unsigned32
	MAX-ACCESS read-only
	STATUS current
	DESCRIPTION
        "
        Current 15-min BER counter :This
        OID gives the current 15-min Coding
        Violation counter value
        "
	::= { pm20002maPerfTelecomBerLinePreFecCurrent15StatEntry 3 }


pm20002maPerfTelecomBerLinePreFecCurrent15StatInvMinBerPortn OBJECT-TYPE
	SYNTAX  EkiOnOff
	MAX-ACCESS read-only
	STATUS current
	DESCRIPTION
        "
        Current 15-min MinBER counter
         inv. :This OID indicates that
         the current 15-min Errored Second
        counter is invalid
        "
	::= { pm20002maPerfTelecomBerLinePreFecCurrent15StatEntry 4 }


pm20002maPerfTelecomBerLinePreFecCurrent15StatMinBerValuePortn OBJECT-TYPE
	SYNTAX  Unsigned32
	MAX-ACCESS read-only
	STATUS current
	DESCRIPTION
        "
        Current 15-min MinBER counter
         :This OID gives the current 15-min
        Errored Second counter value
        "
	::= { pm20002maPerfTelecomBerLinePreFecCurrent15StatEntry 5 }


pm20002maPerfTelecomBerLinePreFecCurrent15StatInvMaxBerPortn OBJECT-TYPE
	SYNTAX  EkiOnOff
	MAX-ACCESS read-only
	STATUS current
	DESCRIPTION
        "
        Current 15-min MaxBER counter
         inv. :This OID indicates that
         the current 15-min severely Errored
        Second counter is invalid
        "
	::= { pm20002maPerfTelecomBerLinePreFecCurrent15StatEntry 6 }


pm20002maPerfTelecomBerLinePreFecCurrent15StatMaxBerValuePortn OBJECT-TYPE
	SYNTAX  Unsigned32
	MAX-ACCESS read-only
	STATUS current
	DESCRIPTION
        "
        Current 15-min MaxBER counter
         :This OID gives the current 15-min
        severely Errored Second counter
        value
        "
	::= { pm20002maPerfTelecomBerLinePreFecCurrent15StatEntry 7 }


--- *****************************************************
---     Leaf of the telecomBerLinePreFecPast15Stat
--- *****************************************************
--- *********************************************************
---     TABLE for the pm20002maPerfTelecomBerLinePreFecPast15StatHistory articles
--- *********************************************************

pm20002maPerfTelecomBerLinePreFecPast15StatHistoryPort1Table OBJECT-TYPE
	SYNTAX  SEQUENCE OF Pm20002maPerfTelecomBerLinePreFecPast15StatHistoryPort1Entry
	MAX-ACCESS not-accessible
	STATUS current
	DESCRIPTION
        "
        List of pm20002maPerfTelecomBerLinePreFecPast15StatHistory
        Article
        "
	::= { pm20002maMonPerfLine 353 }


pm20002maPerfTelecomBerLinePreFecPast15StatHistoryPort1Entry OBJECT-TYPE
	SYNTAX Pm20002maPerfTelecomBerLinePreFecPast15StatHistoryPort1Entry
	MAX-ACCESS not-accessible
	STATUS current
	DESCRIPTION
        "
        Row definition for the pm20002maPerfTelecomBerLinePreFecPast15StatHistory
        table
        "
	INDEX   { pm20002maPerfTelecomBerLinePreFecPast15StatHistoryPort1Index }
	::= { pm20002maPerfTelecomBerLinePreFecPast15StatHistoryPort1Table 1 }


Pm20002maPerfTelecomBerLinePreFecPast15StatHistoryPort1Entry ::=
	SEQUENCE {
	pm20002maPerfTelecomBerLinePreFecPast15StatHistoryPort1Index
		INTEGER,
	pm20002maPerfTelecomBerLinePreFecPast15StatHistoryInvBerPort1
		EkiOnOff,
	pm20002maPerfTelecomBerLinePreFecPast15StatHistoryBerValuePort1
		Unsigned32,
	pm20002maPerfTelecomBerLinePreFecPast15StatHistoryInvMinBerPort1
		EkiOnOff,
	pm20002maPerfTelecomBerLinePreFecPast15StatHistoryMinBerValuePort1
		Unsigned32,
	pm20002maPerfTelecomBerLinePreFecPast15StatHistoryInvMaxBerPort1
		EkiOnOff,
	pm20002maPerfTelecomBerLinePreFecPast15StatHistoryMaxBerValuePort1
		Unsigned32
	}


pm20002maPerfTelecomBerLinePreFecPast15StatHistoryPort1Index OBJECT-TYPE
	SYNTAX  INTEGER(0..128)
	MAX-ACCESS  read-only
	STATUS current
	DESCRIPTION
        "
        Index definition for the pm20002maPerfTelecomBerLinePreFecPast15StatHistory
        table
        "
	::= { pm20002maPerfTelecomBerLinePreFecPast15StatHistoryPort1Entry 1 }


pm20002maPerfTelecomBerLinePreFecPast15StatHistoryInvBerPort1 OBJECT-TYPE
	SYNTAX  EkiOnOff
	MAX-ACCESS read-only
	STATUS current
	DESCRIPTION
        "
        Previous 15-min BER counter inv.
        :This OID indicates that the previous
        15-min Coding Violation counter
        is invalid
        "
	::= { pm20002maPerfTelecomBerLinePreFecPast15StatHistoryPort1Entry 2 }


pm20002maPerfTelecomBerLinePreFecPast15StatHistoryBerValuePort1 OBJECT-TYPE
	SYNTAX  Unsigned32
	MAX-ACCESS read-only
	STATUS current
	DESCRIPTION
        "
        Previous 15-min BER counter :This
        OID gives the previous 15-min Coding
        Violation counter value
        "
	::= { pm20002maPerfTelecomBerLinePreFecPast15StatHistoryPort1Entry 3 }


pm20002maPerfTelecomBerLinePreFecPast15StatHistoryInvMinBerPort1 OBJECT-TYPE
	SYNTAX  EkiOnOff
	MAX-ACCESS read-only
	STATUS current
	DESCRIPTION
        "
        Previous 15-min MinBER counter
        inv. :This OID indicates that the
        previous 15-min Errored Second
         counter is invalid
        "
	::= { pm20002maPerfTelecomBerLinePreFecPast15StatHistoryPort1Entry 4 }


pm20002maPerfTelecomBerLinePreFecPast15StatHistoryMinBerValuePort1 OBJECT-TYPE
	SYNTAX  Unsigned32
	MAX-ACCESS read-only
	STATUS current
	DESCRIPTION
        "
        Previous 15-min MinBER counter
        :This OID gives the previous 15-min
        Errored Second counter value
        "
	::= { pm20002maPerfTelecomBerLinePreFecPast15StatHistoryPort1Entry 5 }


pm20002maPerfTelecomBerLinePreFecPast15StatHistoryInvMaxBerPort1 OBJECT-TYPE
	SYNTAX  EkiOnOff
	MAX-ACCESS read-only
	STATUS current
	DESCRIPTION
        "
        Previous 15-min MaxBER counter
        inv. :This OID indicates that the
        previous 15-min severely Errored
        Second counter is invalid
        "
	::= { pm20002maPerfTelecomBerLinePreFecPast15StatHistoryPort1Entry 6 }


pm20002maPerfTelecomBerLinePreFecPast15StatHistoryMaxBerValuePort1 OBJECT-TYPE
	SYNTAX  Unsigned32
	MAX-ACCESS read-only
	STATUS current
	DESCRIPTION
        "
        Previous 15-min MaxBER counter
        :This OID gives the previous 15-min
        severely Errored Second counter
        value
        "
	::= { pm20002maPerfTelecomBerLinePreFecPast15StatHistoryPort1Entry 7 }


--- *****************************************************
---     Leaf of the telecomBerLinePreFecCurrent24Stat
--- *****************************************************
--- *********************************************************
---     TABLE for the pm20002maPerfTelecomBerLinePreFecCurrent24Stat articles
--- *********************************************************

pm20002maPerfTelecomBerLinePreFecCurrent24StatTable OBJECT-TYPE
	SYNTAX  SEQUENCE OF Pm20002maPerfTelecomBerLinePreFecCurrent24StatEntry
	MAX-ACCESS not-accessible
	STATUS current
	DESCRIPTION
        "
        List of pm20002maPerfTelecomBerLinePreFecCurrent24Stat
        Article
        "
	::= { pm20002maMonPerfLine 354 }


pm20002maPerfTelecomBerLinePreFecCurrent24StatEntry OBJECT-TYPE
	SYNTAX Pm20002maPerfTelecomBerLinePreFecCurrent24StatEntry
	MAX-ACCESS not-accessible
	STATUS current
	DESCRIPTION
        "
        Row definition for the pm20002maPerfTelecomBerLinePreFecCurrent24Stat
        table
        "
	INDEX   { pm20002maPerfTelecomBerLinePreFecCurrent24StatIndex }
	::= { pm20002maPerfTelecomBerLinePreFecCurrent24StatTable 1 }


Pm20002maPerfTelecomBerLinePreFecCurrent24StatEntry ::=
	SEQUENCE {
	pm20002maPerfTelecomBerLinePreFecCurrent24StatIndex
		INTEGER,
	pm20002maPerfTelecomBerLinePreFecCurrent24StatInvBerPortn
		EkiOnOff,
	pm20002maPerfTelecomBerLinePreFecCurrent24StatBerValuePortn
		Unsigned32,
	pm20002maPerfTelecomBerLinePreFecCurrent24StatInvMinBerPortn
		EkiOnOff,
	pm20002maPerfTelecomBerLinePreFecCurrent24StatMinBerValuePortn
		Unsigned32,
	pm20002maPerfTelecomBerLinePreFecCurrent24StatInvMaxBerPortn
		EkiOnOff,
	pm20002maPerfTelecomBerLinePreFecCurrent24StatMaxBerValuePortn
		Unsigned32
	}


pm20002maPerfTelecomBerLinePreFecCurrent24StatIndex OBJECT-TYPE
	SYNTAX  INTEGER(0..128)
	MAX-ACCESS  read-only
	STATUS current
	DESCRIPTION
        "
        Index definition for the pm20002maPerfTelecomBerLinePreFecCurrent24Stat
        table
        "
	::= { pm20002maPerfTelecomBerLinePreFecCurrent24StatEntry 1 }


pm20002maPerfTelecomBerLinePreFecCurrent24StatInvBerPortn OBJECT-TYPE
	SYNTAX  EkiOnOff
	MAX-ACCESS read-only
	STATUS current
	DESCRIPTION
        "
        Current 24-hours BER counter inv.
        :This OID indicates that the current
        24-hours Coding Violation counter
        is invalid
        "
	::= { pm20002maPerfTelecomBerLinePreFecCurrent24StatEntry 2 }


pm20002maPerfTelecomBerLinePreFecCurrent24StatBerValuePortn OBJECT-TYPE
	SYNTAX  Unsigned32
	MAX-ACCESS read-only
	STATUS current
	DESCRIPTION
        "
        Current 24-hours BER counter :This
        OID gives the current 24-hours
         Coding Violation counter value
        "
	::= { pm20002maPerfTelecomBerLinePreFecCurrent24StatEntry 3 }


pm20002maPerfTelecomBerLinePreFecCurrent24StatInvMinBerPortn OBJECT-TYPE
	SYNTAX  EkiOnOff
	MAX-ACCESS read-only
	STATUS current
	DESCRIPTION
        "
        Current 24-hoursMinBER counter
        inv. :This OID indicates that the
        current 24-hours Errored Second
        counter is invalid
        "
	::= { pm20002maPerfTelecomBerLinePreFecCurrent24StatEntry 4 }


pm20002maPerfTelecomBerLinePreFecCurrent24StatMinBerValuePortn OBJECT-TYPE
	SYNTAX  Unsigned32
	MAX-ACCESS read-only
	STATUS current
	DESCRIPTION
        "
        Current 24-hours MinBER counter
        :This OID gives the current 24-hours
        Errored Second counter value
        "
	::= { pm20002maPerfTelecomBerLinePreFecCurrent24StatEntry 5 }


pm20002maPerfTelecomBerLinePreFecCurrent24StatInvMaxBerPortn OBJECT-TYPE
	SYNTAX  EkiOnOff
	MAX-ACCESS read-only
	STATUS current
	DESCRIPTION
        "
        Current 24-hours MaxBER counter
        inv. :This OID indicates that the
        current 24-hours severely Errored
        Second counter is invalid
        "
	::= { pm20002maPerfTelecomBerLinePreFecCurrent24StatEntry 6 }


pm20002maPerfTelecomBerLinePreFecCurrent24StatMaxBerValuePortn OBJECT-TYPE
	SYNTAX  Unsigned32
	MAX-ACCESS read-only
	STATUS current
	DESCRIPTION
        "
        Current 24-hours MaxBER counter
        :This OID gives the current 24-hours
        severely Errored Second counter
        value
        "
	::= { pm20002maPerfTelecomBerLinePreFecCurrent24StatEntry 7 }


--- *****************************************************
---     Leaf of the telecomBerLinePreFecPast24Stat
--- *****************************************************
--- *********************************************************
---     TABLE for the pm20002maPerfTelecomBerLinePreFecPast24StatHistory articles
--- *********************************************************

pm20002maPerfTelecomBerLinePreFecPast24StatHistoryPort1Table OBJECT-TYPE
	SYNTAX  SEQUENCE OF Pm20002maPerfTelecomBerLinePreFecPast24StatHistoryPort1Entry
	MAX-ACCESS not-accessible
	STATUS current
	DESCRIPTION
        "
        List of pm20002maPerfTelecomBerLinePreFecPast24StatHistory
        Article
        "
	::= { pm20002maMonPerfLine 355 }


pm20002maPerfTelecomBerLinePreFecPast24StatHistoryPort1Entry OBJECT-TYPE
	SYNTAX Pm20002maPerfTelecomBerLinePreFecPast24StatHistoryPort1Entry
	MAX-ACCESS not-accessible
	STATUS current
	DESCRIPTION
        "
        Row definition for the pm20002maPerfTelecomBerLinePreFecPast24StatHistory
        table
        "
	INDEX   { pm20002maPerfTelecomBerLinePreFecPast24StatHistoryPort1Index }
	::= { pm20002maPerfTelecomBerLinePreFecPast24StatHistoryPort1Table 1 }


Pm20002maPerfTelecomBerLinePreFecPast24StatHistoryPort1Entry ::=
	SEQUENCE {
	pm20002maPerfTelecomBerLinePreFecPast24StatHistoryPort1Index
		INTEGER,
	pm20002maPerfTelecomBerLinePreFecPast24StatHistoryInvBerPort1
		EkiOnOff,
	pm20002maPerfTelecomBerLinePreFecPast24StatHistoryBerValuePort1
		Unsigned32,
	pm20002maPerfTelecomBerLinePreFecPast24StatHistoryInvMinBerPort1
		EkiOnOff,
	pm20002maPerfTelecomBerLinePreFecPast24StatHistoryMinBerValuePort1
		Unsigned32,
	pm20002maPerfTelecomBerLinePreFecPast24StatHistoryInvMaxBerPort1
		EkiOnOff,
	pm20002maPerfTelecomBerLinePreFecPast24StatHistoryMaxBerValuePort1
		Unsigned32
	}


pm20002maPerfTelecomBerLinePreFecPast24StatHistoryPort1Index OBJECT-TYPE
	SYNTAX  INTEGER(0..128)
	MAX-ACCESS  read-only
	STATUS current
	DESCRIPTION
        "
        Index definition for the pm20002maPerfTelecomBerLinePreFecPast24StatHistory
        table
        "
	::= { pm20002maPerfTelecomBerLinePreFecPast24StatHistoryPort1Entry 1 }


pm20002maPerfTelecomBerLinePreFecPast24StatHistoryInvBerPort1 OBJECT-TYPE
	SYNTAX  EkiOnOff
	MAX-ACCESS read-only
	STATUS current
	DESCRIPTION
        "
        Previous 24-hours BER counter
         inv. :This OID indicates that
         the previous 24-hours Coding Violation
        counter is invalid
        "
	::= { pm20002maPerfTelecomBerLinePreFecPast24StatHistoryPort1Entry 2 }


pm20002maPerfTelecomBerLinePreFecPast24StatHistoryBerValuePort1 OBJECT-TYPE
	SYNTAX  Unsigned32
	MAX-ACCESS read-only
	STATUS current
	DESCRIPTION
        "
        Previous 24-hours BER counter
         :This OID gives the previous 24-hours
        Coding Violation counter value
        "
	::= { pm20002maPerfTelecomBerLinePreFecPast24StatHistoryPort1Entry 3 }


pm20002maPerfTelecomBerLinePreFecPast24StatHistoryInvMinBerPort1 OBJECT-TYPE
	SYNTAX  EkiOnOff
	MAX-ACCESS read-only
	STATUS current
	DESCRIPTION
        "
        Previous 24-hours MinBER counter
        inv. :This OID indicates that the
        previous 24-hours Errored Second
        counter is invalid
        "
	::= { pm20002maPerfTelecomBerLinePreFecPast24StatHistoryPort1Entry 4 }


pm20002maPerfTelecomBerLinePreFecPast24StatHistoryMinBerValuePort1 OBJECT-TYPE
	SYNTAX  Unsigned32
	MAX-ACCESS read-only
	STATUS current
	DESCRIPTION
        "
        Previous 24-hours MinBER counter
        :This OID gives the previous 24-hours
        Errored Second counter value
        "
	::= { pm20002maPerfTelecomBerLinePreFecPast24StatHistoryPort1Entry 5 }


pm20002maPerfTelecomBerLinePreFecPast24StatHistoryInvMaxBerPort1 OBJECT-TYPE
	SYNTAX  EkiOnOff
	MAX-ACCESS read-only
	STATUS current
	DESCRIPTION
        "
        Previous 24-hours MaxBER counter
        inv. :This OID indicates that the
        previous 24-hours severely Errored
        Second counter is invalid
        "
	::= { pm20002maPerfTelecomBerLinePreFecPast24StatHistoryPort1Entry 6 }


pm20002maPerfTelecomBerLinePreFecPast24StatHistoryMaxBerValuePort1 OBJECT-TYPE
	SYNTAX  Unsigned32
	MAX-ACCESS read-only
	STATUS current
	DESCRIPTION
        "
        Previous 24-hours MaxBER counter
        :This OID gives the previous 24-hours
        severely Errored Second counter
        value
        "
	::= { pm20002maPerfTelecomBerLinePreFecPast24StatHistoryPort1Entry 7 }


--- *****************************************************
---     Leaf of the datacomClientCurrent15Stat
--- *****************************************************
--- *********************************************************
---     TABLE for the pm20002maPerfDatacomClientCurrent15Stat articles
--- *********************************************************

pm20002maPerfDatacomClientCurrent15StatTable OBJECT-TYPE
	SYNTAX  SEQUENCE OF Pm20002maPerfDatacomClientCurrent15StatEntry
	MAX-ACCESS not-accessible
	STATUS current
	DESCRIPTION
        "
        List of pm20002maPerfDatacomClientCurrent15Stat
        Article
        "
	::= { pm20002maMonPerfClient 848 }


pm20002maPerfDatacomClientCurrent15StatEntry OBJECT-TYPE
	SYNTAX Pm20002maPerfDatacomClientCurrent15StatEntry
	MAX-ACCESS not-accessible
	STATUS current
	DESCRIPTION
        "
        Row definition for the pm20002maPerfDatacomClientCurrent15Stat
        table
        "
	INDEX   { pm20002maPerfDatacomClientCurrent15StatIndex }
	::= { pm20002maPerfDatacomClientCurrent15StatTable 1 }


Pm20002maPerfDatacomClientCurrent15StatEntry ::=
	SEQUENCE {
	pm20002maPerfDatacomClientCurrent15StatIndex
		INTEGER,
	pm20002maperfdatacomclientCurrent15StatOutPacketCountInvPortn
		EkiOnOff,
	pm20002maperfdatacomclientCurrent15StatOutPacketCountPortn
		Counter64,
	pm20002maperfdatacomclientCurrent15StatOutCrcCountInvPortn
		EkiOnOff,
	pm20002maperfdatacomclientCurrent15StatOutCrcCountPortn
		Counter64,
	pm20002maperfdatacomclientCurrent15StatInPacketCountInvPortn
		EkiOnOff,
	pm20002maperfdatacomclientCurrent15StatInPacketCountPortn
		Counter64,
	pm20002maperfdatacomclientCurrent15StatInCrcCountInvPortn
		EkiOnOff,
	pm20002maperfdatacomclientCurrent15StatInCrcCountPortn
		Counter64
	}


pm20002maPerfDatacomClientCurrent15StatIndex OBJECT-TYPE
	SYNTAX  INTEGER(0..128)
	MAX-ACCESS  read-only
	STATUS current
	DESCRIPTION
        "
        Index definition for the pm20002maPerfDatacomClientCurrent15Stat
        table
        "
	::= { pm20002maPerfDatacomClientCurrent15StatEntry 1 }


pm20002maperfdatacomclientCurrent15StatOutPacketCountInvPortn OBJECT-TYPE
	SYNTAX  EkiOnOff
	MAX-ACCESS read-only
	STATUS current
	DESCRIPTION
        "
        Client Current 15-min Output Packet
        counter inv. :This OID indicates
        that the current 15-min Output
         Packets counter is invalid
        "
	::= { pm20002maPerfDatacomClientCurrent15StatEntry 30 }


pm20002maperfdatacomclientCurrent15StatOutPacketCountPortn OBJECT-TYPE
	SYNTAX  Counter64
	MAX-ACCESS read-only
	STATUS current
	DESCRIPTION
        "
        Client Current 15-min Output Packet
        counter :This OID gives the current
        15-min Output Packets counter value
        "
	::= { pm20002maPerfDatacomClientCurrent15StatEntry 31 }


pm20002maperfdatacomclientCurrent15StatOutCrcCountInvPortn OBJECT-TYPE
	SYNTAX  EkiOnOff
	MAX-ACCESS read-only
	STATUS current
	DESCRIPTION
        "
        Client Current 15-min Output CRC
        counter inv. :This OID indicates
        that the current 15-min Output
         CRC counter is invalid
        "
	::= { pm20002maPerfDatacomClientCurrent15StatEntry 28 }


pm20002maperfdatacomclientCurrent15StatOutCrcCountPortn OBJECT-TYPE
	SYNTAX  Counter64
	MAX-ACCESS read-only
	STATUS current
	DESCRIPTION
        "
        Client Current 15-min Output CRC
        counter :This OID gives the current
        15-min Output CRC counter value
        "
	::= { pm20002maPerfDatacomClientCurrent15StatEntry 29 }


pm20002maperfdatacomclientCurrent15StatInPacketCountInvPortn OBJECT-TYPE
	SYNTAX  EkiOnOff
	MAX-ACCESS read-only
	STATUS current
	DESCRIPTION
        "
        Client Current 15-min Input Packet
        counter inv. :This OID indicates
        that the current 15-min Input Packet
        counter is invalid
        "
	::= { pm20002maPerfDatacomClientCurrent15StatEntry 6 }


pm20002maperfdatacomclientCurrent15StatInPacketCountPortn OBJECT-TYPE
	SYNTAX  Counter64
	MAX-ACCESS read-only
	STATUS current
	DESCRIPTION
        "
        Client Current 15-min Input Packet
        counter :This OID gives the current
        15-min Input Packet counter value
        "
	::= { pm20002maPerfDatacomClientCurrent15StatEntry 7 }


pm20002maperfdatacomclientCurrent15StatInCrcCountInvPortn OBJECT-TYPE
	SYNTAX  EkiOnOff
	MAX-ACCESS read-only
	STATUS current
	DESCRIPTION
        "
        Client Current 15-min Input CRC
        counter inv. :This OID indicates
        that the current 15-min Input CRC
        counter is invalid
        "
	::= { pm20002maPerfDatacomClientCurrent15StatEntry 4 }


pm20002maperfdatacomclientCurrent15StatInCrcCountPortn OBJECT-TYPE
	SYNTAX  Counter64
	MAX-ACCESS read-only
	STATUS current
	DESCRIPTION
        "
        Client Current 15-min Input CRC
        counter :This OID gives the current
        15-min Input CRC counter value
        "
	::= { pm20002maPerfDatacomClientCurrent15StatEntry 5 }


--- *****************************************************
---     Leaf of the datacomClientPast15Stat
--- *****************************************************
--- *********************************************************
---     TABLE for the pm20002maPerfDatacomClientPast15StatHistory articles
--- *********************************************************

pm20002maPerfDatacomClientPast15StatHistoryPort1Table OBJECT-TYPE
	SYNTAX  SEQUENCE OF Pm20002maPerfDatacomClientPast15StatHistoryPort1Entry
	MAX-ACCESS not-accessible
	STATUS current
	DESCRIPTION
        "
        List of pm20002maPerfDatacomClientPast15StatHistory
        Article
        "
	::= { pm20002maMonPerfClient 880 }


pm20002maPerfDatacomClientPast15StatHistoryPort1Entry OBJECT-TYPE
	SYNTAX Pm20002maPerfDatacomClientPast15StatHistoryPort1Entry
	MAX-ACCESS not-accessible
	STATUS current
	DESCRIPTION
        "
        Row definition for the pm20002maPerfDatacomClientPast15StatHistory
        table
        "
	INDEX   { pm20002maPerfDatacomClientPast15StatHistoryPort1Index }
	::= { pm20002maPerfDatacomClientPast15StatHistoryPort1Table 1 }


Pm20002maPerfDatacomClientPast15StatHistoryPort1Entry ::=
	SEQUENCE {
	pm20002maPerfDatacomClientPast15StatHistoryPort1Index
		INTEGER,
	pm20002maperfdatacomclientPast15StatOutPacketCountInvPort1
		EkiOnOff,
	pm20002maperfdatacomclientPast15StatOutPacketCountPort1
		Counter64,
	pm20002maperfdatacomclientPast15StatOutCrcCountInvPort1
		EkiOnOff,
	pm20002maperfdatacomclientPast15StatOutCrcCountPort1
		Counter64,
	pm20002maperfdatacomclientPast15StatInPacketCountInvPort1
		EkiOnOff,
	pm20002maperfdatacomclientPast15StatInPacketCountPort1
		Counter64,
	pm20002maperfdatacomclientPast15StatInCrcCountInvPort1
		EkiOnOff,
	pm20002maperfdatacomclientPast15StatInCrcCountPort1
		Counter64
	}


pm20002maPerfDatacomClientPast15StatHistoryPort1Index OBJECT-TYPE
	SYNTAX  INTEGER(0..128)
	MAX-ACCESS  read-only
	STATUS current
	DESCRIPTION
        "
        Index definition for the pm20002maPerfDatacomClientPast15StatHistory
        table
        "
	::= { pm20002maPerfDatacomClientPast15StatHistoryPort1Entry 1 }


pm20002maperfdatacomclientPast15StatOutPacketCountInvPort1 OBJECT-TYPE
	SYNTAX  EkiOnOff
	MAX-ACCESS read-only
	STATUS current
	DESCRIPTION
        "
        Client Past 15-min Output Packet
        counter inv. :This OID indicates
        that the past 15-min Output Packets
        counter is invalid
        "
	::= { pm20002maPerfDatacomClientPast15StatHistoryPort1Entry 30 }


pm20002maperfdatacomclientPast15StatOutPacketCountPort1 OBJECT-TYPE
	SYNTAX  Counter64
	MAX-ACCESS read-only
	STATUS current
	DESCRIPTION
        "
        Client Past 15-min Output Packet
        counter :This OID gives the past
        15-min Output Packets counter value
        "
	::= { pm20002maPerfDatacomClientPast15StatHistoryPort1Entry 31 }


pm20002maperfdatacomclientPast15StatOutCrcCountInvPort1 OBJECT-TYPE
	SYNTAX  EkiOnOff
	MAX-ACCESS read-only
	STATUS current
	DESCRIPTION
        "
        Client Past 15-min Output CRC
         counter inv. :This OID indicates
        that the past 15-min Output CRC
        counter is invalid
        "
	::= { pm20002maPerfDatacomClientPast15StatHistoryPort1Entry 28 }


pm20002maperfdatacomclientPast15StatOutCrcCountPort1 OBJECT-TYPE
	SYNTAX  Counter64
	MAX-ACCESS read-only
	STATUS current
	DESCRIPTION
        "
        Client Past 15-min Output CRC
         counter :This OID gives the past
        15-min Output CRC counter value
        "
	::= { pm20002maPerfDatacomClientPast15StatHistoryPort1Entry 29 }


pm20002maperfdatacomclientPast15StatInPacketCountInvPort1 OBJECT-TYPE
	SYNTAX  EkiOnOff
	MAX-ACCESS read-only
	STATUS current
	DESCRIPTION
        "
        Client Past 15-min Input Packet
        counter inv. :This OID indicates
        that the past 15-min Input Packet
        counter is invalid
        "
	::= { pm20002maPerfDatacomClientPast15StatHistoryPort1Entry 6 }


pm20002maperfdatacomclientPast15StatInPacketCountPort1 OBJECT-TYPE
	SYNTAX  Counter64
	MAX-ACCESS read-only
	STATUS current
	DESCRIPTION
        "
        Client Past 15-min Input Packet
        counter :This OID gives the past
        15-min Input Packet counter value
        "
	::= { pm20002maPerfDatacomClientPast15StatHistoryPort1Entry 7 }


pm20002maperfdatacomclientPast15StatInCrcCountInvPort1 OBJECT-TYPE
	SYNTAX  EkiOnOff
	MAX-ACCESS read-only
	STATUS current
	DESCRIPTION
        "
        Client Past 15-min Input CRC counter
        inv. :This OID indicates that the
        past 15-min Input CRC counter is
        invalid
        "
	::= { pm20002maPerfDatacomClientPast15StatHistoryPort1Entry 4 }


pm20002maperfdatacomclientPast15StatInCrcCountPort1 OBJECT-TYPE
	SYNTAX  Counter64
	MAX-ACCESS read-only
	STATUS current
	DESCRIPTION
        "
        Client Past 15-min Input CRC counter
        :This OID gives the past 15-min
        Input CRC counter value
        "
	::= { pm20002maPerfDatacomClientPast15StatHistoryPort1Entry 5 }


--- *****************************************************
---     Leaf of the datacomClientCurrent24Stat
--- *****************************************************
--- *********************************************************
---     TABLE for the pm20002maPerfDatacomClientCurrent24Stat articles
--- *********************************************************

pm20002maPerfDatacomClientCurrent24StatTable OBJECT-TYPE
	SYNTAX  SEQUENCE OF Pm20002maPerfDatacomClientCurrent24StatEntry
	MAX-ACCESS not-accessible
	STATUS current
	DESCRIPTION
        "
        List of pm20002maPerfDatacomClientCurrent24Stat
        Article
        "
	::= { pm20002maMonPerfClient 912 }


pm20002maPerfDatacomClientCurrent24StatEntry OBJECT-TYPE
	SYNTAX Pm20002maPerfDatacomClientCurrent24StatEntry
	MAX-ACCESS not-accessible
	STATUS current
	DESCRIPTION
        "
        Row definition for the pm20002maPerfDatacomClientCurrent24Stat
        table
        "
	INDEX   { pm20002maPerfDatacomClientCurrent24StatIndex }
	::= { pm20002maPerfDatacomClientCurrent24StatTable 1 }


Pm20002maPerfDatacomClientCurrent24StatEntry ::=
	SEQUENCE {
	pm20002maPerfDatacomClientCurrent24StatIndex
		INTEGER,
	pm20002maperfdatacomclientCurrent24StatOutPacketCountInvPortn
		EkiOnOff,
	pm20002maperfdatacomclientCurrent24StatOutPacketCountPortn
		Counter64,
	pm20002maperfdatacomclientCurrent24StatOutCrcCountInvPortn
		EkiOnOff,
	pm20002maperfdatacomclientCurrent24StatOutCrcCountPortn
		Counter64,
	pm20002maperfdatacomclientCurrent24StatInPacketCountInvPortn
		EkiOnOff,
	pm20002maperfdatacomclientCurrent24StatInPacketCountPortn
		Counter64,
	pm20002maperfdatacomclientCurrent24StatInCrcCountInvPortn
		EkiOnOff,
	pm20002maperfdatacomclientCurrent24StatInCrcCountPortn
		Counter64
	}


pm20002maPerfDatacomClientCurrent24StatIndex OBJECT-TYPE
	SYNTAX  INTEGER(0..128)
	MAX-ACCESS  read-only
	STATUS current
	DESCRIPTION
        "
        Index definition for the pm20002maPerfDatacomClientCurrent24Stat
        table
        "
	::= { pm20002maPerfDatacomClientCurrent24StatEntry 1 }


pm20002maperfdatacomclientCurrent24StatOutPacketCountInvPortn OBJECT-TYPE
	SYNTAX  EkiOnOff
	MAX-ACCESS read-only
	STATUS current
	DESCRIPTION
        "
        Client Current 24-hours Output
        Packet counter inv. :This OID indicates
        that the current 24-hours Output
        Packets counter is invalid
        "
	::= { pm20002maPerfDatacomClientCurrent24StatEntry 30 }


pm20002maperfdatacomclientCurrent24StatOutPacketCountPortn OBJECT-TYPE
	SYNTAX  Counter64
	MAX-ACCESS read-only
	STATUS current
	DESCRIPTION
        "
        Client Current 24-hours Output
        Packet counter :This OID gives
         the current 24-hours Output Packets
        counter value
        "
	::= { pm20002maPerfDatacomClientCurrent24StatEntry 31 }


pm20002maperfdatacomclientCurrent24StatOutCrcCountInvPortn OBJECT-TYPE
	SYNTAX  EkiOnOff
	MAX-ACCESS read-only
	STATUS current
	DESCRIPTION
        "
        Client Current 24-hours Output
        CRC counter inv. :This OID indicates
        that the current 24-hours Output
        CRC counter is invalid
        "
	::= { pm20002maPerfDatacomClientCurrent24StatEntry 28 }


pm20002maperfdatacomclientCurrent24StatOutCrcCountPortn OBJECT-TYPE
	SYNTAX  Counter64
	MAX-ACCESS read-only
	STATUS current
	DESCRIPTION
        "
        Client Current 24-hours Output
        CRC counter :This OID gives the
        current 24-hours Output CRC counter
        value
        "
	::= { pm20002maPerfDatacomClientCurrent24StatEntry 29 }


pm20002maperfdatacomclientCurrent24StatInPacketCountInvPortn OBJECT-TYPE
	SYNTAX  EkiOnOff
	MAX-ACCESS read-only
	STATUS current
	DESCRIPTION
        "
        Client Current 24-hours Input
         Packet counter inv. :This OID
         indicates that the current 24-hours
        Input Packet counter is invalid
        "
	::= { pm20002maPerfDatacomClientCurrent24StatEntry 6 }


pm20002maperfdatacomclientCurrent24StatInPacketCountPortn OBJECT-TYPE
	SYNTAX  Counter64
	MAX-ACCESS read-only
	STATUS current
	DESCRIPTION
        "
        Client Current 24-hours Input
         Packet counter :This OID gives
        the current 24-hours Input Packet
        counter value
        "
	::= { pm20002maPerfDatacomClientCurrent24StatEntry 7 }


pm20002maperfdatacomclientCurrent24StatInCrcCountInvPortn OBJECT-TYPE
	SYNTAX  EkiOnOff
	MAX-ACCESS read-only
	STATUS current
	DESCRIPTION
        "
        Client Current 24-hours Input
         CRC counter inv. :This OID indicates
        that the current 24-hours Input
        CRC counter is invalid
        "
	::= { pm20002maPerfDatacomClientCurrent24StatEntry 4 }


pm20002maperfdatacomclientCurrent24StatInCrcCountPortn OBJECT-TYPE
	SYNTAX  Counter64
	MAX-ACCESS read-only
	STATUS current
	DESCRIPTION
        "
        Client Current 24-hours Input
         CRC counter :This OID gives the
        current 24-hours Input CRC counter
        value
        "
	::= { pm20002maPerfDatacomClientCurrent24StatEntry 5 }


--- *****************************************************
---     Leaf of the datacomClientPast24Stat
--- *****************************************************
--- *********************************************************
---     TABLE for the pm20002maPerfDatacomClientPast24StatHistory articles
--- *********************************************************

pm20002maPerfDatacomClientPast24StatHistoryPort1Table OBJECT-TYPE
	SYNTAX  SEQUENCE OF Pm20002maPerfDatacomClientPast24StatHistoryPort1Entry
	MAX-ACCESS not-accessible
	STATUS current
	DESCRIPTION
        "
        List of pm20002maPerfDatacomClientPast24StatHistory
        Article
        "
	::= { pm20002maMonPerfClient 944 }


pm20002maPerfDatacomClientPast24StatHistoryPort1Entry OBJECT-TYPE
	SYNTAX Pm20002maPerfDatacomClientPast24StatHistoryPort1Entry
	MAX-ACCESS not-accessible
	STATUS current
	DESCRIPTION
        "
        Row definition for the pm20002maPerfDatacomClientPast24StatHistory
        table
        "
	INDEX   { pm20002maPerfDatacomClientPast24StatHistoryPort1Index }
	::= { pm20002maPerfDatacomClientPast24StatHistoryPort1Table 1 }


Pm20002maPerfDatacomClientPast24StatHistoryPort1Entry ::=
	SEQUENCE {
	pm20002maPerfDatacomClientPast24StatHistoryPort1Index
		INTEGER,
	pm20002maperfdatacomclientPast24StatOutPacketCountInvPort1
		EkiOnOff,
	pm20002maperfdatacomclientPast24StatOutPacketCountPort1
		Counter64,
	pm20002maperfdatacomclientPast24StatOutCrcCountInvPort1
		EkiOnOff,
	pm20002maperfdatacomclientPast24StatOutCrcCountPort1
		Counter64,
	pm20002maperfdatacomclientPast24StatInPacketCountInvPort1
		EkiOnOff,
	pm20002maperfdatacomclientPast24StatInPacketCountPort1
		Counter64,
	pm20002maperfdatacomclientPast24StatInCrcCountInvPort1
		EkiOnOff,
	pm20002maperfdatacomclientPast24StatInCrcCountPort1
		Counter64
	}


pm20002maPerfDatacomClientPast24StatHistoryPort1Index OBJECT-TYPE
	SYNTAX  INTEGER(0..128)
	MAX-ACCESS  read-only
	STATUS current
	DESCRIPTION
        "
        Index definition for the pm20002maPerfDatacomClientPast24StatHistory
        table
        "
	::= { pm20002maPerfDatacomClientPast24StatHistoryPort1Entry 1 }


pm20002maperfdatacomclientPast24StatOutPacketCountInvPort1 OBJECT-TYPE
	SYNTAX  EkiOnOff
	MAX-ACCESS read-only
	STATUS current
	DESCRIPTION
        "
        Client Past 24-hours Output Packet
        counter inv. :This OID indicates
        that the past 24-hours Output Packets
        counter is invalid
        "
	::= { pm20002maPerfDatacomClientPast24StatHistoryPort1Entry 30 }


pm20002maperfdatacomclientPast24StatOutPacketCountPort1 OBJECT-TYPE
	SYNTAX  Counter64
	MAX-ACCESS read-only
	STATUS current
	DESCRIPTION
        "
        Client Past 24-hours Output Packet
        counter :This OID gives the past
        24-hours Output Packets counter
        value
        "
	::= { pm20002maPerfDatacomClientPast24StatHistoryPort1Entry 31 }


pm20002maperfdatacomclientPast24StatOutCrcCountInvPort1 OBJECT-TYPE
	SYNTAX  EkiOnOff
	MAX-ACCESS read-only
	STATUS current
	DESCRIPTION
        "
        Client Past 24-hours Output CRC
        counter inv. :This OID indicates
        that the past 24-hours Output CRC
        counter is invalid
        "
	::= { pm20002maPerfDatacomClientPast24StatHistoryPort1Entry 28 }


pm20002maperfdatacomclientPast24StatOutCrcCountPort1 OBJECT-TYPE
	SYNTAX  Counter64
	MAX-ACCESS read-only
	STATUS current
	DESCRIPTION
        "
        Client Past 24-hours Output CRC
        counter :This OID gives the past
        24-hours Output CRC counter value
        "
	::= { pm20002maPerfDatacomClientPast24StatHistoryPort1Entry 29 }


pm20002maperfdatacomclientPast24StatInPacketCountInvPort1 OBJECT-TYPE
	SYNTAX  EkiOnOff
	MAX-ACCESS read-only
	STATUS current
	DESCRIPTION
        "
        Client Past 24-hours Input Packet
        counter inv. :This OID indicates
        that the past 24-hours Input Packet
        counter is invalid
        "
	::= { pm20002maPerfDatacomClientPast24StatHistoryPort1Entry 6 }


pm20002maperfdatacomclientPast24StatInPacketCountPort1 OBJECT-TYPE
	SYNTAX  Counter64
	MAX-ACCESS read-only
	STATUS current
	DESCRIPTION
        "
        Client Past 24-hours Input Packet
        counter :This OID gives the past
        24-hours Input Packet counter value
        "
	::= { pm20002maPerfDatacomClientPast24StatHistoryPort1Entry 7 }


pm20002maperfdatacomclientPast24StatInCrcCountInvPort1 OBJECT-TYPE
	SYNTAX  EkiOnOff
	MAX-ACCESS read-only
	STATUS current
	DESCRIPTION
        "
        Client Past 24-hours Input CRC
        counter inv. :This OID indicates
        that the past 24-hours Input CRC
        counter is invalid
        "
	::= { pm20002maPerfDatacomClientPast24StatHistoryPort1Entry 4 }


pm20002maperfdatacomclientPast24StatInCrcCountPort1 OBJECT-TYPE
	SYNTAX  Counter64
	MAX-ACCESS read-only
	STATUS current
	DESCRIPTION
        "
        Client Past 24-hours Input CRC
        counter :This OID gives the past
        24-hours Input CRC counter value
        "
	::= { pm20002maPerfDatacomClientPast24StatHistoryPort1Entry 5 }



pm20002maPerfEnable OBJECT-TYPE
	SYNTAX EkiOnOff
	MAX-ACCESS read-write
	STATUS current
	DESCRIPTION
        "
        Perf. Mon. Enable :This OID enables
        the Performance Monitoring application
        "
	::= { pm20002maMonPerfSync 257 }


pm20002maPerf15minSync OBJECT-TYPE
	SYNTAX EkiOnOff
	MAX-ACCESS read-write
	STATUS current
	DESCRIPTION
        "
        Perf. Mon. 15-min sync. :This
         OID must be used in external synchronisation
        mode only to send a 15-min synchronisation
        command
        "
	::= { pm20002maMonPerfSync 259 }


pm20002maPerf24hSync OBJECT-TYPE
	SYNTAX EkiOnOff
	MAX-ACCESS read-write
	STATUS current
	DESCRIPTION
        "
        Perf. Mon. 24-hours sync. :This
        OID must be used in external synchronisation
        mode only to send a 24-hours synchronisation
        command
        "
	::= { pm20002maMonPerfSync 260 }


pm20002maPerf15MinShort OBJECT-TYPE
	SYNTAX EkiOnOff
	MAX-ACCESS read-write
	STATUS current
	DESCRIPTION
        "
        15-min period is short :This OID
        indicates that the 15-min period
        lasts less than 890 seconds
        "
	::= { pm20002maMonPerfTimeStamp 1 }


pm20002maPerf15MinLong OBJECT-TYPE
	SYNTAX EkiOnOff
	MAX-ACCESS read-write
	STATUS current
	DESCRIPTION
        "
        15-min period is long :This OID
        indicates that the 15-min period
        lasts more than 910 seconds
        "
	::= { pm20002maMonPerfTimeStamp 2 }


pm20002maPerf24HoursShort OBJECT-TYPE
	SYNTAX Counter32
	MAX-ACCESS read-write
	STATUS current
	DESCRIPTION
        "
        24-hours period is short :This
        OID indicates that 24-hours period
        lasts less than 86390 seconds
        "
	::= { pm20002maMonPerfTimeStamp 5 }


pm20002maPerf24HoursLong OBJECT-TYPE
	SYNTAX Counter32
	MAX-ACCESS read-write
	STATUS current
	DESCRIPTION
        "
        24-hours period is long :This
         OID indicates that 24-hours period
        lasts more than 86410 seconds
        "
	::= { pm20002maMonPerfTimeStamp 6 }


pm20002maPerfCurrent15MinElapsedTime OBJECT-TYPE
	SYNTAX Counter32
	MAX-ACCESS read-write
	STATUS current
	DESCRIPTION
        "
        Current 15min period Elapsed Time
         :This OID gives the number of
         seconds elapsed in the current
        15-minutes period
        "
	::= { pm20002maMonPerfTimeStamp 7 }


pm20002maPerfCurrent24HoursElapsedTime OBJECT-TYPE
	SYNTAX Counter32
	MAX-ACCESS read-write
	STATUS current
	DESCRIPTION
        "
        Current 24hours period Elapsed
        Time :This OID gives the number
        of seconds elapsed in the current
        24-hours period
        "
	::= { pm20002maMonPerfTimeStamp 8 }






--- *****************************************************
--- $$$$$$$$$$$$$$$$$$$$$$$$$$$$$$$$$$$$$$$$$$$$$$$$$$$$$
---     DOWNLOAD
--- $$$$$$$$$$$$$$$$$$$$$$$$$$$$$$$$$$$$$$$$$$$$$$$$$$$$$
--- *****************************************************



--- *****************************************************
---     LEAF for the restartProcess article
--- *****************************************************
pm20002maDwlrestartProcess OBJECT IDENTIFIER ::= { pm20002maDwlOther 0 }




pm20002maDwlColdRestartProcessed OBJECT-TYPE
	  SYNTAX EkiOnOff
	  MAX-ACCESS read-only
	  STATUS current
	  DESCRIPTION
        "
        Cold Restart :This OID indicates
        that the module last restart was
        a Cold RESTART
        "
	  ::= { pm20002maDwlrestartProcess 2 }



pm20002maDwlWarmRestartProcessed OBJECT-TYPE
	  SYNTAX EkiOnOff
	  MAX-ACCESS read-only
	  STATUS current
	  DESCRIPTION
        "
        Warm Restart :This OID indicates
        that the module last restart was
        a Warm RESTART
        "
	  ::= { pm20002maDwlrestartProcess 1 }



--- *****************************************************
---     LEAF for the swBanksUsed article
--- *****************************************************
pm20002maDwlswBanksUsed OBJECT IDENTIFIER ::= { pm20002maDwlOther 1 }




pm20002maDwlSwBank2Notempty OBJECT-TYPE
	  SYNTAX EkiOnOff
	  MAX-ACCESS read-only
	  STATUS current
	  DESCRIPTION
        "
        SW bank 2 loaded :This OID indicates
        a software is loaded in SW bank
        2  <Help>  This status indicates
        if the SW bank 2 contains SW package
        "
	  ::= { pm20002maDwlswBanksUsed 6 }



pm20002maDwlSwBank1Notempty OBJECT-TYPE
	  SYNTAX EkiOnOff
	  MAX-ACCESS read-only
	  STATUS current
	  DESCRIPTION
        "
        SW bank 1 loaded :This OID indicates
        a software is loaded in SW bank
        1  <Help>  This status indicates
        if the SW bank 1 contains SW package
        "
	  ::= { pm20002maDwlswBanksUsed 5 }



pm20002maDwlSwBank2Used OBJECT-TYPE
	  SYNTAX EkiOnOff
	  MAX-ACCESS read-only
	  STATUS current
	  DESCRIPTION
        "
        SW bank 2 active :This OID indicates
        the module is working on SW bank
        2  <Help>  This status indicates
        if the SW bank 2 is active or standby
        "
	  ::= { pm20002maDwlswBanksUsed 2 }



pm20002maDwlSwBank1Used OBJECT-TYPE
	  SYNTAX EkiOnOff
	  MAX-ACCESS read-only
	  STATUS current
	  DESCRIPTION
        "
        SW bank 1 active :This OID indicates
        the module is working on SW bank
        1  <Help>  This status indicates
        if the SW bank 1 is active or standby
        "
	  ::= { pm20002maDwlswBanksUsed 1 }



--- *****************************************************
---     LEAF for the gwBanksUsed article
--- *****************************************************
pm20002maDwlgwBanksUsed OBJECT IDENTIFIER ::= { pm20002maDwlOther 2 }




pm20002maDwlGwBank4Notempty OBJECT-TYPE
	  SYNTAX EkiOnOff
	  MAX-ACCESS read-only
	  STATUS current
	  DESCRIPTION
        "
        GW bank 4 loaded :This OID indicates
        a gateware is loaded in GW bank
        4
        "
	  ::= { pm20002maDwlgwBanksUsed 8 }



pm20002maDwlGwBank3Notempty OBJECT-TYPE
	  SYNTAX EkiOnOff
	  MAX-ACCESS read-only
	  STATUS current
	  DESCRIPTION
        "
        GW bank 3 loaded :This OID indicates
        a gateware is loaded in GW bank
        3  <Help>  This status indicates
        if the GW bank 3 contains GW package
        "
	  ::= { pm20002maDwlgwBanksUsed 7 }



pm20002maDwlGwBank2Notempty OBJECT-TYPE
	  SYNTAX EkiOnOff
	  MAX-ACCESS read-only
	  STATUS current
	  DESCRIPTION
        "
        GW bank 2 loaded :This OID indicates
        a gateware is loaded in GW bank
        2
        "
	  ::= { pm20002maDwlgwBanksUsed 6 }



pm20002maDwlGwBank1Notempty OBJECT-TYPE
	  SYNTAX EkiOnOff
	  MAX-ACCESS read-only
	  STATUS current
	  DESCRIPTION
        "
        GW bank 1 loaded :This OID indicates
        a gateware is loaded in GW bank
        1  <Help>  This status indicates
        if the GW bank 1 contains GW package
        "
	  ::= { pm20002maDwlgwBanksUsed 5 }



pm20002maDwlGwBank4Used OBJECT-TYPE
	  SYNTAX EkiOnOff
	  MAX-ACCESS read-only
	  STATUS current
	  DESCRIPTION
        "
        GW bank 4 active :This OID indicates
        the module is working on GW bank
        4
        "
	  ::= { pm20002maDwlgwBanksUsed 4 }



pm20002maDwlGwBank3Used OBJECT-TYPE
	  SYNTAX EkiOnOff
	  MAX-ACCESS read-only
	  STATUS current
	  DESCRIPTION
        "
        GW bank 3 active :This OID indicates
        the module is working on GW bank
        3  <Help>  This status indicates
        if the GW bank 3 is active or standby
        "
	  ::= { pm20002maDwlgwBanksUsed 3 }



pm20002maDwlGwBank2Used OBJECT-TYPE
	  SYNTAX EkiOnOff
	  MAX-ACCESS read-only
	  STATUS current
	  DESCRIPTION
        "
        GW bank 2 active :This OID indicates
        the module is working on GW bank
        2
        "
	  ::= { pm20002maDwlgwBanksUsed 2 }



pm20002maDwlGwBank1Used OBJECT-TYPE
	  SYNTAX EkiOnOff
	  MAX-ACCESS read-only
	  STATUS current
	  DESCRIPTION
        "
        GW bank 1 active :This OID indicates
        the module is working on GW bank
        1  <Help>  This status indicates
        if the GW bank 1 is active or standby
        "
	  ::= { pm20002maDwlgwBanksUsed 1 }








--- *****************************************************
--- $$$$$$$$$$$$$$$$$$$$$$$$$$$$$$$$$$$$$$$$$$$$$$$$$$$$$
---     CONFIG
--- $$$$$$$$$$$$$$$$$$$$$$$$$$$$$$$$$$$$$$$$$$$$$$$$$$$$$
--- *****************************************************



--- *****************************************************
---     LEAF for the table Group accessCAisCsf
--- *****************************************************

pm20002maCfgAccessCAisCsf OBJECT IDENTIFIER ::= { pm20002maConfig 1 }



--- *****************************************************
---     LEAF for the table 0012
--- *****************************************************

pm20002maCfgClientcaiscsfTable OBJECT-TYPE
	SYNTAX  SEQUENCE OF Pm20002maCfgClientcaiscsfEntry
	MAX-ACCESS not-accessible
	STATUS current
	DESCRIPTION
        "
        List of  Article
        "
	::= { pm20002maCfgAccessCAisCsf 1 }


pm20002maCfgClientcaiscsfEntry OBJECT-TYPE
	SYNTAX Pm20002maCfgClientcaiscsfEntry
	MAX-ACCESS not-accessible
	STATUS current
	DESCRIPTION
        "
        Row definition for the accessCAisCsf
        table
        "
	INDEX   { pm20002maCfgClientcaiscsfIndex }
	::= { pm20002maCfgClientcaiscsfTable 1 }


Pm20002maCfgClientcaiscsfEntry ::=
	SEQUENCE {
	pm20002maCfgClientcaiscsfIndex
		INTEGER,
	pm20002maCfgReservePortn
		Unsigned32
	}


pm20002maCfgClientcaiscsfIndex OBJECT-TYPE
	SYNTAX  INTEGER(0..128)
	MAX-ACCESS  read-only
	STATUS current
	DESCRIPTION
        "
        Index definition for the clientcaiscsf
        table
        "
	::= { pm20002maCfgClientcaiscsfEntry 1 }


pm20002maCfgReservePortn OBJECT-TYPE
	SYNTAX  Unsigned32 (0..65536)
	MAX-ACCESS read-write
	STATUS current
	DESCRIPTION
        "
        CAIS mode  on Client Port :This
        register enables/disables port
          laser shutdown on CAIS insertion
        condition
        "
	::= { pm20002maCfgClientcaiscsfEntry 3 }


--- *****************************************************
---     LEAF for the table Group startup
--- *****************************************************

pm20002maCfgStartup OBJECT IDENTIFIER ::= { pm20002maConfig 2 }



--- *****************************************************
---     LEAF for the table 2110
--- *****************************************************

pm20002maCfgClientStartupTable OBJECT-TYPE
	SYNTAX  SEQUENCE OF Pm20002maCfgClientStartupEntry
	MAX-ACCESS not-accessible
	STATUS current
	DESCRIPTION
        "
        List of  Article
        "
	::= { pm20002maCfgStartup 1 }


pm20002maCfgClientStartupEntry OBJECT-TYPE
	SYNTAX Pm20002maCfgClientStartupEntry
	MAX-ACCESS not-accessible
	STATUS current
	DESCRIPTION
        "
        Row definition for the startup
        table
        "
	INDEX   { pm20002maCfgClientStartupIndex }
	::= { pm20002maCfgClientStartupTable 1 }


Pm20002maCfgClientStartupEntry ::=
	SEQUENCE {
	pm20002maCfgClientStartupIndex
		INTEGER,
	pm20002maCfgSystConfPortPortn
		Unsigned32,
	pm20002maCfgNetConfPortPortn
		Unsigned32,
	pm20002maCfgOptionsPortPortn
		Unsigned32
	}


pm20002maCfgClientStartupIndex OBJECT-TYPE
	SYNTAX  INTEGER(0..128)
	MAX-ACCESS  read-only
	STATUS current
	DESCRIPTION
        "
        Index definition for the clientStartup
        table
        "
	::= { pm20002maCfgClientStartupEntry 1 }


pm20002maCfgSystConfPortPortn OBJECT-TYPE
	SYNTAX  Unsigned32 (0..65536)
	MAX-ACCESS read-write
	STATUS current
	DESCRIPTION
        "
        Default Settings on Client Port
        :This  register configures the
         default initialisation settings
        on the port.
        "
	::= { pm20002maCfgClientStartupEntry 3 }


pm20002maCfgNetConfPortPortn OBJECT-TYPE
	SYNTAX  Unsigned32 (0..65536)
	MAX-ACCESS read-write
	STATUS current
	DESCRIPTION
        "
        Default Settings on Client Port
        :This  register configures the
         default initialisation settings
        on the port.
        "
	::= { pm20002maCfgClientStartupEntry 4 }


pm20002maCfgOptionsPortPortn OBJECT-TYPE
	SYNTAX  Unsigned32 (0..65536)
	MAX-ACCESS read-write
	STATUS current
	DESCRIPTION
        "
        Default Options on Client Port
        :This register configures the default
        options on the port.
        "
	::= { pm20002maCfgClientStartupEntry 14 }


--- *****************************************************
---     LEAF for the table 2190
--- *****************************************************

pm20002maCfgLineStartupTable OBJECT-TYPE
	SYNTAX  SEQUENCE OF Pm20002maCfgLineStartupEntry
	MAX-ACCESS not-accessible
	STATUS current
	DESCRIPTION
        "
        List of  Article
        "
	::= { pm20002maCfgStartup 2 }


pm20002maCfgLineStartupEntry OBJECT-TYPE
	SYNTAX Pm20002maCfgLineStartupEntry
	MAX-ACCESS not-accessible
	STATUS current
	DESCRIPTION
        "
        Row definition for the startup
        table
        "
	INDEX   { pm20002maCfgLineStartupIndex }
	::= { pm20002maCfgLineStartupTable 1 }


Pm20002maCfgLineStartupEntry ::=
	SEQUENCE {
	pm20002maCfgLineStartupIndex
		INTEGER,
	pm20002maCfgSystConfLinePortn
		Unsigned32,
	pm20002maCfgOptionsLinePortn
		Unsigned32
	}


pm20002maCfgLineStartupIndex OBJECT-TYPE
	SYNTAX  INTEGER(0..128)
	MAX-ACCESS  read-only
	STATUS current
	DESCRIPTION
        "
        Index definition for the lineStartup
        table
        "
	::= { pm20002maCfgLineStartupEntry 1 }


pm20002maCfgSystConfLinePortn OBJECT-TYPE
	SYNTAX  Unsigned32 (0..65536)
	MAX-ACCESS read-write
	STATUS current
	DESCRIPTION
        "
        Default Settings on Line :This
        register configures the default
        initialisation settings on Line
        "
	::= { pm20002maCfgLineStartupEntry 3 }


pm20002maCfgOptionsLinePortn OBJECT-TYPE
	SYNTAX  Unsigned32 (0..65536)
	MAX-ACCESS read-write
	STATUS current
	DESCRIPTION
        "
        Default Options on Line :This
         register configures the default
        options on the line
        "
	::= { pm20002maCfgLineStartupEntry 14 }


--- *****************************************************
---     LEAF for the table 21AB
--- *****************************************************

pm20002maCfgXfpTable OBJECT-TYPE
	SYNTAX  SEQUENCE OF Pm20002maCfgXfpEntry
	MAX-ACCESS not-accessible
	STATUS current
	DESCRIPTION
        "
        List of  Article
        "
	::= { pm20002maCfgStartup 3 }


pm20002maCfgXfpEntry OBJECT-TYPE
	SYNTAX Pm20002maCfgXfpEntry
	MAX-ACCESS not-accessible
	STATUS current
	DESCRIPTION
        "
        Row definition for the startup
        table
        "
	INDEX   { pm20002maCfgXfpIndex }
	::= { pm20002maCfgXfpTable 1 }


Pm20002maCfgXfpEntry ::=
	SEQUENCE {
	pm20002maCfgXfpIndex
		INTEGER,
	pm20002maCfgSystConfMsaLinePortn
		Unsigned32
	}


pm20002maCfgXfpIndex OBJECT-TYPE
	SYNTAX  INTEGER(0..128)
	MAX-ACCESS  read-only
	STATUS current
	DESCRIPTION
        "
        Index definition for the xfp table
        "
	::= { pm20002maCfgXfpEntry 1 }


pm20002maCfgSystConfMsaLinePortn OBJECT-TYPE
	SYNTAX  Unsigned32 (0..65536)
	MAX-ACCESS read-write
	STATUS current
	DESCRIPTION
        "
        Default settings on MSA :This
         register configures the default
        initialisation settings on MSA
        "
	::= { pm20002maCfgXfpEntry 3 }


--- *****************************************************
---     LEAF for the table Group labels
--- *****************************************************

pm20002maCfgLabels OBJECT IDENTIFIER ::= { pm20002maConfig 3 }



--- *****************************************************
---     LEAF for the table 0003
--- *****************************************************

pm20002maCfgLabelclientTable OBJECT-TYPE
	SYNTAX  SEQUENCE OF Pm20002maCfgLabelclientEntry
	MAX-ACCESS not-accessible
	STATUS current
	DESCRIPTION
        "
        List of  Article
        "
	::= { pm20002maCfgLabels 1 }


pm20002maCfgLabelclientEntry OBJECT-TYPE
	SYNTAX Pm20002maCfgLabelclientEntry
	MAX-ACCESS not-accessible
	STATUS current
	DESCRIPTION
        "
        Row definition for the labels
         table
        "
	INDEX   { pm20002maCfgLabelclientIndex }
	::= { pm20002maCfgLabelclientTable 1 }


Pm20002maCfgLabelclientEntry ::=
	SEQUENCE {
	pm20002maCfgLabelclientIndex
		INTEGER,
	pm20002maCfgLabelclientPortn
		DisplayString
	}


pm20002maCfgLabelclientIndex OBJECT-TYPE
	SYNTAX  INTEGER(0..128)
	MAX-ACCESS  read-only
	STATUS current
	DESCRIPTION
        "
        Index definition for the labelclient
        table
        "
	::= { pm20002maCfgLabelclientEntry 1 }


pm20002maCfgLabelclientPortn OBJECT-TYPE
	SYNTAX  DisplayString( SIZE(1..16))
	MAX-ACCESS read-write
	STATUS current
	DESCRIPTION
        "
        Default settings on the label
         of the Ports :These registers
         configures the default initialisation
        settings of the labels of the ports.
        "
	::= { pm20002maCfgLabelclientEntry 3 }


--- *****************************************************
---     LEAF for the table 0004
--- *****************************************************

pm20002maCfgLabellineTable OBJECT-TYPE
	SYNTAX  SEQUENCE OF Pm20002maCfgLabellineEntry
	MAX-ACCESS not-accessible
	STATUS current
	DESCRIPTION
        "
        List of  Article
        "
	::= { pm20002maCfgLabels 2 }


pm20002maCfgLabellineEntry OBJECT-TYPE
	SYNTAX Pm20002maCfgLabellineEntry
	MAX-ACCESS not-accessible
	STATUS current
	DESCRIPTION
        "
        Row definition for the labels
         table
        "
	INDEX   { pm20002maCfgLabellineIndex }
	::= { pm20002maCfgLabellineTable 1 }


Pm20002maCfgLabellineEntry ::=
	SEQUENCE {
	pm20002maCfgLabellineIndex
		INTEGER,
	pm20002maCfgLabellinePortn
		DisplayString
	}


pm20002maCfgLabellineIndex OBJECT-TYPE
	SYNTAX  INTEGER(0..128)
	MAX-ACCESS  read-only
	STATUS current
	DESCRIPTION
        "
        Index definition for the labelline
        table
        "
	::= { pm20002maCfgLabellineEntry 1 }


pm20002maCfgLabellinePortn OBJECT-TYPE
	SYNTAX  DisplayString( SIZE(1..16))
	MAX-ACCESS read-write
	STATUS current
	DESCRIPTION
        "
        Default settings on the label
         of the lines :These registers
         configures the default initialisation
        settings of the labels of the lines.
        "
	::= { pm20002maCfgLabellineEntry 3 }


--- *****************************************************
---     LEAF for the table Group startuptlh
--- *****************************************************

pm20002maCfgStartuptlh OBJECT IDENTIFIER ::= { pm20002maConfig 4 }



--- *****************************************************
---     LEAF for the table 25AB
--- *****************************************************

pm20002maCfgOtxtlhTable OBJECT-TYPE
	SYNTAX  SEQUENCE OF Pm20002maCfgOtxtlhEntry
	MAX-ACCESS not-accessible
	STATUS current
	DESCRIPTION
        "
        List of  Article
        "
	::= { pm20002maCfgStartuptlh 1 }


pm20002maCfgOtxtlhEntry OBJECT-TYPE
	SYNTAX Pm20002maCfgOtxtlhEntry
	MAX-ACCESS not-accessible
	STATUS current
	DESCRIPTION
        "
        Row definition for the startuptlh
        table
        "
	INDEX   { pm20002maCfgOtxtlhIndex }
	::= { pm20002maCfgOtxtlhTable 1 }


Pm20002maCfgOtxtlhEntry ::=
	SEQUENCE {
	pm20002maCfgOtxtlhIndex
		INTEGER,
	pm20002maCfgLinePwrLaserPortn
		Unsigned32,
	pm20002maCfgLineFCurrentPortn
		Unsigned32,
	pm20002maCfgLineGridCurrentPortn
		Unsigned32,
	pm20002maCfgFPortn
		Unsigned32,
	pm20002maCfgRxLineFCurrentPortn
		Unsigned32
	}


pm20002maCfgOtxtlhIndex OBJECT-TYPE
	SYNTAX  INTEGER(0..128)
	MAX-ACCESS  read-only
	STATUS current
	DESCRIPTION
        "
        Index definition for the otxtlh
        table
        "
	::= { pm20002maCfgOtxtlhEntry 1 }


pm20002maCfgLinePwrLaserPortn OBJECT-TYPE
	SYNTAX  Unsigned32 (0..65536)
	MAX-ACCESS read-write
	STATUS current
	DESCRIPTION
        "
        Defaut Line output Power :This
        register configures the start-up
        output power of the Line tranceiver
         (Unit = dBm)
        "
	::= { pm20002maCfgOtxtlhEntry 6 }


pm20002maCfgLineFCurrentPortn OBJECT-TYPE
	SYNTAX  Unsigned32 (0..65536)
	MAX-ACCESS read-write
	STATUS current
	DESCRIPTION
        "
        Default Line transceiver Tx Channel
        :This register configures the start-up
        laser channel of the Line Tx transceiver
        "
	::= { pm20002maCfgOtxtlhEntry 7 }


pm20002maCfgLineGridCurrentPortn OBJECT-TYPE
	SYNTAX  Unsigned32 (0..65536)
	MAX-ACCESS read-write
	STATUS current
	DESCRIPTION
        "
        Default Line transceiver Grid
         :This register configures the
         start-up laser grid of the Line
        transceiver
        "
	::= { pm20002maCfgOtxtlhEntry 8 }


pm20002maCfgFPortn OBJECT-TYPE
	SYNTAX  Unsigned32 (0..65536)
	MAX-ACCESS read-write
	STATUS current
	DESCRIPTION
        "
        Default Line TRX lowest Freq :This
        register configures the start-up
        lowest frequency of the Line transceiver
        "
	::= { pm20002maCfgOtxtlhEntry 9 }


pm20002maCfgRxLineFCurrentPortn OBJECT-TYPE
	SYNTAX  Unsigned32 (0..65536)
	MAX-ACCESS read-write
	STATUS current
	DESCRIPTION
        "
        Default Line transceiver Rx Channel
        :This register configures the start-up
        laser channel of the Line Rx transceiver
        "
	::= { pm20002maCfgOtxtlhEntry 10 }


--- *****************************************************
---     LEAF for the table Group other
--- *****************************************************

pm20002maCfgOther OBJECT IDENTIFIER ::= { pm20002maConfig 5 }



--- *****************************************************
---     LEAF for the table 2300
--- *****************************************************

pm20002matablemoduleOther OBJECT IDENTIFIER ::= { pm20002maCfgOther 1 }



pm20002maCfgmode OBJECT-TYPE
	  SYNTAX Unsigned32 (0..65536)
	  MAX-ACCESS read-write
	  STATUS current
	  DESCRIPTION
        "
        Default settings on Module :This
        register selects the configuration
        mode of the module
        "
	  ::= { pm20002matablemoduleOther 2 }



pm20002maCfgfanLowSpeedThreshold OBJECT-TYPE
	  SYNTAX Unsigned32 (0..65536)
	  MAX-ACCESS read-write
	  STATUS current
	  DESCRIPTION
        "
        Default settings on Module :This
        register selects the speed threshold
        of the fan's
        "
	  ::= { pm20002matablemoduleOther 3 }



pm20002maCfgfanHighSpeedThreshold OBJECT-TYPE
	  SYNTAX Unsigned32 (0..65536)
	  MAX-ACCESS read-write
	  STATUS current
	  DESCRIPTION
        "
        Default settings on Module :This
        register selects the speed threshold
        of the fan's
        "
	  ::= { pm20002matablemoduleOther 4 }



--- *****************************************************
---     LEAF for the table Group startuptablefive
--- *****************************************************

pm20002maCfgStartuptablefive OBJECT IDENTIFIER ::= { pm20002maConfig 6 }



--- *****************************************************
---     LEAF for the table 0005
--- *****************************************************

pm20002maCfgOtxtlhcapabilitiesTable OBJECT-TYPE
	SYNTAX  SEQUENCE OF Pm20002maCfgOtxtlhcapabilitiesEntry
	MAX-ACCESS not-accessible
	STATUS current
	DESCRIPTION
        "
        List of  Article
        "
	::= { pm20002maCfgStartuptablefive 1 }


pm20002maCfgOtxtlhcapabilitiesEntry OBJECT-TYPE
	SYNTAX Pm20002maCfgOtxtlhcapabilitiesEntry
	MAX-ACCESS not-accessible
	STATUS current
	DESCRIPTION
        "
        Row definition for the startuptablefive
        table
        "
	INDEX   { pm20002maCfgOtxtlhcapabilitiesIndex }
	::= { pm20002maCfgOtxtlhcapabilitiesTable 1 }


Pm20002maCfgOtxtlhcapabilitiesEntry ::=
	SEQUENCE {
	pm20002maCfgOtxtlhcapabilitiesIndex
		INTEGER,
	pm20002maCfgComponentTypePortn
		Unsigned32,
	pm20002maCfgMiscellaneousPortn
		Unsigned32,
	pm20002maCfgFirstChannelPortn
		Unsigned32,
	pm20002maCfgLastChannelPortn
		Unsigned32,
	pm20002maCfgGridPortn
		Unsigned32
	}


pm20002maCfgOtxtlhcapabilitiesIndex OBJECT-TYPE
	SYNTAX  INTEGER(0..128)
	MAX-ACCESS  read-only
	STATUS current
	DESCRIPTION
        "
        Index definition for the otxtlhcapabilities
        table
        "
	::= { pm20002maCfgOtxtlhcapabilitiesEntry 1 }


pm20002maCfgComponentTypePortn OBJECT-TYPE
	SYNTAX  Unsigned32 (0..65536)
	MAX-ACCESS read-only
	STATUS current
	DESCRIPTION
        "
        Component parameters :This OID
        defines the component parameters
        "
	::= { pm20002maCfgOtxtlhcapabilitiesEntry 3 }


pm20002maCfgMiscellaneousPortn OBJECT-TYPE
	SYNTAX  Unsigned32 (0..65536)
	MAX-ACCESS read-only
	STATUS current
	DESCRIPTION
        "
        Miscellaneous default settings
        :This OID defines the miscellaneous
        parameters
        "
	::= { pm20002maCfgOtxtlhcapabilitiesEntry 4 }


pm20002maCfgFirstChannelPortn OBJECT-TYPE
	SYNTAX  Unsigned32 (0..65536)
	MAX-ACCESS read-only
	STATUS current
	DESCRIPTION
        "
        Number of the first channel of
        the component :This OID defines
        the first channel number of the
        PM
        "
	::= { pm20002maCfgOtxtlhcapabilitiesEntry 5 }


pm20002maCfgLastChannelPortn OBJECT-TYPE
	SYNTAX  Unsigned32 (0..65536)
	MAX-ACCESS read-only
	STATUS current
	DESCRIPTION
        "
        Number of the last channel of
         the component :This OID defines
        the last channel number of the
         PM
        "
	::= { pm20002maCfgOtxtlhcapabilitiesEntry 6 }


pm20002maCfgGridPortn OBJECT-TYPE
	SYNTAX  Unsigned32 (0..65536)
	MAX-ACCESS read-only
	STATUS current
	DESCRIPTION
        "
        Grid value of the component :This
        OID defines the grid of the PM
        "
	::= { pm20002maCfgOtxtlhcapabilitiesEntry 7 }



pm20002maCfgWriteConfiguration  OBJECT-TYPE
	SYNTAX EkiOnOff
	MAX-ACCESS read-write
	STATUS current
	DESCRIPTION
	"Write configuration to module:This OID
	 writes the complete configuration to the module"
	::= { pm20002maConfig 257 }






--- *****************************************************
---     TRAP OBJECTS
--- *****************************************************

pm20002matrapPortNumber OBJECT-TYPE
	SYNTAX INTEGER(1..64)
	MAX-ACCESS read-only
	STATUS current
	DESCRIPTION
	"Last port which generates a trap"
	::= { pm20002matraps 2 }

pm20002matrapLineNumber OBJECT-TYPE
	SYNTAX INTEGER(1..64)
	MAX-ACCESS read-only
	STATUS current
	DESCRIPTION
	"Last Line which generates a trap"
	::= { pm20002matraps 3 }

pm20002matrapBoardNumber OBJECT-TYPE
	SYNTAX INTEGER(1..64)
	MAX-ACCESS read-only
	STATUS current
	DESCRIPTION
	"Last module which generates a trap"
	::= { pm20002matraps 4 }







--- *****************************************************
---     LINE TRAPS
--- *****************************************************

pm20002maLineTrapNotUrgentGoesOn NOTIFICATION-TYPE
	OBJECTS {pm20002maAlmLineDdmWarningPortn, pm20002matrapLineNumber, pm20002matrapBoardNumber}
	STATUS current
	--&FILTNAME    "PM20002MA Line Not Urgent ON"
	--&ACTIONS     { log, minor }
	--&MATCH       { pm20002maAlmLineDdmWarningPortn "on", pm20002matrapLineNumber "$2", pm20002matrapBoardNumber "$3"}
	--&MESG        "DDM Warning appears on Line Port $2 of PM20002MA in Slot $3 ($A)"
	DESCRIPTION "Not urgent Line default is activated"
	::= { pm20002matraps 30 }

pm20002maLineTrapNotUrgentGoesOff NOTIFICATION-TYPE
	OBJECTS {pm20002maAlmLineDdmWarningPortn, pm20002matrapLineNumber, pm20002matrapBoardNumber}
	STATUS current
	--&FILTNAME    "PM20002MA Line Not Urgent OFF"
	--&ACTIONS     { log, normal }
	--&CLEARS      { "PM20002MA Line Not Urgent ON" }
	--&MATCH       { pm20002maAlmLineDdmWarningPortn "on", pm20002matrapLineNumber "$2", pm20002matrapBoardNumber "$3"}
	--&MESG        "DDM Warning disappears on Line Port $2 of PM20002MA in Slot $3 ($A)"
	DESCRIPTION "Not urgent Line default disappeared"
	::= { pm20002matraps 31 }

pm20002maLineTrapUrgentGoesOn NOTIFICATION-TYPE
	OBJECTS {pm20002maAlmLineDdmAlmPortn, pm20002matrapLineNumber, pm20002matrapBoardNumber}
	STATUS current
	--&FILTNAME    "PM20002MA Line Urgent ON"
	--&ACTIONS     { log, major }
	--&MATCH       { pm20002maAlmLineDdmAlmPortn "on", pm20002matrapLineNumber "$2", pm20002matrapBoardNumber "$3"}
	--&MESG        "DDM Alarm appears on Line Port $2 of PM20002MA in Slot $3 ($A)"
	DESCRIPTION "Urgent Line default is activated"
	::= { pm20002matraps 32 }

pm20002maLineTrapUrgentGoesOff NOTIFICATION-TYPE
	OBJECTS {pm20002maAlmLineDdmAlmPortn, pm20002matrapLineNumber, pm20002matrapBoardNumber}
	STATUS current
	--&FILTNAME    "PM20002MA Line Urgent OFF"
	--&ACTIONS     { log, normal }
	--&CLEARS      { "PM20002MA Line Urgent ON" }
	--&MATCH       { pm20002maAlmLineDdmAlmPortn "on", pm20002matrapLineNumber "$2", pm20002matrapBoardNumber "$3"}
	--&MESG        "DDM Alarm disappears on Line Port $2 of PM20002MA in Slot $3 ($A)"
	DESCRIPTION "Urgent Line default disappeared"
	::= { pm20002matraps 33 }

pm20002maLineTrapCritGoesOn NOTIFICATION-TYPE
	OBJECTS {pm20002maAlmLineFailPortn , pm20002maAlmLineHwFailPortn , pm20002matrapLineNumber, pm20002matrapBoardNumber}
	STATUS current
	--&FILTNAME    "PM20002MA Line Fail ON"
	--&ACTIONS     { log, critical }
	--&MATCH       { pm20002maAlmLineFailPortn "on", pm20002maAlmLineHwFailPortn "*", pm20002matrapLineNumber "$3", pm20002matrapBoardNumber "$4"}
	--&MESG        "Line Port $3 Down on PM20002MA in Slot $4 ($A)"

	--&FILTNAME    "PM20002MA Line HW Fail ON (Hidden)"
	--&ACTIONS     { info }
	--&MATCH       { pm20002maAlmLineFailPortn "*", pm20002maAlmLineHwFailPortn "on", pm20002matrapLineNumber "$3", pm20002matrapBoardNumber "$4"}
	--&MESG        "Line Port $3 Down on PM20002MA in Slot $4 ($A)"
	DESCRIPTION "Critical Line default is activated"
	::= { pm20002matraps 34 }

pm20002maLineTrapCritGoesOff NOTIFICATION-TYPE
	OBJECTS {pm20002maAlmLineFailPortn , pm20002maAlmLineHwFailPortn , pm20002matrapLineNumber, pm20002matrapBoardNumber}
	STATUS current
	--&FILTNAME    "PM20002MA Line Fail OFF"
	--&ACTIONS     { log,  normal }
	--&CLEARS      { "PM20002MA Line Fail ON" }
	--&MATCH       { pm20002maAlmLineFailPortn "on", pm20002maAlmLineHwFailPortn "*", pm20002matrapLineNumber "$3", pm20002matrapBoardNumber "$4"}
	--&MESG        "Line Port $3 Up on PM20002MA in Slot $4 ($A)"

	--&FILTNAME    "PM20002MA Line HW Fail OFF (Hidden)"
	--&ACTIONS     { info }
	--&MATCH       { pm20002maAlmLineFailPortn "*", pm20002maAlmLineHwFailPortn "on", pm20002matrapLineNumber "$3", pm20002matrapBoardNumber "$4"}
	--&MESG        "Line Port $3 Up on PM20002MA in Slot $4 ($A)"
	DESCRIPTION "Critical Line default disappeared"
	::= { pm20002matraps 35 }






--- *****************************************************
---     CLIENT TRAPS
--- *****************************************************

pm20002maClientTrapNotUrgentGoesOn NOTIFICATION-TYPE
	OBJECTS {pm20002maAlmSfpDdmWarningPortn, pm20002matrapPortNumber, pm20002matrapBoardNumber}
	STATUS current
		--&FILTNAME    "PM20002MA Client Not Urgent ON"
		--&ACTIONS     { log, minor }
		--&MATCH       { pm20002maAlmSfpDdmWarningPortn "on", pm20002matrapPortNumber "$2", pm20002matrapBoardNumber "$3"}
		--&MESG        "DDM Warning appears on Client Port $2 of PM20002MA in Slot $3 ($A)"
	DESCRIPTION "Not urgent client default is activated"
	::= { pm20002matraps 40 }

pm20002maClientTrapNotUrgentGoesOff NOTIFICATION-TYPE
	OBJECTS {pm20002maAlmSfpDdmWarningPortn, pm20002matrapPortNumber, pm20002matrapBoardNumber}
	STATUS current
		--&FILTNAME    "PM20002MA Client Not Urgent OFF"
		--&ACTIONS     { log, normal }
		--&CLEARS      { "PM20002MA Client Not Urgent ON" }
		--&MATCH       { pm20002maAlmSfpDdmWarningPortn "on", pm20002matrapPortNumber "$2", pm20002matrapBoardNumber "$3"}
		--&MESG        "DDM Warning appears on Client Port $2 of PM20002MA in Slot $3 ($A)"
	DESCRIPTION "Not urgent client default disappeared"
	::= { pm20002matraps 41 }

pm20002maClientTrapUrgentGoesOn NOTIFICATION-TYPE
	OBJECTS {pm20002maAlmSfpDdmAlmPortn, pm20002matrapPortNumber, pm20002matrapBoardNumber}
	STATUS current
		--&FILTNAME    "PM20002MA Client Urgent ON"
		--&ACTIONS     { log, major }
		--&MATCH       { pm20002maAlmSfpDdmAlmPortn "on", pm20002matrapPortNumber "$2", pm20002matrapBoardNumber "$3"}
		--&MESG        "DDM Alarm appears on Client Port $2 of PM20002MA in Slot $3 ($A)"
	DESCRIPTION "Urgent client default is activated"
	::= { pm20002matraps 42 }

pm20002maClientTrapUrgentGoesOff NOTIFICATION-TYPE
	OBJECTS {pm20002maAlmSfpDdmAlmPortn, pm20002matrapPortNumber, pm20002matrapBoardNumber}
	STATUS current
		--&FILTNAME    "PM20002MA Client Urgent OFF"
		--&ACTIONS     { log, normal }
		--&CLEARS      { "PM20002MA Client Urgent ON" }
		--&MATCH       { pm20002maAlmSfpDdmAlmPortn "on", pm20002matrapPortNumber "$2", pm20002matrapBoardNumber "$3"}
		--&MESG        "DDM Alarm disappears on Client Port $2 of PM20002MA in Slot $3 ($A)"
	DESCRIPTION "Urgent client default disappeared"
	::= { pm20002matraps 43 }

pm20002maClientTrapCritGoesOn NOTIFICATION-TYPE
	OBJECTS {pm20002maAlmFailAccPortn, pm20002maAlmHwFailAccPortn, pm20002matrapPortNumber, pm20002matrapBoardNumber}
	STATUS current
		--&FILTNAME    "PM20002MA Client Fail ON"
		--&ACTIONS     { log, critical }
		--&MATCH       { pm20002maAlmFailAccPortn "on", pm20002maAlmHwFailAccPortn "*", pm20002matrapPortNumber "$3", pm20002matrapBoardNumber "$4"}
		--&MESG        "Client Port $3 Down on PM20002MA in Slot $4 ($A)"

		--&FILTNAME    "PM20002MA Client HW Fail ON (Hidden)"
		--&ACTIONS     { info }
		--&MATCH       { pm20002maAlmFailAccPortn "*", pm20002maAlmHwFailAccPortn "on", pm20002matrapPortNumber "$3", pm20002matrapBoardNumber "$4"}
		--&MESG        "Client Port $3 Down on PM20002MA in Slot $4 ($A)"
	DESCRIPTION "Critical client default is activated"
	::= { pm20002matraps 44 }

pm20002maClientTrapCritGoesOff NOTIFICATION-TYPE
	OBJECTS {pm20002maAlmFailAccPortn, pm20002maAlmHwFailAccPortn, pm20002matrapPortNumber, pm20002matrapBoardNumber}
	STATUS current
		--&FILTNAME    "PM20002MA Client Fail OFF"
		--&ACTIONS     { log, normal }
		--&CLEARS      { "PM20002MA Client Fail ON" }
		--&MATCH       { pm20002maAlmFailAccPortn "on", pm20002maAlmHwFailAccPortn "*", pm20002matrapPortNumber "$3", pm20002matrapBoardNumber "$4"}
		--&MESG        "Client Port $3 Up on PM20002MA in Slot $4 ($A)"

		--&FILTNAME    "PM20002MA Client HW Fail OFF (Hidden)"
		--&ACTIONS     { info }
		--&MATCH       { pm20002maAlmFailAccPortn "*", pm20002maAlmHwFailAccPortn "on", pm20002matrapPortNumber "$3", pm20002matrapBoardNumber "$4"}
		--&MESG        "Client Port $3 Up on PM20002MA in Slot $4 ($A)"
	DESCRIPTION "Critical client default disappeared"
	::= { pm20002matraps 45 }






--- *****************************************************
---     HW TRAPS
--- *****************************************************

pm20002maPowerTrapUrgentGoesOn NOTIFICATION-TYPE
	OBJECTS {pm20002maAlmDefFuseB, pm20002maAlmDefFuseA , pm20002matrapBoardNumber}
	STATUS current
		--&FILTNAME    "PM20002MA Fuse A Fail ON"
		--&ACTIONS     { log, major }
		--&MATCH       { pm20002maAlmDefFuseB "*", pm20002maAlmDefFuseA "on", pm20002matrapBoardNumber "$3"}
		--&MESG        "Power Input A Fail on PM20002MA in Slot $3 ($A)"

		--&FILTNAME    "PM20002MA Fuse B Fail ON"
		--&ACTIONS     { log, major }
		--&MATCH       { pm20002maAlmDefFuseB "on", pm20002maAlmDefFuseA "*", pm20002matrapBoardNumber "$3"}
		--&MESG        "Power Input B Fail on PM20002MA in Slot $3 ($A)"
	DESCRIPTION "Urgent power supply default is activated"
	::= { pm20002matraps 50 }

pm20002maPowerTrapUrgentGoesOff NOTIFICATION-TYPE
	OBJECTS {pm20002maAlmDefFuseB, pm20002maAlmDefFuseA , pm20002matrapBoardNumber}
	STATUS current
		--&FILTNAME    "PM20002MA Fuse A&B Fail OFF"
		--&ACTIONS     { log, normal}
		--&CLEARS      { "PM20002MA Fuse A Fail ON", "PM20002MA Fuse B Fail ON" }
		--&MATCH       { pm20002maAlmDefFuseB "on", pm20002maAlmDefFuseA "on", pm20002matrapBoardNumber "$3"}
		--&MESG        "Power Inputs A and B Present on PM20002MA in Slot $3 ($A)"
	DESCRIPTION "Urgent power supply default disappeared"
	::= { pm20002matraps 51 }






END
