-- *****************************************************************
-- EKINOPS-pmoailhc.TXT:  MIB
--
--MIB Part Number:3MI00209AABE
--MIB Version:1
--
-- Copyright (c) 2016 by Ekinops
-- All rights reserved.
--
-- *****************************************************************

EKINOPS-PmOailhc-MIB DEFINITIONS ::= BEGIN

IMPORTS
	ekinops,
	EkiState,
	EkiOnOff,
	EkiMode,
	EkiProtocol,
	EkiApiState,
	EkiSynchroMode,
	EkiMeasureType
			FROM EKINOPS-MIB
        MODULE-IDENTITY,
        OBJECT-TYPE,
        NOTIFICATION-TYPE,
	Unsigned32,
	Integer32,
	Counter32,
	IpAddress
        		FROM SNMPv2-SMI
 	TEXTUAL-CONVENTION,
	DisplayString
                FROM SNMPv2-TC;

modulepmoailhc MODULE-IDENTITY
        LAST-UPDATED "201605230000Z"
        ORGANIZATION "Ekinops"
        CONTACT-INFO
         "Ekinops

          3, rue Blaise Pascal
          F-22300 Lannion / FRANCE

          Tel : +33 (0)2 96 05 00 30
          Fax : +33 (0)2 96 48 62 39

          E-mail: support@ekinops.net"
        DESCRIPTION
          "Creation"
	REVISION "201209100000Z"
	DESCRIPTION
	  "Initial Version."

	REVISION "201209100000Z"
	DESCRIPTION
	  "Creation"
	REVISION "201302080000Z"
	DESCRIPTION
	  "Ext Pump alarms"
	REVISION "201307020000Z"
	DESCRIPTION
	  "Constant Gain function"
	REVISION "201309160000Z"
	DESCRIPTION
	  "Help change"
	REVISION "201312020000Z"
	DESCRIPTION
	  "External Pump Fail Insertion"
	REVISION "201403260000Z"
	DESCRIPTION
	  "Probcause,AlarmType - NMS completion"
	REVISION "201412100000Z"
	DESCRIPTION
	  "Labels cosmetic updates"
	REVISION "201605230000Z"
	DESCRIPTION
	  "New AlarmType – synthesisAlarm (12)"
        ::= { ekinops 55 }



--- *****************************************************
---     LEAF LEVEL 2
--- *****************************************************


pmoailhcalarms OBJECT IDENTIFIER ::= { modulepmoailhc 2 }
pmoailhcAlmOther OBJECT IDENTIFIER ::= { pmoailhcalarms 1 }
pmoailhcAlmOtherNurg OBJECT IDENTIFIER ::= { pmoailhcAlmOther 1 }
pmoailhcAlmOtherUrg OBJECT IDENTIFIER ::= { pmoailhcAlmOther 2 }
pmoailhcAlmOtherCrit OBJECT IDENTIFIER ::= { pmoailhcAlmOther 3 }

pmoailhcAlmClient OBJECT IDENTIFIER ::= { pmoailhcalarms 2 }
pmoailhcAlmClientNurg OBJECT IDENTIFIER ::= { pmoailhcAlmClient 1 }
pmoailhcAlmClientUrg OBJECT IDENTIFIER ::= { pmoailhcAlmClient 2 }
pmoailhcAlmClientCrit OBJECT IDENTIFIER ::= { pmoailhcAlmClient 3 }

pmoailhcAlmLine OBJECT IDENTIFIER ::= { pmoailhcalarms 3 }
pmoailhcAlmLineNurg OBJECT IDENTIFIER ::= { pmoailhcAlmLine 1 }
pmoailhcAlmLineUrg OBJECT IDENTIFIER ::= { pmoailhcAlmLine 2 }
pmoailhcAlmLineCrit OBJECT IDENTIFIER ::= { pmoailhcAlmLine 3 }


pmoailhcmeasures OBJECT IDENTIFIER ::= { modulepmoailhc 3 }
pmoailhcMesrOther OBJECT IDENTIFIER ::= { pmoailhcmeasures 1 }
pmoailhcMesrClient OBJECT IDENTIFIER ::= { pmoailhcmeasures 2 }
pmoailhcMesrLine OBJECT IDENTIFIER ::= { pmoailhcmeasures 3 }


pmoailhccontrolsWrite OBJECT IDENTIFIER ::= { modulepmoailhc 6 }
pmoailhcCtrlOther OBJECT IDENTIFIER ::= { pmoailhccontrolsWrite 1 }
pmoailhcCtrlClient OBJECT IDENTIFIER ::= { pmoailhccontrolsWrite 2 }
pmoailhcCtrlLine OBJECT IDENTIFIER ::= { pmoailhccontrolsWrite 3 }

pmoailhcri OBJECT IDENTIFIER ::= { modulepmoailhc 7 }


pmoailhcConfig OBJECT IDENTIFIER ::= { modulepmoailhc 9 }

pmoailhctraps OBJECT IDENTIFIER ::= { modulepmoailhc 10 }


--- *****************************************************
--- $$$$$$$$$$$$$$$$$$$$$$$$$$$$$$$$$$$$$$$$$$$$$$$$$$$$$
---     TEXTUAL-CONVENTION
--- $$$$$$$$$$$$$$$$$$$$$$$$$$$$$$$$$$$$$$$$$$$$$$$$$$$$$
--- *****************************************************


PmoailhcpreampMode ::= TEXTUAL-CONVENTION
    STATUS      current
    DESCRIPTION "Different modes on OA preamp"
    SYNTAX INTEGER {
		oailhcpreampdefaultmode(0),
		oailhcpreampconstantcurrentmode(1),
		oailhcpreampconstantpowermode(2)
		oailhcpreampconstantgainmode(3)
		oailhcpreamppoutpinmode(4)
		oailhcpreampmanualmode(5)
		oailhcpreampfeedforwardmode(6)
		oailhcpreamptransientsupmode(7)

           }

PmoailhcboosterMode ::= TEXTUAL-CONVENTION
    STATUS      current
    DESCRIPTION "Different modes on OA booster"
    SYNTAX INTEGER {
		oailhcboosterdefaultmode(0),
		oailhcboosterconstantcurrentmode(1),
		oailhcboosterconstantpowermode(2)
		oailhcboosterconstantgainmode(3)
		oailhcboosterpoutpinmode(4)
		oailhcboostermanualmode(5)
		oailhcboosterfeedforwardmode(6)
		oailhcboostertransientsupmode(7)
           }


PmoailhcaprMode ::= TEXTUAL-CONVENTION
    STATUS      current
    DESCRIPTION "Different modes on APR"
    SYNTAX INTEGER {
		oailhcaproffmode(0),
		oailhcaprsemiautomode(1),
		oailhcaprautomode(2)
		oailhcaprlossforwardingmode(3)
		oailhcaprrepeatmode(4)
           }

PmoailhcPreampGainAdjMode ::= TEXTUAL-CONVENTION
    STATUS      current
    DESCRIPTION "Different modes on Gain"
    SYNTAX INTEGER {
		oailhcpreampgainadjmanualmode(0),
		oailhcpreampgainadjsemiautomode(1),
		oailhcpreampgainadjautomode(2)

           }

PmoailhcBoosterGainAdjMode ::= TEXTUAL-CONVENTION
    STATUS      current
    DESCRIPTION "Different modes on Gain"
    SYNTAX INTEGER {
		oailhcboostergainadjmanualmode(0),
		oailhcboostergainadjsemiautomode(1),
		oailhcboostergainadjautomode(2)

           }


PmoailhcPreampCstGainAdjMode ::= TEXTUAL-CONVENTION
    STATUS      current
    DESCRIPTION "Different modes when constant Gain"
    SYNTAX INTEGER {
		oailhcpreampcstgainadjsemiautomode(1),
		oailhcpreampcstgainadjautomode(2)

           }

PmoailhcBoosterCstGainAdjMode ::= TEXTUAL-CONVENTION
    STATUS      current
    DESCRIPTION "Different modes when constant Gain"
    SYNTAX INTEGER {
		oailhcboostercstgainadjsemiautomode(1),
		oailhcboostercstgainadjautomode(2)

           }




--- *****************************************************
--- $$$$$$$$$$$$$$$$$$$$$$$$$$$$$$$$$$$$$$$$$$$$$$$$$$$$$
---     REMOTE INVENTORY
--- $$$$$$$$$$$$$$$$$$$$$$$$$$$$$$$$$$$$$$$$$$$$$$$$$$$$$
--- *****************************************************

pmoailhcRinvReloadInventory OBJECT-TYPE
  SYNTAX EkiOnOff
  MAX-ACCESS read-write
  STATUS current
  DESCRIPTION
        "Reload the inventory: This OID triggers an
         inventory reload."
  ::= { pmoailhcri 2 }

pmoailhcRinvModulePlatform OBJECT-TYPE
  SYNTAX DisplayString
  MAX-ACCESS read-only
  STATUS current
  DESCRIPTION
        "Module platform description: This OID contains the
         description of the Module."
  ::= { pmoailhcri 3 }

pmoailhcRinvSwPlatform OBJECT-TYPE
  SYNTAX DisplayString
  MAX-ACCESS read-only
  STATUS current
  DESCRIPTION
        "SW platform description: This OID contains the
         description of the Software platform."
  ::= { pmoailhcri 4 }

pmoailhcRinvSwFoa OBJECT-TYPE
  SYNTAX DisplayString
  MAX-ACCESS read-only
  STATUS current
  DESCRIPTION
        "Optical device driver description: This OID contains
	 the description of the driver of the optical devices
	(Booster and Pre-Amp)"
  ::= { pmoailhcri 5 }


pmoailhcRinvInLine1Table OBJECT-TYPE
      SYNTAX  SEQUENCE OF PmoailhcRinvInLine1Entry
      MAX-ACCESS  not-accessible
      STATUS  current
      DESCRIPTION
              "List of the InLine1s on the selected module"
      ::= { pmoailhcri 6 }

pmoailhcRinvInLine1Entry OBJECT-TYPE
        SYNTAX  PmoailhcRinvInLine1Entry
        MAX-ACCESS  not-accessible
        STATUS  current
        DESCRIPTION
              "Row definition for the InLine1s table"
        INDEX   { pmoailhcRinvInLine1Index }
        ::= { pmoailhcRinvInLine1Table 1 }



PmoailhcRinvInLine1Entry::=
        SEQUENCE {
          pmoailhcRinvInLine1Index
              Integer32,
          pmoailhcRinvInLine1
              DisplayString
        }


    pmoailhcRinvInLine1Index OBJECT-TYPE
        SYNTAX  Integer32(1..16)
        MAX-ACCESS  read-only
        STATUS  current
        DESCRIPTION
              "Index for InLine1 table"
        ::= { pmoailhcRinvInLine1Entry 1 }


    pmoailhcRinvInLine1 OBJECT-TYPE
        SYNTAX  DisplayString
        MAX-ACCESS  read-only
        STATUS  current
        DESCRIPTION
              "Inventory for the InLine1: This OID contains the inventory for the InLine1"
        ::= { pmoailhcRinvInLine1Entry 2 }




pmoailhcRinvInLine2Table OBJECT-TYPE
      SYNTAX  SEQUENCE OF PmoailhcRinvInLine2Entry
      MAX-ACCESS  not-accessible
      STATUS  current
      DESCRIPTION
              "List of the InLine2 on the selected module"
      ::= { pmoailhcri 7 }

pmoailhcRinvInLine2Entry OBJECT-TYPE
        SYNTAX  PmoailhcRinvInLine2Entry
        MAX-ACCESS  not-accessible
        STATUS  current
        DESCRIPTION
              "Row definition for the InLine2 table"
        INDEX   { pmoailhcRinvInLine2Index }
        ::= { pmoailhcRinvInLine2Table 1 }



PmoailhcRinvInLine2Entry::=
        SEQUENCE {
          pmoailhcRinvInLine2Index
              Integer32,
          pmoailhcRinvInLine2
              DisplayString
        }


    pmoailhcRinvInLine2Index OBJECT-TYPE
        SYNTAX  Integer32(1..16)
        MAX-ACCESS  read-only
        STATUS  current
        DESCRIPTION
              "Index for InLine2 table"
        ::= { pmoailhcRinvInLine2Entry 1 }


    pmoailhcRinvInLine2 OBJECT-TYPE
        SYNTAX  DisplayString
        MAX-ACCESS  read-only
        STATUS  current
        DESCRIPTION
              "Inventory for the InLine2: This OID contains the inventory for the InLine2"
        ::= { pmoailhcRinvInLine2Entry 2 }








--- *****************************************************
--- $$$$$$$$$$$$$$$$$$$$$$$$$$$$$$$$$$$$$$$$$$$$$$$$$$$$$
---     ALARMS
--- $$$$$$$$$$$$$$$$$$$$$$$$$$$$$$$$$$$$$$$$$$$$$$$$$$$$$
--- *****************************************************



--- *****************************************************
---     LEAF for the synthAlm0 article
--- *****************************************************
pmoailhcAlmsynthAlm0 OBJECT IDENTIFIER ::= { pmoailhcAlmOtherCrit 0 }




pmoailhcAlmDefFuseB OBJECT-TYPE
	  SYNTAX EkiOnOff
	  MAX-ACCESS read-only
	  STATUS current
	  DESCRIPTION
        "
        Fuse B Fail :This OID indicates
        that the fuse of the power input
        B is in fail condition  <Help>
          Status of the Fuse B <Condtype>
        DEF_FUSE_B <Probcause> powerProblem
        (36) <Alarmtype> equipmentAlarm
        (5) <Polarity> (2)
        "
	  ::= { pmoailhcAlmsynthAlm0 16 }



pmoailhcAlmDefFuseA OBJECT-TYPE
	  SYNTAX EkiOnOff
	  MAX-ACCESS read-only
	  STATUS current
	  DESCRIPTION
        "
        Fuse A Fail :This OID indicates
        that the fuse of the power input
        A is in fail condition  <Help>
          Status of the Fuse A <Condtype>
        DEF_FUSE_A <Probcause> powerProblem
        (36) <Alarmtype> equipmentAlarm
        (5) <Polarity> (2)
        "
	  ::= { pmoailhcAlmsynthAlm0 15 }



pmoailhcAlmExtPump2NotLocked OBJECT-TYPE
	  SYNTAX EkiOnOff
	  MAX-ACCESS read-only
	  STATUS current
	  DESCRIPTION
        "
        External Pump2 Not Detected :This
        OID indicates that the second external
        pump is not detected by the amplifier
        module  <Help>  This alarm indicates
        if the second external pump is
         detected by the amplifier module
        <Condtype> EXT_PUMP2_NOT_LOCKED
        <Probcause> pumpFailure (39) <Alarmtype>
        equipmentAlarm (5) <Polarity> (2)
        "
	  ::= { pmoailhcAlmsynthAlm0 13 }



pmoailhcAlmExtPump1NotLocked OBJECT-TYPE
	  SYNTAX EkiOnOff
	  MAX-ACCESS read-only
	  STATUS current
	  DESCRIPTION
        "
        External Pump1 Not Detected :This
        OID indicates that the first external
        pump is not detected by the amplifier
        module  <Help>  This alarm indicates
        if the first external pump is detected
        by the amplifier module <Condtype>
        EXT_PUMP1_NOT_LOCKED <Probcause>
        pumpFailure (39) <Alarmtype> equipmentAlarm
        (5) <Polarity> (2)
        "
	  ::= { pmoailhcAlmsynthAlm0 12 }



pmoailhcAlmDwEdfaInitNotCompl OBJECT-TYPE
	  SYNTAX EkiOnOff
	  MAX-ACCESS read-only
	  STATUS current
	  DESCRIPTION
        "
        IL2 Not Initialized :This OID
         indicates that the initialisation
        of the IL2 is not completed  <Help>
         This status indicates if the IL2
        has been correctly initialized
         <Condtype> DW_EDFA_INIT_NOT_COMPL
        <Probcause> other (1) <Alarmtype>
        other (1) <Polarity> (2)
        "
	  ::= { pmoailhcAlmsynthAlm0 11 }



pmoailhcAlmUpEdfaInitNotCompl OBJECT-TYPE
	  SYNTAX EkiOnOff
	  MAX-ACCESS read-only
	  STATUS current
	  DESCRIPTION
        "
        IL1 Not Initialized :This OID
         indicates that the initialisation
        of the IL1 is not completed  <Help>
         This status indicates if the IL1
        has been correctly initialized
         <Condtype> UP_EDFA_INIT_NOT_COMPL
        <Probcause> other (1) <Alarmtype>
        other (1) <Polarity> (2)
        "
	  ::= { pmoailhcAlmsynthAlm0 10 }



pmoailhcAlmModGlobFail OBJECT-TYPE
	  SYNTAX EkiOnOff
	  MAX-ACCESS read-only
	  STATUS current
	  DESCRIPTION
        "
        Module Failure :This OID is set
        on detection of a failure originating
        from the PM <Condtype> MOD_GLOB_FAIL
        <Probcause> equipmentMalfunction
        (16) <Alarmtype> synthesisAlarm
        (12)  <Polarity> (2)
        "
	  ::= { pmoailhcAlmsynthAlm0 9 }



pmoailhcAlmAprOn OBJECT-TYPE
	  SYNTAX EkiOnOff
	  MAX-ACCESS read-only
	  STATUS current
	  DESCRIPTION
        "
        Automatic Power Reduction :This
        OID indicates that the APR algorithm
        has been operated and the  output
        of the lasers are shutdown  <Help>
          The APR algorithm has been completed
         <Condtype> APR_ON <Probcause>
         other (1) <Alarmtype> other (1)
        <Polarity> (2)
        "
	  ::= { pmoailhcAlmsynthAlm0 2 }



pmoailhcAlmMaintenanceMode OBJECT-TYPE
	  SYNTAX EkiOnOff
	  MAX-ACCESS read-only
	  STATUS current
	  DESCRIPTION
        "
        Maintenance Mode :This OID indicates
        that the PM is in maintenance mode
         <Help>  This status indiates if
        the module is currently in maintenance
        mode <Condtype> MAINTENANCE_MODE
        <Probcause> other (1) <Alarmtype>
        other (1) <Polarity> (2)
        "
	  ::= { pmoailhcAlmsynthAlm0 1 }



--- *****************************************************
---     LEAF for the synthAlm2 article
--- *****************************************************
pmoailhcAlmsynthAlm2 OBJECT IDENTIFIER ::= { pmoailhcAlmOtherNurg 2 }




pmoailhcAlmConfTableLoad OBJECT-TYPE
	  SYNTAX EkiOnOff
	  MAX-ACCESS read-only
	  STATUS current
	  DESCRIPTION
        "
        PM Configuration Load :This OID
         is at 1 during the loading of
         configuration tables in the modules
        RAM. <Condtype> CONF_TABLE_LOAD
        <Probcause> bandwidthReduced(4)
        <Alarmtype> other (1) <Polarity>
        (2)
        "
	  ::= { pmoailhcAlmsynthAlm2 3 }



pmoailhcAlmInvUpload OBJECT-TYPE
	  SYNTAX EkiOnOff
	  MAX-ACCESS read-only
	  STATUS current
	  DESCRIPTION
        "
        Inventory Upload :This OID is
         at 1 during the uploading of PM
        inventory information. <Condtype>
        INV_UPLOAD <Probcause> bandwidthReduced(4)
        <Alarmtype> other (1) <Polarity>
        (2)
        "
	  ::= { pmoailhcAlmsynthAlm2 2 }



pmoailhcAlmConfTableSave OBJECT-TYPE
	  SYNTAX EkiOnOff
	  MAX-ACCESS read-only
	  STATUS current
	  DESCRIPTION
        "
        PM Configuration Save :This OID
        is at 1 during the saving of a
         new configuration table in the
        module Flash memory. <Condtype>
        CONF_TABLE_SAVE <Probcause> bandwidthReduced(4)
        <Alarmtype> other (1) <Polarity>
        (2)
        "
	  ::= { pmoailhcAlmsynthAlm2 1 }



--- *****************************************************
---     LEAF for the synthAlm7 article
--- *****************************************************
pmoailhcAlmsynthAlm7 OBJECT IDENTIFIER ::= { pmoailhcAlmLineCrit 7 }




pmoailhcAlmLineExtPumpFail OBJECT-TYPE
	  SYNTAX EkiOnOff
	  MAX-ACCESS read-only
	  STATUS current
	  DESCRIPTION
        "
        IL1 External Pump Fail :This OID
        indicates that the external pump
        linked to the IL1 is in fail condition
          <Help>  This alarm indicates
         if the external pump linked to
        the IL1 is in fail condition <Condtype>
        LINE_EXT_PUMP_FAIL <Probcause>
         pumpFailure (39) <Alarmtype> equipmentAlarm
        (5) <Polarity> (2)
        "
	  ::= { pmoailhcAlmsynthAlm7 13 }



pmoailhcAlmLineFail OBJECT-TYPE
	  SYNTAX EkiOnOff
	  MAX-ACCESS read-only
	  STATUS current
	  DESCRIPTION
        "
        Line Port Failure :This OID indicates
        a failure on the line port <Condtype>
        LINE_FAIL <Probcause> equipmentMalfunction
        (16) <Alarmtype> synthesisAlarm
        (12)  <Polarity> (2)
        "
	  ::= { pmoailhcAlmsynthAlm7 12 }



pmoailhcAlmLineDdmAlm OBJECT-TYPE
	  SYNTAX EkiOnOff
	  MAX-ACCESS read-only
	  STATUS current
	  DESCRIPTION
        "
        Alarm On Line Optical Module DDM
        :This OID indicates an alarm is
        present coming out of Line optical
        interface DDM <Condtype> LINE_DDM_ALM
        <Probcause> equipmentMalfunction
        (16) <Alarmtype> synthesisAlarm
        (12)  <Polarity> (2)
        "
	  ::= { pmoailhcAlmsynthAlm7 10 }



pmoailhcAlmLineDdmWarning OBJECT-TYPE
	  SYNTAX EkiOnOff
	  MAX-ACCESS read-only
	  STATUS current
	  DESCRIPTION
        "
        Warning On Line Optical Module
        DDM :This OID indicates a warning
        is present coming out of Line optical
        interface DDM <Condtype> LINE_DDM_WARNING
        <Probcause> equipmentMalfunction
        (16) <Alarmtype> synthesisAlarm
        (12)  <Polarity> (2)
        "
	  ::= { pmoailhcAlmsynthAlm7 9 }



pmoailhcAlmLineTxOff OBJECT-TYPE
	  SYNTAX EkiOnOff
	  MAX-ACCESS read-only
	  STATUS current
	  DESCRIPTION
        "
        IL1 Optical Output Shutdown :This
        OID indicates the IL1 optical output
        power is on  <Help>  This status
        indicates if the IL1 laser pump
        is ON or OFF <Condtype> LINE_TX_OFF
        <Probcause> other (1) <Alarmtype>
        equipmentAlarm (5) <Polarity> (2)
        "
	  ::= { pmoailhcAlmsynthAlm7 5 }



pmoailhcAlmLineHwFail OBJECT-TYPE
	  SYNTAX EkiOnOff
	  MAX-ACCESS read-only
	  STATUS current
	  DESCRIPTION
        "
        Line Port HW Failure :This OID
        indicates a failure on line port,
        most probably caused by a HW issue
        <Condtype> LINE_HW_FAIL <Probcause>
        equipmentMalfunction (16) <Alarmtype>
        synthesisAlarm (12)  <Polarity>
        (2)
        "
	  ::= { pmoailhcAlmsynthAlm7 4 }



--- *****************************************************
---     LEAF for the synthAlm8 article
--- *****************************************************
pmoailhcAlmsynthAlm8 OBJECT IDENTIFIER ::= { pmoailhcAlmClientCrit 8 }




pmoailhcAlmClientExtPumpFail OBJECT-TYPE
	  SYNTAX EkiOnOff
	  MAX-ACCESS read-only
	  STATUS current
	  DESCRIPTION
        "
        IL2 External Pump Fail :This OID
        indicates that first external pump
        linked to the IL2 is in fail condition
          <Help>  This alarm indicates
         if the external pump linked to
        the IL2 is in fail condition <Condtype>
        CLIENT_EXT_PUMP_FAIL <Probcause>
        pumpFailure (39) <Alarmtype> equipmentAlarm
        (5) <Polarity> (2)
        "
	  ::= { pmoailhcAlmsynthAlm8 13 }



pmoailhcAlmClientFail OBJECT-TYPE
	  SYNTAX EkiOnOff
	  MAX-ACCESS read-only
	  STATUS current
	  DESCRIPTION
        "
        Client Port Failure :This OID
         indicates a failure on the Client
        port <Condtype> CLIENT_FAIL <Probcause>
        equipmentMalfunction (16) <Alarmtype>
        synthesisAlarm (12)  <Polarity>
        (2)
        "
	  ::= { pmoailhcAlmsynthAlm8 12 }



pmoailhcAlmClientDdmAlm OBJECT-TYPE
	  SYNTAX EkiOnOff
	  MAX-ACCESS read-only
	  STATUS current
	  DESCRIPTION
        "
        Alarm On Client Optical Module
        DDM :This OID indicates an alarm
        is present coming out of Client
        optical interface DDM <Condtype>
        CLIENT_DDM_ALM <Probcause> equipmentMalfunction
        (16) <Alarmtype> synthesisAlarm
        (12)  <Polarity> (2)
        "
	  ::= { pmoailhcAlmsynthAlm8 10 }



pmoailhcAlmClientDdmWarning OBJECT-TYPE
	  SYNTAX EkiOnOff
	  MAX-ACCESS read-only
	  STATUS current
	  DESCRIPTION
        "
        Warning On Client Optical Module
        DDM :This OID indicates a warning
        is present coming out of Client
        optical interface DDM <Condtype>
        CLIENT_DDM_WARNING <Probcause>
         equipmentMalfunction (16) <Alarmtype>
        synthesisAlarm (12)  <Polarity>
        (2)
        "
	  ::= { pmoailhcAlmsynthAlm8 9 }



pmoailhcAlmClientTxOff OBJECT-TYPE
	  SYNTAX EkiOnOff
	  MAX-ACCESS read-only
	  STATUS current
	  DESCRIPTION
        "
        IL2 Optical Output Shutdown :This
        OID indicates the IL2 optical output
        power is on  <Help>  This status
        indicates if the IL2 laser pump
        transceiver laser is ON or OFF
         <Condtype> CLIENT_TX_OFF <Probcause>
        other (1) <Alarmtype> equipmentAlarm
        (5) <Polarity> (2)
        "
	  ::= { pmoailhcAlmsynthAlm8 5 }



pmoailhcAlmClientHwFail OBJECT-TYPE
	  SYNTAX EkiOnOff
	  MAX-ACCESS read-only
	  STATUS current
	  DESCRIPTION
        "
        Client Port HW Failure :This OID
        indicates a failure on Client port,
        most probably caused by a HW issue
        <Condtype> CLIENT_HW_FAIL <Probcause>
        equipmentMalfunction (16) <Alarmtype>
        synthesisAlarm (12)  <Polarity>
        (2)
        "
	  ::= { pmoailhcAlmsynthAlm8 4 }



--- *****************************************************
---     LEAF for the clientEdfaAlarms1 article
--- *****************************************************
pmoailhcAlmclientEdfaAlarms1 OBJECT IDENTIFIER ::= { pmoailhcAlmClientUrg 32 }




pmoailhcAlmClientBiasHighAlarm OBJECT-TYPE
	  SYNTAX EkiOnOff
	  MAX-ACCESS read-only
	  STATUS current
	  DESCRIPTION
        "
        IL2 Bias High Alarm :This OID
         indicates that the Bias is higher
        than the alarm theshold of the
         IL2 Optical Module  <Help>  This
        alarm indicates if the IL2 bias
        is too high <Condtype> CLIENT_BIAS_HIGH_ALARM
        <Probcause> pumpFailure (39) <Alarmtype>
        equipmentAlarm (5) <Polarity> (2)
        "
	  ::= { pmoailhcAlmclientEdfaAlarms1 8 }



pmoailhcAlmClientBiasLowAlarm OBJECT-TYPE
	  SYNTAX EkiOnOff
	  MAX-ACCESS read-only
	  STATUS current
	  DESCRIPTION
        "
        IL2 Bias Low Alarm :This OID indicates
        that the Bias is lower than the
        alarm theshold of the IL2 Optical
        Module  <Help>  This alarm indicates
        if the IL2 bias is too low <Condtype>
        CLIENT_BIAS_LOW_ALARM <Probcause>
        pumpFailure (39) <Alarmtype> equipmentAlarm
        (5) <Polarity> (2)
        "
	  ::= { pmoailhcAlmclientEdfaAlarms1 7 }



pmoailhcAlmClientOutputPwrHighAlarm OBJECT-TYPE
	  SYNTAX EkiOnOff
	  MAX-ACCESS read-only
	  STATUS current
	  DESCRIPTION
        "
        IL2 Tx Pwr High Alarm :This OID
        indicates that the Transmit Power
        is higher than the alarm theshold
        of the IL2 Optical Module  <Help>
         This alarm indicates if the IL2
        tx power is too high <Condtype>
        CLIENT_OUTPUT_PWR_HIGH_ALARM <Probcause>
        transmitterFailure (56) <Alarmtype>
        equipmentAlarm (5) <Polarity> (2)
        "
	  ::= { pmoailhcAlmclientEdfaAlarms1 6 }



pmoailhcAlmClientOutputPwrLowAlarm OBJECT-TYPE
	  SYNTAX EkiOnOff
	  MAX-ACCESS read-only
	  STATUS current
	  DESCRIPTION
        "
        IL2 Tx Pwr Low Alarm :This OID
        indicates that the Transmit Power
        is lower than the alarm theshold
        of the IL2 Optical Module  <Help>
         This alarm indicates if the IL2
        tx power is too low <Condtype>
         CLIENT_OUTPUT_PWR_LOW_ALARM <Probcause>
        transmitterFailure (56) <Alarmtype>
        equipmentAlarm (5) <Polarity> (2)
        "
	  ::= { pmoailhcAlmclientEdfaAlarms1 5 }



pmoailhcAlmClientInputPwrHighAlarm OBJECT-TYPE
	  SYNTAX EkiOnOff
	  MAX-ACCESS read-only
	  STATUS current
	  DESCRIPTION
        "
        IL1 Rx Pwr High Alarm :This OID
        indicates that the Receive Power
        is higher than the alarm theshold
        of the IL1 Optical Module  <Help>
         This alarm indicates if the IL1
        rx power is too high <Condtype>
        CLIENT_INPUT_PWR_HIGH_ALARM <Probcause>
        receiveFailure (41) <Alarmtype>
        equipmentAlarm (5) <Polarity> (2)
        "
	  ::= { pmoailhcAlmclientEdfaAlarms1 4 }



pmoailhcAlmClientInputPwrLowAlarm OBJECT-TYPE
	  SYNTAX EkiOnOff
	  MAX-ACCESS read-only
	  STATUS current
	  DESCRIPTION
        "
        IL1 Rx Pwr Low Alarm :This OID
        indicates that the Receive Power
        is lower than the alarm theshold
        of the IL1 Optical Module  <Help>
         This alarm indicates if the IL1
        rx power is too low <Condtype>
         CLIENT_INPUT_PWR_LOW_ALARM <Probcause>
        receiveFailure (41) <Alarmtype>
        equipmentAlarm (5) <Polarity> (2)
        "
	  ::= { pmoailhcAlmclientEdfaAlarms1 3 }



pmoailhcAlmClientGainHighAlarm OBJECT-TYPE
	  SYNTAX EkiOnOff
	  MAX-ACCESS read-only
	  STATUS current
	  DESCRIPTION
        "
        IL2 Gain High Alarm :This OID
         indicates that the Gain is higher
        than the alarm threshold of the
        IL2 Module  <Help>  This alarm
         indicates if the IL2 gain is too
        high <Condtype> CLIENT_GAIN_HIGH_ALARM
        <Probcause> performanceDegraded
        (35) <Alarmtype> equipmentAlarm
        (5) <Polarity> (2)
        "
	  ::= { pmoailhcAlmclientEdfaAlarms1 2 }



pmoailhcAlmClientGainLowAlarm OBJECT-TYPE
	  SYNTAX EkiOnOff
	  MAX-ACCESS read-only
	  STATUS current
	  DESCRIPTION
        "
        IL2 Gain Low Alarm :This OID indicates
        that the Gain is lower than the
        alarm theshold of the IL2 Module
         <Help>  This alarm indicates if
        the IL2 gain is too low <Condtype>
        CLIENT_GAIN_LOW_ALARM <Probcause>
        performanceDegraded (35) <Alarmtype>
        equipmentAlarm (5) <Polarity> (2)
        "
	  ::= { pmoailhcAlmclientEdfaAlarms1 1 }



--- *****************************************************
---     LEAF for the clientEdfaWarnings article
--- *****************************************************
pmoailhcAlmclientEdfaWarnings OBJECT IDENTIFIER ::= { pmoailhcAlmClientNurg 33 }




pmoailhcAlmClientBiasHighWarning OBJECT-TYPE
	  SYNTAX EkiOnOff
	  MAX-ACCESS read-only
	  STATUS current
	  DESCRIPTION
        "
        IL2 Bias High Warning :This OID
        indicates that the Bias is higher
        than the Warning theshold of the
        IL2 Optical Module  <Help>  This
        warning indicates if the IL2 bias
        is too high <Condtype> CLIENT_BIAS_HIGH_WARNING
        <Probcause> pumpFailure (39) <Alarmtype>
        equipmentAlarm (5) <Polarity> (2)
        "
	  ::= { pmoailhcAlmclientEdfaWarnings 8 }



pmoailhcAlmClientBiasLowWarning OBJECT-TYPE
	  SYNTAX EkiOnOff
	  MAX-ACCESS read-only
	  STATUS current
	  DESCRIPTION
        "
        IL2 Bias Low Warning :This OID
        indicates that the Bias is lower
        than the Warning theshold of the
        IL2 Optical Module  <Help>  This
        warning indicates if the IL2 bias
        is too low <Condtype> CLIENT_BIAS_LOW_WARNING
        <Probcause> pumpFailure (39) <Alarmtype>
        equipmentAlarm (5) <Polarity> (2)
        "
	  ::= { pmoailhcAlmclientEdfaWarnings 7 }



pmoailhcAlmClientOutputPwrHighWarning OBJECT-TYPE
	  SYNTAX EkiOnOff
	  MAX-ACCESS read-only
	  STATUS current
	  DESCRIPTION
        "
        IL2 Tx Pwr High Warning :This
         OID indicates that the Transmit
        Power is higher than the Warning
        theshold of the IL2 Optical Module
         <Help>  This warning indicates
        if the IL2 tx power is too high
        <Condtype> CLIENT_OUTPUT_PWR_HIGH_WARNING
        <Probcause> transmitterFailure
         (56) <Alarmtype> equipmentAlarm
        (5) <Polarity> (2)
        "
	  ::= { pmoailhcAlmclientEdfaWarnings 6 }



pmoailhcAlmClientOutputPwrLowWarning OBJECT-TYPE
	  SYNTAX EkiOnOff
	  MAX-ACCESS read-only
	  STATUS current
	  DESCRIPTION
        "
        IL2 Tx Pwr Low Warning :This OID
        indicates that the Transmit Power
        is lower than the Warning theshold
        of the IL2 Optical Module  <Help>
         This warning indicates if the
         IL2 tx power is too low <Condtype>
        CLIENT_OUTPUT_PWR_LOW_WARNING <Probcause>
        transmitterFailure (56) <Alarmtype>
        equipmentAlarm (5) <Polarity> (2)
        "
	  ::= { pmoailhcAlmclientEdfaWarnings 5 }



pmoailhcAlmClientInputPwrHighWarning OBJECT-TYPE
	  SYNTAX EkiOnOff
	  MAX-ACCESS read-only
	  STATUS current
	  DESCRIPTION
        "
        IL1 Rx Pwr High Warning :This
         OID indicates that the Receive
        Power is higher than the Warning
        theshold of the IL1 Optical Module
         <Help>  This warning indicates
        if the IL1 rx power is too high
        <Condtype> CLIENT_INPUT_PWR_HIGH_WARNING
        <Probcause> receiveFailure (41)
        <Alarmtype> equipmentAlarm (5)
         <Polarity> (2)
        "
	  ::= { pmoailhcAlmclientEdfaWarnings 4 }



pmoailhcAlmClientInputPwrLowWarning OBJECT-TYPE
	  SYNTAX EkiOnOff
	  MAX-ACCESS read-only
	  STATUS current
	  DESCRIPTION
        "
        IL1 Rx Pwr Low Warning :This OID
        indicates that the Receive Power
        is lower than the Warning theshold
        of the IL1 Optical Module  <Help>
         This warning indicates if the
         IL1 rx power is too low <Condtype>
        CLIENT_INPUT_PWR_LOW_WARNING <Probcause>
        receiveFailure (41) <Alarmtype>
        equipmentAlarm (5) <Polarity> (2)
        "
	  ::= { pmoailhcAlmclientEdfaWarnings 3 }



pmoailhcAlmClientGainHighWarning OBJECT-TYPE
	  SYNTAX EkiOnOff
	  MAX-ACCESS read-only
	  STATUS current
	  DESCRIPTION
        "
        IL2 Gain High Warning :This OID
        indicates that the Gain is higher
        than the Warning threshold of the
        IL2 Module  <Help>  This alarm
         indicates if the IL2 gain is too
        high <Condtype> CLIENT_GAIN_HIGH_WARNING
        <Probcause> performanceDegraded
        (35) <Alarmtype> equipmentAlarm
        (5) <Polarity> (2)
        "
	  ::= { pmoailhcAlmclientEdfaWarnings 2 }



pmoailhcAlmClientGainLowWarning OBJECT-TYPE
	  SYNTAX EkiOnOff
	  MAX-ACCESS read-only
	  STATUS current
	  DESCRIPTION
        "
        IL2 Gain Low Warning :This OID
        indicates that the Gain is lower
        than the Warning theshold of the
        IL2 Module  <Help>  This alarm
         indicates if the IL2 gain is too
        low <Condtype> CLIENT_GAIN_LOW_WARNING
        <Probcause> performanceDegraded
        (35) <Alarmtype> equipmentAlarm
        (5) <Polarity> (2)
        "
	  ::= { pmoailhcAlmclientEdfaWarnings 1 }



--- *****************************************************
---     LEAF for the clientEdfaAlarms2 article
--- *****************************************************
pmoailhcAlmclientEdfaAlarms2 OBJECT IDENTIFIER ::= { pmoailhcAlmClientCrit 35 }




pmoailhcAlmClientExtPumpEdfaLowCurrent OBJECT-TYPE
	  SYNTAX EkiOnOff
	  MAX-ACCESS read-only
	  STATUS current
	  DESCRIPTION
        "
        IL2 Pump Low Current :This OID
        indicates that the EDFA pump current
        of IL2 is too low because of the
        external pump high power<Help>
          This alarm (only active when
         there is at least on external
         pump) indicates that the EDFA
         pump current of the IL2 is too
        low because of the external pump
        high power. <Condtype> CLIENT_EXT_PUMP_EDFA_LOW_CURRENT
        <Probcause> pumpFailure (39) <Alarmtype>
        equipmentAlarm (5)  <Polarity>
         (2)
        "
	  ::= { pmoailhcAlmclientEdfaAlarms2 5 }



pmoailhcAlmClientEdfaLos OBJECT-TYPE
	  SYNTAX EkiOnOff
	  MAX-ACCESS read-only
	  STATUS current
	  DESCRIPTION
        "
        IL1 Loss Of Signal :This OID indicates
        a Loss of Signal on the IL1 Optical
        Module  <Help>  This alarm indicates
        if an optical signal is detected
        on the IL1 input <Condtype> CLIENT_EDFA_LOS
        <Probcause> receiveFailure (41)
        <Alarmtype> physicalViolation (9)
        <Polarity> (2)
        "
	  ::= { pmoailhcAlmclientEdfaAlarms2 4 }



pmoailhcAlmClientEdfaLaserFail OBJECT-TYPE
	  SYNTAX EkiOnOff
	  MAX-ACCESS read-only
	  STATUS current
	  DESCRIPTION
        "
        IL2 Pump Laser Fail :This OID
         indicates a Transmit Laser Fail
        on the IL2 Optical Module  <Help>
         This alarm indicates if the laser
        of the IL2 is in fail condition
        <Condtype> CLIENT_EDFA_LASER_FAIL
        <Probcause> pumpFailure (39) <Alarmtype>
        equipmentAlarm (5) <Polarity> (2)
        "
	  ::= { pmoailhcAlmclientEdfaAlarms2 3 }



pmoailhcAlmClientEdfaTecFail OBJECT-TYPE
	  SYNTAX EkiOnOff
	  MAX-ACCESS read-only
	  STATUS current
	  DESCRIPTION
        "
        IL2 TEC Fail :This OID indicates
        that the TEC is in fail condition
        on the IL2 Optical Module  <Help>
         This alarm indicates if the TEC
        of the IL2 is in fail condition
        <Condtype> CLIENT_EDFA_TEC_FAIL
        <Probcause> pumpFailure (39) <Alarmtype>
        equipmentAlarm (5) <Polarity> (2)
        "
	  ::= { pmoailhcAlmclientEdfaAlarms2 2 }



pmoailhcAlmClientEdfaNr OBJECT-TYPE
	  SYNTAX EkiOnOff
	  MAX-ACCESS read-only
	  STATUS current
	  DESCRIPTION
        "
        IL2 Optical Module Not Ready :This
        OID indicates that the IL2 Optical
        Module is not ready  <Help>  This
        status indicates if the IL2 has
        been correctly initialized <Condtype>
        CLIENT_EDFA_NR <Probcause> equipmentMalfunction
        (16) <Alarmtype> equipmentAlarm
        (5) <Polarity> (2)
        "
	  ::= { pmoailhcAlmclientEdfaAlarms2 1 }



--- *****************************************************
---     LEAF for the lineEdfaAlarms1 article
--- *****************************************************
pmoailhcAlmlineEdfaAlarms1 OBJECT IDENTIFIER ::= { pmoailhcAlmLineUrg 40 }




pmoailhcAlmLineBiasHighAlarm OBJECT-TYPE
	  SYNTAX EkiOnOff
	  MAX-ACCESS read-only
	  STATUS current
	  DESCRIPTION
        "
        IL1 Bias High Alarm :This OID
         indicates that the Bias is higher
        than the alarm theshold of the
         IL1 Optical Module  <Help>  This
        alarm indicates if the IL1 bias
        is too high <Condtype> LINE_BIAS_HIGH_ALARM
        <Probcause> pumpFailure (39) <Alarmtype>
        equipmentAlarm (5) <Polarity> (2)
        "
	  ::= { pmoailhcAlmlineEdfaAlarms1 8 }



pmoailhcAlmLineBiasLowAlarm OBJECT-TYPE
	  SYNTAX EkiOnOff
	  MAX-ACCESS read-only
	  STATUS current
	  DESCRIPTION
        "
        IL1 Bias Low Alarm :This OID indicates
        that the Bias is lower than the
        alarm theshold of the IL1 Optical
        Module  <Help>  This alarm indicates
        if the IL1 bias is too low <Condtype>
        LINE_BIAS_LOW_ALARM <Probcause>
        pumpFailure (39) <Alarmtype> equipmentAlarm
        (5) <Polarity> (2)
        "
	  ::= { pmoailhcAlmlineEdfaAlarms1 7 }



pmoailhcAlmLineOutputPwrHighAlarm OBJECT-TYPE
	  SYNTAX EkiOnOff
	  MAX-ACCESS read-only
	  STATUS current
	  DESCRIPTION
        "
        IL1 Tx Pwr High Alarm :This OID
        indicates that the Transmit Power
        is higher than the alarm theshold
        of the IL1 Optical Module  <Help>
         This alarm indicates if the IL1
        tx power is too high <Condtype>
        LINE_OUTPUT_PWR_HIGH_ALARM <Probcause>
        transmitterFailure (56) <Alarmtype>
        equipmentAlarm (5) <Polarity> (2)
        "
	  ::= { pmoailhcAlmlineEdfaAlarms1 6 }



pmoailhcAlmLineOutputPwrLowAlarm OBJECT-TYPE
	  SYNTAX EkiOnOff
	  MAX-ACCESS read-only
	  STATUS current
	  DESCRIPTION
        "
        IL1 Tx Pwr Low Alarm :This OID
        indicates that the Transmit Power
        is lower than the alarm theshold
        of the IL1 Optical Module  <Help>
         This alarm indicates if the IL1
        tx power is too low <Condtype>
         LINE_OUTPUT_PWR_LOW_ALARM <Probcause>
        transmitterFailure (56) <Alarmtype>
        equipmentAlarm (5) <Polarity> (2)
        "
	  ::= { pmoailhcAlmlineEdfaAlarms1 5 }



pmoailhcAlmLineInputPwrHighAlarm OBJECT-TYPE
	  SYNTAX EkiOnOff
	  MAX-ACCESS read-only
	  STATUS current
	  DESCRIPTION
        "
        IL2 Rx Pwr High Alarm :This OID
        indicates that the Receive Power
        is higher than the alarm theshold
        of the IL2 Optical Module  <Help>
         This alarm indicates if the IL2
        rx power is too high <Condtype>
        LINE_INPUT_PWR_HIGH_ALARM <Probcause>
        receiveFailure (41) <Alarmtype>
        equipmentAlarm (5) <Polarity> (2)
        "
	  ::= { pmoailhcAlmlineEdfaAlarms1 4 }



pmoailhcAlmLineInputPwrLowAlarm OBJECT-TYPE
	  SYNTAX EkiOnOff
	  MAX-ACCESS read-only
	  STATUS current
	  DESCRIPTION
        "
        IL2 Rx Pwr Low Alarm :This OID
        indicates that the Receive Power
        is lower than the alarm theshold
        of the IL2 Optical Module  <Help>
         This alarm indicates if the IL2
        rx power is too low <Condtype>
         LINE_INPUT_PWR_LOW_ALARM <Probcause>
        receiveFailure (41) <Alarmtype>
        equipmentAlarm (5) <Polarity> (2)
        "
	  ::= { pmoailhcAlmlineEdfaAlarms1 3 }



pmoailhcAlmLineGainHighAlarm OBJECT-TYPE
	  SYNTAX EkiOnOff
	  MAX-ACCESS read-only
	  STATUS current
	  DESCRIPTION
        "
        IL1 Gain High Alarm :This OID
         indicates that the Gain is higher
        than the alarm threshold of the
        IL1 Module  <Help>  This alarm
         indicates if the IL1 gain is too
        high <Condtype> LINE_GAIN_HIGH_ALARM
        <Probcause> performanceDegraded
        (35) <Alarmtype> equipmentAlarm
        (5) <Polarity> (2)
        "
	  ::= { pmoailhcAlmlineEdfaAlarms1 2 }



pmoailhcAlmLineGainLowAlarm OBJECT-TYPE
	  SYNTAX EkiOnOff
	  MAX-ACCESS read-only
	  STATUS current
	  DESCRIPTION
        "
        IL1 Gain Low Alarm :This OID indicates
        that the Gain is lower than the
        alarm theshold of the IL1 Module
         <Help>  This alarm indicates if
        the IL1 gain is too low <Condtype>
        LINE_GAIN_LOW_ALARM <Probcause>
        performanceDegraded (35) <Alarmtype>
        equipmentAlarm (5) <Polarity> (2)
        "
	  ::= { pmoailhcAlmlineEdfaAlarms1 1 }



--- *****************************************************
---     LEAF for the lineEdfaWarnings article
--- *****************************************************
pmoailhcAlmlineEdfaWarnings OBJECT IDENTIFIER ::= { pmoailhcAlmLineNurg 41 }




pmoailhcAlmLineBiasHighWarning OBJECT-TYPE
	  SYNTAX EkiOnOff
	  MAX-ACCESS read-only
	  STATUS current
	  DESCRIPTION
        "
        IL1 Bias High Warning :This OID
        indicates that the Bias is higher
        than the Warning theshold of the
        IL1 Optical Module  <Help>  This
        warning indicates if the IL1 bias
        is too high <Condtype> LINE_BIAS_HIGH_WARNING
        <Probcause> pumpFailure (39) <Alarmtype>
        equipmentAlarm (5) <Polarity> (2)
        "
	  ::= { pmoailhcAlmlineEdfaWarnings 8 }



pmoailhcAlmLineBiasLowWarning OBJECT-TYPE
	  SYNTAX EkiOnOff
	  MAX-ACCESS read-only
	  STATUS current
	  DESCRIPTION
        "
        IL1 Bias Low Warning :This OID
        indicates that the Bias is lower
        than the Warning theshold of the
        IL1 Optical Module  <Help>  This
        warning indicates if the IL1 bias
        is too low <Condtype> LINE_BIAS_LOW_WARNING
        <Probcause> pumpFailure (39) <Alarmtype>
        equipmentAlarm (5) <Polarity> (2)
        "
	  ::= { pmoailhcAlmlineEdfaWarnings 7 }



pmoailhcAlmLineOutputPwrHighWarning OBJECT-TYPE
	  SYNTAX EkiOnOff
	  MAX-ACCESS read-only
	  STATUS current
	  DESCRIPTION
        "
        IL1 Tx Pwr High Warning :This
         OID indicates that the Transmit
        Power is higher than the Warning
        theshold of the IL1 Optical Module
         <Help>  This warning indicates
        if the IL1 tx power is too high
        <Condtype> LINE_OUTPUT_PWR_HIGH_WARNING
        <Probcause> transmitterFailure
         (56) <Alarmtype> equipmentAlarm
        (5) <Polarity> (2)
        "
	  ::= { pmoailhcAlmlineEdfaWarnings 6 }



pmoailhcAlmLineOutputPwrLowWarning OBJECT-TYPE
	  SYNTAX EkiOnOff
	  MAX-ACCESS read-only
	  STATUS current
	  DESCRIPTION
        "
        IL1 Tx Pwr Low Warning :This OID
        indicates that the Transmit Power
        is lower than the Warning theshold
        of the IL1 Optical Module  <Help>
         This warning indicates if the
         IL1 tx power is too low <Condtype>
        LINE_OUTPUT_PWR_LOW_WARNING <Probcause>
        transmitterFailure (56) <Alarmtype>
        equipmentAlarm (5) <Polarity> (2)
        "
	  ::= { pmoailhcAlmlineEdfaWarnings 5 }



pmoailhcAlmLineInputPwrHighWarning OBJECT-TYPE
	  SYNTAX EkiOnOff
	  MAX-ACCESS read-only
	  STATUS current
	  DESCRIPTION
        "
        IL2 Rx Pwr High Warning :This
         OID indicates that the Receive
        Power is higher than the Warning
        theshold of the IL2 Optical Module
         <Help>  This warning indicates
        if the IL2 rx power is too high
        <Condtype> LINE_INPUT_PWR_HIGH_WARNING
        <Probcause> receiveFailure (41)
        <Alarmtype> equipmentAlarm (5)
         <Polarity> (2)
        "
	  ::= { pmoailhcAlmlineEdfaWarnings 4 }



pmoailhcAlmLineInputPwrLowWarning OBJECT-TYPE
	  SYNTAX EkiOnOff
	  MAX-ACCESS read-only
	  STATUS current
	  DESCRIPTION
        "
        IL2 Rx Pwr Low Warning :This OID
        indicates that the Receive Power
        is lower than the Warning theshold
        of the IL2 Optical Module  <Help>
         This warning indicates if the
         IL2 rx power is too low <Condtype>
        LINE_INPUT_PWR_LOW_WARNING <Probcause>
        receiveFailure (41) <Alarmtype>
        equipmentAlarm (5) <Polarity> (2)
        "
	  ::= { pmoailhcAlmlineEdfaWarnings 3 }



pmoailhcAlmLineGainHighWarning OBJECT-TYPE
	  SYNTAX EkiOnOff
	  MAX-ACCESS read-only
	  STATUS current
	  DESCRIPTION
        "
        IL1 Gain High Warning :This OID
        indicates that the Gain is higher
        than the Warning threshold of the
        IL1 Module  <Help>  This alarm
         indicates if the IL1 gain is too
        high <Condtype> LINE_GAIN_HIGH_WARNING
        <Probcause> performanceDegraded
        (35) <Alarmtype> equipmentAlarm
        (5) <Polarity> (2)
        "
	  ::= { pmoailhcAlmlineEdfaWarnings 2 }



pmoailhcAlmLineGainLowWarning OBJECT-TYPE
	  SYNTAX EkiOnOff
	  MAX-ACCESS read-only
	  STATUS current
	  DESCRIPTION
        "
        IL1 Gain Low Warning :This OID
        indicates that the Gain is lower
        than the Warning theshold of the
        IL1 Module  <Help>  This alarm
         indicates if the IL1 gain is too
        low <Condtype> LINE_GAIN_LOW_WARNING
        <Probcause> performanceDegraded
        (35) <Alarmtype> equipmentAlarm
        (5) <Polarity> (2)
        "
	  ::= { pmoailhcAlmlineEdfaWarnings 1 }



--- *****************************************************
---     LEAF for the lineEdfaAlarms2 article
--- *****************************************************
pmoailhcAlmlineEdfaAlarms2 OBJECT IDENTIFIER ::= { pmoailhcAlmLineCrit 43 }




pmoailhcAlmLineExtPumpEdfaLowCurrent OBJECT-TYPE
	  SYNTAX EkiOnOff
	  MAX-ACCESS read-only
	  STATUS current
	  DESCRIPTION
        "
        IL1 Pump Low Current :This OID
        indicates that the EDFA pump current
        of IL1 is too low because of the
        external pump high power<Help>
          This alarm (only active when
         there is at least on external
         pump) indicates that the EDFA
         pump current of the IL1 is too
        low because of the external pump
        high power. <Condtype> LINE_EXT_PUMP_EDFA_LOW_CURRENT
        <Probcause> pumpFailure (39) <Alarmtype>
        equipmentAlarm (5)  <Polarity>
         (2)
        "
	  ::= { pmoailhcAlmlineEdfaAlarms2 5 }



pmoailhcAlmLineEdfaLos OBJECT-TYPE
	  SYNTAX EkiOnOff
	  MAX-ACCESS read-only
	  STATUS current
	  DESCRIPTION
        "
        IL2 Loss Of Signal :This OID indicates
        a Loss of Signal on the IL2 Optical
        Module  <Help>  This alarm indicates
        if an optical signal is detected
        on the IL2 input <Condtype> LINE_EDFA_LOS
        <Probcause> receiveFailure (41)
        <Alarmtype> physicalViolation (9)
        <Polarity> (2)
        "
	  ::= { pmoailhcAlmlineEdfaAlarms2 4 }



pmoailhcAlmLineEdfaLaserFail OBJECT-TYPE
	  SYNTAX EkiOnOff
	  MAX-ACCESS read-only
	  STATUS current
	  DESCRIPTION
        "
        IL1 Pump Laser Fail :This OID
         indicates a Transmit Laser Fail
        on the IL1 Optical Module  <Help>
         This alarm indicates if the laser
        of the IL1 is in fail condition
        <Condtype> LINE_EDFA_LASER_FAIL
        <Probcause> pumpFailure (39) <Alarmtype>
        equipmentAlarm (5) <Polarity> (2)
        "
	  ::= { pmoailhcAlmlineEdfaAlarms2 3 }



pmoailhcAlmLineEdfaTecFail OBJECT-TYPE
	  SYNTAX EkiOnOff
	  MAX-ACCESS read-only
	  STATUS current
	  DESCRIPTION
        "
        IL1 TEC Fail :This OID indicates
        that the TEC is in fail condition
        on the IL1 Optical Module  <Help>
         This alarm indicates if the TEC
        of the IL1 is in fail condition
        <Condtype> LINE_EDFA_TEC_FAIL <Probcause>
        pumpFailure (39) <Alarmtype> equipmentAlarm
        (5) <Polarity> (2)
        "
	  ::= { pmoailhcAlmlineEdfaAlarms2 2 }



pmoailhcAlmLineEdfaNr OBJECT-TYPE
	  SYNTAX EkiOnOff
	  MAX-ACCESS read-only
	  STATUS current
	  DESCRIPTION
        "
        IL1 Optical Module Not Ready :This
        OID indicates that the IL1 Optical
        Module is not ready  <Help>  This
        status indicates if the IL1 has
        been correctly initialized <Condtype>
        LINE_EDFA_NR <Probcause> equipmentMalfunction
        (16) <Alarmtype> equipmentAlarm
        (5) <Polarity> (2)
        "
	  ::= { pmoailhcAlmlineEdfaAlarms2 1 }



--- *****************************************************
---     LEAF for the foaAlarms article
--- *****************************************************
pmoailhcAlmfoaAlarms OBJECT IDENTIFIER ::= { pmoailhcAlmOtherUrg 74 }




pmoailhcAlmTempHighAlarm OBJECT-TYPE
	  SYNTAX EkiOnOff
	  MAX-ACCESS read-only
	  STATUS current
	  DESCRIPTION
        "
        Temperature High Alarm :This OID
        indicates that the PM temperature
        is higher than the alarm threshold
        <Condtype> TEMP_HIGH_ALARM <Probcause>
        temperatureUnacceptable (51) <Alarmtype>
        equipmentAlarm (5) <Polarity> (2)
        "
	  ::= { pmoailhcAlmfoaAlarms 8 }



pmoailhcAlmTermpLowAlarm OBJECT-TYPE
	  SYNTAX EkiOnOff
	  MAX-ACCESS read-only
	  STATUS current
	  DESCRIPTION
        "
        Temperature Low Alarm :This OID
        indicates that the PM temperature
        if lower than the alarm threshold
        <Condtype> TERMP_LOW_ALARM <Probcause>
        temperatureUnacceptable (51) <Alarmtype>
        equipmentAlarm (5) <Polarity> (2)
        "
	  ::= { pmoailhcAlmfoaAlarms 7 }



--- *****************************************************
---     LEAF for the foaWarnings article
--- *****************************************************
pmoailhcAlmfoaWarnings OBJECT IDENTIFIER ::= { pmoailhcAlmOtherNurg 75 }




pmoailhcAlmTempHighWarning OBJECT-TYPE
	  SYNTAX EkiOnOff
	  MAX-ACCESS read-only
	  STATUS current
	  DESCRIPTION
        "
        Temperature High Warning :This
        OID indicates that the PM temperature
        if higher than the Warning threshold
        <Condtype> TEMP_HIGH_WARNING <Probcause>
        temperatureUnacceptable (51) <Alarmtype>
        equipmentAlarm (5) <Polarity> (2)
        "
	  ::= { pmoailhcAlmfoaWarnings 8 }



pmoailhcAlmTermpLowWarning OBJECT-TYPE
	  SYNTAX EkiOnOff
	  MAX-ACCESS read-only
	  STATUS current
	  DESCRIPTION
        "
        Temperature Low Warning :This
         OID indicates that the PM temperature
        if lower than the Warning threshold
        <Condtype> TERMP_LOW_WARNING <Probcause>
        temperatureUnacceptable (51) <Alarmtype>
        equipmentAlarm (5) <Polarity> (2)
        "
	  ::= { pmoailhcAlmfoaWarnings 7 }








--- *****************************************************
--- $$$$$$$$$$$$$$$$$$$$$$$$$$$$$$$$$$$$$$$$$$$$$$$$$$$$$
---     CONTROLS
--- $$$$$$$$$$$$$$$$$$$$$$$$$$$$$$$$$$$$$$$$$$$$$$$$$$$$$
--- *****************************************************



--- *****************************************************
---     LEAF for the synth0 article
--- *****************************************************
pmoailhcCtrlsynth0 OBJECT IDENTIFIER ::= { pmoailhcCtrlOther 0 }




pmoailhcCtrlConfClear OBJECT-TYPE
	  SYNTAX EkiOnOff
	  MAX-ACCESS read-write
	  STATUS current
	  DESCRIPTION
        "
        Clear Configuration Tables :This
        bit clears the configuration tables
        from configuration in the flash.
         <Help>  This control restores
         the default configuration of the
        module
        "
	  ::= { pmoailhcCtrlsynth0 13 }



pmoailhcCtrlConfFlash OBJECT-TYPE
	  SYNTAX EkiOnOff
	  MAX-ACCESS read-write
	  STATUS current
	  DESCRIPTION
        "
        Write Configuration Tables :This
        bit saves the current configuration
        of the module as configuration
         in the flash.  <Help>  This control
        saves the customer configuration
        on the module
        "
	  ::= { pmoailhcCtrlsynth0 9 }



pmoailhcCtrlConfLoad OBJECT-TYPE
	  SYNTAX EkiOnOff
	  MAX-ACCESS read-write
	  STATUS current
	  DESCRIPTION
        "
        Load Configuration Tables :When
        set this enables loading from flash
        configuration1 into the module.
        "
	  ::= { pmoailhcCtrlsynth0 1 }



--- *****************************************************
---     LEAF for the swMgnt article
--- *****************************************************
pmoailhcCtrlswMgnt OBJECT IDENTIFIER ::= { pmoailhcCtrlOther 5 }




pmoailhcCtrlWarmReset OBJECT-TYPE
	  SYNTAX EkiOnOff
	  MAX-ACCESS read-write
	  STATUS current
	  DESCRIPTION
        "
        PM Warm Reset :This OID, when
         set, causes a warm reset of the
        Software. This reset is not traffic
        affecting, and the configuration
        of the Sofwtare remains unchanged.
         <Help>  This control initiates
        a warm reset of the module.
        "
	  ::= { pmoailhcCtrlswMgnt 3 }



pmoailhcCtrlColdReset OBJECT-TYPE
	  SYNTAX EkiOnOff
	  MAX-ACCESS read-write
	  STATUS current
	  DESCRIPTION
        "
        PM Cold Reset :This OID, when
         set, causes a cold reset of the
        Software. This reset is traffic
        affecting, and the configuration
        of Software is reloaded on start-up.
         <Help>  This control initiates
        a cold reset of the module.
        "
	  ::= { pmoailhcCtrlswMgnt 2 }



--- *****************************************************
---     LEAF for the clientEdfaLaserOff article
--- *****************************************************
pmoailhcCtrlclientEdfaLaserOff OBJECT IDENTIFIER ::= { pmoailhcCtrlClient 32 }




pmoailhcCtrlClientEdfaLaserOff OBJECT-TYPE
	  SYNTAX EkiOnOff
	  MAX-ACCESS read-write
	  STATUS current
	  DESCRIPTION
        "
        IL2 Optical Module Laser Off :This
        OID switches OFF the laser of the
        IL2li Optical Module  <Help>  This
        control defines the laser state
        of the IL2
        "
	  ::= { pmoailhcCtrlclientEdfaLaserOff 1 }



--- *****************************************************
---     LEAF for the clientGainCstMonitorValue article
--- *****************************************************

pmoailhcCtrlclientGainCstMonitorValue OBJECT-TYPE
	  SYNTAX INTEGER (0..65535)
	  MAX-ACCESS read-write
	  STATUS current
	  DESCRIPTION
        "
        IL2 Fiber Aging Period :This OID
        sets the value of the monitoring
        period to detect a fiber aging.
        (Unit = s) This value sets the
         monitoring period to detect a
         fiber aging.
        "
	  ::= { pmoailhcCtrlClient 34 }



--- *****************************************************
---     LEAF for the clientGainCstPoutValue article
--- *****************************************************

pmoailhcCtrlclientGainCstPoutValue OBJECT-TYPE
	  SYNTAX INTEGER (0..65535)
	  MAX-ACCESS read-write
	  STATUS current
	  DESCRIPTION
        "
        IL2 Ref Pout :This OID sets the
        value of the reference output power
        used to compensate the fiber aging
         (active only in constant gain
         mode) (AV=(Gain/0,005) + 32768)
        (Unit = dBm) <Help> This value
         defines the reference output power
        used to compensate the fiber aging
        "
	  ::= { pmoailhcCtrlClient 35 }



--- *****************************************************
---     LEAF for the clientGainSettingValue article
--- *****************************************************

pmoailhcCtrlclientGainSettingValue OBJECT-TYPE
	  SYNTAX INTEGER (0..65535)
	  MAX-ACCESS read-write
	  STATUS current
	  DESCRIPTION
        "
        IL2 Gain Target :This OID sets
        the value of the nominal gain of
        the IL2 Module (active only in
         constant output power mode) (AV=(Gain/0,005)
        + 32768) (Unit = dB) <Help> This
        control sets the value of the nominal
        gain of the IL2 Module (active
         only in constant output power
         mode)
        "
	  ::= { pmoailhcCtrlClient 36 }



--- *****************************************************
---     LEAF for the clientGainProcessing article
--- *****************************************************
pmoailhcCtrlclientGainProcessing OBJECT IDENTIFIER ::= { pmoailhcCtrlClient 37 }




pmoailhcCtrlClientGainProc OBJECT-TYPE
	  SYNTAX EkiOnOff
	  MAX-ACCESS read-write
	  STATUS current
	  DESCRIPTION
        "
        IL2 Gain Adjustment :<Help> This
        control initiates the automatic
        nominal gain adjustment on the
         IL2 Module<Help> This control
         initiates the automatic nominal
        gain adjustment on the IL2 Module
        "
	  ::= { pmoailhcCtrlclientGainProcessing 1 }



--- *****************************************************
---     LEAF for the clientGainCstFiberAgingMarginValue article
--- *****************************************************

pmoailhcCtrlclientGainCstFiberAgingMarginValue OBJECT-TYPE
	  SYNTAX INTEGER (0..65535)
	  MAX-ACCESS read-write
	  STATUS current
	  DESCRIPTION
        "
        IL2 Aging Threshold :This OID
         sets the threshold to consider
        the power drop as a fiber aging.
        (active only in constant gain mode)
        (AV=(Gain/0,005) + 32768) (Unit
        = dB) <Help> This value defines
        the threshold to consider the power
        drop as a fiber aging.
        "
	  ::= { pmoailhcCtrlClient 38 }



--- *****************************************************
---     LEAF for the clientGainCstAdddropMarginValue article
--- *****************************************************

pmoailhcCtrlclientGainCstAdddropMarginValue OBJECT-TYPE
	  SYNTAX INTEGER (0..65535)
	  MAX-ACCESS read-write
	  STATUS current
	  DESCRIPTION
        "
        IL2 AddDrop Threshold :This OID
        sets the threshold to not consider
        the power drop as a fiber aging.
         (active only in constant gain
         mode) (AV=(Gain/0,005) + 32768)
        (Unit = dB) <Help> This value defines
        the threshold to not consider the
        power drop as a fiber aging.
        "
	  ::= { pmoailhcCtrlClient 39 }



--- *****************************************************
---     LEAF for the lineEdfaLaserOff article
--- *****************************************************
pmoailhcCtrllineEdfaLaserOff OBJECT IDENTIFIER ::= { pmoailhcCtrlLine 40 }




pmoailhcCtrlLineEdfaLaserOff OBJECT-TYPE
	  SYNTAX EkiOnOff
	  MAX-ACCESS read-write
	  STATUS current
	  DESCRIPTION
        "
        IL1 Optical Module Laser Off :This
        OID switches OFF the laser of the
        IL1 Optical Module  <Help>  This
        control defines the laser state
        of the IL1
        "
	  ::= { pmoailhcCtrllineEdfaLaserOff 1 }



--- *****************************************************
---     LEAF for the lineGainCstMonitorValue article
--- *****************************************************

pmoailhcCtrllineGainCstMonitorValue OBJECT-TYPE
	  SYNTAX INTEGER (0..65535)
	  MAX-ACCESS read-write
	  STATUS current
	  DESCRIPTION
        "
        IL1 Fiber Aging Period :This OID
        sets the value of the monitoring
        period to detect a fiber aging.
        (Unit = s) This value sets the
         monitoring period to detect a
         fiber aging.
        "
	  ::= { pmoailhcCtrlLine 42 }



--- *****************************************************
---     LEAF for the lineGainCstPoutValue article
--- *****************************************************

pmoailhcCtrllineGainCstPoutValue OBJECT-TYPE
	  SYNTAX INTEGER (0..65535)
	  MAX-ACCESS read-write
	  STATUS current
	  DESCRIPTION
        "
        IL1 Ref Pout :This OID sets the
        value of the reference output power
        used to compensate the fiber aging
         (active only in constant gain
         mode) (AV=(Gain/0,005) + 32768)
        (Unit = dBm) <Help> This value
         defines the reference output power
        used to compensate the fiber aging
        "
	  ::= { pmoailhcCtrlLine 43 }



--- *****************************************************
---     LEAF for the lineGainSettingValue article
--- *****************************************************

pmoailhcCtrllineGainSettingValue OBJECT-TYPE
	  SYNTAX INTEGER (0..65535)
	  MAX-ACCESS read-write
	  STATUS current
	  DESCRIPTION
        "
        IL1 Gain Target :This OID sets
        the value of the nominal gain of
        the IL1 Module (active only in
         constant output power mode) (AV=(Gain/0,005)
        + 32768) (Unit = dB) <Help> This
        control sets the value of the nominal
        gain of the IL1 Module (active
         only in constant output power
         mode)
        "
	  ::= { pmoailhcCtrlLine 44 }



--- *****************************************************
---     LEAF for the lineGainProcessing article
--- *****************************************************
pmoailhcCtrllineGainProcessing OBJECT IDENTIFIER ::= { pmoailhcCtrlLine 45 }




pmoailhcCtrlLineGainProc OBJECT-TYPE
	  SYNTAX EkiOnOff
	  MAX-ACCESS read-write
	  STATUS current
	  DESCRIPTION
        "
        IL1 Gain Adjustment :This OID
         initiates the automatic nominal
        gain adjustment on the IL1 Module<Help>
        This control initiates the automatic
        nominal gain adjustment on the
         IL1 Module
        "
	  ::= { pmoailhcCtrllineGainProcessing 1 }



--- *****************************************************
---     LEAF for the lineGainCstFiberAgingMarginValue article
--- *****************************************************

pmoailhcCtrllineGainCstFiberAgingMarginValue OBJECT-TYPE
	  SYNTAX INTEGER (0..65535)
	  MAX-ACCESS read-write
	  STATUS current
	  DESCRIPTION
        "
        IL1 Aging Threshold :This OID
         sets the threshold to consider
        the power drop as a fiber aging.
        (active only in constant gain mode)
        (AV=(Gain/0,005) + 32768) (Unit
        = dB) <Help> This value defines
        the threshold to consider the power
        drop as a fiber aging.
        "
	  ::= { pmoailhcCtrlLine 46 }



--- *****************************************************
---     LEAF for the lineGainCstAdddropMarginValue article
--- *****************************************************

pmoailhcCtrllineGainCstAdddropMarginValue OBJECT-TYPE
	  SYNTAX INTEGER (0..65535)
	  MAX-ACCESS read-write
	  STATUS current
	  DESCRIPTION
        "
        IL1 AddDrop Threshold :This OID
        sets the threshold to not consider
        the power drop as a fiber aging.
         (active only in constant gain
         mode) (AV=(Gain/0,005) + 32768)
        (Unit = dB) <Help> This value defines
        the threshold to not consider the
        power drop as a fiber aging.
        "
	  ::= { pmoailhcCtrlLine 47 }



--- *****************************************************
---     LEAF for the ledTest article
--- *****************************************************
pmoailhcCtrlledTest OBJECT IDENTIFIER ::= { pmoailhcCtrlOther 73 }




pmoailhcCtrlLedOff OBJECT-TYPE
	  SYNTAX EkiOnOff
	  MAX-ACCESS read-write
	  STATUS current
	  DESCRIPTION
        "
        Leds Off :This OID switches off
        all the Leds as a test feature.
         <Help>  This control initiates
        a test leds turning all the LEDs
        to OFF
        "
	  ::= { pmoailhcCtrlledTest 3 }



pmoailhcCtrlRedLed OBJECT-TYPE
	  SYNTAX EkiOnOff
	  MAX-ACCESS read-write
	  STATUS current
	  DESCRIPTION
        "
        Red Leds Test :This OID switches
        on all the red Leds as a test feature.
         <Help>  This control initiates
        a test leds turning all the LEDs
        to red
        "
	  ::= { pmoailhcCtrlledTest 2 }



pmoailhcCtrlGreenLed OBJECT-TYPE
	  SYNTAX EkiOnOff
	  MAX-ACCESS read-write
	  STATUS current
	  DESCRIPTION
        "
        Green Leds Test :This OID switches
        on all the green Leds as a test
        feature.  <Help>  This control
         initiates a test leds turning
         all the LEDs to green
        "
	  ::= { pmoailhcCtrlledTest 1 }



--- *****************************************************
---     LEAF for the maintMode article
--- *****************************************************
pmoailhcCtrlmaintMode OBJECT IDENTIFIER ::= { pmoailhcCtrlOther 75 }




pmoailhcCtrlMaintenance OBJECT-TYPE
	  SYNTAX EkiOnOff
	  MAX-ACCESS read-write
	  STATUS current
	  DESCRIPTION
        "
        PM Maintenance Mode :This OID
         sets the PM in maintenance mode
         <Help>  This control enables the
        maintenance mode of the module
        "
	  ::= { pmoailhcCtrlmaintMode 1 }



--- *****************************************************
---     LEAF for the aprRestart article
--- *****************************************************
pmoailhcCtrlaprRestart OBJECT IDENTIFIER ::= { pmoailhcCtrlOther 76 }




pmoailhcCtrlAprManualRestart OBJECT-TYPE
	  SYNTAX EkiOnOff
	  MAX-ACCESS read-write
	  STATUS current
	  DESCRIPTION
        "
        APR Manual Restart :This OID initiates
        the Restart mechanism to retrieve
        from the APR state.<Help> This
         control initiates the Restart
         mechanism to retrieve from the
        APR state.
        "
	  ::= { pmoailhcCtrlaprRestart 1 }








--- *****************************************************
--- $$$$$$$$$$$$$$$$$$$$$$$$$$$$$$$$$$$$$$$$$$$$$$$$$$$$$
---     MEASURES
--- $$$$$$$$$$$$$$$$$$$$$$$$$$$$$$$$$$$$$$$$$$$$$$$$$$$$$
--- *****************************************************



--- *****************************************************
---     LEAF for the clientEdfaBiasMeas article
--- *****************************************************

pmoailhcMesrclientEdfaBiasMeas OBJECT-TYPE
	  SYNTAX INTEGER (0..65535)
	  MAX-ACCESS read-only
	  STATUS current
	  DESCRIPTION
        "
        IL2 Pump Laser Current :This OID
        gives the pump laser current of
        the IL2 Optical Module (Current
        =AV/100) (Unit = mA)  <Help>  This
        measure gives the bias of the IL2
        pump laser
        "
	  ::= { pmoailhcMesrClient 32 }



--- *****************************************************
---     LEAF for the clientEdfaTxpwrMeas article
--- *****************************************************

pmoailhcMesrclientEdfaTxpwrMeas OBJECT-TYPE
	  SYNTAX INTEGER (0..65535)
	  MAX-ACCESS read-only
	  STATUS current
	  DESCRIPTION
        "
        IL2 Tx Power :This OID gives the
        transmit power value of the IL2
        Optical Module (Power =(AV-32768)*0,005)
         (Unit = dBm)  <Help>  This measure
        gives the Tx optical power of the
        IL2
        "
	  ::= { pmoailhcMesrClient 33 }



--- *****************************************************
---     LEAF for the clientEdfaRxpwrMeas article
--- *****************************************************

pmoailhcMesrclientEdfaRxpwrMeas OBJECT-TYPE
	  SYNTAX INTEGER (0..65535)
	  MAX-ACCESS read-only
	  STATUS current
	  DESCRIPTION
        "
        IL1 Rx Power :This OID gives the
        receive power value of the IL1
         Optical Module (Power =(AV-32768)*0,005)
        (Unit = dBm)  <Help>  This measure
        gives the Rx optical power of the
        IL1
        "
	  ::= { pmoailhcMesrClient 34 }



--- *****************************************************
---     LEAF for the clientEdfaGainMeas article
--- *****************************************************

pmoailhcMesrclientEdfaGainMeas OBJECT-TYPE
	  SYNTAX INTEGER (0..65535)
	  MAX-ACCESS read-only
	  STATUS current
	  DESCRIPTION
        "
        IL2 Gain Target :This OID gives
        the gain value of the IL2 Module
         (Gain =(AV-32768)*0,005) (Unit
        = dB)  <Help>  This information
        gives the target gain of the amplifier
        for optimal performance
        "
	  ::= { pmoailhcMesrClient 35 }



--- *****************************************************
---     LEAF for the clientCorrectedGain article
--- *****************************************************

pmoailhcMesrclientCorrectedGain OBJECT-TYPE
	  SYNTAX INTEGER (0..65535)
	  MAX-ACCESS read-only
	  STATUS current
	  DESCRIPTION
        "
        IL2 Gain :This OID gives the gain
        value of the IL2 Module corrected
        by the ASE compensation mechanism
        (Gain =(AV-32768)*0,005) (Unit
         = dB)   <Help>  This measure gives
        the effective gain of the amplifier
        "
	  ::= { pmoailhcMesrClient 38 }



--- *****************************************************
---     LEAF for the lineEdfaBiasMeas article
--- *****************************************************

pmoailhcMesrlineEdfaBiasMeas OBJECT-TYPE
	  SYNTAX INTEGER (0..65535)
	  MAX-ACCESS read-only
	  STATUS current
	  DESCRIPTION
        "
        IL1 Pump Laser Current :This OID
        gives the pump laser current of
        the IL1 Optical Module  (Current
        =AV/100) (Unit = mA)  <Help>  This
        measure gives the bias of the IL1
        pump laser
        "
	  ::= { pmoailhcMesrLine 40 }



--- *****************************************************
---     LEAF for the lineEdfaTxpwrMeas article
--- *****************************************************

pmoailhcMesrlineEdfaTxpwrMeas OBJECT-TYPE
	  SYNTAX INTEGER (0..65535)
	  MAX-ACCESS read-only
	  STATUS current
	  DESCRIPTION
        "
        IL1 Tx Power :This OID gives the
        transmit power value of the IL1
        Optical Module (Power =(AV-32768)*0,005)
        (Unit = dBm)  <Help>  This measure
        gives the Tx optical power of the
        IL1
        "
	  ::= { pmoailhcMesrLine 41 }



--- *****************************************************
---     LEAF for the lineEdfaRxpwrMeas article
--- *****************************************************

pmoailhcMesrlineEdfaRxpwrMeas OBJECT-TYPE
	  SYNTAX INTEGER (0..65535)
	  MAX-ACCESS read-only
	  STATUS current
	  DESCRIPTION
        "
        IL2 Rx Power :This OID gives the
        receive power value of the IL2
         Optical Module (Power =(AV-32768)*0,005)
        (Unit = dBm)  <Help>  This measure
        gives the Rx optical power of the
        IL2
        "
	  ::= { pmoailhcMesrLine 42 }



--- *****************************************************
---     LEAF for the lineEdfaGainMeas article
--- *****************************************************

pmoailhcMesrlineEdfaGainMeas OBJECT-TYPE
	  SYNTAX INTEGER (0..65535)
	  MAX-ACCESS read-only
	  STATUS current
	  DESCRIPTION
        "
        IL1 Gain Target :This OID gives
        the gain value of the IL1 Module
         (Gain =(AV-32768)*0,005) (Unit
        = dB)  <Help>  This information
        gives the target gain of the amplifier
        for optimal performance
        "
	  ::= { pmoailhcMesrLine 43 }



--- *****************************************************
---     LEAF for the lineCorrectedGain article
--- *****************************************************

pmoailhcMesrlineCorrectedGain OBJECT-TYPE
	  SYNTAX INTEGER (0..65535)
	  MAX-ACCESS read-only
	  STATUS current
	  DESCRIPTION
        "
        IL1 Gain :This OID gives the gain
        value of the IL1 Module corrected
        by the ASE compensation mechanism
        (Gain =(AV-32768)*0,005) (Unit
         = dB)   <Help>  This measure gives
        the effective gain of the amplifier
        "
	  ::= { pmoailhcMesrLine 46 }



--- *****************************************************
---     LEAF for the tempMeas article
--- *****************************************************

pmoailhcMesrtempMeas OBJECT-TYPE
	  SYNTAX INTEGER (0..65535)
	  MAX-ACCESS read-only
	  STATUS current
	  DESCRIPTION
        "
        Module Temperature :This OID gives
        the temperature of the PM  (Temperature
        =AV/256) (Unit = C)  <Help>  This
        measure gives the temperature of
        the module
        "
	  ::= { pmoailhcMesrOther 72 }








--- *****************************************************
--- $$$$$$$$$$$$$$$$$$$$$$$$$$$$$$$$$$$$$$$$$$$$$$$$$$$$$
---     CONFIG
--- $$$$$$$$$$$$$$$$$$$$$$$$$$$$$$$$$$$$$$$$$$$$$$$$$$$$$
--- *****************************************************



--- *****************************************************
---     LEAF for the table Group noValue
--- *****************************************************

pmoailhcCfgNoValue OBJECT IDENTIFIER ::= { pmoailhcConfig 1 }



--- *****************************************************
---     LEAF for the table 2111
--- *****************************************************

pmoailhctableclientStartup OBJECT IDENTIFIER ::= { pmoailhcCfgNoValue 1 }



pmoailhcCfgclientEdfaLaserCtrl OBJECT-TYPE
	  SYNTAX Unsigned32 (0..65536)
	  MAX-ACCESS read-write
	  STATUS current
	  DESCRIPTION
        "
        Default Settings on Client Laser
        :This OID configures the default
        initialisation settings on the
         client laser.
        "
	  ::= { pmoailhctableclientStartup 2 }



pmoailhcCfgclientEdfaLaserMode OBJECT-TYPE
	  SYNTAX Unsigned32 (0..65536)
	  MAX-ACCESS read-write
	  STATUS current
	  DESCRIPTION
        "
        Default Settings on Client mode
        :This OID configures the default
        mode on the client amplifier.
        "
	  ::= { pmoailhctableclientStartup 3 }



pmoailhcCfgclientGainValue OBJECT-TYPE
	  SYNTAX Unsigned32 (0..65536)
	  MAX-ACCESS read-write
	  STATUS current
	  DESCRIPTION
        "
        Default Settings on Client Gain
        :This OID configures the default
        gain on the client amplifier.
        "
	  ::= { pmoailhctableclientStartup 4 }



pmoailhcCfgclientTiltValue OBJECT-TYPE
	  SYNTAX Unsigned32 (0..65536)
	  MAX-ACCESS read-write
	  STATUS current
	  DESCRIPTION
        "
        Default Settings on Client Tilt
        :This OID configures the default
        tilt on the client amplifier.
        "
	  ::= { pmoailhctableclientStartup 5 }



pmoailhcCfgclientMsaLoss OBJECT-TYPE
	  SYNTAX Unsigned32 (0..65536)
	  MAX-ACCESS read-write
	  STATUS current
	  DESCRIPTION
        "
        Default Settings on Client MSA
        :This OID configures the default
        MSA value on the client amplifier.
        "
	  ::= { pmoailhctableclientStartup 6 }



pmoailhcCfgclientOutputPowerValue OBJECT-TYPE
	  SYNTAX Unsigned32 (0..65536)
	  MAX-ACCESS read-write
	  STATUS current
	  DESCRIPTION
        "
        Default Settings on Client Output
        power :This OID configures the
         default Output power value on
         the client amplifier.
        "
	  ::= { pmoailhctableclientStartup 7 }



pmoailhcCfgclientAseCompensation OBJECT-TYPE
	  SYNTAX Unsigned32 (0..65536)
	  MAX-ACCESS read-write
	  STATUS current
	  DESCRIPTION
        "
        Default Settings on Client ASE
        :This OID configures the default
        ASE compensation value on the client
        amplifier.
        "
	  ::= { pmoailhctableclientStartup 8 }



--- *****************************************************
---     LEAF for the table Group lineStartUp
--- *****************************************************

pmoailhcCfgLineStartUp OBJECT IDENTIFIER ::= { pmoailhcConfig 2 }



--- *****************************************************
---     LEAF for the table 2191
--- *****************************************************

pmoailhctablelineStartup OBJECT IDENTIFIER ::= { pmoailhcCfgLineStartUp 1 }



pmoailhcCfglineEdfaLaserCtrl OBJECT-TYPE
	  SYNTAX Unsigned32 (0..65536)
	  MAX-ACCESS read-write
	  STATUS current
	  DESCRIPTION
        "
        Default Settings on Line Laser
        :This OID configures the default
        initialisation settings on the
         line laser.
        "
	  ::= { pmoailhctablelineStartup 2 }



pmoailhcCfglineEdfaLaserMode OBJECT-TYPE
	  SYNTAX Unsigned32 (0..65536)
	  MAX-ACCESS read-write
	  STATUS current
	  DESCRIPTION
        "
        Default Settings on Line mode
         :This OID configures the default
        mode on the line amplifier.
        "
	  ::= { pmoailhctablelineStartup 3 }



pmoailhcCfglineGainValue OBJECT-TYPE
	  SYNTAX Unsigned32 (0..65536)
	  MAX-ACCESS read-write
	  STATUS current
	  DESCRIPTION
        "
        Default Settings on Line Gain
         :This OID configures the default
        gain on the line amplifier.
        "
	  ::= { pmoailhctablelineStartup 4 }



pmoailhcCfglineTiltValue OBJECT-TYPE
	  SYNTAX Unsigned32 (0..65536)
	  MAX-ACCESS read-write
	  STATUS current
	  DESCRIPTION
        "
        Default Settings on Line Tilt
         :This OID configures the default
        tilt on the line amplifier.
        "
	  ::= { pmoailhctablelineStartup 5 }



pmoailhcCfglineMsaLoss OBJECT-TYPE
	  SYNTAX Unsigned32 (0..65536)
	  MAX-ACCESS read-write
	  STATUS current
	  DESCRIPTION
        "
        Default Settings on Line MSA :This
        OID configures the default MSA
         value on the line amplifier.
        "
	  ::= { pmoailhctablelineStartup 6 }



pmoailhcCfglineOutputPowerValue OBJECT-TYPE
	  SYNTAX Unsigned32 (0..65536)
	  MAX-ACCESS read-write
	  STATUS current
	  DESCRIPTION
        "
        Default Settings on Line Output
        power :This OID configures the
         default Output power value on
         the line amplifier.
        "
	  ::= { pmoailhctablelineStartup 7 }



pmoailhcCfglineAseCompensation OBJECT-TYPE
	  SYNTAX Unsigned32 (0..65536)
	  MAX-ACCESS read-write
	  STATUS current
	  DESCRIPTION
        "
        Default Settings on Line ASE :This
        OID configures the default ASE
         compensation value on the line
        amplifier.
        "
	  ::= { pmoailhctablelineStartup 8 }



pmoailhcCfgaprMode OBJECT-TYPE
	  SYNTAX Unsigned32 (0..65536)
	  MAX-ACCESS read-write
	  STATUS current
	  DESCRIPTION
        "
        Default setting on module :This
        OID configures the default mode
        on the APR
        "
	  ::= { pmoailhctablelineStartup 11 }



--- *****************************************************
---     LEAF for the table Group labels
--- *****************************************************

pmoailhcCfgLabels OBJECT IDENTIFIER ::= { pmoailhcConfig 3 }



--- *****************************************************
---     LEAF for the table NO_VALUE
--- *****************************************************

pmoailhcCfgLabelclientTable OBJECT-TYPE
	SYNTAX  SEQUENCE OF PmoailhcCfgLabelclientEntry
	MAX-ACCESS not-accessible
	STATUS current
	DESCRIPTION
        "
        List of  Article
        "
	::= { pmoailhcCfgLabels 1 }


pmoailhcCfgLabelclientEntry OBJECT-TYPE
	SYNTAX PmoailhcCfgLabelclientEntry
	MAX-ACCESS not-accessible
	STATUS current
	DESCRIPTION
        "
        Row definition for the labels
         table
        "
	INDEX   { pmoailhcCfgLabelclientIndex }
	::= { pmoailhcCfgLabelclientTable 1 }


PmoailhcCfgLabelclientEntry ::=
	SEQUENCE {
	pmoailhcCfgLabelclientIndex
		INTEGER,
	pmoailhcCfgLabelclientPortn
		DisplayString
	}


pmoailhcCfgLabelclientIndex OBJECT-TYPE
	SYNTAX  INTEGER(0..128)
	MAX-ACCESS  read-only
	STATUS current
	DESCRIPTION
        "
        Index definition for the labelclient
        table
        "
	::= { pmoailhcCfgLabelclientEntry 1 }


pmoailhcCfgLabelclientPortn OBJECT-TYPE
	SYNTAX  DisplayString( SIZE(1..16))
	MAX-ACCESS read-write
	STATUS current
	DESCRIPTION
        "
        Default settings on the label
         of the Ports :These registers
         configures the default initialisation
        settings of the labels of the ports.
        "
	::= { pmoailhcCfgLabelclientEntry 3 }


--- *****************************************************
---     LEAF for the table NO_VALUE
--- *****************************************************

pmoailhcCfgLabellineTable OBJECT-TYPE
	SYNTAX  SEQUENCE OF PmoailhcCfgLabellineEntry
	MAX-ACCESS not-accessible
	STATUS current
	DESCRIPTION
        "
        List of  Article
        "
	::= { pmoailhcCfgLabels 2 }


pmoailhcCfgLabellineEntry OBJECT-TYPE
	SYNTAX PmoailhcCfgLabellineEntry
	MAX-ACCESS not-accessible
	STATUS current
	DESCRIPTION
        "
        Row definition for the labels
         table
        "
	INDEX   { pmoailhcCfgLabellineIndex }
	::= { pmoailhcCfgLabellineTable 1 }


PmoailhcCfgLabellineEntry ::=
	SEQUENCE {
	pmoailhcCfgLabellineIndex
		INTEGER,
	pmoailhcCfgLabellinePortn
		DisplayString
	}


pmoailhcCfgLabellineIndex OBJECT-TYPE
	SYNTAX  INTEGER(0..128)
	MAX-ACCESS  read-only
	STATUS current
	DESCRIPTION
        "
        Index definition for the labelline
        table
        "
	::= { pmoailhcCfgLabellineEntry 1 }


pmoailhcCfgLabellinePortn OBJECT-TYPE
	SYNTAX  DisplayString( SIZE(1..16))
	MAX-ACCESS read-write
	STATUS current
	DESCRIPTION
        "
        Default settings on the label
         of the lines :These registers
         configures the default initialisation
        settings of the labels of the lines.
        "
	::= { pmoailhcCfgLabellineEntry 3 }



pmoailhcCfgWriteConfiguration  OBJECT-TYPE
	SYNTAX EkiOnOff
	MAX-ACCESS read-write
	STATUS current
	DESCRIPTION
	"Write configuration to module:This OID
	 writes the complete configuration to the module"
	::= { pmoailhcConfig 257 }






--- *****************************************************
---     TRAP OBJECTS
--- *****************************************************

pmoailhctrapBoardNumber OBJECT-TYPE
	SYNTAX INTEGER(1..64)
	MAX-ACCESS read-only
	STATUS current
	DESCRIPTION
	"Last module which generates a trap"
	::= { pmoailhctraps 4 }







--- *****************************************************
---     GLOBAL TRAPS
--- *****************************************************

pmoailhcLineTrapNotUrgentGoesOn NOTIFICATION-TYPE
	OBJECTS {pmoailhcAlmLineDdmWarning, pmoailhctrapBoardNumber}
	STATUS current
	--&FILTNAME    "PMOAILHC Line Not Urgent ON"
	--&ACTIONS     { log, minor }
	--&MATCH       { pmoailhcAlmLineDdmWarning "on", pmoailhctrapBoardNumber "$2"}
	--&MESG        "DDM Warning appears on Pre-Amp input or Booster Output of PMOAILHC in slot $2 ($A)"
	DESCRIPTION "Not urgent Line default is activated"
	::= { pmoailhctraps 30 }

pmoailhcLineTrapNotUrgentGoesOff NOTIFICATION-TYPE
	OBJECTS {pmoailhcAlmLineDdmWarning, pmoailhctrapBoardNumber}
	STATUS current
	--&FILTNAME    "PMOAILHC Line Not Urgent OFF"
	--&ACTIONS     { log, normal }
	--&CLEARS      {"PMOAILHC Line Not Urgent ON"}
	--&MATCH       { pmoailhcAlmLineDdmWarning "on", pmoailhctrapBoardNumber "$2"}
	--&MESG        "DDM Warning disappears on Pre-Amp input or Booster Output of PMOAILHC in slot $2 ($A)"
	DESCRIPTION "Not urgent Line default disappeared"
	::= { pmoailhctraps 31 }

pmoailhcLineTrapUrgentGoesOn NOTIFICATION-TYPE
	OBJECTS {pmoailhcAlmLineDdmAlm, pmoailhctrapBoardNumber}
	STATUS current
	--&FILTNAME    "PMOAILHC Line Urgent ON"
	--&ACTIONS     { log, major }
	--&MATCH       { pmoailhcAlmLineDdmAlm "on", pmoailhctrapBoardNumber "$2"}
	--&MESG        "DDM Alarm appears on Pre-Amp input or Booster Output of PMOAILHC in slot $2 ($A)"
	DESCRIPTION "Urgent Line default is activated"
	::= { pmoailhctraps 32 }

pmoailhcLineTrapUrgentGoesOff NOTIFICATION-TYPE
	OBJECTS {pmoailhcAlmLineDdmAlm, pmoailhctrapBoardNumber}
	STATUS current
	--&FILTNAME    "PMOAILHC Line Urgent OFF"
	--&ACTIONS     { log, normal }
	--&CLEARS      {"PMOAILHC Line Urgent ON"}
	--&MATCH       { pmoailhcAlmLineDdmAlm "on", pmoailhctrapBoardNumber "$2"}
	--&MESG        "DDM Alarm disappears on Pre-Amp input or Booster Output of PMOAILHC in slot $2 ($A)"
	DESCRIPTION "Urgent Line default disappeared"
	::= { pmoailhctraps 33 }

pmoailhcLineTrapCritGoesOn NOTIFICATION-TYPE
	OBJECTS {pmoailhcAlmLineFail, pmoailhcAlmLineHwFail, pmoailhctrapBoardNumber}
	STATUS current
	--&FILTNAME    "PMOAILHC Line Fail ON"
	--&ACTIONS     { log, critical }
	--&MATCH       { pmoailhcAlmLineFail "on", pmoailhcAlmLineHwFail "*", pmoailhctrapBoardNumber "$3"}
	--&MESG        "Critical Alarm appears on Pre-Amp input or Booster Output of PMOAILHC in slot $3 ($A)"

	--&FILTNAME    "PMOAILHC Line HW Fail ON (Hidden)"
	--&ACTIONS     { info }
	--&MATCH       { pmoailhcAlmLineFail "*", pmoailhcAlmLineHwFail "on", pmoailhctrapBoardNumber "$3"}
	--&MESG        "Critical Alarm appears on Pre-Amp input or Booster Output of PMOAILHC in slot $3 ($A)"
	DESCRIPTION "Critical Line default is activated"
	::= { pmoailhctraps 34 }

pmoailhcLineTrapCritGoesOff NOTIFICATION-TYPE
	OBJECTS {pmoailhcAlmLineFail, pmoailhcAlmLineHwFail, pmoailhctrapBoardNumber}
	STATUS current
	--&FILTNAME    "PMOAILHC Line Fail OFF"
	--&ACTIONS     { log, normal }
	--&CLEARS      {"PMOAILHC Line Fail ON"}
	--&MATCH       { pmoailhcAlmLineFail "on", pmoailhcAlmLineHwFail "*", pmoailhctrapBoardNumber "$3"}
	--&MESG        "Critical Alarm disappears on Pre-Amp input or Booster Output of PMOAILHC in slot $3 ($A)"

	--&FILTNAME    "PMOAILHC Line HW Fail OFF (Hidden)"
	--&ACTIONS     { info }
	--&MATCH       { pmoailhcAlmLineFail "*", pmoailhcAlmLineHwFail "on", pmoailhctrapBoardNumber "$3"}
	--&MESG        "Critical Alarm disappears on Pre-Amp input or Booster Output of PMOAILHC in slot $3 ($A)"
	DESCRIPTION "Critical Line default disappeared"
	::= { pmoailhctraps 35 }






--- *****************************************************
---     PORTS TRAPS
--- *****************************************************

pmoailhcClientTrapNotUrgentGoesOn NOTIFICATION-TYPE
	OBJECTS {pmoailhcAlmClientDdmWarning, pmoailhctrapBoardNumber}
	STATUS current
	--&FILTNAME    "PMOAILHC Client Not Urgent ON"
	--&ACTIONS     { log, minor }
	--&MATCH       { pmoailhcAlmClientDdmWarning "on", pmoailhctrapBoardNumber "$2"}
	--&MESG        "DDM Warning appears on Booster input or Pre-Amp Output of PMOAILHC in slot $2 ($A)"
	DESCRIPTION "Not urgent client default is activated"
	::= { pmoailhctraps 40 }

pmoailhcClientTrapNotUrgentGoesOff NOTIFICATION-TYPE
	OBJECTS {pmoailhcAlmClientDdmWarning, pmoailhctrapBoardNumber}
	STATUS current
	--&FILTNAME    "PMOAILHC Client Not Urgent OFF"
	--&ACTIONS     { log, normal }
	--&CLEARS      {"PMOAILHC Client Not Urgent ON"}
	--&MATCH       { pmoailhcAlmClientDdmWarning "on", pmoailhctrapBoardNumber "$2"}
	--&MESG        "DDM Warning disappears on Booster input or Pre-Amp Output of PMOAILHC in slot $2 ($A)"
	DESCRIPTION "Not urgent client default disappeared"
	::= { pmoailhctraps 41 }

pmoailhcClientTrapUrgentGoesOn NOTIFICATION-TYPE
	OBJECTS {pmoailhcAlmClientDdmAlm, pmoailhctrapBoardNumber}
	STATUS current
	--&FILTNAME    "PMOAILHC Client Urgent ON"
	--&ACTIONS     { log, major }
	--&MATCH       { pmoailhcAlmClientDdmAlm "on", pmoailhctrapBoardNumber "$2"}
	--&MESG        "DDM Alarm appears on Booster input or Pre-Amp Output of PMOAILHC in slot $2 ($A)"
	DESCRIPTION "Urgent client default is activated"
	::= { pmoailhctraps 42 }

pmoailhcClientTrapUrgentGoesOff NOTIFICATION-TYPE
	OBJECTS {pmoailhcAlmClientDdmAlm, pmoailhctrapBoardNumber}
	STATUS current
	--&FILTNAME    "PMOAILHC Client Urgent OFF"
	--&ACTIONS     { log, normal }
	--&CLEARS      {"PMOAILHC Client Urgent ON"}
	--&MATCH       { pmoailhcAlmClientDdmAlm "on", pmoailhctrapBoardNumber "$2"}
	--&MESG        "DDM Alarm disappears on Booster input or Pre-Amp Output of PMOAILHC in slot $2 ($A)"
	DESCRIPTION "Urgent client default disappeared"
	::= { pmoailhctraps 43 }

pmoailhcClientTrapCritGoesOn NOTIFICATION-TYPE
	OBJECTS {pmoailhcAlmClientFail, pmoailhcAlmClientHwFail, pmoailhctrapBoardNumber}
	STATUS current
	--&FILTNAME    "PMOAILHC Client Fail ON"
	--&ACTIONS     { log, critical }
	--&MATCH       { pmoailhcAlmClientFail "on", pmoailhcAlmClientHwFail "*", pmoailhctrapBoardNumber "$3"}
	--&MESG        "Critical Alarm appears on Booster input or Pre-Amp Output of PMOAILHC in slot $3 ($A)"

	--&FILTNAME    "PMOAILHC Client HW Fail ON (Hidden)"
	--&ACTIONS     { info }
	--&MATCH       { pmoailhcAlmClientFail "*", pmoailhcAlmClientHwFail "on", pmoailhctrapBoardNumber "$3"}
	--&MESG        "Critical Alarm appears on Booster input or Pre-Amp Output of PMOAILHC in slot $3 ($A)"
	DESCRIPTION "Critical client default is activated"
	::= { pmoailhctraps 44 }

pmoailhcClientTrapCritGoesOff NOTIFICATION-TYPE
	OBJECTS {pmoailhcAlmClientFail, pmoailhcAlmClientHwFail, pmoailhctrapBoardNumber}
	STATUS current
	--&FILTNAME    "PMOAILHC Client Fail OFF"
	--&ACTIONS     { log, normal }
	--&CLEARS      {"PMOAILHC Client Fail ON"}
	--&MATCH       { pmoailhcAlmClientFail "on", pmoailhcAlmClientHwFail "*", pmoailhctrapBoardNumber "$3"}
	--&MESG        "Critical Alarm disappears on Booster input or Pre-Amp Output of PMOAILHC in slot $3 ($A)"

	--&FILTNAME    "PMOAILHC Client HW Fail OFF (Hidden)"
	--&ACTIONS     { info }
	--&MATCH       { pmoailhcAlmClientFail "*", pmoailhcAlmClientHwFail "on", pmoailhctrapBoardNumber "$3"}
	--&MESG        "Critical Alarm disappears on Booster input or Pre-Amp Output of PMOAILHC in slot $3 ($A)"
	DESCRIPTION "Critical client default disappeared"
	::= { pmoailhctraps 45 }






--- *****************************************************
---     HW TRAPS
--- *****************************************************

pmoailhcPowerTrapUrgentGoesOn NOTIFICATION-TYPE
	OBJECTS {pmoailhcAlmDefFuseB, pmoailhcAlmDefFuseA , pmoailhctrapBoardNumber}
	STATUS current
	--&FILTNAME    "PMOAILHC Fuse A Fail ON"
	--&ACTIONS     { log, major }
	--&MATCH       { pmoailhcAlmDefFuseB "*", pmoailhcAlmDefFuseA "on", pmoailhctrapBoardNumber "$3"}
	--&MESG        "Power Input A Fail on PMOAILHC in Slot $3 ($A)"

	--&FILTNAME    "PMOAILHC Fuse B Fail ON"
	--&ACTIONS     { log, major }
	--&MATCH       { pmoailhcAlmDefFuseB "on", pmoailhcAlmDefFuseA "*", pmoailhctrapBoardNumber "$3"}
	--&MESG        "Power Input B Fail on PMOAILHC in Slot $3 ($A)"
	DESCRIPTION "Urgent power supply default is activated"
	::= { pmoailhctraps 50 }
pmoailhcPowerTrapUrgentGoesOff NOTIFICATION-TYPE
	OBJECTS {pmoailhcAlmDefFuseB, pmoailhcAlmDefFuseA , pmoailhctrapBoardNumber}
	STATUS current
	--&FILTNAME    "PMOAILHC Fuse A&B Fail OFF"
	--&ACTIONS     { log, normal}
	--&CLEARS      { "PMOAILHC Fuse A Fail ON", "PMOAILHC Fuse B Fail ON" }
	--&MATCH       { pmoailhcAlmDefFuseB "on", pmoailhcAlmDefFuseA "on", pmoailhctrapBoardNumber "$3"}
	--&MESG        "Power Inputs A and B Present on PMOAILHC in Slot $3 ($A)"
	DESCRIPTION "Urgent power supply default disappeared"
	::= { pmoailhctraps 51 }






END
