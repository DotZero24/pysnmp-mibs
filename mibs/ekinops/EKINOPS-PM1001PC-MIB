-- *****************************************************************
-- EKINOPS-pm1001pc.TXT:  MIB
--
--MIB Part Number:3MI00005ANAE
--MIB Version:01
--
-- Copyright (c) 2016 by Ekinops
-- All rights reserved.
--
-- *****************************************************************

EKINOPS-PM1001PC-MIB DEFINITIONS ::= BEGIN

IMPORTS
	ekinops,
	EkiState,
	EkiOnOff,
	EkiMode,
	EkiProtocol,
	EkiApiState,
	EkiSynchroMode,
	EkiMeasureType
			FROM EKINOPS-MIB
        MODULE-IDENTITY,
        OBJECT-TYPE,
        NOTIFICATION-TYPE,
	Unsigned32,
	Integer32,
	Counter32,
	IpAddress
        		FROM SNMPv2-SMI
 	TEXTUAL-CONVENTION,
	DisplayString
                FROM SNMPv2-TC;

modulepm1001pc MODULE-IDENTITY
        LAST-UPDATED "201605200000Z"
        ORGANIZATION "Ekinops"
        CONTACT-INFO
         "Ekinops

          3, rue Blaise Pascal
          F-22300 Lannion / FRANCE

          Tel : +33 (0)2 96 05 00 30
          Fax : +33 (0)2 96 48 62 39

          E-mail: support@ekinops.net"
        DESCRIPTION
          "MIB for managing Ekinops modules with PM1001PC software"
	REVISION "200601190000Z"
	DESCRIPTION
	  "Initial Version."
	REVISION "200702210000Z"
	DESCRIPTION
	  "Adding module init fail alarms"
	REVISION "200706290000Z"
	DESCRIPTION
	  "Add DCC alarms"
	REVISION "200712030000Z"
	DESCRIPTION
	  "Update Ekinops Address,Helps on objects, Ports Labels"
	REVISION "200903050000Z"
	DESCRIPTION
	  "Fiber length management insertion"
	REVISION "200904070000Z"
	DESCRIPTION
	  "Storm info suppression"
	REVISION "200904090000Z"
	DESCRIPTION
	  "Add DCC ans MAINTENANCE control"
	REVISION "200910050000Z"
	DESCRIPTION
	  "Add CondType parameters"
	REVISION "201003010000Z"
	DESCRIPTION
	  "Probcause,AlarmType - NMS"
	REVISION "201010190000Z"
	DESCRIPTION
	  "New labels on loopbacks"
	REVISION "201011100000Z"
	DESCRIPTION
	  "Formulas in comments and Event on XFP init"
	REVISION "201207030000Z"
	DESCRIPTION
	  "Minor cosmetic updates"
	REVISION "201304030000Z"
	DESCRIPTION
	  "S1,K1,K2 suppress"
	REVISION "201403250000Z"
	DESCRIPTION
	  "Probcause,AlarmType - NMS completion"
	REVISION "201412240000Z"
	DESCRIPTION
	  "Labels cosmetic updates"
	REVISION "201605200000Z"
	DESCRIPTION
	  "New AlarmType – synthesisAlarm (12)"
        ::= { ekinops 12 }



--- *****************************************************
---     LEAF LEVEL 2
--- *****************************************************


pm1001pcalarms OBJECT IDENTIFIER ::= { modulepm1001pc 2 }
pm1001pcAlmOther OBJECT IDENTIFIER ::= { pm1001pcalarms 1 }
pm1001pcAlmOtherNurg OBJECT IDENTIFIER ::= { pm1001pcAlmOther 1 }
pm1001pcAlmOtherUrg OBJECT IDENTIFIER ::= { pm1001pcAlmOther 2 }
pm1001pcAlmOtherCrit OBJECT IDENTIFIER ::= { pm1001pcAlmOther 3 }

pm1001pcAlmClient OBJECT IDENTIFIER ::= { pm1001pcalarms 2 }
pm1001pcAlmClientNurg OBJECT IDENTIFIER ::= { pm1001pcAlmClient 1 }
pm1001pcAlmClientUrg OBJECT IDENTIFIER ::= { pm1001pcAlmClient 2 }
pm1001pcAlmClientCrit OBJECT IDENTIFIER ::= { pm1001pcAlmClient 3 }

pm1001pcAlmLine OBJECT IDENTIFIER ::= { pm1001pcalarms 3 }
pm1001pcAlmLineNurg OBJECT IDENTIFIER ::= { pm1001pcAlmLine 1 }
pm1001pcAlmLineUrg OBJECT IDENTIFIER ::= { pm1001pcAlmLine 2 }
pm1001pcAlmLineCrit OBJECT IDENTIFIER ::= { pm1001pcAlmLine 3 }





pm1001pcmeasures OBJECT IDENTIFIER ::= { modulepm1001pc 3 }
pm1001pcMesrOther OBJECT IDENTIFIER ::= { pm1001pcmeasures 1 }
pm1001pcMesrClient OBJECT IDENTIFIER ::= { pm1001pcmeasures 2 }
pm1001pcMesrLine OBJECT IDENTIFIER ::= { pm1001pcmeasures 3 }




pm1001pccounters OBJECT IDENTIFIER ::= { modulepm1001pc 4 }
pm1001pcCntOther OBJECT IDENTIFIER ::= { pm1001pccounters 1 }
pm1001pcCntClient OBJECT IDENTIFIER ::= { pm1001pccounters 2 }
pm1001pcCntLine OBJECT IDENTIFIER ::= { pm1001pccounters 3 }


pm1001pccontrolsWrite OBJECT IDENTIFIER ::= { modulepm1001pc 6 }
pm1001pcCtrlOther OBJECT IDENTIFIER ::= { pm1001pccontrolsWrite 1 }
pm1001pcCtrlClient OBJECT IDENTIFIER ::= { pm1001pccontrolsWrite 2 }
pm1001pcCtrlLine OBJECT IDENTIFIER ::= { pm1001pccontrolsWrite 3 }

pm1001pcri OBJECT IDENTIFIER ::= { modulepm1001pc 7 }
pm1001pcriTable OBJECT IDENTIFIER ::= { pm1001pcri 1 }

pm1001pcdownload OBJECT IDENTIFIER ::= { modulepm1001pc 8 }
pm1001pcDwlOther OBJECT IDENTIFIER ::= { pm1001pcdownload 1 }
pm1001pcDwlClient OBJECT IDENTIFIER ::= { pm1001pcdownload 2 }
pm1001pcDwlLine OBJECT IDENTIFIER ::= { pm1001pcdownload 3 }


pm1001pcrmon OBJECT IDENTIFIER ::= { modulepm1001pc 9 }
pm1001pcRmonOther OBJECT IDENTIFIER ::= { pm1001pcrmon 1 }
pm1001pcRmonClient OBJECT IDENTIFIER ::= { pm1001pcrmon 2 }
pm1001pcRmonLine OBJECT IDENTIFIER ::= { pm1001pcrmon 3 }


pm1001pcConfig OBJECT IDENTIFIER ::= { modulepm1001pc 10 }

pm1001pctraps OBJECT IDENTIFIER ::= { modulepm1001pc 11 }



--- *****************************************************
--- $$$$$$$$$$$$$$$$$$$$$$$$$$$$$$$$$$$$$$$$$$$$$$$$$$$$$
---     REMOTE INVENTORY
--- $$$$$$$$$$$$$$$$$$$$$$$$$$$$$$$$$$$$$$$$$$$$$$$$$$$$$
--- *****************************************************

pm1001pcRinvReloadInventory OBJECT-TYPE
  SYNTAX EkiOnOff
  MAX-ACCESS read-write
  STATUS current
  DESCRIPTION
        "Reload the inventory: This OID triggers an
         inventory reload."
  ::= { pm1001pcri 2 }

pm1001pcRinvHwPlatform OBJECT-TYPE
  SYNTAX DisplayString
  MAX-ACCESS read-only
  STATUS current
  DESCRIPTION
        "HW platform description: This OID contains the
         description of the Hardware platform."
  ::= { pm1001pcri 3 }

pm1001pcRinvModulePlatform OBJECT-TYPE
  SYNTAX DisplayString
  MAX-ACCESS read-only
  STATUS current
  DESCRIPTION
        "Module platform description: This OID contains the
         description of the Module."
  ::= { pm1001pcri 4 }

pm1001pcRinvSwPlatform OBJECT-TYPE
  SYNTAX DisplayString
  MAX-ACCESS read-only
  STATUS current
  DESCRIPTION
        "SW platform description: This OID contains the
         description of the Software platform."
  ::= { pm1001pcri 5 }

pm1001pcRinvGwPlatform OBJECT-TYPE
  SYNTAX DisplayString
  MAX-ACCESS read-only
  STATUS current
  DESCRIPTION
        "GW platform desciption: This OID contains the
         description of the Gateware platform."
  ::= { pm1001pcri 6 }


pm1001pcRinvClient OBJECT-TYPE
  SYNTAX DisplayString
  MAX-ACCESS read-only
  STATUS current
  DESCRIPTION
        "Inventory for the Client port: This OID contains
         the inventory for the Client port."
  ::= { pm1001pcri 7 }

pm1001pcRinvLine OBJECT-TYPE
  SYNTAX DisplayString
  MAX-ACCESS read-only
  STATUS current
  DESCRIPTION
        "Inventory for the Line: This OID contains
         the inventory for the Line."
  ::= { pm1001pcri 8 }






--- *****************************************************
--- $$$$$$$$$$$$$$$$$$$$$$$$$$$$$$$$$$$$$$$$$$$$$$$$$$$$$
---     ALARMS
--- $$$$$$$$$$$$$$$$$$$$$$$$$$$$$$$$$$$$$$$$$$$$$$$$$$$$$
--- *****************************************************



--- *****************************************************
---     LEAF for the synthAlm0 article
--- *****************************************************
pm1001pcAlmsynthAlm0 OBJECT IDENTIFIER ::= { pm1001pcAlmOtherCrit 0 }




pm1001pcAlmDefFuseB OBJECT-TYPE
	  SYNTAX EkiOnOff
	  MAX-ACCESS read-only
	  STATUS current
	  DESCRIPTION
        "
        Fuse B Fail :This OID indicates
        that the fuse of the power input
        B is in fail condition  <Help>
          Status of the Fuse B <Condtype>
        DEF_FUSE_B <Probcause> powerProblem
        (36) <Alarmtype> equipmentAlarm
        (5) <Polarity> (2)
        "
	  ::= { pm1001pcAlmsynthAlm0 16 }



pm1001pcAlmDefFuseA OBJECT-TYPE
	  SYNTAX EkiOnOff
	  MAX-ACCESS read-only
	  STATUS current
	  DESCRIPTION
        "
        Fuse A Fail :This OID indicates
        that the fuse of the power input
        A is in fail condition  <Help>
          Status of the Fuse A <Condtype>
        DEF_FUSE_A <Probcause> powerProblem
        (36) <Alarmtype> equipmentAlarm
        (5) <Polarity> (2)
        "
	  ::= { pm1001pcAlmsynthAlm0 15 }



pm1001pcAlmModGlobFail OBJECT-TYPE
	  SYNTAX EkiOnOff
	  MAX-ACCESS read-only
	  STATUS current
	  DESCRIPTION
        "
        Module Failure :This OID is set
        on detection of a failure originating
        from the PM <Condtype> MOD_GLOB_FAIL
        <Probcause> equipmentMalfunction
        (16) <Alarmtype> synthesisAlarm
        (12)  <Polarity> (2)
        "
	  ::= { pm1001pcAlmsynthAlm0 9 }



--- *****************************************************
---     LEAF for the synthAlm2 article
--- *****************************************************
pm1001pcAlmsynthAlm2 OBJECT IDENTIFIER ::= { pm1001pcAlmOtherNurg 2 }




pm1001pcAlmMaintenanceOn OBJECT-TYPE
	  SYNTAX EkiOnOff
	  MAX-ACCESS read-only
	  STATUS current
	  DESCRIPTION
        "
        Maintenance Mode :This OID indicates
        that the PM is in maintenance mode.
         <Help>  This alarm indicates that
        the maintenance mode is enabled
        on the PM <Condtype> MAINTENANCE_ON
        <Probcause> other (1) <Alarmtype>
        other (1) <Polarity> (2)
        "
	  ::= { pm1001pcAlmsynthAlm2 5 }



pm1001pcAlmCorrelatOff OBJECT-TYPE
	  SYNTAX EkiOnOff
	  MAX-ACCESS read-only
	  STATUS current
	  DESCRIPTION
        "
        Not Used :This OID, when set,
         indicates that alarm correlation
        is not being performed. <Condtype>
        CORRELAT_OFF <Probcause> other
         (1) <Alarmtype> other (1) <Polarity>
        (2)
        "
	  ::= { pm1001pcAlmsynthAlm2 4 }



pm1001pcAlmConfTableLoad OBJECT-TYPE
	  SYNTAX EkiOnOff
	  MAX-ACCESS read-only
	  STATUS current
	  DESCRIPTION
        "
        PM Configuration Load :This OID
         is at 1 during the loading of
         configuration tables in the modules
        RAM. <Condtype> CONF_TABLE_LOAD
        <Probcause> other (1) <Alarmtype>
        other (1) <Polarity> (2)
        "
	  ::= { pm1001pcAlmsynthAlm2 3 }



pm1001pcAlmInvUpload OBJECT-TYPE
	  SYNTAX EkiOnOff
	  MAX-ACCESS read-only
	  STATUS current
	  DESCRIPTION
        "
        Inventory Upload :This OID is
         at 1 during the uploading of PM
        inventory information. <Condtype>
        INV_UPLOAD <Probcause> other (1)
        <Alarmtype> other (1) <Polarity>
        (2)
        "
	  ::= { pm1001pcAlmsynthAlm2 2 }



pm1001pcAlmConfTableSave OBJECT-TYPE
	  SYNTAX EkiOnOff
	  MAX-ACCESS read-only
	  STATUS current
	  DESCRIPTION
        "
        PM Configuration Save :This OID
        is at 1 during the saving of a
         new configuration table in the
        module Flash memory. <Condtype>
        CONF_TABLE_SAVE <Probcause> other
        (1) <Alarmtype> other (1) <Polarity>
        (2)
        "
	  ::= { pm1001pcAlmsynthAlm2 1 }



--- *****************************************************
---     LEAF for the synthAlmLine article
--- *****************************************************
pm1001pcAlmsynthAlmLine OBJECT IDENTIFIER ::= { pm1001pcAlmLineCrit 7 }




pm1001pcAlmLineFail OBJECT-TYPE
	  SYNTAX EkiOnOff
	  MAX-ACCESS read-only
	  STATUS current
	  DESCRIPTION
        "
        Line Port Failure :This OID indicates
        a failure on the line port <Condtype>
        LINE_FAIL <Probcause> equipmentMalfunction
        (16) <Alarmtype> synthesisAlarm
        (12)  <Polarity> (2)
        "
	  ::= { pm1001pcAlmsynthAlmLine 12 }



pm1001pcAlmLineDdmAlm OBJECT-TYPE
	  SYNTAX EkiOnOff
	  MAX-ACCESS read-only
	  STATUS current
	  DESCRIPTION
        "
        Alarm On Line Optical Module DDM
        :This OID indicates an alarm is
        present coming out of Line optical
        interface DDM  <Help>  This alarm
        indicates if a DDM Alarm has been
        detected on the line transceiver
        <Condtype> LINE_DDM_ALM <Probcause>
        equipmentMalfunction (16) <Alarmtype>
        synthesisAlarm (12)  <Polarity>
        (2)
        "
	  ::= { pm1001pcAlmsynthAlmLine 10 }



pm1001pcAlmLineDdmWarning OBJECT-TYPE
	  SYNTAX EkiOnOff
	  MAX-ACCESS read-only
	  STATUS current
	  DESCRIPTION
        "
        Warning On Line Optical Module
        DDM :This OID indicates a warning
        is present coming out of Line optical
        interface DDM  <Help>  This alarm
        indicates if a DDM Warning has
         been detected on the line transceiver
        <Condtype> LINE_DDM_WARNING <Probcause>
        equipmentMalfunction (16) <Alarmtype>
        synthesisAlarm (12)  <Polarity>
        (2)
        "
	  ::= { pm1001pcAlmsynthAlmLine 9 }



pm1001pcAlmLineUpRdiIns OBJECT-TYPE
	  SYNTAX EkiOnOff
	  MAX-ACCESS read-only
	  STATUS current
	  DESCRIPTION
        "
        MS-RDI/L-RDI Inserted On Line
         :This OID indicates an upstream
        RDI has been inserted in the outgoing
        10 Gb/s signal.   <Help>  This
         status indicates if a MS-RDI/L-RDI
        is currently inserted on the line
        interface. <Condtype> LINE_UP_RDI_INS
        <Probcause> informationalStatus(1000)
        <Alarmtype> other (1) <Polarity>
        (2)
        "
	  ::= { pm1001pcAlmsynthAlmLine 8 }



pm1001pcAlmLineLocalOos OBJECT-TYPE
	  SYNTAX EkiOnOff
	  MAX-ACCESS read-only
	  STATUS current
	  DESCRIPTION
        "
        Line Port In Service :This OID
        indicates that the Line port is
        In Service (1) of Out or Service
        (2)  <Help>  This status indicates
        if the line port is in service
         <Condtype> LINE_LOCAL_OOS <Probcause>
        informationalStatus(1000) <Alarmtype>
        other (1) <Polarity> (2)
        "
	  ::= { pm1001pcAlmsynthAlmLine 6 }



pm1001pcAlmLineXfpTxOff OBJECT-TYPE
	  SYNTAX EkiOnOff
	  MAX-ACCESS read-only
	  STATUS current
	  DESCRIPTION
        "
        Line Optical Laser Shutdown :This
        OID indicates the line optical
         output power is on  <Help>  This
        status indicates if the line transceiver
        laser is ON or OFF <Condtype> LINE_XFP_TX_OFF
        <Probcause> other (1) <Alarmtype>
        equipmentAlarm (5) <Polarity> (2)
        "
	  ::= { pm1001pcAlmsynthAlmLine 5 }



pm1001pcAlmLineHwFail OBJECT-TYPE
	  SYNTAX EkiOnOff
	  MAX-ACCESS read-only
	  STATUS current
	  DESCRIPTION
        "
        Line Port HW Failure :This OID
        indicates a failure on line port,
        most probably caused by a HW issue
        <Condtype> LINE_HW_FAIL <Probcause>
        equipmentMalfunction (16) <Alarmtype>
        synthesisAlarm (12)  <Polarity>
        (2)
        "
	  ::= { pm1001pcAlmsynthAlmLine 4 }



pm1001pcAlmLineXfpInitNotCompl OBJECT-TYPE
	  SYNTAX EkiOnOff
	  MAX-ACCESS read-only
	  STATUS current
	  DESCRIPTION
        "
        Line Optical Module Ready :This
        OID indicates that the line optical
        interface (XFP or OTX) is not operational.
         <Help>  This status indicates
         if the line transceiver has been
        correctly initialized <Condtype>
        LINE_XFP_INIT_NOT_COMPL <Probcause>
        equipmentMalfunction (16) <Alarmtype>
        equipmentAlarm (5) <Polarity> (2)
        <Event> ObjectCDINV
        "
	  ::= { pm1001pcAlmsynthAlmLine 2 }



pm1001pcAlmLineXfpAbsent OBJECT-TYPE
	  SYNTAX EkiOnOff
	  MAX-ACCESS read-only
	  STATUS current
	  DESCRIPTION
        "
        Line Optical Module Absent :This
        OID indicates that the line optical
        interface (XFP or OTX) is not plugged
        in.  <Help>  This alarm indicates
        if the line transceiver is present.
        <Condtype> LINE_XFP_ABSENT <Probcause>
        inputOutputDeviceError (24) <Alarmtype>
        equipmentAlarm (5) <Polarity> (2)
        <Event> ObjectCDINV
        "
	  ::= { pm1001pcAlmsynthAlmLine 1 }



--- *****************************************************
---     LEAF for the synthAlmPort article
--- *****************************************************
pm1001pcAlmsynthAlmPort OBJECT IDENTIFIER ::= { pm1001pcAlmClientCrit 8 }




pm1001pcAlmClientUpCsf OBJECT-TYPE
	  SYNTAX EkiOnOff
	  MAX-ACCESS read-only
	  STATUS current
	  DESCRIPTION
        "
        Client Signal Fail Inserted :This
        OID indicates a CSF has been inserted
        in the upstream client port.  <Help>
         This status indicates if a Client
        Signal Fail is currently inserted
        on the line signal for this client
        port <Condtype> CLIENT_UP_CSF <Probcause>
        other (1) <Alarmtype> other (1)
        <Polarity> (2)
        "
	  ::= { pm1001pcAlmsynthAlmPort 16 }



pm1001pcAlmClientFail OBJECT-TYPE
	  SYNTAX EkiOnOff
	  MAX-ACCESS read-only
	  STATUS current
	  DESCRIPTION
        "
        Client Access Fail :This OID indicates
        a failure on the Client port <Condtype>
        CLIENT_FAIL <Probcause> equipmentMalfunction
        (16) <Alarmtype> synthesisAlarm
        (12)  <Polarity> (2)
        "
	  ::= { pm1001pcAlmsynthAlmPort 12 }



pm1001pcAlmClientXfpDdmAlm OBJECT-TYPE
	  SYNTAX EkiOnOff
	  MAX-ACCESS read-only
	  STATUS current
	  DESCRIPTION
        "
        Alarm On Client XFP DDM :This
         OID indicates an alarm is being
        received from the Client XFP DDM
         <Help>  This alarm indicates if
        a DDM Alarm has been detected on
        the client transceiver <Condtype>
        CLIENT_XFP_DDM_ALM <Probcause>
         equipmentMalfunction (16) <Alarmtype>
        synthesisAlarm (12)  <Polarity>
        (2)
        "
	  ::= { pm1001pcAlmsynthAlmPort 10 }



pm1001pcAlmClientXfpDdmWarning OBJECT-TYPE
	  SYNTAX EkiOnOff
	  MAX-ACCESS read-only
	  STATUS current
	  DESCRIPTION
        "
        Warning On Client XFP DDM :This
        OID indicates a warning is being
        received from the Client XFP DDM
         <Help>  This alarm indicates if
        a DDM Warning has been detected
        on the client transceiver <Condtype>
        CLIENT_XFP_DDM_WARNING <Probcause>
        equipmentMalfunction (16) <Alarmtype>
        synthesisAlarm (12) ) <Polarity>
        (2)
        "
	  ::= { pm1001pcAlmsynthAlmPort 9 }



pm1001pcAlmClientDwCais OBJECT-TYPE
	  SYNTAX EkiOnOff
	  MAX-ACCESS read-only
	  STATUS current
	  DESCRIPTION
        "
        Client AIS Inserted :This OID
         indicates a CAIS has been inserted
        on the output client port.  <Help>
         This status indicates if a Client
        Alarm Indication Signal is currently
        inserted on the client interface
        <Condtype> CLIENT_DW_CAIS <Probcause>
        informationalStatus(1000) <Alarmtype>
        other (1) <Polarity> (2)
        "
	  ::= { pm1001pcAlmsynthAlmPort 8 }



pm1001pcAlmClientLocalOos OBJECT-TYPE
	  SYNTAX EkiOnOff
	  MAX-ACCESS read-only
	  STATUS current
	  DESCRIPTION
        "
        Local Client Port In Service :This
        OID indicates that the local Client
        port is In Service (1) or Out of
        Service (2)  <Help>  This status
        indicates if the local client port
        is in service <Condtype> CLIENT_LOCAL_OOS
        <Probcause> informationalStatus(1000)
        <Alarmtype> other (1) <Polarity>
        (2)
        "
	  ::= { pm1001pcAlmsynthAlmPort 6 }



pm1001pcAlmClientDwLsd OBJECT-TYPE
	  SYNTAX EkiOnOff
	  MAX-ACCESS read-only
	  STATUS current
	  DESCRIPTION
        "
        Client Optical Laser Shutdown
         :This OID indicates the Client
        XFP transmitter output is ON.
          <Help>  This status indicates
        if the client transceiver laser
        is ON or OFF <Condtype> CLIENT_DW_LSD
        <Probcause> other (1) <Alarmtype>
        equipmentAlarm (5) <Polarity> (2)
        "
	  ::= { pm1001pcAlmsynthAlmPort 5 }



pm1001pcAlmClientHwFail OBJECT-TYPE
	  SYNTAX EkiOnOff
	  MAX-ACCESS read-only
	  STATUS current
	  DESCRIPTION
        "
        Client HW Fail :This OID indicates
        a failure on client port, most
         probably caused by a HW issue.
        <Condtype> CLIENT_HW_FAIL <Probcause>
        equipmentMalfunction (16) <Alarmtype>
        synthesisAlarm (12)  <Polarity>
        (2)
        "
	  ::= { pm1001pcAlmsynthAlmPort 4 }



pm1001pcAlmClientDdmAbsent OBJECT-TYPE
	  SYNTAX EkiOnOff
	  MAX-ACCESS read-only
	  STATUS current
	  DESCRIPTION
        "
        Client Optical Module Ready :This
        OID indicates that the client optical
        interface (XFP or OTX) is not operational.
         <Help>  This status indicates
         if the client transceiver has
         been correctly initialized <Condtype>
        CLIENT_DDM_ABSENT <Probcause> equipmentMalfunction
        (16) <Alarmtype> equipmentAlarm
        (5) <Polarity> (2)
        "
	  ::= { pm1001pcAlmsynthAlmPort 2 }



pm1001pcAlmClientXfpAbsent OBJECT-TYPE
	  SYNTAX EkiOnOff
	  MAX-ACCESS read-only
	  STATUS current
	  DESCRIPTION
        "
        Client Optical Module Absent :This
        OID indicates that the XFP module
        is not present in the client port.
         <Help>  This alarm indicates if
        the client transceiver is present.
        <Condtype> CLIENT_XFP_ABSENT <Probcause>
        inputOutputDeviceError (24) <Alarmtype>
        equipmentAlarm (5) <Polarity> (2)
        <Event> ObjectCDINV
        "
	  ::= { pm1001pcAlmsynthAlmPort 1 }



--- *****************************************************
---     LEAF for the clientAccessioAlm article
--- *****************************************************
pm1001pcAlmclientAccessioAlm OBJECT IDENTIFIER ::= { pm1001pcAlmClientCrit 16 }




pm1001pcAlmClientUpLos OBJECT-TYPE
	  SYNTAX EkiOnOff
	  MAX-ACCESS read-only
	  STATUS current
	  DESCRIPTION
        "
        Client Input Loss Of Signal :This
        OID indicates that no signal is
        present on the XFP of the client
        port  <Help>  This alarm indicates
        if an optical signal is detected
        on the client transceiver input
        <Condtype> CLIENT_UP_LOS <Probcause>
        receiveFailure (41) <Alarmtype>
        physicalViolation (9) <Polarity>
        (2)
        "
	  ::= { pm1001pcAlmclientAccessioAlm 4 }



pm1001pcAlmClientDwLasFail OBJECT-TYPE
	  SYNTAX EkiOnOff
	  MAX-ACCESS read-only
	  STATUS current
	  DESCRIPTION
        "
        Client XFP Tx Failed :This OID
        indicates that the transmitter
         fails for the XFP plugged into
        the client port (this alarm reports
        the transmitter failure alarm generated
        by the XFPs) <Condtype> CLIENT_DW_LAS_FAIL
        <Probcause> transmitterFailure
         (56) <Alarmtype> equipmentAlarm
        (5) <Polarity> (2)
        "
	  ::= { pm1001pcAlmclientAccessioAlm 1 }



--- *****************************************************
---     LEAF for the clientXfpAlarm1 article
--- *****************************************************
pm1001pcAlmclientXfpAlarm1 OBJECT IDENTIFIER ::= { pm1001pcAlmClientUrg 32 }




pm1001pcAlmClientRxPowerHighAlarm OBJECT-TYPE
	  SYNTAX EkiOnOff
	  MAX-ACCESS read-only
	  STATUS current
	  DESCRIPTION
        "
        Client Optical Rx Power High :Alarm
        indicating that the XFP received
        optical power is higher than the
        threshold value written in the
         XFP EEPROM <Condtype> CLIENT_RX_POWER_HIGH_ALARM
        <Probcause> receiveFailure (41)
        <Alarmtype> equipmentAlarm (5)
         <Polarity> (2)
        "
	  ::= { pm1001pcAlmclientXfpAlarm1 16 }



pm1001pcAlmClientRxPowerLowAlarm OBJECT-TYPE
	  SYNTAX EkiOnOff
	  MAX-ACCESS read-only
	  STATUS current
	  DESCRIPTION
        "
        Client Optical Rx Power Low :Alarm
        indicating that the XFP received
        optical power is lower than the
        threshold value written in the
         XFP EEPROM  <Condtype> CLIENT_RX_POWER_LOW_ALARM
        <Probcause> receiveFailure (41)
        <Alarmtype> equipmentAlarm (5)
         <Polarity> (2)
        "
	  ::= { pm1001pcAlmclientXfpAlarm1 15 }



pm1001pcAlmClientTempHighAlarm OBJECT-TYPE
	  SYNTAX EkiOnOff
	  MAX-ACCESS read-only
	  STATUS current
	  DESCRIPTION
        "
        Client Transceiver Temp High :Alarm
        indicating that the XFP/OTX temperature
        is higher than the threshold value
        written in the XFP EEPROM <Condtype>
        CLIENT_TEMP_HIGH_ALARM <Probcause>
        temperatureUnacceptable (51) <Alarmtype>
        equipmentAlarm (5) <Polarity> (2)
        "
	  ::= { pm1001pcAlmclientXfpAlarm1 8 }



pm1001pcAlmClientTempLowAlarm OBJECT-TYPE
	  SYNTAX EkiOnOff
	  MAX-ACCESS read-only
	  STATUS current
	  DESCRIPTION
        "
        Client Transceiver Temp Low :Alarm
        indicating that the XFP/OTX temperature
        is lower than the threshold value
        written in the XFP/OTX EEPROM <Condtype>
        CLIENT_TEMP_LOW_ALARM <Probcause>
        temperatureUnacceptable (51) <Alarmtype>
        equipmentAlarm (5) <Polarity> (2)
        "
	  ::= { pm1001pcAlmclientXfpAlarm1 7 }



pm1001pcAlmClientTxBiasHighAlarm OBJECT-TYPE
	  SYNTAX EkiOnOff
	  MAX-ACCESS read-only
	  STATUS current
	  DESCRIPTION
        "
        Client Transceiver Bias High :Alarm
        indicating that the XFP/OTX transmitter
        laser bias current is higher than
        the threshold value written in
         the XFP EEPROM <Condtype> CLIENT_TX_BIAS_HIGH_ALARM
        <Probcause> transmitterFailure
         (56) <Alarmtype> equipmentAlarm
        (5) <Polarity> (2)
        "
	  ::= { pm1001pcAlmclientXfpAlarm1 4 }



pm1001pcAlmClientTxBiasLowAlarm OBJECT-TYPE
	  SYNTAX EkiOnOff
	  MAX-ACCESS read-only
	  STATUS current
	  DESCRIPTION
        "
        Client Transceiver Bias Low :Alarm
        indicating that the XFP/OTX transmitter
        laser bias current is lower than
        the threshold value written in
         the XFP/OTX EEPROM <Condtype>
         CLIENT_TX_BIAS_LOW_ALARM <Probcause>
        transmitterFailure (56) <Alarmtype>
        equipmentAlarm (5) <Polarity> (2)
        "
	  ::= { pm1001pcAlmclientXfpAlarm1 3 }



pm1001pcAlmClientTxPowerHighAlarm OBJECT-TYPE
	  SYNTAX EkiOnOff
	  MAX-ACCESS read-only
	  STATUS current
	  DESCRIPTION
        "
        Client Optical Tx Power High :Alarm
        indicating that the XFP/OTX transmitter
        transmitter output power is higher
        than the threshold value written
        in the XFP EEPROM <Condtype> CLIENT_TX_POWER_HIGH_ALARM
        <Probcause> transmitterFailure
         (56) <Alarmtype> equipmentAlarm
        (5) <Polarity> (2)
        "
	  ::= { pm1001pcAlmclientXfpAlarm1 2 }



pm1001pcAlmClientTxPowerLowAlarm OBJECT-TYPE
	  SYNTAX EkiOnOff
	  MAX-ACCESS read-only
	  STATUS current
	  DESCRIPTION
        "
        Client Optical Tx Power Low :Alarm
        indicating that the XFP/OTX transmitter
        transmitter output power is lower
        than the threshold value written
        in the XFP/OTX EEPROM <Condtype>
        CLIENT_TX_POWER_LOW_ALARM <Probcause>
        transmitterFailure (56) <Alarmtype>
        equipmentAlarm (5) <Polarity> (2)
        "
	  ::= { pm1001pcAlmclientXfpAlarm1 1 }



--- *****************************************************
---     LEAF for the clientXfpAlarm2 article
--- *****************************************************
pm1001pcAlmclientXfpAlarm2 OBJECT IDENTIFIER ::= { pm1001pcAlmClientCrit 40 }




pm1001pcAlmClientApdSupplyFault OBJECT-TYPE
	  SYNTAX EkiOnOff
	  MAX-ACCESS read-only
	  STATUS current
	  DESCRIPTION
        "
        Client Rx Photodiode Power Failed
        :This OID indicates a failure on
        the APD power supply  <Help>  This
        alarm indicates if the APD power
        supply is in fail condition <Condtype>
        CLIENT_APD_SUPPLY_FAULT <Probcause>
        receiverFailure (42) <Alarmtype>
        equipmentAlarm (5) <Polarity> (2)
        "
	  ::= { pm1001pcAlmclientXfpAlarm2 16 }



pm1001pcAlmClientTecFault OBJECT-TYPE
	  SYNTAX EkiOnOff
	  MAX-ACCESS read-only
	  STATUS current
	  DESCRIPTION
        "
        Client Optical Tx Temp Regul.
         Failed :This OID indicates a failure
        on the TEC module  <Help>  This
        alarm indicates if the TEC of the
        Client transceiver is in fail condition
        <Condtype> CLIENT_TEC_FAULT <Probcause>
        transmitterFailure (56) <Alarmtype>
        equipmentAlarm (5) <Polarity> (2)
        "
	  ::= { pm1001pcAlmclientXfpAlarm2 15 }



pm1001pcAlmClientWavelengthUnlocked OBJECT-TYPE
	  SYNTAX EkiOnOff
	  MAX-ACCESS read-only
	  STATUS current
	  DESCRIPTION
        "
        Client Optical Tx Wavelength Unlocked
        :This OID indicates that the wavelength
        error is exceeding the manufacturer
        tolerance  <Help>  This alarm indicates
        if the wavelenght of the Client
        transceiver is locked <Condtype>
        CLIENT_WAVELENGTH_UNLOCKED <Probcause>
        transmitterFailure (56) <Alarmtype>
        equipmentAlarm (5) <Polarity> (2)
        "
	  ::= { pm1001pcAlmclientXfpAlarm2 14 }



pm1001pcAlmClientTxNr OBJECT-TYPE
	  SYNTAX EkiOnOff
	  MAX-ACCESS read-only
	  STATUS current
	  DESCRIPTION
        "
        Client Optical Tx Not Ready :This
        OID indicates a condition has arisen
        leading to invalid data on the
         transmitting side  <Help>  This
        alarm indicates if the Tx part
         of the Client transceiver is ready
        <Condtype> CLIENT_TX_NR <Probcause>
        transmitterFailure (56) <Alarmtype>
        equipmentAlarm (5) <Polarity> (2)
        "
	  ::= { pm1001pcAlmclientXfpAlarm2 8 }



pm1001pcAlmClientTxFault OBJECT-TYPE
	  SYNTAX EkiOnOff
	  MAX-ACCESS read-only
	  STATUS current
	  DESCRIPTION
        "
        Client Optical Tx Failure :This
        OID indicates a fault condition
        on the laser detected by the safety
        syste  <Help>  This alarm indicates
        if the laser of the Client transceiver
        is in fail condition <Condtype>
        CLIENT_TX_FAULT <Probcause> transmitterFailure
        (56) <Alarmtype> equipmentAlarm
        (5) <Polarity> (2)
        "
	  ::= { pm1001pcAlmclientXfpAlarm2 7 }



pm1001pcAlmClientTxCdrNotLocked1 OBJECT-TYPE
	  SYNTAX EkiOnOff
	  MAX-ACCESS read-only
	  STATUS current
	  DESCRIPTION
        "
        Client Optical Tx CDR Unlocked
        :This OID indicates a loss of lock
        on the transmitting side CDR has
        been detected.  <Help>  This alarm
        indicates if the Tx CDR is locked
        in the Client transceiver <Condtype>
        CLIENT_TX_CDR_NOT_LOCKED1 <Probcause>
        transmitterFailure (56) <Alarmtype>
        equipmentAlarm (5) <Polarity> (2)
        "
	  ::= { pm1001pcAlmclientXfpAlarm2 6 }



pm1001pcAlmClientRxNr OBJECT-TYPE
	  SYNTAX EkiOnOff
	  MAX-ACCESS read-only
	  STATUS current
	  DESCRIPTION
        "
        Client Optical Rx Not Ready :This
        OID indicates that a condition
         has arisen leading to invalid
         data on the receiving side.  <Help>
         This alarm indicates if the Rx
        part of the Client transceiver
         is ready <Condtype> CLIENT_RX_NR
        <Probcause> receiveFailure (41)
        <Alarmtype> equipmentAlarm (5)
         <Polarity> (2)
        "
	  ::= { pm1001pcAlmclientXfpAlarm2 5 }



pm1001pcAlmClientRxCdrNotLocked1 OBJECT-TYPE
	  SYNTAX EkiOnOff
	  MAX-ACCESS read-only
	  STATUS current
	  DESCRIPTION
        "
        Client Optical Rx CDR Unlocked
        :This OID indicates that a loss
        of lock on the receiving side CDR
        has been detected  <Help>  This
        alarm indicates if the Rx CDR is
        locked in the Client transceiver
        <Condtype> CLIENT_RX_CDR_NOT_LOCKED1
        <Probcause> receiveFailure (41)
        <Alarmtype> equipmentAlarm (5)
         <Polarity> (2)
        "
	  ::= { pm1001pcAlmclientXfpAlarm2 3 }



pm1001pcAlmClientModNr OBJECT-TYPE
	  SYNTAX EkiOnOff
	  MAX-ACCESS read-only
	  STATUS current
	  DESCRIPTION
        "
        Client Optical Module Not Ready
        :This OID indicates that the module
        is unable to determine correct
         data.  <Help>  This alarm indicates
        if the Client transceiver is ready
        <Condtype> CLIENT_MOD_NR <Probcause>
        receiveFailure (41) <Alarmtype>
        equipmentAlarm (5) <Polarity> (2)
        "
	  ::= { pm1001pcAlmclientXfpAlarm2 2 }



--- *****************************************************
---     LEAF for the clientXfpWarnings article
--- *****************************************************
pm1001pcAlmclientXfpWarnings OBJECT IDENTIFIER ::= { pm1001pcAlmClientNurg 48 }




pm1001pcAlmClientRxPowerHighWarning OBJECT-TYPE
	  SYNTAX EkiOnOff
	  MAX-ACCESS read-only
	  STATUS current
	  DESCRIPTION
        "
        Client Optical Rx Pwr High Warning
        :Warning indicating that the XFP
        received optical power is higher
        than the threshold value written
        in the XFP EEPROM <Condtype> CLIENT_RX_POWER_HIGH_WARNING
        <Probcause> receiveFailure (41)
        <Alarmtype> equipmentAlarm (5)
         <Polarity> (2)
        "
	  ::= { pm1001pcAlmclientXfpWarnings 16 }



pm1001pcAlmClientRxPowerLowWarning OBJECT-TYPE
	  SYNTAX EkiOnOff
	  MAX-ACCESS read-only
	  STATUS current
	  DESCRIPTION
        "
        Client Optical Rx Pwr Low Warning
        :Warning indicating that the XFP
        received optical power is lower
        than the threshold value written
        in the XFP EEPROM  <Condtype> CLIENT_RX_POWER_LOW_WARNING
        <Probcause> receiveFailure (41)
        <Alarmtype> equipmentAlarm (5)
         <Polarity> (2)
        "
	  ::= { pm1001pcAlmclientXfpWarnings 15 }



pm1001pcAlmClientTempHighWarning OBJECT-TYPE
	  SYNTAX EkiOnOff
	  MAX-ACCESS read-only
	  STATUS current
	  DESCRIPTION
        "
        Client Transceiver Temp High Warning
        :Warning indicating that the XFP/OTX
        temperature is higher than the
         threshold value written in the
        XFP EEPROM <Condtype> CLIENT_TEMP_HIGH_WARNING
        <Probcause> temperatureUnacceptable
        (51) <Alarmtype> equipmentAlarm
        (5) <Polarity> (2)
        "
	  ::= { pm1001pcAlmclientXfpWarnings 8 }



pm1001pcAlmClientTempLowWarning OBJECT-TYPE
	  SYNTAX EkiOnOff
	  MAX-ACCESS read-only
	  STATUS current
	  DESCRIPTION
        "
        Client Transceiver Temp Low Warning
        :Warning indicating that the XFP/OTX
        temperature is lower than the threshold
        value written in the XFP/OTX EEPROM
        <Condtype> CLIENT_TEMP_LOW_WARNING
        <Probcause> temperatureUnacceptable
        (51) <Alarmtype> equipmentAlarm
        (5) <Polarity> (2)
        "
	  ::= { pm1001pcAlmclientXfpWarnings 7 }



pm1001pcAlmClientTxBiasHighWarning OBJECT-TYPE
	  SYNTAX EkiOnOff
	  MAX-ACCESS read-only
	  STATUS current
	  DESCRIPTION
        "
        Client Transceiver Bias High Warning
        :Warning indicating that the XFP/OTX
        transmitter laser bias current
         is higher than the threshold value
        written in the XFP EEPROM <Condtype>
        CLIENT_TX_BIAS_HIGH_WARNING <Probcause>
        transmitterFailure (56) <Alarmtype>
        equipmentAlarm (5) <Polarity> (2)
        "
	  ::= { pm1001pcAlmclientXfpWarnings 4 }



pm1001pcAlmClientTxBiasLowWarning OBJECT-TYPE
	  SYNTAX EkiOnOff
	  MAX-ACCESS read-only
	  STATUS current
	  DESCRIPTION
        "
        Client Transceiver Bias Low Warning
        :Warning indicating that the XFP/OTX
        transmitter laser bias current
         is lower than the threshold value
        written in the XFP/OTX EEPROM <Condtype>
        CLIENT_TX_BIAS_LOW_WARNING <Probcause>
        transmitterFailure (56) <Alarmtype>
        equipmentAlarm (5) <Polarity> (2)
        "
	  ::= { pm1001pcAlmclientXfpWarnings 3 }



pm1001pcAlmClientTxPowerHighWarning OBJECT-TYPE
	  SYNTAX EkiOnOff
	  MAX-ACCESS read-only
	  STATUS current
	  DESCRIPTION
        "
        Client Optical Tx Pwr High Warning
        :Warning indicating that the XFP/OTX
        transmitter transmitter output
         power is higher than the threshold
        value written in the XFP EEPROM
        <Condtype> CLIENT_TX_POWER_HIGH_WARNING
        <Probcause> transmitterFailure
         (56) <Alarmtype> equipmentAlarm
        (5) <Polarity> (2)
        "
	  ::= { pm1001pcAlmclientXfpWarnings 2 }



pm1001pcAlmClientTxPowerLowWarning OBJECT-TYPE
	  SYNTAX EkiOnOff
	  MAX-ACCESS read-only
	  STATUS current
	  DESCRIPTION
        "
        Client Optical Tx Pwr Low Warning
        :Warning indicating that the XFP/OTX
        transmitter transmitter output
         power is lower than the threshold
        value written in the XFP/OTX EEPROM
        <Condtype> CLIENT_TX_POWER_LOW_WARNING
        <Probcause> transmitterFailure
         (56) <Alarmtype> equipmentAlarm
        (5) <Polarity> (2)
        "
	  ::= { pm1001pcAlmclientXfpWarnings 1 }



--- *****************************************************
---     LEAF for the clientXfpSupplyAlarm article
--- *****************************************************
pm1001pcAlmclientXfpSupplyAlarm OBJECT IDENTIFIER ::= { pm1001pcAlmClientUrg 64 }




pm1001pcAlmClientVcc5HighWarning OBJECT-TYPE
	  SYNTAX EkiOnOff
	  MAX-ACCESS read-only
	  STATUS current
	  DESCRIPTION
        "
        VCC5 Power Supply High Warning
        :Warning indicating the XFP/OTX
        VCC5 power supply is higher than
        the threshold written in the EEPROM
        <Condtype> CLIENT_VCC5_HIGH_WARNING
        <Probcause> powerProblem (36) <Alarmtype>
        equipmentAlarm (5) <Polarity> (2)
        "
	  ::= { pm1001pcAlmclientXfpSupplyAlarm 16 }



pm1001pcAlmClientVcc5LowWarning OBJECT-TYPE
	  SYNTAX EkiOnOff
	  MAX-ACCESS read-only
	  STATUS current
	  DESCRIPTION
        "
        VCC5 Power Supply Low Warning
         :Warning indicating the XFP/OTX
        VCC5 power supply is lower than
        the threshold written in the EEPROM
        <Condtype> CLIENT_VCC5_LOW_WARNING
        <Probcause> powerProblem (36) <Alarmtype>
        equipmentAlarm (5) <Polarity> (2)
        "
	  ::= { pm1001pcAlmclientXfpSupplyAlarm 15 }



pm1001pcAlmClientVcc3HighWarning OBJECT-TYPE
	  SYNTAX EkiOnOff
	  MAX-ACCESS read-only
	  STATUS current
	  DESCRIPTION
        "
        VCC3 Power Supply High Warning
        :Warning indicating the XFP/OTX
        VCC3 power supply is higher than
        the threshold written in the EEPROM
        <Condtype> CLIENT_VCC3_HIGH_WARNING
        <Probcause> powerProblem (36) <Alarmtype>
        equipmentAlarm (5) <Polarity> (2)
        "
	  ::= { pm1001pcAlmclientXfpSupplyAlarm 14 }



pm1001pcAlmClientVcc3LowWarning OBJECT-TYPE
	  SYNTAX EkiOnOff
	  MAX-ACCESS read-only
	  STATUS current
	  DESCRIPTION
        "
        VCC3 Power Supply Low Warning
         :Warning indicating the XFP/OTX
        VCC3 power supply is lower than
        the threshold written in the EEPROM
        <Condtype> CLIENT_VCC3_LOW_WARNING
        <Probcause> powerProblem (36) <Alarmtype>
        equipmentAlarm (5) <Polarity> (2)
        "
	  ::= { pm1001pcAlmclientXfpSupplyAlarm 13 }



pm1001pcAlmClientVcc2HighWarning OBJECT-TYPE
	  SYNTAX EkiOnOff
	  MAX-ACCESS read-only
	  STATUS current
	  DESCRIPTION
        "
        VCC2 Power Supply High Warning
        :Warning indicating the XFP/OTX
        VCC2 power supply is higher than
        the threshold written in the EEPROM
        <Condtype> CLIENT_VCC2_HIGH_WARNING
        <Probcause> powerProblem (36) <Alarmtype>
        equipmentAlarm (5) <Polarity> (2)
        "
	  ::= { pm1001pcAlmclientXfpSupplyAlarm 12 }



pm1001pcAlmClientVcc2LowWarning OBJECT-TYPE
	  SYNTAX EkiOnOff
	  MAX-ACCESS read-only
	  STATUS current
	  DESCRIPTION
        "
        VCC2 Power Supply Low Warning
         :Warning indicating the XFP/OTX
        VCC2 power supply is lower than
        the threshold written in the EEPROM
        <Condtype> CLIENT_VCC2_LOW_WARNING
        <Probcause> powerProblem (36) <Alarmtype>
        equipmentAlarm (5) <Polarity> (2)
        "
	  ::= { pm1001pcAlmclientXfpSupplyAlarm 11 }



pm1001pcAlmClientVee5HighWarning OBJECT-TYPE
	  SYNTAX EkiOnOff
	  MAX-ACCESS read-only
	  STATUS current
	  DESCRIPTION
        "
        VEE5 Power Supply High Warning
        :Warning indicating the XFP/OTX
        VEE5 power supply is higher than
        the threshold written in the EEPROM
        <Condtype> CLIENT_VEE5_HIGH_WARNING
        <Probcause> powerProblem (36) <Alarmtype>
        equipmentAlarm (5) <Polarity> (2)
        "
	  ::= { pm1001pcAlmclientXfpSupplyAlarm 10 }



pm1001pcAlmClientVee5LowWarning OBJECT-TYPE
	  SYNTAX EkiOnOff
	  MAX-ACCESS read-only
	  STATUS current
	  DESCRIPTION
        "
        VEE5 Power Supply Low Warning
         :Warning indicating the XFP/OTX
        VEE5 power supply is lower than
        the threshold written in the EEPROM
        <Condtype> CLIENT_VEE5_LOW_WARNING
        <Probcause> powerProblem (36) <Alarmtype>
        equipmentAlarm (5) <Polarity> (2)
        "
	  ::= { pm1001pcAlmclientXfpSupplyAlarm 9 }



pm1001pcAlmClientVcc5HighAlarm OBJECT-TYPE
	  SYNTAX EkiOnOff
	  MAX-ACCESS read-only
	  STATUS current
	  DESCRIPTION
        "
        VCC5 Power Supply High Alarm :Alarm
        indicating the XFP/OTX VCC5 power
        supply is higher than the threshold
        written in the EEPROM <Condtype>
        CLIENT_VCC5_HIGH_ALARM <Probcause>
        powerProblem (36) <Alarmtype> equipmentAlarm
        (5) <Polarity> (2)
        "
	  ::= { pm1001pcAlmclientXfpSupplyAlarm 8 }



pm1001pcAlmClientVcc5LowAlarm OBJECT-TYPE
	  SYNTAX EkiOnOff
	  MAX-ACCESS read-only
	  STATUS current
	  DESCRIPTION
        "
        VCC5 Power Supply Low Alarm :Alarm
        indicating the XFP/OTX VCC5 power
        supply is lower than the threshold
        written in the EEPROM <Condtype>
        CLIENT_VCC5_LOW_ALARM <Probcause>
        powerProblem (36) <Alarmtype> equipmentAlarm
        (5) <Polarity> (2)
        "
	  ::= { pm1001pcAlmclientXfpSupplyAlarm 7 }



pm1001pcAlmClientVcc3HighAlarm OBJECT-TYPE
	  SYNTAX EkiOnOff
	  MAX-ACCESS read-only
	  STATUS current
	  DESCRIPTION
        "
        VCC3 Power Supply High Alarm :Alarm
        indicating the XFP/OTX VCC3 power
        supply is higher than the threshold
        written in the EEPROM <Condtype>
        CLIENT_VCC3_HIGH_ALARM <Probcause>
        powerProblem (36) <Alarmtype> equipmentAlarm
        (5) <Polarity> (2)
        "
	  ::= { pm1001pcAlmclientXfpSupplyAlarm 6 }



pm1001pcAlmClientVcc3LowAlarm OBJECT-TYPE
	  SYNTAX EkiOnOff
	  MAX-ACCESS read-only
	  STATUS current
	  DESCRIPTION
        "
        VCC3 Power Supply Low Alarm :Alarm
        indicating the XFP/OTX VCC3 power
        supply is lower than the threshold
        written in the EEPROM <Condtype>
        CLIENT_VCC3_LOW_ALARM <Probcause>
        powerProblem (36) <Alarmtype> equipmentAlarm
        (5) <Polarity> (2)
        "
	  ::= { pm1001pcAlmclientXfpSupplyAlarm 5 }



pm1001pcAlmClientVcc2HighAlarm OBJECT-TYPE
	  SYNTAX EkiOnOff
	  MAX-ACCESS read-only
	  STATUS current
	  DESCRIPTION
        "
        VCC2 Power Supply High Alarm :Alarm
        indicating the XFP/OTX VCC2 power
        supply is higher than the threshold
        written in the EEPROM <Condtype>
        CLIENT_VCC2_HIGH_ALARM <Probcause>
        powerProblem (36) <Alarmtype> equipmentAlarm
        (5) <Polarity> (2)
        "
	  ::= { pm1001pcAlmclientXfpSupplyAlarm 4 }



pm1001pcAlmClientVcc2LowAlarm OBJECT-TYPE
	  SYNTAX EkiOnOff
	  MAX-ACCESS read-only
	  STATUS current
	  DESCRIPTION
        "
        VCC2 Power Supply Low Alarm :Alarm
        indicating the XFP/OTX VCC2 power
        supply is lower than the threshold
        written in the EEPROM <Condtype>
        CLIENT_VCC2_LOW_ALARM <Probcause>
        powerProblem (36) <Alarmtype> equipmentAlarm
        (5) <Polarity> (2)
        "
	  ::= { pm1001pcAlmclientXfpSupplyAlarm 3 }



pm1001pcAlmClientVee5HighAlarm OBJECT-TYPE
	  SYNTAX EkiOnOff
	  MAX-ACCESS read-only
	  STATUS current
	  DESCRIPTION
        "
        VEE5 Power Supply High Alarm :Alarm
        indicating the XFP/OTX VEE5 power
        supply is higher than the threshold
        written in the EEPROM <Condtype>
        CLIENT_VEE5_HIGH_ALARM <Probcause>
        powerProblem (36) <Alarmtype> equipmentAlarm
        (5) <Polarity> (2)
        "
	  ::= { pm1001pcAlmclientXfpSupplyAlarm 2 }



pm1001pcAlmClientVee5LowAlarm OBJECT-TYPE
	  SYNTAX EkiOnOff
	  MAX-ACCESS read-only
	  STATUS current
	  DESCRIPTION
        "
        VEE5 Power Supply Low Alarm :Alarm
        indicating the XFP/OTX VEE5 power
        supply is lower than the threshold
        written in the EEPROM <Condtype>
        CLIENT_VEE5_LOW_ALARM <Probcause>
        powerProblem (36) <Alarmtype> equipmentAlarm
        (5) <Polarity> (2)
        "
	  ::= { pm1001pcAlmclientXfpSupplyAlarm 1 }



--- *****************************************************
---     LEAF for the clientMapperDeAlm article
--- *****************************************************
pm1001pcAlmclientMapperDeAlm OBJECT IDENTIFIER ::= { pm1001pcAlmClientCrit 72 }




pm1001pcAlmClientDwBufferOvl OBJECT-TYPE
	  SYNTAX EkiOnOff
	  MAX-ACCESS read-only
	  STATUS current
	  DESCRIPTION
        "
        Client Downstream Buffer Overload
        :This OID indicates that the de-mapper
        buffer for client port is in overload.
        <Condtype> CLIENT_DW_BUFFER_OVL
        <Probcause> equipmentMalfunction
        (16) <Alarmtype> equipmentAlarm
        (5) <Polarity> (2)
        "
	  ::= { pm1001pcAlmclientMapperDeAlm 14 }



pm1001pcAlmClientDwCsfDet OBJECT-TYPE
	  SYNTAX EkiOnOff
	  MAX-ACCESS read-only
	  STATUS current
	  DESCRIPTION
        "
        Client Signal Fail Detected :This
        OID indicates that a CSF has been
        detected on client port in the
         downstream direction   <Help>
          This alarm indicates if a Client
        Signal Fail has been detected in
        the incoming line frame for this
        client port <Condtype> CLIENT_DW_CSF_DET
        <Probcause> receiveFailure (41)
        <Alarmtype> other (1) <Polarity>
        (2)
        "
	  ::= { pm1001pcAlmclientMapperDeAlm 11 }



pm1001pcAlmClientUpBufferOvl OBJECT-TYPE
	  SYNTAX EkiOnOff
	  MAX-ACCESS read-only
	  STATUS current
	  DESCRIPTION
        "
        Client Upstream Buffer Overload
        :This OID indicates that the rate
        adaptation buffer for client port
        is in overload. <Condtype> CLIENT_UP_BUFFER_OVL
        <Probcause> receiveFailure (41)
        <Alarmtype> integrityViolation
         (7) <Polarity> (2)
        "
	  ::= { pm1001pcAlmclientMapperDeAlm 10 }



pm1001pcAlmClientUpAccOos OBJECT-TYPE
	  SYNTAX EkiOnOff
	  MAX-ACCESS read-only
	  STATUS current
	  DESCRIPTION
        "
        Client Loss Of Synchronisation
        :This OID indicates the upstream
        client input port is in Loss of
        Synchronization  <Help>  This alarms
        indicates if the input client signal
        is correctly synchronized with
         the 66b/64b decoder <Condtype>
        CLIENT_UP_ACC_OOS <Probcause> receiveFailure
        (41) <Alarmtype> integrityViolation
        (7) <Polarity> (2)
        "
	  ::= { pm1001pcAlmclientMapperDeAlm 1 }



--- *****************************************************
---     LEAF for the dfrmAlm article
--- *****************************************************
pm1001pcAlmdfrmAlm OBJECT IDENTIFIER ::= { pm1001pcAlmLineCrit 128 }




pm1001pcAlmLineDwLof OBJECT-TYPE
	  SYNTAX EkiOnOff
	  MAX-ACCESS read-only
	  STATUS current
	  DESCRIPTION
        "
        SONET/SDH Line Loss Of Frame :This
        OID indicates that a Loss Of Frame
        has been detected on line input
        signal  <Help>  This alarm indicates
        if there is a Loss of Frame is
         detected on the line input signal
        <Condtype> LINE_DW_LOF <Probcause>
        receiveFailure (41) <Alarmtype>
        integrityViolation (7) <Polarity>
        (2)
        "
	  ::= { pm1001pcAlmdfrmAlm 4 }



pm1001pcAlmLineDwOof OBJECT-TYPE
	  SYNTAX EkiOnOff
	  MAX-ACCESS read-only
	  STATUS deprecated
	  DESCRIPTION
        "
        SONET/SDH Line Out Of Frame :This
        OID indicates that an Out Of Frame
        has been detected on line input
        signal  <Help>  This alarm indicates
        if there is a Out of Frame is detected
        on the line input signal <Condtype>
        LINE_DW_OOF <Probcause> receiveFailure
        (41) <Alarmtype> integrityViolation
        (7) <Polarity> (2)
        "
	  ::= { pm1001pcAlmdfrmAlm 3 }



pm1001pcAlmLineDwRdiDet OBJECT-TYPE
	  SYNTAX EkiOnOff
	  MAX-ACCESS read-only
	  STATUS current
	  DESCRIPTION
        "
        MS-RDI/L-RDI Detected On Line
         Input :This OID indicates that
        an MS-RDI has been detected on
         line input signal  <Help>  This
        alarm indicates if there is a MS-RDI/L-RDI
        is detected on the line input signal
        <Condtype> LINE_DW_RDI_DET <Probcause>
        remoteNodeTransmissionError (43)
        <Alarmtype> other (1) <Polarity>
        (2)
        "
	  ::= { pm1001pcAlmdfrmAlm 2 }



pm1001pcAlmLineDwAisDet OBJECT-TYPE
	  SYNTAX EkiOnOff
	  MAX-ACCESS read-only
	  STATUS current
	  DESCRIPTION
        "
        MS-AIS/L-AIS Detected On Line
         Input :This OID indicates that
        an MS-AIS has been detected on
         line input signal  <Help>  This
        alarm indicates if there is a MS-AIS/L-AIS
        is detected on the line input signal
        <Condtype> LINE_DW_AIS_DET <Probcause>
        receiveFailure (41) <Alarmtype>
        operationalViolation (8) <Polarity>
        (2)
        "
	  ::= { pm1001pcAlmdfrmAlm 1 }



--- *****************************************************
---     LEAF for the dfrmBer article
--- *****************************************************
pm1001pcAlmdfrmBer OBJECT IDENTIFIER ::= { pm1001pcAlmLineUrg 129 }




pm1001pcAlmLineDegrade OBJECT-TYPE
	  SYNTAX EkiOnOff
	  MAX-ACCESS read-only
	  STATUS current
	  DESCRIPTION
        "
        Fixed Line Signal Degrade :This
        OID indicates that the line input
        signal is DEGRADE. The assetion
        hysteresis is fixed to 10-8 (assertion)
        and 10-9 (de-assertion) <Condtype>
        LINE_DEGRADE <Probcause> degradedSignal
        (13) <Alarmtype> qualityOfServiceAlarm
        (3) <Polarity> (2)
        "
	  ::= { pm1001pcAlmdfrmBer 5 }



pm1001pcAlmLineSignalFail OBJECT-TYPE
	  SYNTAX EkiOnOff
	  MAX-ACCESS read-only
	  STATUS current
	  DESCRIPTION
        "
        Custom Line Signal Fail :This
         OID indicates that the line input
        signal is FAIL. The assertion hysteresis
        can be customized by the host <Condtype>
        LINE_SIGNAL_FAIL <Probcause> receiveFailure
        (41) <Alarmtype> integrityViolation
        (7) <Polarity> (2)
        "
	  ::= { pm1001pcAlmdfrmBer 2 }



pm1001pcAlmLineSignalDegrade OBJECT-TYPE
	  SYNTAX EkiOnOff
	  MAX-ACCESS read-only
	  STATUS current
	  DESCRIPTION
        "
        Custom Line Signal Degrade :This
        OID indicates that the line input
        signal is DEGRADE. The assertion
        hysteresis can customized by the
        host <Condtype> LINE_SIGNAL_DEGRADE
        <Probcause> degradedSignal (13)
        <Alarmtype> qualityOfServiceAlarm
        (3) <Polarity> (2)
        "
	  ::= { pm1001pcAlmdfrmBer 1 }



--- *****************************************************
---     LEAF for the lineSyncAlarms article
--- *****************************************************
pm1001pcAlmlineSyncAlarms OBJECT IDENTIFIER ::= { pm1001pcAlmLineCrit 133 }




pm1001pcAlmLineDwLos OBJECT-TYPE
	  SYNTAX EkiOnOff
	  MAX-ACCESS read-only
	  STATUS current
	  DESCRIPTION
        "
        Line Input Loss Of Signal :This
        OID indicates a loss of signal
         on the 10 Gb/s input.  <Help>
          This alarm indicates if an optical
        signal is detected on the line
         transceiver input <Condtype> LINE_DW_LOS
        <Probcause> receiveFailure (41)
        <Alarmtype> physicalViolation (9)
        <Polarity> (2)
        "
	  ::= { pm1001pcAlmlineSyncAlarms 16 }



pm1001pcAlmLineUpLockerr OBJECT-TYPE
	  SYNTAX EkiOnOff
	  MAX-ACCESS read-only
	  STATUS current
	  DESCRIPTION
        "
        Upstream Clock Lock Error :This
        OID indicates that the serializer
        output 10 Gb/s clock multiplier
        unit is not locked. <Condtype>
         LINE_UP_LOCKERR <Probcause> receiveFailure
        (41) <Alarmtype> equipmentAlarm
        (5) <Polarity> (2)
        "
	  ::= { pm1001pcAlmlineSyncAlarms 13 }



pm1001pcAlmLineDwLockerr OBJECT-TYPE
	  SYNTAX EkiOnOff
	  MAX-ACCESS read-only
	  STATUS current
	  DESCRIPTION
        "
        Downstream Clock Lock Error :This
        OID indicates that the deserializer
        input 10 Gb/s clock recovery is
        not locked. <Condtype> LINE_DW_LOCKERR
        <Probcause> receiveFailure (41)
        <Alarmtype> equipmentAlarm (5)
         <Polarity> (2)
        "
	  ::= { pm1001pcAlmlineSyncAlarms 12 }



--- *****************************************************
---     LEAF for the modInitFailLevel2 article
--- *****************************************************
pm1001pcAlmmodInitFailLevel2 OBJECT IDENTIFIER ::= { pm1001pcAlmOtherUrg 194 }




pm1001pcAlmSwInitFail OBJECT-TYPE
	  SYNTAX EkiOnOff
	  MAX-ACCESS read-only
	  STATUS current
	  DESCRIPTION
        "
        SW Init Fail :This OID indicates
        that the SW intialization has caused
        unknown intial conditions  <Help>
         This alarm indicates if the SW
        module is correctly initialized
        <Condtype> SW_INIT_FAIL <Probcause>
        softwareError (47) <Alarmtype>
         processingErrorAlarm (4) <Polarity>
        (2)
        "
	  ::= { pm1001pcAlmmodInitFailLevel2 5 }



pm1001pcAlmResetHwInitFail OBJECT-TYPE
	  SYNTAX EkiOnOff
	  MAX-ACCESS read-only
	  STATUS current
	  DESCRIPTION
        "
        Reset HW Init Fail :This OID indicates
        that the HW intialization has caused
        unknown intial conditions  <Help>
         This alarm indicates if the HW
        has been correctly initialized
         <Condtype> RESET_HW_INIT_FAIL
         <Probcause> softwareError (47)
        <Alarmtype> processingErrorAlarm
        (4) <Polarity> (2)
        "
	  ::= { pm1001pcAlmmodInitFailLevel2 4 }



pm1001pcAlmBootUndone OBJECT-TYPE
	  SYNTAX EkiOnOff
	  MAX-ACCESS read-only
	  STATUS current
	  DESCRIPTION
        "
        Boot Undone :This OID indicates
        that the boot has not been correctly
        achieved  <Help>  This alarm indicates
        if the module has correctly boot
        <Condtype> BOOT_UNDONE <Probcause>
        softwareError (47) <Alarmtype>
         processingErrorAlarm (4) <Polarity>
        (2)
        "
	  ::= { pm1001pcAlmmodInitFailLevel2 3 }



pm1001pcAlmNextColdBootForced OBJECT-TYPE
	  SYNTAX EkiOnOff
	  MAX-ACCESS read-only
	  STATUS current
	  DESCRIPTION
        "
        Next Cold Boot Forced :This OID
        indicates that the next Reset will
        be forced Cold  <Help>  This alarm
        indicates that the next reset of
        the module will be forced to cold
        reset <Condtype> NEXT_COLD_BOOT_FORCED
        <Probcause> informationalStatus(1000)
        <Alarmtype> other (1) <Polarity>
        (2)
        "
	  ::= { pm1001pcAlmmodInitFailLevel2 2 }



pm1001pcAlmLedFail OBJECT-TYPE
	  SYNTAX EkiOnOff
	  MAX-ACCESS read-only
	  STATUS current
	  DESCRIPTION
        "
        Led Fail :This OID indicates that
        Led register has not been correctly
        initalized  <Help>  This alarm
         indicates if the module LEDs are
        correctly initialized <Condtype>
        LED_FAIL <Probcause> softwareError
        (47) <Alarmtype> processingErrorAlarm
        (4) <Polarity> (2)
        "
	  ::= { pm1001pcAlmmodInitFailLevel2 1 }



--- *****************************************************
---     LEAF for the modInitFailLevel3 article
--- *****************************************************
pm1001pcAlmmodInitFailLevel3 OBJECT IDENTIFIER ::= { pm1001pcAlmOtherUrg 195 }




pm1001pcAlmClientInitFail OBJECT-TYPE
	  SYNTAX EkiOnOff
	  MAX-ACCESS read-only
	  STATUS current
	  DESCRIPTION
        "
        Client Init Fail :This OID indicates
        that Client 1 registers subset
         has not been correctly initialized
         <Help>  This alarm indicates if
        the client port is correctly initialized
        <Condtype> CLIENT_INIT_FAIL <Probcause>
        softwareError (47) <Alarmtype>
         processingErrorAlarm (4) <Polarity>
        (2)
        "
	  ::= { pm1001pcAlmmodInitFailLevel3 9 }



pm1001pcAlmLineInitFail OBJECT-TYPE
	  SYNTAX EkiOnOff
	  MAX-ACCESS read-only
	  STATUS current
	  DESCRIPTION
        "
        Line Init Fail :This OID indicates
        that the Line registersvsubset
         has not been correctly initialized
         <Help>  This alarm indicates if
        the line port is correctly initialized
        <Condtype> LINE_INIT_FAIL <Probcause>
        softwareError (47) <Alarmtype>
         processingErrorAlarm (4) <Polarity>
        (2)
        "
	  ::= { pm1001pcAlmmodInitFailLevel3 7 }



pm1001pcAlmXfp2InitFail OBJECT-TYPE
	  SYNTAX EkiOnOff
	  MAX-ACCESS read-only
	  STATUS current
	  DESCRIPTION
        "
        XFP2 Init Fail :This OID indicates
        that the XFP has not been correctly
        initialized  <Help>  This alarm
        indicates if the line transceiver
        2 is correctly initialized <Condtype>
        XFP2_INIT_FAIL <Probcause> softwareError
        (47) <Alarmtype> processingErrorAlarm
        (4) <Polarity> (2)
        "
	  ::= { pm1001pcAlmmodInitFailLevel3 6 }



pm1001pcAlmXfp1InitFail OBJECT-TYPE
	  SYNTAX EkiOnOff
	  MAX-ACCESS read-only
	  STATUS current
	  DESCRIPTION
        "
        XFP1 Init Fail :This OID indicates
        that the XFP has not been correctly
        initialized  <Help>  This alarm
        indicates if the line transceiver
        1 is correctly initialized <Condtype>
        XFP1_INIT_FAIL <Probcause> softwareError
        (47) <Alarmtype> processingErrorAlarm
        (4) <Polarity> (2)
        "
	  ::= { pm1001pcAlmmodInitFailLevel3 5 }



pm1001pcAlmInitModuleFail OBJECT-TYPE
	  SYNTAX EkiOnOff
	  MAX-ACCESS read-only
	  STATUS current
	  DESCRIPTION
        "
        Init Module Fail :This OID indicates
        that the Module has not been correctly
        initialized  <Help>  This alarm
        indicates if the SW module is correctly
        initialized <Condtype> INIT_MODULE_FAIL
        <Probcause> softwareError (47)
         <Alarmtype> processingErrorAlarm
        (4) <Polarity> (2)
        "
	  ::= { pm1001pcAlmmodInitFailLevel3 3 }



pm1001pcAlmObmTypeReadFail OBJECT-TYPE
	  SYNTAX EkiOnOff
	  MAX-ACCESS read-only
	  STATUS current
	  DESCRIPTION
        "
        OBM Type Read Fail :This OID indicates
        that OBM type has not been recognized
         <Help>  This alarm indicates if
        the OBM board has been correctly
        identified <Condtype> OBM_TYPE_READ_FAIL
        <Probcause> softwareError (47)
         <Alarmtype> processingErrorAlarm
        (4) <Polarity> (2)
        "
	  ::= { pm1001pcAlmmodInitFailLevel3 2 }



pm1001pcAlmGwIdentFail OBJECT-TYPE
	  SYNTAX EkiOnOff
	  MAX-ACCESS read-only
	  STATUS current
	  DESCRIPTION
        "
        GW Ident Fail :This OID indicates
        that GW identification has not
         been read  <Help>  This alarm
         indicates if the GW has been correctly
        identified <Condtype> GW_IDENT_FAIL
        <Probcause> softwareError (47)
         <Alarmtype> processingErrorAlarm
        (4) <Polarity> (2)
        "
	  ::= { pm1001pcAlmmodInitFailLevel3 1 }



--- *****************************************************
---     LEAF for the lineXfpAlarm1 article
--- *****************************************************
pm1001pcAlmlineXfpAlarm1 OBJECT IDENTIFIER ::= { pm1001pcAlmLineUrg 208 }




pm1001pcAlmLineRxPowerHighAlarm OBJECT-TYPE
	  SYNTAX EkiOnOff
	  MAX-ACCESS read-only
	  STATUS current
	  DESCRIPTION
        "
        Line Optical Rx Power High Alarm
        :Alarm indicating that the XFP
         received optical power is higher
        than the threshold value written
        in the XFP EEPROM <Condtype> LINE_RX_POWER_HIGH_ALARM
        <Probcause> receiveFailure (41)
        <Alarmtype> equipmentAlarm (5)
         <Polarity> (2)
        "
	  ::= { pm1001pcAlmlineXfpAlarm1 16 }



pm1001pcAlmLineRxPowerLowAlarm OBJECT-TYPE
	  SYNTAX EkiOnOff
	  MAX-ACCESS read-only
	  STATUS current
	  DESCRIPTION
        "
        Line Optical Rx Power Low Alarm
        :Alarm indicating that the XFP
         received optical power is lower
        than the threshold value written
        in the XFP EEPROM  <Condtype> LINE_RX_POWER_LOW_ALARM
        <Probcause> receiveFailure (41)
        <Alarmtype> equipmentAlarm (5)
         <Polarity> (2)
        "
	  ::= { pm1001pcAlmlineXfpAlarm1 15 }



pm1001pcAlmLineTempHighAlarm OBJECT-TYPE
	  SYNTAX EkiOnOff
	  MAX-ACCESS read-only
	  STATUS current
	  DESCRIPTION
        "
        Line Transceiver Temp High Alarm
        :Alarm indicating that the XFP/OTX
        temperature is higher than the
         threshold value written in the
        XFP EEPROM <Condtype> LINE_TEMP_HIGH_ALARM
        <Probcause> temperatureUnacceptable
        (51) <Alarmtype> equipmentAlarm
        (5) <Polarity> (2)
        "
	  ::= { pm1001pcAlmlineXfpAlarm1 8 }



pm1001pcAlmLineTempLowAlarm OBJECT-TYPE
	  SYNTAX EkiOnOff
	  MAX-ACCESS read-only
	  STATUS current
	  DESCRIPTION
        "
        Line Transceiver Temp Low Alarm
        :Alarm indicating that the XFP/OTX
        temperature is lower than the threshold
        value written in the XFP/OTX EEPROM
        <Condtype> LINE_TEMP_LOW_ALARM
         <Probcause> temperatureUnacceptable
        (51) <Alarmtype> equipmentAlarm
        (5) <Polarity> (2)
        "
	  ::= { pm1001pcAlmlineXfpAlarm1 7 }



pm1001pcAlmLineTxBiasHighAlarm OBJECT-TYPE
	  SYNTAX EkiOnOff
	  MAX-ACCESS read-only
	  STATUS current
	  DESCRIPTION
        "
        Line Transceiver Bias High Alarm
        :Alarm indicating that the XFP/OTX
        transmitter laser bias current
         is higher than the threshold value
        written in the XFP EEPROM <Condtype>
        LINE_TX_BIAS_HIGH_ALARM <Probcause>
        transmitterFailure (56) <Alarmtype>
        equipmentAlarm (5) <Polarity> (2)
        "
	  ::= { pm1001pcAlmlineXfpAlarm1 4 }



pm1001pcAlmLineTxBiasLowAlarm OBJECT-TYPE
	  SYNTAX EkiOnOff
	  MAX-ACCESS read-only
	  STATUS current
	  DESCRIPTION
        "
        Line Transceiver Bias Low Alarm
        :Alarm indicating that the XFP/OTX
        transmitter laser bias current
         is lower than the threshold value
        written in the XFP/OTX EEPROM <Condtype>
        LINE_TX_BIAS_LOW_ALARM <Probcause>
        transmitterFailure (56) <Alarmtype>
        equipmentAlarm (5) <Polarity> (2)
        "
	  ::= { pm1001pcAlmlineXfpAlarm1 3 }



pm1001pcAlmLineTxPowerHighAlarm OBJECT-TYPE
	  SYNTAX EkiOnOff
	  MAX-ACCESS read-only
	  STATUS current
	  DESCRIPTION
        "
        Line Optical Tx Power High Alarm
        :Alarm indicating that the XFP/OTX
        transmitter transmitter output
         power is higher than the threshold
        value written in the XFP EEPROM
        <Condtype> LINE_TX_POWER_HIGH_ALARM
        <Probcause> transmitterFailure
         (56) <Alarmtype> equipmentAlarm
        (5) <Polarity> (2)
        "
	  ::= { pm1001pcAlmlineXfpAlarm1 2 }



pm1001pcAlmLineTxPowerLowAlarm OBJECT-TYPE
	  SYNTAX EkiOnOff
	  MAX-ACCESS read-only
	  STATUS current
	  DESCRIPTION
        "
        Line Optical Tx Power Low Alarm
        :Alarm indicating that the XFP/OTX
        transmitter transmitter output
         power is lower than the threshold
        value written in the XFP/OTX EEPROM
        <Condtype> LINE_TX_POWER_LOW_ALARM
        <Probcause> transmitterFailure
         (56) <Alarmtype> equipmentAlarm
        (5) <Polarity> (2)
        "
	  ::= { pm1001pcAlmlineXfpAlarm1 1 }



--- *****************************************************
---     LEAF for the lineXfpWarnings article
--- *****************************************************
pm1001pcAlmlineXfpWarnings OBJECT IDENTIFIER ::= { pm1001pcAlmLineNurg 209 }




pm1001pcAlmLineRxPowerHighWarning OBJECT-TYPE
	  SYNTAX EkiOnOff
	  MAX-ACCESS read-only
	  STATUS current
	  DESCRIPTION
        "
        Line Optical Rx Power High Warning
        :Warning indicating that the XFP
        received optical power is higher
        than the threshold value written
        in the XFP EEPROM <Condtype> LINE_RX_POWER_HIGH_WARNING
        <Probcause> receiveFailure (41)
        <Alarmtype> equipmentAlarm (5)
         <Polarity> (2)
        "
	  ::= { pm1001pcAlmlineXfpWarnings 16 }



pm1001pcAlmLineRxPowerLowWarning OBJECT-TYPE
	  SYNTAX EkiOnOff
	  MAX-ACCESS read-only
	  STATUS current
	  DESCRIPTION
        "
        Line Optical Rx Power Low Warning
        :Warning indicating that the XFP
        received optical power is lower
        than the threshold value written
        in the XFP EEPROM  <Condtype> LINE_RX_POWER_LOW_WARNING
        <Probcause> receiveFailure (41)
        <Alarmtype> equipmentAlarm (5)
         <Polarity> (2)
        "
	  ::= { pm1001pcAlmlineXfpWarnings 15 }



pm1001pcAlmLineTempHighWarning OBJECT-TYPE
	  SYNTAX EkiOnOff
	  MAX-ACCESS read-only
	  STATUS current
	  DESCRIPTION
        "
        Line Transceiver Temp High Warning
        :Warning indicating that the XFP/OTX
        temperature is higher than the
         threshold value written in the
        XFP EEPROM <Condtype> LINE_TEMP_HIGH_WARNING
        <Probcause> temperatureUnacceptable
        (51) <Alarmtype> equipmentAlarm
        (5) <Polarity> (2)
        "
	  ::= { pm1001pcAlmlineXfpWarnings 8 }



pm1001pcAlmLineTempLowWarning OBJECT-TYPE
	  SYNTAX EkiOnOff
	  MAX-ACCESS read-only
	  STATUS current
	  DESCRIPTION
        "
        Line Transceiver Temp Low Warning
        :Warning indicating that the XFP/OTX
        temperature is lower than the threshold
        value written in the XFP/OTX EEPROM
        <Condtype> LINE_TEMP_LOW_WARNING
        <Probcause> temperatureUnacceptable
        (51) <Alarmtype> equipmentAlarm
        (5) <Polarity> (2)
        "
	  ::= { pm1001pcAlmlineXfpWarnings 7 }



pm1001pcAlmLineTxBiasHighWarning OBJECT-TYPE
	  SYNTAX EkiOnOff
	  MAX-ACCESS read-only
	  STATUS current
	  DESCRIPTION
        "
        Line Transceiver Bias High Warning
        :Warning indicating that the XFP/OTX
        transmitter laser bias current
         is higher than the threshold value
        written in the XFP EEPROM <Condtype>
        LINE_TX_BIAS_HIGH_WARNING <Probcause>
        transmitterFailure (56) <Alarmtype>
        equipmentAlarm (5) <Polarity> (2)
        "
	  ::= { pm1001pcAlmlineXfpWarnings 4 }



pm1001pcAlmLineTxBiasLowWarning OBJECT-TYPE
	  SYNTAX EkiOnOff
	  MAX-ACCESS read-only
	  STATUS current
	  DESCRIPTION
        "
        Line Transceiver Bias Low Warning
        :Warning indicating that the XFP/OTX
        transmitter laser bias current
         is lower than the threshold value
        written in the XFP/OTX EEPROM <Condtype>
        LINE_TX_BIAS_LOW_WARNING <Probcause>
        transmitterFailure (56) <Alarmtype>
        equipmentAlarm (5) <Polarity> (2)
        "
	  ::= { pm1001pcAlmlineXfpWarnings 3 }



pm1001pcAlmLineTxPowerHighWarning OBJECT-TYPE
	  SYNTAX EkiOnOff
	  MAX-ACCESS read-only
	  STATUS current
	  DESCRIPTION
        "
        Line Optical Tx Power High Warning
        :Warning indicating that the XFP/OTX
        transmitter transmitter output
         power is higher than the threshold
        value written in the XFP EEPROM
        <Condtype> LINE_TX_POWER_HIGH_WARNING
        <Probcause> transmitterFailure
         (56) <Alarmtype> equipmentAlarm
        (5) <Polarity> (2)
        "
	  ::= { pm1001pcAlmlineXfpWarnings 2 }



pm1001pcAlmLineTxPowerLowWarning OBJECT-TYPE
	  SYNTAX EkiOnOff
	  MAX-ACCESS read-only
	  STATUS current
	  DESCRIPTION
        "
        Line Optical Tx Power Low Warning
        :Warning indicating that the XFP/OTX
        transmitter transmitter output
         power is lower than the threshold
        value written in the XFP/OTX EEPROM
        <Condtype> LINE_TX_POWER_LOW_WARNING
        <Probcause> transmitterFailure
         (56) <Alarmtype> equipmentAlarm
        (5) <Polarity> (2)
        "
	  ::= { pm1001pcAlmlineXfpWarnings 1 }



--- *****************************************************
---     LEAF for the lineXfpAlarms2 article
--- *****************************************************
pm1001pcAlmlineXfpAlarms2 OBJECT IDENTIFIER ::= { pm1001pcAlmLineCrit 211 }




pm1001pcAlmLineApdSupplyFault OBJECT-TYPE
	  SYNTAX EkiOnOff
	  MAX-ACCESS read-only
	  STATUS current
	  DESCRIPTION
        "
        Line Rx Photodiode Power Failed
        :This OID indicates a failure on
        the APD power supply  <Help>  This
        alarm indicates if the APD power
        supply is in fail condition <Condtype>
        LINE_APD_SUPPLY_FAULT <Probcause>
        receiverFailure (42) <Alarmtype>
        equipmentAlarm (5) <Polarity> (2)
        "
	  ::= { pm1001pcAlmlineXfpAlarms2 16 }



pm1001pcAlmLineTecFault OBJECT-TYPE
	  SYNTAX EkiOnOff
	  MAX-ACCESS read-only
	  STATUS current
	  DESCRIPTION
        "
        Line Optical Tx Temp Regul. Failed
        :This OID indicates a failure on
        the TEC module  <Help>  This alarm
        indicates if the TEC of the line
        transceiver is in fail condition
        <Condtype> LINE_TEC_FAULT <Probcause>
        transmitterFailure (56) <Alarmtype>
        equipmentAlarm (5) <Polarity> (2)
        "
	  ::= { pm1001pcAlmlineXfpAlarms2 15 }



pm1001pcAlmLineWavelengthUnlocked OBJECT-TYPE
	  SYNTAX EkiOnOff
	  MAX-ACCESS read-only
	  STATUS current
	  DESCRIPTION
        "
        Line Optical Tx Wavelength Unlock
        :This OID indicates that the wavelength
        error is exceeding the manufacturer
        tolerance  <Help>  This alarm indicates
        if the wavelenght of the line transceiver
        is locked <Condtype> LINE_WAVELENGTH_UNLOCKED
        <Probcause> transmitterFailure
         (56) <Alarmtype> equipmentAlarm
        (5) <Polarity> (2)
        "
	  ::= { pm1001pcAlmlineXfpAlarms2 14 }



pm1001pcAlmLineTxNr OBJECT-TYPE
	  SYNTAX EkiOnOff
	  MAX-ACCESS read-only
	  STATUS current
	  DESCRIPTION
        "
        Line Optical Tx Not Ready :This
        OID indicates a condition has arisen
        leading to invalid data on the
         transmitting side  <Help>  This
        alarm indicates if the Tx part
         of the line transceiver is ready
        <Condtype> LINE_TX_NR <Probcause>
        transmitterFailure (56) <Alarmtype>
        equipmentAlarm (5) <Polarity> (2)
        "
	  ::= { pm1001pcAlmlineXfpAlarms2 8 }



pm1001pcAlmLineTxFault OBJECT-TYPE
	  SYNTAX EkiOnOff
	  MAX-ACCESS read-only
	  STATUS current
	  DESCRIPTION
        "
        Line Optical Tx Failure :This
         OID indicates a fault condition
        on the laser detected by the safety
        syste  <Help>  This alarm indicates
        if the laser of the line transceiver
        is in fail condition <Condtype>
        LINE_TX_FAULT <Probcause> transmitterFailure
        (56) <Alarmtype> equipmentAlarm
        (5) <Polarity> (2)
        "
	  ::= { pm1001pcAlmlineXfpAlarms2 7 }



pm1001pcAlmLineTxCdrNotLocked1 OBJECT-TYPE
	  SYNTAX EkiOnOff
	  MAX-ACCESS read-only
	  STATUS current
	  DESCRIPTION
        "
        Line Optical Tx CDR Unlocked :This
        OID indicates a loss of lock on
        the transmitting side CDR has been
        detected.  <Help>  This alarm indicates
        if the Tx CDR is locked in the
         line transceiver <Condtype> LINE_TX_CDR_NOT_LOCKED1
        <Probcause> transmitterFailure
         (56) <Alarmtype> equipmentAlarm
        (5) <Polarity> (2)
        "
	  ::= { pm1001pcAlmlineXfpAlarms2 6 }



pm1001pcAlmLineRxNr OBJECT-TYPE
	  SYNTAX EkiOnOff
	  MAX-ACCESS read-only
	  STATUS current
	  DESCRIPTION
        "
        Line Optical Rx Not Ready :This
        OID indicates that a condition
         has arisen leading to invalid
         data on the receiving side.  <Help>
         This alarm indicates if the Rx
        part of the line transceiver is
        ready <Condtype> LINE_RX_NR <Probcause>
        receiveFailure (41) <Alarmtype>
        equipmentAlarm (5) <Polarity> (2)
        "
	  ::= { pm1001pcAlmlineXfpAlarms2 5 }



pm1001pcAlmLineRxCdrNotLocked1 OBJECT-TYPE
	  SYNTAX EkiOnOff
	  MAX-ACCESS read-only
	  STATUS current
	  DESCRIPTION
        "
        Line Optical Rx CDR Unlocked :This
        OID indicates that a loss of lock
        on the receiving side CDR has been
        detected  <Help>  This alarm indicates
        if the Rx CDR is locked in the
         line transceiver <Condtype> LINE_RX_CDR_NOT_LOCKED1
        <Probcause> receiveFailure (41)
        <Alarmtype> equipmentAlarm (5)
         <Polarity> (2)
        "
	  ::= { pm1001pcAlmlineXfpAlarms2 3 }



pm1001pcAlmLineModNr OBJECT-TYPE
	  SYNTAX EkiOnOff
	  MAX-ACCESS read-only
	  STATUS current
	  DESCRIPTION
        "
        Line Optical Module Not Ready
         :This OID indicates that the module
        is unable to determine correct
         data.  <Help>  This alarm indicates
        if the line transceiver is ready
        <Condtype> LINE_MOD_NR <Probcause>
        receiveFailure (41) <Alarmtype>
        equipmentAlarm (5) <Polarity> (2)
        "
	  ::= { pm1001pcAlmlineXfpAlarms2 2 }



--- *****************************************************
---     LEAF for the lineXfpSupplyAlarm article
--- *****************************************************
pm1001pcAlmlineXfpSupplyAlarm OBJECT IDENTIFIER ::= { pm1001pcAlmLineUrg 212 }




pm1001pcAlmLineVcc5HighWarning OBJECT-TYPE
	  SYNTAX EkiOnOff
	  MAX-ACCESS read-only
	  STATUS current
	  DESCRIPTION
        "
        VCC5 Power Supply High Warning
        :Warning indicating the XFP/OTX
        VCC5 power supply is higher than
        the threshold written in the EEPROM
        <Condtype> LINE_VCC5_HIGH_WARNING
        <Probcause> powerProblem (36) <Alarmtype>
        equipmentAlarm (5) <Polarity> (2)
        "
	  ::= { pm1001pcAlmlineXfpSupplyAlarm 16 }



pm1001pcAlmLineVcc5LowWarning OBJECT-TYPE
	  SYNTAX EkiOnOff
	  MAX-ACCESS read-only
	  STATUS current
	  DESCRIPTION
        "
        VCC5 Power Supply Low Warning
         :Warning indicating the XFP/OTX
        VCC5 power supply is lower than
        the threshold written in the EEPROM
        <Condtype> LINE_VCC5_LOW_WARNING
        <Probcause> powerProblem (36) <Alarmtype>
        equipmentAlarm (5) <Polarity> (2)
        "
	  ::= { pm1001pcAlmlineXfpSupplyAlarm 15 }



pm1001pcAlmLineVcc3HighWarning OBJECT-TYPE
	  SYNTAX EkiOnOff
	  MAX-ACCESS read-only
	  STATUS current
	  DESCRIPTION
        "
        VCC3 Power Supply High Warning
        :Warning indicating the XFP/OTX
        VCC3 power supply is higher than
        the threshold written in the EEPROM
        <Condtype> LINE_VCC3_HIGH_WARNING
        <Probcause> powerProblem (36) <Alarmtype>
        equipmentAlarm (5) <Polarity> (2)
        "
	  ::= { pm1001pcAlmlineXfpSupplyAlarm 14 }



pm1001pcAlmLineVcc3LowWarning OBJECT-TYPE
	  SYNTAX EkiOnOff
	  MAX-ACCESS read-only
	  STATUS current
	  DESCRIPTION
        "
        VCC3 Power Supply Low Warning
         :Warning indicating the XFP/OTX
        VCC3 power supply is lower than
        the threshold written in the EEPROM
        <Condtype> LINE_VCC3_LOW_WARNING
        <Probcause> powerProblem (36) <Alarmtype>
        equipmentAlarm (5) <Polarity> (2)
        "
	  ::= { pm1001pcAlmlineXfpSupplyAlarm 13 }



pm1001pcAlmLineVcc2HighWarning OBJECT-TYPE
	  SYNTAX EkiOnOff
	  MAX-ACCESS read-only
	  STATUS current
	  DESCRIPTION
        "
        VCC2 Power Supply High Warning
        :Warning indicating the XFP/OTX
        VCC2 power supply is higher than
        the threshold written in the EEPROM
        <Condtype> LINE_VCC2_HIGH_WARNING
        <Probcause> powerProblem (36) <Alarmtype>
        equipmentAlarm (5) <Polarity> (2)
        "
	  ::= { pm1001pcAlmlineXfpSupplyAlarm 12 }



pm1001pcAlmLineVcc2LowWarning OBJECT-TYPE
	  SYNTAX EkiOnOff
	  MAX-ACCESS read-only
	  STATUS current
	  DESCRIPTION
        "
        VCC2 Power Supply Low Warning
         :Warning indicating the XFP/OTX
        VCC2 power supply is lower than
        the threshold written in the EEPROM
        <Condtype> LINE_VCC2_LOW_WARNING
        <Probcause> powerProblem (36) <Alarmtype>
        equipmentAlarm (5) <Polarity> (2)
        "
	  ::= { pm1001pcAlmlineXfpSupplyAlarm 11 }



pm1001pcAlmLineVee5HighWarning OBJECT-TYPE
	  SYNTAX EkiOnOff
	  MAX-ACCESS read-only
	  STATUS current
	  DESCRIPTION
        "
        VEE5 Power Supply High Warning
        :Warning indicating the XFP/OTX
        VEE5 power supply is higher than
        the threshold written in the EEPROM
        <Condtype> LINE_VEE5_HIGH_WARNING
        <Probcause> powerProblem (36) <Alarmtype>
        equipmentAlarm (5) <Polarity> (2)
        "
	  ::= { pm1001pcAlmlineXfpSupplyAlarm 10 }



pm1001pcAlmLineVee5LowLineWarning OBJECT-TYPE
	  SYNTAX EkiOnOff
	  MAX-ACCESS read-only
	  STATUS current
	  DESCRIPTION
        "
        VEE5 Power Supply Low Warning
         :Warning indicating the XFP/OTX
        VEE5 power supply is lower than
        the threshold written in the EEPROM
        <Condtype> LINE_VEE5_LOW_LINE_WARNING
        <Probcause> powerProblem (36) <Alarmtype>
        equipmentAlarm (5) <Polarity> (2)
        "
	  ::= { pm1001pcAlmlineXfpSupplyAlarm 9 }



pm1001pcAlmLineVcc5HighAlarm OBJECT-TYPE
	  SYNTAX EkiOnOff
	  MAX-ACCESS read-only
	  STATUS current
	  DESCRIPTION
        "
        VCC5 Power Supply High Alarm :Alarm
        indicating the XFP/OTX VCC5 power
        supply is higher than the threshold
        written in the EEPROM <Condtype>
        LINE_VCC5_HIGH_ALARM <Probcause>
        powerProblem (36) <Alarmtype> equipmentAlarm
        (5) <Polarity> (2)
        "
	  ::= { pm1001pcAlmlineXfpSupplyAlarm 8 }



pm1001pcAlmLineVcc5LowAlarm OBJECT-TYPE
	  SYNTAX EkiOnOff
	  MAX-ACCESS read-only
	  STATUS current
	  DESCRIPTION
        "
        VCC5 Power Supply Low Alarm :Alarm
        indicating the XFP/OTX VCC5 power
        supply is lower than the threshold
        written in the EEPROM <Condtype>
        LINE_VCC5_LOW_ALARM <Probcause>
        powerProblem (36) <Alarmtype> equipmentAlarm
        (5) <Polarity> (2)
        "
	  ::= { pm1001pcAlmlineXfpSupplyAlarm 7 }



pm1001pcAlmLineVcc3HighAlarm OBJECT-TYPE
	  SYNTAX EkiOnOff
	  MAX-ACCESS read-only
	  STATUS current
	  DESCRIPTION
        "
        VCC3 Power Supply High Alarm :Alarm
        indicating the XFP/OTX VCC3 power
        supply is higher than the threshold
        written in the EEPROM <Condtype>
        LINE_VCC3_HIGH_ALARM <Probcause>
        powerProblem (36) <Alarmtype> equipmentAlarm
        (5) <Polarity> (2)
        "
	  ::= { pm1001pcAlmlineXfpSupplyAlarm 6 }



pm1001pcAlmLineVcc3LowAlarm OBJECT-TYPE
	  SYNTAX EkiOnOff
	  MAX-ACCESS read-only
	  STATUS current
	  DESCRIPTION
        "
        VCC3 Power Supply Low Alarm :Alarm
        indicating the XFP/OTX VCC3 power
        supply is lower than the threshold
        written in the EEPROM <Condtype>
        LINE_VCC3_LOW_ALARM <Probcause>
        powerProblem (36) <Alarmtype> equipmentAlarm
        (5) <Polarity> (2)
        "
	  ::= { pm1001pcAlmlineXfpSupplyAlarm 5 }



pm1001pcAlmLineVcc2HighAlarm OBJECT-TYPE
	  SYNTAX EkiOnOff
	  MAX-ACCESS read-only
	  STATUS current
	  DESCRIPTION
        "
        VCC2 Power Supply High Alarm :Alarm
        indicating the XFP/OTX VCC2 power
        supply is higher than the threshold
        written in the EEPROM <Condtype>
        LINE_VCC2_HIGH_ALARM <Probcause>
        powerProblem (36) <Alarmtype> equipmentAlarm
        (5) <Polarity> (2)
        "
	  ::= { pm1001pcAlmlineXfpSupplyAlarm 4 }



pm1001pcAlmLineVcc2LowAlarm OBJECT-TYPE
	  SYNTAX EkiOnOff
	  MAX-ACCESS read-only
	  STATUS current
	  DESCRIPTION
        "
        VCC2 Power Supply Low Alarm :Alarm
        indicating the XFP/OTX VCC2 power
        supply is lower than the threshold
        written in the EEPROM <Condtype>
        LINE_VCC2_LOW_ALARM <Probcause>
        powerProblem (36) <Alarmtype> equipmentAlarm
        (5) <Polarity> (2)
        "
	  ::= { pm1001pcAlmlineXfpSupplyAlarm 3 }



pm1001pcAlmLineVee5HighAlarm OBJECT-TYPE
	  SYNTAX EkiOnOff
	  MAX-ACCESS read-only
	  STATUS current
	  DESCRIPTION
        "
        VEE5 Power Supply High Alarm :Alarm
        indicating the XFP/OTX VEE5 power
        supply is higher than the threshold
        written in the EEPROM <Condtype>
        LINE_VEE5_HIGH_ALARM <Probcause>
        powerProblem (36) <Alarmtype> equipmentAlarm
        (5) <Polarity> (2)
        "
	  ::= { pm1001pcAlmlineXfpSupplyAlarm 2 }



pm1001pcAlmLineVee5LowAlarm OBJECT-TYPE
	  SYNTAX EkiOnOff
	  MAX-ACCESS read-only
	  STATUS current
	  DESCRIPTION
        "
        VEE5 Power Supply Low Alarm :Alarm
        indicating the XFP/OTX VEE5 power
        supply is lower than the threshold
        written in the EEPROM <Condtype>
        LINE_VEE5_LOW_ALARM <Probcause>
        powerProblem (36) <Alarmtype> equipmentAlarm
        (5) <Polarity> (2)
        "
	  ::= { pm1001pcAlmlineXfpSupplyAlarm 1 }








--- *****************************************************
--- $$$$$$$$$$$$$$$$$$$$$$$$$$$$$$$$$$$$$$$$$$$$$$$$$$$$$
---     CONTROLS
--- $$$$$$$$$$$$$$$$$$$$$$$$$$$$$$$$$$$$$$$$$$$$$$$$$$$$$
--- *****************************************************



--- *****************************************************
---     LEAF for the confMgnt1 article
--- *****************************************************
pm1001pcCtrlconfMgnt1 OBJECT IDENTIFIER ::= { pm1001pcCtrlOther 1 }




pm1001pcCtrlConf2Clear1 OBJECT-TYPE
	  SYNTAX EkiOnOff
	  MAX-ACCESS read-write
	  STATUS current
	  DESCRIPTION
        "
        Clear Configuration Tables :This
        OID clears the configuration tables
        from configuration2 in the flash.
         <Help>  This control restores
         the default configuration of the
        module
        "
	  ::= { pm1001pcCtrlconfMgnt1 14 }



pm1001pcCtrlConf2Flash1 OBJECT-TYPE
	  SYNTAX EkiOnOff
	  MAX-ACCESS read-write
	  STATUS current
	  DESCRIPTION
        "
        Write Configuration Tables :This
        OID saves the current configuration
        of the PM as configuration2 in
         the flash.  <Help>  This control
        saves the customer configuration
        on the module
        "
	  ::= { pm1001pcCtrlconfMgnt1 10 }



pm1001pcCtrlConf2Load1 OBJECT-TYPE
	  SYNTAX EkiOnOff
	  MAX-ACCESS read-write
	  STATUS current
	  DESCRIPTION
        "
        Load Configuration Tables Set
         Nb 2 :When set this OID enables
        loading from flash configuration2
        into the PM.
        "
	  ::= { pm1001pcCtrlconfMgnt1 2 }



pm1001pcCtrlConf1Load1 OBJECT-TYPE
	  SYNTAX EkiOnOff
	  MAX-ACCESS read-write
	  STATUS current
	  DESCRIPTION
        "
        Load Configuration Tables Set
         Nb 1 :When set this OID enables
        loading from flash configuration1
        into the PM.
        "
	  ::= { pm1001pcCtrlconfMgnt1 1 }



--- *****************************************************
---     LEAF for the synth4 article
--- *****************************************************
pm1001pcCtrlsynth4 OBJECT IDENTIFIER ::= { pm1001pcCtrlOther 4 }




pm1001pcCtrlCorrelatOff OBJECT-TYPE
	  SYNTAX EkiOnOff
	  MAX-ACCESS read-write
	  STATUS current
	  DESCRIPTION
        "
        Disable Alarm Correlation :This
        OID disables the alarm correlation
        in the PM.
        "
	  ::= { pm1001pcCtrlsynth4 2 }



pm1001pcCtrlCorrelatOn OBJECT-TYPE
	  SYNTAX EkiOnOff
	  MAX-ACCESS read-write
	  STATUS current
	  DESCRIPTION
        "
        Enable Alarm Correlation :This
        OID enables the alarm correlation
        in the PM.
        "
	  ::= { pm1001pcCtrlsynth4 1 }



--- *****************************************************
---     LEAF for the swMgnt article
--- *****************************************************
pm1001pcCtrlswMgnt OBJECT IDENTIFIER ::= { pm1001pcCtrlOther 5 }




pm1001pcCtrlLoadSwBank2 OBJECT-TYPE
	  SYNTAX EkiOnOff
	  MAX-ACCESS read-write
	  STATUS current
	  DESCRIPTION
        "
        Set Software Nb 2 As Active :This
        OID, when set, loads the SW from
        bank2 into the PM. It must be followed
        by a reset.  <Help>  This controls
        selects the second SW bank as the
        active bank for the next module
        reset
        "
	  ::= { pm1001pcCtrlswMgnt 6 }



pm1001pcCtrlLoadSwBank1 OBJECT-TYPE
	  SYNTAX EkiOnOff
	  MAX-ACCESS read-write
	  STATUS current
	  DESCRIPTION
        "
        Set Software Nb 1 As Active :This
        OID, when set, loads the SW from
        bank1 into the PM. It must be followed
        by a reset.  <Help>  This controls
        selects the first SW bank as the
        active bank for the next module
        reset
        "
	  ::= { pm1001pcCtrlswMgnt 5 }



pm1001pcCtrlWarmReset OBJECT-TYPE
	  SYNTAX EkiOnOff
	  MAX-ACCESS read-write
	  STATUS current
	  DESCRIPTION
        "
        PM Warm Reset :This OID, when
         set, causes a warm reset of the
        PM. This reset is not traffic affecting,
        and the configuration of PM remains
        unchanged.  <Help>  This control
        initiates a warm reset of the module.
        "
	  ::= { pm1001pcCtrlswMgnt 3 }



pm1001pcCtrlColdReset OBJECT-TYPE
	  SYNTAX EkiOnOff
	  MAX-ACCESS read-write
	  STATUS current
	  DESCRIPTION
        "
        PM Cold Reset :This OID, when
         set, causes a cold reset of the
        PM. This reset is traffic affecting,
        and the configuration of PM is
         reloaded on start-up.  <Help>
          This control initiates a cold
        reset of the module.
        "
	  ::= { pm1001pcCtrlswMgnt 2 }



--- *****************************************************
---     LEAF for the gwMgnt article
--- *****************************************************
pm1001pcCtrlgwMgnt OBJECT IDENTIFIER ::= { pm1001pcCtrlOther 6 }




pm1001pcCtrlLoadGwBank4 OBJECT-TYPE
	  SYNTAX EkiOnOff
	  MAX-ACCESS read-write
	  STATUS current
	  DESCRIPTION
        "
        Set Gateware Nb 4 As Active :This
        OID, when set, loads the GW from
        bank4 (Flash) into the PM. It is
        followed by an automatic gateware
        cold reset.
        "
	  ::= { pm1001pcCtrlgwMgnt 8 }



pm1001pcCtrlLoadGwBank3 OBJECT-TYPE
	  SYNTAX EkiOnOff
	  MAX-ACCESS read-write
	  STATUS current
	  DESCRIPTION
        "
        Set Gateware Nb 3 As Active :This
        OID, when set, loads the GW from
        bank3 (Flash) into the PM. It is
        followed by an automatic gateware
        cold reset.  <Help>  This controls
        initiates a cold reset of the module
        and select the third GW bank as
        the active bank
        "
	  ::= { pm1001pcCtrlgwMgnt 7 }



pm1001pcCtrlLoadGwBank2 OBJECT-TYPE
	  SYNTAX EkiOnOff
	  MAX-ACCESS read-write
	  STATUS current
	  DESCRIPTION
        "
        Set Gateware Nb 2 As Active :This
        OID, when set, loads the GW from
        bank2 (Flash) into the PM. It is
        followed by an automatic gateware
        cold reset.
        "
	  ::= { pm1001pcCtrlgwMgnt 6 }



pm1001pcCtrlLoadGwBank1 OBJECT-TYPE
	  SYNTAX EkiOnOff
	  MAX-ACCESS read-write
	  STATUS current
	  DESCRIPTION
        "
        Set Gateware Nb 1 As Active :This
        OID, when set, loads the GW from
        bank1 (Flash) into the PM. It is
        followed by an automatic gateware
        cold reset.  <Help>  This controls
        initiates a cold reset of the module
        and select the first GW bank as
        the active bank
        "
	  ::= { pm1001pcCtrlgwMgnt 5 }



pm1001pcCtrlCurrentGwReset OBJECT-TYPE
	  SYNTAX EkiOnOff
	  MAX-ACCESS read-write
	  STATUS current
	  DESCRIPTION
        "
        Active Gateware Reset :This OID,
        when set, resets the active gateware.
        It is traffic affecting.
        "
	  ::= { pm1001pcCtrlgwMgnt 1 }



--- *********************************************************
---     TABLE for the pm1001pcCtrlaccessLoop articles
--- *********************************************************

pm1001pcCtrlaccessLoopTable OBJECT-TYPE
	SYNTAX  SEQUENCE OF Pm1001pcCtrlaccessLoopEntry
	MAX-ACCESS not-accessible
	STATUS current
	DESCRIPTION
        "
        List of pm1001pcCtrlaccessLoop
        Article
        "
	::= { pm1001pcCtrlClient 16 }


pm1001pcCtrlaccessLoopEntry OBJECT-TYPE
	SYNTAX Pm1001pcCtrlaccessLoopEntry
	MAX-ACCESS not-accessible
	STATUS current
	DESCRIPTION
        "
        Row definition for the pm1001pcCtrlaccessLoop
        table
        "
	INDEX   { pm1001pcCtrlaccessLoopIndex }
	::= { pm1001pcCtrlaccessLoopTable 1 }


Pm1001pcCtrlaccessLoopEntry ::=
	SEQUENCE {
	pm1001pcCtrlaccessLoopIndex
		INTEGER,
	pm1001pcCtrlaccessLoopPortn
		EkiState
	}


pm1001pcCtrlaccessLoopIndex OBJECT-TYPE
	SYNTAX  INTEGER(0..128)
	MAX-ACCESS  read-only
	STATUS current
	DESCRIPTION
        "
        Index definition for the pm1001pcCtrlaccessLoop
        table
        "
	::= { pm1001pcCtrlaccessLoopEntry 1 }


pm1001pcCtrlaccessLoopPortn OBJECT-TYPE
	SYNTAX  EkiState
	MAX-ACCESS read-write
	STATUS current
	DESCRIPTION
        "
        Client Facility Loopback :This
        OID operates a Client Facility
         Loopback, looping client input
        signal on the client output port.
        The loop is located on the client
        transceiver  <Help> This maintenance
        parameter operates a Client Facility
        Loopback, looping client input
         signal on the client output port.
        The loop is located on the client
        transceiver
        "
	::= { pm1001pcCtrlaccessLoopEntry 2 }


--- *********************************************************
---     TABLE for the pm1001pcCtrlportOosMode articles
--- *********************************************************

pm1001pcCtrlportOosModeTable OBJECT-TYPE
	SYNTAX  SEQUENCE OF Pm1001pcCtrlportOosModeEntry
	MAX-ACCESS not-accessible
	STATUS current
	DESCRIPTION
        "
        List of pm1001pcCtrlportOosMode
        Article
        "
	::= { pm1001pcCtrlClient 18 }


pm1001pcCtrlportOosModeEntry OBJECT-TYPE
	SYNTAX Pm1001pcCtrlportOosModeEntry
	MAX-ACCESS not-accessible
	STATUS current
	DESCRIPTION
        "
        Row definition for the pm1001pcCtrlportOosMode
        table
        "
	INDEX   { pm1001pcCtrlportOosModeIndex }
	::= { pm1001pcCtrlportOosModeTable 1 }


Pm1001pcCtrlportOosModeEntry ::=
	SEQUENCE {
	pm1001pcCtrlportOosModeIndex
		INTEGER,
	pm1001pcCtrlportOosModePortn
		EkiState
	}


pm1001pcCtrlportOosModeIndex OBJECT-TYPE
	SYNTAX  INTEGER(0..128)
	MAX-ACCESS  read-only
	STATUS current
	DESCRIPTION
        "
        Index definition for the pm1001pcCtrlportOosMode
        table
        "
	::= { pm1001pcCtrlportOosModeEntry 1 }


pm1001pcCtrlportOosModePortn OBJECT-TYPE
	SYNTAX  EkiState
	MAX-ACCESS read-write
	STATUS current
	DESCRIPTION
        "
        Client Port Out Of Service :This
        OID sets the client port Out Of
        Service  <Help>  This controls
         defines the service state of the
        client port
        "
	::= { pm1001pcCtrlportOosModeEntry 2 }


--- *********************************************************
---     TABLE for the pm1001pcCtrlxfpOffCtrl articles
--- *********************************************************

pm1001pcCtrlxfpOffCtrlTable OBJECT-TYPE
	SYNTAX  SEQUENCE OF Pm1001pcCtrlxfpOffCtrlEntry
	MAX-ACCESS not-accessible
	STATUS current
	DESCRIPTION
        "
        List of pm1001pcCtrlxfpOffCtrl
        Article
        "
	::= { pm1001pcCtrlClient 20 }


pm1001pcCtrlxfpOffCtrlEntry OBJECT-TYPE
	SYNTAX Pm1001pcCtrlxfpOffCtrlEntry
	MAX-ACCESS not-accessible
	STATUS current
	DESCRIPTION
        "
        Row definition for the pm1001pcCtrlxfpOffCtrl
        table
        "
	INDEX   { pm1001pcCtrlxfpOffCtrlIndex }
	::= { pm1001pcCtrlxfpOffCtrlTable 1 }


Pm1001pcCtrlxfpOffCtrlEntry ::=
	SEQUENCE {
	pm1001pcCtrlxfpOffCtrlIndex
		INTEGER,
	pm1001pcCtrlxfpOffCtrlPortn
		EkiState
	}


pm1001pcCtrlxfpOffCtrlIndex OBJECT-TYPE
	SYNTAX  INTEGER(0..128)
	MAX-ACCESS  read-only
	STATUS current
	DESCRIPTION
        "
        Index definition for the pm1001pcCtrlxfpOffCtrl
        table
        "
	::= { pm1001pcCtrlxfpOffCtrlEntry 1 }


pm1001pcCtrlxfpOffCtrlPortn OBJECT-TYPE
	SYNTAX  EkiState
	MAX-ACCESS read-write
	STATUS current
	DESCRIPTION
        "
        Client Optical Laser Shutdown
         :This OID switches off the XFP.
         <Help>  This control defines the
        laser state of the client transceiver
        "
	::= { pm1001pcCtrlxfpOffCtrlEntry 2 }


--- *********************************************************
---     TABLE for the pm1001pcCtrlcsfUpIns articles
--- *********************************************************

pm1001pcCtrlcsfUpInsTable OBJECT-TYPE
	SYNTAX  SEQUENCE OF Pm1001pcCtrlcsfUpInsEntry
	MAX-ACCESS not-accessible
	STATUS current
	DESCRIPTION
        "
        List of pm1001pcCtrlcsfUpIns Article
        "
	::= { pm1001pcCtrlClient 21 }


pm1001pcCtrlcsfUpInsEntry OBJECT-TYPE
	SYNTAX Pm1001pcCtrlcsfUpInsEntry
	MAX-ACCESS not-accessible
	STATUS current
	DESCRIPTION
        "
        Row definition for the pm1001pcCtrlcsfUpIns
        table
        "
	INDEX   { pm1001pcCtrlcsfUpInsIndex }
	::= { pm1001pcCtrlcsfUpInsTable 1 }


Pm1001pcCtrlcsfUpInsEntry ::=
	SEQUENCE {
	pm1001pcCtrlcsfUpInsIndex
		INTEGER,
	pm1001pcCtrlcsfUpInsPortn
		EkiState
	}


pm1001pcCtrlcsfUpInsIndex OBJECT-TYPE
	SYNTAX  INTEGER(0..128)
	MAX-ACCESS  read-only
	STATUS current
	DESCRIPTION
        "
        Index definition for the pm1001pcCtrlcsfUpIns
        table
        "
	::= { pm1001pcCtrlcsfUpInsEntry 1 }


pm1001pcCtrlcsfUpInsPortn OBJECT-TYPE
	SYNTAX  EkiState
	MAX-ACCESS read-write
	STATUS current
	DESCRIPTION
        "
        Client Signal Fail Insertion :This
        OID, when set, inserts  a client
        signal fail in the upstream client
        Port.  <Help>  This control inserts
        a Client Signal Fail for the client
        port
        "
	::= { pm1001pcCtrlcsfUpInsEntry 2 }


--- *********************************************************
---     TABLE for the pm1001pcCtrlcaisDwIns articles
--- *********************************************************

pm1001pcCtrlcaisDwInsTable OBJECT-TYPE
	SYNTAX  SEQUENCE OF Pm1001pcCtrlcaisDwInsEntry
	MAX-ACCESS not-accessible
	STATUS current
	DESCRIPTION
        "
        List of pm1001pcCtrlcaisDwIns
         Article
        "
	::= { pm1001pcCtrlClient 22 }


pm1001pcCtrlcaisDwInsEntry OBJECT-TYPE
	SYNTAX Pm1001pcCtrlcaisDwInsEntry
	MAX-ACCESS not-accessible
	STATUS current
	DESCRIPTION
        "
        Row definition for the pm1001pcCtrlcaisDwIns
        table
        "
	INDEX   { pm1001pcCtrlcaisDwInsIndex }
	::= { pm1001pcCtrlcaisDwInsTable 1 }


Pm1001pcCtrlcaisDwInsEntry ::=
	SEQUENCE {
	pm1001pcCtrlcaisDwInsIndex
		INTEGER,
	pm1001pcCtrlcaisDwInsPortn
		EkiState
	}


pm1001pcCtrlcaisDwInsIndex OBJECT-TYPE
	SYNTAX  INTEGER(0..128)
	MAX-ACCESS  read-only
	STATUS current
	DESCRIPTION
        "
        Index definition for the pm1001pcCtrlcaisDwIns
        table
        "
	::= { pm1001pcCtrlcaisDwInsEntry 1 }


pm1001pcCtrlcaisDwInsPortn OBJECT-TYPE
	SYNTAX  EkiState
	MAX-ACCESS read-write
	STATUS current
	DESCRIPTION
        "
        Client AIS Insertion :This OID,
        when set, inserts a client AIS
         on the downstream client Port.
         <Help>  This control inserts a
        Client AIS for the client port
        "
	::= { pm1001pcCtrlcaisDwInsEntry 2 }


--- *********************************************************
---     TABLE for the pm1001pcCtrlflowControl articles
--- *********************************************************

pm1001pcCtrlflowControlTable OBJECT-TYPE
	SYNTAX  SEQUENCE OF Pm1001pcCtrlflowControlEntry
	MAX-ACCESS not-accessible
	STATUS current
	DESCRIPTION
        "
        List of pm1001pcCtrlflowControl
        Article
        "
	::= { pm1001pcCtrlClient 23 }


pm1001pcCtrlflowControlEntry OBJECT-TYPE
	SYNTAX Pm1001pcCtrlflowControlEntry
	MAX-ACCESS not-accessible
	STATUS current
	DESCRIPTION
        "
        Row definition for the pm1001pcCtrlflowControl
        table
        "
	INDEX   { pm1001pcCtrlflowControlIndex }
	::= { pm1001pcCtrlflowControlTable 1 }


Pm1001pcCtrlflowControlEntry ::=
	SEQUENCE {
	pm1001pcCtrlflowControlIndex
		INTEGER,
	pm1001pcCtrlflowControlPortn
		EkiState
	}


pm1001pcCtrlflowControlIndex OBJECT-TYPE
	SYNTAX  INTEGER(0..128)
	MAX-ACCESS  read-only
	STATUS current
	DESCRIPTION
        "
        Index definition for the pm1001pcCtrlflowControl
        table
        "
	::= { pm1001pcCtrlflowControlEntry 1 }


pm1001pcCtrlflowControlPortn OBJECT-TYPE
	SYNTAX  EkiState
	MAX-ACCESS read-write
	STATUS current
	DESCRIPTION
        "
        Flow Control :This OID, when set,
        asserts a Pause Frame management
        on the client Port.
        "
	::= { pm1001pcCtrlflowControlEntry 2 }


--- *****************************************************
---     LEAF for the fiberLength article
--- *****************************************************

pm1001pcCtrlfiberLength OBJECT-TYPE
	  SYNTAX Unsigned32 (0..255)
	  MAX-ACCESS read-write
	  STATUS current
	  DESCRIPTION
        "
        Client Fiber Length [0-24] :This
        OID defines the fiber length (in
        steps of 0.2 km) between the module
        client port and the 10GbE router
        (this OID has no effect in OC192/STM64
        protocol)  (Unit = Kms)  <Help>
         This control defines the fiber
        length (in steps of 0.2 km) between
        the module client port and the
         10GbE router (this OID has no
         effect in OC192/STM64 protocol).
        "
	  ::= { pm1001pcCtrlClient 25 }



--- *********************************************************
---     TABLE for the pm1001pcCtrlclientAccessTermLoop articles
--- *********************************************************

pm1001pcCtrlclientAccessTermLoopTable OBJECT-TYPE
	SYNTAX  SEQUENCE OF Pm1001pcCtrlclientAccessTermLoopEntry
	MAX-ACCESS not-accessible
	STATUS current
	DESCRIPTION
        "
        List of pm1001pcCtrlclientAccessTermLoop
        Article
        "
	::= { pm1001pcCtrlClient 26 }


pm1001pcCtrlclientAccessTermLoopEntry OBJECT-TYPE
	SYNTAX Pm1001pcCtrlclientAccessTermLoopEntry
	MAX-ACCESS not-accessible
	STATUS current
	DESCRIPTION
        "
        Row definition for the pm1001pcCtrlclientAccessTermLoop
        table
        "
	INDEX   { pm1001pcCtrlclientAccessTermLoopIndex }
	::= { pm1001pcCtrlclientAccessTermLoopTable 1 }


Pm1001pcCtrlclientAccessTermLoopEntry ::=
	SEQUENCE {
	pm1001pcCtrlclientAccessTermLoopIndex
		INTEGER,
	pm1001pcCtrlclientAccessTermLoopPortn
		EkiState
	}


pm1001pcCtrlclientAccessTermLoopIndex OBJECT-TYPE
	SYNTAX  INTEGER(0..128)
	MAX-ACCESS  read-only
	STATUS current
	DESCRIPTION
        "
        Index definition for the pm1001pcCtrlclientAccessTermLoop
        table
        "
	::= { pm1001pcCtrlclientAccessTermLoopEntry 1 }


pm1001pcCtrlclientAccessTermLoopPortn OBJECT-TYPE
	SYNTAX  EkiState
	MAX-ACCESS read-write
	STATUS current
	DESCRIPTION
        "
        Client Terminal Loopback :This
        OID operates a Client Terminal
         Loopback, looping client input
        signal on the client output port.
        The loop is located on the line
        transceiver  <Help> This maintenance
        parameter operates a Client Terminal
        Loopback, looping client input
         signal on the client output port.
        The loop is located on the line
        transceiver
        "
	::= { pm1001pcCtrlclientAccessTermLoopEntry 2 }


--- *********************************************************
---     TABLE for the pm1001pcCtrlxfpXfiLoop articles
--- *********************************************************

pm1001pcCtrlxfpXfiLoopTable OBJECT-TYPE
	SYNTAX  SEQUENCE OF Pm1001pcCtrlxfpXfiLoopEntry
	MAX-ACCESS not-accessible
	STATUS current
	DESCRIPTION
        "
        List of pm1001pcCtrlxfpXfiLoop
        Article
        "
	::= { pm1001pcCtrlClient 39 }


pm1001pcCtrlxfpXfiLoopEntry OBJECT-TYPE
	SYNTAX Pm1001pcCtrlxfpXfiLoopEntry
	MAX-ACCESS not-accessible
	STATUS current
	DESCRIPTION
        "
        Row definition for the pm1001pcCtrlxfpXfiLoop
        table
        "
	INDEX   { pm1001pcCtrlxfpXfiLoopIndex }
	::= { pm1001pcCtrlxfpXfiLoopTable 1 }


Pm1001pcCtrlxfpXfiLoopEntry ::=
	SEQUENCE {
	pm1001pcCtrlxfpXfiLoopIndex
		INTEGER,
	pm1001pcCtrlxfpXfiLoopPortn
		EkiState
	}


pm1001pcCtrlxfpXfiLoopIndex OBJECT-TYPE
	SYNTAX  INTEGER(0..128)
	MAX-ACCESS  read-only
	STATUS current
	DESCRIPTION
        "
        Index definition for the pm1001pcCtrlxfpXfiLoop
        table
        "
	::= { pm1001pcCtrlxfpXfiLoopEntry 1 }


pm1001pcCtrlxfpXfiLoopPortn OBJECT-TYPE
	SYNTAX  EkiState
	MAX-ACCESS read-write
	STATUS current
	DESCRIPTION
        "
        Client XFP/OTX XFI Loop :This
         OID operates a line loopback on
        the client XFP or the OTX  <Help>
         This control defines the XFI loop
        back of the client transceiver
        "
	::= { pm1001pcCtrlxfpXfiLoopEntry 2 }


--- *****************************************************
---     LEAF for the commAccessLoop article
--- *****************************************************
pm1001pcCtrlcommAccessLoop OBJECT IDENTIFIER ::= { pm1001pcCtrlLine 64 }




pm1001pcCtrlCommAccessloop OBJECT-TYPE
	  SYNTAX EkiOnOff
	  MAX-ACCESS read-write
	  STATUS deprecated
	  DESCRIPTION
        "
        PM Full Access Loop Mode :This
        OID, when set, puts the module
         in common access loop back, looping
        the 10 Gb/s output signal on the
        10 Gb/s input.
        "
	  ::= { pm1001pcCtrlcommAccessLoop 1 }



--- *****************************************************
---     LEAF for the lineLoop article
--- *****************************************************
pm1001pcCtrllineLoop OBJECT IDENTIFIER ::= { pm1001pcCtrlLine 66 }




pm1001pcCtrlLineLoop OBJECT-TYPE
	  SYNTAX EkiOnOff
	  MAX-ACCESS read-write
	  STATUS current
	  DESCRIPTION
        "
        Line Facility Loopback :This OID
        operates a Line Facility Loopback,
        looping line input signal on the
        line output port. The loop is located
        on the line transceiver. If the
        Line signal carries DCC, the management
        network is impacted  <Help> This
        maintenance parameter operates
         a Line Facility Loopback, looping
        line input signal on the line output
        port. The loop is located on the
        line transceiver. If the Line signal
        carries DCC, the management network
        is impacted
        "
	  ::= { pm1001pcCtrllineLoop 1 }



--- *****************************************************
---     LEAF for the msAis article
--- *****************************************************
pm1001pcCtrlmsAis OBJECT IDENTIFIER ::= { pm1001pcCtrlLine 67 }




pm1001pcCtrlMsAis OBJECT-TYPE
	  SYNTAX EkiOnOff
	  MAX-ACCESS read-write
	  STATUS current
	  DESCRIPTION
        "
        Insert MS-AIS/L-AIS On Line Output
        :This OID, when set, inserts an
        MS-AIS/L-AIS in the outgoing STM-64/OC-192
        signal.
        "
	  ::= { pm1001pcCtrlmsAis 1 }



--- *****************************************************
---     LEAF for the lineOosMode article
--- *****************************************************
pm1001pcCtrllineOosMode OBJECT IDENTIFIER ::= { pm1001pcCtrlLine 74 }




pm1001pcCtrlLineOosMode OBJECT-TYPE
	  SYNTAX EkiOnOff
	  MAX-ACCESS read-write
	  STATUS current
	  DESCRIPTION
        "
        Line Port Out Of Service :This
        OID sets the line port Out Of Service
         <Help>  This control defines the
        service state of the line port
        "
	  ::= { pm1001pcCtrllineOosMode 1 }



--- *****************************************************
---     LEAF for the ledTest article
--- *****************************************************
pm1001pcCtrlledTest OBJECT IDENTIFIER ::= { pm1001pcCtrlOther 192 }




pm1001pcCtrlLedOff OBJECT-TYPE
	  SYNTAX EkiOnOff
	  MAX-ACCESS read-write
	  STATUS current
	  DESCRIPTION
        "
        Leds Off :This OID switches off
        all the Leds as a test feature.
         <Help>  This control initiates
        a test leds turning all the LEDs
        to OFF
        "
	  ::= { pm1001pcCtrlledTest 3 }



pm1001pcCtrlRedLed OBJECT-TYPE
	  SYNTAX EkiOnOff
	  MAX-ACCESS read-write
	  STATUS current
	  DESCRIPTION
        "
        Red Leds Test :This OID switches
        on all the red Leds as a test feature.
         <Help>  This control initiates
        a test leds turning all the LEDs
        to red
        "
	  ::= { pm1001pcCtrlledTest 2 }



pm1001pcCtrlGreenLed OBJECT-TYPE
	  SYNTAX EkiOnOff
	  MAX-ACCESS read-write
	  STATUS current
	  DESCRIPTION
        "
        Green Leds Test :This OID switches
        on all the green Leds as a test
        feature.  <Help>  This control
         initiates a test leds turning
         all the LEDs to green
        "
	  ::= { pm1001pcCtrlledTest 1 }



--- *****************************************************
---     LEAF for the moduleOosMode article
--- *****************************************************
pm1001pcCtrlmoduleOosMode OBJECT IDENTIFIER ::= { pm1001pcCtrlOther 193 }




pm1001pcCtrlModuleOosMode OBJECT-TYPE
	  SYNTAX EkiOnOff
	  MAX-ACCESS read-write
	  STATUS current
	  DESCRIPTION
        "
        PM Out Of Service :This OID sets
        the PM Out Of Service  <Help>
         This control defines the service
        state of the complete module
        "
	  ::= { pm1001pcCtrlmoduleOosMode 1 }



--- *****************************************************
---     LEAF for the maintenanceMode article
--- *****************************************************
pm1001pcCtrlmaintenanceMode OBJECT IDENTIFIER ::= { pm1001pcCtrlOther 197 }




pm1001pcCtrlMaintenanceMode OBJECT-TYPE
	  SYNTAX EkiOnOff
	  MAX-ACCESS read-write
	  STATUS current
	  DESCRIPTION
        "
        Module Maintenance Mode :This
         OID enables the maintenance mode
        on the PM.  <Help>   This control
        enables the maintenance mode on
        the PM.
        "
	  ::= { pm1001pcCtrlmaintenanceMode 1 }



--- *****************************************************
---     LEAF for the dccEnable article
--- *****************************************************
pm1001pcCtrldccEnable OBJECT IDENTIFIER ::= { pm1001pcCtrlOther 198 }




pm1001pcCtrlDccEnable OBJECT-TYPE
	  SYNTAX EkiOnOff
	  MAX-ACCESS read-write
	  STATUS current
	  DESCRIPTION
        "
        DCC Enable :This OID enables the
        DCC mode on the PM   <Help>   This
        control enables the DCC mode on
        the PM
        "
	  ::= { pm1001pcCtrldccEnable 1 }



--- *********************************************************
---     TABLE for the pm1001pcCtrlxfpOnoff articles
--- *********************************************************

pm1001pcCtrlxfpOnoffTable OBJECT-TYPE
	SYNTAX  SEQUENCE OF Pm1001pcCtrlxfpOnoffEntry
	MAX-ACCESS not-accessible
	STATUS current
	DESCRIPTION
        "
        List of pm1001pcCtrlxfpOnoff Article
        "
	::= { pm1001pcCtrlLine 208 }


pm1001pcCtrlxfpOnoffEntry OBJECT-TYPE
	SYNTAX Pm1001pcCtrlxfpOnoffEntry
	MAX-ACCESS not-accessible
	STATUS current
	DESCRIPTION
        "
        Row definition for the pm1001pcCtrlxfpOnoff
        table
        "
	INDEX   { pm1001pcCtrlxfpOnoffIndex }
	::= { pm1001pcCtrlxfpOnoffTable 1 }


Pm1001pcCtrlxfpOnoffEntry ::=
	SEQUENCE {
	pm1001pcCtrlxfpOnoffIndex
		INTEGER,
	pm1001pcCtrlxfpOnoffPortn
		EkiState
	}


pm1001pcCtrlxfpOnoffIndex OBJECT-TYPE
	SYNTAX  INTEGER(0..128)
	MAX-ACCESS  read-only
	STATUS current
	DESCRIPTION
        "
        Index definition for the pm1001pcCtrlxfpOnoff
        table
        "
	::= { pm1001pcCtrlxfpOnoffEntry 1 }


pm1001pcCtrlxfpOnoffPortn OBJECT-TYPE
	SYNTAX  EkiState
	MAX-ACCESS read-write
	STATUS current
	DESCRIPTION
        "
        Line Optical Laser Shutdown :This
        OID switches off the XFP or the
        OTX  <Help>  This control defines
        the laser state of the line transceiver
        "
	::= { pm1001pcCtrlxfpOnoffEntry 2 }


--- *********************************************************
---     TABLE for the pm1001pcCtrlxfpLineLoop articles
--- *********************************************************

pm1001pcCtrlxfpLineLoopTable OBJECT-TYPE
	SYNTAX  SEQUENCE OF Pm1001pcCtrlxfpLineLoopEntry
	MAX-ACCESS not-accessible
	STATUS current
	DESCRIPTION
        "
        List of pm1001pcCtrlxfpLineLoop
        Article
        "
	::= { pm1001pcCtrlLine 209 }


pm1001pcCtrlxfpLineLoopEntry OBJECT-TYPE
	SYNTAX Pm1001pcCtrlxfpLineLoopEntry
	MAX-ACCESS not-accessible
	STATUS current
	DESCRIPTION
        "
        Row definition for the pm1001pcCtrlxfpLineLoop
        table
        "
	INDEX   { pm1001pcCtrlxfpLineLoopIndex }
	::= { pm1001pcCtrlxfpLineLoopTable 1 }


Pm1001pcCtrlxfpLineLoopEntry ::=
	SEQUENCE {
	pm1001pcCtrlxfpLineLoopIndex
		INTEGER,
	pm1001pcCtrlxfpLineLoopPortn
		EkiState
	}


pm1001pcCtrlxfpLineLoopIndex OBJECT-TYPE
	SYNTAX  INTEGER(0..128)
	MAX-ACCESS  read-only
	STATUS current
	DESCRIPTION
        "
        Index definition for the pm1001pcCtrlxfpLineLoop
        table
        "
	::= { pm1001pcCtrlxfpLineLoopEntry 1 }


pm1001pcCtrlxfpLineLoopPortn OBJECT-TYPE
	SYNTAX  EkiState
	MAX-ACCESS read-write
	STATUS current
	DESCRIPTION
        "
        Line XFP/OTX Loop :This OID operates
        a line loopback on the line XFP
        or the OTX  <Help>  This control
        defines the line loop back of the
        line transceiver
        "
	::= { pm1001pcCtrlxfpLineLoopEntry 2 }


--- *********************************************************
---     TABLE for the pm1001pcCtrlxfpLineXfiLoop articles
--- *********************************************************

pm1001pcCtrlxfpLineXfiLoopTable OBJECT-TYPE
	SYNTAX  SEQUENCE OF Pm1001pcCtrlxfpLineXfiLoopEntry
	MAX-ACCESS not-accessible
	STATUS current
	DESCRIPTION
        "
        List of pm1001pcCtrlxfpLineXfiLoop
        Article
        "
	::= { pm1001pcCtrlLine 210 }


pm1001pcCtrlxfpLineXfiLoopEntry OBJECT-TYPE
	SYNTAX Pm1001pcCtrlxfpLineXfiLoopEntry
	MAX-ACCESS not-accessible
	STATUS current
	DESCRIPTION
        "
        Row definition for the pm1001pcCtrlxfpLineXfiLoop
        table
        "
	INDEX   { pm1001pcCtrlxfpLineXfiLoopIndex }
	::= { pm1001pcCtrlxfpLineXfiLoopTable 1 }


Pm1001pcCtrlxfpLineXfiLoopEntry ::=
	SEQUENCE {
	pm1001pcCtrlxfpLineXfiLoopIndex
		INTEGER,
	pm1001pcCtrlxfpLineXfiLoopPortn
		EkiState
	}


pm1001pcCtrlxfpLineXfiLoopIndex OBJECT-TYPE
	SYNTAX  INTEGER(0..128)
	MAX-ACCESS  read-only
	STATUS current
	DESCRIPTION
        "
        Index definition for the pm1001pcCtrlxfpLineXfiLoop
        table
        "
	::= { pm1001pcCtrlxfpLineXfiLoopEntry 1 }


pm1001pcCtrlxfpLineXfiLoopPortn OBJECT-TYPE
	SYNTAX  EkiState
	MAX-ACCESS read-write
	STATUS current
	DESCRIPTION
        "
        Line XFP/OTX XFI Loop :This OID
        operates a XFI loopback on the
         line XFP or the OTX  <Help>  This
        control defines the XFI loop back
        of the line transceiver
        "
	::= { pm1001pcCtrlxfpLineXfiLoopEntry 2 }


--- *********************************************************
---     TABLE for the pm1001pcCtrllineLoopTransceiver articles
--- *********************************************************

pm1001pcCtrllineLoopTransceiverTable OBJECT-TYPE
	SYNTAX  SEQUENCE OF Pm1001pcCtrllineLoopTransceiverEntry
	MAX-ACCESS not-accessible
	STATUS current
	DESCRIPTION
        "
        List of pm1001pcCtrllineLoopTransceiver
        Article
        "
	::= { pm1001pcCtrlLine 218 }


pm1001pcCtrllineLoopTransceiverEntry OBJECT-TYPE
	SYNTAX Pm1001pcCtrllineLoopTransceiverEntry
	MAX-ACCESS not-accessible
	STATUS current
	DESCRIPTION
        "
        Row definition for the pm1001pcCtrllineLoopTransceiver
        table
        "
	INDEX   { pm1001pcCtrllineLoopTransceiverIndex }
	::= { pm1001pcCtrllineLoopTransceiverTable 1 }


Pm1001pcCtrllineLoopTransceiverEntry ::=
	SEQUENCE {
	pm1001pcCtrllineLoopTransceiverIndex
		INTEGER,
	pm1001pcCtrllineLoopTransceiverPortn
		EkiState
	}


pm1001pcCtrllineLoopTransceiverIndex OBJECT-TYPE
	SYNTAX  INTEGER(0..128)
	MAX-ACCESS  read-only
	STATUS current
	DESCRIPTION
        "
        Index definition for the pm1001pcCtrllineLoopTransceiver
        table
        "
	::= { pm1001pcCtrllineLoopTransceiverEntry 1 }


pm1001pcCtrllineLoopTransceiverPortn OBJECT-TYPE
	SYNTAX  EkiState
	MAX-ACCESS read-write
	STATUS current
	DESCRIPTION
        "
        Line Terminal Loopback :This OID
        operates a Line Terminal Loopback,
        looping line input signal on the
        line output port. The loop is located
        on all client transceivers  <Help>
        This maintenance parameter operates
        a Line Terminal Loopback, looping
        line input signal on the line output
        port. The loop is located on all
        client transceivers.
        "
	::= { pm1001pcCtrllineLoopTransceiverEntry 2 }







--- *****************************************************
--- $$$$$$$$$$$$$$$$$$$$$$$$$$$$$$$$$$$$$$$$$$$$$$$$$$$$$
---     COUNTERS
--- $$$$$$$$$$$$$$$$$$$$$$$$$$$$$$$$$$$$$$$$$$$$$$$$$$$$$
--- *****************************************************



--- *********************************************************
---     TABLE for the pm1001pcCntclientUpErrCnt articles
--- *********************************************************

pm1001pcCntclientUpErrCntTable OBJECT-TYPE
	SYNTAX  SEQUENCE OF Pm1001pcCntclientUpErrCntEntry
	MAX-ACCESS not-accessible
	STATUS current
	DESCRIPTION
        "
        List of pm1001pcCntclientUpErrCnt
        Article
        "
	::= { pm1001pcCntClient 32 }


pm1001pcCntclientUpErrCntEntry OBJECT-TYPE
	SYNTAX Pm1001pcCntclientUpErrCntEntry
	MAX-ACCESS not-accessible
	STATUS current
	DESCRIPTION
        "
        Row definition for the pm1001pcCntclientUpErrCnt
        table
        "
	INDEX   { pm1001pcCntclientUpErrCntIndex }
	::= { pm1001pcCntclientUpErrCntTable 1 }


Pm1001pcCntclientUpErrCntEntry ::=
	SEQUENCE {
	pm1001pcCntclientUpErrCntIndex
		INTEGER,
	pm1001pcCntclientUpErrCntValuePortn
		Counter32,
	pm1001pcCntclientUpErrCntErrorPortn
		EkiOnOff,
	pm1001pcCntclientUpErrCntOverloadPortn
		EkiOnOff
	}


pm1001pcCntclientUpErrCntIndex OBJECT-TYPE
	SYNTAX  INTEGER(0..128)
	MAX-ACCESS  read-only
	STATUS current
	DESCRIPTION
        "
        Index definition for the pm1001pcCntclientUpErrCnt
        table
        "
	::= { pm1001pcCntclientUpErrCntEntry 1 }


pm1001pcCntclientUpErrCntValuePortn OBJECT-TYPE
	SYNTAX  Counter32
	MAX-ACCESS read-only
	STATUS current
	DESCRIPTION
        "
        Client Input FCS Counter :This
        counter is increased each time
         a FCS error is detected on the
        client input stream  <Help>  This
        counter gives the number of FCS
        errors on the client input port
        "
	::= { pm1001pcCntclientUpErrCntEntry 2 }


pm1001pcCntclientUpErrCntErrorPortn OBJECT-TYPE
	SYNTAX  EkiOnOff
	MAX-ACCESS read-only
	STATUS current
	DESCRIPTION
        "
        Client Counter Error :This OID
        when set indicates the FCS error
        counter value is invalid on input
        Port
        "
	::= { pm1001pcCntclientUpErrCntEntry 3 }


pm1001pcCntclientUpErrCntOverloadPortn OBJECT-TYPE
	SYNTAX  EkiOnOff
	MAX-ACCESS read-only
	STATUS current
	DESCRIPTION
        "
        Client Counter Overload :This
         OID when set indicates a FCS error
        counter overload on input Port
        "
	::= { pm1001pcCntclientUpErrCntEntry 4 }


--- *********************************************************
---     TABLE for the pm1001pcCntclientUpTimCnt articles
--- *********************************************************

pm1001pcCntclientUpTimCntTable OBJECT-TYPE
	SYNTAX  SEQUENCE OF Pm1001pcCntclientUpTimCntEntry
	MAX-ACCESS not-accessible
	STATUS current
	DESCRIPTION
        "
        List of pm1001pcCntclientUpTimCnt
        Article
        "
	::= { pm1001pcCntClient 40 }


pm1001pcCntclientUpTimCntEntry OBJECT-TYPE
	SYNTAX Pm1001pcCntclientUpTimCntEntry
	MAX-ACCESS not-accessible
	STATUS current
	DESCRIPTION
        "
        Row definition for the pm1001pcCntclientUpTimCnt
        table
        "
	INDEX   { pm1001pcCntclientUpTimCntIndex }
	::= { pm1001pcCntclientUpTimCntTable 1 }


Pm1001pcCntclientUpTimCntEntry ::=
	SEQUENCE {
	pm1001pcCntclientUpTimCntIndex
		INTEGER,
	pm1001pcCntclientUpTimCntValuePortn
		Counter32,
	pm1001pcCntclientUpTimCntErrorPortn
		EkiOnOff,
	pm1001pcCntclientUpTimCntOverloadPortn
		EkiOnOff
	}


pm1001pcCntclientUpTimCntIndex OBJECT-TYPE
	SYNTAX  INTEGER(0..128)
	MAX-ACCESS  read-only
	STATUS current
	DESCRIPTION
        "
        Index definition for the pm1001pcCntclientUpTimCnt
        table
        "
	::= { pm1001pcCntclientUpTimCntEntry 1 }


pm1001pcCntclientUpTimCntValuePortn OBJECT-TYPE
	SYNTAX  Counter32
	MAX-ACCESS read-only
	STATUS current
	DESCRIPTION
        "
        Client Upstream Timer Counter
         :This is the timing counter dedicated
        to the upstream access counters.
        It is incremented every 125 us.
        "
	::= { pm1001pcCntclientUpTimCntEntry 2 }


pm1001pcCntclientUpTimCntErrorPortn OBJECT-TYPE
	SYNTAX  EkiOnOff
	MAX-ACCESS read-only
	STATUS current
	DESCRIPTION
        "
        Client Counter Error :This OID
        when set indicates the upstream
        timing counter value is invalid
        on Port
        "
	::= { pm1001pcCntclientUpTimCntEntry 3 }


pm1001pcCntclientUpTimCntOverloadPortn OBJECT-TYPE
	SYNTAX  EkiOnOff
	MAX-ACCESS read-only
	STATUS current
	DESCRIPTION
        "
        Client Counter Overload :This
         OID when set indicates a upstream
        timing counter overload on Port
        "
	::= { pm1001pcCntclientUpTimCntEntry 4 }


--- *********************************************************
---     TABLE for the pm1001pcCntclientDwErrCnt articles
--- *********************************************************

pm1001pcCntclientDwErrCntTable OBJECT-TYPE
	SYNTAX  SEQUENCE OF Pm1001pcCntclientDwErrCntEntry
	MAX-ACCESS not-accessible
	STATUS current
	DESCRIPTION
        "
        List of pm1001pcCntclientDwErrCnt
        Article
        "
	::= { pm1001pcCntClient 64 }


pm1001pcCntclientDwErrCntEntry OBJECT-TYPE
	SYNTAX Pm1001pcCntclientDwErrCntEntry
	MAX-ACCESS not-accessible
	STATUS current
	DESCRIPTION
        "
        Row definition for the pm1001pcCntclientDwErrCnt
        table
        "
	INDEX   { pm1001pcCntclientDwErrCntIndex }
	::= { pm1001pcCntclientDwErrCntTable 1 }


Pm1001pcCntclientDwErrCntEntry ::=
	SEQUENCE {
	pm1001pcCntclientDwErrCntIndex
		INTEGER,
	pm1001pcCntclientDwErrCntValuePortn
		Counter32,
	pm1001pcCntclientDwErrCntErrorPortn
		EkiOnOff,
	pm1001pcCntclientDwErrCntOverloadPortn
		EkiOnOff
	}


pm1001pcCntclientDwErrCntIndex OBJECT-TYPE
	SYNTAX  INTEGER(0..128)
	MAX-ACCESS  read-only
	STATUS current
	DESCRIPTION
        "
        Index definition for the pm1001pcCntclientDwErrCnt
        table
        "
	::= { pm1001pcCntclientDwErrCntEntry 1 }


pm1001pcCntclientDwErrCntValuePortn OBJECT-TYPE
	SYNTAX  Counter32
	MAX-ACCESS read-only
	STATUS current
	DESCRIPTION
        "
        Client Output FCS Counter :This
        counter is incremented each time
        a FCS error is detected on the
         Client output stream  <Help>
         This counter gives the number
         of FCS errors on the client output
        port
        "
	::= { pm1001pcCntclientDwErrCntEntry 2 }


pm1001pcCntclientDwErrCntErrorPortn OBJECT-TYPE
	SYNTAX  EkiOnOff
	MAX-ACCESS read-only
	STATUS current
	DESCRIPTION
        "
        Client Counter Error :This OID
        when set indicates the FCS error
        counter value is invalid on output
        Port
        "
	::= { pm1001pcCntclientDwErrCntEntry 3 }


pm1001pcCntclientDwErrCntOverloadPortn OBJECT-TYPE
	SYNTAX  EkiOnOff
	MAX-ACCESS read-only
	STATUS current
	DESCRIPTION
        "
        Client Counter Overload :This
         OID when set indicates a FCS error
        counter overload on output Port
        "
	::= { pm1001pcCntclientDwErrCntEntry 4 }


--- *********************************************************
---     TABLE for the pm1001pcCntclientDwTimCnt articles
--- *********************************************************

pm1001pcCntclientDwTimCntTable OBJECT-TYPE
	SYNTAX  SEQUENCE OF Pm1001pcCntclientDwTimCntEntry
	MAX-ACCESS not-accessible
	STATUS current
	DESCRIPTION
        "
        List of pm1001pcCntclientDwTimCnt
        Article
        "
	::= { pm1001pcCntClient 72 }


pm1001pcCntclientDwTimCntEntry OBJECT-TYPE
	SYNTAX Pm1001pcCntclientDwTimCntEntry
	MAX-ACCESS not-accessible
	STATUS current
	DESCRIPTION
        "
        Row definition for the pm1001pcCntclientDwTimCnt
        table
        "
	INDEX   { pm1001pcCntclientDwTimCntIndex }
	::= { pm1001pcCntclientDwTimCntTable 1 }


Pm1001pcCntclientDwTimCntEntry ::=
	SEQUENCE {
	pm1001pcCntclientDwTimCntIndex
		INTEGER,
	pm1001pcCntclientDwTimCntValuePortn
		Counter32,
	pm1001pcCntclientDwTimCntErrorPortn
		EkiOnOff,
	pm1001pcCntclientDwTimCntOverloadPortn
		EkiOnOff
	}


pm1001pcCntclientDwTimCntIndex OBJECT-TYPE
	SYNTAX  INTEGER(0..128)
	MAX-ACCESS  read-only
	STATUS current
	DESCRIPTION
        "
        Index definition for the pm1001pcCntclientDwTimCnt
        table
        "
	::= { pm1001pcCntclientDwTimCntEntry 1 }


pm1001pcCntclientDwTimCntValuePortn OBJECT-TYPE
	SYNTAX  Counter32
	MAX-ACCESS read-only
	STATUS current
	DESCRIPTION
        "
        Client Downstream Timer Counter
        :This is the timing counter dedicated
        to the downstream access counters.
        It is incremented every 125 us.
        "
	::= { pm1001pcCntclientDwTimCntEntry 2 }


pm1001pcCntclientDwTimCntErrorPortn OBJECT-TYPE
	SYNTAX  EkiOnOff
	MAX-ACCESS read-only
	STATUS current
	DESCRIPTION
        "
        Client Counter Error :This OID
        when set indicates the downstream
        timer counter value is invalid
         on Port
        "
	::= { pm1001pcCntclientDwTimCntEntry 3 }


pm1001pcCntclientDwTimCntOverloadPortn OBJECT-TYPE
	SYNTAX  EkiOnOff
	MAX-ACCESS read-only
	STATUS current
	DESCRIPTION
        "
        Client Counter Overload :This
         OID when set indicates a downstream
        timer counter overload on Port
        "
	::= { pm1001pcCntclientDwTimCntEntry 4 }


--- *********************************************************
---     TABLE for the pm1001pcCntlineDfrmErrCnt articles
--- *********************************************************

pm1001pcCntlineDfrmErrCntTable OBJECT-TYPE
	SYNTAX  SEQUENCE OF Pm1001pcCntlineDfrmErrCntEntry
	MAX-ACCESS not-accessible
	STATUS current
	DESCRIPTION
        "
        List of pm1001pcCntlineDfrmErrCnt
        Article
        "
	::= { pm1001pcCntLine 152 }


pm1001pcCntlineDfrmErrCntEntry OBJECT-TYPE
	SYNTAX Pm1001pcCntlineDfrmErrCntEntry
	MAX-ACCESS not-accessible
	STATUS current
	DESCRIPTION
        "
        Row definition for the pm1001pcCntlineDfrmErrCnt
        table
        "
	INDEX   { pm1001pcCntlineDfrmErrCntIndex }
	::= { pm1001pcCntlineDfrmErrCntTable 1 }


Pm1001pcCntlineDfrmErrCntEntry ::=
	SEQUENCE {
	pm1001pcCntlineDfrmErrCntIndex
		INTEGER,
	pm1001pcCntlineDfrmErrCntValuePortn
		Counter32,
	pm1001pcCntlineDfrmErrCntErrorPortn
		EkiOnOff,
	pm1001pcCntlineDfrmErrCntOverloadPortn
		EkiOnOff
	}


pm1001pcCntlineDfrmErrCntIndex OBJECT-TYPE
	SYNTAX  INTEGER(0..128)
	MAX-ACCESS  read-only
	STATUS current
	DESCRIPTION
        "
        Index definition for the pm1001pcCntlineDfrmErrCnt
        table
        "
	::= { pm1001pcCntlineDfrmErrCntEntry 1 }


pm1001pcCntlineDfrmErrCntValuePortn OBJECT-TYPE
	SYNTAX  Counter32
	MAX-ACCESS read-only
	STATUS current
	DESCRIPTION
        "
        Line B1 Error Counter :This counter
        is incremented each time a B1 error
        is detected on the Deframer input
        stream.  <Help>  This counter gives
        the number of B1 errors on the
         line port
        "
	::= { pm1001pcCntlineDfrmErrCntEntry 2 }


pm1001pcCntlineDfrmErrCntErrorPortn OBJECT-TYPE
	SYNTAX  EkiOnOff
	MAX-ACCESS read-only
	STATUS current
	DESCRIPTION
        "
        Line Counter Error :This OID when
        set indicates the B1 error counter
        value is invalid on Port
        "
	::= { pm1001pcCntlineDfrmErrCntEntry 3 }


pm1001pcCntlineDfrmErrCntOverloadPortn OBJECT-TYPE
	SYNTAX  EkiOnOff
	MAX-ACCESS read-only
	STATUS current
	DESCRIPTION
        "
        Line Counter Overload :This OID
        when set indicates a B1 error counter
        overload on Port
        "
	::= { pm1001pcCntlineDfrmErrCntEntry 4 }


--- *********************************************************
---     TABLE for the pm1001pcCntlineDfrmTimCnt articles
--- *********************************************************

pm1001pcCntlineDfrmTimCntTable OBJECT-TYPE
	SYNTAX  SEQUENCE OF Pm1001pcCntlineDfrmTimCntEntry
	MAX-ACCESS not-accessible
	STATUS current
	DESCRIPTION
        "
        List of pm1001pcCntlineDfrmTimCnt
        Article
        "
	::= { pm1001pcCntLine 153 }


pm1001pcCntlineDfrmTimCntEntry OBJECT-TYPE
	SYNTAX Pm1001pcCntlineDfrmTimCntEntry
	MAX-ACCESS not-accessible
	STATUS current
	DESCRIPTION
        "
        Row definition for the pm1001pcCntlineDfrmTimCnt
        table
        "
	INDEX   { pm1001pcCntlineDfrmTimCntIndex }
	::= { pm1001pcCntlineDfrmTimCntTable 1 }


Pm1001pcCntlineDfrmTimCntEntry ::=
	SEQUENCE {
	pm1001pcCntlineDfrmTimCntIndex
		INTEGER,
	pm1001pcCntlineDfrmTimCntValuePortn
		Counter32,
	pm1001pcCntlineDfrmTimCntErrorPortn
		EkiOnOff,
	pm1001pcCntlineDfrmTimCntOverloadPortn
		EkiOnOff
	}


pm1001pcCntlineDfrmTimCntIndex OBJECT-TYPE
	SYNTAX  INTEGER(0..128)
	MAX-ACCESS  read-only
	STATUS current
	DESCRIPTION
        "
        Index definition for the pm1001pcCntlineDfrmTimCnt
        table
        "
	::= { pm1001pcCntlineDfrmTimCntEntry 1 }


pm1001pcCntlineDfrmTimCntValuePortn OBJECT-TYPE
	SYNTAX  Counter32
	MAX-ACCESS read-only
	STATUS current
	DESCRIPTION
        "
        Line Timer Counter :This is the
        timing counter dedicated to the
        downstream deframer counters. It
        is incremented every 125 us.
        "
	::= { pm1001pcCntlineDfrmTimCntEntry 2 }


pm1001pcCntlineDfrmTimCntErrorPortn OBJECT-TYPE
	SYNTAX  EkiOnOff
	MAX-ACCESS read-only
	STATUS current
	DESCRIPTION
        "
        Line Counter Error :This OID when
        set indicates the deframer timer
        counter value is invalid on Port
        "
	::= { pm1001pcCntlineDfrmTimCntEntry 3 }


pm1001pcCntlineDfrmTimCntOverloadPortn OBJECT-TYPE
	SYNTAX  EkiOnOff
	MAX-ACCESS read-only
	STATUS current
	DESCRIPTION
        "
        Line Counter Overload :This OID
        when set indicates a deframer timer
        counter overload on Port
        "
	::= { pm1001pcCntlineDfrmTimCntEntry 4 }


--- *********************************************************
---     TABLE for the pm1001pcCntlineDfrmPrimErrCnt articles
--- *********************************************************

pm1001pcCntlineDfrmPrimErrCntTable OBJECT-TYPE
	SYNTAX  SEQUENCE OF Pm1001pcCntlineDfrmPrimErrCntEntry
	MAX-ACCESS not-accessible
	STATUS current
	DESCRIPTION
        "
        List of pm1001pcCntlineDfrmPrimErrCnt
        Article
        "
	::= { pm1001pcCntLine 154 }


pm1001pcCntlineDfrmPrimErrCntEntry OBJECT-TYPE
	SYNTAX Pm1001pcCntlineDfrmPrimErrCntEntry
	MAX-ACCESS not-accessible
	STATUS current
	DESCRIPTION
        "
        Row definition for the pm1001pcCntlineDfrmPrimErrCnt
        table
        "
	INDEX   { pm1001pcCntlineDfrmPrimErrCntIndex }
	::= { pm1001pcCntlineDfrmPrimErrCntTable 1 }


Pm1001pcCntlineDfrmPrimErrCntEntry ::=
	SEQUENCE {
	pm1001pcCntlineDfrmPrimErrCntIndex
		INTEGER,
	pm1001pcCntlineDfrmPrimErrCntValuePortn
		Counter32,
	pm1001pcCntlineDfrmPrimErrCntErrorPortn
		EkiOnOff,
	pm1001pcCntlineDfrmPrimErrCntOverloadPortn
		EkiOnOff
	}


pm1001pcCntlineDfrmPrimErrCntIndex OBJECT-TYPE
	SYNTAX  INTEGER(0..128)
	MAX-ACCESS  read-only
	STATUS current
	DESCRIPTION
        "
        Index definition for the pm1001pcCntlineDfrmPrimErrCnt
        table
        "
	::= { pm1001pcCntlineDfrmPrimErrCntEntry 1 }


pm1001pcCntlineDfrmPrimErrCntValuePortn OBJECT-TYPE
	SYNTAX  Counter32
	MAX-ACCESS read-only
	STATUS current
	DESCRIPTION
        "
        FEC Corrected Errors Counter :This
        counter is incremented each time
        an error is corrected by the Forward
        Error Correction decoder
        "
	::= { pm1001pcCntlineDfrmPrimErrCntEntry 2 }


pm1001pcCntlineDfrmPrimErrCntErrorPortn OBJECT-TYPE
	SYNTAX  EkiOnOff
	MAX-ACCESS read-only
	STATUS current
	DESCRIPTION
        "
        Line FEC Counter Error :This bit
        when set indicates the FEC counter
        value is invalid on Port
        "
	::= { pm1001pcCntlineDfrmPrimErrCntEntry 3 }


pm1001pcCntlineDfrmPrimErrCntOverloadPortn OBJECT-TYPE
	SYNTAX  EkiOnOff
	MAX-ACCESS read-only
	STATUS current
	DESCRIPTION
        "
        Line FEC Counter Overload :This
        bit when set indicates a FEC counter
        overload on Port
        "
	::= { pm1001pcCntlineDfrmPrimErrCntEntry 4 }


--- *********************************************************
---     TABLE for the pm1001pcCntlineDfrmErrCntS articles
--- *********************************************************

pm1001pcCntlineDfrmErrCntSTable OBJECT-TYPE
	SYNTAX  SEQUENCE OF Pm1001pcCntlineDfrmErrCntSEntry
	MAX-ACCESS not-accessible
	STATUS current
	DESCRIPTION
        "
        List of pm1001pcCntlineDfrmErrCntS
        Article
        "
	::= { pm1001pcCntLine 1160 }


pm1001pcCntlineDfrmErrCntSEntry OBJECT-TYPE
	SYNTAX Pm1001pcCntlineDfrmErrCntSEntry
	MAX-ACCESS not-accessible
	STATUS current
	DESCRIPTION
        "
        Row definition for the pm1001pcCntlineDfrmErrCntS
        table
        "
	INDEX   { pm1001pcCntlineDfrmErrCntSIndex }
	::= { pm1001pcCntlineDfrmErrCntSTable 1 }


Pm1001pcCntlineDfrmErrCntSEntry ::=
	SEQUENCE {
	pm1001pcCntlineDfrmErrCntSIndex
		INTEGER,
	pm1001pcCntlineDfrmErrCntSValuePortn
		Counter32,
	pm1001pcCntlineDfrmErrCntSErrorPortn
		EkiOnOff,
	pm1001pcCntlineDfrmErrCntSOverloadPortn
		EkiOnOff
	}


pm1001pcCntlineDfrmErrCntSIndex OBJECT-TYPE
	SYNTAX  INTEGER(0..128)
	MAX-ACCESS  read-only
	STATUS current
	DESCRIPTION
        "
        Index definition for the pm1001pcCntlineDfrmErrCntS
        table
        "
	::= { pm1001pcCntlineDfrmErrCntSEntry 1 }


pm1001pcCntlineDfrmErrCntSValuePortn OBJECT-TYPE
	SYNTAX  Counter32
	MAX-ACCESS read-only
	STATUS current
	DESCRIPTION
        "
        Line B1 error rate (/s) :This
         OID gives the number of B1 errors
        per second that are detected on
        the Deframer input stream.
        "
	::= { pm1001pcCntlineDfrmErrCntSEntry 2 }


pm1001pcCntlineDfrmErrCntSErrorPortn OBJECT-TYPE
	SYNTAX  EkiOnOff
	MAX-ACCESS read-only
	STATUS current
	DESCRIPTION
        "

        "
	::= { pm1001pcCntlineDfrmErrCntSEntry 3 }


pm1001pcCntlineDfrmErrCntSOverloadPortn OBJECT-TYPE
	SYNTAX  EkiOnOff
	MAX-ACCESS read-only
	STATUS current
	DESCRIPTION
        "

        "
	::= { pm1001pcCntlineDfrmErrCntSEntry 4 }


pm1001pcCntCountersReset  OBJECT-TYPE
	SYNTAX EkiOnOff
	MAX-ACCESS read-write
	STATUS current
	DESCRIPTION
	"Counters Reset:This OID resets and restarts all the counters"
	::= { pm1001pccounters  259 }

pm1001pcCntCountersStop  OBJECT-TYPE
	SYNTAX EkiOnOff
	MAX-ACCESS read-write
	STATUS current
	DESCRIPTION
	"Counters stop:This OID stops all the counters"
	::= { pm1001pccounters 260 }






--- *****************************************************
--- $$$$$$$$$$$$$$$$$$$$$$$$$$$$$$$$$$$$$$$$$$$$$$$$$$$$$
---     RMON
--- $$$$$$$$$$$$$$$$$$$$$$$$$$$$$$$$$$$$$$$$$$$$$$$$$$$$$
--- *****************************************************



--- *********************************************************
---     TABLE for the pm1001pcMonupRmonByteCnt articles
--- *********************************************************

pm1001pcMonupRmonByteCntTable OBJECT-TYPE
	SYNTAX  SEQUENCE OF Pm1001pcMonupRmonByteCntEntry
	MAX-ACCESS not-accessible
	STATUS current
	DESCRIPTION
        "
        List of pm1001pcMonupRmonByteCnt
        Article
        "
	::= { pm1001pcRmonClient 16 }


pm1001pcMonupRmonByteCntEntry OBJECT-TYPE
	SYNTAX Pm1001pcMonupRmonByteCntEntry
	MAX-ACCESS not-accessible
	STATUS current
	DESCRIPTION
        "
        Row definition for the pm1001pcMonupRmonByteCnt
        table
        "
	INDEX   { pm1001pcMonupRmonByteCntIndex }
	::= { pm1001pcMonupRmonByteCntTable 1 }


Pm1001pcMonupRmonByteCntEntry ::=
	SEQUENCE {
	pm1001pcMonupRmonByteCntIndex
		INTEGER,
	pm1001pcMonupRmonByteCntValuePortn
		Counter64,
	pm1001pcMonupRmonByteCntErrorPortn
		EkiOnOff,
	pm1001pcMonupRmonByteCntOverloadPortn
		EkiOnOff
	}


pm1001pcMonupRmonByteCntIndex OBJECT-TYPE
	SYNTAX  INTEGER(0..128)
	MAX-ACCESS  read-only
	STATUS current
	DESCRIPTION
        "
        Index definition for the pm1001pcMonupRmonByteCnt
        table
        "
	::= { pm1001pcMonupRmonByteCntEntry 1 }


pm1001pcMonupRmonByteCntValuePortn OBJECT-TYPE
	SYNTAX  Counter64
	MAX-ACCESS read-only
	STATUS current
	DESCRIPTION
        "
        Client Input Bytes :This counter
        is increased each time a data byte
        is received on the client port
        "
	::= { pm1001pcMonupRmonByteCntEntry 2 }


pm1001pcMonupRmonByteCntErrorPortn OBJECT-TYPE
	SYNTAX  EkiOnOff
	MAX-ACCESS read-only
	STATUS current
	DESCRIPTION
        "
        Input Bytes Counter Error :This
        OID when set indicates the input
        Bytes counter value is invalid
         on client port
        "
	::= { pm1001pcMonupRmonByteCntEntry 3 }


pm1001pcMonupRmonByteCntOverloadPortn OBJECT-TYPE
	SYNTAX  EkiOnOff
	MAX-ACCESS read-only
	STATUS current
	DESCRIPTION
        "
        Input Bytes Counter Overload :This
        OID when set indicates an input
        Bytes counter overload on client
        port
        "
	::= { pm1001pcMonupRmonByteCntEntry 4 }


--- *********************************************************
---     TABLE for the pm1001pcMonupRmonCrcErrorCnt articles
--- *********************************************************

pm1001pcMonupRmonCrcErrorCntTable OBJECT-TYPE
	SYNTAX  SEQUENCE OF Pm1001pcMonupRmonCrcErrorCntEntry
	MAX-ACCESS not-accessible
	STATUS current
	DESCRIPTION
        "
        List of pm1001pcMonupRmonCrcErrorCnt
        Article
        "
	::= { pm1001pcRmonClient 24 }


pm1001pcMonupRmonCrcErrorCntEntry OBJECT-TYPE
	SYNTAX Pm1001pcMonupRmonCrcErrorCntEntry
	MAX-ACCESS not-accessible
	STATUS current
	DESCRIPTION
        "
        Row definition for the pm1001pcMonupRmonCrcErrorCnt
        table
        "
	INDEX   { pm1001pcMonupRmonCrcErrorCntIndex }
	::= { pm1001pcMonupRmonCrcErrorCntTable 1 }


Pm1001pcMonupRmonCrcErrorCntEntry ::=
	SEQUENCE {
	pm1001pcMonupRmonCrcErrorCntIndex
		INTEGER,
	pm1001pcMonupRmonCrcErrorCntValuePortn
		Counter64,
	pm1001pcMonupRmonCrcErrorCntErrorPortn
		EkiOnOff,
	pm1001pcMonupRmonCrcErrorCntOverloadPortn
		EkiOnOff
	}


pm1001pcMonupRmonCrcErrorCntIndex OBJECT-TYPE
	SYNTAX  INTEGER(0..128)
	MAX-ACCESS  read-only
	STATUS current
	DESCRIPTION
        "
        Index definition for the pm1001pcMonupRmonCrcErrorCnt
        table
        "
	::= { pm1001pcMonupRmonCrcErrorCntEntry 1 }


pm1001pcMonupRmonCrcErrorCntValuePortn OBJECT-TYPE
	SYNTAX  Counter64
	MAX-ACCESS read-only
	STATUS current
	DESCRIPTION
        "
        Client Input CRC Errors :This
         counter is increased each time
        a CRC error is detected on the
         input client port  <Help>  This
        counter gives the number of CRC
        Errors received on the client input
        port
        "
	::= { pm1001pcMonupRmonCrcErrorCntEntry 2 }


pm1001pcMonupRmonCrcErrorCntErrorPortn OBJECT-TYPE
	SYNTAX  EkiOnOff
	MAX-ACCESS read-only
	STATUS current
	DESCRIPTION
        "
        Input CRC Errors Counter Error
        :This OID when set indicates the
        input CRC Errors counter value
         is invalid on client port
        "
	::= { pm1001pcMonupRmonCrcErrorCntEntry 3 }


pm1001pcMonupRmonCrcErrorCntOverloadPortn OBJECT-TYPE
	SYNTAX  EkiOnOff
	MAX-ACCESS read-only
	STATUS current
	DESCRIPTION
        "
        Input CRC Errors Counter Overload
        :This OID when set indicates an
        input CRC Errors counter overload
        on client port
        "
	::= { pm1001pcMonupRmonCrcErrorCntEntry 4 }


--- *********************************************************
---     TABLE for the pm1001pcMonupRmonPacketsCnt articles
--- *********************************************************

pm1001pcMonupRmonPacketsCntTable OBJECT-TYPE
	SYNTAX  SEQUENCE OF Pm1001pcMonupRmonPacketsCntEntry
	MAX-ACCESS not-accessible
	STATUS current
	DESCRIPTION
        "
        List of pm1001pcMonupRmonPacketsCnt
        Article
        "
	::= { pm1001pcRmonClient 32 }


pm1001pcMonupRmonPacketsCntEntry OBJECT-TYPE
	SYNTAX Pm1001pcMonupRmonPacketsCntEntry
	MAX-ACCESS not-accessible
	STATUS current
	DESCRIPTION
        "
        Row definition for the pm1001pcMonupRmonPacketsCnt
        table
        "
	INDEX   { pm1001pcMonupRmonPacketsCntIndex }
	::= { pm1001pcMonupRmonPacketsCntTable 1 }


Pm1001pcMonupRmonPacketsCntEntry ::=
	SEQUENCE {
	pm1001pcMonupRmonPacketsCntIndex
		INTEGER,
	pm1001pcMonupRmonPacketsCntValuePortn
		Counter64,
	pm1001pcMonupRmonPacketsCntErrorPortn
		EkiOnOff,
	pm1001pcMonupRmonPacketsCntOverloadPortn
		EkiOnOff
	}


pm1001pcMonupRmonPacketsCntIndex OBJECT-TYPE
	SYNTAX  INTEGER(0..128)
	MAX-ACCESS  read-only
	STATUS current
	DESCRIPTION
        "
        Index definition for the pm1001pcMonupRmonPacketsCnt
        table
        "
	::= { pm1001pcMonupRmonPacketsCntEntry 1 }


pm1001pcMonupRmonPacketsCntValuePortn OBJECT-TYPE
	SYNTAX  Counter64
	MAX-ACCESS read-only
	STATUS current
	DESCRIPTION
        "
        Client Input Packets :This counter
        is increased each time a packet
        is received on the client port
        "
	::= { pm1001pcMonupRmonPacketsCntEntry 2 }


pm1001pcMonupRmonPacketsCntErrorPortn OBJECT-TYPE
	SYNTAX  EkiOnOff
	MAX-ACCESS read-only
	STATUS current
	DESCRIPTION
        "
        Input Packets Counter Error :This
        OID when set indicates the input
        Packets counter value is invalid
        on client port
        "
	::= { pm1001pcMonupRmonPacketsCntEntry 3 }


pm1001pcMonupRmonPacketsCntOverloadPortn OBJECT-TYPE
	SYNTAX  EkiOnOff
	MAX-ACCESS read-only
	STATUS current
	DESCRIPTION
        "
        Input Packets Counter Overload
        :This OID when set indicates an
        input Packets counter overload
         on client port
        "
	::= { pm1001pcMonupRmonPacketsCntEntry 4 }


--- *********************************************************
---     TABLE for the pm1001pcMonupRmonBroadcastCnt articles
--- *********************************************************

pm1001pcMonupRmonBroadcastCntTable OBJECT-TYPE
	SYNTAX  SEQUENCE OF Pm1001pcMonupRmonBroadcastCntEntry
	MAX-ACCESS not-accessible
	STATUS current
	DESCRIPTION
        "
        List of pm1001pcMonupRmonBroadcastCnt
        Article
        "
	::= { pm1001pcRmonClient 40 }


pm1001pcMonupRmonBroadcastCntEntry OBJECT-TYPE
	SYNTAX Pm1001pcMonupRmonBroadcastCntEntry
	MAX-ACCESS not-accessible
	STATUS current
	DESCRIPTION
        "
        Row definition for the pm1001pcMonupRmonBroadcastCnt
        table
        "
	INDEX   { pm1001pcMonupRmonBroadcastCntIndex }
	::= { pm1001pcMonupRmonBroadcastCntTable 1 }


Pm1001pcMonupRmonBroadcastCntEntry ::=
	SEQUENCE {
	pm1001pcMonupRmonBroadcastCntIndex
		INTEGER,
	pm1001pcMonupRmonBroadcastCntValuePortn
		Counter64,
	pm1001pcMonupRmonBroadcastCntErrorPortn
		EkiOnOff,
	pm1001pcMonupRmonBroadcastCntOverloadPortn
		EkiOnOff
	}


pm1001pcMonupRmonBroadcastCntIndex OBJECT-TYPE
	SYNTAX  INTEGER(0..128)
	MAX-ACCESS  read-only
	STATUS current
	DESCRIPTION
        "
        Index definition for the pm1001pcMonupRmonBroadcastCnt
        table
        "
	::= { pm1001pcMonupRmonBroadcastCntEntry 1 }


pm1001pcMonupRmonBroadcastCntValuePortn OBJECT-TYPE
	SYNTAX  Counter64
	MAX-ACCESS read-only
	STATUS current
	DESCRIPTION
        "
        Client Input Broadcast Packets
        :This counter is increased each
        time a broadcast packet is received
        on the client port
        "
	::= { pm1001pcMonupRmonBroadcastCntEntry 2 }


pm1001pcMonupRmonBroadcastCntErrorPortn OBJECT-TYPE
	SYNTAX  EkiOnOff
	MAX-ACCESS read-only
	STATUS current
	DESCRIPTION
        "
        Input Broadcast Counter Error
         :This OID when set indicates the
        input Broadcast counter value is
        invalid on client port
        "
	::= { pm1001pcMonupRmonBroadcastCntEntry 3 }


pm1001pcMonupRmonBroadcastCntOverloadPortn OBJECT-TYPE
	SYNTAX  EkiOnOff
	MAX-ACCESS read-only
	STATUS current
	DESCRIPTION
        "
        Input Broadcast Counter Overload
        :This OID when set indicates an
        input Broadcast counter overload
        on client port
        "
	::= { pm1001pcMonupRmonBroadcastCntEntry 4 }


--- *********************************************************
---     TABLE for the pm1001pcMonupRmonMulticastCnt articles
--- *********************************************************

pm1001pcMonupRmonMulticastCntTable OBJECT-TYPE
	SYNTAX  SEQUENCE OF Pm1001pcMonupRmonMulticastCntEntry
	MAX-ACCESS not-accessible
	STATUS current
	DESCRIPTION
        "
        List of pm1001pcMonupRmonMulticastCnt
        Article
        "
	::= { pm1001pcRmonClient 48 }


pm1001pcMonupRmonMulticastCntEntry OBJECT-TYPE
	SYNTAX Pm1001pcMonupRmonMulticastCntEntry
	MAX-ACCESS not-accessible
	STATUS current
	DESCRIPTION
        "
        Row definition for the pm1001pcMonupRmonMulticastCnt
        table
        "
	INDEX   { pm1001pcMonupRmonMulticastCntIndex }
	::= { pm1001pcMonupRmonMulticastCntTable 1 }


Pm1001pcMonupRmonMulticastCntEntry ::=
	SEQUENCE {
	pm1001pcMonupRmonMulticastCntIndex
		INTEGER,
	pm1001pcMonupRmonMulticastCntValuePortn
		Counter64,
	pm1001pcMonupRmonMulticastCntErrorPortn
		EkiOnOff,
	pm1001pcMonupRmonMulticastCntOverloadPortn
		EkiOnOff
	}


pm1001pcMonupRmonMulticastCntIndex OBJECT-TYPE
	SYNTAX  INTEGER(0..128)
	MAX-ACCESS  read-only
	STATUS current
	DESCRIPTION
        "
        Index definition for the pm1001pcMonupRmonMulticastCnt
        table
        "
	::= { pm1001pcMonupRmonMulticastCntEntry 1 }


pm1001pcMonupRmonMulticastCntValuePortn OBJECT-TYPE
	SYNTAX  Counter64
	MAX-ACCESS read-only
	STATUS current
	DESCRIPTION
        "
        Client Input Multicast Packets
        :This counter is increased each
        time a Multicast packet is received
        on the client port
        "
	::= { pm1001pcMonupRmonMulticastCntEntry 2 }


pm1001pcMonupRmonMulticastCntErrorPortn OBJECT-TYPE
	SYNTAX  EkiOnOff
	MAX-ACCESS read-only
	STATUS current
	DESCRIPTION
        "
        Input Multicast Counter Error
         :This OID when set indicates the
        input Multicast counter value is
        invalid on client port
        "
	::= { pm1001pcMonupRmonMulticastCntEntry 3 }


pm1001pcMonupRmonMulticastCntOverloadPortn OBJECT-TYPE
	SYNTAX  EkiOnOff
	MAX-ACCESS read-only
	STATUS current
	DESCRIPTION
        "
        Input Multicast Counter Overload
        :This OID when set indicates an
        input Multicast counter overload
        on client port
        "
	::= { pm1001pcMonupRmonMulticastCntEntry 4 }


--- *********************************************************
---     TABLE for the pm1001pcMonupRmonTimerCnt articles
--- *********************************************************

pm1001pcMonupRmonTimerCntTable OBJECT-TYPE
	SYNTAX  SEQUENCE OF Pm1001pcMonupRmonTimerCntEntry
	MAX-ACCESS not-accessible
	STATUS current
	DESCRIPTION
        "
        List of pm1001pcMonupRmonTimerCnt
        Article
        "
	::= { pm1001pcRmonClient 56 }


pm1001pcMonupRmonTimerCntEntry OBJECT-TYPE
	SYNTAX Pm1001pcMonupRmonTimerCntEntry
	MAX-ACCESS not-accessible
	STATUS current
	DESCRIPTION
        "
        Row definition for the pm1001pcMonupRmonTimerCnt
        table
        "
	INDEX   { pm1001pcMonupRmonTimerCntIndex }
	::= { pm1001pcMonupRmonTimerCntTable 1 }


Pm1001pcMonupRmonTimerCntEntry ::=
	SEQUENCE {
	pm1001pcMonupRmonTimerCntIndex
		INTEGER,
	pm1001pcMonupRmonTimerCntValuePortn
		Counter64,
	pm1001pcMonupRmonTimerCntErrorPortn
		EkiOnOff,
	pm1001pcMonupRmonTimerCntOverloadPortn
		EkiOnOff
	}


pm1001pcMonupRmonTimerCntIndex OBJECT-TYPE
	SYNTAX  INTEGER(0..128)
	MAX-ACCESS  read-only
	STATUS current
	DESCRIPTION
        "
        Index definition for the pm1001pcMonupRmonTimerCnt
        table
        "
	::= { pm1001pcMonupRmonTimerCntEntry 1 }


pm1001pcMonupRmonTimerCntValuePortn OBJECT-TYPE
	SYNTAX  Counter64
	MAX-ACCESS read-only
	STATUS current
	DESCRIPTION
        "
        RMON Timer On Client Input :This
        is the timing counter dedicated
        to the upstream RMON counters.
         It is incremented every 125 us.
        "
	::= { pm1001pcMonupRmonTimerCntEntry 2 }


pm1001pcMonupRmonTimerCntErrorPortn OBJECT-TYPE
	SYNTAX  EkiOnOff
	MAX-ACCESS read-only
	STATUS current
	DESCRIPTION
        "
        Input RMON Timer Error :This OID
        when set indicates the input RMON
        timer is invalid on client port
        "
	::= { pm1001pcMonupRmonTimerCntEntry 3 }


pm1001pcMonupRmonTimerCntOverloadPortn OBJECT-TYPE
	SYNTAX  EkiOnOff
	MAX-ACCESS read-only
	STATUS current
	DESCRIPTION
        "
        Input RMON Timer Overload :This
        OID when set indicates an input
        RMON timer overload on client port
        "
	::= { pm1001pcMonupRmonTimerCntEntry 4 }


--- *********************************************************
---     TABLE for the pm1001pcMonupRmonPauseFrameCnt articles
--- *********************************************************

pm1001pcMonupRmonPauseFrameCntTable OBJECT-TYPE
	SYNTAX  SEQUENCE OF Pm1001pcMonupRmonPauseFrameCntEntry
	MAX-ACCESS not-accessible
	STATUS current
	DESCRIPTION
        "
        List of pm1001pcMonupRmonPauseFrameCnt
        Article
        "
	::= { pm1001pcRmonClient 64 }


pm1001pcMonupRmonPauseFrameCntEntry OBJECT-TYPE
	SYNTAX Pm1001pcMonupRmonPauseFrameCntEntry
	MAX-ACCESS not-accessible
	STATUS current
	DESCRIPTION
        "
        Row definition for the pm1001pcMonupRmonPauseFrameCnt
        table
        "
	INDEX   { pm1001pcMonupRmonPauseFrameCntIndex }
	::= { pm1001pcMonupRmonPauseFrameCntTable 1 }


Pm1001pcMonupRmonPauseFrameCntEntry ::=
	SEQUENCE {
	pm1001pcMonupRmonPauseFrameCntIndex
		INTEGER,
	pm1001pcMonupRmonPauseFrameCntValuePortn
		Counter64,
	pm1001pcMonupRmonPauseFrameCntErrorPortn
		EkiOnOff,
	pm1001pcMonupRmonPauseFrameCntOverloadPortn
		EkiOnOff
	}


pm1001pcMonupRmonPauseFrameCntIndex OBJECT-TYPE
	SYNTAX  INTEGER(0..128)
	MAX-ACCESS  read-only
	STATUS current
	DESCRIPTION
        "
        Index definition for the pm1001pcMonupRmonPauseFrameCnt
        table
        "
	::= { pm1001pcMonupRmonPauseFrameCntEntry 1 }


pm1001pcMonupRmonPauseFrameCntValuePortn OBJECT-TYPE
	SYNTAX  Counter64
	MAX-ACCESS read-only
	STATUS current
	DESCRIPTION
        "
        Client Input Pause Frames :This
        counter is increased each time
         a Pause frame is received on the
        client port
        "
	::= { pm1001pcMonupRmonPauseFrameCntEntry 2 }


pm1001pcMonupRmonPauseFrameCntErrorPortn OBJECT-TYPE
	SYNTAX  EkiOnOff
	MAX-ACCESS read-only
	STATUS current
	DESCRIPTION
        "
        Input Pause Counter Error :This
        OID when set indicates the input
        Pause counter value is invalid
         on client port
        "
	::= { pm1001pcMonupRmonPauseFrameCntEntry 3 }


pm1001pcMonupRmonPauseFrameCntOverloadPortn OBJECT-TYPE
	SYNTAX  EkiOnOff
	MAX-ACCESS read-only
	STATUS current
	DESCRIPTION
        "
        Input Pause Counter Overload :This
        OID when set indicates an input
        Pause counter overload on client
        port
        "
	::= { pm1001pcMonupRmonPauseFrameCntEntry 4 }


--- *********************************************************
---     TABLE for the pm1001pcMonupRmonDropFrameCnt articles
--- *********************************************************

pm1001pcMonupRmonDropFrameCntTable OBJECT-TYPE
	SYNTAX  SEQUENCE OF Pm1001pcMonupRmonDropFrameCntEntry
	MAX-ACCESS not-accessible
	STATUS current
	DESCRIPTION
        "
        List of pm1001pcMonupRmonDropFrameCnt
        Article
        "
	::= { pm1001pcRmonClient 72 }


pm1001pcMonupRmonDropFrameCntEntry OBJECT-TYPE
	SYNTAX Pm1001pcMonupRmonDropFrameCntEntry
	MAX-ACCESS not-accessible
	STATUS current
	DESCRIPTION
        "
        Row definition for the pm1001pcMonupRmonDropFrameCnt
        table
        "
	INDEX   { pm1001pcMonupRmonDropFrameCntIndex }
	::= { pm1001pcMonupRmonDropFrameCntTable 1 }


Pm1001pcMonupRmonDropFrameCntEntry ::=
	SEQUENCE {
	pm1001pcMonupRmonDropFrameCntIndex
		INTEGER,
	pm1001pcMonupRmonDropFrameCntValuePortn
		Counter64,
	pm1001pcMonupRmonDropFrameCntErrorPortn
		EkiOnOff,
	pm1001pcMonupRmonDropFrameCntOverloadPortn
		EkiOnOff
	}


pm1001pcMonupRmonDropFrameCntIndex OBJECT-TYPE
	SYNTAX  INTEGER(0..128)
	MAX-ACCESS  read-only
	STATUS current
	DESCRIPTION
        "
        Index definition for the pm1001pcMonupRmonDropFrameCnt
        table
        "
	::= { pm1001pcMonupRmonDropFrameCntEntry 1 }


pm1001pcMonupRmonDropFrameCntValuePortn OBJECT-TYPE
	SYNTAX  Counter64
	MAX-ACCESS read-only
	STATUS current
	DESCRIPTION
        "
        Client Input Drop Packets :This
        counter is increased each time
         a Frame is dropped on the input
        client port
        "
	::= { pm1001pcMonupRmonDropFrameCntEntry 2 }


pm1001pcMonupRmonDropFrameCntErrorPortn OBJECT-TYPE
	SYNTAX  EkiOnOff
	MAX-ACCESS read-only
	STATUS current
	DESCRIPTION
        "
        Input Drop Counter Error :This
        OID when set indicates the input
        Drop counter value is invalid on
        client port
        "
	::= { pm1001pcMonupRmonDropFrameCntEntry 3 }


pm1001pcMonupRmonDropFrameCntOverloadPortn OBJECT-TYPE
	SYNTAX  EkiOnOff
	MAX-ACCESS read-only
	STATUS current
	DESCRIPTION
        "
        Input Drop Counter Overload :This
        OID when set indicates an input
        Drop counter overload on client
        port
        "
	::= { pm1001pcMonupRmonDropFrameCntEntry 4 }


--- *********************************************************
---     TABLE for the pm1001pcMonupRmonBitsCnt articles
--- *********************************************************

pm1001pcMonupRmonBitsCntTable OBJECT-TYPE
	SYNTAX  SEQUENCE OF Pm1001pcMonupRmonBitsCntEntry
	MAX-ACCESS not-accessible
	STATUS current
	DESCRIPTION
        "
        List of pm1001pcMonupRmonBitsCnt
        Article
        "
	::= { pm1001pcRmonClient 80 }


pm1001pcMonupRmonBitsCntEntry OBJECT-TYPE
	SYNTAX Pm1001pcMonupRmonBitsCntEntry
	MAX-ACCESS not-accessible
	STATUS current
	DESCRIPTION
        "
        Row definition for the pm1001pcMonupRmonBitsCnt
        table
        "
	INDEX   { pm1001pcMonupRmonBitsCntIndex }
	::= { pm1001pcMonupRmonBitsCntTable 1 }


Pm1001pcMonupRmonBitsCntEntry ::=
	SEQUENCE {
	pm1001pcMonupRmonBitsCntIndex
		INTEGER,
	pm1001pcMonupRmonBitsCntValuePortn
		Counter64,
	pm1001pcMonupRmonBitsCntErrorPortn
		EkiOnOff,
	pm1001pcMonupRmonBitsCntOverloadPortn
		EkiOnOff
	}


pm1001pcMonupRmonBitsCntIndex OBJECT-TYPE
	SYNTAX  INTEGER(0..128)
	MAX-ACCESS  read-only
	STATUS current
	DESCRIPTION
        "
        Index definition for the pm1001pcMonupRmonBitsCnt
        table
        "
	::= { pm1001pcMonupRmonBitsCntEntry 1 }


pm1001pcMonupRmonBitsCntValuePortn OBJECT-TYPE
	SYNTAX  Counter64
	MAX-ACCESS read-only
	STATUS current
	DESCRIPTION
        "
        Client Input Bits :This counter
        is increased each time a bit is
        received on the input client port
        "
	::= { pm1001pcMonupRmonBitsCntEntry 2 }


pm1001pcMonupRmonBitsCntErrorPortn OBJECT-TYPE
	SYNTAX  EkiOnOff
	MAX-ACCESS read-only
	STATUS current
	DESCRIPTION
        "
        Input Bits Counter Error :This
        OID when set indicates the input
        Bits counter value is invalid on
        client port
        "
	::= { pm1001pcMonupRmonBitsCntEntry 3 }


pm1001pcMonupRmonBitsCntOverloadPortn OBJECT-TYPE
	SYNTAX  EkiOnOff
	MAX-ACCESS read-only
	STATUS current
	DESCRIPTION
        "
        Input Bits Counter Overload :This
        OID when set indicates an input
        Bits counter overload on client
        port
        "
	::= { pm1001pcMonupRmonBitsCntEntry 4 }


--- *********************************************************
---     TABLE for the pm1001pcMondwRmonByteCnt articles
--- *********************************************************

pm1001pcMondwRmonByteCntTable OBJECT-TYPE
	SYNTAX  SEQUENCE OF Pm1001pcMondwRmonByteCntEntry
	MAX-ACCESS not-accessible
	STATUS current
	DESCRIPTION
        "
        List of pm1001pcMondwRmonByteCnt
        Article
        "
	::= { pm1001pcRmonClient 112 }


pm1001pcMondwRmonByteCntEntry OBJECT-TYPE
	SYNTAX Pm1001pcMondwRmonByteCntEntry
	MAX-ACCESS not-accessible
	STATUS current
	DESCRIPTION
        "
        Row definition for the pm1001pcMondwRmonByteCnt
        table
        "
	INDEX   { pm1001pcMondwRmonByteCntIndex }
	::= { pm1001pcMondwRmonByteCntTable 1 }


Pm1001pcMondwRmonByteCntEntry ::=
	SEQUENCE {
	pm1001pcMondwRmonByteCntIndex
		INTEGER,
	pm1001pcMondwRmonByteCntValuePortn
		Counter64,
	pm1001pcMondwRmonByteCntErrorPortn
		EkiOnOff,
	pm1001pcMondwRmonByteCntOverloadPortn
		EkiOnOff
	}


pm1001pcMondwRmonByteCntIndex OBJECT-TYPE
	SYNTAX  INTEGER(0..128)
	MAX-ACCESS  read-only
	STATUS current
	DESCRIPTION
        "
        Index definition for the pm1001pcMondwRmonByteCnt
        table
        "
	::= { pm1001pcMondwRmonByteCntEntry 1 }


pm1001pcMondwRmonByteCntValuePortn OBJECT-TYPE
	SYNTAX  Counter64
	MAX-ACCESS read-only
	STATUS current
	DESCRIPTION
        "
        Client Output Bytes :This counter
        is increased each time a data byte
        is transmitted on the client port
        "
	::= { pm1001pcMondwRmonByteCntEntry 2 }


pm1001pcMondwRmonByteCntErrorPortn OBJECT-TYPE
	SYNTAX  EkiOnOff
	MAX-ACCESS read-only
	STATUS current
	DESCRIPTION
        "
        Output Bytes Counter Error :This
        OID when set indicates the output
        Bytes counter value is invalid
         on client port
        "
	::= { pm1001pcMondwRmonByteCntEntry 3 }


pm1001pcMondwRmonByteCntOverloadPortn OBJECT-TYPE
	SYNTAX  EkiOnOff
	MAX-ACCESS read-only
	STATUS current
	DESCRIPTION
        "
        Output Bytes Counter Overload
         :This OID when set indicates an
        output Bytes counter overload on
        client port
        "
	::= { pm1001pcMondwRmonByteCntEntry 4 }


--- *********************************************************
---     TABLE for the pm1001pcMondwRmonCrcErrorCnt articles
--- *********************************************************

pm1001pcMondwRmonCrcErrorCntTable OBJECT-TYPE
	SYNTAX  SEQUENCE OF Pm1001pcMondwRmonCrcErrorCntEntry
	MAX-ACCESS not-accessible
	STATUS current
	DESCRIPTION
        "
        List of pm1001pcMondwRmonCrcErrorCnt
        Article
        "
	::= { pm1001pcRmonClient 120 }


pm1001pcMondwRmonCrcErrorCntEntry OBJECT-TYPE
	SYNTAX Pm1001pcMondwRmonCrcErrorCntEntry
	MAX-ACCESS not-accessible
	STATUS current
	DESCRIPTION
        "
        Row definition for the pm1001pcMondwRmonCrcErrorCnt
        table
        "
	INDEX   { pm1001pcMondwRmonCrcErrorCntIndex }
	::= { pm1001pcMondwRmonCrcErrorCntTable 1 }


Pm1001pcMondwRmonCrcErrorCntEntry ::=
	SEQUENCE {
	pm1001pcMondwRmonCrcErrorCntIndex
		INTEGER,
	pm1001pcMondwRmonCrcErrorCntValuePortn
		Counter64,
	pm1001pcMondwRmonCrcErrorCntErrorPortn
		EkiOnOff,
	pm1001pcMondwRmonCrcErrorCntOverloadPortn
		EkiOnOff
	}


pm1001pcMondwRmonCrcErrorCntIndex OBJECT-TYPE
	SYNTAX  INTEGER(0..128)
	MAX-ACCESS  read-only
	STATUS current
	DESCRIPTION
        "
        Index definition for the pm1001pcMondwRmonCrcErrorCnt
        table
        "
	::= { pm1001pcMondwRmonCrcErrorCntEntry 1 }


pm1001pcMondwRmonCrcErrorCntValuePortn OBJECT-TYPE
	SYNTAX  Counter64
	MAX-ACCESS read-only
	STATUS current
	DESCRIPTION
        "
        Client Output CRC Errors :This
        counter is increased each time
         a CRC error is detected on the
        output client port  <Help>  This
        counter gives the number of CRC
        Errors transmitted on the client
        output port
        "
	::= { pm1001pcMondwRmonCrcErrorCntEntry 2 }


pm1001pcMondwRmonCrcErrorCntErrorPortn OBJECT-TYPE
	SYNTAX  EkiOnOff
	MAX-ACCESS read-only
	STATUS current
	DESCRIPTION
        "
        Output CRC Errors Counter Error
        :This OID when set indicates the
        output CRC Errors counter value
        is invalid on client port
        "
	::= { pm1001pcMondwRmonCrcErrorCntEntry 3 }


pm1001pcMondwRmonCrcErrorCntOverloadPortn OBJECT-TYPE
	SYNTAX  EkiOnOff
	MAX-ACCESS read-only
	STATUS current
	DESCRIPTION
        "
        Output CRC Errors Counter Overload
        :This OID when set indicates an
        output CRC Errors counter overload
        on client port
        "
	::= { pm1001pcMondwRmonCrcErrorCntEntry 4 }


--- *********************************************************
---     TABLE for the pm1001pcMondwRmonPacketsCnt articles
--- *********************************************************

pm1001pcMondwRmonPacketsCntTable OBJECT-TYPE
	SYNTAX  SEQUENCE OF Pm1001pcMondwRmonPacketsCntEntry
	MAX-ACCESS not-accessible
	STATUS current
	DESCRIPTION
        "
        List of pm1001pcMondwRmonPacketsCnt
        Article
        "
	::= { pm1001pcRmonClient 128 }


pm1001pcMondwRmonPacketsCntEntry OBJECT-TYPE
	SYNTAX Pm1001pcMondwRmonPacketsCntEntry
	MAX-ACCESS not-accessible
	STATUS current
	DESCRIPTION
        "
        Row definition for the pm1001pcMondwRmonPacketsCnt
        table
        "
	INDEX   { pm1001pcMondwRmonPacketsCntIndex }
	::= { pm1001pcMondwRmonPacketsCntTable 1 }


Pm1001pcMondwRmonPacketsCntEntry ::=
	SEQUENCE {
	pm1001pcMondwRmonPacketsCntIndex
		INTEGER,
	pm1001pcMondwRmonPacketsCntValuePortn
		Counter64,
	pm1001pcMondwRmonPacketsCntErrorPortn
		EkiOnOff,
	pm1001pcMondwRmonPacketsCntOverloadPortn
		EkiOnOff
	}


pm1001pcMondwRmonPacketsCntIndex OBJECT-TYPE
	SYNTAX  INTEGER(0..128)
	MAX-ACCESS  read-only
	STATUS current
	DESCRIPTION
        "
        Index definition for the pm1001pcMondwRmonPacketsCnt
        table
        "
	::= { pm1001pcMondwRmonPacketsCntEntry 1 }


pm1001pcMondwRmonPacketsCntValuePortn OBJECT-TYPE
	SYNTAX  Counter64
	MAX-ACCESS read-only
	STATUS current
	DESCRIPTION
        "
        Client Output Packets :This counter
        is increased each time a packet
        is transmitted on the client port
        "
	::= { pm1001pcMondwRmonPacketsCntEntry 2 }


pm1001pcMondwRmonPacketsCntErrorPortn OBJECT-TYPE
	SYNTAX  EkiOnOff
	MAX-ACCESS read-only
	STATUS current
	DESCRIPTION
        "
        Output Packets Counter Error :This
        OID when set indicates the output
        Packets counter value is invalid
        on client port
        "
	::= { pm1001pcMondwRmonPacketsCntEntry 3 }


pm1001pcMondwRmonPacketsCntOverloadPortn OBJECT-TYPE
	SYNTAX  EkiOnOff
	MAX-ACCESS read-only
	STATUS current
	DESCRIPTION
        "
        Output Packets Counter Overload
        :This OID when set indicates an
        output Packets counter overload
        on client port
        "
	::= { pm1001pcMondwRmonPacketsCntEntry 4 }


--- *********************************************************
---     TABLE for the pm1001pcMondwRmonBroadcastCnt articles
--- *********************************************************

pm1001pcMondwRmonBroadcastCntTable OBJECT-TYPE
	SYNTAX  SEQUENCE OF Pm1001pcMondwRmonBroadcastCntEntry
	MAX-ACCESS not-accessible
	STATUS current
	DESCRIPTION
        "
        List of pm1001pcMondwRmonBroadcastCnt
        Article
        "
	::= { pm1001pcRmonClient 136 }


pm1001pcMondwRmonBroadcastCntEntry OBJECT-TYPE
	SYNTAX Pm1001pcMondwRmonBroadcastCntEntry
	MAX-ACCESS not-accessible
	STATUS current
	DESCRIPTION
        "
        Row definition for the pm1001pcMondwRmonBroadcastCnt
        table
        "
	INDEX   { pm1001pcMondwRmonBroadcastCntIndex }
	::= { pm1001pcMondwRmonBroadcastCntTable 1 }


Pm1001pcMondwRmonBroadcastCntEntry ::=
	SEQUENCE {
	pm1001pcMondwRmonBroadcastCntIndex
		INTEGER,
	pm1001pcMondwRmonBroadcastCntValuePortn
		Counter64,
	pm1001pcMondwRmonBroadcastCntErrorPortn
		EkiOnOff,
	pm1001pcMondwRmonBroadcastCntOverloadPortn
		EkiOnOff
	}


pm1001pcMondwRmonBroadcastCntIndex OBJECT-TYPE
	SYNTAX  INTEGER(0..128)
	MAX-ACCESS  read-only
	STATUS current
	DESCRIPTION
        "
        Index definition for the pm1001pcMondwRmonBroadcastCnt
        table
        "
	::= { pm1001pcMondwRmonBroadcastCntEntry 1 }


pm1001pcMondwRmonBroadcastCntValuePortn OBJECT-TYPE
	SYNTAX  Counter64
	MAX-ACCESS read-only
	STATUS current
	DESCRIPTION
        "
        Client Output Broadcast Packets
        :This counter is increased each
        time a broadcast packet is transmitted
        on the client port
        "
	::= { pm1001pcMondwRmonBroadcastCntEntry 2 }


pm1001pcMondwRmonBroadcastCntErrorPortn OBJECT-TYPE
	SYNTAX  EkiOnOff
	MAX-ACCESS read-only
	STATUS current
	DESCRIPTION
        "
        Output Broadcast Counter Error
        :This OID when set indicates the
        output Broadcast counter value
         is invalid on client port
        "
	::= { pm1001pcMondwRmonBroadcastCntEntry 3 }


pm1001pcMondwRmonBroadcastCntOverloadPortn OBJECT-TYPE
	SYNTAX  EkiOnOff
	MAX-ACCESS read-only
	STATUS current
	DESCRIPTION
        "
        Output Broadcast Counter Overload
        :This OID when set indicates an
        output Broadcast counter overload
        on client port
        "
	::= { pm1001pcMondwRmonBroadcastCntEntry 4 }


--- *********************************************************
---     TABLE for the pm1001pcMondwRmonMulticastCnt articles
--- *********************************************************

pm1001pcMondwRmonMulticastCntTable OBJECT-TYPE
	SYNTAX  SEQUENCE OF Pm1001pcMondwRmonMulticastCntEntry
	MAX-ACCESS not-accessible
	STATUS current
	DESCRIPTION
        "
        List of pm1001pcMondwRmonMulticastCnt
        Article
        "
	::= { pm1001pcRmonClient 144 }


pm1001pcMondwRmonMulticastCntEntry OBJECT-TYPE
	SYNTAX Pm1001pcMondwRmonMulticastCntEntry
	MAX-ACCESS not-accessible
	STATUS current
	DESCRIPTION
        "
        Row definition for the pm1001pcMondwRmonMulticastCnt
        table
        "
	INDEX   { pm1001pcMondwRmonMulticastCntIndex }
	::= { pm1001pcMondwRmonMulticastCntTable 1 }


Pm1001pcMondwRmonMulticastCntEntry ::=
	SEQUENCE {
	pm1001pcMondwRmonMulticastCntIndex
		INTEGER,
	pm1001pcMondwRmonMulticastCntValuePortn
		Counter64,
	pm1001pcMondwRmonMulticastCntErrorPortn
		EkiOnOff,
	pm1001pcMondwRmonMulticastCntOverloadPortn
		EkiOnOff
	}


pm1001pcMondwRmonMulticastCntIndex OBJECT-TYPE
	SYNTAX  INTEGER(0..128)
	MAX-ACCESS  read-only
	STATUS current
	DESCRIPTION
        "
        Index definition for the pm1001pcMondwRmonMulticastCnt
        table
        "
	::= { pm1001pcMondwRmonMulticastCntEntry 1 }


pm1001pcMondwRmonMulticastCntValuePortn OBJECT-TYPE
	SYNTAX  Counter64
	MAX-ACCESS read-only
	STATUS current
	DESCRIPTION
        "
        Client Output Multicast Packets
        :This counter is increased each
        time a Multicast packet is transmitted
        on the client port
        "
	::= { pm1001pcMondwRmonMulticastCntEntry 2 }


pm1001pcMondwRmonMulticastCntErrorPortn OBJECT-TYPE
	SYNTAX  EkiOnOff
	MAX-ACCESS read-only
	STATUS current
	DESCRIPTION
        "
        Output Multicast Counter Error
        :This OID when set indicates the
        output Multicast counter value
         is invalid on client port
        "
	::= { pm1001pcMondwRmonMulticastCntEntry 3 }


pm1001pcMondwRmonMulticastCntOverloadPortn OBJECT-TYPE
	SYNTAX  EkiOnOff
	MAX-ACCESS read-only
	STATUS current
	DESCRIPTION
        "
        Output Multicast Counter Overload
        :This OID when set indicates an
        output Multicast counter overload
        on client port
        "
	::= { pm1001pcMondwRmonMulticastCntEntry 4 }


--- *********************************************************
---     TABLE for the pm1001pcMondwRmonPauseFrameCnt articles
--- *********************************************************

pm1001pcMondwRmonPauseFrameCntTable OBJECT-TYPE
	SYNTAX  SEQUENCE OF Pm1001pcMondwRmonPauseFrameCntEntry
	MAX-ACCESS not-accessible
	STATUS current
	DESCRIPTION
        "
        List of pm1001pcMondwRmonPauseFrameCnt
        Article
        "
	::= { pm1001pcRmonClient 152 }


pm1001pcMondwRmonPauseFrameCntEntry OBJECT-TYPE
	SYNTAX Pm1001pcMondwRmonPauseFrameCntEntry
	MAX-ACCESS not-accessible
	STATUS current
	DESCRIPTION
        "
        Row definition for the pm1001pcMondwRmonPauseFrameCnt
        table
        "
	INDEX   { pm1001pcMondwRmonPauseFrameCntIndex }
	::= { pm1001pcMondwRmonPauseFrameCntTable 1 }


Pm1001pcMondwRmonPauseFrameCntEntry ::=
	SEQUENCE {
	pm1001pcMondwRmonPauseFrameCntIndex
		INTEGER,
	pm1001pcMondwRmonPauseFrameCntValuePortn
		Counter64,
	pm1001pcMondwRmonPauseFrameCntErrorPortn
		EkiOnOff,
	pm1001pcMondwRmonPauseFrameCntOverloadPortn
		EkiOnOff
	}


pm1001pcMondwRmonPauseFrameCntIndex OBJECT-TYPE
	SYNTAX  INTEGER(0..128)
	MAX-ACCESS  read-only
	STATUS current
	DESCRIPTION
        "
        Index definition for the pm1001pcMondwRmonPauseFrameCnt
        table
        "
	::= { pm1001pcMondwRmonPauseFrameCntEntry 1 }


pm1001pcMondwRmonPauseFrameCntValuePortn OBJECT-TYPE
	SYNTAX  Counter64
	MAX-ACCESS read-only
	STATUS current
	DESCRIPTION
        "
        Client Output Pause Frames :This
        counter is increased each time
         a Pause frame is generated by
         the PM on the client port
        "
	::= { pm1001pcMondwRmonPauseFrameCntEntry 2 }


pm1001pcMondwRmonPauseFrameCntErrorPortn OBJECT-TYPE
	SYNTAX  EkiOnOff
	MAX-ACCESS read-only
	STATUS current
	DESCRIPTION
        "
        Output Pause Counter Error :This
        OID when set indicates the output
        Pause counter value is invalid
         on client port
        "
	::= { pm1001pcMondwRmonPauseFrameCntEntry 3 }


pm1001pcMondwRmonPauseFrameCntOverloadPortn OBJECT-TYPE
	SYNTAX  EkiOnOff
	MAX-ACCESS read-only
	STATUS current
	DESCRIPTION
        "
        Output Pause Counter Overload
         :This OID when set indicates an
        output Pause counter overload on
        client port
        "
	::= { pm1001pcMondwRmonPauseFrameCntEntry 4 }


--- *********************************************************
---     TABLE for the pm1001pcMondwRmonTimerCnt articles
--- *********************************************************

pm1001pcMondwRmonTimerCntTable OBJECT-TYPE
	SYNTAX  SEQUENCE OF Pm1001pcMondwRmonTimerCntEntry
	MAX-ACCESS not-accessible
	STATUS current
	DESCRIPTION
        "
        List of pm1001pcMondwRmonTimerCnt
        Article
        "
	::= { pm1001pcRmonClient 160 }


pm1001pcMondwRmonTimerCntEntry OBJECT-TYPE
	SYNTAX Pm1001pcMondwRmonTimerCntEntry
	MAX-ACCESS not-accessible
	STATUS current
	DESCRIPTION
        "
        Row definition for the pm1001pcMondwRmonTimerCnt
        table
        "
	INDEX   { pm1001pcMondwRmonTimerCntIndex }
	::= { pm1001pcMondwRmonTimerCntTable 1 }


Pm1001pcMondwRmonTimerCntEntry ::=
	SEQUENCE {
	pm1001pcMondwRmonTimerCntIndex
		INTEGER,
	pm1001pcMondwRmonTimerCntValuePortn
		Counter64,
	pm1001pcMondwRmonTimerCntErrorPortn
		EkiOnOff,
	pm1001pcMondwRmonTimerCntOverloadPortn
		EkiOnOff
	}


pm1001pcMondwRmonTimerCntIndex OBJECT-TYPE
	SYNTAX  INTEGER(0..128)
	MAX-ACCESS  read-only
	STATUS current
	DESCRIPTION
        "
        Index definition for the pm1001pcMondwRmonTimerCnt
        table
        "
	::= { pm1001pcMondwRmonTimerCntEntry 1 }


pm1001pcMondwRmonTimerCntValuePortn OBJECT-TYPE
	SYNTAX  Counter64
	MAX-ACCESS read-only
	STATUS current
	DESCRIPTION
        "
        RMON Timer On Client Output :This
        is the timing counter dedicated
        to the downstream RMON counters.
        It is incremented every 125 us.
        "
	::= { pm1001pcMondwRmonTimerCntEntry 2 }


pm1001pcMondwRmonTimerCntErrorPortn OBJECT-TYPE
	SYNTAX  EkiOnOff
	MAX-ACCESS read-only
	STATUS current
	DESCRIPTION
        "
        Output RMON Timer Error :This
         OID when set indicates the output
        RMON timer is invalid on client
        port
        "
	::= { pm1001pcMondwRmonTimerCntEntry 3 }


pm1001pcMondwRmonTimerCntOverloadPortn OBJECT-TYPE
	SYNTAX  EkiOnOff
	MAX-ACCESS read-only
	STATUS current
	DESCRIPTION
        "
        Output RMON Timer Overload :This
        OID when set indicates an output
        RMON timer overload on client port
        "
	::= { pm1001pcMondwRmonTimerCntEntry 4 }


--- *********************************************************
---     TABLE for the pm1001pcMondwRmonBitsCnt articles
--- *********************************************************

pm1001pcMondwRmonBitsCntTable OBJECT-TYPE
	SYNTAX  SEQUENCE OF Pm1001pcMondwRmonBitsCntEntry
	MAX-ACCESS not-accessible
	STATUS current
	DESCRIPTION
        "
        List of pm1001pcMondwRmonBitsCnt
        Article
        "
	::= { pm1001pcRmonClient 168 }


pm1001pcMondwRmonBitsCntEntry OBJECT-TYPE
	SYNTAX Pm1001pcMondwRmonBitsCntEntry
	MAX-ACCESS not-accessible
	STATUS current
	DESCRIPTION
        "
        Row definition for the pm1001pcMondwRmonBitsCnt
        table
        "
	INDEX   { pm1001pcMondwRmonBitsCntIndex }
	::= { pm1001pcMondwRmonBitsCntTable 1 }


Pm1001pcMondwRmonBitsCntEntry ::=
	SEQUENCE {
	pm1001pcMondwRmonBitsCntIndex
		INTEGER,
	pm1001pcMondwRmonBitsCntValuePortn
		Counter64,
	pm1001pcMondwRmonBitsCntErrorPortn
		EkiOnOff,
	pm1001pcMondwRmonBitsCntOverloadPortn
		EkiOnOff
	}


pm1001pcMondwRmonBitsCntIndex OBJECT-TYPE
	SYNTAX  INTEGER(0..128)
	MAX-ACCESS  read-only
	STATUS current
	DESCRIPTION
        "
        Index definition for the pm1001pcMondwRmonBitsCnt
        table
        "
	::= { pm1001pcMondwRmonBitsCntEntry 1 }


pm1001pcMondwRmonBitsCntValuePortn OBJECT-TYPE
	SYNTAX  Counter64
	MAX-ACCESS read-only
	STATUS current
	DESCRIPTION
        "
        Client Output Bits :This counter
        is increased each time a bit is
        received on the Output client port
        "
	::= { pm1001pcMondwRmonBitsCntEntry 2 }


pm1001pcMondwRmonBitsCntErrorPortn OBJECT-TYPE
	SYNTAX  EkiOnOff
	MAX-ACCESS read-only
	STATUS current
	DESCRIPTION
        "
        Output Bits Counter Error :This
        OID when set indicates the output
        Bits counter value is invalid on
        client port
        "
	::= { pm1001pcMondwRmonBitsCntEntry 3 }


pm1001pcMondwRmonBitsCntOverloadPortn OBJECT-TYPE
	SYNTAX  EkiOnOff
	MAX-ACCESS read-only
	STATUS current
	DESCRIPTION
        "
        Output Bits Counter Overload :This
        OID when set indicates an output
        Bits counter overload on client
        port
        "
	::= { pm1001pcMondwRmonBitsCntEntry 4 }


--- *********************************************************
---     TABLE for the pm1001pcMonupRmonByteCntS articles
--- *********************************************************

pm1001pcMonupRmonByteCntSTable OBJECT-TYPE
	SYNTAX  SEQUENCE OF Pm1001pcMonupRmonByteCntSEntry
	MAX-ACCESS not-accessible
	STATUS current
	DESCRIPTION
        "
        List of pm1001pcMonupRmonByteCntS
        Article
        "
	::= { pm1001pcRmonClient 1024 }


pm1001pcMonupRmonByteCntSEntry OBJECT-TYPE
	SYNTAX Pm1001pcMonupRmonByteCntSEntry
	MAX-ACCESS not-accessible
	STATUS current
	DESCRIPTION
        "
        Row definition for the pm1001pcMonupRmonByteCntS
        table
        "
	INDEX   { pm1001pcMonupRmonByteCntSIndex }
	::= { pm1001pcMonupRmonByteCntSTable 1 }


Pm1001pcMonupRmonByteCntSEntry ::=
	SEQUENCE {
	pm1001pcMonupRmonByteCntSIndex
		INTEGER,
	pm1001pcMonupRmonByteCntSValuePortn
		Counter64,
	pm1001pcMonupRmonByteCntSErrorPortn
		EkiOnOff,
	pm1001pcMonupRmonByteCntSOverloadPortn
		EkiOnOff
	}


pm1001pcMonupRmonByteCntSIndex OBJECT-TYPE
	SYNTAX  INTEGER(0..128)
	MAX-ACCESS  read-only
	STATUS current
	DESCRIPTION
        "
        Index definition for the pm1001pcMonupRmonByteCntS
        table
        "
	::= { pm1001pcMonupRmonByteCntSEntry 1 }


pm1001pcMonupRmonByteCntSValuePortn OBJECT-TYPE
	SYNTAX  Counter64
	MAX-ACCESS read-only
	STATUS current
	DESCRIPTION
        "
        Client Input Bytes Rate (/s) :This
        rate indicates the number of bytes
        per second that are received on
        the client port
        "
	::= { pm1001pcMonupRmonByteCntSEntry 2 }


pm1001pcMonupRmonByteCntSErrorPortn OBJECT-TYPE
	SYNTAX  EkiOnOff
	MAX-ACCESS read-only
	STATUS current
	DESCRIPTION
        "
        Input Bytes rate error :This OID
        when set indicates the input Bytes
        rate value is invalid on client
        port
        "
	::= { pm1001pcMonupRmonByteCntSEntry 3 }


pm1001pcMonupRmonByteCntSOverloadPortn OBJECT-TYPE
	SYNTAX  EkiOnOff
	MAX-ACCESS read-only
	STATUS current
	DESCRIPTION
        "
        Input Bytes rate overload :This
        OID when set indicates an input
        Bytes rate overload on client port
        "
	::= { pm1001pcMonupRmonByteCntSEntry 4 }


--- *********************************************************
---     TABLE for the pm1001pcMonupRmonCrcErrorCntS articles
--- *********************************************************

pm1001pcMonupRmonCrcErrorCntSTable OBJECT-TYPE
	SYNTAX  SEQUENCE OF Pm1001pcMonupRmonCrcErrorCntSEntry
	MAX-ACCESS not-accessible
	STATUS current
	DESCRIPTION
        "
        List of pm1001pcMonupRmonCrcErrorCntS
        Article
        "
	::= { pm1001pcRmonClient 1032 }


pm1001pcMonupRmonCrcErrorCntSEntry OBJECT-TYPE
	SYNTAX Pm1001pcMonupRmonCrcErrorCntSEntry
	MAX-ACCESS not-accessible
	STATUS current
	DESCRIPTION
        "
        Row definition for the pm1001pcMonupRmonCrcErrorCntS
        table
        "
	INDEX   { pm1001pcMonupRmonCrcErrorCntSIndex }
	::= { pm1001pcMonupRmonCrcErrorCntSTable 1 }


Pm1001pcMonupRmonCrcErrorCntSEntry ::=
	SEQUENCE {
	pm1001pcMonupRmonCrcErrorCntSIndex
		INTEGER,
	pm1001pcMonupRmonCrcErrorCntSValuePortn
		Counter64,
	pm1001pcMonupRmonCrcErrorCntSErrorPortn
		EkiOnOff,
	pm1001pcMonupRmonCrcErrorCntSOverloadPortn
		EkiOnOff
	}


pm1001pcMonupRmonCrcErrorCntSIndex OBJECT-TYPE
	SYNTAX  INTEGER(0..128)
	MAX-ACCESS  read-only
	STATUS current
	DESCRIPTION
        "
        Index definition for the pm1001pcMonupRmonCrcErrorCntS
        table
        "
	::= { pm1001pcMonupRmonCrcErrorCntSEntry 1 }


pm1001pcMonupRmonCrcErrorCntSValuePortn OBJECT-TYPE
	SYNTAX  Counter64
	MAX-ACCESS read-only
	STATUS current
	DESCRIPTION
        "
        Client Input CRC Errors Rate (/s)
        :This rate indicates the number
        of CRC errors per second that are
        detected on the input client port
        "
	::= { pm1001pcMonupRmonCrcErrorCntSEntry 2 }


pm1001pcMonupRmonCrcErrorCntSErrorPortn OBJECT-TYPE
	SYNTAX  EkiOnOff
	MAX-ACCESS read-only
	STATUS current
	DESCRIPTION
        "
        Input CRC Errors rate error :This
        OID when set indicates the input
        CRC Errors rate value is invalid
        on client port
        "
	::= { pm1001pcMonupRmonCrcErrorCntSEntry 3 }


pm1001pcMonupRmonCrcErrorCntSOverloadPortn OBJECT-TYPE
	SYNTAX  EkiOnOff
	MAX-ACCESS read-only
	STATUS current
	DESCRIPTION
        "
        Input CRC Errors rate overload
        :This OID when set indicates an
        input CRC Errors rate overload
         on client port
        "
	::= { pm1001pcMonupRmonCrcErrorCntSEntry 4 }


--- *********************************************************
---     TABLE for the pm1001pcMonupRmonPacketsCntS articles
--- *********************************************************

pm1001pcMonupRmonPacketsCntSTable OBJECT-TYPE
	SYNTAX  SEQUENCE OF Pm1001pcMonupRmonPacketsCntSEntry
	MAX-ACCESS not-accessible
	STATUS current
	DESCRIPTION
        "
        List of pm1001pcMonupRmonPacketsCntS
        Article
        "
	::= { pm1001pcRmonClient 1040 }


pm1001pcMonupRmonPacketsCntSEntry OBJECT-TYPE
	SYNTAX Pm1001pcMonupRmonPacketsCntSEntry
	MAX-ACCESS not-accessible
	STATUS current
	DESCRIPTION
        "
        Row definition for the pm1001pcMonupRmonPacketsCntS
        table
        "
	INDEX   { pm1001pcMonupRmonPacketsCntSIndex }
	::= { pm1001pcMonupRmonPacketsCntSTable 1 }


Pm1001pcMonupRmonPacketsCntSEntry ::=
	SEQUENCE {
	pm1001pcMonupRmonPacketsCntSIndex
		INTEGER,
	pm1001pcMonupRmonPacketsCntSValuePortn
		Counter64,
	pm1001pcMonupRmonPacketsCntSErrorPortn
		EkiOnOff,
	pm1001pcMonupRmonPacketsCntSOverloadPortn
		EkiOnOff
	}


pm1001pcMonupRmonPacketsCntSIndex OBJECT-TYPE
	SYNTAX  INTEGER(0..128)
	MAX-ACCESS  read-only
	STATUS current
	DESCRIPTION
        "
        Index definition for the pm1001pcMonupRmonPacketsCntS
        table
        "
	::= { pm1001pcMonupRmonPacketsCntSEntry 1 }


pm1001pcMonupRmonPacketsCntSValuePortn OBJECT-TYPE
	SYNTAX  Counter64
	MAX-ACCESS read-only
	STATUS current
	DESCRIPTION
        "
        Client Input Packets Rate (/s)
        :This rate indicates the number
        of packets per second that are
         received on the client port
        "
	::= { pm1001pcMonupRmonPacketsCntSEntry 2 }


pm1001pcMonupRmonPacketsCntSErrorPortn OBJECT-TYPE
	SYNTAX  EkiOnOff
	MAX-ACCESS read-only
	STATUS current
	DESCRIPTION
        "
        Input Packets rate error :This
        OID when set indicates the input
        Packets rate value is invalid on
        client port
        "
	::= { pm1001pcMonupRmonPacketsCntSEntry 3 }


pm1001pcMonupRmonPacketsCntSOverloadPortn OBJECT-TYPE
	SYNTAX  EkiOnOff
	MAX-ACCESS read-only
	STATUS current
	DESCRIPTION
        "
        Input Packets rate overload :This
        OID when set indicates an input
        Packets rate overload on client
        port
        "
	::= { pm1001pcMonupRmonPacketsCntSEntry 4 }


--- *********************************************************
---     TABLE for the pm1001pcMonupRmonBroadcastCntS articles
--- *********************************************************

pm1001pcMonupRmonBroadcastCntSTable OBJECT-TYPE
	SYNTAX  SEQUENCE OF Pm1001pcMonupRmonBroadcastCntSEntry
	MAX-ACCESS not-accessible
	STATUS current
	DESCRIPTION
        "
        List of pm1001pcMonupRmonBroadcastCntS
        Article
        "
	::= { pm1001pcRmonClient 1048 }


pm1001pcMonupRmonBroadcastCntSEntry OBJECT-TYPE
	SYNTAX Pm1001pcMonupRmonBroadcastCntSEntry
	MAX-ACCESS not-accessible
	STATUS current
	DESCRIPTION
        "
        Row definition for the pm1001pcMonupRmonBroadcastCntS
        table
        "
	INDEX   { pm1001pcMonupRmonBroadcastCntSIndex }
	::= { pm1001pcMonupRmonBroadcastCntSTable 1 }


Pm1001pcMonupRmonBroadcastCntSEntry ::=
	SEQUENCE {
	pm1001pcMonupRmonBroadcastCntSIndex
		INTEGER,
	pm1001pcMonupRmonBroadcastCntSValuePortn
		Counter64,
	pm1001pcMonupRmonBroadcastCntSErrorPortn
		EkiOnOff,
	pm1001pcMonupRmonBroadcastCntSOverloadPortn
		EkiOnOff
	}


pm1001pcMonupRmonBroadcastCntSIndex OBJECT-TYPE
	SYNTAX  INTEGER(0..128)
	MAX-ACCESS  read-only
	STATUS current
	DESCRIPTION
        "
        Index definition for the pm1001pcMonupRmonBroadcastCntS
        table
        "
	::= { pm1001pcMonupRmonBroadcastCntSEntry 1 }


pm1001pcMonupRmonBroadcastCntSValuePortn OBJECT-TYPE
	SYNTAX  Counter64
	MAX-ACCESS read-only
	STATUS current
	DESCRIPTION
        "
        Client Input Broadcast Packets
        Rate (/s) :This rate indicates
         the number of broadcast packets
        per second that are received on
        the client port
        "
	::= { pm1001pcMonupRmonBroadcastCntSEntry 2 }


pm1001pcMonupRmonBroadcastCntSErrorPortn OBJECT-TYPE
	SYNTAX  EkiOnOff
	MAX-ACCESS read-only
	STATUS current
	DESCRIPTION
        "
        Input Broadcast rate error :This
        OID when set indicates the input
        Broadcast rate value is invalid
        on client port
        "
	::= { pm1001pcMonupRmonBroadcastCntSEntry 3 }


pm1001pcMonupRmonBroadcastCntSOverloadPortn OBJECT-TYPE
	SYNTAX  EkiOnOff
	MAX-ACCESS read-only
	STATUS current
	DESCRIPTION
        "
        Input Broadcast rate overload
         :This OID when set indicates an
        input Broadcast rate overload on
        client port
        "
	::= { pm1001pcMonupRmonBroadcastCntSEntry 4 }


--- *********************************************************
---     TABLE for the pm1001pcMonupRmonMulticastCntS articles
--- *********************************************************

pm1001pcMonupRmonMulticastCntSTable OBJECT-TYPE
	SYNTAX  SEQUENCE OF Pm1001pcMonupRmonMulticastCntSEntry
	MAX-ACCESS not-accessible
	STATUS current
	DESCRIPTION
        "
        List of pm1001pcMonupRmonMulticastCntS
        Article
        "
	::= { pm1001pcRmonClient 1056 }


pm1001pcMonupRmonMulticastCntSEntry OBJECT-TYPE
	SYNTAX Pm1001pcMonupRmonMulticastCntSEntry
	MAX-ACCESS not-accessible
	STATUS current
	DESCRIPTION
        "
        Row definition for the pm1001pcMonupRmonMulticastCntS
        table
        "
	INDEX   { pm1001pcMonupRmonMulticastCntSIndex }
	::= { pm1001pcMonupRmonMulticastCntSTable 1 }


Pm1001pcMonupRmonMulticastCntSEntry ::=
	SEQUENCE {
	pm1001pcMonupRmonMulticastCntSIndex
		INTEGER,
	pm1001pcMonupRmonMulticastCntSValuePortn
		Counter64,
	pm1001pcMonupRmonMulticastCntSErrorPortn
		EkiOnOff,
	pm1001pcMonupRmonMulticastCntSOverloadPortn
		EkiOnOff
	}


pm1001pcMonupRmonMulticastCntSIndex OBJECT-TYPE
	SYNTAX  INTEGER(0..128)
	MAX-ACCESS  read-only
	STATUS current
	DESCRIPTION
        "
        Index definition for the pm1001pcMonupRmonMulticastCntS
        table
        "
	::= { pm1001pcMonupRmonMulticastCntSEntry 1 }


pm1001pcMonupRmonMulticastCntSValuePortn OBJECT-TYPE
	SYNTAX  Counter64
	MAX-ACCESS read-only
	STATUS current
	DESCRIPTION
        "
        Client Input Multicast Packets
        Rate (/s) :This rate indicates
         the number of multicast packets
        per second that are received on
        the client port
        "
	::= { pm1001pcMonupRmonMulticastCntSEntry 2 }


pm1001pcMonupRmonMulticastCntSErrorPortn OBJECT-TYPE
	SYNTAX  EkiOnOff
	MAX-ACCESS read-only
	STATUS current
	DESCRIPTION
        "
        Input Multicast rate error :This
        OID when set indicates the input
        Multicast rate value is invalid
        on client port
        "
	::= { pm1001pcMonupRmonMulticastCntSEntry 3 }


pm1001pcMonupRmonMulticastCntSOverloadPortn OBJECT-TYPE
	SYNTAX  EkiOnOff
	MAX-ACCESS read-only
	STATUS current
	DESCRIPTION
        "
        Input Multicast rate overload
         :This OID when set indicates an
        input Multicast rate overload on
        client port
        "
	::= { pm1001pcMonupRmonMulticastCntSEntry 4 }


--- *********************************************************
---     TABLE for the pm1001pcMonupRmonPauseFrameCntS articles
--- *********************************************************

pm1001pcMonupRmonPauseFrameCntSTable OBJECT-TYPE
	SYNTAX  SEQUENCE OF Pm1001pcMonupRmonPauseFrameCntSEntry
	MAX-ACCESS not-accessible
	STATUS current
	DESCRIPTION
        "
        List of pm1001pcMonupRmonPauseFrameCntS
        Article
        "
	::= { pm1001pcRmonClient 1072 }


pm1001pcMonupRmonPauseFrameCntSEntry OBJECT-TYPE
	SYNTAX Pm1001pcMonupRmonPauseFrameCntSEntry
	MAX-ACCESS not-accessible
	STATUS current
	DESCRIPTION
        "
        Row definition for the pm1001pcMonupRmonPauseFrameCntS
        table
        "
	INDEX   { pm1001pcMonupRmonPauseFrameCntSIndex }
	::= { pm1001pcMonupRmonPauseFrameCntSTable 1 }


Pm1001pcMonupRmonPauseFrameCntSEntry ::=
	SEQUENCE {
	pm1001pcMonupRmonPauseFrameCntSIndex
		INTEGER,
	pm1001pcMonupRmonPauseFrameCntSValuePortn
		Counter64,
	pm1001pcMonupRmonPauseFrameCntSErrorPortn
		EkiOnOff,
	pm1001pcMonupRmonPauseFrameCntSOverloadPortn
		EkiOnOff
	}


pm1001pcMonupRmonPauseFrameCntSIndex OBJECT-TYPE
	SYNTAX  INTEGER(0..128)
	MAX-ACCESS  read-only
	STATUS current
	DESCRIPTION
        "
        Index definition for the pm1001pcMonupRmonPauseFrameCntS
        table
        "
	::= { pm1001pcMonupRmonPauseFrameCntSEntry 1 }


pm1001pcMonupRmonPauseFrameCntSValuePortn OBJECT-TYPE
	SYNTAX  Counter64
	MAX-ACCESS read-only
	STATUS current
	DESCRIPTION
        "
        Client Input Pause Frames Rate
        (/s) :This rate indicates the number
        of Pause frames per second that
        are received on the client port
        "
	::= { pm1001pcMonupRmonPauseFrameCntSEntry 2 }


pm1001pcMonupRmonPauseFrameCntSErrorPortn OBJECT-TYPE
	SYNTAX  EkiOnOff
	MAX-ACCESS read-only
	STATUS current
	DESCRIPTION
        "
        Input Pause rate error :This OID
        when set indicates the input Pause
        rate value is invalid on client
        port
        "
	::= { pm1001pcMonupRmonPauseFrameCntSEntry 3 }


pm1001pcMonupRmonPauseFrameCntSOverloadPortn OBJECT-TYPE
	SYNTAX  EkiOnOff
	MAX-ACCESS read-only
	STATUS current
	DESCRIPTION
        "
        Input Pause rate overload :This
        OID when set indicates an input
        Pause rate overload on client port
        "
	::= { pm1001pcMonupRmonPauseFrameCntSEntry 4 }


--- *********************************************************
---     TABLE for the pm1001pcMonupRmonDropFrameCntS articles
--- *********************************************************

pm1001pcMonupRmonDropFrameCntSTable OBJECT-TYPE
	SYNTAX  SEQUENCE OF Pm1001pcMonupRmonDropFrameCntSEntry
	MAX-ACCESS not-accessible
	STATUS current
	DESCRIPTION
        "
        List of pm1001pcMonupRmonDropFrameCntS
        Article
        "
	::= { pm1001pcRmonClient 1080 }


pm1001pcMonupRmonDropFrameCntSEntry OBJECT-TYPE
	SYNTAX Pm1001pcMonupRmonDropFrameCntSEntry
	MAX-ACCESS not-accessible
	STATUS current
	DESCRIPTION
        "
        Row definition for the pm1001pcMonupRmonDropFrameCntS
        table
        "
	INDEX   { pm1001pcMonupRmonDropFrameCntSIndex }
	::= { pm1001pcMonupRmonDropFrameCntSTable 1 }


Pm1001pcMonupRmonDropFrameCntSEntry ::=
	SEQUENCE {
	pm1001pcMonupRmonDropFrameCntSIndex
		INTEGER,
	pm1001pcMonupRmonDropFrameCntSValuePortn
		Counter64,
	pm1001pcMonupRmonDropFrameCntSErrorPortn
		EkiOnOff,
	pm1001pcMonupRmonDropFrameCntSOverloadPortn
		EkiOnOff
	}


pm1001pcMonupRmonDropFrameCntSIndex OBJECT-TYPE
	SYNTAX  INTEGER(0..128)
	MAX-ACCESS  read-only
	STATUS current
	DESCRIPTION
        "
        Index definition for the pm1001pcMonupRmonDropFrameCntS
        table
        "
	::= { pm1001pcMonupRmonDropFrameCntSEntry 1 }


pm1001pcMonupRmonDropFrameCntSValuePortn OBJECT-TYPE
	SYNTAX  Counter64
	MAX-ACCESS read-only
	STATUS current
	DESCRIPTION
        "
        Client Input Drop Packets Rate
        (/s) :This rate indicates the number
        packets per second that are received
        on the input client port
        "
	::= { pm1001pcMonupRmonDropFrameCntSEntry 2 }


pm1001pcMonupRmonDropFrameCntSErrorPortn OBJECT-TYPE
	SYNTAX  EkiOnOff
	MAX-ACCESS read-only
	STATUS current
	DESCRIPTION
        "
        Input Drop rate error :This OID
        when set indicates the input Drop
        rate value is invalid on client
        port
        "
	::= { pm1001pcMonupRmonDropFrameCntSEntry 3 }


pm1001pcMonupRmonDropFrameCntSOverloadPortn OBJECT-TYPE
	SYNTAX  EkiOnOff
	MAX-ACCESS read-only
	STATUS current
	DESCRIPTION
        "
        Input Drop rate overload :This
        OID when set indicates an input
        Drop rate overload on client port
        "
	::= { pm1001pcMonupRmonDropFrameCntSEntry 4 }


--- *********************************************************
---     TABLE for the pm1001pcMonupRmonBitsCntS articles
--- *********************************************************

pm1001pcMonupRmonBitsCntSTable OBJECT-TYPE
	SYNTAX  SEQUENCE OF Pm1001pcMonupRmonBitsCntSEntry
	MAX-ACCESS not-accessible
	STATUS current
	DESCRIPTION
        "
        List of pm1001pcMonupRmonBitsCntS
        Article
        "
	::= { pm1001pcRmonClient 1088 }


pm1001pcMonupRmonBitsCntSEntry OBJECT-TYPE
	SYNTAX Pm1001pcMonupRmonBitsCntSEntry
	MAX-ACCESS not-accessible
	STATUS current
	DESCRIPTION
        "
        Row definition for the pm1001pcMonupRmonBitsCntS
        table
        "
	INDEX   { pm1001pcMonupRmonBitsCntSIndex }
	::= { pm1001pcMonupRmonBitsCntSTable 1 }


Pm1001pcMonupRmonBitsCntSEntry ::=
	SEQUENCE {
	pm1001pcMonupRmonBitsCntSIndex
		INTEGER,
	pm1001pcMonupRmonBitsCntSValuePortn
		Counter64,
	pm1001pcMonupRmonBitsCntSErrorPortn
		EkiOnOff,
	pm1001pcMonupRmonBitsCntSOverloadPortn
		EkiOnOff
	}


pm1001pcMonupRmonBitsCntSIndex OBJECT-TYPE
	SYNTAX  INTEGER(0..128)
	MAX-ACCESS  read-only
	STATUS current
	DESCRIPTION
        "
        Index definition for the pm1001pcMonupRmonBitsCntS
        table
        "
	::= { pm1001pcMonupRmonBitsCntSEntry 1 }


pm1001pcMonupRmonBitsCntSValuePortn OBJECT-TYPE
	SYNTAX  Counter64
	MAX-ACCESS read-only
	STATUS current
	DESCRIPTION
        "
        Client Input Bits Rate (/s) :This
        rate indicates the number of bits
        per second that are received on
        the input client port
        "
	::= { pm1001pcMonupRmonBitsCntSEntry 2 }


pm1001pcMonupRmonBitsCntSErrorPortn OBJECT-TYPE
	SYNTAX  EkiOnOff
	MAX-ACCESS read-only
	STATUS current
	DESCRIPTION
        "
        Input Bits rate error :This OID
        when set indicates the input Bits
        rate value is invalid on client
        port
        "
	::= { pm1001pcMonupRmonBitsCntSEntry 3 }


pm1001pcMonupRmonBitsCntSOverloadPortn OBJECT-TYPE
	SYNTAX  EkiOnOff
	MAX-ACCESS read-only
	STATUS current
	DESCRIPTION
        "
        Input Bits rate overload :This
        OID when set indicates an input
        Bits rate overload on client port
        "
	::= { pm1001pcMonupRmonBitsCntSEntry 4 }


--- *********************************************************
---     TABLE for the pm1001pcMondwRmonByteCntS articles
--- *********************************************************

pm1001pcMondwRmonByteCntSTable OBJECT-TYPE
	SYNTAX  SEQUENCE OF Pm1001pcMondwRmonByteCntSEntry
	MAX-ACCESS not-accessible
	STATUS current
	DESCRIPTION
        "
        List of pm1001pcMondwRmonByteCntS
        Article
        "
	::= { pm1001pcRmonClient 1120 }


pm1001pcMondwRmonByteCntSEntry OBJECT-TYPE
	SYNTAX Pm1001pcMondwRmonByteCntSEntry
	MAX-ACCESS not-accessible
	STATUS current
	DESCRIPTION
        "
        Row definition for the pm1001pcMondwRmonByteCntS
        table
        "
	INDEX   { pm1001pcMondwRmonByteCntSIndex }
	::= { pm1001pcMondwRmonByteCntSTable 1 }


Pm1001pcMondwRmonByteCntSEntry ::=
	SEQUENCE {
	pm1001pcMondwRmonByteCntSIndex
		INTEGER,
	pm1001pcMondwRmonByteCntSValuePortn
		Counter64,
	pm1001pcMondwRmonByteCntSErrorPortn
		EkiOnOff,
	pm1001pcMondwRmonByteCntSOverloadPortn
		EkiOnOff
	}


pm1001pcMondwRmonByteCntSIndex OBJECT-TYPE
	SYNTAX  INTEGER(0..128)
	MAX-ACCESS  read-only
	STATUS current
	DESCRIPTION
        "
        Index definition for the pm1001pcMondwRmonByteCntS
        table
        "
	::= { pm1001pcMondwRmonByteCntSEntry 1 }


pm1001pcMondwRmonByteCntSValuePortn OBJECT-TYPE
	SYNTAX  Counter64
	MAX-ACCESS read-only
	STATUS current
	DESCRIPTION
        "
        Client Output Bytes Rate (/s)
         :This rate indicates the number
        of bytes per second that are transmitted
        on the client port
        "
	::= { pm1001pcMondwRmonByteCntSEntry 2 }


pm1001pcMondwRmonByteCntSErrorPortn OBJECT-TYPE
	SYNTAX  EkiOnOff
	MAX-ACCESS read-only
	STATUS current
	DESCRIPTION
        "
        Output Bytes rate error :This
         OID when set indicates the output
        Bytes rate value is invalid on
         client port
        "
	::= { pm1001pcMondwRmonByteCntSEntry 3 }


pm1001pcMondwRmonByteCntSOverloadPortn OBJECT-TYPE
	SYNTAX  EkiOnOff
	MAX-ACCESS read-only
	STATUS current
	DESCRIPTION
        "
        Output Bytes rate overload :This
        OID when set indicates an output
        Bytes rate overload on client port
        "
	::= { pm1001pcMondwRmonByteCntSEntry 4 }


--- *********************************************************
---     TABLE for the pm1001pcMondwRmonCrcErrorCntS articles
--- *********************************************************

pm1001pcMondwRmonCrcErrorCntSTable OBJECT-TYPE
	SYNTAX  SEQUENCE OF Pm1001pcMondwRmonCrcErrorCntSEntry
	MAX-ACCESS not-accessible
	STATUS current
	DESCRIPTION
        "
        List of pm1001pcMondwRmonCrcErrorCntS
        Article
        "
	::= { pm1001pcRmonClient 1128 }


pm1001pcMondwRmonCrcErrorCntSEntry OBJECT-TYPE
	SYNTAX Pm1001pcMondwRmonCrcErrorCntSEntry
	MAX-ACCESS not-accessible
	STATUS current
	DESCRIPTION
        "
        Row definition for the pm1001pcMondwRmonCrcErrorCntS
        table
        "
	INDEX   { pm1001pcMondwRmonCrcErrorCntSIndex }
	::= { pm1001pcMondwRmonCrcErrorCntSTable 1 }


Pm1001pcMondwRmonCrcErrorCntSEntry ::=
	SEQUENCE {
	pm1001pcMondwRmonCrcErrorCntSIndex
		INTEGER,
	pm1001pcMondwRmonCrcErrorCntSValuePortn
		Counter64,
	pm1001pcMondwRmonCrcErrorCntSErrorPortn
		EkiOnOff,
	pm1001pcMondwRmonCrcErrorCntSOverloadPortn
		EkiOnOff
	}


pm1001pcMondwRmonCrcErrorCntSIndex OBJECT-TYPE
	SYNTAX  INTEGER(0..128)
	MAX-ACCESS  read-only
	STATUS current
	DESCRIPTION
        "
        Index definition for the pm1001pcMondwRmonCrcErrorCntS
        table
        "
	::= { pm1001pcMondwRmonCrcErrorCntSEntry 1 }


pm1001pcMondwRmonCrcErrorCntSValuePortn OBJECT-TYPE
	SYNTAX  Counter64
	MAX-ACCESS read-only
	STATUS current
	DESCRIPTION
        "
        Client Output CRC Errors Rate
         (/s) :This rate indicates the
         number of CRC errors per second
        that are detected on the output
        client port
        "
	::= { pm1001pcMondwRmonCrcErrorCntSEntry 2 }


pm1001pcMondwRmonCrcErrorCntSErrorPortn OBJECT-TYPE
	SYNTAX  EkiOnOff
	MAX-ACCESS read-only
	STATUS current
	DESCRIPTION
        "
        Output CRC Errors rate error :This
        OID when set indicates the output
        CRC Errors rate value is invalid
        on client port
        "
	::= { pm1001pcMondwRmonCrcErrorCntSEntry 3 }


pm1001pcMondwRmonCrcErrorCntSOverloadPortn OBJECT-TYPE
	SYNTAX  EkiOnOff
	MAX-ACCESS read-only
	STATUS current
	DESCRIPTION
        "
        Output CRC Errors rate overload
        :This OID when set indicates an
        output CRC Errors rate overload
        on client port
        "
	::= { pm1001pcMondwRmonCrcErrorCntSEntry 4 }


--- *********************************************************
---     TABLE for the pm1001pcMondwRmonPacketsCntS articles
--- *********************************************************

pm1001pcMondwRmonPacketsCntSTable OBJECT-TYPE
	SYNTAX  SEQUENCE OF Pm1001pcMondwRmonPacketsCntSEntry
	MAX-ACCESS not-accessible
	STATUS current
	DESCRIPTION
        "
        List of pm1001pcMondwRmonPacketsCntS
        Article
        "
	::= { pm1001pcRmonClient 1136 }


pm1001pcMondwRmonPacketsCntSEntry OBJECT-TYPE
	SYNTAX Pm1001pcMondwRmonPacketsCntSEntry
	MAX-ACCESS not-accessible
	STATUS current
	DESCRIPTION
        "
        Row definition for the pm1001pcMondwRmonPacketsCntS
        table
        "
	INDEX   { pm1001pcMondwRmonPacketsCntSIndex }
	::= { pm1001pcMondwRmonPacketsCntSTable 1 }


Pm1001pcMondwRmonPacketsCntSEntry ::=
	SEQUENCE {
	pm1001pcMondwRmonPacketsCntSIndex
		INTEGER,
	pm1001pcMondwRmonPacketsCntSValuePortn
		Counter64,
	pm1001pcMondwRmonPacketsCntSErrorPortn
		EkiOnOff,
	pm1001pcMondwRmonPacketsCntSOverloadPortn
		EkiOnOff
	}


pm1001pcMondwRmonPacketsCntSIndex OBJECT-TYPE
	SYNTAX  INTEGER(0..128)
	MAX-ACCESS  read-only
	STATUS current
	DESCRIPTION
        "
        Index definition for the pm1001pcMondwRmonPacketsCntS
        table
        "
	::= { pm1001pcMondwRmonPacketsCntSEntry 1 }


pm1001pcMondwRmonPacketsCntSValuePortn OBJECT-TYPE
	SYNTAX  Counter64
	MAX-ACCESS read-only
	STATUS current
	DESCRIPTION
        "
        Client Output Packets Rate (/s)
        :This rate indicates the number
        of packets per second that are
         transmitted on the client port
        "
	::= { pm1001pcMondwRmonPacketsCntSEntry 2 }


pm1001pcMondwRmonPacketsCntSErrorPortn OBJECT-TYPE
	SYNTAX  EkiOnOff
	MAX-ACCESS read-only
	STATUS current
	DESCRIPTION
        "
        Output Packets rate error :This
        OID when set indicates the output
        Packets rate value is invalid on
        client port
        "
	::= { pm1001pcMondwRmonPacketsCntSEntry 3 }


pm1001pcMondwRmonPacketsCntSOverloadPortn OBJECT-TYPE
	SYNTAX  EkiOnOff
	MAX-ACCESS read-only
	STATUS current
	DESCRIPTION
        "
        Output Packets rate overload :This
        OID when set indicates an output
        Packets rate overload on client
        port
        "
	::= { pm1001pcMondwRmonPacketsCntSEntry 4 }


--- *********************************************************
---     TABLE for the pm1001pcMondwRmonBroadcastCntS articles
--- *********************************************************

pm1001pcMondwRmonBroadcastCntSTable OBJECT-TYPE
	SYNTAX  SEQUENCE OF Pm1001pcMondwRmonBroadcastCntSEntry
	MAX-ACCESS not-accessible
	STATUS current
	DESCRIPTION
        "
        List of pm1001pcMondwRmonBroadcastCntS
        Article
        "
	::= { pm1001pcRmonClient 1144 }


pm1001pcMondwRmonBroadcastCntSEntry OBJECT-TYPE
	SYNTAX Pm1001pcMondwRmonBroadcastCntSEntry
	MAX-ACCESS not-accessible
	STATUS current
	DESCRIPTION
        "
        Row definition for the pm1001pcMondwRmonBroadcastCntS
        table
        "
	INDEX   { pm1001pcMondwRmonBroadcastCntSIndex }
	::= { pm1001pcMondwRmonBroadcastCntSTable 1 }


Pm1001pcMondwRmonBroadcastCntSEntry ::=
	SEQUENCE {
	pm1001pcMondwRmonBroadcastCntSIndex
		INTEGER,
	pm1001pcMondwRmonBroadcastCntSValuePortn
		Counter64,
	pm1001pcMondwRmonBroadcastCntSErrorPortn
		EkiOnOff,
	pm1001pcMondwRmonBroadcastCntSOverloadPortn
		EkiOnOff
	}


pm1001pcMondwRmonBroadcastCntSIndex OBJECT-TYPE
	SYNTAX  INTEGER(0..128)
	MAX-ACCESS  read-only
	STATUS current
	DESCRIPTION
        "
        Index definition for the pm1001pcMondwRmonBroadcastCntS
        table
        "
	::= { pm1001pcMondwRmonBroadcastCntSEntry 1 }


pm1001pcMondwRmonBroadcastCntSValuePortn OBJECT-TYPE
	SYNTAX  Counter64
	MAX-ACCESS read-only
	STATUS current
	DESCRIPTION
        "
        Client Output Broadcast Packets
        Rate (/s) :This rate indicates
         the number of broadcast packets
        per second that are transmitted
        on the client port
        "
	::= { pm1001pcMondwRmonBroadcastCntSEntry 2 }


pm1001pcMondwRmonBroadcastCntSErrorPortn OBJECT-TYPE
	SYNTAX  EkiOnOff
	MAX-ACCESS read-only
	STATUS current
	DESCRIPTION
        "
        Output Broadcast rate error :This
        OID when set indicates the output
        Broadcast rate value is invalid
        on client port
        "
	::= { pm1001pcMondwRmonBroadcastCntSEntry 3 }


pm1001pcMondwRmonBroadcastCntSOverloadPortn OBJECT-TYPE
	SYNTAX  EkiOnOff
	MAX-ACCESS read-only
	STATUS current
	DESCRIPTION
        "
        Output Broadcast rate overload
        :This OID when set indicates an
        output Broadcast rate overload
         on client port
        "
	::= { pm1001pcMondwRmonBroadcastCntSEntry 4 }


--- *********************************************************
---     TABLE for the pm1001pcMondwRmonMulticastCntS articles
--- *********************************************************

pm1001pcMondwRmonMulticastCntSTable OBJECT-TYPE
	SYNTAX  SEQUENCE OF Pm1001pcMondwRmonMulticastCntSEntry
	MAX-ACCESS not-accessible
	STATUS current
	DESCRIPTION
        "
        List of pm1001pcMondwRmonMulticastCntS
        Article
        "
	::= { pm1001pcRmonClient 1152 }


pm1001pcMondwRmonMulticastCntSEntry OBJECT-TYPE
	SYNTAX Pm1001pcMondwRmonMulticastCntSEntry
	MAX-ACCESS not-accessible
	STATUS current
	DESCRIPTION
        "
        Row definition for the pm1001pcMondwRmonMulticastCntS
        table
        "
	INDEX   { pm1001pcMondwRmonMulticastCntSIndex }
	::= { pm1001pcMondwRmonMulticastCntSTable 1 }


Pm1001pcMondwRmonMulticastCntSEntry ::=
	SEQUENCE {
	pm1001pcMondwRmonMulticastCntSIndex
		INTEGER,
	pm1001pcMondwRmonMulticastCntSValuePortn
		Counter64,
	pm1001pcMondwRmonMulticastCntSErrorPortn
		EkiOnOff,
	pm1001pcMondwRmonMulticastCntSOverloadPortn
		EkiOnOff
	}


pm1001pcMondwRmonMulticastCntSIndex OBJECT-TYPE
	SYNTAX  INTEGER(0..128)
	MAX-ACCESS  read-only
	STATUS current
	DESCRIPTION
        "
        Index definition for the pm1001pcMondwRmonMulticastCntS
        table
        "
	::= { pm1001pcMondwRmonMulticastCntSEntry 1 }


pm1001pcMondwRmonMulticastCntSValuePortn OBJECT-TYPE
	SYNTAX  Counter64
	MAX-ACCESS read-only
	STATUS current
	DESCRIPTION
        "
        Client Output Multicast Packets
        Rate (/s) :This rate indicates
         the number of multicast packets
        per second that are transmitted
        on the client port
        "
	::= { pm1001pcMondwRmonMulticastCntSEntry 2 }


pm1001pcMondwRmonMulticastCntSErrorPortn OBJECT-TYPE
	SYNTAX  EkiOnOff
	MAX-ACCESS read-only
	STATUS current
	DESCRIPTION
        "
        Output Multicast rate error :This
        OID when set indicates the output
        Multicast rate value is invalid
        on client port
        "
	::= { pm1001pcMondwRmonMulticastCntSEntry 3 }


pm1001pcMondwRmonMulticastCntSOverloadPortn OBJECT-TYPE
	SYNTAX  EkiOnOff
	MAX-ACCESS read-only
	STATUS current
	DESCRIPTION
        "
        Output Multicast rate overload
        :This OID when set indicates an
        output Multicast rate overload
         on client port
        "
	::= { pm1001pcMondwRmonMulticastCntSEntry 4 }


--- *********************************************************
---     TABLE for the pm1001pcMondwRmonPauseFrameCntS articles
--- *********************************************************

pm1001pcMondwRmonPauseFrameCntSTable OBJECT-TYPE
	SYNTAX  SEQUENCE OF Pm1001pcMondwRmonPauseFrameCntSEntry
	MAX-ACCESS not-accessible
	STATUS current
	DESCRIPTION
        "
        List of pm1001pcMondwRmonPauseFrameCntS
        Article
        "
	::= { pm1001pcRmonClient 1160 }


pm1001pcMondwRmonPauseFrameCntSEntry OBJECT-TYPE
	SYNTAX Pm1001pcMondwRmonPauseFrameCntSEntry
	MAX-ACCESS not-accessible
	STATUS current
	DESCRIPTION
        "
        Row definition for the pm1001pcMondwRmonPauseFrameCntS
        table
        "
	INDEX   { pm1001pcMondwRmonPauseFrameCntSIndex }
	::= { pm1001pcMondwRmonPauseFrameCntSTable 1 }


Pm1001pcMondwRmonPauseFrameCntSEntry ::=
	SEQUENCE {
	pm1001pcMondwRmonPauseFrameCntSIndex
		INTEGER,
	pm1001pcMondwRmonPauseFrameCntSValuePortn
		Counter64,
	pm1001pcMondwRmonPauseFrameCntSErrorPortn
		EkiOnOff,
	pm1001pcMondwRmonPauseFrameCntSOverloadPortn
		EkiOnOff
	}


pm1001pcMondwRmonPauseFrameCntSIndex OBJECT-TYPE
	SYNTAX  INTEGER(0..128)
	MAX-ACCESS  read-only
	STATUS current
	DESCRIPTION
        "
        Index definition for the pm1001pcMondwRmonPauseFrameCntS
        table
        "
	::= { pm1001pcMondwRmonPauseFrameCntSEntry 1 }


pm1001pcMondwRmonPauseFrameCntSValuePortn OBJECT-TYPE
	SYNTAX  Counter64
	MAX-ACCESS read-only
	STATUS current
	DESCRIPTION
        "
        Client Output Pause Frames Rate
        (/s) :This rate indicates the number
        of Pause frames per second that
        are generated by the PM on the
         client port
        "
	::= { pm1001pcMondwRmonPauseFrameCntSEntry 2 }


pm1001pcMondwRmonPauseFrameCntSErrorPortn OBJECT-TYPE
	SYNTAX  EkiOnOff
	MAX-ACCESS read-only
	STATUS current
	DESCRIPTION
        "
        Output Pause rate error :This
         OID when set indicates the output
        Pause rate value is invalid on
         client port
        "
	::= { pm1001pcMondwRmonPauseFrameCntSEntry 3 }


pm1001pcMondwRmonPauseFrameCntSOverloadPortn OBJECT-TYPE
	SYNTAX  EkiOnOff
	MAX-ACCESS read-only
	STATUS current
	DESCRIPTION
        "
        Output Pause rate overload :This
        OID when set indicates an output
        Pause rate overload on client port
        "
	::= { pm1001pcMondwRmonPauseFrameCntSEntry 4 }


--- *********************************************************
---     TABLE for the pm1001pcMondwRmonBitsCntS articles
--- *********************************************************

pm1001pcMondwRmonBitsCntSTable OBJECT-TYPE
	SYNTAX  SEQUENCE OF Pm1001pcMondwRmonBitsCntSEntry
	MAX-ACCESS not-accessible
	STATUS current
	DESCRIPTION
        "
        List of pm1001pcMondwRmonBitsCntS
        Article
        "
	::= { pm1001pcRmonClient 1176 }


pm1001pcMondwRmonBitsCntSEntry OBJECT-TYPE
	SYNTAX Pm1001pcMondwRmonBitsCntSEntry
	MAX-ACCESS not-accessible
	STATUS current
	DESCRIPTION
        "
        Row definition for the pm1001pcMondwRmonBitsCntS
        table
        "
	INDEX   { pm1001pcMondwRmonBitsCntSIndex }
	::= { pm1001pcMondwRmonBitsCntSTable 1 }


Pm1001pcMondwRmonBitsCntSEntry ::=
	SEQUENCE {
	pm1001pcMondwRmonBitsCntSIndex
		INTEGER,
	pm1001pcMondwRmonBitsCntSValuePortn
		Counter64,
	pm1001pcMondwRmonBitsCntSErrorPortn
		EkiOnOff,
	pm1001pcMondwRmonBitsCntSOverloadPortn
		EkiOnOff
	}


pm1001pcMondwRmonBitsCntSIndex OBJECT-TYPE
	SYNTAX  INTEGER(0..128)
	MAX-ACCESS  read-only
	STATUS current
	DESCRIPTION
        "
        Index definition for the pm1001pcMondwRmonBitsCntS
        table
        "
	::= { pm1001pcMondwRmonBitsCntSEntry 1 }


pm1001pcMondwRmonBitsCntSValuePortn OBJECT-TYPE
	SYNTAX  Counter64
	MAX-ACCESS read-only
	STATUS current
	DESCRIPTION
        "
        Client Output Bits Rate (/s) :This
        rate indicates the number of bits
        per second that are transmitted
        by the PM on the client port
        "
	::= { pm1001pcMondwRmonBitsCntSEntry 2 }


pm1001pcMondwRmonBitsCntSErrorPortn OBJECT-TYPE
	SYNTAX  EkiOnOff
	MAX-ACCESS read-only
	STATUS current
	DESCRIPTION
        "
        Output Bits rate error :This OID
        when set indicates the output Bits
        rate value is invalid on client
        port
        "
	::= { pm1001pcMondwRmonBitsCntSEntry 3 }


pm1001pcMondwRmonBitsCntSOverloadPortn OBJECT-TYPE
	SYNTAX  EkiOnOff
	MAX-ACCESS read-only
	STATUS current
	DESCRIPTION
        "
        Output Bits rate overload :This
        OID when set indicates an output
        Bits rate overload on client port
        "
	::= { pm1001pcMondwRmonBitsCntSEntry 4 }


pm1001pcMonCountersReset  OBJECT-TYPE
	SYNTAX EkiOnOff
	MAX-ACCESS read-write
	STATUS current
	DESCRIPTION
	"RMON Counters Reset:This OID resets and restarts all the RMON counters"
	::= { pm1001pcRmonOther 359 }

pm1001pcMonCountersStop  OBJECT-TYPE
	SYNTAX EkiOnOff
	MAX-ACCESS read-write
	STATUS current
	DESCRIPTION
	"RMON Counters stop:This OID stops all the RMON counters"
	::= { pm1001pcRmonOther 360 }






--- *****************************************************
--- $$$$$$$$$$$$$$$$$$$$$$$$$$$$$$$$$$$$$$$$$$$$$$$$$$$$$
---     MEASURES
--- $$$$$$$$$$$$$$$$$$$$$$$$$$$$$$$$$$$$$$$$$$$$$$$$$$$$$
--- *****************************************************



pm1001pcMesrsynth0 OBJECT-TYPE
	  SYNTAX EkiMeasureType
	  MAX-ACCESS read-only
	  STATUS deprecated
	  DESCRIPTION
        "
        Not Used :This OID gives the unit
        used on AUX1 measurement of XFP#1
         (Unit = )
        "
	  ::= { pm1001pcMesrOther 0 }



pm1001pcMesrsynth1 OBJECT-TYPE
	  SYNTAX EkiMeasureType
	  MAX-ACCESS read-only
	  STATUS deprecated
	  DESCRIPTION
        "
        Not Used :This OID gives the unit
        used on AUX2 measurement of XFP#1
         (Unit = )
        "
	  ::= { pm1001pcMesrOther 1 }



--- *****************************************************
---     LEAF for the clientModTempMeas article
--- *****************************************************

pm1001pcMesrclientModTempMeas OBJECT-TYPE
	  SYNTAX Unsigned32 (0..65535)
	  MAX-ACCESS read-only
	  STATUS current
	  DESCRIPTION
        "
        Client Optical Module Temperature
        :This OID gives the temperature
        value of the XFP plugged in port,
        read from the DDM (Digital Diagnostic
        Monitoring)
(Temperature = AV/256)
        (Unit = C)  <Help>  This measure
        gives the temperature of the client
        transceiver
        "
	  ::= { pm1001pcMesrClient 16 }



--- *****************************************************
---     LEAF for the clientBiasCurrentMeas article
--- *****************************************************

pm1001pcMesrclientBiasCurrentMeas OBJECT-TYPE
	  SYNTAX Unsigned32 (0..65535)
	  MAX-ACCESS read-only
	  STATUS current
	  DESCRIPTION
        "
        Client Optical Module Laser Bias
        :This OID gives the bias value
         of the XFP plugged into port,
         read from the DDM (Digital Diagnostic
        Monitoring)  (Bias = AV/500) (Unit
        = mA)  <Help>  This measure gives
        the bias of the client transceiver
        "
	  ::= { pm1001pcMesrClient 32 }



--- *****************************************************
---     LEAF for the clientTxPowerMeas article
--- *****************************************************

pm1001pcMesrclientTxPowerMeas OBJECT-TYPE
	  SYNTAX Unsigned32 (0..65535)
	  MAX-ACCESS read-only
	  STATUS current
	  DESCRIPTION
        "
        Client Optical Module Tx Power
        :This OID gives the transmit power
        value of the XFP plugged into port,
        read from the DDM (Digital Diagnostic
        Monitoring) (Power = 10*log(AV)-40)
        (Unit = dBm)  <Help>  This measure
        gives the Tx optical power of the
        client transceiver
        "
	  ::= { pm1001pcMesrClient 40 }



--- *****************************************************
---     LEAF for the clientRxPowerMeas article
--- *****************************************************

pm1001pcMesrclientRxPowerMeas OBJECT-TYPE
	  SYNTAX Unsigned32 (0..65535)
	  MAX-ACCESS read-only
	  STATUS current
	  DESCRIPTION
        "
        Client Optical Module Rx Power
        :This OID gives the receive power
        value of the XFP plugged into port,
        read in the DDM (Digital Diagnostic
        Monitoring) (Power = 10*log(AV)-40)
        (Unit = dBm)  <Help>  This measure
        gives the Rx optical power of the
        client transceiver
        "
	  ::= { pm1001pcMesrClient 48 }



--- *****************************************************
---     LEAF for the lineModTempMeas article
--- *****************************************************

pm1001pcMesrlineModTempMeas OBJECT-TYPE
	  SYNTAX Unsigned32 (0..65535)
	  MAX-ACCESS read-only
	  STATUS current
	  DESCRIPTION
        "
        Line Optical Module Temperature
        :This OID gives the temperature
        of the XFP or OTX plugged in line#1,
        read from the DDM (Digital Diagnostic
        Monitoring)
(Temperature = AV/256)
        (Unit = C)  <Help>  This measure
        gives the temperature of the line
        transceiver
        "
	  ::= { pm1001pcMesrLine 208 }



--- *****************************************************
---     LEAF for the lineReserved article
--- *****************************************************

pm1001pcMesrlineReserved OBJECT-TYPE
	  SYNTAX Unsigned32 (0..65535)
	  MAX-ACCESS read-only
	  STATUS deprecated
	  DESCRIPTION
        "
        Not Used :
        "
	  ::= { pm1001pcMesrLine 209 }



--- *****************************************************
---     LEAF for the lineBiasCurrentMeas article
--- *****************************************************

pm1001pcMesrlineBiasCurrentMeas OBJECT-TYPE
	  SYNTAX Unsigned32 (0..65535)
	  MAX-ACCESS read-only
	  STATUS current
	  DESCRIPTION
        "
        Line Optical Module Laser Bias
        :This OID gives the bias value
         of the XFP or OTX plugged in line
        #1, read from the DDM (Digital
         Diagnostic Monitoring) (Bias =
        AV/500) (Unit = mA)  <Help>  This
        measure gives the bias of the line
        transceiver
        "
	  ::= { pm1001pcMesrLine 210 }



--- *****************************************************
---     LEAF for the lineTxPowerMeas article
--- *****************************************************

pm1001pcMesrlineTxPowerMeas OBJECT-TYPE
	  SYNTAX Unsigned32 (0..65535)
	  MAX-ACCESS read-only
	  STATUS current
	  DESCRIPTION
        "
        Line Optical Module Tx Power :This
        OID gives the transmit power value
        of the XFP or OTX plugged in line
        #1, read from the DDM (Digital
           Diagnostic Monitoring) (Power
        = 10*log(AV)-40) (Unit = dBm)
         <Help>  This measure gives the
        Tx optical power of the line transceiver
        "
	  ::= { pm1001pcMesrLine 211 }



--- *****************************************************
---     LEAF for the lineRxPowerMeas article
--- *****************************************************

pm1001pcMesrlineRxPowerMeas OBJECT-TYPE
	  SYNTAX Unsigned32 (0..65535)
	  MAX-ACCESS read-only
	  STATUS current
	  DESCRIPTION
        "
        Line Optical Module Rx Power :This
        OID gives the receive power value
        of the XFP or OTX plugged in line
        #1, read from the DDM (Digital
         Diagnostic Monitoring) (Power
         = 10*log(AV)-40) (Unit = dBm)
          <Help>  This measure gives the
        Rx optical power of the line transceiver
        "
	  ::= { pm1001pcMesrLine 212 }



--- *****************************************************
---     LEAF for the lineAux1Meas article
--- *****************************************************

pm1001pcMesrlineAux1Meas OBJECT-TYPE
	  SYNTAX Unsigned32 (0..65535)
	  MAX-ACCESS read-only
	  STATUS deprecated
	  DESCRIPTION
        "
        Not Used :This OID gives the receive
        power value read in the DDM (Digital
        Diagnostic Monitoring) of the XFP
        or OTX plugged in line #1 (Unit
        = ?)
        "
	  ::= { pm1001pcMesrLine 213 }



--- *****************************************************
---     LEAF for the lineAux2Meas article
--- *****************************************************

pm1001pcMesrlineAux2Meas OBJECT-TYPE
	  SYNTAX Unsigned32 (0..65535)
	  MAX-ACCESS read-only
	  STATUS deprecated
	  DESCRIPTION
        "
        Not Used :This OID gives the receive
        power value read in the DDM (Digital
        Diagnostic Monitoring) of the XFP
        or OTX plugged in line #1 (Unit
        = ?)
        "
	  ::= { pm1001pcMesrLine 214 }








--- *****************************************************
--- $$$$$$$$$$$$$$$$$$$$$$$$$$$$$$$$$$$$$$$$$$$$$$$$$$$$$
---     DOWNLOAD
--- $$$$$$$$$$$$$$$$$$$$$$$$$$$$$$$$$$$$$$$$$$$$$$$$$$$$$
--- *****************************************************



--- *****************************************************
---     LEAF for the restartProcess article
--- *****************************************************
pm1001pcDwlrestartProcess OBJECT IDENTIFIER ::= { pm1001pcDwlOther 0 }




pm1001pcDwlColdRestartProcessed OBJECT-TYPE
	  SYNTAX EkiOnOff
	  MAX-ACCESS read-only
	  STATUS current
	  DESCRIPTION
        "
        Cold Restart :This OID indicates
        that the module last restart was
        a Cold RESTART
        "
	  ::= { pm1001pcDwlrestartProcess 2 }



pm1001pcDwlWarmRestartProcessed OBJECT-TYPE
	  SYNTAX EkiOnOff
	  MAX-ACCESS read-only
	  STATUS current
	  DESCRIPTION
        "
        Warm Restart :This OID indicates
        that the module last restart was
        a Warm RESTART
        "
	  ::= { pm1001pcDwlrestartProcess 1 }



--- *****************************************************
---     LEAF for the swBanksUsed article
--- *****************************************************
pm1001pcDwlswBanksUsed OBJECT IDENTIFIER ::= { pm1001pcDwlOther 1 }




pm1001pcDwlSwBank2Notempty OBJECT-TYPE
	  SYNTAX EkiOnOff
	  MAX-ACCESS read-only
	  STATUS current
	  DESCRIPTION
        "
        SW bank 2 loaded  :This OID indicates
        a software is loaded in SW bank
        2  <Help>  This status indicates
        if the SW bank 2 contains SW package
        "
	  ::= { pm1001pcDwlswBanksUsed 6 }



pm1001pcDwlSwBank1Notempty OBJECT-TYPE
	  SYNTAX EkiOnOff
	  MAX-ACCESS read-only
	  STATUS current
	  DESCRIPTION
        "
        SW bank 1 loaded  :This OID indicates
        a software is loaded in SW bank
        1  <Help>  This status indicates
        if the SW bank 1 contains SW package
        "
	  ::= { pm1001pcDwlswBanksUsed 5 }



pm1001pcDwlSwBank2Used OBJECT-TYPE
	  SYNTAX EkiOnOff
	  MAX-ACCESS read-only
	  STATUS current
	  DESCRIPTION
        "
        SW bank 2 active  :This OID indicates
        the module is working on SW bank
        2  <Help>  This status indicates
        if the SW bank 2 is active or standby
        "
	  ::= { pm1001pcDwlswBanksUsed 2 }



pm1001pcDwlSwBank1Used OBJECT-TYPE
	  SYNTAX EkiOnOff
	  MAX-ACCESS read-only
	  STATUS current
	  DESCRIPTION
        "
        SW bank 1 active  :This OID indicates
        the module is working on SW bank
        1  <Help>  This status indicates
        if the SW bank 1 is active or standby
        "
	  ::= { pm1001pcDwlswBanksUsed 1 }



--- *****************************************************
---     LEAF for the gwBanksUsed article
--- *****************************************************
pm1001pcDwlgwBanksUsed OBJECT IDENTIFIER ::= { pm1001pcDwlOther 2 }




pm1001pcDwlGwBank4Notempty OBJECT-TYPE
	  SYNTAX EkiOnOff
	  MAX-ACCESS read-only
	  STATUS deprecated
	  DESCRIPTION
        "
        GW bank 4 loaded  :This OID indicates
        a gateware is loaded in GW bank
        4
        "
	  ::= { pm1001pcDwlgwBanksUsed 8 }



pm1001pcDwlGwBank3Notempty OBJECT-TYPE
	  SYNTAX EkiOnOff
	  MAX-ACCESS read-only
	  STATUS current
	  DESCRIPTION
        "
        GW bank 3 loaded  :This OID indicates
        a gateware is loaded in GW bank
        3  <Help>  This status indicates
        if the GW bank 3 contains GW package
        "
	  ::= { pm1001pcDwlgwBanksUsed 7 }



pm1001pcDwlGwBank2Notempty OBJECT-TYPE
	  SYNTAX EkiOnOff
	  MAX-ACCESS read-only
	  STATUS deprecated
	  DESCRIPTION
        "
        GW bank 2 loaded  :This OID indicates
        a gateware is loaded in GW bank
        2
        "
	  ::= { pm1001pcDwlgwBanksUsed 6 }



pm1001pcDwlGwBank1Notempty OBJECT-TYPE
	  SYNTAX EkiOnOff
	  MAX-ACCESS read-only
	  STATUS current
	  DESCRIPTION
        "
        GW bank 1 loaded  :This OID indicates
        a gateware is loaded in GW bank
        1  <Help>  This status indicates
        if the GW bank 1 contains GW package
        "
	  ::= { pm1001pcDwlgwBanksUsed 5 }



pm1001pcDwlGwBank4Used OBJECT-TYPE
	  SYNTAX EkiOnOff
	  MAX-ACCESS read-only
	  STATUS deprecated
	  DESCRIPTION
        "
        GW bank 4 active  :This OID indicates
        the module is working on GW bank
        4
        "
	  ::= { pm1001pcDwlgwBanksUsed 4 }



pm1001pcDwlGwBank3Used OBJECT-TYPE
	  SYNTAX EkiOnOff
	  MAX-ACCESS read-only
	  STATUS current
	  DESCRIPTION
        "
        GW bank 3 active  :This OID indicates
        the module is working on GW bank
        3  <Help>  This status indicates
        if the GW bank 3 is active or standby
        "
	  ::= { pm1001pcDwlgwBanksUsed 3 }



pm1001pcDwlGwBank2Used OBJECT-TYPE
	  SYNTAX EkiOnOff
	  MAX-ACCESS read-only
	  STATUS deprecated
	  DESCRIPTION
        "
        GW bank 2 active  :This OID indicates
        the module is working on GW bank
        2
        "
	  ::= { pm1001pcDwlgwBanksUsed 2 }



pm1001pcDwlGwBank1Used OBJECT-TYPE
	  SYNTAX EkiOnOff
	  MAX-ACCESS read-only
	  STATUS current
	  DESCRIPTION
        "
        GW bank 1 active  :This OID indicates
        the module is working on GW bank
        1  <Help>  This status indicates
        if the GW bank 1 is active or standby
        "
	  ::= { pm1001pcDwlgwBanksUsed 1 }








--- *****************************************************
--- $$$$$$$$$$$$$$$$$$$$$$$$$$$$$$$$$$$$$$$$$$$$$$$$$$$$$
---     CONFIG
--- $$$$$$$$$$$$$$$$$$$$$$$$$$$$$$$$$$$$$$$$$$$$$$$$$$$$$
--- *****************************************************



--- *****************************************************
---     LEAF for the table Group accessCAisCsf
--- *****************************************************

pm1001pcCfgAccessCAisCsf OBJECT IDENTIFIER ::= { pm1001pcConfig 1 }



--- *****************************************************
---     LEAF for the table 0012
--- *****************************************************

pm1001pcCfgClientcaiscsfTable OBJECT-TYPE
	SYNTAX  SEQUENCE OF Pm1001pcCfgClientcaiscsfEntry
	MAX-ACCESS not-accessible
	STATUS current
	DESCRIPTION
        "
        List of  Article
        "
	::= { pm1001pcCfgAccessCAisCsf 1 }


pm1001pcCfgClientcaiscsfEntry OBJECT-TYPE
	SYNTAX Pm1001pcCfgClientcaiscsfEntry
	MAX-ACCESS not-accessible
	STATUS current
	DESCRIPTION
        "
        Row definition for the accessCAisCsf
        table
        "
	INDEX   { pm1001pcCfgClientcaiscsfIndex }
	::= { pm1001pcCfgClientcaiscsfTable 1 }


Pm1001pcCfgClientcaiscsfEntry ::=
	SEQUENCE {
	pm1001pcCfgClientcaiscsfIndex
		INTEGER,
	pm1001pcCfgCAisModePortn
		Unsigned32,
	pm1001pcCfgUpAccessioAlmPortn
		Unsigned32,
	pm1001pcCfgUpMapperDeAlmPortn
		Unsigned32,
	pm1001pcCfgDownAccessioAlmPortn
		Unsigned32,
	pm1001pcCfgDownMapperDeAlmPortn
		Unsigned32,
	pm1001pcCfgDownDfrmAlmPortn
		Unsigned32,
	pm1001pcCfgDownLineSyncAlarmsPortn
		Unsigned32
	}


pm1001pcCfgClientcaiscsfIndex OBJECT-TYPE
	SYNTAX  INTEGER(0..128)
	MAX-ACCESS  read-only
	STATUS current
	DESCRIPTION
        "
        Index definition for the clientcaiscsf
        table
        "
	::= { pm1001pcCfgClientcaiscsfEntry 1 }


pm1001pcCfgCAisModePortn OBJECT-TYPE
	SYNTAX  Unsigned32 (0..65536)
	MAX-ACCESS read-write
	STATUS current
	DESCRIPTION
        "
        CAIS mode  on Client Port :This
        register enables/disables port
          laser shutdown on CAIS insertion
        condition
        "
	::= { pm1001pcCfgClientcaiscsfEntry 3 }


pm1001pcCfgUpAccessioAlmPortn OBJECT-TYPE
	SYNTAX  Unsigned32 (0..65536)
	MAX-ACCESS read-write
	STATUS current
	DESCRIPTION
        "
        CSF contributors on Client Port
        :This register configures the contributors
        to upstream CSF insertion on the
        port.
        "
	::= { pm1001pcCfgClientcaiscsfEntry 9 }


pm1001pcCfgUpMapperDeAlmPortn OBJECT-TYPE
	SYNTAX  Unsigned32 (0..65536)
	MAX-ACCESS read-write
	STATUS current
	DESCRIPTION
        "
        CSF contributors on Client Port
        :This register configures the contributors
        to upstream CSF insertion on the
        port.
        "
	::= { pm1001pcCfgClientcaiscsfEntry 10 }


pm1001pcCfgDownAccessioAlmPortn OBJECT-TYPE
	SYNTAX  Unsigned32 (0..65536)
	MAX-ACCESS read-write
	STATUS current
	DESCRIPTION
        "
        CAIS contributors on Client Port
        :This register configures the contributors
        to downstream CAIS insertion on
         port.
        "
	::= { pm1001pcCfgClientcaiscsfEntry 17 }


pm1001pcCfgDownMapperDeAlmPortn OBJECT-TYPE
	SYNTAX  Unsigned32 (0..65536)
	MAX-ACCESS read-write
	STATUS current
	DESCRIPTION
        "
        CAIS contributors on Client Port
        :This register configures the contributors
        to downstream CAIS insertion on
         port.
        "
	::= { pm1001pcCfgClientcaiscsfEntry 18 }


pm1001pcCfgDownDfrmAlmPortn OBJECT-TYPE
	SYNTAX  Unsigned32 (0..65536)
	MAX-ACCESS read-write
	STATUS current
	DESCRIPTION
        "
        CAIS contributors on Client Port
        :This register configures the contributors
        to downstream CAIS insertion on
         port.
        "
	::= { pm1001pcCfgClientcaiscsfEntry 19 }


pm1001pcCfgDownLineSyncAlarmsPortn OBJECT-TYPE
	SYNTAX  Unsigned32 (0..65536)
	MAX-ACCESS read-write
	STATUS deprecated
	DESCRIPTION
        "
        CAIS contributors on Client Port
        :This register configures the contributors
        to downstream CAIS insertion on
         port.
        "
	::= { pm1001pcCfgClientcaiscsfEntry 20 }


--- *****************************************************
---     LEAF for the table Group startup
--- *****************************************************

pm1001pcCfgStartup OBJECT IDENTIFIER ::= { pm1001pcConfig 2 }



--- *****************************************************
---     LEAF for the table 2111
--- *****************************************************

pm1001pcCfgClientStartupTable OBJECT-TYPE
	SYNTAX  SEQUENCE OF Pm1001pcCfgClientStartupEntry
	MAX-ACCESS not-accessible
	STATUS current
	DESCRIPTION
        "
        List of  Article
        "
	::= { pm1001pcCfgStartup 1 }


pm1001pcCfgClientStartupEntry OBJECT-TYPE
	SYNTAX Pm1001pcCfgClientStartupEntry
	MAX-ACCESS not-accessible
	STATUS current
	DESCRIPTION
        "
        Row definition for the startup
        table
        "
	INDEX   { pm1001pcCfgClientStartupIndex }
	::= { pm1001pcCfgClientStartupTable 1 }


Pm1001pcCfgClientStartupEntry ::=
	SEQUENCE {
	pm1001pcCfgClientStartupIndex
		INTEGER,
	pm1001pcCfgSystConfPortPortn
		Unsigned32,
	pm1001pcCfgNetConfPortPortn
		Unsigned32,
	pm1001pcCfgFiberLengthPortn
		Unsigned32
	}


pm1001pcCfgClientStartupIndex OBJECT-TYPE
	SYNTAX  INTEGER(0..128)
	MAX-ACCESS  read-only
	STATUS current
	DESCRIPTION
        "
        Index definition for the clientStartup
        table
        "
	::= { pm1001pcCfgClientStartupEntry 1 }


pm1001pcCfgSystConfPortPortn OBJECT-TYPE
	SYNTAX  Unsigned32 (0..65536)
	MAX-ACCESS read-write
	STATUS current
	DESCRIPTION
        "
        Default Settings on Client Port
        :This  register configures the
         default initialisation settings
        on the port.
        "
	::= { pm1001pcCfgClientStartupEntry 3 }


pm1001pcCfgNetConfPortPortn OBJECT-TYPE
	SYNTAX  Unsigned32 (0..65536)
	MAX-ACCESS read-write
	STATUS current
	DESCRIPTION
        "
        Default Protocol on Client Port
        :This register configures the default
        initialisation protocol on the
         port.
        "
	::= { pm1001pcCfgClientStartupEntry 4 }


pm1001pcCfgFiberLengthPortn OBJECT-TYPE
	SYNTAX  Unsigned32 (0..65536)
	MAX-ACCESS read-write
	STATUS current
	DESCRIPTION
        "
        Default Fiber Length on Port :This
        register configures the default
        initialisation of the fiber length
        on the port.
        "
	::= { pm1001pcCfgClientStartupEntry 5 }


--- *****************************************************
---     LEAF for the table 2191
--- *****************************************************

pm1001pctablelineStartup OBJECT IDENTIFIER ::= { pm1001pcCfgStartup 2 }



pm1001pcCfgsynthTransLine OBJECT-TYPE
	  SYNTAX Unsigned32 (0..65536)
	  MAX-ACCESS read-write
	  STATUS current
	  DESCRIPTION
        "
        Default Settings on Line 1 :This
        register configures the default
        initialisation settings on Line
        port 1.
        "
	  ::= { pm1001pctablelineStartup 2 }



pm1001pcCfglineOptions1 OBJECT-TYPE
	  SYNTAX Unsigned32 (0..65536)
	  MAX-ACCESS read-write
	  STATUS current
	  DESCRIPTION
        "
        Default Options on Active Line
        Port :This register configures
         the default options on the active
        line port
        "
	  ::= { pm1001pctablelineStartup 5 }



--- *****************************************************
---     LEAF for the table 21AB
--- *****************************************************

pm1001pcCfgXfpTable OBJECT-TYPE
	SYNTAX  SEQUENCE OF Pm1001pcCfgXfpEntry
	MAX-ACCESS not-accessible
	STATUS current
	DESCRIPTION
        "
        List of  Article
        "
	::= { pm1001pcCfgStartup 3 }


pm1001pcCfgXfpEntry OBJECT-TYPE
	SYNTAX Pm1001pcCfgXfpEntry
	MAX-ACCESS not-accessible
	STATUS current
	DESCRIPTION
        "
        Row definition for the startup
        table
        "
	INDEX   { pm1001pcCfgXfpIndex }
	::= { pm1001pcCfgXfpTable 1 }


Pm1001pcCfgXfpEntry ::=
	SEQUENCE {
	pm1001pcCfgXfpIndex
		INTEGER,
	pm1001pcCfgSystConfXfpPortn
		Unsigned32,
	pm1001pcCfgDataRateConfXfpPortn
		Unsigned32
	}


pm1001pcCfgXfpIndex OBJECT-TYPE
	SYNTAX  INTEGER(0..128)
	MAX-ACCESS  read-only
	STATUS current
	DESCRIPTION
        "
        Index definition for the xfp table
        "
	::= { pm1001pcCfgXfpEntry 1 }


pm1001pcCfgSystConfXfpPortn OBJECT-TYPE
	SYNTAX  Unsigned32 (0..65536)
	MAX-ACCESS read-write
	STATUS current
	DESCRIPTION
        "
        Default settings on XFP Port :This
        register configures the default
        initialisation settings on XFP
         port.
        "
	::= { pm1001pcCfgXfpEntry 3 }


pm1001pcCfgDataRateConfXfpPortn OBJECT-TYPE
	SYNTAX  Unsigned32 (0..65536)
	MAX-ACCESS read-write
	STATUS deprecated
	DESCRIPTION
        "
        :Reserved
        "
	::= { pm1001pcCfgXfpEntry 4 }


--- *****************************************************
---     LEAF for the table Group labels
--- *****************************************************

pm1001pcCfgLabels OBJECT IDENTIFIER ::= { pm1001pcConfig 3 }



--- *****************************************************
---     LEAF for the table NO_VALUE
--- *****************************************************

pm1001pcCfgLabelclientTable OBJECT-TYPE
	SYNTAX  SEQUENCE OF Pm1001pcCfgLabelclientEntry
	MAX-ACCESS not-accessible
	STATUS current
	DESCRIPTION
        "
        List of  Article
        "
	::= { pm1001pcCfgLabels 1 }


pm1001pcCfgLabelclientEntry OBJECT-TYPE
	SYNTAX Pm1001pcCfgLabelclientEntry
	MAX-ACCESS not-accessible
	STATUS current
	DESCRIPTION
        "
        Row definition for the labels
         table
        "
	INDEX   { pm1001pcCfgLabelclientIndex }
	::= { pm1001pcCfgLabelclientTable 1 }


Pm1001pcCfgLabelclientEntry ::=
	SEQUENCE {
	pm1001pcCfgLabelclientIndex
		INTEGER,
	pm1001pcCfgLabelclientPortn
		DisplayString
	}


pm1001pcCfgLabelclientIndex OBJECT-TYPE
	SYNTAX  INTEGER(0..128)
	MAX-ACCESS  read-only
	STATUS current
	DESCRIPTION
        "
        Index definition for the labelclient
        table
        "
	::= { pm1001pcCfgLabelclientEntry 1 }


pm1001pcCfgLabelclientPortn OBJECT-TYPE
	SYNTAX  DisplayString( SIZE(1..16))
	MAX-ACCESS read-write
	STATUS current
	DESCRIPTION
        "
        Default settings on the label
         of the Ports :These registers
         configures the default initialisation
        settings of the labels of the ports.
        "
	::= { pm1001pcCfgLabelclientEntry 3 }


--- *****************************************************
---     LEAF for the table NO_VALUE
--- *****************************************************

pm1001pcCfgLabellineTable OBJECT-TYPE
	SYNTAX  SEQUENCE OF Pm1001pcCfgLabellineEntry
	MAX-ACCESS not-accessible
	STATUS current
	DESCRIPTION
        "
        List of  Article
        "
	::= { pm1001pcCfgLabels 2 }


pm1001pcCfgLabellineEntry OBJECT-TYPE
	SYNTAX Pm1001pcCfgLabellineEntry
	MAX-ACCESS not-accessible
	STATUS current
	DESCRIPTION
        "
        Row definition for the labels
         table
        "
	INDEX   { pm1001pcCfgLabellineIndex }
	::= { pm1001pcCfgLabellineTable 1 }


Pm1001pcCfgLabellineEntry ::=
	SEQUENCE {
	pm1001pcCfgLabellineIndex
		INTEGER,
	pm1001pcCfgLabellinePortn
		DisplayString
	}


pm1001pcCfgLabellineIndex OBJECT-TYPE
	SYNTAX  INTEGER(0..128)
	MAX-ACCESS  read-only
	STATUS current
	DESCRIPTION
        "
        Index definition for the labelline
        table
        "
	::= { pm1001pcCfgLabellineEntry 1 }


pm1001pcCfgLabellinePortn OBJECT-TYPE
	SYNTAX  DisplayString( SIZE(1..16))
	MAX-ACCESS read-write
	STATUS current
	DESCRIPTION
        "
        Default settings on the label
         of the lines :These registers
         configures the default initialisation
        settings of the labels of the lines.
        "
	::= { pm1001pcCfgLabellineEntry 3 }



pm1001pcCfgWriteConfiguration  OBJECT-TYPE
	SYNTAX EkiOnOff
	MAX-ACCESS read-write
	STATUS current
	DESCRIPTION
	"Write configuration to module:This OID
	 writes the complete configuration to the module"
	::= { pm1001pcConfig 257 }






--- *****************************************************
---     TRAP OBJECTS
--- *****************************************************


pm1001pctrapBoardNumber OBJECT-TYPE
	SYNTAX INTEGER(1..64)
	MAX-ACCESS read-only
	STATUS current
	DESCRIPTION
	"Last module which generates a trap"
	::= { pm1001pctraps 1 }







--- *****************************************************
---     LINE TRAPS
--- *****************************************************

pm1001pcLineTrapNotUrgentGoesOn NOTIFICATION-TYPE
	OBJECTS {pm1001pcAlmLineDdmWarning, pm1001pctrapBoardNumber}
	STATUS current
	--&FILTNAME    "PM1001PC Line Not Urgent ON"
	--&ACTIONS     { log, minor }
	--&MATCH       { pm1001pcAlmLineDdmWarning "on", pm1001pctrapBoardNumber "$2"}
	--&MESG        "DDM Warning appears on Line Port of PM1001PC in Slot $2 ($A)"
	DESCRIPTION "Not urgent Line default is activated"
	::= { pm1001pctraps 30 }

pm1001pcLineTrapNotUrgentGoesOff NOTIFICATION-TYPE
	OBJECTS {pm1001pcAlmLineDdmWarning, pm1001pctrapBoardNumber}
	STATUS current
	--&FILTNAME    "PM1001PC Line Not Urgent OFF"
	--&ACTIONS     { log, normal }
	--&CLEARS      { "PM1001PC Line Not Urgent ON" }
	--&MATCH       { pm1001pcAlmLineDdmWarning "on", pm1001pctrapBoardNumber "$2"}
	--&MESG        "DDM Warning disappears on Line Port of PM1001PC in Slot $2 ($A)"
	DESCRIPTION "Not urgent Line default disappeared"
	::= { pm1001pctraps 31 }

pm1001pcLineTrapUrgentGoesOn NOTIFICATION-TYPE
	OBJECTS {pm1001pcAlmLineDdmAlm, pm1001pctrapBoardNumber}
	STATUS current
	--&FILTNAME    "PM1001PC Line Urgent ON"
	--&ACTIONS     { log, major }
	--&MATCH       { pm1001pcAlmLineDdmAlm "on", pm1001pctrapBoardNumber "$2"}
	--&MESG        "DDM Alarm appears on Line Port of PM1001PC in Slot $2 ($A)"
	DESCRIPTION "Urgent Line default is activated"
	::= { pm1001pctraps 32 }

pm1001pcLineTrapUrgentGoesOff NOTIFICATION-TYPE
	OBJECTS {pm1001pcAlmLineDdmAlm, pm1001pctrapBoardNumber}
	STATUS current
	--&FILTNAME    "PM1001PC Line Urgent OFF"
	--&ACTIONS     { log, normal }
	--&CLEARS      { "PM1001PC Line Urgent ON" }
	--&MATCH       { pm1001pcAlmLineDdmAlm "on", pm1001pctrapBoardNumber "$2"}
	--&MESG        "DDM Alarm disappears on Line Port of PM1001PC in Slot $2 ($A)"
	DESCRIPTION "Urgent Line default disappeared"
	::= { pm1001pctraps 33 }

pm1001pcLineTrapCritGoesOn NOTIFICATION-TYPE
	OBJECTS {pm1001pcAlmLineFail , pm1001pcAlmLineHwFail, pm1001pctrapBoardNumber}
	STATUS current
	--&FILTNAME    "PM1001PC Line Fail ON"
	--&ACTIONS     { log, critical }
	--&MATCH       { pm1001pcAlmLineFail "on", pm1001pcAlmLineHwFail "*", pm1001pctrapBoardNumber "$3"}
	--&MESG        "Line Port Down on PM1001PC in Slot $3 ($A)"

	--&FILTNAME    "PM1001PC Line HW Fail ON (Hidden)"
	--&ACTIONS     { info }
	--&MATCH       { pm1001pcAlmLineFail "*", pm1001pcAlmLineHwFail "on", pm1001pctrapBoardNumber "$3"}
	--&MESG        "Line Port Down on PM1001PC in Slot $3 ($A)"
	DESCRIPTION "Critical Line default is activated"
	::= { pm1001pctraps 34 }

pm1001pcLineTrapCritGoesOff NOTIFICATION-TYPE
	OBJECTS {pm1001pcAlmLineFail , pm1001pcAlmLineHwFail, pm1001pctrapBoardNumber}
	STATUS current
	--&FILTNAME    "PM1001PC Line Fail OFF"
	--&ACTIONS     { log,  normal }
	--&CLEARS      { "PM1001PC Line Fail ON" }
	--&MATCH       { pm1001pcAlmLineFail "on", pm1001pcAlmLineHwFail "*", pm1001pctrapBoardNumber "$3"}
	--&MESG        "Line Port Up on PM1001PC in Slot $3 ($A)"

	--&FILTNAME    "PM1001PC Line HW Fail OFF (Hidden)"
	--&ACTIONS     { info }
	--&MATCH       { pm1001pcAlmLineFail "*", pm1001pcAlmLineHwFail "on", pm1001pctrapBoardNumber "$3"}
	--&MESG        "Line Port Up on PM1001PC in Slot $3 ($A)"
	DESCRIPTION "Critical Line default disappeared"
	::= { pm1001pctraps 35 }






--- *****************************************************
---     CLIENT TRAPS
--- *****************************************************

pm1001pcClientTrapNotUrgentGoesOn NOTIFICATION-TYPE
	OBJECTS {pm1001pcAlmClientXfpDdmWarning, pm1001pctrapBoardNumber}
	STATUS current
	--&FILTNAME    "PM1001PC Client Not Urgent ON"
	--&ACTIONS     { log, minor }
	--&MATCH       { pm1001pcAlmClientXfpDdmWarning "on", pm1001pctrapBoardNumber "$2"}
	--&MESG        "DDM Warning appears on Client Port of PM1001PC in Slot $2 ($A)"
	DESCRIPTION "Not urgent client default is activated"
	::= { pm1001pctraps 40 }

pm1001pcClientTrapNotUrgentGoesOff NOTIFICATION-TYPE
	OBJECTS {pm1001pcAlmClientXfpDdmWarning, pm1001pctrapBoardNumber}
	STATUS current
	--&FILTNAME    "PM1001PC Client Not Urgent OFF"
	--&ACTIONS     { log, normal }
	--&CLEARS      { "PM1001PC Client Not Urgent ON" }
	--&MATCH       { pm1001pcAlmClientXfpDdmWarning "on", pm1001pctrapBoardNumber "$2"}
	--&MESG        "DDM Warning appears on Client Port of PM1001PC in Slot $2 ($A)"
	DESCRIPTION "Not urgent client default disappeared"
	::= { pm1001pctraps 41 }

pm1001pcClientTrapUrgentGoesOn NOTIFICATION-TYPE
	OBJECTS {pm1001pcAlmClientXfpDdmAlm, pm1001pctrapBoardNumber}
	STATUS current
	--&FILTNAME    "PM1001PC Client Urgent ON"
	--&ACTIONS     { log, major }
	--&MATCH       { pm1001pcAlmClientXfpDdmAlm "on", pm1001pctrapBoardNumber "$2"}
	--&MESG        "DDM Alarm appears on Client Port of PM1001PC in Slot $2 ($A)"
	DESCRIPTION "Urgent client default is activated"
	::= { pm1001pctraps 42 }

pm1001pcClientTrapUrgentGoesOff NOTIFICATION-TYPE
	OBJECTS {pm1001pcAlmClientXfpDdmAlm, pm1001pctrapBoardNumber}
	STATUS current
	--&FILTNAME    "PM1001PC Client Urgent OFF"
	--&ACTIONS     { log, normal }
	--&CLEARS      { "PM1001PC Client Urgent ON" }
	--&MATCH       { pm1001pcAlmClientXfpDdmAlm "on", pm1001pctrapBoardNumber "$2"}
	--&MESG        "DDM Alarm disappears on Client Port of PM1001PC in Slot $2 ($A)"
	DESCRIPTION "Urgent client default disappeared"
	::= { pm1001pctraps 43 }

pm1001pcClientTrapCritGoesOn NOTIFICATION-TYPE
	OBJECTS {pm1001pcAlmClientFail, pm1001pcAlmClientHwFail, pm1001pctrapBoardNumber}
	STATUS current
	--&FILTNAME    "PM1001PC Client Fail ON"
	--&ACTIONS     { log, critical }
	--&MATCH       { pm1001pcAlmClientFail "on", pm1001pcAlmClientHwFail "*", pm1001pctrapBoardNumber "$3"}
	--&MESG        "Client Port Down on PM1001PC in Slot $3 ($A)"

	--&FILTNAME    "PM1001PC Client HW Fail ON (Hidden)"
	--&ACTIONS     { info }
	--&MATCH       { pm1001pcAlmClientFail "*", pm1001pcAlmClientHwFail "on", pm1001pctrapBoardNumber "$3"}
	--&MESG        "Client Port Down on PM1001PC in Slot $3 ($A)"
	DESCRIPTION "Critical client default is activated"
	::= { pm1001pctraps 44 }

pm1001pcClientTrapCritGoesOff NOTIFICATION-TYPE
	OBJECTS {pm1001pcAlmClientFail, pm1001pcAlmClientHwFail, pm1001pctrapBoardNumber}
	STATUS current
	--&FILTNAME    "PM1001PC Client Fail OFF"
	--&ACTIONS     { log, normal }
	--&CLEARS      { "PM1001PC Client Fail ON" }
	--&MATCH       { pm1001pcAlmClientFail "on", pm1001pcAlmClientHwFail "*", pm1001pctrapBoardNumber "$3"}
	--&MESG        "Client Port Up on PM1001PC in Slot $3 ($A)"

	--&FILTNAME    "PM1001PC Client HW Fail OFF (Hidden)"
	--&ACTIONS     { info }
	--&MATCH       { pm1001pcAlmClientFail "*", pm1001pcAlmClientHwFail "on", pm1001pctrapBoardNumber "$3"}
	--&MESG        "Client Port Up on PM1001PC in Slot $3 ($A)"
	DESCRIPTION "Critical client default disappeared"
	::= { pm1001pctraps 45 }






--- *****************************************************
---     HW TRAPS
--- *****************************************************

pm1001pcPowerTrapUrgentGoesOn NOTIFICATION-TYPE
	OBJECTS {pm1001pcAlmDefFuseB, pm1001pcAlmDefFuseA , pm1001pctrapBoardNumber}
	STATUS current
	--&FILTNAME    "PM1001PC Fuse A Fail ON"
	--&ACTIONS     { log, major }
	--&MATCH       { pm1001pcAlmDefFuseB "*", pm1001pcAlmDefFuseA "on", pm1001pctrapBoardNumber "$3"}
	--&MESG        "Power Input A Fail on PM1001PC in Slot $3 ($A)"

	--&FILTNAME    "PM1001PC Fuse B Fail ON"
	--&ACTIONS     { log, major }
	--&MATCH       { pm1001pcAlmDefFuseB "on", pm1001pcAlmDefFuseA "*", pm1001pctrapBoardNumber "$3"}
	--&MESG        "Power Input B Fail on PM1001PC in Slot $3 ($A)"
	DESCRIPTION "Urgent power supply default is activated"
	::= { pm1001pctraps 50 }

pm1001pcPowerTrapUrgentGoesOff NOTIFICATION-TYPE
	OBJECTS {pm1001pcAlmDefFuseB, pm1001pcAlmDefFuseA , pm1001pctrapBoardNumber}
	STATUS current
	--&FILTNAME    "PM1001PC Fuse A&B Fail OFF"
	--&ACTIONS     { log, normal}
	--&CLEARS      { "PM1001PC Fuse A Fail ON", "PM1001PC Fuse B Fail ON" }
	--&MATCH       { pm1001pcAlmDefFuseB "on", pm1001pcAlmDefFuseA "on", pm1001pctrapBoardNumber "$3"}
	--&MESG        "Power Inputs A and B Present on PM1001PC in Slot $3 ($A)"
	DESCRIPTION "Urgent power supply default disappeared"
	::= { pm1001pctraps 51 }






END
