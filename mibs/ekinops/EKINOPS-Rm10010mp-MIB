-- *****************************************************************
-- EKINOPS-Rm10010mp.TXT:  MIB
--
--MIB Part Number:3MI00028ADAF
--MIB Version:02
--
-- Copyright (c) 2016 by Ekinops
-- All rights reserved.
--
-- *****************************************************************

EKINOPS-Rm10010mp-MIB DEFINITIONS ::= BEGIN

IMPORTS
	ekinops,
	EkiState,
	EkiOnOff,
	EkiMode,
	EkiProtocol,
	EkiApiState,
	EkiSynchroMode,
	EkiMeasureType
			FROM EKINOPS-MIB
        MODULE-IDENTITY,
        OBJECT-TYPE,
        NOTIFICATION-TYPE,
	Unsigned32,
	Integer32,
	Counter32,
	IpAddress
        		FROM SNMPv2-SMI
 	TEXTUAL-CONVENTION,
	DisplayString
                FROM SNMPv2-TC;

moduleRm10010mp MODULE-IDENTITY
        LAST-UPDATED "201606020000Z"
        ORGANIZATION "Ekinops"
        CONTACT-INFO
         "Ekinops

          3, rue Blaise Pascal
          F-22300 Lannion / FRANCE

          Tel : +33 (0)2 96 05 00 30
          Fax : +33 (0)2 96 48 62 39

          E-mail: support@ekinops.fr"
        DESCRIPTION
          "Creation."

	REVISION "201111090000Z"
	DESCRIPTION
	  "Creation"
	REVISION "201111090000Z"
	DESCRIPTION
	  "Creation"
	REVISION "201206180000Z"
	DESCRIPTION
	  "Client In Loop insertion,Multiprotocol insertion"
	REVISION "201206290000Z"
	DESCRIPTION
	  "Client In Loop insertion,Multiprotocol insertion"
	REVISION "201207040000Z"
	DESCRIPTION
	  "New measurements on line"
	REVISION "201207100000Z"
	DESCRIPTION
	  "Fix on traps"
	REVISION "201207240000Z"
	DESCRIPTION
	  "New measurements on line"
	REVISION "201208280000Z"
	DESCRIPTION
	  "Creation for 100G MP"
	REVISION "201208290000Z"
	DESCRIPTION
	  "Add Oid for Measurements reset"
	REVISION "201209030000Z"
	DESCRIPTION
	  "Label change on CRC Error Counter"
	REVISION "201211060000Z"
	DESCRIPTION
	  "Fan Speed Control"
	REVISION "201401160000Z"
	DESCRIPTION
	  "Add ProbCause on CSF detected"
	REVISION "201404010000Z"
	DESCRIPTION
	  "Probcause,AlarmType - NMS completion"
	REVISION "201410140000Z"
	DESCRIPTION
	  "OSNR help completion"
	REVISION "201501210000Z"
	DESCRIPTION
	  "Labels cosmetic updates"
	REVISION "201510210000Z"
	DESCRIPTION
	  "Add F0 objet"
	REVISION "201605200000Z"
	DESCRIPTION
	  "New AlarmType – synthesisAlarm (12)"
	REVISION "201606020000Z"
	DESCRIPTION
	  "Capabilities objects of Table 5"
        ::= { ekinops 54 }



--- *****************************************************
---     LEAF LEVEL 2
--- *****************************************************


rm10010mpalarms OBJECT IDENTIFIER ::= { moduleRm10010mp 2 }
rm10010mpAlmOther OBJECT IDENTIFIER ::= { rm10010mpalarms 1 }
rm10010mpAlmOtherNurg OBJECT IDENTIFIER ::= { rm10010mpAlmOther 1 }
rm10010mpAlmOtherUrg OBJECT IDENTIFIER ::= { rm10010mpAlmOther 2 }
rm10010mpAlmOtherCrit OBJECT IDENTIFIER ::= { rm10010mpAlmOther 3 }

rm10010mpAlmClient OBJECT IDENTIFIER ::= { rm10010mpalarms 2 }
rm10010mpAlmClientNurg OBJECT IDENTIFIER ::= { rm10010mpAlmClient 1 }
rm10010mpAlmClientUrg OBJECT IDENTIFIER ::= { rm10010mpAlmClient 2 }
rm10010mpAlmClientCrit OBJECT IDENTIFIER ::= { rm10010mpAlmClient 3 }

rm10010mpAlmLine OBJECT IDENTIFIER ::= { rm10010mpalarms 3 }
rm10010mpAlmLineNurg OBJECT IDENTIFIER ::= { rm10010mpAlmLine 1 }
rm10010mpAlmLineUrg OBJECT IDENTIFIER ::= { rm10010mpAlmLine 2 }
rm10010mpAlmLineCrit OBJECT IDENTIFIER ::= { rm10010mpAlmLine 3 }





rm10010mpmeasures OBJECT IDENTIFIER ::= { moduleRm10010mp 3 }
rm10010mpMesrOther OBJECT IDENTIFIER ::= { rm10010mpmeasures 1 }
rm10010mpMesrClient OBJECT IDENTIFIER ::= { rm10010mpmeasures 2 }
rm10010mpMesrLine OBJECT IDENTIFIER ::= { rm10010mpmeasures 3 }




rm10010mpcounters OBJECT IDENTIFIER ::= { moduleRm10010mp 4 }
rm10010mpCntOther OBJECT IDENTIFIER ::= { rm10010mpcounters 1 }
rm10010mpCntClient OBJECT IDENTIFIER ::= { rm10010mpcounters 2 }
rm10010mpCntLine OBJECT IDENTIFIER ::= { rm10010mpcounters 3 }


rm10010mpcontrolsWrite OBJECT IDENTIFIER ::= { moduleRm10010mp 6 }
rm10010mpCtrlOther OBJECT IDENTIFIER ::= { rm10010mpcontrolsWrite 1 }
rm10010mpCtrlClient OBJECT IDENTIFIER ::= { rm10010mpcontrolsWrite 2 }
rm10010mpCtrlLine OBJECT IDENTIFIER ::= { rm10010mpcontrolsWrite 3 }

rm10010mpri OBJECT IDENTIFIER ::= { moduleRm10010mp 7 }
rm10010mpriTable OBJECT IDENTIFIER ::= { rm10010mpri 1 }

rm10010mpdownload OBJECT IDENTIFIER ::= { moduleRm10010mp 8 }
rm10010mpDwlOther OBJECT IDENTIFIER ::= { rm10010mpdownload 1 }
rm10010mpDwlClient OBJECT IDENTIFIER ::= { rm10010mpdownload 2 }
rm10010mpDwlLine OBJECT IDENTIFIER ::= { rm10010mpdownload 3 }


rm10010mpConfig OBJECT IDENTIFIER ::= { moduleRm10010mp 9 }

rm10010mptraps OBJECT IDENTIFIER ::= { moduleRm10010mp 10 }



rm10010mpMonitoring OBJECT IDENTIFIER ::= { moduleRm10010mp 11}

rm10010mpMonOther OBJECT IDENTIFIER ::= { rm10010mpMonitoring 1 }
rm10010mpMonRmon OBJECT IDENTIFIER ::= { rm10010mpMonOther 3 }

rm10010mpMonClient OBJECT IDENTIFIER ::= { rm10010mpMonitoring 2 }
rm10010mpMonClientRmonCounter OBJECT IDENTIFIER ::= { rm10010mpMonClient 4 }


--- *****************************************************
--- $$$$$$$$$$$$$$$$$$$$$$$$$$$$$$$$$$$$$$$$$$$$$$$$$$$$$
---     TEXTUAL-CONVENTION
--- $$$$$$$$$$$$$$$$$$$$$$$$$$$$$$$$$$$$$$$$$$$$$$$$$$$$$
--- *****************************************************

Rm10010mpMultiRate ::= TEXTUAL-CONVENTION
    STATUS      current
    DESCRIPTION "different rate for a client port"
    SYNTAX INTEGER {
		rate100Mhz(0),
		rate250Mhz(1),
		rate500Mhz(2),
		rate1Ghz(3)
           }

Rm10010mpOtxMode ::= TEXTUAL-CONVENTION
    STATUS      current
    DESCRIPTION "Different modes on OTX-TLH on client and line ports"
    SYNTAX INTEGER {
		otx80mode(1),
		otx60mode(2),
		otxadjustmode(4)
           }

Rm10010mpOtxGrid ::= TEXTUAL-CONVENTION
    STATUS      current
    DESCRIPTION "Different grids on OTX-TLH on client and line ports"
    SYNTAX INTEGER {
		otxgrid200(200),
		otxgrid100(100),
		otxgrid50(50)
           }

Rm10010mpAdjustValue ::= TEXTUAL-CONVENTION
    STATUS      current
    DESCRIPTION "Different values in Adjust mode on OTX-TLH on client and line ports"
    SYNTAX INTEGER {
		otxadjustvalue0(0),
		otxadjustvalue1(1),
		otxadjustvalue2(2),
		otxadjustvalue3(3),
		otxadjustvalue4(4),
		otxadjustvalue5(5),
		otxadjustvalue6(6),
		otxadjustvalue7(7),
		otxadjustvalue8(8),
		otxadjustvalue9(9),
		otxadjustvalue10(10)
           }

Rm10010mpClientProtocol ::= TEXTUAL-CONVENTION
    STATUS      current
    DESCRIPTION "Different values on the protocol on the client ports"
    SYNTAX INTEGER {
		protocolclientvalue0(0),
		protocolclientvalue1(1),
		protocolclientvalue2(2),
		protocolclientvalue3(3),
		protocolclientvalue4(4),
		protocolclientvalue5(5),
		protocolclientvalue6(6),
		protocolclientvalue7(7),
		protocolclientvalue8(8)
           }

Rm10010mpProtocolMode ::= TEXTUAL-CONVENTION
    STATUS      current
    DESCRIPTION "Different values on the protocol mode"
    SYNTAX INTEGER {
		protocolmodevalue0(0),
		protocolmodevalue1(1),
		protocolmodevalue2(2),
		protocolmodevalue3(3)
           }

Rm10010mpOtxChannel ::= TEXTUAL-CONVENTION
    STATUS      current
    DESCRIPTION "Channel selection on transceiver Tx line ports"
    SYNTAX INTEGER

Rm10010mpOrxChannel ::= TEXTUAL-CONVENTION
    STATUS      current
    DESCRIPTION "Channel selection on transceiver Rx line ports"
    SYNTAX INTEGER

--- *****************************************************
--- $$$$$$$$$$$$$$$$$$$$$$$$$$$$$$$$$$$$$$$$$$$$$$$$$$$$$
---     REMOTE INVENTORY
--- $$$$$$$$$$$$$$$$$$$$$$$$$$$$$$$$$$$$$$$$$$$$$$$$$$$$$
--- *****************************************************

rm10010mpRinvReloadInventory OBJECT-TYPE
  SYNTAX EkiOnOff
  MAX-ACCESS read-write
  STATUS current
  DESCRIPTION
        "Reload the inventory: This OID triggers an
         inventory reload."
  ::= { rm10010mpri 2 }

rm10010mpRinvHwPlatform OBJECT-TYPE
  SYNTAX DisplayString
  MAX-ACCESS read-only
  STATUS current
  DESCRIPTION
        "HW platform description: This OID contains the
         description of the Hardware platform."
  ::= { rm10010mpri 3 }

rm10010mpRinvModulePlatform OBJECT-TYPE
  SYNTAX DisplayString
  MAX-ACCESS read-only
  STATUS current
  DESCRIPTION
        "Module platform description: This OID contains the
         description of the Module."
  ::= { rm10010mpri 4 }

rm10010mpRinvSwPlatform OBJECT-TYPE
  SYNTAX DisplayString
  MAX-ACCESS read-only
  STATUS current
  DESCRIPTION
        "SW platform description: This OID contains the
         description of the Software platform."
  ::= { rm10010mpri 5 }

rm10010mpRinvGwPlatform OBJECT-TYPE
  SYNTAX DisplayString
  MAX-ACCESS read-only
  STATUS current
  DESCRIPTION
        "GW platform desciption: This OID contains the
         description of the Gateware platform."
  ::= { rm10010mpri 6 }


rm10010mpRinvSfpTable OBJECT-TYPE
      SYNTAX  SEQUENCE OF Rm10010mpRinvSfpEntry
      MAX-ACCESS  not-accessible
      STATUS  current
      DESCRIPTION
              "List of the SFPs on the selected module"
      ::= { rm10010mpriTable 1 }

rm10010mpRinvSfpEntry OBJECT-TYPE
        SYNTAX  Rm10010mpRinvSfpEntry
        MAX-ACCESS  not-accessible
        STATUS  current
        DESCRIPTION
              "Row definition for the SFP table"
        INDEX   { rm10010mpRinvSfpIndex }
        ::= { rm10010mpRinvSfpTable 1 }



Rm10010mpRinvSfpEntry::=
        SEQUENCE {
          rm10010mpRinvSfpIndex
              Integer32,
          rm10010mpRinvsfp
              DisplayString
        }


    rm10010mpRinvSfpIndex OBJECT-TYPE
        SYNTAX  Integer32(1..16)
        MAX-ACCESS  read-only
        STATUS  current
        DESCRIPTION
              "Index for SFP table"
        ::= { rm10010mpRinvSfpEntry 1 }


    rm10010mpRinvsfp OBJECT-TYPE
        SYNTAX  DisplayString
        MAX-ACCESS  read-only
        STATUS  current
        DESCRIPTION
              "Inventory for the SFP: This OID contains the inventory for the SFP"
        ::= { rm10010mpRinvSfpEntry 2 }




rm10010mpRinvLineTable OBJECT-TYPE
      SYNTAX  SEQUENCE OF Rm10010mpRinvLineEntry
      MAX-ACCESS  not-accessible
      STATUS  current
      DESCRIPTION
              "List of the XFPs on the selected module"
      ::= { rm10010mpriTable 2 }

rm10010mpRinvLineEntry OBJECT-TYPE
        SYNTAX  Rm10010mpRinvLineEntry
        MAX-ACCESS  not-accessible
        STATUS  current
        DESCRIPTION
              "Row definition for the XFP table"
        INDEX   { rm10010mpRinvLineIndex }
        ::= { rm10010mpRinvLineTable 1 }



Rm10010mpRinvLineEntry::=
        SEQUENCE {
          rm10010mpRinvLineIndex
              Integer32,
          rm10010mpRinvxfpLine
              DisplayString
        }


    rm10010mpRinvLineIndex OBJECT-TYPE
        SYNTAX  Integer32(1..16)
        MAX-ACCESS  read-only
        STATUS  current
        DESCRIPTION
              "Index for XFP table"
        ::= { rm10010mpRinvLineEntry 1 }


    rm10010mpRinvxfpLine OBJECT-TYPE
        SYNTAX  DisplayString
        MAX-ACCESS  read-only
        STATUS  current
        DESCRIPTION
              "Inventory for the XFP: This OID contains the inventory for the XFP"
        ::= { rm10010mpRinvLineEntry 2 }









--- *****************************************************
--- $$$$$$$$$$$$$$$$$$$$$$$$$$$$$$$$$$$$$$$$$$$$$$$$$$$$$
---     ALARMS
--- $$$$$$$$$$$$$$$$$$$$$$$$$$$$$$$$$$$$$$$$$$$$$$$$$$$$$
--- *****************************************************



--- *****************************************************
---     LEAF for the synthAlm0 article
--- *****************************************************
rm10010mpAlmsynthAlm0 OBJECT IDENTIFIER ::= { rm10010mpAlmOtherCrit 0 }




rm10010mpAlmDefFuseB OBJECT-TYPE
	  SYNTAX EkiOnOff
	  MAX-ACCESS read-only
	  STATUS current
	  DESCRIPTION
        "
        Fuse B Fail :This OID indicates
        that the fuse of the power input
        B is in fail condition <Help> Status
        of the Fuse B <Condtype> DEF_FUSE_B
        <Probcause> powerProblem (36) <Alarmtype>
        equipmentAlarm (5) <Polarity> (2)
        "
	  ::= { rm10010mpAlmsynthAlm0 16 }



rm10010mpAlmDefFuseA OBJECT-TYPE
	  SYNTAX EkiOnOff
	  MAX-ACCESS read-only
	  STATUS current
	  DESCRIPTION
        "
        Fuse A Fail :This OID indicates
        that the fuse of the power input
        A is in fail condition <Help> Status
        of the Fuse A <Condtype> DEF_FUSE_A
        <Probcause> powerProblem (36) <Alarmtype>
        equipmentAlarm (5) <Polarity> (2)
        "
	  ::= { rm10010mpAlmsynthAlm0 15 }



rm10010mpAlmModGlobFail OBJECT-TYPE
	  SYNTAX EkiOnOff
	  MAX-ACCESS read-only
	  STATUS current
	  DESCRIPTION
        "
        Module Failure :This OID is set
        on detection of a failure originating
        from the RM <Help> This alarm is
        set on detection of a failure originating
        from the equipment <Condtype> MOD_GLOB_FAIL
        <Probcause> other (1) <Alarmtype>
        synthesisAlarm (12)  <Polarity>
        (2)
        "
	  ::= { rm10010mpAlmsynthAlm0 9 }



rm10010mpAlmFailFan OBJECT-TYPE
	  SYNTAX EkiOnOff
	  MAX-ACCESS read-only
	  STATUS current
	  DESCRIPTION
        "
        Fan Fail :This OID is at 1 when
        any fail occurs on the fan tray
        <Help> This alarm indicates that
        the Fan tray module is in a failure
        condition <Condtype> FAIL_FAN <Probcause>
        equipmentMalfunction (16) <Alarmtype>
        equipmentAlarm (5) <Polarity> (2)
        "
	  ::= { rm10010mpAlmsynthAlm0 2 }



--- *****************************************************
---     LEAF for the synthAlm2 article
--- *****************************************************
rm10010mpAlmsynthAlm2 OBJECT IDENTIFIER ::= { rm10010mpAlmOtherNurg 2 }




rm10010mpAlmMaintenanceOn OBJECT-TYPE
	  SYNTAX EkiOnOff
	  MAX-ACCESS read-only
	  STATUS current
	  DESCRIPTION
        "
        Maintenance Mode :This OID indicates
        that the RM is in maintenance mode.
        <Help> This alarm indicates that
        the maintenance mode is enabled
        on the PM <Condtype> MAINTENANCE_ON
        <Probcause> informationalStatus(1000)
        <Alarmtype> other (1) <Polarity>
        (2)
        "
	  ::= { rm10010mpAlmsynthAlm2 5 }



rm10010mpAlmCorrelatOff OBJECT-TYPE
	  SYNTAX EkiOnOff
	  MAX-ACCESS read-only
	  STATUS current
	  DESCRIPTION
        "
        Not Used :This OID, when set,
         indicates that alarm correlation
        is not being performed. <Condtype>
        CORRELAT_OFF <Probcause> informationalStatus(1000)
        <Alarmtype> other (1) <Polarity>
        (2)
        "
	  ::= { rm10010mpAlmsynthAlm2 4 }



rm10010mpAlmConfTableLoad OBJECT-TYPE
	  SYNTAX EkiOnOff
	  MAX-ACCESS read-only
	  STATUS current
	  DESCRIPTION
        "
        PM Configuration Load :This OID
         is at 1 during the loading of
         configuration tables in the modules
        RAM. <Condtype> CONF_TABLE_LOAD
        <Probcause> informationalStatus(1000)
        <Alarmtype> other (1) <Polarity>
        (2)
        "
	  ::= { rm10010mpAlmsynthAlm2 3 }



rm10010mpAlmInvUpload OBJECT-TYPE
	  SYNTAX EkiOnOff
	  MAX-ACCESS read-only
	  STATUS current
	  DESCRIPTION
        "
        Inventory Upload :This OID is
         at 1 during the uploading of PM
        inventory information. <Condtype>
        INV_UPLOAD <Probcause> informationalStatus(1000)
        <Alarmtype> other (1) <Polarity>
        (2)
        "
	  ::= { rm10010mpAlmsynthAlm2 2 }



rm10010mpAlmConfTableSave OBJECT-TYPE
	  SYNTAX EkiOnOff
	  MAX-ACCESS read-only
	  STATUS current
	  DESCRIPTION
        "
        PM Configuration Save :This OID
        is at 1 during the saving of a
         new configuration table in the
        module Flash memory. <Condtype>
        CONF_TABLE_SAVE <Probcause> informationalStatus(1000)
        <Alarmtype> other (1) <Polarity>
        (2)
        "
	  ::= { rm10010mpAlmsynthAlm2 1 }



--- *********************************************************
---     TABLE for the rm10010mpAlmsynthAlmPort articles
--- *********************************************************

rm10010mpAlmsynthAlmPortTable OBJECT-TYPE
	SYNTAX  SEQUENCE OF Rm10010mpAlmsynthAlmPortEntry
	MAX-ACCESS not-accessible
	STATUS current
	DESCRIPTION
        "
        List of rm10010mpAlmsynthAlmPort
        Article
        "
	::= { rm10010mpAlmClientCrit 8 }


rm10010mpAlmsynthAlmPortEntry OBJECT-TYPE
	SYNTAX Rm10010mpAlmsynthAlmPortEntry
	MAX-ACCESS not-accessible
	STATUS current
	DESCRIPTION
        "
        Row definition for the rm10010mpAlmsynthAlmPort
        table
        "
	INDEX   { rm10010mpAlmsynthAlmPortIndex }
	::= { rm10010mpAlmsynthAlmPortTable 1 }


Rm10010mpAlmsynthAlmPortEntry ::=
	SEQUENCE {
	rm10010mpAlmsynthAlmPortIndex
		INTEGER,
	rm10010mpAlmUpCsfPortn
		EkiOnOff,
	rm10010mpAlmFailAccPortn
		EkiOnOff,
	rm10010mpAlmSfpDdmAlmPortn
		EkiOnOff,
	rm10010mpAlmSfpDdmWarningPortn
		EkiOnOff,
	rm10010mpAlmDwCaisPortn
		EkiOnOff,
	rm10010mpAlmClientRemoteOosPortn
		EkiOnOff,
	rm10010mpAlmClientLocalOosPortn
		EkiOnOff,
	rm10010mpAlmDwLsdPortn
		EkiOnOff,
	rm10010mpAlmHwFailAccPortn
		EkiOnOff,
	rm10010mpAlmDdmAbsentPortn
		EkiOnOff,
	rm10010mpAlmSfpAbsentPortn
		EkiOnOff
	}


rm10010mpAlmsynthAlmPortIndex OBJECT-TYPE
	SYNTAX  INTEGER(0..128)
	MAX-ACCESS  read-only
	STATUS current
	DESCRIPTION
        "
        Index definition for the rm10010mpAlmsynthAlmPort
        table
        "
	::= { rm10010mpAlmsynthAlmPortEntry 1 }


rm10010mpAlmUpCsfPortn OBJECT-TYPE
	SYNTAX  EkiOnOff
	MAX-ACCESS read-only
	STATUS current
	DESCRIPTION
        "
        Client Signal Fail Inserted :This
        OID indicates a CSF has been inserted
        in the upstream client port. <Help>
        This status indicates if a Client
        Signal Fail is currently inserted
        on the line signal for this client
        port <Condtype> UP_CSF_1 <Probcause>
        informationalStatus(1000) <Alarmtype>
        other (1) <Polarity> (2)
        "
	::= { rm10010mpAlmsynthAlmPortEntry 17 }


rm10010mpAlmFailAccPortn OBJECT-TYPE
	SYNTAX  EkiOnOff
	MAX-ACCESS read-only
	STATUS current
	DESCRIPTION
        "
        Client Access Fail :This OID indicates
        a failure on the Client port <Help>
        This alarm indicates a failure
         on the Client port <Condtype>
         FAIL_ACC_1 <Probcause> equipmentMalfunction
        (16) <Alarmtype> synthesisAlarm
        (12)  <Polarity> (2)
        "
	::= { rm10010mpAlmsynthAlmPortEntry 13 }


rm10010mpAlmSfpDdmAlmPortn OBJECT-TYPE
	SYNTAX  EkiOnOff
	MAX-ACCESS read-only
	STATUS current
	DESCRIPTION
        "
        Alarm On Client Trscv DDM :This
        OID indicates an alarm is being
        received from the Client Transceiver
        DDM <Help> This alarm indicates
        if a DDM Alarm has been detected
        on the client transceiver <Condtype>
        SFP_DDM_ALM_1 <Probcause> inputOutputDeviceError
        (24) <Alarmtype> synthesisAlarm
        (12)  <Polarity> (2)
        "
	::= { rm10010mpAlmsynthAlmPortEntry 11 }


rm10010mpAlmSfpDdmWarningPortn OBJECT-TYPE
	SYNTAX  EkiOnOff
	MAX-ACCESS read-only
	STATUS current
	DESCRIPTION
        "
        Warning On Client Trscv DDM :This
        OID indicates a warning is being
        received from the Client Transceiver
        DDM <Help> This alarm indicates
        if a DDM Warning has been detected
        on the client transceiver <Condtype>
        SFP_DDM_WARNING_1 <Probcause> inputOutputDeviceError
        (24) <Alarmtype> synthesisAlarm
        (12)  <Polarity> (2)
        "
	::= { rm10010mpAlmsynthAlmPortEntry 10 }


rm10010mpAlmDwCaisPortn OBJECT-TYPE
	SYNTAX  EkiOnOff
	MAX-ACCESS read-only
	STATUS current
	DESCRIPTION
        "
        Client AIS Inserted :This OID
         indicates a CAIS has been inserted
        on the output client port. <Help>
        This status indicates if a Client
        Alarm Indication Signal is currently
        inserted on the client interface
        <Condtype> DW_CAIS_1 <Probcause>
        informationalStatus(1000) <Alarmtype>
        other (1) <Polarity> (2)
        "
	::= { rm10010mpAlmsynthAlmPortEntry 9 }


rm10010mpAlmClientRemoteOosPortn OBJECT-TYPE
	SYNTAX  EkiOnOff
	MAX-ACCESS read-only
	STATUS current
	DESCRIPTION
        "
        Remote Client Port In Service
         :This OID indicates that the remote
        Client port is In Service (1) or
        Out of Service (2) <Help> This
         status indicates if the remote
        client port is in service <Condtype>
        CLIENT_REMOTE_OOS <Probcause> informationalStatus(1000)
        <Alarmtype> other (1) <Polarity>
        (2)
        "
	::= { rm10010mpAlmsynthAlmPortEntry 8 }


rm10010mpAlmClientLocalOosPortn OBJECT-TYPE
	SYNTAX  EkiOnOff
	MAX-ACCESS read-only
	STATUS current
	DESCRIPTION
        "
        Local Client Port In Service :This
        OID indicates that the local Client
        port is In Service (1) or Out of
        Service (2) <Help> This status
         indicates if the local client
         port is in service <Condtype>
         CLIENT_LOCAL_OOS <Probcause> informationalStatus(1000)
        <Alarmtype> other (1) <Polarity>
        (2)
        "
	::= { rm10010mpAlmsynthAlmPortEntry 7 }


rm10010mpAlmDwLsdPortn OBJECT-TYPE
	SYNTAX  EkiOnOff
	MAX-ACCESS read-only
	STATUS current
	DESCRIPTION
        "
        Client Trscv Laser Shutdown :This
        OID indicates the Client transceiver
        laser is shutdown <Help> This status
        indicates if the client transceiver
        laser is shutdown <Condtype> DW_LSD_1
        <Probcause> other (1) <Alarmtype>
        equipmentAlarm (5) <Polarity> (2)
        "
	::= { rm10010mpAlmsynthAlmPortEntry 6 }


rm10010mpAlmHwFailAccPortn OBJECT-TYPE
	SYNTAX  EkiOnOff
	MAX-ACCESS read-only
	STATUS current
	DESCRIPTION
        "
        Client HW Fail :This OID indicates
        a failure on client port, most
         probably caused by a HW issue.
        <Help> This alarm indicates a failure
        on client port, most probably caused
        by a HW issue. <Condtype> HW_FAIL_ACC_1
        <Probcause> equipmentMalfunction
        (16) <Alarmtype> synthesisAlarm
        (12)  <Polarity> (2)
        "
	::= { rm10010mpAlmsynthAlmPortEntry 5 }


rm10010mpAlmDdmAbsentPortn OBJECT-TYPE
	SYNTAX  EkiOnOff
	MAX-ACCESS read-only
	STATUS current
	DESCRIPTION
        "
        DDM Supported On Client Trscv
         :This OID indicates that the Client
        transceiver supports the Digital
        Diagnostic Monitoring function
         <Help> This status indicates if
        the client transceiver includes
        the DDM feature <Condtype> DDM_ABSENT_1
        <Probcause> informationalStatus(1000)
        <Alarmtype> other (1) <Polarity>
        (2)
        "
	::= { rm10010mpAlmsynthAlmPortEntry 3 }


rm10010mpAlmSfpAbsentPortn OBJECT-TYPE
	SYNTAX  EkiOnOff
	MAX-ACCESS read-only
	STATUS current
	DESCRIPTION
        "
        Client Optical Module Absent :This
        OID indicates that the Transceiver
        is not present in the client port.
        <Help> This alarm indicates if
         the client transceiver is not
         plugged <Condtype> SFP_ABSENT_1
        <Probcause> inputOutputDeviceError
        (24) <Alarmtype> equipmentAlarm
        (5) <Polarity> (2) <Event> ObjectCDINV
        "
	::= { rm10010mpAlmsynthAlmPortEntry 2 }


--- *********************************************************
---     TABLE for the rm10010mpAlmsynthAlmLine articles
--- *********************************************************

rm10010mpAlmsynthAlmLineTable OBJECT-TYPE
	SYNTAX  SEQUENCE OF Rm10010mpAlmsynthAlmLineEntry
	MAX-ACCESS not-accessible
	STATUS current
	DESCRIPTION
        "
        List of rm10010mpAlmsynthAlmLine
        Article
        "
	::= { rm10010mpAlmLineCrit 24 }


rm10010mpAlmsynthAlmLineEntry OBJECT-TYPE
	SYNTAX Rm10010mpAlmsynthAlmLineEntry
	MAX-ACCESS not-accessible
	STATUS current
	DESCRIPTION
        "
        Row definition for the rm10010mpAlmsynthAlmLine
        table
        "
	INDEX   { rm10010mpAlmsynthAlmLineIndex }
	::= { rm10010mpAlmsynthAlmLineTable 1 }


Rm10010mpAlmsynthAlmLineEntry ::=
	SEQUENCE {
	rm10010mpAlmsynthAlmLineIndex
		INTEGER,
	rm10010mpAlmLineActivePortn
		EkiOnOff,
	rm10010mpAlmLineFailPortn
		EkiOnOff,
	rm10010mpAlmLineDdmAlmPortn
		EkiOnOff,
	rm10010mpAlmLineDdmWarningPortn
		EkiOnOff,
	rm10010mpAlmUpRdiInsPortn
		EkiOnOff,
	rm10010mpAlmLineLocalOosPortn
		EkiOnOff,
	rm10010mpAlmXfpTxOffPortn
		EkiOnOff,
	rm10010mpAlmLineHwFailPortn
		EkiOnOff,
	rm10010mpAlmXfpInitNotComplPortn
		EkiOnOff,
	rm10010mpAlmXfpAbsentPortn
		EkiOnOff
	}


rm10010mpAlmsynthAlmLineIndex OBJECT-TYPE
	SYNTAX  INTEGER(0..128)
	MAX-ACCESS  read-only
	STATUS current
	DESCRIPTION
        "
        Index definition for the rm10010mpAlmsynthAlmLine
        table
        "
	::= { rm10010mpAlmsynthAlmLineEntry 1 }


rm10010mpAlmLineActivePortn OBJECT-TYPE
	SYNTAX  EkiOnOff
	MAX-ACCESS read-only
	STATUS current
	DESCRIPTION
        "
        Line Active :This OID indicates
        whether the line is active or standby.
        <Help> This status indicates whether
        the line is active or standby.
         <Condtype> LINE_ACTIVE <Probcause>
        informationalStatus(1000) <Alarmtype>
        other (1) <Polarity> (2)
        "
	::= { rm10010mpAlmsynthAlmLineEntry 17 }


rm10010mpAlmLineFailPortn OBJECT-TYPE
	SYNTAX  EkiOnOff
	MAX-ACCESS read-only
	STATUS current
	DESCRIPTION
        "
        Line Port Failure :This OID indicates
        a failure on the line port <Help>
        This alarm indicates a failure
         on the line port <Condtype> LINE_FAIL
        <Probcause> equipmentMalfunction
        (16) <Alarmtype> synthesisAlarm
        (12)  <Polarity> (2)
        "
	::= { rm10010mpAlmsynthAlmLineEntry 13 }


rm10010mpAlmLineDdmAlmPortn OBJECT-TYPE
	SYNTAX  EkiOnOff
	MAX-ACCESS read-only
	STATUS current
	DESCRIPTION
        "
        Alarm On Line Optical Module DDM
        :This OID indicates an alarm is
        present coming out of Line transceiver
        DDM <Help> This alarm indicates
        if a DDM Alarm has been detected
        on the line transceiver <Condtype>
        LINE_DDM_ALM <Probcause> inputOutputDeviceError
        (24) <Alarmtype> synthesisAlarm
        (12)  <Polarity> (2)
        "
	::= { rm10010mpAlmsynthAlmLineEntry 11 }


rm10010mpAlmLineDdmWarningPortn OBJECT-TYPE
	SYNTAX  EkiOnOff
	MAX-ACCESS read-only
	STATUS current
	DESCRIPTION
        "
        Warning On Line Optical Module
        DDM :This OID indicates a warning
        is present coming out of Line transceiver
        DDM <Help> This alarm indicates
        if a DDM Warning has been detected
        on the line transceiver <Condtype>
        LINE_DDM_WARNING <Probcause> inputOutputDeviceError
        (24) <Alarmtype> synthesisAlarm
        (12)  <Polarity> (2)
        "
	::= { rm10010mpAlmsynthAlmLineEntry 10 }


rm10010mpAlmUpRdiInsPortn OBJECT-TYPE
	SYNTAX  EkiOnOff
	MAX-ACCESS read-only
	STATUS current
	DESCRIPTION
        "
        MS-RDI/L-RDI Inserted On Line
         :This OID indicates an upstream
        MS-RDI/L-RDI has been inserted
         in the outgoing 10 Gb/s SDH/SONET
        signal. <Help> This status indicates
        if a MS-RDI/L-RDI is currently
         inserted on the line interface.
        <Condtype> UP_RDI_INS <Probcause>
        informationalStatus(1000) <Alarmtype>
        other (1) <Polarity> (2)
        "
	::= { rm10010mpAlmsynthAlmLineEntry 9 }


rm10010mpAlmLineLocalOosPortn OBJECT-TYPE
	SYNTAX  EkiOnOff
	MAX-ACCESS read-only
	STATUS current
	DESCRIPTION
        "
        Line Port In Service :This OID
        indicates that the Line port is
        In Service (1) of Out or Service
        (2) <Help> This status indicates
        if the line port is in service
         <Condtype> LINE_LOCAL_OOS <Probcause>
        informationalStatus(1000) <Alarmtype>
        other (1) <Polarity> (2)
        "
	::= { rm10010mpAlmsynthAlmLineEntry 7 }


rm10010mpAlmXfpTxOffPortn OBJECT-TYPE
	SYNTAX  EkiOnOff
	MAX-ACCESS read-only
	STATUS current
	DESCRIPTION
        "
        Line Trscv Laser Shutdown :This
        OID indicates the Line transceiver
        laser is shutdown <Help> This status
        indicates if the Line transceiver
        laser is shutdown <Condtype> XFP_TX_OFF
        <Probcause> other (1) <Alarmtype>
        equipmentAlarm (5) <Polarity> (2)
        "
	::= { rm10010mpAlmsynthAlmLineEntry 6 }


rm10010mpAlmLineHwFailPortn OBJECT-TYPE
	SYNTAX  EkiOnOff
	MAX-ACCESS read-only
	STATUS current
	DESCRIPTION
        "
        Line Port HW Failure :This OID
        indicates a failure on line port,
        most probably caused by a HW issue
        <Help> This alarm indicates a failure
        on line port, most probably caused
        by a HW issue <Condtype> LINE_HW_FAIL
        <Probcause> equipmentMalfunction
        (16) <Alarmtype> synthesisAlarm
        (12)  <Polarity> (2)
        "
	::= { rm10010mpAlmsynthAlmLineEntry 5 }


rm10010mpAlmXfpInitNotComplPortn OBJECT-TYPE
	SYNTAX  EkiOnOff
	MAX-ACCESS read-only
	STATUS current
	DESCRIPTION
        "
        Line Optical Module Ready :This
        OID indicates that the optical
         interface is not operational.
         <Help> This status indicates if
        the line transceiver has been correctly
        initialized <Condtype> XFP_INIT_NOT_COMPL
        <Probcause> equipmentMalfunction
        (16) <Alarmtype> equipmentAlarm
        (5) <Polarity> (2)
        "
	::= { rm10010mpAlmsynthAlmLineEntry 3 }


rm10010mpAlmXfpAbsentPortn OBJECT-TYPE
	SYNTAX  EkiOnOff
	MAX-ACCESS read-only
	STATUS current
	DESCRIPTION
        "
        Line Optical Module Absent :This
        OID indicates that the line optical
        interface is not present. <Help>
        This alarm indicates if the line
        transceiver is not plugged <Condtype>
        XFP_ABSENT <Probcause> inputOutputDeviceError
        (24) <Alarmtype> equipmentAlarm
        (5) <Polarity> (2)
        "
	::= { rm10010mpAlmsynthAlmLineEntry 2 }


--- *****************************************************
---     LEAF for the clientModuleState article
--- *****************************************************
rm10010mpAlmclientModuleState OBJECT IDENTIFIER ::= { rm10010mpAlmOtherCrit 40 }




rm10010mpAlmCfpHighPowerDown OBJECT-TYPE
	  SYNTAX EkiOnOff
	  MAX-ACCESS read-only
	  STATUS current
	  DESCRIPTION
        "
        Client Trscv High Power Down :This
        OID indicates the Client Trscv
         is entering Low Power state <Help>
        Status indicating the Client Trscv
        is entering Low Power state <Condtype>
        CFP_HIGH_POWER_DOWN <Probcause>
        informationalStatus(1000) <Alarmtype>
        other (1) <Polarity> (2)
        "
	  ::= { rm10010mpAlmclientModuleState 9 }



rm10010mpAlmCfpTxTurnOff OBJECT-TYPE
	  SYNTAX EkiOnOff
	  MAX-ACCESS read-only
	  STATUS current
	  DESCRIPTION
        "
        Client Trscv Laser Turn Off :This
        OID indicates the Client Trscv
         is turning off its laser <Help>
        Status indicating the Client Trscv
        is turning off its laser <Condtype>
        CFP_TX_TURN_OFF <Probcause> informationalStatus(1000)
        <Alarmtype> other (1) <Polarity>
        (2)
        "
	  ::= { rm10010mpAlmclientModuleState 8 }



rm10010mpAlmCfpFault OBJECT-TYPE
	  SYNTAX EkiOnOff
	  MAX-ACCESS read-only
	  STATUS current
	  DESCRIPTION
        "
        Client Trscv Fault :This OID indicates
        the Client Trscv is in Fault state
        <Help> Status indicating the Client
        Trscv is in Fault state <Condtype>
        CFP_FAULT <Probcause> informationalStatus(1000)
        <Alarmtype> other (1) <Polarity>
        (2)
        "
	  ::= { rm10010mpAlmclientModuleState 7 }



rm10010mpAlmCfpReady OBJECT-TYPE
	  SYNTAX EkiOnOff
	  MAX-ACCESS read-only
	  STATUS current
	  DESCRIPTION
        "
        Client Trscv Ready :This OID indicates
        the Client Trscv is ready to operate
        <Help> Status indicating the Client
        Trscv is ready to operate <Condtype>
        CFP_READY <Probcause> informationalStatus(1000)
        <Alarmtype> other (1) <Polarity>
        (2)
        "
	  ::= { rm10010mpAlmclientModuleState 6 }



rm10010mpAlmCfpTxTurnOn OBJECT-TYPE
	  SYNTAX EkiOnOff
	  MAX-ACCESS read-only
	  STATUS current
	  DESCRIPTION
        "
        Client Trscv Laser Turn On :This
        OID indicates the Client Trscv
         is turning on its laser <Help>
        Status indicating the Client Trscv
        is turning on its laser <Condtype>
        CFP_TX_TURN_ON <Probcause> informationalStatus(1000)
        <Alarmtype> other (1) <Polarity>
        (2)
        "
	  ::= { rm10010mpAlmclientModuleState 5 }



rm10010mpAlmCfpTxOff OBJECT-TYPE
	  SYNTAX EkiOnOff
	  MAX-ACCESS read-only
	  STATUS current
	  DESCRIPTION
        "
        Client Trscv Laser Shutdown :This
        OID indicates the Client Trscv
         Laser is OFF <Help> Status indicating
        the Client Trscv Laser is OFF <Condtype>
        CFP_TX_OFF <Probcause> informationalStatus(1000)
        <Alarmtype> other (1) <Polarity>
        (2)
        "
	  ::= { rm10010mpAlmclientModuleState 4 }



rm10010mpAlmCfpHighPowerUp OBJECT-TYPE
	  SYNTAX EkiOnOff
	  MAX-ACCESS read-only
	  STATUS current
	  DESCRIPTION
        "
        Client Trscv High Power Up :This
        OID indicates the Client Trscv
         is leaving Low Power state <Help>
        Status indicating the Client Trscv
        is leaving Low Power state <Condtype>
        CFP_HIGH_POWER_UP <Probcause> informationalStatus(1000)
        <Alarmtype> other (1) <Polarity>
        (2)
        "
	  ::= { rm10010mpAlmclientModuleState 3 }



rm10010mpAlmCfpLowPower OBJECT-TYPE
	  SYNTAX EkiOnOff
	  MAX-ACCESS read-only
	  STATUS current
	  DESCRIPTION
        "
        Client Trscv Low Power :This OID
        indicates the Client Trscv is in
        low power state <Help> Status indicating
        the Client Trscv is in low power
        state <Condtype> CFP_LOW_POWER
         <Probcause> informationalStatus(1000)
        <Alarmtype> other (1) <Polarity>
        (2)
        "
	  ::= { rm10010mpAlmclientModuleState 2 }



rm10010mpAlmCfpInitialize OBJECT-TYPE
	  SYNTAX EkiOnOff
	  MAX-ACCESS read-only
	  STATUS current
	  DESCRIPTION
        "
        Client Trscv Initialize :This
         OID indicates the Client Trscv
        initialization is in progress <Help>
        Status indicating the Client Trscv
        initialization is in progress <Condtype>
        CFP_INITIALIZE <Probcause> informationalStatus(1000)
        <Alarmtype> other (1) <Polarity>
        (2)
        "
	  ::= { rm10010mpAlmclientModuleState 1 }



--- *****************************************************
---     LEAF for the clientModuleGeneralStatus article
--- *****************************************************
rm10010mpAlmclientModuleGeneralStatus OBJECT IDENTIFIER ::= { rm10010mpAlmOtherCrit 41 }




rm10010mpAlmCfpHwInterlock OBJECT-TYPE
	  SYNTAX EkiOnOff
	  MAX-ACCESS read-only
	  STATUS current
	  DESCRIPTION
        "
        Client Trscv Hardware Interlock
        :This OID indicates the Client
         Trscv power is higher than the
        cooling capacity <Help> Alarm indicating
        the Client Trscv power is higher
        than the cooling capacity <Condtype>
        CFP_HW_INTERLOCK <Probcause> temperatureUnacceptable
        (51) <Alarmtype> equipmentAlarm
        (5) <Polarity> (2)
        "
	  ::= { rm10010mpAlmclientModuleGeneralStatus 14 }



rm10010mpAlmCfpLossOfRefclk OBJECT-TYPE
	  SYNTAX EkiOnOff
	  MAX-ACCESS read-only
	  STATUS current
	  DESCRIPTION
        "
        Client Trscv Loss Of Ref Clock
        :This OID indicates a Loss of Reference
        clock is detected on the Client
        Trscv <Help> Alarm indicating a
        Loss of Reference clock is detected
        on the Client Trscv <Condtype>
         CFP_LOSS_OF_REFCLK <Probcause>
        inputOutputDeviceError (24) <Alarmtype>
        equipmentAlarm (5) <Polarity> (2)
        "
	  ::= { rm10010mpAlmclientModuleGeneralStatus 11 }



rm10010mpAlmCfpTxJitterPllLol OBJECT-TYPE
	  SYNTAX EkiOnOff
	  MAX-ACCESS read-only
	  STATUS current
	  DESCRIPTION
        "
        Client Trscv Tx Jitter PLL Loss
        Of Lock :This OID indicates a Tx
        Jitter PLL Loss of Lock is dtected
        on the Client Trscv <Help> Alarm
        indicating a Tx Jitter PLL Loss
        of Lock is dtected on the Client
        Trscv <Condtype> CFP_TX_JITTER_PLL_LOL
        <Probcause> inputOutputDeviceError
        (24) <Alarmtype> equipmentAlarm
        (5) <Polarity> (2)
        "
	  ::= { rm10010mpAlmclientModuleGeneralStatus 10 }



rm10010mpAlmCfpTxCmuLol OBJECT-TYPE
	  SYNTAX EkiOnOff
	  MAX-ACCESS read-only
	  STATUS current
	  DESCRIPTION
        "
        Client Trscv CMU Loss Of Lock
         :This OID indicates a Clock Multiplier
        Unit Loss of Lock is detected on
        the Client Trscv <Help> Alarm indicating
        a Clock Multiplier Unit Loss of
        Lock is detected on the Client
         Trscv <Condtype> CFP_TX_CMU_LOL
        <Probcause> inputOutputDeviceError
        (24) <Alarmtype> equipmentAlarm
        (5) <Polarity> (2)
        "
	  ::= { rm10010mpAlmclientModuleGeneralStatus 9 }



rm10010mpAlmCfpTxLosf OBJECT-TYPE
	  SYNTAX EkiOnOff
	  MAX-ACCESS read-only
	  STATUS current
	  DESCRIPTION
        "
        Client Trscv Loss Of Signal Functionality
        :This OID indicates a Loss of Signal
        functionality is detected on the
        Client Trscv <Help> Alarm indicating
        a Loss of Signal functionality
         is detected on the Client Trscv
        <Condtype> CFP_TX_LOSF <Probcause>
        lossOfSignal (30) <Alarmtype> equipmentAlarm
        (5) <Polarity> (2)
        "
	  ::= { rm10010mpAlmclientModuleGeneralStatus 8 }



rm10010mpAlmCfpTxHostLol OBJECT-TYPE
	  SYNTAX EkiOnOff
	  MAX-ACCESS read-only
	  STATUS current
	  DESCRIPTION
        "
        Client Trscv Tx Host Loss Of Lock
        :This OID indicates of Loss of
         Lock is detected on the Client
        Trscv Tx Host interface <Help>
         Alarm indicating of Loss of Lock
        is detected on the Client Trscv
        Tx Host interface <Condtype> CFP_TX_HOST_LOL
        <Probcause> receiverFailure (42)
        <Alarmtype> equipmentAlarm (5)
         <Polarity> (2)
        "
	  ::= { rm10010mpAlmclientModuleGeneralStatus 7 }



rm10010mpAlmCfpRxLos OBJECT-TYPE
	  SYNTAX EkiOnOff
	  MAX-ACCESS read-only
	  STATUS current
	  DESCRIPTION
        "
        Client Trscv Loss Of Signal :This
        OID indicates a Loss of Signal
         is detected on the Client Trscv
        <Help> Alarm indicating a Loss
         of Signal is detected on the Client
        Trscv <Condtype> CFP_RX_LOS <Probcause>
        lossOfSignal (30) <Alarmtype> equipmentAlarm
        (5) <Polarity> (2)
        "
	  ::= { rm10010mpAlmclientModuleGeneralStatus 6 }



rm10010mpAlmCfpRxNetworkLol OBJECT-TYPE
	  SYNTAX EkiOnOff
	  MAX-ACCESS read-only
	  STATUS current
	  DESCRIPTION
        "
        Client Trscv Rx Network Loss Of
        Lock :This OID indicates of Loss
        of Lock is dected on the Client
        Trscv Rx Network interface <Help>
        Alarm indicating of Loss of Lock
        is dected on the Client Trscv Rx
        Network interface <Condtype> CFP_RX_NETWORK_LOL
        <Probcause> receiverFailure (42)
        <Alarmtype> equipmentAlarm (5)
         <Polarity> (2)
        "
	  ::= { rm10010mpAlmclientModuleGeneralStatus 5 }



rm10010mpAlmCfpOutOfAlignment OBJECT-TYPE
	  SYNTAX EkiOnOff
	  MAX-ACCESS read-only
	  STATUS current
	  DESCRIPTION
        "
        Client Trscv Out Of Alignment
         :This OID indicates an Out of
         alignment on the Client Trscv
         Host Interface <Help> Alarm indicating
        an Out of alignment on the Client
        Trscv Host Interface <Condtype>
        CFP_OUT_OF_ALIGNMENT <Probcause>
        receiverFailure (42) <Alarmtype>
        equipmentAlarm (5) <Polarity> (2)
        "
	  ::= { rm10010mpAlmclientModuleGeneralStatus 4 }



--- *****************************************************
---     LEAF for the clientGlobalAlarmSummary article
--- *****************************************************
rm10010mpAlmclientGlobalAlarmSummary OBJECT IDENTIFIER ::= { rm10010mpAlmOtherCrit 42 }




rm10010mpAlmCfpGlobAlarmAssertion  OBJECT-TYPE
	  SYNTAX EkiOnOff
	  MAX-ACCESS read-only
	  STATUS current
	  DESCRIPTION
        "
        Client Trscv Global Alarm :This
        OID indicates at least one  Fault
        or Status is detected on the Client
        Trscv module <Help> Synthesis alarm
        indicating at least one Alarm,
         Warning, Fault or Status is detected
        on the Client Trscv module <Condtype>
        CFP_GLOB_ALARM_ASSERTION  <Probcause>
        informationalStatus(1000) <Alarmtype>
        other (1) <Polarity> (2)
        "
	  ::= { rm10010mpAlmclientGlobalAlarmSummary 16 }



rm10010mpAlmCfpHostLaneFaultStatus  OBJECT-TYPE
	  SYNTAX EkiOnOff
	  MAX-ACCESS read-only
	  STATUS current
	  DESCRIPTION
        "
        Client Trscv Host Fault And Status
        :This OID indicates at least one
        Fault or Status is detected on
         the Client Trscv Host Interface
        <Help> Synthesis alarm indicating
        at least one Fault or Status is
        detected on the Client Trscv Host
        Interface <Condtype> CFP_HOST_LANE_FAULT_STATUS
         <Probcause> informationalStatus(1000)
        <Alarmtype> other (1) <Polarity>
        (2)
        "
	  ::= { rm10010mpAlmclientGlobalAlarmSummary 15 }



rm10010mpAlmCfpNetworkLaneFaultStatus  OBJECT-TYPE
	  SYNTAX EkiOnOff
	  MAX-ACCESS read-only
	  STATUS current
	  DESCRIPTION
        "
        Client Trscv Network Fault And
        Status :This OID indicates at least
        one Fault or Status is detected
        on the Client Trscv Network Interface
        <Help> Synthesis alarm indicating
        at least one Fault or Status is
        detected on the Client Trscv Network
        Interface <Condtype> CFP_NETWORK_LANE_FAULT_STATUS
         <Probcause> informationalStatus(1000)
        <Alarmtype> other (1) <Polarity>
        (2)
        "
	  ::= { rm10010mpAlmclientGlobalAlarmSummary 14 }



rm10010mpAlmCfpNetworkLaneAlarmWarning1 OBJECT-TYPE
	  SYNTAX EkiOnOff
	  MAX-ACCESS read-only
	  STATUS current
	  DESCRIPTION
        "
        Client Trscv Network Alarm And
        Warning 1 :This OID indicates at
        least one DDM  is detected on the
        Client Trscv Network Interface
         <Help> Synthesis alarm indicating
        at least one DDM Alarm or DDM Warning
        is detected on the Client Trscv
        Network Interface <Condtype> CFP_NETWORK_LANE_ALARM_WARNING_1
        <Probcause> informationalStatus(1000)
        <Alarmtype> other (1) <Polarity>
        (2)
        "
	  ::= { rm10010mpAlmclientGlobalAlarmSummary 13 }



rm10010mpAlmCfpModuleAlarmWarning2 OBJECT-TYPE
	  SYNTAX EkiOnOff
	  MAX-ACCESS read-only
	  STATUS current
	  DESCRIPTION
        "
        Client Trscv Module Alarm And
         Warning 2 :This OID indicates
         at least one DDM is detected on
        the Client Trscv module <Help>
         Synthesis alarm indicating at
         least one DDM Alarm or DDM Warning
        is detected on the Client Trscv
        module <Condtype> CFP_MODULE_ALARM_WARNING_2
        <Probcause> informationalStatus(1000)
        <Alarmtype> other (1) <Polarity>
        (2)
        "
	  ::= { rm10010mpAlmclientGlobalAlarmSummary 12 }



rm10010mpAlmCfpModuleAlarmWarning1  OBJECT-TYPE
	  SYNTAX EkiOnOff
	  MAX-ACCESS read-only
	  STATUS current
	  DESCRIPTION
        "
        Client Trscv Module Alarm And
         Warning 1 :This OID indicates
         at least one DDM  This OID is
         detected on the Client Trscv module
        <Help> Synthesis alarm indicating
        at least one DDM Alarm or DDM Warning
        is detected on the Client Trscv
        module <Condtype> CFP_MODULE_ALARM_WARNING_1
         <Probcause> informationalStatus(1000)
        <Alarmtype> other (1) <Polarity>
        (2)
        "
	  ::= { rm10010mpAlmclientGlobalAlarmSummary 11 }



rm10010mpAlmCfpModuleFault  OBJECT-TYPE
	  SYNTAX EkiOnOff
	  MAX-ACCESS read-only
	  STATUS current
	  DESCRIPTION
        "
        Client Trscv Module Fault :This
        OID indicates at least one Fault
        is detected on the Client Trscv
        module <Help> Synthesis alarm indicating
        at least one Fault is detected
         on the Client Trscv module <Condtype>
        CFP_MODULE_FAULT  <Probcause> informationalStatus(1000)
        <Alarmtype> other (1) <Polarity>
        (2)
        "
	  ::= { rm10010mpAlmclientGlobalAlarmSummary 10 }



rm10010mpAlmCfpModuleGeneralStatus  OBJECT-TYPE
	  SYNTAX EkiOnOff
	  MAX-ACCESS read-only
	  STATUS current
	  DESCRIPTION
        "
        Client Trscv General Status :This
        OID indicates the Client Trscv
         module general status <Help> Synthesis
        alarm indicating the Client Trscv
        module general status <Condtype>
        CFP_MODULE_GENERAL_STATUS  <Probcause>
        informationalStatus(1000) <Alarmtype>
        other (1) <Polarity> (2)
        "
	  ::= { rm10010mpAlmclientGlobalAlarmSummary 9 }



rm10010mpAlmCfpModuleState  OBJECT-TYPE
	  SYNTAX EkiOnOff
	  MAX-ACCESS read-only
	  STATUS current
	  DESCRIPTION
        "
        Client Trscv Module State :This
        OID indicates the Client Trscv
         module state <Help> Synthesis
         alarm indicating the Client Trscv
        module state <Condtype> CFP_MODULE_STATE
         <Probcause> informationalStatus(1000)
        <Alarmtype> other (1) <Polarity>
        (2)
        "
	  ::= { rm10010mpAlmclientGlobalAlarmSummary 8 }



rm10010mpAlmCfpNetworkLaneAlarmWarning2 OBJECT-TYPE
	  SYNTAX EkiOnOff
	  MAX-ACCESS read-only
	  STATUS current
	  DESCRIPTION
        "
        Client Trscv Network Alarm And
        Warning 2 :This OID indicates at
        least one DDM is detected on the
        Client Trscv Network Interface
         <Help> Synthesis alarm indicating
        at least one DDM Alarm or DDM Warning
        is detected on the Client Trscv
        Network Interface <Condtype> CFP_NETWORK_LANE_ALARM_WARNING_2
        <Probcause> informationalStatus(1000)
        <Alarmtype> other (1) <Polarity>
        (2)
        "
	  ::= { rm10010mpAlmclientGlobalAlarmSummary 7 }



rm10010mpAlmCfpSoftGlobAlarmTest  OBJECT-TYPE
	  SYNTAX EkiOnOff
	  MAX-ACCESS read-only
	  STATUS current
	  DESCRIPTION
        "
        Client Trscv Global Alarm SW Test
        :This OID indicates the Client
         Trscv Global Alarm This OID is
        raised by SW request for test purpose
        <Help> Status indicating the Client
        Trscv Global Alarm is raised by
        SW request for test purpose <Condtype>
        CFP_SOFT_GLOB_ALARM_TEST  <Probcause>
        informationalStatus(1000) <Alarmtype>
        other (1) <Polarity> (2)
        "
	  ::= { rm10010mpAlmclientGlobalAlarmSummary 1 }



--- *****************************************************
---     LEAF for the msaModuleState article
--- *****************************************************
rm10010mpAlmmsaModuleState OBJECT IDENTIFIER ::= { rm10010mpAlmOtherCrit 46 }




rm10010mpAlmMsaHighPowerDown OBJECT-TYPE
	  SYNTAX EkiOnOff
	  MAX-ACCESS read-only
	  STATUS current
	  DESCRIPTION
        "
        Line Trscv High Power Down :This
        OID indicates the Line Trscv is
        entering Low Power state <Help>
        Status indicating the Line Trscv
        is entering Low Power state <Condtype>
        MSA_HIGH_POWER_DOWN <Probcause>
        informationalStatus(1000) <Alarmtype>
        other (1) <Polarity> (2)
        "
	  ::= { rm10010mpAlmmsaModuleState 9 }



rm10010mpAlmMsaTxTurnOff OBJECT-TYPE
	  SYNTAX EkiOnOff
	  MAX-ACCESS read-only
	  STATUS current
	  DESCRIPTION
        "
        Line Trscv Laser Turn Off :This
        OID indicates the Line Trscv is
        turning off its laser <Help> Status
        indicating the Line Trscv is turning
        off its laser <Condtype> MSA_TX_TURN_OFF
        <Probcause> informationalStatus(1000)
        <Alarmtype> other (1) <Polarity>
        (2)
        "
	  ::= { rm10010mpAlmmsaModuleState 8 }



rm10010mpAlmMsaFault OBJECT-TYPE
	  SYNTAX EkiOnOff
	  MAX-ACCESS read-only
	  STATUS current
	  DESCRIPTION
        "
        Line Trscv Fault :This OID indicates
        the Line Trscv is in Fault state
        <Help> Status indicating the Line
        Trscv is in Fault state <Condtype>
        MSA_FAULT <Probcause> informationalStatus(1000)
        <Alarmtype> other (1) <Polarity>
        (2)
        "
	  ::= { rm10010mpAlmmsaModuleState 7 }



rm10010mpAlmMsaReady OBJECT-TYPE
	  SYNTAX EkiOnOff
	  MAX-ACCESS read-only
	  STATUS current
	  DESCRIPTION
        "
        Line Trscv Ready :This OID indicates
        the Line Trscv is ready to operate
        <Help> Status indicating the Line
        Trscv is ready to operate <Condtype>
        MSA_READY <Probcause> informationalStatus(1000)
        <Alarmtype> other (1) <Polarity>
        (2)
        "
	  ::= { rm10010mpAlmmsaModuleState 6 }



rm10010mpAlmMsaTxTurnOn OBJECT-TYPE
	  SYNTAX EkiOnOff
	  MAX-ACCESS read-only
	  STATUS current
	  DESCRIPTION
        "
        Line Trscv Laser Turn On :This
        OID indicates the Line Trscv is
        turning on its laser <Help> Status
        indicating the Line Trscv is turning
        on its laser <Condtype> MSA_TX_TURN_ON
        <Probcause> informationalStatus(1000)
        <Alarmtype> other (1) <Polarity>
        (2)
        "
	  ::= { rm10010mpAlmmsaModuleState 5 }



rm10010mpAlmMsaTxOff OBJECT-TYPE
	  SYNTAX EkiOnOff
	  MAX-ACCESS read-only
	  STATUS current
	  DESCRIPTION
        "
        Line Trscv Laser Shutdown :This
        OID indicates the Line Trscv Laser
        is OFF <Help> Status indicating
        the Line Trscv Laser is OFF <Condtype>
        MSA_TX_OFF <Probcause> informationalStatus(1000)
        <Alarmtype> other (1) <Polarity>
        (2)
        "
	  ::= { rm10010mpAlmmsaModuleState 4 }



rm10010mpAlmMsaHighPowerUp OBJECT-TYPE
	  SYNTAX EkiOnOff
	  MAX-ACCESS read-only
	  STATUS current
	  DESCRIPTION
        "
        Line Trscv High Power Up :This
        OID indicates the Line Trscv is
        leaving Low Power state <Help>
         Status indicating the Line Trscv
        is leaving Low Power state <Condtype>
        MSA_HIGH_POWER_UP <Probcause> informationalStatus(1000)
        <Alarmtype> other (1) <Polarity>
        (2)
        "
	  ::= { rm10010mpAlmmsaModuleState 3 }



rm10010mpAlmMsaLowPower OBJECT-TYPE
	  SYNTAX EkiOnOff
	  MAX-ACCESS read-only
	  STATUS current
	  DESCRIPTION
        "
        Line Trscv Low Power :This OID
        indicates the Line Trscv is in
         low power state <Help> Status
         indicating the Line Trscv is in
        low power state <Condtype> MSA_LOW_POWER
        <Probcause> informationalStatus(1000)
        <Alarmtype> other (1) <Polarity>
        (2)
        "
	  ::= { rm10010mpAlmmsaModuleState 2 }



rm10010mpAlmMsaInitialize OBJECT-TYPE
	  SYNTAX EkiOnOff
	  MAX-ACCESS read-only
	  STATUS current
	  DESCRIPTION
        "
        Line Trscv Initialize :This OID
        indicates the Line Trscv initialization
        is in progress <Help> Status indicating
        the Line Trscv initialization is
        in progress <Condtype> MSA_INITIALIZE
        <Probcause> informationalStatus(1000)
        <Alarmtype> other (1) <Polarity>
        (2)
        "
	  ::= { rm10010mpAlmmsaModuleState 1 }



--- *****************************************************
---     LEAF for the msaModuleGeneralStatus article
--- *****************************************************
rm10010mpAlmmsaModuleGeneralStatus OBJECT IDENTIFIER ::= { rm10010mpAlmOtherCrit 47 }




rm10010mpAlmMsaHwInterlock OBJECT-TYPE
	  SYNTAX EkiOnOff
	  MAX-ACCESS read-only
	  STATUS current
	  DESCRIPTION
        "
        Line Trscv Hardware Interlock
         :This OID indicates the Line Trscv
        power is higher than the cooling
        capacity <Help> Alarm indicating
        the Line Trscv power is higher
         than the cooling capacity <Condtype>
        MSA_HW_INTERLOCK <Probcause> temperatureUnacceptable
        (51) <Alarmtype> equipmentAlarm
        (5) <Polarity> (2)
        "
	  ::= { rm10010mpAlmmsaModuleGeneralStatus 14 }



rm10010mpAlmMsaLossOfRefclk OBJECT-TYPE
	  SYNTAX EkiOnOff
	  MAX-ACCESS read-only
	  STATUS current
	  DESCRIPTION
        "
        Line Trscv Loss Of Ref Clock :This
        OID indicates a Loss of Reference
        clock is detected on the Line Trscv
        <Help> Alarm indicating a Loss
         of Reference clock is detected
        on the Line Trscv <Condtype> MSA_LOSS_OF_REFCLK
        <Probcause> inputOutputDeviceError
        (24) <Alarmtype> equipmentAlarm
        (5) <Polarity> (2)
        "
	  ::= { rm10010mpAlmmsaModuleGeneralStatus 11 }



rm10010mpAlmMsaTxJitterPllLol OBJECT-TYPE
	  SYNTAX EkiOnOff
	  MAX-ACCESS read-only
	  STATUS current
	  DESCRIPTION
        "
        Line Trscv Tx Jitter PLL Loss
         Of Lock :This OID indicates a
         Tx Jitter PLL Loss of Lock is
         detected on the Line Trscv <Help>
        Alarm indicating a Tx Jitter PLL
        Loss of Lock is detected on the
        Line Trscv <Condtype> MSA_TX_JITTER_PLL_LOL
        <Probcause> inputOutputDeviceError
        (24) <Alarmtype> equipmentAlarm
        (5) <Polarity> (2)
        "
	  ::= { rm10010mpAlmmsaModuleGeneralStatus 10 }



rm10010mpAlmMsaTxCmuLol OBJECT-TYPE
	  SYNTAX EkiOnOff
	  MAX-ACCESS read-only
	  STATUS current
	  DESCRIPTION
        "
        Line Trscv CMU Loss Of Lock :This
        OID indicates a Clock Multiplier
        Unit Loss of Lock is detected on
        the Line Trscv <Help> Alarm indicating
        a Clock Multiplier Unit Loss of
        Lock is detected on the Line Trscv
        <Condtype> MSA_TX_CMU_LOL <Probcause>
        inputOutputDeviceError (24) <Alarmtype>
        equipmentAlarm (5) <Polarity> (2)
        "
	  ::= { rm10010mpAlmmsaModuleGeneralStatus 9 }



rm10010mpAlmMsaTxLosf OBJECT-TYPE
	  SYNTAX EkiOnOff
	  MAX-ACCESS read-only
	  STATUS current
	  DESCRIPTION
        "
        Line Trscv Loss Of Signal Functionality
        :This OID indicates a Loss of Signal
        functionality is detected on the
        Line Trscv <Help> Alarm indicating
        a Loss of Signal functionality
         is detected on the Line Trscv
         <Condtype> MSA_TX_LOSF <Probcause>
        lossOfSignal (30) <Alarmtype> equipmentAlarm
        (5) <Polarity> (2)
        "
	  ::= { rm10010mpAlmmsaModuleGeneralStatus 8 }



rm10010mpAlmMsaTxHostLol OBJECT-TYPE
	  SYNTAX EkiOnOff
	  MAX-ACCESS read-only
	  STATUS current
	  DESCRIPTION
        "
        Line Trscv Tx Host Loss Of Lock
        :This OID indicates of Loss of
         Lock is detected on the Line Trscv
        Tx Host interface <Help> Alarm
         indicating of Loss of Lock is
         detected on the Line Trscv Tx
         Host interface <Condtype> MSA_TX_HOST_LOL
        <Probcause> receiverFailure (42)
        <Alarmtype> equipmentAlarm (5)
         <Polarity> (2)
        "
	  ::= { rm10010mpAlmmsaModuleGeneralStatus 7 }



rm10010mpAlmMsaRxLos OBJECT-TYPE
	  SYNTAX EkiOnOff
	  MAX-ACCESS read-only
	  STATUS current
	  DESCRIPTION
        "
        Line Trscv Loss Of Signal :This
        OID indicates a Loss of Signal
         is detected on the Line Trscv
         <Help> Alarm indicating a Loss
        of Signal is detected on the Line
        Trscv <Condtype> MSA_RX_LOS <Probcause>
        lossOfSignal (30) <Alarmtype> equipmentAlarm
        (5) <Polarity> (2)
        "
	  ::= { rm10010mpAlmmsaModuleGeneralStatus 6 }



rm10010mpAlmMsaRxNetworkLol OBJECT-TYPE
	  SYNTAX EkiOnOff
	  MAX-ACCESS read-only
	  STATUS current
	  DESCRIPTION
        "
        Line Trscv Rx Network Loss Of
         Lock :This OID indicates of Loss
        of Lock is detected on the Line
        Trscv Rx Network interface <Help>
        Alarm indicating of Loss of Lock
        is detected on the Line Trscv Rx
        Network interface <Condtype> MSA_RX_NETWORK_LOL
        <Probcause> receiverFailure (42)
        <Alarmtype> equipmentAlarm (5)
         <Polarity> (2)
        "
	  ::= { rm10010mpAlmmsaModuleGeneralStatus 5 }



rm10010mpAlmMsaOutOfAlignment OBJECT-TYPE
	  SYNTAX EkiOnOff
	  MAX-ACCESS read-only
	  STATUS current
	  DESCRIPTION
        "
        Line Trscv Out Of Alignment :This
        OID indicates an Out of alignment
        on the Line Trscv Host Interface
        <Help> Alarm indicating an Out
         of alignment on the Line Trscv
        Host Interface <Condtype> MSA_OUT_OF_ALIGNMENT
        <Probcause> receiverFailure (42)
        <Alarmtype> equipmentAlarm (5)
         <Polarity> (2)
        "
	  ::= { rm10010mpAlmmsaModuleGeneralStatus 4 }



--- *****************************************************
---     LEAF for the msaGlobalAlarmSummary article
--- *****************************************************
rm10010mpAlmmsaGlobalAlarmSummary OBJECT IDENTIFIER ::= { rm10010mpAlmOtherCrit 48 }




rm10010mpAlmMsaGlobAlarmAssertion  OBJECT-TYPE
	  SYNTAX EkiOnOff
	  MAX-ACCESS read-only
	  STATUS current
	  DESCRIPTION
        "
        Line Trscv Global Alarm :This
         OID indicates at least one Fault
        or Status is detected on the Line
        Trscv module <Help> Synthesis alarm
        indicating at least one Alarm,
         Warning, Fault or Status is detected
        on the Line Trscv module <Condtype>
        MSA_GLOB_ALARM_ASSERTION  <Probcause>
        informationalStatus(1000) <Alarmtype>
        other (1) <Polarity> (2)
        "
	  ::= { rm10010mpAlmmsaGlobalAlarmSummary 16 }



rm10010mpAlmMsaHostLaneFaultStatus  OBJECT-TYPE
	  SYNTAX EkiOnOff
	  MAX-ACCESS read-only
	  STATUS current
	  DESCRIPTION
        "
        Line Trscv Host Fault And Status
        :This OID indicates at least one
        Fault or Status is detected on
         the Line Trscv Host Interface
         <Help> Synthesis alarm indicating
        at least one Fault or Status is
        detected on the Line Trscv Host
        Interface <Condtype> MSA_HOST_LANE_FAULT_STATUS
         <Probcause> informationalStatus(1000)
        <Alarmtype> other (1) <Polarity>
        (2)
        "
	  ::= { rm10010mpAlmmsaGlobalAlarmSummary 15 }



rm10010mpAlmMsaNetworkLaneFaultStatus  OBJECT-TYPE
	  SYNTAX EkiOnOff
	  MAX-ACCESS read-only
	  STATUS current
	  DESCRIPTION
        "
        Line Trscv Network Fault And Status
        :This OID indicates at least one
        Fault or Status is detected on
         the Line Trscv Network Interface
        <Help> Synthesis alarm indicating
        at least one Fault or Status is
        detected on the Line Trscv Network
        Interface <Condtype> MSA_NETWORK_LANE_FAULT_STATUS
         <Probcause> informationalStatus(1000)
        <Alarmtype> other (1) <Polarity>
        (2)
        "
	  ::= { rm10010mpAlmmsaGlobalAlarmSummary 14 }



rm10010mpAlmMsaNetworkLaneAlarmWarning1 OBJECT-TYPE
	  SYNTAX EkiOnOff
	  MAX-ACCESS read-only
	  STATUS current
	  DESCRIPTION
        "
        Line Trscv Network Alarm And Warning
        1 :This OID indicates at least
         one DDM is detected on the Line
        Trscv Network Interface <Help>
         Synthesis alarm indicating at
         least one DDM Alarm or DDM Warning
        is detected on the Line Trscv Network
        Interface <Condtype> MSA_NETWORK_LANE_ALARM_WARNING_1
        <Probcause> informationalStatus(1000)
        <Alarmtype> other (1) <Polarity>
        (2)
        "
	  ::= { rm10010mpAlmmsaGlobalAlarmSummary 13 }



rm10010mpAlmMsaModuleAlarmWarning2 OBJECT-TYPE
	  SYNTAX EkiOnOff
	  MAX-ACCESS read-only
	  STATUS current
	  DESCRIPTION
        "
        Line Trscv Module Alarm And Warning
        2 :This OID indicates at least
         one DDM is detected on the Line
        Trscv module <Help> Synthesis alarm
        indicating at least one DDM Alarm
        or DDM Warning is detected on the
        Line Trscv module <Condtype> MSA_MODULE_ALARM_WARNING_2
        <Probcause> informationalStatus(1000)
        <Alarmtype> other (1) <Polarity>
        (2)
        "
	  ::= { rm10010mpAlmmsaGlobalAlarmSummary 12 }



rm10010mpAlmMsaModuleAlarmWarning1  OBJECT-TYPE
	  SYNTAX EkiOnOff
	  MAX-ACCESS read-only
	  STATUS current
	  DESCRIPTION
        "
        Line Trscv Module Alarm And Warning
        1 :This OID indicates at least
         one DDM is detected on the Line
        Trscv module <Help> Synthesis alarm
        indicating at least one DDM Alarm
        or DDM Warning is detected on the
        Line Trscv module <Condtype> MSA_MODULE_ALARM_WARNING_1
         <Probcause> informationalStatus(1000)
        <Alarmtype> other (1) <Polarity>
        (2)
        "
	  ::= { rm10010mpAlmmsaGlobalAlarmSummary 11 }



rm10010mpAlmModuleFault  OBJECT-TYPE
	  SYNTAX EkiOnOff
	  MAX-ACCESS read-only
	  STATUS current
	  DESCRIPTION
        "
        Line Trscv Module Fault :This
         OID indicates at least one Fault
        is detected on the Line Trscv module
        <Help> Synthesis alarm indicating
        at least one Fault is detected
         on the Line Trscv module <Condtype>
        MODULE_FAULT  <Probcause> informationalStatus(1000)
        <Alarmtype> other (1) <Polarity>
        (2)
        "
	  ::= { rm10010mpAlmmsaGlobalAlarmSummary 10 }



rm10010mpAlmMsaModuleGeneralStatus  OBJECT-TYPE
	  SYNTAX EkiOnOff
	  MAX-ACCESS read-only
	  STATUS current
	  DESCRIPTION
        "
        Line Trscv General Status :This
        OID indicates the Line Trscv module
        general <Help> Synthesis alarm
         indicating the Line Trscv module
        general status <Condtype> MSA_MODULE_GENERAL_STATUS
         <Probcause> informationalStatus(1000)
        <Alarmtype> other (1) <Polarity>
        (2)
        "
	  ::= { rm10010mpAlmmsaGlobalAlarmSummary 9 }



rm10010mpAlmMsaModuleState  OBJECT-TYPE
	  SYNTAX EkiOnOff
	  MAX-ACCESS read-only
	  STATUS current
	  DESCRIPTION
        "
        Line Trscv Module State :This
         OID indicates the Line Trscv module
        state <Help> Synthesis alarm indicating
        the Line Trscv module state <Condtype>
        MSA_MODULE_STATE  <Probcause> informationalStatus(1000)
        <Alarmtype> other (1) <Polarity>
        (2)
        "
	  ::= { rm10010mpAlmmsaGlobalAlarmSummary 8 }



rm10010mpAlmMsaNetworkLaneAlarmWarning2 OBJECT-TYPE
	  SYNTAX EkiOnOff
	  MAX-ACCESS read-only
	  STATUS current
	  DESCRIPTION
        "
        Line Trscv Network Alarm And Warning
        2 :This OID indicates at least
         one DDM This OID is detected on
        the Line Trscv Network Interface
        <Help> Synthesis alarm indicating
        at least one DDM Alarm or DDM Warning
        is detected on the Line Trscv Network
        Interface <Condtype> MSA_NETWORK_LANE_ALARM_WARNING_2
        <Probcause> informationalStatus(1000)
        <Alarmtype> other (1) <Polarity>
        (2)
        "
	  ::= { rm10010mpAlmmsaGlobalAlarmSummary 7 }



rm10010mpAlmMsaNetworkHostAlarmStatus OBJECT-TYPE
	  SYNTAX EkiOnOff
	  MAX-ACCESS read-only
	  STATUS current
	  DESCRIPTION
        "
        Line Trscv Network/Host Alarm
         Status :This OID indicates the
        state of the Network and Host interface
        of the Line Trscv <Help> Synthesis
        alarm indicating the alarm state
        of the Network and Host interface
        of the Line Trscv <Condtype> MSA_NETWORK_HOST_ALARM_STATUS
        <Probcause> informationalStatus(1000)
        <Alarmtype> other (1) <Polarity>
        (2)
        "
	  ::= { rm10010mpAlmmsaGlobalAlarmSummary 6 }



rm10010mpAlmMsaSoftGlobAlarmTest  OBJECT-TYPE
	  SYNTAX EkiOnOff
	  MAX-ACCESS read-only
	  STATUS current
	  DESCRIPTION
        "
        Line Trscv Global Alarm SW Test
        :This OID indicates the Line Trscv
        Global alarm This OID is raised
        by SW request for test purpose
         <Help> Status indicating the Line
        Trscv Global Alarm is raised by
        SW request for test purpose <Condtype>
        MSA_SOFT_GLOB_ALARM_TEST  <Probcause>
        informationalStatus(1000) <Alarmtype>
        other (1) <Polarity> (2)
        "
	  ::= { rm10010mpAlmmsaGlobalAlarmSummary 1 }



--- *****************************************************
---     LEAF for the msaNetworkTxAlignment article
--- *****************************************************
rm10010mpAlmmsaNetworkTxAlignment OBJECT IDENTIFIER ::= { rm10010mpAlmOtherCrit 49 }




rm10010mpAlmNetTxLossOfAlignment OBJECT-TYPE
	  SYNTAX EkiOnOff
	  MAX-ACCESS read-only
	  STATUS current
	  DESCRIPTION
        "
        Line Trscv Network Tx Loss Of
         Alignment :This OID indicates
         a Tx Loss of Alignment is detected
        on the Line Trscv Network interface
        <Help> Alarm indicating a Tx Loss
        of Alignment is detected on the
        Line Trscv Network interface <Condtype>
        NET_TX_LOSS_OF_ALIGNMENT <Probcause>
        transmitterFailure (56) <Alarmtype>
        equipmentAlarm (5) <Polarity> (2)
        "
	  ::= { rm10010mpAlmmsaNetworkTxAlignment 16 }



rm10010mpAlmNetTxOutOfAlignment OBJECT-TYPE
	  SYNTAX EkiOnOff
	  MAX-ACCESS read-only
	  STATUS current
	  DESCRIPTION
        "
        Line Trscv Network Tx Out Of Alignment
        :This OID indicates a Tx Out of
        Alignment is detected on the Line
        Trscv Network interface <Help>
         Alarm indicating a Tx Out of Alignment
        is detected on the Line Trscv Network
        interface <Condtype> NET_TX_OUT_OF_ALIGNMENT
        <Probcause> transmitterFailure
         (56) <Alarmtype> equipmentAlarm
        (5) <Polarity> (2)
        "
	  ::= { rm10010mpAlmmsaNetworkTxAlignment 15 }



rm10010mpAlmNetTxCmuLockFault OBJECT-TYPE
	  SYNTAX EkiOnOff
	  MAX-ACCESS read-only
	  STATUS current
	  DESCRIPTION
        "
        Line Trscv Network Tx CMU Lock
        Fault :This OID indicates a Tx
         Clock Multiplier Unit Lock Fault
        is detected on the Line Trscv Network
        interface <Help> Alarm indicating
        a Tx Clock Multiplier Unit Lock
        Fault is detected on the Line Trscv
        Network interface <Condtype> NET_TX_CMU_LOCK_FAULT
        <Probcause> transmitterFailure
         (56) <Alarmtype> equipmentAlarm
        (5) <Polarity> (2)
        "
	  ::= { rm10010mpAlmmsaNetworkTxAlignment 14 }



rm10010mpAlmNetTxReferenceClockFault OBJECT-TYPE
	  SYNTAX EkiOnOff
	  MAX-ACCESS read-only
	  STATUS current
	  DESCRIPTION
        "
        Line Trscv Network Tx Ref Clock
        Fault :This OID indicates a Tx
         Reference Clock Fault is detected
        on the Line Trscv Network interface
        <Help> Alarm indicating a Tx Reference
        Clock Fault is detected on the
         Line Trscv Network interface <Condtype>
        NET_TX_REFERENCE_CLOCK_FAULT <Probcause>
        transmitterFailure (56) <Alarmtype>
        equipmentAlarm (5) <Polarity> (2)
        "
	  ::= { rm10010mpAlmmsaNetworkTxAlignment 13 }



rm10010mpAlmNetTxTimingFault OBJECT-TYPE
	  SYNTAX EkiOnOff
	  MAX-ACCESS read-only
	  STATUS current
	  DESCRIPTION
        "
        Line Trscv Network Tx Timing Fault
        :This OID indicates a Tx Timing
        Fault is detected on the Line Trscv
        Network interface <Help> Alarm
         indicating a Tx Timing Fault is
        detected on the Line Trscv Network
        interface <Condtype> NET_TX_TIMING_FAULT
        <Probcause> transmitterFailure
         (56) <Alarmtype> equipmentAlarm
        (5) <Polarity> (2)
        "
	  ::= { rm10010mpAlmmsaNetworkTxAlignment 12 }



--- *****************************************************
---     LEAF for the msaNetworkRxAlignment article
--- *****************************************************
rm10010mpAlmmsaNetworkRxAlignment OBJECT IDENTIFIER ::= { rm10010mpAlmOtherCrit 50 }




rm10010mpAlmNetRxModemSyncDetectFault OBJECT-TYPE
	  SYNTAX EkiOnOff
	  MAX-ACCESS read-only
	  STATUS current
	  DESCRIPTION
        "
        Line Trscv Network Rx Modem Sync
        Detect Fault :This OID indicates
        a Rx Modem Synchronisation Detection
        Fault is detected on the Line Trscv
        Network interface <Help> Alarm
         indicating a Rx Modem Synchronisation
        Detection Fault is detected on
         the Line Trscv Network interface
        <Condtype> NET_RX_MODEM_SYNC_DETECT_FAULT
        <Probcause> receiverFailure (42)
        <Alarmtype> equipmentAlarm (5)
         <Polarity> (2)
        "
	  ::= { rm10010mpAlmmsaNetworkRxAlignment 16 }



rm10010mpAlmNetRxModemLockFault OBJECT-TYPE
	  SYNTAX EkiOnOff
	  MAX-ACCESS read-only
	  STATUS current
	  DESCRIPTION
        "
        Line Trscv Network Rx Modem Lock
        Fault :This OID indicates a Rx
         Modem Lock Fault is detected on
        the Line Trscv Network interface
        <Help> Alarm indicating a Rx Modem
        Lock Fault is detected on the Line
        Trscv Network interface <Condtype>
        NET_RX_MODEM_LOCK_FAULT <Probcause>
        receiverFailure (42) <Alarmtype>
        equipmentAlarm (5) <Polarity> (2)
        "
	  ::= { rm10010mpAlmmsaNetworkRxAlignment 15 }



rm10010mpAlmNetRxLossOfAlignment OBJECT-TYPE
	  SYNTAX EkiOnOff
	  MAX-ACCESS read-only
	  STATUS current
	  DESCRIPTION
        "
        Line Trscv Network Rx Loss Of
         Alignment :This OID indicates
         a Rx Loss of Alignment is detected
        on the Line Trscv Network interface
        <Help> Alarm indicating a Rx Loss
        of Alignment is detected on the
        Line Trscv Network interface <Condtype>
        NET_RX_LOSS_OF_ALIGNMENT <Probcause>
        receiverFailure (42) <Alarmtype>
        equipmentAlarm (5) <Polarity> (2)
        "
	  ::= { rm10010mpAlmmsaNetworkRxAlignment 14 }



rm10010mpAlmNetRxOutOfAlignment OBJECT-TYPE
	  SYNTAX EkiOnOff
	  MAX-ACCESS read-only
	  STATUS current
	  DESCRIPTION
        "
        Line Trscv Network Rx Out Of Alignment
        :This OID indicates a Rx Out of
        Alignment is detected on the Line
        Trscv Network interface <Help>
         Alarm indicating a Rx Out of Alignment
        is detected on the Line Trscv Network
        interface <Condtype> NET_RX_OUT_OF_ALIGNMENT
        <Probcause> receiverFailure (42)
        <Alarmtype> equipmentAlarm (5)
         <Polarity> (2)
        "
	  ::= { rm10010mpAlmmsaNetworkRxAlignment 13 }



rm10010mpAlmNetRxTimingFault OBJECT-TYPE
	  SYNTAX EkiOnOff
	  MAX-ACCESS read-only
	  STATUS current
	  DESCRIPTION
        "
        Line Trscv Network Rx Timing Fault
        :This OID indicates a Rx Timing
        Fault is detected on the Line Trscv
        Network interface <Help> Alarm
         indicating a Rx Timing Fault is
        detected on the Line Trscv Network
        interface <Condtype> NET_RX_TIMING_FAULT
        <Probcause> receiverFailure (42)
        <Alarmtype> equipmentAlarm (5)
         <Polarity> (2)
        "
	  ::= { rm10010mpAlmmsaNetworkRxAlignment 12 }



--- *****************************************************
---     LEAF for the msaNetworkHostNetworkAlarmSummary article
--- *****************************************************
rm10010mpAlmmsaNetworkHostNetworkAlarmSummary OBJECT IDENTIFIER ::= { rm10010mpAlmOtherCrit 51 }




rm10010mpAlmHostTxOtnStatus OBJECT-TYPE
	  SYNTAX EkiOnOff
	  MAX-ACCESS read-only
	  STATUS current
	  DESCRIPTION
        "
        Line Trscv Host Tx OTN :This OID
        indicates a Tx OTN Fault is detected
        on the Line Trscv Host interface
        <Help> Synthesis Alarm indicating
        a Tx OTN Fault is detected on the
        Line Trscv Host interface <Condtype>
        HOST_TX_OTN_STATUS <Probcause>
         informationalStatus(1000) <Alarmtype>
        other (1) <Polarity> (2)
        "
	  ::= { rm10010mpAlmmsaNetworkHostNetworkAlarmSummary 16 }



rm10010mpAlmHostTxAlignment OBJECT-TYPE
	  SYNTAX EkiOnOff
	  MAX-ACCESS read-only
	  STATUS current
	  DESCRIPTION
        "
        Line Trscv Host Tx Alignment :This
        OID indicates a Tx Alignment Fault
        is detected on the Line Trscv Host
        interface <Help> Synthesis Alarm
        indicating a Tx Alignment Fault
        is detected on the Line Trscv Host
        interface <Condtype> HOST_TX_ALIGNMENT
        <Probcause> informationalStatus(1000)
        <Alarmtype> other (1) <Polarity>
        (2)
        "
	  ::= { rm10010mpAlmmsaNetworkHostNetworkAlarmSummary 15 }



rm10010mpAlmHostRxAlignment OBJECT-TYPE
	  SYNTAX EkiOnOff
	  MAX-ACCESS read-only
	  STATUS current
	  DESCRIPTION
        "
        Line Trscv Host Rx Alignment :This
        OID indicates a Rx Alignment Fault
        is detected on the Line Trscv Host
        interface <Help> Synthesis Alarm
        indicating a Rx Alignment Fault
        is detected on the Line Trscv Host
        interface <Condtype> HOST_RX_ALIGNMENT
        <Probcause> informationalStatus(1000)
        <Alarmtype> other (1) <Polarity>
        (2)
        "
	  ::= { rm10010mpAlmmsaNetworkHostNetworkAlarmSummary 14 }



rm10010mpAlmNetworkRxOtn OBJECT-TYPE
	  SYNTAX EkiOnOff
	  MAX-ACCESS read-only
	  STATUS current
	  DESCRIPTION
        "
        Line Trscv Network Rx OTN :This
        OID indicates a Rx OTN Fault is
        detected on the Line Trscv Network
        interface <Help> Synthesis Alarm
        indicating a Rx OTN Fault is detected
        on the Line Trscv Network interface
        <Condtype> NETWORK_RX_OTN <Probcause>
        informationalStatus(1000) <Alarmtype>
        other (1) <Polarity> (2)
        "
	  ::= { rm10010mpAlmmsaNetworkHostNetworkAlarmSummary 13 }



rm10010mpAlmNetworkRxAlignment OBJECT-TYPE
	  SYNTAX EkiOnOff
	  MAX-ACCESS read-only
	  STATUS current
	  DESCRIPTION
        "
        Line Trscv Network Rx Alignment
        :This OID indicates a Rx Alignment
        Fault is detected on the Line Trscv
        Network interface <Help> Synthesis
        Alarm indicating a Rx Alignment
        Fault is detected on the Line Trscv
        Network interface <Condtype> NETWORK_RX_ALIGNMENT
        <Probcause> informationalStatus(1000)
        <Alarmtype> other (1) <Polarity>
        (2)
        "
	  ::= { rm10010mpAlmmsaNetworkHostNetworkAlarmSummary 12 }



rm10010mpAlmNetworkTxAlignment OBJECT-TYPE
	  SYNTAX EkiOnOff
	  MAX-ACCESS read-only
	  STATUS current
	  DESCRIPTION
        "
        Line Trscv Network Tx Alignment
        :This OID indicates a Tx Alignment
        Fault is detected on the Line Trscv
        Network interface <Help> Synthesis
        Alarm indicating a Tx Alignment
        Fault is detected on the Line Trscv
        Network interface <Condtype> NETWORK_TX_ALIGNMENT
        <Probcause> informationalStatus(1000)
        <Alarmtype> other (1) <Polarity>
        (2)
        "
	  ::= { rm10010mpAlmmsaNetworkHostNetworkAlarmSummary 11 }



--- *****************************************************
---     LEAF for the msaHostTxAlignment article
--- *****************************************************
rm10010mpAlmmsaHostTxAlignment OBJECT IDENTIFIER ::= { rm10010mpAlmOtherCrit 52 }




rm10010mpAlmHostTxCdrLockFault OBJECT-TYPE
	  SYNTAX EkiOnOff
	  MAX-ACCESS read-only
	  STATUS current
	  DESCRIPTION
        "
        Line Trscv Host Tx CDR Lock Fault
        :This OID indicates a Tx Clock
         Data Recovery Lock Fault is detected
        on the Line Trscv Host interface
        <Help> Alarm indicating a Tx Clock
        Data Recovery Lock Fault is detected
        on the Line Trscv Host interface
        <Condtype> HOST_TX_CDR_LOCK_FAULT
        <Probcause> receiverFailure (42)
        <Alarmtype> equipmentAlarm (5)
         <Polarity> (2)
        "
	  ::= { rm10010mpAlmmsaHostTxAlignment 16 }



rm10010mpAlmHostTxLossOfAlignment OBJECT-TYPE
	  SYNTAX EkiOnOff
	  MAX-ACCESS read-only
	  STATUS current
	  DESCRIPTION
        "
        Line Trscv Host Tx Loss Of Alignment
        :This OID indicates a Tx Loss of
        Alignment is detected on the Line
        Trscv Host interface <Help> Alarm
        indicating a Tx Loss of Alignment
        is detected on the Line Trscv Host
        interface <Condtype> HOST_TX_LOSS_OF_ALIGNMENT
        <Probcause> receiverFailure (42)
        <Alarmtype> equipmentAlarm (5)
         <Polarity> (2)
        "
	  ::= { rm10010mpAlmmsaHostTxAlignment 15 }



rm10010mpAlmHostTxOutOfAlignment OBJECT-TYPE
	  SYNTAX EkiOnOff
	  MAX-ACCESS read-only
	  STATUS current
	  DESCRIPTION
        "
        Line Trscv Host Tx Out Of Alignment
        :This OID indicates a Tx Out of
        Alignment is detected on the Line
        Trscv Host interface <Help> Alarm
        indicating a Tx Out of Alignment
        is detected on the Line Trscv Host
        interface <Condtype> HOST_TX_OUT_OF_ALIGNMENT
        <Probcause> receiverFailure (42)
        <Alarmtype> equipmentAlarm (5)
         <Polarity> (2)
        "
	  ::= { rm10010mpAlmmsaHostTxAlignment 14 }



rm10010mpAlmHostTxDeskewLockFault OBJECT-TYPE
	  SYNTAX EkiOnOff
	  MAX-ACCESS read-only
	  STATUS current
	  DESCRIPTION
        "
        Line Trscv Host Tx Deskew Lock
        Fault :This OID indicates a Tx
         Deskew Lock Fault is detected
         on  the Line Trscv Host interface
        <Help> Alarm indicating a Tx Deskew
        Lock Fault is detected on  the
         Line Trscv Host interface <Condtype>
        HOST_TX_DESKEW_LOCK_FAULT <Probcause>
        receiverFailure (42) <Alarmtype>
        equipmentAlarm (5) <Polarity> (2)
        "
	  ::= { rm10010mpAlmmsaHostTxAlignment 13 }



--- *****************************************************
---     LEAF for the msaHostRxAlignment article
--- *****************************************************
rm10010mpAlmmsaHostRxAlignment OBJECT IDENTIFIER ::= { rm10010mpAlmOtherCrit 53 }




rm10010mpAlmHostRxLossOfAlignment OBJECT-TYPE
	  SYNTAX EkiOnOff
	  MAX-ACCESS read-only
	  STATUS current
	  DESCRIPTION
        "
        Line Trscv Host Rx Loss Of Alignment
        :This OID indicates a Rx Loss of
        Alignment is detected on the Line
        Trscv Host interface <Help> Alarm
        indicating a Rx Loss of Alignment
        is detected on the Line Trscv Host
        interface <Condtype> HOST_RX_LOSS_OF_ALIGNMENT
        <Probcause> transmitterFailure
         (56) <Alarmtype> equipmentAlarm
        (5) <Polarity> (2)
        "
	  ::= { rm10010mpAlmmsaHostRxAlignment 16 }



rm10010mpAlmHostRxOutOfAlignment OBJECT-TYPE
	  SYNTAX EkiOnOff
	  MAX-ACCESS read-only
	  STATUS current
	  DESCRIPTION
        "
        Line Trscv Host Rx Out Of Alignment
        :This OID indicates a Rx Out of
        Alignment is detected on the Line
        Trscv Host interface <Help> Alarm
        indicating a Rx Out of Alignment
        is detected on the Line Trscv Host
        interface <Condtype> HOST_RX_OUT_OF_ALIGNMENT
        <Probcause> transmitterFailure
         (56) <Alarmtype> equipmentAlarm
        (5) <Polarity> (2)
        "
	  ::= { rm10010mpAlmmsaHostRxAlignment 15 }



rm10010mpAlmHostRxCmuLockFault OBJECT-TYPE
	  SYNTAX EkiOnOff
	  MAX-ACCESS read-only
	  STATUS current
	  DESCRIPTION
        "
        Line Trscv Host Rx CMU Lock Fault
        :This OID indicates a Rx Clock
         Multiplier Unit Lock Fault is
         detected on the Line Trscv Host
        interface <Help> Alarm indicating
        a Rx Clock Multiplier Unit Lock
        Fault is detected on the Line Trscv
        Host interface <Condtype> HOST_RX_CMU_LOCK_FAULT
        <Probcause> transmitterFailure
         (56) <Alarmtype> equipmentAlarm
        (5) <Polarity> (2)
        "
	  ::= { rm10010mpAlmmsaHostRxAlignment 14 }



--- *********************************************************
---     TABLE for the rm10010mpAlmclientNetworkLaneAlarmWarning articles
--- *********************************************************

rm10010mpAlmclientNetworkLaneAlarmWarningTable OBJECT-TYPE
	SYNTAX  SEQUENCE OF Rm10010mpAlmclientNetworkLaneAlarmWarningEntry
	MAX-ACCESS not-accessible
	STATUS current
	DESCRIPTION
        "
        List of rm10010mpAlmclientNetworkLaneAlarmWarning
        Article
        "
	::= { rm10010mpAlmClientNurg 56 }


rm10010mpAlmclientNetworkLaneAlarmWarningEntry OBJECT-TYPE
	SYNTAX Rm10010mpAlmclientNetworkLaneAlarmWarningEntry
	MAX-ACCESS not-accessible
	STATUS current
	DESCRIPTION
        "
        Row definition for the rm10010mpAlmclientNetworkLaneAlarmWarning
        table
        "
	INDEX   { rm10010mpAlmclientNetworkLaneAlarmWarningIndex }
	::= { rm10010mpAlmclientNetworkLaneAlarmWarningTable 1 }


Rm10010mpAlmclientNetworkLaneAlarmWarningEntry ::=
	SEQUENCE {
	rm10010mpAlmclientNetworkLaneAlarmWarningIndex
		INTEGER,
	rm10010mpAlmClientBiasHighAlarmPortn
		EkiOnOff,
	rm10010mpAlmClientBiasHighWarningPortn
		EkiOnOff,
	rm10010mpAlmClientBiasLowWarningPortn
		EkiOnOff,
	rm10010mpAlmClientBiasLowAlarmPortn
		EkiOnOff,
	rm10010mpAlmClientTxPowerHighAlarmPortn
		EkiOnOff,
	rm10010mpAlmClientTxPowerHighWarningPortn
		EkiOnOff,
	rm10010mpAlmClientTxPowerLowWarningPortn
		EkiOnOff,
	rm10010mpAlmClientTxPowerLowAlarmPortn
		EkiOnOff,
	rm10010mpAlmClientLaserTempHighAlarmPortn
		EkiOnOff,
	rm10010mpAlmClientLaserTempHighWarningPortn
		EkiOnOff,
	rm10010mpAlmClientLaserTempLowWarningPortn
		EkiOnOff,
	rm10010mpAlmLaserTempLowAlarmPortn
		EkiOnOff,
	rm10010mpAlmClientRxPowerHighAlarmPortn
		EkiOnOff,
	rm10010mpAlmClientRxPowerHighWarningPortn
		EkiOnOff,
	rm10010mpAlmClientRxPowerLowWarningPortn
		EkiOnOff,
	rm10010mpAlmClientRxPowerLowAlarmPortn
		EkiOnOff
	}


rm10010mpAlmclientNetworkLaneAlarmWarningIndex OBJECT-TYPE
	SYNTAX  INTEGER(0..128)
	MAX-ACCESS  read-only
	STATUS current
	DESCRIPTION
        "
        Index definition for the rm10010mpAlmclientNetworkLaneAlarmWarning
        table
        "
	::= { rm10010mpAlmclientNetworkLaneAlarmWarningEntry 1 }


rm10010mpAlmClientBiasHighAlarmPortn OBJECT-TYPE
	SYNTAX  EkiOnOff
	MAX-ACCESS read-only
	STATUS current
	DESCRIPTION
        "
        Client Trscv Bias High Alarm :This
        OID indicates that the Trscv laser
        bias current is higher than the
        threshold value written in the
         Trscv EEPROM <Help> Alarm indicating
        that the Trscv laser bias current
        is higher than the threshold value
        written in the Trscv EEPROM <Condtype>
        CLIENT_BIAS_HIGH_ALARM <Probcause>
        transmitterFailure (56) <Alarmtype>
        equipmentAlarm (5) <Polarity> (2)
        "
	::= { rm10010mpAlmclientNetworkLaneAlarmWarningEntry 17 }


rm10010mpAlmClientBiasHighWarningPortn OBJECT-TYPE
	SYNTAX  EkiOnOff
	MAX-ACCESS read-only
	STATUS current
	DESCRIPTION
        "
        Client Trscv Bias High Warning
        :This OID indicates that the Trscv
        laser bias current is higher than
        the threshold value written in
         the Trscv EEPROM <Help> Warning
        indicating that the Trscv laser
        bias current is higher than the
        threshold value written in the
         Trscv EEPROM <Condtype> CLIENT_BIAS_HIGH_WARNING
        <Probcause> transmitterFailure
         (56) <Alarmtype> equipmentAlarm
        (5) <Polarity> (2)
        "
	::= { rm10010mpAlmclientNetworkLaneAlarmWarningEntry 16 }


rm10010mpAlmClientBiasLowWarningPortn OBJECT-TYPE
	SYNTAX  EkiOnOff
	MAX-ACCESS read-only
	STATUS current
	DESCRIPTION
        "
        Client Trscv Bias Low Warning
         :This OID indicates that the Trscv
        laser bias current is lower than
        the threshold value written in
         the Trscv EEPROM <Help> Warning
        indicating that the Trscv laser
        bias current is lower than the
         threshold value written in the
        Trscv EEPROM <Condtype> CLIENT_BIAS_LOW_WARNING
        <Probcause> transmitterFailure
         (56) <Alarmtype> equipmentAlarm
        (5) <Polarity> (2)
        "
	::= { rm10010mpAlmclientNetworkLaneAlarmWarningEntry 15 }


rm10010mpAlmClientBiasLowAlarmPortn OBJECT-TYPE
	SYNTAX  EkiOnOff
	MAX-ACCESS read-only
	STATUS current
	DESCRIPTION
        "
        Client Trscv Bias Low Alarm :This
        OID indicates that the Trscv laser
        bias current is lower than the
         threshold value written in the
        Trscv EEPROM <Help> Alarm indicating
        that the Trscv laser bias current
        is lower than the threshold value
        written in the Trscv EEPROM <Condtype>
        CLIENT_BIAS_LOW_ALARM <Probcause>
        transmitterFailure (56) <Alarmtype>
        equipmentAlarm (5) <Polarity> (2)
        "
	::= { rm10010mpAlmclientNetworkLaneAlarmWarningEntry 14 }


rm10010mpAlmClientTxPowerHighAlarmPortn OBJECT-TYPE
	SYNTAX  EkiOnOff
	MAX-ACCESS read-only
	STATUS current
	DESCRIPTION
        "
        Client Trscv Tx Power High Alarm
        :This OID indicates that the Trscv
        output power is higher than the
        threshold value written in the
         Trscv EEPROM <Help> Alarm indicating
        that the Trscv output power is
         higher than the threshold value
        written in the Trscv EEPROM <Condtype>
        CLIENT_TX_POWER_HIGH_ALARM <Probcause>
        transmitterFailure (56) <Alarmtype>
        equipmentAlarm (5) <Polarity> (2)
        "
	::= { rm10010mpAlmclientNetworkLaneAlarmWarningEntry 13 }


rm10010mpAlmClientTxPowerHighWarningPortn OBJECT-TYPE
	SYNTAX  EkiOnOff
	MAX-ACCESS read-only
	STATUS current
	DESCRIPTION
        "
        Client Trscv Tx Power High Warning
        :This OID indicates that the Trscv
        output power is higher than the
        threshold value written in the
         Trscv EEPROM <Help> Warning indicating
        that the Trscv output power is
         higher than the threshold value
        written in the Trscv EEPROM <Condtype>
        CLIENT_TX_POWER_HIGH_WARNING <Probcause>
        transmitterFailure (56) <Alarmtype>
        equipmentAlarm (5) <Polarity> (2)
        "
	::= { rm10010mpAlmclientNetworkLaneAlarmWarningEntry 12 }


rm10010mpAlmClientTxPowerLowWarningPortn OBJECT-TYPE
	SYNTAX  EkiOnOff
	MAX-ACCESS read-only
	STATUS current
	DESCRIPTION
        "
        Client Trscv Tx Power Low Warning
        :This OID indicates that the Trscv
        output power is lower than the
         threshold value written in the
        Trscv EEPROM <Help> Warning indicating
        that the Trscv output power is
         lower than the threshold value
        written in the Trscv EEPROM <Condtype>
        CLIENT_TX_POWER_LOW_WARNING <Probcause>
        transmitterFailure (56) <Alarmtype>
        equipmentAlarm (5) <Polarity> (2)
        "
	::= { rm10010mpAlmclientNetworkLaneAlarmWarningEntry 11 }


rm10010mpAlmClientTxPowerLowAlarmPortn OBJECT-TYPE
	SYNTAX  EkiOnOff
	MAX-ACCESS read-only
	STATUS current
	DESCRIPTION
        "
        Client Trscv Tx Power Low Alarm
        :This OID indicates that the Trscv
        output power is lower than the
         threshold value written in the
        Trscv EEPROM <Help> Alarm indicating
        that the Trscv output power is
         lower than the threshold value
        written in the Trscv EEPROM <Condtype>
        CLIENT_TX_POWER_LOW_ALARM <Probcause>
        transmitterFailure (56) <Alarmtype>
        equipmentAlarm (5) <Polarity> (2)
        "
	::= { rm10010mpAlmclientNetworkLaneAlarmWarningEntry 10 }


rm10010mpAlmClientLaserTempHighAlarmPortn OBJECT-TYPE
	SYNTAX  EkiOnOff
	MAX-ACCESS read-only
	STATUS current
	DESCRIPTION
        "
        Client Trscv Laser Temp High Alarm
        :This OID indicates that the Trscv
        Laser Temperature is higher than
        the threshold value written in
         the Trscv EEPROM <Help> Alarm
         indicating that the Trscv Laser
        Temperature is higher than the
         threshold value written in the
        Trscv EEPROM <Condtype> CLIENT_LASER_TEMP_HIGH_ALARM
        <Probcause> temperatureUnacceptable
        (51) <Alarmtype> equipmentAlarm
        (5) <Polarity> (2)
        "
	::= { rm10010mpAlmclientNetworkLaneAlarmWarningEntry 9 }


rm10010mpAlmClientLaserTempHighWarningPortn OBJECT-TYPE
	SYNTAX  EkiOnOff
	MAX-ACCESS read-only
	STATUS current
	DESCRIPTION
        "
        Client Trscv Laser Temp High Warning
        :This OID indicates that the Trscv
        Laser Temperature is higher than
        the threshold value written in
         the Trscv EEPROM <Help> Warning
        indicating that the Trscv Laser
        Temperature is higher than the
         threshold value written in the
        Trscv EEPROM <Condtype> CLIENT_LASER_TEMP_HIGH_WARNING
        <Probcause> temperatureUnacceptable
        (51) <Alarmtype> equipmentAlarm
        (5) <Polarity> (2)
        "
	::= { rm10010mpAlmclientNetworkLaneAlarmWarningEntry 8 }


rm10010mpAlmClientLaserTempLowWarningPortn OBJECT-TYPE
	SYNTAX  EkiOnOff
	MAX-ACCESS read-only
	STATUS current
	DESCRIPTION
        "
        Client Trscv Laser Temp Low Warning
        :This OID indicates that the Trscv
        Laser Temperature is lower than
        the threshold value written in
         the Trscv EEPROM <Help> Warning
        indicating that the Trscv Laser
        Temperature is lower than the threshold
        value written in the Trscv EEPROM
        <Condtype> CLIENT_LASER_TEMP_LOW_WARNING
        <Probcause> temperatureUnacceptable
        (51) <Alarmtype> equipmentAlarm
        (5) <Polarity> (2)
        "
	::= { rm10010mpAlmclientNetworkLaneAlarmWarningEntry 7 }


rm10010mpAlmLaserTempLowAlarmPortn OBJECT-TYPE
	SYNTAX  EkiOnOff
	MAX-ACCESS read-only
	STATUS current
	DESCRIPTION
        "
        Client Trscv Laser Temp Low Alarm
        :This OID indicates that the Trscv
        Laser Temperature is lower than
        the threshold value written in
         the Trscv EEPROM <Help> Alarm
         indicating that the Trscv Laser
        Temperature is lower than the threshold
        value written in the Trscv EEPROM
        <Condtype> LASER_TEMP_LOW_ALARM
        <Probcause> temperatureUnacceptable
        (51) <Alarmtype> equipmentAlarm
        (5) <Polarity> (2)
        "
	::= { rm10010mpAlmclientNetworkLaneAlarmWarningEntry 6 }


rm10010mpAlmClientRxPowerHighAlarmPortn OBJECT-TYPE
	SYNTAX  EkiOnOff
	MAX-ACCESS read-only
	STATUS current
	DESCRIPTION
        "
        Client Trscv Rx Power High Alarm
        :This OID indicates that the Trscv
        input power is higher than the
         threshold value written in the
        Trscv EEPROM <Help> Alarm indicating
        that the Trscv input power is higher
        than the threshold value written
        in the Trscv EEPROM <Condtype>
         CLIENT_RX_POWER_HIGH_ALARM <Probcause>
        receiveFailure (41) <Alarmtype>
        equipmentAlarm (5) <Polarity> (2)
        "
	::= { rm10010mpAlmclientNetworkLaneAlarmWarningEntry 5 }


rm10010mpAlmClientRxPowerHighWarningPortn OBJECT-TYPE
	SYNTAX  EkiOnOff
	MAX-ACCESS read-only
	STATUS current
	DESCRIPTION
        "
        Client Trscv Rx Power High Warning
        :This OID indicates that the Trscv
        input power is higher than the
         threshold value written in the
        Trscv EEPROM <Help> Warning indicating
        that the Trscv input power is higher
        than the threshold value written
        in the Trscv EEPROM <Condtype>
         CLIENT_RX_POWER_HIGH_WARNING <Probcause>
        receiveFailure (41) <Alarmtype>
        equipmentAlarm (5) <Polarity> (2)
        "
	::= { rm10010mpAlmclientNetworkLaneAlarmWarningEntry 4 }


rm10010mpAlmClientRxPowerLowWarningPortn OBJECT-TYPE
	SYNTAX  EkiOnOff
	MAX-ACCESS read-only
	STATUS current
	DESCRIPTION
        "
        Client Trscv Rx Power Low Warning
        :This OID indicates that the Trscv
        input power is lower than the threshold
        value written in the Trscv EEPROM
        <Help> Warning indicating that
         the Trscv input power is lower
        than the threshold value written
        in the Trscv EEPROM <Condtype>
         CLIENT_RX_POWER_LOW_WARNING <Probcause>
        receiveFailure (41) <Alarmtype>
        equipmentAlarm (5) <Polarity> (2)
        "
	::= { rm10010mpAlmclientNetworkLaneAlarmWarningEntry 3 }


rm10010mpAlmClientRxPowerLowAlarmPortn OBJECT-TYPE
	SYNTAX  EkiOnOff
	MAX-ACCESS read-only
	STATUS current
	DESCRIPTION
        "
        Client Trscv Rx Power Low Alarm
        :This OID indicates that the Trscv
        input power is lower than the threshold
        value written in the Trscv EEPROM
        <Help> Alarm indicating that the
        Trscv input power is lower than
        the threshold value written in
         the Trscv EEPROM <Condtype> CLIENT_RX_POWER_LOW_ALARM
        <Probcause> receiveFailure (41)
        <Alarmtype> equipmentAlarm (5)
         <Polarity> (2)
        "
	::= { rm10010mpAlmclientNetworkLaneAlarmWarningEntry 2 }


--- *********************************************************
---     TABLE for the rm10010mpAlmclientNetworkLaneFault articles
--- *********************************************************

rm10010mpAlmclientNetworkLaneFaultTable OBJECT-TYPE
	SYNTAX  SEQUENCE OF Rm10010mpAlmclientNetworkLaneFaultEntry
	MAX-ACCESS not-accessible
	STATUS current
	DESCRIPTION
        "
        List of rm10010mpAlmclientNetworkLaneFault
        Article
        "
	::= { rm10010mpAlmClientUrg 72 }


rm10010mpAlmclientNetworkLaneFaultEntry OBJECT-TYPE
	SYNTAX Rm10010mpAlmclientNetworkLaneFaultEntry
	MAX-ACCESS not-accessible
	STATUS current
	DESCRIPTION
        "
        Row definition for the rm10010mpAlmclientNetworkLaneFault
        table
        "
	INDEX   { rm10010mpAlmclientNetworkLaneFaultIndex }
	::= { rm10010mpAlmclientNetworkLaneFaultTable 1 }


Rm10010mpAlmclientNetworkLaneFaultEntry ::=
	SEQUENCE {
	rm10010mpAlmclientNetworkLaneFaultIndex
		INTEGER,
	rm10010mpAlmClientLaneTecFaultPortn
		EkiOnOff,
	rm10010mpAlmClientLaneWavelengthUnlockedPortn
		EkiOnOff,
	rm10010mpAlmClientLaneApdPowerSupplyPortn
		EkiOnOff,
	rm10010mpAlmClientLaneTxLosfPortn
		EkiOnOff,
	rm10010mpAlmClientLaneTxLolPortn
		EkiOnOff,
	rm10010mpAlmClientLaneRxLosPortn
		EkiOnOff,
	rm10010mpAlmClientLaneRxLolPortn
		EkiOnOff,
	rm10010mpAlmClientLaneRxFifoErrorPortn
		EkiOnOff
	}


rm10010mpAlmclientNetworkLaneFaultIndex OBJECT-TYPE
	SYNTAX  INTEGER(0..128)
	MAX-ACCESS  read-only
	STATUS current
	DESCRIPTION
        "
        Index definition for the rm10010mpAlmclientNetworkLaneFault
        table
        "
	::= { rm10010mpAlmclientNetworkLaneFaultEntry 1 }


rm10010mpAlmClientLaneTecFaultPortn OBJECT-TYPE
	SYNTAX  EkiOnOff
	MAX-ACCESS read-only
	STATUS current
	DESCRIPTION
        "
        Client Network Lane TEC Fault
         :This OID indicates a TEC Fault
        on the Client Trscv Network Lane
        <Help> Alarm indicating a TEC Fault
        on the Client Trscv Network Lane
        <Condtype> CLIENT_LANE_TEC_FAULT
        <Probcause> transmitterFailure
         (56) <Alarmtype> equipmentAlarm
        (5) <Polarity> (2)
        "
	::= { rm10010mpAlmclientNetworkLaneFaultEntry 17 }


rm10010mpAlmClientLaneWavelengthUnlockedPortn OBJECT-TYPE
	SYNTAX  EkiOnOff
	MAX-ACCESS read-only
	STATUS current
	DESCRIPTION
        "
        Client Network Lane Wavelength
        Unlock :This OID indicates a Wavelength
        unlock on the Client Trscv Network
        Lane <Help> Alarm indicating a
         Wavelength unlock on the Client
        Trscv Network Lane <Condtype> CLIENT_LANE_WAVELENGTH_UNLOCKED
        <Probcause> transmitterFailure
         (56) <Alarmtype> equipmentAlarm
        (5) <Polarity> (2)
        "
	::= { rm10010mpAlmclientNetworkLaneFaultEntry 16 }


rm10010mpAlmClientLaneApdPowerSupplyPortn OBJECT-TYPE
	SYNTAX  EkiOnOff
	MAX-ACCESS read-only
	STATUS current
	DESCRIPTION
        "
        Client Network Lane APD Power
         Supply :This OID indicates an
         APD Power supply failure on the
        Client Trscv Network Lane <Help>
        Alarm indicating an APD Power supply
        failure on the Client Trscv Network
        Lane <Condtype> CLIENT_LANE_APD_POWER_SUPPLY
        <Probcause> transmitterFailure
         (56) <Alarmtype> equipmentAlarm
        (5) <Polarity> (2)
        "
	::= { rm10010mpAlmclientNetworkLaneFaultEntry 15 }


rm10010mpAlmClientLaneTxLosfPortn OBJECT-TYPE
	SYNTAX  EkiOnOff
	MAX-ACCESS read-only
	STATUS current
	DESCRIPTION
        "
        Client Network Lane Tx Loss Of
        Signal Functionality :This OID
         indicates a Tx Loss of Signal
         Functionality on the Client Trscv
        Network Lane <Help> Alarm indicating
        a Tx Loss of Signal Functionality
        on the Client Trscv Network Lane
        <Condtype> CLIENT_LANE_TX_LOSF
         <Probcause> transmitterFailure
        (56) <Alarmtype> equipmentAlarm
        (5) <Polarity> (2)
        "
	::= { rm10010mpAlmclientNetworkLaneFaultEntry 9 }


rm10010mpAlmClientLaneTxLolPortn OBJECT-TYPE
	SYNTAX  EkiOnOff
	MAX-ACCESS read-only
	STATUS current
	DESCRIPTION
        "
        Client Network Lane Tx Loss Of
        Lock :This OID indicates a Tx Loss
        of Lock on the Client Trscv Network
        Lane <Help> Alarm indicating a
         Tx Loss of Lock on the Client
         Trscv Network Lane <Condtype>
         CLIENT_LANE_TX_LOL <Probcause>
        transmitterFailure (56) <Alarmtype>
        equipmentAlarm (5) <Polarity> (2)
        "
	::= { rm10010mpAlmclientNetworkLaneFaultEntry 8 }


rm10010mpAlmClientLaneRxLosPortn OBJECT-TYPE
	SYNTAX  EkiOnOff
	MAX-ACCESS read-only
	STATUS current
	DESCRIPTION
        "
        Client Network Lane Rx Loss Of
        Signal :This OID indicates a Rx
        Loss of Signal on the Client Trscv
        Network Lane <Help> Alarm indicating
        a Rx Loss of Signal on the Client
        Trscv Network Lane <Condtype> CLIENT_LANE_RX_LOS
        <Probcause> receiveFailure (41)
        <Alarmtype> physicalViolation (9)
        <Polarity> (2)
        "
	::= { rm10010mpAlmclientNetworkLaneFaultEntry 6 }


rm10010mpAlmClientLaneRxLolPortn OBJECT-TYPE
	SYNTAX  EkiOnOff
	MAX-ACCESS read-only
	STATUS current
	DESCRIPTION
        "
        Client Network Lane Rx Loss Of
        Lock :This OID indicates a Rx Loss
        of Lock on the Client Trscv Network
        Lane <Help> Alarm indicating a
         Rx Loss of Lock on the Client
         Trscv Network Lane <Condtype>
         CLIENT_LANE_RX_LOL <Probcause>
        receiverFailure (42) <Alarmtype>
        equipmentAlarm (5) <Polarity> (2)
        "
	::= { rm10010mpAlmclientNetworkLaneFaultEntry 5 }


rm10010mpAlmClientLaneRxFifoErrorPortn OBJECT-TYPE
	SYNTAX  EkiOnOff
	MAX-ACCESS read-only
	STATUS current
	DESCRIPTION
        "
        Client Network Lane Rx FIFO Error
        :This OID indicates a Rx FIFO Error
        on the Client Trscv Network Lane
        <Help> Alarm indicating a Rx FIFO
        Error on the Client Trscv Network
        Lane <Condtype> CLIENT_LANE_RX_FIFO_ERROR
        <Probcause> receiverFailure (42)
        <Alarmtype> equipmentAlarm (5)
         <Polarity> (2)
        "
	::= { rm10010mpAlmclientNetworkLaneFaultEntry 4 }


--- *********************************************************
---     TABLE for the rm10010mpAlmclientHostLaneFault articles
--- *********************************************************

rm10010mpAlmclientHostLaneFaultTable OBJECT-TYPE
	SYNTAX  SEQUENCE OF Rm10010mpAlmclientHostLaneFaultEntry
	MAX-ACCESS not-accessible
	STATUS current
	DESCRIPTION
        "
        List of rm10010mpAlmclientHostLaneFault
        Article
        "
	::= { rm10010mpAlmClientUrg 88 }


rm10010mpAlmclientHostLaneFaultEntry OBJECT-TYPE
	SYNTAX Rm10010mpAlmclientHostLaneFaultEntry
	MAX-ACCESS not-accessible
	STATUS current
	DESCRIPTION
        "
        Row definition for the rm10010mpAlmclientHostLaneFault
        table
        "
	INDEX   { rm10010mpAlmclientHostLaneFaultIndex }
	::= { rm10010mpAlmclientHostLaneFaultTable 1 }


Rm10010mpAlmclientHostLaneFaultEntry ::=
	SEQUENCE {
	rm10010mpAlmclientHostLaneFaultIndex
		INTEGER,
	rm10010mpAlmClientLaneTxFifoErrorPortn
		EkiOnOff,
	rm10010mpAlmClientTxHostLolPortn
		EkiOnOff,
	rm10010mpAlmClientCsfDetectedPortn
		EkiOnOff,
	rm10010mpAlmClientLanesNotAlignedPortn
		EkiOnOff,
	rm10010mpAlmClientLanes6466UnlockPortn
		EkiOnOff,
	rm10010mpAlmClientLanesMarkerUnlockPortn
		EkiOnOff,
	rm10010mpAlmClientInputLossOfSigPortn
		EkiOnOff,
	rm10010mpAlmClientLossOfSyncPortn
		EkiOnOff
	}


rm10010mpAlmclientHostLaneFaultIndex OBJECT-TYPE
	SYNTAX  INTEGER(0..128)
	MAX-ACCESS  read-only
	STATUS current
	DESCRIPTION
        "
        Index definition for the rm10010mpAlmclientHostLaneFault
        table
        "
	::= { rm10010mpAlmclientHostLaneFaultEntry 1 }


rm10010mpAlmClientLaneTxFifoErrorPortn OBJECT-TYPE
	SYNTAX  EkiOnOff
	MAX-ACCESS read-only
	STATUS current
	DESCRIPTION
        "
        Client Host Lane Tx FIFO Error
        :This OID indicates a Tx FIFO Error
        on the Client Trscv Host Lane <Help>
        Alarm indicating a Tx FIFO Error
        on the Client Trscv Host Lane <Condtype>
        CLIENT_LANE_TX_FIFO_ERROR <Probcause>
        receiverFailure (42) <Alarmtype>
        equipmentAlarm (5) <Polarity> (2)
        "
	::= { rm10010mpAlmclientHostLaneFaultEntry 11 }


rm10010mpAlmClientTxHostLolPortn OBJECT-TYPE
	SYNTAX  EkiOnOff
	MAX-ACCESS read-only
	STATUS current
	DESCRIPTION
        "
        Client Host Lane Tx Loss Of Lock
        :This OID indicates a Tx Loss of
        Lock on the Client Trscv Host Lane
        <Help> Alarm indicating a Tx Loss
        of Lock on the Client Trscv Host
        Lane <Condtype> CLIENT_TX_HOST_LOL
        <Probcause> receiverFailure (42)
        <Alarmtype> equipmentAlarm (5)
         <Polarity> (2)
        "
	::= { rm10010mpAlmclientHostLaneFaultEntry 10 }


rm10010mpAlmClientCsfDetectedPortn OBJECT-TYPE
	SYNTAX  EkiOnOff
	MAX-ACCESS read-only
	STATUS current
	DESCRIPTION
        "
        Client Signal Fail Detected :This
        OID indicates that a CSF has been
        detected on client port in the
         downstream direction   <Help>
          This alarm indicates if a Client
        Signal Fail has been detected in
        the incoming line frame for this
        client port <Condtype> CLIENT_CSF_DETECTED
        <Probcause> receiveFailure (41)
        <Alarmtype> other(1) <Polarity>
        (2)
        "
	::= { rm10010mpAlmclientHostLaneFaultEntry 7 }


rm10010mpAlmClientLanesNotAlignedPortn OBJECT-TYPE
	SYNTAX  EkiOnOff
	MAX-ACCESS read-only
	STATUS current
	DESCRIPTION
        "
        Client Lanes Not Aligned :This
        OID indicates the Client lanes
         are not aligned <Help> Alarm indicating
        the Client lanes are not aligned
        <Condtype> CLIENT_LANES_NOT_ALIGNED
        <Probcause> receiveFailure (41)
        <Alarmtype> integrityViolation
         (7) <Polarity> (2)
        "
	::= { rm10010mpAlmclientHostLaneFaultEntry 6 }


rm10010mpAlmClientLanes6466UnlockPortn OBJECT-TYPE
	SYNTAX  EkiOnOff
	MAX-ACCESS read-only
	STATUS current
	DESCRIPTION
        "
        Client Lanes 64/66b Unlock :This
        OID indicates the Client 64/66b
        decoder is not lock <Help> Alarm
        indicating the Client 64/66b decoder
        is not lock <Condtype> CLIENT_LANES_64_66_UNLOCK
        <Probcause> receiveFailure (41)
        <Alarmtype> integrityViolation
         (7) <Polarity> (2)
        "
	::= { rm10010mpAlmclientHostLaneFaultEntry 5 }


rm10010mpAlmClientLanesMarkerUnlockPortn OBJECT-TYPE
	SYNTAX  EkiOnOff
	MAX-ACCESS read-only
	STATUS current
	DESCRIPTION
        "
        Client Lanes Marker Unlock :This
        OID indicates the Client lanes
         marker alignment is not lock <Help>
        Alarm indicating the Client lanes
        marker alignment is not lock <Condtype>
        CLIENT_LANES_MARKER_UNLOCK <Probcause>
        receiveFailure (41) <Alarmtype>
        integrityViolation (7) <Polarity>
        (2)
        "
	::= { rm10010mpAlmclientHostLaneFaultEntry 4 }


rm10010mpAlmClientInputLossOfSigPortn OBJECT-TYPE
	SYNTAX  EkiOnOff
	MAX-ACCESS read-only
	STATUS current
	DESCRIPTION
        "
        Client Input Loss Of Signal :This
        OID indicates a Loss of Signal
         is detected on the Client Trscv
        <Help> Alarm indicating a Loss
         of Signal is detected on the Client
        Trscv <Condtype> CLIENT_INPUT_LOSS_OF_SIG
        <Probcause> receiveFailure (41)
        <Alarmtype> physicalViolation (9)
        <Polarity> (2)
        "
	::= { rm10010mpAlmclientHostLaneFaultEntry 3 }


rm10010mpAlmClientLossOfSyncPortn OBJECT-TYPE
	SYNTAX  EkiOnOff
	MAX-ACCESS read-only
	STATUS current
	DESCRIPTION
        "
        Client Frame Alignment Loss :This
        OID indicates the module is not
        aligned with the incoming Client
        signal <Help> Alarm indicating
         the module is not aligned with
        the incoming client signal <Condtype>
        CLIENT_LOSS_OF_SYNC <Probcause>
        receiveFailure (41) <Alarmtype>
        integrityViolation (7) <Polarity>
        (2)
        "
	::= { rm10010mpAlmclientHostLaneFaultEntry 2 }


--- *********************************************************
---     TABLE for the rm10010mpAlmlineNetworkLaneAlarmWarning1 articles
--- *********************************************************

rm10010mpAlmlineNetworkLaneAlarmWarning1Table OBJECT-TYPE
	SYNTAX  SEQUENCE OF Rm10010mpAlmlineNetworkLaneAlarmWarning1Entry
	MAX-ACCESS not-accessible
	STATUS current
	DESCRIPTION
        "
        List of rm10010mpAlmlineNetworkLaneAlarmWarning1
        Article
        "
	::= { rm10010mpAlmLineNurg 104 }


rm10010mpAlmlineNetworkLaneAlarmWarning1Entry OBJECT-TYPE
	SYNTAX Rm10010mpAlmlineNetworkLaneAlarmWarning1Entry
	MAX-ACCESS not-accessible
	STATUS current
	DESCRIPTION
        "
        Row definition for the rm10010mpAlmlineNetworkLaneAlarmWarning1
        table
        "
	INDEX   { rm10010mpAlmlineNetworkLaneAlarmWarning1Index }
	::= { rm10010mpAlmlineNetworkLaneAlarmWarning1Table 1 }


Rm10010mpAlmlineNetworkLaneAlarmWarning1Entry ::=
	SEQUENCE {
	rm10010mpAlmlineNetworkLaneAlarmWarning1Index
		INTEGER,
	rm10010mpAlmLineBiasHighAlarmPortn
		EkiOnOff,
	rm10010mpAlmLineBiasHighWarningPortn
		EkiOnOff,
	rm10010mpAlmLineBiasLowWarningPortn
		EkiOnOff,
	rm10010mpAlmLineBiasLowAlarmPortn
		EkiOnOff,
	rm10010mpAlmLineTxPowerHighAlarmPortn
		EkiOnOff,
	rm10010mpAlmLineTxPowerHighWarningPortn
		EkiOnOff,
	rm10010mpAlmLineTxPowerLowWarningPortn
		EkiOnOff,
	rm10010mpAlmLineTxPowerLowAlarmPortn
		EkiOnOff,
	rm10010mpAlmLineLaserTempHighAlarmPortn
		EkiOnOff,
	rm10010mpAlmLineLaserTempHighWarningPortn
		EkiOnOff,
	rm10010mpAlmLineLaserTempLowWarningPortn
		EkiOnOff,
	rm10010mpAlmLineLaserTempLowAlarmPortn
		EkiOnOff,
	rm10010mpAlmLineRxPowerHighAlarmPortn
		EkiOnOff,
	rm10010mpAlmLineRxPowerHighWarningPortn
		EkiOnOff,
	rm10010mpAlmLineRxPowerLowWarningPortn
		EkiOnOff,
	rm10010mpAlmLineRxPowerLowAlarmPortn
		EkiOnOff
	}


rm10010mpAlmlineNetworkLaneAlarmWarning1Index OBJECT-TYPE
	SYNTAX  INTEGER(0..128)
	MAX-ACCESS  read-only
	STATUS current
	DESCRIPTION
        "
        Index definition for the rm10010mpAlmlineNetworkLaneAlarmWarning1
        table
        "
	::= { rm10010mpAlmlineNetworkLaneAlarmWarning1Entry 1 }


rm10010mpAlmLineBiasHighAlarmPortn OBJECT-TYPE
	SYNTAX  EkiOnOff
	MAX-ACCESS read-only
	STATUS current
	DESCRIPTION
        "
        Line Trscv Tx Bias High Alarm
         :This OID indicates that the Trscv
        laser bias current is higher than
        the threshold value written in
         the Trscv EEPROM <Help> Alarm
         indicating that the Trscv laser
        bias current is higher than the
        threshold value written in the
         Trscv EEPROM <Condtype> LINE_BIAS_HIGH_ALARM
        <Probcause> transmitterFailure
         (56) <Alarmtype> equipmentAlarm
        (5) <Polarity> (2)
        "
	::= { rm10010mpAlmlineNetworkLaneAlarmWarning1Entry 17 }


rm10010mpAlmLineBiasHighWarningPortn OBJECT-TYPE
	SYNTAX  EkiOnOff
	MAX-ACCESS read-only
	STATUS current
	DESCRIPTION
        "
        Line Trscv Tx Bias High Warning
        :This OID indicates that the Trscv
        laser bias current is higher than
        the threshold value written in
         the Trscv EEPROM <Help> Warning
        indicating that the Trscv laser
        bias current is higher than the
        threshold value written in the
         Trscv EEPROM <Condtype> LINE_BIAS_HIGH_WARNING
        <Probcause> transmitterFailure
         (56) <Alarmtype> equipmentAlarm
        (5) <Polarity> (2)
        "
	::= { rm10010mpAlmlineNetworkLaneAlarmWarning1Entry 16 }


rm10010mpAlmLineBiasLowWarningPortn OBJECT-TYPE
	SYNTAX  EkiOnOff
	MAX-ACCESS read-only
	STATUS current
	DESCRIPTION
        "
        Line Trscv Tx Bias Low Warning
        :This OID indicates that the Trscv
        laser bias current is lower than
        the threshold value written in
         the Trscv EEPROM <Help> Warning
        indicating that the Trscv laser
        bias current is lower than the
         threshold value written in the
        Trscv EEPROM <Condtype> LINE_BIAS_LOW_WARNING
        <Probcause> transmitterFailure
         (56) <Alarmtype> equipmentAlarm
        (5) <Polarity> (2)
        "
	::= { rm10010mpAlmlineNetworkLaneAlarmWarning1Entry 15 }


rm10010mpAlmLineBiasLowAlarmPortn OBJECT-TYPE
	SYNTAX  EkiOnOff
	MAX-ACCESS read-only
	STATUS current
	DESCRIPTION
        "
        Line Trscv Tx Bias Low Alarm :This
        OID indicates that the Trscv laser
        bias current is lower than the
         threshold value written in the
        Trscv EEPROM <Help> Alarm indicating
        that the Trscv laser bias current
        is lower than the threshold value
        written in the Trscv EEPROM <Condtype>
        LINE_BIAS_LOW_ALARM <Probcause>
        transmitterFailure (56) <Alarmtype>
        equipmentAlarm (5) <Polarity> (2)
        "
	::= { rm10010mpAlmlineNetworkLaneAlarmWarning1Entry 14 }


rm10010mpAlmLineTxPowerHighAlarmPortn OBJECT-TYPE
	SYNTAX  EkiOnOff
	MAX-ACCESS read-only
	STATUS current
	DESCRIPTION
        "
        Line Trscv Tx Power High Alarm
        :This OID indicates that the Trscv
        output power is higher than the
        threshold value written in the
         Trscv EEPROM <Help> Alarm indicating
        that the Trscv output power is
         higher than the threshold value
        written in the Trscv EEPROM <Condtype>
        LINE_TX_POWER_HIGH_ALARM <Probcause>
        transmitterFailure (56) <Alarmtype>
        equipmentAlarm (5) <Polarity> (2)
        "
	::= { rm10010mpAlmlineNetworkLaneAlarmWarning1Entry 13 }


rm10010mpAlmLineTxPowerHighWarningPortn OBJECT-TYPE
	SYNTAX  EkiOnOff
	MAX-ACCESS read-only
	STATUS current
	DESCRIPTION
        "
        Line Trscv Tx Power High Warning
        :This OID indicates that the Trscv
        output power is higher than the
        threshold value written in the
         Trscv EEPROM <Help> Warning indicating
        that the Trscv output power is
         higher than the threshold value
        written in the Trscv EEPROM <Condtype>
        LINE_TX_POWER_HIGH_WARNING <Probcause>
        transmitterFailure (56) <Alarmtype>
        equipmentAlarm (5) <Polarity> (2)
        "
	::= { rm10010mpAlmlineNetworkLaneAlarmWarning1Entry 12 }


rm10010mpAlmLineTxPowerLowWarningPortn OBJECT-TYPE
	SYNTAX  EkiOnOff
	MAX-ACCESS read-only
	STATUS current
	DESCRIPTION
        "
        Line Trscv Tx Power Low Warning
        :This OID indicates that the Trscv
        output power is lower than the
         threshold value written in the
        Trscv EEPROM <Help> Warning indicating
        that the Trscv output power is
         lower than the threshold value
        written in the Trscv EEPROM <Condtype>
        LINE_TX_POWER_LOW_WARNING <Probcause>
        transmitterFailure (56) <Alarmtype>
        equipmentAlarm (5) <Polarity> (2)
        "
	::= { rm10010mpAlmlineNetworkLaneAlarmWarning1Entry 11 }


rm10010mpAlmLineTxPowerLowAlarmPortn OBJECT-TYPE
	SYNTAX  EkiOnOff
	MAX-ACCESS read-only
	STATUS current
	DESCRIPTION
        "
        Line Trscv Tx Power Low Alarm
         :This OID indicates that the Trscv
        output power is lower than the
         threshold value written in the
        Trscv EEPROM <Help> Alarm indicating
        that the Trscv output power is
         lower than the threshold value
        written in the Trscv EEPROM <Condtype>
        LINE_TX_POWER_LOW_ALARM <Probcause>
        transmitterFailure (56) <Alarmtype>
        equipmentAlarm (5) <Polarity> (2)
        "
	::= { rm10010mpAlmlineNetworkLaneAlarmWarning1Entry 10 }


rm10010mpAlmLineLaserTempHighAlarmPortn OBJECT-TYPE
	SYNTAX  EkiOnOff
	MAX-ACCESS read-only
	STATUS current
	DESCRIPTION
        "
        Line Trscv Tx Laser Temp High
         Alarm :This OID indicates that
        the Trscv Tx Laser Temperature
         is higher than the threshold value
        written in the Trscv EEPROM <Help>
        Alarm indicating that the Trscv
        Tx Laser Temperature is higher
         than the threshold value written
        in the Trscv EEPROM <Condtype>
         LINE_LASER_TEMP_HIGH_ALARM <Probcause>
        temperatureUnacceptable (51) <Alarmtype>
        equipmentAlarm (5) <Polarity> (2)
        "
	::= { rm10010mpAlmlineNetworkLaneAlarmWarning1Entry 9 }


rm10010mpAlmLineLaserTempHighWarningPortn OBJECT-TYPE
	SYNTAX  EkiOnOff
	MAX-ACCESS read-only
	STATUS current
	DESCRIPTION
        "
        Line Trscv Tx Laser Temp High
         Warning :This OID indicates that
        the Trscv Tx Laser Temperature
         is higher than the threshold value
        written in the Trscv EEPROM <Help>
        Warning indicating that the Trscv
        Tx Laser Temperature is higher
         than the threshold value written
        in the Trscv EEPROM <Condtype>
         LINE_LASER_TEMP_HIGH_WARNING <Probcause>
        temperatureUnacceptable (51) <Alarmtype>
        equipmentAlarm (5) <Polarity> (2)
        "
	::= { rm10010mpAlmlineNetworkLaneAlarmWarning1Entry 8 }


rm10010mpAlmLineLaserTempLowWarningPortn OBJECT-TYPE
	SYNTAX  EkiOnOff
	MAX-ACCESS read-only
	STATUS current
	DESCRIPTION
        "
        Line Trscv Tx Laser Temp Low Warning
        :This OID indicates that the Trscv
        Tx Laser Temperature is lower than
        the threshold value written in
         the Trscv EEPROM <Help> Warning
        indicating that the Trscv Tx Laser
        Temperature is lower than the threshold
        value written in the Trscv EEPROM
        <Condtype> LINE_LASER_TEMP_LOW_WARNING
        <Probcause> temperatureUnacceptable
        (51) <Alarmtype> equipmentAlarm
        (5) <Polarity> (2)
        "
	::= { rm10010mpAlmlineNetworkLaneAlarmWarning1Entry 7 }


rm10010mpAlmLineLaserTempLowAlarmPortn OBJECT-TYPE
	SYNTAX  EkiOnOff
	MAX-ACCESS read-only
	STATUS current
	DESCRIPTION
        "
        Line Trscv Tx Laser Temp Low Alarm
        :This OID indicates that the Trscv
        Tx Laser Temperature is lower than
        the threshold value written in
         the Trscv EEPROM <Help> Alarm
         indicating that the Trscv Tx Laser
        Temperature is lower than the threshold
        value written in the Trscv EEPROM
        <Condtype> LINE_LASER_TEMP_LOW_ALARM
        <Probcause> temperatureUnacceptable
        (51) <Alarmtype> equipmentAlarm
        (5) <Polarity> (2)
        "
	::= { rm10010mpAlmlineNetworkLaneAlarmWarning1Entry 6 }


rm10010mpAlmLineRxPowerHighAlarmPortn OBJECT-TYPE
	SYNTAX  EkiOnOff
	MAX-ACCESS read-only
	STATUS current
	DESCRIPTION
        "
        Line Trscv Rx Power High Alarm
        :This OID indicates that the Trscv
        input power is higher than the
         threshold value written in the
        Trscv EEPROM <Help> Alarm indicating
        that the Trscv input power is higher
        than the threshold value written
        in the Trscv EEPROM <Condtype>
         LINE_RX_POWER_HIGH_ALARM <Probcause>
        receiveFailure (41) <Alarmtype>
        equipmentAlarm (5) <Polarity> (2)
        "
	::= { rm10010mpAlmlineNetworkLaneAlarmWarning1Entry 5 }


rm10010mpAlmLineRxPowerHighWarningPortn OBJECT-TYPE
	SYNTAX  EkiOnOff
	MAX-ACCESS read-only
	STATUS current
	DESCRIPTION
        "
        Line Trscv Rx Power High Warning
        :This OID indicates that the Trscv
        input power is higher than the
         threshold value written in the
        Trscv EEPROM <Help> Warning indicating
        that the Trscv input power is higher
        than the threshold value written
        in the Trscv EEPROM <Condtype>
         LINE_RX_POWER_HIGH_WARNING <Probcause>
        receiveFailure (41) <Alarmtype>
        equipmentAlarm (5) <Polarity> (2)
        "
	::= { rm10010mpAlmlineNetworkLaneAlarmWarning1Entry 4 }


rm10010mpAlmLineRxPowerLowWarningPortn OBJECT-TYPE
	SYNTAX  EkiOnOff
	MAX-ACCESS read-only
	STATUS current
	DESCRIPTION
        "
        Line Trscv Rx Power Low Warning
        :This OID indicates that the Trscv
        input power is lower than the threshold
        value written in the Trscv EEPROM
        <Help> Warning indicating that
         the Trscv input power is lower
        than the threshold value written
        in the Trscv EEPROM <Condtype>
         LINE_RX_POWER_LOW_WARNING <Probcause>
        receiveFailure (41) <Alarmtype>
        equipmentAlarm (5) <Polarity> (2)
        "
	::= { rm10010mpAlmlineNetworkLaneAlarmWarning1Entry 3 }


rm10010mpAlmLineRxPowerLowAlarmPortn OBJECT-TYPE
	SYNTAX  EkiOnOff
	MAX-ACCESS read-only
	STATUS current
	DESCRIPTION
        "
        Line Trscv Rx Power Low Alarm
         :This OID indicates that the Trscv
        input power is lower than the threshold
        value written in the Trscv EEPROM
        <Help> Alarm indicating that the
        Trscv input power is lower than
        the threshold value written in
         the Trscv EEPROM <Condtype> LINE_RX_POWER_LOW_ALARM
        <Probcause> receiveFailure (41)
        <Alarmtype> equipmentAlarm (5)
         <Polarity> (2)
        "
	::= { rm10010mpAlmlineNetworkLaneAlarmWarning1Entry 2 }


--- *********************************************************
---     TABLE for the rm10010mpAlmlineNetworkLaneAlarmWarning2 articles
--- *********************************************************

rm10010mpAlmlineNetworkLaneAlarmWarning2Table OBJECT-TYPE
	SYNTAX  SEQUENCE OF Rm10010mpAlmlineNetworkLaneAlarmWarning2Entry
	MAX-ACCESS not-accessible
	STATUS current
	DESCRIPTION
        "
        List of rm10010mpAlmlineNetworkLaneAlarmWarning2
        Article
        "
	::= { rm10010mpAlmLineNurg 120 }


rm10010mpAlmlineNetworkLaneAlarmWarning2Entry OBJECT-TYPE
	SYNTAX Rm10010mpAlmlineNetworkLaneAlarmWarning2Entry
	MAX-ACCESS not-accessible
	STATUS current
	DESCRIPTION
        "
        Row definition for the rm10010mpAlmlineNetworkLaneAlarmWarning2
        table
        "
	INDEX   { rm10010mpAlmlineNetworkLaneAlarmWarning2Index }
	::= { rm10010mpAlmlineNetworkLaneAlarmWarning2Table 1 }


Rm10010mpAlmlineNetworkLaneAlarmWarning2Entry ::=
	SEQUENCE {
	rm10010mpAlmlineNetworkLaneAlarmWarning2Index
		INTEGER,
	rm10010mpAlmRxLaserBiasHighAlarmPortn
		EkiOnOff,
	rm10010mpAlmRxLaserBiasHighWarningPortn
		EkiOnOff,
	rm10010mpAlmRxLaserBiasLowWarningPortn
		EkiOnOff,
	rm10010mpAlmRxLaserBiasLowAlarmPortn
		EkiOnOff,
	rm10010mpAlmRxLaserOutputHighAlarmPortn
		EkiOnOff,
	rm10010mpAlmRxLaserOutputHighWarningPortn
		EkiOnOff,
	rm10010mpAlmRxLaserOutputLowWarningPortn
		EkiOnOff,
	rm10010mpAlmRxLaserOutputLowAlarmPortn
		EkiOnOff,
	rm10010mpAlmRxLaserTempHighAlarmPortn
		EkiOnOff,
	rm10010mpAlmRxLaserTempHighWarningPortn
		EkiOnOff,
	rm10010mpAlmRxLaserTempLowWarningPortn
		EkiOnOff,
	rm10010mpAlmRxLaserTempLowAlarmPortn
		EkiOnOff,
	rm10010mpAlmTxModulatorBiasHighAlarmPortn
		EkiOnOff,
	rm10010mpAlmTxModulatorBiasHighWarningPortn
		EkiOnOff,
	rm10010mpAlmTxModulatorBiasLowWarningPortn
		EkiOnOff,
	rm10010mpAlmTxModulatorBiasLowAlarmPortn
		EkiOnOff
	}


rm10010mpAlmlineNetworkLaneAlarmWarning2Index OBJECT-TYPE
	SYNTAX  INTEGER(0..128)
	MAX-ACCESS  read-only
	STATUS current
	DESCRIPTION
        "
        Index definition for the rm10010mpAlmlineNetworkLaneAlarmWarning2
        table
        "
	::= { rm10010mpAlmlineNetworkLaneAlarmWarning2Entry 1 }


rm10010mpAlmRxLaserBiasHighAlarmPortn OBJECT-TYPE
	SYNTAX  EkiOnOff
	MAX-ACCESS read-only
	STATUS current
	DESCRIPTION
        "
        Line Trscv Rx Bias High Alarm
         :This OID indicates that the Trscv
        Rx laser bias current is higher
        than the threshold value written
        in the Trscv EEPROM <Help> Alarm
        indicating that the Trscv Rx laser
        bias current is higher than the
        threshold value written in the
         Trscv EEPROM <Condtype> RX_LASER_BIAS_HIGH_ALARM
        <Probcause> receiveFailure (41)
        <Alarmtype> equipmentAlarm (5)
         <Polarity> (2)
        "
	::= { rm10010mpAlmlineNetworkLaneAlarmWarning2Entry 17 }


rm10010mpAlmRxLaserBiasHighWarningPortn OBJECT-TYPE
	SYNTAX  EkiOnOff
	MAX-ACCESS read-only
	STATUS current
	DESCRIPTION
        "
        Line Trscv Rx Bias High Warning
        :This OID indicates that the Trscv
        Rx laser bias current is higher
        than the threshold value written
        in the Trscv EEPROM <Help> Warning
        indicating that the Trscv Rx laser
        bias current is higher than the
        threshold value written in the
         Trscv EEPROM <Condtype> RX_LASER_BIAS_HIGH_WARNING
        <Probcause> receiveFailure (41)
        <Alarmtype> equipmentAlarm (5)
         <Polarity> (2)
        "
	::= { rm10010mpAlmlineNetworkLaneAlarmWarning2Entry 16 }


rm10010mpAlmRxLaserBiasLowWarningPortn OBJECT-TYPE
	SYNTAX  EkiOnOff
	MAX-ACCESS read-only
	STATUS current
	DESCRIPTION
        "
        Line Trscv Rx Bias Low Warning
        :This OID indicates that the Trscv
        Rx laser bias current is lower
         than the threshold value written
        in the Trscv EEPROM <Help> Warning
        indicating that the Trscv Rx laser
        bias current is lower than the
         threshold value written in the
        Trscv EEPROM <Condtype> RX_LASER_BIAS_LOW_WARNING
        <Probcause> receiveFailure (41)
        <Alarmtype> equipmentAlarm (5)
         <Polarity> (2)
        "
	::= { rm10010mpAlmlineNetworkLaneAlarmWarning2Entry 15 }


rm10010mpAlmRxLaserBiasLowAlarmPortn OBJECT-TYPE
	SYNTAX  EkiOnOff
	MAX-ACCESS read-only
	STATUS current
	DESCRIPTION
        "
        Line Trscv Rx Bias Low Alarm :This
        OID indicates that the Trscv Rx
        laser bias current is lower than
        the threshold value written in
         the Trscv EEPROM <Help> Alarm
         indicating that the Trscv Rx laser
        bias current is lower than the
         threshold value written in the
        Trscv EEPROM <Condtype> RX_LASER_BIAS_LOW_ALARM
        <Probcause> receiveFailure (41)
        <Alarmtype> equipmentAlarm (5)
         <Polarity> (2)
        "
	::= { rm10010mpAlmlineNetworkLaneAlarmWarning2Entry 14 }


rm10010mpAlmRxLaserOutputHighAlarmPortn OBJECT-TYPE
	SYNTAX  EkiOnOff
	MAX-ACCESS read-only
	STATUS current
	DESCRIPTION
        "
        Line Trscv Rx Output Power High
        Alarm :This OID indicates that
         the Trscv Rx output power is higher
        than the threshold value written
        in the Trscv EEPROM <Help> Alarm
        indicating that the Trscv Rx output
        power is higher than the threshold
        value written in the Trscv EEPROM
        <Condtype> RX_LASER_OUTPUT_HIGH_ALARM
        <Probcause> receiveFailure (41)
        <Alarmtype> equipmentAlarm (5)
         <Polarity> (2)
        "
	::= { rm10010mpAlmlineNetworkLaneAlarmWarning2Entry 13 }


rm10010mpAlmRxLaserOutputHighWarningPortn OBJECT-TYPE
	SYNTAX  EkiOnOff
	MAX-ACCESS read-only
	STATUS current
	DESCRIPTION
        "
        Line Trscv Rx Output Power High
        Warning :This OID indicates that
        the Trscv Rx output power is higher
        than the threshold value written
        in the Trscv EEPROM <Help> Warning
        indicating that the Trscv Rx output
        power is higher than the threshold
        value written in the Trscv EEPROM
        <Condtype> RX_LASER_OUTPUT_HIGH_WARNING
        <Probcause> receiveFailure (41)
        <Alarmtype> equipmentAlarm (5)
         <Polarity> (2)
        "
	::= { rm10010mpAlmlineNetworkLaneAlarmWarning2Entry 12 }


rm10010mpAlmRxLaserOutputLowWarningPortn OBJECT-TYPE
	SYNTAX  EkiOnOff
	MAX-ACCESS read-only
	STATUS current
	DESCRIPTION
        "
        Line Trscv Rx Output Power Low
        Warning :This OID indicates that
        the Trscv Rx output power is lower
        than the threshold value written
        in the Trscv EEPROM <Help> Warning
        indicating that the Trscv Rx output
        power is lower than the threshold
        value written in the Trscv EEPROM
        <Condtype> RX_LASER_OUTPUT_LOW_WARNING
        <Probcause> receiveFailure (41)
        <Alarmtype> equipmentAlarm (5)
         <Polarity> (2)
        "
	::= { rm10010mpAlmlineNetworkLaneAlarmWarning2Entry 11 }


rm10010mpAlmRxLaserOutputLowAlarmPortn OBJECT-TYPE
	SYNTAX  EkiOnOff
	MAX-ACCESS read-only
	STATUS current
	DESCRIPTION
        "
        Line Trscv Rx Output Power Low
        Alarm :This OID indicates that
         the Trscv Rx output power is lower
        than the threshold value written
        in the Trscv EEPROM <Help> Alarm
        indicating that the Trscv Rx output
        power is lower than the threshold
        value written in the Trscv EEPROM
        <Condtype> RX_LASER_OUTPUT_LOW_ALARM
        <Probcause> receiveFailure (41)
        <Alarmtype> equipmentAlarm (5)
         <Polarity> (2)
        "
	::= { rm10010mpAlmlineNetworkLaneAlarmWarning2Entry 10 }


rm10010mpAlmRxLaserTempHighAlarmPortn OBJECT-TYPE
	SYNTAX  EkiOnOff
	MAX-ACCESS read-only
	STATUS current
	DESCRIPTION
        "
        Line Trscv Rx Laser Temp High
         Alarm :This OID indicates that
        the Trscv Rx Laser Temperature
         is higher than the threshold value
        written in the Trscv EEPROM <Help>
        Alarm indicating that the Trscv
        Rx Laser Temperature is higher
         than the threshold value written
        in the Trscv EEPROM <Condtype>
         RX_LASER_TEMP_HIGH_ALARM <Probcause>
        temperatureUnacceptable (51) <Alarmtype>
        equipmentAlarm (5) <Polarity> (2)
        "
	::= { rm10010mpAlmlineNetworkLaneAlarmWarning2Entry 9 }


rm10010mpAlmRxLaserTempHighWarningPortn OBJECT-TYPE
	SYNTAX  EkiOnOff
	MAX-ACCESS read-only
	STATUS current
	DESCRIPTION
        "
        Line Trscv Rx Laser Temp High
         Warning :This OID indicates that
        the Trscv Rx Laser Temperature
         is higher than the threshold value
        written in the Trscv EEPROM <Help>
        Warning indicating that the Trscv
        Rx Laser Temperature is higher
         than the threshold value written
        in the Trscv EEPROM <Condtype>
         RX_LASER_TEMP_HIGH_WARNING <Probcause>
        temperatureUnacceptable (51) <Alarmtype>
        equipmentAlarm (5) <Polarity> (2)
        "
	::= { rm10010mpAlmlineNetworkLaneAlarmWarning2Entry 8 }


rm10010mpAlmRxLaserTempLowWarningPortn OBJECT-TYPE
	SYNTAX  EkiOnOff
	MAX-ACCESS read-only
	STATUS current
	DESCRIPTION
        "
        Line Trscv Rx Laser Temp Low Warning
        :This OID indicates that the Trscv
        Rx Laser Temperature is lower than
        the threshold value written in
         the Trscv EEPROM <Help> Warning
        indicating that the Trscv Rx Laser
        Temperature is lower than the threshold
        value written in the Trscv EEPROM
        <Condtype> RX_LASER_TEMP_LOW_WARNING
        <Probcause> temperatureUnacceptable
        (51) <Alarmtype> equipmentAlarm
        (5) <Polarity> (2)
        "
	::= { rm10010mpAlmlineNetworkLaneAlarmWarning2Entry 7 }


rm10010mpAlmRxLaserTempLowAlarmPortn OBJECT-TYPE
	SYNTAX  EkiOnOff
	MAX-ACCESS read-only
	STATUS current
	DESCRIPTION
        "
        Line Trscv Rx Laser Temp Low Alarm
        :This OID indicates that the Trscv
        Rx Laser Temperature is lower than
        the threshold value written in
         the Trscv EEPROM <Help> Alarm
         indicating that the Trscv Rx Laser
        Temperature is lower than the threshold
        value written in the Trscv EEPROM
        <Condtype> RX_LASER_TEMP_LOW_ALARM
        <Probcause> temperatureUnacceptable
        (51) <Alarmtype> equipmentAlarm
        (5) <Polarity> (2)
        "
	::= { rm10010mpAlmlineNetworkLaneAlarmWarning2Entry 6 }


rm10010mpAlmTxModulatorBiasHighAlarmPortn OBJECT-TYPE
	SYNTAX  EkiOnOff
	MAX-ACCESS read-only
	STATUS current
	DESCRIPTION
        "
        Line Trscv Tx Modulator Bias High
        Alarm :This OID indicates that
         the Trscv Tx modulator bias current
        is higher than the threshold value
        written in the Trscv EEPROM <Help>
        Alarm indicating that the Trscv
        Tx modulator bias current is higher
        than the threshold value written
        in the Trscv EEPROM <Condtype>
         TX_MODULATOR_BIAS_HIGH_ALARM <Probcause>
        transmitterFailure (56) <Alarmtype>
        equipmentAlarm (5) <Polarity> (2)
        "
	::= { rm10010mpAlmlineNetworkLaneAlarmWarning2Entry 5 }


rm10010mpAlmTxModulatorBiasHighWarningPortn OBJECT-TYPE
	SYNTAX  EkiOnOff
	MAX-ACCESS read-only
	STATUS current
	DESCRIPTION
        "
        Line Trscv Tx Modulator Bias High
        Warning :This OID indicates that
        the Trscv Tx modulator bias current
        is higher than the threshold value
        written in the Trscv EEPROM <Help>
        Warning indicating that the Trscv
        Tx modulator bias current is higher
        than the threshold value written
        in the Trscv EEPROM <Condtype>
         TX_MODULATOR_BIAS_HIGH_WARNING
        <Probcause> transmitterFailure
         (56) <Alarmtype> equipmentAlarm
        (5) <Polarity> (2)
        "
	::= { rm10010mpAlmlineNetworkLaneAlarmWarning2Entry 4 }


rm10010mpAlmTxModulatorBiasLowWarningPortn OBJECT-TYPE
	SYNTAX  EkiOnOff
	MAX-ACCESS read-only
	STATUS current
	DESCRIPTION
        "
        Line Trscv Tx Modulator Bias Low
        Warning :This OID indicates that
        the Trscv Tx modulator bias current
        is lower than the threshold value
        written in the Trscv EEPROM <Help>
        Warning indicating that the Trscv
        Tx modulator bias current is lower
        than the threshold value written
        in the Trscv EEPROM <Condtype>
         TX_MODULATOR_BIAS_LOW_WARNING
         <Probcause> transmitterFailure
        (56) <Alarmtype> equipmentAlarm
        (5) <Polarity> (2)
        "
	::= { rm10010mpAlmlineNetworkLaneAlarmWarning2Entry 3 }


rm10010mpAlmTxModulatorBiasLowAlarmPortn OBJECT-TYPE
	SYNTAX  EkiOnOff
	MAX-ACCESS read-only
	STATUS current
	DESCRIPTION
        "
        Line Trscv Tx Modulator Bias Low
        Alarm :This OID indicates that
         the Trscv Tx modulator bias current
        is lower than the threshold value
        written in the Trscv EEPROM <Help>
        Alarm indicating that the Trscv
        Tx modulator bias current is lower
        than the threshold value written
        in the Trscv EEPROM <Condtype>
         TX_MODULATOR_BIAS_LOW_ALARM <Probcause>
        transmitterFailure (56) <Alarmtype>
        equipmentAlarm (5) <Polarity> (2)
        "
	::= { rm10010mpAlmlineNetworkLaneAlarmWarning2Entry 2 }


--- *********************************************************
---     TABLE for the rm10010mpAlmlineNetworkLaneFault articles
--- *********************************************************

rm10010mpAlmlineNetworkLaneFaultTable OBJECT-TYPE
	SYNTAX  SEQUENCE OF Rm10010mpAlmlineNetworkLaneFaultEntry
	MAX-ACCESS not-accessible
	STATUS current
	DESCRIPTION
        "
        List of rm10010mpAlmlineNetworkLaneFault
        Article
        "
	::= { rm10010mpAlmLineUrg 136 }


rm10010mpAlmlineNetworkLaneFaultEntry OBJECT-TYPE
	SYNTAX Rm10010mpAlmlineNetworkLaneFaultEntry
	MAX-ACCESS not-accessible
	STATUS current
	DESCRIPTION
        "
        Row definition for the rm10010mpAlmlineNetworkLaneFault
        table
        "
	INDEX   { rm10010mpAlmlineNetworkLaneFaultIndex }
	::= { rm10010mpAlmlineNetworkLaneFaultTable 1 }


Rm10010mpAlmlineNetworkLaneFaultEntry ::=
	SEQUENCE {
	rm10010mpAlmlineNetworkLaneFaultIndex
		INTEGER,
	rm10010mpAlmLineLaneTecFaultPortn
		EkiOnOff,
	rm10010mpAlmLineLaneWavelengthUnlockedPortn
		EkiOnOff,
	rm10010mpAlmLineLaneApdPowerSupplyPortn
		EkiOnOff,
	rm10010mpAlmLineLaneTxLosfPortn
		EkiOnOff,
	rm10010mpAlmLineLaneTxLolPortn
		EkiOnOff,
	rm10010mpAlmLineLaneRxLosPortn
		EkiOnOff,
	rm10010mpAlmLineLaneRxLolPortn
		EkiOnOff,
	rm10010mpAlmLineLaneRxFifoErrorPortn
		EkiOnOff,
	rm10010mpAlmLineLaneRxTecFaultPortn
		EkiOnOff
	}


rm10010mpAlmlineNetworkLaneFaultIndex OBJECT-TYPE
	SYNTAX  INTEGER(0..128)
	MAX-ACCESS  read-only
	STATUS current
	DESCRIPTION
        "
        Index definition for the rm10010mpAlmlineNetworkLaneFault
        table
        "
	::= { rm10010mpAlmlineNetworkLaneFaultEntry 1 }


rm10010mpAlmLineLaneTecFaultPortn OBJECT-TYPE
	SYNTAX  EkiOnOff
	MAX-ACCESS read-only
	STATUS current
	DESCRIPTION
        "
        Line Network Lane TEC Fault :This
        OID indicates a Tx TEC Fault on
        the Line Trscv Network Lane <Help>
        Alarm indicating a Tx TEC Fault
        on the Line Trscv Network Lane
         <Condtype> LINE_LANE_TEC_FAULT
        <Probcause> transmitterFailure
         (56) <Alarmtype> equipmentAlarm
        (5) <Polarity> (2)
        "
	::= { rm10010mpAlmlineNetworkLaneFaultEntry 17 }


rm10010mpAlmLineLaneWavelengthUnlockedPortn OBJECT-TYPE
	SYNTAX  EkiOnOff
	MAX-ACCESS read-only
	STATUS current
	DESCRIPTION
        "
        Line Network Lane Wavelength Unlock
        :This OID indicates a Wavelength
        unlock on the Line Trscv Network
        Lane <Help> Alarm indicating a
         Wavelength unlock on the Line
         Trscv Network Lane <Condtype>
         LINE_LANE_WAVELENGTH_UNLOCKED
         <Probcause> transmitterFailure
        (56) <Alarmtype> equipmentAlarm
        (5) <Polarity> (2)
        "
	::= { rm10010mpAlmlineNetworkLaneFaultEntry 16 }


rm10010mpAlmLineLaneApdPowerSupplyPortn OBJECT-TYPE
	SYNTAX  EkiOnOff
	MAX-ACCESS read-only
	STATUS current
	DESCRIPTION
        "
        Line Network Lane APD Power Supply
        :This OID indicates an APD Power
        supply failure on the Line Trscv
        Network Lane <Help> Alarm indicating
        an APD Power supply failure on
         the Line Trscv Network Lane <Condtype>
        LINE_LANE_APD_POWER_SUPPLY <Probcause>
        transmitterFailure (56) <Alarmtype>
        equipmentAlarm (5) <Polarity> (2)
        "
	::= { rm10010mpAlmlineNetworkLaneFaultEntry 15 }


rm10010mpAlmLineLaneTxLosfPortn OBJECT-TYPE
	SYNTAX  EkiOnOff
	MAX-ACCESS read-only
	STATUS current
	DESCRIPTION
        "
        Line Network Lane Tx Loss Of Signal
        Functionality :This OID indicates
        a Tx Loss of Signal Functionality
        on the Line Trscv Network Lane
         <Help> Alarm indicating a Tx Loss
        of Signal Functionality on the
         Line Trscv Network Lane <Condtype>
        LINE_LANE_TX_LOSF <Probcause> transmitterFailure
        (56) <Alarmtype> equipmentAlarm
        (5) <Polarity> (2)
        "
	::= { rm10010mpAlmlineNetworkLaneFaultEntry 9 }


rm10010mpAlmLineLaneTxLolPortn OBJECT-TYPE
	SYNTAX  EkiOnOff
	MAX-ACCESS read-only
	STATUS current
	DESCRIPTION
        "
        Line Network Lane Tx Loss Of Lock
        :This OID indicates a Tx Loss of
        Lock on the Line Trscv Network
         Lane <Help> Alarm indicating a
        Tx Loss of Lock on the Line Trscv
        Network Lane <Condtype> LINE_LANE_TX_LOL
        <Probcause> transmitterFailure
         (56) <Alarmtype> equipmentAlarm
        (5) <Polarity> (2)
        "
	::= { rm10010mpAlmlineNetworkLaneFaultEntry 8 }


rm10010mpAlmLineLaneRxLosPortn OBJECT-TYPE
	SYNTAX  EkiOnOff
	MAX-ACCESS read-only
	STATUS current
	DESCRIPTION
        "
        Line Network Lane Rx Loss Of Signal
        :This OID indicates a Rx Loss of
        Signal on the Line Trscv Network
        Lane <Help> Alarm indicating a
         Rx Loss of Signal on the Line
         Trscv Network Lane <Condtype>
         LINE_LANE_RX_LOS <Probcause> receiveFailure
        (41) <Alarmtype> physicalViolation
        (9) <Polarity> (2)
        "
	::= { rm10010mpAlmlineNetworkLaneFaultEntry 6 }


rm10010mpAlmLineLaneRxLolPortn OBJECT-TYPE
	SYNTAX  EkiOnOff
	MAX-ACCESS read-only
	STATUS current
	DESCRIPTION
        "
        Line Network Lane Rx Loss Of Lock
        :This OID indicates a Rx Loss of
        Lock on the Line Trscv Network
         Lane <Help> Alarm indicating a
        Rx Loss of Lock on the Line Trscv
        Network Lane <Condtype> LINE_LANE_RX_LOL
        <Probcause> receiverFailure (42)
        <Alarmtype> equipmentAlarm (5)
         <Polarity> (2)
        "
	::= { rm10010mpAlmlineNetworkLaneFaultEntry 5 }


rm10010mpAlmLineLaneRxFifoErrorPortn OBJECT-TYPE
	SYNTAX  EkiOnOff
	MAX-ACCESS read-only
	STATUS current
	DESCRIPTION
        "
        Line Network Lane Rx FIFO Error
        :This OID indicates a Rx FIFO Error
        on the Line Trscv Network Lane
         <Help> Alarm indicating a Rx FIFO
        Error on the Line Trscv Network
        Lane <Condtype> LINE_LANE_RX_FIFO_ERROR
        <Probcause> receiverFailure (42)
        <Alarmtype> equipmentAlarm (5)
         <Polarity> (2)
        "
	::= { rm10010mpAlmlineNetworkLaneFaultEntry 4 }


rm10010mpAlmLineLaneRxTecFaultPortn OBJECT-TYPE
	SYNTAX  EkiOnOff
	MAX-ACCESS read-only
	STATUS current
	DESCRIPTION
        "
        Line Network Lane Rx TEC Fault
        :This OID indicates a Rx TEC Fault
        on the Line Trscv Network Lane
         <Help> Alarm indicating a Rx TEC
        Fault on the Line Trscv Network
        Lane <Condtype> LINE_LANE_RX_TEC_FAULT
        <Probcause> receiverFailure (42)
        <Alarmtype> equipmentAlarm (5)
         <Polarity> (2)
        "
	::= { rm10010mpAlmlineNetworkLaneFaultEntry 3 }


--- *********************************************************
---     TABLE for the rm10010mpAlmlineHostLaneFault articles
--- *********************************************************

rm10010mpAlmlineHostLaneFaultTable OBJECT-TYPE
	SYNTAX  SEQUENCE OF Rm10010mpAlmlineHostLaneFaultEntry
	MAX-ACCESS not-accessible
	STATUS current
	DESCRIPTION
        "
        List of rm10010mpAlmlineHostLaneFault
        Article
        "
	::= { rm10010mpAlmLineUrg 152 }


rm10010mpAlmlineHostLaneFaultEntry OBJECT-TYPE
	SYNTAX Rm10010mpAlmlineHostLaneFaultEntry
	MAX-ACCESS not-accessible
	STATUS current
	DESCRIPTION
        "
        Row definition for the rm10010mpAlmlineHostLaneFault
        table
        "
	INDEX   { rm10010mpAlmlineHostLaneFaultIndex }
	::= { rm10010mpAlmlineHostLaneFaultTable 1 }


Rm10010mpAlmlineHostLaneFaultEntry ::=
	SEQUENCE {
	rm10010mpAlmlineHostLaneFaultIndex
		INTEGER,
	rm10010mpAlmLineLaneTxFifoErrorPortn
		EkiOnOff,
	rm10010mpAlmLineTxHostLolPortn
		EkiOnOff,
	rm10010mpAlmLineSmIaeDetectedPortn
		EkiOnOff,
	rm10010mpAlmLineSmIaeInsertedPortn
		EkiOnOff,
	rm10010mpAlmLineSmBdiDetectedPortn
		EkiOnOff,
	rm10010mpAlmLineSmBdiInsertedPortn
		EkiOnOff,
	rm10010mpAlmLineLossOfFramePortn
		EkiOnOff,
	rm10010mpAlmLineInputLossOfSignalPortn
		EkiOnOff
	}


rm10010mpAlmlineHostLaneFaultIndex OBJECT-TYPE
	SYNTAX  INTEGER(0..128)
	MAX-ACCESS  read-only
	STATUS current
	DESCRIPTION
        "
        Index definition for the rm10010mpAlmlineHostLaneFault
        table
        "
	::= { rm10010mpAlmlineHostLaneFaultEntry 1 }


rm10010mpAlmLineLaneTxFifoErrorPortn OBJECT-TYPE
	SYNTAX  EkiOnOff
	MAX-ACCESS read-only
	STATUS current
	DESCRIPTION
        "
        Line Host Lane Tx FIFO Error :This
        OID indicates a Tx FIFO Error on
        the Line Trscv Host Lane <Help>
        Alarm indicating a Tx FIFO Error
        on the Line Trscv Host Lane <Condtype>
        LINE_LANE_TX_FIFO_ERROR <Probcause>
        receiverFailure (42) <Alarmtype>
        equipmentAlarm (5) <Polarity> (2)
        "
	::= { rm10010mpAlmlineHostLaneFaultEntry 11 }


rm10010mpAlmLineTxHostLolPortn OBJECT-TYPE
	SYNTAX  EkiOnOff
	MAX-ACCESS read-only
	STATUS current
	DESCRIPTION
        "
        Line Host Lane Tx Loss Of Lock
        :This OID indicates a Tx Loss of
        Lock on the Line Trscv Host Lane
        <Help> Alarm indicating a Tx Loss
        of Lock on the Line Trscv Host
         Lane <Condtype> LINE_TX_HOST_LOL
        <Probcause> receiverFailure (42)
        <Alarmtype> equipmentAlarm (5)
         <Polarity> (2)
        "
	::= { rm10010mpAlmlineHostLaneFaultEntry 10 }


rm10010mpAlmLineSmIaeDetectedPortn OBJECT-TYPE
	SYNTAX  EkiOnOff
	MAX-ACCESS read-only
	STATUS current
	DESCRIPTION
        "
        Line SM IAE Detected :This OID
        indicates a SM Incoming Alignment
        Error is detected on the incoming
        Line signal <Help> Alarm indicating
        a SM Incoming Alignment Error is
        detected on the incoming Line signal
        <Condtype> LINE_SM_IAE_DETECTED
        <Probcause> receiveFailure (41)
        <Alarmtype> integrityViolation
         (7) <Polarity> (2)
        "
	::= { rm10010mpAlmlineHostLaneFaultEntry 7 }


rm10010mpAlmLineSmIaeInsertedPortn OBJECT-TYPE
	SYNTAX  EkiOnOff
	MAX-ACCESS read-only
	STATUS current
	DESCRIPTION
        "
        Line SM IAE Inserted :This OID
        indicates a SM Incoming Alignment
        Error is inserted on the outgoing
        Line signal <Help> Status indicating
        a SM Incoming Alignment Error is
        inserted on the outgoing Line signal
        <Condtype> LINE_SM_IAE_INSERTED
        <Probcause> informationalStatus(1000)
        <Alarmtype> other (1) <Polarity>
        (2)
        "
	::= { rm10010mpAlmlineHostLaneFaultEntry 6 }


rm10010mpAlmLineSmBdiDetectedPortn OBJECT-TYPE
	SYNTAX  EkiOnOff
	MAX-ACCESS read-only
	STATUS current
	DESCRIPTION
        "
        Line SM BDI Detected :This OID
        indicates a SM Backward Defect
         Indication is detected on the
         incoming Line signal <Help> Alarm
        indicating a SM Backward Defect
        Indication is detected on the incoming
        Line signal <Condtype> LINE_SM_BDI_DETECTED
        <Probcause> receiveFailure (41)
        <Alarmtype> integrityViolation
         (7) <Polarity> (2)
        "
	::= { rm10010mpAlmlineHostLaneFaultEntry 5 }


rm10010mpAlmLineSmBdiInsertedPortn OBJECT-TYPE
	SYNTAX  EkiOnOff
	MAX-ACCESS read-only
	STATUS current
	DESCRIPTION
        "
        Line SM BDI Inserted :This OID
        indicates a SM Backward Defect
         Indication is inserted on the
         outgoing Line signal <Help> Status
        indicating a SM Backward Defect
        Indication is inserted on the outgoing
        Line signal <Condtype> LINE_SM_BDI_INSERTED
        <Probcause> informationalStatus(1000)
        <Alarmtype> other (1) <Polarity>
        (2)
        "
	::= { rm10010mpAlmlineHostLaneFaultEntry 4 }


rm10010mpAlmLineLossOfFramePortn OBJECT-TYPE
	SYNTAX  EkiOnOff
	MAX-ACCESS read-only
	STATUS current
	DESCRIPTION
        "
        Line Loss Of Frame :This OID indicates
        the module is not aligned with
         the incoming Line signal <Help>
        Alarm indicating the module is
         not aligned with the incoming
         Line signal <Condtype> LINE_LOSS_OF_FRAME
        <Probcause> receiveFailure (41)
        <Alarmtype> integrityViolation
         (7) <Polarity> (2)
        "
	::= { rm10010mpAlmlineHostLaneFaultEntry 3 }


rm10010mpAlmLineInputLossOfSignalPortn OBJECT-TYPE
	SYNTAX  EkiOnOff
	MAX-ACCESS read-only
	STATUS current
	DESCRIPTION
        "
        Line Input Loss Of Signal :This
        OID indicates a Loss of Signal
         is detected on the Line Trscv
         <Help> Alarm indicating a Loss
        of Signal is detected on the Line
        Trscv <Condtype> LINE_INPUT_LOSS_OF_SIGNAL
        <Probcause> receiveFailure (41)
        <Alarmtype> physicalViolation (9)
        <Polarity> (2)
        "
	::= { rm10010mpAlmlineHostLaneFaultEntry 2 }


--- *********************************************************
---     TABLE for the rm10010mpAlmlineNetworkLaneRxOtn articles
--- *********************************************************

rm10010mpAlmlineNetworkLaneRxOtnTable OBJECT-TYPE
	SYNTAX  SEQUENCE OF Rm10010mpAlmlineNetworkLaneRxOtnEntry
	MAX-ACCESS not-accessible
	STATUS current
	DESCRIPTION
        "
        List of rm10010mpAlmlineNetworkLaneRxOtn
        Article
        "
	::= { rm10010mpAlmLineUrg 168 }


rm10010mpAlmlineNetworkLaneRxOtnEntry OBJECT-TYPE
	SYNTAX Rm10010mpAlmlineNetworkLaneRxOtnEntry
	MAX-ACCESS not-accessible
	STATUS current
	DESCRIPTION
        "
        Row definition for the rm10010mpAlmlineNetworkLaneRxOtn
        table
        "
	INDEX   { rm10010mpAlmlineNetworkLaneRxOtnIndex }
	::= { rm10010mpAlmlineNetworkLaneRxOtnTable 1 }


Rm10010mpAlmlineNetworkLaneRxOtnEntry ::=
	SEQUENCE {
	rm10010mpAlmlineNetworkLaneRxOtnIndex
		INTEGER,
	rm10010mpAlmLineRxOtnLofPortn
		EkiOnOff,
	rm10010mpAlmLineRxOtnOofPortn
		EkiOnOff,
	rm10010mpAlmLineRxOtnLomPortn
		EkiOnOff,
	rm10010mpAlmLineRxOtnOomPortn
		EkiOnOff,
	rm10010mpAlmLineRxOtnIaePortn
		EkiOnOff,
	rm10010mpAlmLineRxSmBdiPortn
		EkiOnOff,
	rm10010mpAlmLineRxOtnOtuAisPortn
		EkiOnOff,
	rm10010mpAlmLineRxOtnOduAisPortn
		EkiOnOff
	}


rm10010mpAlmlineNetworkLaneRxOtnIndex OBJECT-TYPE
	SYNTAX  INTEGER(0..128)
	MAX-ACCESS  read-only
	STATUS current
	DESCRIPTION
        "
        Index definition for the rm10010mpAlmlineNetworkLaneRxOtn
        table
        "
	::= { rm10010mpAlmlineNetworkLaneRxOtnEntry 1 }


rm10010mpAlmLineRxOtnLofPortn OBJECT-TYPE
	SYNTAX  EkiOnOff
	MAX-ACCESS read-only
	STATUS current
	DESCRIPTION
        "
        Line Network Rx LOF :This OID
         indicates a Loss of Frame is detected
        on the Rx Network interface of
         the Line Trscv <Help> Alarm indicating
        a Loss of Frame is detected on
         the Rx Network interface of the
        Line Trscv <Condtype> LINE_RX_OTN_LOF
        <Probcause> receiveFailure (41)
        <Alarmtype> equipmentAlarm (5)
         <Polarity> (2)
        "
	::= { rm10010mpAlmlineNetworkLaneRxOtnEntry 17 }


rm10010mpAlmLineRxOtnOofPortn OBJECT-TYPE
	SYNTAX  EkiOnOff
	MAX-ACCESS read-only
	STATUS current
	DESCRIPTION
        "
        Line Network Rx OOF :This OID
         indicates an Out of Frame is detected
        on the Rx Network interface of
         the Line Trscv <Help> Alarm indicating
        an Out of Frame is detected on
         the Rx Network interface of the
        Line Trscv <Condtype> LINE_RX_OTN_OOF
        <Probcause> receiveFailure (41)
        <Alarmtype> equipmentAlarm (5)
         <Polarity> (2)
        "
	::= { rm10010mpAlmlineNetworkLaneRxOtnEntry 16 }


rm10010mpAlmLineRxOtnLomPortn OBJECT-TYPE
	SYNTAX  EkiOnOff
	MAX-ACCESS read-only
	STATUS current
	DESCRIPTION
        "
        Line Network Rx LOM :This OID
         indicates a Loss of Multiframe
        is detected on the Rx Network interface
        of the Line Trscv <Help> Alarm
         indicating a Loss of Multiframe
        is detected on the Rx Network interface
        of the Line Trscv <Condtype> LINE_RX_OTN_LOM
        <Probcause> receiveFailure (41)
        <Alarmtype> equipmentAlarm (5)
         <Polarity> (2)
        "
	::= { rm10010mpAlmlineNetworkLaneRxOtnEntry 15 }


rm10010mpAlmLineRxOtnOomPortn OBJECT-TYPE
	SYNTAX  EkiOnOff
	MAX-ACCESS read-only
	STATUS current
	DESCRIPTION
        "
        Line Network Rx OOM :This OID
         indicates an Out of Multiframe
        is detected on the Rx Network interface
        of the Line Trscv <Help> Alarm
         indicating an Out of Multiframe
        is detected on the Rx Network interface
        of the Line Trscv <Condtype> LINE_RX_OTN_OOM
        <Probcause> receiveFailure (41)
        <Alarmtype> equipmentAlarm (5)
         <Polarity> (2)
        "
	::= { rm10010mpAlmlineNetworkLaneRxOtnEntry 14 }


rm10010mpAlmLineRxOtnIaePortn OBJECT-TYPE
	SYNTAX  EkiOnOff
	MAX-ACCESS read-only
	STATUS current
	DESCRIPTION
        "
        Line Network Rx IAE :This OID
         indicates an Incoming Alignment
        Error is detected on the Rx Network
        interface of the Line Trscv <Help>
        Alarm indicating an Incoming Alignment
        Error is detected on the Rx Network
        interface of the Line Trscv <Condtype>
        LINE_RX_OTN_IAE <Probcause> receiveFailure
        (41) <Alarmtype> equipmentAlarm
        (5) <Polarity> (2)
        "
	::= { rm10010mpAlmlineNetworkLaneRxOtnEntry 13 }


rm10010mpAlmLineRxSmBdiPortn OBJECT-TYPE
	SYNTAX  EkiOnOff
	MAX-ACCESS read-only
	STATUS current
	DESCRIPTION
        "
        Line Network Rx SM BDI :This OID
        indicates an SM Backward Defect
        Indication is detected on the Rx
        Network interface of the Line Trscv
        <Help> Alarm indicating an SM Backward
        Defect Indication is detected on
        the Rx Network interface of the
        Line Trscv <Condtype> LINE_RX_SM_BDI
        <Probcause> informationalStatus(1000)
        <Alarmtype> other (1) <Polarity>
        (2)
        "
	::= { rm10010mpAlmlineNetworkLaneRxOtnEntry 12 }


rm10010mpAlmLineRxOtnOtuAisPortn OBJECT-TYPE
	SYNTAX  EkiOnOff
	MAX-ACCESS read-only
	STATUS current
	DESCRIPTION
        "
        Line Network Rx OTU AIS :This
         OID indicates an OTU This OID
         Indication Signal is detected
         on the Rx Network interface of
        the Line Trscv <Help> Alarm indicating
        an OTU Alarm Indication Signal
         is detected on the Rx Network
         interface of the Line Trscv <Condtype>
        LINE_RX_OTN_OTU_AIS <Probcause>
        receiveFailure (41) <Alarmtype>
        equipmentAlarm (5) <Polarity> (2)
        "
	::= { rm10010mpAlmlineNetworkLaneRxOtnEntry 11 }


rm10010mpAlmLineRxOtnOduAisPortn OBJECT-TYPE
	SYNTAX  EkiOnOff
	MAX-ACCESS read-only
	STATUS current
	DESCRIPTION
        "
        Line Network Rx ODU AIS :This
         OID indicates an ODU This OID
         Indication Signal is detected
         on the Rx Network interface of
        the Line Trscv <Help> Alarm indicating
        an ODU Alarm Indication Signal
         is detected on the Rx Network
         interface of the Line Trscv <Condtype>
        LINE_RX_OTN_ODU_AIS <Probcause>
        receiveFailure (41) <Alarmtype>
        equipmentAlarm (5) <Polarity> (2)
        "
	::= { rm10010mpAlmlineNetworkLaneRxOtnEntry 10 }


--- *********************************************************
---     TABLE for the rm10010mpAlmlineHostLaneTxOtn articles
--- *********************************************************

rm10010mpAlmlineHostLaneTxOtnTable OBJECT-TYPE
	SYNTAX  SEQUENCE OF Rm10010mpAlmlineHostLaneTxOtnEntry
	MAX-ACCESS not-accessible
	STATUS current
	DESCRIPTION
        "
        List of rm10010mpAlmlineHostLaneTxOtn
        Article
        "
	::= { rm10010mpAlmLineUrg 184 }


rm10010mpAlmlineHostLaneTxOtnEntry OBJECT-TYPE
	SYNTAX Rm10010mpAlmlineHostLaneTxOtnEntry
	MAX-ACCESS not-accessible
	STATUS current
	DESCRIPTION
        "
        Row definition for the rm10010mpAlmlineHostLaneTxOtn
        table
        "
	INDEX   { rm10010mpAlmlineHostLaneTxOtnIndex }
	::= { rm10010mpAlmlineHostLaneTxOtnTable 1 }


Rm10010mpAlmlineHostLaneTxOtnEntry ::=
	SEQUENCE {
	rm10010mpAlmlineHostLaneTxOtnIndex
		INTEGER,
	rm10010mpAlmLineTxOtnLofPortn
		EkiOnOff,
	rm10010mpAlmLineTxOtnOofPortn
		EkiOnOff,
	rm10010mpAlmLineTxOtnLomPortn
		EkiOnOff,
	rm10010mpAlmLineTxOtnOomPortn
		EkiOnOff,
	rm10010mpAlmLineTxOtnIaePortn
		EkiOnOff,
	rm10010mpAlmLineTxSmBdiPortn
		EkiOnOff,
	rm10010mpAlmLineTxOtnOtuAisPortn
		EkiOnOff,
	rm10010mpAlmLineTxOtnOduAisPortn
		EkiOnOff
	}


rm10010mpAlmlineHostLaneTxOtnIndex OBJECT-TYPE
	SYNTAX  INTEGER(0..128)
	MAX-ACCESS  read-only
	STATUS current
	DESCRIPTION
        "
        Index definition for the rm10010mpAlmlineHostLaneTxOtn
        table
        "
	::= { rm10010mpAlmlineHostLaneTxOtnEntry 1 }


rm10010mpAlmLineTxOtnLofPortn OBJECT-TYPE
	SYNTAX  EkiOnOff
	MAX-ACCESS read-only
	STATUS current
	DESCRIPTION
        "
        Line Host Tx LOF :This OID indicates
        a Loss of Frame is detected on
         the Tx Host interface of the Line
        Trscv <Help> Alarm indicating a
        Loss of Frame is detected on the
        Tx Host interface of the Line Trscv
        <Condtype> LINE_TX_OTN_LOF <Probcause>
        receiveFailure (41) <Alarmtype>
        equipmentAlarm (5) <Polarity> (2)
        "
	::= { rm10010mpAlmlineHostLaneTxOtnEntry 17 }


rm10010mpAlmLineTxOtnOofPortn OBJECT-TYPE
	SYNTAX  EkiOnOff
	MAX-ACCESS read-only
	STATUS current
	DESCRIPTION
        "
        Line Host Tx OOF :This OID indicates
        an Out of Frame is detected on
         the Tx Host interface of the Line
        Trscv <Help> Alarm indicating an
        Out of Frame is detected on the
        Tx Host interface of the Line Trscv
        <Condtype> LINE_TX_OTN_OOF <Probcause>
        receiveFailure (41) <Alarmtype>
        equipmentAlarm (5) <Polarity> (2)
        "
	::= { rm10010mpAlmlineHostLaneTxOtnEntry 16 }


rm10010mpAlmLineTxOtnLomPortn OBJECT-TYPE
	SYNTAX  EkiOnOff
	MAX-ACCESS read-only
	STATUS current
	DESCRIPTION
        "
        Line Host Tx LOM :This OID indicates
        a Loss of Multiframe is detected
        on the Tx Host interface of the
        Line Trscv <Help> Alarm indicating
        a Loss of Multiframe is detected
        on the Tx Host interface of the
        Line Trscv <Condtype> LINE_TX_OTN_LOM
        <Probcause> receiveFailure (41)
        <Alarmtype> equipmentAlarm (5)
         <Polarity> (2)
        "
	::= { rm10010mpAlmlineHostLaneTxOtnEntry 15 }


rm10010mpAlmLineTxOtnOomPortn OBJECT-TYPE
	SYNTAX  EkiOnOff
	MAX-ACCESS read-only
	STATUS current
	DESCRIPTION
        "
        Line Host Tx OOM :This OID indicates
        an Out of Multiframe is detected
        on the Tx Host interface of the
        Line Trscv <Help> Alarm indicating
        an Out of Multiframe is detected
        on the Tx Host interface of the
        Line Trscv <Condtype> LINE_TX_OTN_OOM
        <Probcause> receiveFailure (41)
        <Alarmtype> equipmentAlarm (5)
         <Polarity> (2)
        "
	::= { rm10010mpAlmlineHostLaneTxOtnEntry 14 }


rm10010mpAlmLineTxOtnIaePortn OBJECT-TYPE
	SYNTAX  EkiOnOff
	MAX-ACCESS read-only
	STATUS current
	DESCRIPTION
        "
        Line Host Tx IAE :This OID indicates
        an Incoming Alignment Error is
         detected on the Tx Host interface
        of the Line Trscv <Help> Alarm
         indicating an Incoming Alignment
        Error is detected on the Tx Host
        interface of the Line Trscv <Condtype>
        LINE_TX_OTN_IAE <Probcause> receiveFailure
        (41) <Alarmtype> equipmentAlarm
        (5) <Polarity> (2)
        "
	::= { rm10010mpAlmlineHostLaneTxOtnEntry 13 }


rm10010mpAlmLineTxSmBdiPortn OBJECT-TYPE
	SYNTAX  EkiOnOff
	MAX-ACCESS read-only
	STATUS current
	DESCRIPTION
        "
        Line Host Tx SM BDI :This OID
         indicates an SM Backward Defect
        Indication is detected on the Tx
        Host interface of the Line Trscv
        <Help> Alarm indicating an SM Backward
        Defect Indication is detected on
        the Tx Host interface of the Line
        Trscv <Condtype> LINE_TX_SM_BDI
        <Probcause> informationalStatus(1000)
        <Alarmtype> other (1) <Polarity>
        (2)
        "
	::= { rm10010mpAlmlineHostLaneTxOtnEntry 12 }


rm10010mpAlmLineTxOtnOtuAisPortn OBJECT-TYPE
	SYNTAX  EkiOnOff
	MAX-ACCESS read-only
	STATUS current
	DESCRIPTION
        "
        Line Host Tx OTU AIS :This OID
        indicates an OTU This OID Indication
        Signal is detected on the Tx Host
        interface of the Line Trscv <Help>
        Alarm indicating an OTU Alarm Indication
        Signal is detected on the Tx Host
        interface of the Line Trscv <Condtype>
        LINE_TX_OTN_OTU_AIS <Probcause>
        receiveFailure (41) <Alarmtype>
        equipmentAlarm (5) <Polarity> (2)
        "
	::= { rm10010mpAlmlineHostLaneTxOtnEntry 11 }


rm10010mpAlmLineTxOtnOduAisPortn OBJECT-TYPE
	SYNTAX  EkiOnOff
	MAX-ACCESS read-only
	STATUS current
	DESCRIPTION
        "
        Line Host Tx ODU AIS :This OID
        indicates an ODU This OID Indication
        Signal is detected on the Tx Host
        interface of the Line Trscv <Help>
        Alarm indicating an ODU Alarm Indication
        Signal is detected on the Tx Host
        interface of the Line Trscv <Condtype>
        LINE_TX_OTN_ODU_AIS <Probcause>
        receiveFailure (41) <Alarmtype>
        equipmentAlarm (5) <Polarity> (2)
        "
	::= { rm10010mpAlmlineHostLaneTxOtnEntry 10 }


--- *********************************************************
---     TABLE for the rm10010mpAlmclientSfpAlmDdm articles
--- *********************************************************

rm10010mpAlmclientSfpAlmDdmTable OBJECT-TYPE
	SYNTAX  SEQUENCE OF Rm10010mpAlmclientSfpAlmDdmEntry
	MAX-ACCESS not-accessible
	STATUS current
	DESCRIPTION
        "
        List of rm10010mpAlmclientSfpAlmDdm
        Article
        "
	::= { rm10010mpAlmClientUrg 216 }


rm10010mpAlmclientSfpAlmDdmEntry OBJECT-TYPE
	SYNTAX Rm10010mpAlmclientSfpAlmDdmEntry
	MAX-ACCESS not-accessible
	STATUS current
	DESCRIPTION
        "
        Row definition for the rm10010mpAlmclientSfpAlmDdm
        table
        "
	INDEX   { rm10010mpAlmclientSfpAlmDdmIndex }
	::= { rm10010mpAlmclientSfpAlmDdmTable 1 }


Rm10010mpAlmclientSfpAlmDdmEntry ::=
	SEQUENCE {
	rm10010mpAlmclientSfpAlmDdmIndex
		INTEGER,
	rm10010mpAlmRxPwrHighAlaPortn
		EkiOnOff,
	rm10010mpAlmRxPwrLowAlaPortn
		EkiOnOff,
	rm10010mpAlmTempHighAlaPortn
		EkiOnOff,
	rm10010mpAlmTempLowAlaPortn
		EkiOnOff,
	rm10010mpAlmVccHighAlaPortn
		EkiOnOff,
	rm10010mpAlmVccLowAlaPortn
		EkiOnOff,
	rm10010mpAlmTxBiasHighAlaPortn
		EkiOnOff,
	rm10010mpAlmTxBiasLowAlaPortn
		EkiOnOff,
	rm10010mpAlmTxPwrHighAlaPortn
		EkiOnOff,
	rm10010mpAlmTxPwrLowAlaPortn
		EkiOnOff
	}


rm10010mpAlmclientSfpAlmDdmIndex OBJECT-TYPE
	SYNTAX  INTEGER(0..128)
	MAX-ACCESS  read-only
	STATUS current
	DESCRIPTION
        "
        Index definition for the rm10010mpAlmclientSfpAlmDdm
        table
        "
	::= { rm10010mpAlmclientSfpAlmDdmEntry 1 }


rm10010mpAlmRxPwrHighAlaPortn OBJECT-TYPE
	SYNTAX  EkiOnOff
	MAX-ACCESS read-only
	STATUS current
	DESCRIPTION
        "
        Client Trscv Rx Power High :This
        OID indicates that the Trscv input
        power of port is higher than the
        threshold value written in the
         Trscv EEPROM <Help> Alarm indicating
        that the Trscv input power of port
        is higher than the threshold value
        written in the Trscv EEPROM <Condtype>
        RX_PWR_HIGH_ALA_1 <Probcause> receiveFailure
        (41) <Alarmtype> equipmentAlarm
        (5) <Polarity> (2)
        "
	::= { rm10010mpAlmclientSfpAlmDdmEntry 17 }


rm10010mpAlmRxPwrLowAlaPortn OBJECT-TYPE
	SYNTAX  EkiOnOff
	MAX-ACCESS read-only
	STATUS current
	DESCRIPTION
        "
        Client Trscv Rx Power Low :This
        OID indicates that the Trscv input
        power of port is lower than the
        threshold value written in the
         Trscv EEPROM <Help> Alarm indicating
        that the Trscv input power of port
        is lower than the threshold value
        written in the Trscv EEPROM <Condtype>
        RX_PWR_LOW_ALA_1 <Probcause> receiveFailure
        (41) <Alarmtype> equipmentAlarm
        (5) <Polarity> (2)
        "
	::= { rm10010mpAlmclientSfpAlmDdmEntry 16 }


rm10010mpAlmTempHighAlaPortn OBJECT-TYPE
	SYNTAX  EkiOnOff
	MAX-ACCESS read-only
	STATUS current
	DESCRIPTION
        "
        Client Trscv Temp High :This OID
        indicates that the Trscv temperature
        of port is higher than the threshold
        value written in the Trscv EEPROM
        <Help> Alarm indicating that the
        Trscv temperature of port is higher
        than the threshold value written
        in the Trscv EEPROM <Condtype>
         TEMP_HIGH_ALA_1 <Probcause> temperatureUnacceptable
        (51) <Alarmtype> equipmentAlarm
        (5) <Polarity> (2)
        "
	::= { rm10010mpAlmclientSfpAlmDdmEntry 9 }


rm10010mpAlmTempLowAlaPortn OBJECT-TYPE
	SYNTAX  EkiOnOff
	MAX-ACCESS read-only
	STATUS current
	DESCRIPTION
        "
        Client Trscv Temp Low :This OID
        indicates that the Trscv temperature
        of port is lower than the threshold
        value written in the Trscv EEPROM
        <Help> Alarm indicating that the
        Trscv temperature of port is lower
        than the threshold value written
        in the Trscv EEPROM <Condtype>
         TEMP_LOW_ALA_1 <Probcause> temperatureUnacceptable
        (51) <Alarmtype> equipmentAlarm
        (5) <Polarity> (2)
        "
	::= { rm10010mpAlmclientSfpAlmDdmEntry 8 }


rm10010mpAlmVccHighAlaPortn OBJECT-TYPE
	SYNTAX  EkiOnOff
	MAX-ACCESS read-only
	STATUS current
	DESCRIPTION
        "
        Client Trscv Power Supply High
        :This OID indicates that the Trscv
        power supply of port is higher
         than the threshold value written
        in the Trscv EEPROM <Help> Alarm
        indicating that the Trscv power
        supply of port is higher than the
        threshold value written in the
         Trscv EEPROM <Condtype> VCC_HIGH_ALA_1
        <Probcause> powerProblem (36) <Alarmtype>
        equipmentAlarm (5) <Polarity> (2)
        "
	::= { rm10010mpAlmclientSfpAlmDdmEntry 7 }


rm10010mpAlmVccLowAlaPortn OBJECT-TYPE
	SYNTAX  EkiOnOff
	MAX-ACCESS read-only
	STATUS current
	DESCRIPTION
        "
        Client Trscv Power Supply Low
         :This OID indicates that the Trscv
        power supply of port is lower than
        the threshold value written in
         the Trscv EEPROM <Help> Alarm
         indicating that the Trscv power
        supply of port is lower than the
        threshold value written in the
         Trscv EEPROM <Condtype> VCC_LOW_ALA_1
        <Probcause> powerProblem (36) <Alarmtype>
        equipmentAlarm (5) <Polarity> (2)
        "
	::= { rm10010mpAlmclientSfpAlmDdmEntry 6 }


rm10010mpAlmTxBiasHighAlaPortn OBJECT-TYPE
	SYNTAX  EkiOnOff
	MAX-ACCESS read-only
	STATUS current
	DESCRIPTION
        "
        Client Trscv Bias High :This OID
        indicates that the Trscv laser
         bias current of port is higher
        than the threshold value written
        in the Trscv EEPROM <Help> Alarm
        indicating that the Trscv laser
        bias current of port is higher
         than the threshold value written
        in the Trscv EEPROM <Condtype>
         TX_BIAS_HIGH_ALA_1 <Probcause>
        transmitterFailure (56) <Alarmtype>
        equipmentAlarm (5) <Polarity> (2)
        "
	::= { rm10010mpAlmclientSfpAlmDdmEntry 5 }


rm10010mpAlmTxBiasLowAlaPortn OBJECT-TYPE
	SYNTAX  EkiOnOff
	MAX-ACCESS read-only
	STATUS current
	DESCRIPTION
        "
        Client Trscv Bias Low :This OID
        indicates that the Trscv laser
         bias current of port is lower
         than the threshold value written
        in the Trscv EEPROM <Help> Alarm
        indicating that the Trscv laser
        bias current of port is lower than
        the threshold value written in
         the Trscv EEPROM <Condtype> TX_BIAS_LOW_ALA_1
        <Probcause> transmitterFailure
         (56) <Alarmtype> equipmentAlarm
        (5) <Polarity> (2)
        "
	::= { rm10010mpAlmclientSfpAlmDdmEntry 4 }


rm10010mpAlmTxPwrHighAlaPortn OBJECT-TYPE
	SYNTAX  EkiOnOff
	MAX-ACCESS read-only
	STATUS current
	DESCRIPTION
        "
        Client Trscv Tx Power High :This
        OID indicates that the Trscv output
        power of port is higher than the
        threshold value written in the
         Trscv EEPROM <Help> Alarm indicating
        that the Trscv output power of
         port is higher than the threshold
        value written in the Trscv EEPROM
        <Condtype> TX_PWR_HIGH_ALA_1 <Probcause>
        transmitterFailure (56) <Alarmtype>
        equipmentAlarm (5) <Polarity> (2)
        "
	::= { rm10010mpAlmclientSfpAlmDdmEntry 3 }


rm10010mpAlmTxPwrLowAlaPortn OBJECT-TYPE
	SYNTAX  EkiOnOff
	MAX-ACCESS read-only
	STATUS current
	DESCRIPTION
        "
        Client Trscv Tx Power Low :This
        OID indicates that the Trscv output
        power of port is lower than the
        threshold value written in the
         Trscv EEPROM <Help> Alarm indicating
        that the Trscv output power of
         port is lower than the threshold
        value written in the Trscv EEPROM
        <Condtype> TX_PWR_LOW_ALA_1 <Probcause>
        transmitterFailure (56) <Alarmtype>
        equipmentAlarm (5) <Polarity> (2)
        "
	::= { rm10010mpAlmclientSfpAlmDdmEntry 2 }


--- *********************************************************
---     TABLE for the rm10010mpAlmclientSfpWarnDdm articles
--- *********************************************************

rm10010mpAlmclientSfpWarnDdmTable OBJECT-TYPE
	SYNTAX  SEQUENCE OF Rm10010mpAlmclientSfpWarnDdmEntry
	MAX-ACCESS not-accessible
	STATUS current
	DESCRIPTION
        "
        List of rm10010mpAlmclientSfpWarnDdm
        Article
        "
	::= { rm10010mpAlmClientNurg 232 }


rm10010mpAlmclientSfpWarnDdmEntry OBJECT-TYPE
	SYNTAX Rm10010mpAlmclientSfpWarnDdmEntry
	MAX-ACCESS not-accessible
	STATUS current
	DESCRIPTION
        "
        Row definition for the rm10010mpAlmclientSfpWarnDdm
        table
        "
	INDEX   { rm10010mpAlmclientSfpWarnDdmIndex }
	::= { rm10010mpAlmclientSfpWarnDdmTable 1 }


Rm10010mpAlmclientSfpWarnDdmEntry ::=
	SEQUENCE {
	rm10010mpAlmclientSfpWarnDdmIndex
		INTEGER,
	rm10010mpAlmRxPwrHighWngPortn
		EkiOnOff,
	rm10010mpAlmRxPwrLowWngPortn
		EkiOnOff,
	rm10010mpAlmTempHighWngPortn
		EkiOnOff,
	rm10010mpAlmTempLowWngPortn
		EkiOnOff,
	rm10010mpAlmVccHighWngPortn
		EkiOnOff,
	rm10010mpAlmVccLowWngPortn
		EkiOnOff,
	rm10010mpAlmTxBiasHighWngPortn
		EkiOnOff,
	rm10010mpAlmTxBiasLowWngPortn
		EkiOnOff,
	rm10010mpAlmTxPwrHighWngPortn
		EkiOnOff,
	rm10010mpAlmTxPwLowWngPortn
		EkiOnOff
	}


rm10010mpAlmclientSfpWarnDdmIndex OBJECT-TYPE
	SYNTAX  INTEGER(0..128)
	MAX-ACCESS  read-only
	STATUS current
	DESCRIPTION
        "
        Index definition for the rm10010mpAlmclientSfpWarnDdm
        table
        "
	::= { rm10010mpAlmclientSfpWarnDdmEntry 1 }


rm10010mpAlmRxPwrHighWngPortn OBJECT-TYPE
	SYNTAX  EkiOnOff
	MAX-ACCESS read-only
	STATUS current
	DESCRIPTION
        "
        Client Trscv Rx Power High Warning
        :This OID indicates that the Trscv
        input power is higher than the
         threshold value written in the
        Trscv EEPROM <Help> Warning indicating
        that the Trscv input power is higher
        than the threshold value written
        in the Trscv EEPROM <Condtype>
         RX_PWR_HIGH_WNG_1 <Probcause>
         receiveFailure (41) <Alarmtype>
        equipmentAlarm (5) <Polarity> (2)
        "
	::= { rm10010mpAlmclientSfpWarnDdmEntry 17 }


rm10010mpAlmRxPwrLowWngPortn OBJECT-TYPE
	SYNTAX  EkiOnOff
	MAX-ACCESS read-only
	STATUS current
	DESCRIPTION
        "
        Client Trscv Rx Power Low Warning
        :This OID indicates that the Trscv
        input power is lower than the threshold
        value written in the Trscv EEPROM
        <Help> Warning indicating that
         the Trscv input power is lower
        than the threshold value written
        in the Trscv EEPROM <Condtype>
         RX_PWR_LOW_WNG_1 <Probcause> receiveFailure
        (41) <Alarmtype> equipmentAlarm
        (5) <Polarity> (2)
        "
	::= { rm10010mpAlmclientSfpWarnDdmEntry 16 }


rm10010mpAlmTempHighWngPortn OBJECT-TYPE
	SYNTAX  EkiOnOff
	MAX-ACCESS read-only
	STATUS current
	DESCRIPTION
        "
        Client Trscv Temp High Warning
        :This OID indicates that the Trscv
        temperature is higher than the
         threshold value written in the
        Trscv EEPROM <Help> Warning indicating
        that the Trscv temperature is higher
        than the threshold value written
        in the Trscv EEPROM <Condtype>
         TEMP_HIGH_WNG_1 <Probcause> temperatureUnacceptable
        (51) <Alarmtype> equipmentAlarm
        (5) <Polarity> (2)
        "
	::= { rm10010mpAlmclientSfpWarnDdmEntry 9 }


rm10010mpAlmTempLowWngPortn OBJECT-TYPE
	SYNTAX  EkiOnOff
	MAX-ACCESS read-only
	STATUS current
	DESCRIPTION
        "
        Client Trscv Temp Low Warning
         :This OID indicates that the Trscv
        temperature is lower than the threshold
        value written in the Trscv EEPROM
        <Help> Warning indicating that
         the Trscv temperature is lower
        than the threshold value written
        in the Trscv EEPROM <Condtype>
         TEMP_LOW_WNG_1 <Probcause> temperatureUnacceptable
        (51) <Alarmtype> equipmentAlarm
        (5) <Polarity> (2)
        "
	::= { rm10010mpAlmclientSfpWarnDdmEntry 8 }


rm10010mpAlmVccHighWngPortn OBJECT-TYPE
	SYNTAX  EkiOnOff
	MAX-ACCESS read-only
	STATUS current
	DESCRIPTION
        "
        Client Trscv Power Supply High
        Warning :This OID indicates that
        the Trscv power supply is higher
        than the threshold value written
        in the Trscv EEPROM <Help> Warning
        indicating that the Trscv power
        supply is higher than the threshold
        value written in the Trscv EEPROM
        <Condtype> VCC_HIGH_WNG_1 <Probcause>
        powerProblem (36) <Alarmtype> equipmentAlarm
        (5) <Polarity> (2)
        "
	::= { rm10010mpAlmclientSfpWarnDdmEntry 7 }


rm10010mpAlmVccLowWngPortn OBJECT-TYPE
	SYNTAX  EkiOnOff
	MAX-ACCESS read-only
	STATUS current
	DESCRIPTION
        "
        Client Trscv Power Supply Low
         Warning :This OID indicates that
        the Trscv power supply is lower
        than the threshold value written
        in the Trscv EEPROM <Help> Warning
        indicating that the Trscv power
        supply is lower than the threshold
        value written in the Trscv EEPROM
        <Condtype> VCC_LOW_WNG_1 <Probcause>
        powerProblem (36) <Alarmtype> equipmentAlarm
        (5) <Polarity> (2)
        "
	::= { rm10010mpAlmclientSfpWarnDdmEntry 6 }


rm10010mpAlmTxBiasHighWngPortn OBJECT-TYPE
	SYNTAX  EkiOnOff
	MAX-ACCESS read-only
	STATUS current
	DESCRIPTION
        "
        Client Trscv Bias High Warning
        :This OID indicates that the Trscv
        laser bias current is higher than
        the threshold value written in
         the Trscv EEPROM <Help> Warning
        indicating that the Trscv laser
        bias current is higher than the
        threshold value written in the
         Trscv EEPROM <Condtype> TX_BIAS_HIGH_WNG_1
        <Probcause> transmitterFailure
         (56) <Alarmtype> equipmentAlarm
        (5) <Polarity> (2)
        "
	::= { rm10010mpAlmclientSfpWarnDdmEntry 5 }


rm10010mpAlmTxBiasLowWngPortn OBJECT-TYPE
	SYNTAX  EkiOnOff
	MAX-ACCESS read-only
	STATUS current
	DESCRIPTION
        "
        Client Trscv Bias Low Warning
         :This OID indicates that the Trscv
        laser bias current is lower than
        the threshold value written in
         the Trscv EEPROM <Help> Warning
        indicating that the Trscv laser
        bias current is lower than the
         threshold value written in the
        Trscv EEPROM <Condtype> TX_BIAS_LOW_WNG_1
        <Probcause> transmitterFailure
         (56) <Alarmtype> equipmentAlarm
        (5) <Polarity> (2)
        "
	::= { rm10010mpAlmclientSfpWarnDdmEntry 4 }


rm10010mpAlmTxPwrHighWngPortn OBJECT-TYPE
	SYNTAX  EkiOnOff
	MAX-ACCESS read-only
	STATUS current
	DESCRIPTION
        "
        Client Trscv Tx Power High Warning
        :This OID indicates that the Trscv
        output power is higher than the
        threshold value written in the
         Trscv EEPROM <Help> Warning indicating
        that the Trscv output power is
         higher than the threshold value
        written in the Trscv EEPROM <Condtype>
        TX_PWR_HIGH_WNG_1 <Probcause> transmitterFailure
        (56) <Alarmtype> equipmentAlarm
        (5) <Polarity> (2)
        "
	::= { rm10010mpAlmclientSfpWarnDdmEntry 3 }


rm10010mpAlmTxPwLowWngPortn OBJECT-TYPE
	SYNTAX  EkiOnOff
	MAX-ACCESS read-only
	STATUS current
	DESCRIPTION
        "
        Client Trscv Tx Power Low Warning
        :This OID indicates that the Trscv
        output power is lower than the
         threshold value written in the
        Trscv EEPROM <Help> Warning indicating
        that the Trscv output power is
         lower than the threshold value
        written in the Trscv EEPROM <Condtype>
        TX_PW_LOW_WNG_1 <Probcause> transmitterFailure
        (56) <Alarmtype> equipmentAlarm
        (5) <Polarity> (2)
        "
	::= { rm10010mpAlmclientSfpWarnDdmEntry 2 }


--- *****************************************************
---     LEAF for the modFanFail article
--- *****************************************************
rm10010mpAlmmodFanFail OBJECT IDENTIFIER ::= { rm10010mpAlmOtherUrg 248 }




rm10010mpAlmFan4Fail OBJECT-TYPE
	  SYNTAX EkiOnOff
	  MAX-ACCESS read-only
	  STATUS current
	  DESCRIPTION
        "
        Fan Unit N°4 Failed On Fan Module
        :This OID indicates a failure on
        fan 4. Removal of the fan unit
         or no rotation sets the OID.
         <Help>  This alarm indicates if
        the FAN n°4 is in fail condition
        <Condtype> FAN4_FAIL <Probcause>
        heatingVentCoolingSystemProblem
        (22) <Alarmtype> equipmentAlarm
        (5) <Polarity> (2)
        "
	  ::= { rm10010mpAlmmodFanFail 7 }



rm10010mpAlmFan3Fail OBJECT-TYPE
	  SYNTAX EkiOnOff
	  MAX-ACCESS read-only
	  STATUS current
	  DESCRIPTION
        "
        Fan Unit N°3 Failed On Fan Module
        :This OID indicates a failure on
        fan 3. Removal of the fan unit
         or no rotation sets the OID.
         <Help>  This alarm indicates if
        the FAN n°3 is in fail condition
        <Condtype> FAN3_FAIL <Probcause>
        heatingVentCoolingSystemProblem
        (22) <Alarmtype> equipmentAlarm
        (5) <Polarity> (2)
        "
	  ::= { rm10010mpAlmmodFanFail 6 }



rm10010mpAlmFan2Fail OBJECT-TYPE
	  SYNTAX EkiOnOff
	  MAX-ACCESS read-only
	  STATUS current
	  DESCRIPTION
        "
        Fan Unit N°2 Failed On Fan Module
        :This OID indicates a failure on
        fan 2. Removal of the fan unit
         or no rotation sets the OID.
         <Help>  This alarm indicates if
        the FAN n°2 is in fail condition
        <Condtype> FAN2_FAIL <Probcause>
        heatingVentCoolingSystemProblem
        (22) <Alarmtype> equipmentAlarm
        (5) <Polarity> (2)
        "
	  ::= { rm10010mpAlmmodFanFail 5 }



rm10010mpAlmFan1Fail OBJECT-TYPE
	  SYNTAX EkiOnOff
	  MAX-ACCESS read-only
	  STATUS current
	  DESCRIPTION
        "
        Fan Unit N°1 Failed On Fan Module
        :This OID indicates a failure on
        fan 1. Removal of the fan unit
         or no rotation sets the OID.
         <Help>  This alarm indicates if
        the FAN n°1 is in fail condition
        <Condtype> FAN1_FAIL <Probcause>
        heatingVentCoolingSystemProblem
        (22) <Alarmtype> equipmentAlarm
        (5) <Polarity> (2)
        "
	  ::= { rm10010mpAlmmodFanFail 4 }



rm10010mpAlmFansFail OBJECT-TYPE
	  SYNTAX EkiOnOff
	  MAX-ACCESS read-only
	  STATUS current
	  DESCRIPTION
        "
        Fan Module Failure :This OID indicates
        that at least one of the 4 FAN
         unit of the FAN module is in fail
        condition  <Help>  This alarm indicates
        if one the FANs is in a fail condition.
        <Condtype> FANS_FAIL <Probcause>
        heatingVentCoolingSystemProblem
        (22) <Alarmtype> equipmentAlarm
        (5) <Polarity> (2)
        "
	  ::= { rm10010mpAlmmodFanFail 2 }



rm10010mpAlmFanModuleAbsent OBJECT-TYPE
	  SYNTAX EkiOnOff
	  MAX-ACCESS read-only
	  STATUS current
	  DESCRIPTION
        "
        Fan Module Absent :This OID indicates
        the presence of the FAN module
         in the Chassis.  <Help>  This
         alarm indicates if the FAN module
        is detected in the chassis. <Condtype>
        FAN_MODULE_ABSENT <Probcause> heatingVentCoolingSystemProblem
        (22) <Alarmtype> equipmentAlarm
        (5) <Polarity> (2) <Event> ObjectCDINV
        "
	  ::= { rm10010mpAlmmodFanFail 1 }








--- *****************************************************
--- $$$$$$$$$$$$$$$$$$$$$$$$$$$$$$$$$$$$$$$$$$$$$$$$$$$$$
---     CONTROLS
--- $$$$$$$$$$$$$$$$$$$$$$$$$$$$$$$$$$$$$$$$$$$$$$$$$$$$$
--- *****************************************************



--- *****************************************************
---     LEAF for the confMgnt1 article
--- *****************************************************
rm10010mpCtrlconfMgnt1 OBJECT IDENTIFIER ::= { rm10010mpCtrlOther 1 }




rm10010mpCtrlConf2Clear1 OBJECT-TYPE
	  SYNTAX EkiOnOff
	  MAX-ACCESS read-write
	  STATUS current
	  DESCRIPTION
        "
        Clear Configuration Tables :This
        OID clears the configuration tables
        from configuration2 in the flash.
         <Help>  This control restores
         the default configuration of the
        module
        "
	  ::= { rm10010mpCtrlconfMgnt1 14 }



rm10010mpCtrlConf2Flash1 OBJECT-TYPE
	  SYNTAX EkiOnOff
	  MAX-ACCESS read-write
	  STATUS current
	  DESCRIPTION
        "
        Write Configuration Tables :This
        OID saves the current configuration
        of the PM as configuration2 in
         the flash.  <Help>  This control
        saves the customer configuration
        on the module
        "
	  ::= { rm10010mpCtrlconfMgnt1 10 }



rm10010mpCtrlConf2Load1 OBJECT-TYPE
	  SYNTAX EkiOnOff
	  MAX-ACCESS read-write
	  STATUS current
	  DESCRIPTION
        "
        Load Configuration Tables Set
         Nb 2 :When set this OID enables
        loading from flash configuration2
        into the PM.
        "
	  ::= { rm10010mpCtrlconfMgnt1 2 }



rm10010mpCtrlConf1Load1 OBJECT-TYPE
	  SYNTAX EkiOnOff
	  MAX-ACCESS read-write
	  STATUS current
	  DESCRIPTION
        "
        Load Configuration Tables Set
         Nb 1 :When set this OID enables
        loading from flash configuration1
        into the PM.
        "
	  ::= { rm10010mpCtrlconfMgnt1 1 }



--- *****************************************************
---     LEAF for the synth4 article
--- *****************************************************
rm10010mpCtrlsynth4 OBJECT IDENTIFIER ::= { rm10010mpCtrlOther 4 }




rm10010mpCtrlCorrelatOff OBJECT-TYPE
	  SYNTAX EkiOnOff
	  MAX-ACCESS read-write
	  STATUS current
	  DESCRIPTION
        "
        Disable Alarm Correlation :This
        OID disables the alarm correlation
        in the PM.
        "
	  ::= { rm10010mpCtrlsynth4 2 }



rm10010mpCtrlCorrelatOn OBJECT-TYPE
	  SYNTAX EkiOnOff
	  MAX-ACCESS read-write
	  STATUS current
	  DESCRIPTION
        "
        Enable Alarm Correlation :This
        OID enables the alarm correlation
        in the PM.
        "
	  ::= { rm10010mpCtrlsynth4 1 }



--- *****************************************************
---     LEAF for the swMgnt article
--- *****************************************************
rm10010mpCtrlswMgnt OBJECT IDENTIFIER ::= { rm10010mpCtrlOther 5 }




rm10010mpCtrlLoadSwBank2 OBJECT-TYPE
	  SYNTAX EkiOnOff
	  MAX-ACCESS read-write
	  STATUS current
	  DESCRIPTION
        "
        Set Software Nb 2 As Active :This
        OID, when set, loads the SW from
        bank2 into the PM. It must be followed
        by a reset.  <Help>  This controls
        selects the second SW bank as the
        active bank for the next module
        reset
        "
	  ::= { rm10010mpCtrlswMgnt 6 }



rm10010mpCtrlLoadSwBank1 OBJECT-TYPE
	  SYNTAX EkiOnOff
	  MAX-ACCESS read-write
	  STATUS current
	  DESCRIPTION
        "
        Set Software Nb 1 As Active :This
        OID, when set, loads the SW from
        bank1 into the PM. It must be followed
        by a reset.  <Help>  This controls
        selects the first SW bank as the
        active bank for the next module
        reset
        "
	  ::= { rm10010mpCtrlswMgnt 5 }



rm10010mpCtrlWarmReset OBJECT-TYPE
	  SYNTAX EkiOnOff
	  MAX-ACCESS read-write
	  STATUS current
	  DESCRIPTION
        "
        PM Warm Reset :This OID, when
         set, causes a warm reset of the
        PM. This reset is not traffic affecting,
        and the configuration of PM remains
        unchanged.  <Help>  This control
        initiates a warm reset of the module.
        "
	  ::= { rm10010mpCtrlswMgnt 3 }



rm10010mpCtrlColdReset OBJECT-TYPE
	  SYNTAX EkiOnOff
	  MAX-ACCESS read-write
	  STATUS current
	  DESCRIPTION
        "
        PM Cold Reset :This OID, when
         set, causes a cold reset of the
        PM. This reset is traffic affecting,
        and the configuration of PM is
         reloaded on start-up.  <Help>
          This control initiates a cold
        reset of the module.
        "
	  ::= { rm10010mpCtrlswMgnt 2 }



--- *****************************************************
---     LEAF for the gwMgnt article
--- *****************************************************
rm10010mpCtrlgwMgnt OBJECT IDENTIFIER ::= { rm10010mpCtrlOther 6 }




rm10010mpCtrlLoadGwBank4 OBJECT-TYPE
	  SYNTAX EkiOnOff
	  MAX-ACCESS read-write
	  STATUS current
	  DESCRIPTION
        "
        Set Gateware Nb 4 As Active :This
        OID, when set, loads the GW from
        bank4 (Flash) into the PM. It is
        followed by an automatic gateware
        cold reset.
        "
	  ::= { rm10010mpCtrlgwMgnt 8 }



rm10010mpCtrlLoadGwBank3 OBJECT-TYPE
	  SYNTAX EkiOnOff
	  MAX-ACCESS read-write
	  STATUS current
	  DESCRIPTION
        "
        Set Gateware Nb 3 As Active :This
        OID, when set, loads the GW from
        bank3 (Flash) into the PM. It is
        followed by an automatic gateware
        cold reset.  <Help>  This controls
        initiates a cold reset of the module
        and select the third GW bank as
        the active bank
        "
	  ::= { rm10010mpCtrlgwMgnt 7 }



rm10010mpCtrlLoadGwBank2 OBJECT-TYPE
	  SYNTAX EkiOnOff
	  MAX-ACCESS read-write
	  STATUS current
	  DESCRIPTION
        "
        Set Gateware Nb 2 As Active :This
        OID, when set, loads the GW from
        bank2 (Flash) into the PM. It is
        followed by an automatic gateware
        cold reset.
        "
	  ::= { rm10010mpCtrlgwMgnt 6 }



rm10010mpCtrlLoadGwBank1 OBJECT-TYPE
	  SYNTAX EkiOnOff
	  MAX-ACCESS read-write
	  STATUS current
	  DESCRIPTION
        "
        Set Gateware Nb 1 As Active :This
        OID, when set, loads the GW from
        bank1 (Flash) into the PM. It is
        followed by an automatic gateware
        cold reset.  <Help>  This controls
        initiates a cold reset of the module
        and select the first GW bank as
        the active bank
        "
	  ::= { rm10010mpCtrlgwMgnt 5 }



rm10010mpCtrlCurrentGwReset OBJECT-TYPE
	  SYNTAX EkiOnOff
	  MAX-ACCESS read-write
	  STATUS current
	  DESCRIPTION
        "
        Active Gateware Reset :This OID,
        when set, resets the active gateware.
        It is traffic affecting.
        "
	  ::= { rm10010mpCtrlgwMgnt 1 }



--- *********************************************************
---     TABLE for the rm10010mpCtrlaccessLoop articles
--- *********************************************************

rm10010mpCtrlaccessLoopTable OBJECT-TYPE
	SYNTAX  SEQUENCE OF Rm10010mpCtrlaccessLoopEntry
	MAX-ACCESS not-accessible
	STATUS current
	DESCRIPTION
        "
        List of rm10010mpCtrlaccessLoop
        Article
        "
	::= { rm10010mpCtrlClient 16 }


rm10010mpCtrlaccessLoopEntry OBJECT-TYPE
	SYNTAX Rm10010mpCtrlaccessLoopEntry
	MAX-ACCESS not-accessible
	STATUS current
	DESCRIPTION
        "
        Row definition for the rm10010mpCtrlaccessLoop
        table
        "
	INDEX   { rm10010mpCtrlaccessLoopIndex }
	::= { rm10010mpCtrlaccessLoopTable 1 }


Rm10010mpCtrlaccessLoopEntry ::=
	SEQUENCE {
	rm10010mpCtrlaccessLoopIndex
		INTEGER,
	rm10010mpCtrlaccessLoopPortn
		EkiState
	}


rm10010mpCtrlaccessLoopIndex OBJECT-TYPE
	SYNTAX  INTEGER(0..128)
	MAX-ACCESS  read-only
	STATUS current
	DESCRIPTION
        "
        Index definition for the rm10010mpCtrlaccessLoop
        table
        "
	::= { rm10010mpCtrlaccessLoopEntry 1 }


rm10010mpCtrlaccessLoopPortn OBJECT-TYPE
	SYNTAX  EkiState
	MAX-ACCESS read-write
	STATUS current
	DESCRIPTION
        "
        Client Facility Loopback :This
        OID, when set at '1' puts the client
        port in loopback, looping the received
        10 Gb/s signal on the transmit
         10 Gb/s output.  <Help> This control
        enables the Out Loopback on the
        client port, looping the client
        input signal on the client output
        "
	::= { rm10010mpCtrlaccessLoopEntry 2 }


--- *********************************************************
---     TABLE for the rm10010mpCtrlclientLoopToLine articles
--- *********************************************************

rm10010mpCtrlclientLoopToLineTable OBJECT-TYPE
	SYNTAX  SEQUENCE OF Rm10010mpCtrlclientLoopToLineEntry
	MAX-ACCESS not-accessible
	STATUS current
	DESCRIPTION
        "
        List of rm10010mpCtrlclientLoopToLine
        Article
        "
	::= { rm10010mpCtrlClient 17 }


rm10010mpCtrlclientLoopToLineEntry OBJECT-TYPE
	SYNTAX Rm10010mpCtrlclientLoopToLineEntry
	MAX-ACCESS not-accessible
	STATUS current
	DESCRIPTION
        "
        Row definition for the rm10010mpCtrlclientLoopToLine
        table
        "
	INDEX   { rm10010mpCtrlclientLoopToLineIndex }
	::= { rm10010mpCtrlclientLoopToLineTable 1 }


Rm10010mpCtrlclientLoopToLineEntry ::=
	SEQUENCE {
	rm10010mpCtrlclientLoopToLineIndex
		INTEGER,
	rm10010mpCtrlclientLoopToLinePortn
		EkiState
	}


rm10010mpCtrlclientLoopToLineIndex OBJECT-TYPE
	SYNTAX  INTEGER(0..128)
	MAX-ACCESS  read-only
	STATUS current
	DESCRIPTION
        "
        Index definition for the rm10010mpCtrlclientLoopToLine
        table
        "
	::= { rm10010mpCtrlclientLoopToLineEntry 1 }


rm10010mpCtrlclientLoopToLinePortn OBJECT-TYPE
	SYNTAX  EkiState
	MAX-ACCESS read-write
	STATUS current
	DESCRIPTION
        "
        Client Terminal Loopback :This
        OID, when set, puts the client
         port in loop back, looping the
        10 Gb/s output signal on the 10
        Gb/s input.<Help> This control
         enables the In Loopback on the
        client port, looping the client
        output signal on the client input
        "
	::= { rm10010mpCtrlclientLoopToLineEntry 2 }


--- *********************************************************
---     TABLE for the rm10010mpCtrlcsfUpIns articles
--- *********************************************************

rm10010mpCtrlcsfUpInsTable OBJECT-TYPE
	SYNTAX  SEQUENCE OF Rm10010mpCtrlcsfUpInsEntry
	MAX-ACCESS not-accessible
	STATUS current
	DESCRIPTION
        "
        List of rm10010mpCtrlcsfUpIns
         Article
        "
	::= { rm10010mpCtrlClient 21 }


rm10010mpCtrlcsfUpInsEntry OBJECT-TYPE
	SYNTAX Rm10010mpCtrlcsfUpInsEntry
	MAX-ACCESS not-accessible
	STATUS current
	DESCRIPTION
        "
        Row definition for the rm10010mpCtrlcsfUpIns
        table
        "
	INDEX   { rm10010mpCtrlcsfUpInsIndex }
	::= { rm10010mpCtrlcsfUpInsTable 1 }


Rm10010mpCtrlcsfUpInsEntry ::=
	SEQUENCE {
	rm10010mpCtrlcsfUpInsIndex
		INTEGER,
	rm10010mpCtrlcsfUpInsPortn
		EkiState
	}


rm10010mpCtrlcsfUpInsIndex OBJECT-TYPE
	SYNTAX  INTEGER(0..128)
	MAX-ACCESS  read-only
	STATUS current
	DESCRIPTION
        "
        Index definition for the rm10010mpCtrlcsfUpIns
        table
        "
	::= { rm10010mpCtrlcsfUpInsEntry 1 }


rm10010mpCtrlcsfUpInsPortn OBJECT-TYPE
	SYNTAX  EkiState
	MAX-ACCESS read-write
	STATUS current
	DESCRIPTION
        "
        Client Signal Fail Insertion :This
        OID, when set, inserts  a client
        signal fail in the upstream client
        Port.  <Help>  This control inserts
        a Client Signal Fail for the client
        port
        "
	::= { rm10010mpCtrlcsfUpInsEntry 2 }


--- *********************************************************
---     TABLE for the rm10010mpCtrlcaisDwIns articles
--- *********************************************************

rm10010mpCtrlcaisDwInsTable OBJECT-TYPE
	SYNTAX  SEQUENCE OF Rm10010mpCtrlcaisDwInsEntry
	MAX-ACCESS not-accessible
	STATUS current
	DESCRIPTION
        "
        List of rm10010mpCtrlcaisDwIns
        Article
        "
	::= { rm10010mpCtrlClient 22 }


rm10010mpCtrlcaisDwInsEntry OBJECT-TYPE
	SYNTAX Rm10010mpCtrlcaisDwInsEntry
	MAX-ACCESS not-accessible
	STATUS current
	DESCRIPTION
        "
        Row definition for the rm10010mpCtrlcaisDwIns
        table
        "
	INDEX   { rm10010mpCtrlcaisDwInsIndex }
	::= { rm10010mpCtrlcaisDwInsTable 1 }


Rm10010mpCtrlcaisDwInsEntry ::=
	SEQUENCE {
	rm10010mpCtrlcaisDwInsIndex
		INTEGER,
	rm10010mpCtrlcaisDwInsPortn
		EkiState
	}


rm10010mpCtrlcaisDwInsIndex OBJECT-TYPE
	SYNTAX  INTEGER(0..128)
	MAX-ACCESS  read-only
	STATUS current
	DESCRIPTION
        "
        Index definition for the rm10010mpCtrlcaisDwIns
        table
        "
	::= { rm10010mpCtrlcaisDwInsEntry 1 }


rm10010mpCtrlcaisDwInsPortn OBJECT-TYPE
	SYNTAX  EkiState
	MAX-ACCESS read-write
	STATUS current
	DESCRIPTION
        "
        Client AIS Insertion :This OID,
        when set, inserts a client AIS
         on the downstream client Port.
         <Help>  This control inserts a
        Client AIS for the client port
        "
	::= { rm10010mpCtrlcaisDwInsEntry 2 }


--- *********************************************************
---     TABLE for the rm10010mpCtrlcommAccessLoop articles
--- *********************************************************

rm10010mpCtrlcommAccessLoopTable OBJECT-TYPE
	SYNTAX  SEQUENCE OF Rm10010mpCtrlcommAccessLoopEntry
	MAX-ACCESS not-accessible
	STATUS current
	DESCRIPTION
        "
        List of rm10010mpCtrlcommAccessLoop
        Article
        "
	::= { rm10010mpCtrlLine 64 }


rm10010mpCtrlcommAccessLoopEntry OBJECT-TYPE
	SYNTAX Rm10010mpCtrlcommAccessLoopEntry
	MAX-ACCESS not-accessible
	STATUS current
	DESCRIPTION
        "
        Row definition for the rm10010mpCtrlcommAccessLoop
        table
        "
	INDEX   { rm10010mpCtrlcommAccessLoopIndex }
	::= { rm10010mpCtrlcommAccessLoopTable 1 }


Rm10010mpCtrlcommAccessLoopEntry ::=
	SEQUENCE {
	rm10010mpCtrlcommAccessLoopIndex
		INTEGER,
	rm10010mpCtrlcommAccessLoopPortn
		EkiState
	}


rm10010mpCtrlcommAccessLoopIndex OBJECT-TYPE
	SYNTAX  INTEGER(0..128)
	MAX-ACCESS  read-only
	STATUS current
	DESCRIPTION
        "
        Index definition for the rm10010mpCtrlcommAccessLoop
        table
        "
	::= { rm10010mpCtrlcommAccessLoopEntry 1 }


rm10010mpCtrlcommAccessLoopPortn OBJECT-TYPE
	SYNTAX  EkiState
	MAX-ACCESS read-write
	STATUS current
	DESCRIPTION
        "
        Line Terminal Loopback :This OID,
        when set, puts the module in common
        access loop back, looping the 100
        Gb/s output signal on the 100 Gb/s
        input.<Help> This control enables
        the In Loopback on the line port,
        looping the 100 Gb/s output signal
        on the 100 Gb/s input
        "
	::= { rm10010mpCtrlcommAccessLoopEntry 2 }


--- *********************************************************
---     TABLE for the rm10010mpCtrllineLoop articles
--- *********************************************************

rm10010mpCtrllineLoopTable OBJECT-TYPE
	SYNTAX  SEQUENCE OF Rm10010mpCtrllineLoopEntry
	MAX-ACCESS not-accessible
	STATUS current
	DESCRIPTION
        "
        List of rm10010mpCtrllineLoop
         Article
        "
	::= { rm10010mpCtrlLine 66 }


rm10010mpCtrllineLoopEntry OBJECT-TYPE
	SYNTAX Rm10010mpCtrllineLoopEntry
	MAX-ACCESS not-accessible
	STATUS current
	DESCRIPTION
        "
        Row definition for the rm10010mpCtrllineLoop
        table
        "
	INDEX   { rm10010mpCtrllineLoopIndex }
	::= { rm10010mpCtrllineLoopTable 1 }


Rm10010mpCtrllineLoopEntry ::=
	SEQUENCE {
	rm10010mpCtrllineLoopIndex
		INTEGER,
	rm10010mpCtrllineLoopPortn
		EkiState
	}


rm10010mpCtrllineLoopIndex OBJECT-TYPE
	SYNTAX  INTEGER(0..128)
	MAX-ACCESS  read-only
	STATUS current
	DESCRIPTION
        "
        Index definition for the rm10010mpCtrllineLoop
        table
        "
	::= { rm10010mpCtrllineLoopEntry 1 }


rm10010mpCtrllineLoopPortn OBJECT-TYPE
	SYNTAX  EkiState
	MAX-ACCESS read-write
	STATUS current
	DESCRIPTION
        "
        Line Facility Loopback :This OID,
        when set at '1' puts the module
        in line loopback mode, looping
         the received 100 Gb/s signal on
        the transmit 100 Gb/s output. The
        Upstream part of the module is
         timed on the 100 Gb/s recovered
        clock in that case.<Help> This
         control enables the Out Loopback
        on the line port, looping the 100
        Gb/s input signal on the 100 Gb/s
        output
        "
	::= { rm10010mpCtrllineLoopEntry 2 }


--- *********************************************************
---     TABLE for the rm10010mpCtrlfecDisable articles
--- *********************************************************

rm10010mpCtrlfecDisableTable OBJECT-TYPE
	SYNTAX  SEQUENCE OF Rm10010mpCtrlfecDisableEntry
	MAX-ACCESS not-accessible
	STATUS current
	DESCRIPTION
        "
        List of rm10010mpCtrlfecDisable
        Article
        "
	::= { rm10010mpCtrlLine 69 }


rm10010mpCtrlfecDisableEntry OBJECT-TYPE
	SYNTAX Rm10010mpCtrlfecDisableEntry
	MAX-ACCESS not-accessible
	STATUS current
	DESCRIPTION
        "
        Row definition for the rm10010mpCtrlfecDisable
        table
        "
	INDEX   { rm10010mpCtrlfecDisableIndex }
	::= { rm10010mpCtrlfecDisableTable 1 }


Rm10010mpCtrlfecDisableEntry ::=
	SEQUENCE {
	rm10010mpCtrlfecDisableIndex
		INTEGER,
	rm10010mpCtrlfecDisablePortn
		EkiState
	}


rm10010mpCtrlfecDisableIndex OBJECT-TYPE
	SYNTAX  INTEGER(0..128)
	MAX-ACCESS  read-only
	STATUS current
	DESCRIPTION
        "
        Index definition for the rm10010mpCtrlfecDisable
        table
        "
	::= { rm10010mpCtrlfecDisableEntry 1 }


rm10010mpCtrlfecDisablePortn OBJECT-TYPE
	SYNTAX  EkiState
	MAX-ACCESS read-write
	STATUS current
	DESCRIPTION
        "
        Forward Error Correction Inhibition
        :This OID, when set, inhibits the
        Forward Error Correction feature
        on the line input  <Help>  This
        control enables/disables the Forward
        Error Correction on the line interface
        "
	::= { rm10010mpCtrlfecDisableEntry 2 }


--- *****************************************************
---     LEAF for the ledTest article
--- *****************************************************
rm10010mpCtrlledTest OBJECT IDENTIFIER ::= { rm10010mpCtrlOther 192 }




rm10010mpCtrlLedOff OBJECT-TYPE
	  SYNTAX EkiOnOff
	  MAX-ACCESS read-write
	  STATUS current
	  DESCRIPTION
        "
        Leds Off :This OID switches off
        all the Leds as a test feature.
         <Help>  This control initiates
        a test leds turning all the LEDs
        to OFF
        "
	  ::= { rm10010mpCtrlledTest 3 }



rm10010mpCtrlRedLed OBJECT-TYPE
	  SYNTAX EkiOnOff
	  MAX-ACCESS read-write
	  STATUS current
	  DESCRIPTION
        "
        Red Leds Test :This OID switches
        on all the red Leds as a test feature.
         <Help>  This control initiates
        a test leds turning all the LEDs
        to red
        "
	  ::= { rm10010mpCtrlledTest 2 }



rm10010mpCtrlGreenLed OBJECT-TYPE
	  SYNTAX EkiOnOff
	  MAX-ACCESS read-write
	  STATUS current
	  DESCRIPTION
        "
        Green Leds Test :This OID switches
        on all the green Leds as a test
        feature.  <Help>  This control
         initiates a test leds turning
         all the LEDs to green
        "
	  ::= { rm10010mpCtrlledTest 1 }



--- *****************************************************
---     LEAF for the initSwitchMarvell article
--- *****************************************************
rm10010mpCtrlinitSwitchMarvell OBJECT IDENTIFIER ::= { rm10010mpCtrlOther 201 }




rm10010mpCtrlInitSwitchMarvell OBJECT-TYPE
	  SYNTAX EkiOnOff
	  MAX-ACCESS read-write
	  STATUS current
	  DESCRIPTION
        "
        Switch Initialization :This OID
        operates an initialization of the
        switch managed through the module
         <Help>  This control activates
        an initialization of the switch
        managed through the module
        "
	  ::= { rm10010mpCtrlinitSwitchMarvell 1 }



--- *********************************************************
---     TABLE for the rm10010mpCtrlmsaLineLoop articles
--- *********************************************************

rm10010mpCtrlmsaLineLoopTable OBJECT-TYPE
	SYNTAX  SEQUENCE OF Rm10010mpCtrlmsaLineLoopEntry
	MAX-ACCESS not-accessible
	STATUS current
	DESCRIPTION
        "
        List of rm10010mpCtrlmsaLineLoop
        Article
        "
	::= { rm10010mpCtrlLine 209 }


rm10010mpCtrlmsaLineLoopEntry OBJECT-TYPE
	SYNTAX Rm10010mpCtrlmsaLineLoopEntry
	MAX-ACCESS not-accessible
	STATUS current
	DESCRIPTION
        "
        Row definition for the rm10010mpCtrlmsaLineLoop
        table
        "
	INDEX   { rm10010mpCtrlmsaLineLoopIndex }
	::= { rm10010mpCtrlmsaLineLoopTable 1 }


Rm10010mpCtrlmsaLineLoopEntry ::=
	SEQUENCE {
	rm10010mpCtrlmsaLineLoopIndex
		INTEGER,
	rm10010mpCtrlmsaLineLoopPortn
		EkiState
	}


rm10010mpCtrlmsaLineLoopIndex OBJECT-TYPE
	SYNTAX  INTEGER(0..128)
	MAX-ACCESS  read-only
	STATUS current
	DESCRIPTION
        "
        Index definition for the rm10010mpCtrlmsaLineLoop
        table
        "
	::= { rm10010mpCtrlmsaLineLoopEntry 1 }


rm10010mpCtrlmsaLineLoopPortn OBJECT-TYPE
	SYNTAX  EkiState
	MAX-ACCESS read-write
	STATUS current
	DESCRIPTION
        "
        MSA Line Loop :This OID operates
        a line loopback on the MSA Line
         <Help>  This control defines the
        line loop back of the line transceiver
        "
	::= { rm10010mpCtrlmsaLineLoopEntry 2 }


--- *********************************************************
---     TABLE for the rm10010mpCtrlmsaTxReset articles
--- *********************************************************

rm10010mpCtrlmsaTxResetTable OBJECT-TYPE
	SYNTAX  SEQUENCE OF Rm10010mpCtrlmsaTxResetEntry
	MAX-ACCESS not-accessible
	STATUS current
	DESCRIPTION
        "
        List of rm10010mpCtrlmsaTxReset
        Article
        "
	::= { rm10010mpCtrlLine 210 }


rm10010mpCtrlmsaTxResetEntry OBJECT-TYPE
	SYNTAX Rm10010mpCtrlmsaTxResetEntry
	MAX-ACCESS not-accessible
	STATUS current
	DESCRIPTION
        "
        Row definition for the rm10010mpCtrlmsaTxReset
        table
        "
	INDEX   { rm10010mpCtrlmsaTxResetIndex }
	::= { rm10010mpCtrlmsaTxResetTable 1 }


Rm10010mpCtrlmsaTxResetEntry ::=
	SEQUENCE {
	rm10010mpCtrlmsaTxResetIndex
		INTEGER,
	rm10010mpCtrlmsaTxResetPortn
		EkiState
	}


rm10010mpCtrlmsaTxResetIndex OBJECT-TYPE
	SYNTAX  INTEGER(0..128)
	MAX-ACCESS  read-only
	STATUS current
	DESCRIPTION
        "
        Index definition for the rm10010mpCtrlmsaTxReset
        table
        "
	::= { rm10010mpCtrlmsaTxResetEntry 1 }


rm10010mpCtrlmsaTxResetPortn OBJECT-TYPE
	SYNTAX  EkiState
	MAX-ACCESS read-write
	STATUS current
	DESCRIPTION
        "
        Line MSA TX Reset :This OID resets
        the TX portion of the MSA line
         module  <Help > This control
         initiates a reset of the transmitting
        side
        "
	::= { rm10010mpCtrlmsaTxResetEntry 2 }


--- *********************************************************
---     TABLE for the rm10010mpCtrlmsaRxReset articles
--- *********************************************************

rm10010mpCtrlmsaRxResetTable OBJECT-TYPE
	SYNTAX  SEQUENCE OF Rm10010mpCtrlmsaRxResetEntry
	MAX-ACCESS not-accessible
	STATUS current
	DESCRIPTION
        "
        List of rm10010mpCtrlmsaRxReset
        Article
        "
	::= { rm10010mpCtrlLine 211 }


rm10010mpCtrlmsaRxResetEntry OBJECT-TYPE
	SYNTAX Rm10010mpCtrlmsaRxResetEntry
	MAX-ACCESS not-accessible
	STATUS current
	DESCRIPTION
        "
        Row definition for the rm10010mpCtrlmsaRxReset
        table
        "
	INDEX   { rm10010mpCtrlmsaRxResetIndex }
	::= { rm10010mpCtrlmsaRxResetTable 1 }


Rm10010mpCtrlmsaRxResetEntry ::=
	SEQUENCE {
	rm10010mpCtrlmsaRxResetIndex
		INTEGER,
	rm10010mpCtrlmsaRxResetPortn
		EkiState
	}


rm10010mpCtrlmsaRxResetIndex OBJECT-TYPE
	SYNTAX  INTEGER(0..128)
	MAX-ACCESS  read-only
	STATUS current
	DESCRIPTION
        "
        Index definition for the rm10010mpCtrlmsaRxReset
        table
        "
	::= { rm10010mpCtrlmsaRxResetEntry 1 }


rm10010mpCtrlmsaRxResetPortn OBJECT-TYPE
	SYNTAX  EkiState
	MAX-ACCESS read-write
	STATUS current
	DESCRIPTION
        "
        Line MSA RX Reset :This OID resets
        the RX portion of the MSA line
         module  <Help > This control
         initiates a reset of the receiving
        side
        "
	::= { rm10010mpCtrlmsaRxResetEntry 2 }


--- *********************************************************
---     TABLE for the rm10010mpCtrlmsaShutdown articles
--- *********************************************************

rm10010mpCtrlmsaShutdownTable OBJECT-TYPE
	SYNTAX  SEQUENCE OF Rm10010mpCtrlmsaShutdownEntry
	MAX-ACCESS not-accessible
	STATUS current
	DESCRIPTION
        "
        List of rm10010mpCtrlmsaShutdown
        Article
        "
	::= { rm10010mpCtrlLine 212 }


rm10010mpCtrlmsaShutdownEntry OBJECT-TYPE
	SYNTAX Rm10010mpCtrlmsaShutdownEntry
	MAX-ACCESS not-accessible
	STATUS current
	DESCRIPTION
        "
        Row definition for the rm10010mpCtrlmsaShutdown
        table
        "
	INDEX   { rm10010mpCtrlmsaShutdownIndex }
	::= { rm10010mpCtrlmsaShutdownTable 1 }


Rm10010mpCtrlmsaShutdownEntry ::=
	SEQUENCE {
	rm10010mpCtrlmsaShutdownIndex
		INTEGER,
	rm10010mpCtrlmsaShutdownPortn
		EkiState
	}


rm10010mpCtrlmsaShutdownIndex OBJECT-TYPE
	SYNTAX  INTEGER(0..128)
	MAX-ACCESS  read-only
	STATUS current
	DESCRIPTION
        "
        Index definition for the rm10010mpCtrlmsaShutdown
        table
        "
	::= { rm10010mpCtrlmsaShutdownEntry 1 }


rm10010mpCtrlmsaShutdownPortn OBJECT-TYPE
	SYNTAX  EkiState
	MAX-ACCESS read-write
	STATUS current
	DESCRIPTION
        "
        Line MSA Shutdown :This OID enters
        a process to shutdown the MSA line
        module  <Help > This control  initiates
        a shutdown of the module
        "
	::= { rm10010mpCtrlmsaShutdownEntry 2 }


--- *****************************************************
---     LEAF for the resetCount article
--- *****************************************************
rm10010mpCtrlresetCount OBJECT IDENTIFIER ::= { rm10010mpCtrlOther 259 }




rm10010mpCtrlResetcount OBJECT-TYPE
	  SYNTAX EkiOnOff
	  MAX-ACCESS read-write
	  STATUS current
	  DESCRIPTION
        "
        Module Count Global Reset :This
        OID resets all the errors counters
        on the module  <Help > This control
         initiates a reset of the errors
        counters on the module
        "
	  ::= { rm10010mpCtrlresetCount 1 }



--- *****************************************************
---     LEAF for the resetRmon article
--- *****************************************************
rm10010mpCtrlresetRmon OBJECT IDENTIFIER ::= { rm10010mpCtrlOther 260 }




rm10010mpCtrlResetrmon OBJECT-TYPE
	  SYNTAX EkiOnOff
	  MAX-ACCESS read-write
	  STATUS current
	  DESCRIPTION
        "
        Module Rmon Global Reset :This
        OID resets all the Rmon counters
        on the module  <Help > This control
         initiates a reset of the Rmon
         counters on the module
        "
	  ::= { rm10010mpCtrlresetRmon 1 }



--- *****************************************************
---     LEAF for the resetMeasurements article
--- *****************************************************
rm10010mpCtrlresetMeasurements OBJECT IDENTIFIER ::= { rm10010mpCtrlOther 261 }




rm10010mpCtrlResetmeasurements OBJECT-TYPE
	  SYNTAX EkiOnOff
	  MAX-ACCESS read-write
	  STATUS current
	  DESCRIPTION
        "
        Management Meas Global Reset :This
        OID resets some measurements on
        the management  <Help > This control
         initiates a reset of some measurements
        on the management
        "
	  ::= { rm10010mpCtrlresetMeasurements 1 }








--- *****************************************************
--- $$$$$$$$$$$$$$$$$$$$$$$$$$$$$$$$$$$$$$$$$$$$$$$$$$$$$
---     COUNTERS
--- $$$$$$$$$$$$$$$$$$$$$$$$$$$$$$$$$$$$$$$$$$$$$$$$$$$$$
--- *****************************************************



--- *********************************************************
---     TABLE for the rm10010mpCntclientInputErrorCounterLaneOne articles
--- *********************************************************

rm10010mpCntclientInputErrorCounterLaneOneTable OBJECT-TYPE
	SYNTAX  SEQUENCE OF Rm10010mpCntclientInputErrorCounterLaneOneEntry
	MAX-ACCESS not-accessible
	STATUS current
	DESCRIPTION
        "
        List of rm10010mpCntclientInputErrorCounterLaneOne
        Article
        "
	::= { rm10010mpCntClient 16 }


rm10010mpCntclientInputErrorCounterLaneOneEntry OBJECT-TYPE
	SYNTAX Rm10010mpCntclientInputErrorCounterLaneOneEntry
	MAX-ACCESS not-accessible
	STATUS current
	DESCRIPTION
        "
        Row definition for the rm10010mpCntclientInputErrorCounterLaneOne
        table
        "
	INDEX   { rm10010mpCntclientInputErrorCounterLaneOneIndex }
	::= { rm10010mpCntclientInputErrorCounterLaneOneTable 1 }


Rm10010mpCntclientInputErrorCounterLaneOneEntry ::=
	SEQUENCE {
	rm10010mpCntclientInputErrorCounterLaneOneIndex
		INTEGER,
	rm10010mpCntclientInputErrorCounterLaneOneValuePortn
		Counter32,
	rm10010mpCntclientInputErrorCounterLaneOneErrorPortn
		EkiOnOff,
	rm10010mpCntclientInputErrorCounterLaneOneOverloadPortn
		EkiOnOff
	}


rm10010mpCntclientInputErrorCounterLaneOneIndex OBJECT-TYPE
	SYNTAX  INTEGER(0..128)
	MAX-ACCESS  read-only
	STATUS current
	DESCRIPTION
        "
        Index definition for the rm10010mpCntclientInputErrorCounterLaneOne
        table
        "
	::= { rm10010mpCntclientInputErrorCounterLaneOneEntry 1 }


rm10010mpCntclientInputErrorCounterLaneOneValuePortn OBJECT-TYPE
	SYNTAX  Counter32
	MAX-ACCESS read-only
	STATUS current
	DESCRIPTION
        "
        Client_Input_Error_Counter_Lane1
        :This counter is incremented each
        time a coding violation is detected
        on the host lane of the client
         transceiver <Help> This counter
        is incremented each time a coding
        violation is detected on the host
        lane of the client transceiver
        "
	::= { rm10010mpCntclientInputErrorCounterLaneOneEntry 2 }


rm10010mpCntclientInputErrorCounterLaneOneErrorPortn OBJECT-TYPE
	SYNTAX  EkiOnOff
	MAX-ACCESS read-only
	STATUS current
	DESCRIPTION
        "
        Client Input Counter Error :This
        OID when set indicates the rate
        adaptation removal counter value
        is invalid on Port
        "
	::= { rm10010mpCntclientInputErrorCounterLaneOneEntry 3 }


rm10010mpCntclientInputErrorCounterLaneOneOverloadPortn OBJECT-TYPE
	SYNTAX  EkiOnOff
	MAX-ACCESS read-only
	STATUS current
	DESCRIPTION
        "
        Client Input Counter Overload
         :This OID when set indicates a
        rate adaptation removal counter
        overload on Port
        "
	::= { rm10010mpCntclientInputErrorCounterLaneOneEntry 4 }


--- *********************************************************
---     TABLE for the rm10010mpCntclientInputErrorCounterLaneTwo articles
--- *********************************************************

rm10010mpCntclientInputErrorCounterLaneTwoTable OBJECT-TYPE
	SYNTAX  SEQUENCE OF Rm10010mpCntclientInputErrorCounterLaneTwoEntry
	MAX-ACCESS not-accessible
	STATUS current
	DESCRIPTION
        "
        List of rm10010mpCntclientInputErrorCounterLaneTwo
        Article
        "
	::= { rm10010mpCntClient 32 }


rm10010mpCntclientInputErrorCounterLaneTwoEntry OBJECT-TYPE
	SYNTAX Rm10010mpCntclientInputErrorCounterLaneTwoEntry
	MAX-ACCESS not-accessible
	STATUS current
	DESCRIPTION
        "
        Row definition for the rm10010mpCntclientInputErrorCounterLaneTwo
        table
        "
	INDEX   { rm10010mpCntclientInputErrorCounterLaneTwoIndex }
	::= { rm10010mpCntclientInputErrorCounterLaneTwoTable 1 }


Rm10010mpCntclientInputErrorCounterLaneTwoEntry ::=
	SEQUENCE {
	rm10010mpCntclientInputErrorCounterLaneTwoIndex
		INTEGER,
	rm10010mpCntclientInputErrorCounterLaneTwoValuePortn
		Counter32,
	rm10010mpCntclientInputErrorCounterLaneTwoErrorPortn
		EkiOnOff,
	rm10010mpCntclientInputErrorCounterLaneTwoOverloadPortn
		EkiOnOff
	}


rm10010mpCntclientInputErrorCounterLaneTwoIndex OBJECT-TYPE
	SYNTAX  INTEGER(0..128)
	MAX-ACCESS  read-only
	STATUS current
	DESCRIPTION
        "
        Index definition for the rm10010mpCntclientInputErrorCounterLaneTwo
        table
        "
	::= { rm10010mpCntclientInputErrorCounterLaneTwoEntry 1 }


rm10010mpCntclientInputErrorCounterLaneTwoValuePortn OBJECT-TYPE
	SYNTAX  Counter32
	MAX-ACCESS read-only
	STATUS current
	DESCRIPTION
        "
        Client_Input_Error_Counter_Lane2
        :This counter is incremented each
        time a coding violation is detected
        on the host lane of the client
         transceiver <Help> This counter
        is incremented each time a coding
        violation is detected on the host
        lane of the client transceiver
        "
	::= { rm10010mpCntclientInputErrorCounterLaneTwoEntry 2 }


rm10010mpCntclientInputErrorCounterLaneTwoErrorPortn OBJECT-TYPE
	SYNTAX  EkiOnOff
	MAX-ACCESS read-only
	STATUS current
	DESCRIPTION
        "
        Client Input Counter Error :This
        OID when set indicates the client
        error counter value is invalid
         on Port
        "
	::= { rm10010mpCntclientInputErrorCounterLaneTwoEntry 3 }


rm10010mpCntclientInputErrorCounterLaneTwoOverloadPortn OBJECT-TYPE
	SYNTAX  EkiOnOff
	MAX-ACCESS read-only
	STATUS current
	DESCRIPTION
        "
        Client Input Counter Overload
         :This OID when set indicates a
        client input error counter overload
        on Port
        "
	::= { rm10010mpCntclientInputErrorCounterLaneTwoEntry 4 }


--- *********************************************************
---     TABLE for the rm10010mpCntclientInputErrorCounter articles
--- *********************************************************

rm10010mpCntclientInputErrorCounterTable OBJECT-TYPE
	SYNTAX  SEQUENCE OF Rm10010mpCntclientInputErrorCounterEntry
	MAX-ACCESS not-accessible
	STATUS current
	DESCRIPTION
        "
        List of rm10010mpCntclientInputErrorCounter
        Article
        "
	::= { rm10010mpCntClient 80 }


rm10010mpCntclientInputErrorCounterEntry OBJECT-TYPE
	SYNTAX Rm10010mpCntclientInputErrorCounterEntry
	MAX-ACCESS not-accessible
	STATUS current
	DESCRIPTION
        "
        Row definition for the rm10010mpCntclientInputErrorCounter
        table
        "
	INDEX   { rm10010mpCntclientInputErrorCounterIndex }
	::= { rm10010mpCntclientInputErrorCounterTable 1 }


Rm10010mpCntclientInputErrorCounterEntry ::=
	SEQUENCE {
	rm10010mpCntclientInputErrorCounterIndex
		INTEGER,
	rm10010mpCntclientInputErrorCounterValuePortn
		Counter32,
	rm10010mpCntclientInputErrorCounterErrorPortn
		EkiOnOff,
	rm10010mpCntclientInputErrorCounterOverloadPortn
		EkiOnOff
	}


rm10010mpCntclientInputErrorCounterIndex OBJECT-TYPE
	SYNTAX  INTEGER(0..128)
	MAX-ACCESS  read-only
	STATUS current
	DESCRIPTION
        "
        Index definition for the rm10010mpCntclientInputErrorCounter
        table
        "
	::= { rm10010mpCntclientInputErrorCounterEntry 1 }


rm10010mpCntclientInputErrorCounterValuePortn OBJECT-TYPE
	SYNTAX  Counter32
	MAX-ACCESS read-only
	STATUS current
	DESCRIPTION
        "
        Client Input Errors :This counter
        is increased each time a 10b/8b
        running disparity error is detected
        on the Client input stream  <Help>
         This counter gives the number
         of 10b/8b running disparity errors
        on the client port
        "
	::= { rm10010mpCntclientInputErrorCounterEntry 2 }


rm10010mpCntclientInputErrorCounterErrorPortn OBJECT-TYPE
	SYNTAX  EkiOnOff
	MAX-ACCESS read-only
	STATUS current
	DESCRIPTION
        "
        Client Counter Error :This OID
        when set indicates the client error
        counter value is invalid on Port
        "
	::= { rm10010mpCntclientInputErrorCounterEntry 3 }


rm10010mpCntclientInputErrorCounterOverloadPortn OBJECT-TYPE
	SYNTAX  EkiOnOff
	MAX-ACCESS read-only
	STATUS current
	DESCRIPTION
        "
        Client Counter Overload :This
         OID when set indicates a client
        input error counter overload on
        Port
        "
	::= { rm10010mpCntclientInputErrorCounterEntry 4 }


--- *********************************************************
---     TABLE for the rm10010mpCntclientCbipCounter articles
--- *********************************************************

rm10010mpCntclientCbipCounterTable OBJECT-TYPE
	SYNTAX  SEQUENCE OF Rm10010mpCntclientCbipCounterEntry
	MAX-ACCESS not-accessible
	STATUS current
	DESCRIPTION
        "
        List of rm10010mpCntclientCbipCounter
        Article
        "
	::= { rm10010mpCntClient 96 }


rm10010mpCntclientCbipCounterEntry OBJECT-TYPE
	SYNTAX Rm10010mpCntclientCbipCounterEntry
	MAX-ACCESS not-accessible
	STATUS current
	DESCRIPTION
        "
        Row definition for the rm10010mpCntclientCbipCounter
        table
        "
	INDEX   { rm10010mpCntclientCbipCounterIndex }
	::= { rm10010mpCntclientCbipCounterTable 1 }


Rm10010mpCntclientCbipCounterEntry ::=
	SEQUENCE {
	rm10010mpCntclientCbipCounterIndex
		INTEGER,
	rm10010mpCntclientCbipCounterValuePortn
		Counter32,
	rm10010mpCntclientCbipCounterErrorPortn
		EkiOnOff,
	rm10010mpCntclientCbipCounterOverloadPortn
		EkiOnOff
	}


rm10010mpCntclientCbipCounterIndex OBJECT-TYPE
	SYNTAX  INTEGER(0..128)
	MAX-ACCESS  read-only
	STATUS current
	DESCRIPTION
        "
        Index definition for the rm10010mpCntclientCbipCounter
        table
        "
	::= { rm10010mpCntclientCbipCounterEntry 1 }


rm10010mpCntclientCbipCounterValuePortn OBJECT-TYPE
	SYNTAX  Counter32
	MAX-ACCESS read-only
	STATUS current
	DESCRIPTION
        "
        Client Output Errors :This counter
        is incremented each time a CBIP
        parity error is detected on the
        Client output stream  <Help>  This
        counter gives the number of CBIP
        errors on the client port
        "
	::= { rm10010mpCntclientCbipCounterEntry 2 }


rm10010mpCntclientCbipCounterErrorPortn OBJECT-TYPE
	SYNTAX  EkiOnOff
	MAX-ACCESS read-only
	STATUS current
	DESCRIPTION
        "
        Client Counter Error :This OID
        when set indicates the CBIP error
        counter value is invalid on Port
        "
	::= { rm10010mpCntclientCbipCounterEntry 3 }


rm10010mpCntclientCbipCounterOverloadPortn OBJECT-TYPE
	SYNTAX  EkiOnOff
	MAX-ACCESS read-only
	STATUS current
	DESCRIPTION
        "
        Client CBIP Counter Overload :This
        OID when set indicates a CBIP error
        counter overload on Port
        "
	::= { rm10010mpCntclientCbipCounterEntry 4 }


--- *********************************************************
---     TABLE for the rm10010mpCntlocalLineSmBip8ErrorCounter articles
--- *********************************************************

rm10010mpCntlocalLineSmBip8ErrorCounterTable OBJECT-TYPE
	SYNTAX  SEQUENCE OF Rm10010mpCntlocalLineSmBip8ErrorCounterEntry
	MAX-ACCESS not-accessible
	STATUS current
	DESCRIPTION
        "
        List of rm10010mpCntlocalLineSmBip8ErrorCounter
        Article
        "
	::= { rm10010mpCntLine 192 }


rm10010mpCntlocalLineSmBip8ErrorCounterEntry OBJECT-TYPE
	SYNTAX Rm10010mpCntlocalLineSmBip8ErrorCounterEntry
	MAX-ACCESS not-accessible
	STATUS current
	DESCRIPTION
        "
        Row definition for the rm10010mpCntlocalLineSmBip8ErrorCounter
        table
        "
	INDEX   { rm10010mpCntlocalLineSmBip8ErrorCounterIndex }
	::= { rm10010mpCntlocalLineSmBip8ErrorCounterTable 1 }


Rm10010mpCntlocalLineSmBip8ErrorCounterEntry ::=
	SEQUENCE {
	rm10010mpCntlocalLineSmBip8ErrorCounterIndex
		INTEGER,
	rm10010mpCntlocalLineSmBip8ErrorCounterValuePortn
		Counter64,
	rm10010mpCntlocalLineSmBip8ErrorCounterErrorPortn
		EkiOnOff,
	rm10010mpCntlocalLineSmBip8ErrorCounterOverloadPortn
		EkiOnOff
	}


rm10010mpCntlocalLineSmBip8ErrorCounterIndex OBJECT-TYPE
	SYNTAX  INTEGER(0..128)
	MAX-ACCESS  read-only
	STATUS current
	DESCRIPTION
        "
        Index definition for the rm10010mpCntlocalLineSmBip8ErrorCounter
        table
        "
	::= { rm10010mpCntlocalLineSmBip8ErrorCounterEntry 1 }


rm10010mpCntlocalLineSmBip8ErrorCounterValuePortn OBJECT-TYPE
	SYNTAX  Counter64
	MAX-ACCESS read-only
	STATUS current
	DESCRIPTION
        "
        Line Input SM-BIP8 Errors :This
        OID gives the current Bit Error
        Rate (residual SM-BIP8 error) after
        FEC   <Help> This counter gives
        the current Bit Error Rate (residual
        SM-BIP8 error) after FEC
        "
	::= { rm10010mpCntlocalLineSmBip8ErrorCounterEntry 2 }


rm10010mpCntlocalLineSmBip8ErrorCounterErrorPortn OBJECT-TYPE
	SYNTAX  EkiOnOff
	MAX-ACCESS read-only
	STATUS current
	DESCRIPTION
        "
        Line Counter Error :This OID when
        set indicates the B1 error counter
        value is invalid on Port
        "
	::= { rm10010mpCntlocalLineSmBip8ErrorCounterEntry 3 }


rm10010mpCntlocalLineSmBip8ErrorCounterOverloadPortn OBJECT-TYPE
	SYNTAX  EkiOnOff
	MAX-ACCESS read-only
	STATUS current
	DESCRIPTION
        "
        Line Counter Overload :This OID
        when set indicates a B1 error counter
        overload on Port
        "
	::= { rm10010mpCntlocalLineSmBip8ErrorCounterEntry 4 }


--- *********************************************************
---     TABLE for the rm10010mpCntlocalLineFecCorrectedErrorsCounter articles
--- *********************************************************

rm10010mpCntlocalLineFecCorrectedErrorsCounterTable OBJECT-TYPE
	SYNTAX  SEQUENCE OF Rm10010mpCntlocalLineFecCorrectedErrorsCounterEntry
	MAX-ACCESS not-accessible
	STATUS current
	DESCRIPTION
        "
        List of rm10010mpCntlocalLineFecCorrectedErrorsCounter
        Article
        "
	::= { rm10010mpCntLine 193 }


rm10010mpCntlocalLineFecCorrectedErrorsCounterEntry OBJECT-TYPE
	SYNTAX Rm10010mpCntlocalLineFecCorrectedErrorsCounterEntry
	MAX-ACCESS not-accessible
	STATUS current
	DESCRIPTION
        "
        Row definition for the rm10010mpCntlocalLineFecCorrectedErrorsCounter
        table
        "
	INDEX   { rm10010mpCntlocalLineFecCorrectedErrorsCounterIndex }
	::= { rm10010mpCntlocalLineFecCorrectedErrorsCounterTable 1 }


Rm10010mpCntlocalLineFecCorrectedErrorsCounterEntry ::=
	SEQUENCE {
	rm10010mpCntlocalLineFecCorrectedErrorsCounterIndex
		INTEGER,
	rm10010mpCntlocalLineFecCorrectedErrorsCounterValuePortn
		Counter64,
	rm10010mpCntlocalLineFecCorrectedErrorsCounterErrorPortn
		EkiOnOff,
	rm10010mpCntlocalLineFecCorrectedErrorsCounterOverloadPortn
		EkiOnOff
	}


rm10010mpCntlocalLineFecCorrectedErrorsCounterIndex OBJECT-TYPE
	SYNTAX  INTEGER(0..128)
	MAX-ACCESS  read-only
	STATUS current
	DESCRIPTION
        "
        Index definition for the rm10010mpCntlocalLineFecCorrectedErrorsCounter
        table
        "
	::= { rm10010mpCntlocalLineFecCorrectedErrorsCounterEntry 1 }


rm10010mpCntlocalLineFecCorrectedErrorsCounterValuePortn OBJECT-TYPE
	SYNTAX  Counter64
	MAX-ACCESS read-only
	STATUS current
	DESCRIPTION
        "
        Line Input HD FEC Corrected Errors
        :This OID gives the current Bit
        Error Rate before the Hard Decision
        FEC  <Help> This counter gives
         the current Bit Error Rate before
        the Hard Decision FEC
        "
	::= { rm10010mpCntlocalLineFecCorrectedErrorsCounterEntry 2 }


rm10010mpCntlocalLineFecCorrectedErrorsCounterErrorPortn OBJECT-TYPE
	SYNTAX  EkiOnOff
	MAX-ACCESS read-only
	STATUS current
	DESCRIPTION
        "
        FEC Counter Error :This bit when
        set indicates the FEC corrected
        errors counter value is invalid
        on Line
        "
	::= { rm10010mpCntlocalLineFecCorrectedErrorsCounterEntry 3 }


rm10010mpCntlocalLineFecCorrectedErrorsCounterOverloadPortn OBJECT-TYPE
	SYNTAX  EkiOnOff
	MAX-ACCESS read-only
	STATUS current
	DESCRIPTION
        "
        FEC Counter Overload :This bit
        when set indicates a FEC corrected
        errors counter overload on Line
        "
	::= { rm10010mpCntlocalLineFecCorrectedErrorsCounterEntry 4 }


--- *********************************************************
---     TABLE for the rm10010mpCntremoteLineSmBip8ErrorCounter articles
--- *********************************************************

rm10010mpCntremoteLineSmBip8ErrorCounterTable OBJECT-TYPE
	SYNTAX  SEQUENCE OF Rm10010mpCntremoteLineSmBip8ErrorCounterEntry
	MAX-ACCESS not-accessible
	STATUS current
	DESCRIPTION
        "
        List of rm10010mpCntremoteLineSmBip8ErrorCounter
        Article
        "
	::= { rm10010mpCntLine 194 }


rm10010mpCntremoteLineSmBip8ErrorCounterEntry OBJECT-TYPE
	SYNTAX Rm10010mpCntremoteLineSmBip8ErrorCounterEntry
	MAX-ACCESS not-accessible
	STATUS current
	DESCRIPTION
        "
        Row definition for the rm10010mpCntremoteLineSmBip8ErrorCounter
        table
        "
	INDEX   { rm10010mpCntremoteLineSmBip8ErrorCounterIndex }
	::= { rm10010mpCntremoteLineSmBip8ErrorCounterTable 1 }


Rm10010mpCntremoteLineSmBip8ErrorCounterEntry ::=
	SEQUENCE {
	rm10010mpCntremoteLineSmBip8ErrorCounterIndex
		INTEGER,
	rm10010mpCntremoteLineSmBip8ErrorCounterValuePortn
		Counter64,
	rm10010mpCntremoteLineSmBip8ErrorCounterErrorPortn
		EkiOnOff,
	rm10010mpCntremoteLineSmBip8ErrorCounterOverloadPortn
		EkiOnOff
	}


rm10010mpCntremoteLineSmBip8ErrorCounterIndex OBJECT-TYPE
	SYNTAX  INTEGER(0..128)
	MAX-ACCESS  read-only
	STATUS current
	DESCRIPTION
        "
        Index definition for the rm10010mpCntremoteLineSmBip8ErrorCounter
        table
        "
	::= { rm10010mpCntremoteLineSmBip8ErrorCounterEntry 1 }


rm10010mpCntremoteLineSmBip8ErrorCounterValuePortn OBJECT-TYPE
	SYNTAX  Counter64
	MAX-ACCESS read-only
	STATUS current
	DESCRIPTION
        "
        Remote SM BIP8 :This OID gives
        the current Bit Error Rate (residual
        SM-BIP8 error) after FEC on the
        remote side  <Help> This counter
        gives the current Bit Error Rate
        (residual SM-BIP8 error) after
         FEC on the remote side
        "
	::= { rm10010mpCntremoteLineSmBip8ErrorCounterEntry 2 }


rm10010mpCntremoteLineSmBip8ErrorCounterErrorPortn OBJECT-TYPE
	SYNTAX  EkiOnOff
	MAX-ACCESS read-only
	STATUS current
	DESCRIPTION
        "
        Remote Counter Error :
        "
	::= { rm10010mpCntremoteLineSmBip8ErrorCounterEntry 3 }


rm10010mpCntremoteLineSmBip8ErrorCounterOverloadPortn OBJECT-TYPE
	SYNTAX  EkiOnOff
	MAX-ACCESS read-only
	STATUS current
	DESCRIPTION
        "
        Remote Counter Overload :
        "
	::= { rm10010mpCntremoteLineSmBip8ErrorCounterEntry 4 }


--- *********************************************************
---     TABLE for the rm10010mpCntlineDfrmTimCnt articles
--- *********************************************************

rm10010mpCntlineDfrmTimCntTable OBJECT-TYPE
	SYNTAX  SEQUENCE OF Rm10010mpCntlineDfrmTimCntEntry
	MAX-ACCESS not-accessible
	STATUS current
	DESCRIPTION
        "
        List of rm10010mpCntlineDfrmTimCnt
        Article
        "
	::= { rm10010mpCntLine 195 }


rm10010mpCntlineDfrmTimCntEntry OBJECT-TYPE
	SYNTAX Rm10010mpCntlineDfrmTimCntEntry
	MAX-ACCESS not-accessible
	STATUS current
	DESCRIPTION
        "
        Row definition for the rm10010mpCntlineDfrmTimCnt
        table
        "
	INDEX   { rm10010mpCntlineDfrmTimCntIndex }
	::= { rm10010mpCntlineDfrmTimCntTable 1 }


Rm10010mpCntlineDfrmTimCntEntry ::=
	SEQUENCE {
	rm10010mpCntlineDfrmTimCntIndex
		INTEGER,
	rm10010mpCntlineDfrmTimCntValuePortn
		Counter64,
	rm10010mpCntlineDfrmTimCntErrorPortn
		EkiOnOff,
	rm10010mpCntlineDfrmTimCntOverloadPortn
		EkiOnOff
	}


rm10010mpCntlineDfrmTimCntIndex OBJECT-TYPE
	SYNTAX  INTEGER(0..128)
	MAX-ACCESS  read-only
	STATUS current
	DESCRIPTION
        "
        Index definition for the rm10010mpCntlineDfrmTimCnt
        table
        "
	::= { rm10010mpCntlineDfrmTimCntEntry 1 }


rm10010mpCntlineDfrmTimCntValuePortn OBJECT-TYPE
	SYNTAX  Counter64
	MAX-ACCESS read-only
	STATUS current
	DESCRIPTION
        "
        Line Timer Counter :
        "
	::= { rm10010mpCntlineDfrmTimCntEntry 2 }


rm10010mpCntlineDfrmTimCntErrorPortn OBJECT-TYPE
	SYNTAX  EkiOnOff
	MAX-ACCESS read-only
	STATUS current
	DESCRIPTION
        "
        Line Counter Error :This OID when
        set indicates the deframer timer
        counter value is invalid on Port
        "
	::= { rm10010mpCntlineDfrmTimCntEntry 3 }


rm10010mpCntlineDfrmTimCntOverloadPortn OBJECT-TYPE
	SYNTAX  EkiOnOff
	MAX-ACCESS read-only
	STATUS current
	DESCRIPTION
        "
        Line Counter Overload :This OID
        when set indicates a deframer timer
        counter overload on Port
        "
	::= { rm10010mpCntlineDfrmTimCntEntry 4 }


--- *********************************************************
---     TABLE for the rm10010mpCntlocalLineTrscvFecCorrectedErrorCounter articles
--- *********************************************************

rm10010mpCntlocalLineTrscvFecCorrectedErrorCounterTable OBJECT-TYPE
	SYNTAX  SEQUENCE OF Rm10010mpCntlocalLineTrscvFecCorrectedErrorCounterEntry
	MAX-ACCESS not-accessible
	STATUS current
	DESCRIPTION
        "
        List of rm10010mpCntlocalLineTrscvFecCorrectedErrorCounter
        Article
        "
	::= { rm10010mpCntLine 196 }


rm10010mpCntlocalLineTrscvFecCorrectedErrorCounterEntry OBJECT-TYPE
	SYNTAX Rm10010mpCntlocalLineTrscvFecCorrectedErrorCounterEntry
	MAX-ACCESS not-accessible
	STATUS current
	DESCRIPTION
        "
        Row definition for the rm10010mpCntlocalLineTrscvFecCorrectedErrorCounter
        table
        "
	INDEX   { rm10010mpCntlocalLineTrscvFecCorrectedErrorCounterIndex }
	::= { rm10010mpCntlocalLineTrscvFecCorrectedErrorCounterTable 1 }


Rm10010mpCntlocalLineTrscvFecCorrectedErrorCounterEntry ::=
	SEQUENCE {
	rm10010mpCntlocalLineTrscvFecCorrectedErrorCounterIndex
		INTEGER,
	rm10010mpCntlocalLineTrscvFecCorrectedErrorCounterValuePortn
		Counter64,
	rm10010mpCntlocalLineTrscvFecCorrectedErrorCounterErrorPortn
		EkiOnOff,
	rm10010mpCntlocalLineTrscvFecCorrectedErrorCounterOverloadPortn
		EkiOnOff
	}


rm10010mpCntlocalLineTrscvFecCorrectedErrorCounterIndex OBJECT-TYPE
	SYNTAX  INTEGER(0..128)
	MAX-ACCESS  read-only
	STATUS current
	DESCRIPTION
        "
        Index definition for the rm10010mpCntlocalLineTrscvFecCorrectedErrorCounter
        table
        "
	::= { rm10010mpCntlocalLineTrscvFecCorrectedErrorCounterEntry 1 }


rm10010mpCntlocalLineTrscvFecCorrectedErrorCounterValuePortn OBJECT-TYPE
	SYNTAX  Counter64
	MAX-ACCESS read-only
	STATUS current
	DESCRIPTION
        "
        Line Input SD FEC Corrected Errors
        :This OID gives the current Bit
        Error Rate before the Soft Decision
        FEC  <Help> This counter gives
         the current Bit Error Rate before
        the Soft Decision FEC
        "
	::= { rm10010mpCntlocalLineTrscvFecCorrectedErrorCounterEntry 2 }


rm10010mpCntlocalLineTrscvFecCorrectedErrorCounterErrorPortn OBJECT-TYPE
	SYNTAX  EkiOnOff
	MAX-ACCESS read-only
	STATUS current
	DESCRIPTION
        "
        Line Counter Error :This OID when
        set indicates the deframer timer
        counter value is invalid on Port
        "
	::= { rm10010mpCntlocalLineTrscvFecCorrectedErrorCounterEntry 3 }


rm10010mpCntlocalLineTrscvFecCorrectedErrorCounterOverloadPortn OBJECT-TYPE
	SYNTAX  EkiOnOff
	MAX-ACCESS read-only
	STATUS current
	DESCRIPTION
        "
        Line Counter Overload :This OID
        when set indicates a deframer timer
        counter overload on Port
        "
	::= { rm10010mpCntlocalLineTrscvFecCorrectedErrorCounterEntry 4 }


--- *********************************************************
---     TABLE for the rm10010mpCntlocalLineTrscvFecUncorrectedErrorCounter articles
--- *********************************************************

rm10010mpCntlocalLineTrscvFecUncorrectedErrorCounterTable OBJECT-TYPE
	SYNTAX  SEQUENCE OF Rm10010mpCntlocalLineTrscvFecUncorrectedErrorCounterEntry
	MAX-ACCESS not-accessible
	STATUS current
	DESCRIPTION
        "
        List of rm10010mpCntlocalLineTrscvFecUncorrectedErrorCounter
        Article
        "
	::= { rm10010mpCntLine 197 }


rm10010mpCntlocalLineTrscvFecUncorrectedErrorCounterEntry OBJECT-TYPE
	SYNTAX Rm10010mpCntlocalLineTrscvFecUncorrectedErrorCounterEntry
	MAX-ACCESS not-accessible
	STATUS current
	DESCRIPTION
        "
        Row definition for the rm10010mpCntlocalLineTrscvFecUncorrectedErrorCounter
        table
        "
	INDEX   { rm10010mpCntlocalLineTrscvFecUncorrectedErrorCounterIndex }
	::= { rm10010mpCntlocalLineTrscvFecUncorrectedErrorCounterTable 1 }


Rm10010mpCntlocalLineTrscvFecUncorrectedErrorCounterEntry ::=
	SEQUENCE {
	rm10010mpCntlocalLineTrscvFecUncorrectedErrorCounterIndex
		INTEGER,
	rm10010mpCntlocalLineTrscvFecUncorrectedErrorCounterValuePortn
		Counter64,
	rm10010mpCntlocalLineTrscvFecUncorrectedErrorCounterErrorPortn
		EkiOnOff,
	rm10010mpCntlocalLineTrscvFecUncorrectedErrorCounterOverloadPortn
		EkiOnOff
	}


rm10010mpCntlocalLineTrscvFecUncorrectedErrorCounterIndex OBJECT-TYPE
	SYNTAX  INTEGER(0..128)
	MAX-ACCESS  read-only
	STATUS current
	DESCRIPTION
        "
        Index definition for the rm10010mpCntlocalLineTrscvFecUncorrectedErrorCounter
        table
        "
	::= { rm10010mpCntlocalLineTrscvFecUncorrectedErrorCounterEntry 1 }


rm10010mpCntlocalLineTrscvFecUncorrectedErrorCounterValuePortn OBJECT-TYPE
	SYNTAX  Counter64
	MAX-ACCESS read-only
	STATUS current
	DESCRIPTION
        "
        SD Uncorrected :This OID gives
        the current Bit Error Rate after
        the Soft Decision FEC (residual)
         <Help> This counter gives the
         current Bit Error Rate after the
        Soft Decision FEC (residual)
        "
	::= { rm10010mpCntlocalLineTrscvFecUncorrectedErrorCounterEntry 2 }


rm10010mpCntlocalLineTrscvFecUncorrectedErrorCounterErrorPortn OBJECT-TYPE
	SYNTAX  EkiOnOff
	MAX-ACCESS read-only
	STATUS current
	DESCRIPTION
        "
        Line Counter Error :This OID when
        set indicates the deframer timer
        counter value is invalid on Port
        "
	::= { rm10010mpCntlocalLineTrscvFecUncorrectedErrorCounterEntry 3 }


rm10010mpCntlocalLineTrscvFecUncorrectedErrorCounterOverloadPortn OBJECT-TYPE
	SYNTAX  EkiOnOff
	MAX-ACCESS read-only
	STATUS current
	DESCRIPTION
        "
        Line Counter Overload :This OID
        when set indicates a deframer timer
        counter overload on Port
        "
	::= { rm10010mpCntlocalLineTrscvFecUncorrectedErrorCounterEntry 4 }







--- *****************************************************
--- $$$$$$$$$$$$$$$$$$$$$$$$$$$$$$$$$$$$$$$$$$$$$$$$$$$$$
---     RMON
--- $$$$$$$$$$$$$$$$$$$$$$$$$$$$$$$$$$$$$$$$$$$$$$$$$$$$$
--- *****************************************************



--- *********************************************************
---     TABLE for the rm10010mpMonupRmonBytesCounterClientInput articles
--- *********************************************************

rm10010mpMonupRmonBytesCounterClientInputTable OBJECT-TYPE
	SYNTAX  SEQUENCE OF Rm10010mpMonupRmonBytesCounterClientInputEntry
	MAX-ACCESS not-accessible
	STATUS current
	DESCRIPTION
        "
        List of rm10010mpMonupRmonBytesCounterClientInput
        Article
        "
	::= { rm10010mpMonClientRmonCounter 16 }


rm10010mpMonupRmonBytesCounterClientInputEntry OBJECT-TYPE
	SYNTAX Rm10010mpMonupRmonBytesCounterClientInputEntry
	MAX-ACCESS not-accessible
	STATUS current
	DESCRIPTION
        "
        Row definition for the rm10010mpMonupRmonBytesCounterClientInput
        table
        "
	INDEX   { rm10010mpMonupRmonBytesCounterClientInputIndex }
	::= { rm10010mpMonupRmonBytesCounterClientInputTable 1 }


Rm10010mpMonupRmonBytesCounterClientInputEntry ::=
	SEQUENCE {
	rm10010mpMonupRmonBytesCounterClientInputIndex
		INTEGER,
	rm10010mpMonupRmonBytesCounterClientInputValuePortn
		Counter64,
	rm10010mpMonupRmonBytesCounterClientInputErrorPortn
		EkiOnOff,
	rm10010mpMonupRmonBytesCounterClientInputOverloadPortn
		EkiOnOff
	}


rm10010mpMonupRmonBytesCounterClientInputIndex OBJECT-TYPE
	SYNTAX  INTEGER(0..128)
	MAX-ACCESS  read-only
	STATUS current
	DESCRIPTION
        "
        Index definition for the rm10010mpMonupRmonBytesCounterClientInput
        table
        "
	::= { rm10010mpMonupRmonBytesCounterClientInputEntry 1 }


rm10010mpMonupRmonBytesCounterClientInputValuePortn OBJECT-TYPE
	SYNTAX  Counter64
	MAX-ACCESS read-only
	STATUS current
	DESCRIPTION
        "
        Client Input Bytes :This counter
        is increased each time a data byte
        is received on the client port
          <Help>  This counter gives the
        number of bytes received on the
        client port
        "
	::= { rm10010mpMonupRmonBytesCounterClientInputEntry 2 }


rm10010mpMonupRmonBytesCounterClientInputErrorPortn OBJECT-TYPE
	SYNTAX  EkiOnOff
	MAX-ACCESS read-only
	STATUS current
	DESCRIPTION
        "
        Bytes Counter Error :This OID
         when set indicates the Bytes counter
        value is invalid on client port
        "
	::= { rm10010mpMonupRmonBytesCounterClientInputEntry 3 }


rm10010mpMonupRmonBytesCounterClientInputOverloadPortn OBJECT-TYPE
	SYNTAX  EkiOnOff
	MAX-ACCESS read-only
	STATUS current
	DESCRIPTION
        "
        Bytes Counter Overload :This OID
        when set indicates a Bytes counter
        overload on client port
        "
	::= { rm10010mpMonupRmonBytesCounterClientInputEntry 4 }


--- *********************************************************
---     TABLE for the rm10010mpMonupRmonCrcErrorsCounterClientInput articles
--- *********************************************************

rm10010mpMonupRmonCrcErrorsCounterClientInputTable OBJECT-TYPE
	SYNTAX  SEQUENCE OF Rm10010mpMonupRmonCrcErrorsCounterClientInputEntry
	MAX-ACCESS not-accessible
	STATUS current
	DESCRIPTION
        "
        List of rm10010mpMonupRmonCrcErrorsCounterClientInput
        Article
        "
	::= { rm10010mpMonClientRmonCounter 32 }


rm10010mpMonupRmonCrcErrorsCounterClientInputEntry OBJECT-TYPE
	SYNTAX Rm10010mpMonupRmonCrcErrorsCounterClientInputEntry
	MAX-ACCESS not-accessible
	STATUS current
	DESCRIPTION
        "
        Row definition for the rm10010mpMonupRmonCrcErrorsCounterClientInput
        table
        "
	INDEX   { rm10010mpMonupRmonCrcErrorsCounterClientInputIndex }
	::= { rm10010mpMonupRmonCrcErrorsCounterClientInputTable 1 }


Rm10010mpMonupRmonCrcErrorsCounterClientInputEntry ::=
	SEQUENCE {
	rm10010mpMonupRmonCrcErrorsCounterClientInputIndex
		INTEGER,
	rm10010mpMonupRmonCrcErrorsCounterClientInputValuePortn
		Counter64,
	rm10010mpMonupRmonCrcErrorsCounterClientInputErrorPortn
		EkiOnOff,
	rm10010mpMonupRmonCrcErrorsCounterClientInputOverloadPortn
		EkiOnOff
	}


rm10010mpMonupRmonCrcErrorsCounterClientInputIndex OBJECT-TYPE
	SYNTAX  INTEGER(0..128)
	MAX-ACCESS  read-only
	STATUS current
	DESCRIPTION
        "
        Index definition for the rm10010mpMonupRmonCrcErrorsCounterClientInput
        table
        "
	::= { rm10010mpMonupRmonCrcErrorsCounterClientInputEntry 1 }


rm10010mpMonupRmonCrcErrorsCounterClientInputValuePortn OBJECT-TYPE
	SYNTAX  Counter64
	MAX-ACCESS read-only
	STATUS current
	DESCRIPTION
        "
        Client Input CRC Errors :This
         counter is increased each time
        a B1/CRC error is detected on the
        client port  <Help>  This counter
        gives the number of B1/CRC Errors
        received on the client port
        "
	::= { rm10010mpMonupRmonCrcErrorsCounterClientInputEntry 2 }


rm10010mpMonupRmonCrcErrorsCounterClientInputErrorPortn OBJECT-TYPE
	SYNTAX  EkiOnOff
	MAX-ACCESS read-only
	STATUS current
	DESCRIPTION
        "
        CRC Errors Counter Error :This
        OID when set indicates the CRC
         Errors counter value is invalid
        on client port
        "
	::= { rm10010mpMonupRmonCrcErrorsCounterClientInputEntry 3 }


rm10010mpMonupRmonCrcErrorsCounterClientInputOverloadPortn OBJECT-TYPE
	SYNTAX  EkiOnOff
	MAX-ACCESS read-only
	STATUS current
	DESCRIPTION
        "
        CRC Errors Counter Overload :This
        OID when set indicates a CRC Errors
        counter overload on client port
        "
	::= { rm10010mpMonupRmonCrcErrorsCounterClientInputEntry 4 }


--- *********************************************************
---     TABLE for the rm10010mpMonupRmonPacketsCounterClientInput articles
--- *********************************************************

rm10010mpMonupRmonPacketsCounterClientInputTable OBJECT-TYPE
	SYNTAX  SEQUENCE OF Rm10010mpMonupRmonPacketsCounterClientInputEntry
	MAX-ACCESS not-accessible
	STATUS current
	DESCRIPTION
        "
        List of rm10010mpMonupRmonPacketsCounterClientInput
        Article
        "
	::= { rm10010mpMonClientRmonCounter 48 }


rm10010mpMonupRmonPacketsCounterClientInputEntry OBJECT-TYPE
	SYNTAX Rm10010mpMonupRmonPacketsCounterClientInputEntry
	MAX-ACCESS not-accessible
	STATUS current
	DESCRIPTION
        "
        Row definition for the rm10010mpMonupRmonPacketsCounterClientInput
        table
        "
	INDEX   { rm10010mpMonupRmonPacketsCounterClientInputIndex }
	::= { rm10010mpMonupRmonPacketsCounterClientInputTable 1 }


Rm10010mpMonupRmonPacketsCounterClientInputEntry ::=
	SEQUENCE {
	rm10010mpMonupRmonPacketsCounterClientInputIndex
		INTEGER,
	rm10010mpMonupRmonPacketsCounterClientInputValuePortn
		Counter64,
	rm10010mpMonupRmonPacketsCounterClientInputErrorPortn
		EkiOnOff,
	rm10010mpMonupRmonPacketsCounterClientInputOverloadPortn
		EkiOnOff
	}


rm10010mpMonupRmonPacketsCounterClientInputIndex OBJECT-TYPE
	SYNTAX  INTEGER(0..128)
	MAX-ACCESS  read-only
	STATUS current
	DESCRIPTION
        "
        Index definition for the rm10010mpMonupRmonPacketsCounterClientInput
        table
        "
	::= { rm10010mpMonupRmonPacketsCounterClientInputEntry 1 }


rm10010mpMonupRmonPacketsCounterClientInputValuePortn OBJECT-TYPE
	SYNTAX  Counter64
	MAX-ACCESS read-only
	STATUS current
	DESCRIPTION
        "
        Client Input Packets :This counter
        is increased each time a packet
        is received on the client port
          <Help>  This counter gives the
        number of packets received on the
        client port
        "
	::= { rm10010mpMonupRmonPacketsCounterClientInputEntry 2 }


rm10010mpMonupRmonPacketsCounterClientInputErrorPortn OBJECT-TYPE
	SYNTAX  EkiOnOff
	MAX-ACCESS read-only
	STATUS current
	DESCRIPTION
        "
        Packets Counter Error :This OID
        when set indicates the Packets
         counter value is invalid on client
        port
        "
	::= { rm10010mpMonupRmonPacketsCounterClientInputEntry 3 }


rm10010mpMonupRmonPacketsCounterClientInputOverloadPortn OBJECT-TYPE
	SYNTAX  EkiOnOff
	MAX-ACCESS read-only
	STATUS current
	DESCRIPTION
        "
        Packets Counter Overload :This
        OID when set indicates a Packets
        counter overload on client port
        "
	::= { rm10010mpMonupRmonPacketsCounterClientInputEntry 4 }


--- *********************************************************
---     TABLE for the rm10010mpMonupRmonBroadcastCounterClientInput articles
--- *********************************************************

rm10010mpMonupRmonBroadcastCounterClientInputTable OBJECT-TYPE
	SYNTAX  SEQUENCE OF Rm10010mpMonupRmonBroadcastCounterClientInputEntry
	MAX-ACCESS not-accessible
	STATUS current
	DESCRIPTION
        "
        List of rm10010mpMonupRmonBroadcastCounterClientInput
        Article
        "
	::= { rm10010mpMonClientRmonCounter 64 }


rm10010mpMonupRmonBroadcastCounterClientInputEntry OBJECT-TYPE
	SYNTAX Rm10010mpMonupRmonBroadcastCounterClientInputEntry
	MAX-ACCESS not-accessible
	STATUS current
	DESCRIPTION
        "
        Row definition for the rm10010mpMonupRmonBroadcastCounterClientInput
        table
        "
	INDEX   { rm10010mpMonupRmonBroadcastCounterClientInputIndex }
	::= { rm10010mpMonupRmonBroadcastCounterClientInputTable 1 }


Rm10010mpMonupRmonBroadcastCounterClientInputEntry ::=
	SEQUENCE {
	rm10010mpMonupRmonBroadcastCounterClientInputIndex
		INTEGER,
	rm10010mpMonupRmonBroadcastCounterClientInputValuePortn
		Counter64,
	rm10010mpMonupRmonBroadcastCounterClientInputErrorPortn
		EkiOnOff,
	rm10010mpMonupRmonBroadcastCounterClientInputOverloadPortn
		EkiOnOff
	}


rm10010mpMonupRmonBroadcastCounterClientInputIndex OBJECT-TYPE
	SYNTAX  INTEGER(0..128)
	MAX-ACCESS  read-only
	STATUS current
	DESCRIPTION
        "
        Index definition for the rm10010mpMonupRmonBroadcastCounterClientInput
        table
        "
	::= { rm10010mpMonupRmonBroadcastCounterClientInputEntry 1 }


rm10010mpMonupRmonBroadcastCounterClientInputValuePortn OBJECT-TYPE
	SYNTAX  Counter64
	MAX-ACCESS read-only
	STATUS current
	DESCRIPTION
        "
        Client Input Broadcast Packets
        :This counter is increased each
        time a broadcast packet is received
        on the client port  <Help>  This
        counter gives the number of Broadcast
        packets received on the client
         port
        "
	::= { rm10010mpMonupRmonBroadcastCounterClientInputEntry 2 }


rm10010mpMonupRmonBroadcastCounterClientInputErrorPortn OBJECT-TYPE
	SYNTAX  EkiOnOff
	MAX-ACCESS read-only
	STATUS current
	DESCRIPTION
        "
        Broadcast Counter Error :This
         OID when set indicates the Broadcast
        counter value is invalid on client
        port
        "
	::= { rm10010mpMonupRmonBroadcastCounterClientInputEntry 3 }


rm10010mpMonupRmonBroadcastCounterClientInputOverloadPortn OBJECT-TYPE
	SYNTAX  EkiOnOff
	MAX-ACCESS read-only
	STATUS current
	DESCRIPTION
        "
        Broadcast Counter Overload :This
        OID when set indicates a Broadcast
        counter overload on client port
        "
	::= { rm10010mpMonupRmonBroadcastCounterClientInputEntry 4 }


--- *********************************************************
---     TABLE for the rm10010mpMonupRmonMulticastCounterClientInput articles
--- *********************************************************

rm10010mpMonupRmonMulticastCounterClientInputTable OBJECT-TYPE
	SYNTAX  SEQUENCE OF Rm10010mpMonupRmonMulticastCounterClientInputEntry
	MAX-ACCESS not-accessible
	STATUS current
	DESCRIPTION
        "
        List of rm10010mpMonupRmonMulticastCounterClientInput
        Article
        "
	::= { rm10010mpMonClientRmonCounter 80 }


rm10010mpMonupRmonMulticastCounterClientInputEntry OBJECT-TYPE
	SYNTAX Rm10010mpMonupRmonMulticastCounterClientInputEntry
	MAX-ACCESS not-accessible
	STATUS current
	DESCRIPTION
        "
        Row definition for the rm10010mpMonupRmonMulticastCounterClientInput
        table
        "
	INDEX   { rm10010mpMonupRmonMulticastCounterClientInputIndex }
	::= { rm10010mpMonupRmonMulticastCounterClientInputTable 1 }


Rm10010mpMonupRmonMulticastCounterClientInputEntry ::=
	SEQUENCE {
	rm10010mpMonupRmonMulticastCounterClientInputIndex
		INTEGER,
	rm10010mpMonupRmonMulticastCounterClientInputValuePortn
		Counter64,
	rm10010mpMonupRmonMulticastCounterClientInputErrorPortn
		EkiOnOff,
	rm10010mpMonupRmonMulticastCounterClientInputOverloadPortn
		EkiOnOff
	}


rm10010mpMonupRmonMulticastCounterClientInputIndex OBJECT-TYPE
	SYNTAX  INTEGER(0..128)
	MAX-ACCESS  read-only
	STATUS current
	DESCRIPTION
        "
        Index definition for the rm10010mpMonupRmonMulticastCounterClientInput
        table
        "
	::= { rm10010mpMonupRmonMulticastCounterClientInputEntry 1 }


rm10010mpMonupRmonMulticastCounterClientInputValuePortn OBJECT-TYPE
	SYNTAX  Counter64
	MAX-ACCESS read-only
	STATUS current
	DESCRIPTION
        "
        Client Input Multicast Packets
        :This counter is increased each
        time a Multicast packet is received
        on the client port  <Help>  This
        counter gives the number of Multicast
        packets received on the client
         port
        "
	::= { rm10010mpMonupRmonMulticastCounterClientInputEntry 2 }


rm10010mpMonupRmonMulticastCounterClientInputErrorPortn OBJECT-TYPE
	SYNTAX  EkiOnOff
	MAX-ACCESS read-only
	STATUS current
	DESCRIPTION
        "
        Multicast Counter Error :This
         OID when set indicates the Multicast
        counter value is invalid on client
        port
        "
	::= { rm10010mpMonupRmonMulticastCounterClientInputEntry 3 }


rm10010mpMonupRmonMulticastCounterClientInputOverloadPortn OBJECT-TYPE
	SYNTAX  EkiOnOff
	MAX-ACCESS read-only
	STATUS current
	DESCRIPTION
        "
        Multicast Counter Overload :This
        OID when set indicates a Multicast
        counter overload on client port
        "
	::= { rm10010mpMonupRmonMulticastCounterClientInputEntry 4 }


--- *********************************************************
---     TABLE for the rm10010mpMonupRmonPauseFrameCounterClientInput articles
--- *********************************************************

rm10010mpMonupRmonPauseFrameCounterClientInputTable OBJECT-TYPE
	SYNTAX  SEQUENCE OF Rm10010mpMonupRmonPauseFrameCounterClientInputEntry
	MAX-ACCESS not-accessible
	STATUS current
	DESCRIPTION
        "
        List of rm10010mpMonupRmonPauseFrameCounterClientInput
        Article
        "
	::= { rm10010mpMonClientRmonCounter 96 }


rm10010mpMonupRmonPauseFrameCounterClientInputEntry OBJECT-TYPE
	SYNTAX Rm10010mpMonupRmonPauseFrameCounterClientInputEntry
	MAX-ACCESS not-accessible
	STATUS current
	DESCRIPTION
        "
        Row definition for the rm10010mpMonupRmonPauseFrameCounterClientInput
        table
        "
	INDEX   { rm10010mpMonupRmonPauseFrameCounterClientInputIndex }
	::= { rm10010mpMonupRmonPauseFrameCounterClientInputTable 1 }


Rm10010mpMonupRmonPauseFrameCounterClientInputEntry ::=
	SEQUENCE {
	rm10010mpMonupRmonPauseFrameCounterClientInputIndex
		INTEGER,
	rm10010mpMonupRmonPauseFrameCounterClientInputValuePortn
		Counter64,
	rm10010mpMonupRmonPauseFrameCounterClientInputErrorPortn
		EkiOnOff,
	rm10010mpMonupRmonPauseFrameCounterClientInputOverloadPortn
		EkiOnOff
	}


rm10010mpMonupRmonPauseFrameCounterClientInputIndex OBJECT-TYPE
	SYNTAX  INTEGER(0..128)
	MAX-ACCESS  read-only
	STATUS current
	DESCRIPTION
        "
        Index definition for the rm10010mpMonupRmonPauseFrameCounterClientInput
        table
        "
	::= { rm10010mpMonupRmonPauseFrameCounterClientInputEntry 1 }


rm10010mpMonupRmonPauseFrameCounterClientInputValuePortn OBJECT-TYPE
	SYNTAX  Counter64
	MAX-ACCESS read-only
	STATUS current
	DESCRIPTION
        "
        Client Input Pause Frames :This
        counter is increased each time
         a Pause frame is received on the
        client port  <Help>  This counter
        gives the number of Pause frames
        received on the client port
        "
	::= { rm10010mpMonupRmonPauseFrameCounterClientInputEntry 2 }


rm10010mpMonupRmonPauseFrameCounterClientInputErrorPortn OBJECT-TYPE
	SYNTAX  EkiOnOff
	MAX-ACCESS read-only
	STATUS current
	DESCRIPTION
        "
        Pause Counter Error :This OID
         when set indicates the Pause counter
        value is invalid on client port
        "
	::= { rm10010mpMonupRmonPauseFrameCounterClientInputEntry 3 }


rm10010mpMonupRmonPauseFrameCounterClientInputOverloadPortn OBJECT-TYPE
	SYNTAX  EkiOnOff
	MAX-ACCESS read-only
	STATUS current
	DESCRIPTION
        "
        Pause Counter Overload :This OID
        when set indicates a Pause counter
        overload on client port
        "
	::= { rm10010mpMonupRmonPauseFrameCounterClientInputEntry 4 }







--- *****************************************************
--- $$$$$$$$$$$$$$$$$$$$$$$$$$$$$$$$$$$$$$$$$$$$$$$$$$$$$
---     MEASURES
--- $$$$$$$$$$$$$$$$$$$$$$$$$$$$$$$$$$$$$$$$$$$$$$$$$$$$$
--- *****************************************************



rm10010mpMesrsynth0 OBJECT-TYPE
	  SYNTAX EkiMeasureType
	  MAX-ACCESS read-only
	  STATUS deprecated
	  DESCRIPTION
        "
        Not Used :
        "
	  ::= { rm10010mpMesrOther 0 }



rm10010mpMesrsynth1 OBJECT-TYPE
	  SYNTAX EkiMeasureType
	  MAX-ACCESS read-only
	  STATUS deprecated
	  DESCRIPTION
        "
        Not Used :
        "
	  ::= { rm10010mpMesrOther 1 }



--- *****************************************************
---     LEAF for the pmIntervalNumber article
--- *****************************************************

rm10010mpMesrpmIntervalNumber OBJECT-TYPE
	  SYNTAX Unsigned32 (0..65535)
	  MAX-ACCESS read-only
	  STATUS current
	  DESCRIPTION
        "
        PM Interval Counter :
        "
	  ::= { rm10010mpMesrOther 7 }



--- *****************************************************
---     LEAF for the clientCfpTemp article
--- *****************************************************

rm10010mpMesrclientCfpTemp OBJECT-TYPE
	  SYNTAX Unsigned32 (0..65535)
	  MAX-ACCESS read-only
	  STATUS current
	  DESCRIPTION
        "
        Client Trscv Temperature :This
        OID gives the temperature value
        of the Client Transceiver, read
        from the DDM (Digital Diagnostic
        Monitoring) (Temperature = AV/256)
        (Unit = C) <Help> This Measure
         gives the temperature value of
        the Client Transceiver
        "
	  ::= { rm10010mpMesrClient 8 }



--- *****************************************************
---     LEAF for the clientCfp3v3Voltage article
--- *****************************************************

rm10010mpMesrclientCfp3v3Voltage OBJECT-TYPE
	  SYNTAX Unsigned32 (0..65535)
	  MAX-ACCESS read-only
	  STATUS current
	  DESCRIPTION
        "
        Client Trscv Voltage :This OID
        gives the 3V3 voltage value of
         the Client Transceiver, read from
        the DDM (Digital Diagnostic Monitoring)
         (Voltage = AV/1000) (Unit = V)
        <Help> This Measure gives the 3V3
        voltage value of the Client Transceiver
        "
	  ::= { rm10010mpMesrClient 9 }



--- *****************************************************
---     LEAF for the clientSoaBiasCurrent article
--- *****************************************************

rm10010mpMesrclientSoaBiasCurrent OBJECT-TYPE
	  SYNTAX Unsigned32 (0..65535)
	  MAX-ACCESS read-only
	  STATUS current
	  DESCRIPTION
        "
        Client Trscv SOA Bias :This OID
        gives the SOA bias value of the
        Client Transceiver, read from the
        DDM (Digital Diagnostic Monitoring)
         (Bias = AV/500) (Unit = mA) <Help>
        This Measure gives the SOA bias
        value of the Client Transceiver
        "
	  ::= { rm10010mpMesrClient 10 }



--- *****************************************************
---     LEAF for the lineMsaTemp article
--- *****************************************************

rm10010mpMesrlineMsaTemp OBJECT-TYPE
	  SYNTAX Unsigned32 (0..65535)
	  MAX-ACCESS read-only
	  STATUS current
	  DESCRIPTION
        "
        Line Trscv Temperature :This OID
        gives the temperature value of
         the Line Transceiver, read from
        the DDM (Digital Diagnostic Monitoring)
         (Temperature = AV/256) (Unit =
        C) <Help> This Measure gives the
        temperature value of the Line Transceiver
        "
	  ::= { rm10010mpMesrLine 12 }



--- *****************************************************
---     LEAF for the lineMsa3v3Voltage article
--- *****************************************************

rm10010mpMesrlineMsa3v3Voltage OBJECT-TYPE
	  SYNTAX Unsigned32 (0..65535)
	  MAX-ACCESS read-only
	  STATUS current
	  DESCRIPTION
        "
        Line Trscv Voltage :This OID gives
        the 3V3 voltage value of the Line
        Transceiver, read from the DDM
         (Digital Diagnostic Monitoring)
        (Voltage = AV/1000) (Unit = V)
         <Help> This Measure gives the
         3V3 voltage value of the Line
         Transceiver
        "
	  ::= { rm10010mpMesrLine 13 }



--- *****************************************************
---     LEAF for the lineSoaBiasCurrent article
--- *****************************************************

rm10010mpMesrlineSoaBiasCurrent OBJECT-TYPE
	  SYNTAX Unsigned32 (0..65535)
	  MAX-ACCESS read-only
	  STATUS current
	  DESCRIPTION
        "
        Line Trscv SOA Bias :This OID
         gives the SOA bias value of the
        Line Transceiver,read from the
         DDM (Digital Diagnostic Monitoring)
         (Bias = AV/500) (Unit = mA) <Help>
        This Measure gives the SOA bias
        value of the Line Transceiver
        "
	  ::= { rm10010mpMesrLine 14 }



--- *********************************************************
---     TABLE for the rm10010mpMesrclientNetTxTemp articles
--- *********************************************************

rm10010mpMesrclientNetTxTempTable OBJECT-TYPE
	SYNTAX  SEQUENCE OF Rm10010mpMesrclientNetTxTempEntry
	MAX-ACCESS not-accessible
	STATUS current
	DESCRIPTION
        "
        List of rm10010mpMesrclientNetTxTemp
        Article
        "
	::= { rm10010mpMesrClient 16 }


rm10010mpMesrclientNetTxTempEntry OBJECT-TYPE
	SYNTAX Rm10010mpMesrclientNetTxTempEntry
	MAX-ACCESS not-accessible
	STATUS current
	DESCRIPTION
        "
        Row definition for the rm10010mpMesrclientNetTxTemp
        table
        "
	INDEX   { rm10010mpMesrclientNetTxTempIndex }
	::= { rm10010mpMesrclientNetTxTempTable 1 }


Rm10010mpMesrclientNetTxTempEntry ::=
	SEQUENCE {
	rm10010mpMesrclientNetTxTempIndex
		INTEGER,
	rm10010mpMesrclientNetTxTempPortn
		INTEGER
	}


rm10010mpMesrclientNetTxTempIndex OBJECT-TYPE
	SYNTAX  INTEGER(0..128)
	MAX-ACCESS  read-only
	STATUS current
	DESCRIPTION
        "
        Index definition for the rm10010mpMesrclientNetTxTemp
        table
        "
	::= { rm10010mpMesrclientNetTxTempEntry 1 }


rm10010mpMesrclientNetTxTempPortn OBJECT-TYPE
	SYNTAX  INTEGER (0..65535)
	MAX-ACCESS read-only
	STATUS current
	DESCRIPTION
        "
        Client Trscv Temperature :This
        OID gives the Laser temperature
        value of the Client Transceiver,
        read from the DDM (Digital Diagnostic
        Monitoring) (Temperature = AV/256)
        (Unit = C) <Help> This Measure
         gives the Laser temperature value
        of the Client Transceiver
        "
	::= { rm10010mpMesrclientNetTxTempEntry 2 }


--- *********************************************************
---     TABLE for the rm10010mpMesrclientNetTxBias articles
--- *********************************************************

rm10010mpMesrclientNetTxBiasTable OBJECT-TYPE
	SYNTAX  SEQUENCE OF Rm10010mpMesrclientNetTxBiasEntry
	MAX-ACCESS not-accessible
	STATUS current
	DESCRIPTION
        "
        List of rm10010mpMesrclientNetTxBias
        Article
        "
	::= { rm10010mpMesrClient 32 }


rm10010mpMesrclientNetTxBiasEntry OBJECT-TYPE
	SYNTAX Rm10010mpMesrclientNetTxBiasEntry
	MAX-ACCESS not-accessible
	STATUS current
	DESCRIPTION
        "
        Row definition for the rm10010mpMesrclientNetTxBias
        table
        "
	INDEX   { rm10010mpMesrclientNetTxBiasIndex }
	::= { rm10010mpMesrclientNetTxBiasTable 1 }


Rm10010mpMesrclientNetTxBiasEntry ::=
	SEQUENCE {
	rm10010mpMesrclientNetTxBiasIndex
		INTEGER,
	rm10010mpMesrclientNetTxBiasPortn
		INTEGER
	}


rm10010mpMesrclientNetTxBiasIndex OBJECT-TYPE
	SYNTAX  INTEGER(0..128)
	MAX-ACCESS  read-only
	STATUS current
	DESCRIPTION
        "
        Index definition for the rm10010mpMesrclientNetTxBias
        table
        "
	::= { rm10010mpMesrclientNetTxBiasEntry 1 }


rm10010mpMesrclientNetTxBiasPortn OBJECT-TYPE
	SYNTAX  INTEGER (0..65535)
	MAX-ACCESS read-only
	STATUS current
	DESCRIPTION
        "
        Client Trscv Laser Bias :This
         OID gives the Laser bias value
        of the Client Transceiver, read
        from the DDM (Digital Diagnostic
        Monitoring) (Bias = AV/500) (Unit
        = mA) <Help> This Measure gives
        the Laser bias value of the Client
        Transceiver
        "
	::= { rm10010mpMesrclientNetTxBiasEntry 2 }


--- *********************************************************
---     TABLE for the rm10010mpMesrclientNetTxPwr articles
--- *********************************************************

rm10010mpMesrclientNetTxPwrTable OBJECT-TYPE
	SYNTAX  SEQUENCE OF Rm10010mpMesrclientNetTxPwrEntry
	MAX-ACCESS not-accessible
	STATUS current
	DESCRIPTION
        "
        List of rm10010mpMesrclientNetTxPwr
        Article
        "
	::= { rm10010mpMesrClient 48 }


rm10010mpMesrclientNetTxPwrEntry OBJECT-TYPE
	SYNTAX Rm10010mpMesrclientNetTxPwrEntry
	MAX-ACCESS not-accessible
	STATUS current
	DESCRIPTION
        "
        Row definition for the rm10010mpMesrclientNetTxPwr
        table
        "
	INDEX   { rm10010mpMesrclientNetTxPwrIndex }
	::= { rm10010mpMesrclientNetTxPwrTable 1 }


Rm10010mpMesrclientNetTxPwrEntry ::=
	SEQUENCE {
	rm10010mpMesrclientNetTxPwrIndex
		INTEGER,
	rm10010mpMesrclientNetTxPwrPortn
		INTEGER
	}


rm10010mpMesrclientNetTxPwrIndex OBJECT-TYPE
	SYNTAX  INTEGER(0..128)
	MAX-ACCESS  read-only
	STATUS current
	DESCRIPTION
        "
        Index definition for the rm10010mpMesrclientNetTxPwr
        table
        "
	::= { rm10010mpMesrclientNetTxPwrEntry 1 }


rm10010mpMesrclientNetTxPwrPortn OBJECT-TYPE
	SYNTAX  INTEGER (0..65535)
	MAX-ACCESS read-only
	STATUS current
	DESCRIPTION
        "
        Client Trscv Tx Power :This OID
        gives the transmit power value
         of the Client Transceiver, read
        from the DDM (Digital Diagnostic
        Monitoring) (Power = 10*log(AV)-40)
        (Unit = dBm) <Help> This Measure
        gives the transmit power value
         of the Client Transceiver
        "
	::= { rm10010mpMesrclientNetTxPwrEntry 2 }


--- *********************************************************
---     TABLE for the rm10010mpMesrclientNetRxPwr articles
--- *********************************************************

rm10010mpMesrclientNetRxPwrTable OBJECT-TYPE
	SYNTAX  SEQUENCE OF Rm10010mpMesrclientNetRxPwrEntry
	MAX-ACCESS not-accessible
	STATUS current
	DESCRIPTION
        "
        List of rm10010mpMesrclientNetRxPwr
        Article
        "
	::= { rm10010mpMesrClient 64 }


rm10010mpMesrclientNetRxPwrEntry OBJECT-TYPE
	SYNTAX Rm10010mpMesrclientNetRxPwrEntry
	MAX-ACCESS not-accessible
	STATUS current
	DESCRIPTION
        "
        Row definition for the rm10010mpMesrclientNetRxPwr
        table
        "
	INDEX   { rm10010mpMesrclientNetRxPwrIndex }
	::= { rm10010mpMesrclientNetRxPwrTable 1 }


Rm10010mpMesrclientNetRxPwrEntry ::=
	SEQUENCE {
	rm10010mpMesrclientNetRxPwrIndex
		INTEGER,
	rm10010mpMesrclientNetRxPwrPortn
		INTEGER
	}


rm10010mpMesrclientNetRxPwrIndex OBJECT-TYPE
	SYNTAX  INTEGER(0..128)
	MAX-ACCESS  read-only
	STATUS current
	DESCRIPTION
        "
        Index definition for the rm10010mpMesrclientNetRxPwr
        table
        "
	::= { rm10010mpMesrclientNetRxPwrEntry 1 }


rm10010mpMesrclientNetRxPwrPortn OBJECT-TYPE
	SYNTAX  INTEGER (0..65535)
	MAX-ACCESS read-only
	STATUS current
	DESCRIPTION
        "
        Client Trscv Rx Power :This OID
        gives the receive power value of
        the Client Transceiver, read in
        the DDM (Digital Diagnostic Monitoring)
        (Power = 10*log(AV)-40) (Unit =
        dBm) <Help> This Measure gives
         the receive power value of the
        Client Transceiver
        "
	::= { rm10010mpMesrclientNetRxPwrEntry 2 }


--- *********************************************************
---     TABLE for the rm10010mpMesrlineNetTxLaserOutputPwr articles
--- *********************************************************

rm10010mpMesrlineNetTxLaserOutputPwrTable OBJECT-TYPE
	SYNTAX  SEQUENCE OF Rm10010mpMesrlineNetTxLaserOutputPwrEntry
	MAX-ACCESS not-accessible
	STATUS current
	DESCRIPTION
        "
        List of rm10010mpMesrlineNetTxLaserOutputPwr
        Article
        "
	::= { rm10010mpMesrLine 80 }


rm10010mpMesrlineNetTxLaserOutputPwrEntry OBJECT-TYPE
	SYNTAX Rm10010mpMesrlineNetTxLaserOutputPwrEntry
	MAX-ACCESS not-accessible
	STATUS current
	DESCRIPTION
        "
        Row definition for the rm10010mpMesrlineNetTxLaserOutputPwr
        table
        "
	INDEX   { rm10010mpMesrlineNetTxLaserOutputPwrIndex }
	::= { rm10010mpMesrlineNetTxLaserOutputPwrTable 1 }


Rm10010mpMesrlineNetTxLaserOutputPwrEntry ::=
	SEQUENCE {
	rm10010mpMesrlineNetTxLaserOutputPwrIndex
		INTEGER,
	rm10010mpMesrlineNetTxLaserOutputPwrPortn
		INTEGER
	}


rm10010mpMesrlineNetTxLaserOutputPwrIndex OBJECT-TYPE
	SYNTAX  INTEGER(0..128)
	MAX-ACCESS  read-only
	STATUS current
	DESCRIPTION
        "
        Index definition for the rm10010mpMesrlineNetTxLaserOutputPwr
        table
        "
	::= { rm10010mpMesrlineNetTxLaserOutputPwrEntry 1 }


rm10010mpMesrlineNetTxLaserOutputPwrPortn OBJECT-TYPE
	SYNTAX  INTEGER (0..65535)
	MAX-ACCESS read-only
	STATUS current
	DESCRIPTION
        "
        Current Line Trscv Tx Power :This
        OID gives the Tx Laser transmit
        power value of the Line Transceiver,
        read in the DDM (Digital Diagnostic
        Monitoring) (Power = AV/100) (Unit
        = dBm) <Help> This Measure gives
        the Tx Laser transmit power value
        of the Line Transceiver
        "
	::= { rm10010mpMesrlineNetTxLaserOutputPwrEntry 2 }


--- *********************************************************
---     TABLE for the rm10010mpMesrlineNetTxLaserTemp articles
--- *********************************************************

rm10010mpMesrlineNetTxLaserTempTable OBJECT-TYPE
	SYNTAX  SEQUENCE OF Rm10010mpMesrlineNetTxLaserTempEntry
	MAX-ACCESS not-accessible
	STATUS current
	DESCRIPTION
        "
        List of rm10010mpMesrlineNetTxLaserTemp
        Article
        "
	::= { rm10010mpMesrLine 96 }


rm10010mpMesrlineNetTxLaserTempEntry OBJECT-TYPE
	SYNTAX Rm10010mpMesrlineNetTxLaserTempEntry
	MAX-ACCESS not-accessible
	STATUS current
	DESCRIPTION
        "
        Row definition for the rm10010mpMesrlineNetTxLaserTemp
        table
        "
	INDEX   { rm10010mpMesrlineNetTxLaserTempIndex }
	::= { rm10010mpMesrlineNetTxLaserTempTable 1 }


Rm10010mpMesrlineNetTxLaserTempEntry ::=
	SEQUENCE {
	rm10010mpMesrlineNetTxLaserTempIndex
		INTEGER,
	rm10010mpMesrlineNetTxLaserTempPortn
		INTEGER
	}


rm10010mpMesrlineNetTxLaserTempIndex OBJECT-TYPE
	SYNTAX  INTEGER(0..128)
	MAX-ACCESS  read-only
	STATUS current
	DESCRIPTION
        "
        Index definition for the rm10010mpMesrlineNetTxLaserTemp
        table
        "
	::= { rm10010mpMesrlineNetTxLaserTempEntry 1 }


rm10010mpMesrlineNetTxLaserTempPortn OBJECT-TYPE
	SYNTAX  INTEGER (0..65535)
	MAX-ACCESS read-only
	STATUS current
	DESCRIPTION
        "
        Current Line Trscv Tx Laser Temperature
        :This OID gives the Tx Laser Temperature
        value of the Line Transceiver,
         read from the DDM (Digital Diagnostic
        Monitoring) (Temperature = AV/256)
        (Unit = C) <Help> This Measure
         gives the Tx Laser Temperature
        value of the Line Transceiver
        "
	::= { rm10010mpMesrlineNetTxLaserTempEntry 2 }


--- *********************************************************
---     TABLE for the rm10010mpMesrlineNetTxBiasCurrent articles
--- *********************************************************

rm10010mpMesrlineNetTxBiasCurrentTable OBJECT-TYPE
	SYNTAX  SEQUENCE OF Rm10010mpMesrlineNetTxBiasCurrentEntry
	MAX-ACCESS not-accessible
	STATUS current
	DESCRIPTION
        "
        List of rm10010mpMesrlineNetTxBiasCurrent
        Article
        "
	::= { rm10010mpMesrLine 112 }


rm10010mpMesrlineNetTxBiasCurrentEntry OBJECT-TYPE
	SYNTAX Rm10010mpMesrlineNetTxBiasCurrentEntry
	MAX-ACCESS not-accessible
	STATUS current
	DESCRIPTION
        "
        Row definition for the rm10010mpMesrlineNetTxBiasCurrent
        table
        "
	INDEX   { rm10010mpMesrlineNetTxBiasCurrentIndex }
	::= { rm10010mpMesrlineNetTxBiasCurrentTable 1 }


Rm10010mpMesrlineNetTxBiasCurrentEntry ::=
	SEQUENCE {
	rm10010mpMesrlineNetTxBiasCurrentIndex
		INTEGER,
	rm10010mpMesrlineNetTxBiasCurrentPortn
		INTEGER
	}


rm10010mpMesrlineNetTxBiasCurrentIndex OBJECT-TYPE
	SYNTAX  INTEGER(0..128)
	MAX-ACCESS  read-only
	STATUS current
	DESCRIPTION
        "
        Index definition for the rm10010mpMesrlineNetTxBiasCurrent
        table
        "
	::= { rm10010mpMesrlineNetTxBiasCurrentEntry 1 }


rm10010mpMesrlineNetTxBiasCurrentPortn OBJECT-TYPE
	SYNTAX  INTEGER (0..65535)
	MAX-ACCESS read-only
	STATUS current
	DESCRIPTION
        "
        Current Line Trscv Tx Laser Bias
        :This OID gives the Tx Laser Bias
        value of the Line Transceiver,
         read from the DDM (Digital Diagnostic
        Monitoring) (Bias = AV/10) (Unit
        = mA) <Help> This Measure gives
        the Tx Laser Bias value of the
         Line Transceiver
        "
	::= { rm10010mpMesrlineNetTxBiasCurrentEntry 2 }


--- *********************************************************
---     TABLE for the rm10010mpMesrlineNetRxInputPwr articles
--- *********************************************************

rm10010mpMesrlineNetRxInputPwrTable OBJECT-TYPE
	SYNTAX  SEQUENCE OF Rm10010mpMesrlineNetRxInputPwrEntry
	MAX-ACCESS not-accessible
	STATUS current
	DESCRIPTION
        "
        List of rm10010mpMesrlineNetRxInputPwr
        Article
        "
	::= { rm10010mpMesrLine 128 }


rm10010mpMesrlineNetRxInputPwrEntry OBJECT-TYPE
	SYNTAX Rm10010mpMesrlineNetRxInputPwrEntry
	MAX-ACCESS not-accessible
	STATUS current
	DESCRIPTION
        "
        Row definition for the rm10010mpMesrlineNetRxInputPwr
        table
        "
	INDEX   { rm10010mpMesrlineNetRxInputPwrIndex }
	::= { rm10010mpMesrlineNetRxInputPwrTable 1 }


Rm10010mpMesrlineNetRxInputPwrEntry ::=
	SEQUENCE {
	rm10010mpMesrlineNetRxInputPwrIndex
		INTEGER,
	rm10010mpMesrlineNetRxInputPwrPortn
		INTEGER
	}


rm10010mpMesrlineNetRxInputPwrIndex OBJECT-TYPE
	SYNTAX  INTEGER(0..128)
	MAX-ACCESS  read-only
	STATUS current
	DESCRIPTION
        "
        Index definition for the rm10010mpMesrlineNetRxInputPwr
        table
        "
	::= { rm10010mpMesrlineNetRxInputPwrEntry 1 }


rm10010mpMesrlineNetRxInputPwrPortn OBJECT-TYPE
	SYNTAX  INTEGER (0..65535)
	MAX-ACCESS read-only
	STATUS current
	DESCRIPTION
        "
        Current Line Trscv Rx Power :This
        OID gives the Receive power value
        of the Line Transceiver, read in
        the DDM (Digital Diagnostic Monitoring)
        (Power = AV/100) (Unit = dBm) <Help>
        This Measure gives the Receive
         power value of the Line Transceiver
        "
	::= { rm10010mpMesrlineNetRxInputPwrEntry 2 }


--- *********************************************************
---     TABLE for the rm10010mpMesrlineResidualChromaticDisp articles
--- *********************************************************

rm10010mpMesrlineResidualChromaticDispTable OBJECT-TYPE
	SYNTAX  SEQUENCE OF Rm10010mpMesrlineResidualChromaticDispEntry
	MAX-ACCESS not-accessible
	STATUS current
	DESCRIPTION
        "
        List of rm10010mpMesrlineResidualChromaticDisp
        Article
        "
	::= { rm10010mpMesrLine 144 }


rm10010mpMesrlineResidualChromaticDispEntry OBJECT-TYPE
	SYNTAX Rm10010mpMesrlineResidualChromaticDispEntry
	MAX-ACCESS not-accessible
	STATUS current
	DESCRIPTION
        "
        Row definition for the rm10010mpMesrlineResidualChromaticDisp
        table
        "
	INDEX   { rm10010mpMesrlineResidualChromaticDispIndex }
	::= { rm10010mpMesrlineResidualChromaticDispTable 1 }


Rm10010mpMesrlineResidualChromaticDispEntry ::=
	SEQUENCE {
	rm10010mpMesrlineResidualChromaticDispIndex
		INTEGER,
	rm10010mpMesrlineResidualChromaticDispPortn
		INTEGER
	}


rm10010mpMesrlineResidualChromaticDispIndex OBJECT-TYPE
	SYNTAX  INTEGER(0..128)
	MAX-ACCESS  read-only
	STATUS current
	DESCRIPTION
        "
        Index definition for the rm10010mpMesrlineResidualChromaticDisp
        table
        "
	::= { rm10010mpMesrlineResidualChromaticDispEntry 1 }


rm10010mpMesrlineResidualChromaticDispPortn OBJECT-TYPE
	SYNTAX  INTEGER (0..65535)
	MAX-ACCESS read-only
	STATUS current
	DESCRIPTION
        "
        Current Residual Chromatic Dispersion
        :This OID gives the current Residual
        Chromatic Dispersion on the Line
        interface  (Unit = ps/nm)<Help>
        This measure gives the current
         Residual Chromatic Dispersion
         on the Line interface.
        "
	::= { rm10010mpMesrlineResidualChromaticDispEntry 2 }


--- *********************************************************
---     TABLE for the rm10010mpMesrlineDiffGroupDelay articles
--- *********************************************************

rm10010mpMesrlineDiffGroupDelayTable OBJECT-TYPE
	SYNTAX  SEQUENCE OF Rm10010mpMesrlineDiffGroupDelayEntry
	MAX-ACCESS not-accessible
	STATUS current
	DESCRIPTION
        "
        List of rm10010mpMesrlineDiffGroupDelay
        Article
        "
	::= { rm10010mpMesrLine 148 }


rm10010mpMesrlineDiffGroupDelayEntry OBJECT-TYPE
	SYNTAX Rm10010mpMesrlineDiffGroupDelayEntry
	MAX-ACCESS not-accessible
	STATUS current
	DESCRIPTION
        "
        Row definition for the rm10010mpMesrlineDiffGroupDelay
        table
        "
	INDEX   { rm10010mpMesrlineDiffGroupDelayIndex }
	::= { rm10010mpMesrlineDiffGroupDelayTable 1 }


Rm10010mpMesrlineDiffGroupDelayEntry ::=
	SEQUENCE {
	rm10010mpMesrlineDiffGroupDelayIndex
		INTEGER,
	rm10010mpMesrlineDiffGroupDelayPortn
		INTEGER
	}


rm10010mpMesrlineDiffGroupDelayIndex OBJECT-TYPE
	SYNTAX  INTEGER(0..128)
	MAX-ACCESS  read-only
	STATUS current
	DESCRIPTION
        "
        Index definition for the rm10010mpMesrlineDiffGroupDelay
        table
        "
	::= { rm10010mpMesrlineDiffGroupDelayEntry 1 }


rm10010mpMesrlineDiffGroupDelayPortn OBJECT-TYPE
	SYNTAX  INTEGER (0..65535)
	MAX-ACCESS read-only
	STATUS current
	DESCRIPTION
        "
        Current Differential Group Delay
        :This OID gives the current Differential
        Group Delay on the Line interface
          (Unit = ps)<Help> This measure
        gives the current Differential
         Group Delay on the Line interface.
        "
	::= { rm10010mpMesrlineDiffGroupDelayEntry 2 }


--- *********************************************************
---     TABLE for the rm10010mpMesrlineQFactor articles
--- *********************************************************

rm10010mpMesrlineQFactorTable OBJECT-TYPE
	SYNTAX  SEQUENCE OF Rm10010mpMesrlineQFactorEntry
	MAX-ACCESS not-accessible
	STATUS current
	DESCRIPTION
        "
        List of rm10010mpMesrlineQFactor
        Article
        "
	::= { rm10010mpMesrLine 152 }


rm10010mpMesrlineQFactorEntry OBJECT-TYPE
	SYNTAX Rm10010mpMesrlineQFactorEntry
	MAX-ACCESS not-accessible
	STATUS current
	DESCRIPTION
        "
        Row definition for the rm10010mpMesrlineQFactor
        table
        "
	INDEX   { rm10010mpMesrlineQFactorIndex }
	::= { rm10010mpMesrlineQFactorTable 1 }


Rm10010mpMesrlineQFactorEntry ::=
	SEQUENCE {
	rm10010mpMesrlineQFactorIndex
		INTEGER,
	rm10010mpMesrlineQFactorPortn
		INTEGER
	}


rm10010mpMesrlineQFactorIndex OBJECT-TYPE
	SYNTAX  INTEGER(0..128)
	MAX-ACCESS  read-only
	STATUS current
	DESCRIPTION
        "
        Index definition for the rm10010mpMesrlineQFactor
        table
        "
	::= { rm10010mpMesrlineQFactorEntry 1 }


rm10010mpMesrlineQFactorPortn OBJECT-TYPE
	SYNTAX  INTEGER (0..65535)
	MAX-ACCESS read-only
	STATUS current
	DESCRIPTION
        "
        Current Q Factor :This OID gives
        the current Q Factor on the Line
        interface   (Unit = dB) <Help>
         This measure gives the current
        Q Factor on the Line interface.
        "
	::= { rm10010mpMesrlineQFactorEntry 2 }


--- *********************************************************
---     TABLE for the rm10010mpMesrlineCarrierFreqOffset articles
--- *********************************************************

rm10010mpMesrlineCarrierFreqOffsetTable OBJECT-TYPE
	SYNTAX  SEQUENCE OF Rm10010mpMesrlineCarrierFreqOffsetEntry
	MAX-ACCESS not-accessible
	STATUS current
	DESCRIPTION
        "
        List of rm10010mpMesrlineCarrierFreqOffset
        Article
        "
	::= { rm10010mpMesrLine 156 }


rm10010mpMesrlineCarrierFreqOffsetEntry OBJECT-TYPE
	SYNTAX Rm10010mpMesrlineCarrierFreqOffsetEntry
	MAX-ACCESS not-accessible
	STATUS current
	DESCRIPTION
        "
        Row definition for the rm10010mpMesrlineCarrierFreqOffset
        table
        "
	INDEX   { rm10010mpMesrlineCarrierFreqOffsetIndex }
	::= { rm10010mpMesrlineCarrierFreqOffsetTable 1 }


Rm10010mpMesrlineCarrierFreqOffsetEntry ::=
	SEQUENCE {
	rm10010mpMesrlineCarrierFreqOffsetIndex
		INTEGER,
	rm10010mpMesrlineCarrierFreqOffsetPortn
		INTEGER
	}


rm10010mpMesrlineCarrierFreqOffsetIndex OBJECT-TYPE
	SYNTAX  INTEGER(0..128)
	MAX-ACCESS  read-only
	STATUS current
	DESCRIPTION
        "
        Index definition for the rm10010mpMesrlineCarrierFreqOffset
        table
        "
	::= { rm10010mpMesrlineCarrierFreqOffsetEntry 1 }


rm10010mpMesrlineCarrierFreqOffsetPortn OBJECT-TYPE
	SYNTAX  INTEGER (0..65535)
	MAX-ACCESS read-only
	STATUS current
	DESCRIPTION
        "
        Current Carrier Frequency Offset
        :This OID gives the current Carrier
        Frequency Offset on the Line interface
          (Unit = Mhz)<Help> This measure
        gives the current Carrier Frequency
        Offset on the Line interface.
        "
	::= { rm10010mpMesrlineCarrierFreqOffsetEntry 2 }


--- *********************************************************
---     TABLE for the rm10010mpMesrlineOsnr articles
--- *********************************************************

rm10010mpMesrlineOsnrTable OBJECT-TYPE
	SYNTAX  SEQUENCE OF Rm10010mpMesrlineOsnrEntry
	MAX-ACCESS not-accessible
	STATUS current
	DESCRIPTION
        "
        List of rm10010mpMesrlineOsnr
         Article
        "
	::= { rm10010mpMesrLine 160 }


rm10010mpMesrlineOsnrEntry OBJECT-TYPE
	SYNTAX Rm10010mpMesrlineOsnrEntry
	MAX-ACCESS not-accessible
	STATUS current
	DESCRIPTION
        "
        Row definition for the rm10010mpMesrlineOsnr
        table
        "
	INDEX   { rm10010mpMesrlineOsnrIndex }
	::= { rm10010mpMesrlineOsnrTable 1 }


Rm10010mpMesrlineOsnrEntry ::=
	SEQUENCE {
	rm10010mpMesrlineOsnrIndex
		INTEGER,
	rm10010mpMesrlineOsnrPortn
		INTEGER
	}


rm10010mpMesrlineOsnrIndex OBJECT-TYPE
	SYNTAX  INTEGER(0..128)
	MAX-ACCESS  read-only
	STATUS current
	DESCRIPTION
        "
        Index definition for the rm10010mpMesrlineOsnr
        table
        "
	::= { rm10010mpMesrlineOsnrEntry 1 }


rm10010mpMesrlineOsnrPortn OBJECT-TYPE
	SYNTAX  INTEGER (0..65535)
	MAX-ACCESS read-only
	STATUS current
	DESCRIPTION
        "
        Current OSNR :This OID gives the
        current OSNR on the Line interface
          (OSNR = AV/10) (Unit = dB)<Help>
        This measure gives the current
         OSNR on the Line interface.
        "
	::= { rm10010mpMesrlineOsnrEntry 2 }


--- *****************************************************
---     LEAF for the lineNetTxLaserOutputPwrAverage article
--- *****************************************************

rm10010mpMesrlineNetTxLaserOutputPwrAverage OBJECT-TYPE
	  SYNTAX Unsigned32 (0..65535)
	  MAX-ACCESS read-only
	  STATUS current
	  DESCRIPTION
        "
        Average Line Trscv Tx Power :This
        OID gives the average Tx Laser
         transmit power value among the
        network lanes of the Line Transceiver,
        read in the DDM (Digital Diagnostic
        Monitoring)  (Power = AV/100) (Unit
        = dBm) (Unit = dBm) <Help> This
        Measure gives the average Tx Laser
        transmit power value among the
         network lanes of the Line Transceiver
        "
	  ::= { rm10010mpMesrOther 180 }



--- *****************************************************
---     LEAF for the lineNetTxLaserTempAverage article
--- *****************************************************

rm10010mpMesrlineNetTxLaserTempAverage OBJECT-TYPE
	  SYNTAX Unsigned32 (0..65535)
	  MAX-ACCESS read-only
	  STATUS current
	  DESCRIPTION
        "
        Average Line Trscv Tx Laser Temperature
        :This OID gives the average Tx
         Laser Temperature value among
         the network lanes of the Line
         Transceiver, read from the DDM
        (Digital Diagnostic Monitoring)
        (Temperature = AV/256) (Unit =
         C) <Help> This Measure gives the
        average Tx Laser Temperature value
        among the network lanes of the
         Line Transceiver
        "
	  ::= { rm10010mpMesrOther 181 }



--- *****************************************************
---     LEAF for the lineNetTxBiasCurrentAverage article
--- *****************************************************

rm10010mpMesrlineNetTxBiasCurrentAverage OBJECT-TYPE
	  SYNTAX Unsigned32 (0..65535)
	  MAX-ACCESS read-only
	  STATUS current
	  DESCRIPTION
        "
        Average Line Trscv Tx Laser Bias
        :This OID gives the average Tx
         Laser Bias value among the network
        lanes of the Line Transceiver,
         read from the DDM (Digital Diagnostic
        Monitoring) (Bias = AV/10) (Unit
        = mA) <Help> This Measure gives
        the average Tx Laser Bias value
        among the network lanes of the
         Line Transceiver
        "
	  ::= { rm10010mpMesrOther 182 }



--- *****************************************************
---     LEAF for the lineNetRxInputPwrAverage article
--- *****************************************************

rm10010mpMesrlineNetRxInputPwrAverage OBJECT-TYPE
	  SYNTAX Unsigned32 (0..65535)
	  MAX-ACCESS read-only
	  STATUS current
	  DESCRIPTION
        "
        Average Line Trscv Rx Power :This
        OID gives the average Receive power
        value among the network lanes of
        the Line Transceiver, read in the
        DDM (Digital Diagnostic Monitoring)
        (Power = AV/100) (Unit = dBm) <Help>
        This Measure gives the average
         Receive power value among the
         network lanes of the Line Transceiver
        "
	  ::= { rm10010mpMesrOther 183 }



--- *****************************************************
---     LEAF for the lineResidualChromaticDispAverage article
--- *****************************************************

rm10010mpMesrlineResidualChromaticDispAverage OBJECT-TYPE
	  SYNTAX Unsigned32 (0..65535)
	  MAX-ACCESS read-only
	  STATUS current
	  DESCRIPTION
        "
        Average Residual Chromatic Dispersion
        :This OID gives the average Residual
        Chromatic Dispersion on the Line
        interface since the last measure
        reset <Help> This measure gives
        the average Residual Chromatic
         Dispersion on the Line interface
        since the last measure reset.
        "
	  ::= { rm10010mpMesrOther 184 }



--- *****************************************************
---     LEAF for the lineDiffGroupDelayAverage article
--- *****************************************************

rm10010mpMesrlineDiffGroupDelayAverage OBJECT-TYPE
	  SYNTAX Unsigned32 (0..65535)
	  MAX-ACCESS read-only
	  STATUS current
	  DESCRIPTION
        "
        Average Differential Group Delay
        :This OID gives the average Group
        Delay on the Line interface since
        the last measure reset <Help> This
        measure gives the average Differential
        Group Delay on the Line interface
        since the last measure reset.
        "
	  ::= { rm10010mpMesrOther 185 }



--- *****************************************************
---     LEAF for the lineQFactorAverage article
--- *****************************************************

rm10010mpMesrlineQFactorAverage OBJECT-TYPE
	  SYNTAX Unsigned32 (0..65535)
	  MAX-ACCESS read-only
	  STATUS current
	  DESCRIPTION
        "
        Average Q Factor :This OID gives
        the average Q Factor on the Line
        interface since the last measure
        reset <Help> This measure gives
        the average Q Factor on the Line
        interface since the last measure
        reset.
        "
	  ::= { rm10010mpMesrOther 186 }



--- *****************************************************
---     LEAF for the lineCarrierFreqOffsetAverage article
--- *****************************************************

rm10010mpMesrlineCarrierFreqOffsetAverage OBJECT-TYPE
	  SYNTAX Unsigned32 (0..65535)
	  MAX-ACCESS read-only
	  STATUS current
	  DESCRIPTION
        "
        Average Carrier Frequency Offset
        :This OID gives the average Carrier
        Frequency Offset on the Line interface
        since the last measure reset <Help>
        This measure gives the average
         Carrier Frequency Offset on the
        Line interface since the last measure
        reset
        "
	  ::= { rm10010mpMesrOther 187 }



--- *****************************************************
---     LEAF for the lineOsnrAverage article
--- *****************************************************

rm10010mpMesrlineOsnrAverage OBJECT-TYPE
	  SYNTAX Unsigned32 (0..65535)
	  MAX-ACCESS read-only
	  STATUS current
	  DESCRIPTION
        "
        Average OSNR :This OID gives the
        average OSNR on the Line interface
        since the last measure reset <Help>
        This measure gives the average
         OSNR on the Line interface since
        the last measure reset.
        "
	  ::= { rm10010mpMesrOther 188 }



--- *****************************************************
---     LEAF for the clientNetTxTempMin article
--- *****************************************************

rm10010mpMesrclientNetTxTempMin OBJECT-TYPE
	  SYNTAX Unsigned32 (0..65535)
	  MAX-ACCESS read-only
	  STATUS current
	  DESCRIPTION
        "
        Min Client Trscv Laser Temperature
        :This OID gives the minimum Laser
        temperature value among the network
        lanes of the Client Transceiver,
        read from the DDM (Digital Diagnostic
        Monitoring) (Temperature = AV/256)
        (Unit = C) <Help> This Measure
         gives the minimum Laser temperature
        value among the network lanes of
        the Client Transceiver
        "
	  ::= { rm10010mpMesrOther 192 }



--- *****************************************************
---     LEAF for the clientNetTxBiasMin article
--- *****************************************************

rm10010mpMesrclientNetTxBiasMin OBJECT-TYPE
	  SYNTAX Unsigned32 (0..65535)
	  MAX-ACCESS read-only
	  STATUS current
	  DESCRIPTION
        "
        Min Client Trscv Laser Bias :This
        OID gives the minimum Laser bias
        value among the network lanes of
        the Client Transceiver, read from
        the DDM (Digital Diagnostic Monitoring)
        (Bias = AV/500) (Unit = mA) <Help>
        This Measure gives the minimum
         Laser bias value among the network
        lanes of the Client Transceiver
        "
	  ::= { rm10010mpMesrOther 193 }



--- *****************************************************
---     LEAF for the clientNetTxPwrMin article
--- *****************************************************

rm10010mpMesrclientNetTxPwrMin OBJECT-TYPE
	  SYNTAX Unsigned32 (0..65535)
	  MAX-ACCESS read-only
	  STATUS current
	  DESCRIPTION
        "
        Min Client Trscv Tx Power :This
        OID gives the minimum transmit
         power value among the network
         lanes of the Client Transceiver,
        read from the DDM (Digital Diagnostic
        Monitoring) (Power = 10*log(AV)-40)
        (Unit = dBm) <Help> This Measure
        gives the minimum transmit power
        value among the network lanes of
        the Client Transceiver
        "
	  ::= { rm10010mpMesrOther 194 }



--- *****************************************************
---     LEAF for the clientNetRxPwrMin article
--- *****************************************************

rm10010mpMesrclientNetRxPwrMin OBJECT-TYPE
	  SYNTAX Unsigned32 (0..65535)
	  MAX-ACCESS read-only
	  STATUS current
	  DESCRIPTION
        "
        Min Client Trscv Rx Power :This
        OID gives the minimum receive power
        value among the network lanes of
        the Client Transceiver, read in
        the DDM (Digital Diagnostic Monitoring)
        (Power = 10*log(AV)-40) (Unit =
        dBm) <Help> This Measure gives
         the minimum receive power value
        among the network lanes of the
         Client Transceiver
        "
	  ::= { rm10010mpMesrOther 195 }



--- *****************************************************
---     LEAF for the lineNetTxLaserOutputPwrMin article
--- *****************************************************

rm10010mpMesrlineNetTxLaserOutputPwrMin OBJECT-TYPE
	  SYNTAX Unsigned32 (0..65535)
	  MAX-ACCESS read-only
	  STATUS current
	  DESCRIPTION
        "
        Min Line Trscv Tx Power :This
         OID gives the minimum Tx Laser
        transmit power value among the
         network lanes of the Line Transceiver,
        read in the DDM (Digital Diagnostic
        Monitoring)  (Power = AV/100) (Unit
        = dBm) (Unit = dBm) <Help> This
        Measure gives the minimum Tx Laser
        transmit power value among the
         network lanes of the Line Transceiver
        "
	  ::= { rm10010mpMesrOther 196 }



--- *****************************************************
---     LEAF for the lineNetTxLaserTempMin article
--- *****************************************************

rm10010mpMesrlineNetTxLaserTempMin OBJECT-TYPE
	  SYNTAX Unsigned32 (0..65535)
	  MAX-ACCESS read-only
	  STATUS current
	  DESCRIPTION
        "
        Min Line Trscv Tx Laser Temperature
        :This OID gives the minimum Tx
         Laser Temperature value among
         the network lanes of the Line
         Transceiver, read from the DDM
        (Digital Diagnostic Monitoring)
        (Temperature = AV/256) (Unit =
         C) <Help> This Measure gives the
        minimum Tx Laser Temperature value
        among the network lanes of the
         Line Transceiver
        "
	  ::= { rm10010mpMesrOther 197 }



--- *****************************************************
---     LEAF for the lineNetTxBiasCurrentMin article
--- *****************************************************

rm10010mpMesrlineNetTxBiasCurrentMin OBJECT-TYPE
	  SYNTAX Unsigned32 (0..65535)
	  MAX-ACCESS read-only
	  STATUS current
	  DESCRIPTION
        "
        Min Line Trscv Tx Laser Bias :This
        OID gives the minimum Tx Laser
         Bias value among the network lanes
        of the Line Transceiver, read from
        the DDM (Digital Diagnostic Monitoring)
        (Bias = AV/10) (Unit = mA) <Help>
        This Measure gives the minimum
         Tx Laser Bias value among the
         network lanes of the Line Transceiver
        "
	  ::= { rm10010mpMesrOther 198 }



--- *****************************************************
---     LEAF for the lineNetRxInputPwrMin article
--- *****************************************************

rm10010mpMesrlineNetRxInputPwrMin OBJECT-TYPE
	  SYNTAX Unsigned32 (0..65535)
	  MAX-ACCESS read-only
	  STATUS current
	  DESCRIPTION
        "
        Min Line Trscv Rx Power :This
         OID gives the minimum Receive
         power value among the network
         lanes of the Line Transceiver,
        read in the DDM (Digital Diagnostic
        Monitoring) (Power = AV/100) (Unit
        = dBm) <Help> This Measure gives
        the minimum Receive power value
        among the network lanes of the
         Line Transceiver
        "
	  ::= { rm10010mpMesrOther 199 }



--- *****************************************************
---     LEAF for the lineResidualChromaticDispMin article
--- *****************************************************

rm10010mpMesrlineResidualChromaticDispMin OBJECT-TYPE
	  SYNTAX Unsigned32 (0..65535)
	  MAX-ACCESS read-only
	  STATUS current
	  DESCRIPTION
        "
        Min Residual Chromatic Dispersion
        :This OID gives the minimum Residual
        Chromatic Dispersion on the Line
        interface since the last measure
        reset  (Unit = ps/nm)<Help> This
        measure gives the minimum Residual
        Chromatic Dispersion on the Line
        interface since the last measure
        reset.
        "
	  ::= { rm10010mpMesrOther 200 }



--- *****************************************************
---     LEAF for the lineDiffGroupDelayMin article
--- *****************************************************

rm10010mpMesrlineDiffGroupDelayMin OBJECT-TYPE
	  SYNTAX Unsigned32 (0..65535)
	  MAX-ACCESS read-only
	  STATUS current
	  DESCRIPTION
        "
        Min Differential Group Delay :This
        OID gives the minimum Differential
        Group Delay  on the Line interface
        since the last measure reset  (Unit
        = ps)<Help> This measure gives
         the minimum Differential Group
        Delay on the Line interface since
        the last measure reset.
        "
	  ::= { rm10010mpMesrOther 201 }



--- *****************************************************
---     LEAF for the lineQFactorMin article
--- *****************************************************

rm10010mpMesrlineQFactorMin OBJECT-TYPE
	  SYNTAX Unsigned32 (0..65535)
	  MAX-ACCESS read-only
	  STATUS current
	  DESCRIPTION
        "
        Min Q Factor :This OID gives the
        minimum Q Factor on the Line interface
        since the last measure reset  (Unit
        = dB)<Help> This measure gives
         the minimum Q Factor on the Line
        interface since the last measure
        reset.
        "
	  ::= { rm10010mpMesrOther 202 }



--- *****************************************************
---     LEAF for the lineCarrierFreqOffsetMin article
--- *****************************************************

rm10010mpMesrlineCarrierFreqOffsetMin OBJECT-TYPE
	  SYNTAX Unsigned32 (0..65535)
	  MAX-ACCESS read-only
	  STATUS current
	  DESCRIPTION
        "
        Min Carrier Frequency Offset :This
        OID gives the minimum Carrier Frequency
        Offset on the Line interface since
        the last measure reset  (Unit =
        Mhz)<Help> This measure gives the
        minimum Carrier Frequency Offset
        on the Line interface since the
        last measure reset
        "
	  ::= { rm10010mpMesrOther 203 }



--- *****************************************************
---     LEAF for the lineOsnrMin article
--- *****************************************************

rm10010mpMesrlineOsnrMin OBJECT-TYPE
	  SYNTAX Unsigned32 (0..65535)
	  MAX-ACCESS read-only
	  STATUS current
	  DESCRIPTION
        "
        Min OSNR :This OID gives the minimum
        OSNR on the Line interface since
        the last measure reset  (OSNR =
        AV/10) (Unit = dB)<Help> This measure
        gives the minimum OSNR on the Line
        interface since the last measure
        reset.
        "
	  ::= { rm10010mpMesrOther 204 }



--- *****************************************************
---     LEAF for the clientNetTxTempMax article
--- *****************************************************

rm10010mpMesrclientNetTxTempMax OBJECT-TYPE
	  SYNTAX Unsigned32 (0..65535)
	  MAX-ACCESS read-only
	  STATUS current
	  DESCRIPTION
        "
        Max Client Trscv Laser Temperature
        :This OID gives the maximum Laser
        temperature value among the network
        lanes of the Client Transceiver,
        read from the DDM (Digital Diagnostic
        Monitoring) (Temperature = AV/256)
        (Unit = C) <Help> This Measure
         gives the maximum Laser temperature
        value among the network lanes of
        the Client Transceiver
        "
	  ::= { rm10010mpMesrOther 208 }



--- *****************************************************
---     LEAF for the clientNetTxBiasMax article
--- *****************************************************

rm10010mpMesrclientNetTxBiasMax OBJECT-TYPE
	  SYNTAX Unsigned32 (0..65535)
	  MAX-ACCESS read-only
	  STATUS current
	  DESCRIPTION
        "
        Max Client Trscv Laser Bias :This
        OID gives the maximum Laser bias
        value among the network lanes of
        the Client Transceiver, read from
        the DDM (Digital Diagnostic Monitoring)
        (Bias = AV/500) (Unit = mA) <Help>
        This Measure gives the maximum
         Laser bias value among the network
        lanes of the Client Transceiver
        "
	  ::= { rm10010mpMesrOther 209 }



--- *****************************************************
---     LEAF for the clientNetTxPwrMax article
--- *****************************************************

rm10010mpMesrclientNetTxPwrMax OBJECT-TYPE
	  SYNTAX Unsigned32 (0..65535)
	  MAX-ACCESS read-only
	  STATUS current
	  DESCRIPTION
        "
        Max Client Trscv Tx Power :This
        OID gives the maximum transmit
         power value among the network
         lanes of the Client Transceiver,
        read from the DDM (Digital Diagnostic
        Monitoring) (Power = 10*log(AV)-40)
        (Unit = dBm) <Help> This Measure
        gives the maximum transmit power
        value among the network lanes of
        the Client Transceiver
        "
	  ::= { rm10010mpMesrOther 210 }



--- *****************************************************
---     LEAF for the clientNetRxPwrMax article
--- *****************************************************

rm10010mpMesrclientNetRxPwrMax OBJECT-TYPE
	  SYNTAX Unsigned32 (0..65535)
	  MAX-ACCESS read-only
	  STATUS current
	  DESCRIPTION
        "
        Max Client Trscv Rx Power :This
        OID gives the maximum receive power
        value among the network lanes of
        the Client Transceiver, read in
        the DDM (Digital Diagnostic Monitoring)
        (Power = 10*log(AV)-40) (Unit =
        dBm) <Help> This Measure gives
         the maximum receive power value
        among the network lanes of the
         Client Transceiver
        "
	  ::= { rm10010mpMesrOther 211 }



--- *****************************************************
---     LEAF for the lineNetTxLaserOutputPwrMax article
--- *****************************************************

rm10010mpMesrlineNetTxLaserOutputPwrMax OBJECT-TYPE
	  SYNTAX Unsigned32 (0..65535)
	  MAX-ACCESS read-only
	  STATUS current
	  DESCRIPTION
        "
        Max Line Trscv Tx Power :This
         OID gives the maximum Tx Laser
        transmit power value among the
         network lanes of the Line Transceiver,
        read in the DDM (Digital Diagnostic
        Monitoring) (Power = 10*log(AV)-40)
        (Unit = dBm) <Help> This Measure
        gives the maximum Tx Laser transmit
        power value among the network lanes
        of the Line Transceiver
        "
	  ::= { rm10010mpMesrOther 212 }



--- *****************************************************
---     LEAF for the lineNetTxLaserTempMax article
--- *****************************************************

rm10010mpMesrlineNetTxLaserTempMax OBJECT-TYPE
	  SYNTAX Unsigned32 (0..65535)
	  MAX-ACCESS read-only
	  STATUS current
	  DESCRIPTION
        "
        Max Line Trscv Tx Laser Temperature
        :This OID gives the maximum Tx
         Laser Temperature value among
         the network lanes of the Line
         Transceiver, read from the DDM
        (Digital Diagnostic Monitoring)
        (Temperature = AV/256) (Unit =
         C) <Help> This Measure gives the
        maximum Tx Laser Temperature value
        among the network lanes of the
         Line Transceiver
        "
	  ::= { rm10010mpMesrOther 213 }



--- *****************************************************
---     LEAF for the lineNetTxBiasCurrentMax article
--- *****************************************************

rm10010mpMesrlineNetTxBiasCurrentMax OBJECT-TYPE
	  SYNTAX Unsigned32 (0..65535)
	  MAX-ACCESS read-only
	  STATUS current
	  DESCRIPTION
        "
        Max Line Trscv Tx Laser Bias :This
        OID gives the maximum Tx Laser
         Bias value among the network lanes
        of the Line Transceiver, read from
        the DDM (Digital Diagnostic Monitoring)
        (Bias = AV/10) (Unit = mA) <Help>
        This Measure gives the maximum
         Tx Laser Bias value among the
         network lanes of the Line Transceiver
        "
	  ::= { rm10010mpMesrOther 214 }



--- *****************************************************
---     LEAF for the lineNetRxInputPwrMax article
--- *****************************************************

rm10010mpMesrlineNetRxInputPwrMax OBJECT-TYPE
	  SYNTAX Unsigned32 (0..65535)
	  MAX-ACCESS read-only
	  STATUS current
	  DESCRIPTION
        "
        Max Line Trscv Rx Power :This
         OID gives the maximum Receive
         power value among the network
         lanes of the Line Transceiver,
        read in the DDM (Digital Diagnostic
        Monitoring) (Power = 10*log(AV)-40)
        (Unit = dBm) <Help> This Measure
        gives the maximum Receive power
        value among the network lanes of
        the Line Transceiver
        "
	  ::= { rm10010mpMesrOther 215 }



--- *****************************************************
---     LEAF for the lineResidualChromaticDispMax article
--- *****************************************************

rm10010mpMesrlineResidualChromaticDispMax OBJECT-TYPE
	  SYNTAX Unsigned32 (0..65535)
	  MAX-ACCESS read-only
	  STATUS current
	  DESCRIPTION
        "
        Max Residual Chromatic Dispersion
        :This OID gives the maximum Residual
        Chromatic Dispersion on the Line
        interface since the last measure
        reset  (Unit = ps/nm)<Help> This
        measure gives the maximum Residual
        Chromatic Dispersion on the Line
        interface since the last measure
        reset.
        "
	  ::= { rm10010mpMesrOther 216 }



--- *****************************************************
---     LEAF for the lineDiffGroupDelayMax article
--- *****************************************************

rm10010mpMesrlineDiffGroupDelayMax OBJECT-TYPE
	  SYNTAX Unsigned32 (0..65535)
	  MAX-ACCESS read-only
	  STATUS current
	  DESCRIPTION
        "
        Max Differential Group Delay :This
        OID gives the maximum Differential
        Group Delay  on the Line interface
        since the last measure reset
         (Unit = ps)<Help> This measure
        gives the maximum Differential
         Group Delay on the Line interface
        since the last measure reset.
        "
	  ::= { rm10010mpMesrOther 217 }



--- *****************************************************
---     LEAF for the lineQFactorMax article
--- *****************************************************

rm10010mpMesrlineQFactorMax OBJECT-TYPE
	  SYNTAX Unsigned32 (0..65535)
	  MAX-ACCESS read-only
	  STATUS current
	  DESCRIPTION
        "
        Max Q Factor :This OID gives the
        maximum Q Factor on the Line interface
        since the last measure reset  (Unit
        = dB)<Help> This measure gives
         the maximum Q Factor on the Line
        interface since the last measure
        reset.
        "
	  ::= { rm10010mpMesrOther 218 }



--- *****************************************************
---     LEAF for the lineCarrierFreqOffsetMax article
--- *****************************************************

rm10010mpMesrlineCarrierFreqOffsetMax OBJECT-TYPE
	  SYNTAX Unsigned32 (0..65535)
	  MAX-ACCESS read-only
	  STATUS current
	  DESCRIPTION
        "
        Max Carrier Frequency Offset :This
        OID gives the maximum Carrier Frequency
        Offset on the Line interface since
        the last measure reset   (Unit
         = Mhz)<Help> This measure gives
        the maximum Carrier Frequency Offset
        on the Line interface since the
        last measure reset.
        "
	  ::= { rm10010mpMesrOther 219 }



--- *****************************************************
---     LEAF for the lineOsnrMax article
--- *****************************************************

rm10010mpMesrlineOsnrMax OBJECT-TYPE
	  SYNTAX Unsigned32 (0..65535)
	  MAX-ACCESS read-only
	  STATUS current
	  DESCRIPTION
        "
        Max OSNR :This OID gives the maximum
        OSNR on the Line interface since
        the last measure reset  (OSNR =
        AV/10) (Unit = dB)<Help> This measure
        gives the maximum OSNR on the Line
        interface since the last measure
        reset
        "
	  ::= { rm10010mpMesrOther 220 }








--- *****************************************************
--- $$$$$$$$$$$$$$$$$$$$$$$$$$$$$$$$$$$$$$$$$$$$$$$$$$$$$
---     DOWNLOAD
--- $$$$$$$$$$$$$$$$$$$$$$$$$$$$$$$$$$$$$$$$$$$$$$$$$$$$$
--- *****************************************************



--- *****************************************************
---     LEAF for the restartProcess article
--- *****************************************************
rm10010mpDwlrestartProcess OBJECT IDENTIFIER ::= { rm10010mpDwlOther 0 }




rm10010mpDwlColdRestartProcessed OBJECT-TYPE
	  SYNTAX EkiOnOff
	  MAX-ACCESS read-only
	  STATUS current
	  DESCRIPTION
        "
        Cold Restart :This OID indicates
        that the module last restart was
        a Cold RESTART
        "
	  ::= { rm10010mpDwlrestartProcess 2 }



rm10010mpDwlWarmRestartProcessed OBJECT-TYPE
	  SYNTAX EkiOnOff
	  MAX-ACCESS read-only
	  STATUS current
	  DESCRIPTION
        "
        Warm Restart :This OID indicates
        that the module last restart was
        a Warm RESTART
        "
	  ::= { rm10010mpDwlrestartProcess 1 }



--- *****************************************************
---     LEAF for the swBanksUsed article
--- *****************************************************
rm10010mpDwlswBanksUsed OBJECT IDENTIFIER ::= { rm10010mpDwlOther 1 }




rm10010mpDwlSwBank2Notempty OBJECT-TYPE
	  SYNTAX EkiOnOff
	  MAX-ACCESS read-only
	  STATUS current
	  DESCRIPTION
        "
        SW bank 2 loaded :This OID indicates
        a software is loaded in SW bank
        2  <Help>  This status indicates
        if the SW bank 2 contains SW package
        "
	  ::= { rm10010mpDwlswBanksUsed 6 }



rm10010mpDwlSwBank1Notempty OBJECT-TYPE
	  SYNTAX EkiOnOff
	  MAX-ACCESS read-only
	  STATUS current
	  DESCRIPTION
        "
        SW bank 1 loaded :This OID indicates
        a software is loaded in SW bank
        1  <Help>  This status indicates
        if the SW bank 1 contains SW package
        "
	  ::= { rm10010mpDwlswBanksUsed 5 }



rm10010mpDwlSwBank2Used OBJECT-TYPE
	  SYNTAX EkiOnOff
	  MAX-ACCESS read-only
	  STATUS current
	  DESCRIPTION
        "
        SW bank 2 active :This OID indicates
        the module is working on SW bank
        2  <Help>  This status indicates
        if the SW bank 2 is active or standby
        "
	  ::= { rm10010mpDwlswBanksUsed 2 }



rm10010mpDwlSwBank1Used OBJECT-TYPE
	  SYNTAX EkiOnOff
	  MAX-ACCESS read-only
	  STATUS current
	  DESCRIPTION
        "
        SW bank 1 active :This OID indicates
        the module is working on SW bank
        1  <Help>  This status indicates
        if the SW bank 1 is active or standby
        "
	  ::= { rm10010mpDwlswBanksUsed 1 }



--- *****************************************************
---     LEAF for the gwBanksUsed article
--- *****************************************************
rm10010mpDwlgwBanksUsed OBJECT IDENTIFIER ::= { rm10010mpDwlOther 2 }




rm10010mpDwlGwBank4Notempty OBJECT-TYPE
	  SYNTAX EkiOnOff
	  MAX-ACCESS read-only
	  STATUS current
	  DESCRIPTION
        "
        GW bank 4 loaded :This OID indicates
        a gateware is loaded in GW bank
        4
        "
	  ::= { rm10010mpDwlgwBanksUsed 8 }



rm10010mpDwlGwBank3Notempty OBJECT-TYPE
	  SYNTAX EkiOnOff
	  MAX-ACCESS read-only
	  STATUS current
	  DESCRIPTION
        "
        GW bank 3 loaded :This OID indicates
        a gateware is loaded in GW bank
        3  <Help>  This status indicates
        if the GW bank 3 contains GW package
        "
	  ::= { rm10010mpDwlgwBanksUsed 7 }



rm10010mpDwlGwBank2Notempty OBJECT-TYPE
	  SYNTAX EkiOnOff
	  MAX-ACCESS read-only
	  STATUS current
	  DESCRIPTION
        "
        GW bank 2 loaded :This OID indicates
        a gateware is loaded in GW bank
        2
        "
	  ::= { rm10010mpDwlgwBanksUsed 6 }



rm10010mpDwlGwBank1Notempty OBJECT-TYPE
	  SYNTAX EkiOnOff
	  MAX-ACCESS read-only
	  STATUS current
	  DESCRIPTION
        "
        GW bank 1 loaded :This OID indicates
        a gateware is loaded in GW bank
        1  <Help>  This status indicates
        if the GW bank 1 contains GW package
        "
	  ::= { rm10010mpDwlgwBanksUsed 5 }



rm10010mpDwlGwBank4Used OBJECT-TYPE
	  SYNTAX EkiOnOff
	  MAX-ACCESS read-only
	  STATUS current
	  DESCRIPTION
        "
        GW bank 4 active :This OID indicates
        the module is working on GW bank
        4
        "
	  ::= { rm10010mpDwlgwBanksUsed 4 }



rm10010mpDwlGwBank3Used OBJECT-TYPE
	  SYNTAX EkiOnOff
	  MAX-ACCESS read-only
	  STATUS current
	  DESCRIPTION
        "
        GW bank 3 active :This OID indicates
        the module is working on GW bank
        3  <Help>  This status indicates
        if the GW bank 3 is active or standby
        "
	  ::= { rm10010mpDwlgwBanksUsed 3 }



rm10010mpDwlGwBank2Used OBJECT-TYPE
	  SYNTAX EkiOnOff
	  MAX-ACCESS read-only
	  STATUS current
	  DESCRIPTION
        "
        GW bank 2 active :This OID indicates
        the module is working on GW bank
        2
        "
	  ::= { rm10010mpDwlgwBanksUsed 2 }



rm10010mpDwlGwBank1Used OBJECT-TYPE
	  SYNTAX EkiOnOff
	  MAX-ACCESS read-only
	  STATUS current
	  DESCRIPTION
        "
        GW bank 1 active :This OID indicates
        the module is working on GW bank
        1  <Help>  This status indicates
        if the GW bank 1 is active or standby
        "
	  ::= { rm10010mpDwlgwBanksUsed 1 }








--- *****************************************************
--- $$$$$$$$$$$$$$$$$$$$$$$$$$$$$$$$$$$$$$$$$$$$$$$$$$$$$
---     CONFIG
--- $$$$$$$$$$$$$$$$$$$$$$$$$$$$$$$$$$$$$$$$$$$$$$$$$$$$$
--- *****************************************************



--- *****************************************************
---     LEAF for the table Group accessCAisCsf
--- *****************************************************

rm10010mpCfgAccessCAisCsf OBJECT IDENTIFIER ::= { rm10010mpConfig 1 }



--- *****************************************************
---     LEAF for the table 0012
--- *****************************************************

rm10010mpCfgClientcaiscsfTable OBJECT-TYPE
	SYNTAX  SEQUENCE OF Rm10010mpCfgClientcaiscsfEntry
	MAX-ACCESS not-accessible
	STATUS current
	DESCRIPTION
        "
        List of  Article
        "
	::= { rm10010mpCfgAccessCAisCsf 1 }


rm10010mpCfgClientcaiscsfEntry OBJECT-TYPE
	SYNTAX Rm10010mpCfgClientcaiscsfEntry
	MAX-ACCESS not-accessible
	STATUS current
	DESCRIPTION
        "
        Row definition for the accessCAisCsf
        table
        "
	INDEX   { rm10010mpCfgClientcaiscsfIndex }
	::= { rm10010mpCfgClientcaiscsfTable 1 }


Rm10010mpCfgClientcaiscsfEntry ::=
	SEQUENCE {
	rm10010mpCfgClientcaiscsfIndex
		INTEGER,
	rm10010mpCfgReservePortn
		Unsigned32
	}


rm10010mpCfgClientcaiscsfIndex OBJECT-TYPE
	SYNTAX  INTEGER(0..128)
	MAX-ACCESS  read-only
	STATUS current
	DESCRIPTION
        "
        Index definition for the clientcaiscsf
        table
        "
	::= { rm10010mpCfgClientcaiscsfEntry 1 }


rm10010mpCfgReservePortn OBJECT-TYPE
	SYNTAX  Unsigned32 (0..65536)
	MAX-ACCESS read-write
	STATUS current
	DESCRIPTION
        "
        CAIS mode  on Client Port :This
        register enables/disables port
          laser shutdown on CAIS insertion
        condition
        "
	::= { rm10010mpCfgClientcaiscsfEntry 3 }


--- *****************************************************
---     LEAF for the table Group startup
--- *****************************************************

rm10010mpCfgStartup OBJECT IDENTIFIER ::= { rm10010mpConfig 2 }



--- *****************************************************
---     LEAF for the table 2110
--- *****************************************************

rm10010mpCfgClientStartupTable OBJECT-TYPE
	SYNTAX  SEQUENCE OF Rm10010mpCfgClientStartupEntry
	MAX-ACCESS not-accessible
	STATUS current
	DESCRIPTION
        "
        List of  Article
        "
	::= { rm10010mpCfgStartup 1 }


rm10010mpCfgClientStartupEntry OBJECT-TYPE
	SYNTAX Rm10010mpCfgClientStartupEntry
	MAX-ACCESS not-accessible
	STATUS current
	DESCRIPTION
        "
        Row definition for the startup
        table
        "
	INDEX   { rm10010mpCfgClientStartupIndex }
	::= { rm10010mpCfgClientStartupTable 1 }


Rm10010mpCfgClientStartupEntry ::=
	SEQUENCE {
	rm10010mpCfgClientStartupIndex
		INTEGER,
	rm10010mpCfgSystConfPortPortn
		Unsigned32,
	rm10010mpCfgNetConfPortPortn
		Unsigned32,
	rm10010mpCfgOptionsPortPortn
		Unsigned32
	}


rm10010mpCfgClientStartupIndex OBJECT-TYPE
	SYNTAX  INTEGER(0..128)
	MAX-ACCESS  read-only
	STATUS current
	DESCRIPTION
        "
        Index definition for the clientStartup
        table
        "
	::= { rm10010mpCfgClientStartupEntry 1 }


rm10010mpCfgSystConfPortPortn OBJECT-TYPE
	SYNTAX  Unsigned32 (0..65536)
	MAX-ACCESS read-write
	STATUS current
	DESCRIPTION
        "
        Default Settings on Client Port
        :This  register configures the
         default initialisation settings
        on the port.
        "
	::= { rm10010mpCfgClientStartupEntry 3 }


rm10010mpCfgNetConfPortPortn OBJECT-TYPE
	SYNTAX  Unsigned32 (0..65536)
	MAX-ACCESS read-write
	STATUS current
	DESCRIPTION
        "
        Default Settings on Client Port
        :This  register configures the
         default initialisation settings
        on the port.
        "
	::= { rm10010mpCfgClientStartupEntry 4 }


rm10010mpCfgOptionsPortPortn OBJECT-TYPE
	SYNTAX  Unsigned32 (0..65536)
	MAX-ACCESS read-write
	STATUS current
	DESCRIPTION
        "
        Default Options on Client Port
        :This register configures the default
        options on the port.
        "
	::= { rm10010mpCfgClientStartupEntry 14 }


--- *****************************************************
---     LEAF for the table 2190
--- *****************************************************

rm10010mpCfgLineStartupTable OBJECT-TYPE
	SYNTAX  SEQUENCE OF Rm10010mpCfgLineStartupEntry
	MAX-ACCESS not-accessible
	STATUS current
	DESCRIPTION
        "
        List of  Article
        "
	::= { rm10010mpCfgStartup 2 }


rm10010mpCfgLineStartupEntry OBJECT-TYPE
	SYNTAX Rm10010mpCfgLineStartupEntry
	MAX-ACCESS not-accessible
	STATUS current
	DESCRIPTION
        "
        Row definition for the startup
        table
        "
	INDEX   { rm10010mpCfgLineStartupIndex }
	::= { rm10010mpCfgLineStartupTable 1 }


Rm10010mpCfgLineStartupEntry ::=
	SEQUENCE {
	rm10010mpCfgLineStartupIndex
		INTEGER,
	rm10010mpCfgSystConfLinePortn
		Unsigned32,
	rm10010mpCfgOptionsLinePortn
		Unsigned32
	}


rm10010mpCfgLineStartupIndex OBJECT-TYPE
	SYNTAX  INTEGER(0..128)
	MAX-ACCESS  read-only
	STATUS current
	DESCRIPTION
        "
        Index definition for the lineStartup
        table
        "
	::= { rm10010mpCfgLineStartupEntry 1 }


rm10010mpCfgSystConfLinePortn OBJECT-TYPE
	SYNTAX  Unsigned32 (0..65536)
	MAX-ACCESS read-write
	STATUS current
	DESCRIPTION
        "
        Default Settings on Line :This
        register configures the default
        initialisation settings on Line
        "
	::= { rm10010mpCfgLineStartupEntry 3 }


rm10010mpCfgOptionsLinePortn OBJECT-TYPE
	SYNTAX  Unsigned32 (0..65536)
	MAX-ACCESS read-write
	STATUS current
	DESCRIPTION
        "
        Default Options on Line :This
         register configures the default
        options on the line
        "
	::= { rm10010mpCfgLineStartupEntry 14 }


--- *****************************************************
---     LEAF for the table 21AB
--- *****************************************************

rm10010mpCfgXfpTable OBJECT-TYPE
	SYNTAX  SEQUENCE OF Rm10010mpCfgXfpEntry
	MAX-ACCESS not-accessible
	STATUS current
	DESCRIPTION
        "
        List of  Article
        "
	::= { rm10010mpCfgStartup 3 }


rm10010mpCfgXfpEntry OBJECT-TYPE
	SYNTAX Rm10010mpCfgXfpEntry
	MAX-ACCESS not-accessible
	STATUS current
	DESCRIPTION
        "
        Row definition for the startup
        table
        "
	INDEX   { rm10010mpCfgXfpIndex }
	::= { rm10010mpCfgXfpTable 1 }


Rm10010mpCfgXfpEntry ::=
	SEQUENCE {
	rm10010mpCfgXfpIndex
		INTEGER,
	rm10010mpCfgSystConfMsaLinePortn
		Unsigned32
	}


rm10010mpCfgXfpIndex OBJECT-TYPE
	SYNTAX  INTEGER(0..128)
	MAX-ACCESS  read-only
	STATUS current
	DESCRIPTION
        "
        Index definition for the xfp table
        "
	::= { rm10010mpCfgXfpEntry 1 }


rm10010mpCfgSystConfMsaLinePortn OBJECT-TYPE
	SYNTAX  Unsigned32 (0..65536)
	MAX-ACCESS read-write
	STATUS current
	DESCRIPTION
        "
        Default settings on MSA :This
         register configures the default
        initialisation settings on MSA
        "
	::= { rm10010mpCfgXfpEntry 3 }


--- *****************************************************
---     LEAF for the table Group labels
--- *****************************************************

rm10010mpCfgLabels OBJECT IDENTIFIER ::= { rm10010mpConfig 3 }



--- *****************************************************
---     LEAF for the table 0003
--- *****************************************************

rm10010mpCfgLabelclientTable OBJECT-TYPE
	SYNTAX  SEQUENCE OF Rm10010mpCfgLabelclientEntry
	MAX-ACCESS not-accessible
	STATUS current
	DESCRIPTION
        "
        List of  Article
        "
	::= { rm10010mpCfgLabels 1 }


rm10010mpCfgLabelclientEntry OBJECT-TYPE
	SYNTAX Rm10010mpCfgLabelclientEntry
	MAX-ACCESS not-accessible
	STATUS current
	DESCRIPTION
        "
        Row definition for the labels
         table
        "
	INDEX   { rm10010mpCfgLabelclientIndex }
	::= { rm10010mpCfgLabelclientTable 1 }


Rm10010mpCfgLabelclientEntry ::=
	SEQUENCE {
	rm10010mpCfgLabelclientIndex
		INTEGER,
	rm10010mpCfgLabelclientPortn
		DisplayString
	}


rm10010mpCfgLabelclientIndex OBJECT-TYPE
	SYNTAX  INTEGER(0..128)
	MAX-ACCESS  read-only
	STATUS current
	DESCRIPTION
        "
        Index definition for the labelclient
        table
        "
	::= { rm10010mpCfgLabelclientEntry 1 }


rm10010mpCfgLabelclientPortn OBJECT-TYPE
	SYNTAX  DisplayString( SIZE(1..16))
	MAX-ACCESS read-write
	STATUS current
	DESCRIPTION
        "
        Default settings on the label
         of the Ports :These registers
         configures the default initialisation
        settings of the labels of the ports.
        "
	::= { rm10010mpCfgLabelclientEntry 3 }


--- *****************************************************
---     LEAF for the table 0004
--- *****************************************************

rm10010mpCfgLabellineTable OBJECT-TYPE
	SYNTAX  SEQUENCE OF Rm10010mpCfgLabellineEntry
	MAX-ACCESS not-accessible
	STATUS current
	DESCRIPTION
        "
        List of  Article
        "
	::= { rm10010mpCfgLabels 2 }


rm10010mpCfgLabellineEntry OBJECT-TYPE
	SYNTAX Rm10010mpCfgLabellineEntry
	MAX-ACCESS not-accessible
	STATUS current
	DESCRIPTION
        "
        Row definition for the labels
         table
        "
	INDEX   { rm10010mpCfgLabellineIndex }
	::= { rm10010mpCfgLabellineTable 1 }


Rm10010mpCfgLabellineEntry ::=
	SEQUENCE {
	rm10010mpCfgLabellineIndex
		INTEGER,
	rm10010mpCfgLabellinePortn
		DisplayString
	}


rm10010mpCfgLabellineIndex OBJECT-TYPE
	SYNTAX  INTEGER(0..128)
	MAX-ACCESS  read-only
	STATUS current
	DESCRIPTION
        "
        Index definition for the labelline
        table
        "
	::= { rm10010mpCfgLabellineEntry 1 }


rm10010mpCfgLabellinePortn OBJECT-TYPE
	SYNTAX  DisplayString( SIZE(1..16))
	MAX-ACCESS read-write
	STATUS current
	DESCRIPTION
        "
        Default settings on the label
         of the lines :These registers
         configures the default initialisation
        settings of the labels of the lines.
        "
	::= { rm10010mpCfgLabellineEntry 3 }


--- *****************************************************
---     LEAF for the table Group startuptlh
--- *****************************************************

rm10010mpCfgStartuptlh OBJECT IDENTIFIER ::= { rm10010mpConfig 4 }



--- *****************************************************
---     LEAF for the table 25AB
--- *****************************************************

rm10010mpCfgOtxtlhTable OBJECT-TYPE
	SYNTAX  SEQUENCE OF Rm10010mpCfgOtxtlhEntry
	MAX-ACCESS not-accessible
	STATUS current
	DESCRIPTION
        "
        List of  Article
        "
	::= { rm10010mpCfgStartuptlh 1 }


rm10010mpCfgOtxtlhEntry OBJECT-TYPE
	SYNTAX Rm10010mpCfgOtxtlhEntry
	MAX-ACCESS not-accessible
	STATUS current
	DESCRIPTION
        "
        Row definition for the startuptlh
        table
        "
	INDEX   { rm10010mpCfgOtxtlhIndex }
	::= { rm10010mpCfgOtxtlhTable 1 }


Rm10010mpCfgOtxtlhEntry ::=
	SEQUENCE {
	rm10010mpCfgOtxtlhIndex
		INTEGER,
	rm10010mpCfgLinePwrLaserPortn
		Unsigned32,
	rm10010mpCfgLineFCurrentPortn
		Unsigned32,
	rm10010mpCfgLineGridCurrentPortn
		Unsigned32,
	rm10010mpCfgFPortn
		Unsigned32,
	rm10010mpCfgRxLineFCurrentPortn
		Unsigned32
	}


rm10010mpCfgOtxtlhIndex OBJECT-TYPE
	SYNTAX  INTEGER(0..128)
	MAX-ACCESS  read-only
	STATUS current
	DESCRIPTION
        "
        Index definition for the otxtlh
        table
        "
	::= { rm10010mpCfgOtxtlhEntry 1 }


rm10010mpCfgLinePwrLaserPortn OBJECT-TYPE
	SYNTAX  Unsigned32 (0..65536)
	MAX-ACCESS read-write
	STATUS current
	DESCRIPTION
        "
        Defaut Line output Power :This
        register configures the start-up
        output power of the Line tranceiver
         (Unit = dBm)
        "
	::= { rm10010mpCfgOtxtlhEntry 6 }


rm10010mpCfgLineFCurrentPortn OBJECT-TYPE
	SYNTAX  Unsigned32 (0..65536)
	MAX-ACCESS read-write
	STATUS current
	DESCRIPTION
        "
        Default Line transceiver Tx Channel
        :This register configures the start-up
        laser channel of the Line Tx transceiver
        "
	::= { rm10010mpCfgOtxtlhEntry 7 }


rm10010mpCfgLineGridCurrentPortn OBJECT-TYPE
	SYNTAX  Unsigned32 (0..65536)
	MAX-ACCESS read-write
	STATUS current
	DESCRIPTION
        "
        Default Line transceiver Grid
         :This register configures the
         start-up laser grid of the Line
        transceiver
        "
	::= { rm10010mpCfgOtxtlhEntry 8 }


rm10010mpCfgFPortn OBJECT-TYPE
	SYNTAX  Unsigned32 (0..65536)
	MAX-ACCESS read-write
	STATUS current
	DESCRIPTION
        "
        Default Line TRX lowest Freq :This
        register configures the start-up
        lowest frequency of the Line transceiver
        "
	::= { rm10010mpCfgOtxtlhEntry 9 }


rm10010mpCfgRxLineFCurrentPortn OBJECT-TYPE
	SYNTAX  Unsigned32 (0..65536)
	MAX-ACCESS read-write
	STATUS current
	DESCRIPTION
        "
        Default Line transceiver Rx Channel
        :This register configures the start-up
        laser channel of the Line Rx transceiver
        "
	::= { rm10010mpCfgOtxtlhEntry 10 }


--- *****************************************************
---     LEAF for the table Group other
--- *****************************************************

rm10010mpCfgOther OBJECT IDENTIFIER ::= { rm10010mpConfig 5 }



--- *****************************************************
---     LEAF for the table 2300
--- *****************************************************

rm10010mptablemoduleOther OBJECT IDENTIFIER ::= { rm10010mpCfgOther 1 }



rm10010mpCfgmode OBJECT-TYPE
	  SYNTAX Unsigned32 (0..65536)
	  MAX-ACCESS read-write
	  STATUS current
	  DESCRIPTION
        "
        Default settings on Module :This
        register selects the configuration
        mode of the module
        "
	  ::= { rm10010mptablemoduleOther 2 }



rm10010mpCfgfanLowSpeedThreshold OBJECT-TYPE
	  SYNTAX Unsigned32 (0..65536)
	  MAX-ACCESS read-write
	  STATUS current
	  DESCRIPTION
        "
        Default settings on Module :This
        register selects the speed threshold
        of the fan's
        "
	  ::= { rm10010mptablemoduleOther 3 }



rm10010mpCfgfanHighSpeedThreshold OBJECT-TYPE
	  SYNTAX Unsigned32 (0..65536)
	  MAX-ACCESS read-write
	  STATUS current
	  DESCRIPTION
        "
        Default settings on Module :This
        register selects the speed threshold
        of the fan's
        "
	  ::= { rm10010mptablemoduleOther 4 }



--- *****************************************************
---     LEAF for the table Group startuptablefive
--- *****************************************************

rm10010mpCfgStartuptablefive OBJECT IDENTIFIER ::= { rm10010mpConfig 6 }



--- *****************************************************
---     LEAF for the table 0005
--- *****************************************************

rm10010mpCfgOtxtlhcapabilitiesTable OBJECT-TYPE
	SYNTAX  SEQUENCE OF Rm10010mpCfgOtxtlhcapabilitiesEntry
	MAX-ACCESS not-accessible
	STATUS current
	DESCRIPTION
        "
        List of  Article
        "
	::= { rm10010mpCfgStartuptablefive 1 }


rm10010mpCfgOtxtlhcapabilitiesEntry OBJECT-TYPE
	SYNTAX Rm10010mpCfgOtxtlhcapabilitiesEntry
	MAX-ACCESS not-accessible
	STATUS current
	DESCRIPTION
        "
        Row definition for the startuptablefive
        table
        "
	INDEX   { rm10010mpCfgOtxtlhcapabilitiesIndex }
	::= { rm10010mpCfgOtxtlhcapabilitiesTable 1 }


Rm10010mpCfgOtxtlhcapabilitiesEntry ::=
	SEQUENCE {
	rm10010mpCfgOtxtlhcapabilitiesIndex
		INTEGER,
	rm10010mpCfgComponentTypePortn
		Unsigned32,
	rm10010mpCfgMiscellaneousPortn
		Unsigned32,
	rm10010mpCfgFirstChannelPortn
		Unsigned32,
	rm10010mpCfgLastChannelPortn
		Unsigned32,
	rm10010mpCfgGridPortn
		Unsigned32
	}


rm10010mpCfgOtxtlhcapabilitiesIndex OBJECT-TYPE
	SYNTAX  INTEGER(0..128)
	MAX-ACCESS  read-only
	STATUS current
	DESCRIPTION
        "
        Index definition for the otxtlhcapabilities
        table
        "
	::= { rm10010mpCfgOtxtlhcapabilitiesEntry 1 }


rm10010mpCfgComponentTypePortn OBJECT-TYPE
	SYNTAX  Unsigned32 (0..65536)
	MAX-ACCESS read-only
	STATUS current
	DESCRIPTION
        "
        Component parameters :This OID
        defines the component parameters
        "
	::= { rm10010mpCfgOtxtlhcapabilitiesEntry 3 }


rm10010mpCfgMiscellaneousPortn OBJECT-TYPE
	SYNTAX  Unsigned32 (0..65536)
	MAX-ACCESS read-only
	STATUS current
	DESCRIPTION
        "
        Miscellaneous default settings
        :This OID defines the miscellaneous
        parameters
        "
	::= { rm10010mpCfgOtxtlhcapabilitiesEntry 4 }


rm10010mpCfgFirstChannelPortn OBJECT-TYPE
	SYNTAX  Unsigned32 (0..65536)
	MAX-ACCESS read-only
	STATUS current
	DESCRIPTION
        "
        Number of the first channel of
        the component :This OID defines
        the first channel number of the
        PM
        "
	::= { rm10010mpCfgOtxtlhcapabilitiesEntry 5 }


rm10010mpCfgLastChannelPortn OBJECT-TYPE
	SYNTAX  Unsigned32 (0..65536)
	MAX-ACCESS read-only
	STATUS current
	DESCRIPTION
        "
        Number of the last channel of
         the component :This OID defines
        the last channel number of the
         PM
        "
	::= { rm10010mpCfgOtxtlhcapabilitiesEntry 6 }


rm10010mpCfgGridPortn OBJECT-TYPE
	SYNTAX  Unsigned32 (0..65536)
	MAX-ACCESS read-only
	STATUS current
	DESCRIPTION
        "
        Grid value of the component :This
        OID defines the grid of the PM
        "
	::= { rm10010mpCfgOtxtlhcapabilitiesEntry 7 }



rm10010mpCfgWriteConfiguration  OBJECT-TYPE
	SYNTAX EkiOnOff
	MAX-ACCESS read-write
	STATUS current
	DESCRIPTION
	"Write configuration to module:This OID
	 writes the complete configuration to the module"
	::= { rm10010mpConfig 257 }






--- *****************************************************
---     TRAP OBJECTS
--- *****************************************************

rm10010mptrapPortNumber OBJECT-TYPE
	SYNTAX INTEGER(1..64)
	MAX-ACCESS read-only
	STATUS current
	DESCRIPTION
	"Last port which generates a trap"
	::= { rm10010mptraps 2 }

rm10010mptrapLineNumber OBJECT-TYPE
	SYNTAX INTEGER(1..64)
	MAX-ACCESS read-only
	STATUS current
	DESCRIPTION
	"Last Line which generates a trap"
	::= { rm10010mptraps 3 }

rm10010mptrapBoardNumber OBJECT-TYPE
	SYNTAX INTEGER(1..64)
	MAX-ACCESS read-only
	STATUS current
	DESCRIPTION
	"Last module which generates a trap"
	::= { rm10010mptraps 4 }







--- *****************************************************
---     LINE TRAPS
--- *****************************************************

rm10010mpLineTrapNotUrgentGoesOn NOTIFICATION-TYPE
	OBJECTS {rm10010mpAlmLineDdmWarningPortn, rm10010mptrapLineNumber, rm10010mptrapBoardNumber}
	STATUS current
	--&FILTNAME    "RM10010MP Line Not Urgent ON"
	--&ACTIONS     { log, minor }
	--&MATCH       { rm10010mpAlmLineDdmWarningPortn "on", rm10010mptrapLineNumber "$2", rm10010mptrapBoardNumber "$3"}
	--&MESG        "DDM Warning appears on Line Port $2 of RM10010MP in Slot $3 ($A)"
	DESCRIPTION "Not urgent Line default is activated"
	::= { rm10010mptraps 30 }

rm10010mpLineTrapNotUrgentGoesOff NOTIFICATION-TYPE
	OBJECTS {rm10010mpAlmLineDdmWarningPortn, rm10010mptrapLineNumber, rm10010mptrapBoardNumber}
	STATUS current
	--&FILTNAME    "RM10010MP Line Not Urgent OFF"
	--&ACTIONS     { log, normal }
	--&CLEARS      { "RM10010MP Line Not Urgent ON" }
	--&MATCH       { rm10010mpAlmLineDdmWarningPortn "on", rm10010mptrapLineNumber "$2", rm10010mptrapBoardNumber "$3"}
	--&MESG        "DDM Warning disappears on Line Port $2 of RM10010MP in Slot $3 ($A)"
	DESCRIPTION "Not urgent Line default disappeared"
	::= { rm10010mptraps 31 }

rm10010mpLineTrapUrgentGoesOn NOTIFICATION-TYPE
	OBJECTS {rm10010mpAlmLineDdmAlmPortn, rm10010mptrapLineNumber, rm10010mptrapBoardNumber}
	STATUS current
	--&FILTNAME    "RM10010MP Line Urgent ON"
	--&ACTIONS     { log, major }
	--&MATCH       { rm10010mpAlmLineDdmAlmPortn "on", rm10010mptrapLineNumber "$2", rm10010mptrapBoardNumber "$3"}
	--&MESG        "DDM Alarm appears on Line Port $2 of RM10010MP in Slot $3 ($A)"
	DESCRIPTION "Urgent Line default is activated"
	::= { rm10010mptraps 32 }

rm10010mpLineTrapUrgentGoesOff NOTIFICATION-TYPE
	OBJECTS {rm10010mpAlmLineDdmAlmPortn, rm10010mptrapLineNumber, rm10010mptrapBoardNumber}
	STATUS current
	--&FILTNAME    "RM10010MP Line Urgent OFF"
	--&ACTIONS     { log, normal }
	--&CLEARS      { "RM10010MP Line Urgent ON" }
	--&MATCH       { rm10010mpAlmLineDdmAlmPortn "on", rm10010mptrapLineNumber "$2", rm10010mptrapBoardNumber "$3"}
	--&MESG        "DDM Alarm disappears on Line Port $2 of RM10010MP in Slot $3 ($A)"
	DESCRIPTION "Urgent Line default disappeared"
	::= { rm10010mptraps 33 }

rm10010mpLineTrapCritGoesOn NOTIFICATION-TYPE
	OBJECTS {rm10010mpAlmLineFailPortn , rm10010mpAlmLineHwFailPortn , rm10010mptrapLineNumber, rm10010mptrapBoardNumber}
	STATUS current
	--&FILTNAME    "RM10010MP Line Fail ON"
	--&ACTIONS     { log, critical }
	--&MATCH       { rm10010mpAlmLineFailPortn "on", rm10010mpAlmLineHwFailPortn "*", rm10010mptrapLineNumber "$3", rm10010mptrapBoardNumber "$4"}
	--&MESG        "Line Port $3 Down on RM10010MP in Slot $4 ($A)"

	--&FILTNAME    "RM10010MP Line HW Fail ON (Hidden)"
	--&ACTIONS     { info }
	--&MATCH       { rm10010mpAlmLineFailPortn "*", rm10010mpAlmLineHwFailPortn "on", rm10010mptrapLineNumber "$3", rm10010mptrapBoardNumber "$4"}
	--&MESG        "Line Port $3 Down on RM10010MP in Slot $4 ($A)"
	DESCRIPTION "Critical Line default is activated"
	::= { rm10010mptraps 34 }

rm10010mpLineTrapCritGoesOff NOTIFICATION-TYPE
	OBJECTS {rm10010mpAlmLineFailPortn , rm10010mpAlmLineHwFailPortn , rm10010mptrapLineNumber, rm10010mptrapBoardNumber}
	STATUS current
	--&FILTNAME    "RM10010MP Line Fail OFF"
	--&ACTIONS     { log,  normal }
	--&CLEARS      { "RM10010MP Line Fail ON" }
	--&MATCH       { rm10010mpAlmLineFailPortn "on", rm10010mpAlmLineHwFailPortn "*", rm10010mptrapLineNumber "$3", rm10010mptrapBoardNumber "$4"}
	--&MESG        "Line Port $3 Up on RM10010MP in Slot $4 ($A)"

	--&FILTNAME    "RM10010MP Line HW Fail OFF (Hidden)"
	--&ACTIONS     { info }
	--&MATCH       { rm10010mpAlmLineFailPortn "*", rm10010mpAlmLineHwFailPortn "on", rm10010mptrapLineNumber "$3", rm10010mptrapBoardNumber "$4"}
	--&MESG        "Line Port $3 Up on RM10010MP in Slot $4 ($A)"
	DESCRIPTION "Critical Line default disappeared"
	::= { rm10010mptraps 35 }






--- *****************************************************
---     CLIENT TRAPS
--- *****************************************************

rm10010mpClientTrapNotUrgentGoesOn NOTIFICATION-TYPE
	OBJECTS {rm10010mpAlmSfpDdmWarningPortn, rm10010mptrapPortNumber, rm10010mptrapBoardNumber}
	STATUS current
		--&FILTNAME    "RM10010MP Client Not Urgent ON"
		--&ACTIONS     { log, minor }
		--&MATCH       { rm10010mpAlmSfpDdmWarningPortn "on", rm10010mptrapPortNumber "$2", rm10010mptrapBoardNumber "$3"}
		--&MESG        "DDM Warning appears on Client Port $2 of RM10010MP in Slot $3 ($A)"
	DESCRIPTION "Not urgent client default is activated"
	::= { rm10010mptraps 40 }

rm10010mpClientTrapNotUrgentGoesOff NOTIFICATION-TYPE
	OBJECTS {rm10010mpAlmSfpDdmWarningPortn, rm10010mptrapPortNumber, rm10010mptrapBoardNumber}
	STATUS current
		--&FILTNAME    "RM10010MP Client Not Urgent OFF"
		--&ACTIONS     { log, normal }
		--&CLEARS      { "RM10010MP Client Not Urgent ON" }
		--&MATCH       { rm10010mpAlmSfpDdmWarningPortn "on", rm10010mptrapPortNumber "$2", rm10010mptrapBoardNumber "$3"}
		--&MESG        "DDM Warning appears on Client Port $2 of RM10010MP in Slot $3 ($A)"
	DESCRIPTION "Not urgent client default disappeared"
	::= { rm10010mptraps 41 }

rm10010mpClientTrapUrgentGoesOn NOTIFICATION-TYPE
	OBJECTS {rm10010mpAlmSfpDdmAlmPortn, rm10010mptrapPortNumber, rm10010mptrapBoardNumber}
	STATUS current
		--&FILTNAME    "RM10010MP Client Urgent ON"
		--&ACTIONS     { log, major }
		--&MATCH       { rm10010mpAlmSfpDdmAlmPortn "on", rm10010mptrapPortNumber "$2", rm10010mptrapBoardNumber "$3"}
		--&MESG        "DDM Alarm appears on Client Port $2 of RM10010MP in Slot $3 ($A)"
	DESCRIPTION "Urgent client default is activated"
	::= { rm10010mptraps 42 }

rm10010mpClientTrapUrgentGoesOff NOTIFICATION-TYPE
	OBJECTS {rm10010mpAlmSfpDdmAlmPortn, rm10010mptrapPortNumber, rm10010mptrapBoardNumber}
	STATUS current
		--&FILTNAME    "RM10010MP Client Urgent OFF"
		--&ACTIONS     { log, normal }
		--&CLEARS      { "RM10010MP Client Urgent ON" }
		--&MATCH       { rm10010mpAlmSfpDdmAlmPortn "on", rm10010mptrapPortNumber "$2", rm10010mptrapBoardNumber "$3"}
		--&MESG        "DDM Alarm disappears on Client Port $2 of RM10010MP in Slot $3 ($A)"
	DESCRIPTION "Urgent client default disappeared"
	::= { rm10010mptraps 43 }

rm10010mpClientTrapCritGoesOn NOTIFICATION-TYPE
	OBJECTS {rm10010mpAlmFailAccPortn, rm10010mpAlmHwFailAccPortn, rm10010mptrapPortNumber, rm10010mptrapBoardNumber}
	STATUS current
		--&FILTNAME    "RM10010MP Client Fail ON"
		--&ACTIONS     { log, critical }
		--&MATCH       { rm10010mpAlmFailAccPortn "on", rm10010mpAlmHwFailAccPortn "*", rm10010mptrapPortNumber "$3", rm10010mptrapBoardNumber "$4"}
		--&MESG        "Client Port $3 Down on RM10010MP in Slot $4 ($A)"

		--&FILTNAME    "RM10010MP Client HW Fail ON (Hidden)"
		--&ACTIONS     { info }
		--&MATCH       { rm10010mpAlmFailAccPortn "*", rm10010mpAlmHwFailAccPortn "on", rm10010mptrapPortNumber "$3", rm10010mptrapBoardNumber "$4"}
		--&MESG        "Client Port $3 Down on RM10010MP in Slot $4 ($A)"
	DESCRIPTION "Critical client default is activated"
	::= { rm10010mptraps 44 }

rm10010mpClientTrapCritGoesOff NOTIFICATION-TYPE
	OBJECTS {rm10010mpAlmFailAccPortn, rm10010mpAlmHwFailAccPortn, rm10010mptrapPortNumber, rm10010mptrapBoardNumber}
	STATUS current
		--&FILTNAME    "RM10010MP Client Fail OFF"
		--&ACTIONS     { log, normal }
		--&CLEARS      { "RM10010mp Client Fail ON" }
		--&MATCH       { rm10010mpAlmFailAccPortn "on", rm10010mpAlmHwFailAccPortn "*", rm10010mptrapPortNumber "$3", rm10010mptrapBoardNumber "$4"}
		--&MESG        "Client Port $3 Up on RM10010MP in Slot $4 ($A)"

		--&FILTNAME    "RM10010MP Client HW Fail OFF (Hidden)"
		--&ACTIONS     { info }
		--&MATCH       { rm10010mpAlmFailAccPortn "*", rm10010mpAlmHwFailAccPortn "on", rm10010mptrapPortNumber "$3", rm10010mptrapBoardNumber "$4"}
		--&MESG        "Client Port $3 Up on RM10010MP in Slot $4 ($A)"
	DESCRIPTION "Critical client default disappeared"
	::= { rm10010mptraps 45 }






--- *****************************************************
---     HW TRAPS
--- *****************************************************

rm10010mpPowerTrapUrgentGoesOn NOTIFICATION-TYPE
	OBJECTS {rm10010mpAlmDefFuseB, rm10010mpAlmDefFuseA , rm10010mptrapBoardNumber}
	STATUS current
		--&FILTNAME    "RM10010MP Fuse A Fail ON"
		--&ACTIONS     { log, major }
		--&MATCH       { rm10010mpAlmDefFuseB "*", rm10010mpAlmDefFuseA "on", rm10010mptrapBoardNumber "$3"}
		--&MESG        "Power Input A Fail on RM10010MP in Slot $3 ($A)"

		--&FILTNAME    "RM10010MP Fuse B Fail ON"
		--&ACTIONS     { log, major }
		--&MATCH       { rm10010mpAlmDefFuseB "on", rm10010mpAlmDefFuseA "*", rm10010mptrapBoardNumber "$3"}
		--&MESG        "Power Input B Fail on RM10010MP in Slot $3 ($A)"
	DESCRIPTION "Urgent power supply default is activated"
	::= { rm10010mptraps 50 }

rm10010mpPowerTrapUrgentGoesOff NOTIFICATION-TYPE
	OBJECTS {rm10010mpAlmDefFuseB, rm10010mpAlmDefFuseA , rm10010mptrapBoardNumber}
	STATUS current
		--&FILTNAME    "RM10010MP Fuse A&B Fail OFF"
		--&ACTIONS     { log, normal}
		--&CLEARS      { "RM10010MP Fuse A Fail ON", "RM10010MP Fuse B Fail ON" }
		--&MATCH       { rm10010mpAlmDefFuseB "on", rm10010mpAlmDefFuseA "on", rm10010mptrapBoardNumber "$3"}
		--&MESG        "Power Inputs A and B Present on RM10010MP in Slot $3 ($A)"
	DESCRIPTION "Urgent power supply default disappeared"
	::= { rm10010mptraps 51 }






END
