-- ************************************************************************************************
-- FileName    :mpAtmCallCtl.my
-- Description :MultiMedia Platform private MIB
-- Revision History     :
--   Ver.     mark   date
--   04.00    @011  11/15/2000
--
-- ************************************************************************************************
--


MP-ATM-MIB DEFINITIONS ::= BEGIN

   IMPORTS
      mgmt, NetworkAddress, IpAddress, Counter, Gauge, TimeTicks
      FROM RFC1155-SMI

      ifIndex
      FROM RFC1213-MIB

      OBJECT-TYPE
      FROM RFC-1212

--      DisplayString
--      FROM RFC1155-SMI

      TRAP-TYPE
      FROM RFC-1215

		AtmTrafficDescrParamIndex FROM ATM-MIB;

   RowStatus   ::= INTEGER { active(1), notInService(2), notReady(3),
                       createAndGo(4), createAndWait(5), destroy(6) }

   NetPrefix ::= OCTET STRING (SIZE (13))

   DisplayString ::= OCTET STRING

-- The following definition was gotten from rfc1514
   DateAndTime ::= OCTET STRING (SIZE (8 | 11))
-- in OpenView , DateAndTime must be comment   98/12/15 YI
   --        A date-time specification for the local time of day.
   --        This data type is intended to provide a consistent
   --        method of reporting date information.
   --
   --            field  octets  contents                  range
   --            _____  ______  ________                  _____
   --              1      1-2   year                      0..65536
   --                           (in network byte order)
   --              2       3    month                     1..12
   --              3       4    day                       1..31
   --              4       5    hour                      0..23
   --              5       6    minutes                   0..59
   --              6       7    seconds                   0..60
   --                           (use 60 for leap-second)
   --              7       8    deci-seconds              0..9
   --              8       9    direction from UTC        "+" / "-"
   --                           (in ascii notation)
   --              9      10    hours from UTC            0..11
   --             10      11    minutes from UTC          0..59
   --
   --            Note that if only local time is known, then
   --            timezone information (fields 8-10) is not present.

-- The following definition was cadged from the Bridge MIB
      MacAddress ::= OCTET STRING (SIZE (6))
                                                -- a 6 octet address
                                                -- in the
                                                -- "canonical"
                                                -- order
      -- defined by IEEE 802.1a, i.e., as if it were transmitted
      -- least significant bit first, even though 802.5 (in
      -- contrast to other n802.x protocols) requires MAC
      -- addresses to be transmitted most significant bit first.
      --
      -- 16-bit addresses, if needed, are represented by setting
      -- their upper 4 octets to all 0's, i.e., AAFF would be
      -- represented as 00000000AAFF.

-- The following definition is privately defined for Sanfran Private MIB
      PhysAddress ::= OCTET STRING (SIZE (6))


--   nec               OBJECT IDENTIFIER ::= { enterprises 119}

--   necProduct        OBJECT IDENTIFIER ::= { nec 1 }
--   nec-mib           OBJECT IDENTIFIER ::= { nec 2 }
--   necExperimental   OBJECT IDENTIFIER ::= { nec 3 }

--   datax             OBJECT IDENTIFIER ::= { necProduct 3 }
--   ether-sw          OBJECT IDENTIFIER ::= { datax 10 }
--   sf                OBJECT IDENTIFIER ::= { ether-sw 3 }

--   necCommon         OBJECT IDENTIFIER ::= { nec-mib 1 }
--   necFunction       OBJECT IDENTIFIER ::= { nec-mib 2 }
--   necProductDepend  OBJECT IDENTIFIER ::= { nec-mib 3 }

--   datax-mib         OBJECT IDENTIFIER ::= { necProductDepend 3 }
--   ether-sw-mib      OBJECT IDENTIFIER ::= { datax-mib 10 }
--   ether-sw          OBJECT IDENTIFIER ::= { datax 10 }




  org         OBJECT IDENTIFIER     ::= { iso 3 }
  dod         OBJECT IDENTIFIER     ::= { org 6 }
  internet    OBJECT IDENTIFIER     ::= { dod 1 }
  private     OBJECT IDENTIFIER     ::= { internet 4 }
  enterprises OBJECT IDENTIFIER     ::= { private 1 }
  nec               OBJECT IDENTIFIER ::= { enterprises 119}


-- 98/12/15 YI mmpf => mmpf-mib CHG start
-- sysObjectID
   necProduct        OBJECT IDENTIFIER ::= { nec 1 }
   datax             OBJECT IDENTIFIER ::= { necProduct 3 }
   mmpf              OBJECT IDENTIFIER ::= { datax 13 }
   mmn9110           OBJECT IDENTIFIER ::= { mmpf 1 }
   mmn9120           OBJECT IDENTIFIER ::= { mmpf 2 }
-- [sysObjectID]  MM-Node9110/MM-Node9120
--  mmn9110           OBJECT IDENTIFIER ::= { nec necProduct(1) datax(3) mmpf(13) mmn9110(1) }
--  mmn9120           OBJECT IDENTIFIER ::= { nec necProduct(1) datax(3) mmpf(13) mmn9110(2) }


   nec-mib           OBJECT IDENTIFIER ::= { nec 2 }
   necProductDepend  OBJECT IDENTIFIER ::= { nec-mib 3 }
   datax-mib         OBJECT IDENTIFIER ::= { necProductDepend 3 }
   mmpf-mib          OBJECT IDENTIFIER ::= { datax-mib 13 }

   mpSystem                 OBJECT IDENTIFIER ::= { mmpf-mib 1 }
   mpIfCard                 OBJECT IDENTIFIER ::= { mmpf-mib 2 }
   mpEtherPort              OBJECT IDENTIFIER ::= { mmpf-mib 3 }
   mpVlan                   OBJECT IDENTIFIER ::= { mmpf-mib 4 }
   mpBridge                 OBJECT IDENTIFIER ::= { mmpf-mib 5 }
   mpDbAccess               OBJECT IDENTIFIER ::= { mmpf-mib 6 }
   mpEventLog               OBJECT IDENTIFIER ::= { mmpf-mib 7 }
   mpUiSession              OBJECT IDENTIFIER ::= { mmpf-mib 8 }
   mpFtp                    OBJECT IDENTIFIER ::= { mmpf-mib 9 }
   mpDhcp                   OBJECT IDENTIFIER ::= { mmpf-mib 10 }
   mpIp                     OBJECT IDENTIFIER ::= { mmpf-mib 11 }
   mpRip                    OBJECT IDENTIFIER ::= { mmpf-mib 12 }
   mpSnmp                   OBJECT IDENTIFIER ::= { mmpf-mib 13 }
   mpStats                  OBJECT IDENTIFIER ::= { mmpf-mib 14 }
   mpCli                    OBJECT IDENTIFIER ::= { mmpf-mib 15 }
   mpAtm                    OBJECT IDENTIFIER ::= { mmpf-mib 16 }
   mpLis                    OBJECT IDENTIFIER ::= { mmpf-mib 17 }
   mpDns                    OBJECT IDENTIFIER ::= { mmpf-mib 18 }
   mpLec                    OBJECT IDENTIFIER ::= { mmpf-mib 19 }
   mpMpc                    OBJECT IDENTIFIER ::= { mmpf-mib 20 }
   mpStp                    OBJECT IDENTIFIER ::= { mmpf-mib 21 }
   mpLlc                    OBJECT IDENTIFIER ::= { mmpf-mib 22 }
   mpOspf                   OBJECT IDENTIFIER ::= { mmpf-mib 23 }

   mpObsCtl                 OBJECT IDENTIFIER ::= { mmpf-mib 101 }
   mpCardInfo               OBJECT IDENTIFIER ::= { mmpf-mib 102 }
   mpInterface              OBJECT IDENTIFIER ::= { mmpf-mib 103 }
   mpPvoice                 OBJECT IDENTIFIER ::= { mmpf-mib 104 }
-- 98/12/15 YI mmpf => mmpf-mib CHG end

   mpAtmCallCtl             OBJECT IDENTIFIER ::= { mmpf-mib 110 }
   mpCes                    OBJECT IDENTIFIER ::= { mmpf-mib 111 }
   mpIpsw                   OBJECT IDENTIFIER ::= { mmpf-mib 112 }
   mpInsCtl                 OBJECT IDENTIFIER ::= { mmpf-mib 113 }
   mpFfr                    OBJECT IDENTIFIER ::= { mmpf-mib 114 }



AtmAddr ::= OCTET STRING (SIZE(0|8|20))


MpAtmCCCladType ::= INTEGER{ com(1),
                             mux(2),
                             atm-uni(3),
                             atm-trunk(4),
                             atm-uni-vmc(5),
                             lvc(6),
                             ffr(7),
                             odt(8),
                             ces(9),
                             ins(10),
                             sel(11),
                             eth(12),
                             atm-trunk-cdm(13)
                           }



--
-- スカラー型ＭＩＢ
--

        mpAtmCCBaseGroup      OBJECT IDENTIFIER ::= { mpAtmCallCtl 1 }

        mpAtmCCNextTrafficDescrIndex  OBJECT-TYPE
                SYNTAX  AtmTrafficDescrParamIndex
                ACCESS  read-only
                STATUS  mandatory
                DESCRIPTION
                     "A unique value to identify ATM Traffic Descriptor."
--                   ATM Traffic Descriptor IDを得るObject。
                ::= { mpAtmCCBaseGroup 1 }

        mpAtmCCNextNodeVci    OBJECT-TYPE
                SYNTAX  INTEGER
                ACCESS  read-only
                STATUS  mandatory
                DESCRIPTION
                     "A unique value to identify Node VCI."
--                   Node VCIを得るObject。
                ::= { mpAtmCCBaseGroup 2 }


--
--      Ｓｔａｔｉｃ－ＰＶＰ／ＰＶＣ制御
--

        mpAtmCCStaticPVPC     OBJECT IDENTIFIER ::= { mpAtmCallCtl 2 }

--
--      Ｓｔａｔｉｃ－ＰＶＰ制御テーブル
--

        mpAtmCCStaticPvpTable OBJECT-TYPE
                SYNTAX  SEQUENCE OF MpAtmCCStaticPvpEntry
                ACCESS  not-accessible
                STATUS  mandatory
                DESCRIPTION
                        "Static-PVP Table"
                ::= { mpAtmCCStaticPVPC 1 }

        mpAtmCCStaticPvpEntry OBJECT-TYPE
                SYNTAX  MpAtmCCStaticPvpEntry
                ACCESS  not-accessible
                STATUS  mandatory
                DESCRIPTION
                        "Static-PVP Entry"
                INDEX { mpAtmCCStaticPvpIndex,
                        mpAtmCCStaticPvpLowIfIndex,
                        mpAtmCCStaticPvpLowVpi,
                        mpAtmCCStaticPvpHighIfIndex,
                        mpAtmCCStaticPvpHighVpi }
                ::= { mpAtmCCStaticPvpTable 1 }

        MpAtmCCStaticPvpEntry ::=
                SEQUENCE {
                        mpAtmCCStaticPvpIndex         INTEGER,
                        mpAtmCCStaticPvpLowIfIndex    INTEGER,
                        mpAtmCCStaticPvpLowVpi        INTEGER,
                        mpAtmCCStaticPvpHighIfIndex   INTEGER,
                        mpAtmCCStaticPvpHighVpi       INTEGER,
                        mpAtmCCStaticPvpLowReceiveTrafficDescrIndex
                                                AtmTrafficDescrParamIndex,
                        mpAtmCCStaticPvpLowTransmitTrafficDescrIndex
                                                AtmTrafficDescrParamIndex,
                        mpAtmCCStaticPvpHighReceiveTrafficDescrIndex
                                                AtmTrafficDescrParamIndex,
                        mpAtmCCStaticPvpHighTransmitTrafficDescrIndex
                                                AtmTrafficDescrParamIndex,
                        mpAtmCCStaticPvpPriority      INTEGER,
                        mpAtmCCStaticPvpLowCladType   MpAtmCCCladType,
                        mpAtmCCStaticPvpHighCladType  MpAtmCCCladType,
                        mpAtmCCStaticPvpAdminStatus   INTEGER,
                        mpAtmCCStaticPvpOperStatus    INTEGER,
                        mpAtmCCStaticPvpPvpId         INTEGER,
                        mpAtmCCStaticPvpSeqNo         INTEGER,
                        mpAtmCCStaticPvpPgcRequest    INTEGER,    -- @007 追加
                        mpAtmCCStaticPvpCfgStatus     INTEGER,
                        mpAtmCCStaticPvpErrInfo       INTEGER
                        }

        mpAtmCCStaticPvpIndex OBJECT-TYPE
                SYNTAX  INTEGER(1..2147483647)                    -- @001 修正
--              SYNTAX  INTEGER(1)
                ACCESS  not-accessible
                STATUS  mandatory
                DESCRIPTION
                        "A unique value to identify this Static-PVP.
                        The value is used only 1 (p2p)."
--                        Static-PVP識別子。Point to Pointでは1固定
                ::= { mpAtmCCStaticPvpEntry 1 }

        mpAtmCCStaticPvpLowIfIndex    OBJECT-TYPE
                SYNTAX  INTEGER
                ACCESS  not-accessible
                STATUS  mandatory
                DESCRIPTION
                     "The value of this object is equal to MIB II's
                      ifIndex value of the ATM interface port for this
                      Static-PVP."
--                      Low側ATM Port。MIB2のifIndex相当。
                ::= { mpAtmCCStaticPvpEntry 2 }

        mpAtmCCStaticPvpLowVpi        OBJECT-TYPE
                SYNTAX  INTEGER(0..4095)
                ACCESS  not-accessible
                STATUS  mandatory
                DESCRIPTION
                     "The value of this object is equal to the VPI
                      value at the ATM interface associated with
                      the Static-PVP that is identified by
                      mpAtmCCStaticPvcLowIfIndex.
                      The VPI value cannot exceed the number
                      supported by the atmInterfaceMaxVpiBits
                      at the low ATM interface port."
--                      mpAtmCCStaticPvcLowIfIndexによって識別される
--                      Static-PVPのATMインタフェースでのVPI値。
--                      Low ATM PortのatmInterfaceMaxVpiBitsにサポート
--                      される値を越えない。
                ::= { mpAtmCCStaticPvpEntry 3 }

        mpAtmCCStaticPvpHighIfIndex   OBJECT-TYPE
                SYNTAX  INTEGER
                ACCESS  not-accessible
                STATUS  mandatory
                DESCRIPTION
                     "The value of this object is equal to MIB II's
                      ifIndex value for the ATM interface port for
                      this static-PVP."
--                      High側ATM Port。MIB2のifIndex相当。
                ::= { mpAtmCCStaticPvpEntry 4 }

        mpAtmCCStaticPvpHighVpi       OBJECT-TYPE
                SYNTAX  INTEGER(0..4095)
                ACCESS  not-accessible
                STATUS  mandatory
                DESCRIPTION
                     "The value of this object is equal to the VPI
                      value at the ATM interface
                      associated with the Static-PVP that is
                      identified by mpAtmCCStaticPvcHighIfIndex.
                      The VPI value cannot exceed
                      the number supported by the atmInterfaceMaxVpiBits
                      at the high ATM interface port."
--                      mpAtmCCStaticPvcLowIfIndexによって識別されるStatic
--                      -PVPのATMインタフェースでのVPI値。
--                      High ATM PortのatmInterfaceMaxVpiBitsにサポート
--                      される値を越えない。
                ::= { mpAtmCCStaticPvpEntry 5 }

        mpAtmCCStaticPvpLowReceiveTrafficDescrIndex   OBJECT-TYPE
                SYNTAX  AtmTrafficDescrParamIndex
                ACCESS  read-write
                STATUS  mandatory
                DESCRIPTION
                     "The value of this object identifies
                      in the ATM Traffic Descriptor Table which
                      applies to the receive direction of this Static-PVP."
--                      Static-PVPのLow-受け側ATM Traffic Descriptor識別子。
                ::= { mpAtmCCStaticPvpEntry 6 }

        mpAtmCCStaticPvpLowTransmitTrafficDescrIndex  OBJECT-TYPE
                SYNTAX  AtmTrafficDescrParamIndex
                ACCESS  read-write
                STATUS  mandatory
                DESCRIPTION
                     "The value of this object identifies
                      in the ATM Traffic Descriptor Table which
                      applies to the transmit direction of this Static-PVP."
--                      Static-PVPのLow-送り側ATM Traffic Descriptor識別子。
                ::= { mpAtmCCStaticPvpEntry 7 }

        mpAtmCCStaticPvpHighReceiveTrafficDescrIndex  OBJECT-TYPE
                SYNTAX  AtmTrafficDescrParamIndex
                ACCESS  read-write
                STATUS  mandatory
                DESCRIPTION
                     "The value of this object identifies
                      in the ATM Traffic Descriptor Table which
                      applies to the receive direction of this Static-PVP."
--                      Static-PVPのHigh-受け側ATM Traffic Descriptor識別子。
                ::= { mpAtmCCStaticPvpEntry 8 }

        mpAtmCCStaticPvpHighTransmitTrafficDescrIndex OBJECT-TYPE
                SYNTAX  AtmTrafficDescrParamIndex
                ACCESS  read-write
                STATUS  mandatory
                DESCRIPTION
                     "The value of this object identifies
                      in the ATM Traffic Descriptor Table which
                      applies to the transmit direction of this Static-PVP."
--                      Static-PVPのHigh-送り側ATM Traffic Descriptor識別子。
                ::= { mpAtmCCStaticPvpEntry 9 }

        mpAtmCCStaticPvpPriority      OBJECT-TYPE
                SYNTAX  INTEGER(1..3)                               -- @001 修正
                ACCESS  read-write
                STATUS  mandatory
                DESCRIPTION
                     "Connection priority"
--                     Static-PVPの優先度
                DEFVAL { 1 }                                        -- @001 修正
                ::= { mpAtmCCStaticPvpEntry 10 }

        mpAtmCCStaticPvpLowCladType      OBJECT-TYPE
                SYNTAX  MpAtmCCCladType
                ACCESS  read-only
                STATUS  mandatory
                DESCRIPTION
                     "CLAD Type"
--                     CLAD種別
                ::= { mpAtmCCStaticPvpEntry 11 }

        mpAtmCCStaticPvpHighCladType      OBJECT-TYPE
                SYNTAX  MpAtmCCCladType
                ACCESS  read-only
                STATUS  mandatory
                DESCRIPTION
                     "CLAD Type"
--                     CLAD種別
                ::= { mpAtmCCStaticPvpEntry 12 }

        mpAtmCCStaticPvpAdminStatus   OBJECT-TYPE
                SYNTAX  INTEGER {
                                up(1),
                                down(2)
                                }
                ACCESS  read-write
                STATUS  mandatory
                DESCRIPTION
                     "The value of this object identifies the desired
                      administrative status of this Static-PVP.
                      The up and down states indicate that the traffic
                      flow is enabled and disabled respectively on this
                      Static-PVP."
--                      Static-PVPのAdmin Status。up/down = 送受信enable/disable
                DEFVAL { down }
                ::= { mpAtmCCStaticPvpEntry 13 }

        mpAtmCCStaticPvpOperStatus    OBJECT-TYPE
                SYNTAX  INTEGER
                ACCESS  read-only
                STATUS  mandatory
                DESCRIPTION
                     "The value of this object identifies the desired
                      operational status of this Static-PVP."
--                     Static-PVPのOper Status。up/down = 送受信enable/disable
                ::= { mpAtmCCStaticPvpEntry 14 }

        mpAtmCCStaticPvpPvpId      OBJECT-TYPE
                SYNTAX  INTEGER
                ACCESS  read-write
                STATUS  mandatory
                DESCRIPTION
                     "The value of this object identifies the desired
                      cross connection."
--                    End-to-End PVP を構成する CrossConnection で共通のID
--              DEFVAL { 0 }
                ::= { mpAtmCCStaticPvpEntry 15 }

        mpAtmCCStaticPvpSeqNo      OBJECT-TYPE
                SYNTAX  INTEGER
                ACCESS  read-write
                STATUS  mandatory
                DESCRIPTION
                     "Order information in the cross connection."
--                     End-to-End PVP を構成する CrossConnection での順序情報
--              DEFVAL { 0 }
                ::= { mpAtmCCStaticPvpEntry 16 }


        mpAtmCCStaticPvpPgcRequest      OBJECT-TYPE             -- @007追加
                SYNTAX  INTEGER
                ACCESS  read-only
                STATUS  mandatory
                DESCRIPTION
                     "Indicates whether this PVP was configureated from
                      the PVC-Group-Cutover function.
                      The value of '0' indicates that this PVP was normal.
                      The value of '!=0' indicates that this PVP was
                      configrated form PVC-Group-Cutover function.
                       In this case, the value was indicated the PVC-Group Number"
--                     PVCグループ切り替えリクエスト表示
--                       ０：PVC登録
--                     ≠０：PVCグループ番号
                ::= { mpAtmCCStaticPvpEntry 17 }


        mpAtmCCStaticPvpCfgStatus  OBJECT-TYPE
                SYNTAX  INTEGER {
                                enable(1),
                                cancel(2),
                                delete(3),
                                unknown(4)
                                }
                ACCESS  read-write
                STATUS  mandatory
                DESCRIPTION
                        "Configuration setting start object. If this object is
                         set the setting of the configuration is started."
--                        ConfigSet開始設定
                DEFVAL { unknown }
                ::= { mpAtmCCStaticPvpEntry 98 }

        mpAtmCCStaticPvpErrInfo    OBJECT-TYPE
                SYNTAX  INTEGER
                ACCESS  read-only
                STATUS  mandatory
                DESCRIPTION
                        "Object that the configuration setting result is set up."
--                        Config設定結果
                ::= { mpAtmCCStaticPvpEntry 99 }


--
--      Ｓｔａｔｉｃ－ＰＶＣ制御テーブル
--

        mpAtmCCStaticPvcTable OBJECT-TYPE
                SYNTAX  SEQUENCE OF MpAtmCCStaticPvcEntry
                ACCESS  not-accessible
                STATUS  mandatory
                DESCRIPTION
                        "Static-PVC Table"
                ::= { mpAtmCCStaticPVPC 2 }

        mpAtmCCStaticPvcEntry OBJECT-TYPE
                SYNTAX  MpAtmCCStaticPvcEntry
                ACCESS  not-accessible
                STATUS  mandatory
                DESCRIPTION
                        "Static-PVC Entry"
                INDEX { mpAtmCCStaticPvcIndex,
                        mpAtmCCStaticPvcLowIfIndex,
                        mpAtmCCStaticPvcLowVpi,
                        mpAtmCCStaticPvcLowVci,
                        mpAtmCCStaticPvcHighIfIndex,
                        mpAtmCCStaticPvcHighVpi,
                        mpAtmCCStaticPvcHighVci }
                ::= { mpAtmCCStaticPvcTable 1 }

        MpAtmCCStaticPvcEntry ::=
                SEQUENCE {
                        mpAtmCCStaticPvcIndex         INTEGER,
                        mpAtmCCStaticPvcLowIfIndex    INTEGER,
                        mpAtmCCStaticPvcLowVpi        INTEGER,
                        mpAtmCCStaticPvcLowVci        INTEGER,
                        mpAtmCCStaticPvcHighIfIndex   INTEGER,
                        mpAtmCCStaticPvcHighVpi       INTEGER,
                        mpAtmCCStaticPvcHighVci       INTEGER,
                        mpAtmCCStaticPvcLowReceiveTrafficDescrIndex
                                                AtmTrafficDescrParamIndex,
                        mpAtmCCStaticPvcLowTransmitTrafficDescrIndex
                                                AtmTrafficDescrParamIndex,
                        mpAtmCCStaticPvcHighReceiveTrafficDescrIndex
                                                AtmTrafficDescrParamIndex,
                        mpAtmCCStaticPvcHighTransmitTrafficDescrIndex
                                                AtmTrafficDescrParamIndex,
                        mpAtmCCStaticPvcPriority      INTEGER,
                        mpAtmCCStaticPvcLowCladType   MpAtmCCCladType,
                        mpAtmCCStaticPvcHighCladType  MpAtmCCCladType,
                        mpAtmCCStaticPvcAdminStatus   INTEGER,
                        mpAtmCCStaticPvcOperStatus    INTEGER,
                        mpAtmCCStaticPvcPvcId         INTEGER,
                        mpAtmCCStaticPvcSeqNo         INTEGER,
                        mpAtmCCStaticPvcPgcRequest    INTEGER,      -- @007 追加
                        mpAtmCCStaticPvcCfgStatus     INTEGER,
                        mpAtmCCStaticPvcErrInfo       INTEGER
                        }

        mpAtmCCStaticPvcIndex OBJECT-TYPE
                SYNTAX  INTEGER(1..2147483647)                      -- @001 修正
--              SYNTAX  INTEGER(1)                                     @001 修正
                ACCESS  not-accessible
                STATUS  mandatory
                DESCRIPTION
                        "A unique value to identify this Static-PVC.
                        The value is used only 1 (p2p)."
--                        Static-PVC識別子。Point to Pointならば１固定
                ::= { mpAtmCCStaticPvcEntry 1 }

        mpAtmCCStaticPvcLowIfIndex    OBJECT-TYPE
                SYNTAX  INTEGER
                ACCESS  not-accessible
                STATUS  mandatory
                DESCRIPTION
                     "The value of this object is equal to MIB II's
                      ifIndex value of the ATM interface port for this
                      Static-PVC."
--                      Low側ATM Port。MIB2のifIndex相当。
                ::= { mpAtmCCStaticPvcEntry 2 }

        mpAtmCCStaticPvcLowVpi        OBJECT-TYPE
                SYNTAX  INTEGER(0..4095)
                ACCESS  not-accessible
                STATUS  mandatory
                DESCRIPTION
                     "The value of this object is equal to the VPI
                      value at the ATM interface associated with
                      the Static-PVC that is identified by
                      mpAtmCCStaticPvcLowIfIndex.
                      The VPI value cannot exceed the number
                      supported by the atmInterfaceMaxVpiBits
                      at the low ATM interface port."
--                    Low側VPI値。Low側ATM PortのatmInterfaceMaxVpiBits
--                    を越えることはない
                ::= { mpAtmCCStaticPvcEntry 3 }

        mpAtmCCStaticPvcLowVci        OBJECT-TYPE
                SYNTAX  INTEGER(0..65535)
                ACCESS  not-accessible
                STATUS  mandatory
                DESCRIPTION
                     "The value of this object is equal to the VCI
                      value at the ATM interface
                      associated with this Static-PVC that is
                      identified by mpAtmCCStaticPvcLowIfIndex.
                      The VCI value cannot exceed the number
                      supported by the atmInterfaceMaxVciBits
                      at the low ATM interface port."
--                    Low側VCI。Low側ATM PortのatmInterfaceMaxVciBits
--                    を越えることはない。
                ::= { mpAtmCCStaticPvcEntry 4 }

        mpAtmCCStaticPvcHighIfIndex   OBJECT-TYPE
                SYNTAX  INTEGER
                ACCESS  not-accessible
                STATUS  mandatory
                DESCRIPTION
                     "The value of this object is equal to MIB II's
                      ifIndex value for the ATM interface port for
                      this static-PVC."
--                      High側ATM Port。MIB2のifIndex相当。
                ::= { mpAtmCCStaticPvcEntry 5 }

        mpAtmCCStaticPvcHighVpi       OBJECT-TYPE
                SYNTAX  INTEGER(0..4095)
                ACCESS  not-accessible
                STATUS  mandatory
                DESCRIPTION
                     "The value of this object is equal to the VPI
                      value at the ATM interface
                      associated with the Static-PVC that is
                      identified by mpAtmCCStaticPvcHighIfIndex.
                      The VPI value cannot exceed
                      the number supported by the atmInterfaceMaxVpiBits
                      at the high ATM interface port."
--                    High側VPI値。High側ATM PortのatmInterfaceMaxVpiBits
--                    を越えることはない
                ::= { mpAtmCCStaticPvcEntry 6 }

        mpAtmCCStaticPvcHighVci       OBJECT-TYPE
                SYNTAX  INTEGER(0..65535)
                ACCESS  not-accessible
                STATUS  mandatory
                DESCRIPTION
                     "The value of this object is equal to the VCI
                      value at the ATM interface
                      associated with the static-PVC that is
                      identified by mpAtmCCStaticPvcHighIfIndex.
                      The VCI value cannot exceed
                      the number supported by the atmInterfaceMaxVciBits
                      at the high ATM interface port."
--                    High側VCI値。High側ATM PortのatmInterfaceMaxVciBits
--                   を越えることはない
                ::= { mpAtmCCStaticPvcEntry 7 }

        mpAtmCCStaticPvcLowReceiveTrafficDescrIndex   OBJECT-TYPE
                SYNTAX  AtmTrafficDescrParamIndex
                ACCESS  read-write
                STATUS  mandatory
                DESCRIPTION
                     "The value of this object identifies
                      in the ATM Traffic Descriptor Table which
                      applies to the receive direction of this Static-PVC."
--                      Static-PVCのLow受け側ATM Traffic Descriptor識別子。
                ::= { mpAtmCCStaticPvcEntry 8 }

        mpAtmCCStaticPvcLowTransmitTrafficDescrIndex  OBJECT-TYPE
                SYNTAX  AtmTrafficDescrParamIndex
                ACCESS  read-write
                STATUS  mandatory
                DESCRIPTION
                     "The value of this object identifies
                      in the ATM Traffic Descriptor Table which
                      applies to the transmit direction of this Static-PVC."
--                      Static-PVCのLow送り側ATM Traffic Descriptor識別子。
                ::= { mpAtmCCStaticPvcEntry 9 }

        mpAtmCCStaticPvcHighReceiveTrafficDescrIndex  OBJECT-TYPE
                SYNTAX  AtmTrafficDescrParamIndex
                ACCESS  read-write
                STATUS  mandatory
                DESCRIPTION
                     "The value of this object identifies
                      in the ATM Traffic Descriptor Table which
                      applies to the receive direction of this Static-PVC."
--                      Static-PVCのHigh受け側ATM Traffic Descriptor識別子。
                ::= { mpAtmCCStaticPvcEntry 10 }

        mpAtmCCStaticPvcHighTransmitTrafficDescrIndex OBJECT-TYPE
                SYNTAX  AtmTrafficDescrParamIndex
                ACCESS  read-write
                STATUS  mandatory
                DESCRIPTION
                     "The value of this object identifies
                      in the ATM Traffic Descriptor Table which
                      applies to the transmit direction of this Static-PVC."
--                      Static-PVCのHigh送り側ATM Traffic Descriptor識別子。
                ::= { mpAtmCCStaticPvcEntry 11 }

        mpAtmCCStaticPvcPriority      OBJECT-TYPE
                SYNTAX  INTEGER(1..3)                               -- @001 修正
                ACCESS  read-write
                STATUS  mandatory
                DESCRIPTION
                     "Connection priority"
--                     PVC優先度
                DEFVAL { 1 }                                        -- @001 修正
                ::= { mpAtmCCStaticPvcEntry 12 }

        mpAtmCCStaticPvcLowCladType      OBJECT-TYPE
                SYNTAX  MpAtmCCCladType
                ACCESS  read-only
                STATUS  mandatory
                DESCRIPTION
                     "CLAD Type"
--                     CLAD種別
                ::= { mpAtmCCStaticPvcEntry 13 }

        mpAtmCCStaticPvcHighCladType      OBJECT-TYPE
                SYNTAX  MpAtmCCCladType
                ACCESS  read-only
                STATUS  mandatory
                DESCRIPTION
                     "CLAD Type"
--                     CLAD種別
                ::= { mpAtmCCStaticPvcEntry 14 }

        mpAtmCCStaticPvcAdminStatus   OBJECT-TYPE
                SYNTAX  INTEGER {
                                up(1),
                                down(2)
                                }
                ACCESS  read-write
                STATUS  mandatory
                DESCRIPTION
                     "The value of this object identifies the desired
                      administrative status of this Static-PVC.
                      The up and down states indicate that the traffic
                      flow is enabled and disabled respectively on this
                      Static-PVC."
--                      Static-PVCのAdmin Status。up/down = 送受信enable/disable
                DEFVAL { down }
                ::= { mpAtmCCStaticPvcEntry 15 }

        mpAtmCCStaticPvcOperStatus    OBJECT-TYPE
                SYNTAX  INTEGER
                ACCESS  read-only
                STATUS  mandatory
                DESCRIPTION
                     "The value of this object identifies the desired
                      operational status of this Static-PVC."
--                    Static-PVCのOper Status。up/down = 送受信enable/disable
                ::= { mpAtmCCStaticPvcEntry 16 }

        mpAtmCCStaticPvcPvcId      OBJECT-TYPE
                SYNTAX  INTEGER
                ACCESS  read-write
                STATUS  mandatory
                DESCRIPTION
                     "The value of this object identifies the desired
                      cross connection."
--                    End-to-End PVC を構成する CrossConnection で共通のID
--              DEFVAL { 0 }
                ::= { mpAtmCCStaticPvcEntry 17 }

        mpAtmCCStaticPvcSeqNo      OBJECT-TYPE
                SYNTAX  INTEGER
                ACCESS  read-write
                STATUS  mandatory
                DESCRIPTION
                     "Order information in the cross connection."
--                     End-to-End PVC を構成する CrossConnection での順序情報
--              DEFVAL { 0 }
                ::= { mpAtmCCStaticPvcEntry 18 }


        mpAtmCCStaticPvcPgcRequest      OBJECT-TYPE             -- @007追加
                SYNTAX  INTEGER
                ACCESS  read-only
                STATUS  mandatory
                DESCRIPTION
                     "Indicates whether this PVP was configureated from
                      the PVC-Group-Cutover function.
                      The value of '0' indicates that this PVP was normal.
                      The value of '!=0' indicates that this PVP was
                      configrated form PVC-Group-Cutover function.
                       In this case, the value was indicated the PVC-Group Number"
--                     PVCグループ切り替えリクエスト表示
--                       ０：PVC登録
--                     ≠０：PVCグループ番号
                ::= { mpAtmCCStaticPvcEntry 19 }


        mpAtmCCStaticPvcCfgStatus  OBJECT-TYPE
                SYNTAX  INTEGER {
                                enable(1),
                                cancel(2),
                                delete(3),
                                unknown(4)
                                }
                ACCESS  read-write
                STATUS  mandatory
                DESCRIPTION
                        "Configuration setting start object. If this object is
                         set the setting of the configuration is started."
--                        ConfigSet開始設定
                DEFVAL { unknown }
                ::= { mpAtmCCStaticPvcEntry 98 }

        mpAtmCCStaticPvcErrInfo        OBJECT-TYPE
                SYNTAX  INTEGER
                ACCESS  read-only
                STATUS  mandatory
                DESCRIPTION
                        "Object that the configuration setting result is set up."
--                        Config設定結果
                ::= { mpAtmCCStaticPvcEntry 99 }




--
-- Ｓｏｆｔ－ＰＶＰ／ＰＶＣ制御
--

        mpAtmCCSoftPVPC       OBJECT IDENTIFIER ::= { mpAtmCallCtl 3 }

--
-- Ｓｏｆｔ－ＰＶＰ／ＰＶＣ発側制御
--

--
-- Ｓｏｆｔ－ＰＶＰ発側制御テーブル
--

        mpAtmCCSoftPvpTable   OBJECT-TYPE
                SYNTAX  SEQUENCE OF MpAtmCCSoftPvpEntry
                ACCESS  not-accessible
                STATUS  mandatory
                DESCRIPTION
                        "Soft-PVP(Calling) Table"
                ::= { mpAtmCCSoftPVPC 1 }

        mpAtmCCSoftPvpEntry   OBJECT-TYPE
                SYNTAX  MpAtmCCSoftPvpEntry
                ACCESS  not-accessible
                STATUS  mandatory
                DESCRIPTION
                        "Soft-PVP(Calling) Entry"
                INDEX { mpAtmCCSoftPvpLeafReference,
                        mpAtmCCSoftPvpIfIndex,
                        mpAtmCCSoftPvpVpi
                }
                ::= { mpAtmCCSoftPvpTable 1 }

        MpAtmCCSoftPvpEntry ::=
                SEQUENCE {
                        mpAtmCCSoftPvpLeafReference   INTEGER,
                        mpAtmCCSoftPvpIfIndex         INTEGER,
                        mpAtmCCSoftPvpVpi             INTEGER,
                        mpAtmCCSoftPvpReceiveTrafficDescrIndex
                                                AtmTrafficDescrParamIndex,
                        mpAtmCCSoftPvpTransmitTrafficDescrIndex
                                                AtmTrafficDescrParamIndex,
                        mpAtmCCSoftPvpTargetAddress   AtmAddr,
                        mpAtmCCSoftPvpTargetVpi       INTEGER,
                        mpAtmCCSoftPvpLastReleaseCause INTEGER,
                        mpAtmCCSoftPvpLastReleaseDiagnostic
                                                OCTET STRING,
                        mpAtmCCSoftPvpPriority        INTEGER,
                        mpAtmCCSoftPvpCladType        MpAtmCCCladType,
                        mpAtmCCSoftPvpOriginalAddress AtmAddr,
                        mpAtmCCSoftPvpAdminStatus     INTEGER,
                        mpAtmCCSoftPvpOperStatus      INTEGER,
                        mpAtmCCSoftPvpPgcRequest      INTEGER,      -- @007 追加
                        mpAtmCCSoftPvpCfgStatus       INTEGER,
                        mpAtmCCSoftPvpErrInfo         INTEGER
                        }

        mpAtmCCSoftPvpLeafReference   OBJECT-TYPE
                SYNTAX  INTEGER(1..65535)                           -- @001 修正
--              SYNTAX  INTEGER(1)                                     @001 修正
                ACCESS  not-accessible
                STATUS  mandatory
                DESCRIPTION
                        "A unique value to identify this Soft-PVP.
                        The value is used only 1 (p2p)."
--                        Soft-PVP識別子。Point to Point時は１固定。
                ::= { mpAtmCCSoftPvpEntry 1 }

        mpAtmCCSoftPvpIfIndex OBJECT-TYPE
                SYNTAX  INTEGER
                ACCESS  not-accessible
                STATUS  mandatory
                DESCRIPTION
                     "The value of this object is equal to MIB II's
                      ifIndex value of the ATM interface port for this
                      Soft-PVP."
--                      ATM Port。MIB2のifIndex相当。
                ::= { mpAtmCCSoftPvpEntry 2 }

        mpAtmCCSoftPvpVpi     OBJECT-TYPE
                SYNTAX  INTEGER
                ACCESS  not-accessible
                STATUS  mandatory
                DESCRIPTION
                     "The value of this object is equal to the VPI
                      value at the ATM interface associated with
                      the Soft-PVP that is identified by
                      mpAtmCCSoftPvpIfIndex.
                      The VPI value cannot exceed the number
                      supported by the atmInterfaceMaxVpiBits
                      at the ATM interface port."
--                    mpAtmCCSoftPvpIfIndexで識別されるSoft-PVPのVPI値
--                    atmInterfaceMaxVpiBitsの有効範囲は越えない。
                ::= { mpAtmCCSoftPvpEntry 3 }

        mpAtmCCSoftPvpReceiveTrafficDescrIndex        OBJECT-TYPE
                SYNTAX  AtmTrafficDescrParamIndex
                ACCESS  read-write
                STATUS  mandatory
                DESCRIPTION
                     "The value of this object identifies
                      in the ATM Traffic Descriptor Table which
                      applies to the receive direction of this Soft-PVP."
--                      Soft-PVPの受け側ATM Traffic Descriptor識別子。
                ::= { mpAtmCCSoftPvpEntry 4 }

        mpAtmCCSoftPvpTransmitTrafficDescrIndex       OBJECT-TYPE
                SYNTAX  AtmTrafficDescrParamIndex
                ACCESS  read-write
                STATUS  mandatory
                DESCRIPTION
                     "The value of this object identifies
                      in the ATM Traffic Descriptor Table which
                      applies to the transmit direction of this Soft-PVP."
--                      Soft-PVPの送り側ATM Traffic Descriptor識別子。
                ::= { mpAtmCCSoftPvpEntry 5 }

        mpAtmCCSoftPvpTargetAddress   OBJECT-TYPE
                SYNTAX  AtmAddr
                ACCESS  read-write
                STATUS  mandatory
                DESCRIPTION
                        "The target ATM Address of this Soft-PVP.  If no
                        address is supplied, no attempts to establish the
                        Soft-PVP are initiated."
--                        Soft-PVPの宛て先アドレス
                ::= { mpAtmCCSoftPvpEntry 6 }

        mpAtmCCSoftPvpTargetVpi       OBJECT-TYPE
                SYNTAX  INTEGER (0..4095)
                ACCESS  read-write
                STATUS  mandatory
                DESCRIPTION
                        "The VPI value of the VCL used at the target interface."
--                        宛て先のVPI。
                DEFVAL { 0 }
                ::= { mpAtmCCSoftPvpEntry 7 }

        mpAtmCCSoftPvpLastReleaseCause        OBJECT-TYPE
                SYNTAX  INTEGER(1..127)
                ACCESS  read-only
                STATUS  mandatory
                DESCRIPTION
                        "Value of the Cause field of the Cause
                        Information Element in the last RELEASE
                        signalling message received for this Soft-PVP.
                        Indicates the reason for the Release."
--                        切断理由
                ::= { mpAtmCCSoftPvpEntry 8 }

        mpAtmCCSoftPvpLastReleaseDiagnostic   OBJECT-TYPE
                SYNTAX  OCTET STRING (SIZE(0..8))
                ACCESS  read-only
                STATUS  mandatory
                DESCRIPTION
                        "Value of the first 8 bytes of diagnostic information
                        from the Cause field of the Cause Information Element
                        in the last RELEASE signalling message received for
                        this Soft-PVP."
--                        切断診断結果
                ::= { mpAtmCCSoftPvpEntry 9 }

        mpAtmCCSoftPvpPriority        OBJECT-TYPE
                SYNTAX  INTEGER(1..3)                               -- @001 修正
                ACCESS  read-write
                STATUS  mandatory
                DESCRIPTION
                     "Connection priority"
--                        Soft-PVP優先度
                DEFVAL { 1 }                                        -- @001 修正
                ::= { mpAtmCCSoftPvpEntry 10 }

        mpAtmCCSoftPvpCladType        OBJECT-TYPE
                SYNTAX  MpAtmCCCladType
                ACCESS  read-only
                STATUS  mandatory
                DESCRIPTION
                     "CLAD Type"
--                     CLAD種別
                ::= { mpAtmCCSoftPvpEntry 11 }

        mpAtmCCSoftPvpOriginalAddress   OBJECT-TYPE
                SYNTAX  AtmAddr
                ACCESS  read-only
                STATUS  mandatory
                DESCRIPTION
                        "The original ATM Address of this Soft-PVP.  If no
                        address is supplied, no attempts to establish the
                        Soft-PVP are initiated."
--                        自ＡＴＭアドレス
                ::= { mpAtmCCSoftPvpEntry 12 }

        mpAtmCCSoftPvpAdminStatus     OBJECT-TYPE
                SYNTAX  INTEGER {
                                up(1),
                                down(2)
                                }
                ACCESS  read-write
                STATUS  mandatory
                DESCRIPTION
                     "The value of this object identifies the desired
                      administrative status of this Soft-PVP.
                      The up and down states indicate that the traffic
                      flow is enabled and disabled respectively on this
                      Soft-PVP."
--                      Soft-PVPのAdmin Status。up/down = 送受信enable/disable
                DEFVAL { down }
                ::= { mpAtmCCSoftPvpEntry 13 }

        mpAtmCCSoftPvpOperStatus      OBJECT-TYPE
                SYNTAX  INTEGER
                ACCESS  read-only
                STATUS  mandatory
                DESCRIPTION
                     "Soft-PVPのOper Status。up/down = 送受信enable/disable"
                --      Soft-PVPの接続状態を表示する。
                --      機能ブロックが認識している状態を値の桁を変え反映している
                --              １桁目　　：up/down   1/2
                --              ２～３桁目：ATM呼制御が認識している状態
                --              ４～５桁目：シグナリング制御が認識している状態
                ::= { mpAtmCCSoftPvpEntry 14 }

        mpAtmCCSoftPvpPgcRequest      OBJECT-TYPE             -- @007追加
                SYNTAX  INTEGER
                ACCESS  read-only
                STATUS  mandatory
                DESCRIPTION
                     "Indicates whether this PVP was configureated from
                      the PVC-Group-Cutover function.
                      The value of '0' indicates that this PVP was normal.
                      The value of '!=0' indicates that this PVP was
                      configrated form PVC-Group-Cutover function.
                       In this case, the value was indicated the PVC-Group Number"
--                     PVCグループ切り替えリクエスト表示
--                       ０：PVC登録
--                     ≠０：PVCグループ番号
                ::= { mpAtmCCSoftPvpEntry 15 }

        mpAtmCCSoftPvpCfgStatus    OBJECT-TYPE
                SYNTAX  INTEGER {
                                enable(1),
                                cancel(2),
                                delete(3),
                                unknown(4)
                                }
                ACCESS  read-write
                STATUS  mandatory
                DESCRIPTION
                        "Configuration setting start object. If this object is
                         set the setting of the configuration is started."
--                        ConfigSet開始設定
                DEFVAL { unknown }
                ::= { mpAtmCCSoftPvpEntry 98 }

        mpAtmCCSoftPvpErrInfo          OBJECT-TYPE
                SYNTAX  INTEGER
                ACCESS  read-only
                STATUS  mandatory
                DESCRIPTION
                        "Object that the configuration setting result is set up."
--                        Config設定結果
                ::= { mpAtmCCSoftPvpEntry 99 }


--
-- Ｓｏｆｔ－ＰＶＣ発側制御テーブル
--

        mpAtmCCSoftPvcTable   OBJECT-TYPE
                SYNTAX  SEQUENCE OF MpAtmCCSoftPvcEntry
                ACCESS  not-accessible
                STATUS  mandatory
                DESCRIPTION
                        "Soft-PVC(Calling) Table"
                ::= { mpAtmCCSoftPVPC 2 }

        mpAtmCCSoftPvcEntry   OBJECT-TYPE
                SYNTAX  MpAtmCCSoftPvcEntry
                ACCESS  not-accessible
                STATUS  mandatory
                DESCRIPTION
                        "Soft-PVC(Calling) Entry"
                INDEX { mpAtmCCSoftPvcLeafReference,
                        mpAtmCCSoftPvcIfIndex,
                        mpAtmCCSoftPvcVpi,
                        mpAtmCCSoftPvcVci
                }
                ::= { mpAtmCCSoftPvcTable 1 }

        MpAtmCCSoftPvcEntry ::=
                SEQUENCE {
                        mpAtmCCSoftPvcLeafReference   INTEGER,
                        mpAtmCCSoftPvcIfIndex         INTEGER,
                        mpAtmCCSoftPvcVpi             INTEGER,
                        mpAtmCCSoftPvcVci             INTEGER,
                        mpAtmCCSoftPvcReceiveTrafficDescrIndex
                                                AtmTrafficDescrParamIndex,
                        mpAtmCCSoftPvcTransmitTrafficDescrIndex
                                                AtmTrafficDescrParamIndex,
                        mpAtmCCSoftPvcTargetAddress   AtmAddr,
                        mpAtmCCSoftPvcTargetVpi       INTEGER,
                        mpAtmCCSoftPvcTargetVci       INTEGER,
                        mpAtmCCSoftPvcLastReleaseCause INTEGER,
                        mpAtmCCSoftPvcLastReleaseDiagnostic
                                                OCTET STRING,
                        mpAtmCCSoftPvcPriority        INTEGER,
                        mpAtmCCSoftPvcCladType        MpAtmCCCladType,
                        mpAtmCCSoftPvcOriginalAddress AtmAddr,
                        mpAtmCCSoftPvcAdminStatus     INTEGER,
                        mpAtmCCSoftPvcOperStatus      INTEGER,
                        mpAtmCCSoftPvcPgcRequest      INTEGER,      -- @007 追加
                        mpAtmCCSoftPvcCfgStatus       INTEGER,
                        mpAtmCCSoftPvcErrInfo         INTEGER
                        }

        mpAtmCCSoftPvcLeafReference   OBJECT-TYPE
                SYNTAX  INTEGER(1..65535)                           -- @001 修正
--              SYNTAX  INTEGER(1)                                     @001 修正
                ACCESS  not-accessible
                STATUS  mandatory
                DESCRIPTION
                        "A unique value to identify this Soft-PVC.
                        The value is used only 1 (p2p)."
--                        Soft-PVC識別子。Point to Point時は１固定。
                ::= { mpAtmCCSoftPvcEntry 1 }

        mpAtmCCSoftPvcIfIndex OBJECT-TYPE
                SYNTAX  INTEGER
                ACCESS  not-accessible
                STATUS  mandatory
                DESCRIPTION
                     "The value of this object is equal to MIB II's
                      ifIndex value of the ATM interface port for this
                      Soft-PVC."
--                      ATM Port。MIB2のifIndex相当。
                ::= { mpAtmCCSoftPvcEntry 2 }

        mpAtmCCSoftPvcVpi     OBJECT-TYPE
                SYNTAX  INTEGER
                ACCESS  not-accessible
                STATUS  mandatory
                DESCRIPTION
                     "The value of this object is equal to the VPI
                      value at the ATM interface associated with
                      the Soft-PVC that is identified by
                      mpAtmCCSoftPvcIfIndex.
                      The VPI value cannot exceed the number
                      supported by the atmInterfaceMaxVpiBits
                      at the ATM interface port."
--                    mpAtmCCSoftPvcIfIndexで識別されるSoft-PVCのVPI値。
--                    atmInterfaceMaxVpiBitsの有効範囲は越えない。
                ::= { mpAtmCCSoftPvcEntry 3 }

        mpAtmCCSoftPvcVci     OBJECT-TYPE
                SYNTAX  INTEGER
                ACCESS  not-accessible
                STATUS  mandatory
                DESCRIPTION
                     "The value of this object is equal to the VCI
                      value at the ATM interface associated with
                      the Soft-PVC that is identified by
                      mpAtmCCSoftPvcIfIndex.
                      The VPI value cannot exceed the number
                      supported by the atmInterfaceMaxVciBits
                      at the ATM interface port."
--                    mpAtmCCSoftPvcIfIndexで識別されるSoft-PVCのVCI値。
--                    atmInterfaceMaxVciBitsの有効範囲は越えない。
                ::= { mpAtmCCSoftPvcEntry 4 }

        mpAtmCCSoftPvcReceiveTrafficDescrIndex        OBJECT-TYPE
                SYNTAX  AtmTrafficDescrParamIndex
                ACCESS  read-write
                STATUS  mandatory
                DESCRIPTION
                     "The value of this object identifies
                      in the ATM Traffic Descriptor Table which
                      applies to the receive direction of this Soft-PVC."
--                      Soft-PVCの受け側ATM Traffic Descriptor識別子。
                ::= { mpAtmCCSoftPvcEntry 5 }

        mpAtmCCSoftPvcTransmitTrafficDescrIndex       OBJECT-TYPE
                SYNTAX  AtmTrafficDescrParamIndex
                ACCESS  read-write
                STATUS  mandatory
                DESCRIPTION
                     "The value of this object identifies
                      in the ATM Traffic Descriptor Table which
                      applies to the transmit direction of this Soft-PVC."
--                      Soft-PVCの送り側ATM Traffic Descriptor識別子。
                ::= { mpAtmCCSoftPvcEntry 6 }

        mpAtmCCSoftPvcTargetAddress   OBJECT-TYPE
                SYNTAX  AtmAddr
                ACCESS  read-write
                STATUS  mandatory
                DESCRIPTION
                        "The target ATM Address of this Soft PVCC.  If no
                        address is supplied, no attempts to establish the
                        Soft PVCC are initiated."
--                        Soft-PVCの宛て先アドレス
                ::= { mpAtmCCSoftPvcEntry 7 }

        mpAtmCCSoftPvcTargetVpi       OBJECT-TYPE
                SYNTAX  INTEGER (0..4095)
                ACCESS  read-write
                STATUS  mandatory
                DESCRIPTION
                        "The VPI value of the VCL used at the target interface."
--                        Soft-PVCの宛て先VPI
                DEFVAL { 0 }
                ::= { mpAtmCCSoftPvcEntry 8 }

        mpAtmCCSoftPvcTargetVci       OBJECT-TYPE
                SYNTAX  INTEGER (0..65535)
                ACCESS  read-write
                STATUS  mandatory
                DESCRIPTION
                        "The VCI value of the VCL used at the target interface."
--                        Soft-PVCの宛て先VCI
                ::= { mpAtmCCSoftPvcEntry 9 }

        mpAtmCCSoftPvcLastReleaseCause        OBJECT-TYPE
                SYNTAX  INTEGER(1..127)
                ACCESS  read-only
                STATUS  mandatory
                DESCRIPTION
                        "Value of the Cause field of the Cause
                        Information Element in the last RELEASE
                        signalling message received for this Soft PVCC.
                        Indicates the reason for the Release."
--                        切断理由
                ::= { mpAtmCCSoftPvcEntry 10 }

        mpAtmCCSoftPvcLastReleaseDiagnostic   OBJECT-TYPE
                SYNTAX  OCTET STRING (SIZE(0..8))
                ACCESS  read-only
                STATUS  mandatory
                DESCRIPTION
                        "Value of the first 8 bytes of diagnostic information
                        from the Cause field of the Cause Information Element
                        in the last RELEASE signalling message received for
                        this Soft-PVC."
--                        切断時診断結果
                ::= { mpAtmCCSoftPvcEntry 11 }

        mpAtmCCSoftPvcPriority        OBJECT-TYPE
                SYNTAX  INTEGER(1..3)                               -- @001 修正
                ACCESS  read-write
                STATUS  mandatory
                DESCRIPTION
                     "Connection priority"
--                        PVC優先度
                DEFVAL { 1 }                                        -- @001 修正
                ::= { mpAtmCCSoftPvcEntry 12 }

        mpAtmCCSoftPvcCladType        OBJECT-TYPE
                SYNTAX  MpAtmCCCladType
                ACCESS  read-only
                STATUS  mandatory
                DESCRIPTION
                     "CLAD Type"
--                     CLAD種別
                ::= { mpAtmCCSoftPvcEntry 13 }

        mpAtmCCSoftPvcOriginalAddress   OBJECT-TYPE
                SYNTAX  AtmAddr
                ACCESS  read-only
                STATUS  mandatory
                DESCRIPTION
                        "The origjnal ATM Address of this Soft PVCC.  If no
                        address is supplied, no attempts to establish the
                        Soft PVCC are initiated."
--                        自ＡＴＭアドレス
                ::= { mpAtmCCSoftPvcEntry 14 }

        mpAtmCCSoftPvcAdminStatus     OBJECT-TYPE
                SYNTAX  INTEGER {
                                up(1),
                                down(2)
                                }
                ACCESS  read-write
                STATUS  mandatory
                DESCRIPTION
                     "The value of this object identifies the desired
                      administrative status of this Soft-PVC.
                      The up and down states indicate that the traffic
                      flow is enabled and disabled respectively on this
                      Soft-PVC."
--                      Soft-PVCのAdmin Status。up/down = 送受信enable/disable
                DEFVAL { down }
                ::= { mpAtmCCSoftPvcEntry 15 }

        mpAtmCCSoftPvcOperStatus      OBJECT-TYPE
                SYNTAX  INTEGER
                ACCESS  read-only
                STATUS  mandatory
                DESCRIPTION
                     "The value of this object identifies the desired
                      operational status of this Soft-PVC."
--                     Soft-PVCのOper Status。up/down = 送受信enable/disable
                ::= { mpAtmCCSoftPvcEntry 16 }

        mpAtmCCSoftPvcPgcRequest      OBJECT-TYPE             -- @007追加
                SYNTAX  INTEGER
                ACCESS  read-only
                STATUS  mandatory
                DESCRIPTION
                     "Indicates whether this PVP was configureated from
                      the PVC-Group-Cutover function.
                      The value of '0' indicates that this PVP was normal.
                      The value of '!=0' indicates that this PVP was
                      configrated form PVC-Group-Cutover function.
                       In this case, the value was indicated the PVC-Group Number"
--                     PVCグループ切り替えリクエスト表示
--                       ０：PVC登録
--                     ≠０：PVCグループ番号
                ::= { mpAtmCCSoftPvcEntry 17 }


        mpAtmCCSoftPvcCfgStatus    OBJECT-TYPE
                SYNTAX  INTEGER {
                                enable(1),
                                cancel(2),
                                delete(3),
                                unknown(4)
                                }
                ACCESS  read-write
                STATUS  mandatory
                DESCRIPTION
                        "Configuration setting start object. If this object is
                         set the setting of the configuration is started."
--                        ConfigSet開始設定
                DEFVAL { unknown }
                ::= { mpAtmCCSoftPvcEntry 98 }

        mpAtmCCSoftPvcErrInfo          OBJECT-TYPE
                SYNTAX  INTEGER
                ACCESS  read-only
                STATUS  mandatory
                DESCRIPTION
                        "Object that the configuration setting result is set up."
--                        Config設定結果
                ::= { mpAtmCCSoftPvcEntry 99 }


--
-- Ｓｏｆｔ－ＰＶＰ／ＰＶＣ着側設定
--

--
-- Ｓｏｆｔ－ＰＶＰ着側制御テーブル
--

        mpAtmCCSoftPvpCalledTable     OBJECT-TYPE
                SYNTAX  SEQUENCE OF MpAtmCCSoftPvpCalledEntry
                ACCESS  not-accessible
                STATUS  mandatory
                DESCRIPTION
                        "Soft-PVP(Called) Table"
                ::= { mpAtmCCSoftPVPC 3 }

        mpAtmCCSoftPvpCalledEntry     OBJECT-TYPE
                SYNTAX  MpAtmCCSoftPvpCalledEntry
                ACCESS  not-accessible
                STATUS  mandatory
                DESCRIPTION
                        "Soft-PVP(Called) Entry"
                INDEX { mpAtmCCSoftPvpCalledLeafReference,
                        mpAtmCCSoftPvpCalledIfIndex,
                        mpAtmCCSoftPvpCalledVpi
                }
                ::= { mpAtmCCSoftPvpCalledTable 1 }

        MpAtmCCSoftPvpCalledEntry ::=
                SEQUENCE {
                        mpAtmCCSoftPvpCalledLeafReference     INTEGER,
                        mpAtmCCSoftPvpCalledIfIndex           INTEGER,
                        mpAtmCCSoftPvpCalledVpi               INTEGER,
                        mpAtmCCSoftPvpCalledReceiveTrafficDescrIndex
                                                AtmTrafficDescrParamIndex,
                        mpAtmCCSoftPvpCalledTransmitTrafficDescrIndex
                                                AtmTrafficDescrParamIndex,
                        mpAtmCCSoftPvpCalledTargetAddress     AtmAddr,
                        mpAtmCCSoftPvpCalledTargetVpi         INTEGER,
                        mpAtmCCSoftPvpCalledLastReleaseCause  INTEGER,
                        mpAtmCCSoftPvpCalledLastReleaseDiagnostic
                                                        OCTET STRING,
                        mpAtmCCSoftPvpCalledPriority          INTEGER,
                        mpAtmCCSoftPvpCalledCladType          MpAtmCCCladType,
                        mpAtmCCSoftPvpCalledOriginalAddress   AtmAddr,
                        mpAtmCCSoftPvpCalledAdminStatus       INTEGER,
                        mpAtmCCSoftPvpCalledOperStatus        INTEGER,
                        mpAtmCCSoftPvpCalledPgcRequest        INTEGER,  -- @010 追加
                        mpAtmCCSoftPvpCalledCfgStatus         INTEGER,
                        mpAtmCCSoftPvpCalledErrInfo           INTEGER
                        }

        mpAtmCCSoftPvpCalledLeafReference     OBJECT-TYPE
                SYNTAX  INTEGER(1..65535)                           -- @001 修正
--              SYNTAX  INTEGER(1)                                     @001 修正
                ACCESS  not-accessible
                STATUS  mandatory
                DESCRIPTION
                        "A unique value to identify this Soft-PVP.
                        The value is used only 1 (p2p)."
--                        Soft-PVP識別子。Point to Point時は１固定。
                ::= { mpAtmCCSoftPvpCalledEntry 1 }

        mpAtmCCSoftPvpCalledIfIndex   OBJECT-TYPE
                SYNTAX  INTEGER
                ACCESS  not-accessible
                STATUS  mandatory
                DESCRIPTION
                     "The value of this object is equal to MIB II's
                      ifIndex value of the ATM interface port for this
                      Soft-PVP."
--                      ATM Port。MIB2のifIndex相当。
                ::= { mpAtmCCSoftPvpCalledEntry 2 }

        mpAtmCCSoftPvpCalledVpi       OBJECT-TYPE
                SYNTAX  INTEGER
                ACCESS  not-accessible
                STATUS  mandatory
                DESCRIPTION
                     "The value of this object is equal to the VPI
                      value at the ATM interface associated with
                      the Soft-PVP that is identified by
                      mpAtmCCSoftPvpCalledIfIndex.
                      The VPI value cannot exceed the number
                      supported by the atmInterfaceMaxVpiBits
                      at the ATM interface port."
--                      mpAtmCCSoftPvpCalledIfIndexで識別されるSoft-PVPのVPI値。
--                     atmInterfaceMaxVpiBitsの有効範囲は越えない。
                ::= { mpAtmCCSoftPvpCalledEntry 3 }

        mpAtmCCSoftPvpCalledReceiveTrafficDescrIndex  OBJECT-TYPE
                SYNTAX  AtmTrafficDescrParamIndex
                ACCESS  read-write
                STATUS  mandatory
                DESCRIPTION
                     "The value of this object identifies
                      in the ATM Traffic Descriptor Table which
                      applies to the receive direction of this Soft-PVP."
--                      Soft-PVPの受け側ATM Traffic Descriptor識別子。
                ::= { mpAtmCCSoftPvpCalledEntry 4 }

        mpAtmCCSoftPvpCalledTransmitTrafficDescrIndex OBJECT-TYPE
                SYNTAX  AtmTrafficDescrParamIndex
                ACCESS  read-write
                STATUS  mandatory
                DESCRIPTION
                     "The value of this object identifies
                      in the ATM Traffic Descriptor Table which
                      applies to the transmit direction of this Soft-PVP."
--                      Soft-PVPの送り側ATM Traffic Descriptor識別子。
                ::= { mpAtmCCSoftPvpCalledEntry 5 }

        mpAtmCCSoftPvpCalledTargetAddress     OBJECT-TYPE
                SYNTAX  AtmAddr
                ACCESS  read-write
                STATUS  mandatory
                DESCRIPTION
                        "The target ATM Address of this Soft-PVP.  If no
                        address is supplied, no attempts to establish the
                        Soft-PVP are initiated."
--                        Soft-PVPの発信元アドレス
                ::= { mpAtmCCSoftPvpCalledEntry 6 }

        mpAtmCCSoftPvpCalledTargetVpi OBJECT-TYPE
                SYNTAX  INTEGER (0..4095)
                ACCESS  read-write
                STATUS  mandatory
                DESCRIPTION
                        "The VPI value of the VCL used at the target interface."
--                        Soft-PVPの発信元VPI
                DEFVAL { 0 }
                ::= { mpAtmCCSoftPvpCalledEntry 7 }

        mpAtmCCSoftPvpCalledLastReleaseCause  OBJECT-TYPE
                SYNTAX  INTEGER(1..127)
                ACCESS  read-only
                STATUS  mandatory
                DESCRIPTION
                        "Value of the Cause field of the Cause
                        Information Element in the last RELEASE
                        signalling message received for this Soft-PVP.
                        Indicates the reason for the Release."
--                        切断理由
                ::= { mpAtmCCSoftPvpCalledEntry 8 }

        mpAtmCCSoftPvpCalledLastReleaseDiagnostic     OBJECT-TYPE
                SYNTAX  OCTET STRING (SIZE(0..8))
                ACCESS  read-only
                STATUS  mandatory
                DESCRIPTION
                        "Value of the first 8 bytes of diagnostic information
                        from the Cause field of the Cause Information Element
                        in the last RELEASE signalling message received for
                        this Soft-PVP."
--                        切断時診断結果
                ::= { mpAtmCCSoftPvpCalledEntry 9 }

        mpAtmCCSoftPvpCalledPriority  OBJECT-TYPE
                SYNTAX  INTEGER(1..3)                               -- @001 修正
                ACCESS  read-write
                STATUS  mandatory
                DESCRIPTION
                     "Connection priority"
--                        Soft-PVP優先度
                DEFVAL { 1 }                                        -- @001 修正
                ::= { mpAtmCCSoftPvpCalledEntry 10 }

        mpAtmCCSoftPvpCalledCladType  OBJECT-TYPE
                SYNTAX  MpAtmCCCladType
                ACCESS  read-only
                STATUS  mandatory
                DESCRIPTION
                     "CLAD Type"
--                     CLAD種別
                ::= { mpAtmCCSoftPvpCalledEntry 11 }

        mpAtmCCSoftPvpCalledOriginalAddress     OBJECT-TYPE
                SYNTAX  AtmAddr
                ACCESS  read-only
                STATUS  mandatory
                DESCRIPTION
                        "The original ATM Address of this Soft-PVP.  If no
                        address is supplied, no attempts to establish the
                        Soft-PVP are initiated."
--                        自ＡＴＭアドレス
                ::= { mpAtmCCSoftPvpCalledEntry 12 }

        mpAtmCCSoftPvpCalledAdminStatus       OBJECT-TYPE
                SYNTAX  INTEGER {
                                up(1),
                                down(2)
                                }
                ACCESS  read-write
                STATUS  mandatory
                DESCRIPTION
                     "The value of this object identifies the desired
                      administrative status of this Soft-PVP.
                      The up and down states indicate that the traffic
                      flow is enabled and disabled respectively on this
                      Soft-PVP."
--                      Soft-PVPのAdmin Status。up/down = 送受信enable/disable
                DEFVAL { down }
                ::= { mpAtmCCSoftPvpCalledEntry 13 }

        mpAtmCCSoftPvpCalledOperStatus        OBJECT-TYPE
                SYNTAX  INTEGER
                ACCESS  read-only
                STATUS  mandatory
                DESCRIPTION
                     "The value of this object identifies the desired
                      operational status of this Soft-PVP."
--                     Soft-PVPのOper Status。up/down = 送受信enable/disable
                ::= { mpAtmCCSoftPvpCalledEntry 14 }

        mpAtmCCSoftPvpCalledPgcRequest     OBJECT-TYPE    -- @010 追加
                SYNTAX  INTEGER
                ACCESS  read-only
                STATUS  mandatory
                DESCRIPTION
                     "Indicates whether this PVP was configureated from
                      the PVC-Group-Cutover function.
                      The value of '0' indicates that this PVP was normal.
                      The value of '!=0' indicates that this PVP was
                      configrated form PVC-Group-Cutover function.
                       In this case, the value was indicated the PVC-Group Number"
--                     PVCグループ切り替えリクエスト表示
--                       ０：PVC登録
--                     ≠０：PVCグループ番号
                ::= { mpAtmCCSoftPvpCalledEntry 15 }

        mpAtmCCSoftPvpCalledCfgStatus      OBJECT-TYPE
                SYNTAX  INTEGER {
                                enable(1),
                                cancel(2),
                                delete(3),
                                unknown(4)
                                }
                ACCESS  read-write
                STATUS  mandatory
                DESCRIPTION
                        "Configuration setting start object. If this object is
                         set the setting of the configuration is started."
--                        ConfigSet開始設定
                DEFVAL { unknown }
                ::= { mpAtmCCSoftPvpCalledEntry 98 }

        mpAtmCCSoftPvpCalledErrInfo    OBJECT-TYPE
                SYNTAX  INTEGER
                ACCESS  read-only
                STATUS  mandatory
                DESCRIPTION
                        "Object that the configuration setting result is set up."
--                        Config設定結果
                ::= { mpAtmCCSoftPvpCalledEntry 99 }


--
-- Ｓｏｆｔ－ＰＶＣ着側制御テーブル
--

        mpAtmCCSoftPvcCalledTable     OBJECT-TYPE
                SYNTAX  SEQUENCE OF MpAtmCCSoftPvcCalledEntry
                ACCESS  not-accessible
                STATUS  mandatory
                DESCRIPTION
                        "Soft-PVC(Called) Table"
                ::= { mpAtmCCSoftPVPC 4 }

        mpAtmCCSoftPvcCalledEntry     OBJECT-TYPE
                SYNTAX  MpAtmCCSoftPvcCalledEntry
                ACCESS  not-accessible
                STATUS  mandatory
                DESCRIPTION
                        "Soft-PVC(Called) Entry"
                INDEX { mpAtmCCSoftPvcCalledLeafReference,
                        mpAtmCCSoftPvcCalledIfIndex,
                        mpAtmCCSoftPvcCalledVpi,
                        mpAtmCCSoftPvcCalledVci
                }
                ::= { mpAtmCCSoftPvcCalledTable 1 }

        MpAtmCCSoftPvcCalledEntry ::=
                SEQUENCE {
                        mpAtmCCSoftPvcCalledLeafReference     INTEGER,
                        mpAtmCCSoftPvcCalledIfIndex           INTEGER,
                        mpAtmCCSoftPvcCalledVpi               INTEGER,
                        mpAtmCCSoftPvcCalledVci               INTEGER,
                        mpAtmCCSoftPvcCalledReceiveTrafficDescrIndex
                                                AtmTrafficDescrParamIndex,
                        mpAtmCCSoftPvcCalledTransmitTrafficDescrIndex
                                                AtmTrafficDescrParamIndex,
                        mpAtmCCSoftPvcCalledTargetAddress     AtmAddr,
                        mpAtmCCSoftPvcCalledTargetVpi         INTEGER,
                        mpAtmCCSoftPvcCalledTargetVci         INTEGER,
                        mpAtmCCSoftPvcCalledLastReleaseCause  INTEGER,
                        mpAtmCCSoftPvcCalledLastReleaseDiagnostic
                                                        OCTET STRING,
                        mpAtmCCSoftPvcCalledPriority          INTEGER,
                        mpAtmCCSoftPvcCalledCladType          MpAtmCCCladType,
                        mpAtmCCSoftPvcCalledOriginalAddress   AtmAddr,
                        mpAtmCCSoftPvcCalledAdminStatus       INTEGER,
                        mpAtmCCSoftPvcCalledOperStatus        INTEGER,
                        mpAtmCCSoftPvcCalledPgcRequest        INTEGER,  -- @010 追加
                        mpAtmCCSoftPvcCalledCfgStatus         INTEGER,
                        mpAtmCCSoftPvcCalledErrInfo           INTEGER
                        }

        mpAtmCCSoftPvcCalledLeafReference     OBJECT-TYPE
                SYNTAX  INTEGER(1..65535)                           -- @001 修正
--              SYNTAX  INTEGER(1)                                     @001 修正
                ACCESS  not-accessible
                STATUS  mandatory
                DESCRIPTION
                        "A unique value to identify this Soft-PVC.
                        The value is used only 1 (p2p)."
--                        Soft-PVC識別子。Point to Point時は１固定。
                ::= { mpAtmCCSoftPvcCalledEntry 1 }

        mpAtmCCSoftPvcCalledIfIndex   OBJECT-TYPE
                SYNTAX  INTEGER
                ACCESS  not-accessible
                STATUS  mandatory
                DESCRIPTION
                     "The value of this object is equal to MIB II's
                      ifIndex value of the ATM interface port for this
                      Soft-PVC."
--                      ATM Port。MIB2のifIndex相当。
                ::= { mpAtmCCSoftPvcCalledEntry 2 }

        mpAtmCCSoftPvcCalledVpi       OBJECT-TYPE
                SYNTAX  INTEGER
                ACCESS  not-accessible
                STATUS  mandatory
                DESCRIPTION
                     "The value of this object is equal to the VPI
                      value at the ATM interface associated with
                      the Soft-PVC that is identified by
                      mpAtmCCSoftPvcCalledIfIndex.
                      The VPI value cannot exceed the number
                      supported by the atmInterfaceMaxVpiBits
                      at the ATM interface port."
--                      mpAtmCCSoftPvcCalledIfIndexで識別されるSoft-PVCのVPI値。
--                      atmInterfaceMaxVpiBitsの有効範囲は越えない。
                ::= { mpAtmCCSoftPvcCalledEntry 3 }

        mpAtmCCSoftPvcCalledVci       OBJECT-TYPE
                SYNTAX  INTEGER
                ACCESS  not-accessible
                STATUS  mandatory
                DESCRIPTION
                     "The value of this object is equal to the VCI
                      value at the ATM interface associated with
                      the Soft-PVC that is identified by
                      mpAtmCCSoftPvcCalledIfIndex.
                      The VPI value cannot exceed the number
                      supported by the atmInterfaceMaxVciBits
                      at the ATM interface port."
--                      mpAtmCCSoftPvcCalledIfIndexで識別されるSoft-PVCのVCI値。
--                      atmInterfaceMaxVciBitsの有効範囲は越えない。
                ::= { mpAtmCCSoftPvcCalledEntry 4 }

        mpAtmCCSoftPvcCalledReceiveTrafficDescrIndex  OBJECT-TYPE
                SYNTAX  AtmTrafficDescrParamIndex
                ACCESS  read-write
                STATUS  mandatory
                DESCRIPTION
                     "The value of this object identifies
                      in the ATM Traffic Descriptor Table which
                      applies to the receive direction of this Soft-PVC."
--                      Soft-PVCの受け側ATM Traffic Descriptor識別子。
                ::= { mpAtmCCSoftPvcCalledEntry 5 }

        mpAtmCCSoftPvcCalledTransmitTrafficDescrIndex OBJECT-TYPE
                SYNTAX  AtmTrafficDescrParamIndex
                ACCESS  read-write
                STATUS  mandatory
                DESCRIPTION
                     "The value of this object identifies
                      in the ATM Traffic Descriptor Table which
                      applies to the transmit direction of this Soft-PVC."
--                      Soft-PVCの送り側ATM Traffic Descriptor識別子。
                ::= { mpAtmCCSoftPvcCalledEntry 6 }

        mpAtmCCSoftPvcCalledTargetAddress     OBJECT-TYPE
                SYNTAX  AtmAddr
                ACCESS  read-write
                STATUS  mandatory
                DESCRIPTION
                        "The target ATM Address of this Soft PVCC.  If no
                        address is supplied, no attempts to establish the
                        Soft PVCC are initiated."
--                        Soft-PVCの発信元アドレス
                ::= { mpAtmCCSoftPvcCalledEntry 7 }

        mpAtmCCSoftPvcCalledTargetVpi OBJECT-TYPE
                SYNTAX  INTEGER (0..4095)
                ACCESS  read-write
                STATUS  mandatory
                DESCRIPTION
                        "The VPI value of the VCL used at the target interface."
--                        Soft-PVCの発信元VPI
                DEFVAL { 0 }
                ::= { mpAtmCCSoftPvcCalledEntry 8 }

        mpAtmCCSoftPvcCalledTargetVci OBJECT-TYPE
                SYNTAX  INTEGER (0..65535)
                ACCESS  read-write
                STATUS  mandatory
                DESCRIPTION
                        "The VCI value of the VCL used at the target interface."
--                        Soft-PVCの発信元VCI
                ::= { mpAtmCCSoftPvcCalledEntry 9 }

        mpAtmCCSoftPvcCalledLastReleaseCause  OBJECT-TYPE
                SYNTAX  INTEGER(1..127)
                ACCESS  read-only
                STATUS  mandatory
                DESCRIPTION
                        "Value of the Cause field of the Cause
                        Information Element in the last RELEASE
                        signalling message received for this Soft PVCC.
                        Indicates the reason for the Release."
--                        切断理由
                ::= { mpAtmCCSoftPvcCalledEntry 10 }

        mpAtmCCSoftPvcCalledLastReleaseDiagnostic     OBJECT-TYPE
                SYNTAX  OCTET STRING (SIZE(0..8))
                ACCESS  read-only
                STATUS  mandatory
                DESCRIPTION
                        "Value of the first 8 bytes of diagnostic information
                        from the Cause field of the Cause Information Element
                        in the last RELEASE signalling message received for
                        this Soft-PVC."
--                        切断時診断結果
                ::= { mpAtmCCSoftPvcCalledEntry 11 }

        mpAtmCCSoftPvcCalledPriority  OBJECT-TYPE
                SYNTAX  INTEGER(1..3)                               -- @001 修正
                ACCESS  read-write
                STATUS  mandatory
                DESCRIPTION
                     "Connection priority"
--                        Soft-PVC優先度
                DEFVAL { 1 }                                        -- @001 修正
                ::= { mpAtmCCSoftPvcCalledEntry 12 }

        mpAtmCCSoftPvcCalledCladType  OBJECT-TYPE
                SYNTAX  MpAtmCCCladType
                ACCESS  read-only
                STATUS  mandatory
                DESCRIPTION
                     "CLAD Type"
--                     CLAD種別
                ::= { mpAtmCCSoftPvcCalledEntry 13 }

        mpAtmCCSoftPvcCalledOriginalAddress     OBJECT-TYPE
                SYNTAX  AtmAddr
                ACCESS  read-only
                STATUS  mandatory
                DESCRIPTION
                        "The original ATM Address of this Soft PVCC.  If no
                        address is supplied, no attempts to establish the
                        Soft PVCC are initiated."
--                        自ＡＴＭアドレス
                ::= { mpAtmCCSoftPvcCalledEntry 14 }

        mpAtmCCSoftPvcCalledAdminStatus       OBJECT-TYPE
                SYNTAX  INTEGER {
                                up(1),
                                down(2)
                                }
                ACCESS  read-write
                STATUS  mandatory
                DESCRIPTION
                     "The value of this object identifies the desired
                      administrative status of this Soft-PVC.
                      The up and down states indicate that the traffic
                      flow is enabled and disabled respectively on this
                      Soft-PVC."
--                      Soft-PVPのAdmin Status。up/down = 送受信enable/disable
                DEFVAL { down }
                ::= { mpAtmCCSoftPvcCalledEntry 15 }

        mpAtmCCSoftPvcCalledOperStatus        OBJECT-TYPE
                SYNTAX  INTEGER
                ACCESS  read-only
                STATUS  mandatory
                DESCRIPTION
                     "The value of this object identifies the desired
                      operational status of this Soft-PVC."
--                     Soft-PVCのOper Status。up/down = 送受信enable/disable
                ::= { mpAtmCCSoftPvcCalledEntry 16 }

        mpAtmCCSoftPvcCalledPgcRequest        OBJECT-TYPE    -- @010 追加
                SYNTAX  INTEGER
                ACCESS  read-only
                STATUS  mandatory
                DESCRIPTION
                     "Indicates whether this PVC was configureated from
                      the PVC-Group-Cutover function.
                      The value of '0' indicates that this PVC was normal.
                      The value of '!=0' indicates that this PVC was
                      configrated form PVC-Group-Cutover function.
                       In this case, the value was indicated the PVC-Group Number"
--                     PVCグループ切り替えリクエスト表示
--                       ０：PVC登録
--                     ≠０：PVCグループ番号
                ::= { mpAtmCCSoftPvcCalledEntry 17 }

        mpAtmCCSoftPvcCalledCfgStatus      OBJECT-TYPE
                SYNTAX  INTEGER {
                                enable(1),
                                cancel(2),
                                delete(3),
                                unknown(4)
                                }
                ACCESS  read-write
                STATUS  mandatory
                DESCRIPTION
                        "Configuration setting start object. If this object is
                         set the setting of the configuration is started."
--                        ConfigSet開始設定
                DEFVAL { unknown }
                ::= { mpAtmCCSoftPvcCalledEntry 98 }

        mpAtmCCSoftPvcCalledErrInfo    OBJECT-TYPE
                SYNTAX  INTEGER
                ACCESS  read-only
                STATUS  mandatory
                DESCRIPTION
                        "Object that the configuration setting result is set up."
--                        Config設定結果
                ::= { mpAtmCCSoftPvcCalledEntry 99 }


--
--    ＡＴＭトラフィック情報
--

        mpAtmCCStatistics      OBJECT IDENTIFIER ::= { mpAtmCallCtl 4 }

--
--    ＶＰトラフィック参照テーブル
--

mpAtmCCVpStatisticsTable OBJECT-TYPE
        SYNTAX  SEQUENCE OF MpAtmCCVpStatisticsEntry
        ACCESS  not-accessible
        STATUS  mandatory
        DESCRIPTION
                " Indicate traffic counter information per connection."
        --      コネクション毎のトラヒックカウンタ情報表示を行なう.
        ::= { mpAtmCCStatistics 1 }

mpAtmCCVpStatisticsEntry OBJECT-TYPE
        SYNTAX  MpAtmCCVpStatisticsEntry
        ACCESS  not-accessible
        STATUS  mandatory
        DESCRIPTION
                " Entry of traffic per connection."
        --      コネクション毎のトラヒックのエントリ
        INDEX{ ifIndex, mpAtmCCVpStatVpi }
        ::= { mpAtmCCVpStatisticsTable 1 }

MpAtmCCVpStatisticsEntry ::=
        SEQUENCE {
                mpAtmCCVpStatVpi
                        INTEGER,
                mpAtmCCVpStatInCells
                        OCTET STRING,
                mpAtmCCVpStatInCellsCounters
                        Counter,
                mpAtmCCVpStatOutCells
                        OCTET STRING,
                mpAtmCCVpStatOutCellsCounters
                        Counter,
                mpAtmCCVpStatInDropCells
                        OCTET STRING,
                mpAtmCCVpStatInDropCellsCounters
                        Counter
        }

mpAtmCCVpStatVpi       OBJECT-TYPE
        SYNTAX  INTEGER
        ACCESS  not-accessible
        STATUS  mandatory
        DESCRIPTION
                "Indicate value for the specific VPI "
        --      統計情報を参照するVPI
        ::= { mpAtmCCVpStatisticsEntry 1 }

mpAtmCCVpStatInCells       OBJECT-TYPE
        SYNTAX  OCTET STRING
        ACCESS  read-only
        STATUS  mandatory
        DESCRIPTION
                " The number of receive cells  64 bit counter"
        --      受信セル数 64ビットカウンタ
        ::= { mpAtmCCVpStatisticsEntry 2 }

mpAtmCCVpStatInCellsCounters       OBJECT-TYPE
        SYNTAX  Counter
        ACCESS  read-only
        STATUS  mandatory
        DESCRIPTION
                " The number of receive cells  32 bit counter"
        --      受信セル数 32ビットカウンタ
        ::= { mpAtmCCVpStatisticsEntry 3 }

mpAtmCCVpStatOutCells      OBJECT-TYPE
        SYNTAX  OCTET STRING
        ACCESS  read-only
        STATUS  mandatory
        DESCRIPTION
                " The number of transmit cells  64 bit counter"
        --      送信セル数 64ビットカウンタ
        ::= { mpAtmCCVpStatisticsEntry 4 }

mpAtmCCVpStatOutCellsCounters      OBJECT-TYPE
        SYNTAX  Counter
        ACCESS  read-only
        STATUS  mandatory
        DESCRIPTION
                " The number of transmit cells  32 bit counter"
        --      送信セル数 32ビットカウンタ
        ::= { mpAtmCCVpStatisticsEntry 5 }

mpAtmCCVpStatInDropCells   OBJECT-TYPE
        SYNTAX  OCTET STRING
        ACCESS  read-only
        STATUS  mandatory
        DESCRIPTION
                " The number of receive drop cells  64 bit counter "
        --      受信廃棄セル数 64ビットカウンタ
        ::= { mpAtmCCVpStatisticsEntry 6 }

mpAtmCCVpStatInDropCellsCounters   OBJECT-TYPE
        SYNTAX  Counter
        ACCESS  read-only
        STATUS  mandatory
        DESCRIPTION
                " The number of receive drop cells  32 bit counter"
        --      受信廃棄セル数 32ビットカウンタ
        ::= { mpAtmCCVpStatisticsEntry 7 }

--
--    ＶＣトラフィック参照テーブル
--

mpAtmCCVcStatisticsTable OBJECT-TYPE
        SYNTAX  SEQUENCE OF MpAtmCCVcStatisticsEntry
        ACCESS  not-accessible
        STATUS  mandatory
        DESCRIPTION
                " Indicate traffic counter information per connection."
        --      コネクション毎のトラヒックカウンタ情報表示を行なう.
        ::= { mpAtmCCStatistics 2 }

mpAtmCCVcStatisticsEntry OBJECT-TYPE
        SYNTAX  MpAtmCCVcStatisticsEntry
        ACCESS  not-accessible
        STATUS  mandatory
        DESCRIPTION
                " Entry of traffic per connection."
        --      コネクション毎のトラヒックのエントリ
        INDEX{ ifIndex, mpAtmCCVcStatVpi, mpAtmCCVcStatVci }
        ::= { mpAtmCCVcStatisticsTable 1 }

MpAtmCCVcStatisticsEntry ::=
        SEQUENCE {
                mpAtmCCVcStatVpi
                        INTEGER,
                mpAtmCCVcStatVci
                        INTEGER,
                mpAtmCCVcStatInCells
                        OCTET STRING,
                mpAtmCCVcStatInCellsCounters
                        Counter,
                mpAtmCCVcStatOutCells
                        OCTET STRING,
                mpAtmCCVcStatOutCellsCounters
                        Counter,
                mpAtmCCVcStatInDropCells
                        OCTET STRING,
                mpAtmCCVcStatInDropCellsCounters
                        Counter
        }

mpAtmCCVcStatVpi       OBJECT-TYPE
        SYNTAX  INTEGER
        ACCESS  not-accessible
        STATUS  mandatory
        DESCRIPTION
                "Indicate value for the specific VPI "
        --      統計情報を参照するVPI
        ::= { mpAtmCCVcStatisticsEntry 1 }

mpAtmCCVcStatVci       OBJECT-TYPE
        SYNTAX  INTEGER
        ACCESS  not-accessible
        STATUS  mandatory
        DESCRIPTION
                "Indicate value for the specific VCI "
        --      統計情報を参照するVCI
        ::= { mpAtmCCVcStatisticsEntry 2 }

mpAtmCCVcStatInCells       OBJECT-TYPE
        SYNTAX  OCTET STRING
        ACCESS  read-only
        STATUS  mandatory
        DESCRIPTION
                " The number of receive cells  64 bit counter"
        --      受信セル数 64ビットカウンタ
        ::= { mpAtmCCVcStatisticsEntry 3 }

mpAtmCCVcStatInCellsCounters       OBJECT-TYPE
        SYNTAX  Counter
        ACCESS  read-only
        STATUS  mandatory
        DESCRIPTION
                " The number of receive cells  32 bit counter"
        --      受信セル数 32ビットカウンタ
        ::= { mpAtmCCVcStatisticsEntry 4 }

mpAtmCCVcStatOutCells      OBJECT-TYPE
        SYNTAX  OCTET STRING
        ACCESS  read-only
        STATUS  mandatory
        DESCRIPTION
                " The number of transmit cells  64 bit counter"
        --      送信セル数 64ビットカウンタ
        ::= { mpAtmCCVcStatisticsEntry 5 }

mpAtmCCVcStatOutCellsCounters      OBJECT-TYPE
        SYNTAX  Counter
        ACCESS  read-only
        STATUS  mandatory
        DESCRIPTION
                " The number of transmit cells  32 bit counter"
        --      送信セル数 32ビットカウンタ
        ::= { mpAtmCCVcStatisticsEntry 6 }

mpAtmCCVcStatInDropCells   OBJECT-TYPE
        SYNTAX  OCTET STRING
        ACCESS  read-only
        STATUS  mandatory
        DESCRIPTION
                " The number of receive drop cells  64 bit counter "
        --      受信廃棄セル数 64ビットカウンタ
        ::= { mpAtmCCVcStatisticsEntry 7 }

mpAtmCCVcStatInDropCellsCounters   OBJECT-TYPE
        SYNTAX  Counter
        ACCESS  read-only
        STATUS  mandatory
        DESCRIPTION
                " The number of receive drop cells  32 bit counter"
        --      受信廃棄セル数 32ビットカウンタ
        ::= { mpAtmCCVcStatisticsEntry 8 }


-- @001 以下のテーブル定義を追加

--
--    カード品質情報参照テーブル                      @001 追加
--                                                    @005 エントリ定義修正
--

mpAtmCCOuspStatisticsTable OBJECT-TYPE
        SYNTAX  SEQUENCE OF MpAtmCCOuspStatisticsEntry
        ACCESS  not-accessible
        STATUS  mandatory
        DESCRIPTION
                "Quality information by the unit of card.
                 All entrys are detected by the OUS-P."
        --      ＯＵＳ－Ｐがカード単位に収集している品質情報
        ::= { mpAtmCCStatistics 3 }

mpAtmCCOuspStatisticsEntry OBJECT-TYPE
        SYNTAX  MpAtmCCOuspStatisticsEntry
        ACCESS  not-accessible
        STATUS  mandatory
        DESCRIPTION
                " An entry of mpAtmCCOuspStatisticsTable."
        --      ＯＵＳ－Ｐが収集している品質情報テーブルのエントリ
        INDEX{ mpAtmCCOuspStatIndex }
        ::= { mpAtmCCOuspStatisticsTable 1 }

MpAtmCCOuspStatisticsEntry ::=
        SEQUENCE {
                mpAtmCCOuspStatIndex
                        INTEGER,
                mpAtmCCOuspStatRcvCrcErrCellsCounters
                        Counter,
                mpAtmCCOuspStatSendOfifoFullCounters
                        Counter,
                mpAtmCCOuspStatRcvBufOverCounters
                        Counter,
                mpAtmCCOuspStatRcvUnknownCellsCounters        --@006修正
                        Counter,
                mpAtmCCOuspStatRcvInvalidCellsCounters
                        Counter,
                mpAtmCCOuspStatSendScheduleErrorCounters
                        Counter,
                mpAtmCCOuspStatRcvScheduleErrorCounters
                        Counter,
                mpAtmCCOuspStatSendInvalidCdvCounters
                        Counter
        }

mpAtmCCOuspStatIndex       OBJECT-TYPE
        SYNTAX  INTEGER
        ACCESS  not-accessible
        STATUS  mandatory
        DESCRIPTION
                "The index value at this table. It consist of card number."
        --      本テーブルのindex、カード（スロット）を使用する
        ::= { mpAtmCCOuspStatisticsEntry 1 }

mpAtmCCOuspStatRcvCrcErrCellsCounters       OBJECT-TYPE
        SYNTAX  Counter
        ACCESS  read-only
        STATUS  mandatory
        DESCRIPTION
                "The number of OAM cells received by the port with CRC errors."
        --      受信OAM Cellの CRC-10 ERROR cell 検出回数
        ::= { mpAtmCCOuspStatisticsEntry 2 }

mpAtmCCOuspStatSendOfifoFullCounters       OBJECT-TYPE
        SYNTAX  Counter
        ACCESS  read-only
        STATUS  mandatory
        DESCRIPTION
                "The number of cells discarded due to Out-FIFO overflow."
        --      O-FIFO（送信FIFO）fullによるcell廃棄数
        ::= { mpAtmCCOuspStatisticsEntry 3 }

mpAtmCCOuspStatRcvBufOverCounters       OBJECT-TYPE
        SYNTAX  Counter
        ACCESS  read-only
        STATUS  mandatory
        DESCRIPTION
                "The number of overflow cells at the reveive buffer."
        --      受信 cell_buffer overflow
        ::= { mpAtmCCOuspStatisticsEntry 4 }

mpAtmCCOuspStatRcvUnknownCellsCounters       OBJECT-TYPE         --@006修正
        SYNTAX  Counter
        ACCESS  read-only
        STATUS  mandatory
        DESCRIPTION
                "The number of cells received by the port with unknown cells."
        --      cell 種別 error（受信）
        ::= { mpAtmCCOuspStatisticsEntry 5 }

mpAtmCCOuspStatRcvInvalidCellsCounters       OBJECT-TYPE
        SYNTAX  Counter
        ACCESS  read-only
        STATUS  mandatory
        DESCRIPTION
                "The number of cells received by the port with invalid cells."
        --      invalid cell 受信数
        ::= { mpAtmCCOuspStatisticsEntry 6 }

mpAtmCCOuspStatSendScheduleErrorCounters       OBJECT-TYPE
        SYNTAX  Counter
        ACCESS  read-only
        STATUS  mandatory
        DESCRIPTION
                "The number of transmission cells discaded due to fail
                 the scheduling"
        --      送信時スケジューリングできない
        ::= { mpAtmCCOuspStatisticsEntry 7 }

mpAtmCCOuspStatRcvScheduleErrorCounters       OBJECT-TYPE
        SYNTAX  Counter
        ACCESS  read-only
        STATUS  mandatory
        DESCRIPTION
                "The number of received cells discaded due to fail
                 the scheduling"
        --      受信時スケジューリングできない
        ::= { mpAtmCCOuspStatisticsEntry 8 }

mpAtmCCOuspStatSendInvalidCdvCounters       OBJECT-TYPE
        SYNTAX  Counter
        ACCESS  read-only
        STATUS  mandatory
        DESCRIPTION
                "The number of un-scheduling cells due to invalid CDV."
        --      スケジューリング時CDV不正値
        ::= { mpAtmCCOuspStatisticsEntry 9 }


--
--    回線品質情報参照テーブル                        @001 追加
--

mpAtmCCPhyStatisticsTable OBJECT-TYPE
        SYNTAX  SEQUENCE OF MpAtmCCPhyStatisticsEntry
        ACCESS  not-accessible
        STATUS  mandatory
        DESCRIPTION
                "Quality information by the unit of port.
                 All entrys are detected by the PHY.
                 This table are supports for ATM CARDs
                 NOTE:ATM CARD
                      ATM-S155, ATM-M155, 2TRK-45, 2TRK6.3I,
                      ATRK-1.5I, ATRK-192K, 2UNI-VMC, 4ATM-25"
        --      ＰＨＹチップがポート単位に収集している品質情報
        --      ATMカードが対象で� る。
        ::= { mpAtmCCStatistics 4 }

mpAtmCCPhyStatisticsEntry OBJECT-TYPE
        SYNTAX  MpAtmCCPhyStatisticsEntry
        ACCESS  not-accessible
        STATUS  mandatory
        DESCRIPTION
                " An entry of mpAtmCCPhyStatisticsTable."
        --      ＰＨＹチップが収集している品質情報テーブルのエントリ
        INDEX{ ifIndex }
        ::= { mpAtmCCPhyStatisticsTable 1 }

MpAtmCCPhyStatisticsEntry ::=
        SEQUENCE {
                mpAtmCCPhyStatTmtCellsCounters
                        Counter,
                mpAtmCCPhyStatRcvCellsCounters
                        Counter,
                mpAtmCCPhyStatCorrectHecErrCounters
                        Counter,
                mpAtmCCPhyStatUncorrectHecErrCounters
                        Counter,
                mpAtmCCPhyStatB1ErrCounters
                        Counter,
                mpAtmCCPhyStatB2ErrCounters
                        Counter,
                mpAtmCCPhyStatB3ErrCounters
                        Counter,
                mpAtmCCPhyStatFebeCounters
                        Counter,
                mpAtmCCPhyStatSymbolErrCounters
                        Counter,
                mpAtmCCPhyStatParityErrCounters
                        Counter
        }

mpAtmCCPhyStatTmtCellsCounters       OBJECT-TYPE
        SYNTAX  Counter
        ACCESS  read-only
        STATUS  mandatory
        DESCRIPTION
                "The number of cells transmitted regardless of error status."
        --      送信セル数
        ::= { mpAtmCCPhyStatisticsEntry 1 }

mpAtmCCPhyStatRcvCellsCounters       OBJECT-TYPE
        SYNTAX  Counter
        ACCESS  read-only
        STATUS  mandatory
        DESCRIPTION
                "The number of cells received regardless of error status"
        --      受信セル数
        ::= { mpAtmCCPhyStatisticsEntry 2 }

mpAtmCCPhyStatCorrectHecErrCounters       OBJECT-TYPE
        SYNTAX  Counter
        ACCESS  read-only
        STATUS  mandatory
        DESCRIPTION
                "The number of cells reveived by the port with correctable
                 HEC error.
                 NOTE: At the 4ATM-25 card, this object incudeing the
                       mpAtmCCPhyUncountCorrectHecErrCounters."
        --      修正可能なHECエラー受信数
        --      4ATM-25は、修正不可能なHECエラーを含めた HECエラー受信
        --      回数を示す
        ::= { mpAtmCCPhyStatisticsEntry 3 }

mpAtmCCPhyStatUncorrectHecErrCounters       OBJECT-TYPE
        SYNTAX  Counter
        ACCESS  read-only
        STATUS  mandatory
        DESCRIPTION
                "The number of cells reveived by the port with un-correctable
                 HEC error.
                   NOTE: At the 4ATM-25 card, this object is always ZERO."
        --      修正可能なHECエラー受信数
        --      4ATM-25は常に０が読める
        ::= { mpAtmCCPhyStatisticsEntry 4 }

mpAtmCCPhyStatB1ErrCounters       OBJECT-TYPE
        SYNTAX  Counter
        ACCESS  read-only
        STATUS  mandatory
        DESCRIPTION
                "The number of cells with B1 error.
                   NOTE: At the 4ATM-25 card, this object is always ZERO."
        --      Ｂ１エラー回数
        --      4ATM-25は常に０が読める
        ::= { mpAtmCCPhyStatisticsEntry 5 }

mpAtmCCPhyStatB2ErrCounters       OBJECT-TYPE
        SYNTAX  Counter
        ACCESS  read-only
        STATUS  mandatory
        DESCRIPTION
                "The number of cells with B2 error.
                 NOTE: This object is ATM-S155 and ATM-M155 only.
                       Other cards are always ZERO."
        --      Ｂ２エラー回数
        --      ATM-S155とATM-M155のみ有効。その他のカードは常に０が読める
        ::= { mpAtmCCPhyStatisticsEntry 6 }

mpAtmCCPhyStatB3ErrCounters       OBJECT-TYPE
        SYNTAX  Counter
        ACCESS  read-only
        STATUS  mandatory
        DESCRIPTION
                "The number of cells with B3 error
                 NOTE: This object is ATM-S155 and ATM-M155 only.
                       Other cards are always ZERO."
        --      Ｂ３エラー回数
        --      ATM-S155とATM-M155のみ有効。その他のカードは常に０が読める
        ::= { mpAtmCCPhyStatisticsEntry 7 }


mpAtmCCPhyStatFebeCounters       OBJECT-TYPE
        SYNTAX  Counter
        ACCESS  read-only
        STATUS  mandatory
        DESCRIPTION
                "The number of cells with FEBE error.
                   NOTE: At the 4ATM-25 card, this object is always ZERO."
        --      FEBEエラー回数
        --      4ATM-25は常に０が読める
        ::= { mpAtmCCPhyStatisticsEntry 8 }

mpAtmCCPhyStatSymbolErrCounters       OBJECT-TYPE
        SYNTAX  Counter
        ACCESS  read-only
        STATUS  mandatory
        DESCRIPTION
                "The number of cells with symbol error.
                 NOTE: This object is 4ATM-25 only.
                       Other cards are always ZERO."
        --      シンボルエラー回数
        --      4ATM-25のみ有効。その他のカードは常に０が読める
        ::= { mpAtmCCPhyStatisticsEntry 9 }

mpAtmCCPhyStatParityErrCounters       OBJECT-TYPE
        SYNTAX  Counter
        ACCESS  read-only
        STATUS  mandatory
        DESCRIPTION
                "The number of cells with parity error.
                   NOTE: At the 4ATM-25 card, this object is always ZERO."
        --      パリティエラー回数
        --      4ATM-25は常に０が読める
        ::= { mpAtmCCPhyStatisticsEntry 10 }


--
--    回線アラーム情報参照テーブル                    @001 追加
--

mpAtmCCPortAlarmStatisticsTable OBJECT-TYPE
        SYNTAX  SEQUENCE OF MpAtmCCPortAlarmStatisticsEntry
        ACCESS  not-accessible
        STATUS  mandatory
        DESCRIPTION
                "Table of port alarm infomation."
        --      ポートアラーム発生回数情報
        ::= { mpAtmCCStatistics 5 }

mpAtmCCPortAlarmStatisticsEntry OBJECT-TYPE
        SYNTAX  MpAtmCCPortAlarmStatisticsEntry
        ACCESS  not-accessible
        STATUS  mandatory
        DESCRIPTION
                " An entry of mpAtmCCPortAlarmStatisticsTable."
        --      ポートアラーム発生回数情報テーブルのエントリ
        INDEX{ ifIndex }
        ::= { mpAtmCCPortAlarmStatisticsTable 1 }

MpAtmCCPortAlarmStatisticsEntry ::=
        SEQUENCE {
                mpAtmCCPortAlarmStatRedLosCounters
                        Counter,
                mpAtmCCPortAlarmStatRedLofCounters
                        Counter,
                mpAtmCCPortAlarmStatRedMsAisCounters
                        Counter,
                mpAtmCCPortAlarmStatRedLopCounters
                        Counter,
                mpAtmCCPortAlarmStatRedPAisCounters
                        Counter,
                mpAtmCCPortAlarmStatRedLocCounters
                        Counter,
                mpAtmCCPortAlarmStatRedResetCounters
                        Counter,
                mpAtmCCPortAlarmStatRedCcRedCounters
                        Counter,
                mpAtmCCPortAlarmStatRedOofCounters
                        Counter,
                mpAtmCCPortAlarmStatRedAisCounters
                        Counter,
                mpAtmCCPortAlarmStatRedPOofCounters
                        Counter,
                mpAtmCCPortAlarmStatRedBadSigCounters
                        Counter,
                mpAtmCCPortAlarmStatRedLcdCounters
                        Counter,
                mpAtmCCPortAlarmStatRedLinkAisCounters
                        Counter,
                mpAtmCCPortAlarmStatRedInfo0Counters
                        Counter,
                mpAtmCCPortAlarmStatYelMsRdiCounters
                        Counter,
                mpAtmCCPortAlarmStatYelPRdiCounters
                        Counter,
                mpAtmCCPortAlarmStatYelCcYelCounters
                        Counter,
                mpAtmCCPortAlarmStatYelRaiCounters
                        Counter,
                mpAtmCCPortAlarmStatYelPRaiCounters
                        Counter,
                mpAtmCCPortAlarmStatYelInfo2Counters
                        Counter
        }

mpAtmCCPortAlarmStatRedLosCounters       OBJECT-TYPE
        SYNTAX  Counter
        ACCESS  read-only
        STATUS  mandatory
        DESCRIPTION
                "Total number of LOS alarm detected by HW.
                 NOTE: This object is
                          ATM-S155, ATM-M155, 2ATM-45,
                          2UNI-VMC, 2TRK-6.3I, 4TRK-1.5I
                       only.   Other cards are always ZERO."
        --      LOS発生回数
        --      サポートカード種別：ATM-S155, ATM-M155, 2ATM-45,
        --                          2UNI-VMC, 2TRK-6.3I, 4TRK-1.5I
        ::= { mpAtmCCPortAlarmStatisticsEntry 1 }

mpAtmCCPortAlarmStatRedLofCounters       OBJECT-TYPE
        SYNTAX  Counter
        ACCESS  read-only
        STATUS  mandatory
        DESCRIPTION
                "Total number of LOF alarm detected by HW.
                 NOTE: This object is
                          ATM-S155, ATM-M155, 2TRK-6.3I, 4TRK-1.5I
                       only.   Other cards are always ZERO."
        --      LOF発生回数
        --      サポートカード種別：ATM-S155, ATM-M155, 2TRK-6.3I, 4TRK-1.5I
        ::= { mpAtmCCPortAlarmStatisticsEntry 2 }

mpAtmCCPortAlarmStatRedMsAisCounters       OBJECT-TYPE
        SYNTAX  Counter
        ACCESS  read-only
        STATUS  mandatory
        DESCRIPTION
                "Total number of MS-AIS alarm detected by HW.
                 NOTE: This object is
                          ATM-S155, ATM-M155
                       only.   Other cards are always ZERO."
        --      MS-AIS発生回数
        --      サポートカード種別：ATM-S155, ATM-M155
        ::= { mpAtmCCPortAlarmStatisticsEntry 3 }

mpAtmCCPortAlarmStatRedLopCounters       OBJECT-TYPE
        SYNTAX  Counter
        ACCESS  read-only
        STATUS  mandatory
        DESCRIPTION
                "Total number of LOP alarm detected by HW.
                 NOTE: This object is
                          ATM-S155, ATM-M155
                       only.   Other cards are always ZERO."
        --      LOP発生回数
        --      サポートカード種別：ATM-S155, ATM-M155
        ::= { mpAtmCCPortAlarmStatisticsEntry 4 }

mpAtmCCPortAlarmStatRedPAisCounters       OBJECT-TYPE
        SYNTAX  Counter
        ACCESS  read-only
        STATUS  mandatory
        DESCRIPTION
                "Total number of P-AIS alarm detected by HW.
                 NOTE: This object is
                          ATM-S155, ATM-M155
                       only.   Other cards are always ZERO."
        --      P-AIS発生回数
        --      サポートカード種別：ATM-S155, ATM-M155
        ::= { mpAtmCCPortAlarmStatisticsEntry 5 }

mpAtmCCPortAlarmStatRedLocCounters       OBJECT-TYPE
        SYNTAX  Counter
        ACCESS  read-only
        STATUS  mandatory
        DESCRIPTION
                "Total number of LOC alarm detected by HW.
                 NOTE: This object is
                          ATM-S155, ATM-M155
                       only.   Other cards are always ZERO."
        --      LOC発生回数
        --      サポートカード種別：ATM-S155, ATM-M155
        ::= { mpAtmCCPortAlarmStatisticsEntry 6 }

mpAtmCCPortAlarmStatRedResetCounters       OBJECT-TYPE
        SYNTAX  Counter
        ACCESS  read-only
        STATUS  mandatory
        DESCRIPTION
                "Total number of Reset alarm detected by HW.
                 NOTE: This object is
                          ATM-S155, ATM-M155
                       only.   Other cards are always ZERO."
        --      Reset発生回数
        --      サポートカード種別：ATM-S155, ATM-M155
        ::= { mpAtmCCPortAlarmStatisticsEntry 7 }

mpAtmCCPortAlarmStatRedCcRedCounters       OBJECT-TYPE
        SYNTAX  Counter
        ACCESS  read-only
        STATUS  mandatory
        DESCRIPTION
                "Total number of CC-RED alarm detected by HW.
                 NOTE: This object is ATM CARDs only."
        --      CC-RED発生回数
        --      サポートカード種別：ATMカード
        ::= { mpAtmCCPortAlarmStatisticsEntry 8 }

mpAtmCCPortAlarmStatRedOofCounters       OBJECT-TYPE
        SYNTAX  Counter
        ACCESS  read-only
        STATUS  mandatory
        DESCRIPTION
                "Total number of OOF alarm detected by HW.
                 NOTE: This object is 2ATM-45 only.
                       Other cards are always ZERO."
        --      OOF発生回数
        --      サポートカード種別：2ATM-45
        ::= { mpAtmCCPortAlarmStatisticsEntry 9 }

mpAtmCCPortAlarmStatRedAisCounters       OBJECT-TYPE
        SYNTAX  Counter
        ACCESS  read-only
        STATUS  mandatory
        DESCRIPTION
                "Total number of AIS alarm detected by HW.
                 NOTE: This object is
                          2ATM-45, 2TRK-6.3I, 4TRK-1.5I
                       only.   Other cards are always ZERO."
        --      AIS発生回数
        --      サポートカード種別：2ATM-45, 2TRK-6.3I, 4ATM-1.5I
        ::= { mpAtmCCPortAlarmStatisticsEntry 10 }

mpAtmCCPortAlarmStatRedPOofCounters       OBJECT-TYPE
        SYNTAX  Counter
        ACCESS  read-only
        STATUS  mandatory
        DESCRIPTION
                "Total number of P-OOF alarm detected by HW.
                 NOTE: This object is 2ATM-45, 2TRK-6.3I, 4TRK-1.5I
                       only.   Other cards are always ZERO."
        --      P-OOF発生回数
        --      サポートカード種別：2ATM-45, 2TRK-6.3I, 4ATM-1.5I
        ::= { mpAtmCCPortAlarmStatisticsEntry 11 }

mpAtmCCPortAlarmStatRedBadSigCounters       OBJECT-TYPE
        SYNTAX  Counter
        ACCESS  read-only
        STATUS  mandatory
        DESCRIPTION
                "Total number of Bad-sig alarm detected by HW.
                 NOTE: This object is 4ATM-45 only.
                       Other cards are always ZERO."
        --      Bad-sig発生回数
        --      サポートカード種別：4ATM-25
        ::= { mpAtmCCPortAlarmStatisticsEntry 12 }

mpAtmCCPortAlarmStatRedLcdCounters       OBJECT-TYPE
        SYNTAX  Counter
        ACCESS  read-only
        STATUS  mandatory
        DESCRIPTION
                "Total number of LCD alarm detected by HW.
                 NOTE: This object is
                          2UNI-VMC, 2TRK-6.3I, 4TRK-1.5I, 2TRK-192K
                       only.   Other cards are always ZERO."
        --      LCD発生回数
        --      サポートカード種別：2UNI-VMC, 2TRK-6.3I, 4ATM-1.5I
        --                          2TRK-192KI
        ::= { mpAtmCCPortAlarmStatisticsEntry 13 }

mpAtmCCPortAlarmStatRedLinkAisCounters       OBJECT-TYPE
        SYNTAX  Counter
        ACCESS  read-only
        STATUS  mandatory
        DESCRIPTION
                "Total number of LINK-AIS alarm detected by HW.
                 NOTE: This object is
                          2TRK-6.3I, 4TRK-1.5I, 2TRK-192K
                       only.   Other cards are always ZERO."
        --      LINK-AIS発生回数
        --      サポートカード種別：2TRK-6.3I, 4ATM-1.5I, 2TRK-192KI
        ::= { mpAtmCCPortAlarmStatisticsEntry 14 }

mpAtmCCPortAlarmStatRedInfo0Counters       OBJECT-TYPE
        SYNTAX  Counter
        ACCESS  read-only
        STATUS  mandatory
        DESCRIPTION
                "Total number of INDO0 alarm detected by HW.
                 NOTE: This object is 2TRK-192KI only.
                       Other cards are always ZERO."
        --      INFO0発生回数
        --      サポートカード種別：2TRK-192KI
        ::= { mpAtmCCPortAlarmStatisticsEntry 15 }

mpAtmCCPortAlarmStatYelMsRdiCounters       OBJECT-TYPE
        SYNTAX  Counter
        ACCESS  read-only
        STATUS  mandatory
        DESCRIPTION
                "Total number of MS-RDI alarm detected by HW.
                 NOTE: This object is
                          ATM-S155, ATM-M155
                       only.   Other cards are always ZERO."
        --      MS-RDI発生回数
        --      サポートカード種別：ATM-S155, ATM-M155
        ::= { mpAtmCCPortAlarmStatisticsEntry 16 }

mpAtmCCPortAlarmStatYelPRdiCounters       OBJECT-TYPE
        SYNTAX  Counter
        ACCESS  read-only
        STATUS  mandatory
        DESCRIPTION
                "Total number of P-RDI alarm detected by HW.
                 NOTE: This object is
                          ATM-S155, ATM-M155
                       only.   Other cards are always ZERO."
        --      P-RDI発生回数
        --      サポートカード種別：ATM-S155, ATM-M155
        ::= { mpAtmCCPortAlarmStatisticsEntry 17 }

mpAtmCCPortAlarmStatYelCcYelCounters       OBJECT-TYPE
        SYNTAX  Counter
        ACCESS  read-only
        STATUS  mandatory
        DESCRIPTION
                "Total number of CC-YEL alarm detected by HW.
                 NOTE: This object is ATM CARDs only."
        --      CC-YEL発生回数
        --      サポートカード種別：ATMカード
        ::= { mpAtmCCPortAlarmStatisticsEntry 18 }

mpAtmCCPortAlarmStatYelRaiCounters       OBJECT-TYPE
        SYNTAX  Counter
        ACCESS  read-only
        STATUS  mandatory
        DESCRIPTION
                "Total number of RAI alarm detected by HW.
                 NOTE: This object is
                          2ATM-45, 2TRK-6.3I, 4TRK-1.5I
                       only.   Other cards are always ZERO."
        --      RAI発生回数
        --      サポートカード種別：2ATM-45, 2TRK-6.3I, 4TRK-1.5I
        ::= { mpAtmCCPortAlarmStatisticsEntry 19 }

mpAtmCCPortAlarmStatYelPRaiCounters       OBJECT-TYPE
        SYNTAX  Counter
        ACCESS  read-only
        STATUS  mandatory
        DESCRIPTION
                "Total number of P-RAI alarm detected by HW.
                 NOTE: This object is 2ATM-45 only.
                       Other cards are always ZERO."
        --      P-RAI発生回数
        --      サポートカード種別：2ATM-45
        ::= { mpAtmCCPortAlarmStatisticsEntry 20 }

mpAtmCCPortAlarmStatYelInfo2Counters       OBJECT-TYPE
        SYNTAX  Counter
        ACCESS  read-only
        STATUS  mandatory
        DESCRIPTION
                "Total number of INFO2 alarm detected by HW.
                 NOTE: This object is 2TRK-192KI only.
                       Other cards are always ZERO."
        --      INFO2発生回数
        --      サポートカード種別：2TRK-192KI
        ::= { mpAtmCCPortAlarmStatisticsEntry 21 }


--
--    ＶＰトンネリング統計情報参照テーブル            @001 追加
--

mpAtmCCVpTunnellingStatisticsTable OBJECT-TYPE
        SYNTAX  SEQUENCE OF MpAtmCCVpTunnellingStatisticsEntry
        ACCESS  not-accessible
        STATUS  mandatory
        DESCRIPTION
                "This table indicate traffic counter information
                 per VP-tunnelling."
        --      VP Tunnellingポートの統計情報
        ::= { mpAtmCCStatistics 6 }

mpAtmCCVpTunnellingStatisticsEntry OBJECT-TYPE
        SYNTAX  MpAtmCCVpTunnellingStatisticsEntry
        ACCESS  not-accessible
        STATUS  mandatory
        DESCRIPTION
                " An entry of mpAtmCCVpTunnellingStatisticsTable."
        --      ＰＨＹチップが収集している品質情報テーブルのエントリ
        INDEX{ ifIndex }
        ::= { mpAtmCCVpTunnellingStatisticsTable 1 }

MpAtmCCVpTunnellingStatisticsEntry ::=
        SEQUENCE {
                mpAtmCCVpTunStatTmtCellsCounters
                        Counter,
                mpAtmCCVpTunStatRcvCellsCounters
                        Counter
        }

mpAtmCCVpTunStatTmtCellsCounters       OBJECT-TYPE
        SYNTAX  Counter
        ACCESS  read-only
        STATUS  mandatory
        DESCRIPTION
                "The number of cells transmitted regardless of error status."
        --     VP Tunnellingポート 送信セル数
        ::= { mpAtmCCVpTunnellingStatisticsEntry 1 }

mpAtmCCVpTunStatRcvCellsCounters       OBJECT-TYPE
        SYNTAX  Counter
        ACCESS  read-only
        STATUS  mandatory
        DESCRIPTION
                "The number of cells received regardless of error status"
        --      VP Tunnellingポート 受信セル数
        ::= { mpAtmCCVpTunnellingStatisticsEntry 2 }


--
--    登録して収集するＶＣ統計情報                             @011 追加
--

mpAtmCCVccStatisticsRegTable OBJECT-TYPE
        SYNTAX  SEQUENCE OF MpAtmCCVccStatisticsRegEntry
        ACCESS  not-accessible
        STATUS  mandatory
        DESCRIPTION
                " Indicate traffic counter information per connection."
        --      ＶＣ統計情報を登録・参照するテーブル
        ::= { mpAtmCCStatistics 7 }

mpAtmCCVccStatisticsRegEntry OBJECT-TYPE
        SYNTAX  MpAtmCCVccStatisticsRegEntry
        ACCESS  not-accessible
        STATUS  mandatory
        DESCRIPTION
                " Entry of traffic per connection."
        --      コネクション毎のトラヒックのエントリ
        INDEX{ ifIndex, mpAtmCCVccStatRegVpi, mpAtmCCVccStatRegVci }
        ::= { mpAtmCCVccStatisticsRegTable 1 }

MpAtmCCVccStatisticsRegEntry ::=
        SEQUENCE {
                mpAtmCCVccStatRegVpi
                        INTEGER,
                mpAtmCCVccStatRegVci
                        INTEGER,
                mpAtmCCVccStatRegInCellsCounters
                        Counter,
                mpAtmCCVccStatRegOutCellsCounters
                        Counter,
                mpAtmCCVccStatRegStatus
                        INTEGER,
                mpAtmCCVccStatRegErrInfo
                        INTEGER
        }

mpAtmCCVccStatRegVpi       OBJECT-TYPE
        SYNTAX  INTEGER
        ACCESS  not-accessible
        STATUS  mandatory
        DESCRIPTION
                "Indicate value for the specific VPI "
        --      統計情報を収集するVPI
        ::= { mpAtmCCVccStatisticsRegEntry 1 }

mpAtmCCVccStatRegVci       OBJECT-TYPE
        SYNTAX  INTEGER
        ACCESS  not-accessible
        STATUS  mandatory
        DESCRIPTION
                "Indicate value for the specific VCI "
        --      統計情報を収集するVCI
        ::= { mpAtmCCVccStatisticsRegEntry 2 }

mpAtmCCVccStatRegInCellsCounters       OBJECT-TYPE
        SYNTAX  Counter
        ACCESS  read-only
        STATUS  mandatory
        DESCRIPTION
                " The number of receive cells"
        --      受信セル数
        ::= { mpAtmCCVccStatisticsRegEntry 3 }

mpAtmCCVccStatRegOutCellsCounters      OBJECT-TYPE
        SYNTAX  Counter
        ACCESS  read-only
        STATUS  mandatory
        DESCRIPTION
                " The number of transmit cells"
        --      送信セル数
        ::= { mpAtmCCVccStatisticsRegEntry 4 }

mpAtmCCVccStatRegStatus    OBJECT-TYPE
        SYNTAX  INTEGER{
                        start(1),
                        stop(2)
                       }
        ACCESS  read-write
        STATUS  mandatory
        DESCRIPTION
                "This variable indicates the registratoin status.
                 - 'start', which indicates that start and collecting the
                    taffic information.
                 - 'stop', which indicates that stopn and delete the traffic
                   information."
        --      統計情報の要求状態
        --      startで統計情報の登録をすると共に収集を開始し、
        --      stopで収集を停止すると共に統計情報を削除する
        ::= { mpAtmCCVccStatisticsRegEntry 5 }

mpAtmCCVccStatRegErrInfo    OBJECT-TYPE
        SYNTAX  INTEGER
        ACCESS  read-only
        STATUS  mandatory
        DESCRIPTION
            "Indicats the result of setting to the
             mpAtmCCVccStatRegStatus."
        --      mpAtmCCVccStatRegStatusへの要求の処理結果
        ::= { mpAtmCCVccStatisticsRegEntry 99 }



--
--    ＡＴＭリソース管理情報                          @001 追加
--

        mpAtmCCResourceControl      OBJECT IDENTIFIER ::= { mpAtmCallCtl 5 }

--
--    ポート管理データ情報参照テーブル                @001 追加
--

mpAtmCCPortResourceInfomationTable OBJECT-TYPE
        SYNTAX  SEQUENCE OF MpAtmCCPortResourceInfomationEntry
        ACCESS  not-accessible
        STATUS  mandatory
        DESCRIPTION
                "This table indicate the resource infomation at the
                 ATM port.
                 NOTE:
                   This table is supported the physical port only."
        --      ＡＴＭリソース管理の情報を表示するテーブル
        ::= { mpAtmCCResourceControl 1 }

mpAtmCCPortResourceInfomationEntry OBJECT-TYPE
        SYNTAX  MpAtmCCPortResourceInfomationEntry
        ACCESS  not-accessible
        STATUS  mandatory
        DESCRIPTION
                " Entry of mpAtmCCPortResourceInfomationTable."
        --      ＡＴＭリソース管理情報のエントリ
        INDEX{ ifIndex }
        ::= { mpAtmCCPortResourceInfomationTable 1 }

MpAtmCCPortResourceInfomationEntry ::=
        SEQUENCE {
                mpAtmCCPortResInfoPortSpeed
                        Gauge,
                mpAtmCCPortResInfoMaxVpiBits
                        INTEGER,
                mpAtmCCPortResInfoMaxVciBits
                        INTEGER,
                mpAtmCCPortResInfoMaxVPC
                        INTEGER,
                mpAtmCCPortResInfoMaxVCC
                        INTEGER,
                mpAtmCCPortResInfoMaxSvpcVpi
                        INTEGER,
                mpAtmCCPortResInfoMaxSvccVpi
                        INTEGER,
                mpAtmCCPortResInfoMinSvccVci
                        INTEGER,
                mpAtmCCPortResInfoShaperKind
                        INTEGER,
                mpAtmCCPortResInfoVpTunnellingConfig
                        INTEGER,
                mpAtmCCPortResInfoSvccVciHuntWay
                        INTEGER,
                mpAtmCCPortResInfoVpiCounters
                        Counter,
                mpAtmCCPortResInfoVpcCounters
                        Counter,
                mpAtmCCPortResInfoVccCounters
                        Counter
        }

mpAtmCCPortResInfoPortSpeed       OBJECT-TYPE
        SYNTAX  Gauge
        ACCESS  read-only
        STATUS  mandatory
        DESCRIPTION
                "The port's bandwidth in bit per second at this ATM port."
        --      ポートスピード
        ::= { mpAtmCCPortResourceInfomationEntry 1 }

mpAtmCCPortResInfoMaxVpiBits       OBJECT-TYPE
        SYNTAX  INTEGER
        ACCESS  read-only
        STATUS  mandatory
        DESCRIPTION
                "The number of VPI bits at this ATM port."
        --      VPIのビット数
        ::= { mpAtmCCPortResourceInfomationEntry 2 }

mpAtmCCPortResInfoMaxVciBits       OBJECT-TYPE
        SYNTAX  INTEGER
        ACCESS  read-only
        STATUS  mandatory
        DESCRIPTION
                "The number of VCI bits at this ATM port."
        --      VCIのビット数
        ::= { mpAtmCCPortResourceInfomationEntry 3 }

mpAtmCCPortResInfoMaxVPC       OBJECT-TYPE
        SYNTAX  INTEGER
        ACCESS  read-only
        STATUS  mandatory
        DESCRIPTION
                "The maximum number of VPCs ( PVPs and SVPs )
                 supported at this port."
        --      最大ＶＰコネクション数
        ::= { mpAtmCCPortResourceInfomationEntry 4 }

mpAtmCCPortResInfoMaxVCC       OBJECT-TYPE
        SYNTAX  INTEGER
        ACCESS  read-only
        STATUS  mandatory
        DESCRIPTION
                "The maximum number of VCCs ( PVCs and SVCs )
                 supported at this port."
        --      最大ＶＣコネクション数
        ::= { mpAtmCCPortResourceInfomationEntry 5 }

mpAtmCCPortResInfoMaxSvpcVpi       OBJECT-TYPE
        SYNTAX  INTEGER
        ACCESS  read-only
        STATUS  mandatory
        DESCRIPTION
                "The maximum VPI that the signaling stack on
                 the ATM interface is configured to support for
                 allocation to switched virtual path connections."
        --      SVPCコネクション最大VPI
        ::= { mpAtmCCPortResourceInfomationEntry 6 }

mpAtmCCPortResInfoMaxSvccVpi       OBJECT-TYPE
        SYNTAX  INTEGER
        ACCESS  read-only
        STATUS  mandatory
        DESCRIPTION
                "The maximum VPI that the signaling stack on
                 the ATM interface is configured to support for
                 allocation to switched virtual channel connections."
        --      SVCCコネクション最大VPI
        ::= { mpAtmCCPortResourceInfomationEntry 7 }

mpAtmCCPortResInfoMinSvccVci       OBJECT-TYPE
        SYNTAX  INTEGER
        ACCESS  read-only
        STATUS  mandatory
        DESCRIPTION
                "The minimum VPI that the signalling stack is
                 configured to support for allocation to switched
                 virtual channel connections."
        --      SVCCコネクション最小VCI
        ::= { mpAtmCCPortResourceInfomationEntry 8 }

mpAtmCCPortResInfoShaperKind       OBJECT-TYPE
        SYNTAX  INTEGER{
                    none(1),     -- シェーパーなし
                    vp(2),       -- VPシェーパー
                    vc(3),       -- VCシェーパー
                    vpAndVc(4)   -- VPシェーパー＋VPシェーパー
                }
        ACCESS  read-only
        STATUS  mandatory
        DESCRIPTION
                "The kind of shaper at this port."
        --      シェーパー種別
        ::= { mpAtmCCPortResourceInfomationEntry 9 }

mpAtmCCPortResInfoVpTunnellingConfig       OBJECT-TYPE
        SYNTAX  INTEGER{
                    notConfigured(1),  -- 登録無し
                    configured(2)      -- 登録有り
                }
        ACCESS  read-only
        STATUS  mandatory
        DESCRIPTION
                "Indicates whether the vp-tunnelling is configered
                 at this port."
        --      ＶＰトンネリング登録表示
        ::= { mpAtmCCPortResourceInfomationEntry 10 }


mpAtmCCPortResInfoSvccVciHuntWay       OBJECT-TYPE
        SYNTAX  INTEGER{
                    low2high(1),  -- 若番から老番へハント
                    high2low(2)   -- 老番から若番へハント
                }
        ACCESS  read-only
        STATUS  mandatory
        DESCRIPTION
                "This value indicates the way of VCI use at the SVCs.
                 The value low2high indicates that hunt the lowest not-used
                 VCI when received the SETUP message.
                 The value low2high indicates that hunt the highest not-used
                 VCI when received the SETUP message."
        --      SVCC VCI ハント方向
        ::= { mpAtmCCPortResourceInfomationEntry 11 }

mpAtmCCPortResInfoVpiCounters       OBJECT-TYPE
        SYNTAX  Counter
        ACCESS  read-only
        STATUS  mandatory
        DESCRIPTION
                "The number of using VPIs at this port."
        --      ポート内ＶＰ使用数
        ::= { mpAtmCCPortResourceInfomationEntry 12 }

mpAtmCCPortResInfoVpcCounters       OBJECT-TYPE
        SYNTAX  Counter
        ACCESS  read-only
        STATUS  mandatory
        DESCRIPTION
                "The number of VPCs ( PVPs and SVPs )
                 established at this port."
        --      ＶＰコネクション設定数
        ::= { mpAtmCCPortResourceInfomationEntry 13 }

mpAtmCCPortResInfoVccCounters       OBJECT-TYPE
        SYNTAX  Counter
        ACCESS  read-only
        STATUS  mandatory
        DESCRIPTION
                "The number of VCCs ( PVCs and SVCs )
                 established at this port."
        --      ＶＣコネクション設定数
        ::= { mpAtmCCPortResourceInfomationEntry 14 }


--
--    帯域管理データ情報参照テーブル                  @001 追加
--

mpAtmCCPortBandwidthInfomationTable OBJECT-TYPE
        SYNTAX  SEQUENCE OF MpAtmCCPortBandwidthInfomationEntry
        ACCESS  not-accessible
        STATUS  mandatory
        DESCRIPTION
                "This table indicate that infom the bandwidth at
                 the ATM port."
        --      ＡＴＭリソース管理の帯域情報を表示するテーブル
        ::= { mpAtmCCResourceControl 2 }

mpAtmCCPortBandwidthInfomationEntry OBJECT-TYPE
        SYNTAX  MpAtmCCPortBandwidthInfomationEntry
        ACCESS  not-accessible
        STATUS  mandatory
        DESCRIPTION
                " Entry of mpAtmCCPortBandwidthInfomationTable."
        --      ＡＴＭリソース管理の帯域情報を表示するエントリ
        INDEX{ ifIndex, mpAtmCCPortBwInfoVpi }                   -- @005修正
        ::= { mpAtmCCPortBandwidthInfomationTable 1 }

MpAtmCCPortBandwidthInfomationEntry ::=
        SEQUENCE {
                mpAtmCCPortBwInfoVpi                             -- @005追加
                        INTEGER,                                 -- @005追加
                mpAtmCCPortBwInfoRawBandwidthBps
                        INTEGER,
                mpAtmCCPortBwInfoRawBandwidthCps
                        INTEGER,
                mpAtmCCPortBwInfoTmitUsedBwCps
                        INTEGER,
                mpAtmCCPortBwInfoRcvUsedBwCps
                        INTEGER,
                mpAtmCCPortBwInfoVciCounters
                        Counter
        }

mpAtmCCPortBwInfoVpi    OBJECT-TYPE                       -- @005追加
        SYNTAX  INTEGER
        ACCESS  not-accessible
        STATUS  mandatory
        DESCRIPTION
                "A index value at this table."
        --      VPI値
        ::= { mpAtmCCPortBandwidthInfomationEntry 1 }

mpAtmCCPortBwInfoRawBandwidthBps       OBJECT-TYPE
        SYNTAX  INTEGER
        ACCESS  read-only
        STATUS  mandatory
        DESCRIPTION
                "Adminsitratively desired bandwidth size
                 in kilo bit per second for this ATM port."
        --      ポートの全帯域（Ｋｂｐｓ）
        ::= { mpAtmCCPortBandwidthInfomationEntry 2 }   -- @005修正

mpAtmCCPortBwInfoRawBandwidthCps       OBJECT-TYPE
        SYNTAX  INTEGER
        ACCESS  read-only
        STATUS  mandatory
        DESCRIPTION
                "Adminsitratively desired bandwidth size
                 in cell per second for this ATM port."
        --      ポートの全帯域（ｃｐｓ）
        ::= { mpAtmCCPortBandwidthInfomationEntry 3 }   -- @005修正

mpAtmCCPortBwInfoTmitUsedBwCps       OBJECT-TYPE
        SYNTAX  INTEGER
        ACCESS  read-only
        STATUS  mandatory
        DESCRIPTION
                "The current using transmission bandwidth value ( total of
                 assigned bandwidth for each connections ) in cell per
                 second for this ATM port."
        --      使用中の送信帯域
        ::= { mpAtmCCPortBandwidthInfomationEntry 4 }   -- @005修正

mpAtmCCPortBwInfoRcvUsedBwCps       OBJECT-TYPE
        SYNTAX  INTEGER
        ACCESS  read-only
        STATUS  mandatory
        DESCRIPTION
                "The current using receved bandwidth value ( total of
                 assigned bandwidth for each connections ) in cell per
                 second for this ATM port."
        --      使用中の受信帯域
        ::= { mpAtmCCPortBandwidthInfomationEntry 5 }   -- @005修正

mpAtmCCPortBwInfoVciCounters       OBJECT-TYPE
        SYNTAX  INTEGER
        ACCESS  read-only
        STATUS  mandatory
        DESCRIPTION
                "The number of using VCIs at this port."
        --      ポート内ＶＣ使用数
        ::= { mpAtmCCPortBandwidthInfomationEntry 6 }   -- @005修正


--
--    ポート帯域管理データ情報参照テーブル（２）               @011 追加
--

mpAtmCCBwInfoPortTable OBJECT-TYPE
        SYNTAX  SEQUENCE OF MpAtmCCBwInfoPortEntry
        ACCESS  not-accessible
        STATUS  mandatory
        DESCRIPTION
                "This table indicate the resource infomation at the
                 ATM port and vp-tunneling port"
        --      ＡＴＭリソース管理の帯域情報を表示するテーブル（２）
        ::= { mpAtmCCResourceControl 3 }

mpAtmCCBwInfoPortEntry OBJECT-TYPE
        SYNTAX  MpAtmCCBwInfoPortEntry
        ACCESS  not-accessible
        STATUS  mandatory
        DESCRIPTION
                " Entry of mpAtmCCBwInfoPortTable."
        --      ＡＴＭリソース管理の帯域情報を表示するエントリ
        INDEX{ ifIndex }
        ::= { mpAtmCCBwInfoPortTable 1 }

MpAtmCCBwInfoPortEntry ::=
        SEQUENCE {
                mpAtmCCBwInfoPortRawBandwidthBps
                        INTEGER,
                mpAtmCCBwInfoPortRawBandwidthCps
                        INTEGER,
                mpAtmCCBwInfoPortTmitUsedBwCps
                        INTEGER,
                mpAtmCCBwInfoPortRcvUsedBwCps
                        INTEGER,
                mpAtmCCBwInfoPortTmitRemainBwCps
                        INTEGER,
                mpAtmCCBwInfoPortRcvRemainBwCps
                        INTEGER,
                mpAtmCCBwInfoPortVpTunneling
                        INTEGER
        }

mpAtmCCBwInfoPortRawBandwidthBps    OBJECT-TYPE
        SYNTAX  INTEGER
        ACCESS  read-only
        STATUS  mandatory
        DESCRIPTION
                "Adminsitratively desired bandwidth size
                 in kilo bit per second for this ATM port."
        -- ポート全帯域（ｂｐｓ）
        ::= { mpAtmCCBwInfoPortEntry 1 }

mpAtmCCBwInfoPortRawBandwidthCps    OBJECT-TYPE
        SYNTAX  INTEGER
        ACCESS  read-only
        STATUS  mandatory
        DESCRIPTION
                "Adminsitratively desired bandwidth size
                 in cell per second for this ATM port."
        -- ポート全帯域（ｃｐｓ）
        ::= { mpAtmCCBwInfoPortEntry 2 }

mpAtmCCBwInfoPortTmitUsedBwCps    OBJECT-TYPE
        SYNTAX  INTEGER
        ACCESS  read-only
        STATUS  mandatory
        DESCRIPTION
                "The current using transmission bandwidth value ( total of
                 assigned bandwidth for each connections ) in cell per
                 second for this ATM port."
        -- 送信方向使用中帯域（ｃｐｓ）
        ::= { mpAtmCCBwInfoPortEntry 3 }

mpAtmCCBwInfoPortRcvUsedBwCps    OBJECT-TYPE
        SYNTAX  INTEGER
        ACCESS  read-only
        STATUS  mandatory
        DESCRIPTION
                "The current using receved bandwidth value ( total of
                 assigned bandwidth for each connections ) in cell per
                 second for this ATM port."
        -- 受信方向使用中帯域（ｃｐｓ）
        ::= { mpAtmCCBwInfoPortEntry 4 }

mpAtmCCBwInfoPortTmitRemainBwCps    OBJECT-TYPE
        SYNTAX  INTEGER
        ACCESS  read-only
        STATUS  mandatory
        DESCRIPTION
                "The current remaining transmission bandwidth value (
                 total of assigned bandwidth for each connections ) in
                 cell per second for this ATM port."
        -- 送信方向残り帯域（ｃｐｓ）
        ::= { mpAtmCCBwInfoPortEntry 5 }

mpAtmCCBwInfoPortRcvRemainBwCps    OBJECT-TYPE
        SYNTAX  INTEGER
        ACCESS  read-only
        STATUS  mandatory
        DESCRIPTION
                "The current remaining receved bandwidth value ( total
                 of assigned bandwidth for each connections ) in cell
                 per second for this ATM port."
        -- 受信方向残り帯域（ｃｐｓ）
        ::= { mpAtmCCBwInfoPortEntry 6 }

mpAtmCCBwInfoPortVpTunneling       OBJECT-TYPE
        SYNTAX  INTEGER(1..2)
        ACCESS  read-only
        STATUS  mandatory
        DESCRIPTION
                "VP-Tunneling indication.
                   1:VP-Tunneling
                   2:Not VP-Tunneling"
        --      VP-Tunneling表示
        --        1:VP-Tunneling
        --        2:専用線
        ::= { mpAtmCCBwInfoPortEntry 7 }



--
--      プロトコル制御                                @001 追加
--

        mpAtmCCProtocol     OBJECT IDENTIFIER ::= { mpAtmCallCtl 6 }

--
--      SSCOP                                         @001 追加
--

mpAtmCCSscopTable OBJECT-TYPE
        SYNTAX  SEQUENCE OF MpAtmCCSscopEntry
        ACCESS  not-accessible
        STATUS  mandatory
        DESCRIPTION
                "SSCOP parameter Table"
        ::= { mpAtmCCProtocol 1 }

mpAtmCCSscopEntry OBJECT-TYPE
        SYNTAX  MpAtmCCSscopEntry
        ACCESS  not-accessible
        STATUS  mandatory
        DESCRIPTION
                "Entry of mpATMCCSscopTable."
        INDEX { ifIndex }
        ::= { mpAtmCCSscopTable 1 }

MpAtmCCSscopEntry ::=
        SEQUENCE {
                mpAtmCCSscopTimerPoll
                        INTEGER,
                mpAtmCCSscopTimerNoResponce
                        INTEGER,
                mpAtmCCSscopTimerKeepAlive
                        INTEGER,
                mpAtmCCSscopTimerIdle
                        INTEGER,
                mpAtmCCSscopTimerCc
                        INTEGER,
                mpAtmCCSscopMaxCc
                        INTEGER,
                mpAtmCCSscopMaxPd
                        INTEGER,
                mpAtmCCSscopMaxStat
                        INTEGER,
                mpAtmCCSscopClearBuffs
                        INTEGER,
                mpAtmCCSscopCredit
                        INTEGER
        }

mpAtmCCSscopTimerPoll       OBJECT-TYPE
        SYNTAX  INTEGER
        ACCESS  read-write
        STATUS  mandatory
        DESCRIPTION
                "Expert variable: timer in milliseconds
                 (default is 750 msecs for Uni 3.1)."
        REFERENCE
                "ATM Forum User-Network Interface Specification,
                 Version 3.1"
        --      Timer_POLL 単位：ｍｓ
        DEFVAL { 750 }
        ::= { mpAtmCCSscopEntry 1 }

mpAtmCCSscopTimerNoResponce       OBJECT-TYPE
        SYNTAX  INTEGER
        ACCESS  read-write
        STATUS  mandatory
        DESCRIPTION
                "Expert variable: timer in milliseconds
                 (default is 7000 msecs for Uni 3.1)."
        REFERENCE
                "ATM Forum User-Network Interface Specification,
                 Version 3.1"
        --      Timer_NO_RESPONCE 単位：ｍｓ
        DEFVAL { 7000 }
        ::= { mpAtmCCSscopEntry 2 }

mpAtmCCSscopTimerKeepAlive       OBJECT-TYPE
        SYNTAX  INTEGER
        ACCESS  read-write
        STATUS  mandatory
        DESCRIPTION
                "Expert variable: timer in milliseconds
                 (default is 2000 msecs for Uni 3.1)."
        REFERENCE
                "ATM Forum User-Network Interface Specification,
                 Version 3.1"
        --      Timer_KEEP_ALIVE 単位：ｍｓ
        DEFVAL { 2000 }
        ::= { mpAtmCCSscopEntry 3 }

mpAtmCCSscopTimerIdle       OBJECT-TYPE
        SYNTAX  INTEGER
        ACCESS  read-write
        STATUS  mandatory
        DESCRIPTION
                "Expert variable: timer in milliseconds
                 (default is 1500 msecs for Uni 3.1)."
        REFERENCE
                "ATM Forum User-Network Interface Specification,
                 Version 3.1"
        --      Timer_IDLE 単位：ｍｓ
        DEFVAL { 15000 }
        ::= { mpAtmCCSscopEntry 4 }

mpAtmCCSscopTimerCc       OBJECT-TYPE
        SYNTAX  INTEGER
        ACCESS  read-write
        STATUS  mandatory
        DESCRIPTION
                "Expert variable: timer in milliseconds
                  (default is 1000 msecs for Uni 3.1)."
        REFERENCE
                "ATM Forum User-Network Interface Specification,
                 Version 3.1"
        --      Timer_CC 単位：秒
        DEFVAL { 1000 }
        ::= { mpAtmCCSscopEntry 5 }

mpAtmCCSscopMaxCc       OBJECT-TYPE
        SYNTAX  INTEGER
        ACCESS  read-write
        STATUS  mandatory
        DESCRIPTION
                "Expert variable
                  (default is 4 for Uni 3.1)."
        --      MaxCC
        REFERENCE
                "ATM Forum User-Network Interface Specification,
                 Version 3.1"
        DEFVAL { 4 }
        ::= { mpAtmCCSscopEntry 6 }

mpAtmCCSscopMaxPd       OBJECT-TYPE
        SYNTAX  INTEGER
        ACCESS  read-write
        STATUS  mandatory
        DESCRIPTION
                "Expert variable
                  (default is 25 for Uni 3.1)."
        --      MaxPD
        REFERENCE
                "ATM Forum User-Network Interface Specification,
                 Version 3.1"
        DEFVAL { 25 }
        ::= { mpAtmCCSscopEntry 7 }

mpAtmCCSscopMaxStat       OBJECT-TYPE
        SYNTAX  INTEGER
        ACCESS  read-write
        STATUS  mandatory
        DESCRIPTION
                "Expert variable
                  (default is 67 for Uni 3.1)."
        --      MaxSTAT
        REFERENCE
                "ATM Forum User-Network Interface Specification,
                 Version 3.1"
        DEFVAL { 67 }
        ::= { mpAtmCCSscopEntry 8 }

mpAtmCCSscopClearBuffs       OBJECT-TYPE
        SYNTAX  INTEGER{
                    yes(1),
                    no(2)
                }
        ACCESS  read-only
        STATUS  mandatory
        DESCRIPTION
                "Expert variable."
        --      Clear-Buffs
        REFERENCE
                "ATM Forum User-Network Interface Specification,
                 Version 3.1"
        ::= { mpAtmCCSscopEntry 9 }

mpAtmCCSscopCredit       OBJECT-TYPE
        SYNTAX  INTEGER{
                    yes(1),
                    no(2)
                }
        ACCESS  read-only
        STATUS  mandatory
        DESCRIPTION
                "Expert variable."
        --      credit
        REFERENCE
                "ATM Forum User-Network Interface Specification,
                 Version 3.1"
        ::= { mpAtmCCSscopEntry 10 }



--
--      ILMI                                          @001 追加
--

mpAtmCCIlmiTable OBJECT-TYPE
        SYNTAX  SEQUENCE OF MpAtmCCIlmiEntry
        ACCESS  not-accessible
        STATUS  mandatory
        DESCRIPTION
                "ILMI parameter Table"
        ::= { mpAtmCCProtocol 2 }

mpAtmCCIlmiEntry OBJECT-TYPE
        SYNTAX  MpAtmCCIlmiEntry
        ACCESS  not-accessible
        STATUS  mandatory
        DESCRIPTION
                "Entry of mpATMCCIlmiTable."
        INDEX { ifIndex }
        ::= { mpAtmCCIlmiTable 1 }

MpAtmCCIlmiEntry ::=
        SEQUENCE {
                mpAtmCCIlmiConfigStatus
                        INTEGER,
                mpAtmCClmiMaxTransmissions
                        INTEGER,
                mpAtmCCIlmiRetransmitInterval
                        INTEGER
         }

mpAtmCCIlmiConfigStatus OBJECT-TYPE
         SYNTAX  INTEGER {
                         enabled(1),
                         disabled(2)
                 }
         ACCESS  read-write
         STATUS  mandatory
         DESCRIPTION
                 "Indicates whether ilmi is currently enabled at
                  this interface."
         --      IMLIを行うか否か
         DEFVAL  { enabled }
         ::= { mpAtmCCIlmiEntry 1 }

mpAtmCClmiMaxTransmissions OBJECT-TYPE
         SYNTAX  INTEGER
         ACCESS  read-write
         STATUS  mandatory
         DESCRIPTION
                 "In a situation where a request is not receiving
                  a response within
                  mpAtmCCLimiRetransmitInterval, the number of
                  consecutive transmissions/non-responses that will
                  cause the UME to declare a loss of ILMI
                  connectivity
                  This variable is intended to promote
                  interoperability, so no range restriction is
                  given."
         --      ヘルスチェック リトライ回数
         DEFVAL { 4 }
         ::= { mpAtmCCIlmiEntry 2 }

mpAtmCCIlmiRetransmitInterval OBJECT-TYPE
         SYNTAX  INTEGER
         ACCESS  read-write
         STATUS  mandatory
         DESCRIPTION
                 "The time in seconds between retransmissions of
                  ILMI requests
                  This variable is intended to promote
                  interoperability, so no range restriction is
                  given."
         --      ヘルスチェック間隔 単位：秒
         DEFVAL { 5 }
         ::= { mpAtmCCIlmiEntry 3 }


--
--      SIGNALLING                                    @001 追加
--

mpAtmCCSignallingTable OBJECT-TYPE
        SYNTAX  SEQUENCE OF MpAtmCCSignallingEntry
        ACCESS  not-accessible
        STATUS  mandatory
        DESCRIPTION
                "ILMI parameter Table"
        ::= { mpAtmCCProtocol 3 }

mpAtmCCSignallingEntry OBJECT-TYPE
        SYNTAX  MpAtmCCSignallingEntry
        ACCESS  not-accessible
        STATUS  mandatory
        DESCRIPTION
                "Entry of mpATMCCSignallingTable."
        INDEX { ifIndex }
        ::= { mpAtmCCSignallingTable 1 }

MpAtmCCSignallingEntry ::=
        SEQUENCE {
                mpAtmCCSignallingT301
                        INTEGER,
                mpAtmCCSignallingT303
                        INTEGER,
                mpAtmCCSignallingT308
                        INTEGER,
                mpAtmCCSignallingT309
                        INTEGER,
                mpAtmCCSignallingT310
                        INTEGER,
                mpAtmCCSignallingT313
                        INTEGER,
                mpAtmCCSignallingT316
                        INTEGER,
                mpAtmCCSignallingT317
                        INTEGER,
                mpAtmCCSignallingT322
                        INTEGER,
                mpAtmCCSignallingT331
                        INTEGER,
                mpAtmCCSignallingT397
                        INTEGER,
                mpAtmCCSignallingT398
                        INTEGER,
                mpAtmCCSignallingT399
                        INTEGER
        }

mpAtmCCSignallingT301 OBJECT-TYPE
         SYNTAX  INTEGER
         ACCESS  read-write
         STATUS  mandatory
         DESCRIPTION
                 "Expert variable: timer in seconds"
         --      T301 のタイマー値
         REFERENCE
                 "ATM Forum User-Network Interface Specification,
                  Version 3.1"
         DEFVAL  { 180 }
         ::= { mpAtmCCSignallingEntry 1 }

mpAtmCCSignallingT303 OBJECT-TYPE
         SYNTAX  INTEGER
         ACCESS  read-write
         STATUS  mandatory
         DESCRIPTION
                 "Expert variable: timer in seconds"
         --      T303 のタイマー値
         REFERENCE
                 "ATM Forum User-Network Interface Specification,
                  Version 3.1"
         DEFVAL  { 4 }
         ::= { mpAtmCCSignallingEntry 2 }

mpAtmCCSignallingT308 OBJECT-TYPE
         SYNTAX  INTEGER
         ACCESS  read-write
         STATUS  mandatory
         DESCRIPTION
                 "Expert variable: timer in seconds"
         --      T308 のタイマー値
         REFERENCE
                 "ATM Forum User-Network Interface Specification,
                  Version 3.1"
         DEFVAL  { 30 }
         ::= { mpAtmCCSignallingEntry 3 }

mpAtmCCSignallingT309 OBJECT-TYPE
         SYNTAX  INTEGER
         ACCESS  read-write
         STATUS  mandatory
         DESCRIPTION
                 "Expert variable: timer in seconds"
         --      T309 のタイマー値
         REFERENCE
                 "ATM Forum User-Network Interface Specification,
                  Version 3.1"
         DEFVAL  { 10 }
         ::= { mpAtmCCSignallingEntry 4 }

mpAtmCCSignallingT310 OBJECT-TYPE
         SYNTAX  INTEGER
         ACCESS  read-write
         STATUS  mandatory
         DESCRIPTION
                 "Expert variable: timer in seconds"
         --      T310 のタイマー値
         REFERENCE
                 "ATM Forum User-Network Interface Specification,
                  Version 3.1"
         DEFVAL  { 30 }
         ::= { mpAtmCCSignallingEntry 5 }

mpAtmCCSignallingT313 OBJECT-TYPE
         SYNTAX  INTEGER
         ACCESS  read-write
         STATUS  mandatory
         DESCRIPTION
                 "Expert variable: timer in seconds"
         --      T313 のタイマー値
         REFERENCE
                 "ATM Forum User-Network Interface Specification,
                  Version 3.1"
         DEFVAL  { 4 }
         ::= { mpAtmCCSignallingEntry 6 }

mpAtmCCSignallingT316 OBJECT-TYPE
         SYNTAX  INTEGER
         ACCESS  read-write
         STATUS  mandatory
         DESCRIPTION
                 "Expert variable: timer in seconds"
         --      T316 のタイマー値
         REFERENCE
                 "ATM Forum User-Network Interface Specification,
                  Version 3.1"
         DEFVAL  { 120 }
         ::= { mpAtmCCSignallingEntry 7 }

mpAtmCCSignallingT317 OBJECT-TYPE
         SYNTAX  INTEGER
         ACCESS  read-write
         STATUS  mandatory
         DESCRIPTION
                 "Expert variable: timer in seconds"
         --      T317 のタイマー値
         REFERENCE
                 "ATM Forum User-Network Interface Specification,
                  Version 3.1"
         DEFVAL  { 180 }
         ::= { mpAtmCCSignallingEntry 8 }

mpAtmCCSignallingT322 OBJECT-TYPE
         SYNTAX  INTEGER
         ACCESS  read-write
         STATUS  mandatory
         DESCRIPTION
                 "Expert variable: timer in seconds"
         --      T322 のタイマー値
         REFERENCE
                 "ATM Forum User-Network Interface Specification,
                  Version 3.1"
         DEFVAL  { 4 }
         ::= { mpAtmCCSignallingEntry 9 }

mpAtmCCSignallingT331 OBJECT-TYPE
         SYNTAX  INTEGER
         ACCESS  read-write
         STATUS  mandatory
         DESCRIPTION
                 "Expert variable: timer in seconds"
         --      T331 のタイマー値
         REFERENCE
                 "ATM Forum User-Network Interface Specification,
                  Version 3.1"
         DEFVAL  { 60 }
         ::= { mpAtmCCSignallingEntry 10 }

mpAtmCCSignallingT397 OBJECT-TYPE
         SYNTAX  INTEGER
         ACCESS  read-write
         STATUS  mandatory
         DESCRIPTION
                 "Expert variable: timer in seconds"
         --      T397 のタイマー値
         REFERENCE
                 "ATM Forum User-Network Interface Specification,
                  Version 3.1"
         DEFVAL  { 180 }
         ::= { mpAtmCCSignallingEntry 11 }

mpAtmCCSignallingT398 OBJECT-TYPE
         SYNTAX  INTEGER
         ACCESS  read-write
         STATUS  mandatory
         DESCRIPTION
                 "Expert variable: timer in seconds"
         --      T398 のタイマー値
         REFERENCE
                 "ATM Forum User-Network Interface Specification,
                  Version 3.1"
         DEFVAL  { 4 }
         ::= { mpAtmCCSignallingEntry 12 }

mpAtmCCSignallingT399 OBJECT-TYPE
         SYNTAX  INTEGER
         ACCESS  read-write
         STATUS  mandatory
         DESCRIPTION
                 "Expert variable: timer in seconds"
         --      T399 のタイマー値
         REFERENCE
                 "ATM Forum User-Network Interface Specification,
                  Version 3.1"
         DEFVAL  { 34 }
         ::= { mpAtmCCSignallingEntry 13 }


--
--      Trap Infomation                                @003 追加
--

mpAtmCCProtocolTrapInfoTable OBJECT-TYPE
        SYNTAX  SEQUENCE OF MpAtmCCProtocolTrapInfoEntry
        ACCESS  not-accessible
        STATUS  mandatory
        DESCRIPTION
                "ATM Protocol Control Trap Infomation tabale"
        ::= { mpAtmCCProtocol 4 }

mpAtmCCProtocolTrapInfoEntry OBJECT-TYPE
        SYNTAX  MpAtmCCProtocolTrapInfoEntry
        ACCESS  not-accessible
        STATUS  mandatory
        DESCRIPTION
                "Entry of mpATMCCProtocolTrapInfoTable."
        INDEX { mpAtmCCProtocolTrapInfoIndex }
        ::= { mpAtmCCProtocolTrapInfoTable 1 }

MpAtmCCProtocolTrapInfoEntry ::=
        SEQUENCE {
                mpAtmCCProtocolTrapInfoIndex
                        INTEGER,
                mpAtmCCProtocolTrapInfoCause
                        INTEGER
                 }

mpAtmCCProtocolTrapInfoIndex OBJECT-TYPE
         SYNTAX  INTEGER
         ACCESS  read-only
         STATUS  mandatory
         DESCRIPTION
                 "The index value at this table"
         --      本テーブルのindex
         ::= { mpAtmCCProtocolTrapInfoEntry 1 }

mpAtmCCProtocolTrapInfoCause OBJECT-TYPE
         SYNTAX  INTEGER
         ACCESS  read-only
         STATUS  mandatory
         DESCRIPTION
                 "Indicates why this trap send "
         --      Trapを送信した要因
         ::= { mpAtmCCProtocolTrapInfoEntry 2 }


--
--    ＡＴＭパストレース情報                          @001 追加
--

        mpAtmCCPathTrace      OBJECT IDENTIFIER ::= { mpAtmCallCtl 7 }

--
--    ＶＣＣ接続情報参照テーブル                      @001 追加
--

mpAtmCCVccStatusTable OBJECT-TYPE
        SYNTAX  SEQUENCE OF MpAtmCCVccStatusEntry
        ACCESS  not-accessible
        STATUS  mandatory
        DESCRIPTION
                "This table indicate the vcc status infomation at the
                 ATM port."
        --      ＶＣＣの状態を表示するテーブル
        ::= { mpAtmCCPathTrace 1 }

mpAtmCCVccStatusEntry OBJECT-TYPE
        SYNTAX  MpAtmCCVccStatusEntry
        ACCESS  not-accessible
        STATUS  mandatory
        DESCRIPTION
                " Entry of mpAtmCCVccStatusTable."
        --      ＶＣＣ状態テーブルのエントリ
        INDEX{ mpAtmCCVccStatusOrgPort,
               mpAtmCCVccStatusOrgVpi,
               mpAtmCCVccStatusOrgVci
             }
        ::= { mpAtmCCVccStatusTable 1 }

MpAtmCCVccStatusEntry ::=
        SEQUENCE {
               mpAtmCCVccStatusOrgPort
                        INTEGER,
               mpAtmCCVccStatusOrgVpi
                        INTEGER,
               mpAtmCCVccStatusOrgVci
                        INTEGER,
               mpAtmCCVccStatusDestPort
                        INTEGER,
               mpAtmCCVccStatusDestVpi
                        INTEGER,
               mpAtmCCVccStatusDestVci
                        INTEGER,
               mpAtmCCVccStatusPathKind
                        INTEGER,
               mpAtmCCVccStatusOrgCallKind
                        INTEGER,
               mpAtmCCVccStatusDestCallKind
                        INTEGER,
               mpAtmCCVccStatusAdminStatus
                        INTEGER,
               mpAtmCCVccStatusOperStatus
                        INTEGER,
               mpAtmCCVccStatusInsStatus
                        INTEGER,
               mpAtmCCVccStatusOrgPortVpTunneling    -- @007 追加
                        INTEGER,
               mpAtmCCVccStatusDestPortVpTunneling   -- @007 追加
                        INTEGER,
               mpAtmCCVccStatusConnCastType          -- @011 追加
                        INTEGER
        }

mpAtmCCVccStatusOrgPort       OBJECT-TYPE
        SYNTAX  INTEGER
        ACCESS  not-accessible
        STATUS  mandatory
        DESCRIPTION
                "Specified PORT number."
        --      指定ポート番号（ifIndex）
        ::= { mpAtmCCVccStatusEntry 1 }

mpAtmCCVccStatusOrgVpi       OBJECT-TYPE
        SYNTAX  INTEGER
        ACCESS  not-accessible
        STATUS  mandatory
        DESCRIPTION
                "Specified VPI number."
        --      指定VPI番号
        ::= { mpAtmCCVccStatusEntry 2 }

mpAtmCCVccStatusOrgVci       OBJECT-TYPE
        SYNTAX  INTEGER
        ACCESS  not-accessible
        STATUS  mandatory
        DESCRIPTION
                "Specified VCI number."
        --      指定VCI番号
        ::= { mpAtmCCVccStatusEntry 3 }

mpAtmCCVccStatusDestPort       OBJECT-TYPE
        SYNTAX  INTEGER
        ACCESS  read-only
        STATUS  mandatory
        DESCRIPTION
                "Destination PORT number."
        --      接続先ポート番号（ifIndex）
        ::= { mpAtmCCVccStatusEntry 4 }

mpAtmCCVccStatusDestVpi       OBJECT-TYPE
        SYNTAX  INTEGER
        ACCESS  read-only
        STATUS  mandatory
        DESCRIPTION
                "Destination VPI number."
        --      接続先VPI番号
        ::= { mpAtmCCVccStatusEntry 5 }

mpAtmCCVccStatusDestVci       OBJECT-TYPE
        SYNTAX  INTEGER
        ACCESS  read-only
        STATUS  mandatory
        DESCRIPTION
                "Destination VCI number."
        --      接続先VCI番号
        ::= { mpAtmCCVccStatusEntry 6 }

mpAtmCCVccStatusPathKind       OBJECT-TYPE
        SYNTAX  INTEGER{
                        pvc(1),
                        softpvc(2),
                        insPvc(3),            -- @005修正
                        pvp(4),               -- @005追加
                        softpvp(5)            -- @005追加
                       }
        ACCESS  read-only
        STATUS  mandatory
        DESCRIPTION
                "Path classification."
        --      パス種別
        ::= { mpAtmCCVccStatusEntry 7 }

mpAtmCCVccStatusOrgCallKind       OBJECT-TYPE
        SYNTAX  INTEGER{
                        calling(1),      -- 発側
                        outgoing(2),     -- 中継出側
                        incoming(3),     -- 中継入り側
                        called(4)        -- 着側
                       }
        ACCESS  read-only
        STATUS  mandatory
        DESCRIPTION
                "Port classification for specified an edge point."
        --      指定端点ポート種別
        ::= { mpAtmCCVccStatusEntry 8 }

mpAtmCCVccStatusDestCallKind       OBJECT-TYPE
        SYNTAX  INTEGER{
                        calling(1),      -- 発側
                        outgoing(2),     -- 中継出側
                        incoming(3),     -- 中継入り側
                        called(4)        -- 着側
                       }
        ACCESS  read-only
        STATUS  mandatory
        DESCRIPTION
                "Port classification for destination an edge point."
        --      接続先端点ポート種別
        ::= { mpAtmCCVccStatusEntry 9 }

mpAtmCCVccStatusAdminStatus       OBJECT-TYPE
        SYNTAX  INTEGER{
                       up(1),
                       down(2)
                       }
        ACCESS  read-only
        STATUS  mandatory
        DESCRIPTION
                "Control status."
        --      管理状態
        ::= { mpAtmCCVccStatusEntry 10 }

mpAtmCCVccStatusOperStatus       OBJECT-TYPE
        SYNTAX  INTEGER{
                       up(1),
                       down(2)
                       }
        ACCESS  read-only
        STATUS  mandatory
        DESCRIPTION
                "Connection status."
        --      接続状態
        ::= { mpAtmCCVccStatusEntry 11 }

mpAtmCCVccStatusInsStatus       OBJECT-TYPE
        SYNTAX  INTEGER{
                        trunkPort(1),  -- 専用線接続
                        insPort(2)     -- INS回線接続
                        }
        ACCESS  read-only
        STATUS  mandatory
        DESCRIPTION
                "INS detour indication."
        --      INS迂回表示
        ::= { mpAtmCCVccStatusEntry 12 }


mpAtmCCVccStatusOrgPortVpTunneling       OBJECT-TYPE
        SYNTAX  INTEGER(1..2)
        ACCESS  read-only
        STATUS  mandatory
        DESCRIPTION
                "Original port VP-Tunneling indication.
                   1:VP-Tunneling
                   2:Not VP-Tunneling"
        --      ORG側VP-Tunneling表示
        --        1:VP-Tunneling
        --        2:専用線
        ::= { mpAtmCCVccStatusEntry 13 }


mpAtmCCVccStatusDestPortVpTunneling       OBJECT-TYPE
        SYNTAX  INTEGER(1..2)
        ACCESS  read-only
        STATUS  mandatory
        DESCRIPTION
                "Destination port VP-Tunneling indication.
                   1:VP-Tunneling
                   2:Not VP-Tunneling"
        --      DEST側VP-Tunneling表示
        --        1:VP-Tunneling
        --        2:専用線
        ::= { mpAtmCCVccStatusEntry 14 }

mpAtmCCVccStatusConnCastType       OBJECT-TYPE              -- @011 追加
        SYNTAX  INTEGER{
                        p2p(1),
                        p2mpRoot(2),
                        p2mpLeaf(3)
                       }
        ACCESS  read-only
        STATUS  mandatory
        DESCRIPTION
              "The type of topology of a connection (point-
              to-point, point-to-multipoint)."
        --    indexで指定した端点のコネクションの種別
        ::= { mpAtmCCVccStatusEntry 15 }



--
--    ＰＶＣパストレース登録                      @007 追加
--

mpAtmCCPvcTraceControlTable OBJECT-TYPE
        SYNTAX  SEQUENCE OF MpAtmCCPvcTraceCtlEntry
        ACCESS  not-accessible
        STATUS  mandatory
        DESCRIPTION
                "This is the table type object of the
                 PVC PathTrace registration."
        --      ＰＶＣパストレース登録テーブル
        ::= { mpAtmCCPathTrace 2 }

mpAtmCCPvcTraceCtlEntry OBJECT-TYPE
        SYNTAX  MpAtmCCPvcTraceCtlEntry
        ACCESS  not-accessible
        STATUS  mandatory
        DESCRIPTION
                " Entry of mpAtmCCPvcTraceInfoTable."
        --      ＰＶＣパストレース登録テーブルのエントリ
        INDEX{ mpAtmCCPvcTraceIndex }
        ::= { mpAtmCCPvcTraceControlTable 1 }

MpAtmCCPvcTraceCtlEntry ::=
        SEQUENCE {
               mpAtmCCPvcTraceIndex
                        INTEGER,
               mpAtmCCPvcTraceCtlPathKind
                        INTEGER,
               mpAtmCCPvcTraceCtlIfIndex
                        INTEGER,
               mpAtmCCPvcTraceCtlVpi
                        INTEGER,
               mpAtmCCPvcTraceCtlVci
                        INTEGER,
               mpAtmCCPvcTraceCtlStatus
                        INTEGER
        }

mpAtmCCPvcTraceIndex    OBJECT-TYPE
        SYNTAX  INTEGER(1..10)
        ACCESS  read-only
        STATUS  mandatory
        DESCRIPTION
                "The value of this object identifies the
                 PVC PathTrace collection number."
--               PVCパストレース収集番号
        ::= { mpAtmCCPvcTraceCtlEntry 1 }

mpAtmCCPvcTraceCtlPathKind    OBJECT-TYPE
        SYNTAX  INTEGER{
                  vcc(1),
                  vpc(2)
                }
        ACCESS  read-write
        STATUS  mandatory
        DESCRIPTION
                "The value of this object identifies the
                 path kind."
--               パス種別
        ::= { mpAtmCCPvcTraceCtlEntry 2 }

mpAtmCCPvcTraceCtlIfIndex    OBJECT-TYPE
        SYNTAX  INTEGER
        ACCESS  read-write
        STATUS  mandatory
        DESCRIPTION
                "The value of this object identifies the
                 interface number."
--               ポート番号
        ::= { mpAtmCCPvcTraceCtlEntry 3 }

mpAtmCCPvcTraceCtlVpi    OBJECT-TYPE
        SYNTAX  INTEGER
        ACCESS  read-write
        STATUS  mandatory
        DESCRIPTION
                "The value of this object identifies the
                 VPI number."
--               VPI
        ::= { mpAtmCCPvcTraceCtlEntry 4 }

mpAtmCCPvcTraceCtlVci    OBJECT-TYPE
        SYNTAX  INTEGER
        ACCESS  read-write
        STATUS  mandatory
        DESCRIPTION
                "The value of this object identifies the
                 VCI number."
--               VCI
        ::= { mpAtmCCPvcTraceCtlEntry 5 }

mpAtmCCPvcTraceCtlStatus    OBJECT-TYPE
        SYNTAX  INTEGER{
                    idle(1),        -- read-only
                    start(2),       -- write-only
                    collecting(3),  -- read-only
                    done(4),        -- read-only
                    cancel(5),      -- write-only
                    unknown(6)      -- read-ony
                }
        ACCESS  read-write
        STATUS  mandatory
        DESCRIPTION
                "The value of this object identifies the
                 PVC PathTrace condition."
--               ＰＶＣパストレース状態
        ::= { mpAtmCCPvcTraceCtlEntry 6 }


--
--    ＰＶＣパストレース参照                      @007 追加
--


mpAtmCCPvcTraceInfoTable OBJECT-TYPE
        SYNTAX  SEQUENCE OF MpAtmCCPvcTraceInfoEntry
        ACCESS  not-accessible
        STATUS  mandatory
        DESCRIPTION
                "This is the table type object of the
                 PVC PathTrace information."
        --      ＰＶＣパストレース参照テーブル
        ::= { mpAtmCCPathTrace 3 }

mpAtmCCPvcTraceInfoEntry OBJECT-TYPE
--        SYNTAX  MpAtmCCPvcTraceControlEntry
        SYNTAX  MpAtmCCPvcTraceInfoEntry
        ACCESS  not-accessible
        STATUS  mandatory
        DESCRIPTION
                " Entry of mpAtmCCPvcTraceInfoTable."
        --      ＰＶＣパストレース参照テーブルのエントリ
        INDEX{ mpAtmCCPvcTraceIndex, mpAtmCCPvcTraceEntryIndex }
        ::= { mpAtmCCPvcTraceInfoTable 1 }

MpAtmCCPvcTraceInfoEntry ::=
        SEQUENCE {
               mpAtmCCPvcTraceEntryIndex
                        INTEGER,
               mpAtmCCPvcTraceInfoSysName
                        DisplayString,
               mpAtmCCPvcTraceInfoIfIndex
                        INTEGER,
               mpAtmCCPvcTraceInfoVpi
                        INTEGER,
               mpAtmCCPvcTraceInfoVci
                        INTEGER,
               mpAtmCCPvcTraceInfoPathKind
                        INTEGER,
               mpAtmCCPvcTraceInfoCallKind
                        INTEGER,
               mpAtmCCPvcTraceInfoLastSegment
                        INTEGER
        }

mpAtmCCPvcTraceEntryIndex    OBJECT-TYPE
        SYNTAX  INTEGER(1..20)
        ACCESS  not-accessible
        STATUS  mandatory
        DESCRIPTION
                "The value of this object identifies the
                 inside index of PVC PathTrace information."
--              PVCパストレース情報内部index
        ::= { mpAtmCCPvcTraceInfoEntry 1 }

mpAtmCCPvcTraceInfoSysName    OBJECT-TYPE
        SYNTAX  DisplayString(SIZE(0..255))
        ACCESS  read-only
        STATUS  mandatory
        DESCRIPTION
                "The value of this object identifies the
                 node name."
--              ノード名
        ::= { mpAtmCCPvcTraceInfoEntry 2 }

mpAtmCCPvcTraceInfoIfIndex    OBJECT-TYPE
        SYNTAX  INTEGER
        ACCESS  read-only
        STATUS  mandatory
        DESCRIPTION
                "The value of this object identifies the
                 interface number."
--              ポート番号
        ::= { mpAtmCCPvcTraceInfoEntry 3 }

mpAtmCCPvcTraceInfoVpi    OBJECT-TYPE
        SYNTAX  INTEGER
        ACCESS  read-only
        STATUS  mandatory
        DESCRIPTION
                "The value of this object identifies the
                 VPI number."
--              VPI
        ::= { mpAtmCCPvcTraceInfoEntry 4 }

mpAtmCCPvcTraceInfoVci    OBJECT-TYPE
        SYNTAX  INTEGER
        ACCESS  read-only
        STATUS  mandatory
        DESCRIPTION
                "The value of this object identifies the
                 VCI number."
--              VCI
        ::= { mpAtmCCPvcTraceInfoEntry 5 }

mpAtmCCPvcTraceInfoPathKind    OBJECT-TYPE
        SYNTAX  INTEGER{
                    pvc(1),
                    softpvc(2),
                    inspvc(3),
                    pvp(4),
                    softpvp(5)
                }
        ACCESS  read-only
        STATUS  mandatory
        DESCRIPTION
                "The value of this object identifies the
                 path kind."
--              パス種別
        ::= { mpAtmCCPvcTraceInfoEntry 6 }

mpAtmCCPvcTraceInfoCallKind    OBJECT-TYPE
        SYNTAX  INTEGER{
                    calling(1),
                    outgoing(2),
                    incoming(3),
                    called(4)
                }
        ACCESS  read-only
        STATUS  mandatory
        DESCRIPTION
                "The value of this object identifies the
                 connection type."
--              コネクション種別
        ::= { mpAtmCCPvcTraceInfoEntry 7 }

mpAtmCCPvcTraceInfoLastSegment    OBJECT-TYPE
        SYNTAX  INTEGER{
                    notlast(1),
                    last(2)
                }
        ACCESS  read-only
        STATUS  mandatory
        DESCRIPTION
                "The value of this object identifies the
                 last segment."
--              最終表示
        ::= { mpAtmCCPvcTraceInfoEntry 8 }



--
--    ＭＵＸ                                         @002 追加
--

        mpAtmCCMuxMib      OBJECT IDENTIFIER ::= { mpAtmCallCtl 8 }

--
--    ＭＵＸ統計情報参照テーブル                    @002 追加
--

        mpAtmCCMuxStatistics    OBJECT IDENTIFIER ::= { mpAtmCCMuxMib 1 }


mpAtmCCMuxStatReceiveCellsCounters      OBJECT-TYPE
        SYNTAX  Counter
        ACCESS  read-only
        STATUS  mandatory
        DESCRIPTION
                "Counter of MUX receive cells."
        --      受信セル数
        ::= { mpAtmCCMuxStatistics 1 }

mpAtmCCMuxStatReceiveCellsCntOvfCounters      OBJECT-TYPE
        SYNTAX  Counter
        ACCESS  read-only
        STATUS  mandatory
        DESCRIPTION
                "Overflow counter of MUX receive cells counter."
        --      受信セルカウンターオバーフロー回数
        ::= { mpAtmCCMuxStatistics 2 }

mpAtmCCMuxStatDiscardCellsBufOvfCounters      OBJECT-TYPE
        SYNTAX  Counter
        ACCESS  read-only
        STATUS  mandatory
        DESCRIPTION
                "Discard cell counter on buffer overflow."
        --      バッファメモリ不足による廃棄セル数
        ::= { mpAtmCCMuxStatistics 3 }

mpAtmCCMuxStatDiscardCellsBufOvfCntOvfCounters      OBJECT-TYPE
        SYNTAX  Counter
        ACCESS  read-only
        STATUS  mandatory
        DESCRIPTION
                "Overflow counter of discard cell counter on buffer overflow."
        --      バッファメモリ不足による廃棄セル数オバーフロー回数
        ::= { mpAtmCCMuxStatistics 4 }


mpAtmCCMuxStatDiscardCellsHTErrCounters      OBJECT-TYPE
        SYNTAX  Counter
        ACCESS  read-only
        STATUS  mandatory
        DESCRIPTION
                "Discard cell counter on header transration error."
        --      ヘッダ変換エラーによる廃棄セル数
        ::= { mpAtmCCMuxStatistics 5 }

mpAtmCCMuxStatDiscardCellsHTErrCntOvfCounters      OBJECT-TYPE
        SYNTAX  Counter
        ACCESS  read-only
        STATUS  mandatory
        DESCRIPTION
                "Overflow counter of discard cell counter on header transration error."
        --      ヘッダ変換エラーによる廃棄セル数オバーフロー回数
        ::= { mpAtmCCMuxStatistics 6 }


mpAtmCCMuxStatDiscardCellsThresholdOvfCounters      OBJECT-TYPE
        SYNTAX  Counter
        ACCESS  read-only
        STATUS  mandatory
        DESCRIPTION
                "Discard cell counter on threshold overflow."
        --      閾値越えによる廃棄セル数
        ::= { mpAtmCCMuxStatistics 7 }

mpAtmCCMuxStatDiscardCellsThresholdOvfCntOvfCounters      OBJECT-TYPE
        SYNTAX  Counter
        ACCESS  read-only
        STATUS  mandatory
        DESCRIPTION
                "Overflow counter of discard cell counter on threshold overflow."
        --      閾値越えによるによる廃棄セル数オバーフロー回数
        ::= { mpAtmCCMuxStatistics 8 }


--
--    ＶＰトンネリング                              @002 追加
--

        mpAtmCCVpTunneling      OBJECT IDENTIFIER ::= { mpAtmCallCtl 9 }

--
--    ＶＰトンネリングテーブル                      @002 追加
--

mpAtmCCVpTunnelingTable OBJECT-TYPE
        SYNTAX  SEQUENCE OF MpAtmCCVpTunnelingEntry
        ACCESS  not-accessible
        STATUS  mandatory
        DESCRIPTION
                "VP-Tunneling parameter Table"
        --      VP-Tunnelingポート
        ::= { mpAtmCCVpTunneling 1 }

mpAtmCCVpTunnelingEntry OBJECT-TYPE
        SYNTAX  MpAtmCCVpTunnelingEntry
        ACCESS  not-accessible
        STATUS  mandatory
        DESCRIPTION
                " Entry of mpAtmCCVpTunnelingTable."
        --      VP Tunnelingテーブルのエントリ
        INDEX{ ifIndex, mpAtmCCVpTunnelingVpi }
        ::= { mpAtmCCVpTunnelingTable 1 }

MpAtmCCVpTunnelingEntry ::=
        SEQUENCE {
               mpAtmCCVpTunnelingVpi
                        INTEGER,
               mpAtmCCVpTunnelingAdminStatus
                        INTEGER,
               mpAtmCCVpTunnelingOperStatus
                        INTEGER,
               mpAtmCCVpTunnelingSpeed
                        INTEGER,
               mpAtmCCVpTunnelingNeighborInfo
                        INTEGER,
               mpAtmCCVpTunnelingPnniVer
                        INTEGER,
               mpAtmCCVpTunnelingContinuityCheck
                        INTEGER,
               mpAtmCCVpTunnelingTrapState
                        INTEGER,
               mpAtmCCVpTunnelingSeverity
                        INTEGER,
               mpAtmCCVpTunnelingCfgStatus
                        INTEGER,
               mpAtmCCVpTunnelingErrInfo
                        INTEGER
        }

mpAtmCCVpTunnelingVpi       OBJECT-TYPE
        SYNTAX  INTEGER
        ACCESS  not-accessible
        STATUS  mandatory
        DESCRIPTION
                "Specified VPI number."
        --      指定VPI番号
        ::= { mpAtmCCVpTunnelingEntry 1 }

mpAtmCCVpTunnelingAdminStatus       OBJECT-TYPE
        SYNTAX  INTEGER{
                       up(1),
                       down(2)
                       }
        ACCESS  read-write
        STATUS  mandatory
        DESCRIPTION
                "Control status."
        --      管理状態
        ::= { mpAtmCCVpTunnelingEntry 2 }

mpAtmCCVpTunnelingOperStatus       OBJECT-TYPE
        SYNTAX  INTEGER{
                       up(1),
                       down(2)
                       }
        ACCESS  read-only
        STATUS  mandatory
        DESCRIPTION
                "Connection status."
        --      接続状態
        ::= { mpAtmCCVpTunnelingEntry 3 }

mpAtmCCVpTunnelingSpeed       OBJECT-TYPE
        SYNTAX  INTEGER
        ACCESS  read-only
        STATUS  mandatory
        DESCRIPTION
                "VP bandwidth(kbps)."
        --      VP帯域
        ::= { mpAtmCCVpTunnelingEntry 4 }

mpAtmCCVpTunnelingNeighborInfo       OBJECT-TYPE
        SYNTAX  INTEGER
        ACCESS  read-only
        STATUS  mandatory
        DESCRIPTION
                "Neighbor Info(ifIndex)."
        --      隣接Node情報(ifIndex)
        ::= { mpAtmCCVpTunnelingEntry 5 }

mpAtmCCVpTunnelingPnniVer       OBJECT-TYPE
        SYNTAX  INTEGER
        ACCESS  read-only
        STATUS  mandatory
        DESCRIPTION
                "PNNI Signaling version."
        --      PNNI シグナリングバージョン
        ::= { mpAtmCCVpTunnelingEntry 6 }

mpAtmCCVpTunnelingContinuityCheck       OBJECT-TYPE
        SYNTAX  INTEGER{
                       off(1),
                       on(2)
                       }
        ACCESS  read-only
        STATUS  mandatory
        DESCRIPTION
                "Continuity Check."
        --      コンティニュティチェック制御
        ::= { mpAtmCCVpTunnelingEntry 7 }

mpAtmCCVpTunnelingTrapState       OBJECT-TYPE
        SYNTAX  INTEGER{
                       off(1),
                       on(2)
                       }
        ACCESS  read-only
        STATUS  mandatory
        DESCRIPTION
                "Trap State."
        --      TRAP出力制御
        ::= { mpAtmCCVpTunnelingEntry 8 }

mpAtmCCVpTunnelingSeverity       OBJECT-TYPE
        SYNTAX  INTEGER{
                       critical(1),
                       major(2),
                       minor(3),
                       warning(4),
                       informational(5)
                       }
        ACCESS  read-only
        STATUS  mandatory
        DESCRIPTION
                "Severity."
        --      アラーム重要度
        ::= { mpAtmCCVpTunnelingEntry 9 }

mpAtmCCVpTunnelingCfgStatus      OBJECT-TYPE
        SYNTAX  INTEGER {
                        enable(1),
                        cancel(2),
                        delete(3),
                        unknown(4)
                        }
        ACCESS  read-write
        STATUS  mandatory
        DESCRIPTION
                "Configuration setting start object. If this object is
                 set the setting of the configuration is started."
--                        ConfigSet開始設定
        DEFVAL { unknown }
        ::= { mpAtmCCVpTunnelingEntry 98 }

mpAtmCCVpTunnelingErrInfo    OBJECT-TYPE
        SYNTAX  INTEGER
        ACCESS  read-only
        STATUS  mandatory
        DESCRIPTION
                "Object that the configuration setting result is set up."
--                        Config設定結果
        ::= { mpAtmCCVpTunnelingEntry 99 }



--
--    ＰＶＣパステスト                              @004 追加
--

        mpAtmCCPathTest      OBJECT IDENTIFIER ::= { mpAtmCallCtl 10 }

--
--    ＰＶＣパステスト登録テーブル            @004 追加
--

mpAtmCCPathTestTable OBJECT-TYPE
        SYNTAX  SEQUENCE OF MpAtmCCPathTestEntry
        ACCESS  not-accessible
        STATUS  mandatory
        DESCRIPTION
                "This Table is control for the PATH TEST(F5 OAM CELL)
                 function"
        --      PVC path test設定
        ::= { mpAtmCCPathTest 1 }

mpAtmCCPathTestEntry OBJECT-TYPE
        SYNTAX  MpAtmCCPathTestEntry
        ACCESS  not-accessible
        STATUS  mandatory
        DESCRIPTION
                " Entry of mpAtmCCPathTestTable."
        --      Pvc path test送信側設定テーブルのエントリ
        INDEX{ ifIndex, mpAtmCCPathTestVpi, mpAtmCCPathTestVci }
        ::= { mpAtmCCPathTestTable 1 }

MpAtmCCPathTestEntry ::=
        SEQUENCE {
               mpAtmCCPathTestVpi
                        INTEGER,
               mpAtmCCPathTestVci
                        INTEGER,
               mpAtmCCPathTestStatus
                        INTEGER,
               mpAtmCCPathTestSendDirection         -- @006追加
                        INTEGER,                    -- @006追加
               mpAtmCCPathTestSendTime
                        INTEGER,
               mpAtmCCPathTestSendCellsCounters
                        Counter,
               mpAtmCCPathTestRcvCellsCounters
                        Counter,
               mpAtmCCPathTestErrInfo
                        INTEGER
        }

mpAtmCCPathTestVpi    OBJECT-TYPE
        SYNTAX  INTEGER
        ACCESS  read-only                           -- @006変更
        STATUS  mandatory
        DESCRIPTION
                "Index value for the specific VPI"
--               PVCパステストを行うVPI
        ::= { mpAtmCCPathTestEntry 1 }

mpAtmCCPathTestVci    OBJECT-TYPE
        SYNTAX  INTEGER
        ACCESS  read-only                           -- @006変更
        STATUS  mandatory
        DESCRIPTION
                "Index value for the specific VCI"
--               PVCパステストを行うVCI
        ::= { mpAtmCCPathTestEntry 2 }

mpAtmCCPathTestStatus    OBJECT-TYPE
        SYNTAX  INTEGER{                                          -- @005定義値変更
                    testReq(1),       -- test point registration (read-only)
                    sendStart(2),     -- start sending F5OAM-cell
                    sendStop(3),      -- stop sending F5OAM-cell
                    loopSet(4),       -- loop point registration
                    loopRelease(5),   -- loop point deletion (read-only)
                    delete(6),        -- delete send or loop point (write-only)
                    unknown(7)        -- unknown status(read-only)  --   -- @006修正
                }
        ACCESS  read-write
        STATUS  mandatory
        DESCRIPTION
                "The value of this object identifies the desired status of this table."
--               PVCパステスト端点の設定
        DEFVAL{ unknown }                               -- @006修正
        ::= { mpAtmCCPathTestEntry 3 }

mpAtmCCPathTestSendDirection    OBJECT-TYPE             -- @006追加
        SYNTAX  INTEGER{
                    port(1),      -- to port
                    mux(2)        -- to mux
                       }
        ACCESS  read-write
        STATUS  mandatory
        DESCRIPTION
                "Indicate the direction which send the F5 OAM cells."
--               F5 OAM cell送信方向
--               送信側のみ有効
        DEFVAL{ port }
        ::= { mpAtmCCPathTestEntry 4 }

mpAtmCCPathTestSendTime    OBJECT-TYPE
        SYNTAX  INTEGER(1..68400)                       -- @005修正
        ACCESS  read-write
        STATUS  mandatory
        DESCRIPTION
                "The amount of time this path will send the F5 OAM cells."
--               PVCパステスト実行時間（秒）
--               送信側のみ有効
        DEFVAL{ 5 }
        ::= { mpAtmCCPathTestEntry 5 }                  -- @006修正

mpAtmCCPathTestSendCellsCounters    OBJECT-TYPE
        SYNTAX  Counter
        ACCESS  read-only
        STATUS  mandatory
        DESCRIPTION
                "A amount of the number of F5 OAM cells sending."
--               F5OAM-Cell送信セル数
        ::= { mpAtmCCPathTestEntry 6 }                  -- @006修正

mpAtmCCPathTestRcvCellsCounters    OBJECT-TYPE
        SYNTAX  Counter
        ACCESS  read-only
        STATUS  mandatory
        DESCRIPTION
                "A aomut of the number of F5 OAN cells received."
--               F5OAM-Cell受信セル数
        ::= { mpAtmCCPathTestEntry 7 }                  -- @006修正

mpAtmCCPathTestErrInfo    OBJECT-TYPE
        SYNTAX  INTEGER
        ACCESS  read-only
        STATUS  mandatory
        DESCRIPTION
                "A additonal infomation for the error-response."
--               PVCパステスト登録処理エラー情報
        ::= { mpAtmCCPathTestEntry 99 }



--
--    ＰＶＣグループ切り替え                                           @007追加
--

        mpAtmCCPvcGroupCutover      OBJECT IDENTIFIER ::= { mpAtmCallCtl 11 }


--
--    ＰＶＣグループ機能基本情報                                       @007追加
--

       mpAtmCCPvcGroupCutoverBaseInfo   OBJECT IDENTIFIER ::= { mpAtmCCPvcGroupCutover 1 }


mpAtmCCPvcGroupCutoverEnable    OBJECT-TYPE
        SYNTAX  INTEGER{
                    ture(1),   -- サポート
                    false(2)   -- 未サポート
                }
        ACCESS  read-only
        STATUS  mandatory
        DESCRIPTION
                "Specifies whether the node is currently operating the
                 PVC-Group-CutOver functions. If the value is 'false', then it
                 can not support the PVC-Group-CutOver service. This attribute
                 reflects the node configration data in the PVC-Group-CutOver
                 Service Request State and functiins condition.
                 It can change only Command Line Interface(CLI).
                 (Node reboot is indispensable chage to the PVC-Group-CutOver
                  Service Request Status )"
--               PVCグループ切り替えサポート表示
--               局データ内のグループ切り替えサポート要求と機能の状態を反映して
--               いる。サポート要求の変更は（ノードのリブートが必要なため）CLI
--               からしかサポートしない。
        ::= { mpAtmCCPvcGroupCutoverBaseInfo 1 }

mpAtmCCPvcGroupCutoverStatus    OBJECT-TYPE                       -- @010追加
        SYNTAX  INTEGER{
                           null(1),
                           underAvtivate(2),
                           underDeactivate(3)
                       }
        ACCESS  read-only
        STATUS  mandatory
        DESCRIPTION
                "The current status of PVC-Group-Cutover function status."
--              PVCグループ切り替え処理状態表示
        ::= { mpAtmCCPvcGroupCutoverBaseInfo 2 }



--
--    総括グループ                                                     @007追加
--

       mpAtmCCUnitePvcGroup   OBJECT IDENTIFIER ::= { mpAtmCCPvcGroupCutover 2 }


--
--    スカラー型ＭＩＢ                                                 @007追加
--

       mpAtmCCUpgcBaseInfo   OBJECT IDENTIFIER ::= { mpAtmCCUnitePvcGroup 1 }


mpAtmCCUpgcTotalGroupNumber    OBJECT-TYPE
        SYNTAX  INTEGER
        ACCESS  read-only
        STATUS  mandatory
        DESCRIPTION
                "The total number of registerd to Unite Pvc Group in this node."
--               総括グループ登録数
        ::= { mpAtmCCUpgcBaseInfo 1 }

mpAtmCCUpgcBaseActiveGroupNumber    OBJECT-TYPE
        SYNTAX  INTEGER
        ACCESS  read-only
        STATUS  mandatory
        DESCRIPTION
                "The number of active Unite Pvc Group."
--               接続中の総括グループ番号
        ::= { mpAtmCCUpgcBaseInfo 2 }


--
--    総括グループ制御テーブル                                         @007追加
--


--  総括グループの登録・接続（切り替え）・削除の手順を示す

--  １、登録手順
--   (1)mpAtmCCUnitePvcGroupControlTable に対して mpAtmCCUpgcUpgcIndex に総括
--      グループ番号を指定し mpAtmCCUpgcCtlStatus に register(1) を設定し、総
--      括グループを登録する（空の総括グループが存在する）
--   (2)mpAtmCCUnitePvcGroupRegisterTable で mpAtmCCUpgcUpgcIndex・
--      mpAtmCCUpgcPgcIndex を指定して、mpAtmCCUpgcRegiStatus に add(1) を設
--      定することで、(1) で登録した総括グループにＰＶＣグループを登録する。
--   (3)登録すべきＰＶＣグループが� る限り②を行う。
--   (4)登録すべき総括グループが� る限り①～③を繰り返す

--  ２、接続（切り替え）手順
--   (1)接続する（切り替える）総括グループ番号を mpAtmCCUpgcUpgcIndex に指定し
--      mpAtmCCUpgcCtlStatus に active(2) を設定する

--  ３、削除手順
--   １．１  総括グループの削除
--    (1)mpAtmCCUnitePvcGroupControlTable に対して mpAtmCCUpgcUpgcIndex に削除
--       する総括グループ番号を指定し mpAtmCCUpgcCtlStatus に delete(4) を設定
--       する（PVCグループが登録されていても削除を行う）
--   １．２  総括グループ内PVCグループを削除する場合
--    (1)mpAtmCCUnitePvcGroupRegisterTable で mpAtmCCUpgcUpgcIndex・
--       mpAtmCCUpgcPgcIndex を指定して、mpAtmCCUpgcRegiStatus に delete(2) を
--       設定する。（総括グループ内のPVCグループが全て削除されても総括グループ
--                   は削除しない）


mpAtmCCUnitePvcGroupControlTable OBJECT-TYPE
        SYNTAX  SEQUENCE OF MpAtmCCUpgcCtlEntry
        ACCESS  not-accessible
        STATUS  mandatory
        DESCRIPTION
                "This table contains the control of the Unite Pvc Group objects"
        --      総括グループ制御テーブル
        ::= { mpAtmCCUnitePvcGroup 2 }

mpAtmCCUpgcCtlEntry OBJECT-TYPE
        SYNTAX  MpAtmCCUpgcCtlEntry
        ACCESS  not-accessible
        STATUS  mandatory
        DESCRIPTION
                "An entry in the mpAtmCCUpgcCtlTable."
        --      総括グループ制御テーブルのエントリ
        INDEX{ mpAtmCCUpgcIndex }
        ::= { mpAtmCCUnitePvcGroupControlTable 1 }

MpAtmCCUpgcCtlEntry ::=
        SEQUENCE {
               mpAtmCCUpgcIndex
                   INTEGER,
               mpAtmCCUpgcCtlStatus
                   INTEGER,
               mpAtmCCUpgcCtlCountPgc
                   INTEGER,
               mpAtmCCUpgcCtlResult
                   INTEGER
        }

mpAtmCCUpgcIndex    OBJECT-TYPE
        SYNTAX  INTEGER(1..64)
        ACCESS  read-only
        STATUS  mandatory
        DESCRIPTION
                "The Unite Pvc Group identifier for this node.
                 A value assigned to a node in this node that uniquely
                 identifies in the MIB."
--               総括グループ番号を示すindex
        ::= { mpAtmCCUpgcCtlEntry 1 }

mpAtmCCUpgcCtlStatus    OBJECT-TYPE
        SYNTAX  INTEGER{
                    register(1),        -- write-only
                    active(2),          -- read-write
                    inactive(3),        -- read-write
                    delete(4),          -- write-only
                    stsInactive(5),     -- write-only
                    underEstablish(6),  -- read-only
                    underDeactivate(7)  -- read-only
                }
        ACCESS  read-write
        STATUS  mandatory
        DESCRIPTION
                "This variable indicates the Control Status of this Unite
                 Pvc Group.
                  - 'register', which indicates that request to careate a
                    new instance (Unite PVC Group) in the node.
                  - 'active', which indicates that the Unite Pvc Group is
                    connected.
                  - 'inactive', which indicates that the Unite Pvc Group is
                    disconnected.
                  - 'delete', which indicates that request to delete the Unite
                    Pvc Group.
                  - 'stsInactive', which indicates that request to only the
                    status is change to 'inactive'. This request is not
                    disconnect the connecting PVC's.
                  - 'underEstablish', which indicates that the under the
                    connecting progress in the Unite Pvc Group.
                  - 'underDeactivate', which indicates that the under the
                    disconnecting progress in the Unite Pvc Group.
                  "
--               総括グループの制御状態
--                  register(1) write:総括グループを登録する
--                  active(2)   read :接続中
--                              write:総括グループを接続（切り替え）る
--                  inactive(3) read :未接続
--                              write:総括グループを切断する
--                  delete(4)   write:総括グループを削除する
--                  stsInactive(5)     write:総括グループの状態のみinactiveに
--                                           遷移させ、設定済みのPVCグループ及
--                                           びPVCは切断しない
--                  underEstablish(6)  read :接続処理中
--                  underDeactivate(7) read :切断処理中
        ::= { mpAtmCCUpgcCtlEntry 2 }

mpAtmCCUpgcCtlCountPgc    OBJECT-TYPE
        SYNTAX  INTEGER
        ACCESS  read-only
        STATUS  mandatory
        DESCRIPTION
                "The total number of registered Pvc Group in the Unite Pvc Group."
--               総括グループ内PVCグループ登録総数
        ::= { mpAtmCCUpgcCtlEntry 3 }

mpAtmCCUpgcCtlResult    OBJECT-TYPE
        SYNTAX  INTEGER
        ACCESS  read-only
        STATUS  mandatory
        DESCRIPTION
                "Indicate the result at which process the Unite Pvc Group
                 CutOver."
--               総括グループ切り替え処理結果
        ::= { mpAtmCCUpgcCtlEntry 4 }



--
--    総括グループ登録テーブル                                         @007追加
--

mpAtmCCUnitePvcGroupRegisterTable OBJECT-TYPE
        SYNTAX  SEQUENCE OF MpAtmCCUpgcRegiEntry
        ACCESS  not-accessible
        STATUS  mandatory
        DESCRIPTION
                "This table uesd that register the Pvc Group for the Unite Pvc
                 Group."
        --      総括グループ登録テーブル
        ::= { mpAtmCCUnitePvcGroup 3 }

mpAtmCCUpgcRegiEntry OBJECT-TYPE
        SYNTAX  MpAtmCCUpgcRegiEntry
        ACCESS  not-accessible
        STATUS  mandatory
        DESCRIPTION
                "An entry in the mpAtmCCUpgcRegiTable."
        --      総括グループ登録テーブルのエントリ
        INDEX{ mpAtmCCUpgcIndex, mpAtmCCUpgcPgcIndex }
        ::= { mpAtmCCUnitePvcGroupRegisterTable 1 }

MpAtmCCUpgcRegiEntry ::=
        SEQUENCE {
               mpAtmCCUpgcPgcIndex
                   INTEGER,
               mpAtmCCUpgcRegiStatus
                   INTEGER
        }


mpAtmCCUpgcPgcIndex    OBJECT-TYPE
        SYNTAX  INTEGER(1..256)
        ACCESS  read-only
        STATUS  mandatory
        DESCRIPTION
                "The Index value for specified the Pvc Group that
                 to add (or delete) from Unite Pvc Group."
--               PVCグループ番号
        ::= { mpAtmCCUpgcRegiEntry 1 }

mpAtmCCUpgcRegiStatus    OBJECT-TYPE
        SYNTAX  INTEGER{
                    add(1),      -- write-only
                    delete(2),   -- write-only
                    enable(3)    -- read-only
                }
        ACCESS  read-write                             --  @009 修正
        STATUS  mandatory
        DESCRIPTION
                "This variable indicates the ragistratoin Status the PVC
                 Groupe to specified the Unite Pvc Group.
                 - 'add', which indicates that add the Pvc group to Unite
                   Pvc Group.
                 - 'delete', which indicates that delete the Pvc group to
                   Unite Pvc Group.
                 - 'enable', which indicates that ragisterd the Pvc group
                   in the Unite Pvc Group."
--              総括グループ内PVCグループの状態
--               add   ：登録
--               delete：削除
--               enable：登録� り
--                         登録済みの総括グループとその総括グループ内 PVCを指定
--                         してGETした場合、本値が読みだせる。従って、本MIBをア
--                         クセスして読み出せる値は'eable'しかない。
        ::= { mpAtmCCUpgcRegiEntry 2 }



--
--    ＰＶＣグループ                                                   @007追加
--

       mpAtmCCPvcGroup   OBJECT IDENTIFIER ::= { mpAtmCCPvcGroupCutover 3 }


--
--    ＰＶＣグループ基本情報                                           @007追加
--

       mpAtmCCPgcBaseInfo   OBJECT IDENTIFIER ::= { mpAtmCCPvcGroup 1 }


mpAtmCCPgcTotalGroupNumber    OBJECT-TYPE
        SYNTAX  INTEGER
        ACCESS  read-only
        STATUS  mandatory
        DESCRIPTION
                "The total number of registerd to Pvc Group in this node."
--               PVCグループ登録数
        ::= { mpAtmCCPgcBaseInfo 1 }


--  ＰＶＣグループの登録・接続・切断・削除の手順を示す

--  １、グループ登録
--    mpAtmCCPvcGroupRegisterTable に index で� る
--        mpAtmCCPgcIndex（グループ番号）
--        mpAtmCCPgcPvcIfIndex（グループ化する端点のifIndex）
--        mpAtmCCPgcPvcVpi（グループ化する端点のVPI）
--        mpAtmCCPgcPvcVpi（グループ化する端点のVPI）
--    を指定し、下記手順で登録する

--   (1)mpAtmCCPgcPvcKind にPVC種別を設定する
--      最初にこのエントリを設定する。
--      最初にこのエントリ以外を設定した場合、エラーを返す。
--      尚、このエントリは（上書きを含め）変更は認めない。
--   (2)Static-PVCで� れば
--      mpAtmCCStaticPvcDestIfIndex, mpAtmCCPgcPvcDestVpi,
--      mpAtmCCPgcPvcDestVci, mpAtmCCPgcPvcReceiveTrafficDescrIndex,
--      mpAtmCCPgcPvcTransmitTrafficDescrIndex, mpAtmCCPgcPvcPriority(*),
--      mpAtmCCPgcStaticPvcId(*), mpAtmCCPgcStaticPvcSeqNo(*)
--     Soft-PVCで� れば
--      mpAtmCCSoftPvcDestAtmAddress, mpAtmCCPgcPvcDestVpi,
--      mpAtmCCPgcPvcDestVci, mpAtmCCPgcPvcReceiveTrafficDescrIndex,
--      mpAtmCCPgcPvcTransmitTrafficDescrIndex, mpAtmCCPgcPvcPriority(*),
--      mpAtmCCPgcSoftPvcCallKind(*)
--     を設定した後、
--      mpAtmCCPgcCfgStatus
--     に enable(1) を設定する。
--      (*)は設定しなくとも良いが、上記以外の設定は受け付けない。
--      登録時のAdminStatusについて、inactive(2)しか認めない
--      （active(1)の設定は認めない）

--  ２、グループ接続・切断要求
--    mpAtmCCPvcGroupControlTable に index で� る mpAtmCCPgcIndex を指定し、
--    mpAtmCCPgcCtlStatus に要求するアクションを設定する。
--      他のテーブルと異なり、CfgStatusはなく、本テーブルは mpAtmCCPgcCtlStatus
--      に値が設定されたことを契機にグループの操作を行う。
--    mpAtmCCPgcCtlStatus の stsInactve(3) はグループの状態をinactive(1)に
--    するだけで、PVCの切断処理は行わない

--  ３、PVCグループ内PVC個別操作
--    mpAtmCCPvcGroupRegisterTable に index で� る
--        mpAtmCCPgcIndex（グループ番号）
--        mpAtmCCPgcPvcIfIndex（グループ化する端点のifIndex）
--        mpAtmCCPgcPvcVpi（グループ化する端点のVPI）
--        mpAtmCCPgcPvcVpi（グループ化する端点のVPI）
--    を指定し、mpAtmCCPgcRegiAdminStatus に要求の状態を設定した後、
--    mpAtmCCPgcCfgStatus に enable(1) を設定する。


--
--    ＰＶＣグループ制御テーブル                                       @007追加
--

mpAtmCCPvcGroupControlTable OBJECT-TYPE
        SYNTAX  SEQUENCE OF MpAtmCCPgcCtlEntry
        ACCESS  not-accessible
        STATUS  mandatory
        DESCRIPTION
                "This table contains the control of the Pvc Group objects"
        --      PVCグループ制御テーブル
        ::= { mpAtmCCPvcGroup 2 }

mpAtmCCPgcCtlEntry OBJECT-TYPE
        SYNTAX  MpAtmCCPgcCtlEntry
        ACCESS  not-accessible
        STATUS  mandatory
        DESCRIPTION
                "An entry in the mpAtmCCPgcCtlTable."
        --      PVCグループ制御テーブルのエントリ
        INDEX{ mpAtmCCPgcIndex }
        ::= { mpAtmCCPvcGroupControlTable 1 }

MpAtmCCPgcCtlEntry ::=
        SEQUENCE {
               mpAtmCCPgcIndex
                   INTEGER,
               mpAtmCCPgcCtlStatus
                   INTEGER,
               mpAtmCCPgcCtlCountPvc
                   INTEGER,
               mpAtmCCPgcCtlResult
                   INTEGER
        }

mpAtmCCPgcIndex    OBJECT-TYPE
        SYNTAX  INTEGER(1..4096)
        ACCESS  read-only
        STATUS  mandatory
        DESCRIPTION
                "The Pvc Group identifier for this node. A value assigned
                 to a node in this node that uniquely identifies in the MIB."
--               PVCグループ番号を示すindex
        ::= { mpAtmCCPgcCtlEntry 1 }

mpAtmCCPgcCtlStatus    OBJECT-TYPE
        SYNTAX  INTEGER{
                    register(1),        -- write-only
                    active(2),          -- read-write
                    inactive(3),        -- read-write
                    delete(4),          -- write-only
                    stsInactive(5),     -- write-only
                    underEstablish(6),  -- read-only
                    underDeactivate(7)  -- read-only
                }
        ACCESS  read-write
        STATUS  mandatory
        DESCRIPTION
                "This variable indicates the Control Status of this Pvc
                 Group.
                  - 'register', which indicates that request to careate a
                    new instance (PVC Group) in the node.
                  - 'active', which indicates that the Pvc Group is connected.
                  - 'inactive', which indicates that the Pvc Group is
                    disconnected.
                  - 'delete', which indicates that request to delete the Pvc
                    Group.
                  - 'stsInactive', which indicates that request to only the
                    status is change to 'inactive'. This request is not
                    disconnect the connecting PVC's.
                  - 'underEstablish', which indicates that the under the
                    connecting progress in the Pvc Group.
                  - 'underDeactivate', which indicates that the under the
                    disconnecting progress in the Pvc Group.
                  "
--               PVCグループの制御状態
--                  register(1) write:PVCグループを登録する
--                  active(2)   read :接続中
--                              write:PVCグループを接続する
--                  inactive(3) read :未接続
--                              write:PVCグループを切断する
--                  delete(4)   write:PVCグループを削除する
--                  stsInactive(5)     write:PVCグループの状態のみinactiveに
--                                           遷移させ、設定済みのPVCは切断しない
--                  underEstablish(6)  read :接続処理中
--                  underDeactivate(7) read :切断処理中
        ::= { mpAtmCCPgcCtlEntry 2 }

mpAtmCCPgcCtlCountPvc    OBJECT-TYPE
        SYNTAX  INTEGER
        ACCESS  read-only
        STATUS  mandatory
        DESCRIPTION
                "The total number of registered Pvc in the Pvc Group."
--               PVCグループ内 PVC登録数
        ::= { mpAtmCCPgcCtlEntry 3 }

mpAtmCCPgcCtlResult    OBJECT-TYPE
        SYNTAX  INTEGER
        ACCESS  read-only
        STATUS  mandatory
        DESCRIPTION
                "Indicate the result at which process the Pvc Group CutOver."
--               PVCグループ切り替え処理結果
        ::= { mpAtmCCPgcCtlEntry 4 }



--
--    PVCグループ登録テーブル                                          @007追加
--

mpAtmCCPvcGroupRegisterTable OBJECT-TYPE
        SYNTAX  SEQUENCE OF MpAtmCCPgcRegiEntry
        ACCESS  not-accessible
        STATUS  mandatory
        DESCRIPTION
                "This table uesd that register the Pvc for the Pvc Group."
        --      PVCグループ登録テーブル
        ::= { mpAtmCCPvcGroup 3 }

mpAtmCCPgcRegiEntry OBJECT-TYPE
        SYNTAX  MpAtmCCPgcRegiEntry
        ACCESS  not-accessible
        STATUS  mandatory
        DESCRIPTION
                "An entry in the mpAtmCCPgcRegiTable."
        --      PVCグループ登録テーブルのエントリ
        INDEX{ mpAtmCCPgcIndex,
               mpAtmCCPgcPvcIfIndex,
               mpAtmCCPgcPvcVpi,
               mpAtmCCPgcPvcVci }
        ::= { mpAtmCCPvcGroupRegisterTable 1 }

MpAtmCCPgcRegiEntry ::=
        SEQUENCE {
               mpAtmCCPgcPvcIfIndex
                   INTEGER,
               mpAtmCCPgcPvcVpi
                   INTEGER,
               mpAtmCCPgcPvcVci
                   INTEGER,
               mpAtmCCPgcPvcKind
                   INTEGER,
               mpAtmCCPgcStaticPvcDestIfIndex
                   INTEGER,
               mpAtmCCPgcSoftPvcDestAtmAddress
                   AtmAddr,
               mpAtmCCPgcPvcDestVpi
                   INTEGER,
               mpAtmCCPgcPvcDestVci
                   INTEGER,
               mpAtmCCPgcPvcReceiveTrafficDescrIndex
                   AtmTrafficDescrParamIndex,
               mpAtmCCPgcPvcTransmitTrafficDescrIndex
                   AtmTrafficDescrParamIndex,
               mpAtmCCPgcPvcPriority
                   INTEGER,
               mpAtmCCPgcStaticPvcId
                   INTEGER,
               mpAtmCCPgcStaticPvcSeqNo
                   INTEGER,
               mpAtmCCPgcSoftPvcCallKind
                   INTEGER,
               mpAtmCCPgcRegiAdminStatus
                   INTEGER,
               mpAtmCCPgcRegiCfgStatus
                   INTEGER,
               mpAtmCCPgcRegiErrInfo
                   INTEGER
        }

mpAtmCCPgcPvcIfIndex    OBJECT-TYPE
        SYNTAX  INTEGER
        ACCESS  not-accessible
        STATUS  mandatory
        DESCRIPTION
                "The value of this object is equal to MIB II's ifIndex value
                 of the ATM interface port for this pvc in PVC Group."
--               グループ管理するPVCのifIndex
        ::= { mpAtmCCPgcRegiEntry 1 }

mpAtmCCPgcPvcVpi    OBJECT-TYPE
        SYNTAX  INTEGER
        ACCESS  not-accessible
        STATUS  mandatory
        DESCRIPTION
                "The VPI value of the pvc in PVC Group."
--               グループ管理するPVCのVPI
        ::= { mpAtmCCPgcRegiEntry 2 }

mpAtmCCPgcPvcVci    OBJECT-TYPE
        SYNTAX  INTEGER
        ACCESS  not-accessible
        STATUS  mandatory
        DESCRIPTION
                "The VCI value of the pvc in PVC Group.
                 The value of 0 can used with PVP."
--               グループ管理するPVCのVCI
--               '0' を設定した場合、PVPの登録とみなす
        ::= { mpAtmCCPgcRegiEntry 3 }

mpAtmCCPgcPvcKind    OBJECT-TYPE
        SYNTAX  INTEGER{
                    staticPvc(1),
                    softPvc(2)
                }
        ACCESS  read-write
        STATUS  mandatory
        DESCRIPTION
                "This object is indicates the kind of pvc."
--               PVCの種別
        ::= { mpAtmCCPgcRegiEntry 4 }

mpAtmCCPgcStaticPvcDestIfIndex    OBJECT-TYPE
        SYNTAX  INTEGER
        ACCESS  read-write
        STATUS  mandatory
        DESCRIPTION
                "The value of this object is equal to MIB II's ifIndex value
                 of the distination ATM interface port.
                 This value is not relevant when the value of mpAtmCCPgcPvcKind
                 is 'softPvc'."
--               接続先端点のifIndex(Static-PVC)
        ::= { mpAtmCCPgcRegiEntry 5 }

mpAtmCCPgcSoftPvcDestAtmAddress    OBJECT-TYPE
--        SYNTAX  INTEGER                      @008 change
        SYNTAX  AtmAddr                     -- @008 change
        ACCESS  read-write
        STATUS  mandatory
        DESCRIPTION
                "The distinaniton ATM address of this pvc in the PVC Group.
                 This value is not relevant when the value of mpAtmCCPgcPvcKind
                 is 'staticPvc'."
--               接続先端点のATM Address(Soft-PVC)
        ::= { mpAtmCCPgcRegiEntry 6 }

mpAtmCCPgcPvcDestVpi    OBJECT-TYPE
        SYNTAX  INTEGER
        ACCESS  read-write
        STATUS  mandatory
        DESCRIPTION
                "The VPI value of the distination pvc."
--               接続先端点のVPI
        ::= { mpAtmCCPgcRegiEntry 7 }

mpAtmCCPgcPvcDestVci    OBJECT-TYPE
        SYNTAX  INTEGER
        ACCESS  read-write
        STATUS  mandatory
        DESCRIPTION
                "The VCI value of the distination pvc.
                 When the value of mpAtmCCPgcPvcVci is 0, the value of
                 this object is accept 0 only."
--               接続先端点のVCI
        ::= { mpAtmCCPgcRegiEntry 8 }

mpAtmCCPgcPvcReceiveTrafficDescrIndex    OBJECT-TYPE
        SYNTAX  AtmTrafficDescrParamIndex
        ACCESS  read-write
        STATUS  mandatory
        DESCRIPTION
                "The value of this ofject identifies the row of the ATM
                 Traffic Descriptor Table which applies to the receive
                 direction of this pvc in PVC Group."
--               受信トラフィックパラメータのテーブルのindex
        ::= { mpAtmCCPgcRegiEntry 9 }

mpAtmCCPgcPvcTransmitTrafficDescrIndex    OBJECT-TYPE
        SYNTAX  AtmTrafficDescrParamIndex
        ACCESS  read-write
        STATUS  mandatory
        DESCRIPTION
                "The value of this ofject identifies the row of the ATM
                 Traffic Descriptor Table which applies to the transmit
                 direction of this pvc in PVC Group."
--               送信トラフィックパラメータのテーブルのindex
        ::= { mpAtmCCPgcRegiEntry 10 }

mpAtmCCPgcPvcPriority    OBJECT-TYPE
        SYNTAX  INTEGER(1..3)
        ACCESS  read-write
        STATUS  mandatory
        DESCRIPTION
                "The value of this ofject identifies the connect priority
                 of the pvc in the PVC Group"
--               PVC優先度
        ::= { mpAtmCCPgcRegiEntry 11 }

mpAtmCCPgcStaticPvcId    OBJECT-TYPE
        SYNTAX  INTEGER
        ACCESS  read-write
        STATUS  mandatory
        DESCRIPTION
                "The value of this object identifies the Static-PVC IDENTIFY
                 the pvc in the PVC Group.
                 This value is not relevant when the value of mpAtmCCPgcPvcKind
                 is 'softPvc'."
--               PVC識別子(Static-PVC)
        ::= { mpAtmCCPgcRegiEntry 12 }

mpAtmCCPgcStaticPvcSeqNo    OBJECT-TYPE
        SYNTAX  INTEGER
        ACCESS  read-write
        STATUS  mandatory
        DESCRIPTION
                "The value of this object identifies the Sequence Number of
                 the static-pvc in the PvcGroup.
                 This value is not relevant when the value of mpAtmCCPgcPvcKind
                 is 'softPvc'."
--               PVC番号(Static-PVC)
        ::= { mpAtmCCPgcRegiEntry 13 }

mpAtmCCPgcSoftPvcCallKind    OBJECT-TYPE
        SYNTAX  INTEGER{
                    calling(1),  -- 発側
                    called(2)    -- 着側
                }
        ACCESS  read-write
        STATUS  mandatory
        DESCRIPTION
                "The value of this object identifies the call kind of the
                 soft-pvc in the PvcGroup.
                 This value is not relevant when the value of mpAtmCCPgcPvcKind
                 is 'staticPvc'."
--               発着種別(Soft-PVC)
        ::= { mpAtmCCPgcRegiEntry 14 }

mpAtmCCPgcRegiAdminStatus    OBJECT-TYPE
        SYNTAX  INTEGER{
                    inactive(1),      -- read-write
                    active(2),        -- read-write
                    stsInactive(3),   -- write-only
                    connectWait(4),   -- read-only
                    disconnectWait(5) -- read-only
                }
        ACCESS  read-write
        STATUS  mandatory
        DESCRIPTION
                "The value of this object identifies the desired administrative
                 status of this pvc in the PVC Group.
                  - 'inactive', which indicates that request to disconnect the
                     pvc.
                  - 'active', which indicates that request to connect the pvc.
                  - 'stsInactive', which indicates that request to only a
                     status is change, not disconnect the pvc.
                  - 'connectWait', which indicates that connecting progress at
                    this pvc.
                  - 'disconnectWait', which indicates that disconnecting
                    progress at this pvc.
                 "
--               PVCのAdminStatus
--                 inactive read    :未接続
--                          write   :切断要求
--                 active   read    :接続
--                          write   :接続要求
--                 stsInactive write:状態のみ未接続に変更要求
--                 connectWai       :接続待ち
--                 disconnectWait   :切断待ち
        ::= { mpAtmCCPgcRegiEntry 15 }

mpAtmCCPgcRegiCfgStatus    OBJECT-TYPE
        SYNTAX  INTEGER{
                    enable(1),
                    cancel(2),
                    delete(3),
                    unknown(4)
                }
        ACCESS  read-write
        STATUS  mandatory
        DESCRIPTION
                "The value of this object identifies the desired configration
                 status of this pvc in the PVC Group.
                  - 'enable', which indicates that set to the configration
                  - 'cancel', which indicates that request to clear the
                    procedure
                  - 'delete', which indicates that deleted form the configration
                  - 'unkown',
                "
--               PVCのConfigration Status
        ::= { mpAtmCCPgcRegiEntry 16 }

mpAtmCCPgcRegiErrInfo    OBJECT-TYPE
        SYNTAX  INTEGER
        ACCESS  read-only
        STATUS  mandatory
        DESCRIPTION
                "The value of this object indicate the result of set request."
--               登録エラー情報
        ::= { mpAtmCCPgcRegiEntry 17 }


--
--    接続中のPVCグループ情報                        @010 追加
--

mpAtmCCPvcGroupActiveInfoTable OBJECT-TYPE
        SYNTAX  SEQUENCE OF MpAtmCCPgcActInfoEntry
        ACCESS  not-accessible
        STATUS  mandatory
        DESCRIPTION
                "Confirm to the PVC Group that status is active."
        --      接続中PVCグループのグループ番号を参照するためのテーブル
        ::= { mpAtmCCPvcGroup 4 }

mpAtmCCPgcActInfoEntry OBJECT-TYPE
        SYNTAX  MpAtmCCPgcActInfoEntry
        ACCESS  not-accessible
        STATUS  mandatory
        DESCRIPTION
                "The entry of mpAtmCCPvcGroupActiveInfoTable."
        --      接続中PVCグループ グループ番号参照テーブルのエントリ
        INDEX{ mpAtmCCPgcActGrpNum }
        ::= { mpAtmCCPvcGroupActiveInfoTable 1 }

MpAtmCCPgcActInfoEntry ::=
        SEQUENCE {
               mpAtmCCPgcActGrpNum
                       INTEGER
               }

mpAtmCCPgcActGrpNum    OBJECT-TYPE
        SYNTAX  INTEGER
        ACCESS  read-only
        STATUS  mandatory
        DESCRIPTION
                "The number of the PVC Group that status is active."
--               接続中PVCグループのグループ番号
        ::= { mpAtmCCPgcActInfoEntry 1 }



--
--    ＡＴＭマルチキャスト                                     @011 追加
--

        mpAtmCCAtmMulticast      OBJECT IDENTIFIER ::= { mpAtmCallCtl 12 }


--
--    ＡＴＭマルチキャスト登録                                 @011 追加
--

mpAtmCCAtmMulticastRegistration  OBJECT IDENTIFIER ::= { mpAtmCCAtmMulticast 1 }

mpAtmCCAtmMultiRootIfIndex    OBJECT-TYPE
        SYNTAX  INTEGER
        ACCESS  read-write
        STATUS  mandatory
        DESCRIPTION
                "The value of this object is equal to MIB II's ifIndex value
                 of the ATM interface port."
--              Root側ifIndex
        ::= { mpAtmCCAtmMulticastRegistration 1 }

mpAtmCCAtmMultiRootVpi    OBJECT-TYPE
        SYNTAX  INTEGER
        ACCESS  read-write
        STATUS  mandatory
        DESCRIPTION
                "The VPI value of the Multicast-Root-PVC."
--              Root側VPI
        ::= { mpAtmCCAtmMulticastRegistration 2 }

mpAtmCCAtmMultiRootVci    OBJECT-TYPE
        SYNTAX  INTEGER
        ACCESS  read-write
        STATUS  mandatory
        DESCRIPTION
                "The VCI value of the Multicast-Root-PVC."
--              Root側VCI
        ::= { mpAtmCCAtmMulticastRegistration 3 }

mpAtmCCAtmMultiLeafIfIndex    OBJECT-TYPE
        SYNTAX  INTEGER
        ACCESS  read-write
        STATUS  mandatory
        DESCRIPTION
                "The value of this object is equal to MIB II's ifIndex value
                 of the ATM interface port."
--              Leaf側ifIndex
        ::= { mpAtmCCAtmMulticastRegistration 4 }

mpAtmCCAtmMultiLeafVpi    OBJECT-TYPE
        SYNTAX  INTEGER
        ACCESS  read-write
        STATUS  mandatory
        DESCRIPTION
                "The VPI value of the Multicast-Leaf-PVC."
--              Leaf側VPI
        ::= { mpAtmCCAtmMulticastRegistration 5 }

mpAtmCCAtmMultiLeafVci    OBJECT-TYPE
        SYNTAX  INTEGER
        ACCESS  read-write
        STATUS  mandatory
        DESCRIPTION
                "The VCI value of the Multicast-Leaf-PVC."
--              Leaf側VCI
        ::= { mpAtmCCAtmMulticastRegistration 6 }

mpAtmCCAtmMultiTrafficDescrIndex    OBJECT-TYPE
        SYNTAX  AtmTrafficDescrParamIndex
        ACCESS  read-write
        STATUS  mandatory
        DESCRIPTION
                "The value of this object identifies in the ATM
                 Traffic Descriptor Table which applies to this
                 multicast PVC."
--              ATM Multicast パスのトラフィックパラメータのテーブルのindex
        ::= { mpAtmCCAtmMulticastRegistration 7 }

mpAtmCCAtmMultiSlotNumber    OBJECT-TYPE
        SYNTAX  INTEGER
        ACCESS  read-write
        STATUS  mandatory
        DESCRIPTION
                "Specified the slot number which used the Multicast Card."
--              ATM Multicast Card のスロット番号
        ::= { mpAtmCCAtmMulticastRegistration 8 }

mpAtmCCAtmMultiVcRdiResponse    OBJECT-TYPE
        SYNTAX  INTEGER{
                        ture(1),
                        false(2)   -- default
                       }
        ACCESS  read-write
        STATUS  mandatory
        DESCRIPTION
                "Specified responds to the VC-AIS or not when the VC-RDI
                 received."
--              VC-AISを受信してVC-RDIを返送するか
        ::= { mpAtmCCAtmMulticastRegistration 9 }

mpAtmCCAtmMultiPvcId    OBJECT-TYPE
        SYNTAX  INTEGER
        ACCESS  read-write
        STATUS  mandatory
        DESCRIPTION
                "The value of this object identifies the desired
                 this connection."
--              PVC ID（NMSが管理する情報）
--      DEFVAL { 0 }
        ::= { mpAtmCCAtmMulticastRegistration 10 }

mpAtmCCAtmMultiSeqNo    OBJECT-TYPE
        SYNTAX  INTEGER
        ACCESS  read-write
        STATUS  mandatory
        DESCRIPTION
                "Order information in this connection."
--              PVC シーケンス番号（NMSが管理する情報）
--      DEFVAL { 0 }
        ::= { mpAtmCCAtmMulticastRegistration 11 }

mpAtmCCAtmMultiCfgStatus    OBJECT-TYPE
        SYNTAX  INTEGER {
                         enable(1),   -- write-only
                         cancel(2),   -- write-only
                         delete(3),   -- write-only
                         unknown(4)   -- read-only
                        }
        ACCESS  read-write
        STATUS  mandatory
        DESCRIPTION
                "The value of this object identifies configration
                 status for this table."
--              ATM Multicast パスの CfgStatus
        DEFVAL { unknown }
        ::= { mpAtmCCAtmMulticastRegistration 98 }

mpAtmCCAtmMultiRegErrInfo    OBJECT-TYPE
        SYNTAX  INTEGER
        ACCESS  read-only
        STATUS  mandatory
        DESCRIPTION
                "The value of this object indicates error
                 information that became an error set to MIB
                 in this table."
--              ATM Multicast パスのErrInfo
        ::= { mpAtmCCAtmMulticastRegistration 99 }



--
--    ＡＴＭマルチキャスト制御                                 @011 追加
--

mpAtmCCAtmMulticastCtlTable OBJECT-TYPE
        SYNTAX  SEQUENCE OF MpAtmCCAtmMultiCtlEntry
        ACCESS  not-accessible
        STATUS  mandatory
        DESCRIPTION
                "This table used when control of the multicast root
                 or leaf PVC."
        --      ATMマルチキャスト制御テーブル
        ::= { mpAtmCCAtmMulticast 2 }

mpAtmCCAtmMultiCtlEntry OBJECT-TYPE
        SYNTAX  MpAtmCCAtmMultiCtlEntry
        ACCESS  not-accessible
        STATUS  mandatory
        DESCRIPTION
                "An entry in the mpAtmCCAtmMulticastCtlTable."
        --      ATMマルチキャスト制御テーブルのエントリ
        INDEX{
               mpAtmCCAtmMultiIfIndex,
               mpAtmCCAtmMultiVpi,
               mpAtmCCAtmMultiVci
             }
        ::= { mpAtmCCAtmMulticastCtlTable 1 }

MpAtmCCAtmMultiCtlEntry ::=
        SEQUENCE {
               mpAtmCCAtmMultiIfIndex
                   INTEGER,
               mpAtmCCAtmMultiVpi
                   INTEGER,
               mpAtmCCAtmMultiVci
                   INTEGER,
               mpAtmCCAtmMultiAdminStatus
                   INTEGER,
               mpAtmCCAtmMultiOperStatus
                   INTEGER,
               mpAtmCCAtmMultiErrInfo
                   INTEGER
        }

mpAtmCCAtmMultiIfIndex    OBJECT-TYPE
        SYNTAX  INTEGER
        ACCESS  not-accessible
        STATUS  mandatory
        DESCRIPTION
                "The value of this object is equal to MIB II's ifIndex value
                 of the ATM interface port."
--              ifIndex
        ::= { mpAtmCCAtmMultiCtlEntry 1 }

mpAtmCCAtmMultiVpi    OBJECT-TYPE
        SYNTAX  INTEGER
        ACCESS  not-accessible
        STATUS  mandatory
        DESCRIPTION
                "The VPI value of this PVC."
--              VPI
        ::= { mpAtmCCAtmMultiCtlEntry 2 }

mpAtmCCAtmMultiVci    OBJECT-TYPE
        SYNTAX  INTEGER
        ACCESS  not-accessible
        STATUS  mandatory
        DESCRIPTION
                "The VCI value of this PVC."
--              VCI
        ::= { mpAtmCCAtmMultiCtlEntry 3 }

mpAtmCCAtmMultiAdminStatus    OBJECT-TYPE
        SYNTAX  INTEGER{
                        up(1),
                        down(2)
                       }
        ACCESS  read-write
        STATUS  mandatory
        DESCRIPTION
                "The value of this object identifies the desired
                 administrative status of this Multicast-PVC.
                 The up and down states indicate that the traffic
                 flow is enabled and disabled respectively on this
                 Multicast-PVC."
--              ATM Multicast 端点の AdminStatus
        DEFVAL { down }
        ::= { mpAtmCCAtmMultiCtlEntry 4 }

mpAtmCCAtmMultiOperStatus    OBJECT-TYPE
        SYNTAX  INTEGER{
                        up(1),
                        down(2)
                       }
        ACCESS  read-only
        STATUS  mandatory
        DESCRIPTION
                "The value of this object identifies the desired
                 operational status of this Multicast-PVC."
--              ATM Multicast 端点のOperStatus
        ::= { mpAtmCCAtmMultiCtlEntry 5 }

mpAtmCCAtmMultiErrInfo    OBJECT-TYPE
        SYNTAX  INTEGER
        ACCESS  read-only
        STATUS  mandatory
        DESCRIPTION
                "The value of this object indicates error
                 information that became an error set to MIB
                 in this table."
--              ATM Multicast のErrInfo
        ::= { mpAtmCCAtmMultiCtlEntry 99 }



--
--    ＡＴＭマルチキャスト参照                                 @011 追加
--

mpAtmCCAtmMulticastConfTable OBJECT-TYPE
        SYNTAX  SEQUENCE OF MpAtmCCAtmMultiConfEntry
        ACCESS  not-accessible
        STATUS  mandatory
        DESCRIPTION
                "This table indicate that infom the ATM-Multicast-PVC."
        --      ATMマルチキャスト参照テーブル
        ::= { mpAtmCCAtmMulticast 3 }

mpAtmCCAtmMultiConfEntry OBJECT-TYPE
        SYNTAX  MpAtmCCAtmMultiConfEntry
        ACCESS  not-accessible
        STATUS  mandatory
        DESCRIPTION
                "An entry in the mpAtmCCAtmMulticastConfTable."
        --      ATMマルチキャスト参照テーブルのエントリ
        INDEX{
               mpAtmCCAtmMultiRootIfIndex,
               mpAtmCCAtmMultiRootVpi,
               mpAtmCCAtmMultiRootVci,
               mpAtmCCAtmMultiLeafIfIndex,
               mpAtmCCAtmMultiLeafVpi,
               mpAtmCCAtmMultiLeafVci
             }
        ::= { mpAtmCCAtmMulticastConfTable 1 }

MpAtmCCAtmMultiConfEntry ::=
        SEQUENCE {
               mpAtmCCAtmMultiConfRootIfIndex
                   INTEGER,
               mpAtmCCAtmMultiConfRootVpi
                   INTEGER,
               mpAtmCCAtmMultiConfRootVci
                   INTEGER,
               mpAtmCCAtmMultiConfLeafIfIndex
                   INTEGER,
               mpAtmCCAtmMultiConfLeafVpi
                   INTEGER,
               mpAtmCCAtmMultiConfLeafVci
                   INTEGER,
               mpAtmCCAtmMultiConfRootAdminStatus
                   INTEGER,
               mpAtmCCAtmMultiConfRootOperStatus
                   INTEGER,
               mpAtmCCAtmMultiConfLeafAdminStatus
                   INTEGER,
               mpAtmCCAtmMultiConfLeafOperStatus
                   INTEGER,
               mpAtmCCAtmMultiConfTrafficDescrIndex
                   AtmTrafficDescrParamIndex,
               mpAtmCCAtmMultiConfSlotNumber
                   INTEGER,
               mpAtmCCAtmMultiConfVcRdiResponse
                   INTEGER,
               mpAtmCCAtmMultiConfPvcId
                   INTEGER,
               mpAtmCCAtmMultiConfSeqNo
                   INTEGER,
               mpAtmCCAtmMultiConfShaperRate
                   INTEGER,
               mpAtmCCAtmMultiConfRootVpTunneling
                   INTEGER,
               mpAtmCCAtmMultiConfLeafVpTunneling
                   INTEGER,
               mpAtmCCAtmMultiConfNextLeaf
                   INTEGER
        }

mpAtmCCAtmMultiConfRootIfIndex    OBJECT-TYPE
        SYNTAX  INTEGER
        ACCESS  read-only
        STATUS  mandatory
        DESCRIPTION
                "The value of this object is equal to MIB II's ifIndex value
                 of the ATM interface port."
--              マルチキャストPVC Root側 ifIndex
        ::= { mpAtmCCAtmMultiConfEntry 1 }

mpAtmCCAtmMultiConfRootVpi    OBJECT-TYPE
        SYNTAX  INTEGER
        ACCESS  read-only
        STATUS  mandatory
        DESCRIPTION
                "The VPI value of the Multicast-Root-PVC."
--              マルチキャストPVC Root側 VPI
        ::= { mpAtmCCAtmMultiConfEntry 2 }

mpAtmCCAtmMultiConfRootVci    OBJECT-TYPE
        SYNTAX  INTEGER
        ACCESS  read-only
        STATUS  mandatory
        DESCRIPTION
                "The VCI value of the Multicast-Root-PVC."
--              マルチキャストPVC Root側 VCI
        ::= { mpAtmCCAtmMultiConfEntry 3 }
mpAtmCCAtmMultiConfLeafIfIndex    OBJECT-TYPE
        SYNTAX  INTEGER
        ACCESS  read-only
        STATUS  mandatory
        DESCRIPTION
                "The value of this object is equal to MIB II's ifIndex value
                 of the ATM interface port."
--              マルチキャストPVC leaf側 ifIndex
        ::= { mpAtmCCAtmMultiConfEntry 4 }

mpAtmCCAtmMultiConfLeafVpi    OBJECT-TYPE
        SYNTAX  INTEGER
        ACCESS  read-only
        STATUS  mandatory
        DESCRIPTION
                "The VPI value of the Multicast-Leaf-PVC."
--             マルチキャストPVC leaf側 VPI
        ::= { mpAtmCCAtmMultiConfEntry 5 }

mpAtmCCAtmMultiConfLeafVci    OBJECT-TYPE
        SYNTAX  INTEGER
        ACCESS  read-only
        STATUS  mandatory
        DESCRIPTION
                "The VCI value of the Multicast-Leaf-PVC."
--              マルチキャストPVC leaf側 VCI
        ::= { mpAtmCCAtmMultiConfEntry 6 }

mpAtmCCAtmMultiConfRootAdminStatus    OBJECT-TYPE
        SYNTAX  INTEGER{
                        up(1),
                        down(2)
                       }
        ACCESS  read-only
        STATUS  mandatory
        DESCRIPTION
                "The value of this object identifies the desired
                 administrative status of this Multicast-Root-PVC."
--              RootのAdminStatus
        ::= { mpAtmCCAtmMultiConfEntry 7 }

mpAtmCCAtmMultiConfRootOperStatus    OBJECT-TYPE
        SYNTAX  INTEGER{
                        up(1),
                        down(2)
                       }
        ACCESS  read-only
        STATUS  mandatory
        DESCRIPTION
                "The value of this object identifies the desired
                 operational status of this Multicast-Root-PVC."
--              RootのOperStatus
        ::= { mpAtmCCAtmMultiConfEntry 8 }

mpAtmCCAtmMultiConfLeafAdminStatus    OBJECT-TYPE
        SYNTAX  INTEGER{
                        up(1),
                        down(2)
                       }
        ACCESS  read-only
        STATUS  mandatory
        DESCRIPTION
                "The value of this object identifies the desired
                 administrative status of this Multicast-Leaf-PVC."
--              leafのAdminStatus
        ::= { mpAtmCCAtmMultiConfEntry 9 }

mpAtmCCAtmMultiConfLeafOperStatus    OBJECT-TYPE
        SYNTAX  INTEGER{
                        up(1),
                        down(2)
                       }
        ACCESS  read-only
        STATUS  mandatory
        DESCRIPTION
                "The value of this object identifies the desired
                 operational status of this Multicast-Leaf-PVC."
--              leafのOperStatus
        ::= { mpAtmCCAtmMultiConfEntry 10 }

mpAtmCCAtmMultiConfTrafficDescrIndex    OBJECT-TYPE
        SYNTAX  AtmTrafficDescrParamIndex
        ACCESS  read-only
        STATUS  mandatory
        DESCRIPTION
                "The value of this object identifies
                 in the ATM Traffic Descriptor Table which
                 applies of this Multicast-PVC."
--              指定 ATM Multicastパスの使用しているTraffic Index
        ::= { mpAtmCCAtmMultiConfEntry 11 }

mpAtmCCAtmMultiConfSlotNumber    OBJECT-TYPE
        SYNTAX  INTEGER
        ACCESS  read-only
        STATUS  mandatory
        DESCRIPTION
                "The value of this object identifies the slot number
                 which used the Multicast Card."
--              指定 ATM Multicastパスが使用してる ATM Multicast Card
--              が実装されているSlot位置
        ::= { mpAtmCCAtmMultiConfEntry 12 }

mpAtmCCAtmMultiConfVcRdiResponse    OBJECT-TYPE
        SYNTAX  INTEGER{
                        true(1),
                        false(2)
                       }
        ACCESS  read-only
        STATUS  mandatory
        DESCRIPTION
                "he value of this object identifies that responds to the
                 VC-AIS or not when the VC-RDI received."
--              VC-AIS受信時にVC-RDIを返すか否かを示す
        ::= { mpAtmCCAtmMultiConfEntry 13 }

mpAtmCCAtmMultiConfPvcId    OBJECT-TYPE
        SYNTAX  INTEGER
        ACCESS  read-only
        STATUS  mandatory
        DESCRIPTION
                "The value of this object identifies the desired
                 this connection."
--              PVC ID（NMSより設定された値）
        ::= { mpAtmCCAtmMultiConfEntry 14 }

mpAtmCCAtmMultiConfSeqNo    OBJECT-TYPE
        SYNTAX  INTEGER
        ACCESS  read-only
        STATUS  mandatory
        DESCRIPTION
                "Order information in this connection."
--              PVCシーケンス番号（NMSより設定された値）
        ::= { mpAtmCCAtmMultiConfEntry 15 }

mpAtmCCAtmMultiConfShaperRate    OBJECT-TYPE
        SYNTAX  INTEGER
        ACCESS  read-only
        STATUS  mandatory
        DESCRIPTION
                "The bandwidth value of this Multicast-PVC in cell per
                 second."
--              指定 ATM Multicastパスのシェーパーレート(CPS)
        ::= { mpAtmCCAtmMultiConfEntry 16 }

mpAtmCCAtmMultiConfRootVpTunneling    OBJECT-TYPE
        SYNTAX  INTEGER{
                        ture(1),
                        false(2)
                       }
        ACCESS  read-only
        STATUS  mandatory
        DESCRIPTION
                "The value of this object identifies the port (at the
                 Multicast-Root-PVC) VP-Tunneling indication.
                   1:VP-Tunneling
                   2:Not VP-Tunneling"
--              root側のポートが VP-tunnelingで� るかを示す
        ::= { mpAtmCCAtmMultiConfEntry 17 }

mpAtmCCAtmMultiConfLeafVpTunneling    OBJECT-TYPE
        SYNTAX  INTEGER{
                        ture(1),
                        false(2)
                       }
        ACCESS  read-only
        STATUS  mandatory
        DESCRIPTION
                "The value of this object identifies the port (at the
                 Multicast-Leaf-PVC) VP-Tunneling indication."
--              leaf側のポートが VP-tunnelingで� るかを示す
        ::= { mpAtmCCAtmMultiConfEntry 18 }

mpAtmCCAtmMultiConfNextLeaf    OBJECT-TYPE
        SYNTAX  INTEGER{
                        ture(1),
                        false(2)
                       }
        ACCESS  read-only
        STATUS  mandatory
        DESCRIPTION
                "The value of this object identifies the
                 last segment."
--              読み出したLeafに続くLeafが� るかを示す
--                ture ：次のLeaf� り
--                false：次のLeafなし
--              indexでLeafを指定した場合は常に”false”が読める
        ::= { mpAtmCCAtmMultiConfEntry 19 }


END
