-- ****************************************************************************
-- FileName    :mpIpv6Mib.my
-- Description :Ipv6 Private MIB
-- Revision History :
--  Ver.   mark  date
--  01.00   -    08/07/2001
-- ****************************************************************************
--
MP-IPV6-MIB DEFINITIONS ::= BEGIN

   IMPORTS
      mgmt, NetworkAddress, IpAddress, Counter, Gauge, TimeTicks
      FROM RFC1155-SMI

      ifIndex
      FROM RFC1213-MIB

      OBJECT-TYPE
      FROM RFC-1212

		mmpf-mib
		FROM MMPF-MIB

      TRAP-TYPE
      FROM RFC-1215;

      Ipv6Address ::= OCTET STRING (SIZE (16))


-- The following definition is privately defined for IX5000 Private MIB

      mpIpv6          OBJECT IDENTIFIER ::= { mmpf-mib 131 }


--  Ipv6 Private MIB

       mpIpv6PingTable OBJECT-TYPE
              SYNTAX  SEQUENCE OF MpIpv6PingEntry
              ACCESS  not-accessible
              STATUS  mandatory
              DESCRIPTION "The table of ping6 management information relevant to
                           this entity's ICMPv6 echo identifier."
              ::= { mpIpv6 1 }

       mpIpv6PingEntry OBJECT-TYPE
              SYNTAX  MpIpv6PingEntry
              ACCESS  not-accessible
              STATUS  mandatory
              DESCRIPTION "The ping6 management information for one of this
                           entity's ICMPv6 echo identifier."
              INDEX { mpIpv6PingId }
              ::= { mpIpv6PingTable 1 }

       MpIpv6PingEntry ::=
              SEQUENCE {
                  mpIpv6PingId
                      INTEGER,
                  mpIpv6PingTarget
                      Ipv6Address,
                  mpIpv6PingTargetSiteId
                      INTEGER,
                  mpIpv6PingRequestSend
                      INTEGER,
                  mpIpv6PingDataLength
                      INTEGER,
                  mpIpv6PingSendHopLimit
                      INTEGER,
                  mpIpv6PingSendTimeOut
                      INTEGER,
                  mpIpv6PingSendInterface
                      INTEGER,
                  mpIpv6PingStatus
                      INTEGER,
                  mpIpv6PingResult
                      INTEGER,
                  mpIpv6PingErrorSourceAddress
                      Ipv6Address
              }

       mpIpv6PingId OBJECT-TYPE
              SYNTAX  INTEGER
              ACCESS  read-only
              STATUS  mandatory
              DESCRIPTION "This is the index to identify the ping6 entry.
                           The value of this index must be assigned uniquely,
                           within the range of 1 - 65535.
                           But generable ping entry is four simultaneously."

              ::= { mpIpv6PingEntry 1 }

       mpIpv6PingTarget OBJECT-TYPE
              SYNTAX  Ipv6Address
              ACCESS  read-write
              STATUS  mandatory
              DESCRIPTION "The value of this object is the destination IPv6
                           address for this entry. This IPv6 address must
                           always be a unicast IPv6 address."
              ::= { mpIpv6PingEntry 2 }

       mpIpv6PingTargetSiteId OBJECT-TYPE
              SYNTAX  INTEGER
              ACCESS  read-write
              STATUS  mandatory
              DESCRIPTION "The value of this object is the site id to which the
                           destination belong, within the range of 1 - 8.(1 is default site.)
                           it is necessary to set up this value, Only when a
                           site local address is specified to be mpIpv6PingTarget.
                           this value can be omitted and 1 is set up when it omits."
              ::= { mpIpv6PingEntry 3 }

       mpIpv6PingRequestSend OBJECT-TYPE
              SYNTAX  INTEGER
              ACCESS  read-only
              STATUS  mandatory
              DESCRIPTION "The value of this object is the ping6 request
                           number of the times, within the range of 1 - 65535(default 1)."
              ::= { mpIpv6PingEntry 4 }

       mpIpv6PingDataLength OBJECT-TYPE
              SYNTAX  INTEGER
              ACCESS  read-write
              STATUS  mandatory
              DESCRIPTION "The value of this object is the ping6 data
                           length, within the range of 0 - 65507(default 64)."
              ::= { mpIpv6PingEntry 5 }

       mpIpv6PingSendHopLimit OBJECT-TYPE
              SYNTAX  INTEGER
              ACCESS  read-write
              STATUS  mandatory
              DESCRIPTION "The value of this object is the HOP LIMIT value in
                           ping6 packet, within the range of 1 - 255(default 64)."
              ::= { mpIpv6PingEntry 6 }

       mpIpv6PingSendTimeOut OBJECT-TYPE
              SYNTAX  INTEGER
              ACCESS  read-write
              STATUS  mandatory
              DESCRIPTION "The value of this object is the ping6 time out
                           value, within the range of 1 - 60 seconds(default 1)."
              ::= { mpIpv6PingEntry 7 }

       mpIpv6PingSendInterface OBJECT-TYPE
              SYNTAX  INTEGER
              ACCESS  read-write
              STATUS  mandatory
              DESCRIPTION "The value of this object is ifIndex. IPv6 address
                           assigned ifIndex is set as source IPv6 address in
                           ping6 packets."
              ::= { mpIpv6PingEntry 8 }

       mpIpv6PingStatus OBJECT-TYPE
              SYNTAX  INTEGER {
                              create(1),
                              inProgress(2),
                              complete(3),
                              destroy(4)
                              }
              ACCESS  read-write
              STATUS  mandatory
              DESCRIPTION "This object refers to the ping6 entry status.
                           When this object is set to create(1), ping6
                           entry is created. Set to inProgress(2), ping6
                           is Started. When a reply or icmpv6 error
                           receiveed and time out occured, the status
                           become complete(3). This object can not set to
                           complete(3). Set to destroy(4), entry is deleted."
              ::= { mpIpv6PingEntry 9 }

       mpIpv6PingResult OBJECT-TYPE
              SYNTAX  INTEGER
              ACCESS  read-only
              STATUS  mandatory
              DESCRIPTION "This object refers to the ping6 result status."
              ::= { mpIpv6PingEntry 10 }

       mpIpv6PingErrorSourceAddress OBJECT-TYPE
              SYNTAX  Ipv6Address
              ACCESS  read-only
              STATUS  mandatory
              DESCRIPTION "This value of this object is the error source
                           IPv6 address in icmpv6 error reply message."
              ::= { mpIpv6PingEntry 11 }
END
