--
-- ASN.1 MIB Definitions
-- Output Date: Tue Jul 12 15:00:56 2016
--

IPE-ETH-RING-MIB DEFINITIONS ::= BEGIN

-----------------------------------------------
-- IMPORTS Definitions
-----------------------------------------------

    IMPORTS
        InterfaceIndex
            FROM IF-MIB
        enterprises, Integer32, IpAddress, NOTIFICATION-TYPE, OBJECT-TYPE,
        Opaque
            FROM SNMPv2-SMI
        DisplayString, RowStatus, TEXTUAL-CONVENTION
            FROM SNMPv2-TC;

-----------------------------------------------
-- Textual Convention Definitions
-----------------------------------------------

    IpeAdminStatus ::= TEXTUAL-CONVENTION
        STATUS       current
        DESCRIPTION  ""
        SYNTAX       INTEGER { invalid(0), down(1), up(2) }

    IpeEnableDisableValue ::= TEXTUAL-CONVENTION
        STATUS       current
        DESCRIPTION  ""
        SYNTAX       INTEGER { invalid(0), disabled(1), enabled(2) }

    IpeEtherRingIndex ::= TEXTUAL-CONVENTION
        DISPLAY-HINT "d"
        STATUS       current
        DESCRIPTION  "EtherRing Instance Index."
        SYNTAX       Integer32 (1..16)

    IpeEtherRingIndexOrZero ::= TEXTUAL-CONVENTION
        DISPLAY-HINT "d"
        STATUS       current
        DESCRIPTION  "EtherRing Instance Index with zero value."
        SYNTAX       Integer32 (0..16)

    IpeEtherRingPortId ::= TEXTUAL-CONVENTION
        DISPLAY-HINT "d"
        STATUS       current
        DESCRIPTION  ""
        SYNTAX       Integer32 (1..2)

    IpeEtherRingPortIdOrZero ::= TEXTUAL-CONVENTION
        DISPLAY-HINT "d"
        STATUS       current
        DESCRIPTION  ""
        SYNTAX       Integer32 (0..2)

    IpeEtherRingProtoVersion ::= TEXTUAL-CONVENTION
        STATUS       current
        DESCRIPTION  "Definition of EtherRing Protocol Version."
        SYNTAX       INTEGER { invalid(0), g8032v1(1), g8032v2(2) }

    IpeEtherRingVlanIndex ::= TEXTUAL-CONVENTION
        DISPLAY-HINT "d"
        STATUS       current
        DESCRIPTION  "Definition of VLAN ID. VLAN ID 4095 is reserved."
        SYNTAX       Integer32 (1..4094)

    IpeMepIdOrZero ::= TEXTUAL-CONVENTION
        DISPLAY-HINT "d"
        STATUS       current
        DESCRIPTION
            "Administrative MEP ID value.
            This value is not same as MEP ID in protocol sense. And value 0
            means no MEP is specified."
        SYNTAX       Integer32 (0..128)

    IpeRingType ::= TEXTUAL-CONVENTION
        STATUS       current
        DESCRIPTION  ""
        SYNTAX       INTEGER { invalid(0), major(1), sub(2) }

    IpeVlanList ::= TEXTUAL-CONVENTION
        STATUS       current
        DESCRIPTION  ""
        SYNTAX       OCTET STRING (SIZE(512..512))

-----------------------------------------------
-- Begin User MIB Object Definitions
-----------------------------------------------

    nec OBJECT IDENTIFIER
        ::= { enterprises 119 }

    nec-mib OBJECT IDENTIFIER
        ::= { nec 2 }

    necProductDepend OBJECT IDENTIFIER
        ::= { nec-mib 3 }

    radioEquipment OBJECT IDENTIFIER
        ::= { necProductDepend 69 }

    pasoNeoIpe-common OBJECT IDENTIFIER
        ::= { radioEquipment 501 }

-----------------------------------------------
-- IPE COMMON Group Definitions
-----------------------------------------------

    alarmStatusGroup OBJECT IDENTIFIER
        ::= { pasoNeoIpe-common 3 }

    provisioningGroup OBJECT IDENTIFIER
        ::= { pasoNeoIpe-common 5 }

    maintenanceGroup OBJECT IDENTIFIER
        ::= { pasoNeoIpe-common 6 }

-----------------------------------------------
-- alarmStatusGroup Definitions
-----------------------------------------------

    asEtherRingGroup OBJECT IDENTIFIER
        ::= { alarmStatusGroup 39 }

    asEtherRingTable OBJECT-TYPE
        SYNTAX       SEQUENCE OF AsEtherRingEntry
        MAX-ACCESS   not-accessible
        STATUS       current
        DESCRIPTION
            "This table contains Alarm & Status of Ethernet Ring Instance."
        ::= { asEtherRingGroup 1 }

    asEtherRingEntry OBJECT-TYPE
        SYNTAX       AsEtherRingEntry
        MAX-ACCESS   not-accessible
        STATUS       current
        DESCRIPTION  ""
        INDEX        { asEtherRingRingIndex }
        ::= { asEtherRingTable 1 }

    AsEtherRingEntry ::= SEQUENCE {
        asEtherRingRingIndex            IpeEtherRingIndex,
        asEtherRingNEAddress            IpAddress,
        asEtherRingState                INTEGER,
        asEtherRingCause                INTEGER,
        asEtherRingMultiRplOwnerDetect  INTEGER
    }

    asEtherRingRingIndex OBJECT-TYPE
        SYNTAX       IpeEtherRingIndex
        MAX-ACCESS   not-accessible
        STATUS       current
        DESCRIPTION  "Index of this table."
        ::= { asEtherRingEntry 1 }

    asEtherRingNEAddress OBJECT-TYPE
        SYNTAX       IpAddress
        MAX-ACCESS   not-accessible
        STATUS       current
        DESCRIPTION  "reserved."
        ::= { asEtherRingEntry 2 }

    asEtherRingState OBJECT-TYPE
        SYNTAX       INTEGER {
                         invalid(0),
                         disabled(1),
                         idle(2),
                         protection(3),
                         forced(4),
                         manual(5),
                         pending(6)
                     }
        MAX-ACCESS   read-only
        STATUS       current
        DESCRIPTION
            "The status of Etherring instance.
            The value 'idle' is initial and normal value. And that means
            there is no fault on the Ring Network (i.e. the RPL Port is
            closed). When the RPL port is opened because of the detection of
            Signal Failure on the Network, the value will change to
            'protection'. 'force' and 'manual' shows switch control is
            performed on the Ring Network. When the switch control is cleared
            or the Signal Failure is cleared, the value will show 'pending'."
        ::= { asEtherRingEntry 3 }

    asEtherRingCause OBJECT-TYPE
        SYNTAX       INTEGER {
                         invalid(0),
                         none(1),
                         localSf(2),
                         localNr(3),
                         remoteSf(4),
                         remoteNr(5),
                         localFs(6),
                         localMs(7),
                         remoteFs(8),
                         remoteMs(9)
                     }
        MAX-ACCESS   read-only
        STATUS       current
        DESCRIPTION
            "The object shows the reason of the asEtherRingStatus change.
             'localSf' : Signal Failure of the local node.
             'localNr' : Normal Request of the local node.
             'remoteSf' : Signal Failure from the other node.
             'remoteNr' : Normal Request from the other node.
             'localFs' : Forced Switch Request of the local node.
             'localMs' : Manual Switch Request of the local node.
             'remoteFs' : Forced Switch Request from the other node.
             'remoteMs' : Manual Switch Request from the other node."
        ::= { asEtherRingEntry 4 }

    asEtherRingMultiRplOwnerDetect OBJECT-TYPE
        SYNTAX       INTEGER { invalid(0), none(1), detected(2) }
        MAX-ACCESS   read-only
        STATUS       current
        DESCRIPTION
            "when the multiple RPL Owner is detected on the Ring Network, the
            value will change to 'detected'."
        ::= { asEtherRingEntry 5 }

    asEtherRingPortTable OBJECT-TYPE
        SYNTAX       SEQUENCE OF AsEtherRingPortEntry
        MAX-ACCESS   not-accessible
        STATUS       current
        DESCRIPTION
            "This table contains Alarm & Status of Ethernet Ring Instance."
        ::= { asEtherRingGroup 2 }

    asEtherRingPortEntry OBJECT-TYPE
        SYNTAX       AsEtherRingPortEntry
        MAX-ACCESS   not-accessible
        STATUS       current
        DESCRIPTION  ""
        INDEX        { asEtherRingPortRingIndex, asEtherRingPortId }
        ::= { asEtherRingPortTable 1 }

    AsEtherRingPortEntry ::= SEQUENCE {
        asEtherRingPortRingIndex     IpeEtherRingIndex,
        asEtherRingPortId            IpeEtherRingPortId,
        asEtherRingPortNEAddress     IpAddress,
        asEtherRingPortState         INTEGER,
        asEtherRingPortLoopDetect    INTEGER,
        asEtherRingPortProtoTimeout  INTEGER
    }

    asEtherRingPortRingIndex OBJECT-TYPE
        SYNTAX       IpeEtherRingIndex
        MAX-ACCESS   not-accessible
        STATUS       current
        DESCRIPTION  "Index of this table."
        ::= { asEtherRingPortEntry 1 }

    asEtherRingPortId OBJECT-TYPE
        SYNTAX       IpeEtherRingPortId
        MAX-ACCESS   not-accessible
        STATUS       current
        DESCRIPTION
            "Index of this table. This object represents the Ring port id of
            the ring instance."
        ::= { asEtherRingPortEntry 2 }

    asEtherRingPortNEAddress OBJECT-TYPE
        SYNTAX       IpAddress
        MAX-ACCESS   not-accessible
        STATUS       current
        DESCRIPTION  "reserved."
        ::= { asEtherRingPortEntry 3 }

    asEtherRingPortState OBJECT-TYPE
        SYNTAX       INTEGER {
                         invalid(0),
                         disabled(1),
                         initBlocking(2),
                         rplBlocking(3),
                         forwarding(4),
                         signalFail(5),
                         recovery(6),
                         waitToRestore(7),
                         forcedSwitch(8),
                         manualSwitch(9),
                         waitToBlock(10)
                     }
        MAX-ACCESS   read-only
        STATUS       current
        DESCRIPTION
            "Port Status.
            'initBlocking' is the initial value. At this point the no R-APS
            frame is received. When the port is configured as RPL port and
            the port is closed, the value will show 'rplBlocking'. The port
            forwards the frames, the value will show 'forwarding'.
            If the signal failure is detected on the port and the port is
            closed, the object will return the value 'signalFail'. And then
            the condition of Signal Failure is cleared but the port is still
            closed, the object will return the value 'recovery'.
            'waitToRestore' shows the RPL port is still closed till expiring
            the wait-to-restore timer.
            'forcedSwitch' and 'manualSwitch' represents the port is
            controlled by the maintenance control. 'waitToBlock' is waiting
            the RPL Port open after clearing maintenance control."
        ::= { asEtherRingPortEntry 4 }

    asEtherRingPortLoopDetect OBJECT-TYPE
        SYNTAX       INTEGER { invalid(0), none(1), detected(2) }
        MAX-ACCESS   read-only
        STATUS       current
        DESCRIPTION
            "The loop detection status.
            The object will show the value 'detected', when the Loop
            connection is detected."
        ::= { asEtherRingPortEntry 5 }

    asEtherRingPortProtoTimeout OBJECT-TYPE
        SYNTAX       INTEGER { invalid(0), none(1), detected(2) }
        MAX-ACCESS   read-only
        STATUS       current
        DESCRIPTION
            "The status of Protocol Timeout.
            If the R-APS frame is not received in a specified time, the
            object will show the value 'detected'."
        ::= { asEtherRingPortEntry 6 }

-----------------------------------------------
-- provisioningGroup Definitions
-----------------------------------------------

    provEtherRingGroup OBJECT IDENTIFIER
        ::= { provisioningGroup 39 }

    provEtherRingTable OBJECT-TYPE
        SYNTAX       SEQUENCE OF ProvEtherRingEntry
        MAX-ACCESS   not-accessible
        STATUS       current
        DESCRIPTION  "Configure EtherRing Instance."
        ::= { provEtherRingGroup 1 }

    provEtherRingEntry OBJECT-TYPE
        SYNTAX       ProvEtherRingEntry
        MAX-ACCESS   not-accessible
        STATUS       current
        DESCRIPTION  ""
        INDEX        { provEtherRingIndex }
        ::= { provEtherRingTable 1 }

    ProvEtherRingEntry ::= SEQUENCE {
        provEtherRingIndex         IpeEtherRingIndex,
        provEtherRingNEAddress     IpAddress,
        provEtherRingProtoVersion  IpeEtherRingProtoVersion,
        provEtherRingName          DisplayString,
        provEtherRingAdminStatus   IpeAdminStatus,
        provEtherRingRowStatus     RowStatus,
        provEtherRingType          IpeRingType
    }

    provEtherRingIndex OBJECT-TYPE
        SYNTAX       IpeEtherRingIndex
        MAX-ACCESS   not-accessible
        STATUS       current
        DESCRIPTION  "Index of this table."
        ::= { provEtherRingEntry 1 }

    provEtherRingNEAddress OBJECT-TYPE
        SYNTAX       IpAddress
        MAX-ACCESS   not-accessible
        STATUS       current
        DESCRIPTION
            "Reserved Object Identifier for the Northbound interface
            interface for the EMS."
        ::= { provEtherRingEntry 2 }

    provEtherRingProtoVersion OBJECT-TYPE
        SYNTAX       IpeEtherRingProtoVersion
        MAX-ACCESS   read-create
        STATUS       current
        DESCRIPTION
            "EtherRing Protocol Version for this EtherRing instance."
        DEFVAL       { g8032v2 }
        ::= { provEtherRingEntry 3 }

    provEtherRingName OBJECT-TYPE
        SYNTAX       DisplayString (SIZE(0..32))
        MAX-ACCESS   read-create
        STATUS       current
        DESCRIPTION  "Administrative name for this EtherRing instance."
        DEFVAL       { "" }
        ::= { provEtherRingEntry 4 }

    provEtherRingAdminStatus OBJECT-TYPE
        SYNTAX       IpeAdminStatus
        MAX-ACCESS   read-create
        STATUS       current
        DESCRIPTION
            "Administrative State for this EtherRing instance.
            This object must be set to down,when changing the parameters
            for the EtherRing Instance."
        DEFVAL       { down }
        ::= { provEtherRingEntry 5 }

    provEtherRingRowStatus OBJECT-TYPE
        SYNTAX       RowStatus
        MAX-ACCESS   read-create
        STATUS       current
        DESCRIPTION
            "This object is used to create a new EtherRing instance or
            delete an exising instance.
            Each EtherRing instance has provEtherRingTable or provEther-
            RingInterConnTable depends on the type of EtherRing and the
            following tables.
              provEtherRingVirtualChannelTable.
              provEtherRingCtrlVlanTable.
              provEtherRingMemberVlanTable.
              provEtherRingRPLPortTable.
              provEtherRingTimerTable.
            So it is necessary to set all objects of the above tables
            which has no default value, when creating new EtherRing
            instance."
        ::= { provEtherRingEntry 6 }

    provEtherRingType OBJECT-TYPE
        SYNTAX       IpeRingType
        MAX-ACCESS   read-create
        STATUS       current
        DESCRIPTION  "Ring Type"
        ::= { provEtherRingEntry 7 }

    provEtherRingInterConnTable OBJECT-TYPE
        SYNTAX       SEQUENCE OF ProvEtherRingInterConnEntry
        MAX-ACCESS   not-accessible
        STATUS       current
        DESCRIPTION  "Configure EtherRing InterConnect Node Instance."
        ::= { provEtherRingGroup 2 }

    provEtherRingInterConnEntry OBJECT-TYPE
        SYNTAX       ProvEtherRingInterConnEntry
        MAX-ACCESS   not-accessible
        STATUS       current
        DESCRIPTION  ""
        INDEX        { provEtherRingInterConnRingIndex }
        ::= { provEtherRingInterConnTable 1 }

    ProvEtherRingInterConnEntry ::= SEQUENCE {
        provEtherRingInterConnRingIndex       IpeEtherRingIndex,
        provEtherRingInterConnNEAddress       IpAddress,
        provEtherRingInterConnProtoVersion    IpeEtherRingProtoVersion,
        provEtherRingInterConnUpperRingIndex  IpeEtherRingIndexOrZero,
        provEtherRingInterConnName            DisplayString,
        provEtherRingInterConnAdminStatus     IpeAdminStatus,
        provEtherRingInterConnFlushPropagate  IpeEnableDisableValue,
        provEtherRingInterConnRowStatus       RowStatus
    }

    provEtherRingInterConnRingIndex OBJECT-TYPE
        SYNTAX       IpeEtherRingIndex
        MAX-ACCESS   not-accessible
        STATUS       current
        DESCRIPTION  "Index of this table."
        ::= { provEtherRingInterConnEntry 1 }

    provEtherRingInterConnNEAddress OBJECT-TYPE
        SYNTAX       IpAddress
        MAX-ACCESS   not-accessible
        STATUS       current
        DESCRIPTION
            "Reserved Object Identifier for the Northbound interface
            interface for the EMS."
        ::= { provEtherRingInterConnEntry 2 }

    provEtherRingInterConnProtoVersion OBJECT-TYPE
        SYNTAX       IpeEtherRingProtoVersion
        MAX-ACCESS   read-create
        STATUS       current
        DESCRIPTION
            "EtherRing Protocol Version for this EtherRing instance."
        DEFVAL       { g8032v2 }
        ::= { provEtherRingInterConnEntry 3 }

    provEtherRingInterConnUpperRingIndex OBJECT-TYPE
        SYNTAX       IpeEtherRingIndexOrZero
        MAX-ACCESS   read-create
        STATUS       current
        DESCRIPTION  "Upper Ring ID"
        ::= { provEtherRingInterConnEntry 4 }

    provEtherRingInterConnName OBJECT-TYPE
        SYNTAX       DisplayString (SIZE(0..32))
        MAX-ACCESS   read-create
        STATUS       current
        DESCRIPTION  "Administrative name for this EtherRing instance."
        DEFVAL       { "" }
        ::= { provEtherRingInterConnEntry 5 }

    provEtherRingInterConnAdminStatus OBJECT-TYPE
        SYNTAX       IpeAdminStatus
        MAX-ACCESS   read-create
        STATUS       current
        DESCRIPTION  "Ring Admin Status"
        DEFVAL       { down }
        ::= { provEtherRingInterConnEntry 6 }

    provEtherRingInterConnFlushPropagate OBJECT-TYPE
        SYNTAX       IpeEnableDisableValue
        MAX-ACCESS   read-create
        STATUS       current
        DESCRIPTION  "Flush Event"
        DEFVAL       { enabled }
        ::= { provEtherRingInterConnEntry 7 }

    provEtherRingInterConnRowStatus OBJECT-TYPE
        SYNTAX       RowStatus
        MAX-ACCESS   read-create
        STATUS       current
        DESCRIPTION
            "This object is used to Create a new  EtherRing InterConn
            Instance.
            Each Interconnection ring instance has
            provEtherRingInterConnTable. provEtherRingInterConnTable depends
            on the type of EtherRing and the  following tables.
              provEtherRingVirtualChannelTable.
              provEtherRingCtrlVlanTable.
              provEtherRingMemberVlanTable.
              provEtherRingRPLPortTable.
              provEtherRingTimerTable.
            So it is necessary to set all objects of the above tables
            which has no default value when creating new EtherRingInterConn
            ring
            instance."
        ::= { provEtherRingInterConnEntry 8 }

    provEtherRingPortTable OBJECT-TYPE
        SYNTAX       SEQUENCE OF ProvEtherRingPortEntry
        MAX-ACCESS   not-accessible
        STATUS       current
        DESCRIPTION  ""
        ::= { provEtherRingGroup 3 }

    provEtherRingPortEntry OBJECT-TYPE
        SYNTAX       ProvEtherRingPortEntry
        MAX-ACCESS   not-accessible
        STATUS       current
        DESCRIPTION  ""
        INDEX        { provEtherRingPortRingIndex, provEtherRingPortId }
        ::= { provEtherRingPortTable 1 }

    ProvEtherRingPortEntry ::= SEQUENCE {
        provEtherRingPortRingIndex     IpeEtherRingIndex,
        provEtherRingPortId            IpeEtherRingPortId,
        provEtherRingPortNEAddress     IpAddress,
        provEtherRingPortRowStatus     RowStatus,
        provEtherRingPortIfIndex       InterfaceIndex,
        provEtherRingPortLocDetectMep  IpeMepIdOrZero
    }

    provEtherRingPortRingIndex OBJECT-TYPE
        SYNTAX       IpeEtherRingIndex
        MAX-ACCESS   not-accessible
        STATUS       current
        DESCRIPTION  "Index of this table."
        ::= { provEtherRingPortEntry 1 }

    provEtherRingPortId OBJECT-TYPE
        SYNTAX       IpeEtherRingPortId
        MAX-ACCESS   not-accessible
        STATUS       current
        DESCRIPTION  "Ring Port"
        ::= { provEtherRingPortEntry 2 }

    provEtherRingPortNEAddress OBJECT-TYPE
        SYNTAX       IpAddress
        MAX-ACCESS   not-accessible
        STATUS       current
        DESCRIPTION  "reserved."
        ::= { provEtherRingPortEntry 3 }

    provEtherRingPortRowStatus OBJECT-TYPE
        SYNTAX       RowStatus
        MAX-ACCESS   read-create
        STATUS       current
        DESCRIPTION
            "This objects controls creation/deletion of Ring Port in the ERP
            ring instance"
        ::= { provEtherRingPortEntry 4 }

    provEtherRingPortIfIndex OBJECT-TYPE
        SYNTAX       InterfaceIndex
        MAX-ACCESS   read-create
        STATUS       current
        DESCRIPTION  "Interface index for assigning this Ether Ring Port."
        ::= { provEtherRingPortEntry 5 }

    provEtherRingPortLocDetectMep OBJECT-TYPE
        SYNTAX       IpeMepIdOrZero
        MAX-ACCESS   read-create
        STATUS       current
        DESCRIPTION  "LOC Detection MEP Index"
        DEFVAL       { 0 }
        ::= { provEtherRingPortEntry 6 }

    provEtherRingVirtualChannelTable OBJECT-TYPE
        SYNTAX       SEQUENCE OF ProvEtherRingVirtualChannelEntry
        MAX-ACCESS   not-accessible
        STATUS       current
        DESCRIPTION  ""
        ::= { provEtherRingGroup 4 }

    provEtherRingVirtualChannelEntry OBJECT-TYPE
        SYNTAX       ProvEtherRingVirtualChannelEntry
        MAX-ACCESS   not-accessible
        STATUS       current
        DESCRIPTION  ""
        INDEX        { provEtherRingVirtualChannelRingIndex }
        ::= { provEtherRingVirtualChannelTable 1 }

    ProvEtherRingVirtualChannelEntry ::= SEQUENCE {
        provEtherRingVirtualChannelRingIndex  IpeEtherRingIndex,
        provEtherRingVirtualChannelNEAddress  IpAddress,
        provEtherRingVirtualChannelEnabled    IpeEnableDisableValue
    }

    provEtherRingVirtualChannelRingIndex OBJECT-TYPE
        SYNTAX       IpeEtherRingIndex
        MAX-ACCESS   not-accessible
        STATUS       current
        DESCRIPTION  "Index of this table."
        ::= { provEtherRingVirtualChannelEntry 1 }

    provEtherRingVirtualChannelNEAddress OBJECT-TYPE
        SYNTAX       IpAddress
        MAX-ACCESS   not-accessible
        STATUS       current
        DESCRIPTION  "reserved."
        ::= { provEtherRingVirtualChannelEntry 2 }

    provEtherRingVirtualChannelEnabled OBJECT-TYPE
        SYNTAX       IpeEnableDisableValue
        MAX-ACCESS   read-create
        STATUS       current
        DESCRIPTION  "Virtual Channel"
        DEFVAL       { enabled }
        ::= { provEtherRingVirtualChannelEntry 3 }

    provEtherRingCtrlVlanTable OBJECT-TYPE
        SYNTAX       SEQUENCE OF ProvEtherRingCtrlVlanEntry
        MAX-ACCESS   not-accessible
        STATUS       current
        DESCRIPTION  ""
        ::= { provEtherRingGroup 5 }

    provEtherRingCtrlVlanEntry OBJECT-TYPE
        SYNTAX       ProvEtherRingCtrlVlanEntry
        MAX-ACCESS   not-accessible
        STATUS       current
        DESCRIPTION  ""
        INDEX        { provEtherRingCtrlVlanRingIndex }
        ::= { provEtherRingCtrlVlanTable 1 }

    ProvEtherRingCtrlVlanEntry ::= SEQUENCE {
        provEtherRingCtrlVlanRingIndex  IpeEtherRingIndex,
        provEtherRingCtrlVlanNEAddress  IpAddress,
        provEtherRingCtrlVlanId         IpeEtherRingVlanIndex,
        provEtherRingCtrlVlanRingId     Integer32,
        provEtherRingCtrlVlanMegLevel   Integer32,
        provEtherRingCtrlVlanPriority   Integer32
    }

    provEtherRingCtrlVlanRingIndex OBJECT-TYPE
        SYNTAX       IpeEtherRingIndex
        MAX-ACCESS   not-accessible
        STATUS       current
        DESCRIPTION  "Index of this table."
        ::= { provEtherRingCtrlVlanEntry 1 }

    provEtherRingCtrlVlanNEAddress OBJECT-TYPE
        SYNTAX       IpAddress
        MAX-ACCESS   not-accessible
        STATUS       current
        DESCRIPTION  "reserved."
        ::= { provEtherRingCtrlVlanEntry 2 }

    provEtherRingCtrlVlanId OBJECT-TYPE
        SYNTAX       IpeEtherRingVlanIndex
        MAX-ACCESS   read-create
        STATUS       current
        DESCRIPTION  "Control VLAN ID"
        ::= { provEtherRingCtrlVlanEntry 3 }

    provEtherRingCtrlVlanRingId OBJECT-TYPE
        SYNTAX       Integer32 (1..239)
        MAX-ACCESS   read-create
        STATUS       current
        DESCRIPTION  "Control MAC Address"
        ::= { provEtherRingCtrlVlanEntry 4 }

    provEtherRingCtrlVlanMegLevel OBJECT-TYPE
        SYNTAX       Integer32 (0..7)
        MAX-ACCESS   read-create
        STATUS       current
        DESCRIPTION  "R-APS Message MEG Level"
        ::= { provEtherRingCtrlVlanEntry 5 }

    provEtherRingCtrlVlanPriority OBJECT-TYPE
        SYNTAX       Integer32 (0..7)
        MAX-ACCESS   read-create
        STATUS       current
        DESCRIPTION  "R-APS Message Priority"
        DEFVAL       { 7 }
        ::= { provEtherRingCtrlVlanEntry 6 }

    provEtherRingMemberVlanTable OBJECT-TYPE
        SYNTAX       SEQUENCE OF ProvEtherRingMemberVlanEntry
        MAX-ACCESS   not-accessible
        STATUS       current
        DESCRIPTION  ""
        ::= { provEtherRingGroup 6 }

    provEtherRingMemberVlanEntry OBJECT-TYPE
        SYNTAX       ProvEtherRingMemberVlanEntry
        MAX-ACCESS   not-accessible
        STATUS       current
        DESCRIPTION  ""
        INDEX        { provEtherRingMemberVlanRingIndex }
        ::= { provEtherRingMemberVlanTable 1 }

    ProvEtherRingMemberVlanEntry ::= SEQUENCE {
        provEtherRingMemberVlanRingIndex  IpeEtherRingIndex,
        provEtherRingMemberVlanNEAddress  IpAddress,
        provEtherRingMemberVlanList       IpeVlanList
    }

    provEtherRingMemberVlanRingIndex OBJECT-TYPE
        SYNTAX       IpeEtherRingIndex
        MAX-ACCESS   not-accessible
        STATUS       current
        DESCRIPTION  "Index of this table."
        ::= { provEtherRingMemberVlanEntry 1 }

    provEtherRingMemberVlanNEAddress OBJECT-TYPE
        SYNTAX       IpAddress
        MAX-ACCESS   not-accessible
        STATUS       current
        DESCRIPTION  "reserved."
        ::= { provEtherRingMemberVlanEntry 2 }

    provEtherRingMemberVlanList OBJECT-TYPE
        SYNTAX       IpeVlanList
        MAX-ACCESS   read-create
        STATUS       current
        DESCRIPTION  "Traffic VLAN ID"
        ::= { provEtherRingMemberVlanEntry 3 }

    provEtherRingRPLPortTable OBJECT-TYPE
        SYNTAX       SEQUENCE OF ProvEtherRingRPLPortEntry
        MAX-ACCESS   not-accessible
        STATUS       current
        DESCRIPTION  ""
        ::= { provEtherRingGroup 7 }

    provEtherRingRPLPortEntry OBJECT-TYPE
        SYNTAX       ProvEtherRingRPLPortEntry
        MAX-ACCESS   not-accessible
        STATUS       current
        DESCRIPTION  ""
        INDEX        { provEtherRingRPLPortRingIndex }
        ::= { provEtherRingRPLPortTable 1 }

    ProvEtherRingRPLPortEntry ::= SEQUENCE {
        provEtherRingRPLPortRingIndex  IpeEtherRingIndex,
        provEtherRingRPLPortNEAddress  IpAddress,
        provEtherRingRPLPortEnable     IpeEnableDisableValue,
        provEtherRingRPLPortId         IpeEtherRingPortIdOrZero,
        provEtherRingRPLMode           INTEGER
    }

    provEtherRingRPLPortRingIndex OBJECT-TYPE
        SYNTAX       IpeEtherRingIndex
        MAX-ACCESS   not-accessible
        STATUS       current
        DESCRIPTION  "Index of this table."
        ::= { provEtherRingRPLPortEntry 1 }

    provEtherRingRPLPortNEAddress OBJECT-TYPE
        SYNTAX       IpAddress
        MAX-ACCESS   not-accessible
        STATUS       current
        DESCRIPTION  "reserved."
        ::= { provEtherRingRPLPortEntry 2 }

    provEtherRingRPLPortEnable OBJECT-TYPE
        SYNTAX       IpeEnableDisableValue
        MAX-ACCESS   read-create
        STATUS       current
        DESCRIPTION  "RPL Owner"
        DEFVAL       { disabled }
        ::= { provEtherRingRPLPortEntry 3 }

    provEtherRingRPLPortId OBJECT-TYPE
        SYNTAX       IpeEtherRingPortIdOrZero
        MAX-ACCESS   read-create
        STATUS       current
        DESCRIPTION  "RPL Port"
        DEFVAL       { 0 }
        ::= { provEtherRingRPLPortEntry 4 }

    provEtherRingRPLMode OBJECT-TYPE
        SYNTAX       INTEGER { invalid(0), revertive(1), nonRevertive(2) }
        MAX-ACCESS   read-create
        STATUS       current
        DESCRIPTION  "Revertive Mode"
        DEFVAL       { nonRevertive }
        ::= { provEtherRingRPLPortEntry 5 }

    provEtherRingTimerTable OBJECT-TYPE
        SYNTAX       SEQUENCE OF ProvEtherRingTimerEntry
        MAX-ACCESS   not-accessible
        STATUS       current
        DESCRIPTION  ""
        ::= { provEtherRingGroup 8 }

    provEtherRingTimerEntry OBJECT-TYPE
        SYNTAX       ProvEtherRingTimerEntry
        MAX-ACCESS   not-accessible
        STATUS       current
        DESCRIPTION  ""
        INDEX        { provEtherRingTimerRingIndex }
        ::= { provEtherRingTimerTable 1 }

    ProvEtherRingTimerEntry ::= SEQUENCE {
        provEtherRingTimerRingIndex  IpeEtherRingIndex,
        provEtherRingTimerNEAddress  IpAddress,
        provEtherRingTimerWtrTimer   Integer32,
        provEtherRingTimerGrdTimer   Integer32
    }

    provEtherRingTimerRingIndex OBJECT-TYPE
        SYNTAX       IpeEtherRingIndex
        MAX-ACCESS   not-accessible
        STATUS       current
        DESCRIPTION  "Index of this table."
        ::= { provEtherRingTimerEntry 1 }

    provEtherRingTimerNEAddress OBJECT-TYPE
        SYNTAX       IpAddress
        MAX-ACCESS   not-accessible
        STATUS       current
        DESCRIPTION  "reserved."
        ::= { provEtherRingTimerEntry 2 }

    provEtherRingTimerWtrTimer OBJECT-TYPE
        SYNTAX       Integer32 (1..12)
        UNITS        "minutes"
        MAX-ACCESS   read-create
        STATUS       current
        DESCRIPTION  "WTR Timer"
        DEFVAL       { 5 }
        ::= { provEtherRingTimerEntry 3 }

    provEtherRingTimerGrdTimer OBJECT-TYPE
        SYNTAX       Integer32 (1..200)
        UNITS        "10 milliseconds"
        MAX-ACCESS   read-create
        STATUS       current
        DESCRIPTION  "Guard Timer"
        DEFVAL       { 50 }
        ::= { provEtherRingTimerEntry 4 }

    provEtherRingExtraTimerTable OBJECT-TYPE
        SYNTAX       SEQUENCE OF ProvEtherRingExtraTimerEntry
        MAX-ACCESS   not-accessible
        STATUS       current
        DESCRIPTION  ""
        ::= { provEtherRingGroup 9 }

    provEtherRingExtraTimerEntry OBJECT-TYPE
        SYNTAX       ProvEtherRingExtraTimerEntry
        MAX-ACCESS   not-accessible
        STATUS       current
        DESCRIPTION  ""
        INDEX        { provEtherRingExtraTimerRingIndex }
        ::= { provEtherRingExtraTimerTable 1 }

    ProvEtherRingExtraTimerEntry ::= SEQUENCE {
        provEtherRingExtraTimerRingIndex  IpeEtherRingIndex,
        provEtherRingExtraTimerNEAddress  IpAddress,
        provEtherRingExtraTimerFlushGrd   Integer32
    }

    provEtherRingExtraTimerRingIndex OBJECT-TYPE
        SYNTAX       IpeEtherRingIndex
        MAX-ACCESS   not-accessible
        STATUS       current
        DESCRIPTION  "Index of this table."
        ::= { provEtherRingExtraTimerEntry 1 }

    provEtherRingExtraTimerNEAddress OBJECT-TYPE
        SYNTAX       IpAddress
        MAX-ACCESS   not-accessible
        STATUS       current
        DESCRIPTION  "reserved."
        ::= { provEtherRingExtraTimerEntry 2 }

    provEtherRingExtraTimerFlushGrd OBJECT-TYPE
        SYNTAX       Integer32 (1..200)
        UNITS        "10 milliseconds"
        MAX-ACCESS   read-create
        STATUS       current
        DESCRIPTION  "Flush Guard Timer"
        DEFVAL       { 50 }
        ::= { provEtherRingExtraTimerEntry 3 }

    provEtherRingEquipmentTable OBJECT-TYPE
        SYNTAX       SEQUENCE OF ProvEtherRingEquipmentEntry
        MAX-ACCESS   not-accessible
        STATUS       current
        DESCRIPTION  ""
        ::= { provEtherRingGroup 10 }

    provEtherRingEquipmentEntry OBJECT-TYPE
        SYNTAX       ProvEtherRingEquipmentEntry
        MAX-ACCESS   not-accessible
        STATUS       current
        DESCRIPTION  ""
        INDEX        { provEtherRingEquipmentIndex }
        ::= { provEtherRingEquipmentTable 1 }

    ProvEtherRingEquipmentEntry ::= SEQUENCE {
        provEtherRingEquipmentIndex      Integer32,
        provEtherRingEquipmentNEAddress  IpAddress,
        provEtherRingEquipmentEnable     IpeEnableDisableValue
    }

    provEtherRingEquipmentIndex OBJECT-TYPE
        SYNTAX       Integer32 (1..1)
        MAX-ACCESS   not-accessible
        STATUS       current
        DESCRIPTION  "Index of this table."
        ::= { provEtherRingEquipmentEntry 1 }

    provEtherRingEquipmentNEAddress OBJECT-TYPE
        SYNTAX       IpAddress
        MAX-ACCESS   not-accessible
        STATUS       current
        DESCRIPTION  "reserved."
        ::= { provEtherRingEquipmentEntry 2 }

    provEtherRingEquipmentEnable OBJECT-TYPE
        SYNTAX       IpeEnableDisableValue
        MAX-ACCESS   read-write
        STATUS       current
        DESCRIPTION  "ERP Mode"
        DEFVAL       { disabled }
        ::= { provEtherRingEquipmentEntry 3 }

-----------------------------------------------
-- maintenanceGroup Definitions
-----------------------------------------------

    maintEtherRingGroup OBJECT IDENTIFIER
        ::= { maintenanceGroup 39 }

    maintEtherRingLoopDetectClearTable OBJECT-TYPE
        SYNTAX       SEQUENCE OF MaintEtherRingLoopDetectClearEntry
        MAX-ACCESS   not-accessible
        STATUS       current
        DESCRIPTION  ""
        ::= { maintEtherRingGroup 1 }

    maintEtherRingLoopDetectClearEntry OBJECT-TYPE
        SYNTAX       MaintEtherRingLoopDetectClearEntry
        MAX-ACCESS   not-accessible
        STATUS       current
        DESCRIPTION  ""
        INDEX        {
                         maintEtherRingLoopDetectClearRingId,
                         maintEtherRingLoopDetectClearPortId
                     }
        ::= { maintEtherRingLoopDetectClearTable 1 }

    MaintEtherRingLoopDetectClearEntry ::= SEQUENCE {
        maintEtherRingLoopDetectClearRingId     IpeEtherRingIndex,
        maintEtherRingLoopDetectClearPortId     IpeEtherRingPortId,
        maintEtherRingLoopDetectClearNEAddress  IpAddress,
        maintEtherRingLoopDetectClearCommand    INTEGER
    }

    maintEtherRingLoopDetectClearRingId OBJECT-TYPE
        SYNTAX       IpeEtherRingIndex
        MAX-ACCESS   not-accessible
        STATUS       current
        DESCRIPTION  "ERP Control Ring ID"
        ::= { maintEtherRingLoopDetectClearEntry 1 }

    maintEtherRingLoopDetectClearPortId OBJECT-TYPE
        SYNTAX       IpeEtherRingPortId
        MAX-ACCESS   not-accessible
        STATUS       current
        DESCRIPTION  "ERP Control Port ID"
        ::= { maintEtherRingLoopDetectClearEntry 2 }

    maintEtherRingLoopDetectClearNEAddress OBJECT-TYPE
        SYNTAX       IpAddress
        MAX-ACCESS   not-accessible
        STATUS       current
        DESCRIPTION  "reserved."
        ::= { maintEtherRingLoopDetectClearEntry 3 }

    maintEtherRingLoopDetectClearCommand OBJECT-TYPE
        SYNTAX       INTEGER { invalid(0), none(1), clear(2) }
        MAX-ACCESS   read-write
        STATUS       current
        DESCRIPTION  "Loop Detection Restart"
        ::= { maintEtherRingLoopDetectClearEntry 4 }

    maintEtherRingSwitchControlTable OBJECT-TYPE
        SYNTAX       SEQUENCE OF MaintEtherRingSwitchControlEntry
        MAX-ACCESS   not-accessible
        STATUS       current
        DESCRIPTION  ""
        ::= { maintEtherRingGroup 2 }

    maintEtherRingSwitchControlEntry OBJECT-TYPE
        SYNTAX       MaintEtherRingSwitchControlEntry
        MAX-ACCESS   not-accessible
        STATUS       current
        DESCRIPTION  ""
        INDEX        {
                         maintEtherRingSwitchControlRingId,
                         maintEtherRingSwitchControlPortId
                     }
        ::= { maintEtherRingSwitchControlTable 1 }

    MaintEtherRingSwitchControlEntry ::= SEQUENCE {
        maintEtherRingSwitchControlRingId     IpeEtherRingIndex,
        maintEtherRingSwitchControlPortId     IpeEtherRingPortId,
        maintEtherRingSwitchControlNEAddress  IpAddress,
        maintEtherRingSwitchControlCommand    INTEGER
    }

    maintEtherRingSwitchControlRingId OBJECT-TYPE
        SYNTAX       IpeEtherRingIndex
        MAX-ACCESS   not-accessible
        STATUS       current
        DESCRIPTION  "ERP Control Ring ID"
        ::= { maintEtherRingSwitchControlEntry 1 }

    maintEtherRingSwitchControlPortId OBJECT-TYPE
        SYNTAX       IpeEtherRingPortId
        MAX-ACCESS   not-accessible
        STATUS       current
        DESCRIPTION  "ERP Control Port ID"
        ::= { maintEtherRingSwitchControlEntry 2 }

    maintEtherRingSwitchControlNEAddress OBJECT-TYPE
        SYNTAX       IpAddress
        MAX-ACCESS   not-accessible
        STATUS       current
        DESCRIPTION  "reserved."
        ::= { maintEtherRingSwitchControlEntry 3 }

    maintEtherRingSwitchControlCommand OBJECT-TYPE
        SYNTAX       INTEGER {
                         invalid(0),
                         none(1),
                         forced(2),
                         manual(3),
                         clear(4)
                     }
        MAX-ACCESS   read-write
        STATUS       current
        DESCRIPTION  "ERP Switch Control"
        ::= { maintEtherRingSwitchControlEntry 4 }

-----------------------------------------------
-- End User MIB Object Definitions
-----------------------------------------------

END
