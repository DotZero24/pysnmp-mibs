--
-- ASN.1 MIB Definitions
-- Output Date: Tue Jul 12 15:00:51 2016
--

IPE-LAG-MIB DEFINITIONS ::= BEGIN

-----------------------------------------------
-- IMPORTS Definitions
-----------------------------------------------

    IMPORTS
        InterfaceIndex, InterfaceIndexOrZero
            FROM IF-MIB
        Counter32, enterprises, Integer32, IpAddress, NOTIFICATION-TYPE,
        OBJECT-TYPE, Opaque
            FROM SNMPv2-SMI
        DisplayString, RowStatus, TEXTUAL-CONVENTION
            FROM SNMPv2-TC;

-----------------------------------------------
-- Textual Convention Definitions
-----------------------------------------------

    IpeEnableDisableValue ::= TEXTUAL-CONVENTION
        STATUS       current
        DESCRIPTION  ""
        SYNTAX       INTEGER { invalid(0), disabled(1), enabled(2) }

    SeverityValue ::= TEXTUAL-CONVENTION
        STATUS       current
        DESCRIPTION  "Severity (CCITT Rec. X.733)"
        SYNTAX       INTEGER {
                         cleared(1),
                         indetermine(2),
                         critical(3),
                         major(4),
                         minor(5),
                         warning(6)
                     }

-----------------------------------------------
-- Begin User MIB Object Definitions
-----------------------------------------------

    nec OBJECT IDENTIFIER
        ::= { enterprises 119 }

    nec-mib OBJECT IDENTIFIER
        ::= { nec 2 }

    necProductDepend OBJECT IDENTIFIER
        ::= { nec-mib 3 }

    radioEquipment OBJECT IDENTIFIER
        ::= { necProductDepend 69 }

    pasoNeoIpe-common OBJECT IDENTIFIER
        ::= { radioEquipment 501 }

-----------------------------------------------
-- IPE COMMON Group Definitions
-----------------------------------------------

    alarmStatusGroup OBJECT IDENTIFIER
        ::= { pasoNeoIpe-common 3 }

    provisioningGroup OBJECT IDENTIFIER
        ::= { pasoNeoIpe-common 5 }

    maintenanceGroup OBJECT IDENTIFIER
        ::= { pasoNeoIpe-common 6 }

-----------------------------------------------
-- alarmStatusGroup Definitions
-----------------------------------------------

    asLinkAggrGroup OBJECT IDENTIFIER
        ::= { alarmStatusGroup 38 }

    asLinkAggrGroupTable OBJECT-TYPE
        SYNTAX       SEQUENCE OF AsLinkAggrGroupEntry
        MAX-ACCESS   not-accessible
        STATUS       current
        DESCRIPTION
            "Alarm/Status for Link Aggregation Group. This table is created
            automatically when the Link Aggregation Group is defined."
        ::= { asLinkAggrGroup 1 }

    asLinkAggrGroupEntry OBJECT-TYPE
        SYNTAX       AsLinkAggrGroupEntry
        MAX-ACCESS   not-accessible
        STATUS       current
        DESCRIPTION  ""
        INDEX        { asLinkAggrGroupIfIndex }
        ::= { asLinkAggrGroupTable 1 }

    AsLinkAggrGroupEntry ::= SEQUENCE {
        asLinkAggrGroupIfIndex     InterfaceIndex,
        asLinkAggrGroupNEAddress   IpAddress,
        asLinkAggrGroupLinkStatus  SeverityValue,
        asLinkAggrGroupLLFStatus   INTEGER,
        asLinkAggrGroupOperStatus  INTEGER
    }

    asLinkAggrGroupIfIndex OBJECT-TYPE
        SYNTAX       InterfaceIndex
        MAX-ACCESS   not-accessible
        STATUS       current
        DESCRIPTION  "Index of this table."
        ::= { asLinkAggrGroupEntry 1 }

    asLinkAggrGroupNEAddress OBJECT-TYPE
        SYNTAX       IpAddress
        MAX-ACCESS   not-accessible
        STATUS       current
        DESCRIPTION  "reserved."
        ::= { asLinkAggrGroupEntry 2 }

    asLinkAggrGroupLinkStatus OBJECT-TYPE
        SYNTAX       SeverityValue
        MAX-ACCESS   read-only
        STATUS       current
        DESCRIPTION
            "Link Status for Link Aggregation Group. The all member ports
            become link down, this state becomes alarm state.
            But the lower layer is in alarm state, the link status becomes
            'normal' state because of alarm mask function."
        ::= { asLinkAggrGroupEntry 3 }

    asLinkAggrGroupLLFStatus OBJECT-TYPE
        SYNTAX       INTEGER { invalid(0), normal(1), force(2) }
        MAX-ACCESS   read-only
        STATUS       current
        DESCRIPTION
            "The status for link loss forwarding. 'force' means the interface
            is shutting down by the link loss forwarding."
        ::= { asLinkAggrGroupEntry 4 }

    asLinkAggrGroupOperStatus OBJECT-TYPE
        SYNTAX       INTEGER { invalid(0), linkDown(1), linkUp(2) }
        MAX-ACCESS   read-only
        STATUS       current
        DESCRIPTION
            "Link Status for Link Aggregation Group. This object keeps
            linkDown state, when the lower layer is in alarm state."
        ::= { asLinkAggrGroupEntry 5 }

    asLinkAggrPortTable OBJECT-TYPE
        SYNTAX       SEQUENCE OF AsLinkAggrPortEntry
        MAX-ACCESS   not-accessible
        STATUS       current
        DESCRIPTION
            "The Link Aggregation Member Port Status. This table is created
            automatically when a link aggregation group is defined.
            This table is created per each member port per link aggregation
            group."
        ::= { asLinkAggrGroup 2 }

    asLinkAggrPortEntry OBJECT-TYPE
        SYNTAX       AsLinkAggrPortEntry
        MAX-ACCESS   not-accessible
        STATUS       current
        DESCRIPTION  ""
        INDEX        { asLinkAggrPortGroupIfIndex, asLinkAggrPortIfIndex }
        ::= { asLinkAggrPortTable 1 }

    AsLinkAggrPortEntry ::= SEQUENCE {
        asLinkAggrPortGroupIfIndex       InterfaceIndex,
        asLinkAggrPortIfIndex            InterfaceIndex,
        asLinkAggrPortNEAddress          IpAddress,
        asLinkAggrPortStatus             INTEGER,
        asLinkAggrPortActorLacpStatus    BITS,
        asLinkAggrPortPartnerLacpStatus  BITS,
        asLinkAggrPortLoopDetect         INTEGER
    }

    asLinkAggrPortGroupIfIndex OBJECT-TYPE
        SYNTAX       InterfaceIndex
        MAX-ACCESS   not-accessible
        STATUS       current
        DESCRIPTION  "Index of this table."
        ::= { asLinkAggrPortEntry 1 }

    asLinkAggrPortIfIndex OBJECT-TYPE
        SYNTAX       InterfaceIndex
        MAX-ACCESS   not-accessible
        STATUS       current
        DESCRIPTION  "Index of this table."
        ::= { asLinkAggrPortEntry 2 }

    asLinkAggrPortNEAddress OBJECT-TYPE
        SYNTAX       IpAddress
        MAX-ACCESS   not-accessible
        STATUS       current
        DESCRIPTION  "reserved."
        ::= { asLinkAggrPortEntry 3 }

    asLinkAggrPortStatus OBJECT-TYPE
        SYNTAX       INTEGER { invalid(0), active(1), standby(2) }
        MAX-ACCESS   read-only
        STATUS       current
        DESCRIPTION
            "The port role of the member port.
            'active' means the port forwards/receives the packets on the
            interface."
        ::= { asLinkAggrPortEntry 4 }

    asLinkAggrPortActorLacpStatus OBJECT-TYPE
        SYNTAX       BITS {
                         lacpActivity(0),
                         lacpTimeout(1),
                         aggregation(2),
                         synchronization(3),
                         collecting(4),
                         distributing(5),
                         defaulted(6),
                         expired(7)
                     }
        MAX-ACCESS   read-only
        STATUS       current
        DESCRIPTION
            "A string of 8 bits, corresponding to the current operational
            values of Actor_State as transmitted by the Actor in LACPDUs."
        ::= { asLinkAggrPortEntry 5 }

    asLinkAggrPortPartnerLacpStatus OBJECT-TYPE
        SYNTAX       BITS {
                         lacpActivity(0),
                         lacpTimeout(1),
                         aggregation(2),
                         synchronization(3),
                         collecting(4),
                         distributing(5),
                         defaulted(6),
                         expired(7)
                     }
        MAX-ACCESS   read-only
        STATUS       current
        DESCRIPTION
            "A string of 8 bits, corresponding to the current values of
            Actor_State in the most recently received LACPDU transmitted by
            the protocol Partner."
        ::= { asLinkAggrPortEntry 6 }

    asLinkAggrPortLoopDetect OBJECT-TYPE
        SYNTAX       INTEGER { invalid(0), none(1), detected(2) }
        MAX-ACCESS   read-only
        STATUS       current
        DESCRIPTION
            "LACP Control frames loop detect status for that port. This
            status will be cleared when the condition is not detected for a
            fixed time."
        ::= { asLinkAggrPortEntry 7 }

    asLinkAggrPortStatsTable OBJECT-TYPE
        SYNTAX       SEQUENCE OF AsLinkAggrPortStatsEntry
        MAX-ACCESS   not-accessible
        STATUS       current
        DESCRIPTION  "Link Aggregation Statistics."
        ::= { asLinkAggrGroup 3 }

    asLinkAggrPortStatsEntry OBJECT-TYPE
        SYNTAX       AsLinkAggrPortStatsEntry
        MAX-ACCESS   not-accessible
        STATUS       current
        DESCRIPTION  ""
        INDEX        { asLinkAggrPortStatsIfIndex }
        ::= { asLinkAggrPortStatsTable 1 }

    AsLinkAggrPortStatsEntry ::= SEQUENCE {
        asLinkAggrPortStatsIfIndex           InterfaceIndex,
        asLinkAggrPortStatsNEAddress         IpAddress,
        asLinkAggrPortStatsLACPDUsRx         Counter32,
        asLinkAggrPortStatsLACPDUsTx         Counter32,
        asLinkAggrPortStatsMarkerPDUsRx      Counter32,
        asLinkAggrPortStatsMarkerRespPDUsRx  Counter32,
        asLinkAggrPortStatsMarkerPDUsTx      Counter32,
        asLinkAggrPortStatsMarkerRespPDUsTx  Counter32
    }

    asLinkAggrPortStatsIfIndex OBJECT-TYPE
        SYNTAX       InterfaceIndex
        MAX-ACCESS   not-accessible
        STATUS       current
        DESCRIPTION  "Index of this table."
        ::= { asLinkAggrPortStatsEntry 1 }

    asLinkAggrPortStatsNEAddress OBJECT-TYPE
        SYNTAX       IpAddress
        MAX-ACCESS   not-accessible
        STATUS       current
        DESCRIPTION  "reserved."
        ::= { asLinkAggrPortStatsEntry 2 }

    asLinkAggrPortStatsLACPDUsRx OBJECT-TYPE
        SYNTAX       Counter32
        MAX-ACCESS   read-only
        STATUS       current
        DESCRIPTION
            "The number of valid LACPDUs received on this Aggregation Port."
        ::= { asLinkAggrPortStatsEntry 3 }

    asLinkAggrPortStatsLACPDUsTx OBJECT-TYPE
        SYNTAX       Counter32
        MAX-ACCESS   read-only
        STATUS       current
        DESCRIPTION
            "The number of LACPDUs transmitted on this
            Aggregation Port."
        ::= { asLinkAggrPortStatsEntry 4 }

    asLinkAggrPortStatsMarkerPDUsRx OBJECT-TYPE
        SYNTAX       Counter32
        MAX-ACCESS   read-only
        STATUS       current
        DESCRIPTION
            "The number of valid Marker PDUs received on this Aggregation
            Port."
        ::= { asLinkAggrPortStatsEntry 5 }

    asLinkAggrPortStatsMarkerRespPDUsRx OBJECT-TYPE
        SYNTAX       Counter32
        MAX-ACCESS   read-only
        STATUS       current
        DESCRIPTION
            "The number of valid Marker Response PDUs received on this
            Aggregation Port."
        ::= { asLinkAggrPortStatsEntry 6 }

    asLinkAggrPortStatsMarkerPDUsTx OBJECT-TYPE
        SYNTAX       Counter32
        MAX-ACCESS   read-only
        STATUS       current
        DESCRIPTION
            "The number of Marker PDUs transmitted on this Aggregation Port."
        ::= { asLinkAggrPortStatsEntry 7 }

    asLinkAggrPortStatsMarkerRespPDUsTx OBJECT-TYPE
        SYNTAX       Counter32
        MAX-ACCESS   read-only
        STATUS       current
        DESCRIPTION
            "The number of Marker Response PDUs transmitted on this
            Aggregation Port."
        ::= { asLinkAggrPortStatsEntry 8 }

-----------------------------------------------
-- provisioningGroup Definitions
-----------------------------------------------

    provLinkAggrGroup OBJECT IDENTIFIER
        ::= { provisioningGroup 38 }

    provLinkAggrGroupTable OBJECT-TYPE
        SYNTAX       SEQUENCE OF ProvLinkAggrGroupEntry
        MAX-ACCESS   not-accessible
        STATUS       current
        DESCRIPTION
            "Link Aggregation Table.
            This table controls creation and deletion of link aggregation
            group."
        ::= { provLinkAggrGroup 1 }

    provLinkAggrGroupEntry OBJECT-TYPE
        SYNTAX       ProvLinkAggrGroupEntry
        MAX-ACCESS   not-accessible
        STATUS       current
        DESCRIPTION  ""
        INDEX        { provLinkAggrGroupIfIndex }
        ::= { provLinkAggrGroupTable 1 }

    ProvLinkAggrGroupEntry ::= SEQUENCE {
        provLinkAggrGroupIfIndex      InterfaceIndex,
        provLinkAggrGroupNEAddress    IpAddress,
        provLinkAggrGroupMode         INTEGER,
        provLinkAggrGrLacpTxInterval  INTEGER,
        provLinkAggrGroupRevertive    IpeEnableDisableValue,
        provLinkAggrGroupTxType       INTEGER,
        provLinkAggrGroupName         DisplayString,
        provLinkAggrGroupRowStatus    RowStatus,
        provLinkAggrGroupMemberPort1  InterfaceIndexOrZero,
        provLinkAggrGroupMemberPort2  InterfaceIndexOrZero,
        provLinkAggrGroupMemberPort3  InterfaceIndexOrZero,
        provLinkAggrGroupMemberPort4  InterfaceIndexOrZero,
        provLinkAggrGroupMemberPort5  InterfaceIndexOrZero,
        provLinkAggrGroupMemberPort6  InterfaceIndexOrZero,
        provLinkAggrGroupMemberPort7  InterfaceIndexOrZero,
        provLinkAggrGroupMemberPort8  InterfaceIndexOrZero
    }

    provLinkAggrGroupIfIndex OBJECT-TYPE
        SYNTAX       InterfaceIndex
        MAX-ACCESS   not-accessible
        STATUS       current
        DESCRIPTION  "Index of this table."
        ::= { provLinkAggrGroupEntry 1 }

    provLinkAggrGroupNEAddress OBJECT-TYPE
        SYNTAX       IpAddress
        MAX-ACCESS   not-accessible
        STATUS       current
        DESCRIPTION  "reserved."
        ::= { provLinkAggrGroupEntry 2 }

    provLinkAggrGroupMode OBJECT-TYPE
        SYNTAX       INTEGER { invalid(0), active(1), passive(2), local(3) }
        MAX-ACCESS   read-create
        STATUS       current
        DESCRIPTION
            "Link Aggregation Group Mode configuration.
            When the 'active' is configured, LACPDUs are always sent along
            with configured links. On the other hand, LACPDUs are sent only
            when receiving LACPDUs from other switch. In the 'local' mode,
            the port status such as active or standby is statically
            configured."
        ::= { provLinkAggrGroupEntry 3 }

    provLinkAggrGrLacpTxInterval OBJECT-TYPE
        SYNTAX       INTEGER { invalid(0), short(1), long(2) }
        MAX-ACCESS   read-create
        STATUS       current
        DESCRIPTION
            "The sending interval of LACPDUs.'short' mode sends LACPDUs in
            every 1 second. 'long' mode sends LACPDUs in every 30 seconds."
        DEFVAL       { short }
        ::= { provLinkAggrGroupEntry 4 }

    provLinkAggrGroupRevertive OBJECT-TYPE
        SYNTAX       IpeEnableDisableValue
        MAX-ACCESS   read-create
        STATUS       current
        DESCRIPTION
            "Indicates the revertive method(When Static mode is enabled)"
        DEFVAL       { disabled }
        ::= { provLinkAggrGroupEntry 5 }

    provLinkAggrGroupTxType OBJECT-TYPE
        SYNTAX       INTEGER { invalid(0), macVid(1), mplsLabel(2), ipVid(3) }
        MAX-ACCESS   read-create
        STATUS       current
        DESCRIPTION
            "A rule of frame transmission among the multiple member ports."
        DEFVAL       { macVid }
        ::= { provLinkAggrGroupEntry 6 }

    provLinkAggrGroupName OBJECT-TYPE
        SYNTAX       DisplayString (SIZE(0..32))
        MAX-ACCESS   read-create
        STATUS       current
        DESCRIPTION  "Indicates the name of Link Aggregation Group "
        DEFVAL       { "" }
        ::= { provLinkAggrGroupEntry 7 }

    provLinkAggrGroupRowStatus OBJECT-TYPE
        SYNTAX       RowStatus
        MAX-ACCESS   read-create
        STATUS       current
        DESCRIPTION
            "This object is used to create and remove the Link Aggregation
            Group. When creating new Link Aggregation Group, it is necessary
            to configure at least one member port by using
            provLinkAggrGroupMemberPort."
        ::= { provLinkAggrGroupEntry 8 }

    provLinkAggrGroupMemberPort1 OBJECT-TYPE
        SYNTAX       InterfaceIndexOrZero
        MAX-ACCESS   read-create
        STATUS       current
        DESCRIPTION  "Link Aggregation Group member Port1"
        DEFVAL       { 0 }
        ::= { provLinkAggrGroupEntry 9 }

    provLinkAggrGroupMemberPort2 OBJECT-TYPE
        SYNTAX       InterfaceIndexOrZero
        MAX-ACCESS   read-create
        STATUS       current
        DESCRIPTION  "Link Aggregation Group member Port2"
        DEFVAL       { 0 }
        ::= { provLinkAggrGroupEntry 10 }

    provLinkAggrGroupMemberPort3 OBJECT-TYPE
        SYNTAX       InterfaceIndexOrZero
        MAX-ACCESS   read-create
        STATUS       current
        DESCRIPTION  "Link Aggregation Group member Port3"
        DEFVAL       { 0 }
        ::= { provLinkAggrGroupEntry 11 }

    provLinkAggrGroupMemberPort4 OBJECT-TYPE
        SYNTAX       InterfaceIndexOrZero
        MAX-ACCESS   read-create
        STATUS       current
        DESCRIPTION  "Link Aggregation Group member Port4"
        DEFVAL       { 0 }
        ::= { provLinkAggrGroupEntry 12 }

    provLinkAggrGroupMemberPort5 OBJECT-TYPE
        SYNTAX       InterfaceIndexOrZero
        MAX-ACCESS   read-create
        STATUS       current
        DESCRIPTION  "Link Aggregation Group member Port5"
        DEFVAL       { 0 }
        ::= { provLinkAggrGroupEntry 13 }

    provLinkAggrGroupMemberPort6 OBJECT-TYPE
        SYNTAX       InterfaceIndexOrZero
        MAX-ACCESS   read-create
        STATUS       current
        DESCRIPTION  "Link Aggregation Group member Port6"
        DEFVAL       { 0 }
        ::= { provLinkAggrGroupEntry 14 }

    provLinkAggrGroupMemberPort7 OBJECT-TYPE
        SYNTAX       InterfaceIndexOrZero
        MAX-ACCESS   read-create
        STATUS       current
        DESCRIPTION  "Link Aggregation Group member Port7"
        DEFVAL       { 0 }
        ::= { provLinkAggrGroupEntry 15 }

    provLinkAggrGroupMemberPort8 OBJECT-TYPE
        SYNTAX       InterfaceIndexOrZero
        MAX-ACCESS   read-create
        STATUS       current
        DESCRIPTION  "Link Aggregation Group member Port8"
        DEFVAL       { 0 }
        ::= { provLinkAggrGroupEntry 16 }

    provLinkAggrPortTable OBJECT-TYPE
        SYNTAX       SEQUENCE OF ProvLinkAggrPortEntry
        MAX-ACCESS   not-accessible
        STATUS       current
        DESCRIPTION
            "The table configures the link aggregation member port. This
            table is created automatically by setting interface index to
            provLinkAggrGroupMemberPort."
        ::= { provLinkAggrGroup 2 }

    provLinkAggrPortEntry OBJECT-TYPE
        SYNTAX       ProvLinkAggrPortEntry
        MAX-ACCESS   not-accessible
        STATUS       current
        DESCRIPTION  ""
        INDEX        { provLinkAggrPortGroupIfIndex, provLinkAggrPortIfIndex }
        ::= { provLinkAggrPortTable 1 }

    ProvLinkAggrPortEntry ::= SEQUENCE {
        provLinkAggrPortGroupIfIndex  InterfaceIndex,
        provLinkAggrPortIfIndex       InterfaceIndex,
        provLinkAggrPortNEAddress     IpAddress,
        provLinkAggrPortRole          INTEGER
    }

    provLinkAggrPortGroupIfIndex OBJECT-TYPE
        SYNTAX       InterfaceIndex
        MAX-ACCESS   not-accessible
        STATUS       current
        DESCRIPTION  "Index of this table."
        ::= { provLinkAggrPortEntry 1 }

    provLinkAggrPortIfIndex OBJECT-TYPE
        SYNTAX       InterfaceIndex
        MAX-ACCESS   not-accessible
        STATUS       current
        DESCRIPTION  "Index of this table."
        ::= { provLinkAggrPortEntry 2 }

    provLinkAggrPortNEAddress OBJECT-TYPE
        SYNTAX       IpAddress
        MAX-ACCESS   not-accessible
        STATUS       current
        DESCRIPTION  "reserved."
        ::= { provLinkAggrPortEntry 3 }

    provLinkAggrPortRole OBJECT-TYPE
        SYNTAX       INTEGER { invalid(0), active(1), standby(2) }
        MAX-ACCESS   read-write
        STATUS       current
        DESCRIPTION
            "Port role configuration. When the Link Aggregation Group
            operates in static mode, port status is decided by this object.
            In other operating mode, the configuration is used in negotiation
            with peer switch."
        ::= { provLinkAggrPortEntry 4 }

    provLinkAggrPortExtTable OBJECT-TYPE
        SYNTAX       SEQUENCE OF ProvLinkAggrPortExtEntry
        MAX-ACCESS   not-accessible
        STATUS       current
        DESCRIPTION
            "This table configures the Port priority and is used for internal
            use only."
        ::= { provLinkAggrGroup 3 }

    provLinkAggrPortExtEntry OBJECT-TYPE
        SYNTAX       ProvLinkAggrPortExtEntry
        MAX-ACCESS   not-accessible
        STATUS       current
        DESCRIPTION  ""
        INDEX        {
                         provLinkAggrPortExtGroupIfIndex,
                         provLinkAggrPortExtIfIndex
                     }
        ::= { provLinkAggrPortExtTable 1 }

    ProvLinkAggrPortExtEntry ::= SEQUENCE {
        provLinkAggrPortExtGroupIfIndex  InterfaceIndex,
        provLinkAggrPortExtIfIndex       InterfaceIndex,
        provLinkAggrPortExtNEAddress     IpAddress,
        provLinkAggrPortExtPriority      Integer32
    }

    provLinkAggrPortExtGroupIfIndex OBJECT-TYPE
        SYNTAX       InterfaceIndex
        MAX-ACCESS   not-accessible
        STATUS       current
        DESCRIPTION  "Index of this table."
        ::= { provLinkAggrPortExtEntry 1 }

    provLinkAggrPortExtIfIndex OBJECT-TYPE
        SYNTAX       InterfaceIndex
        MAX-ACCESS   not-accessible
        STATUS       current
        DESCRIPTION  "Index of this table."
        ::= { provLinkAggrPortExtEntry 2 }

    provLinkAggrPortExtNEAddress OBJECT-TYPE
        SYNTAX       IpAddress
        MAX-ACCESS   not-accessible
        STATUS       current
        DESCRIPTION  "reserved."
        ::= { provLinkAggrPortExtEntry 3 }

    provLinkAggrPortExtPriority OBJECT-TYPE
        SYNTAX       Integer32 (1..65535)
        MAX-ACCESS   read-write
        STATUS       current
        DESCRIPTION
            "Port Priority Setting. This object is defined for internal use
            only. The port priority is configured automatically by its port
            status."
        DEFVAL       { 128 }
        ::= { provLinkAggrPortExtEntry 4 }

    provLinkAggrEquipmentTable OBJECT-TYPE
        SYNTAX       SEQUENCE OF ProvLinkAggrEquipmentEntry
        MAX-ACCESS   not-accessible
        STATUS       current
        DESCRIPTION
            "This table configures system parameter for link aggregation
            function. The table is created when the agent boots up."
        ::= { provLinkAggrGroup 4 }

    provLinkAggrEquipmentEntry OBJECT-TYPE
        SYNTAX       ProvLinkAggrEquipmentEntry
        MAX-ACCESS   not-accessible
        STATUS       current
        DESCRIPTION  ""
        INDEX        { provLinkAggrEquipmentIndex }
        ::= { provLinkAggrEquipmentTable 1 }

    ProvLinkAggrEquipmentEntry ::= SEQUENCE {
        provLinkAggrEquipmentIndex        Integer32,
        provLinkAggrEquipmentNEAddress    IpAddress,
        provLinkAggrEquipmentSysPriority  Integer32
    }

    provLinkAggrEquipmentIndex OBJECT-TYPE
        SYNTAX       Integer32 (1..1)
        MAX-ACCESS   not-accessible
        STATUS       current
        DESCRIPTION  "Index of this table."
        ::= { provLinkAggrEquipmentEntry 1 }

    provLinkAggrEquipmentNEAddress OBJECT-TYPE
        SYNTAX       IpAddress
        MAX-ACCESS   not-accessible
        STATUS       current
        DESCRIPTION  "reserved."
        ::= { provLinkAggrEquipmentEntry 2 }

    provLinkAggrEquipmentSysPriority OBJECT-TYPE
        SYNTAX       Integer32 (1..65535)
        MAX-ACCESS   read-write
        STATUS       current
        DESCRIPTION  "Indicates system Priority"
        DEFVAL       { 32768 }
        ::= { provLinkAggrEquipmentEntry 3 }

-----------------------------------------------
-- maintenanceGroup Definitions
-----------------------------------------------

    maintLinkAggrGroup OBJECT IDENTIFIER
        ::= { maintenanceGroup 38 }

    maintLinkAggrGroupTable OBJECT-TYPE
        SYNTAX       SEQUENCE OF MaintLinkAggrGroupEntry
        MAX-ACCESS   not-accessible
        STATUS       current
        DESCRIPTION
            "This table provides revert function per link aggregation group.
            The function performs re-initialize the lacp port status
            machine."
        ::= { maintLinkAggrGroup 1 }

    maintLinkAggrGroupEntry OBJECT-TYPE
        SYNTAX       MaintLinkAggrGroupEntry
        MAX-ACCESS   not-accessible
        STATUS       current
        DESCRIPTION  ""
        INDEX        { maintLinkAggrGroupIfIndex }
        ::= { maintLinkAggrGroupTable 1 }

    MaintLinkAggrGroupEntry ::= SEQUENCE {
        maintLinkAggrGroupIfIndex    InterfaceIndex,
        maintLinkAggrGroupNEAddress  IpAddress,
        maintLinkAggrGroupRevert     INTEGER
    }

    maintLinkAggrGroupIfIndex OBJECT-TYPE
        SYNTAX       InterfaceIndex
        MAX-ACCESS   not-accessible
        STATUS       current
        DESCRIPTION  "Index of this table."
        ::= { maintLinkAggrGroupEntry 1 }

    maintLinkAggrGroupNEAddress OBJECT-TYPE
        SYNTAX       IpAddress
        MAX-ACCESS   not-accessible
        STATUS       current
        DESCRIPTION  "reserved."
        ::= { maintLinkAggrGroupEntry 2 }

    maintLinkAggrGroupRevert OBJECT-TYPE
        SYNTAX       INTEGER { invalid(0), none(1), revert(2) }
        MAX-ACCESS   read-write
        STATUS       current
        DESCRIPTION  "Maintenance operation for the revertive control"
        ::= { maintLinkAggrGroupEntry 3 }

-----------------------------------------------
-- End User MIB Object Definitions
-----------------------------------------------

END
