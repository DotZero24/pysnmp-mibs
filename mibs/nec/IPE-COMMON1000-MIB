--
-- ASN.1 MIB Definitions
-- Output Date: Tue Jul 12 15:00:41 2016
--

IPE-COMMON1000-MIB DEFINITIONS ::= BEGIN

-----------------------------------------------
-- IMPORTS Definitions
-----------------------------------------------

    IMPORTS
        enterprises, Integer32, IpAddress, NOTIFICATION-TYPE, OBJECT-TYPE,
        Opaque
            FROM SNMPv2-SMI
        DateAndTime, DisplayString, TEXTUAL-CONVENTION
            FROM SNMPv2-TC;

-----------------------------------------------
-- Textual Convention Definitions
-----------------------------------------------

    OffOnValue ::= TEXTUAL-CONVENTION
        STATUS       current
        DESCRIPTION  "Off/On Type"
        SYNTAX       INTEGER { invalid(0), off(1), on(2) }

    SeverityValue ::= TEXTUAL-CONVENTION
        STATUS       current
        DESCRIPTION  "Severity (CCITT Rec. X.733)"
        SYNTAX       INTEGER {
                         cleared(1),
                         indetermine(2),
                         critical(3),
                         major(4),
                         minor(5),
                         warning(6)
                     }

-----------------------------------------------
-- Begin User MIB Object Definitions
-----------------------------------------------

    nec OBJECT IDENTIFIER
        ::= { enterprises 119 }

    nec-mib OBJECT IDENTIFIER
        ::= { nec 2 }

    necProductDepend OBJECT IDENTIFIER
        ::= { nec-mib 3 }

    radioEquipment OBJECT IDENTIFIER
        ::= { necProductDepend 69 }

    system5 OBJECT IDENTIFIER
        ::= { radioEquipment 5 }

    pasoNeoIpe-common OBJECT IDENTIFIER
        ::= { radioEquipment 501 }

-----------------------------------------------
-- system5 Group Definitions
-----------------------------------------------

    ipeConfigurationGroup OBJECT IDENTIFIER
        ::= { system5 3 }

    ipeCfgPortGroup OBJECT IDENTIFIER
        ::= { ipeConfigurationGroup 15 }

    ipeCfgPortLct1kTable OBJECT-TYPE
        SYNTAX       SEQUENCE OF IpeCfgPortLct1kEntry
        MAX-ACCESS   not-accessible
        STATUS       current
        DESCRIPTION
            "LCT port set up information table.
            TABSZ=1"
        ::= { ipeCfgPortGroup 8 }

    ipeCfgPortLct1kEntry OBJECT-TYPE
        SYNTAX       IpeCfgPortLct1kEntry
        MAX-ACCESS   not-accessible
        STATUS       current
        DESCRIPTION  "entry of  LCT port set up information table."
        INDEX        { ipeCfgPortLct1kIndex }
        ::= { ipeCfgPortLct1kTable 1 }

    IpeCfgPortLct1kEntry ::= SEQUENCE {
        ipeCfgPortLct1kIndex      Integer32,
        ipeCfgPortLct1kNEAddress  IpAddress,
        ipeCfgPortLct1kIpAddress  IpAddress,
        ipeCfgPortLct1kNetMask    IpAddress,
        ipeCfgPortLct1kEnable     INTEGER,
        ipeCfgPortLct1kMtu        Integer32,
        ipeCfgPortLct1kAutoNeg    INTEGER
    }

    ipeCfgPortLct1kIndex OBJECT-TYPE
        SYNTAX       Integer32 (1..2)
        MAX-ACCESS   not-accessible
        STATUS       current
        DESCRIPTION  "Index of this table."
        ::= { ipeCfgPortLct1kEntry 1 }

    ipeCfgPortLct1kNEAddress OBJECT-TYPE
        SYNTAX       IpAddress
        MAX-ACCESS   not-accessible
        STATUS       current
        DESCRIPTION  "reserved."
        ::= { ipeCfgPortLct1kEntry 2 }

    ipeCfgPortLct1kIpAddress OBJECT-TYPE
        SYNTAX       IpAddress
        MAX-ACCESS   read-write
        STATUS       current
        DESCRIPTION  "IPaddress of LCT port."
        ::= { ipeCfgPortLct1kEntry 3 }

    ipeCfgPortLct1kNetMask OBJECT-TYPE
        SYNTAX       IpAddress
        MAX-ACCESS   read-write
        STATUS       current
        DESCRIPTION  "Subnet mask of LCT port."
        ::= { ipeCfgPortLct1kEntry 4 }

    ipeCfgPortLct1kEnable OBJECT-TYPE
        SYNTAX       INTEGER { enabled(1), disabled(2) }
        MAX-ACCESS   read-write
        STATUS       current
        DESCRIPTION  "Effective/invalid setting of LCT port."
        ::= { ipeCfgPortLct1kEntry 5 }

    ipeCfgPortLct1kMtu OBJECT-TYPE
        SYNTAX       Integer32 (256..1500)
        MAX-ACCESS   read-write
        STATUS       current
        DESCRIPTION
            "MTU value of LCT.
            value range:256 to 1500"
        ::= { ipeCfgPortLct1kEntry 6 }

    ipeCfgPortLct1kAutoNeg OBJECT-TYPE
        SYNTAX       INTEGER { enabled(1), disabled(2) }
        MAX-ACCESS   read-write
        STATUS       current
        DESCRIPTION
            "Effective/invalid setting of LCT AUTO NEGOTIATION.
            value range: enabled
                        disabled"
        ::= { ipeCfgPortLct1kEntry 7 }

-----------------------------------------------
-- IPE COMMON Group Definitions
-----------------------------------------------

    alarmStatusGroup OBJECT IDENTIFIER
        ::= { pasoNeoIpe-common 3 }

    provisioningGroup OBJECT IDENTIFIER
        ::= { pasoNeoIpe-common 5 }

    maintenanceGroup OBJECT IDENTIFIER
        ::= { pasoNeoIpe-common 6 }

-----------------------------------------------
-- alarmStatusGroup Definitions
-----------------------------------------------

    asMainCtrlGroup OBJECT IDENTIFIER
        ::= { alarmStatusGroup 35 }

    asMainCtrlGroupTable OBJECT-TYPE
        SYNTAX       SEQUENCE OF AsMainCtrlGroupEntry
        MAX-ACCESS   not-accessible
        STATUS       current
        DESCRIPTION  "Main card group object for iPASO1000."
        ::= { asMainCtrlGroup 1 }

    asMainCtrlGroupEntry OBJECT-TYPE
        SYNTAX       AsMainCtrlGroupEntry
        MAX-ACCESS   not-accessible
        STATUS       current
        DESCRIPTION  ""
        INDEX        { asMainCtrlGroupIndex }
        ::= { asMainCtrlGroupTable 1 }

    AsMainCtrlGroupEntry ::= SEQUENCE {
        asMainCtrlGroupIndex                 Integer32,
        asMainCtrlGroupNEAddress             IpAddress,
        ctrlGroupSvLineAlarm                 SeverityValue,
        ctrlGroupIduTotalAlarm               SeverityValue,
        ctrlGroupMaintenance                 OffOnValue,
        ctrlGroupComFail                     SeverityValue,
        ctrlGroupFirmwareVerMismatch         SeverityValue,
        ctrlGroupCardMismatch                SeverityValue,
        ctrlGroupHardwareVerMismatch         SeverityValue,
        ctrlGroupMountedClk2mMismatch        SeverityValue,
        ctrlGroupSwitchOverFailure           OffOnValue,
        ctrlGroupSwitchComplete              OffOnValue,
        ctrlGroupForcedSbySwitchComplete     OffOnValue,
        ctrlGroupSwitchedTime                DateAndTime,
        ctrlGroupSwitchedReason              DisplayString,
        ctrlGroupConfigDataStoredTime        DateAndTime,
        ctrlGroupSbyBusErrorTx               SeverityValue,
        ctrlGroupSbyBusErrorRx               SeverityValue,
        ctrlGroupSbyTermComFailAlarm         SeverityValue,
        ctrlGroupDbMismatch                  SeverityValue,
        ctrlGroupSoftkeyEquipSerialMismatch  SeverityValue
    }

    asMainCtrlGroupIndex OBJECT-TYPE
        SYNTAX       Integer32 (1..1)
        MAX-ACCESS   not-accessible
        STATUS       current
        DESCRIPTION  "Index of this table."
        ::= { asMainCtrlGroupEntry 1 }

    asMainCtrlGroupNEAddress OBJECT-TYPE
        SYNTAX       IpAddress
        MAX-ACCESS   not-accessible
        STATUS       current
        DESCRIPTION  "reserved."
        ::= { asMainCtrlGroupEntry 2 }

    ctrlGroupSvLineAlarm OBJECT-TYPE
        SYNTAX       SeverityValue
        MAX-ACCESS   read-only
        STATUS       current
        DESCRIPTION  "SV Line Alarm"
        ::= { asMainCtrlGroupEntry 3 }

    ctrlGroupIduTotalAlarm OBJECT-TYPE
        SYNTAX       SeverityValue
        MAX-ACCESS   read-only
        STATUS       current
        DESCRIPTION  "IDU Alarm"
        ::= { asMainCtrlGroupEntry 4 }

    ctrlGroupMaintenance OBJECT-TYPE
        SYNTAX       OffOnValue
        MAX-ACCESS   read-only
        STATUS       current
        DESCRIPTION  "Maintenance"
        ::= { asMainCtrlGroupEntry 5 }

    ctrlGroupComFail OBJECT-TYPE
        SYNTAX       SeverityValue
        MAX-ACCESS   read-only
        STATUS       current
        DESCRIPTION  "Communication FAIL"
        ::= { asMainCtrlGroupEntry 6 }

    ctrlGroupFirmwareVerMismatch OBJECT-TYPE
        SYNTAX       SeverityValue
        MAX-ACCESS   read-only
        STATUS       current
        DESCRIPTION  "Firmware Version Mismatch"
        ::= { asMainCtrlGroupEntry 7 }

    ctrlGroupCardMismatch OBJECT-TYPE
        SYNTAX       SeverityValue
        MAX-ACCESS   read-only
        STATUS       current
        DESCRIPTION  "Card Type Mismatch"
        ::= { asMainCtrlGroupEntry 8 }

    ctrlGroupHardwareVerMismatch OBJECT-TYPE
        SYNTAX       SeverityValue
        MAX-ACCESS   read-only
        STATUS       current
        DESCRIPTION  "Hardware Version Mismatch"
        ::= { asMainCtrlGroupEntry 9 }

    ctrlGroupMountedClk2mMismatch OBJECT-TYPE
        SYNTAX       SeverityValue
        MAX-ACCESS   read-only
        STATUS       current
        DESCRIPTION  "Option Card Mismatch"
        ::= { asMainCtrlGroupEntry 10 }

    ctrlGroupSwitchOverFailure OBJECT-TYPE
        SYNTAX       OffOnValue
        MAX-ACCESS   read-only
        STATUS       current
        DESCRIPTION  "Switch Over Fail"
        ::= { asMainCtrlGroupEntry 11 }

    ctrlGroupSwitchComplete OBJECT-TYPE
        SYNTAX       OffOnValue
        MAX-ACCESS   read-only
        STATUS       current
        DESCRIPTION  "Switch Complete"
        ::= { asMainCtrlGroupEntry 12 }

    ctrlGroupForcedSbySwitchComplete OBJECT-TYPE
        SYNTAX       OffOnValue
        MAX-ACCESS   read-only
        STATUS       current
        DESCRIPTION  "Forced Switch Complete"
        ::= { asMainCtrlGroupEntry 13 }

    ctrlGroupSwitchedTime OBJECT-TYPE
        SYNTAX       DateAndTime
        MAX-ACCESS   read-only
        STATUS       current
        DESCRIPTION  "Switched Time"
        ::= { asMainCtrlGroupEntry 14 }

    ctrlGroupSwitchedReason OBJECT-TYPE
        SYNTAX       DisplayString (SIZE(0..32))
        MAX-ACCESS   read-only
        STATUS       current
        DESCRIPTION  "Switched Reason"
        ::= { asMainCtrlGroupEntry 15 }

    ctrlGroupConfigDataStoredTime OBJECT-TYPE
        SYNTAX       DateAndTime
        MAX-ACCESS   read-only
        STATUS       current
        DESCRIPTION  "Config Data Stored Time"
        ::= { asMainCtrlGroupEntry 16 }

    ctrlGroupSbyBusErrorTx OBJECT-TYPE
        SYNTAX       SeverityValue
        MAX-ACCESS   read-only
        STATUS       current
        DESCRIPTION  "SBY TX Bus Error"
        ::= { asMainCtrlGroupEntry 17 }

    ctrlGroupSbyBusErrorRx OBJECT-TYPE
        SYNTAX       SeverityValue
        MAX-ACCESS   read-only
        STATUS       current
        DESCRIPTION  "SBY RX Bus Error"
        ::= { asMainCtrlGroupEntry 18 }

    ctrlGroupSbyTermComFailAlarm OBJECT-TYPE
        SYNTAX       SeverityValue
        MAX-ACCESS   read-only
        STATUS       current
        DESCRIPTION  "SBY Communication Fail (TERM)"
        ::= { asMainCtrlGroupEntry 19 }

    ctrlGroupDbMismatch OBJECT-TYPE
        SYNTAX       SeverityValue
        MAX-ACCESS   read-only
        STATUS       current
        DESCRIPTION  "DB Mismatch"
        ::= { asMainCtrlGroupEntry 20 }

    ctrlGroupSoftkeyEquipSerialMismatch OBJECT-TYPE
        SYNTAX       SeverityValue
        MAX-ACCESS   read-only
        STATUS       current
        DESCRIPTION  "Software Key Equip Serial Mismatch"
        ::= { asMainCtrlGroupEntry 21 }

    asMainCtrlCardTable OBJECT-TYPE
        SYNTAX       SEQUENCE OF AsMainCtrlCardEntry
        MAX-ACCESS   not-accessible
        STATUS       current
        DESCRIPTION  "Main card object for iPASO1000."
        ::= { asMainCtrlGroup 2 }

    asMainCtrlCardEntry OBJECT-TYPE
        SYNTAX       AsMainCtrlCardEntry
        MAX-ACCESS   not-accessible
        STATUS       current
        DESCRIPTION  ""
        INDEX        { asMainCtrlCardIndex }
        ::= { asMainCtrlCardTable 1 }

    AsMainCtrlCardEntry ::= SEQUENCE {
        asMainCtrlCardIndex      Integer32,
        asMainCtrlCardNEAddress  IpAddress,
        mainCardAlarm            SeverityValue,
        mainUsbFailure           SeverityValue,
        mainCpuAlarm             SeverityValue,
        mainMemoryFailure        SeverityValue,
        mainClk2mMount           INTEGER,
        mainCardRunningStatus    INTEGER,
        mainTempAlarm            SeverityValue,
        mainCtrlUnequipped       SeverityValue,
        mainCtrlBusError         SeverityValue,
        mainTemperature          Integer32,
        mainFPGAMismatch         SeverityValue
    }

    asMainCtrlCardIndex OBJECT-TYPE
        SYNTAX       Integer32 (17..18)
        MAX-ACCESS   not-accessible
        STATUS       current
        DESCRIPTION  "Index of this table."
        ::= { asMainCtrlCardEntry 1 }

    asMainCtrlCardNEAddress OBJECT-TYPE
        SYNTAX       IpAddress
        MAX-ACCESS   not-accessible
        STATUS       current
        DESCRIPTION  "reserved."
        ::= { asMainCtrlCardEntry 2 }

    mainCardAlarm OBJECT-TYPE
        SYNTAX       SeverityValue
        MAX-ACCESS   read-only
        STATUS       current
        DESCRIPTION  "Main Card Alarm"
        ::= { asMainCtrlCardEntry 3 }

    mainUsbFailure OBJECT-TYPE
        SYNTAX       SeverityValue
        MAX-ACCESS   read-only
        STATUS       current
        DESCRIPTION  "Main Card USB Fail"
        ::= { asMainCtrlCardEntry 4 }

    mainCpuAlarm OBJECT-TYPE
        SYNTAX       SeverityValue
        MAX-ACCESS   read-only
        STATUS       current
        DESCRIPTION  "Main Card CPU Alarm"
        ::= { asMainCtrlCardEntry 5 }

    mainMemoryFailure OBJECT-TYPE
        SYNTAX       SeverityValue
        MAX-ACCESS   read-only
        STATUS       current
        DESCRIPTION  "Main Card Memory Fail"
        ::= { asMainCtrlCardEntry 6 }

    mainClk2mMount OBJECT-TYPE
        SYNTAX       INTEGER { unmount(1), mount(2) }
        MAX-ACCESS   read-only
        STATUS       current
        DESCRIPTION  "Main Clock Mount status"
        ::= { asMainCtrlCardEntry 7 }

    mainCardRunningStatus OBJECT-TYPE
        SYNTAX       INTEGER {
                         invalid(0),
                         act(1),
                         sby(2),
                         flt(3),
                         actFlt(4),
                         sbyFlt(5),
                         init(6),
                         oos(7),
                         initFlt(8),
                         unmount(9)
                     }
        MAX-ACCESS   read-only
        STATUS       current
        DESCRIPTION  "Running Status"
        ::= { asMainCtrlCardEntry 8 }

    mainTempAlarm OBJECT-TYPE
        SYNTAX       SeverityValue
        MAX-ACCESS   read-only
        STATUS       current
        DESCRIPTION  "Temperature"
        ::= { asMainCtrlCardEntry 9 }

    mainCtrlUnequipped OBJECT-TYPE
        SYNTAX       SeverityValue
        MAX-ACCESS   read-only
        STATUS       current
        DESCRIPTION  "Mount Status"
        ::= { asMainCtrlCardEntry 10 }

    mainCtrlBusError OBJECT-TYPE
        SYNTAX       SeverityValue
        MAX-ACCESS   read-only
        STATUS       current
        DESCRIPTION  "Bus Error"
        ::= { asMainCtrlCardEntry 11 }

    mainTemperature OBJECT-TYPE
        SYNTAX       Integer32 (-999..-999|-500..1500)
        UNITS        "0.1 degree"
        MAX-ACCESS   read-only
        STATUS       current
        DESCRIPTION
            "Main Card Temperature.
            range: -200~900(iPASOLINK200/400/1000series/EX/iX),
            -200~1500(iPASOLINK VR series), -500~1500(iPASOLINK EX/A)
            if the unexpected condition happened, the object reports value
            '-999'."
        ::= { asMainCtrlCardEntry 12 }

    mainFPGAMismatch OBJECT-TYPE
        SYNTAX       SeverityValue
        MAX-ACCESS   read-only
        STATUS       current
        DESCRIPTION  "Firmware / FPGA Mismatch"
        ::= { asMainCtrlCardEntry 13 }

-----------------------------------------------
-- provisioningGroup Definitions
-----------------------------------------------

    provCtrl1kGroup OBJECT IDENTIFIER
        ::= { provisioningGroup 35 }

    provMiscDescriptionTable OBJECT-TYPE
        SYNTAX       SEQUENCE OF ProvMiscDescriptionEntry
        MAX-ACCESS   not-accessible
        STATUS       current
        DESCRIPTION
            "Represents the description table that the user can describe."
        ::= { provCtrl1kGroup 1 }

    provMiscDescriptionEntry OBJECT-TYPE
        SYNTAX       ProvMiscDescriptionEntry
        MAX-ACCESS   not-accessible
        STATUS       current
        DESCRIPTION  ""
        INDEX        { provMiscDescriptionIndex }
        ::= { provMiscDescriptionTable 1 }

    ProvMiscDescriptionEntry ::= SEQUENCE {
        provMiscDescriptionIndex      Integer32,
        provMiscDescriptionNEAddress  IpAddress,
        provMiscDescription1          DisplayString,
        provMiscDescription2          DisplayString,
        provMiscDescription3          DisplayString,
        provMiscDescription4          DisplayString,
        provMiscDescription5          DisplayString,
        provMiscDescription6          DisplayString,
        provMiscDescription7          DisplayString,
        provMiscDescription8          DisplayString,
        provMiscDescription9          DisplayString
    }

    provMiscDescriptionIndex OBJECT-TYPE
        SYNTAX       Integer32 (1..23)
        MAX-ACCESS   not-accessible
        STATUS       current
        DESCRIPTION  "Index of this table."
        ::= { provMiscDescriptionEntry 1 }

    provMiscDescriptionNEAddress OBJECT-TYPE
        SYNTAX       IpAddress
        MAX-ACCESS   not-accessible
        STATUS       current
        DESCRIPTION  "reserved."
        ::= { provMiscDescriptionEntry 2 }

    provMiscDescription1 OBJECT-TYPE
        SYNTAX       DisplayString (SIZE(0..32))
        MAX-ACCESS   read-write
        STATUS       current
        DESCRIPTION  "Description area 1."
        ::= { provMiscDescriptionEntry 3 }

    provMiscDescription2 OBJECT-TYPE
        SYNTAX       DisplayString (SIZE(0..32))
        MAX-ACCESS   read-write
        STATUS       current
        DESCRIPTION  "Description area 2."
        ::= { provMiscDescriptionEntry 4 }

    provMiscDescription3 OBJECT-TYPE
        SYNTAX       DisplayString (SIZE(0..32))
        MAX-ACCESS   read-write
        STATUS       current
        DESCRIPTION  "Description area 3."
        ::= { provMiscDescriptionEntry 5 }

    provMiscDescription4 OBJECT-TYPE
        SYNTAX       DisplayString (SIZE(0..32))
        MAX-ACCESS   read-write
        STATUS       current
        DESCRIPTION  "Description area 4."
        ::= { provMiscDescriptionEntry 6 }

    provMiscDescription5 OBJECT-TYPE
        SYNTAX       DisplayString (SIZE(0..32))
        MAX-ACCESS   read-write
        STATUS       current
        DESCRIPTION  "Description area 5."
        ::= { provMiscDescriptionEntry 7 }

    provMiscDescription6 OBJECT-TYPE
        SYNTAX       DisplayString (SIZE(0..32))
        MAX-ACCESS   read-write
        STATUS       current
        DESCRIPTION  "Description area 6."
        ::= { provMiscDescriptionEntry 8 }

    provMiscDescription7 OBJECT-TYPE
        SYNTAX       DisplayString (SIZE(0..32))
        MAX-ACCESS   read-write
        STATUS       current
        DESCRIPTION  "Description area 7."
        ::= { provMiscDescriptionEntry 9 }

    provMiscDescription8 OBJECT-TYPE
        SYNTAX       DisplayString (SIZE(0..32))
        MAX-ACCESS   read-write
        STATUS       current
        DESCRIPTION  "Description area 8."
        ::= { provMiscDescriptionEntry 10 }

    provMiscDescription9 OBJECT-TYPE
        SYNTAX       DisplayString (SIZE(0..32))
        MAX-ACCESS   read-write
        STATUS       current
        DESCRIPTION  "Description area 9."
        ::= { provMiscDescriptionEntry 11 }

-----------------------------------------------
-- maintenanceGroup Definitions
-----------------------------------------------

    maintCtrlGroup OBJECT IDENTIFIER
        ::= { maintenanceGroup 35 }

    maintCtrlGroupTable OBJECT-TYPE
        SYNTAX       SEQUENCE OF MaintCtrlGroupEntry
        MAX-ACCESS   not-accessible
        STATUS       current
        DESCRIPTION
            "Maintenance function for main card group on iPASO1000."
        ::= { maintCtrlGroup 1 }

    maintCtrlGroupEntry OBJECT-TYPE
        SYNTAX       MaintCtrlGroupEntry
        MAX-ACCESS   not-accessible
        STATUS       current
        DESCRIPTION  ""
        INDEX        { maintCtrlGroupIndex }
        ::= { maintCtrlGroupTable 1 }

    MaintCtrlGroupEntry ::= SEQUENCE {
        maintCtrlGroupIndex               Integer32,
        maintCtrlGroupNEAddress           IpAddress,
        maintCtrlGroupReset               INTEGER,
        maintCtrlGroupSwControl           INTEGER,
        maintCtrlGroupMain1Oos            INTEGER,
        maintCtrlGroupMain2Oos            INTEGER,
        maintCtrlGroupMain1ForcedOos      INTEGER,
        maintCtrlGroupMain2ForcedOos      INTEGER,
        maintCtrlGroupFirmwareCopy        INTEGER,
        maintCtrlGroupFirmwareCopyStatus  INTEGER
    }

    maintCtrlGroupIndex OBJECT-TYPE
        SYNTAX       Integer32 (1..1)
        MAX-ACCESS   not-accessible
        STATUS       current
        DESCRIPTION  "Index of this table."
        ::= { maintCtrlGroupEntry 1 }

    maintCtrlGroupNEAddress OBJECT-TYPE
        SYNTAX       IpAddress
        MAX-ACCESS   not-accessible
        STATUS       current
        DESCRIPTION  "reserved."
        ::= { maintCtrlGroupEntry 2 }

    maintCtrlGroupSwControl OBJECT-TYPE
        SYNTAX       INTEGER { invalid(0), switchOver(1) }
        MAX-ACCESS   read-write
        STATUS       current
        DESCRIPTION  "Switch Over"
        ::= { maintCtrlGroupEntry 4 }

    maintCtrlGroupMain1Oos OBJECT-TYPE
        SYNTAX       INTEGER { invalid(0), oos(1) }
        MAX-ACCESS   read-write
        STATUS       current
        DESCRIPTION  "Main1 Card Status Change"
        ::= { maintCtrlGroupEntry 5 }

    maintCtrlGroupMain2Oos OBJECT-TYPE
        SYNTAX       INTEGER { invalid(0), oos(1) }
        MAX-ACCESS   read-write
        STATUS       current
        DESCRIPTION  "Main2 Card Status Change"
        ::= { maintCtrlGroupEntry 6 }

    maintCtrlCardTable OBJECT-TYPE
        SYNTAX       SEQUENCE OF MaintCtrlCardEntry
        MAX-ACCESS   not-accessible
        STATUS       current
        DESCRIPTION  "Maintenance function for main card on iPASO1000."
        ::= { maintCtrlGroup 2 }

    maintCtrlCardEntry OBJECT-TYPE
        SYNTAX       MaintCtrlCardEntry
        MAX-ACCESS   not-accessible
        STATUS       current
        DESCRIPTION  ""
        INDEX        { maintCtrlCardIndex }
        ::= { maintCtrlCardTable 1 }

    MaintCtrlCardEntry ::= SEQUENCE {
        maintCtrlCardIndex           Integer32,
        maintCtrlCardNEAddress       IpAddress,
        maintCtrlCardReset           INTEGER,
        maintCtrlCardLANDeviceReset  INTEGER,
        maintCtrlSoftwareReset       INTEGER,
        maintCtrlCardHardwareReset   INTEGER
    }

    maintCtrlCardIndex OBJECT-TYPE
        SYNTAX       Integer32 (17..18)
        MAX-ACCESS   not-accessible
        STATUS       current
        DESCRIPTION  "Index of this table."
        ::= { maintCtrlCardEntry 1 }

    maintCtrlCardNEAddress OBJECT-TYPE
        SYNTAX       IpAddress
        MAX-ACCESS   not-accessible
        STATUS       current
        DESCRIPTION  "reserved."
        ::= { maintCtrlCardEntry 2 }

    maintCtrlCardReset OBJECT-TYPE
        SYNTAX       INTEGER { invalid(0), reset(1) }
        MAX-ACCESS   read-write
        STATUS       current
        DESCRIPTION  "H/W Reset"
        ::= { maintCtrlCardEntry 3 }

    maintCtrlSoftwareReset OBJECT-TYPE
        SYNTAX       INTEGER {
                         invalid(0),
                         resetNormal(1),
                         resetRevert(2),
                         resetNone(3)
                     }
        MAX-ACCESS   read-write
        STATUS       current
        DESCRIPTION  "F/W Reset"
        ::= { maintCtrlCardEntry 5 }

    maintCtrlCardHardwareReset OBJECT-TYPE
        SYNTAX       INTEGER { invalid(0), reset(1) }
        MAX-ACCESS   read-write
        STATUS       current
        DESCRIPTION  "H/W Reset"
        ::= { maintCtrlCardEntry 6 }

-----------------------------------------------
-- End User MIB Object Definitions
-----------------------------------------------

END
