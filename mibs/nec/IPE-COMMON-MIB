--
-- ASN.1 MIB Definitions
-- Output Date: Tue Jul 12 15:00:04 2016
--

IPE-COMMON-MIB DEFINITIONS ::= BEGIN

-----------------------------------------------
-- IMPORTS Definitions
-----------------------------------------------

    IMPORTS
        BridgeId
            FROM BRIDGE-MIB
        InterfaceIndex, InterfaceIndexOrZero
            FROM IF-MIB
        Counter32, Counter64, enterprises, Gauge32, Integer32, IpAddress,
        NOTIFICATION-TYPE, OBJECT-TYPE, Opaque, Unsigned32
            FROM SNMPv2-SMI
        DateAndTime, DisplayString, MacAddress, RowStatus,
        TEXTUAL-CONVENTION, TruthValue
            FROM SNMPv2-TC;

-----------------------------------------------
-- Textual Convention Definitions
-----------------------------------------------

    AlarmTypeValue ::= TEXTUAL-CONVENTION
        STATUS       current
        DESCRIPTION  "Alarm Type (CCITT Rec. X.733)"
        SYNTAX       INTEGER {
                         invalid(0),
                         communicationsAlarm(1),
                         qualityOfServiceAlarm(2),
                         processingErrorAlarm(3),
                         equipmentAlarm(4),
                         environmentalAlarm(5),
                         integrityViolationAlarm(6),
                         operationalViolationAlarm(7),
                         physicalViolationAlarm(8),
                         securityViolationAlarm(9),
                         timeDomainViolationAlarm(10)
                     }

    EnableDisableValue ::= TEXTUAL-CONVENTION
        STATUS       current
        DESCRIPTION  "Enable/Disable Type"
        SYNTAX       INTEGER { invalid(0), disable(1), enable(2) }

    IpeMepId ::= TEXTUAL-CONVENTION
        DISPLAY-HINT "d"
        STATUS       current
        DESCRIPTION
            "Administrative MEP ID value.
            This value is not same as MEP ID in protocol sense."
        SYNTAX       Integer32 (1..128)

    IpeStatsInfo ::= TEXTUAL-CONVENTION
        STATUS       current
        DESCRIPTION
            "PMON/RMON monitoring status.
            'invalid' means the corresponding monitoring value is not
            reliable because of the alarm or other reasons. 'maintenance'
            means that some maintenance functions are executed on the current
            interval."
        SYNTAX       INTEGER {
                         invalid(0),
                         validNoMaint(1),
                         validMaint(2),
                         invalidNoMaint(3),
                         invalidMaint(4)
                     }

    IpeVlanIndex ::= TEXTUAL-CONVENTION
        DISPLAY-HINT "d"
        STATUS       current
        DESCRIPTION
            "VLAN ID.
            Value '4095' is reserved, and cannot set to the system."
        SYNTAX       Integer32 (1..4094)

    IpeVlanIndexOrZero ::= TEXTUAL-CONVENTION
        DISPLAY-HINT "d"
        STATUS       current
        DESCRIPTION
            "VLAN ID.
            Value '4095' is reserved, and cannot set to the system.
            Value '0' is special value, and the definition depends on the
            object which uses this TEXTUAL-CONVENTION."
        SYNTAX       Integer32 (0..4094)

    IpeVlanListOrZero ::= TEXTUAL-CONVENTION
        STATUS       current
        DESCRIPTION
            "VLAN List.
            Each octet represents a set of eight VIDs. The first octet
            specifying VID 1 through 8, the second octet specifying VID 9
            through 16, etc.
            If that bit has a value of '1' then that VID is included in the
            set of VIDs; the VID is not included if its bit has a value of
            '0'."
        SYNTAX       OCTET STRING (SIZE(0..0|512..512))

    OffOnValue ::= TEXTUAL-CONVENTION
        STATUS       current
        DESCRIPTION  "Off/On Type"
        SYNTAX       INTEGER { invalid(0), off(1), on(2) }

    ProbableCauseValue ::= TEXTUAL-CONVENTION
        STATUS       current
        DESCRIPTION  "Probable Cause (CCITT Rec. X.733)"
        SYNTAX       INTEGER {
                         invalid(0),
                         aIS(1),
                         callSetUpFailure(2),
                         degradedSignal(3),
                         farEndReceiverFailure(4),
                         framingError(5),
                         lossOfFrame(6),
                         lossOfPointer(7),
                         lossOfSignal(8),
                         payloadTypeMismatch(9),
                         transmissionError(10),
                         remoteAlarmInterface(11),
                         excessiveBER(12),
                         pathTraceMismatch(13),
                         unavailable(14),
                         signalLabelMismatch(15),
                         lossOfMultiFrame(16),
                         receiveFailure(17),
                         transmitFailure(18),
                         modulationFailure(19),
                         demodulationFailure(20),
                         broadcastChannelFailure(21),
                         connectionEstablishmentError(22),
                         invalidMessageReceived(23),
                         localNodeTransmissionError(24),
                         remoteNodeTransmissionError(25),
                         routingFailure(26),
                         backplaneFailure(51),
                         dataSetProblem(52),
                         equipmentIdentifierDuplication(53),
                         externalIFDeviceProblem(54),
                         lineCardProblem(55),
                         multiplexerProblem(56),
                         nEIdentifierDuplication(57),
                         powerProblem(58),
                         processorProblem(59),
                         protectionPathFailure(60),
                         receiverFailure(61),
                         replaceableUnitMissing(62),
                         replaceableUnitTypeMismatch(63),
                         synchronizationSourceMismatch(64),
                         terminalProblem(65),
                         timingProblem(66),
                         transmitterFailure(67),
                         trunkCardProblem(68),
                         replaceableUnitProblem(69),
                         realTimeClockFailure(70),
                         antennaFailure(71),
                         batteryChargingFailure(72),
                         diskFailure(73),
                         frequencyHoppingFailure(74),
                         iODeviceError(75),
                         lossOfSynchronisation(76),
                         lossOfRedundancy(77),
                         powerSupplyFailure(78),
                         signalQualityEvaluationFailure(79),
                         tranceiverFailure(80),
                         protectionMechanismFailure(81),
                         protectingResourceFailure(82),
                         airCompressorFailure(101),
                         airConditioningFailure(102),
                         airDryerFailure(103),
                         batteryDischarging(104),
                         batteryFailure(105),
                         commercialPowerFailure(106),
                         coolingFanFailure(107),
                         engineFailure(108),
                         fireDetectorFailure(109),
                         fuseFailure(110),
                         generatorFailure(111),
                         lowBatteryThreshold(112),
                         pumpFailure(113),
                         rectifierFailure(114),
                         rectifierHighVoltage(115),
                         rectifierLowFVoltage(116),
                         ventilationsSystemFailure(117),
                         enclosureDoorOpen(118),
                         explosiveGas(119),
                         fire(120),
                         flood(121),
                         highHumidity(122),
                         highTemperature(123),
                         highWind(124),
                         iceBuildUp(125),
                         intrusionDetection(126),
                         lowFuel(127),
                         lowHumidity(128),
                         lowCablePressure(129),
                         lowTemperatue(130),
                         lowWater(131),
                         smoke(132),
                         toxicGas(133),
                         coolingSystemFailure(134),
                         externalEquipmentFailure(135),
                         externalPointFailure(136),
                         storageCapacityProblem(151),
                         memoryMismatch(152),
                         corruptData(153),
                         outOfCPUCycles(154),
                         sfwrEnvironmentProblem(155),
                         sfwrDownloadFailure(156),
                         lossOfRealTimel(157),
                         applicationSubsystemFailure(158),
                         configurationOrCustomisationError(159),
                         databaseInconsistency(160),
                         fileError(161),
                         outOfMemory(162),
                         softwareError(163),
                         timeoutExpired(164),
                         underlayingResourceUnavailable(165),
                         versionMismatch(166),
                         bandwidthReduced(201),
                         congestion(202),
                         excessiveErrorRate(203),
                         excessiveResponseTime(204),
                         excessiveRetransmissionRate(205),
                         reducedLoggingCapability(206),
                         systemResourcesOverload(207),
                         adapterError(500),
                         applicationSubsystemFailture(501),
                         bandwidthReducedX733(502),
                         callEstablishmentError(503),
                         communicationsProtocolError(504),
                         communicationsSubsystemFailure(505),
                         configurationOrCustomizationError(506),
                         congestionX733(507),
                         coruptData(508),
                         cpuCyclesLimitExceeded(509),
                         dataSetOrModemError(510),
                         degradedSignalX733(511),
                         dteDceInterfaceError(512),
                         enclosureDoorOpenX733(513),
                         equipmentMalfunction(514),
                         excessiveVibration(515),
                         fileErrorX733(516),
                         fireDetected(517),
                         framingErrorX733(518),
                         heatingVentCoolingSystemProblem(519),
                         humidityUnacceptable(520),
                         inputOutputDeviceError(521),
                         inputDeviceError(522),
                         lanError(523),
                         leakDetected(524),
                         localNodeTransmissionErrorX733(525),
                         lossOfFrameX733(526),
                         lossOfSignalX733(527),
                         materialSupplyExhausted(528),
                         multiplexerProblemX733(529),
                         outOfMemoryX733(530),
                         ouputDeviceError(531),
                         performanceDegraded(532),
                         powerProblems(533),
                         pressureUnacceptable(534),
                         processorProblems(535),
                         pumpFailureX733(536),
                         queueSizeExceeded(537),
                         receiveFailureX733(538),
                         receiverFailureX733(539),
                         remoteNodeTransmissionErrorX733(540),
                         resourceAtOrNearingCapacity(541),
                         responseTimeExecessive(542),
                         retransmissionRateExcessive(543),
                         softwareErrorX733(544),
                         softwareProgramAbnormallyTerminated(545),
                         softwareProgramError(546),
                         storageCapacityProblemX733(547),
                         temperatureUnacceptable(548),
                         thresholdCrossed(549),
                         timingProblemX733(550),
                         toxicLeakDetected(551),
                         transmitFailureX733(552),
                         transmiterFailure(553),
                         underlyingResourceUnavailable(554),
                         versionMismatchX733(555),
                         authenticationFailure(600),
                         breachOfConfidentiality(601),
                         cableTamper(602),
                         delayedInformation(603),
                         denialOfService(604),
                         duplicateInformation(605),
                         informationMissing(606),
                         informationModificationDetected(607),
                         informationOutOfSequence(608),
                         keyExpired(609),
                         nonRepudiationFailure(610),
                         outOfHoursActivity(611),
                         outOfService(612),
                         proceduralError(613),
                         unauthorizedAccessAttempt(614),
                         unexpectedInformation(615),
                         other(1024)
                     }

    ReportNotreportValue ::= TEXTUAL-CONVENTION
        STATUS       current
        DESCRIPTION  "Enable/Disable Type"
        SYNTAX       INTEGER { invalid(0), notReport(1), report(2) }

    SeverityValue ::= TEXTUAL-CONVENTION
        STATUS       current
        DESCRIPTION  "Severity (CCITT Rec. X.733)"
        SYNTAX       INTEGER {
                         cleared(1),
                         indetermine(2),
                         critical(3),
                         major(4),
                         minor(5),
                         warning(6)
                     }

    UsedNotusedValue ::= TEXTUAL-CONVENTION
        STATUS       current
        DESCRIPTION  "Used/NotUsed Type"
        SYNTAX       INTEGER { invalid(0), notUsed(1), used(2) }

    ValidInvalidValue ::= TEXTUAL-CONVENTION
        STATUS       current
        DESCRIPTION  "Valid/Invalid Type"
        SYNTAX       INTEGER { invalid(0), valid(1) }

-----------------------------------------------
-- Begin User MIB Object Definitions
-----------------------------------------------

    nec OBJECT IDENTIFIER
        ::= { enterprises 119 }

    nec-mib OBJECT IDENTIFIER
        ::= { nec 2 }

    necProductDepend OBJECT IDENTIFIER
        ::= { nec-mib 3 }

    radioEquipment OBJECT IDENTIFIER
        ::= { necProductDepend 69 }

    pasoNeoIpe-common OBJECT IDENTIFIER
        ::= { radioEquipment 501 }

-----------------------------------------------
-- IPE COMMON Group Definitions
-----------------------------------------------

    summaryGroup OBJECT IDENTIFIER
        ::= { pasoNeoIpe-common 1 }

    trapGroup OBJECT IDENTIFIER
        ::= { pasoNeoIpe-common 2 }

    alarmStatusGroup OBJECT IDENTIFIER
        ::= { pasoNeoIpe-common 3 }

    equipmentSetUpGroup OBJECT IDENTIFIER
        ::= { pasoNeoIpe-common 4 }

    provisioningGroup OBJECT IDENTIFIER
        ::= { pasoNeoIpe-common 5 }

    maintenanceGroup OBJECT IDENTIFIER
        ::= { pasoNeoIpe-common 6 }

    inventoryGroup OBJECT IDENTIFIER
        ::= { pasoNeoIpe-common 7 }

    meteringGroup OBJECT IDENTIFIER
        ::= { pasoNeoIpe-common 8 }

    pmonGroup OBJECT IDENTIFIER
        ::= { pasoNeoIpe-common 9 }

    pmonTxRxLevGroup OBJECT IDENTIFIER
        ::= { pasoNeoIpe-common 10 }

    rmonGroup OBJECT IDENTIFIER
        ::= { pasoNeoIpe-common 11 }

-----------------------------------------------
-- summaryGroup Definitions
-----------------------------------------------

    alarmSummaryGroup OBJECT IDENTIFIER
        ::= { summaryGroup 1 }

    alarmSummaryCommonInfoTable OBJECT-TYPE
        SYNTAX       SEQUENCE OF AlarmSummaryCommonInfoEntry
        MAX-ACCESS   not-accessible
        STATUS       current
        DESCRIPTION
            "Alarm Summary Table.
            Alarm Summary objects represents the maximum severity value of
            raised alarms of the entity."
        ::= { alarmSummaryGroup 1 }

    alarmSummaryCommonInfoEntry OBJECT-TYPE
        SYNTAX       AlarmSummaryCommonInfoEntry
        MAX-ACCESS   not-accessible
        STATUS       current
        DESCRIPTION  ""
        INDEX        { alarmSummaryCommonInfoIndex }
        ::= { alarmSummaryCommonInfoTable 1 }

    AlarmSummaryCommonInfoEntry ::= SEQUENCE {
        alarmSummaryCommonInfoIndex      Integer32,
        alarmSummaryCommonInfoNEAddress  IpAddress,
        alarmTotalSummary                SeverityValue,
        alarmIduSummary                  SeverityValue,
        alarmCtrlSummary                 SeverityValue,
        alarmOduSummary                  SeverityValue,
        alarmAuxInputSummary             SeverityValue,
        alarmPmonTcnSummary              SeverityValue,
        alarmRmonTcnSummary              SeverityValue,
        alarmRmonTcnCtrlSummary          SeverityValue
    }

    alarmSummaryCommonInfoIndex OBJECT-TYPE
        SYNTAX       Integer32 (1..1)
        MAX-ACCESS   not-accessible
        STATUS       current
        DESCRIPTION  "Index of this table."
        ::= { alarmSummaryCommonInfoEntry 1 }

    alarmSummaryCommonInfoNEAddress OBJECT-TYPE
        SYNTAX       IpAddress
        MAX-ACCESS   not-accessible
        STATUS       current
        DESCRIPTION  "reserved."
        ::= { alarmSummaryCommonInfoEntry 2 }

    alarmTotalSummary OBJECT-TYPE
        SYNTAX       SeverityValue
        MAX-ACCESS   read-only
        STATUS       current
        DESCRIPTION  "Total Summary Alarm."
        ::= { alarmSummaryCommonInfoEntry 3 }

    alarmIduSummary OBJECT-TYPE
        SYNTAX       SeverityValue
        MAX-ACCESS   read-only
        STATUS       current
        DESCRIPTION  "IDU Summary Alarm."
        ::= { alarmSummaryCommonInfoEntry 4 }

    alarmCtrlSummary OBJECT-TYPE
        SYNTAX       SeverityValue
        MAX-ACCESS   read-only
        STATUS       current
        DESCRIPTION
            "Main Board / Ctrl Card Summary Alarm (including Equipment clock
            alarms)"
        ::= { alarmSummaryCommonInfoEntry 5 }

    alarmOduSummary OBJECT-TYPE
        SYNTAX       SeverityValue
        MAX-ACCESS   read-only
        STATUS       current
        DESCRIPTION  "ODU Summary Alarm."
        ::= { alarmSummaryCommonInfoEntry 6 }

    alarmAuxInputSummary OBJECT-TYPE
        SYNTAX       SeverityValue
        MAX-ACCESS   read-only
        STATUS       current
        DESCRIPTION  "AUX Input Summary Alarm."
        ::= { alarmSummaryCommonInfoEntry 7 }

    alarmPmonTcnSummary OBJECT-TYPE
        SYNTAX       SeverityValue
        MAX-ACCESS   read-only
        STATUS       current
        DESCRIPTION  "PMON TCN Summary Alarm."
        ::= { alarmSummaryCommonInfoEntry 8 }

    alarmRmonTcnSummary OBJECT-TYPE
        SYNTAX       SeverityValue
        MAX-ACCESS   read-only
        STATUS       current
        DESCRIPTION  "RMON TCN Summary Alarm."
        ::= { alarmSummaryCommonInfoEntry 9 }

    alarmRmonTcnCtrlSummary OBJECT-TYPE
        SYNTAX       SeverityValue
        MAX-ACCESS   read-only
        STATUS       current
        DESCRIPTION  "RMON TCN Main Board / Ctrl Card Summary Alarm."
        ::= { alarmSummaryCommonInfoEntry 10 }

    alarmSummaryIduGroup OBJECT IDENTIFIER
        ::= { alarmSummaryGroup 2 }

    alarmSummaryIduSlotInfoTable OBJECT-TYPE
        SYNTAX       SEQUENCE OF AlarmSummaryIduSlotInfoEntry
        MAX-ACCESS   not-accessible
        STATUS       current
        DESCRIPTION  "Alarm Summary per IDU Slot."
        ::= { alarmSummaryIduGroup 1 }

    alarmSummaryIduSlotInfoEntry OBJECT-TYPE
        SYNTAX       AlarmSummaryIduSlotInfoEntry
        MAX-ACCESS   not-accessible
        STATUS       current
        DESCRIPTION  ""
        INDEX        { alarmSummaryIduSlotInfoIndex }
        ::= { alarmSummaryIduSlotInfoTable 1 }

    AlarmSummaryIduSlotInfoEntry ::= SEQUENCE {
        alarmSummaryIduSlotInfoIndex      Integer32,
        alarmSummaryIduSlotInfoNEAddress  IpAddress,
        alarmIduSlotSummary               SeverityValue
    }

    alarmSummaryIduSlotInfoIndex OBJECT-TYPE
        SYNTAX       Integer32
        MAX-ACCESS   not-accessible
        STATUS       current
        DESCRIPTION  "Index of this table."
        ::= { alarmSummaryIduSlotInfoEntry 1 }

    alarmSummaryIduSlotInfoNEAddress OBJECT-TYPE
        SYNTAX       IpAddress
        MAX-ACCESS   not-accessible
        STATUS       current
        DESCRIPTION  "reserved."
        ::= { alarmSummaryIduSlotInfoEntry 2 }

    alarmIduSlotSummary OBJECT-TYPE
        SYNTAX       SeverityValue
        MAX-ACCESS   read-only
        STATUS       current
        DESCRIPTION
            "IDU Slot Summary Alarm. the maximum severity value of raised
            alarms per slot."
        ::= { alarmSummaryIduSlotInfoEntry 3 }

    alarmSummaryIduSwGrpInfoTable OBJECT-TYPE
        SYNTAX       SEQUENCE OF AlarmSummaryIduSwGrpInfoEntry
        MAX-ACCESS   not-accessible
        STATUS       current
        DESCRIPTION  "Alarm Summary per MODEM Switch group."
        ::= { alarmSummaryIduGroup 2 }

    alarmSummaryIduSwGrpInfoEntry OBJECT-TYPE
        SYNTAX       AlarmSummaryIduSwGrpInfoEntry
        MAX-ACCESS   not-accessible
        STATUS       current
        DESCRIPTION  ""
        INDEX        { alarmSummaryIduSwGrpInfoIndex }
        ::= { alarmSummaryIduSwGrpInfoTable 1 }

    AlarmSummaryIduSwGrpInfoEntry ::= SEQUENCE {
        alarmSummaryIduSwGrpInfoIndex      Integer32,
        alarmSummaryIduSwGrpInfoNEAddress  IpAddress,
        alarmIduSwGrpSummary               SeverityValue
    }

    alarmSummaryIduSwGrpInfoIndex OBJECT-TYPE
        SYNTAX       Integer32
        MAX-ACCESS   not-accessible
        STATUS       current
        DESCRIPTION  "Index of this table."
        ::= { alarmSummaryIduSwGrpInfoEntry 1 }

    alarmSummaryIduSwGrpInfoNEAddress OBJECT-TYPE
        SYNTAX       IpAddress
        MAX-ACCESS   not-accessible
        STATUS       current
        DESCRIPTION  "reserved."
        ::= { alarmSummaryIduSwGrpInfoEntry 2 }

    alarmIduSwGrpSummary OBJECT-TYPE
        SYNTAX       SeverityValue
        MAX-ACCESS   read-only
        STATUS       current
        DESCRIPTION
            "IDU SW Group Summary Alarm. the maximum severity value of raised
            alarms per MODEM Switch group."
        ::= { alarmSummaryIduSwGrpInfoEntry 3 }

    alarmSummaryOduInfoTable OBJECT-TYPE
        SYNTAX       SEQUENCE OF AlarmSummaryOduInfoEntry
        MAX-ACCESS   not-accessible
        STATUS       current
        DESCRIPTION  "Alarm Summary per ODU."
        ::= { alarmSummaryGroup 3 }

    alarmSummaryOduInfoEntry OBJECT-TYPE
        SYNTAX       AlarmSummaryOduInfoEntry
        MAX-ACCESS   not-accessible
        STATUS       current
        DESCRIPTION  ""
        INDEX        { alarmSummaryOduInfoIndex }
        ::= { alarmSummaryOduInfoTable 1 }

    AlarmSummaryOduInfoEntry ::= SEQUENCE {
        alarmSummaryOduInfoIndex      Integer32,
        alarmSummaryOduInfoNEAddress  IpAddress,
        alarmOduEachSummary           SeverityValue
    }

    alarmSummaryOduInfoIndex OBJECT-TYPE
        SYNTAX       Integer32
        MAX-ACCESS   not-accessible
        STATUS       current
        DESCRIPTION  "Index of this table."
        ::= { alarmSummaryOduInfoEntry 1 }

    alarmSummaryOduInfoNEAddress OBJECT-TYPE
        SYNTAX       IpAddress
        MAX-ACCESS   not-accessible
        STATUS       current
        DESCRIPTION  "reserved."
        ::= { alarmSummaryOduInfoEntry 2 }

    alarmOduEachSummary OBJECT-TYPE
        SYNTAX       SeverityValue
        MAX-ACCESS   read-only
        STATUS       current
        DESCRIPTION
            "ODU Each Summary Alarm. the maximum severity value of raised
            alarms per ODU."
        ::= { alarmSummaryOduInfoEntry 3 }

    alarmSummaryPmonTcnInfoTable OBJECT-TYPE
        SYNTAX       SEQUENCE OF AlarmSummaryPmonTcnInfoEntry
        MAX-ACCESS   not-accessible
        STATUS       current
        DESCRIPTION  "Alarm Summay of Threshold Crossing Alarms per Slot."
        ::= { alarmSummaryGroup 4 }

    alarmSummaryPmonTcnInfoEntry OBJECT-TYPE
        SYNTAX       AlarmSummaryPmonTcnInfoEntry
        MAX-ACCESS   not-accessible
        STATUS       current
        DESCRIPTION  ""
        INDEX        { alarmSummaryPmonTcnInfoIndex }
        ::= { alarmSummaryPmonTcnInfoTable 1 }

    AlarmSummaryPmonTcnInfoEntry ::= SEQUENCE {
        alarmSummaryPmonTcnInfoIndex      Integer32,
        alarmSummaryPmonTcnInfoNEAddress  IpAddress,
        alarmPmonTcnSlotSummary           SeverityValue
    }

    alarmSummaryPmonTcnInfoIndex OBJECT-TYPE
        SYNTAX       Integer32
        MAX-ACCESS   not-accessible
        STATUS       current
        DESCRIPTION  "Index of this table."
        ::= { alarmSummaryPmonTcnInfoEntry 1 }

    alarmSummaryPmonTcnInfoNEAddress OBJECT-TYPE
        SYNTAX       IpAddress
        MAX-ACCESS   not-accessible
        STATUS       current
        DESCRIPTION  "reserved."
        ::= { alarmSummaryPmonTcnInfoEntry 2 }

    alarmPmonTcnSlotSummary OBJECT-TYPE
        SYNTAX       SeverityValue
        MAX-ACCESS   read-only
        STATUS       current
        DESCRIPTION
            "PMON (TCN) Slot Summary Alarm. the maximum severity value of
            raised Threshold Crossing Alarms per slot."
        ::= { alarmSummaryPmonTcnInfoEntry 3 }

    alarmSummaryCtrlInfoTable OBJECT-TYPE
        SYNTAX       SEQUENCE OF AlarmSummaryCtrlInfoEntry
        MAX-ACCESS   not-accessible
        STATUS       current
        DESCRIPTION  "Alarm Summary of Main Board or Ctrl Card."
        ::= { alarmSummaryGroup 5 }

    alarmSummaryCtrlInfoEntry OBJECT-TYPE
        SYNTAX       AlarmSummaryCtrlInfoEntry
        MAX-ACCESS   not-accessible
        STATUS       current
        DESCRIPTION  ""
        INDEX        { alarmSummaryEoamInfoIndex }
        ::= { alarmSummaryCtrlInfoTable 1 }

    AlarmSummaryCtrlInfoEntry ::= SEQUENCE {
        alarmSummaryEoamInfoIndex      Integer32,
        alarmSummaryEoamInfoNEAddress  IpAddress,
        alarmEoamSummary               SeverityValue,
        alarmRmonEoamSummary           SeverityValue
    }

    alarmSummaryEoamInfoIndex OBJECT-TYPE
        SYNTAX       Integer32 (1..1)
        MAX-ACCESS   not-accessible
        STATUS       current
        DESCRIPTION  "Index of this table."
        ::= { alarmSummaryCtrlInfoEntry 1 }

    alarmSummaryEoamInfoNEAddress OBJECT-TYPE
        SYNTAX       IpAddress
        MAX-ACCESS   not-accessible
        STATUS       current
        DESCRIPTION  "reserved."
        ::= { alarmSummaryCtrlInfoEntry 2 }

    alarmEoamSummary OBJECT-TYPE
        SYNTAX       SeverityValue
        MAX-ACCESS   read-only
        STATUS       current
        DESCRIPTION
            "ETH-OAM including MPLS-TP OAM Summary Alarm. The maximum
            severity value of raised alarms which are related to EtherOAM
            functions."
        ::= { alarmSummaryCtrlInfoEntry 3 }

    alarmRmonEoamSummary OBJECT-TYPE
        SYNTAX       SeverityValue
        MAX-ACCESS   read-only
        STATUS       current
        DESCRIPTION
            "RMON ETH-OAM including MPLS-TP OAM Summary Alarm. The maximum
            severity value of raised alarms which are related to EtherOAM
            Threshold Crossing Alarms."
        ::= { alarmSummaryCtrlInfoEntry 4 }

    alarmSummaryRmonTcnInfoTable OBJECT-TYPE
        SYNTAX       SEQUENCE OF AlarmSummaryRmonTcnInfoEntry
        MAX-ACCESS   not-accessible
        STATUS       current
        DESCRIPTION
            "Alarm summary of RMON Threshold Crossing Alarms per slot."
        ::= { alarmSummaryGroup 6 }

    alarmSummaryRmonTcnInfoEntry OBJECT-TYPE
        SYNTAX       AlarmSummaryRmonTcnInfoEntry
        MAX-ACCESS   not-accessible
        STATUS       current
        DESCRIPTION  ""
        INDEX        { alarmSummaryRmonTcnInfoIndex }
        ::= { alarmSummaryRmonTcnInfoTable 1 }

    AlarmSummaryRmonTcnInfoEntry ::= SEQUENCE {
        alarmSummaryRmonTcnInfoIndex      Integer32,
        alarmSummaryRmonTcnInfoNEAddress  IpAddress,
        alarmRmonTcnSlotSummary           SeverityValue
    }

    alarmSummaryRmonTcnInfoIndex OBJECT-TYPE
        SYNTAX       Integer32
        MAX-ACCESS   not-accessible
        STATUS       current
        DESCRIPTION  "Index of this table."
        ::= { alarmSummaryRmonTcnInfoEntry 1 }

    alarmSummaryRmonTcnInfoNEAddress OBJECT-TYPE
        SYNTAX       IpAddress
        MAX-ACCESS   not-accessible
        STATUS       current
        DESCRIPTION  "reserved."
        ::= { alarmSummaryRmonTcnInfoEntry 2 }

    alarmRmonTcnSlotSummary OBJECT-TYPE
        SYNTAX       SeverityValue
        MAX-ACCESS   read-only
        STATUS       current
        DESCRIPTION
            "RMON (TCN) Slot Summary Alarm. The maximum value of raised
            alarms which are related RMON Threshold Crossing Alarm."
        ::= { alarmSummaryRmonTcnInfoEntry 3 }

    maintSummaryGroup OBJECT IDENTIFIER
        ::= { summaryGroup 2 }

    maintSummaryCommonInfoTable OBJECT-TYPE
        SYNTAX       SEQUENCE OF MaintSummaryCommonInfoEntry
        MAX-ACCESS   not-accessible
        STATUS       current
        DESCRIPTION
            "This table represents the status of maintenance functions."
        ::= { maintSummaryGroup 1 }

    maintSummaryCommonInfoEntry OBJECT-TYPE
        SYNTAX       MaintSummaryCommonInfoEntry
        MAX-ACCESS   not-accessible
        STATUS       current
        DESCRIPTION  ""
        INDEX        { maintSummaryCommonInfoIndex }
        ::= { maintSummaryCommonInfoTable 1 }

    MaintSummaryCommonInfoEntry ::= SEQUENCE {
        maintSummaryCommonInfoIndex      Integer32,
        maintSummaryCommonInfoNEAddress  IpAddress,
        maintTotalSummary                OffOnValue
    }

    maintSummaryCommonInfoIndex OBJECT-TYPE
        SYNTAX       Integer32 (1..1)
        MAX-ACCESS   not-accessible
        STATUS       current
        DESCRIPTION  "Index of this table."
        ::= { maintSummaryCommonInfoEntry 1 }

    maintSummaryCommonInfoNEAddress OBJECT-TYPE
        SYNTAX       IpAddress
        MAX-ACCESS   not-accessible
        STATUS       current
        DESCRIPTION  "reserved."
        ::= { maintSummaryCommonInfoEntry 2 }

    maintTotalSummary OBJECT-TYPE
        SYNTAX       OffOnValue
        MAX-ACCESS   read-only
        STATUS       current
        DESCRIPTION
            "Maintenance Total Summary. Represents the status of maintenance
            functions.
            'on' means some maintenance functions are performed on this
            equipment."
        ::= { maintSummaryCommonInfoEntry 3 }

-----------------------------------------------
-- trapGroup Definitions
-----------------------------------------------

    ipeTrapCommon OBJECT IDENTIFIER
        ::= { trapGroup 1 }

    ipeTrapCommonVars OBJECT IDENTIFIER
        ::= { ipeTrapCommon 1 }

    eventTotalCount OBJECT-TYPE
        SYNTAX       Counter32
        MAX-ACCESS   read-only
        STATUS       current
        DESCRIPTION
            "The total count of SNMP TRAP/INFORM messages since this
            equipment was booted"
        ::= { ipeTrapCommonVars 1 }

    eventCount OBJECT-TYPE
        SYNTAX       Counter32
        MAX-ACCESS   read-only
        STATUS       current
        DESCRIPTION
            "The count of SNMP TRAP/INFORM messages per event type
            (alarm/status/control) since this equipment was booted."
        ::= { ipeTrapCommonVars 2 }

    eventTime OBJECT-TYPE
        SYNTAX       DateAndTime
        MAX-ACCESS   read-only
        STATUS       current
        DESCRIPTION
            "The local date and time when the TRAP/INFORM event occurred."
        ::= { ipeTrapCommonVars 3 }

    eventType OBJECT-TYPE
        SYNTAX       INTEGER {
                         alarmStateChage(1),
                         statusChange(2),
                         controlEvent(3)
                     }
        MAX-ACCESS   read-only
        STATUS       current
        DESCRIPTION  "The event type of TRAP/INFORM message."
        ::= { ipeTrapCommonVars 4 }

    eventResourceID OBJECT-TYPE
        SYNTAX       OBJECT IDENTIFIER
        MAX-ACCESS   read-only
        STATUS       current
        DESCRIPTION
            "The OBJECT IDENTIFIER of the object which raised the event."
        ::= { ipeTrapCommonVars 5 }

    ipeTrapCommonAdditionalVars OBJECT IDENTIFIER
        ::= { ipeTrapCommon 2 }

    eventAdditionalText1 OBJECT-TYPE
        SYNTAX       DisplayString
        MAX-ACCESS   read-only
        STATUS       current
        DESCRIPTION  "Additional Information about the TRAP/INFORM event."
        ::= { ipeTrapCommonAdditionalVars 1 }

    eventAdditionalText2 OBJECT-TYPE
        SYNTAX       DisplayString
        MAX-ACCESS   read-only
        STATUS       current
        DESCRIPTION  "Additional Information about the TRAP/INFORM event."
        ::= { ipeTrapCommonAdditionalVars 2 }

    eventAdditionalText3 OBJECT-TYPE
        SYNTAX       DisplayString
        MAX-ACCESS   read-only
        STATUS       current
        DESCRIPTION  "Additional Information about the TRAP/INFORM event."
        ::= { ipeTrapCommonAdditionalVars 3 }

    eventAdditionalText4 OBJECT-TYPE
        SYNTAX       DisplayString
        MAX-ACCESS   read-only
        STATUS       current
        DESCRIPTION  "Additional Information about the TRAP/INFORM event."
        ::= { ipeTrapCommonAdditionalVars 4 }

    eventAdditionalText5 OBJECT-TYPE
        SYNTAX       DisplayString
        MAX-ACCESS   read-only
        STATUS       current
        DESCRIPTION  "Additional Information about the TRAP/INFORM event."
        ::= { ipeTrapCommonAdditionalVars 5 }

    ipeTrapAlarmVars OBJECT IDENTIFIER
        ::= { ipeTrapCommon 3 }

    eventSeverity OBJECT-TYPE
        SYNTAX       SeverityValue
        MAX-ACCESS   read-only
        STATUS       current
        DESCRIPTION  "Severity value of notified alarm event."
        ::= { ipeTrapAlarmVars 1 }

    eventAlarmType OBJECT-TYPE
        SYNTAX       AlarmTypeValue
        MAX-ACCESS   read-only
        STATUS       current
        DESCRIPTION
            "Represents the X.733 based event type value for the alarms."
        ::= { ipeTrapAlarmVars 2 }

    eventProbableCause OBJECT-TYPE
        SYNTAX       ProbableCauseValue
        MAX-ACCESS   read-only
        STATUS       current
        DESCRIPTION
            "Represents the X.733 based probable cause value for the alarms."
        ::= { ipeTrapAlarmVars 3 }

    ipeTrapStatusValueVars OBJECT IDENTIFIER
        ::= { ipeTrapCommon 4 }

    eventStatusValue OBJECT-TYPE
        SYNTAX       Integer32
        MAX-ACCESS   read-only
        STATUS       current
        DESCRIPTION
            "the changed value of status object whose syntax is integer.
            Event object is represented by 'eventResourceID'"
        ::= { ipeTrapStatusValueVars 1 }

    eventStatusValueDspStr OBJECT-TYPE
        SYNTAX       DisplayString
        MAX-ACCESS   read-only
        STATUS       current
        DESCRIPTION
            "the changed value of status object whose syntax is DISPLAY
            STRING. Event object is represented by 'eventResourceID'"
        ::= { ipeTrapStatusValueVars 2 }

    eventStatusValueOctStr OBJECT-TYPE
        SYNTAX       OCTET STRING (SIZE(0..512|32..32))
        MAX-ACCESS   read-only
        STATUS       current
        DESCRIPTION
            "the changed value of status object whose syntax is OCTET STRING.
            Event object is represented by 'eventResourceID'

            SYNTAX:  OCTET STRING (SIZE(32..32))
            [iPASOLINK200/400/1000series/EX/iX],
                     OCTET STRING (SIZE(0..512)) [iPASOLINK VR series]"
        ::= { ipeTrapStatusValueVars 3 }

    eventStatusValueUnsigned32 OBJECT-TYPE
        SYNTAX       Unsigned32
        MAX-ACCESS   read-only
        STATUS       current
        DESCRIPTION
            "the changed value of status object whose syntax is unsigned32.
            Event object is represented by 'eventResourceID'"
        ::= { ipeTrapStatusValueVars 4 }

    ipeTrapControlValueVars OBJECT IDENTIFIER
        ::= { ipeTrapCommon 5 }

    eventControlValue OBJECT-TYPE
        SYNTAX       Integer32
        MAX-ACCESS   read-only
        STATUS       current
        DESCRIPTION
            "the changed value of control event whose syntax is integer32.
            Event object is represented by 'eventResourceID'"
        ::= { ipeTrapControlValueVars 1 }

    eventControlValueDspStr OBJECT-TYPE
        SYNTAX       DisplayString
        MAX-ACCESS   read-only
        STATUS       current
        DESCRIPTION
            "the changed value of control event whose syntax is DISPLAY
            STRING. Event object is represented by 'eventResourceID'"
        ::= { ipeTrapControlValueVars 2 }

    eventControlValueOctStr OBJECT-TYPE
        SYNTAX       OCTET STRING (SIZE(32..32))
        MAX-ACCESS   read-only
        STATUS       current
        DESCRIPTION
            "the changed value of control event whose syntax is OCTET STRING.
            Event object is represented by 'eventResourceID'"
        ::= { ipeTrapControlValueVars 3 }

    eventControlValueUnsigned32 OBJECT-TYPE
        SYNTAX       Unsigned32
        MAX-ACCESS   read-only
        STATUS       current
        DESCRIPTION
            "the changed value of control event whose syntax is Unsigned32.
            Event object is represented by 'eventResourceID'"
        ::= { ipeTrapControlValueVars 4 }

    ipeTrapControlVars OBJECT IDENTIFIER
        ::= { ipeTrapCommon 6 }

    eventRecordUserName OBJECT-TYPE
        SYNTAX       DisplayString
        MAX-ACCESS   read-only
        STATUS       current
        DESCRIPTION
            "the user name who triggered the control event. In SNMPv1/v2
            cases, this object reports 'unknown' unless 'ipeAccessUserName'
            is set within the SNMP SET PDU.
            In SNMPv3 cases, this object reports user name which is specified
            in SET-REQUEST."
        ::= { ipeTrapControlVars 1 }

    eventRecordAccessType OBJECT-TYPE
        SYNTAX       INTEGER {
                         invalid(0),
                         nms(1),
                         webLct(2),
                         cli(3),
                         internal(4)
                     }
        MAX-ACCESS   read-only
        STATUS       current
        DESCRIPTION
            "the access type which triggered the control event. This object
            reports 'nms' unless 'ipeAccessType' is set within the SNMP SET
            PDU. Otherwise this object reports the same value of
            'ipeAccessType'."
        ::= { ipeTrapControlVars 2 }

    eventRecordAccessFrom OBJECT-TYPE
        SYNTAX       IpAddress
        MAX-ACCESS   read-only
        STATUS       current
        DESCRIPTION
            "the ip address which triggered the control event. The ip address
            is normally recognized by source ip address of SET-REQUEST. But
            when 'ipeAccessFrom' is set in the SET-REQUEST, this object
            reports same value of 'ipeAccessFrom'."
        ::= { ipeTrapControlVars 3 }

    ipeTrapFileDownloadValueVars OBJECT IDENTIFIER
        ::= { ipeTrapCommon 7 }

    eventDownloadModule OBJECT-TYPE
        SYNTAX       Integer32
        MAX-ACCESS   read-only
        STATUS       current
        DESCRIPTION
            "Represents download module type which triggered download event.
            The type values are same as 'ipeSysOpFileDownloadModule'."
        ::= { ipeTrapFileDownloadValueVars 1 }

    eventDownloadStatus OBJECT-TYPE
        SYNTAX       Integer32
        MAX-ACCESS   read-only
        STATUS       current
        DESCRIPTION
            "Represents download status. The status values are same as
            'ipeSysOpFileDownloadStatus'."
        ::= { ipeTrapFileDownloadValueVars 2 }

    eventUpdateDetail OBJECT-TYPE
        SYNTAX       DisplayString
        MAX-ACCESS   read-only
        STATUS       current
        DESCRIPTION
            "Represents download file name which is specified by
            'ipeFsUpdateFileDetail'."
        ::= { ipeTrapFileDownloadValueVars 3 }

    eventUpdateStatus OBJECT-TYPE
        SYNTAX       Integer32
        MAX-ACCESS   read-only
        STATUS       current
        DESCRIPTION
            "Represents download file progress. The value is same as
            'ipeFsUpdateFileStatus'."
        ::= { ipeTrapFileDownloadValueVars 4 }

    ipeTrapItemVar OBJECT IDENTIFIER
        ::= { trapGroup 3 }

    ipeAlarmTrapItemVar OBJECT IDENTIFIER
        ::= { ipeTrapItemVar 1 }

    alarmStateChange NOTIFICATION-TYPE
        OBJECTS      {
                         eventTotalCount,
                         eventCount,
                         eventTime,
                         eventType,
                         eventResourceID,
                         eventSeverity,
                         eventAlarmType,
                         eventProbableCause,
                         eventAdditionalText1,
                         eventAdditionalText2,
                         eventAdditionalText3,
                         eventAdditionalText4,
                         eventAdditionalText5
                     }
        STATUS       current
        DESCRIPTION
            "Trap for Alarm
            This notification reports that a processed alarm status may have
            changed.
            The object information is recorded in 'eventResourceID' and also
            changed alarm status is recorded in 'eventSeverity'.
            The 'eventTotalCount' and 'eventCount' is sequential number.
            'eventTotalCount' is notification event count since agent was
            booted.
            'eventAdditionalText' provides some event description."
        ::= { ipeAlarmTrapItemVar 1 }

    ipeStatusTrapItemVar OBJECT IDENTIFIER
        ::= { ipeTrapItemVar 2 }

    statusChange NOTIFICATION-TYPE
        OBJECTS      {
                         eventTotalCount,
                         eventCount,
                         eventTime,
                         eventType,
                         eventResourceID,
                         eventStatusValue,
                         eventAdditionalText1,
                         eventAdditionalText2,
                         eventAdditionalText3,
                         eventAdditionalText4,
                         eventAdditionalText5
                     }
        STATUS       current
        DESCRIPTION
            "Trap for Status (Integer)
            This notification reports that the object's status whose SYNTAX
            is INTEGER type may have changed.
            The object information is recorded in 'eventResourceID'.
            The 'eventTotalCount' and 'eventCount' is sequential number.
            'eventTotalCount' is notification event count since agent was
            booted.
            'eventAdditionalText' provides some event description."
        ::= { ipeStatusTrapItemVar 1 }

    statusChangeDspStr NOTIFICATION-TYPE
        OBJECTS      {
                         eventTotalCount,
                         eventCount,
                         eventTime,
                         eventType,
                         eventResourceID,
                         eventStatusValueDspStr,
                         eventAdditionalText1,
                         eventAdditionalText2,
                         eventAdditionalText3,
                         eventAdditionalText4,
                         eventAdditionalText5
                     }
        STATUS       current
        DESCRIPTION
            "Trap for Status (Display String)
            This notification reports that the object's status whose SYNTAX
            is DISPLAY STRING type may have changed.
            The object information is recorded in 'eventResourceID'.
            The 'eventTotalCount' and 'eventCount' is sequential number.
            'eventTotalCount' is notification event count since agent was
            booted.
            'eventAdditionalText' provides some event description."
        ::= { ipeStatusTrapItemVar 2 }

    statusChangeOctStr NOTIFICATION-TYPE
        OBJECTS      {
                         eventTotalCount,
                         eventCount,
                         eventTime,
                         eventType,
                         eventResourceID,
                         eventStatusValueOctStr,
                         eventAdditionalText1,
                         eventAdditionalText2,
                         eventAdditionalText3,
                         eventAdditionalText4,
                         eventAdditionalText5
                     }
        STATUS       current
        DESCRIPTION
            "Trap for Status (Octet String)
            This notification reports that the object's status whose SYNTAX
            is OCTET STRING type may have changed.
            The object information is recorded in 'eventResourceID'.
            The 'eventTotalCount' and 'eventCount' is sequential number.
            'eventTotalCount' is notification event count since agent was
            booted.
            'eventAdditionalText' provides some event description."
        ::= { ipeStatusTrapItemVar 3 }

    statusChangeUnsigned32 NOTIFICATION-TYPE
        OBJECTS      {
                         eventTotalCount,
                         eventCount,
                         eventTime,
                         eventType,
                         eventResourceID,
                         eventStatusValueUnsigned32,
                         eventAdditionalText1,
                         eventAdditionalText2,
                         eventAdditionalText3,
                         eventAdditionalText4,
                         eventAdditionalText5
                     }
        STATUS       current
        DESCRIPTION
            "Trap for Status (Unsigned32)
            This notification reports that the object's status whose SYNTAX
            is Unsigned type may have changed.
            The object information is recorded in 'eventResourceID' and also
            changed alarm status is recorded in 'eventSeverity'.
            The 'eventTotalCount' and 'eventCount' is sequential number.
            'eventTotalCount' is notification event count since agent was
            booted.
            'eventAdditionalText' provides some event description."
        ::= { ipeStatusTrapItemVar 4 }

    ipeControlTrapItemVar OBJECT IDENTIFIER
        ::= { ipeTrapItemVar 3 }

    controlEvent NOTIFICATION-TYPE
        OBJECTS      {
                         eventTotalCount,
                         eventCount,
                         eventTime,
                         eventType,
                         eventResourceID,
                         eventControlValue,
                         eventRecordUserName,
                         eventRecordAccessType,
                         eventRecordAccessFrom,
                         eventAdditionalText1,
                         eventAdditionalText2,
                         eventAdditionalText3,
                         eventAdditionalText4,
                         eventAdditionalText5
                     }
        STATUS       current
        DESCRIPTION
            "Trap for Control (Integer)
            This notification reports that the object's value is changed by
            snmp-set request.
            The object information is recorded in 'eventResourceID' and also
            changed value is recorded in 'eventControlValue'.
            The 'eventTotalCount' and 'eventCount' is sequential number.
            'eventTotalCount' is notification event count since agent was
            booted.
            'eventAdditionalText' provides some event description."
        ::= { ipeControlTrapItemVar 1 }

    controlEventDspStr NOTIFICATION-TYPE
        OBJECTS      {
                         eventTotalCount,
                         eventCount,
                         eventTime,
                         eventType,
                         eventResourceID,
                         eventControlValueDspStr,
                         eventRecordUserName,
                         eventRecordAccessType,
                         eventRecordAccessFrom,
                         eventAdditionalText1,
                         eventAdditionalText2,
                         eventAdditionalText3,
                         eventAdditionalText4,
                         eventAdditionalText5
                     }
        STATUS       current
        DESCRIPTION
            "Trap for Control (Display String)
            This notification reports that the object's value is changed by
            snmp-set request.
            The object information is recorded in 'eventResourceID' and also
            changed value is recorded in 'eventControlValueDspStr'.
            The 'eventTotalCount' and 'eventCount' is sequential number.
            'eventTotalCount' is notification event count since agent was
            booted.
            'eventAdditionalText' provides some event description."
        ::= { ipeControlTrapItemVar 2 }

    controlEventOctStr NOTIFICATION-TYPE
        OBJECTS      {
                         eventTotalCount,
                         eventCount,
                         eventTime,
                         eventType,
                         eventResourceID,
                         eventControlValueOctStr,
                         eventRecordUserName,
                         eventRecordAccessType,
                         eventRecordAccessFrom,
                         eventAdditionalText1,
                         eventAdditionalText2,
                         eventAdditionalText3,
                         eventAdditionalText4,
                         eventAdditionalText5
                     }
        STATUS       current
        DESCRIPTION
            "Trap for Control (Octet String)
            This notification reports that the object's value is changed by
            snmp-set request.
            The object information is recorded in 'eventResourceID' and also
            changed value is recorded in 'eventControlValueOctStr'.
            The 'eventTotalCount' and 'eventCount' is sequential number.
            'eventTotalCount' is notification event count since agent was
            booted.
            'eventAdditionalText' provides some event description."
        ::= { ipeControlTrapItemVar 3 }

    controlEventUnsigned32 NOTIFICATION-TYPE
        OBJECTS      {
                         eventTotalCount,
                         eventCount,
                         eventTime,
                         eventType,
                         eventResourceID,
                         eventControlValueUnsigned32,
                         eventRecordUserName,
                         eventRecordAccessType,
                         eventRecordAccessFrom,
                         eventAdditionalText1,
                         eventAdditionalText2,
                         eventAdditionalText3,
                         eventAdditionalText4,
                         eventAdditionalText5
                     }
        STATUS       current
        DESCRIPTION
            "Trap for Control (Unsigned32)
            This notification reports that the object's value is changed by
            snmp-set request.
            The object information is recorded in 'eventResourceID' and also
            changed value is recorded in 'eventControlValueUnsigned32'.
            The 'eventTotalCount' and 'eventCount' is sequential number.
            'eventTotalCount' is notification event count since agent was
            booted.
            'eventAdditionalText' provides some event description."
        ::= { ipeControlTrapItemVar 4 }

    ipeFileDownloadTrapItemVar OBJECT IDENTIFIER
        ::= { ipeTrapItemVar 4 }

    fileDownloadEvent NOTIFICATION-TYPE
        OBJECTS      {
                         eventTotalCount,
                         eventCount,
                         eventTime,
                         eventType,
                         eventResourceID,
                         eventDownloadModule,
                         eventDownloadStatus,
                         eventAdditionalText1,
                         eventAdditionalText2,
                         eventAdditionalText3,
                         eventAdditionalText4,
                         eventAdditionalText5
                     }
        STATUS       current
        DESCRIPTION
            "Trap for File Download
            This notification reports that the executed download status is
            changed. Changed value is recorded in 'eventDownloadStatus'. The
            'eventTotalCount' and 'eventCount' is sequential number.
            'eventTotalCount' is notification event count since agent was
            booted.
            'eventAdditionalText' provides some event description."
        ::= { ipeFileDownloadTrapItemVar 1 }

    fileUpdateEvent NOTIFICATION-TYPE
        OBJECTS      {
                         eventTotalCount,
                         eventCount,
                         eventTime,
                         eventType,
                         eventResourceID,
                         eventUpdateDetail,
                         eventUpdateStatus,
                         eventAdditionalText1,
                         eventAdditionalText2,
                         eventAdditionalText3,
                         eventAdditionalText4,
                         eventAdditionalText5
                     }
        STATUS       current
        DESCRIPTION
            "Trap for File Update
            This notification reports that the executed file update status is
            changed. Changed value is recorded in 'eventUpdateStatus'. The
            'eventTotalCount' and 'eventCount' is sequential number.
            'eventTotalCount' is notification event count since agent was
            booted.
            'eventAdditionalText' provides some event description."
        ::= { ipeFileDownloadTrapItemVar 2 }

    ipeEventGroup OBJECT IDENTIFIER
        ::= { trapGroup 4 }

    eventTable OBJECT-TYPE
        SYNTAX       SEQUENCE OF EventEntry
        MAX-ACCESS   not-accessible
        STATUS       current
        DESCRIPTION
            "This table represents trap counter value of each event type."
        ::= { ipeEventGroup 1 }

    eventEntry OBJECT-TYPE
        SYNTAX       EventEntry
        MAX-ACCESS   not-accessible
        STATUS       current
        DESCRIPTION  ""
        INDEX        { eventIndex }
        ::= { eventTable 1 }

    EventEntry ::= SEQUENCE {
        eventIndex        INTEGER,
        eventNEAddress    IpAddress,
        eventDescription  DisplayString,
        eventCounter      Counter32,
        eventLastTime     DateAndTime
    }

    eventIndex OBJECT-TYPE
        SYNTAX       INTEGER {
                         alarmStateChage(1),
                         statusChange(2),
                         controlEvent(3)
                     }
        MAX-ACCESS   not-accessible
        STATUS       current
        DESCRIPTION  "Index of this table."
        ::= { eventEntry 1 }

    eventNEAddress OBJECT-TYPE
        SYNTAX       IpAddress
        MAX-ACCESS   not-accessible
        STATUS       current
        DESCRIPTION  "reserved."
        ::= { eventEntry 2 }

    eventDescription OBJECT-TYPE
        SYNTAX       DisplayString
        MAX-ACCESS   read-only
        STATUS       current
        DESCRIPTION  "A textual string information about the event."
        ::= { eventEntry 3 }

    eventCounter OBJECT-TYPE
        SYNTAX       Counter32
        MAX-ACCESS   read-only
        STATUS       current
        DESCRIPTION
            "The count of SNMP TRAP/INFORM messages per event type
            (alarm/status/control) since this equipment was booted."
        ::= { eventEntry 4 }

    eventLastTime OBJECT-TYPE
        SYNTAX       DateAndTime
        MAX-ACCESS   read-only
        STATUS       current
        DESCRIPTION
            "The date and time when this event type was last updated."
        ::= { eventEntry 5 }

    eventTypeTable OBJECT-TYPE
        SYNTAX       SEQUENCE OF EventTypeEntry
        MAX-ACCESS   not-accessible
        STATUS       current
        DESCRIPTION  "This table represents event information."
        ::= { ipeEventGroup 2 }

    eventTypeEntry OBJECT-TYPE
        SYNTAX       EventTypeEntry
        MAX-ACCESS   not-accessible
        STATUS       current
        DESCRIPTION  ""
        INDEX        {
                         eventTypeIndex,
                         eventTypeSourceCategory,
                         eventTypeElemId
                     }
        ::= { eventTypeTable 1 }

    EventTypeEntry ::= SEQUENCE {
        eventTypeIndex           Integer32,
        eventTypeSourceCategory  Integer32,
        eventTypeElemId          Integer32,
        eventTypeNEAddress       IpAddress,
        eventTypeTrapId          Integer32,
        eventTypeDescription     DisplayString,
        eventTypeRowStatus       RowStatus
    }

    eventTypeIndex OBJECT-TYPE
        SYNTAX       Integer32
        MAX-ACCESS   not-accessible
        STATUS       current
        DESCRIPTION  "Index of this table."
        ::= { eventTypeEntry 1 }

    eventTypeSourceCategory OBJECT-TYPE
        SYNTAX       Integer32
        MAX-ACCESS   not-accessible
        STATUS       current
        DESCRIPTION
            "Index of this table. This object represents category of
            generator of the event."
        ::= { eventTypeEntry 2 }

    eventTypeElemId OBJECT-TYPE
        SYNTAX       Integer32
        MAX-ACCESS   not-accessible
        STATUS       current
        DESCRIPTION
            "Index of this table. Administrative index value of the event
            which is uniquely identified among the eventTypeSourceCategory."
        ::= { eventTypeEntry 3 }

    eventTypeNEAddress OBJECT-TYPE
        SYNTAX       IpAddress
        MAX-ACCESS   not-accessible
        STATUS       current
        DESCRIPTION  "reserved."
        ::= { eventTypeEntry 4 }

    eventTypeTrapId OBJECT-TYPE
        SYNTAX       Integer32
        MAX-ACCESS   read-only
        STATUS       current
        DESCRIPTION
            "Represents event type id same as eventTypeIndex. This object
            indicates which counter will be incremented when this event
            occurs."
        ::= { eventTypeEntry 5 }

    eventTypeDescription OBJECT-TYPE
        SYNTAX       DisplayString
        MAX-ACCESS   read-only
        STATUS       current
        DESCRIPTION  "A Textual string information about the event."
        ::= { eventTypeEntry 6 }

    eventTypeRowStatus OBJECT-TYPE
        SYNTAX       RowStatus
        MAX-ACCESS   read-create
        STATUS       current
        DESCRIPTION
            "RowStatus of this table. This table is created automatically
            when the agent starts, and cannot create or destroy from
            manager."
        ::= { eventTypeEntry 7 }

    ipeTrapStatusGroup OBJECT IDENTIFIER
        ::= { trapGroup 5 }

    ipeTrapCounterTable OBJECT-TYPE
        SYNTAX       SEQUENCE OF IpeTrapCounterEntry
        MAX-ACCESS   not-accessible
        STATUS       current
        DESCRIPTION  "This table represents event total count."
        ::= { ipeTrapStatusGroup 1 }

    ipeTrapCounterEntry OBJECT-TYPE
        SYNTAX       IpeTrapCounterEntry
        MAX-ACCESS   not-accessible
        STATUS       current
        DESCRIPTION  ""
        INDEX        { ipeTrapCounterIndex }
        ::= { ipeTrapCounterTable 1 }

    IpeTrapCounterEntry ::= SEQUENCE {
        ipeTrapCounterIndex           Integer32,
        ipeTrapTotalCounterNEAddress  IpAddress,
        ipeTrapTotalCounter           Counter32
    }

    ipeTrapCounterIndex OBJECT-TYPE
        SYNTAX       Integer32
        MAX-ACCESS   not-accessible
        STATUS       current
        DESCRIPTION  "Index of this table."
        ::= { ipeTrapCounterEntry 1 }

    ipeTrapTotalCounterNEAddress OBJECT-TYPE
        SYNTAX       IpAddress
        MAX-ACCESS   not-accessible
        STATUS       current
        DESCRIPTION  "reserved."
        ::= { ipeTrapCounterEntry 2 }

    ipeTrapTotalCounter OBJECT-TYPE
        SYNTAX       Counter32
        MAX-ACCESS   read-only
        STATUS       current
        DESCRIPTION
            "represents total counter value which counts all event type of
            TRAP/INFORM messages."
        ::= { ipeTrapCounterEntry 3 }

-----------------------------------------------
-- alarmStatusGroup Definitions
-----------------------------------------------

    asOduGroup OBJECT IDENTIFIER
        ::= { alarmStatusGroup 1 }

    oduGroupTable OBJECT-TYPE
        SYNTAX       SEQUENCE OF OduGroupEntry
        MAX-ACCESS   not-accessible
        STATUS       current
        DESCRIPTION  "This table represents alarm and status information."
        ::= { asOduGroup 1 }

    oduGroupEntry OBJECT-TYPE
        SYNTAX       OduGroupEntry
        MAX-ACCESS   not-accessible
        STATUS       current
        DESCRIPTION  ""
        INDEX        { oduGroupIfIndex }
        ::= { oduGroupTable 1 }

    OduGroupEntry ::= SEQUENCE {
        oduGroupIfIndex    InterfaceIndex,
        oduGroupNEAddress  IpAddress,
        oduAlarm           SeverityValue,
        txPowerAlarm       SeverityValue,
        txInputAlarm       SeverityValue,
        rxLevelAlarm       SeverityValue,
        cpuCableOpenAlarm  SeverityValue,
        loRefAlarm         SeverityValue,
        muteStatus         OffOnValue,
        oduPsAlarm         SeverityValue,
        oduPsSetStatus     OffOnValue,
        oduTypeMismatch    SeverityValue,
        oduTotalAlarm      SeverityValue
    }

    oduGroupIfIndex OBJECT-TYPE
        SYNTAX       InterfaceIndex
        MAX-ACCESS   not-accessible
        STATUS       current
        DESCRIPTION  "Index of this table."
        ::= { oduGroupEntry 1 }

    oduGroupNEAddress OBJECT-TYPE
        SYNTAX       IpAddress
        MAX-ACCESS   not-accessible
        STATUS       current
        DESCRIPTION  "reserved."
        ::= { oduGroupEntry 2 }

    oduAlarm OBJECT-TYPE
        SYNTAX       SeverityValue
        MAX-ACCESS   read-only
        STATUS       current
        DESCRIPTION  "ODU Alarm."
        ::= { oduGroupEntry 3 }

    txPowerAlarm OBJECT-TYPE
        SYNTAX       SeverityValue
        MAX-ACCESS   read-only
        STATUS       current
        DESCRIPTION  "ODU TX Power Alarm."
        ::= { oduGroupEntry 4 }

    txInputAlarm OBJECT-TYPE
        SYNTAX       SeverityValue
        MAX-ACCESS   read-only
        STATUS       current
        DESCRIPTION  "ODU TX Input Alarm."
        ::= { oduGroupEntry 5 }

    rxLevelAlarm OBJECT-TYPE
        SYNTAX       SeverityValue
        MAX-ACCESS   read-only
        STATUS       current
        DESCRIPTION  "ODU RX Level Alarm."
        ::= { oduGroupEntry 6 }

    cpuCableOpenAlarm OBJECT-TYPE
        SYNTAX       SeverityValue
        MAX-ACCESS   read-only
        STATUS       current
        DESCRIPTION  "ODU CPU / Cable Open Alarm."
        ::= { oduGroupEntry 7 }

    loRefAlarm OBJECT-TYPE
        SYNTAX       SeverityValue
        MAX-ACCESS   read-only
        STATUS       current
        DESCRIPTION  "ODU LO REF Alarm"
        ::= { oduGroupEntry 8 }

    muteStatus OBJECT-TYPE
        SYNTAX       OffOnValue
        MAX-ACCESS   read-only
        STATUS       current
        DESCRIPTION  "ODU mute status."
        ::= { oduGroupEntry 9 }

    oduPsAlarm OBJECT-TYPE
        SYNTAX       SeverityValue
        MAX-ACCESS   read-only
        STATUS       current
        DESCRIPTION  "ODU Power Supply Alarm"
        ::= { oduGroupEntry 10 }

    oduPsSetStatus OBJECT-TYPE
        SYNTAX       OffOnValue
        MAX-ACCESS   read-only
        STATUS       current
        DESCRIPTION  "ODU Power Supply Status."
        ::= { oduGroupEntry 11 }

    oduTypeMismatch OBJECT-TYPE
        SYNTAX       SeverityValue
        MAX-ACCESS   read-only
        STATUS       current
        DESCRIPTION  "ODU Type Mismatch Alarm."
        ::= { oduGroupEntry 12 }

    oduTotalAlarm OBJECT-TYPE
        SYNTAX       SeverityValue
        MAX-ACCESS   read-only
        STATUS       current
        DESCRIPTION  "ODU Total Alarm."
        ::= { oduGroupEntry 13 }

    oduSwGroupTable OBJECT-TYPE
        SYNTAX       SEQUENCE OF OduSwGroupEntry
        MAX-ACCESS   not-accessible
        STATUS       current
        DESCRIPTION  "This table represents ODU Switch Group Status."
        ::= { asOduGroup 2 }

    oduSwGroupEntry OBJECT-TYPE
        SYNTAX       OduSwGroupEntry
        MAX-ACCESS   not-accessible
        STATUS       current
        DESCRIPTION  ""
        INDEX        { oduSwGroupIfIndex }
        ::= { oduSwGroupTable 1 }

    OduSwGroupEntry ::= SEQUENCE {
        oduSwGroupIfIndex         InterfaceIndex,
        oduSwGroupNEAddress       IpAddress,
        txSWStatus                INTEGER,
        rxSWStatus                INTEGER,
        txSWLockInStatus          INTEGER,
        txSwReverseReqRecvStatus  INTEGER
    }

    oduSwGroupIfIndex OBJECT-TYPE
        SYNTAX       InterfaceIndex
        MAX-ACCESS   not-accessible
        STATUS       current
        DESCRIPTION  "Index of this table."
        ::= { oduSwGroupEntry 1 }

    oduSwGroupNEAddress OBJECT-TYPE
        SYNTAX       IpAddress
        MAX-ACCESS   not-accessible
        STATUS       current
        DESCRIPTION  "reserved."
        ::= { oduSwGroupEntry 2 }

    txSWStatus OBJECT-TYPE
        SYNTAX       INTEGER { no1(1), no2(2) }
        MAX-ACCESS   read-only
        STATUS       current
        DESCRIPTION  "ODU TX SW Status"
        ::= { oduSwGroupEntry 3 }

    rxSWStatus OBJECT-TYPE
        SYNTAX       INTEGER { no1(1), no2(2) }
        MAX-ACCESS   read-only
        STATUS       current
        DESCRIPTION  "ODU RX SW Status"
        ::= { oduSwGroupEntry 4 }

    txSWLockInStatus OBJECT-TYPE
        SYNTAX       INTEGER { normal(1), lockin(2) }
        MAX-ACCESS   read-only
        STATUS       current
        DESCRIPTION  "MODEM TX SW Lock-in Status"
        ::= { oduSwGroupEntry 5 }

    txSwReverseReqRecvStatus OBJECT-TYPE
        SYNTAX       INTEGER { normal(1), received(2), execute(3) }
        MAX-ACCESS   read-only
        STATUS       current
        DESCRIPTION  "MODEM TX SW Reverse Request Status."
        ::= { oduSwGroupEntry 6 }

    asModemGroup OBJECT IDENTIFIER
        ::= { alarmStatusGroup 2 }

    modemGroupTable OBJECT-TYPE
        SYNTAX       SEQUENCE OF ModemGroupEntry
        MAX-ACCESS   not-accessible
        STATUS       current
        DESCRIPTION
            "This table represents MODEM Alarm Status information."
        ::= { asModemGroup 1 }

    modemGroupEntry OBJECT-TYPE
        SYNTAX       ModemGroupEntry
        MAX-ACCESS   not-accessible
        STATUS       current
        DESCRIPTION  ""
        INDEX        { modemGroupIfIndex }
        ::= { modemGroupTable 1 }

    ModemGroupEntry ::= SEQUENCE {
        modemGroupIfIndex    InterfaceIndex,
        modemGroupNEAddress  IpAddress,
        lof                  SeverityValue,
        frameID              SeverityValue,
        highBERAlarm         SeverityValue,
        lowBERAlarm          SeverityValue,
        earlyWarningAlarm    SeverityValue,
        modAlarm             SeverityValue,
        ifCableShortAlarm    SeverityValue,
        atpcPowerMode        INTEGER,
        inPhaseStatus        INTEGER,
        amrRangeMismatch     SeverityValue,
        txModulation         INTEGER,
        rxModulation         INTEGER,
        l2SyncLossAlarm      SeverityValue,
        rdiAlarm             SeverityValue,
        uaeAlarm             SeverityValue,
        unlocked             SeverityValue,
        tempAlarm            SeverityValue,
        tdmRangeMismatch     SeverityValue,
        modemPsOff           OffOnValue
    }

    modemGroupIfIndex OBJECT-TYPE
        SYNTAX       InterfaceIndex
        MAX-ACCESS   not-accessible
        STATUS       current
        DESCRIPTION  "Index of this table."
        ::= { modemGroupEntry 1 }

    modemGroupNEAddress OBJECT-TYPE
        SYNTAX       IpAddress
        MAX-ACCESS   not-accessible
        STATUS       current
        DESCRIPTION  "reserved."
        ::= { modemGroupEntry 2 }

    lof OBJECT-TYPE
        SYNTAX       SeverityValue
        MAX-ACCESS   read-only
        STATUS       current
        DESCRIPTION  "MODEM LOF Alarm"
        ::= { modemGroupEntry 3 }

    frameID OBJECT-TYPE
        SYNTAX       SeverityValue
        MAX-ACCESS   read-only
        STATUS       current
        DESCRIPTION  "MODEM Frame ID Alarm"
        ::= { modemGroupEntry 4 }

    highBERAlarm OBJECT-TYPE
        SYNTAX       SeverityValue
        MAX-ACCESS   read-only
        STATUS       current
        DESCRIPTION  "MODEM High BER Alarm."
        ::= { modemGroupEntry 5 }

    lowBERAlarm OBJECT-TYPE
        SYNTAX       SeverityValue
        MAX-ACCESS   read-only
        STATUS       current
        DESCRIPTION  "MODEM Low BER Alarm."
        ::= { modemGroupEntry 6 }

    earlyWarningAlarm OBJECT-TYPE
        SYNTAX       SeverityValue
        MAX-ACCESS   read-only
        STATUS       current
        DESCRIPTION  "MODEM Early Warning Alarm"
        ::= { modemGroupEntry 7 }

    modAlarm OBJECT-TYPE
        SYNTAX       SeverityValue
        MAX-ACCESS   read-only
        STATUS       current
        DESCRIPTION  "MODEM MOD Alarm"
        ::= { modemGroupEntry 8 }

    ifCableShortAlarm OBJECT-TYPE
        SYNTAX       SeverityValue
        MAX-ACCESS   read-only
        STATUS       current
        DESCRIPTION  "MODEM IF Cable Short Alarm"
        ::= { modemGroupEntry 9 }

    atpcPowerMode OBJECT-TYPE
        SYNTAX       INTEGER { stop(1), active(2) }
        MAX-ACCESS   read-only
        STATUS       current
        DESCRIPTION  "MODEM ATPC Power Mode Status"
        ::= { modemGroupEntry 10 }

    inPhaseStatus OBJECT-TYPE
        SYNTAX       INTEGER { inphase(1), outphase(2) }
        MAX-ACCESS   read-only
        STATUS       current
        DESCRIPTION  "MODEM Inphase Status"
        ::= { modemGroupEntry 11 }

    amrRangeMismatch OBJECT-TYPE
        SYNTAX       SeverityValue
        MAX-ACCESS   read-only
        STATUS       obsolete
        DESCRIPTION  "obsoleted"
        ::= { modemGroupEntry 12 }

    txModulation OBJECT-TYPE
        SYNTAX       INTEGER {
                         invalid(0),
                         qpsk(1),
                         qam16(2),
                         qam32(3),
                         qam64(4),
                         qam128(5),
                         qam256(6),
                         qam512(7),
                         qam1024(8),
                         qam2048(9)
                     }
        MAX-ACCESS   read-only
        STATUS       current
        DESCRIPTION  "MODEM TX Modulation Status"
        ::= { modemGroupEntry 13 }

    rxModulation OBJECT-TYPE
        SYNTAX       INTEGER {
                         invalid(0),
                         qpsk(1),
                         qam16(2),
                         qam32(3),
                         qam64(4),
                         qam128(5),
                         qam256(6),
                         qam512(7),
                         qam1024(8),
                         qam2048(9)
                     }
        MAX-ACCESS   read-only
        STATUS       current
        DESCRIPTION  "MODEM RX Modulation Status."
        ::= { modemGroupEntry 14 }

    l2SyncLossAlarm OBJECT-TYPE
        SYNTAX       SeverityValue
        MAX-ACCESS   read-only
        STATUS       current
        DESCRIPTION  "MODEM L2SYNC Loss Alarm."
        ::= { modemGroupEntry 15 }

    rdiAlarm OBJECT-TYPE
        SYNTAX       SeverityValue
        MAX-ACCESS   read-only
        STATUS       current
        DESCRIPTION  "MODEM RDI Alarm"
        ::= { modemGroupEntry 16 }

    uaeAlarm OBJECT-TYPE
        SYNTAX       SeverityValue
        MAX-ACCESS   read-only
        STATUS       current
        DESCRIPTION  "MODEM UAE Alarm"
        ::= { modemGroupEntry 17 }

    unlocked OBJECT-TYPE
        SYNTAX       SeverityValue
        MAX-ACCESS   read-only
        STATUS       current
        DESCRIPTION  "MODEM Unlocked Alarm"
        ::= { modemGroupEntry 18 }

    tempAlarm OBJECT-TYPE
        SYNTAX       SeverityValue
        MAX-ACCESS   read-only
        STATUS       deprecated
        DESCRIPTION  "MODEM Temperature Alarm"
        ::= { modemGroupEntry 19 }

    tdmRangeMismatch OBJECT-TYPE
        SYNTAX       SeverityValue
        MAX-ACCESS   read-only
        STATUS       current
        DESCRIPTION  "MODEM TDM / AMR / AMBR Range Mismatch Alarm"
        ::= { modemGroupEntry 20 }

    modemPsOff OBJECT-TYPE
        SYNTAX       OffOnValue
        MAX-ACCESS   read-only
        STATUS       current
        DESCRIPTION  "MDOEM Power Supply Status"
        ::= { modemGroupEntry 21 }

    modemXpicTable OBJECT-TYPE
        SYNTAX       SEQUENCE OF ModemXpicEntry
        MAX-ACCESS   not-accessible
        STATUS       current
        DESCRIPTION  "Represents XPIC Alarm and Status"
        ::= { asModemGroup 2 }

    modemXpicEntry OBJECT-TYPE
        SYNTAX       ModemXpicEntry
        MAX-ACCESS   not-accessible
        STATUS       current
        DESCRIPTION  ""
        INDEX        { modemXpicIfIndex }
        ::= { modemXpicTable 1 }

    ModemXpicEntry ::= SEQUENCE {
        modemXpicIfIndex    InterfaceIndex,
        modemXpicNEAddress  IpAddress,
        xIFLevelAlarm       SeverityValue,
        xpicTypeMismatch    SeverityValue
    }

    modemXpicIfIndex OBJECT-TYPE
        SYNTAX       InterfaceIndex
        MAX-ACCESS   not-accessible
        STATUS       current
        DESCRIPTION  "Index of this table."
        ::= { modemXpicEntry 1 }

    modemXpicNEAddress OBJECT-TYPE
        SYNTAX       IpAddress
        MAX-ACCESS   not-accessible
        STATUS       current
        DESCRIPTION  "reserved."
        ::= { modemXpicEntry 2 }

    xIFLevelAlarm OBJECT-TYPE
        SYNTAX       SeverityValue
        MAX-ACCESS   read-only
        STATUS       current
        DESCRIPTION  "MODEM XIF Alarm."
        ::= { modemXpicEntry 3 }

    xpicTypeMismatch OBJECT-TYPE
        SYNTAX       SeverityValue
        MAX-ACCESS   read-only
        STATUS       current
        DESCRIPTION  "MODEM XPIC Mode Mismatch Alarm."
        ::= { modemXpicEntry 4 }

    modemCardTable OBJECT-TYPE
        SYNTAX       SEQUENCE OF ModemCardEntry
        MAX-ACCESS   not-accessible
        STATUS       current
        DESCRIPTION  "Represents MODEM Card Alarm Status."
        ::= { asModemGroup 3 }

    modemCardEntry OBJECT-TYPE
        SYNTAX       ModemCardEntry
        MAX-ACCESS   not-accessible
        STATUS       current
        DESCRIPTION  ""
        INDEX        { modemCardIndex }
        ::= { modemCardTable 1 }

    ModemCardEntry ::= SEQUENCE {
        modemCardIndex         Integer32,
        modemCardNEAddress     IpAddress,
        modemComFailAlarm      SeverityValue,
        modemUnequipped        SeverityValue,
        modemAlarm             SeverityValue,
        modemBusErrorTx        SeverityValue,
        modemBusErrorRx        SeverityValue,
        modemTypeMismatch      SeverityValue,
        modemCardOnlineStatus  INTEGER,
        modemCardPsAlarm       SeverityValue
    }

    modemCardIndex OBJECT-TYPE
        SYNTAX       Integer32
        MAX-ACCESS   not-accessible
        STATUS       current
        DESCRIPTION  "Index of this table."
        ::= { modemCardEntry 1 }

    modemCardNEAddress OBJECT-TYPE
        SYNTAX       IpAddress
        MAX-ACCESS   not-accessible
        STATUS       current
        DESCRIPTION  "reserved."
        ::= { modemCardEntry 2 }

    modemComFailAlarm OBJECT-TYPE
        SYNTAX       SeverityValue
        MAX-ACCESS   read-only
        STATUS       current
        DESCRIPTION  "MODEM Communication FAIL Alarm."
        ::= { modemCardEntry 3 }

    modemUnequipped OBJECT-TYPE
        SYNTAX       SeverityValue
        MAX-ACCESS   read-only
        STATUS       current
        DESCRIPTION  "MODEM Unequipped Alarm."
        ::= { modemCardEntry 4 }

    modemAlarm OBJECT-TYPE
        SYNTAX       SeverityValue
        MAX-ACCESS   read-only
        STATUS       current
        DESCRIPTION  "MODEM Module Alarm."
        ::= { modemCardEntry 5 }

    modemBusErrorTx OBJECT-TYPE
        SYNTAX       SeverityValue
        MAX-ACCESS   read-only
        STATUS       current
        DESCRIPTION  "MODEM Tx Bus Error Alarm."
        ::= { modemCardEntry 6 }

    modemBusErrorRx OBJECT-TYPE
        SYNTAX       SeverityValue
        MAX-ACCESS   read-only
        STATUS       current
        DESCRIPTION  "MODEM Rx Bus Error Alarm."
        ::= { modemCardEntry 7 }

    modemTypeMismatch OBJECT-TYPE
        SYNTAX       SeverityValue
        MAX-ACCESS   read-only
        STATUS       current
        DESCRIPTION  "MODEM Type Mismatch Alarm."
        ::= { modemCardEntry 8 }

    modemCardOnlineStatus OBJECT-TYPE
        SYNTAX       INTEGER { invalid(0), offline(1), online(2) }
        MAX-ACCESS   read-only
        STATUS       current
        DESCRIPTION  "MODEM Online Status"
        ::= { modemCardEntry 9 }

    modemCardPsAlarm OBJECT-TYPE
        SYNTAX       SeverityValue
        MAX-ACCESS   read-only
        STATUS       current
        DESCRIPTION  "MODEM Power Supply Alarm."
        ::= { modemCardEntry 10 }

    asModemHeaderCompressTable OBJECT-TYPE
        SYNTAX       SEQUENCE OF AsModemHeaderCompressEntry
        MAX-ACCESS   not-accessible
        STATUS       current
        DESCRIPTION
            "Header Compression Function Status.
            This table is created automatically when the Modem Card is
            provisioned, if the F/W supports the new Header Compression
            function."
        ::= { asModemGroup 4 }

    asModemHeaderCompressEntry OBJECT-TYPE
        SYNTAX       AsModemHeaderCompressEntry
        MAX-ACCESS   not-accessible
        STATUS       current
        DESCRIPTION  ""
        INDEX        { asModemHeaderCompressIfIndex }
        ::= { asModemHeaderCompressTable 1 }

    AsModemHeaderCompressEntry ::= SEQUENCE {
        asModemHeaderCompressIfIndex      InterfaceIndex,
        asModemHeaderCompressNEAddress    IpAddress,
        asModemHeaderCompressMismatch     SeverityValue,
        asModemHeaderCompressCurrentMode  INTEGER,
        asModemHeaderCompressVersion      Integer32
    }

    asModemHeaderCompressIfIndex OBJECT-TYPE
        SYNTAX       InterfaceIndex
        MAX-ACCESS   not-accessible
        STATUS       current
        DESCRIPTION  "Index of this table."
        ::= { asModemHeaderCompressEntry 1 }

    asModemHeaderCompressNEAddress OBJECT-TYPE
        SYNTAX       IpAddress
        MAX-ACCESS   not-accessible
        STATUS       current
        DESCRIPTION  "reserved."
        ::= { asModemHeaderCompressEntry 2 }

    asModemHeaderCompressMismatch OBJECT-TYPE
        SYNTAX       SeverityValue
        MAX-ACCESS   read-only
        STATUS       current
        DESCRIPTION
            "Header/Payload* Compression Mismatch Alarm.
            If the configuration of local and remote header compression mode
            is different, the alarm will be reported.
            (*iPASOLINK VR series only)"
        ::= { asModemHeaderCompressEntry 3 }

    asModemHeaderCompressCurrentMode OBJECT-TYPE
        SYNTAX       INTEGER {
                         invalid(0),
                         disable(1),
                         mac(2),
                         macWithIpv4(3),
                         macWithIpv6(4),
                         macWithMpls(5),
                         enhancedMacWithIpv4(6),
                         enhancedMacWithIpv6(7),
                         enhancedMacWithMpls(8)
                     }
        MAX-ACCESS   read-only
        STATUS       current
        DESCRIPTION
            "Current Header/Payload* Compression Mode.
            This value shows same value as 'provModemHeaderCompressMode'
            usually. But the value will be different from
            'provModemHeaderCompressMode', when the new Header Compression
            Function is configured to the old Modem Card (which does not have
            new Header Compression capabilities)
            (*iPASOLINK VR series only)"
        ::= { asModemHeaderCompressEntry 4 }

    asModemHeaderCompressVersion OBJECT-TYPE
        SYNTAX       Integer32
        MAX-ACCESS   read-only
        STATUS       current
        DESCRIPTION
            "The version of Header/Payload* Compression Function.
             '1' means the Header Compression is not supported and the
            Payload* Compression is not supported.
             '2' means the Header Compression is supported and the Payload*
            Compression is not supported.
             '3' means the Header Compression is not supported and the
            Payload* Compression is supported.
             '4' means the Header Compression is supported and the Payload*
            Compression is supported.
            (*iPASOLINK VR series only)"
        ::= { asModemHeaderCompressEntry 5 }

    asModemHeaderCompressRemoteTable OBJECT-TYPE
        SYNTAX       SEQUENCE OF AsModemHeaderCompressRemoteEntry
        MAX-ACCESS   not-accessible
        STATUS       current
        DESCRIPTION
            "Remote Modem Header Compression Function Status.
            This table is created automatically when the Modem Card is
            provisioned, if the F/W supports the new Header Compression
            function."
        ::= { asModemGroup 5 }

    asModemHeaderCompressRemoteEntry OBJECT-TYPE
        SYNTAX       AsModemHeaderCompressRemoteEntry
        MAX-ACCESS   not-accessible
        STATUS       current
        DESCRIPTION  ""
        INDEX        { asModemHeaderCompressRemoteIfIndex }
        ::= { asModemHeaderCompressRemoteTable 1 }

    AsModemHeaderCompressRemoteEntry ::= SEQUENCE {
        asModemHeaderCompressRemoteIfIndex    InterfaceIndex,
        asModemHeaderCompressRemoteNEAddress  IpAddress,
        asModemHeaderCompressRemoteMode       INTEGER,
        asModemHeaderCompressRemoteVlanMode   INTEGER,
        asModemHeaderCompressRemoteVersion    Integer32
    }

    asModemHeaderCompressRemoteIfIndex OBJECT-TYPE
        SYNTAX       InterfaceIndex
        MAX-ACCESS   not-accessible
        STATUS       current
        DESCRIPTION  "Index of this table."
        ::= { asModemHeaderCompressRemoteEntry 1 }

    asModemHeaderCompressRemoteNEAddress OBJECT-TYPE
        SYNTAX       IpAddress
        MAX-ACCESS   not-accessible
        STATUS       current
        DESCRIPTION  "reserved."
        ::= { asModemHeaderCompressRemoteEntry 2 }

    asModemHeaderCompressRemoteMode OBJECT-TYPE
        SYNTAX       INTEGER {
                         invalid(0),
                         disable(1),
                         mac(2),
                         macWithIpv4(3),
                         macWithIpv6(4),
                         macWithMpls(5),
                         enhancedMacWithIpv4(6),
                         enhancedMacWithIpv6(7),
                         enhancedMacWithMpls(8),
                         unknown(99)
                     }
        MAX-ACCESS   read-only
        STATUS       current
        DESCRIPTION
            "Header/Payload* Compression Mode of Remote Modem.
            When the Radio link is not established, the value will be changed
            to 'unknown'.
            (*iPASOLINK VR series only)"
        ::= { asModemHeaderCompressRemoteEntry 3 }

    asModemHeaderCompressRemoteVlanMode OBJECT-TYPE
        SYNTAX       INTEGER { invalid(0), dot1q(1), dot1ad(2), unknown(99) }
        MAX-ACCESS   read-only
        STATUS       current
        DESCRIPTION
            "VLAN Mode of Remote equipment.
            When the Radio link is not established, the object will show the
            value 'unknown'."
        ::= { asModemHeaderCompressRemoteEntry 4 }

    asModemHeaderCompressRemoteVersion OBJECT-TYPE
        SYNTAX       Integer32
        MAX-ACCESS   read-only
        STATUS       current
        DESCRIPTION
            "The version of Header/Payload* Compression Function for the
            Remote Modem.
             '1' means the Header Compression is not supported and the
            Payload* Compression is not supported.
             '2' means the Header Compression is supported and the Payload*
            Compression is not supported.
             '3' means the Header Compression is not supported and the
            Payload* Compression is supported.
             '4' means the Header Compression is supported and the Payload*
            Compression is supported.

            When the Radio link is not established, the object will return
            '99'.
            If the object returns other value, the local node cannot
            recognize the received value from remote node.
            (*iPASOLINK VR series only)"
        ::= { asModemHeaderCompressRemoteEntry 5 }

    asModemTrafficAggrTable OBJECT-TYPE
        SYNTAX       SEQUENCE OF AsModemTrafficAggrEntry
        MAX-ACCESS   not-accessible
        STATUS       current
        DESCRIPTION
            "This table contains alarm and status object for Radio Traffic
            Aggregation mode."
        ::= { asModemGroup 6 }

    asModemTrafficAggrEntry OBJECT-TYPE
        SYNTAX       AsModemTrafficAggrEntry
        MAX-ACCESS   not-accessible
        STATUS       current
        DESCRIPTION  ""
        INDEX        { asModemTrafficAggrIfIndex }
        ::= { asModemTrafficAggrTable 1 }

    AsModemTrafficAggrEntry ::= SEQUENCE {
        asModemTrafficAggrIfIndex       InterfaceIndex,
        asModemTrafficAggrNEAddress     IpAddress,
        asModemTrafficAggrModeMismatch  SeverityValue,
        asModemTrafficAggrVersion       Integer32,
        asModemTrafficAggrEncapStatus   INTEGER
    }

    asModemTrafficAggrIfIndex OBJECT-TYPE
        SYNTAX       InterfaceIndex
        MAX-ACCESS   not-accessible
        STATUS       current
        DESCRIPTION  "Index of this table."
        ::= { asModemTrafficAggrEntry 1 }

    asModemTrafficAggrNEAddress OBJECT-TYPE
        SYNTAX       IpAddress
        MAX-ACCESS   not-accessible
        STATUS       current
        DESCRIPTION  "reserved."
        ::= { asModemTrafficAggrEntry 2 }

    asModemTrafficAggrModeMismatch OBJECT-TYPE
        SYNTAX       SeverityValue
        MAX-ACCESS   read-only
        STATUS       current
        DESCRIPTION
            "Radio Traffic Aggregation Mode Mismatch Alarm.
            This alarm is asserted if the Radio Traffic Aggregation is
            configured when the H/W and/or F/W does not support the function.
            And also the alarm is asserted when the configuration is
            mismatched between local node and peer node."
        ::= { asModemTrafficAggrEntry 3 }

    asModemTrafficAggrVersion OBJECT-TYPE
        SYNTAX       Integer32
        MAX-ACCESS   read-only
        STATUS       current
        DESCRIPTION
            "The support version of Radio Traffic Aggreation function.
             '5' means the physical advanced mode aggregation, physical mode
                 aggregation, and legacy radio traffic aggregation are
                 supported (valid for iPASO VR 10 only)
             '2' means the physical mode aggregation and legacy radio traffic
                 aggregation are supported
             '1' means the legacy radio traffic aggregation is supported
                 but physical mode is not supported.
             '0' means the physical mode and legacy radio traffic aggregation
                 are not supported
                 (license is not installed or Modem card does not have that
            capability)."
        ::= { asModemTrafficAggrEntry 4 }

    asModemTrafficAggrEncapStatus OBJECT-TYPE
        SYNTAX       INTEGER { invalid(0), normal(1), fail(2) }
        MAX-ACCESS   read-only
        STATUS       current
        DESCRIPTION
            "Radio Traffic Aggregation Encapsulation Status.
            When the Modem cannot build frames continuously, the object will
            assert the 'fail'.
            The value will change to 'normal' if the condition is cleared."
        ::= { asModemTrafficAggrEntry 5 }

    asCtrlGroup OBJECT IDENTIFIER
        ::= { alarmStatusGroup 3 }

    ctrlGroupTable OBJECT-TYPE
        SYNTAX       SEQUENCE OF CtrlGroupEntry
        MAX-ACCESS   not-accessible
        STATUS       current
        DESCRIPTION  "Represents Main Board/Ctrl Card Alarm and Status"
        ::= { asCtrlGroup 1 }

    ctrlGroupEntry OBJECT-TYPE
        SYNTAX       CtrlGroupEntry
        MAX-ACCESS   not-accessible
        STATUS       current
        DESCRIPTION  ""
        INDEX        { ctrlGroupIndex }
        ::= { ctrlGroupTable 1 }

    CtrlGroupEntry ::= SEQUENCE {
        ctrlGroupIndex      Integer32,
        ctrlGroupNEAddress  IpAddress,
        ctrlAlarm           SeverityValue,
        usbFailure          SeverityValue,
        svLineAlarm         SeverityValue,
        iduCpuAlarm         SeverityValue,
        iduTotalAlarm       SeverityValue,
        maintenance         OffOnValue,
        busError            SeverityValue,
        memoryFailure       SeverityValue,
        clk2mMount          INTEGER,
        ctrlTempAlarm       SeverityValue,
        ctrlTemperature     Integer32
    }

    ctrlGroupIndex OBJECT-TYPE
        SYNTAX       Integer32
        MAX-ACCESS   not-accessible
        STATUS       current
        DESCRIPTION  "Index of this table."
        ::= { ctrlGroupEntry 1 }

    ctrlGroupNEAddress OBJECT-TYPE
        SYNTAX       IpAddress
        MAX-ACCESS   not-accessible
        STATUS       current
        DESCRIPTION  "reserved."
        ::= { ctrlGroupEntry 2 }

    ctrlAlarm OBJECT-TYPE
        SYNTAX       SeverityValue
        MAX-ACCESS   read-only
        STATUS       current
        DESCRIPTION  "Main Board / Ctrl Card Module Alarm"
        ::= { ctrlGroupEntry 3 }

    usbFailure OBJECT-TYPE
        SYNTAX       SeverityValue
        MAX-ACCESS   read-only
        STATUS       current
        DESCRIPTION  "Main Board / Ctrl Card USB FAIL Alarm"
        ::= { ctrlGroupEntry 4 }

    svLineAlarm OBJECT-TYPE
        SYNTAX       SeverityValue
        MAX-ACCESS   read-only
        STATUS       current
        DESCRIPTION  "Main Board / Ctrl Card SV Line Alarm"
        ::= { ctrlGroupEntry 5 }

    iduCpuAlarm OBJECT-TYPE
        SYNTAX       SeverityValue
        MAX-ACCESS   read-only
        STATUS       current
        DESCRIPTION  "Main Board / Ctrl Card IDU CPU Alarm"
        ::= { ctrlGroupEntry 6 }

    iduTotalAlarm OBJECT-TYPE
        SYNTAX       SeverityValue
        MAX-ACCESS   read-only
        STATUS       current
        DESCRIPTION  "Main Board / Ctrl Card IDU Total Alarm"
        ::= { ctrlGroupEntry 7 }

    maintenance OBJECT-TYPE
        SYNTAX       OffOnValue
        MAX-ACCESS   read-only
        STATUS       current
        DESCRIPTION
            "Main Board / Ctrl Card Maintenance Status.
            This object shows that some maintenance functions are performed
            under that equipment."
        ::= { ctrlGroupEntry 8 }

    busError OBJECT-TYPE
        SYNTAX       SeverityValue
        MAX-ACCESS   read-only
        STATUS       current
        DESCRIPTION  "Main Board / Ctrl Card Bus Error Alarm."
        ::= { ctrlGroupEntry 9 }

    memoryFailure OBJECT-TYPE
        SYNTAX       SeverityValue
        MAX-ACCESS   read-only
        STATUS       current
        DESCRIPTION  "Main Board / Ctrl Card Memory FAIL Alarm."
        ::= { ctrlGroupEntry 10 }

    clk2mMount OBJECT-TYPE
        SYNTAX       INTEGER { unmount(1), mount(2) }
        MAX-ACCESS   read-only
        STATUS       current
        DESCRIPTION  "Main Board / Ctrl Card EXT CLK Mount Status."
        ::= { ctrlGroupEntry 11 }

    ctrlTempAlarm OBJECT-TYPE
        SYNTAX       SeverityValue
        MAX-ACCESS   read-only
        STATUS       current
        DESCRIPTION  "Main Board / Ctrl Card Temperature Alarm."
        ::= { ctrlGroupEntry 12 }

    ctrlTemperature OBJECT-TYPE
        SYNTAX       Integer32 (-999|-200..900)
        UNITS        "0.1 degree"
        MAX-ACCESS   read-only
        STATUS       current
        DESCRIPTION
            "Main Board / Ctrl Card Temperature.
            if the unexpected condition happened, the object reports value
            '-999'."
        ::= { ctrlGroupEntry 13 }

    sncpGroupTable OBJECT-TYPE
        SYNTAX       SEQUENCE OF SncpGroupEntry
        MAX-ACCESS   not-accessible
        STATUS       current
        DESCRIPTION  "Represents E1 SNCP Status."
        ::= { asCtrlGroup 2 }

    sncpGroupEntry OBJECT-TYPE
        SYNTAX       SncpGroupEntry
        MAX-ACCESS   not-accessible
        STATUS       current
        DESCRIPTION  ""
        INDEX        { sncpGroupIndex }
        ::= { sncpGroupTable 1 }

    SncpGroupEntry ::= SEQUENCE {
        sncpGroupIndex           Integer32,
        sncpGroupNEAddress       IpAddress,
        ppsFail                  SeverityValue,
        sncpProtectionStatusCh1  INTEGER,
        sncpProtectionStatusCh2  INTEGER,
        sncpOnlineStatus         INTEGER,
        sncpSwStatus             INTEGER
    }

    sncpGroupIndex OBJECT-TYPE
        SYNTAX       Integer32 (1..2352)
        MAX-ACCESS   not-accessible
        STATUS       current
        DESCRIPTION  "Index of this table."
        ::= { sncpGroupEntry 1 }

    sncpGroupNEAddress OBJECT-TYPE
        SYNTAX       IpAddress
        MAX-ACCESS   not-accessible
        STATUS       current
        DESCRIPTION  "reserved."
        ::= { sncpGroupEntry 2 }

    ppsFail OBJECT-TYPE
        SYNTAX       SeverityValue
        MAX-ACCESS   read-only
        STATUS       current
        DESCRIPTION  "Main Board / Ctrl Card PPS FAIL Alarm."
        ::= { sncpGroupEntry 3 }

    sncpProtectionStatusCh1 OBJECT-TYPE
        SYNTAX       INTEGER { fs(1), sf(2), sd(3), ms(4), nr(5) }
        MAX-ACCESS   read-only
        STATUS       current
        DESCRIPTION
            "Main Board / Ctrl Card SNCP Protection Status for Channel 1"
        ::= { sncpGroupEntry 4 }

    sncpProtectionStatusCh2 OBJECT-TYPE
        SYNTAX       INTEGER { fs(1), sf(2), sd(3), ms(4), nr(5) }
        MAX-ACCESS   read-only
        STATUS       current
        DESCRIPTION
            "Main Board / Ctrl Card SNCP Protection Status for Channel 2"
        ::= { sncpGroupEntry 5 }

    sncpOnlineStatus OBJECT-TYPE
        SYNTAX       INTEGER { work(1), protection(2) }
        MAX-ACCESS   read-only
        STATUS       current
        DESCRIPTION  "Main Board / Ctrl Card SNCP Online Status."
        ::= { sncpGroupEntry 6 }

    sncpSwStatus OBJECT-TYPE
        SYNTAX       INTEGER { no1(1), no2(2) }
        MAX-ACCESS   read-only
        STATUS       current
        DESCRIPTION  "Main Board / Ctrl Card SNCP Switch Status."
        ::= { sncpGroupEntry 7 }

    asAuxGroup OBJECT IDENTIFIER
        ::= { alarmStatusGroup 4 }

    auxGroupTable OBJECT-TYPE
        SYNTAX       SEQUENCE OF AuxGroupEntry
        MAX-ACCESS   not-accessible
        STATUS       current
        DESCRIPTION  "Represents AUX Card Alarm / Status."
        ::= { asAuxGroup 1 }

    auxGroupEntry OBJECT-TYPE
        SYNTAX       AuxGroupEntry
        MAX-ACCESS   not-accessible
        STATUS       current
        DESCRIPTION  ""
        INDEX        { auxGroupIndex }
        ::= { auxGroupTable 1 }

    AuxGroupEntry ::= SEQUENCE {
        auxGroupIndex      Integer32,
        auxGroupNEAddress  IpAddress,
        auxUnequipped      SeverityValue,
        auxTypeMismatch    SeverityValue,
        auxAlarm           SeverityValue,
        auxComFailAlarm    SeverityValue,
        auxBusErrorTx      SeverityValue,
        auxBusErrorRx      SeverityValue
    }

    auxGroupIndex OBJECT-TYPE
        SYNTAX       Integer32
        MAX-ACCESS   not-accessible
        STATUS       current
        DESCRIPTION  "Index of this table."
        ::= { auxGroupEntry 1 }

    auxGroupNEAddress OBJECT-TYPE
        SYNTAX       IpAddress
        MAX-ACCESS   not-accessible
        STATUS       current
        DESCRIPTION  "reserved."
        ::= { auxGroupEntry 2 }

    auxUnequipped OBJECT-TYPE
        SYNTAX       SeverityValue
        MAX-ACCESS   read-only
        STATUS       current
        DESCRIPTION  "AUX Unequipped Alarm"
        ::= { auxGroupEntry 3 }

    auxTypeMismatch OBJECT-TYPE
        SYNTAX       SeverityValue
        MAX-ACCESS   read-only
        STATUS       current
        DESCRIPTION  "AUX Type Mismatch Alarm."
        ::= { auxGroupEntry 4 }

    auxAlarm OBJECT-TYPE
        SYNTAX       SeverityValue
        MAX-ACCESS   read-only
        STATUS       current
        DESCRIPTION  "AUX Module Alarm."
        ::= { auxGroupEntry 5 }

    auxComFailAlarm OBJECT-TYPE
        SYNTAX       SeverityValue
        MAX-ACCESS   read-only
        STATUS       current
        DESCRIPTION  "AUX Communication FAIL Alarm."
        ::= { auxGroupEntry 6 }

    auxBusErrorTx OBJECT-TYPE
        SYNTAX       SeverityValue
        MAX-ACCESS   read-only
        STATUS       current
        DESCRIPTION  "AUX Tx Bus Error Alarm"
        ::= { auxGroupEntry 7 }

    auxBusErrorRx OBJECT-TYPE
        SYNTAX       SeverityValue
        MAX-ACCESS   read-only
        STATUS       current
        DESCRIPTION  "AUX Rx Bus Error Alarm"
        ::= { auxGroupEntry 8 }

    asClkGroup OBJECT IDENTIFIER
        ::= { alarmStatusGroup 5 }

    clkCommonTable OBJECT-TYPE
        SYNTAX       SEQUENCE OF ClkCommonEntry
        MAX-ACCESS   not-accessible
        STATUS       current
        DESCRIPTION  "Represents Main Board / Ctrl Card CLK Status."
        ::= { asClkGroup 1 }

    clkCommonEntry OBJECT-TYPE
        SYNTAX       ClkCommonEntry
        MAX-ACCESS   not-accessible
        STATUS       current
        DESCRIPTION  ""
        INDEX        { clkCommonIndex }
        ::= { clkCommonTable 1 }

    ClkCommonEntry ::= SEQUENCE {
        clkCommonIndex             INTEGER,
        clkCommonNEAddress         IpAddress,
        ltiAlarm                   SeverityValue,
        refClkChange               INTEGER,
        extClkLoop                 SeverityValue,
        currentTimingSource        INTEGER,
        timingSourceCondition      INTEGER,
        timingSourceControlStatus  INTEGER
    }

    clkCommonIndex OBJECT-TYPE
        SYNTAX       INTEGER { clk(1) }
        MAX-ACCESS   not-accessible
        STATUS       current
        DESCRIPTION  "Index of this table."
        ::= { clkCommonEntry 1 }

    clkCommonNEAddress OBJECT-TYPE
        SYNTAX       IpAddress
        MAX-ACCESS   not-accessible
        STATUS       current
        DESCRIPTION  "reserved."
        ::= { clkCommonEntry 2 }

    ltiAlarm OBJECT-TYPE
        SYNTAX       SeverityValue
        MAX-ACCESS   read-only
        STATUS       current
        DESCRIPTION  "Main Board / Ctrl Card LTI Alarm."
        ::= { clkCommonEntry 3 }

    refClkChange OBJECT-TYPE
        SYNTAX       INTEGER {
                         lockedRef1(1),
                         lockedRef2(2),
                         lockedRef3(3),
                         holdover(4),
                         freerun(5)
                     }
        MAX-ACCESS   read-only
        STATUS       current
        DESCRIPTION  "Main Board / Ctrl Card CLK Status."
        ::= { clkCommonEntry 4 }

    extClkLoop OBJECT-TYPE
        SYNTAX       SeverityValue
        MAX-ACCESS   read-only
        STATUS       current
        DESCRIPTION  "Main Board / Ctrl Card EXT CLK Timing Loop Alarm."
        ::= { clkCommonEntry 5 }

    currentTimingSource OBJECT-TYPE
        SYNTAX       INTEGER { selectRef1(1), selectRef2(2), selectRef3(3) }
        MAX-ACCESS   read-only
        STATUS       current
        DESCRIPTION  "Main Board / Ctrl Card Current Timing Source."
        ::= { clkCommonEntry 6 }

    timingSourceCondition OBJECT-TYPE
        SYNTAX       INTEGER { locked(1), holdover(2), freerun(3) }
        MAX-ACCESS   read-only
        STATUS       current
        DESCRIPTION  "Main Board / Ctrl Card Timing Source Status."
        ::= { clkCommonEntry 7 }

    timingSourceControlStatus OBJECT-TYPE
        SYNTAX       INTEGER { auto(1), manualSelect(2), forcedSelect(3) }
        MAX-ACCESS   read-only
        STATUS       current
        DESCRIPTION  "Main Board / Ctrl Card Timing Source Switch Status."
        ::= { clkCommonEntry 8 }

    clkRefTable OBJECT-TYPE
        SYNTAX       SEQUENCE OF ClkRefEntry
        MAX-ACCESS   not-accessible
        STATUS       current
        DESCRIPTION  "Represents Timing Source Status."
        ::= { asClkGroup 2 }

    clkRefEntry OBJECT-TYPE
        SYNTAX       ClkRefEntry
        MAX-ACCESS   not-accessible
        STATUS       current
        DESCRIPTION  ""
        INDEX        { clkRefIndex }
        ::= { clkRefTable 1 }

    ClkRefEntry ::= SEQUENCE {
        clkRefIndex        INTEGER,
        clkRefNEAddress    IpAddress,
        clkFailedAlarm     SeverityValue,
        clkDriftAlarm      SeverityValue,
        clkRefFailedAlarm  SeverityValue,
        refLockoutStatus   INTEGER,
        refQL              INTEGER
    }

    clkRefIndex OBJECT-TYPE
        SYNTAX       INTEGER { refclk1(1), refclk2(2), refclk3(3) }
        MAX-ACCESS   not-accessible
        STATUS       current
        DESCRIPTION  "Index of this table."
        ::= { clkRefEntry 1 }

    clkRefNEAddress OBJECT-TYPE
        SYNTAX       IpAddress
        MAX-ACCESS   not-accessible
        STATUS       current
        DESCRIPTION  "reserved."
        ::= { clkRefEntry 2 }

    clkFailedAlarm OBJECT-TYPE
        SYNTAX       SeverityValue
        MAX-ACCESS   read-only
        STATUS       current
        DESCRIPTION
            "Main Board / Ctrl Card CLK FAIL Alarm per CLK Reference."
        ::= { clkRefEntry 3 }

    clkDriftAlarm OBJECT-TYPE
        SYNTAX       SeverityValue
        MAX-ACCESS   read-only
        STATUS       current
        DESCRIPTION
            "Main Board / Ctrl Card CLK Drift Alarm per CLK Reference."
        ::= { clkRefEntry 4 }

    clkRefFailedAlarm OBJECT-TYPE
        SYNTAX       SeverityValue
        MAX-ACCESS   read-only
        STATUS       current
        DESCRIPTION
            "Main Board / Ctrl Card SSM FAIL Alarm per CLK Reference."
        ::= { clkRefEntry 5 }

    refLockoutStatus OBJECT-TYPE
        SYNTAX       INTEGER { lockout(1), normal(2) }
        MAX-ACCESS   read-only
        STATUS       current
        DESCRIPTION
            "Main Board / Ctrl Card Lockout Status per CLK Reference."
        ::= { clkRefEntry 6 }

    refQL OBJECT-TYPE
        SYNTAX       INTEGER {
                         qlPrc(1),
                         qlSsuA(2),
                         qlSsuB(3),
                         qlOriginal(4),
                         qlSec(5),
                         qlDnu(6),
                         qlInvx(7),
                         qlFailed(8),
                         notAvail(9)
                     }
        MAX-ACCESS   read-only
        STATUS       current
        DESCRIPTION
            "Main Board / Ctrl Card Quality level per CLK Reference."
        ::= { clkRefEntry 7 }

    asExtClkGroup OBJECT IDENTIFIER
        ::= { alarmStatusGroup 6 }

    extClkGroupTable OBJECT-TYPE
        SYNTAX       SEQUENCE OF ExtClkGroupEntry
        MAX-ACCESS   not-accessible
        STATUS       current
        DESCRIPTION  "Represents Ext CLK Alarm / Status."
        ::= { asExtClkGroup 1 }

    extClkGroupEntry OBJECT-TYPE
        SYNTAX       ExtClkGroupEntry
        MAX-ACCESS   not-accessible
        STATUS       current
        DESCRIPTION  ""
        INDEX        { extClkGroupIndex }
        ::= { extClkGroupTable 1 }

    ExtClkGroupEntry ::= SEQUENCE {
        extClkGroupIndex      INTEGER,
        extClkGroupNEAddress  IpAddress,
        clk2mLosAlarm         SeverityValue,
        aisAlarm              SeverityValue,
        lofAlarm              SeverityValue,
        clk2mUnequipped       SeverityValue,
        extClkOutputStatus    INTEGER,
        extClkOutputQlValue   INTEGER,
        squelch               INTEGER,
        clk2mTypeMismatch     SeverityValue
    }

    extClkGroupIndex OBJECT-TYPE
        SYNTAX       INTEGER { extclk(1), extclk2(2) }
        MAX-ACCESS   not-accessible
        STATUS       current
        DESCRIPTION  "Index of this table."
        ::= { extClkGroupEntry 1 }

    extClkGroupNEAddress OBJECT-TYPE
        SYNTAX       IpAddress
        MAX-ACCESS   not-accessible
        STATUS       current
        DESCRIPTION  "reserved."
        ::= { extClkGroupEntry 2 }

    clk2mLosAlarm OBJECT-TYPE
        SYNTAX       SeverityValue
        MAX-ACCESS   read-only
        STATUS       current
        DESCRIPTION  "Main Board / Ctrl Card EXT CLK LOS Alarm."
        ::= { extClkGroupEntry 3 }

    aisAlarm OBJECT-TYPE
        SYNTAX       SeverityValue
        MAX-ACCESS   read-only
        STATUS       current
        DESCRIPTION  "Main Board / Ctrl Card EXT CLK AIS Alarm."
        ::= { extClkGroupEntry 4 }

    lofAlarm OBJECT-TYPE
        SYNTAX       SeverityValue
        MAX-ACCESS   read-only
        STATUS       current
        DESCRIPTION  "Main Board / Ctrl Card EXT CLK LOF Alarm."
        ::= { extClkGroupEntry 5 }

    clk2mUnequipped OBJECT-TYPE
        SYNTAX       SeverityValue
        MAX-ACCESS   read-only
        STATUS       current
        DESCRIPTION  "Main Board / Ctrl Card EXT CLK Unequipped Alarm."
        ::= { extClkGroupEntry 6 }

    extClkOutputStatus OBJECT-TYPE
        SYNTAX       INTEGER { normal(1), ais(2), shutdown(3) }
        MAX-ACCESS   read-only
        STATUS       current
        DESCRIPTION  "Main Board / Ctrl Card EXT CLK Output Status."
        ::= { extClkGroupEntry 7 }

    extClkOutputQlValue OBJECT-TYPE
        SYNTAX       INTEGER {
                         qlPrc(1),
                         qlSsuA(2),
                         qlSsuB(3),
                         qlOriginal(4),
                         qlSec(5),
                         qlDnu(6),
                         qlInvx(7),
                         qlFailed(8),
                         notAvail(9)
                     }
        MAX-ACCESS   read-only
        STATUS       current
        DESCRIPTION  "Main Board / Ctrl Card EXT CLK Quality Level."
        ::= { extClkGroupEntry 8 }

    squelch OBJECT-TYPE
        SYNTAX       INTEGER { normal(1), squelch(2) }
        MAX-ACCESS   read-only
        STATUS       current
        DESCRIPTION  "Main Board / Ctrl Card EXT CLK Squelch Status."
        ::= { extClkGroupEntry 9 }

    clk2mTypeMismatch OBJECT-TYPE
        SYNTAX       SeverityValue
        MAX-ACCESS   read-only
        STATUS       current
        DESCRIPTION  "Main Board / Ctrl Card EXT CLK Type Mismatch Alarm."
        ::= { extClkGroupEntry 10 }

    asFanGroup OBJECT IDENTIFIER
        ::= { alarmStatusGroup 7 }

    fanGroupTable OBJECT-TYPE
        SYNTAX       SEQUENCE OF FanGroupEntry
        MAX-ACCESS   not-accessible
        STATUS       current
        DESCRIPTION  "Represents FAN Card Alarm / Status."
        ::= { asFanGroup 1 }

    fanGroupEntry OBJECT-TYPE
        SYNTAX       FanGroupEntry
        MAX-ACCESS   not-accessible
        STATUS       current
        DESCRIPTION  ""
        INDEX        { fanGroupIndex }
        ::= { fanGroupTable 1 }

    FanGroupEntry ::= SEQUENCE {
        fanGroupIndex      Integer32,
        fanGroupNEAddress  IpAddress,
        fanAlarm           SeverityValue,
        fanUnequipped      SeverityValue
    }

    fanGroupIndex OBJECT-TYPE
        SYNTAX       Integer32
        MAX-ACCESS   not-accessible
        STATUS       current
        DESCRIPTION  "Index of this table."
        ::= { fanGroupEntry 1 }

    fanGroupNEAddress OBJECT-TYPE
        SYNTAX       IpAddress
        MAX-ACCESS   not-accessible
        STATUS       current
        DESCRIPTION  "reserved."
        ::= { fanGroupEntry 2 }

    fanAlarm OBJECT-TYPE
        SYNTAX       SeverityValue
        MAX-ACCESS   read-only
        STATUS       current
        DESCRIPTION  "FAN FAIL Alarm."
        ::= { fanGroupEntry 3 }

    fanUnequipped OBJECT-TYPE
        SYNTAX       SeverityValue
        MAX-ACCESS   read-only
        STATUS       current
        DESCRIPTION  "FAN Unequipped Alarm."
        ::= { fanGroupEntry 4 }

    asPsGroup OBJECT IDENTIFIER
        ::= { alarmStatusGroup 8 }

    psGroupTable OBJECT-TYPE
        SYNTAX       SEQUENCE OF PsGroupEntry
        MAX-ACCESS   not-accessible
        STATUS       current
        DESCRIPTION
            "Represents Main Board / Ctrl Card Power Supply Alarm / Status."
        ::= { asPsGroup 1 }

    psGroupEntry OBJECT-TYPE
        SYNTAX       PsGroupEntry
        MAX-ACCESS   not-accessible
        STATUS       current
        DESCRIPTION  ""
        INDEX        { psGroupIndex }
        ::= { psGroupTable 1 }

    PsGroupEntry ::= SEQUENCE {
        psGroupIndex      Integer32,
        psGroupNEAddress  IpAddress,
        psPowerSupply     SeverityValue,
        psUnequipped      SeverityValue
    }

    psGroupIndex OBJECT-TYPE
        SYNTAX       Integer32
        MAX-ACCESS   not-accessible
        STATUS       current
        DESCRIPTION  "Index of this table."
        ::= { psGroupEntry 1 }

    psGroupNEAddress OBJECT-TYPE
        SYNTAX       IpAddress
        MAX-ACCESS   not-accessible
        STATUS       current
        DESCRIPTION  "reserved."
        ::= { psGroupEntry 2 }

    psPowerSupply OBJECT-TYPE
        SYNTAX       SeverityValue
        MAX-ACCESS   read-only
        STATUS       current
        DESCRIPTION  "Main Board / Ctrl Card Power Supply Alarm."
        ::= { psGroupEntry 3 }

    psUnequipped OBJECT-TYPE
        SYNTAX       SeverityValue
        MAX-ACCESS   read-only
        STATUS       current
        DESCRIPTION
            "Main Board / Ctrl Card Power Supply Unequipped Alarm."
        ::= { psGroupEntry 4 }

    asTCNGroup OBJECT IDENTIFIER
        ::= { alarmStatusGroup 9 }

    tcn15minDataRadioGroup OBJECT IDENTIFIER
        ::= { asTCNGroup 1 }

    tcn15minDataRadioTable OBJECT-TYPE
        SYNTAX       SEQUENCE OF Tcn15minDataRadioEntry
        MAX-ACCESS   not-accessible
        STATUS       current
        DESCRIPTION
            "Represents Threashold Crossing Alarm Status of 15 minutes PMON
            for Radio."
        ::= { tcn15minDataRadioGroup 1 }

    tcn15minDataRadioEntry OBJECT-TYPE
        SYNTAX       Tcn15minDataRadioEntry
        MAX-ACCESS   not-accessible
        STATUS       current
        DESCRIPTION  ""
        INDEX        { tcn15minDataModemIfIndex, tcn15minDataModemMonitorName }
        ::= { tcn15minDataRadioTable 1 }

    Tcn15minDataRadioEntry ::= SEQUENCE {
        tcn15minDataModemIfIndex      InterfaceIndex,
        tcn15minDataModemMonitorName  INTEGER,
        tcn15minDataRadioNEAddress    IpAddress,
        tcn15minDataRf                SeverityValue
    }

    tcn15minDataModemIfIndex OBJECT-TYPE
        SYNTAX       InterfaceIndex
        MAX-ACCESS   not-accessible
        STATUS       current
        DESCRIPTION  "Index of this table."
        ::= { tcn15minDataRadioEntry 1 }

    tcn15minDataModemMonitorName OBJECT-TYPE
        SYNTAX       INTEGER { bbe(1), es(2), ses(3), sep(4), uas(5), ofs(6) }
        MAX-ACCESS   not-accessible
        STATUS       current
        DESCRIPTION
            "Index of this table. The index value shows counting item."
        ::= { tcn15minDataRadioEntry 2 }

    tcn15minDataRadioNEAddress OBJECT-TYPE
        SYNTAX       IpAddress
        MAX-ACCESS   not-accessible
        STATUS       current
        DESCRIPTION  "reserved."
        ::= { tcn15minDataRadioEntry 3 }

    tcn15minDataRf OBJECT-TYPE
        SYNTAX       SeverityValue
        MAX-ACCESS   read-only
        STATUS       current
        DESCRIPTION
            "TCN MODEM 15 minutes RF Monitoring Alarm per counting item."
        ::= { tcn15minDataRadioEntry 4 }

    tcn15minRxLevTable OBJECT-TYPE
        SYNTAX       SEQUENCE OF Tcn15minRxLevEntry
        MAX-ACCESS   not-accessible
        STATUS       current
        DESCRIPTION
            "Represents Threshold Crossing Alarm Status of 15 minutes Rx
            Level Alarm."
        ::= { tcn15minDataRadioGroup 2 }

    tcn15minRxLevEntry OBJECT-TYPE
        SYNTAX       Tcn15minRxLevEntry
        MAX-ACCESS   not-accessible
        STATUS       current
        DESCRIPTION  ""
        INDEX        { tcn15minRxLevIfIndex }
        ::= { tcn15minRxLevTable 1 }

    Tcn15minRxLevEntry ::= SEQUENCE {
        tcn15minRxLevIfIndex    InterfaceIndex,
        tcn15minRxLevNEAddress  IpAddress,
        tcn15minRxLev           SeverityValue
    }

    tcn15minRxLevIfIndex OBJECT-TYPE
        SYNTAX       InterfaceIndex
        MAX-ACCESS   not-accessible
        STATUS       current
        DESCRIPTION  "Index of this table."
        ::= { tcn15minRxLevEntry 1 }

    tcn15minRxLevNEAddress OBJECT-TYPE
        SYNTAX       IpAddress
        MAX-ACCESS   not-accessible
        STATUS       current
        DESCRIPTION  "reserved."
        ::= { tcn15minRxLevEntry 2 }

    tcn15minRxLev OBJECT-TYPE
        SYNTAX       SeverityValue
        MAX-ACCESS   read-only
        STATUS       current
        DESCRIPTION  "TCN MODEM 15 minutes RX Level (Min) Alarm."
        ::= { tcn15minRxLevEntry 3 }

    tcn15minDataCableGroup OBJECT IDENTIFIER
        ::= { asTCNGroup 2 }

    tcn15minDataThroughModeGroup OBJECT IDENTIFIER
        ::= { tcn15minDataCableGroup 1 }

    tcn15minDataTmRsTable OBJECT-TYPE
        SYNTAX       SEQUENCE OF Tcn15minDataTmRsEntry
        MAX-ACCESS   not-accessible
        STATUS       current
        DESCRIPTION
            "Represents Threshold Crossing Alarm of 15 minutes PMON for RS
            Layer of through mode STM-1."
        ::= { tcn15minDataThroughModeGroup 1 }

    tcn15minDataTmRsEntry OBJECT-TYPE
        SYNTAX       Tcn15minDataTmRsEntry
        MAX-ACCESS   not-accessible
        STATUS       current
        DESCRIPTION  ""
        INDEX        { tcn15minDataTmRsIfIndex, tcn15minDataTmRsMonitorName }
        ::= { tcn15minDataTmRsTable 1 }

    Tcn15minDataTmRsEntry ::= SEQUENCE {
        tcn15minDataTmRsIfIndex      InterfaceIndex,
        tcn15minDataTmRsMonitorName  INTEGER,
        tcn15minDataTmRsNEAddress    IpAddress,
        tcn15minDataTmRs             SeverityValue
    }

    tcn15minDataTmRsIfIndex OBJECT-TYPE
        SYNTAX       InterfaceIndex
        MAX-ACCESS   not-accessible
        STATUS       current
        DESCRIPTION  "Index of this table."
        ::= { tcn15minDataTmRsEntry 1 }

    tcn15minDataTmRsMonitorName OBJECT-TYPE
        SYNTAX       INTEGER { bbe(1), es(2), ses(3), sep(4), uas(5), ofs(6) }
        MAX-ACCESS   not-accessible
        STATUS       current
        DESCRIPTION
            "Index of this table. The index value shows counting item."
        ::= { tcn15minDataTmRsEntry 2 }

    tcn15minDataTmRsNEAddress OBJECT-TYPE
        SYNTAX       IpAddress
        MAX-ACCESS   not-accessible
        STATUS       current
        DESCRIPTION  "reserved."
        ::= { tcn15minDataTmRsEntry 3 }

    tcn15minDataTmRs OBJECT-TYPE
        SYNTAX       SeverityValue
        MAX-ACCESS   read-only
        STATUS       current
        DESCRIPTION
            "TCN STM-1 15 minutes (Through Mode) RS Monitoring Alarm."
        ::= { tcn15minDataTmRsEntry 4 }

    tcn15minDataTmDMRRsTable OBJECT-TYPE
        SYNTAX       SEQUENCE OF Tcn15minDataTmDMRRsEntry
        MAX-ACCESS   not-accessible
        STATUS       current
        DESCRIPTION
            "Represents Threshold Crossing Alarm of 15 minutes PMON for DMR
            RS Layer of STM-1"
        ::= { tcn15minDataThroughModeGroup 2 }

    tcn15minDataTmDMRRsEntry OBJECT-TYPE
        SYNTAX       Tcn15minDataTmDMRRsEntry
        MAX-ACCESS   not-accessible
        STATUS       current
        DESCRIPTION  ""
        INDEX        {
                         tcn15minDataTmDMRRsIfIndex,
                         tcn15minDataTmDMRRsMonitorName
                     }
        ::= { tcn15minDataTmDMRRsTable 1 }

    Tcn15minDataTmDMRRsEntry ::= SEQUENCE {
        tcn15minDataTmDMRRsIfIndex      InterfaceIndex,
        tcn15minDataTmDMRRsMonitorName  INTEGER,
        tcn15minDataTmDMRRsNEAddress    IpAddress,
        tcn15minDataTmDMRRs             SeverityValue
    }

    tcn15minDataTmDMRRsIfIndex OBJECT-TYPE
        SYNTAX       InterfaceIndex
        MAX-ACCESS   not-accessible
        STATUS       current
        DESCRIPTION  "Index of this table."
        ::= { tcn15minDataTmDMRRsEntry 1 }

    tcn15minDataTmDMRRsMonitorName OBJECT-TYPE
        SYNTAX       INTEGER { bbe(1), es(2), ses(3), sep(4), uas(5), ofs(6) }
        MAX-ACCESS   not-accessible
        STATUS       current
        DESCRIPTION
            "Index of this table. The index value shows counting item."
        ::= { tcn15minDataTmDMRRsEntry 2 }

    tcn15minDataTmDMRRsNEAddress OBJECT-TYPE
        SYNTAX       IpAddress
        MAX-ACCESS   not-accessible
        STATUS       current
        DESCRIPTION  "reserved."
        ::= { tcn15minDataTmDMRRsEntry 3 }

    tcn15minDataTmDMRRs OBJECT-TYPE
        SYNTAX       SeverityValue
        MAX-ACCESS   read-only
        STATUS       current
        DESCRIPTION
            "TCN STM-1 15 minutes (Through Mode)DMR RS Monitoring Alarm."
        ::= { tcn15minDataTmDMRRsEntry 4 }

    tcn15minDataChannelizedModeGroup OBJECT IDENTIFIER
        ::= { tcn15minDataCableGroup 2 }

    tcn15minDataChRsTable OBJECT-TYPE
        SYNTAX       SEQUENCE OF Tcn15minDataChRsEntry
        MAX-ACCESS   not-accessible
        STATUS       current
        DESCRIPTION
            "Represents Threshold Crossing Alarm of 15 minutes PMON for
            Channelized Mode RS Layer of STM-1."
        ::= { tcn15minDataChannelizedModeGroup 1 }

    tcn15minDataChRsEntry OBJECT-TYPE
        SYNTAX       Tcn15minDataChRsEntry
        MAX-ACCESS   not-accessible
        STATUS       current
        DESCRIPTION  ""
        INDEX        { tcn15minDataChRsIfIndex, tcn15minDataChRsMonitorName }
        ::= { tcn15minDataChRsTable 1 }

    Tcn15minDataChRsEntry ::= SEQUENCE {
        tcn15minDataChRsIfIndex      InterfaceIndex,
        tcn15minDataChRsMonitorName  INTEGER,
        tcn15minDataChRsNEAddress    IpAddress,
        tcn15minDataChRs             SeverityValue
    }

    tcn15minDataChRsIfIndex OBJECT-TYPE
        SYNTAX       InterfaceIndex
        MAX-ACCESS   not-accessible
        STATUS       current
        DESCRIPTION  "Index of this table."
        ::= { tcn15minDataChRsEntry 1 }

    tcn15minDataChRsMonitorName OBJECT-TYPE
        SYNTAX       INTEGER { bbe(1), es(2), ses(3), sep(4), uas(5), ofs(6) }
        MAX-ACCESS   not-accessible
        STATUS       current
        DESCRIPTION
            "Index of this table. The index value shows counting item."
        ::= { tcn15minDataChRsEntry 2 }

    tcn15minDataChRsNEAddress OBJECT-TYPE
        SYNTAX       IpAddress
        MAX-ACCESS   not-accessible
        STATUS       current
        DESCRIPTION  "reserved."
        ::= { tcn15minDataChRsEntry 3 }

    tcn15minDataChRs OBJECT-TYPE
        SYNTAX       SeverityValue
        MAX-ACCESS   read-only
        STATUS       current
        DESCRIPTION
            "TCN STM-1 15 minutes (Channelized Mode) RS Monitoring Alarm per
            counting item."
        ::= { tcn15minDataChRsEntry 4 }

    tcn15minDataChMsTable OBJECT-TYPE
        SYNTAX       SEQUENCE OF Tcn15minDataChMsEntry
        MAX-ACCESS   not-accessible
        STATUS       current
        DESCRIPTION
            "Represents Threshold Crossing Alarm of 15 minutes PMON for
            Channelized Mode MS Layer of STM-1."
        ::= { tcn15minDataChannelizedModeGroup 2 }

    tcn15minDataChMsEntry OBJECT-TYPE
        SYNTAX       Tcn15minDataChMsEntry
        MAX-ACCESS   not-accessible
        STATUS       current
        DESCRIPTION  ""
        INDEX        { tcn15minDataChMsIfIndex, tcn15minDataChMsMonitorName }
        ::= { tcn15minDataChMsTable 1 }

    Tcn15minDataChMsEntry ::= SEQUENCE {
        tcn15minDataChMsIfIndex      InterfaceIndex,
        tcn15minDataChMsMonitorName  INTEGER,
        tcn15minDataChMsNEAddress    IpAddress,
        tcn15minDataChMs             SeverityValue
    }

    tcn15minDataChMsIfIndex OBJECT-TYPE
        SYNTAX       InterfaceIndex
        MAX-ACCESS   not-accessible
        STATUS       current
        DESCRIPTION  "Index of this table."
        ::= { tcn15minDataChMsEntry 1 }

    tcn15minDataChMsMonitorName OBJECT-TYPE
        SYNTAX       INTEGER { bbe(1), es(2), ses(3), sep(4), uas(5) }
        MAX-ACCESS   not-accessible
        STATUS       current
        DESCRIPTION
            "Index of this table. The index value shows counting item."
        ::= { tcn15minDataChMsEntry 2 }

    tcn15minDataChMsNEAddress OBJECT-TYPE
        SYNTAX       IpAddress
        MAX-ACCESS   not-accessible
        STATUS       current
        DESCRIPTION  "reserved."
        ::= { tcn15minDataChMsEntry 3 }

    tcn15minDataChMs OBJECT-TYPE
        SYNTAX       SeverityValue
        MAX-ACCESS   read-only
        STATUS       current
        DESCRIPTION
            "TCN STM-1 15 minutes (Channelized Mode) MS Monitoring Alarm."
        ::= { tcn15minDataChMsEntry 4 }

    tcn15minData16E1Group OBJECT IDENTIFIER
        ::= { tcn15minDataCableGroup 3 }

    tcn15minData16E1PdhTable OBJECT-TYPE
        SYNTAX       SEQUENCE OF Tcn15minData16E1PdhEntry
        MAX-ACCESS   not-accessible
        STATUS       current
        DESCRIPTION
            "Represents Threshold Crossing Alarm of 15 minutes PMON for E1
            Channel."
        ::= { tcn15minData16E1Group 1 }

    tcn15minData16E1PdhEntry OBJECT-TYPE
        SYNTAX       Tcn15minData16E1PdhEntry
        MAX-ACCESS   not-accessible
        STATUS       current
        DESCRIPTION  ""
        INDEX        {
                         tcn15minData16E1PdhIfIndex,
                         tcn15minData16E1PdhMonitorName
                     }
        ::= { tcn15minData16E1PdhTable 1 }

    Tcn15minData16E1PdhEntry ::= SEQUENCE {
        tcn15minData16E1PdhIfIndex      InterfaceIndex,
        tcn15minData16E1PdhMonitorName  INTEGER,
        tcn15minData16E1PdhNEAddress    IpAddress,
        tcn15minData16E1Pdh             SeverityValue
    }

    tcn15minData16E1PdhIfIndex OBJECT-TYPE
        SYNTAX       InterfaceIndex
        MAX-ACCESS   not-accessible
        STATUS       current
        DESCRIPTION  "Index of this table."
        ::= { tcn15minData16E1PdhEntry 1 }

    tcn15minData16E1PdhMonitorName OBJECT-TYPE
        SYNTAX       INTEGER { cv(1) }
        MAX-ACCESS   not-accessible
        STATUS       current
        DESCRIPTION
            "Index of this table. The index value shows counting item."
        ::= { tcn15minData16E1PdhEntry 2 }

    tcn15minData16E1PdhNEAddress OBJECT-TYPE
        SYNTAX       IpAddress
        MAX-ACCESS   not-accessible
        STATUS       current
        DESCRIPTION  "reserved."
        ::= { tcn15minData16E1PdhEntry 3 }

    tcn15minData16E1Pdh OBJECT-TYPE
        SYNTAX       SeverityValue
        MAX-ACCESS   read-only
        STATUS       current
        DESCRIPTION  "TCN 15 minutes E1 CV Alarm."
        ::= { tcn15minData16E1PdhEntry 4 }

    tcn1dayDataRadioGroup OBJECT IDENTIFIER
        ::= { asTCNGroup 3 }

    tcn1dayDataRadioTable OBJECT-TYPE
        SYNTAX       SEQUENCE OF Tcn1dayDataRadioEntry
        MAX-ACCESS   not-accessible
        STATUS       current
        DESCRIPTION
            "Represents Threashold Crossing Alarm Status of 1 day PMON for
            Radio."
        ::= { tcn1dayDataRadioGroup 1 }

    tcn1dayDataRadioEntry OBJECT-TYPE
        SYNTAX       Tcn1dayDataRadioEntry
        MAX-ACCESS   not-accessible
        STATUS       current
        DESCRIPTION  ""
        INDEX        { tcn1dayDataModemIfIndex, tcn1dayDataModemMonitorName }
        ::= { tcn1dayDataRadioTable 1 }

    Tcn1dayDataRadioEntry ::= SEQUENCE {
        tcn1dayDataModemIfIndex      InterfaceIndex,
        tcn1dayDataModemMonitorName  INTEGER,
        tcn1dayDataRadioNEAddress    IpAddress,
        tcn1dayDataRf                SeverityValue
    }

    tcn1dayDataModemIfIndex OBJECT-TYPE
        SYNTAX       InterfaceIndex
        MAX-ACCESS   not-accessible
        STATUS       current
        DESCRIPTION  "Index of this table."
        ::= { tcn1dayDataRadioEntry 1 }

    tcn1dayDataModemMonitorName OBJECT-TYPE
        SYNTAX       INTEGER { bbe(1), es(2), ses(3), sep(4), uas(5), ofs(6) }
        MAX-ACCESS   not-accessible
        STATUS       current
        DESCRIPTION
            "Index of this table. The index value shows counting item."
        ::= { tcn1dayDataRadioEntry 2 }

    tcn1dayDataRadioNEAddress OBJECT-TYPE
        SYNTAX       IpAddress
        MAX-ACCESS   not-accessible
        STATUS       current
        DESCRIPTION  "reserved."
        ::= { tcn1dayDataRadioEntry 3 }

    tcn1dayDataRf OBJECT-TYPE
        SYNTAX       SeverityValue
        MAX-ACCESS   read-only
        STATUS       current
        DESCRIPTION
            "TCN MODEM 1 day RF Monitoring Alarm per counting item."
        ::= { tcn1dayDataRadioEntry 4 }

    tcn1dayRxLevTable OBJECT-TYPE
        SYNTAX       SEQUENCE OF Tcn1dayRxLevEntry
        MAX-ACCESS   not-accessible
        STATUS       current
        DESCRIPTION
            "Represents Threshold Crossing Alarm Status of 1 day Rx Level
            Alarm."
        ::= { tcn1dayDataRadioGroup 2 }

    tcn1dayRxLevEntry OBJECT-TYPE
        SYNTAX       Tcn1dayRxLevEntry
        MAX-ACCESS   not-accessible
        STATUS       current
        DESCRIPTION  ""
        INDEX        { tcn1dayRxLevIfIndex }
        ::= { tcn1dayRxLevTable 1 }

    Tcn1dayRxLevEntry ::= SEQUENCE {
        tcn1dayRxLevIfIndex    InterfaceIndex,
        tcn1dayRxLevNEAddress  IpAddress,
        tcn1dayRxLev           SeverityValue
    }

    tcn1dayRxLevIfIndex OBJECT-TYPE
        SYNTAX       InterfaceIndex
        MAX-ACCESS   not-accessible
        STATUS       current
        DESCRIPTION  "Index of this table."
        ::= { tcn1dayRxLevEntry 1 }

    tcn1dayRxLevNEAddress OBJECT-TYPE
        SYNTAX       IpAddress
        MAX-ACCESS   not-accessible
        STATUS       current
        DESCRIPTION  "reserved."
        ::= { tcn1dayRxLevEntry 2 }

    tcn1dayRxLev OBJECT-TYPE
        SYNTAX       SeverityValue
        MAX-ACCESS   read-only
        STATUS       current
        DESCRIPTION  "TCN MODEM 1 day RX Level (Min) Alarm."
        ::= { tcn1dayRxLevEntry 3 }

    tcn1dayDataCableGroup OBJECT IDENTIFIER
        ::= { asTCNGroup 4 }

    tcn1dayDataThroughModeGroup OBJECT IDENTIFIER
        ::= { tcn1dayDataCableGroup 1 }

    tcn1dayDataTmRsTable OBJECT-TYPE
        SYNTAX       SEQUENCE OF Tcn1dayDataTmRsEntry
        MAX-ACCESS   not-accessible
        STATUS       current
        DESCRIPTION
            "Represents Threshold Crossing Alarm of 1 day PMON for RS Layer
            of through mode STM-1."
        ::= { tcn1dayDataThroughModeGroup 1 }

    tcn1dayDataTmRsEntry OBJECT-TYPE
        SYNTAX       Tcn1dayDataTmRsEntry
        MAX-ACCESS   not-accessible
        STATUS       current
        DESCRIPTION  ""
        INDEX        { tcn1dayDataTmRsIfIndex, tcn1dayDataTmRsMonitorName }
        ::= { tcn1dayDataTmRsTable 1 }

    Tcn1dayDataTmRsEntry ::= SEQUENCE {
        tcn1dayDataTmRsIfIndex      InterfaceIndex,
        tcn1dayDataTmRsMonitorName  INTEGER,
        tcn1dayDataTmRsNEAddress    IpAddress,
        tcn1dayDataTmRs             SeverityValue
    }

    tcn1dayDataTmRsIfIndex OBJECT-TYPE
        SYNTAX       InterfaceIndex
        MAX-ACCESS   not-accessible
        STATUS       current
        DESCRIPTION  "Index of this table."
        ::= { tcn1dayDataTmRsEntry 1 }

    tcn1dayDataTmRsMonitorName OBJECT-TYPE
        SYNTAX       INTEGER { bbe(1), es(2), ses(3), sep(4), uas(5), ofs(6) }
        MAX-ACCESS   not-accessible
        STATUS       current
        DESCRIPTION
            "Index of this table. The index value shows counting item."
        ::= { tcn1dayDataTmRsEntry 2 }

    tcn1dayDataTmRsNEAddress OBJECT-TYPE
        SYNTAX       IpAddress
        MAX-ACCESS   not-accessible
        STATUS       current
        DESCRIPTION  "reserved."
        ::= { tcn1dayDataTmRsEntry 3 }

    tcn1dayDataTmRs OBJECT-TYPE
        SYNTAX       SeverityValue
        MAX-ACCESS   read-only
        STATUS       current
        DESCRIPTION  "TCN STM-1 1 day (Through Mode) RS Monitoring Alarm."
        ::= { tcn1dayDataTmRsEntry 4 }

    tcn1dayDataTmDMRRsTable OBJECT-TYPE
        SYNTAX       SEQUENCE OF Tcn1dayDataTmDMRRsEntry
        MAX-ACCESS   not-accessible
        STATUS       current
        DESCRIPTION
            "Represents Threshold Crossing Alarm of 1 day PMON for DMR RS
            Layer of STM-1"
        ::= { tcn1dayDataThroughModeGroup 2 }

    tcn1dayDataTmDMRRsEntry OBJECT-TYPE
        SYNTAX       Tcn1dayDataTmDMRRsEntry
        MAX-ACCESS   not-accessible
        STATUS       current
        DESCRIPTION  ""
        INDEX        {
                         tcn1dayDataTmDMRRsIfIndex,
                         tcn1dayDataTmDMRRsMonitorName
                     }
        ::= { tcn1dayDataTmDMRRsTable 1 }

    Tcn1dayDataTmDMRRsEntry ::= SEQUENCE {
        tcn1dayDataTmDMRRsIfIndex      InterfaceIndex,
        tcn1dayDataTmDMRRsMonitorName  INTEGER,
        tcn1dayDataTmDMRRsNEAddress    IpAddress,
        tcn1dayDataTmDMRRs             SeverityValue
    }

    tcn1dayDataTmDMRRsIfIndex OBJECT-TYPE
        SYNTAX       InterfaceIndex
        MAX-ACCESS   not-accessible
        STATUS       current
        DESCRIPTION  "Index of this table."
        ::= { tcn1dayDataTmDMRRsEntry 1 }

    tcn1dayDataTmDMRRsMonitorName OBJECT-TYPE
        SYNTAX       INTEGER { bbe(1), es(2), ses(3), sep(4), uas(5), ofs(6) }
        MAX-ACCESS   not-accessible
        STATUS       current
        DESCRIPTION
            "Index of this table. The index value shows counting item."
        ::= { tcn1dayDataTmDMRRsEntry 2 }

    tcn1dayDataTmDMRRsNEAddress OBJECT-TYPE
        SYNTAX       IpAddress
        MAX-ACCESS   not-accessible
        STATUS       current
        DESCRIPTION  "reserved."
        ::= { tcn1dayDataTmDMRRsEntry 3 }

    tcn1dayDataTmDMRRs OBJECT-TYPE
        SYNTAX       SeverityValue
        MAX-ACCESS   read-only
        STATUS       current
        DESCRIPTION
            "TCN STM-1 1 day (Through Mode)DMR RS Monitoring Alarm."
        ::= { tcn1dayDataTmDMRRsEntry 4 }

    tcn1dayDataChannelizedModeGroup OBJECT IDENTIFIER
        ::= { tcn1dayDataCableGroup 2 }

    tcn1dayDataChRsTable OBJECT-TYPE
        SYNTAX       SEQUENCE OF Tcn1dayDataChRsEntry
        MAX-ACCESS   not-accessible
        STATUS       current
        DESCRIPTION
            "Represents Threshold Crossing Alarm of 1 day PMON for
            Channelized Mode RS Layer of STM-1."
        ::= { tcn1dayDataChannelizedModeGroup 1 }

    tcn1dayDataChRsEntry OBJECT-TYPE
        SYNTAX       Tcn1dayDataChRsEntry
        MAX-ACCESS   not-accessible
        STATUS       current
        DESCRIPTION  ""
        INDEX        { tcn1dayDataChRsIfIndex, tcn1dayDataChRsMonitorName }
        ::= { tcn1dayDataChRsTable 1 }

    Tcn1dayDataChRsEntry ::= SEQUENCE {
        tcn1dayDataChRsIfIndex      InterfaceIndex,
        tcn1dayDataChRsMonitorName  INTEGER,
        tcn1dayDataChRsNEAddress    IpAddress,
        tcn1dayDataChRs             SeverityValue
    }

    tcn1dayDataChRsIfIndex OBJECT-TYPE
        SYNTAX       InterfaceIndex
        MAX-ACCESS   not-accessible
        STATUS       current
        DESCRIPTION  "Index of this table."
        ::= { tcn1dayDataChRsEntry 1 }

    tcn1dayDataChRsMonitorName OBJECT-TYPE
        SYNTAX       INTEGER { bbe(1), es(2), ses(3), sep(4), uas(5), ofs(6) }
        MAX-ACCESS   not-accessible
        STATUS       current
        DESCRIPTION
            "Index of this table. The index value shows counting item."
        ::= { tcn1dayDataChRsEntry 2 }

    tcn1dayDataChRsNEAddress OBJECT-TYPE
        SYNTAX       IpAddress
        MAX-ACCESS   not-accessible
        STATUS       current
        DESCRIPTION  "reserved."
        ::= { tcn1dayDataChRsEntry 3 }

    tcn1dayDataChRs OBJECT-TYPE
        SYNTAX       SeverityValue
        MAX-ACCESS   read-only
        STATUS       current
        DESCRIPTION
            "TCN STM-1 1 day (Channelized Mode) RS Monitoring Alarm per
            counting item."
        ::= { tcn1dayDataChRsEntry 4 }

    tcn1dayDataChMsTable OBJECT-TYPE
        SYNTAX       SEQUENCE OF Tcn1dayDataChMsEntry
        MAX-ACCESS   not-accessible
        STATUS       current
        DESCRIPTION
            "Represents Threshold Crossing Alarm of 1 day PMON for
            Channelized Mode MS Layer of STM-1."
        ::= { tcn1dayDataChannelizedModeGroup 2 }

    tcn1dayDataChMsEntry OBJECT-TYPE
        SYNTAX       Tcn1dayDataChMsEntry
        MAX-ACCESS   not-accessible
        STATUS       current
        DESCRIPTION  ""
        INDEX        { tcn1dayDataChMsIfIndex, tcn1dayDataChMsMonitorName }
        ::= { tcn1dayDataChMsTable 1 }

    Tcn1dayDataChMsEntry ::= SEQUENCE {
        tcn1dayDataChMsIfIndex      InterfaceIndex,
        tcn1dayDataChMsMonitorName  INTEGER,
        tcn1dayDataChMsNEAddress    IpAddress,
        tcn1dayDataChMs             SeverityValue
    }

    tcn1dayDataChMsIfIndex OBJECT-TYPE
        SYNTAX       InterfaceIndex
        MAX-ACCESS   not-accessible
        STATUS       current
        DESCRIPTION  "Index of this table."
        ::= { tcn1dayDataChMsEntry 1 }

    tcn1dayDataChMsMonitorName OBJECT-TYPE
        SYNTAX       INTEGER { bbe(1), es(2), ses(3), sep(4), uas(5) }
        MAX-ACCESS   not-accessible
        STATUS       current
        DESCRIPTION
            "Index of this table. The index value shows counting item."
        ::= { tcn1dayDataChMsEntry 2 }

    tcn1dayDataChMsNEAddress OBJECT-TYPE
        SYNTAX       IpAddress
        MAX-ACCESS   not-accessible
        STATUS       current
        DESCRIPTION  "reserved."
        ::= { tcn1dayDataChMsEntry 3 }

    tcn1dayDataChMs OBJECT-TYPE
        SYNTAX       SeverityValue
        MAX-ACCESS   read-only
        STATUS       current
        DESCRIPTION
            "TCN STM-1 1 day (Channelized Mode) MS Monitoring Alarm."
        ::= { tcn1dayDataChMsEntry 4 }

    tcn1dayData16E1Group OBJECT IDENTIFIER
        ::= { tcn1dayDataCableGroup 3 }

    tcn1dayData16E1PdhTable OBJECT-TYPE
        SYNTAX       SEQUENCE OF Tcn1dayData16E1PdhEntry
        MAX-ACCESS   not-accessible
        STATUS       current
        DESCRIPTION
            "Represents Threshold Crossing Alarm of 1 day PMON for E1
            Channel."
        ::= { tcn1dayData16E1Group 1 }

    tcn1dayData16E1PdhEntry OBJECT-TYPE
        SYNTAX       Tcn1dayData16E1PdhEntry
        MAX-ACCESS   not-accessible
        STATUS       current
        DESCRIPTION  ""
        INDEX        {
                         tcn1dayData16E1PdhIfIndex,
                         tcn1dayData16E1PdhMonitorName
                     }
        ::= { tcn1dayData16E1PdhTable 1 }

    Tcn1dayData16E1PdhEntry ::= SEQUENCE {
        tcn1dayData16E1PdhIfIndex      InterfaceIndex,
        tcn1dayData16E1PdhMonitorName  INTEGER,
        tcn1dayData16E1PdhNEAddress    IpAddress,
        tcn1dayData16E1Pdh             SeverityValue
    }

    tcn1dayData16E1PdhIfIndex OBJECT-TYPE
        SYNTAX       InterfaceIndex
        MAX-ACCESS   not-accessible
        STATUS       current
        DESCRIPTION  "Index of this table."
        ::= { tcn1dayData16E1PdhEntry 1 }

    tcn1dayData16E1PdhMonitorName OBJECT-TYPE
        SYNTAX       INTEGER { cv(1) }
        MAX-ACCESS   not-accessible
        STATUS       current
        DESCRIPTION
            "Index of this table. The index value shows counting item."
        ::= { tcn1dayData16E1PdhEntry 2 }

    tcn1dayData16E1PdhNEAddress OBJECT-TYPE
        SYNTAX       IpAddress
        MAX-ACCESS   not-accessible
        STATUS       current
        DESCRIPTION  "reserved."
        ::= { tcn1dayData16E1PdhEntry 3 }

    tcn1dayData16E1Pdh OBJECT-TYPE
        SYNTAX       SeverityValue
        MAX-ACCESS   read-only
        STATUS       current
        DESCRIPTION  "TCN 1 day E1 CV Alarm."
        ::= { tcn1dayData16E1PdhEntry 4 }

    tcn15minDataRmonGroup OBJECT IDENTIFIER
        ::= { asTCNGroup 5 }

    tcn15minDataRmonTable OBJECT-TYPE
        SYNTAX       SEQUENCE OF Tcn15minDataRmonEntry
        MAX-ACCESS   not-accessible
        STATUS       current
        DESCRIPTION
            "Represents Threshold Crossing Alarm of 15 minutes RMON for
            Ethernet Port."
        ::= { tcn15minDataRmonGroup 1 }

    tcn15minDataRmonEntry OBJECT-TYPE
        SYNTAX       Tcn15minDataRmonEntry
        MAX-ACCESS   not-accessible
        STATUS       current
        DESCRIPTION  ""
        INDEX        { tcn15minRmonIfIndex }
        ::= { tcn15minDataRmonTable 1 }

    Tcn15minDataRmonEntry ::= SEQUENCE {
        tcn15minRmonIfIndex                 InterfaceIndex,
        tcn15minRmonNEAddress               IpAddress,
        tcn15minHCRxEthStatsDropEvents      SeverityValue,
        tcn15minHCRxEthStatsUndersizePkts   SeverityValue,
        tcn15minHCRxEthStatsFragments       SeverityValue,
        tcn15minHCRxEthStatsCRCAlignErrors  SeverityValue,
        tcn15minHCRxEthStatsOversizePkts    SeverityValue,
        tcn15minHCTxEthStatsCollisions      SeverityValue
    }

    tcn15minRmonIfIndex OBJECT-TYPE
        SYNTAX       InterfaceIndex
        MAX-ACCESS   not-accessible
        STATUS       current
        DESCRIPTION  "Index of this table."
        ::= { tcn15minDataRmonEntry 1 }

    tcn15minRmonNEAddress OBJECT-TYPE
        SYNTAX       IpAddress
        MAX-ACCESS   not-accessible
        STATUS       current
        DESCRIPTION  "reserved."
        ::= { tcn15minDataRmonEntry 2 }

    tcn15minHCRxEthStatsDropEvents OBJECT-TYPE
        SYNTAX       SeverityValue
        MAX-ACCESS   read-only
        STATUS       current
        DESCRIPTION
            "RMON(Ethernet Port) TCN 15 minutes RX Drop Events Alarm"
        ::= { tcn15minDataRmonEntry 3 }

    tcn15minHCRxEthStatsUndersizePkts OBJECT-TYPE
        SYNTAX       SeverityValue
        MAX-ACCESS   read-only
        STATUS       current
        DESCRIPTION
            "RMON(Ethernet Port) TCN 15 minutes RX Undersize Packets Alarm."
        ::= { tcn15minDataRmonEntry 4 }

    tcn15minHCRxEthStatsFragments OBJECT-TYPE
        SYNTAX       SeverityValue
        MAX-ACCESS   read-only
        STATUS       current
        DESCRIPTION
            "RMON(Ethernet Port) TCN 15 minutes RX Fragments Alarm."
        ::= { tcn15minDataRmonEntry 5 }

    tcn15minHCRxEthStatsCRCAlignErrors OBJECT-TYPE
        SYNTAX       SeverityValue
        MAX-ACCESS   read-only
        STATUS       current
        DESCRIPTION
            "RMON(Ethernet Port) TCN 15 minutes RX CRC Alignment Errors
            Alarm."
        ::= { tcn15minDataRmonEntry 6 }

    tcn15minHCRxEthStatsOversizePkts OBJECT-TYPE
        SYNTAX       SeverityValue
        MAX-ACCESS   read-only
        STATUS       current
        DESCRIPTION
            "RMON(Ethernet Port) TCN 15 minutes RX Oversize Packets Alarm."
        ::= { tcn15minDataRmonEntry 7 }

    tcn15minHCTxEthStatsCollisions OBJECT-TYPE
        SYNTAX       SeverityValue
        MAX-ACCESS   read-only
        STATUS       current
        DESCRIPTION
            "RMON(Ethernet Port) TCN 15 minutes TX Collisions Alarm."
        ::= { tcn15minDataRmonEntry 8 }

    tcn1dayDataRmonGroup OBJECT IDENTIFIER
        ::= { asTCNGroup 6 }

    tcn1dayDataRmonTable OBJECT-TYPE
        SYNTAX       SEQUENCE OF Tcn1dayDataRmonEntry
        MAX-ACCESS   not-accessible
        STATUS       current
        DESCRIPTION
            "Represents Threshold Crossing Alarm of 1 day RMON for Ethernet
            Port"
        ::= { tcn1dayDataRmonGroup 1 }

    tcn1dayDataRmonEntry OBJECT-TYPE
        SYNTAX       Tcn1dayDataRmonEntry
        MAX-ACCESS   not-accessible
        STATUS       current
        DESCRIPTION  ""
        INDEX        { tcn1dayRmonIfIndex }
        ::= { tcn1dayDataRmonTable 1 }

    Tcn1dayDataRmonEntry ::= SEQUENCE {
        tcn1dayRmonIfIndex                 InterfaceIndex,
        tcn1dayRmonNEAddress               IpAddress,
        tcn1dayHCRxEthStatsDropEvents      SeverityValue,
        tcn1dayHCRxEthStatsUndersizePkts   SeverityValue,
        tcn1dayHCRxEthStatsFragments       SeverityValue,
        tcn1dayHCRxEthStatsCRCAlignErrors  SeverityValue,
        tcn1dayHCRxEthStatsOversizePkts    SeverityValue,
        tcn1dayHCTxEthStatsCollisions      SeverityValue
    }

    tcn1dayRmonIfIndex OBJECT-TYPE
        SYNTAX       InterfaceIndex
        MAX-ACCESS   not-accessible
        STATUS       current
        DESCRIPTION  "Index of this table."
        ::= { tcn1dayDataRmonEntry 1 }

    tcn1dayRmonNEAddress OBJECT-TYPE
        SYNTAX       IpAddress
        MAX-ACCESS   not-accessible
        STATUS       current
        DESCRIPTION  "reserved."
        ::= { tcn1dayDataRmonEntry 2 }

    tcn1dayHCRxEthStatsDropEvents OBJECT-TYPE
        SYNTAX       SeverityValue
        MAX-ACCESS   read-only
        STATUS       current
        DESCRIPTION  "RMON(Ethernet Port) TCN 1 day RX Drop Events Alarm"
        ::= { tcn1dayDataRmonEntry 3 }

    tcn1dayHCRxEthStatsUndersizePkts OBJECT-TYPE
        SYNTAX       SeverityValue
        MAX-ACCESS   read-only
        STATUS       current
        DESCRIPTION
            "RMON(Ethernet Port) TCN 1 day RX Undersize Packets Alarm."
        ::= { tcn1dayDataRmonEntry 4 }

    tcn1dayHCRxEthStatsFragments OBJECT-TYPE
        SYNTAX       SeverityValue
        MAX-ACCESS   read-only
        STATUS       current
        DESCRIPTION  "RMON(Ethernet Port) TCN 1 day RX Fragments Alarm."
        ::= { tcn1dayDataRmonEntry 5 }

    tcn1dayHCRxEthStatsCRCAlignErrors OBJECT-TYPE
        SYNTAX       SeverityValue
        MAX-ACCESS   read-only
        STATUS       current
        DESCRIPTION
            "RMON(Ethernet Port) TCN 1 day RX CRC Alignment Errors Alarm."
        ::= { tcn1dayDataRmonEntry 6 }

    tcn1dayHCRxEthStatsOversizePkts OBJECT-TYPE
        SYNTAX       SeverityValue
        MAX-ACCESS   read-only
        STATUS       current
        DESCRIPTION
            "RMON(Ethernet Port) TCN 1 day RX Oversize Packets Alarm."
        ::= { tcn1dayDataRmonEntry 7 }

    tcn1dayHCTxEthStatsCollisions OBJECT-TYPE
        SYNTAX       SeverityValue
        MAX-ACCESS   read-only
        STATUS       current
        DESCRIPTION  "RMON(Ethernet Port) TCN 1 day TX Collisions Alarm."
        ::= { tcn1dayDataRmonEntry 8 }

    asHkGroup OBJECT IDENTIFIER
        ::= { alarmStatusGroup 10 }

    hkInputStatusTable OBJECT-TYPE
        SYNTAX       SEQUENCE OF HkInputStatusEntry
        MAX-ACCESS   not-accessible
        STATUS       current
        DESCRIPTION  "AUX HK Input Status"
        ::= { asHkGroup 1 }

    hkInputStatusEntry OBJECT-TYPE
        SYNTAX       HkInputStatusEntry
        MAX-ACCESS   not-accessible
        STATUS       current
        DESCRIPTION  ""
        INDEX        { hkInputStatusIndex }
        ::= { hkInputStatusTable 1 }

    HkInputStatusEntry ::= SEQUENCE {
        hkInputStatusIndex      INTEGER,
        hkInputStatusNEAddress  IpAddress,
        hkInputAlarm            SeverityValue,
        hkInputStatus           INTEGER
    }

    hkInputStatusIndex OBJECT-TYPE
        SYNTAX       INTEGER {
                         hkInput1(1),
                         hkInput2(2),
                         hkInput3(3),
                         hkInput4(4),
                         hkInput5(5),
                         hkInput6(6)
                     }
        MAX-ACCESS   not-accessible
        STATUS       current
        DESCRIPTION  "Index of this table."
        ::= { hkInputStatusEntry 1 }

    hkInputStatusNEAddress OBJECT-TYPE
        SYNTAX       IpAddress
        MAX-ACCESS   not-accessible
        STATUS       current
        DESCRIPTION  "reserved."
        ::= { hkInputStatusEntry 2 }

    hkInputAlarm OBJECT-TYPE
        SYNTAX       SeverityValue
        MAX-ACCESS   read-only
        STATUS       current
        DESCRIPTION  "AUX HK IN Alarm."
        ::= { hkInputStatusEntry 3 }

    hkInputStatus OBJECT-TYPE
        SYNTAX       INTEGER { eventOff(1), eventOn(2) }
        MAX-ACCESS   read-only
        STATUS       current
        DESCRIPTION  "AUX HK IN Status."
        ::= { hkInputStatusEntry 4 }

    hkOutputStatusTable OBJECT-TYPE
        SYNTAX       SEQUENCE OF HkOutputStatusEntry
        MAX-ACCESS   not-accessible
        STATUS       current
        DESCRIPTION  "AUX HK Output Status"
        ::= { asHkGroup 2 }

    hkOutputStatusEntry OBJECT-TYPE
        SYNTAX       HkOutputStatusEntry
        MAX-ACCESS   not-accessible
        STATUS       current
        DESCRIPTION  ""
        INDEX        { hkOutputStatusIndex }
        ::= { hkOutputStatusTable 1 }

    HkOutputStatusEntry ::= SEQUENCE {
        hkOutputStatusIndex      INTEGER,
        hkOutputStatusNEAddress  IpAddress,
        hkOutputStatusValue      OffOnValue
    }

    hkOutputStatusIndex OBJECT-TYPE
        SYNTAX       INTEGER {
                         hkOutput1(1),
                         hkOutput2(2),
                         hkOutput3(3),
                         hkOutput4(4)
                     }
        MAX-ACCESS   not-accessible
        STATUS       current
        DESCRIPTION  "Index of this table."
        ::= { hkOutputStatusEntry 1 }

    hkOutputStatusNEAddress OBJECT-TYPE
        SYNTAX       IpAddress
        MAX-ACCESS   not-accessible
        STATUS       current
        DESCRIPTION  "reserved."
        ::= { hkOutputStatusEntry 2 }

    hkOutputStatusValue OBJECT-TYPE
        SYNTAX       OffOnValue
        MAX-ACCESS   read-only
        STATUS       current
        DESCRIPTION  "AUX HK OUT Status"
        ::= { hkOutputStatusEntry 3 }

    clusterAlarmGroup OBJECT IDENTIFIER
        ::= { asHkGroup 3 }

    clusterAlarmInTable OBJECT-TYPE
        SYNTAX       SEQUENCE OF ClusterAlarmInEntry
        MAX-ACCESS   not-accessible
        STATUS       current
        DESCRIPTION
            "Represents Cluster Alarm Input (Cluster Alarm to Peer Equipment)
            Status"
        ::= { clusterAlarmGroup 1 }

    clusterAlarmInEntry OBJECT-TYPE
        SYNTAX       ClusterAlarmInEntry
        MAX-ACCESS   not-accessible
        STATUS       current
        DESCRIPTION  ""
        INDEX        { clusterAlarmInIfIndex }
        ::= { clusterAlarmInTable 1 }

    ClusterAlarmInEntry ::= SEQUENCE {
        clusterAlarmInIfIndex    InterfaceIndex,
        clusterAlarmInNEAddress  IpAddress,
        clusterAlarmInStatus     INTEGER
    }

    clusterAlarmInIfIndex OBJECT-TYPE
        SYNTAX       InterfaceIndex
        MAX-ACCESS   not-accessible
        STATUS       current
        DESCRIPTION  "Index of this table."
        ::= { clusterAlarmInEntry 1 }

    clusterAlarmInNEAddress OBJECT-TYPE
        SYNTAX       IpAddress
        MAX-ACCESS   not-accessible
        STATUS       current
        DESCRIPTION  "reserved."
        ::= { clusterAlarmInEntry 2 }

    clusterAlarmInStatus OBJECT-TYPE
        SYNTAX       INTEGER { alarm(1), normal(2) }
        MAX-ACCESS   read-only
        STATUS       current
        DESCRIPTION  "Cluster Alarm Input Status."
        ::= { clusterAlarmInEntry 3 }

    clusterAlarmOutTable OBJECT-TYPE
        SYNTAX       SEQUENCE OF ClusterAlarmOutEntry
        MAX-ACCESS   not-accessible
        STATUS       current
        DESCRIPTION
            "Represents Cluster Alarm Output (Cluster Alarm from Peer
            Equipment) Status"
        ::= { clusterAlarmGroup 2 }

    clusterAlarmOutEntry OBJECT-TYPE
        SYNTAX       ClusterAlarmOutEntry
        MAX-ACCESS   not-accessible
        STATUS       current
        DESCRIPTION  ""
        INDEX        { clusterAlarmOutIndex }
        ::= { clusterAlarmOutTable 1 }

    ClusterAlarmOutEntry ::= SEQUENCE {
        clusterAlarmOutIndex      Integer32,
        clusterAlarmOutNEAddress  IpAddress,
        clusterAlarmOutStatus     INTEGER
    }

    clusterAlarmOutIndex OBJECT-TYPE
        SYNTAX       Integer32
        MAX-ACCESS   not-accessible
        STATUS       current
        DESCRIPTION  "Index of this table."
        ::= { clusterAlarmOutEntry 1 }

    clusterAlarmOutNEAddress OBJECT-TYPE
        SYNTAX       IpAddress
        MAX-ACCESS   not-accessible
        STATUS       current
        DESCRIPTION  "reserved."
        ::= { clusterAlarmOutEntry 2 }

    clusterAlarmOutStatus OBJECT-TYPE
        SYNTAX       INTEGER { alarm(1), normal(2) }
        MAX-ACCESS   read-only
        STATUS       current
        DESCRIPTION  "MODEM Cluster Alarm Out."
        ::= { clusterAlarmOutEntry 3 }

    asStm1Group OBJECT IDENTIFIER
        ::= { alarmStatusGroup 11 }

    asStm1ChPortTable OBJECT-TYPE
        SYNTAX       SEQUENCE OF AsStm1ChPortEntry
        MAX-ACCESS   not-accessible
        STATUS       current
        DESCRIPTION
            "Alarm / Status Information of STM-1 Channelized Mode. This table
            is not used when the STM-1 Port is running on Through Mode."
        ::= { asStm1Group 1 }

    asStm1ChPortEntry OBJECT-TYPE
        SYNTAX       AsStm1ChPortEntry
        MAX-ACCESS   not-accessible
        STATUS       current
        DESCRIPTION  ""
        INDEX        { asStm1ChPortIfIndex }
        ::= { asStm1ChPortTable 1 }

    AsStm1ChPortEntry ::= SEQUENCE {
        asStm1ChPortIfIndex                InterfaceIndex,
        asStm1ChPortNEAddress              IpAddress,
        msAisAlarm                         SeverityValue,
        msRdiAlarm                         SeverityValue,
        pjeStatus                          INTEGER,
        auAisAlarm                         SeverityValue,
        auLopAlarm                         SeverityValue,
        hpUnequipedAlarm                   SeverityValue,
        hpTimAlarm                         SeverityValue,
        hpPlmAlarm                         SeverityValue,
        hpRdiAlarm                         SeverityValue,
        lomAlarm                           SeverityValue,
        higherOrderPathTraceReceivedValue  DisplayString,
        lowerOrderPathTraceReceivedValue   DisplayString
    }

    asStm1ChPortIfIndex OBJECT-TYPE
        SYNTAX       InterfaceIndex
        MAX-ACCESS   not-accessible
        STATUS       current
        DESCRIPTION  "Index of this table."
        ::= { asStm1ChPortEntry 1 }

    asStm1ChPortNEAddress OBJECT-TYPE
        SYNTAX       IpAddress
        MAX-ACCESS   not-accessible
        STATUS       current
        DESCRIPTION  "reserved."
        ::= { asStm1ChPortEntry 2 }

    msAisAlarm OBJECT-TYPE
        SYNTAX       SeverityValue
        MAX-ACCESS   read-only
        STATUS       current
        DESCRIPTION  "STM-1 MS AIS Alarm."
        ::= { asStm1ChPortEntry 3 }

    msRdiAlarm OBJECT-TYPE
        SYNTAX       SeverityValue
        MAX-ACCESS   read-only
        STATUS       current
        DESCRIPTION  "STM-1 MS RDI Alarm."
        ::= { asStm1ChPortEntry 4 }

    pjeStatus OBJECT-TYPE
        SYNTAX       INTEGER { noDetected(1), detected(2) }
        MAX-ACCESS   read-only
        STATUS       current
        DESCRIPTION  "STM-1 PJE Status."
        ::= { asStm1ChPortEntry 5 }

    auAisAlarm OBJECT-TYPE
        SYNTAX       SeverityValue
        MAX-ACCESS   read-only
        STATUS       current
        DESCRIPTION  "STM-1 AU AIS Alarm."
        ::= { asStm1ChPortEntry 6 }

    auLopAlarm OBJECT-TYPE
        SYNTAX       SeverityValue
        MAX-ACCESS   read-only
        STATUS       current
        DESCRIPTION  "STM-1 AU LOP Alarm."
        ::= { asStm1ChPortEntry 7 }

    hpUnequipedAlarm OBJECT-TYPE
        SYNTAX       SeverityValue
        MAX-ACCESS   read-only
        STATUS       current
        DESCRIPTION  "STM-1 HP UNEQ Alarm."
        ::= { asStm1ChPortEntry 8 }

    hpTimAlarm OBJECT-TYPE
        SYNTAX       SeverityValue
        MAX-ACCESS   read-only
        STATUS       current
        DESCRIPTION  "STM-1 HP TIM Alarm"
        ::= { asStm1ChPortEntry 9 }

    hpPlmAlarm OBJECT-TYPE
        SYNTAX       SeverityValue
        MAX-ACCESS   read-only
        STATUS       current
        DESCRIPTION  "STM-1 HP PLM Alarm"
        ::= { asStm1ChPortEntry 10 }

    hpRdiAlarm OBJECT-TYPE
        SYNTAX       SeverityValue
        MAX-ACCESS   read-only
        STATUS       current
        DESCRIPTION  "STM-1 HP RDI Alarm"
        ::= { asStm1ChPortEntry 11 }

    lomAlarm OBJECT-TYPE
        SYNTAX       SeverityValue
        MAX-ACCESS   read-only
        STATUS       current
        DESCRIPTION  "STM-1 LOM Alarm."
        ::= { asStm1ChPortEntry 12 }

    higherOrderPathTraceReceivedValue OBJECT-TYPE
        SYNTAX       DisplayString
        MAX-ACCESS   read-only
        STATUS       current
        DESCRIPTION  "STM-1 HP Trace Received Value."
        ::= { asStm1ChPortEntry 13 }

    lowerOrderPathTraceReceivedValue OBJECT-TYPE
        SYNTAX       DisplayString
        MAX-ACCESS   read-only
        STATUS       current
        DESCRIPTION  "STM-1 LP Trace Received Value."
        ::= { asStm1ChPortEntry 14 }

    asStm1PortTable OBJECT-TYPE
        SYNTAX       SEQUENCE OF AsStm1PortEntry
        MAX-ACCESS   not-accessible
        STATUS       current
        DESCRIPTION  "Alarm / Status Information of STM-1 Interface."
        ::= { asStm1Group 2 }

    asStm1PortEntry OBJECT-TYPE
        SYNTAX       AsStm1PortEntry
        MAX-ACCESS   not-accessible
        STATUS       current
        DESCRIPTION  ""
        INDEX        { asStm1PortIfIndex }
        ::= { asStm1PortTable 1 }

    AsStm1PortEntry ::= SEQUENCE {
        asStm1PortIfIndex          InterfaceIndex,
        asStm1PortNEAddress        IpAddress,
        portTypeMismatchAlarm      SeverityValue,
        portRemovedAlarm           SeverityValue,
        stm1LosAlarm               SeverityValue,
        tfAlarm                    SeverityValue,
        rsLofAlarm                 SeverityValue,
        rsTimAlarm                 SeverityValue,
        rsExcAlarm                 SeverityValue,
        rsDegAlarm                 SeverityValue,
        rsUasStatus                INTEGER,
        sectionTraceReceivedValue  DisplayString,
        alsStatus                  OffOnValue,
        sdhAisGenStatus            INTEGER,
        stm1LoopbackStatus         INTEGER,
        stm1LaserShutdownStatus    OffOnValue
    }

    asStm1PortIfIndex OBJECT-TYPE
        SYNTAX       InterfaceIndex
        MAX-ACCESS   not-accessible
        STATUS       current
        DESCRIPTION  "Index of this table."
        ::= { asStm1PortEntry 1 }

    asStm1PortNEAddress OBJECT-TYPE
        SYNTAX       IpAddress
        MAX-ACCESS   not-accessible
        STATUS       current
        DESCRIPTION  "reserved."
        ::= { asStm1PortEntry 2 }

    portTypeMismatchAlarm OBJECT-TYPE
        SYNTAX       SeverityValue
        MAX-ACCESS   read-only
        STATUS       current
        DESCRIPTION  "STM-1 SFP Type Mismatch Alarm."
        ::= { asStm1PortEntry 3 }

    portRemovedAlarm OBJECT-TYPE
        SYNTAX       SeverityValue
        MAX-ACCESS   read-only
        STATUS       current
        DESCRIPTION  "STM-1 SFP Removed Alarm."
        ::= { asStm1PortEntry 4 }

    stm1LosAlarm OBJECT-TYPE
        SYNTAX       SeverityValue
        MAX-ACCESS   read-only
        STATUS       current
        DESCRIPTION  "STM-1 LOS Alarm."
        ::= { asStm1PortEntry 5 }

    tfAlarm OBJECT-TYPE
        SYNTAX       SeverityValue
        MAX-ACCESS   read-only
        STATUS       current
        DESCRIPTION  "STM-1 Transmit FAIL Alarm."
        ::= { asStm1PortEntry 6 }

    rsLofAlarm OBJECT-TYPE
        SYNTAX       SeverityValue
        MAX-ACCESS   read-only
        STATUS       current
        DESCRIPTION  "STM-1 RS LOF Alarm."
        ::= { asStm1PortEntry 7 }

    rsTimAlarm OBJECT-TYPE
        SYNTAX       SeverityValue
        MAX-ACCESS   read-only
        STATUS       current
        DESCRIPTION  "STM-1 RS TIM Alarm."
        ::= { asStm1PortEntry 8 }

    rsExcAlarm OBJECT-TYPE
        SYNTAX       SeverityValue
        MAX-ACCESS   read-only
        STATUS       current
        DESCRIPTION  "STM-1 RS EXC Alarm."
        ::= { asStm1PortEntry 9 }

    rsDegAlarm OBJECT-TYPE
        SYNTAX       SeverityValue
        MAX-ACCESS   read-only
        STATUS       current
        DESCRIPTION  "STM-1 RS DEG Alarm."
        ::= { asStm1PortEntry 10 }

    rsUasStatus OBJECT-TYPE
        SYNTAX       INTEGER { normal(1), uas(2) }
        MAX-ACCESS   read-only
        STATUS       current
        DESCRIPTION  "STM-1 RS UAS Status"
        ::= { asStm1PortEntry 11 }

    sectionTraceReceivedValue OBJECT-TYPE
        SYNTAX       DisplayString
        MAX-ACCESS   read-only
        STATUS       current
        DESCRIPTION  "STM-1 Section Trace Received Value."
        ::= { asStm1PortEntry 12 }

    alsStatus OBJECT-TYPE
        SYNTAX       OffOnValue
        MAX-ACCESS   read-only
        STATUS       current
        DESCRIPTION  "STM-1 ALS Status"
        ::= { asStm1PortEntry 13 }

    sdhAisGenStatus OBJECT-TYPE
        SYNTAX       INTEGER { invalid(0), normal(1), generated(2), shutdown(3) }
        MAX-ACCESS   read-only
        STATUS       current
        DESCRIPTION  "STM-1 AIS Generated Status."
        ::= { asStm1PortEntry 14 }

    stm1LoopbackStatus OBJECT-TYPE
        SYNTAX       INTEGER { ne(1), fe(2), normal(3) }
        MAX-ACCESS   read-only
        STATUS       current
        DESCRIPTION  "STM-1 Loopback Status."
        ::= { asStm1PortEntry 15 }

    stm1LaserShutdownStatus OBJECT-TYPE
        SYNTAX       OffOnValue
        MAX-ACCESS   read-only
        STATUS       current
        DESCRIPTION  "STM-1 Laser Shutdown status."
        ::= { asStm1PortEntry 16 }

    asStm1ChTable OBJECT-TYPE
        SYNTAX       SEQUENCE OF AsStm1ChEntry
        MAX-ACCESS   not-accessible
        STATUS       current
        DESCRIPTION
            "Alarm / Status Information of STM-1 Channelized. This table is
            created per E1 channel allocated to the STM-1 interface."
        ::= { asStm1Group 3 }

    asStm1ChEntry OBJECT-TYPE
        SYNTAX       AsStm1ChEntry
        MAX-ACCESS   not-accessible
        STATUS       current
        DESCRIPTION  ""
        INDEX        { asStm1ChIfIndex }
        ::= { asStm1ChTable 1 }

    AsStm1ChEntry ::= SEQUENCE {
        asStm1ChIfIndex    InterfaceIndex,
        asStm1ChNEAddress  IpAddress,
        tuAisAlarm         SeverityValue,
        tuLopAlarm         SeverityValue,
        lpUnequipedAlarm   SeverityValue,
        lpRdiAlarm         SeverityValue,
        lpPlmAlarm         SeverityValue,
        slpAisGenStatus    INTEGER
    }

    asStm1ChIfIndex OBJECT-TYPE
        SYNTAX       InterfaceIndex
        MAX-ACCESS   not-accessible
        STATUS       current
        DESCRIPTION  "Index of this table."
        ::= { asStm1ChEntry 1 }

    asStm1ChNEAddress OBJECT-TYPE
        SYNTAX       IpAddress
        MAX-ACCESS   not-accessible
        STATUS       current
        DESCRIPTION  "reserved."
        ::= { asStm1ChEntry 2 }

    tuAisAlarm OBJECT-TYPE
        SYNTAX       SeverityValue
        MAX-ACCESS   read-only
        STATUS       current
        DESCRIPTION  "STM-1 TU AIS Alarm."
        ::= { asStm1ChEntry 3 }

    tuLopAlarm OBJECT-TYPE
        SYNTAX       SeverityValue
        MAX-ACCESS   read-only
        STATUS       current
        DESCRIPTION  "STM-1 TU LOP Alarm."
        ::= { asStm1ChEntry 4 }

    lpUnequipedAlarm OBJECT-TYPE
        SYNTAX       SeverityValue
        MAX-ACCESS   read-only
        STATUS       current
        DESCRIPTION  "STM-1 LP UNEQ Alarm."
        ::= { asStm1ChEntry 5 }

    lpRdiAlarm OBJECT-TYPE
        SYNTAX       SeverityValue
        MAX-ACCESS   read-only
        STATUS       current
        DESCRIPTION  "STM-1 LP RDI Alarm."
        ::= { asStm1ChEntry 6 }

    lpPlmAlarm OBJECT-TYPE
        SYNTAX       SeverityValue
        MAX-ACCESS   read-only
        STATUS       current
        DESCRIPTION  "STM-1 LP PLM Alarm."
        ::= { asStm1ChEntry 7 }

    slpAisGenStatus OBJECT-TYPE
        SYNTAX       INTEGER { normal(1), generated(2) }
        MAX-ACCESS   read-only
        STATUS       current
        DESCRIPTION  "STM-1 E1 AIS Generated Status."
        ::= { asStm1ChEntry 8 }

    asStm1CardTable OBJECT-TYPE
        SYNTAX       SEQUENCE OF AsStm1CardEntry
        MAX-ACCESS   not-accessible
        STATUS       current
        DESCRIPTION  "Alarm / Status information of STM-1 Card."
        ::= { asStm1Group 4 }

    asStm1CardEntry OBJECT-TYPE
        SYNTAX       AsStm1CardEntry
        MAX-ACCESS   not-accessible
        STATUS       current
        DESCRIPTION  ""
        INDEX        { asStm1CardIndex }
        ::= { asStm1CardTable 1 }

    AsStm1CardEntry ::= SEQUENCE {
        asStm1CardIndex      Integer32,
        asStm1CardNEAddress  IpAddress,
        stm1Alarm            SeverityValue,
        stm1ComFailAlarm     SeverityValue,
        stm1Unequipped       SeverityValue,
        stm1TypeMismatch     SeverityValue,
        stm1BusErrorTx       SeverityValue,
        stm1BusErrorRx       SeverityValue
    }

    asStm1CardIndex OBJECT-TYPE
        SYNTAX       Integer32
        MAX-ACCESS   not-accessible
        STATUS       current
        DESCRIPTION  "Index of this table."
        ::= { asStm1CardEntry 1 }

    asStm1CardNEAddress OBJECT-TYPE
        SYNTAX       IpAddress
        MAX-ACCESS   not-accessible
        STATUS       current
        DESCRIPTION  "reserved."
        ::= { asStm1CardEntry 2 }

    stm1Alarm OBJECT-TYPE
        SYNTAX       SeverityValue
        MAX-ACCESS   read-only
        STATUS       current
        DESCRIPTION  "STM-1 Module Alarm."
        ::= { asStm1CardEntry 3 }

    stm1ComFailAlarm OBJECT-TYPE
        SYNTAX       SeverityValue
        MAX-ACCESS   read-only
        STATUS       current
        DESCRIPTION  "STM-1 Communication FAIL Alarm."
        ::= { asStm1CardEntry 4 }

    stm1Unequipped OBJECT-TYPE
        SYNTAX       SeverityValue
        MAX-ACCESS   read-only
        STATUS       current
        DESCRIPTION  "STM-1 Unequipped Alarm."
        ::= { asStm1CardEntry 5 }

    stm1TypeMismatch OBJECT-TYPE
        SYNTAX       SeverityValue
        MAX-ACCESS   read-only
        STATUS       current
        DESCRIPTION  "STM-1 Type Mismatch Alarm."
        ::= { asStm1CardEntry 6 }

    stm1BusErrorTx OBJECT-TYPE
        SYNTAX       SeverityValue
        MAX-ACCESS   read-only
        STATUS       current
        DESCRIPTION  "STM-1 TX Bus Error Alarm."
        ::= { asStm1CardEntry 7 }

    stm1BusErrorRx OBJECT-TYPE
        SYNTAX       SeverityValue
        MAX-ACCESS   read-only
        STATUS       current
        DESCRIPTION  "STM-1 RX Bus Error Alarm."
        ::= { asStm1CardEntry 8 }

    asE1Group OBJECT IDENTIFIER
        ::= { alarmStatusGroup 12 }

    asE1CardTable OBJECT-TYPE
        SYNTAX       SEQUENCE OF AsE1CardEntry
        MAX-ACCESS   not-accessible
        STATUS       current
        DESCRIPTION  "Alarm / Status information of 16E1 Card."
        ::= { asE1Group 1 }

    asE1CardEntry OBJECT-TYPE
        SYNTAX       AsE1CardEntry
        MAX-ACCESS   not-accessible
        STATUS       current
        DESCRIPTION  ""
        INDEX        { asE1CardIndex }
        ::= { asE1CardTable 1 }

    AsE1CardEntry ::= SEQUENCE {
        asE1CardIndex      Integer32,
        asE1CardNEAddress  IpAddress,
        e1Alarm            SeverityValue,
        e1ComFailAlarm     SeverityValue,
        e1Unequipped       SeverityValue,
        e1TypeMismatch     SeverityValue,
        e1BusErrorTx       SeverityValue,
        e1BusErrorRx       SeverityValue
    }

    asE1CardIndex OBJECT-TYPE
        SYNTAX       Integer32
        MAX-ACCESS   not-accessible
        STATUS       current
        DESCRIPTION  "Index of this table."
        ::= { asE1CardEntry 1 }

    asE1CardNEAddress OBJECT-TYPE
        SYNTAX       IpAddress
        MAX-ACCESS   not-accessible
        STATUS       current
        DESCRIPTION  "reserved."
        ::= { asE1CardEntry 2 }

    e1Alarm OBJECT-TYPE
        SYNTAX       SeverityValue
        MAX-ACCESS   read-only
        STATUS       current
        DESCRIPTION  "16E1 Module Alarm."
        ::= { asE1CardEntry 3 }

    e1ComFailAlarm OBJECT-TYPE
        SYNTAX       SeverityValue
        MAX-ACCESS   read-only
        STATUS       current
        DESCRIPTION  "16E1 Communication FAIL Alarm."
        ::= { asE1CardEntry 4 }

    e1Unequipped OBJECT-TYPE
        SYNTAX       SeverityValue
        MAX-ACCESS   read-only
        STATUS       current
        DESCRIPTION  "16E1 Unequipped Alarm."
        ::= { asE1CardEntry 5 }

    e1TypeMismatch OBJECT-TYPE
        SYNTAX       SeverityValue
        MAX-ACCESS   read-only
        STATUS       current
        DESCRIPTION  "16E1 Type Mismatch Alarm."
        ::= { asE1CardEntry 6 }

    e1BusErrorTx OBJECT-TYPE
        SYNTAX       SeverityValue
        MAX-ACCESS   read-only
        STATUS       current
        DESCRIPTION  "16E1 TX Bus Error Alarm."
        ::= { asE1CardEntry 7 }

    e1BusErrorRx OBJECT-TYPE
        SYNTAX       SeverityValue
        MAX-ACCESS   read-only
        STATUS       current
        DESCRIPTION  "16E1 RX Bus Error Alarm."
        ::= { asE1CardEntry 8 }

    asE1ChTable OBJECT-TYPE
        SYNTAX       SEQUENCE OF AsE1ChEntry
        MAX-ACCESS   not-accessible
        STATUS       current
        DESCRIPTION  "Alarm / Status information of E1 Channel."
        ::= { asE1Group 2 }

    asE1ChEntry OBJECT-TYPE
        SYNTAX       AsE1ChEntry
        MAX-ACCESS   not-accessible
        STATUS       current
        DESCRIPTION  ""
        INDEX        { asE1ChIfIndex }
        ::= { asE1ChTable 1 }

    AsE1ChEntry ::= SEQUENCE {
        asE1ChIfIndex     InterfaceIndex,
        asE1ChNEAddress   IpAddress,
        chUsageAlarm      SeverityValue,
        e1LosAlarm        SeverityValue,
        ppiAisAlarm       SeverityValue,
        e1AisGenStatus    INTEGER,
        e1LoopbackStatus  INTEGER,
        ppiAisStatus      INTEGER
    }

    asE1ChIfIndex OBJECT-TYPE
        SYNTAX       InterfaceIndex
        MAX-ACCESS   not-accessible
        STATUS       current
        DESCRIPTION  "Index of this table."
        ::= { asE1ChEntry 1 }

    asE1ChNEAddress OBJECT-TYPE
        SYNTAX       IpAddress
        MAX-ACCESS   not-accessible
        STATUS       current
        DESCRIPTION  "reserved."
        ::= { asE1ChEntry 2 }

    chUsageAlarm OBJECT-TYPE
        SYNTAX       SeverityValue
        MAX-ACCESS   read-only
        STATUS       current
        DESCRIPTION  "E1 Channel Usage Error Alarm."
        ::= { asE1ChEntry 3 }

    e1LosAlarm OBJECT-TYPE
        SYNTAX       SeverityValue
        MAX-ACCESS   read-only
        STATUS       current
        DESCRIPTION  "E1 Channel LOS Alarm."
        ::= { asE1ChEntry 4 }

    ppiAisAlarm OBJECT-TYPE
        SYNTAX       SeverityValue
        MAX-ACCESS   read-only
        STATUS       current
        DESCRIPTION  "E1 Channel AIS Alarm."
        ::= { asE1ChEntry 5 }

    e1AisGenStatus OBJECT-TYPE
        SYNTAX       INTEGER { normal(1), generated(2) }
        MAX-ACCESS   read-only
        STATUS       current
        DESCRIPTION  "E1 Channel AIS Generated Status."
        ::= { asE1ChEntry 6 }

    e1LoopbackStatus OBJECT-TYPE
        SYNTAX       INTEGER { ne(1), fe(2), normal(3) }
        MAX-ACCESS   read-only
        STATUS       current
        DESCRIPTION  "E1 Channel Loopback Status."
        ::= { asE1ChEntry 7 }

    ppiAisStatus OBJECT-TYPE
        SYNTAX       INTEGER { normal(1), ais(2) }
        MAX-ACCESS   read-only
        STATUS       current
        DESCRIPTION  "E1 Channel AIS Status."
        ::= { asE1ChEntry 8 }

    asETHGroup OBJECT IDENTIFIER
        ::= { alarmStatusGroup 13 }

    asRstpGroup OBJECT IDENTIFIER
        ::= { asETHGroup 2 }

    asRstpBridgeTable OBJECT-TYPE
        SYNTAX       SEQUENCE OF AsRstpBridgeEntry
        MAX-ACCESS   not-accessible
        STATUS       current
        DESCRIPTION  "Alarm / Status information of RSTP."
        ::= { asRstpGroup 1 }

    asRstpBridgeEntry OBJECT-TYPE
        SYNTAX       AsRstpBridgeEntry
        MAX-ACCESS   not-accessible
        STATUS       current
        DESCRIPTION  ""
        INDEX        { asRstpBridgeIndex }
        ::= { asRstpBridgeTable 1 }

    AsRstpBridgeEntry ::= SEQUENCE {
        asRstpBridgeIndex           Integer32,
        asRstpBridgeNEAddress       IpAddress,
        asRstpBridgeDesignatedRoot  BridgeId,
        asRstpBridgeTopChanges      Integer32
    }

    asRstpBridgeIndex OBJECT-TYPE
        SYNTAX       Integer32 (1..1)
        MAX-ACCESS   not-accessible
        STATUS       current
        DESCRIPTION  "Index of this table."
        ::= { asRstpBridgeEntry 1 }

    asRstpBridgeNEAddress OBJECT-TYPE
        SYNTAX       IpAddress
        MAX-ACCESS   not-accessible
        STATUS       current
        DESCRIPTION  "reserved."
        ::= { asRstpBridgeEntry 2 }

    asRstpBridgeDesignatedRoot OBJECT-TYPE
        SYNTAX       BridgeId
        MAX-ACCESS   read-only
        STATUS       current
        DESCRIPTION
            "The bridge identifier of the root of the spanning tree."
        ::= { asRstpBridgeEntry 3 }

    asRstpBridgeTopChanges OBJECT-TYPE
        SYNTAX       Integer32
        MAX-ACCESS   read-only
        STATUS       current
        DESCRIPTION
            "RSTP Topology Changed Status. The total number of topology
            chagnes detected by this bridge since the equipment was last
            initialized."
        ::= { asRstpBridgeEntry 4 }

    asRstpPortTable OBJECT-TYPE
        SYNTAX       SEQUENCE OF AsRstpPortEntry
        MAX-ACCESS   not-accessible
        STATUS       current
        DESCRIPTION
            "Alarm / Status information of RSTP per Ethernet Port."
        ::= { asRstpGroup 2 }

    asRstpPortEntry OBJECT-TYPE
        SYNTAX       AsRstpPortEntry
        MAX-ACCESS   not-accessible
        STATUS       current
        DESCRIPTION  ""
        INDEX        { asRstpIfIndex }
        ::= { asRstpPortTable 1 }

    AsRstpPortEntry ::= SEQUENCE {
        asRstpIfIndex                                  InterfaceIndex,
        asRstpPortNEAddress                            IpAddress,
        asRstpPortRole                                 INTEGER,
        asRstpPortState                                INTEGER,
        asRstpPortNewRootBridgeDetectedBridgePriority  BridgeId,
        asRstpPortProtocolMigrationVersion             INTEGER,
        asRstpPortPathCost                             Integer32,
        asRstpPortInvalidBpduCause                     INTEGER,
        asRstpPortDesignatedCost                       Integer32,
        asRstpPortDesignatedBridge                     BridgeId,
        asRstpPortDesignatedPort                       OCTET STRING,
        asRstpPortForwardTransitions                   Counter32,
        asRstpPortOperEdgePort                         INTEGER,
        asRstpPortOperPointToPoint                     EnableDisableValue
    }

    asRstpIfIndex OBJECT-TYPE
        SYNTAX       InterfaceIndex
        MAX-ACCESS   not-accessible
        STATUS       current
        DESCRIPTION  "Index of this table."
        ::= { asRstpPortEntry 1 }

    asRstpPortNEAddress OBJECT-TYPE
        SYNTAX       IpAddress
        MAX-ACCESS   not-accessible
        STATUS       current
        DESCRIPTION  "reserved."
        ::= { asRstpPortEntry 2 }

    asRstpPortRole OBJECT-TYPE
        SYNTAX       INTEGER {
                         disabledPort(1),
                         alternatePort(2),
                         backupPort(3),
                         rootPort(4),
                         designatedPort(5)
                     }
        MAX-ACCESS   read-only
        STATUS       current
        DESCRIPTION
            "RSTP Port Role. The port's current state, as defined by
            application of the Spanning Tree Protocol. This state controls
            what action a port takes on reception of a frame."
        ::= { asRstpPortEntry 3 }

    asRstpPortState OBJECT-TYPE
        SYNTAX       INTEGER {
                         disabled(1),
                         blocking(2),
                         listening(3),
                         learning(4),
                         forwarding(5),
                         broken(6),
                         discarding(7)
                     }
        MAX-ACCESS   read-only
        STATUS       current
        DESCRIPTION
            "RSTP Port Status. The port's current state, as defined by
            application of the Spanning Tree Protocol. This state controls
            what action a port takes on reception of a frame."
        ::= { asRstpPortEntry 4 }

    asRstpPortNewRootBridgeDetectedBridgePriority OBJECT-TYPE
        SYNTAX       BridgeId
        MAX-ACCESS   read-only
        STATUS       current
        DESCRIPTION
            "RSTP New Bridge Detect Status. The unique Bridge Identifier of
            the Bridge recorded as the Root in the Configuration BPDUs."
        ::= { asRstpPortEntry 5 }

    asRstpPortProtocolMigrationVersion OBJECT-TYPE
        SYNTAX       INTEGER { stp(1), rstp(2) }
        MAX-ACCESS   read-only
        STATUS       current
        DESCRIPTION
            "RSTP Protocol Migration. The port's operating protocol version."
        ::= { asRstpPortEntry 6 }

    asRstpPortPathCost OBJECT-TYPE
        SYNTAX       Integer32 (1..200000000)
        MAX-ACCESS   read-only
        STATUS       current
        DESCRIPTION
            "The port's path cost, defined by application depends on its port
            speed."
        ::= { asRstpPortEntry 7 }

    asRstpPortInvalidBpduCause OBJECT-TYPE
        SYNTAX       INTEGER {
                         restore(0),
                         protocolID(1),
                         bpduType(2),
                         tcnLength(3),
                         rstpLength(4),
                         configLength(5),
                         maxAge(6),
                         fwdDelay(7),
                         helloTime(8)
                     }
        MAX-ACCESS   read-only
        STATUS       current
        DESCRIPTION
            "RSTP Invalid BPDU Received. The event status of invalid BPDU
            received."
        ::= { asRstpPortEntry 8 }

    asRstpPortDesignatedCost OBJECT-TYPE
        SYNTAX       Integer32 (1..200000000)
        MAX-ACCESS   read-only
        STATUS       current
        DESCRIPTION
            "The path cost of the Designated Port of the segment connected to
            this port."
        ::= { asRstpPortEntry 9 }

    asRstpPortDesignatedBridge OBJECT-TYPE
        SYNTAX       BridgeId
        MAX-ACCESS   read-only
        STATUS       current
        DESCRIPTION
            "The bridge identifier of the bridge that this port considers to
            be the designated Bridge for this port's segment."
        ::= { asRstpPortEntry 10 }

    asRstpPortDesignatedPort OBJECT-TYPE
        SYNTAX       OCTET STRING
        MAX-ACCESS   read-only
        STATUS       current
        DESCRIPTION
            "The port identifier of the port on the designated bridge for
            this port's segment."
        ::= { asRstpPortEntry 11 }

    asRstpPortForwardTransitions OBJECT-TYPE
        SYNTAX       Counter32
        MAX-ACCESS   read-only
        STATUS       current
        DESCRIPTION
            "The number of times this port has transitioned from the learning
            state to the forwarding state."
        ::= { asRstpPortEntry 12 }

    asRstpPortOperEdgePort OBJECT-TYPE
        SYNTAX       INTEGER { alarmOff(0), alarmOn(1) }
        MAX-ACCESS   read-only
        STATUS       current
        DESCRIPTION
            "The operational value of the edge port parameter. This object is
            initialized to 'alarmOff'. This object will be changed to
            'alarmOn' on reception of a BPDU if the corresponding
            'provRstpExtPortAdminEdgePort' is set to 'enabled'."
        ::= { asRstpPortEntry 13 }

    asRstpPortOperPointToPoint OBJECT-TYPE
        SYNTAX       EnableDisableValue
        MAX-ACCESS   read-only
        STATUS       current
        DESCRIPTION
            "The operational value of the point-to-point port parameter."
        ::= { asRstpPortEntry 14 }

    asEthOamGroup OBJECT IDENTIFIER
        ::= { asETHGroup 3 }

    asEthOamCcGroup OBJECT IDENTIFIER
        ::= { asEthOamGroup 1 }

    asEthOamMepCcmFaultTable OBJECT-TYPE
        SYNTAX       SEQUENCE OF AsEthOamMepCcmFaultEntry
        MAX-ACCESS   not-accessible
        STATUS       current
        DESCRIPTION  "ETH-CC Fault Management Table"
        ::= { asEthOamCcGroup 1 }

    asEthOamMepCcmFaultEntry OBJECT-TYPE
        SYNTAX       AsEthOamMepCcmFaultEntry
        MAX-ACCESS   not-accessible
        STATUS       current
        DESCRIPTION  ""
        INDEX        { asEthOamMepCcmIndex }
        ::= { asEthOamMepCcmFaultTable 1 }

    AsEthOamMepCcmFaultEntry ::= SEQUENCE {
        asEthOamMepCcmIndex                   IpeMepId,
        asEthOamMepCcmFaultNEAddress          IpAddress,
        asEthOamMepCcmLOC                     SeverityValue,
        asEthOamMepCcmRdiReceived             SeverityValue,
        asEthOamMepCcmMismergeCondition       SeverityValue,
        asEthOamMepCcmUnexpectedMepCondition  SeverityValue
    }

    asEthOamMepCcmIndex OBJECT-TYPE
        SYNTAX       IpeMepId
        MAX-ACCESS   not-accessible
        STATUS       current
        DESCRIPTION  "Index of this table."
        ::= { asEthOamMepCcmFaultEntry 1 }

    asEthOamMepCcmFaultNEAddress OBJECT-TYPE
        SYNTAX       IpAddress
        MAX-ACCESS   not-accessible
        STATUS       current
        DESCRIPTION  "reserved."
        ::= { asEthOamMepCcmFaultEntry 2 }

    asEthOamMepCcmLOC OBJECT-TYPE
        SYNTAX       SeverityValue
        MAX-ACCESS   read-only
        STATUS       current
        DESCRIPTION
            "ETH-OAM LOC Alarm. The MEP is not receiveing valid CCM from at
            least one of the remote MEP."
        ::= { asEthOamMepCcmFaultEntry 3 }

    asEthOamMepCcmRdiReceived OBJECT-TYPE
        SYNTAX       SeverityValue
        MAX-ACCESS   read-only
        STATUS       current
        DESCRIPTION
            "ETH-OAM RDI Alarm. A remote MEP is reported the RDI in is last
            CCM."
        ::= { asEthOamMepCcmFaultEntry 4 }

    asEthOamMepCcmMismergeCondition OBJECT-TYPE
        SYNTAX       SeverityValue
        MAX-ACCESS   read-only
        STATUS       obsolete
        DESCRIPTION  "obsoleted"
        ::= { asEthOamMepCcmFaultEntry 5 }

    asEthOamMepCcmUnexpectedMepCondition OBJECT-TYPE
        SYNTAX       SeverityValue
        MAX-ACCESS   read-only
        STATUS       obsolete
        DESCRIPTION  "obsoleted"
        ::= { asEthOamMepCcmFaultEntry 6 }

    asEthOamMepCcmDbTable OBJECT-TYPE
        SYNTAX       SEQUENCE OF AsEthOamMepCcmDbEntry
        MAX-ACCESS   not-accessible
        STATUS       current
        DESCRIPTION  "ETH-CCM Database Table"
        ::= { asEthOamCcGroup 2 }

    asEthOamMepCcmDbEntry OBJECT-TYPE
        SYNTAX       AsEthOamMepCcmDbEntry
        MAX-ACCESS   not-accessible
        STATUS       current
        DESCRIPTION  ""
        INDEX        { asEthOamMepCcmDbPeerMepIndex }
        ::= { asEthOamMepCcmDbTable 1 }

    AsEthOamMepCcmDbEntry ::= SEQUENCE {
        asEthOamMepCcmDbPeerMepIndex  IpeMepId,
        asEthOamMepCcmDbNEAddress     IpAddress,
        asEthOamMepCcmDbMepIndex      IpeMepId,
        asEthOamMepCcmDbPeerMepId     Integer32,
        asEthOamMepCcmDbMepId         Integer32,
        asEthOamMepCcmDbCondition     TruthValue,
        asEthOamMepCcmDbRdiReceived   TruthValue
    }

    asEthOamMepCcmDbPeerMepIndex OBJECT-TYPE
        SYNTAX       IpeMepId
        MAX-ACCESS   not-accessible
        STATUS       current
        DESCRIPTION  "Index of this table."
        ::= { asEthOamMepCcmDbEntry 1 }

    asEthOamMepCcmDbNEAddress OBJECT-TYPE
        SYNTAX       IpAddress
        MAX-ACCESS   not-accessible
        STATUS       current
        DESCRIPTION  "reserved."
        ::= { asEthOamMepCcmDbEntry 2 }

    asEthOamMepCcmDbMepIndex OBJECT-TYPE
        SYNTAX       IpeMepId
        MAX-ACCESS   read-only
        STATUS       current
        DESCRIPTION  "Administrative Mep Index of own MEP."
        ::= { asEthOamMepCcmDbEntry 3 }

    asEthOamMepCcmDbPeerMepId OBJECT-TYPE
        SYNTAX       Integer32 (0..8191)
        MAX-ACCESS   read-only
        STATUS       current
        DESCRIPTION
            "this object represents protocol sense MEP ID of peer MEP."
        ::= { asEthOamMepCcmDbEntry 4 }

    asEthOamMepCcmDbMepId OBJECT-TYPE
        SYNTAX       Integer32 (0..8191)
        MAX-ACCESS   read-only
        STATUS       current
        DESCRIPTION
            "this object represents protocol sense MEP ID of local MEP."
        ::= { asEthOamMepCcmDbEntry 5 }

    asEthOamMepCcmDbCondition OBJECT-TYPE
        SYNTAX       TruthValue
        MAX-ACCESS   read-only
        STATUS       current
        DESCRIPTION
            "This object represents the status of LOC detection per Peer
            MEP."
        ::= { asEthOamMepCcmDbEntry 6 }

    asEthOamMepCcmDbRdiReceived OBJECT-TYPE
        SYNTAX       TruthValue
        MAX-ACCESS   read-only
        STATUS       current
        DESCRIPTION
            "This object represents the status of RDI receive status per peer
            MEP."
        ::= { asEthOamMepCcmDbEntry 7 }

    asEthOamMegCcmFaultTable OBJECT-TYPE
        SYNTAX       SEQUENCE OF AsEthOamMegCcmFaultEntry
        MAX-ACCESS   not-accessible
        STATUS       current
        DESCRIPTION  "ETH-CC Fault Management Table(MEG)"
        ::= { asEthOamCcGroup 3 }

    asEthOamMegCcmFaultEntry OBJECT-TYPE
        SYNTAX       AsEthOamMegCcmFaultEntry
        MAX-ACCESS   not-accessible
        STATUS       current
        DESCRIPTION  ""
        INDEX        { asEthOamMegCcmIndex }
        ::= { asEthOamMegCcmFaultTable 1 }

    AsEthOamMegCcmFaultEntry ::= SEQUENCE {
        asEthOamMegCcmIndex                   Integer32,
        asEthOamMegCcmFaultNEAddress          IpAddress,
        asEthOamMegCcmMismergeCondition       SeverityValue,
        asEthOamMegCcmUnexpectedMepCondition  SeverityValue
    }

    asEthOamMegCcmIndex OBJECT-TYPE
        SYNTAX       Integer32 (1..128)
        MAX-ACCESS   not-accessible
        STATUS       current
        DESCRIPTION  "Index of this table."
        ::= { asEthOamMegCcmFaultEntry 1 }

    asEthOamMegCcmFaultNEAddress OBJECT-TYPE
        SYNTAX       IpAddress
        MAX-ACCESS   not-accessible
        STATUS       current
        DESCRIPTION  "reserved."
        ::= { asEthOamMegCcmFaultEntry 2 }

    asEthOamMegCcmMismergeCondition OBJECT-TYPE
        SYNTAX       SeverityValue
        MAX-ACCESS   read-only
        STATUS       current
        DESCRIPTION
            "ETH-OAM Mismerge Alarm. The MEP received a CCM frame with
            correct MEG level but an incorrect MEG ID (Maintenance Domain
            Name)."
        ::= { asEthOamMegCcmFaultEntry 3 }

    asEthOamMegCcmUnexpectedMepCondition OBJECT-TYPE
        SYNTAX       SeverityValue
        MAX-ACCESS   read-only
        STATUS       current
        DESCRIPTION
            "ETH-OAM Unexpected MEP Alarm. The MEP Received a CCM frame with
            the correct MEG level and MEG ID, but unexpected MEP ID."
        ::= { asEthOamMegCcmFaultEntry 4 }

    asEthOamAisGroup OBJECT IDENTIFIER
        ::= { asEthOamGroup 2 }

    asEthOamAisTable OBJECT-TYPE
        SYNTAX       SEQUENCE OF AsEthOamAisEntry
        MAX-ACCESS   not-accessible
        STATUS       obsolete
        DESCRIPTION  "ETH-AIS Status Table"
        ::= { asEthOamAisGroup 1 }

    asEthOamAisEntry OBJECT-TYPE
        SYNTAX       AsEthOamAisEntry
        MAX-ACCESS   not-accessible
        STATUS       obsolete
        DESCRIPTION  ""
        INDEX        { asEthOamAisMepIndex }
        ::= { asEthOamAisTable 1 }

    AsEthOamAisEntry ::= SEQUENCE {
        asEthOamAisMepIndex   IpeMepId,
        asEthOamAisNEAddress  IpAddress,
        asEthOamAisCondition  SeverityValue,
        asEthOamAisPeriod     INTEGER
    }

    asEthOamAisMepIndex OBJECT-TYPE
        SYNTAX       IpeMepId
        MAX-ACCESS   not-accessible
        STATUS       obsolete
        DESCRIPTION  "Index of this table."
        ::= { asEthOamAisEntry 1 }

    asEthOamAisNEAddress OBJECT-TYPE
        SYNTAX       IpAddress
        MAX-ACCESS   not-accessible
        STATUS       obsolete
        DESCRIPTION  "reserved."
        ::= { asEthOamAisEntry 2 }

    asEthOamAisCondition OBJECT-TYPE
        SYNTAX       SeverityValue
        MAX-ACCESS   read-only
        STATUS       obsolete
        DESCRIPTION  "obsoleted"
        ::= { asEthOamAisEntry 3 }

    asEthOamAisPeriod OBJECT-TYPE
        SYNTAX       INTEGER { invalid(0), period-1s(4), period-1min(6) }
        MAX-ACCESS   read-only
        STATUS       obsolete
        DESCRIPTION  "obsoleted"
        ::= { asEthOamAisEntry 4 }

    asFdbGroup OBJECT IDENTIFIER
        ::= { asETHGroup 6 }

    asFdbEquipmentTable OBJECT-TYPE
        SYNTAX       SEQUENCE OF AsFdbEquipmentEntry
        MAX-ACCESS   not-accessible
        STATUS       current
        DESCRIPTION  "Forwarding Database Status per Equipment."
        ::= { asFdbGroup 1 }

    asFdbEquipmentEntry OBJECT-TYPE
        SYNTAX       AsFdbEquipmentEntry
        MAX-ACCESS   not-accessible
        STATUS       current
        DESCRIPTION  ""
        INDEX        { asFdbEquipmentIndex }
        ::= { asFdbEquipmentTable 1 }

    AsFdbEquipmentEntry ::= SEQUENCE {
        asFdbEquipmentIndex              Integer32,
        asFdbEquipmentNEAddress          IpAddress,
        asFdbEquipmentLearningCount      Gauge32,
        asFdbEquipmentLearningLimitOver  INTEGER
    }

    asFdbEquipmentIndex OBJECT-TYPE
        SYNTAX       Integer32 (1..1)
        MAX-ACCESS   not-accessible
        STATUS       current
        DESCRIPTION  "Index of this table."
        ::= { asFdbEquipmentEntry 1 }

    asFdbEquipmentNEAddress OBJECT-TYPE
        SYNTAX       IpAddress
        MAX-ACCESS   not-accessible
        STATUS       current
        DESCRIPTION  "reserved."
        ::= { asFdbEquipmentEntry 2 }

    asFdbEquipmentLearningCount OBJECT-TYPE
        SYNTAX       Gauge32
        MAX-ACCESS   read-only
        STATUS       current
        DESCRIPTION
            "Total FDB Dynamic Entry Count. the number of forwarding entries
            which is learned currently."
        ::= { asFdbEquipmentEntry 3 }

    asFdbEquipmentLearningLimitOver OBJECT-TYPE
        SYNTAX       INTEGER { notReached(1), reached(2) }
        MAX-ACCESS   read-only
        STATUS       current
        DESCRIPTION
            "Total FDB Full. learning limit status. When
            'asFdbEquipmentLearningCount' reaches
            'provFdbEquipmentNumberOfLearningEntry', this object will be
            changed to 'reached'."
        ::= { asFdbEquipmentEntry 4 }

    asFdbPortTable OBJECT-TYPE
        SYNTAX       SEQUENCE OF AsFdbPortEntry
        MAX-ACCESS   not-accessible
        STATUS       current
        DESCRIPTION  ""
        ::= { asFdbGroup 2 }

    asFdbPortEntry OBJECT-TYPE
        SYNTAX       AsFdbPortEntry
        MAX-ACCESS   not-accessible
        STATUS       current
        DESCRIPTION  "Forwarding Database Status per port."
        INDEX        { asFdbPortIfIndex }
        ::= { asFdbPortTable 1 }

    AsFdbPortEntry ::= SEQUENCE {
        asFdbPortIfIndex            InterfaceIndex,
        asFdbPortNEAddress          IpAddress,
        asFdbPortLearningCount      Gauge32,
        asFdbPortLearningLimitOver  INTEGER
    }

    asFdbPortIfIndex OBJECT-TYPE
        SYNTAX       InterfaceIndex
        MAX-ACCESS   not-accessible
        STATUS       current
        DESCRIPTION  "Index of this table."
        ::= { asFdbPortEntry 1 }

    asFdbPortNEAddress OBJECT-TYPE
        SYNTAX       IpAddress
        MAX-ACCESS   not-accessible
        STATUS       current
        DESCRIPTION  "reserved."
        ::= { asFdbPortEntry 2 }

    asFdbPortLearningCount OBJECT-TYPE
        SYNTAX       Gauge32
        MAX-ACCESS   read-only
        STATUS       current
        DESCRIPTION
            "FDB Dynamic Entry Count. The number of forwarding entries which
            is learned currently."
        ::= { asFdbPortEntry 3 }

    asFdbPortLearningLimitOver OBJECT-TYPE
        SYNTAX       INTEGER { notReached(1), reached(2) }
        MAX-ACCESS   read-only
        STATUS       current
        DESCRIPTION
            "FDB Full. learning limit status. When 'asFdbPortLearningCount'
            reaches corresponding 'provFdbPortLearningLimit', this object
            will be changed to 'reached'."
        ::= { asFdbPortEntry 4 }

    asFdbVlanTable OBJECT-TYPE
        SYNTAX       SEQUENCE OF AsFdbVlanEntry
        MAX-ACCESS   not-accessible
        STATUS       current
        DESCRIPTION  "Forwarding Database status per VLAN."
        ::= { asFdbGroup 3 }

    asFdbVlanEntry OBJECT-TYPE
        SYNTAX       AsFdbVlanEntry
        MAX-ACCESS   not-accessible
        STATUS       current
        DESCRIPTION  ""
        INDEX        { asFdbVlanIndex }
        ::= { asFdbVlanTable 1 }

    AsFdbVlanEntry ::= SEQUENCE {
        asFdbVlanIndex              Integer32,
        asFdbVlanNEAddress          IpAddress,
        asFdbVlanLearningCount      Gauge32,
        asFdbVlanLearningLimitOver  INTEGER
    }

    asFdbVlanIndex OBJECT-TYPE
        SYNTAX       Integer32 (1..4094)
        MAX-ACCESS   not-accessible
        STATUS       current
        DESCRIPTION  "Index of this table."
        ::= { asFdbVlanEntry 1 }

    asFdbVlanNEAddress OBJECT-TYPE
        SYNTAX       IpAddress
        MAX-ACCESS   not-accessible
        STATUS       current
        DESCRIPTION  "reserved."
        ::= { asFdbVlanEntry 2 }

    asFdbVlanLearningCount OBJECT-TYPE
        SYNTAX       Gauge32
        MAX-ACCESS   read-only
        STATUS       current
        DESCRIPTION
            "FDB Dynamic Entry Count per VLAN. The number of forwarding
            entries which is learned currently."
        ::= { asFdbVlanEntry 3 }

    asFdbVlanLearningLimitOver OBJECT-TYPE
        SYNTAX       INTEGER { notReached(1), reached(2) }
        MAX-ACCESS   read-only
        STATUS       current
        DESCRIPTION
            "FDB Full Per VLAN. Learning limit status. When
            'asFdbVlanLearningCount' reaches corresponding
            'provFdbVlanNumberOfLearningEntry', this object will be changed
            to 'reached'."
        ::= { asFdbVlanEntry 4 }

    asLlfGroup OBJECT IDENTIFIER
        ::= { asETHGroup 7 }

    asLlfGroupTable OBJECT-TYPE
        SYNTAX       SEQUENCE OF AsLlfGroupEntry
        MAX-ACCESS   not-accessible
        STATUS       current
        DESCRIPTION  "Link Loss Forwarding(LLF) Status per LLF Group."
        ::= { asLlfGroup 1 }

    asLlfGroupEntry OBJECT-TYPE
        SYNTAX       AsLlfGroupEntry
        MAX-ACCESS   not-accessible
        STATUS       current
        DESCRIPTION  ""
        INDEX        { asLlfGroupIndex }
        ::= { asLlfGroupTable 1 }

    AsLlfGroupEntry ::= SEQUENCE {
        asLlfGroupIndex       Integer32,
        asLlfGroupNEAddress   IpAddress,
        asLlfGroupForceClose  INTEGER,
        asLlfGroupTimeout     INTEGER
    }

    asLlfGroupIndex OBJECT-TYPE
        SYNTAX       Integer32 (1..16)
        MAX-ACCESS   not-accessible
        STATUS       current
        DESCRIPTION  "Index of this table."
        ::= { asLlfGroupEntry 1 }

    asLlfGroupNEAddress OBJECT-TYPE
        SYNTAX       IpAddress
        MAX-ACCESS   not-accessible
        STATUS       current
        DESCRIPTION  "reserved."
        ::= { asLlfGroupEntry 2 }

    asLlfGroupForceClose OBJECT-TYPE
        SYNTAX       INTEGER { not-forceclose(1), forceclose(2) }
        MAX-ACCESS   read-only
        STATUS       current
        DESCRIPTION
            "LLF close status. 'forceclose' means that edge port which is
            assigned to the LLF group is closed because of LLF."
        ::= { asLlfGroupEntry 3 }

    asLlfGroupTimeout OBJECT-TYPE
        SYNTAX       INTEGER { received(1), timeout(2) }
        MAX-ACCESS   read-only
        STATUS       current
        DESCRIPTION
            "LLF Timeout Status. The periodic LLF messages is not received."
        ::= { asLlfGroupEntry 4 }

    asLlfReceiveInfoTable OBJECT-TYPE
        SYNTAX       SEQUENCE OF AsLlfReceiveInfoEntry
        MAX-ACCESS   not-accessible
        STATUS       obsolete
        DESCRIPTION  "Link Loss Forwarding (LLF) Status per port."
        ::= { asLlfGroup 2 }

    asLlfReceiveInfoEntry OBJECT-TYPE
        SYNTAX       AsLlfReceiveInfoEntry
        MAX-ACCESS   not-accessible
        STATUS       obsolete
        DESCRIPTION  ""
        INDEX        { asLlfReceiveInfoIfIndex, asLlfReceiveInfoGroupIndex }
        ::= { asLlfReceiveInfoTable 1 }

    AsLlfReceiveInfoEntry ::= SEQUENCE {
        asLlfReceiveInfoIfIndex     InterfaceIndex,
        asLlfReceiveInfoGroupIndex  Integer32,
        asLlfReceiveInfoNEAddress   IpAddress,
        asLlfReceiveInfoLinkSts     INTEGER
    }

    asLlfReceiveInfoIfIndex OBJECT-TYPE
        SYNTAX       InterfaceIndex
        MAX-ACCESS   not-accessible
        STATUS       obsolete
        DESCRIPTION  "Index of this table."
        ::= { asLlfReceiveInfoEntry 1 }

    asLlfReceiveInfoGroupIndex OBJECT-TYPE
        SYNTAX       Integer32 (1..16)
        MAX-ACCESS   not-accessible
        STATUS       obsolete
        DESCRIPTION  "Index of this table."
        ::= { asLlfReceiveInfoEntry 2 }

    asLlfReceiveInfoNEAddress OBJECT-TYPE
        SYNTAX       IpAddress
        MAX-ACCESS   not-accessible
        STATUS       obsolete
        DESCRIPTION  "reserved."
        ::= { asLlfReceiveInfoEntry 3 }

    asLlfReceiveInfoLinkSts OBJECT-TYPE
        SYNTAX       INTEGER { down(1), up(2) }
        MAX-ACCESS   read-only
        STATUS       obsolete
        DESCRIPTION  "LLF Link Information which is received from peer."
        ::= { asLlfReceiveInfoEntry 4 }

    asETHPortGroup OBJECT IDENTIFIER
        ::= { asETHGroup 8 }

    asETHPortTable OBJECT-TYPE
        SYNTAX       SEQUENCE OF AsETHPortEntry
        MAX-ACCESS   not-accessible
        STATUS       current
        DESCRIPTION  "Ethernet Port Status Table."
        ::= { asETHPortGroup 1 }

    asETHPortEntry OBJECT-TYPE
        SYNTAX       AsETHPortEntry
        MAX-ACCESS   not-accessible
        STATUS       current
        DESCRIPTION  ""
        INDEX        { asETHPortIfIndex }
        ::= { asETHPortTable 1 }

    AsETHPortEntry ::= SEQUENCE {
        asETHPortIfIndex          InterfaceIndex,
        asETHPortNEAddress        IpAddress,
        asETHPortInterfaceType    INTEGER,
        asETHPortSpeedDuplex      INTEGER,
        asETHPortFlowControl      INTEGER,
        asETHPortMDIMDIX          INTEGER,
        asETHPortLinkStatus       SeverityValue,
        asETHPortAdminStatus      INTEGER,
        asETHPortSFPEquip         SeverityValue,
        asETHPortSFPLos           SeverityValue,
        asETHPortSFPTxError       SeverityValue,
        asETHPortSFPTypeMismatch  SeverityValue,
        asETHPortOperStatus       INTEGER,
        asETHPortLlfOamReceived   INTEGER
    }

    asETHPortIfIndex OBJECT-TYPE
        SYNTAX       InterfaceIndex
        MAX-ACCESS   not-accessible
        STATUS       current
        DESCRIPTION  "Index of this table."
        ::= { asETHPortEntry 1 }

    asETHPortNEAddress OBJECT-TYPE
        SYNTAX       IpAddress
        MAX-ACCESS   not-accessible
        STATUS       current
        DESCRIPTION  "reserved."
        ::= { asETHPortEntry 2 }

    asETHPortInterfaceType OBJECT-TYPE
        SYNTAX       INTEGER { invalid(0), fiber(1), copper(2) }
        MAX-ACCESS   read-only
        STATUS       current
        DESCRIPTION
            "GbE SFP Port Type Status. This object represents interface type
            which is installed currently."
        ::= { asETHPortEntry 3 }

    asETHPortSpeedDuplex OBJECT-TYPE
        SYNTAX       INTEGER {
                         invalid(0),
                         s10M-HALF(1),
                         s10M-FULL(2),
                         s100M-HALF(3),
                         s100M-FULL(4),
                         s1000M-FULL(5)
                     }
        MAX-ACCESS   read-only
        STATUS       current
        DESCRIPTION  "GbE Speed & Duplex Status."
        ::= { asETHPortEntry 4 }

    asETHPortFlowControl OBJECT-TYPE
        SYNTAX       INTEGER { disable(1), enable(2) }
        MAX-ACCESS   read-only
        STATUS       current
        DESCRIPTION  "GbE Flow Control Status."
        ::= { asETHPortEntry 5 }

    asETHPortMDIMDIX OBJECT-TYPE
        SYNTAX       INTEGER { invalid(0), mdi(1), mdi-x(2) }
        MAX-ACCESS   read-only
        STATUS       current
        DESCRIPTION  "GbE MDI / MDI-X Status."
        ::= { asETHPortEntry 6 }

    asETHPortLinkStatus OBJECT-TYPE
        SYNTAX       SeverityValue
        MAX-ACCESS   read-only
        STATUS       current
        DESCRIPTION  "GbE LAN Link Alarm."
        ::= { asETHPortEntry 7 }

    asETHPortAdminStatus OBJECT-TYPE
        SYNTAX       INTEGER { normal(1), force(2), oamSend(3) }
        MAX-ACCESS   read-only
        STATUS       current
        DESCRIPTION
            "GbE LLF Status. When the port is closed by LLF, the object will
            be changed to 'force'.
            But if 'provLlfPortMode' is configured to 'edgeOamSend', this
            object will be changed to 'oamSend' when the port is controlled
            by LLF."
        ::= { asETHPortEntry 8 }

    asETHPortSFPEquip OBJECT-TYPE
        SYNTAX       SeverityValue
        MAX-ACCESS   read-only
        STATUS       current
        DESCRIPTION  "GbE SFP Removed Alarm."
        ::= { asETHPortEntry 9 }

    asETHPortSFPLos OBJECT-TYPE
        SYNTAX       SeverityValue
        MAX-ACCESS   read-only
        STATUS       current
        DESCRIPTION  "GbE ETH LOS Alarm."
        ::= { asETHPortEntry 10 }

    asETHPortSFPTxError OBJECT-TYPE
        SYNTAX       SeverityValue
        MAX-ACCESS   read-only
        STATUS       current
        DESCRIPTION  "GbE ETH TF (Transmit FAIL) Alarm."
        ::= { asETHPortEntry 11 }

    asETHPortSFPTypeMismatch OBJECT-TYPE
        SYNTAX       SeverityValue
        MAX-ACCESS   read-only
        STATUS       current
        DESCRIPTION
            "GbE SFP Type Mismatch Alarm. This object reports that the
            provisioned interface type and the installed media type are
            inconsistent."
        ::= { asETHPortEntry 12 }

    asETHPortOperStatus OBJECT-TYPE
        SYNTAX       INTEGER { invalid(0), linkDown(1), linkUp(2) }
        MAX-ACCESS   read-only
        STATUS       current
        DESCRIPTION
            "GbE ETH LAN Link Status. This object is not suppressed by the
            lower layer alarms."
        ::= { asETHPortEntry 13 }

    asETHPortLlfOamReceived OBJECT-TYPE
        SYNTAX       INTEGER { invalid(0), normal(1), receive(2) }
        MAX-ACCESS   read-only
        STATUS       current
        DESCRIPTION
            "GbE LLF message receive status.
            When the port received LLF request messages, the object will
            return the value 'receive'."
        ::= { asETHPortEntry 14 }

    asSyncETHGroup OBJECT IDENTIFIER
        ::= { asETHGroup 9 }

    asSyncETHTable OBJECT-TYPE
        SYNTAX       SEQUENCE OF AsSyncETHEntry
        MAX-ACCESS   not-accessible
        STATUS       current
        DESCRIPTION  "Sync Ethernet Status table."
        ::= { asSyncETHGroup 2 }

    asSyncETHEntry OBJECT-TYPE
        SYNTAX       AsSyncETHEntry
        MAX-ACCESS   not-accessible
        STATUS       current
        DESCRIPTION  ""
        INDEX        { asSyncETHIfIndex }
        ::= { asSyncETHTable 1 }

    AsSyncETHEntry ::= SEQUENCE {
        asSyncETHIfIndex     InterfaceIndex,
        asSyncETHNEAddress   IpAddress,
        asSyncETHPortCLKSts  Integer32
    }

    asSyncETHIfIndex OBJECT-TYPE
        SYNTAX       InterfaceIndex
        MAX-ACCESS   read-only
        STATUS       current
        DESCRIPTION  "Index of this table."
        ::= { asSyncETHEntry 1 }

    asSyncETHNEAddress OBJECT-TYPE
        SYNTAX       IpAddress
        MAX-ACCESS   read-only
        STATUS       current
        DESCRIPTION  "reserved."
        ::= { asSyncETHEntry 2 }

    asSyncETHPortCLKSts OBJECT-TYPE
        SYNTAX       Integer32
        MAX-ACCESS   read-only
        STATUS       current
        DESCRIPTION  "Sync ETH Port CLK Status."
        ::= { asSyncETHEntry 3 }

    asQosGroup OBJECT IDENTIFIER
        ::= { asETHGroup 10 }

    asQosTable OBJECT-TYPE
        SYNTAX       SEQUENCE OF AsQosEntry
        MAX-ACCESS   not-accessible
        STATUS       obsolete
        DESCRIPTION  "Qos Information per port."
        ::= { asQosGroup 1 }

    asQosEntry OBJECT-TYPE
        SYNTAX       AsQosEntry
        MAX-ACCESS   not-accessible
        STATUS       obsolete
        DESCRIPTION  ""
        INDEX        { asQosPortindex }
        ::= { asQosTable 1 }

    AsQosEntry ::= SEQUENCE {
        asQosPortindex     InterfaceIndex,
        asQosNEAddress     IpAddress,
        asQosAmrBandWidth  Integer32
    }

    asQosPortindex OBJECT-TYPE
        SYNTAX       InterfaceIndex
        MAX-ACCESS   not-accessible
        STATUS       obsolete
        DESCRIPTION  "Index of this table."
        ::= { asQosEntry 1 }

    asQosNEAddress OBJECT-TYPE
        SYNTAX       IpAddress
        MAX-ACCESS   not-accessible
        STATUS       obsolete
        DESCRIPTION  "reserved."
        ::= { asQosEntry 2 }

    asQosAmrBandWidth OBJECT-TYPE
        SYNTAX       Integer32
        MAX-ACCESS   read-only
        STATUS       obsolete
        DESCRIPTION
            "The value of Qos bandwidth which is  determined by the smaller
            value of the followings.
             AMR bandwidth - E1 bandwidth - total EIR bandwidth.
              Or
             AMR bandwidth - E1 bandwidth - total CIR bandwidth."
        ::= { asQosEntry 3 }

    asETHCardGroup OBJECT IDENTIFIER
        ::= { asETHGroup 32 }

    asETHCardTable OBJECT-TYPE
        SYNTAX       SEQUENCE OF AsETHCardEntry
        MAX-ACCESS   not-accessible
        STATUS       current
        DESCRIPTION  "ETH Card Status table."
        ::= { asETHCardGroup 1 }

    asETHCardEntry OBJECT-TYPE
        SYNTAX       AsETHCardEntry
        MAX-ACCESS   not-accessible
        STATUS       current
        DESCRIPTION  ""
        INDEX        { asETHCardIndex }
        ::= { asETHCardTable 1 }

    AsETHCardEntry ::= SEQUENCE {
        asETHCardIndex      Integer32,
        asETHCardNEAddress  IpAddress,
        ethAlarm            SeverityValue,
        ethComFailAlarm     SeverityValue,
        ethUnequipped       SeverityValue,
        ethTypeMismatch     SeverityValue,
        ethBusErrorTx       SeverityValue,
        ethBusErrorRx       SeverityValue
    }

    asETHCardIndex OBJECT-TYPE
        SYNTAX       Integer32
        MAX-ACCESS   not-accessible
        STATUS       current
        DESCRIPTION  "Index of this table."
        ::= { asETHCardEntry 1 }

    asETHCardNEAddress OBJECT-TYPE
        SYNTAX       IpAddress
        MAX-ACCESS   not-accessible
        STATUS       current
        DESCRIPTION  "reserved."
        ::= { asETHCardEntry 2 }

    ethAlarm OBJECT-TYPE
        SYNTAX       SeverityValue
        MAX-ACCESS   read-only
        STATUS       current
        DESCRIPTION  "GbE Module Alarm."
        ::= { asETHCardEntry 3 }

    ethComFailAlarm OBJECT-TYPE
        SYNTAX       SeverityValue
        MAX-ACCESS   read-only
        STATUS       current
        DESCRIPTION  "GbE Communication FAIL Alarm."
        ::= { asETHCardEntry 4 }

    ethUnequipped OBJECT-TYPE
        SYNTAX       SeverityValue
        MAX-ACCESS   read-only
        STATUS       current
        DESCRIPTION  "GbE Unequipped Alarm."
        ::= { asETHCardEntry 5 }

    ethTypeMismatch OBJECT-TYPE
        SYNTAX       SeverityValue
        MAX-ACCESS   read-only
        STATUS       current
        DESCRIPTION  "GbE Type Mismatch Alarm."
        ::= { asETHCardEntry 6 }

    ethBusErrorTx OBJECT-TYPE
        SYNTAX       SeverityValue
        MAX-ACCESS   read-only
        STATUS       current
        DESCRIPTION  "GbE TX Bus Error Alarm."
        ::= { asETHCardEntry 7 }

    ethBusErrorRx OBJECT-TYPE
        SYNTAX       SeverityValue
        MAX-ACCESS   read-only
        STATUS       current
        DESCRIPTION  "GbE RX Bus Error Alarm."
        ::= { asETHCardEntry 8 }

    asCommonGroup OBJECT IDENTIFIER
        ::= { alarmStatusGroup 14 }

    iduCommonTable OBJECT-TYPE
        SYNTAX       SEQUENCE OF IduCommonEntry
        MAX-ACCESS   not-accessible
        STATUS       current
        DESCRIPTION  "Equipment Configuration Status Table."
        ::= { asCommonGroup 1 }

    iduCommonEntry OBJECT-TYPE
        SYNTAX       IduCommonEntry
        MAX-ACCESS   not-accessible
        STATUS       current
        DESCRIPTION  ""
        INDEX        { iduCommonIndex }
        ::= { iduCommonTable 1 }

    IduCommonEntry ::= SEQUENCE {
        iduCommonIndex      INTEGER,
        iduCommonNEAddress  IpAddress,
        equipConfigStatus   Integer32
    }

    iduCommonIndex OBJECT-TYPE
        SYNTAX       INTEGER { iduCommon(1) }
        MAX-ACCESS   not-accessible
        STATUS       current
        DESCRIPTION  "Index of this table."
        ::= { iduCommonEntry 1 }

    iduCommonNEAddress OBJECT-TYPE
        SYNTAX       IpAddress
        MAX-ACCESS   not-accessible
        STATUS       current
        DESCRIPTION  "reserved."
        ::= { iduCommonEntry 2 }

    equipConfigStatus OBJECT-TYPE
        SYNTAX       Integer32
        MAX-ACCESS   read-only
        STATUS       current
        DESCRIPTION
            "Equipment Configuration Status. The object is used for
            determining the status synchronization method for the manager
            entity."
        ::= { iduCommonEntry 3 }

    asCommonTable OBJECT-TYPE
        SYNTAX       SEQUENCE OF AsCommonEntry
        MAX-ACCESS   not-accessible
        STATUS       current
        DESCRIPTION  "Installed Card Status table."
        ::= { asCommonGroup 2 }

    asCommonEntry OBJECT-TYPE
        SYNTAX       AsCommonEntry
        MAX-ACCESS   not-accessible
        STATUS       current
        DESCRIPTION  ""
        INDEX        { asCommonIndex }
        ::= { asCommonTable 1 }

    AsCommonEntry ::= SEQUENCE {
        asCommonIndex        Integer32,
        asCommonNEAddress    IpAddress,
        asUserInterface      INTEGER,
        asConfigStatus       INTEGER,
        asClk2mType          INTEGER,
        asClk2mConfigStatus  INTEGER
    }

    asCommonIndex OBJECT-TYPE
        SYNTAX       Integer32
        MAX-ACCESS   not-accessible
        STATUS       current
        DESCRIPTION  "Index of this table."
        ::= { asCommonEntry 1 }

    asCommonNEAddress OBJECT-TYPE
        SYNTAX       IpAddress
        MAX-ACCESS   not-accessible
        STATUS       current
        DESCRIPTION  "reserved."
        ::= { asCommonEntry 2 }

    asUserInterface OBJECT-TYPE
        SYNTAX       INTEGER {
                         invalid(0),
                         notUsed(1),
                         modem(2),
                         e1(3),
                         gbex4p(6),
                         mse(9),
                         aux(11),
                         stm1x2p(12),
                         clk2m(13),
                         ps(14),
                         fan(15),
                         term(16),
                         main(17),
                         modemE(19),
                         unknown(99)
                     }
        MAX-ACCESS   read-only
        STATUS       current
        DESCRIPTION  "Installed card type."
        ::= { asCommonEntry 3 }

    asConfigStatus OBJECT-TYPE
        SYNTAX       INTEGER {
                         invalid(0),
                         unequipped(1),
                         configured(2),
                         unconfigured(3),
                         mismatch(4)
                     }
        MAX-ACCESS   read-only
        STATUS       current
        DESCRIPTION
            "Configuration status of installed card. The value is determined
            from provisioned card type and installed card type."
        ::= { asCommonEntry 4 }

    asClk2mType OBJECT-TYPE
        SYNTAX       INTEGER { invalid(0), notUsed(1), clk2m(2), unknown(99) }
        MAX-ACCESS   read-only
        STATUS       current
        DESCRIPTION  "Installed CLK type."
        ::= { asCommonEntry 5 }

    asClk2mConfigStatus OBJECT-TYPE
        SYNTAX       INTEGER {
                         invalid(0),
                         unequipped(1),
                         configured(2),
                         unconfigured(3),
                         mismatch(4)
                     }
        MAX-ACCESS   read-only
        STATUS       current
        DESCRIPTION
            "Configuration status of CLK card. The value is determined from
            provisioned CLK type and installed CLK type."
        ::= { asCommonEntry 6 }

    asProtectionGroup OBJECT IDENTIFIER
        ::= { alarmStatusGroup 33 }

    asStm1ApsTable OBJECT-TYPE
        SYNTAX       SEQUENCE OF AsStm1ApsEntry
        MAX-ACCESS   not-accessible
        STATUS       current
        DESCRIPTION
            "APS Status Table. This table is created automatically when the
            APS is configured."
        ::= { asProtectionGroup 1 }

    asStm1ApsEntry OBJECT-TYPE
        SYNTAX       AsStm1ApsEntry
        MAX-ACCESS   not-accessible
        STATUS       current
        DESCRIPTION  ""
        INDEX        { asStm1ApsIfIndex }
        ::= { asStm1ApsTable 1 }

    AsStm1ApsEntry ::= SEQUENCE {
        asStm1ApsIfIndex        InterfaceIndex,
        asStm1ApsNEAddress      IpAddress,
        apsProtectionStatusCh1  INTEGER,
        apsProtectionStatusCh2  INTEGER,
        apsOnlineStatus         INTEGER,
        apsLockinStatus         INTEGER,
        apsSwStatus             INTEGER
    }

    asStm1ApsIfIndex OBJECT-TYPE
        SYNTAX       InterfaceIndex
        MAX-ACCESS   not-accessible
        STATUS       current
        DESCRIPTION  "Index of this table."
        ::= { asStm1ApsEntry 1 }

    asStm1ApsNEAddress OBJECT-TYPE
        SYNTAX       IpAddress
        MAX-ACCESS   not-accessible
        STATUS       current
        DESCRIPTION  "reserved."
        ::= { asStm1ApsEntry 2 }

    apsProtectionStatusCh1 OBJECT-TYPE
        SYNTAX       INTEGER { fs(1), sf(2), sd(3), ms(4), nr(5) }
        MAX-ACCESS   read-only
        STATUS       current
        DESCRIPTION  "APS Protection Status for Ch1"
        ::= { asStm1ApsEntry 3 }

    apsProtectionStatusCh2 OBJECT-TYPE
        SYNTAX       INTEGER { fs(1), sf(2), sd(3), ms(4), nr(5) }
        MAX-ACCESS   read-only
        STATUS       current
        DESCRIPTION  "APS Protection Status for Ch2"
        ::= { asStm1ApsEntry 4 }

    apsOnlineStatus OBJECT-TYPE
        SYNTAX       INTEGER { work(1), protection(2) }
        MAX-ACCESS   read-only
        STATUS       current
        DESCRIPTION  "APS Online Status"
        ::= { asStm1ApsEntry 5 }

    apsLockinStatus OBJECT-TYPE
        SYNTAX       INTEGER { normal(1), lockin(2) }
        MAX-ACCESS   read-only
        STATUS       current
        DESCRIPTION  "APS Lockin Status"
        ::= { asStm1ApsEntry 6 }

    apsSwStatus OBJECT-TYPE
        SYNTAX       INTEGER { work(1), protection(2) }
        MAX-ACCESS   read-only
        STATUS       current
        DESCRIPTION  "APS Switch Status"
        ::= { asStm1ApsEntry 7 }

    asLicenseGroup OBJECT IDENTIFIER
        ::= { alarmStatusGroup 45 }

    asLicenseAlarmTable OBJECT-TYPE
        SYNTAX       SEQUENCE OF AsLicenseAlarmEntry
        MAX-ACCESS   not-accessible
        STATUS       current
        DESCRIPTION  "License Alarm Table."
        ::= { asLicenseGroup 1 }

    asLicenseAlarmEntry OBJECT-TYPE
        SYNTAX       AsLicenseAlarmEntry
        MAX-ACCESS   not-accessible
        STATUS       current
        DESCRIPTION  ""
        INDEX        { asLicenseAlarmIndex }
        ::= { asLicenseAlarmTable 1 }

    AsLicenseAlarmEntry ::= SEQUENCE {
        asLicenseAlarmIndex      Integer32,
        asLicenseAlarmNEAddress  IpAddress,
        asLicenseAlarm           SeverityValue
    }

    asLicenseAlarmIndex OBJECT-TYPE
        SYNTAX       Integer32 (1..1)
        MAX-ACCESS   not-accessible
        STATUS       current
        DESCRIPTION  "Index of this table."
        ::= { asLicenseAlarmEntry 1 }

    asLicenseAlarmNEAddress OBJECT-TYPE
        SYNTAX       IpAddress
        MAX-ACCESS   not-accessible
        STATUS       current
        DESCRIPTION  "reserved."
        ::= { asLicenseAlarmEntry 2 }

    asLicenseAlarm OBJECT-TYPE
        SYNTAX       SeverityValue
        MAX-ACCESS   read-only
        STATUS       current
        DESCRIPTION
            "License Alarm.
            The alarm will be asserted when the configuration and install
            license are mismatch. The following operations can be trigger the
            alarm.
              - license downgrade
              - multiple chassis configuration (2U XPIC)
            The alarm will be cleared when the conditions mentioned above are
            cleared."
        ::= { asLicenseAlarmEntry 3 }

    esCommonTable OBJECT-TYPE
        SYNTAX       SEQUENCE OF EsCommonEntry
        MAX-ACCESS   not-accessible
        STATUS       current
        DESCRIPTION  "Configure Card information."
        ::= { equipmentSetUpGroup 1 }

    esCommonEntry OBJECT-TYPE
        SYNTAX       EsCommonEntry
        MAX-ACCESS   not-accessible
        STATUS       current
        DESCRIPTION
            "The entries are created automatically per each slot when the
            agent boots."
        INDEX        { esCommonIndex }
        ::= { esCommonTable 1 }

    EsCommonEntry ::= SEQUENCE {
        esCommonIndex      Integer32,
        esCommonNEAddress  IpAddress,
        esUserInterface    INTEGER,
        esClk2mType        INTEGER
    }

    esCommonIndex OBJECT-TYPE
        SYNTAX       Integer32
        MAX-ACCESS   not-accessible
        STATUS       current
        DESCRIPTION  "Index of this table."
        ::= { esCommonEntry 1 }

    esCommonNEAddress OBJECT-TYPE
        SYNTAX       IpAddress
        MAX-ACCESS   not-accessible
        STATUS       current
        DESCRIPTION  "reserved."
        ::= { esCommonEntry 2 }

    esUserInterface OBJECT-TYPE
        SYNTAX       INTEGER {
                         invalid(0),
                         notUsed(1),
                         modem(2),
                         e1(3),
                         gbex4p(6),
                         mse(9),
                         aux(11),
                         stm1x2p(12),
                         clk2m(13),
                         ps(14),
                         fan(15),
                         term(16),
                         main(17),
                         modemE(19)
                     }
        MAX-ACCESS   read-write
        STATUS       current
        DESCRIPTION
            "Equipment Configuration. This object configures card type to
            use. If the object is set to 'notUsed' from other value, the
            related objects are automatically removed. For example, the
            crossconnect whose end point is located on the removed card, the
            Ethernt OAM MEP entities, the clock reference on the card, and so
            on."
        ::= { esCommonEntry 3 }

    esClk2mType OBJECT-TYPE
        SYNTAX       INTEGER { invalid(0), notUsed(1), clk2m(2) }
        MAX-ACCESS   read-write
        STATUS       current
        DESCRIPTION
            "EXT CLK Type. This object configures Clock card information.
            This object is available only for SLOT whose card type is ctrl."
        ::= { esCommonEntry 4 }

    esModemTable OBJECT-TYPE
        SYNTAX       SEQUENCE OF EsModemEntry
        MAX-ACCESS   not-accessible
        STATUS       current
        DESCRIPTION  "Configure Radio Parameters."
        ::= { equipmentSetUpGroup 2 }

    esModemEntry OBJECT-TYPE
        SYNTAX       EsModemEntry
        MAX-ACCESS   not-accessible
        STATUS       current
        DESCRIPTION  ""
        INDEX        { esModemIfIndex }
        ::= { esModemTable 1 }

    EsModemEntry ::= SEQUENCE {
        esModemIfIndex                  InterfaceIndex,
        esModemNEAddress                IpAddress,
        esModemTxFreq                   DisplayString,
        esModemRxFreq                   DisplayString,
        esModemTxPowerCont              INTEGER,
        esModemFrameID                  Integer32,
        esModemModulation               INTEGER,
        esModemChSpacing                INTEGER,
        esModemAmrOperation             OffOnValue,
        esModemAmrRangeQPSK             OffOnValue,
        esModemAmrRange16QAM            OffOnValue,
        esModemAmrRange32QAM            OffOnValue,
        esModemAmrRange64QAM            OffOnValue,
        esModemAmrRange128QAM           OffOnValue,
        esModemAmrRange256QAM           OffOnValue,
        esModemConfiguration            INTEGER,
        esModemGroupSetting             INTEGER,
        esModemRadioMode                INTEGER,
        esTdmEtherMapping               Integer32,
        esTdmEtherMappingAmrQPSK        Integer32,
        esTdmEtherMappingAmr16QAM       Integer32,
        esTdmEtherMappingAmr32QAM       Integer32,
        esTdmEtherMappingAmr64QAM       Integer32,
        esTdmEtherMappingAmr128QAM      Integer32,
        esTdmEtherMappingAmr256QAM      Integer32,
        esTdmEtherMappingRst            Integer32,
        esTdmEtherMappingRstAmrQPSK     Integer32,
        esTdmEtherMappingRstAmr16QAM    Integer32,
        esTdmEtherMappingRstAmr32QAM    Integer32,
        esTdmEtherMappingRstAmr64QAM    Integer32,
        esTdmEtherMappingRstAmr128QAM   Integer32,
        esTdmEtherMappingRstAmr256QAM   Integer32,
        esModemAmrRange512QAM           OffOnValue,
        esModemAmrRange1024QAM          OffOnValue,
        esTdmEtherMappingAmr512QAM      Integer32,
        esTdmEtherMappingAmr1024QAM     Integer32,
        esTdmEtherMappingRstAmr512QAM   Integer32,
        esTdmEtherMappingRstAmr1024QAM  Integer32,
        esModemGroupMode                INTEGER,
        esModemAmrRange2048QAM          OffOnValue,
        esTdmEtherMappingAmr2048QAM     Integer32,
        esTdmEtherMappingRstAmr2048QAM  Integer32,
        esModemEthTransparentClockPath  Integer32
    }

    esModemIfIndex OBJECT-TYPE
        SYNTAX       InterfaceIndex
        MAX-ACCESS   not-accessible
        STATUS       current
        DESCRIPTION  "Index of this table."
        ::= { esModemEntry 1 }

    esModemNEAddress OBJECT-TYPE
        SYNTAX       IpAddress
        MAX-ACCESS   not-accessible
        STATUS       current
        DESCRIPTION  "reserved."
        ::= { esModemEntry 2 }

    esModemTxFreq OBJECT-TYPE
        SYNTAX       DisplayString (SIZE(1..9))
        MAX-ACCESS   read-write
        STATUS       current
        DESCRIPTION  "Tx RF Frequency."
        ::= { esModemEntry 3 }

    esModemRxFreq OBJECT-TYPE
        SYNTAX       DisplayString (SIZE(1..9))
        MAX-ACCESS   read-write
        STATUS       current
        DESCRIPTION  "Rx RF Frequency."
        ::= { esModemEntry 4 }

    esModemTxPowerCont OBJECT-TYPE
        SYNTAX       INTEGER { invalid(0), mtpc(1), atpc(2) }
        MAX-ACCESS   read-write
        STATUS       current
        DESCRIPTION  "Tx Power Control."
        ::= { esModemEntry 5 }

    esModemFrameID OBJECT-TYPE
        SYNTAX       Integer32 (0..32)
        MAX-ACCESS   read-write
        STATUS       current
        DESCRIPTION  "Frame ID."
        ::= { esModemEntry 6 }

    esModemModulation OBJECT-TYPE
        SYNTAX       INTEGER {
                         invalid(0),
                         qpsk(1),
                         qam16(2),
                         qam32(3),
                         qam64(4),
                         qam128(5),
                         qam256(6),
                         qam512(7),
                         qam1024(8),
                         qam2048(9)
                     }
        MAX-ACCESS   read-write
        STATUS       current
        DESCRIPTION
            "Reference Modulation.
            If the provisioned card does not support the specified modulation
            or the installed license is not enough, the agent will reject the
            request.
            When this parameter changes, the agent will adjust the E1/RST
            mappings according to this parameter. And the XCs whose channel
            number is exceeded to the E1/RST mapping number are automatically
            deleted."
        ::= { esModemEntry 7 }

    esModemChSpacing OBJECT-TYPE
        SYNTAX       INTEGER {
                         invalid(0),
                         cs7m(2),
                         cs14m(3),
                         cs28m(4),
                         cs56m(5),
                         cs40m(6)
                     }
        MAX-ACCESS   read-write
        STATUS       current
        DESCRIPTION
            "Channel Spacing.
            If the card does not support the specified parameter, the agent
            will reject the request.
            When this parameter changes, the agent will adjust the E1/RST
            mappings according to this parameter. And the XCs whose channel
            number is exceeded to the E1/RST mapping number are automatically
            deleted."
        ::= { esModemEntry 8 }

    esModemAmrOperation OBJECT-TYPE
        SYNTAX       OffOnValue
        MAX-ACCESS   read-write
        STATUS       current
        DESCRIPTION
            "AMR Operation.
            When this parameter changes, the agent will adjust the E1/RST
            mappings according to this parameter. And the XCs whose channel
            number is exceeded to the E1/RST mapping number are automatically
            deleted."
        ::= { esModemEntry 9 }

    esModemAmrRangeQPSK OBJECT-TYPE
        SYNTAX       OffOnValue
        MAX-ACCESS   read-write
        STATUS       current
        DESCRIPTION
            "AMR Range (QPSK).
            When this parameter changes, the agent will adjust the E1/RST
            mappings according to this parameter. And the XCs whose channel
            number is exceeded to the E1/RST mapping number are automatically
            deleted."
        ::= { esModemEntry 10 }

    esModemAmrRange16QAM OBJECT-TYPE
        SYNTAX       OffOnValue
        MAX-ACCESS   read-write
        STATUS       current
        DESCRIPTION
            "AMR Ragne (16QAM).
            When this parameter changes, the agent will adjust the E1/RST
            mappings according to this parameter. And the XCs whose channel
            number is exceeded to the E1/RST mapping number are automatically
            deleted."
        ::= { esModemEntry 11 }

    esModemAmrRange32QAM OBJECT-TYPE
        SYNTAX       OffOnValue
        MAX-ACCESS   read-write
        STATUS       current
        DESCRIPTION
            "AMR Range (32QAM).
            When this parameter changes, the agent will adjust the E1/RST
            mappings according to this parameter. And the XCs whose channel
            number is exceeded to the E1/RST mapping number are automatically
            deleted."
        ::= { esModemEntry 12 }

    esModemAmrRange64QAM OBJECT-TYPE
        SYNTAX       OffOnValue
        MAX-ACCESS   read-write
        STATUS       current
        DESCRIPTION
            "AMR Range (64QAM).
            When this parameter changes, the agent will adjust the E1/RST
            mappings according to this parameter. And the XCs whose channel
            number is exceeded to the E1/RST mapping number are automatically
            deleted."
        ::= { esModemEntry 13 }

    esModemAmrRange128QAM OBJECT-TYPE
        SYNTAX       OffOnValue
        MAX-ACCESS   read-write
        STATUS       current
        DESCRIPTION
            "AMR Range (128QAM).
            When this parameter changes, the agent will adjust the E1/RST
            mappings according to this parameter. And the XCs whose channel
            number is exceeded to the E1/RST mapping number are automatically
            deleted."
        ::= { esModemEntry 14 }

    esModemAmrRange256QAM OBJECT-TYPE
        SYNTAX       OffOnValue
        MAX-ACCESS   read-write
        STATUS       current
        DESCRIPTION
            "AMR Range (256QAM).
            When this parameter changes, the agent will adjust the E1/RST
            mappings according to this parameter. And the XCs whose channel
            number is exceeded to the E1/RST mapping number are automatically
            deleted."
        ::= { esModemEntry 15 }

    esModemConfiguration OBJECT-TYPE
        SYNTAX       INTEGER { ivalid(0), notUsed(1), used(2) }
        MAX-ACCESS   read-write
        STATUS       current
        DESCRIPTION
            "This object configure the MODEM usage. When the object is set to
            'notUsed', the corresponding modem will be disabled.
            This function is available only for the iPASOLINK200."
        ::= { esModemEntry 16 }

    esModemGroupSetting OBJECT-TYPE
        SYNTAX       INTEGER {
                         notUsed(0),
                         group1(1),
                         group2(2),
                         group3(3),
                         group4(4),
                         group5(5),
                         group6(6),
                         group7(7)
                     }
        MAX-ACCESS   read-write
        STATUS       current
        DESCRIPTION
            "Radio Traffic Aggregation. The modem ports whose
            'esModemGroupSetting' has same value construct the Radio Link
            Aggregation.
            This configuration is automatically cleared when the SWG
            configuration ('esSWGConfiguration') is changed."
        ::= { esModemEntry 17 }

    esModemRadioMode OBJECT-TYPE
        SYNTAX       INTEGER { invalid(0), highCapacity(1), highSystemGain(2) }
        MAX-ACCESS   read-write
        STATUS       current
        DESCRIPTION
            "Radio Mode.
            When this parameter changes, the agent will adjust the E1/RST
            mappings according to this parameter. And the XCs whose channel
            number is exceeded to the E1/RST mapping number are automatically
            deleted."
        ::= { esModemEntry 18 }

    esTdmEtherMapping OBJECT-TYPE
        SYNTAX       Integer32
        MAX-ACCESS   read-write
        STATUS       current
        DESCRIPTION
            "E1 Mapping. This object configures the E1 channel count which is
            mapped to the radio link.
            When this parameter changes, the agent will adjust the E1/RST
            mappings according to this parameter. And the XCs whose channel
            number is exceeded to the E1/RST mapping number are automatically
            deleted."
        ::= { esModemEntry 19 }

    esTdmEtherMappingAmrQPSK OBJECT-TYPE
        SYNTAX       Integer32
        MAX-ACCESS   read-write
        STATUS       current
        DESCRIPTION
            "E1 Mapping (QPSK). This object configures the E1 channel count
            which is mapped to the radio link running on QPSK on the AMR
            mode.
            When this parameter changes, the agent will adjust the E1/RST
            mappings according to this parameter. And the XCs whose channel
            number is exceeded to the E1/RST mapping number are automatically
            deleted."
        ::= { esModemEntry 20 }

    esTdmEtherMappingAmr16QAM OBJECT-TYPE
        SYNTAX       Integer32
        MAX-ACCESS   read-write
        STATUS       current
        DESCRIPTION
            "E1 Mapping (16QAM). This object configures the E1 channel count
            which is mapped to the radio link running on 16QAM on the AMR
            mode.
            When this parameter changes, the agent will adjust the E1/RST
            mappings according to this parameter. And the XCs whose channel
            number is exceeded to the E1/RST mapping number are automatically
            deleted."
        ::= { esModemEntry 21 }

    esTdmEtherMappingAmr32QAM OBJECT-TYPE
        SYNTAX       Integer32
        MAX-ACCESS   read-write
        STATUS       current
        DESCRIPTION
            "E1 Mapping (32QAM). This object configures the E1 channel count
            which is mapped to the radio link running on 32QAM on the AMR
            mode.
            When this parameter changes, the agent will adjust the E1/RST
            mappings according to this parameter. And the XCs whose channel
            number is exceeded to the E1/RST mapping number are automatically
            deleted."
        ::= { esModemEntry 22 }

    esTdmEtherMappingAmr64QAM OBJECT-TYPE
        SYNTAX       Integer32
        MAX-ACCESS   read-write
        STATUS       current
        DESCRIPTION
            "E1 Mapping (64QAM). This object configures the E1 channel count
            which is mapped to the radio link running on 64QAM on the AMR
            mode.
            When this parameter changes, the agent will adjust the E1/RST
            mappings according to this parameter. And the XCs whose channel
            number is exceeded to the E1/RST mapping number are automatically
            deleted."
        ::= { esModemEntry 23 }

    esTdmEtherMappingAmr128QAM OBJECT-TYPE
        SYNTAX       Integer32
        MAX-ACCESS   read-write
        STATUS       current
        DESCRIPTION
            "E1 Mapping (128QAM). This object configures the E1 channel count
            which is mapped to the radio link running on 128QAM on the AMR
            mode.
            When this parameter changes, the agent will adjust the E1/RST
            mappings according to this parameter. And the XCs whose channel
            number is exceeded to the E1/RST mapping number are automatically
            deleted."
        ::= { esModemEntry 24 }

    esTdmEtherMappingAmr256QAM OBJECT-TYPE
        SYNTAX       Integer32
        MAX-ACCESS   read-write
        STATUS       current
        DESCRIPTION
            "E1 Mapping (256QAM). This object configures the E1 channel count
            which is mapped to the radio link running on 256QAM on the AMR
            mode.
            When this parameter changes, the agent will adjust the E1/RST
            mappings according to this parameter. And the XCs whose channel
            number is exceeded to the E1/RST mapping number are automatically
            deleted."
        ::= { esModemEntry 25 }

    esTdmEtherMappingRst OBJECT-TYPE
        SYNTAX       Integer32
        MAX-ACCESS   read-write
        STATUS       current
        DESCRIPTION
            "STM-1 Mapping. This object configures the STM-1 channel count
            which is mapped to the radio link.
            When this parameter changes, the agent will adjust the E1/RST
            mappings according to this parameter. And the XCs whose channel
            number is exceeded to the E1/RST mapping number are automatically
            deleted."
        ::= { esModemEntry 26 }

    esTdmEtherMappingRstAmrQPSK OBJECT-TYPE
        SYNTAX       Integer32
        MAX-ACCESS   read-write
        STATUS       current
        DESCRIPTION
            "STM-1 Mapping (QPSK). This object configures the STM-1 channel
            count which is mapped to the radio link running on QPSK on the
            AMR mode.
            When this parameter changes, the agent will adjust the E1/RST
            mappings according to this parameter. And the XCs whose channel
            number is exceeded to the E1/RST mapping number are automatically
            deleted."
        ::= { esModemEntry 27 }

    esTdmEtherMappingRstAmr16QAM OBJECT-TYPE
        SYNTAX       Integer32
        MAX-ACCESS   read-write
        STATUS       current
        DESCRIPTION
            "STM-1 Mapping (16QAM). This object configures the STM-1 channel
            count which is mapped to the radio link running on 16QAM on the
            AMR mode.
            When this parameter changes, the agent will adjust the E1/RST
            mappings according to this parameter. And the XCs whose channel
            number is exceeded to the E1/RST mapping number are automatically
            deleted."
        ::= { esModemEntry 28 }

    esTdmEtherMappingRstAmr32QAM OBJECT-TYPE
        SYNTAX       Integer32
        MAX-ACCESS   read-write
        STATUS       current
        DESCRIPTION
            "STM-1 Mapping (32QAM). This object configures the STM-1 channel
            count which is mapped to the radio link running on 32QAM on the
            AMR mode.
            When this parameter changes, the agent will adjust the E1/RST
            mappings according to this parameter. And the XCs whose channel
            number is exceeded to the E1/RST mapping number are automatically
            deleted."
        ::= { esModemEntry 29 }

    esTdmEtherMappingRstAmr64QAM OBJECT-TYPE
        SYNTAX       Integer32
        MAX-ACCESS   read-write
        STATUS       current
        DESCRIPTION
            "STM-1 Mapping (64QAM). This object configures the STM-1 channel
            count which is mapped to the radio link running on 64QAM on the
            AMR mode.
            When this parameter changes, the agent will adjust the E1/RST
            mappings according to this parameter. And the XCs whose channel
            number is exceeded to the E1/RST mapping number are automatically
            deleted."
        ::= { esModemEntry 30 }

    esTdmEtherMappingRstAmr128QAM OBJECT-TYPE
        SYNTAX       Integer32
        MAX-ACCESS   read-write
        STATUS       current
        DESCRIPTION
            "STM-1 Mapping (128QAM). This object configures the STM-1 channel
            count which is mapped to the radio link running on 128QAM on the
            AMR mode.
            When this parameter changes, the agent will adjust the E1/RST
            mappings according to this parameter. And the XCs whose channel
            number is exceeded to the E1/RST mapping number are automatically
            deleted."
        ::= { esModemEntry 31 }

    esTdmEtherMappingRstAmr256QAM OBJECT-TYPE
        SYNTAX       Integer32
        MAX-ACCESS   read-write
        STATUS       current
        DESCRIPTION
            "STM-1 Mapping (256QAM). This object configures the STM-1 channel
            count which is mapped to the radio link running on 256QAM on the
            AMR mode.
            When this parameter changes, the agent will adjust the E1/RST
            mappings according to this parameter. And the XCs whose channel
            number is exceeded to the E1/RST mapping number are automatically
            deleted."
        ::= { esModemEntry 32 }

    esModemAmrRange512QAM OBJECT-TYPE
        SYNTAX       OffOnValue
        MAX-ACCESS   read-write
        STATUS       current
        DESCRIPTION
            "AMR Range (512QAM).
            When this parameter changes, the agent will adjust the E1/RST
            mappings according to this parameter. And the XCs whose channel
            number is exceeded to the E1/RST mapping number are automatically
            deleted."
        ::= { esModemEntry 33 }

    esModemAmrRange1024QAM OBJECT-TYPE
        SYNTAX       OffOnValue
        MAX-ACCESS   read-write
        STATUS       current
        DESCRIPTION
            "AMR Range (1024QAM).
            When this parameter changes, the agent will adjust the E1/RST
            mappings according to this parameter. And the XCs whose channel
            number is exceeded to the E1/RST mapping number are automatically
            deleted."
        ::= { esModemEntry 34 }

    esTdmEtherMappingAmr512QAM OBJECT-TYPE
        SYNTAX       Integer32
        MAX-ACCESS   read-write
        STATUS       current
        DESCRIPTION
            "E1 Mapping (512QAM). This object configures the E1 channel count
            which is mapped to the radio link running on 512QAM on the AMR
            mode.
            When this parameter changes, the agent will adjust the E1/RST
            mappings according to this parameter. And the XCs whose channel
            number is exceeded to the E1/RST mapping number are automatically
            deleted."
        ::= { esModemEntry 35 }

    esTdmEtherMappingAmr1024QAM OBJECT-TYPE
        SYNTAX       Integer32
        MAX-ACCESS   read-write
        STATUS       current
        DESCRIPTION
            "E1 Mapping (1024QAM). This object configures the E1 channel
            count which is mapped to the radio link running on 1024QAM on the
            AMR mode.
            When this parameter changes, the agent will adjust the E1/RST
            mappings according to this parameter. And the XCs whose channel
            number is exceeded to the E1/RST mapping number are automatically
            deleted."
        ::= { esModemEntry 36 }

    esTdmEtherMappingRstAmr512QAM OBJECT-TYPE
        SYNTAX       Integer32
        MAX-ACCESS   read-write
        STATUS       current
        DESCRIPTION
            "STM-1 Mapping (512QAM). This object configures the STM-1 channel
            count which is mapped to the radio link running on 512QAM on the
            AMR mode.
            When this parameter changes, the agent will adjust the E1/RST
            mappings according to this parameter. And the XCs whose channel
            number is exceeded to the E1/RST mapping number are automatically
            deleted."
        ::= { esModemEntry 37 }

    esTdmEtherMappingRstAmr1024QAM OBJECT-TYPE
        SYNTAX       Integer32
        MAX-ACCESS   read-write
        STATUS       current
        DESCRIPTION
            "STM-1 Mapping (1024QAM). This object configures the STM-1
            channel count which is mapped to the radio link running on
            1024QAM on the AMR mode.
            When this parameter changes, the agent will adjust the E1/RST
            mappings according to this parameter. And the XCs whose channel
            number is exceeded to the E1/RST mapping number are automatically
            deleted."
        ::= { esModemEntry 38 }

    esModemGroupMode OBJECT-TYPE
        SYNTAX       INTEGER { invalid(0), normal(1), phyMode(2) }
        MAX-ACCESS   read-write
        STATUS       current
        DESCRIPTION
            "Configure Radio Traffic Aggregation Mode.
            When the 'normal' mode aggregation is configured, Ethernet frames
            are distributed to the multiple radio links based on usual Link
            aggregation behaviour. when the 'phyMode' mode, Ethernet frames
            are distributed to the multiple radio links based on the ratio
            for the radio link speed.

            'phyMode' must be configured to the modem cards which are
            belonging to the same radio traffic aggregation group. And
            'phyMode' must be configured to continuous 2 slots (lower slot is
            odd number). If 'phyMode' is configured to the single modem or 3
            or more slots, the agent will reject the request.

            'phyAdvancedMode' must be configured to the modem cards which are
            belonging to the same radio traffic aggregation group. And
            'phyAdvancedMode' must be configured to continuous 3 or more
            slots (lower slot is odd number). If 'phyAdvancedMode' is
            configured to the one or 2 modems, the agent will reject the
            request. 'phyAdvancedMode' is valid for iPASO VR 10 only."
        ::= { esModemEntry 39 }

    esModemAmrRange2048QAM OBJECT-TYPE
        SYNTAX       OffOnValue
        MAX-ACCESS   read-write
        STATUS       current
        DESCRIPTION
            "AMR Range (2048QAM).
            When this parameter changes, the agent will adjust the E1/RST
            mappings according to this parameter. And the XCs whose channel
            number is exceeded to the E1/RST mapping number are automatically
            deleted."
        ::= { esModemEntry 40 }

    esTdmEtherMappingAmr2048QAM OBJECT-TYPE
        SYNTAX       Integer32
        MAX-ACCESS   read-write
        STATUS       current
        DESCRIPTION
            "E1 Mapping (2048QAM). This object configures the E1 channel
            count which is mapped to the radio link running on 2048QAM on the
            AMR mode.
            When this parameter changes, the agent will adjust the E1/RST
            mappings according to this parameter. And the XCs whose channel
            number is exceeded to the E1/RST mapping number are automatically
            deleted."
        ::= { esModemEntry 41 }

    esTdmEtherMappingRstAmr2048QAM OBJECT-TYPE
        SYNTAX       Integer32
        MAX-ACCESS   read-write
        STATUS       current
        DESCRIPTION
            "STM-1 Mapping (2048QAM). This object configures the STM-1
            channel count which is mapped to the radio link running on
            2048QAM on the AMR mode.
            When this parameter changes, the agent will adjust the E1/RST
            mappings according to this parameter. And the XCs whose channel
            number is exceeded to the E1/RST mapping number are automatically
            deleted."
        ::= { esModemEntry 42 }

    esModemEthTransparentClockPath OBJECT-TYPE
        SYNTAX       Integer32
        UNITS        "Mbps"
        MAX-ACCESS   read-write
        STATUS       current
        DESCRIPTION
            "This object configures the bandwidth for Transparent Clock path.
            The configuration step is 0 (notUsed), 2, 4, 8 Mbps."
        ::= { esModemEntry 43 }

    esModemSwGroupTable OBJECT-TYPE
        SYNTAX       SEQUENCE OF EsModemSwGroupEntry
        MAX-ACCESS   not-accessible
        STATUS       current
        DESCRIPTION  "Configures the MODEM Switch group and XPIC group."
        ::= { equipmentSetUpGroup 3 }

    esModemSwGroupEntry OBJECT-TYPE
        SYNTAX       EsModemSwGroupEntry
        MAX-ACCESS   not-accessible
        STATUS       current
        DESCRIPTION  ""
        INDEX        { esModemSwGroupIfIndex }
        ::= { esModemSwGroupTable 1 }

    EsModemSwGroupEntry ::= SEQUENCE {
        esModemSwGroupIfIndex    InterfaceIndex,
        esModemSwGroupNEAddress  IpAddress,
        esModemSwRowStatus       INTEGER,
        esSWGConfiguration       INTEGER
    }

    esModemSwGroupIfIndex OBJECT-TYPE
        SYNTAX       InterfaceIndex
        MAX-ACCESS   not-accessible
        STATUS       current
        DESCRIPTION  "Index of this table."
        ::= { esModemSwGroupEntry 1 }

    esModemSwGroupNEAddress OBJECT-TYPE
        SYNTAX       IpAddress
        MAX-ACCESS   not-accessible
        STATUS       current
        DESCRIPTION  "reserved."
        ::= { esModemSwGroupEntry 2 }

    esModemSwRowStatus OBJECT-TYPE
        SYNTAX       INTEGER {
                         active(1),
                         notInservice(2),
                         notReady(3),
                         createAndGo(4),
                         createAndWait(5),
                         destroy(6)
                     }
        MAX-ACCESS   read-create
        STATUS       current
        DESCRIPTION  "RowStatus of this table."
        ::= { esModemSwGroupEntry 3 }

    esSWGConfiguration OBJECT-TYPE
        SYNTAX       INTEGER {
                         invalid(0),
                         notUsed(1),
                         hs1plus1(2),
                         tp1plus1(3),
                         xpic1plus0(4),
                         xpic1plus1HsMaster(5),
                         xpic1plus1HsSlave(6),
                         xpic1plus1TpMaster(7),
                         xpic1plus1TpSlave(8)
                     }
        MAX-ACCESS   read-create
        STATUS       current
        DESCRIPTION
            "MODEM SW/XPIC Group Configuration. Configures the type of MODEM
            Switch group and XPIC group. Changing the SW/XPIC Group
            configuration will remove the CrossConnections and VLANs which
            are configured to the protection port."
        ::= { esModemSwGroupEntry 4 }

    esStm1ApsTable OBJECT-TYPE
        SYNTAX       SEQUENCE OF EsStm1ApsEntry
        MAX-ACCESS   not-accessible
        STATUS       current
        DESCRIPTION  "STM1 APS configuration."
        ::= { equipmentSetUpGroup 4 }

    esStm1ApsEntry OBJECT-TYPE
        SYNTAX       EsStm1ApsEntry
        MAX-ACCESS   not-accessible
        STATUS       current
        DESCRIPTION  ""
        INDEX        { esStm1ApsIfIndex }
        ::= { esStm1ApsTable 1 }

    EsStm1ApsEntry ::= SEQUENCE {
        esStm1ApsIfIndex    InterfaceIndex,
        esStm1ApsNEAddress  IpAddress,
        esApsSwRowStauts    RowStatus,
        esApsConfiguration  INTEGER
    }

    esStm1ApsIfIndex OBJECT-TYPE
        SYNTAX       InterfaceIndex
        MAX-ACCESS   not-accessible
        STATUS       current
        DESCRIPTION  "Index of this table."
        ::= { esStm1ApsEntry 1 }

    esStm1ApsNEAddress OBJECT-TYPE
        SYNTAX       IpAddress
        MAX-ACCESS   not-accessible
        STATUS       current
        DESCRIPTION  "reserved."
        ::= { esStm1ApsEntry 2 }

    esApsSwRowStauts OBJECT-TYPE
        SYNTAX       RowStatus
        MAX-ACCESS   read-create
        STATUS       current
        DESCRIPTION  "RowStatus of this table."
        ::= { esStm1ApsEntry 3 }

    esApsConfiguration OBJECT-TYPE
        SYNTAX       INTEGER { invalid(0), sameCard(1), diffCard(2) }
        MAX-ACCESS   read-create
        STATUS       current
        DESCRIPTION
            "STM-1 APS Group Configuration. This object indicates the STM1
            APS configuration. When the row is created, either sameCard or
            diffCard must
            be specified. The value cannot be changed to other type once
            esStm1ApsTable is created."
        ::= { esStm1ApsEntry 4 }

    esStm1PortModeTable OBJECT-TYPE
        SYNTAX       SEQUENCE OF EsStm1PortModeEntry
        MAX-ACCESS   not-accessible
        STATUS       current
        DESCRIPTION  "Configures the STM-1 Channel mode."
        ::= { equipmentSetUpGroup 9 }

    esStm1PortModeEntry OBJECT-TYPE
        SYNTAX       EsStm1PortModeEntry
        MAX-ACCESS   not-accessible
        STATUS       current
        DESCRIPTION  ""
        INDEX        { esStm1PortModeIfIndex }
        ::= { esStm1PortModeTable 1 }

    EsStm1PortModeEntry ::= SEQUENCE {
        esStm1PortModeIfIndex    InterfaceIndex,
        esStm1PortModeNEAddress  IpAddress,
        esStm1PortMode           INTEGER
    }

    esStm1PortModeIfIndex OBJECT-TYPE
        SYNTAX       InterfaceIndex
        MAX-ACCESS   not-accessible
        STATUS       current
        DESCRIPTION  "Index of this table."
        ::= { esStm1PortModeEntry 1 }

    esStm1PortModeNEAddress OBJECT-TYPE
        SYNTAX       IpAddress
        MAX-ACCESS   not-accessible
        STATUS       current
        DESCRIPTION  "reserved."
        ::= { esStm1PortModeEntry 2 }

    esStm1PortMode OBJECT-TYPE
        SYNTAX       INTEGER { invalid(0), through(1), channelized(2) }
        MAX-ACCESS   read-write
        STATUS       current
        DESCRIPTION
            "STM-1 Port Mode. Changing the port mode to other will remove the
            CrossConnections and Clock reference setting which are configured
            to that port."
        ::= { esStm1PortModeEntry 3 }

-----------------------------------------------
-- provisioningGroup Definitions
-----------------------------------------------

    provAlarmGroup OBJECT IDENTIFIER
        ::= { provisioningGroup 1 }

    provAlarmCommonTable OBJECT-TYPE
        SYNTAX       SEQUENCE OF ProvAlarmCommonEntry
        MAX-ACCESS   not-accessible
        STATUS       current
        DESCRIPTION  "Configures the system alarm mode."
        ::= { provAlarmGroup 1 }

    provAlarmCommonEntry OBJECT-TYPE
        SYNTAX       ProvAlarmCommonEntry
        MAX-ACCESS   not-accessible
        STATUS       current
        DESCRIPTION  ""
        INDEX        { provAlarmCommonIndex }
        ::= { provAlarmCommonTable 1 }

    ProvAlarmCommonEntry ::= SEQUENCE {
        provAlarmCommonIndex      INTEGER,
        provAlarmCommonNEAddress  IpAddress,
        alarmCorrelation          OffOnValue,
        alarmDelay                Integer32,
        alarmStretch              Integer32
    }

    provAlarmCommonIndex OBJECT-TYPE
        SYNTAX       INTEGER { alarm(1) }
        MAX-ACCESS   not-accessible
        STATUS       current
        DESCRIPTION  "Index of this table."
        ::= { provAlarmCommonEntry 1 }

    provAlarmCommonNEAddress OBJECT-TYPE
        SYNTAX       IpAddress
        MAX-ACCESS   not-accessible
        STATUS       current
        DESCRIPTION  "reserved."
        ::= { provAlarmCommonEntry 2 }

    alarmCorrelation OBJECT-TYPE
        SYNTAX       OffOnValue
        MAX-ACCESS   read-write
        STATUS       current
        DESCRIPTION
            "Correlation Setting. Enables/Disables alarm correlation
            function."
        ::= { provAlarmCommonEntry 3 }

    alarmDelay OBJECT-TYPE
        SYNTAX       Integer32
        MAX-ACCESS   read-write
        STATUS       current
        DESCRIPTION  "Delay Setting."
        ::= { provAlarmCommonEntry 4 }

    alarmStretch OBJECT-TYPE
        SYNTAX       Integer32
        MAX-ACCESS   read-write
        STATUS       current
        DESCRIPTION  "Stretch Setting."
        ::= { provAlarmCommonEntry 5 }

    provAlarmEventTable OBJECT-TYPE
        SYNTAX       SEQUENCE OF ProvAlarmEventEntry
        MAX-ACCESS   not-accessible
        STATUS       current
        DESCRIPTION  "configures the alarm severity value."
        ::= { provAlarmGroup 2 }

    provAlarmEventEntry OBJECT-TYPE
        SYNTAX       ProvAlarmEventEntry
        MAX-ACCESS   not-accessible
        STATUS       current
        DESCRIPTION  ""
        INDEX        {
                         alarmEventIndex,
                         alarmEventSourceCategory,
                         alarmEventElemId
                     }
        ::= { provAlarmEventTable 1 }

    ProvAlarmEventEntry ::= SEQUENCE {
        alarmEventIndex              INTEGER,
        alarmEventSourceCategory     Integer32,
        alarmEventElemId             Integer32,
        provAlarmEventNEAddress      IpAddress,
        alarmEventSeverity           INTEGER,
        alarmEventAlarmType          AlarmTypeValue,
        alarmEventProbableCause      ProbableCauseValue,
        alarmEventDelayStretchUsage  UsedNotusedValue
    }

    alarmEventIndex OBJECT-TYPE
        SYNTAX       INTEGER { alarmStateChange(1) }
        MAX-ACCESS   not-accessible
        STATUS       current
        DESCRIPTION  "Index of this table."
        ::= { provAlarmEventEntry 1 }

    alarmEventSourceCategory OBJECT-TYPE
        SYNTAX       Integer32
        MAX-ACCESS   not-accessible
        STATUS       current
        DESCRIPTION
            "index of this table. Each alarm is categorized depending on the
            generator of that alarm."
        ::= { provAlarmEventEntry 2 }

    alarmEventElemId OBJECT-TYPE
        SYNTAX       Integer32
        MAX-ACCESS   not-accessible
        STATUS       current
        DESCRIPTION
            "index of this table. This object is administrative value which
            can distinguish the alarm among the alarmEventSourceCategory."
        ::= { provAlarmEventEntry 3 }

    provAlarmEventNEAddress OBJECT-TYPE
        SYNTAX       IpAddress
        MAX-ACCESS   not-accessible
        STATUS       current
        DESCRIPTION  "reserved."
        ::= { provAlarmEventEntry 4 }

    alarmEventSeverity OBJECT-TYPE
        SYNTAX       INTEGER {
                         invalid(0),
                         critical(1),
                         major(2),
                         minor(3),
                         warning(4)
                     }
        MAX-ACCESS   read-write
        STATUS       current
        DESCRIPTION
            "Configures the alarm severity. Once the alarm severity is
            changed, the system changes the alarm severity of all raised
            alarms, but the corresponding notifications are suppressed. The
            manager must synchronize the alarm status after receiving the
            equipConfigStatus change notification."
        ::= { provAlarmEventEntry 5 }

    alarmEventAlarmType OBJECT-TYPE
        SYNTAX       AlarmTypeValue
        MAX-ACCESS   read-only
        STATUS       current
        DESCRIPTION
            "Configures the alarm type based on the X.733 definitions."
        ::= { provAlarmEventEntry 6 }

    alarmEventProbableCause OBJECT-TYPE
        SYNTAX       ProbableCauseValue
        MAX-ACCESS   read-only
        STATUS       current
        DESCRIPTION
            "Configures the probable cause based on the X.733 definitions."
        ::= { provAlarmEventEntry 7 }

    alarmEventDelayStretchUsage OBJECT-TYPE
        SYNTAX       UsedNotusedValue
        MAX-ACCESS   read-write
        STATUS       current
        DESCRIPTION
            "Delay Stretch Usage. Configures the usage of the delay/stretch
            behaviour."
        ::= { provAlarmEventEntry 8 }

    provAlsTable OBJECT-TYPE
        SYNTAX       SEQUENCE OF ProvAlsEntry
        MAX-ACCESS   not-accessible
        STATUS       current
        DESCRIPTION  "Confgiures Automatic Laser Shutdown mode."
        ::= { provisioningGroup 2 }

    provAlsEntry OBJECT-TYPE
        SYNTAX       ProvAlsEntry
        MAX-ACCESS   not-accessible
        STATUS       current
        DESCRIPTION  ""
        INDEX        { provAlsIfIndex }
        ::= { provAlsTable 1 }

    ProvAlsEntry ::= SEQUENCE {
        provAlsIfIndex    InterfaceIndex,
        provAlsNEAddress  IpAddress,
        alsUsage          EnableDisableValue,
        alsInterval       INTEGER
    }

    provAlsIfIndex OBJECT-TYPE
        SYNTAX       InterfaceIndex
        MAX-ACCESS   not-accessible
        STATUS       current
        DESCRIPTION  "Index of this table."
        ::= { provAlsEntry 1 }

    provAlsNEAddress OBJECT-TYPE
        SYNTAX       IpAddress
        MAX-ACCESS   not-accessible
        STATUS       current
        DESCRIPTION  "reserved."
        ::= { provAlsEntry 2 }

    alsUsage OBJECT-TYPE
        SYNTAX       EnableDisableValue
        MAX-ACCESS   read-write
        STATUS       current
        DESCRIPTION
            "ALS Usage. Enables/Disables ALS function of the STM-1 port."
        ::= { provAlsEntry 3 }

    alsInterval OBJECT-TYPE
        SYNTAX       INTEGER { invalid(0), sec60(1), sec180(2), sec300(3) }
        MAX-ACCESS   read-write
        STATUS       current
        DESCRIPTION  "ALS Interval."
        ::= { provAlsEntry 4 }

    provE1Group OBJECT IDENTIFIER
        ::= { provisioningGroup 3 }

    provE1ChSetTable OBJECT-TYPE
        SYNTAX       SEQUENCE OF ProvE1ChSetEntry
        MAX-ACCESS   not-accessible
        STATUS       current
        DESCRIPTION  "Configure E1 Channel Parameters."
        ::= { provE1Group 1 }

    provE1ChSetEntry OBJECT-TYPE
        SYNTAX       ProvE1ChSetEntry
        MAX-ACCESS   not-accessible
        STATUS       current
        DESCRIPTION  ""
        INDEX        { provE1ChSetIfIndex }
        ::= { provE1ChSetTable 1 }

    ProvE1ChSetEntry ::= SEQUENCE {
        provE1ChSetIfIndex    InterfaceIndex,
        provE1ChSetNEAddress  IpAddress,
        e1PortName            DisplayString,
        chUsage               UsedNotusedValue,
        chUsageErrorReport    ReportNotreportValue,
        impedanceSetting      INTEGER
    }

    provE1ChSetIfIndex OBJECT-TYPE
        SYNTAX       InterfaceIndex
        MAX-ACCESS   not-accessible
        STATUS       current
        DESCRIPTION  "Index of this table."
        ::= { provE1ChSetEntry 1 }

    provE1ChSetNEAddress OBJECT-TYPE
        SYNTAX       IpAddress
        MAX-ACCESS   not-accessible
        STATUS       current
        DESCRIPTION  "reserved."
        ::= { provE1ChSetEntry 2 }

    e1PortName OBJECT-TYPE
        SYNTAX       DisplayString (SIZE(0..32))
        MAX-ACCESS   read-write
        STATUS       current
        DESCRIPTION  "Port Name."
        ::= { provE1ChSetEntry 3 }

    chUsage OBJECT-TYPE
        SYNTAX       UsedNotusedValue
        MAX-ACCESS   read-write
        STATUS       current
        DESCRIPTION  "CH Usage."
        ::= { provE1ChSetEntry 4 }

    chUsageErrorReport OBJECT-TYPE
        SYNTAX       ReportNotreportValue
        MAX-ACCESS   read-write
        STATUS       current
        DESCRIPTION  "CH Usage Error Report."
        ::= { provE1ChSetEntry 5 }

    impedanceSetting OBJECT-TYPE
        SYNTAX       INTEGER { invalid(0), ohm120(1), ohm75(2) }
        MAX-ACCESS   read-write
        STATUS       current
        DESCRIPTION  "Impedance."
        ::= { provE1ChSetEntry 6 }

    provE1AisCondTable OBJECT-TYPE
        SYNTAX       SEQUENCE OF ProvE1AisCondEntry
        MAX-ACCESS   not-accessible
        STATUS       current
        DESCRIPTION  "Configures E1 AIS Usage."
        ::= { provE1Group 2 }

    provE1AisCondEntry OBJECT-TYPE
        SYNTAX       ProvE1AisCondEntry
        MAX-ACCESS   not-accessible
        STATUS       current
        DESCRIPTION  ""
        INDEX        { provE1AisCondIndex }
        ::= { provE1AisCondTable 1 }

    ProvE1AisCondEntry ::= SEQUENCE {
        provE1AisCondIndex      Integer32,
        provE1AisCondNEAddress  IpAddress,
        e1AisActivationCond     EnableDisableValue
    }

    provE1AisCondIndex OBJECT-TYPE
        SYNTAX       Integer32
        MAX-ACCESS   not-accessible
        STATUS       current
        DESCRIPTION  "Index of this table."
        ::= { provE1AisCondEntry 1 }

    provE1AisCondNEAddress OBJECT-TYPE
        SYNTAX       IpAddress
        MAX-ACCESS   not-accessible
        STATUS       current
        DESCRIPTION  "reserved."
        ::= { provE1AisCondEntry 2 }

    e1AisActivationCond OBJECT-TYPE
        SYNTAX       EnableDisableValue
        MAX-ACCESS   read-write
        STATUS       current
        DESCRIPTION  "Enables/Disables E1 AIS Report."
        ::= { provE1AisCondEntry 3 }

    provE1CardSetTable OBJECT-TYPE
        SYNTAX       SEQUENCE OF ProvE1CardSetEntry
        MAX-ACCESS   not-accessible
        STATUS       current
        DESCRIPTION  "Configures E1 Card Parameters."
        ::= { provE1Group 3 }

    provE1CardSetEntry OBJECT-TYPE
        SYNTAX       ProvE1CardSetEntry
        MAX-ACCESS   not-accessible
        STATUS       current
        DESCRIPTION  ""
        INDEX        { provE1CardSetIndex }
        ::= { provE1CardSetTable 1 }

    ProvE1CardSetEntry ::= SEQUENCE {
        provE1CardSetIndex      Integer32,
        provE1CardSetNEAddress  IpAddress,
        e1CardLineClkSelect     Integer32
    }

    provE1CardSetIndex OBJECT-TYPE
        SYNTAX       Integer32
        MAX-ACCESS   not-accessible
        STATUS       current
        DESCRIPTION  "Index of this table."
        ::= { provE1CardSetEntry 1 }

    provE1CardSetNEAddress OBJECT-TYPE
        SYNTAX       IpAddress
        MAX-ACCESS   not-accessible
        STATUS       current
        DESCRIPTION  "reserved."
        ::= { provE1CardSetEntry 2 }

    e1CardLineClkSelect OBJECT-TYPE
        SYNTAX       Integer32 (1..16)
        MAX-ACCESS   read-write
        STATUS       current
        DESCRIPTION  "Select the timing source from 16 E1 channels."
        ::= { provE1CardSetEntry 3 }

    provAisGroup OBJECT IDENTIFIER
        ::= { provisioningGroup 4 }

    provAisGenerationTable OBJECT-TYPE
        SYNTAX       SEQUENCE OF ProvAisGenerationEntry
        MAX-ACCESS   not-accessible
        STATUS       current
        DESCRIPTION  "Configures AIS Generation Mode of STM-1 Port."
        ::= { provAisGroup 1 }

    provAisGenerationEntry OBJECT-TYPE
        SYNTAX       ProvAisGenerationEntry
        MAX-ACCESS   not-accessible
        STATUS       current
        DESCRIPTION  ""
        INDEX        { provAisGenerationIfIndex }
        ::= { provAisGenerationTable 1 }

    ProvAisGenerationEntry ::= SEQUENCE {
        provAisGenerationIfIndex    InterfaceIndex,
        provAisGenerationNEAddress  IpAddress,
        msAisGeneration             INTEGER
    }

    provAisGenerationIfIndex OBJECT-TYPE
        SYNTAX       InterfaceIndex
        MAX-ACCESS   not-accessible
        STATUS       current
        DESCRIPTION  "Index of this table."
        ::= { provAisGenerationEntry 1 }

    provAisGenerationNEAddress OBJECT-TYPE
        SYNTAX       IpAddress
        MAX-ACCESS   not-accessible
        STATUS       current
        DESCRIPTION  "reserved."
        ::= { provAisGenerationEntry 2 }

    msAisGeneration OBJECT-TYPE
        SYNTAX       INTEGER { invalid(0), shutdown(1), output(2) }
        MAX-ACCESS   read-write
        STATUS       current
        DESCRIPTION
            "MS-AIS Generation. This object configures the behaviour of STM-1
            Port on receiving AIS from Radio link."
        ::= { provAisGenerationEntry 3 }

    provAisSettingTable OBJECT-TYPE
        SYNTAX       SEQUENCE OF ProvAisSettingEntry
        MAX-ACCESS   not-accessible
        STATUS       current
        DESCRIPTION  "Configures AIS Generate condition."
        ::= { provAisGroup 2 }

    provAisSettingEntry OBJECT-TYPE
        SYNTAX       ProvAisSettingEntry
        MAX-ACCESS   not-accessible
        STATUS       current
        DESCRIPTION  ""
        INDEX        { provAisSettingIndex }
        ::= { provAisSettingTable 1 }

    ProvAisSettingEntry ::= SEQUENCE {
        provAisSettingIndex      Integer32,
        provAisSettingNEAddress  IpAddress,
        aisActivationDelay       OffOnValue,
        aisActivationCond        INTEGER,
        aisGeneratedReport       ReportNotreportValue,
        aisReceivedReport        ReportNotreportValue,
        aisReceivedCondSet       INTEGER
    }

    provAisSettingIndex OBJECT-TYPE
        SYNTAX       Integer32 (1..1)
        MAX-ACCESS   not-accessible
        STATUS       current
        DESCRIPTION  "Index of this table."
        ::= { provAisSettingEntry 1 }

    provAisSettingNEAddress OBJECT-TYPE
        SYNTAX       IpAddress
        MAX-ACCESS   not-accessible
        STATUS       current
        DESCRIPTION  "reserved."
        ::= { provAisSettingEntry 2 }

    aisActivationDelay OBJECT-TYPE
        SYNTAX       OffOnValue
        MAX-ACCESS   read-write
        STATUS       current
        DESCRIPTION  "AIS Activation Delay."
        ::= { provAisSettingEntry 3 }

    aisActivationCond OBJECT-TYPE
        SYNTAX       INTEGER { invalid(0), lofHighber(1), lof(2) }
        MAX-ACCESS   read-write
        STATUS       current
        DESCRIPTION  "AIS Activation Condition."
        ::= { provAisSettingEntry 4 }

    aisGeneratedReport OBJECT-TYPE
        SYNTAX       ReportNotreportValue
        MAX-ACCESS   read-write
        STATUS       current
        DESCRIPTION
            "AIS Generated Report (E1/STM-1). This object enables the
            notification on generating the AIS on the E1 channel/STM-1 port."
        ::= { provAisSettingEntry 5 }

    aisReceivedReport OBJECT-TYPE
        SYNTAX       ReportNotreportValue
        MAX-ACCESS   read-write
        STATUS       current
        DESCRIPTION
            "AIS Received Report (E1). This object enables the notification
            on receiving the AIS on the E1 channel."
        ::= { provAisSettingEntry 6 }

    aisReceivedCondSet OBJECT-TYPE
        SYNTAX       INTEGER { invalid(0), alarm(1), status(2) }
        MAX-ACCESS   read-write
        STATUS       current
        DESCRIPTION
            "AIS Received Condition (E1). When the object is set to 'alarm',
            the AIS receive event will be reported as alarm event."
        ::= { provAisSettingEntry 7 }

    provRadioSettingGroup OBJECT IDENTIFIER
        ::= { provisioningGroup 5 }

    provModemSettingTable OBJECT-TYPE
        SYNTAX       SEQUENCE OF ProvModemSettingEntry
        MAX-ACCESS   not-accessible
        STATUS       current
        DESCRIPTION  "Configures MODEM Port parameters."
        ::= { provRadioSettingGroup 1 }

    provModemSettingEntry OBJECT-TYPE
        SYNTAX       ProvModemSettingEntry
        MAX-ACCESS   not-accessible
        STATUS       current
        DESCRIPTION  ""
        INDEX        { provModemSettingIfIndex }
        ::= { provModemSettingTable 1 }

    ProvModemSettingEntry ::= SEQUENCE {
        provModemSettingIfIndex    InterfaceIndex,
        provModemSettingNEAddress  IpAddress,
        modemPortName              DisplayString,
        headerCompress             EnableDisableValue
    }

    provModemSettingIfIndex OBJECT-TYPE
        SYNTAX       InterfaceIndex
        MAX-ACCESS   not-accessible
        STATUS       current
        DESCRIPTION  "Index of this table."
        ::= { provModemSettingEntry 1 }

    provModemSettingNEAddress OBJECT-TYPE
        SYNTAX       IpAddress
        MAX-ACCESS   not-accessible
        STATUS       current
        DESCRIPTION  "reserved."
        ::= { provModemSettingEntry 2 }

    modemPortName OBJECT-TYPE
        SYNTAX       DisplayString (SIZE(0..32))
        MAX-ACCESS   read-write
        STATUS       current
        DESCRIPTION  "Port Name."
        ::= { provModemSettingEntry 3 }

    headerCompress OBJECT-TYPE
        SYNTAX       EnableDisableValue
        MAX-ACCESS   read-write
        STATUS       current
        DESCRIPTION  "Enables/Disables Header compression."
        ::= { provModemSettingEntry 4 }

    provSWCondTable OBJECT-TYPE
        SYNTAX       SEQUENCE OF ProvSWCondEntry
        MAX-ACCESS   not-accessible
        STATUS       current
        DESCRIPTION  "Configures Tx/Rx Sw Conditions."
        ::= { provRadioSettingGroup 2 }

    provSWCondEntry OBJECT-TYPE
        SYNTAX       ProvSWCondEntry
        MAX-ACCESS   not-accessible
        STATUS       current
        DESCRIPTION  ""
        INDEX        { provSWCondIfIndex }
        ::= { provSWCondTable 1 }

    ProvSWCondEntry ::= SEQUENCE {
        provSWCondIfIndex     InterfaceIndex,
        provSWCondNEAddress   IpAddress,
        txSwPriority          INTEGER,
        rxSwPriority          INTEGER,
        txSwLockinUsage       UsedNotusedValue,
        txSwDetectionTime     Integer32,
        txSwDetectionCounter  Integer32,
        txSwClearLockinTime   Integer32,
        reverseFunctionUsage  UsedNotusedValue,
        rxSwEwCondition       INTEGER
    }

    provSWCondIfIndex OBJECT-TYPE
        SYNTAX       InterfaceIndex
        MAX-ACCESS   not-accessible
        STATUS       current
        DESCRIPTION  "Index of this table."
        ::= { provSWCondEntry 1 }

    provSWCondNEAddress OBJECT-TYPE
        SYNTAX       IpAddress
        MAX-ACCESS   not-accessible
        STATUS       current
        DESCRIPTION  "reserved."
        ::= { provSWCondEntry 2 }

    txSwPriority OBJECT-TYPE
        SYNTAX       INTEGER { invalid(0), no1(1), nonPriority(2) }
        MAX-ACCESS   read-write
        STATUS       current
        DESCRIPTION  "Tx SW Priority."
        ::= { provSWCondEntry 3 }

    rxSwPriority OBJECT-TYPE
        SYNTAX       INTEGER { invalid(0), no1(1), nonPriority(2) }
        MAX-ACCESS   read-write
        STATUS       current
        DESCRIPTION  "Rx SW Priority."
        ::= { provSWCondEntry 4 }

    txSwLockinUsage OBJECT-TYPE
        SYNTAX       UsedNotusedValue
        MAX-ACCESS   read-write
        STATUS       current
        DESCRIPTION  "Tx SW Lock-in Usage."
        ::= { provSWCondEntry 5 }

    txSwDetectionTime OBJECT-TYPE
        SYNTAX       Integer32 (1..60)
        MAX-ACCESS   read-write
        STATUS       current
        DESCRIPTION  "Tx SW Detection Time."
        ::= { provSWCondEntry 6 }

    txSwDetectionCounter OBJECT-TYPE
        SYNTAX       Integer32 (1..255)
        MAX-ACCESS   read-write
        STATUS       current
        DESCRIPTION  "Tx SW Detection Counter."
        ::= { provSWCondEntry 7 }

    txSwClearLockinTime OBJECT-TYPE
        SYNTAX       Integer32 (1..48)
        MAX-ACCESS   read-write
        STATUS       current
        DESCRIPTION  "Tx SW Clear Lock-in Time."
        ::= { provSWCondEntry 8 }

    reverseFunctionUsage OBJECT-TYPE
        SYNTAX       UsedNotusedValue
        MAX-ACCESS   read-write
        STATUS       current
        DESCRIPTION  "Tx SW Reverse Function Usage."
        ::= { provSWCondEntry 9 }

    rxSwEwCondition OBJECT-TYPE
        SYNTAX       INTEGER { invalid(0), include(1), exclude(2) }
        MAX-ACCESS   read-write
        STATUS       current
        DESCRIPTION
            "Rx SW Condition Early Warning. This object determines the Early
            Warning is included as Rx Sw trigger or not."
        ::= { provSWCondEntry 10 }

    provAmrSWCondTable OBJECT-TYPE
        SYNTAX       SEQUENCE OF ProvAmrSWCondEntry
        MAX-ACCESS   not-accessible
        STATUS       current
        DESCRIPTION  "Configure AMR modulation switch condition."
        ::= { provRadioSettingGroup 4 }

    provAmrSWCondEntry OBJECT-TYPE
        SYNTAX       ProvAmrSWCondEntry
        MAX-ACCESS   not-accessible
        STATUS       current
        DESCRIPTION  ""
        INDEX        { provAmrSWCondIfIndex }
        ::= { provAmrSWCondTable 1 }

    ProvAmrSWCondEntry ::= SEQUENCE {
        provAmrSWCondIfIndex    InterfaceIndex,
        provAmrSWCondNEAddress  IpAddress,
        amrSwitchCondition      INTEGER,
        amrSwitchTransition     INTEGER
    }

    provAmrSWCondIfIndex OBJECT-TYPE
        SYNTAX       InterfaceIndex
        MAX-ACCESS   not-accessible
        STATUS       current
        DESCRIPTION  "Index of this table."
        ::= { provAmrSWCondEntry 1 }

    provAmrSWCondNEAddress OBJECT-TYPE
        SYNTAX       IpAddress
        MAX-ACCESS   not-accessible
        STATUS       current
        DESCRIPTION  "reserved."
        ::= { provAmrSWCondEntry 2 }

    amrSwitchCondition OBJECT-TYPE
        SYNTAX       INTEGER { invalid(0), cnrRsl(1), cnr(2) }
        MAX-ACCESS   read-write
        STATUS       current
        DESCRIPTION
            "AMR Switch Condition. This object determines the AMR modulation
            switch condition includes Receive Signal Level or not."
        ::= { provAmrSWCondEntry 3 }

    amrSwitchTransition OBJECT-TYPE
        SYNTAX       INTEGER { invalid(0), normal(1), sensitive(2) }
        MAX-ACCESS   read-write
        STATUS       current
        DESCRIPTION  "AMR Switch Transition."
        ::= { provAmrSWCondEntry 4 }

    provModemHeaderCompressTable OBJECT-TYPE
        SYNTAX       SEQUENCE OF ProvModemHeaderCompressEntry
        MAX-ACCESS   not-accessible
        STATUS       current
        DESCRIPTION
            "This table configures Header Compression Function.
            This table is created automatically when the Modem Card is
            provisioned, if the F/W supports the new Header Compression
            function."
        ::= { provRadioSettingGroup 5 }

    provModemHeaderCompressEntry OBJECT-TYPE
        SYNTAX       ProvModemHeaderCompressEntry
        MAX-ACCESS   not-accessible
        STATUS       current
        DESCRIPTION  ""
        INDEX        { provModemHeaderCompressIfIndex }
        ::= { provModemHeaderCompressTable 1 }

    ProvModemHeaderCompressEntry ::= SEQUENCE {
        provModemHeaderCompressIfIndex    InterfaceIndex,
        provModemHeaderCompressNEAddress  IpAddress,
        provModemHeaderCompressMode       INTEGER
    }

    provModemHeaderCompressIfIndex OBJECT-TYPE
        SYNTAX       InterfaceIndex
        MAX-ACCESS   not-accessible
        STATUS       current
        DESCRIPTION  "Index of this table."
        ::= { provModemHeaderCompressEntry 1 }

    provModemHeaderCompressNEAddress OBJECT-TYPE
        SYNTAX       IpAddress
        MAX-ACCESS   not-accessible
        STATUS       current
        DESCRIPTION  "reserved."
        ::= { provModemHeaderCompressEntry 2 }

    provModemHeaderCompressMode OBJECT-TYPE
        SYNTAX       INTEGER {
                         disable(1),
                         mac(2),
                         macWithIpv4(3),
                         macWithIpv6(4),
                         macWithMpls(5),
                         enhancedMacWithIpv4(6),
                         enhancedMacWithIpv6(7),
                         enhancedMacWithMpls(8)
                     }
        MAX-ACCESS   read-write
        STATUS       current
        DESCRIPTION
            "Modem Header/Payload* Compression.
            The previous header compress object 'headerCompress' acts as
            read-only object, when this object is supported. And this object
            is set to other than 'mac', the value of 'headerCompress' will be
            changed to 'disable'.
            (*iPASOLINK VR series only)"
        DEFVAL       { disable }
        ::= { provModemHeaderCompressEntry 3 }

    provTxPowerContTable OBJECT-TYPE
        SYNTAX       SEQUENCE OF ProvTxPowerContEntry
        MAX-ACCESS   not-accessible
        STATUS       current
        DESCRIPTION  "Configures the Tx Power Control."
        ::= { provisioningGroup 6 }

    provTxPowerContEntry OBJECT-TYPE
        SYNTAX       ProvTxPowerContEntry
        MAX-ACCESS   not-accessible
        STATUS       current
        DESCRIPTION  ""
        INDEX        { provTxPowerContIfIndex }
        ::= { provTxPowerContTable 1 }

    ProvTxPowerContEntry ::= SEQUENCE {
        provTxPowerContIfIndex    InterfaceIndex,
        provTxPowerContNEAddress  IpAddress,
        atpcRangeMax              Integer32,
        atpcRangeMin              Integer32,
        atpcHysteresis            Integer32,
        mtpcTxPower               Integer32,
        rxThresholdLevel          Integer32
    }

    provTxPowerContIfIndex OBJECT-TYPE
        SYNTAX       InterfaceIndex
        MAX-ACCESS   not-accessible
        STATUS       current
        DESCRIPTION  "Index of this table."
        ::= { provTxPowerContEntry 1 }

    provTxPowerContNEAddress OBJECT-TYPE
        SYNTAX       IpAddress
        MAX-ACCESS   not-accessible
        STATUS       current
        DESCRIPTION  "reserved."
        ::= { provTxPowerContEntry 2 }

    atpcRangeMax OBJECT-TYPE
        SYNTAX       Integer32 (-380..400)
        MAX-ACCESS   read-write
        STATUS       current
        DESCRIPTION  "The maximum range of ATPC Power."
        ::= { provTxPowerContEntry 3 }

    atpcRangeMin OBJECT-TYPE
        SYNTAX       Integer32 (-380..400)
        MAX-ACCESS   read-write
        STATUS       current
        DESCRIPTION  "The minimum range of ATPC Power."
        ::= { provTxPowerContEntry 4 }

    atpcHysteresis OBJECT-TYPE
        SYNTAX       Integer32 (0..9)
        MAX-ACCESS   read-write
        STATUS       current
        DESCRIPTION  "Hysterisis of the ATPC."
        ::= { provTxPowerContEntry 5 }

    mtpcTxPower OBJECT-TYPE
        SYNTAX       Integer32 (-380..400)
        MAX-ACCESS   read-write
        STATUS       current
        DESCRIPTION  "Power Setting of MTPC Mode."
        ::= { provTxPowerContEntry 6 }

    rxThresholdLevel OBJECT-TYPE
        SYNTAX       Integer32 (-90..-30)
        MAX-ACCESS   read-write
        STATUS       current
        DESCRIPTION  "The RX Threshold Level of ATPC Mode."
        ::= { provTxPowerContEntry 7 }

    provAlmModeTable OBJECT-TYPE
        SYNTAX       SEQUENCE OF ProvAlmModeEntry
        MAX-ACCESS   not-accessible
        STATUS       current
        DESCRIPTION  ""
        ::= { provisioningGroup 7 }

    provAlmModeEntry OBJECT-TYPE
        SYNTAX       ProvAlmModeEntry
        MAX-ACCESS   not-accessible
        STATUS       current
        DESCRIPTION  ""
        INDEX        { provAlmModeIfIndex }
        ::= { provAlmModeTable 1 }

    ProvAlmModeEntry ::= SEQUENCE {
        provAlmModeIfIndex    InterfaceIndex,
        provAlmModeNEAddress  IpAddress,
        atpcPowerModeSet      INTEGER,
        oduCommAlmModeSet     INTEGER
    }

    provAlmModeIfIndex OBJECT-TYPE
        SYNTAX       InterfaceIndex
        MAX-ACCESS   not-accessible
        STATUS       current
        DESCRIPTION  "Index of this table."
        ::= { provAlmModeEntry 1 }

    provAlmModeNEAddress OBJECT-TYPE
        SYNTAX       IpAddress
        MAX-ACCESS   not-accessible
        STATUS       current
        DESCRIPTION  "reserved."
        ::= { provAlmModeEntry 2 }

    atpcPowerModeSet OBJECT-TYPE
        SYNTAX       INTEGER { invalid(0), max(1), min(2), hold(3) }
        MAX-ACCESS   read-write
        STATUS       current
        DESCRIPTION  "ATPC Power Mode."
        ::= { provAlmModeEntry 3 }

    oduCommAlmModeSet OBJECT-TYPE
        SYNTAX       INTEGER { invalid(0), mute(1), hold(2) }
        MAX-ACCESS   read-write
        STATUS       current
        DESCRIPTION  "ODU Communication Alarm Mode."
        ::= { provAlmModeEntry 4 }

    provBERThresholdGroup OBJECT IDENTIFIER
        ::= { provisioningGroup 8 }

    provRadioBERThresholdTable OBJECT-TYPE
        SYNTAX       SEQUENCE OF ProvRadioBERThresholdEntry
        MAX-ACCESS   not-accessible
        STATUS       current
        DESCRIPTION  ""
        ::= { provBERThresholdGroup 1 }

    provRadioBERThresholdEntry OBJECT-TYPE
        SYNTAX       ProvRadioBERThresholdEntry
        MAX-ACCESS   not-accessible
        STATUS       current
        DESCRIPTION  ""
        INDEX        { provRadioBERThresholdIfIndex }
        ::= { provRadioBERThresholdTable 1 }

    ProvRadioBERThresholdEntry ::= SEQUENCE {
        provRadioBERThresholdIfIndex    InterfaceIndex,
        provRadioBERThresholdNEAddress  IpAddress,
        highBER                         INTEGER,
        lowBER                          INTEGER
    }

    provRadioBERThresholdIfIndex OBJECT-TYPE
        SYNTAX       InterfaceIndex
        MAX-ACCESS   not-accessible
        STATUS       current
        DESCRIPTION  "Index of this table."
        ::= { provRadioBERThresholdEntry 1 }

    provRadioBERThresholdNEAddress OBJECT-TYPE
        SYNTAX       IpAddress
        MAX-ACCESS   not-accessible
        STATUS       current
        DESCRIPTION  "reserved."
        ::= { provRadioBERThresholdEntry 2 }

    highBER OBJECT-TYPE
        SYNTAX       INTEGER {
                         invalid(0),
                         ber1e2(1),
                         ber1e3(2),
                         ber1e4(3),
                         ber1e5(4)
                     }
        MAX-ACCESS   read-write
        STATUS       current
        DESCRIPTION  "The threshold configuration of High BER alarm."
        ::= { provRadioBERThresholdEntry 3 }

    lowBER OBJECT-TYPE
        SYNTAX       INTEGER {
                         invalid(0),
                         ber1e6(1),
                         ber1e7(2),
                         ber1e8(3),
                         ber1e9(4)
                     }
        MAX-ACCESS   read-write
        STATUS       current
        DESCRIPTION  "The threshold configuration of Low BER alarm."
        ::= { provRadioBERThresholdEntry 4 }

    provStm1BERThresholdTable OBJECT-TYPE
        SYNTAX       SEQUENCE OF ProvStm1BERThresholdEntry
        MAX-ACCESS   not-accessible
        STATUS       current
        DESCRIPTION  ""
        ::= { provBERThresholdGroup 2 }

    provStm1BERThresholdEntry OBJECT-TYPE
        SYNTAX       ProvStm1BERThresholdEntry
        MAX-ACCESS   not-accessible
        STATUS       current
        DESCRIPTION  ""
        INDEX        { provStm1BERThresholdIfIndex }
        ::= { provStm1BERThresholdTable 1 }

    ProvStm1BERThresholdEntry ::= SEQUENCE {
        provStm1BERThresholdIfIndex    InterfaceIndex,
        provStm1BERThresholdNEAddress  IpAddress,
        eBER                           INTEGER,
        sd                             INTEGER
    }

    provStm1BERThresholdIfIndex OBJECT-TYPE
        SYNTAX       InterfaceIndex
        MAX-ACCESS   not-accessible
        STATUS       current
        DESCRIPTION  "Index of this table."
        ::= { provStm1BERThresholdEntry 1 }

    provStm1BERThresholdNEAddress OBJECT-TYPE
        SYNTAX       IpAddress
        MAX-ACCESS   not-accessible
        STATUS       current
        DESCRIPTION  "reserved."
        ::= { provStm1BERThresholdEntry 2 }

    eBER OBJECT-TYPE
        SYNTAX       INTEGER { invalid(0), ber1e3(1), ber1e4(2), ber1e5(3) }
        MAX-ACCESS   read-write
        STATUS       current
        DESCRIPTION  "The threshold configuration of eBER alarm."
        ::= { provStm1BERThresholdEntry 3 }

    sd OBJECT-TYPE
        SYNTAX       INTEGER {
                         invalid(0),
                         ber1e5(1),
                         ber1e6(2),
                         ber1e7(3),
                         ber1e8(4),
                         ber1e9(5)
                     }
        MAX-ACCESS   read-write
        STATUS       current
        DESCRIPTION  "The threshold configuration of Signal Degrade."
        ::= { provStm1BERThresholdEntry 4 }

    provPMONSelectTable OBJECT-TYPE
        SYNTAX       SEQUENCE OF ProvPMONSelectEntry
        MAX-ACCESS   not-accessible
        STATUS       current
        DESCRIPTION  ""
        ::= { provisioningGroup 9 }

    provPMONSelectEntry OBJECT-TYPE
        SYNTAX       ProvPMONSelectEntry
        MAX-ACCESS   not-accessible
        STATUS       current
        DESCRIPTION  ""
        INDEX        { provPMONSelectIfIndex }
        ::= { provPMONSelectTable 1 }

    ProvPMONSelectEntry ::= SEQUENCE {
        provPMONSelectIfIndex    Integer32,
        provPMONSelectNEAddress  IpAddress,
        pmonRxLevelTCNThreshold  Integer32
    }

    provPMONSelectIfIndex OBJECT-TYPE
        SYNTAX       Integer32
        MAX-ACCESS   not-accessible
        STATUS       current
        DESCRIPTION  "Index of this table."
        ::= { provPMONSelectEntry 1 }

    provPMONSelectNEAddress OBJECT-TYPE
        SYNTAX       IpAddress
        MAX-ACCESS   not-accessible
        STATUS       current
        DESCRIPTION  "reserved."
        ::= { provPMONSelectEntry 2 }

    pmonRxLevelTCNThreshold OBJECT-TYPE
        SYNTAX       Integer32 (-99..-30)
        MAX-ACCESS   read-write
        STATUS       current
        DESCRIPTION  "The minimum threshold of Rx Level Alarm."
        ::= { provPMONSelectEntry 3 }

    provTCNThresholdGroup OBJECT IDENTIFIER
        ::= { provisioningGroup 10 }

    provTCNThreshold15minRadioGroup OBJECT IDENTIFIER
        ::= { provTCNThresholdGroup 1 }

    provTCNThreshold15minRadioTable OBJECT-TYPE
        SYNTAX       SEQUENCE OF ProvTCNThreshold15minRadioEntry
        MAX-ACCESS   not-accessible
        STATUS       current
        DESCRIPTION
            "This table contains threshold configuration for monitoring of
            Radio Link.
            For high capacity radio equipment, if
            provTCNThreshold15minRadio2Table is instantiated, this table acts
            as read-only and this table returns same value of
            provTCNThreshold15minRadio2Table."
        ::= { provTCNThreshold15minRadioGroup 1 }

    provTCNThreshold15minRadioEntry OBJECT-TYPE
        SYNTAX       ProvTCNThreshold15minRadioEntry
        MAX-ACCESS   not-accessible
        STATUS       current
        DESCRIPTION  ""
        INDEX        {
                         provTCNThreshold15minModemIfIndex,
                         provTCNThreshold15minModemMonitorName
                     }
        ::= { provTCNThreshold15minRadioTable 1 }

    ProvTCNThreshold15minRadioEntry ::= SEQUENCE {
        provTCNThreshold15minModemIfIndex      InterfaceIndex,
        provTCNThreshold15minModemMonitorName  INTEGER,
        provTCNThreshold15minRadioNEAddress    IpAddress,
        provTCNThreshold15minRfOccurValue      Integer32,
        provTCNThreshold15minRfRecoverValue    Integer32
    }

    provTCNThreshold15minModemIfIndex OBJECT-TYPE
        SYNTAX       InterfaceIndex
        MAX-ACCESS   not-accessible
        STATUS       current
        DESCRIPTION  "Index of this table."
        ::= { provTCNThreshold15minRadioEntry 1 }

    provTCNThreshold15minModemMonitorName OBJECT-TYPE
        SYNTAX       INTEGER { bbe(1), es(2), ses(3), sep(4), uas(5), ofs(6) }
        MAX-ACCESS   not-accessible
        STATUS       current
        DESCRIPTION
            "Index of this table. This object represents the monitoring
            item."
        ::= { provTCNThreshold15minRadioEntry 2 }

    provTCNThreshold15minRadioNEAddress OBJECT-TYPE
        SYNTAX       IpAddress
        MAX-ACCESS   not-accessible
        STATUS       current
        DESCRIPTION  "reserved."
        ::= { provTCNThreshold15minRadioEntry 3 }

    provTCNThreshold15minRfOccurValue OBJECT-TYPE
        SYNTAX       Integer32
        MAX-ACCESS   read-write
        STATUS       current
        DESCRIPTION
            "The threshold of alarm detection per 15 minutes monitoring item
            of the Radio Link."
        ::= { provTCNThreshold15minRadioEntry 4 }

    provTCNThreshold15minRfRecoverValue OBJECT-TYPE
        SYNTAX       Integer32
        MAX-ACCESS   read-write
        STATUS       current
        DESCRIPTION
            "The threshold of alarm clearing per 15minites monitoring item of
            the Radio Link."
        ::= { provTCNThreshold15minRadioEntry 5 }

    provTCNThreshold15minCableGroup OBJECT IDENTIFIER
        ::= { provTCNThresholdGroup 2 }

    provTCNThreshold15minThroughModeGroup OBJECT IDENTIFIER
        ::= { provTCNThreshold15minCableGroup 1 }

    provTCNThreshold15minTmRsTable OBJECT-TYPE
        SYNTAX       SEQUENCE OF ProvTCNThreshold15minTmRsEntry
        MAX-ACCESS   not-accessible
        STATUS       current
        DESCRIPTION  ""
        ::= { provTCNThreshold15minThroughModeGroup 1 }

    provTCNThreshold15minTmRsEntry OBJECT-TYPE
        SYNTAX       ProvTCNThreshold15minTmRsEntry
        MAX-ACCESS   not-accessible
        STATUS       current
        DESCRIPTION  ""
        INDEX        {
                         provTCNThreshold15minTmRsIfIndex,
                         provTCNThreshold15minTmRsMonitorName
                     }
        ::= { provTCNThreshold15minTmRsTable 1 }

    ProvTCNThreshold15minTmRsEntry ::= SEQUENCE {
        provTCNThreshold15minTmRsIfIndex       InterfaceIndex,
        provTCNThreshold15minTmRsMonitorName   INTEGER,
        provTCNThreshold15minTmRsNEAddress     IpAddress,
        provTCNThreshold15minTmRsOccurValue    Integer32,
        provTCNThreshold15minTmRsRecoverValue  Integer32
    }

    provTCNThreshold15minTmRsIfIndex OBJECT-TYPE
        SYNTAX       InterfaceIndex
        MAX-ACCESS   not-accessible
        STATUS       current
        DESCRIPTION  "Index of this table."
        ::= { provTCNThreshold15minTmRsEntry 1 }

    provTCNThreshold15minTmRsMonitorName OBJECT-TYPE
        SYNTAX       INTEGER { bbe(1), es(2), ses(3), sep(4), uas(5), ofs(6) }
        MAX-ACCESS   not-accessible
        STATUS       current
        DESCRIPTION
            "Index of this table. The object represents the montioring item."
        ::= { provTCNThreshold15minTmRsEntry 2 }

    provTCNThreshold15minTmRsNEAddress OBJECT-TYPE
        SYNTAX       IpAddress
        MAX-ACCESS   not-accessible
        STATUS       current
        DESCRIPTION  "reserved."
        ::= { provTCNThreshold15minTmRsEntry 3 }

    provTCNThreshold15minTmRsOccurValue OBJECT-TYPE
        SYNTAX       Integer32
        MAX-ACCESS   read-write
        STATUS       current
        DESCRIPTION
            "The threshold of alarm detection per 15 minutes monitoring item
            of the Throughmode STM-1 RS layer."
        ::= { provTCNThreshold15minTmRsEntry 4 }

    provTCNThreshold15minTmRsRecoverValue OBJECT-TYPE
        SYNTAX       Integer32
        MAX-ACCESS   read-write
        STATUS       current
        DESCRIPTION
            "the threshold of alarm clearing per 15 minutes monitoring item
            of the throughmode STM-1 RS layer."
        ::= { provTCNThreshold15minTmRsEntry 5 }

    provTCNThreshold15minTmDMRRsTable OBJECT-TYPE
        SYNTAX       SEQUENCE OF ProvTCNThreshold15minTmDMRRsEntry
        MAX-ACCESS   not-accessible
        STATUS       current
        DESCRIPTION  ""
        ::= { provTCNThreshold15minThroughModeGroup 2 }

    provTCNThreshold15minTmDMRRsEntry OBJECT-TYPE
        SYNTAX       ProvTCNThreshold15minTmDMRRsEntry
        MAX-ACCESS   not-accessible
        STATUS       current
        DESCRIPTION  ""
        INDEX        {
                         provTCNThreshold15minTmDMRRsIfIndex,
                         provTCNThreshold15minTmDMRRsMonitorName
                     }
        ::= { provTCNThreshold15minTmDMRRsTable 1 }

    ProvTCNThreshold15minTmDMRRsEntry ::= SEQUENCE {
        provTCNThreshold15minTmDMRRsIfIndex       InterfaceIndex,
        provTCNThreshold15minTmDMRRsMonitorName   INTEGER,
        provTCNThreshold15minTmDMRRsNEAddress     IpAddress,
        provTCNThreshold15minTmDMRRsOccurValue    Integer32,
        provTCNThreshold15minTmDMRRsRecoverValue  Integer32
    }

    provTCNThreshold15minTmDMRRsIfIndex OBJECT-TYPE
        SYNTAX       InterfaceIndex
        MAX-ACCESS   not-accessible
        STATUS       current
        DESCRIPTION  "Index of this table."
        ::= { provTCNThreshold15minTmDMRRsEntry 1 }

    provTCNThreshold15minTmDMRRsMonitorName OBJECT-TYPE
        SYNTAX       INTEGER { bbe(1), es(2), ses(3), sep(4), uas(5), ofs(6) }
        MAX-ACCESS   not-accessible
        STATUS       current
        DESCRIPTION
            "Index of the table. The object represents the monintoring item."
        ::= { provTCNThreshold15minTmDMRRsEntry 2 }

    provTCNThreshold15minTmDMRRsNEAddress OBJECT-TYPE
        SYNTAX       IpAddress
        MAX-ACCESS   not-accessible
        STATUS       current
        DESCRIPTION  "reserved."
        ::= { provTCNThreshold15minTmDMRRsEntry 3 }

    provTCNThreshold15minTmDMRRsOccurValue OBJECT-TYPE
        SYNTAX       Integer32
        MAX-ACCESS   read-write
        STATUS       current
        DESCRIPTION
            "The threshold of alarm detection per 15 minute montioring item
            of DMR Mode STM-1 RS layer."
        ::= { provTCNThreshold15minTmDMRRsEntry 4 }

    provTCNThreshold15minTmDMRRsRecoverValue OBJECT-TYPE
        SYNTAX       Integer32
        MAX-ACCESS   read-write
        STATUS       current
        DESCRIPTION
            "The threshold of alarm clearing per 15 minute monitoring item of
            DMR Mode STM-1 Rs layer."
        ::= { provTCNThreshold15minTmDMRRsEntry 5 }

    provTCNThreshold15minChannelizedModeGroup OBJECT IDENTIFIER
        ::= { provTCNThreshold15minCableGroup 2 }

    provTCNThreshold15minChRsTable OBJECT-TYPE
        SYNTAX       SEQUENCE OF ProvTCNThreshold15minChRsEntry
        MAX-ACCESS   not-accessible
        STATUS       current
        DESCRIPTION  ""
        ::= { provTCNThreshold15minChannelizedModeGroup 1 }

    provTCNThreshold15minChRsEntry OBJECT-TYPE
        SYNTAX       ProvTCNThreshold15minChRsEntry
        MAX-ACCESS   not-accessible
        STATUS       current
        DESCRIPTION  ""
        INDEX        {
                         provTCNThreshold15minChRsIfIndex,
                         provTCNThreshold15minChRsMonitorName
                     }
        ::= { provTCNThreshold15minChRsTable 1 }

    ProvTCNThreshold15minChRsEntry ::= SEQUENCE {
        provTCNThreshold15minChRsIfIndex       InterfaceIndex,
        provTCNThreshold15minChRsMonitorName   INTEGER,
        provTCNThreshold15minChRsNEAddress     IpAddress,
        provTCNThreshold15minChRsOccurValue    Integer32,
        provTCNThreshold15minChRsRecoverValue  Integer32
    }

    provTCNThreshold15minChRsIfIndex OBJECT-TYPE
        SYNTAX       InterfaceIndex
        MAX-ACCESS   not-accessible
        STATUS       current
        DESCRIPTION  "Index of this table."
        ::= { provTCNThreshold15minChRsEntry 1 }

    provTCNThreshold15minChRsMonitorName OBJECT-TYPE
        SYNTAX       INTEGER { bbe(1), es(2), ses(3), sep(4), uas(5), ofs(6) }
        MAX-ACCESS   not-accessible
        STATUS       current
        DESCRIPTION
            "Index of this table. The object represents the monitoring item."
        ::= { provTCNThreshold15minChRsEntry 2 }

    provTCNThreshold15minChRsNEAddress OBJECT-TYPE
        SYNTAX       IpAddress
        MAX-ACCESS   not-accessible
        STATUS       current
        DESCRIPTION  "reserved."
        ::= { provTCNThreshold15minChRsEntry 3 }

    provTCNThreshold15minChRsOccurValue OBJECT-TYPE
        SYNTAX       Integer32
        MAX-ACCESS   read-write
        STATUS       current
        DESCRIPTION
            "The threshold of alarm detection of 15 minute monitoring of
            Channerized mode of STM-1 RS layer."
        ::= { provTCNThreshold15minChRsEntry 4 }

    provTCNThreshold15minChRsRecoverValue OBJECT-TYPE
        SYNTAX       Integer32
        MAX-ACCESS   read-write
        STATUS       current
        DESCRIPTION
            "The threshold of alarm clearing of 15 minute monitoring of
            Channerized mode of STM-1 RS layer."
        ::= { provTCNThreshold15minChRsEntry 5 }

    provTCNThreshold15minChMsTable OBJECT-TYPE
        SYNTAX       SEQUENCE OF ProvTCNThreshold15minChMsEntry
        MAX-ACCESS   not-accessible
        STATUS       current
        DESCRIPTION  ""
        ::= { provTCNThreshold15minChannelizedModeGroup 2 }

    provTCNThreshold15minChMsEntry OBJECT-TYPE
        SYNTAX       ProvTCNThreshold15minChMsEntry
        MAX-ACCESS   not-accessible
        STATUS       current
        DESCRIPTION  ""
        INDEX        {
                         provTCNThreshold15minChMsIfIndex,
                         provTCNThreshold15minChMsMonitorName
                     }
        ::= { provTCNThreshold15minChMsTable 1 }

    ProvTCNThreshold15minChMsEntry ::= SEQUENCE {
        provTCNThreshold15minChMsIfIndex       InterfaceIndex,
        provTCNThreshold15minChMsMonitorName   INTEGER,
        provTCNThreshold15minChMsNEAddress     IpAddress,
        provTCNThreshold15minChMsOccurValue    Integer32,
        provTCNThreshold15minChMsRecoverValue  Integer32
    }

    provTCNThreshold15minChMsIfIndex OBJECT-TYPE
        SYNTAX       InterfaceIndex
        MAX-ACCESS   not-accessible
        STATUS       current
        DESCRIPTION  "Index of this table."
        ::= { provTCNThreshold15minChMsEntry 1 }

    provTCNThreshold15minChMsMonitorName OBJECT-TYPE
        SYNTAX       INTEGER { bbe(1), es(2), ses(3), sep(4), uas(5) }
        MAX-ACCESS   not-accessible
        STATUS       current
        DESCRIPTION
            "Index of the table. The object represents the monitoring item."
        ::= { provTCNThreshold15minChMsEntry 2 }

    provTCNThreshold15minChMsNEAddress OBJECT-TYPE
        SYNTAX       IpAddress
        MAX-ACCESS   not-accessible
        STATUS       current
        DESCRIPTION  "reserved."
        ::= { provTCNThreshold15minChMsEntry 3 }

    provTCNThreshold15minChMsOccurValue OBJECT-TYPE
        SYNTAX       Integer32
        MAX-ACCESS   read-write
        STATUS       current
        DESCRIPTION
            "The threshold of alarm detection of 15 minutes monitoring of
            Channelized STM-1 MS layer."
        ::= { provTCNThreshold15minChMsEntry 4 }

    provTCNThreshold15minChMsRecoverValue OBJECT-TYPE
        SYNTAX       Integer32
        MAX-ACCESS   read-write
        STATUS       current
        DESCRIPTION
            "The threshold of alarm clearing of 15 minutes monitoring of
            Channelized STM-1 MS layer."
        ::= { provTCNThreshold15minChMsEntry 5 }

    provTCNThreshold15min16E1Group OBJECT IDENTIFIER
        ::= { provTCNThreshold15minCableGroup 3 }

    provTCNThreshold15min16E1PdhTable OBJECT-TYPE
        SYNTAX       SEQUENCE OF ProvTCNThreshold15min16E1PdhEntry
        MAX-ACCESS   not-accessible
        STATUS       current
        DESCRIPTION  ""
        ::= { provTCNThreshold15min16E1Group 1 }

    provTCNThreshold15min16E1PdhEntry OBJECT-TYPE
        SYNTAX       ProvTCNThreshold15min16E1PdhEntry
        MAX-ACCESS   not-accessible
        STATUS       current
        DESCRIPTION  ""
        INDEX        {
                         provTCNThreshold15min16E1PdhIfIndex,
                         provTCNThreshold15min16E1PdhMonitorName
                     }
        ::= { provTCNThreshold15min16E1PdhTable 1 }

    ProvTCNThreshold15min16E1PdhEntry ::= SEQUENCE {
        provTCNThreshold15min16E1PdhIfIndex       InterfaceIndex,
        provTCNThreshold15min16E1PdhMonitorName   INTEGER,
        provTCNThreshold15min16E1PdhNEAddress     IpAddress,
        provTCNThreshold15min16E1PdhOccurValue    Unsigned32,
        provTCNThreshold15min16E1PdhRecoverValue  Unsigned32
    }

    provTCNThreshold15min16E1PdhIfIndex OBJECT-TYPE
        SYNTAX       InterfaceIndex
        MAX-ACCESS   not-accessible
        STATUS       current
        DESCRIPTION  "Index of this table."
        ::= { provTCNThreshold15min16E1PdhEntry 1 }

    provTCNThreshold15min16E1PdhMonitorName OBJECT-TYPE
        SYNTAX       INTEGER { cv(1) }
        MAX-ACCESS   not-accessible
        STATUS       current
        DESCRIPTION
            "Index of this table. The object represents the monitoring item."
        ::= { provTCNThreshold15min16E1PdhEntry 2 }

    provTCNThreshold15min16E1PdhNEAddress OBJECT-TYPE
        SYNTAX       IpAddress
        MAX-ACCESS   not-accessible
        STATUS       current
        DESCRIPTION  "reserved."
        ::= { provTCNThreshold15min16E1PdhEntry 3 }

    provTCNThreshold15min16E1PdhOccurValue OBJECT-TYPE
        SYNTAX       Unsigned32
        MAX-ACCESS   read-write
        STATUS       current
        DESCRIPTION
            "The threshold of the alarm detection of 15 minutes monitoring of
            16E1."
        ::= { provTCNThreshold15min16E1PdhEntry 4 }

    provTCNThreshold15min16E1PdhRecoverValue OBJECT-TYPE
        SYNTAX       Unsigned32
        MAX-ACCESS   read-write
        STATUS       current
        DESCRIPTION
            "The threshold of the alarm clearing of 15 minutes monitoring of
            16E1."
        ::= { provTCNThreshold15min16E1PdhEntry 5 }

    provTCNThreshold1dayRadioGroup OBJECT IDENTIFIER
        ::= { provTCNThresholdGroup 3 }

    provTCNThreshold1dayRadioTable OBJECT-TYPE
        SYNTAX       SEQUENCE OF ProvTCNThreshold1dayRadioEntry
        MAX-ACCESS   not-accessible
        STATUS       current
        DESCRIPTION
            "This table contains threshold configuration for monitoring of
            Radio Link.
            For high capacity radio equipment, if
            provTCNThreshold1dayRadio2Table is instantiated, this table acts
            as read-only and this table returns same value of
            provTCNThreshold1dayRadio2Table."
        ::= { provTCNThreshold1dayRadioGroup 1 }

    provTCNThreshold1dayRadioEntry OBJECT-TYPE
        SYNTAX       ProvTCNThreshold1dayRadioEntry
        MAX-ACCESS   not-accessible
        STATUS       current
        DESCRIPTION  ""
        INDEX        {
                         provTCNThreshold1dayModemIfIndex,
                         provTCNThreshold1dayModemMonitorName
                     }
        ::= { provTCNThreshold1dayRadioTable 1 }

    ProvTCNThreshold1dayRadioEntry ::= SEQUENCE {
        provTCNThreshold1dayModemIfIndex      InterfaceIndex,
        provTCNThreshold1dayModemMonitorName  INTEGER,
        provTCNThreshold1dayRadioNEAddress    IpAddress,
        provTCNThreshold1dayRfOccurValue      Integer32,
        provTCNThreshold1dayRfRecoverValue    Integer32
    }

    provTCNThreshold1dayModemIfIndex OBJECT-TYPE
        SYNTAX       InterfaceIndex
        MAX-ACCESS   not-accessible
        STATUS       current
        DESCRIPTION  "Index of this table."
        ::= { provTCNThreshold1dayRadioEntry 1 }

    provTCNThreshold1dayModemMonitorName OBJECT-TYPE
        SYNTAX       INTEGER { bbe(1), es(2), ses(3), sep(4), uas(5), ofs(6) }
        MAX-ACCESS   not-accessible
        STATUS       current
        DESCRIPTION
            "Index of this table. The object represents the monitoring item."
        ::= { provTCNThreshold1dayRadioEntry 2 }

    provTCNThreshold1dayRadioNEAddress OBJECT-TYPE
        SYNTAX       IpAddress
        MAX-ACCESS   not-accessible
        STATUS       current
        DESCRIPTION  "reserved."
        ::= { provTCNThreshold1dayRadioEntry 3 }

    provTCNThreshold1dayRfOccurValue OBJECT-TYPE
        SYNTAX       Integer32
        MAX-ACCESS   read-write
        STATUS       current
        DESCRIPTION
            "The threshold of alarm detection of 1 day montioring of Radio
            Link."
        ::= { provTCNThreshold1dayRadioEntry 4 }

    provTCNThreshold1dayRfRecoverValue OBJECT-TYPE
        SYNTAX       Integer32
        MAX-ACCESS   read-write
        STATUS       current
        DESCRIPTION
            "The threshold of alarm clearing of 1 day monitoring of Radio
            Link."
        ::= { provTCNThreshold1dayRadioEntry 5 }

    provTCNThreshold1dayCableGroup OBJECT IDENTIFIER
        ::= { provTCNThresholdGroup 4 }

    provTCNThreshold1dayThroughModeGroup OBJECT IDENTIFIER
        ::= { provTCNThreshold1dayCableGroup 1 }

    provTCNThreshold1dayTmRsTable OBJECT-TYPE
        SYNTAX       SEQUENCE OF ProvTCNThreshold1dayTmRsEntry
        MAX-ACCESS   not-accessible
        STATUS       current
        DESCRIPTION  ""
        ::= { provTCNThreshold1dayThroughModeGroup 1 }

    provTCNThreshold1dayTmRsEntry OBJECT-TYPE
        SYNTAX       ProvTCNThreshold1dayTmRsEntry
        MAX-ACCESS   not-accessible
        STATUS       current
        DESCRIPTION  ""
        INDEX        {
                         provTCNThreshold1dayTmRsIfIndex,
                         provTCNThreshold1dayTmRsMonitorName
                     }
        ::= { provTCNThreshold1dayTmRsTable 1 }

    ProvTCNThreshold1dayTmRsEntry ::= SEQUENCE {
        provTCNThreshold1dayTmRsIfIndex       InterfaceIndex,
        provTCNThreshold1dayTmRsMonitorName   INTEGER,
        provTCNThreshold1dayTmRsNEAddress     IpAddress,
        provTCNThreshold1dayTmRsOccurValue    Integer32,
        provTCNThreshold1dayTmRsRecoverValue  Integer32
    }

    provTCNThreshold1dayTmRsIfIndex OBJECT-TYPE
        SYNTAX       InterfaceIndex
        MAX-ACCESS   not-accessible
        STATUS       current
        DESCRIPTION  "Index of this table."
        ::= { provTCNThreshold1dayTmRsEntry 1 }

    provTCNThreshold1dayTmRsMonitorName OBJECT-TYPE
        SYNTAX       INTEGER { bbe(1), es(2), ses(3), sep(4), uas(5), ofs(6) }
        MAX-ACCESS   not-accessible
        STATUS       current
        DESCRIPTION
            "Index of this table. The object of the monitoring item."
        ::= { provTCNThreshold1dayTmRsEntry 2 }

    provTCNThreshold1dayTmRsNEAddress OBJECT-TYPE
        SYNTAX       IpAddress
        MAX-ACCESS   not-accessible
        STATUS       current
        DESCRIPTION  "reserved."
        ::= { provTCNThreshold1dayTmRsEntry 3 }

    provTCNThreshold1dayTmRsOccurValue OBJECT-TYPE
        SYNTAX       Integer32
        MAX-ACCESS   read-write
        STATUS       current
        DESCRIPTION
            "The threshold of alarm detection of 1 day monitoring of
            Throughmode of STM-1 RS layer."
        ::= { provTCNThreshold1dayTmRsEntry 4 }

    provTCNThreshold1dayTmRsRecoverValue OBJECT-TYPE
        SYNTAX       Integer32
        MAX-ACCESS   read-write
        STATUS       current
        DESCRIPTION
            "The threshold of alarm clearing of 1 day monitoring of
            Throughmode of STM-1 RS layer."
        ::= { provTCNThreshold1dayTmRsEntry 5 }

    provTCNThreshold1dayTmDMRRsTable OBJECT-TYPE
        SYNTAX       SEQUENCE OF ProvTCNThreshold1dayTmDMRRsEntry
        MAX-ACCESS   not-accessible
        STATUS       current
        DESCRIPTION  ""
        ::= { provTCNThreshold1dayThroughModeGroup 2 }

    provTCNThreshold1dayTmDMRRsEntry OBJECT-TYPE
        SYNTAX       ProvTCNThreshold1dayTmDMRRsEntry
        MAX-ACCESS   not-accessible
        STATUS       current
        DESCRIPTION  ""
        INDEX        {
                         provTCNThreshold1dayTmDMRRsIfIndex,
                         provTCNThreshold1dayTmDMRRsMonitorName
                     }
        ::= { provTCNThreshold1dayTmDMRRsTable 1 }

    ProvTCNThreshold1dayTmDMRRsEntry ::= SEQUENCE {
        provTCNThreshold1dayTmDMRRsIfIndex       InterfaceIndex,
        provTCNThreshold1dayTmDMRRsMonitorName   INTEGER,
        provTCNThreshold1dayTmDMRRsNEAddress     IpAddress,
        provTCNThreshold1dayTmDMRRsOccurValue    Integer32,
        provTCNThreshold1dayTmDMRRsRecoverValue  Integer32
    }

    provTCNThreshold1dayTmDMRRsIfIndex OBJECT-TYPE
        SYNTAX       InterfaceIndex
        MAX-ACCESS   not-accessible
        STATUS       current
        DESCRIPTION  "Index of this table."
        ::= { provTCNThreshold1dayTmDMRRsEntry 1 }

    provTCNThreshold1dayTmDMRRsMonitorName OBJECT-TYPE
        SYNTAX       INTEGER { bbe(1), es(2), ses(3), sep(4), uas(5), ofs(6) }
        MAX-ACCESS   not-accessible
        STATUS       current
        DESCRIPTION
            "Index of this table. This object represents the monitoring
            item."
        ::= { provTCNThreshold1dayTmDMRRsEntry 2 }

    provTCNThreshold1dayTmDMRRsNEAddress OBJECT-TYPE
        SYNTAX       IpAddress
        MAX-ACCESS   not-accessible
        STATUS       current
        DESCRIPTION  "reserved."
        ::= { provTCNThreshold1dayTmDMRRsEntry 3 }

    provTCNThreshold1dayTmDMRRsOccurValue OBJECT-TYPE
        SYNTAX       Integer32
        MAX-ACCESS   read-write
        STATUS       current
        DESCRIPTION
            "The threshold of alarm detection of 1 day monitoring of DMR Mode
            STM-1 RS Layer."
        ::= { provTCNThreshold1dayTmDMRRsEntry 4 }

    provTCNThreshold1dayTmDMRRsRecoverValue OBJECT-TYPE
        SYNTAX       Integer32
        MAX-ACCESS   read-write
        STATUS       current
        DESCRIPTION
            "The threshold of alarm clearing of 1 day monitoring of DMR Mode
            STM-1 RS Layer."
        ::= { provTCNThreshold1dayTmDMRRsEntry 5 }

    provTCNThreshold1dayChannelizedModeGroup OBJECT IDENTIFIER
        ::= { provTCNThreshold1dayCableGroup 2 }

    provTCNThreshold1dayChRsTable OBJECT-TYPE
        SYNTAX       SEQUENCE OF ProvTCNThreshold1dayChRsEntry
        MAX-ACCESS   not-accessible
        STATUS       current
        DESCRIPTION  ""
        ::= { provTCNThreshold1dayChannelizedModeGroup 1 }

    provTCNThreshold1dayChRsEntry OBJECT-TYPE
        SYNTAX       ProvTCNThreshold1dayChRsEntry
        MAX-ACCESS   not-accessible
        STATUS       current
        DESCRIPTION  ""
        INDEX        {
                         provTCNThreshold1dayChRsIfIndex,
                         provTCNThreshold1dayChRsMonitorName
                     }
        ::= { provTCNThreshold1dayChRsTable 1 }

    ProvTCNThreshold1dayChRsEntry ::= SEQUENCE {
        provTCNThreshold1dayChRsIfIndex       InterfaceIndex,
        provTCNThreshold1dayChRsMonitorName   INTEGER,
        provTCNThreshold1dayChRsNEAddress     IpAddress,
        provTCNThreshold1dayChRsOccurValue    Integer32,
        provTCNThreshold1dayChRsRecoverValue  Integer32
    }

    provTCNThreshold1dayChRsIfIndex OBJECT-TYPE
        SYNTAX       InterfaceIndex
        MAX-ACCESS   not-accessible
        STATUS       current
        DESCRIPTION  "Index of this table."
        ::= { provTCNThreshold1dayChRsEntry 1 }

    provTCNThreshold1dayChRsMonitorName OBJECT-TYPE
        SYNTAX       INTEGER { bbe(1), es(2), ses(3), sep(4), uas(5), ofs(6) }
        MAX-ACCESS   not-accessible
        STATUS       current
        DESCRIPTION
            "Index of this table. The object represents the monitoring item."
        ::= { provTCNThreshold1dayChRsEntry 2 }

    provTCNThreshold1dayChRsNEAddress OBJECT-TYPE
        SYNTAX       IpAddress
        MAX-ACCESS   not-accessible
        STATUS       current
        DESCRIPTION  "reserved."
        ::= { provTCNThreshold1dayChRsEntry 3 }

    provTCNThreshold1dayChRsOccurValue OBJECT-TYPE
        SYNTAX       Integer32
        MAX-ACCESS   read-write
        STATUS       current
        DESCRIPTION
            "The threshold of alarm detection per 1 day monitoring item of
            Channelized mode of STM-1 RS layer."
        ::= { provTCNThreshold1dayChRsEntry 4 }

    provTCNThreshold1dayChRsRecoverValue OBJECT-TYPE
        SYNTAX       Integer32
        MAX-ACCESS   read-write
        STATUS       current
        DESCRIPTION
            "the threshold of alarm clearing per 1 day monitoring item of
            Channelized mode of STM-1 RS layer."
        ::= { provTCNThreshold1dayChRsEntry 5 }

    provTCNThreshold1dayChMsTable OBJECT-TYPE
        SYNTAX       SEQUENCE OF ProvTCNThreshold1dayChMsEntry
        MAX-ACCESS   not-accessible
        STATUS       current
        DESCRIPTION  ""
        ::= { provTCNThreshold1dayChannelizedModeGroup 2 }

    provTCNThreshold1dayChMsEntry OBJECT-TYPE
        SYNTAX       ProvTCNThreshold1dayChMsEntry
        MAX-ACCESS   not-accessible
        STATUS       current
        DESCRIPTION  ""
        INDEX        {
                         provTCNThreshold1dayChMsIfIndex,
                         provTCNThreshold1dayChMsMonitorName
                     }
        ::= { provTCNThreshold1dayChMsTable 1 }

    ProvTCNThreshold1dayChMsEntry ::= SEQUENCE {
        provTCNThreshold1dayChMsIfIndex       InterfaceIndex,
        provTCNThreshold1dayChMsMonitorName   INTEGER,
        provTCNThreshold1dayChMsNEAddress     IpAddress,
        provTCNThreshold1dayChMsOccurValue    Integer32,
        provTCNThreshold1dayChMsRecoverValue  Integer32
    }

    provTCNThreshold1dayChMsIfIndex OBJECT-TYPE
        SYNTAX       InterfaceIndex
        MAX-ACCESS   not-accessible
        STATUS       current
        DESCRIPTION  "Index of this table."
        ::= { provTCNThreshold1dayChMsEntry 1 }

    provTCNThreshold1dayChMsMonitorName OBJECT-TYPE
        SYNTAX       INTEGER { bbe(1), es(2), ses(3), sep(4), uas(5) }
        MAX-ACCESS   not-accessible
        STATUS       current
        DESCRIPTION
            "Index of this table. The object represents the monitoring item."
        ::= { provTCNThreshold1dayChMsEntry 2 }

    provTCNThreshold1dayChMsNEAddress OBJECT-TYPE
        SYNTAX       IpAddress
        MAX-ACCESS   not-accessible
        STATUS       current
        DESCRIPTION  "reserved."
        ::= { provTCNThreshold1dayChMsEntry 3 }

    provTCNThreshold1dayChMsOccurValue OBJECT-TYPE
        SYNTAX       Integer32
        MAX-ACCESS   read-write
        STATUS       current
        DESCRIPTION
            "the threshold of alarm detection per 1 day monitoring of
            Channelized mode STM-1 MS layer."
        ::= { provTCNThreshold1dayChMsEntry 4 }

    provTCNThreshold1dayChMsRecoverValue OBJECT-TYPE
        SYNTAX       Integer32
        MAX-ACCESS   read-write
        STATUS       current
        DESCRIPTION
            "the threshold of alarm clearing per 1 day monitoring of
            Channelized mode STM-1 MS layer."
        ::= { provTCNThreshold1dayChMsEntry 5 }

    provTCNThreshold1day16E1Group OBJECT IDENTIFIER
        ::= { provTCNThreshold1dayCableGroup 3 }

    provTCNThreshold1day16E1PdhTable OBJECT-TYPE
        SYNTAX       SEQUENCE OF ProvTCNThreshold1day16E1PdhEntry
        MAX-ACCESS   not-accessible
        STATUS       current
        DESCRIPTION  ""
        ::= { provTCNThreshold1day16E1Group 1 }

    provTCNThreshold1day16E1PdhEntry OBJECT-TYPE
        SYNTAX       ProvTCNThreshold1day16E1PdhEntry
        MAX-ACCESS   not-accessible
        STATUS       current
        DESCRIPTION  ""
        INDEX        {
                         provTCNThreshold1day16E1PdhIfIndex,
                         provTCNThreshold1day16E1PdhMonitorName
                     }
        ::= { provTCNThreshold1day16E1PdhTable 1 }

    ProvTCNThreshold1day16E1PdhEntry ::= SEQUENCE {
        provTCNThreshold1day16E1PdhIfIndex       InterfaceIndex,
        provTCNThreshold1day16E1PdhMonitorName   INTEGER,
        provTCNThreshold1day16E1PdhNEAddress     IpAddress,
        provTCNThreshold1day16E1PdhOccurValue    Unsigned32,
        provTCNThreshold1day16E1PdhRecoverValue  Unsigned32
    }

    provTCNThreshold1day16E1PdhIfIndex OBJECT-TYPE
        SYNTAX       InterfaceIndex
        MAX-ACCESS   not-accessible
        STATUS       current
        DESCRIPTION  "Index of this table."
        ::= { provTCNThreshold1day16E1PdhEntry 1 }

    provTCNThreshold1day16E1PdhMonitorName OBJECT-TYPE
        SYNTAX       INTEGER { cv(1) }
        MAX-ACCESS   not-accessible
        STATUS       current
        DESCRIPTION
            "Index of this table. The object represents the monitoring item."
        ::= { provTCNThreshold1day16E1PdhEntry 2 }

    provTCNThreshold1day16E1PdhNEAddress OBJECT-TYPE
        SYNTAX       IpAddress
        MAX-ACCESS   not-accessible
        STATUS       current
        DESCRIPTION  "reserved."
        ::= { provTCNThreshold1day16E1PdhEntry 3 }

    provTCNThreshold1day16E1PdhOccurValue OBJECT-TYPE
        SYNTAX       Unsigned32
        MAX-ACCESS   read-write
        STATUS       current
        DESCRIPTION
            "The threshold of alarm detection per the 1 day monitoring of
            16E1."
        ::= { provTCNThreshold1day16E1PdhEntry 4 }

    provTCNThreshold1day16E1PdhRecoverValue OBJECT-TYPE
        SYNTAX       Unsigned32
        MAX-ACCESS   read-write
        STATUS       current
        DESCRIPTION
            "The threshold of alarm clearing per the 1 day monitoring of
            16E1."
        ::= { provTCNThreshold1day16E1PdhEntry 5 }

    provTCNThreshold15minRmonGroup OBJECT IDENTIFIER
        ::= { provTCNThresholdGroup 5 }

    provTCNThreshold15minRmonTable OBJECT-TYPE
        SYNTAX       SEQUENCE OF ProvTCNThreshold15minRmonEntry
        MAX-ACCESS   not-accessible
        STATUS       current
        DESCRIPTION  "Threshold configuration of 15 min RMON items."
        ::= { provTCNThreshold15minRmonGroup 1 }

    provTCNThreshold15minRmonEntry OBJECT-TYPE
        SYNTAX       ProvTCNThreshold15minRmonEntry
        MAX-ACCESS   not-accessible
        STATUS       current
        DESCRIPTION  ""
        INDEX        { provTCNThreshold15minRmonIndex }
        ::= { provTCNThreshold15minRmonTable 1 }

    ProvTCNThreshold15minRmonEntry ::= SEQUENCE {
        provTCNThreshold15minRmonIndex                   Integer32,
        provTCNThreshold15minRmonNEAddress               IpAddress,
        provTCNThreshold15minHCRxEthStatsDropEvents      Unsigned32,
        provTCNThreshold15minHCRxEthStatsUndersizePkts   Unsigned32,
        provTCNThreshold15minHCRxEthStatsFragments       Unsigned32,
        provTCNThreshold15minHCRxEthStatsCRCAlignErrors  Unsigned32,
        provTCNThreshold15minHCRxEthStatsOversizePkts    Unsigned32,
        provTCNThreshold15minHCTxEthStatsCollisions      Unsigned32
    }

    provTCNThreshold15minRmonIndex OBJECT-TYPE
        SYNTAX       Integer32 (1..1)
        MAX-ACCESS   not-accessible
        STATUS       current
        DESCRIPTION  "Index of this table."
        ::= { provTCNThreshold15minRmonEntry 1 }

    provTCNThreshold15minRmonNEAddress OBJECT-TYPE
        SYNTAX       IpAddress
        MAX-ACCESS   not-accessible
        STATUS       current
        DESCRIPTION  "reserved."
        ::= { provTCNThreshold15minRmonEntry 2 }

    provTCNThreshold15minHCRxEthStatsDropEvents OBJECT-TYPE
        SYNTAX       Unsigned32
        MAX-ACCESS   read-write
        STATUS       current
        DESCRIPTION
            "TCN DropEvent Threshold - 15min
            value range :0-133929000
            Default    :133929000"
        ::= { provTCNThreshold15minRmonEntry 3 }

    provTCNThreshold15minHCRxEthStatsUndersizePkts OBJECT-TYPE
        SYNTAX       Unsigned32
        MAX-ACCESS   read-write
        STATUS       current
        DESCRIPTION
            "TCN UndersizePkts  Threshold - 15min
            value range :0-133929000
            Default    :133929000"
        ::= { provTCNThreshold15minRmonEntry 4 }

    provTCNThreshold15minHCRxEthStatsFragments OBJECT-TYPE
        SYNTAX       Unsigned32
        MAX-ACCESS   read-write
        STATUS       current
        DESCRIPTION
            "TCN Fragments  Threshold - 15min
            value range :0-133929000
            Default    :133929000"
        ::= { provTCNThreshold15minRmonEntry 5 }

    provTCNThreshold15minHCRxEthStatsCRCAlignErrors OBJECT-TYPE
        SYNTAX       Unsigned32
        MAX-ACCESS   read-write
        STATUS       current
        DESCRIPTION
            "TCN CRCAlignErrors  Threshold - 15min
            value range :0-133929000
            Default    :133929000"
        ::= { provTCNThreshold15minRmonEntry 6 }

    provTCNThreshold15minHCRxEthStatsOversizePkts OBJECT-TYPE
        SYNTAX       Unsigned32
        MAX-ACCESS   read-write
        STATUS       current
        DESCRIPTION
            "TCN OversizePkts  Threshold - 15min
            value range :0-133929000
            Default    :133929000"
        ::= { provTCNThreshold15minRmonEntry 7 }

    provTCNThreshold15minHCTxEthStatsCollisions OBJECT-TYPE
        SYNTAX       Unsigned32
        MAX-ACCESS   read-write
        STATUS       current
        DESCRIPTION
            "TCN Collisions  Threshold - 15min
            value range :0-133929000
            Default    :133929000"
        ::= { provTCNThreshold15minRmonEntry 8 }

    provTCNThreshold1dayRmonGroup OBJECT IDENTIFIER
        ::= { provTCNThresholdGroup 6 }

    provTCNThreshold1dayRmonTable OBJECT-TYPE
        SYNTAX       SEQUENCE OF ProvTCNThreshold1dayRmonEntry
        MAX-ACCESS   not-accessible
        STATUS       current
        DESCRIPTION  "TCN Threshold 1day"
        ::= { provTCNThreshold1dayRmonGroup 1 }

    provTCNThreshold1dayRmonEntry OBJECT-TYPE
        SYNTAX       ProvTCNThreshold1dayRmonEntry
        MAX-ACCESS   not-accessible
        STATUS       current
        DESCRIPTION  "TCN Threshold 1day"
        INDEX        { provTCNThreshold1dayRmonIndex }
        ::= { provTCNThreshold1dayRmonTable 1 }

    ProvTCNThreshold1dayRmonEntry ::= SEQUENCE {
        provTCNThreshold1dayRmonIndex                   Integer32,
        provTCNThreshold1dayRmonNEAddress               IpAddress,
        provTCNThreshold1dayHCRxEthStatsDropEvents      Unsigned32,
        provTCNThreshold1dayHCRxEthStatsUndersizePkts   Unsigned32,
        provTCNThreshold1dayHCRxEthStatsFragments       Unsigned32,
        provTCNThreshold1dayHCRxEthStatsCRCAlignErrors  Unsigned32,
        provTCNThreshold1dayHCRxEthStatsOversizePkts    Unsigned32,
        provTCNThreshold1dayHCTxEthStatsCollisions      Unsigned32
    }

    provTCNThreshold1dayRmonIndex OBJECT-TYPE
        SYNTAX       Integer32 (1..1)
        MAX-ACCESS   not-accessible
        STATUS       current
        DESCRIPTION  "Index of this table."
        ::= { provTCNThreshold1dayRmonEntry 1 }

    provTCNThreshold1dayRmonNEAddress OBJECT-TYPE
        SYNTAX       IpAddress
        MAX-ACCESS   not-accessible
        STATUS       current
        DESCRIPTION  "IP Address"
        ::= { provTCNThreshold1dayRmonEntry 2 }

    provTCNThreshold1dayHCRxEthStatsDropEvents OBJECT-TYPE
        SYNTAX       Unsigned32
        MAX-ACCESS   read-write
        STATUS       current
        DESCRIPTION
            "TCN DropEvent Threshold - 1day
            value range :0-4294967294
            Default    :4294967294"
        ::= { provTCNThreshold1dayRmonEntry 3 }

    provTCNThreshold1dayHCRxEthStatsUndersizePkts OBJECT-TYPE
        SYNTAX       Unsigned32
        MAX-ACCESS   read-write
        STATUS       current
        DESCRIPTION
            "TCN UndersizePkts  Threshold - 1day
            value range :0-4294967294
            Default    :4294967294"
        ::= { provTCNThreshold1dayRmonEntry 4 }

    provTCNThreshold1dayHCRxEthStatsFragments OBJECT-TYPE
        SYNTAX       Unsigned32
        MAX-ACCESS   read-write
        STATUS       current
        DESCRIPTION
            "TCN Fragments  Threshold - 1day
            value range :0-4294967294
            Default    :4294967294"
        ::= { provTCNThreshold1dayRmonEntry 5 }

    provTCNThreshold1dayHCRxEthStatsCRCAlignErrors OBJECT-TYPE
        SYNTAX       Unsigned32
        MAX-ACCESS   read-write
        STATUS       current
        DESCRIPTION
            "TCN CRCAlignErrors  Threshold - 1day
            value range :0-4294967294
            Default    :4294967294"
        ::= { provTCNThreshold1dayRmonEntry 6 }

    provTCNThreshold1dayHCRxEthStatsOversizePkts OBJECT-TYPE
        SYNTAX       Unsigned32
        MAX-ACCESS   read-write
        STATUS       current
        DESCRIPTION
            "TCN OversizePkts  Threshold - 1day
            value range :0-4294967294
            Default    :4294967294"
        ::= { provTCNThreshold1dayRmonEntry 7 }

    provTCNThreshold1dayHCTxEthStatsCollisions OBJECT-TYPE
        SYNTAX       Unsigned32
        MAX-ACCESS   read-write
        STATUS       current
        DESCRIPTION
            "TCN Collisions  Threshold - 1day
            value range :0-4294967294
            Default    :4294967294"
        ::= { provTCNThreshold1dayRmonEntry 8 }

    provDXCGroup OBJECT IDENTIFIER
        ::= { provisioningGroup 11 }

    provDXCTable OBJECT-TYPE
        SYNTAX       SEQUENCE OF ProvDXCEntry
        MAX-ACCESS   not-accessible
        STATUS       current
        DESCRIPTION  ""
        ::= { provDXCGroup 1 }

    provDXCEntry OBJECT-TYPE
        SYNTAX       ProvDXCEntry
        MAX-ACCESS   not-accessible
        STATUS       current
        DESCRIPTION  ""
        INDEX        { provDXCIndex }
        ::= { provDXCTable 1 }

    ProvDXCEntry ::= SEQUENCE {
        provDXCIndex      Integer32,
        provDXCNEAddress  IpAddress,
        dxcRowStatus      INTEGER,
        serviceName       DisplayString,
        aTermProtection   INTEGER,
        aTerm1            InterfaceIndexOrZero,
        aTerm2            InterfaceIndexOrZero,
        bTermProtection   INTEGER,
        bTerm1            InterfaceIndexOrZero,
        bTerm2            InterfaceIndexOrZero,
        dxcMode           INTEGER
    }

    provDXCIndex OBJECT-TYPE
        SYNTAX       Integer32 (1..2352)
        MAX-ACCESS   not-accessible
        STATUS       current
        DESCRIPTION  "Index of this table."
        ::= { provDXCEntry 1 }

    provDXCNEAddress OBJECT-TYPE
        SYNTAX       IpAddress
        MAX-ACCESS   not-accessible
        STATUS       current
        DESCRIPTION  "reserved."
        ::= { provDXCEntry 2 }

    dxcRowStatus OBJECT-TYPE
        SYNTAX       INTEGER {
                         active(1),
                         notInservice(2),
                         notReady(3),
                         createAndGo(4),
                         createAndWait(5),
                         destroy(6)
                     }
        MAX-ACCESS   read-create
        STATUS       current
        DESCRIPTION  "RowStatus of this table."
        ::= { provDXCEntry 3 }

    serviceName OBJECT-TYPE
        SYNTAX       DisplayString (SIZE(0..32))
        MAX-ACCESS   read-create
        STATUS       current
        DESCRIPTION  "Service Name"
        ::= { provDXCEntry 4 }

    aTermProtection OBJECT-TYPE
        SYNTAX       INTEGER { nonProtection(1), protection(2) }
        MAX-ACCESS   read-create
        STATUS       current
        DESCRIPTION  "Edge.A Protection"
        ::= { provDXCEntry 5 }

    aTerm1 OBJECT-TYPE
        SYNTAX       InterfaceIndexOrZero
        MAX-ACCESS   read-create
        STATUS       current
        DESCRIPTION  "Edge.A Term1"
        ::= { provDXCEntry 6 }

    aTerm2 OBJECT-TYPE
        SYNTAX       InterfaceIndexOrZero
        MAX-ACCESS   read-create
        STATUS       current
        DESCRIPTION  "Edge.A Term2"
        ::= { provDXCEntry 7 }

    bTermProtection OBJECT-TYPE
        SYNTAX       INTEGER { nonProtection(1), protection(2) }
        MAX-ACCESS   read-create
        STATUS       current
        DESCRIPTION  "Edge.B Protection"
        ::= { provDXCEntry 8 }

    bTerm1 OBJECT-TYPE
        SYNTAX       InterfaceIndexOrZero
        MAX-ACCESS   read-create
        STATUS       current
        DESCRIPTION  "Edge.B Term1"
        ::= { provDXCEntry 9 }

    bTerm2 OBJECT-TYPE
        SYNTAX       InterfaceIndexOrZero
        MAX-ACCESS   read-create
        STATUS       current
        DESCRIPTION  "Edge.B Term2"
        ::= { provDXCEntry 10 }

    dxcMode OBJECT-TYPE
        SYNTAX       INTEGER { e1(1), rst(2) }
        MAX-ACCESS   read-create
        STATUS       current
        DESCRIPTION  "Cross Connect Type"
        ::= { provDXCEntry 11 }

    provE1SncpTable OBJECT-TYPE
        SYNTAX       SEQUENCE OF ProvE1SncpEntry
        MAX-ACCESS   not-accessible
        STATUS       current
        DESCRIPTION  ""
        ::= { provDXCGroup 2 }

    provE1SncpEntry OBJECT-TYPE
        SYNTAX       ProvE1SncpEntry
        MAX-ACCESS   not-accessible
        STATUS       current
        DESCRIPTION  ""
        INDEX        { provE1SncpIndex }
        ::= { provE1SncpTable 1 }

    ProvE1SncpEntry ::= SEQUENCE {
        provE1SncpIndex      Integer32,
        provE1SncpNEAddress  IpAddress,
        holdOff              UsedNotusedValue
    }

    provE1SncpIndex OBJECT-TYPE
        SYNTAX       Integer32 (1..1)
        MAX-ACCESS   not-accessible
        STATUS       current
        DESCRIPTION  "Index of this table."
        ::= { provE1SncpEntry 1 }

    provE1SncpNEAddress OBJECT-TYPE
        SYNTAX       IpAddress
        MAX-ACCESS   not-accessible
        STATUS       current
        DESCRIPTION  "reserved."
        ::= { provE1SncpEntry 2 }

    holdOff OBJECT-TYPE
        SYNTAX       UsedNotusedValue
        MAX-ACCESS   read-write
        STATUS       current
        DESCRIPTION  "Hold Off Timer"
        ::= { provE1SncpEntry 3 }

    provDXCNumberTable OBJECT-TYPE
        SYNTAX       SEQUENCE OF ProvDXCNumberEntry
        MAX-ACCESS   not-accessible
        STATUS       current
        DESCRIPTION  ""
        ::= { provDXCGroup 5 }

    provDXCNumberEntry OBJECT-TYPE
        SYNTAX       ProvDXCNumberEntry
        MAX-ACCESS   not-accessible
        STATUS       current
        DESCRIPTION  ""
        INDEX        { provDXCNumberIndex }
        ::= { provDXCNumberTable 1 }

    ProvDXCNumberEntry ::= SEQUENCE {
        provDXCNumberIndex               Integer32,
        provDXCNumberNEAddress           IpAddress,
        provDXCTotalNumber               Integer32,
        provDXCEdgeNumOnRestrictedSlots  Integer32
    }

    provDXCNumberIndex OBJECT-TYPE
        SYNTAX       Integer32 (1..1)
        MAX-ACCESS   not-accessible
        STATUS       current
        DESCRIPTION  "Index of this table."
        ::= { provDXCNumberEntry 1 }

    provDXCNumberNEAddress OBJECT-TYPE
        SYNTAX       IpAddress
        MAX-ACCESS   not-accessible
        STATUS       current
        DESCRIPTION  "reserved."
        ::= { provDXCNumberEntry 2 }

    provDXCTotalNumber OBJECT-TYPE
        SYNTAX       Integer32 (0..2352)
        MAX-ACCESS   read-only
        STATUS       current
        DESCRIPTION  "The Total Number of Cross Connect"
        ::= { provDXCNumberEntry 3 }

    provDXCEdgeNumOnRestrictedSlots OBJECT-TYPE
        SYNTAX       Integer32 (0..336)
        MAX-ACCESS   read-only
        STATUS       current
        DESCRIPTION  "The Total Number of Channels for Restricted Slot"
        ::= { provDXCNumberEntry 4 }

    provXPICGroup OBJECT IDENTIFIER
        ::= { provisioningGroup 12 }

    provXPICTable OBJECT-TYPE
        SYNTAX       SEQUENCE OF ProvXPICEntry
        MAX-ACCESS   not-accessible
        STATUS       current
        DESCRIPTION  ""
        ::= { provXPICGroup 1 }

    provXPICEntry OBJECT-TYPE
        SYNTAX       ProvXPICEntry
        MAX-ACCESS   not-accessible
        STATUS       current
        DESCRIPTION  ""
        INDEX        { provXPICIfIndex }
        ::= { provXPICTable 1 }

    ProvXPICEntry ::= SEQUENCE {
        provXPICIfIndex       InterfaceIndex,
        provXPICNEAddress     IpAddress,
        xpicCondLoSignalFail  INTEGER,
        xdemDelayAdjust       INTEGER,
        xdemDelayAdjustNo2    INTEGER
    }

    provXPICIfIndex OBJECT-TYPE
        SYNTAX       InterfaceIndex
        MAX-ACCESS   not-accessible
        STATUS       current
        DESCRIPTION  "Index of this table."
        ::= { provXPICEntry 1 }

    provXPICNEAddress OBJECT-TYPE
        SYNTAX       IpAddress
        MAX-ACCESS   not-accessible
        STATUS       current
        DESCRIPTION  "reserved."
        ::= { provXPICEntry 2 }

    xpicCondLoSignalFail OBJECT-TYPE
        SYNTAX       INTEGER { invalid(0), mute(1), refloSelflo(2) }
        MAX-ACCESS   read-write
        STATUS       current
        DESCRIPTION  "XPIC Local Fail"
        ::= { provXPICEntry 3 }

    xdemDelayAdjust OBJECT-TYPE
        SYNTAX       INTEGER {
                         invalid(0),
                         m32ToM24(2),
                         m24ToM16(3),
                         m16ToM8(4),
                         m8ToP8(5),
                         p8ToP16(6),
                         p16ToP24(7),
                         p24ToP32(8)
                     }
        MAX-ACCESS   read-write
        STATUS       current
        DESCRIPTION  "X-DEM Delay Adjust"
        ::= { provXPICEntry 4 }

    xdemDelayAdjustNo2 OBJECT-TYPE
        SYNTAX       INTEGER {
                         invalid(0),
                         m32ToM24(2),
                         m24ToM16(3),
                         m16ToM8(4),
                         m8ToP8(5),
                         p8ToP16(6),
                         p16ToP24(7),
                         p24ToP32(8)
                     }
        MAX-ACCESS   read-write
        STATUS       current
        DESCRIPTION  "X-DEM Delay Adjust"
        ::= { provXPICEntry 5 }

    provStm1Group OBJECT IDENTIFIER
        ::= { provisioningGroup 13 }

    provStm1PortSetTable OBJECT-TYPE
        SYNTAX       SEQUENCE OF ProvStm1PortSetEntry
        MAX-ACCESS   not-accessible
        STATUS       current
        DESCRIPTION  ""
        ::= { provStm1Group 1 }

    provStm1PortSetEntry OBJECT-TYPE
        SYNTAX       ProvStm1PortSetEntry
        MAX-ACCESS   not-accessible
        STATUS       current
        DESCRIPTION  ""
        INDEX        { provStm1PortSetIfIndex }
        ::= { provStm1PortSetTable 1 }

    ProvStm1PortSetEntry ::= SEQUENCE {
        provStm1PortSetIfIndex     InterfaceIndex,
        provStm1PortSetNEAddress   IpAddress,
        stm1PortName               DisplayString,
        stm1PortUsage              UsedNotusedValue,
        stm1PathTraceTxValueJ0     DisplayString,
        stm1PathTraceRxExpValueJ0  DisplayString
    }

    provStm1PortSetIfIndex OBJECT-TYPE
        SYNTAX       InterfaceIndex
        MAX-ACCESS   not-accessible
        STATUS       current
        DESCRIPTION  "Index of this table."
        ::= { provStm1PortSetEntry 1 }

    provStm1PortSetNEAddress OBJECT-TYPE
        SYNTAX       IpAddress
        MAX-ACCESS   not-accessible
        STATUS       current
        DESCRIPTION  "reserved."
        ::= { provStm1PortSetEntry 2 }

    stm1PortName OBJECT-TYPE
        SYNTAX       DisplayString (SIZE(0..32))
        MAX-ACCESS   read-write
        STATUS       current
        DESCRIPTION  "Port Name"
        ::= { provStm1PortSetEntry 3 }

    stm1PortUsage OBJECT-TYPE
        SYNTAX       UsedNotusedValue
        MAX-ACCESS   read-write
        STATUS       current
        DESCRIPTION  "Port Usage"
        ::= { provStm1PortSetEntry 4 }

    stm1PathTraceTxValueJ0 OBJECT-TYPE
        SYNTAX       DisplayString (SIZE(0..15))
        MAX-ACCESS   read-write
        STATUS       current
        DESCRIPTION  "Section Trace Send Value"
        ::= { provStm1PortSetEntry 5 }

    stm1PathTraceRxExpValueJ0 OBJECT-TYPE
        SYNTAX       DisplayString (SIZE(0..15))
        MAX-ACCESS   read-write
        STATUS       current
        DESCRIPTION  "Expected Section Trace Value"
        ::= { provStm1PortSetEntry 6 }

    provStm1ChPortSetTable OBJECT-TYPE
        SYNTAX       SEQUENCE OF ProvStm1ChPortSetEntry
        MAX-ACCESS   not-accessible
        STATUS       current
        DESCRIPTION  ""
        ::= { provStm1Group 2 }

    provStm1ChPortSetEntry OBJECT-TYPE
        SYNTAX       ProvStm1ChPortSetEntry
        MAX-ACCESS   not-accessible
        STATUS       current
        DESCRIPTION  ""
        INDEX        { provStm1ChPortSetIfIndex }
        ::= { provStm1ChPortSetTable 1 }

    ProvStm1ChPortSetEntry ::= SEQUENCE {
        provStm1ChPortSetIfIndex    InterfaceIndex,
        provStm1ChPortSetNEAddress  IpAddress,
        stm1ModeSetting             INTEGER,
        stm1LowOrderPathTrace       Integer32,
        stm1PathTraceTxValueJ1      DisplayString,
        stm1PathTraceRxExpValueJ1   DisplayString
    }

    provStm1ChPortSetIfIndex OBJECT-TYPE
        SYNTAX       InterfaceIndex
        MAX-ACCESS   not-accessible
        STATUS       current
        DESCRIPTION  "Index of this table."
        ::= { provStm1ChPortSetEntry 1 }

    provStm1ChPortSetNEAddress OBJECT-TYPE
        SYNTAX       IpAddress
        MAX-ACCESS   not-accessible
        STATUS       current
        DESCRIPTION  "reserved."
        ::= { provStm1ChPortSetEntry 2 }

    stm1ModeSetting OBJECT-TYPE
        SYNTAX       INTEGER { invalid(0), through(1), channelized(2) }
        MAX-ACCESS   read-write
        STATUS       current
        DESCRIPTION  "STM-1 Mode"
        ::= { provStm1ChPortSetEntry 3 }

    stm1LowOrderPathTrace OBJECT-TYPE
        SYNTAX       Integer32 (0..63)
        MAX-ACCESS   read-write
        STATUS       current
        DESCRIPTION  "Low Order Path Trace Send Value"
        ::= { provStm1ChPortSetEntry 4 }

    stm1PathTraceTxValueJ1 OBJECT-TYPE
        SYNTAX       DisplayString (SIZE(0..15))
        MAX-ACCESS   read-write
        STATUS       current
        DESCRIPTION  "High Order Path Trace Send Value"
        ::= { provStm1ChPortSetEntry 5 }

    stm1PathTraceRxExpValueJ1 OBJECT-TYPE
        SYNTAX       DisplayString (SIZE(0..15))
        MAX-ACCESS   read-write
        STATUS       current
        DESCRIPTION  "Expected High Order Path Trace Value"
        ::= { provStm1ChPortSetEntry 6 }

    provStm1CardSetTable OBJECT-TYPE
        SYNTAX       SEQUENCE OF ProvStm1CardSetEntry
        MAX-ACCESS   not-accessible
        STATUS       current
        DESCRIPTION  ""
        ::= { provStm1Group 3 }

    provStm1CardSetEntry OBJECT-TYPE
        SYNTAX       ProvStm1CardSetEntry
        MAX-ACCESS   not-accessible
        STATUS       current
        DESCRIPTION  ""
        INDEX        { provStm1CardSetIndex }
        ::= { provStm1CardSetTable 1 }

    ProvStm1CardSetEntry ::= SEQUENCE {
        provStm1CardSetIndex      Integer32,
        provStm1CardSetNEAddress  IpAddress,
        stm1TraceUsageSelect      INTEGER,
        stm1TraceMismatchAction   EnableDisableValue,
        stm1SfAlarmTransfer       OffOnValue,
        stm1SdAlarmTransfer       OffOnValue,
        stm1CardLineClkSelect     Integer32
    }

    provStm1CardSetIndex OBJECT-TYPE
        SYNTAX       Integer32
        MAX-ACCESS   not-accessible
        STATUS       current
        DESCRIPTION  "Index of this table."
        ::= { provStm1CardSetEntry 1 }

    provStm1CardSetNEAddress OBJECT-TYPE
        SYNTAX       IpAddress
        MAX-ACCESS   not-accessible
        STATUS       current
        DESCRIPTION  "reserved."
        ::= { provStm1CardSetEntry 2 }

    stm1TraceUsageSelect OBJECT-TYPE
        SYNTAX       INTEGER { invalid(0), j0(1), j1(2) }
        MAX-ACCESS   read-write
        STATUS       current
        DESCRIPTION  "Trace Mode"
        ::= { provStm1CardSetEntry 3 }

    stm1TraceMismatchAction OBJECT-TYPE
        SYNTAX       EnableDisableValue
        MAX-ACCESS   read-write
        STATUS       current
        DESCRIPTION  "Trace Mismatch AIS Generation Action"
        ::= { provStm1CardSetEntry 4 }

    stm1SfAlarmTransfer OBJECT-TYPE
        SYNTAX       OffOnValue
        MAX-ACCESS   read-write
        STATUS       current
        DESCRIPTION
            "Signal Fail is transferred as TU-AIS.
            New definition for 400."
        ::= { provStm1CardSetEntry 5 }

    stm1SdAlarmTransfer OBJECT-TYPE
        SYNTAX       OffOnValue
        MAX-ACCESS   read-write
        STATUS       current
        DESCRIPTION
            "Signal Degrade is transferred by N2 byte.
            New definition for 400."
        ::= { provStm1CardSetEntry 6 }

    stm1CardLineClkSelect OBJECT-TYPE
        SYNTAX       Integer32 (1..2)
        MAX-ACCESS   read-write
        STATUS       current
        DESCRIPTION
            "Select the timing source from two STM1 channels.
            New definition for 400."
        ::= { provStm1CardSetEntry 7 }

    provExtClockGroup OBJECT IDENTIFIER
        ::= { provisioningGroup 14 }

    provTimingSourceGroup OBJECT IDENTIFIER
        ::= { provExtClockGroup 2 }

    provClkSelect400Table OBJECT-TYPE
        SYNTAX       SEQUENCE OF ProvClkSelect400Entry
        MAX-ACCESS   not-accessible
        STATUS       current
        DESCRIPTION  ""
        ::= { provTimingSourceGroup 11 }

    provClkSelect400Entry OBJECT-TYPE
        SYNTAX       ProvClkSelect400Entry
        MAX-ACCESS   not-accessible
        STATUS       current
        DESCRIPTION  ""
        INDEX        { provClkSelect400Index }
        ::= { provClkSelect400Table 1 }

    ProvClkSelect400Entry ::= SEQUENCE {
        provClkSelect400Index        Integer32,
        provClkSelect400NEAddress    IpAddress,
        e1LineClkSelect400           Integer32,
        gbeLineClkSelect400          Integer32,
        mbTimingSourceSelect400      INTEGER,
        waitToRestore400             INTEGER,
        clockSourceSelectiveMode400  INTEGER,
        gbeLineClkSelect2            Integer32
    }

    provClkSelect400Index OBJECT-TYPE
        SYNTAX       Integer32
        MAX-ACCESS   not-accessible
        STATUS       current
        DESCRIPTION  "Index of this table."
        ::= { provClkSelect400Entry 1 }

    provClkSelect400NEAddress OBJECT-TYPE
        SYNTAX       IpAddress
        MAX-ACCESS   not-accessible
        STATUS       current
        DESCRIPTION  "reserved."
        ::= { provClkSelect400Entry 2 }

    e1LineClkSelect400 OBJECT-TYPE
        SYNTAX       Integer32 (1..16)
        MAX-ACCESS   read-write
        STATUS       current
        DESCRIPTION  "E1 Line Clock Select"
        ::= { provClkSelect400Entry 3 }

    gbeLineClkSelect400 OBJECT-TYPE
        SYNTAX       Integer32 (1..8)
        MAX-ACCESS   read-write
        STATUS       current
        DESCRIPTION
            "Select the timing source from GbE channels on Main Card.
            range : 1 - 8 [iPASOLINK VR 4]
                    1 - 6 [iPASOLINK 400A/VR 2]
                    1 - 4 [iPASOLINK 400/1000/EX]
                    1 - 2, 5 - 6[iPASOLINK 200A/iX]
                    1 - 3[iPASOLINK EX/A]"
        ::= { provClkSelect400Entry 4 }

    mbTimingSourceSelect400 OBJECT-TYPE
        SYNTAX       INTEGER {
                         invalid(0),
                         internal(1),
                         dmrLineclk1(2),
                         dmrLineclk2(3),
                         auto(4),
                         dmrLineclk3(5),
                         dmrLineclk4(6),
                         dmrLineclk5(7),
                         dmrLineclk6(8),
                         dmrLineclk7(9),
                         dmrLineclk8(10),
                         dmrLineclk9(11),
                         dmrLineclk10(12),
                         dmrLineclk11(13),
                         dmrLineclk12(14),
                         dmrLineclk13(15),
                         dmrLineclk14(16)
                     }
        MAX-ACCESS   read-write
        STATUS       current
        DESCRIPTION  "Configure Timing Source."
        ::= { provClkSelect400Entry 5 }

    waitToRestore400 OBJECT-TYPE
        SYNTAX       INTEGER {
                         invalid(0),
                         sec0(1),
                         sec10(2),
                         sec20(3),
                         sec30(4),
                         min1(5),
                         min2(6),
                         min3(7),
                         min4(8),
                         min5(9),
                         min6(10),
                         min7(11),
                         min8(12),
                         min9(13),
                         min10(14),
                         min11(15),
                         min12(16),
                         min13(17),
                         min14(18),
                         min15(19)
                     }
        MAX-ACCESS   read-write
        STATUS       current
        DESCRIPTION  "Wait To Restore Timer"
        ::= { provClkSelect400Entry 6 }

    clockSourceSelectiveMode400 OBJECT-TYPE
        SYNTAX       INTEGER { qlMode(1), plMode(2) }
        MAX-ACCESS   read-write
        STATUS       current
        DESCRIPTION  "Clock Source Selective Mode"
        ::= { provClkSelect400Entry 7 }

    gbeLineClkSelect2 OBJECT-TYPE
        SYNTAX       Integer32 (1..6)
        MAX-ACCESS   read-write
        STATUS       current
        DESCRIPTION
            "Select the timing source from GbE channels on Main Card.
            range : 1 - 6 [iPASOLINK 400A]
                    1 - 4 [iPASOLINK 400/1000/EX/VR 4/VR 2]
                    1 - 2, 5 - 6[iPASOLINK 200A/iX]
                    1 [iPASOLINK EX/A]"
        ::= { provClkSelect400Entry 8 }

    provTimingSourceSelect400Table OBJECT-TYPE
        SYNTAX       SEQUENCE OF ProvTimingSourceSelect400Entry
        MAX-ACCESS   not-accessible
        STATUS       current
        DESCRIPTION  ""
        ::= { provTimingSourceGroup 12 }

    provTimingSourceSelect400Entry OBJECT-TYPE
        SYNTAX       ProvTimingSourceSelect400Entry
        MAX-ACCESS   not-accessible
        STATUS       current
        DESCRIPTION  ""
        INDEX        { provTimingSourceSelect400Index }
        ::= { provTimingSourceSelect400Table 1 }

    ProvTimingSourceSelect400Entry ::= SEQUENCE {
        provTimingSourceSelect400Index      Integer32,
        provTimingSourceSelect400NEAddress  IpAddress,
        clk2MTimingSource400Select          INTEGER,
        clk2MTimingSource400Priority        Integer32,
        forcedSsmValue400                   INTEGER,
        ssmUsage400                         UsedNotusedValue
    }

    provTimingSourceSelect400Index OBJECT-TYPE
        SYNTAX       Integer32
        MAX-ACCESS   not-accessible
        STATUS       current
        DESCRIPTION  "Index of this table."
        ::= { provTimingSourceSelect400Entry 1 }

    provTimingSourceSelect400NEAddress OBJECT-TYPE
        SYNTAX       IpAddress
        MAX-ACCESS   not-accessible
        STATUS       current
        DESCRIPTION  "reserved."
        ::= { provTimingSourceSelect400Entry 2 }

    clk2MTimingSource400Select OBJECT-TYPE
        SYNTAX       INTEGER {
                         noEntry(0),
                         extClk1(1),
                         extClk2(2),
                         lineClk1(3),
                         lineClk2(4),
                         lineClk3(5),
                         lineClk4(6),
                         lineClk5(7),
                         lineClk6(8),
                         lineClk7(9),
                         lineClk8(10),
                         lineClk9(11),
                         lineClk10(12),
                         lineClk11(13),
                         lineClk12(14),
                         lineClk13(15),
                         lineClk14(16),
                         gbeLineClk1(17),
                         gbeLineClk2(18),
                         e1LineClk(19)
                     }
        MAX-ACCESS   read-write
        STATUS       current
        DESCRIPTION  "Timing Source Select"
        ::= { provTimingSourceSelect400Entry 3 }

    clk2MTimingSource400Priority OBJECT-TYPE
        SYNTAX       Integer32 (0..12)
        MAX-ACCESS   read-write
        STATUS       current
        DESCRIPTION  "Timing Source Priority Level"
        ::= { provTimingSourceSelect400Entry 4 }

    forcedSsmValue400 OBJECT-TYPE
        SYNTAX       INTEGER { qlPrc(1), qlSsuA(2), qlSsuB(3), qlSec(4) }
        MAX-ACCESS   read-write
        STATUS       current
        DESCRIPTION  "Forced SSM Value"
        ::= { provTimingSourceSelect400Entry 5 }

    ssmUsage400 OBJECT-TYPE
        SYNTAX       UsedNotusedValue
        MAX-ACCESS   read-write
        STATUS       current
        DESCRIPTION  "SSM Usage"
        ::= { provTimingSourceSelect400Entry 6 }

    provExtClock400Table OBJECT-TYPE
        SYNTAX       SEQUENCE OF ProvExtClock400Entry
        MAX-ACCESS   not-accessible
        STATUS       current
        DESCRIPTION  ""
        ::= { provExtClockGroup 11 }

    provExtClock400Entry OBJECT-TYPE
        SYNTAX       ProvExtClock400Entry
        MAX-ACCESS   not-accessible
        STATUS       current
        DESCRIPTION  ""
        INDEX        { provExtClock400Index }
        ::= { provExtClock400Table 1 }

    ProvExtClock400Entry ::= SEQUENCE {
        provExtClock400Index               INTEGER,
        provExtClock400NEAddress           IpAddress,
        provExtClock400ExtImpedance        INTEGER,
        provExtClock400ExtInterface        INTEGER,
        provExtClock400Crc                 OffOnValue,
        provExtClock400Ssm                 INTEGER,
        provExtClock400SaBit               INTEGER,
        provExtClock400MessagePathThrough  OffOnValue,
        provExtClock400QlThreshold         INTEGER,
        provExtClock400ThresholdAisGen     UsedNotusedValue,
        provExtClock400ExtClkSel           INTEGER,
        provExtClock400AisHizSelect        INTEGER,
        provExtClock400DnuIns              OffOnValue,
        provExtClock400InsQlValue          INTEGER
    }

    provExtClock400Index OBJECT-TYPE
        SYNTAX       INTEGER { extclk(1), extclk2(2) }
        MAX-ACCESS   not-accessible
        STATUS       current
        DESCRIPTION  "Index of this table."
        ::= { provExtClock400Entry 1 }

    provExtClock400NEAddress OBJECT-TYPE
        SYNTAX       IpAddress
        MAX-ACCESS   not-accessible
        STATUS       current
        DESCRIPTION  "reserved."
        ::= { provExtClock400Entry 2 }

    provExtClock400ExtImpedance OBJECT-TYPE
        SYNTAX       INTEGER { invalid(0), ohm120(1), ohm75(2) }
        MAX-ACCESS   read-write
        STATUS       current
        DESCRIPTION  "External Clock Impedance"
        ::= { provExtClock400Entry 3 }

    provExtClock400ExtInterface OBJECT-TYPE
        SYNTAX       INTEGER { invalid(0), bps(1), hz(2) }
        MAX-ACCESS   read-write
        STATUS       current
        DESCRIPTION  "External Clock Interface"
        ::= { provExtClock400Entry 4 }

    provExtClock400Crc OBJECT-TYPE
        SYNTAX       OffOnValue
        MAX-ACCESS   read-write
        STATUS       current
        DESCRIPTION  "CRC On / Off"
        ::= { provExtClock400Entry 5 }

    provExtClock400Ssm OBJECT-TYPE
        SYNTAX       INTEGER { invalid(0), notSupport(1), support(2) }
        MAX-ACCESS   read-write
        STATUS       current
        DESCRIPTION  "SSM Support"
        ::= { provExtClock400Entry 6 }

    provExtClock400SaBit OBJECT-TYPE
        SYNTAX       INTEGER {
                         invalid(0),
                         sa4(1),
                         sa5(2),
                         sa6(3),
                         sa7(4),
                         sa8(5)
                     }
        MAX-ACCESS   read-write
        STATUS       current
        DESCRIPTION  "Sa Bit"
        ::= { provExtClock400Entry 7 }

    provExtClock400MessagePathThrough OBJECT-TYPE
        SYNTAX       OffOnValue
        MAX-ACCESS   read-write
        STATUS       current
        DESCRIPTION  "Message Pass Through"
        ::= { provExtClock400Entry 8 }

    provExtClock400QlThreshold OBJECT-TYPE
        SYNTAX       INTEGER { qlPrc(1), qlSsuA(2), qlSsuB(3), qlSec(4) }
        MAX-ACCESS   read-write
        STATUS       current
        DESCRIPTION  "QL Threshold"
        ::= { provExtClock400Entry 9 }

    provExtClock400ThresholdAisGen OBJECT-TYPE
        SYNTAX       UsedNotusedValue
        MAX-ACCESS   read-write
        STATUS       current
        DESCRIPTION  "Threshold AIS Generation Mode"
        ::= { provExtClock400Entry 10 }

    provExtClock400ExtClkSel OBJECT-TYPE
        SYNTAX       INTEGER {
                         notSelect(0),
                         neClk(1),
                         lineClk1(2),
                         lineClk2(3),
                         lineClk3(4),
                         lineClk4(5),
                         lineClk5(6),
                         lineClk6(7),
                         lineClk7(8),
                         lineClk8(9),
                         lineClk9(10),
                         lineClk10(11),
                         lineClk11(12),
                         lineClk12(13),
                         lineClk13(14),
                         lineClk14(15),
                         gbeLineClk1(16),
                         gbeLineClk2(17),
                         e1LineClk(18)
                     }
        MAX-ACCESS   read-write
        STATUS       current
        DESCRIPTION  "External Clock Out Select"
        ::= { provExtClock400Entry 11 }

    provExtClock400AisHizSelect OBJECT-TYPE
        SYNTAX       INTEGER { invalid(0), hiZ(1), ais(2) }
        MAX-ACCESS   read-write
        STATUS       current
        DESCRIPTION  "AIS Generation Mode"
        ::= { provExtClock400Entry 12 }

    provExtClock400DnuIns OBJECT-TYPE
        SYNTAX       OffOnValue
        MAX-ACCESS   read-write
        STATUS       current
        DESCRIPTION  "Timing Loop Prevention"
        ::= { provExtClock400Entry 13 }

    provExtClock400InsQlValue OBJECT-TYPE
        SYNTAX       INTEGER {
                         qlPrc(1),
                         qlSsuA(2),
                         qlSsuB(3),
                         qlOriginal(4),
                         qlSec(5),
                         qlDnu(6),
                         qlInvx(7),
                         qlFailed(8),
                         notAvail(9)
                     }
        MAX-ACCESS   read-write
        STATUS       current
        DESCRIPTION  "Forced SSM Send Value"
        ::= { provExtClock400Entry 14 }

    provRelayGroup OBJECT IDENTIFIER
        ::= { provisioningGroup 15 }

    provRelayConfigTable OBJECT-TYPE
        SYNTAX       SEQUENCE OF ProvRelayConfigEntry
        MAX-ACCESS   not-accessible
        STATUS       current
        DESCRIPTION
            "This table contains relay control and alarm output
            configuration."
        ::= { provRelayGroup 1 }

    provRelayConfigEntry OBJECT-TYPE
        SYNTAX       ProvRelayConfigEntry
        MAX-ACCESS   not-accessible
        STATUS       current
        DESCRIPTION  ""
        INDEX        { provRelayConfigIndex }
        ::= { provRelayConfigTable 1 }

    ProvRelayConfigEntry ::= SEQUENCE {
        provRelayConfigIndex      INTEGER,
        provRelayConfigNEAddress  IpAddress,
        provRelayConfigData       OCTET STRING,
        provRelayConfigData2      OCTET STRING
    }

    provRelayConfigIndex OBJECT-TYPE
        SYNTAX       INTEGER { rl1(1), rl2(2), rl3(3), rl4(4), rl5(5), rl6(6) }
        MAX-ACCESS   not-accessible
        STATUS       current
        DESCRIPTION  "Index of this table."
        ::= { provRelayConfigEntry 1 }

    provRelayConfigNEAddress OBJECT-TYPE
        SYNTAX       IpAddress
        MAX-ACCESS   not-accessible
        STATUS       current
        DESCRIPTION  "reserved."
        ::= { provRelayConfigEntry 2 }

    provRelayConfigData OBJECT-TYPE
        SYNTAX       OCTET STRING (SIZE(560..560))
        MAX-ACCESS   read-write
        STATUS       current
        DESCRIPTION  "configure alarms to be outputted to relay."
        ::= { provRelayConfigEntry 3 }

    provRelayConfigData2 OBJECT-TYPE
        SYNTAX       OCTET STRING (SIZE(100..100))
        MAX-ACCESS   read-write
        STATUS       current
        DESCRIPTION  "configure alarms to be outputted to relay."
        ::= { provRelayConfigEntry 4 }

    provClusterAssignInputTable OBJECT-TYPE
        SYNTAX       SEQUENCE OF ProvClusterAssignInputEntry
        MAX-ACCESS   not-accessible
        STATUS       current
        DESCRIPTION  "This table contains Cluster Alarm Input assignment."
        ::= { provRelayGroup 2 }

    provClusterAssignInputEntry OBJECT-TYPE
        SYNTAX       ProvClusterAssignInputEntry
        MAX-ACCESS   not-accessible
        STATUS       current
        DESCRIPTION  ""
        INDEX        { provClusterAssignInputIfIndex }
        ::= { provClusterAssignInputTable 1 }

    ProvClusterAssignInputEntry ::= SEQUENCE {
        provClusterAssignInputIfIndex    InterfaceIndex,
        provClusterAssignInputNEAddress  IpAddress,
        relayClusterAssignInput          Integer32
    }

    provClusterAssignInputIfIndex OBJECT-TYPE
        SYNTAX       InterfaceIndex
        MAX-ACCESS   not-accessible
        STATUS       current
        DESCRIPTION  "Index of this table."
        ::= { provClusterAssignInputEntry 1 }

    provClusterAssignInputNEAddress OBJECT-TYPE
        SYNTAX       IpAddress
        MAX-ACCESS   not-accessible
        STATUS       current
        DESCRIPTION  "reserved."
        ::= { provClusterAssignInputEntry 2 }

    relayClusterAssignInput OBJECT-TYPE
        SYNTAX       Integer32
        MAX-ACCESS   read-write
        STATUS       current
        DESCRIPTION  "Cluster Alarm Input assign"
        ::= { provClusterAssignInputEntry 3 }

    provClusterAssignOutputTable OBJECT-TYPE
        SYNTAX       SEQUENCE OF ProvClusterAssignOutputEntry
        MAX-ACCESS   not-accessible
        STATUS       current
        DESCRIPTION  "This table contains Cluster Alarm Output assignment."
        ::= { provRelayGroup 3 }

    provClusterAssignOutputEntry OBJECT-TYPE
        SYNTAX       ProvClusterAssignOutputEntry
        MAX-ACCESS   not-accessible
        STATUS       current
        DESCRIPTION  ""
        INDEX        { provClusterAssignOutputIndex }
        ::= { provClusterAssignOutputTable 1 }

    ProvClusterAssignOutputEntry ::= SEQUENCE {
        provClusterAssignOutputIndex      Integer32,
        provClusterAssignOutputNEAddress  IpAddress,
        relayClusterAssignOutput          Integer32,
        provHkcOutputSetting              INTEGER
    }

    provClusterAssignOutputIndex OBJECT-TYPE
        SYNTAX       Integer32
        MAX-ACCESS   not-accessible
        STATUS       current
        DESCRIPTION  "Index of this table."
        ::= { provClusterAssignOutputEntry 1 }

    provClusterAssignOutputNEAddress OBJECT-TYPE
        SYNTAX       IpAddress
        MAX-ACCESS   not-accessible
        STATUS       current
        DESCRIPTION  "reserved."
        ::= { provClusterAssignOutputEntry 2 }

    relayClusterAssignOutput OBJECT-TYPE
        SYNTAX       Integer32
        MAX-ACCESS   read-write
        STATUS       current
        DESCRIPTION  "Cluster Alarm Output assignment."
        ::= { provClusterAssignOutputEntry 3 }

    provHkcOutputSetting OBJECT-TYPE
        SYNTAX       INTEGER { invalid(0), normal(1), alarm(2) }
        MAX-ACCESS   read-write
        STATUS       current
        DESCRIPTION  "House Keeping Control Output setting."
        ::= { provClusterAssignOutputEntry 4 }

    provEOWGroup OBJECT IDENTIFIER
        ::= { provisioningGroup 16 }

    provEOWCallPolarityTable OBJECT-TYPE
        SYNTAX       SEQUENCE OF ProvEOWCallPolarityEntry
        MAX-ACCESS   not-accessible
        STATUS       current
        DESCRIPTION  "This table contains EOW Call Polarity setting."
        ::= { provEOWGroup 1 }

    provEOWCallPolarityEntry OBJECT-TYPE
        SYNTAX       ProvEOWCallPolarityEntry
        MAX-ACCESS   not-accessible
        STATUS       current
        DESCRIPTION  ""
        INDEX        { provEOWCallPolaritySlotIndex }
        ::= { provEOWCallPolarityTable 1 }

    ProvEOWCallPolarityEntry ::= SEQUENCE {
        provEOWCallPolaritySlotIndex  Integer32,
        provEOWCallPolarityNEAddress  IpAddress,
        provCallPolarity              INTEGER
    }

    provEOWCallPolaritySlotIndex OBJECT-TYPE
        SYNTAX       Integer32
        MAX-ACCESS   not-accessible
        STATUS       current
        DESCRIPTION  "Index of this table."
        ::= { provEOWCallPolarityEntry 1 }

    provEOWCallPolarityNEAddress OBJECT-TYPE
        SYNTAX       IpAddress
        MAX-ACCESS   not-accessible
        STATUS       current
        DESCRIPTION  "reserved."
        ::= { provEOWCallPolarityEntry 2 }

    provCallPolarity OBJECT-TYPE
        SYNTAX       INTEGER { invalid(0), low(1), high(2) }
        MAX-ACCESS   read-write
        STATUS       current
        DESCRIPTION  "EOW Call Polarity setting."
        ::= { provEOWCallPolarityEntry 3 }

    provEOWDscTable OBJECT-TYPE
        SYNTAX       SEQUENCE OF ProvEOWDscEntry
        MAX-ACCESS   not-accessible
        STATUS       current
        DESCRIPTION  "This table contains EOW DSC setting."
        ::= { provEOWGroup 2 }

    provEOWDscEntry OBJECT-TYPE
        SYNTAX       ProvEOWDscEntry
        MAX-ACCESS   not-accessible
        STATUS       current
        DESCRIPTION  ""
        INDEX        { provEOWDscIfIndex }
        ::= { provEOWDscTable 1 }

    ProvEOWDscEntry ::= SEQUENCE {
        provEOWDscIfIndex    InterfaceIndex,
        provEOWDscNEAddress  IpAddress,
        provEOWDscUsage      UsedNotusedValue
    }

    provEOWDscIfIndex OBJECT-TYPE
        SYNTAX       InterfaceIndex
        MAX-ACCESS   not-accessible
        STATUS       current
        DESCRIPTION  "Index of this table."
        ::= { provEOWDscEntry 1 }

    provEOWDscNEAddress OBJECT-TYPE
        SYNTAX       IpAddress
        MAX-ACCESS   not-accessible
        STATUS       current
        DESCRIPTION  "reserved."
        ::= { provEOWDscEntry 2 }

    provEOWDscUsage OBJECT-TYPE
        SYNTAX       UsedNotusedValue
        MAX-ACCESS   read-write
        STATUS       current
        DESCRIPTION  "EOW DSC setting."
        ::= { provEOWDscEntry 3 }

    provSCAssignGroup OBJECT IDENTIFIER
        ::= { provisioningGroup 17 }

    provSCAssignSetGroup OBJECT IDENTIFIER
        ::= { provSCAssignGroup 1 }

    provSCAssignV11Table OBJECT-TYPE
        SYNTAX       SEQUENCE OF ProvSCAssignV11Entry
        MAX-ACCESS   not-accessible
        STATUS       current
        DESCRIPTION
            "This table contains V11 Interface Direction setting and
            assignment."
        ::= { provSCAssignSetGroup 1 }

    provSCAssignV11Entry OBJECT-TYPE
        SYNTAX       ProvSCAssignV11Entry
        MAX-ACCESS   not-accessible
        STATUS       current
        DESCRIPTION  ""
        INDEX        { provSCAssignV11Index }
        ::= { provSCAssignV11Table 1 }

    ProvSCAssignV11Entry ::= SEQUENCE {
        provSCAssignV11Index      INTEGER,
        provSCAssignV11NEAddress  IpAddress,
        v11Interface              INTEGER,
        v11Assign                 Integer32
    }

    provSCAssignV11Index OBJECT-TYPE
        SYNTAX       INTEGER { port1(1), port2(2) }
        MAX-ACCESS   not-accessible
        STATUS       current
        DESCRIPTION  "Index of this table."
        ::= { provSCAssignV11Entry 1 }

    provSCAssignV11NEAddress OBJECT-TYPE
        SYNTAX       IpAddress
        MAX-ACCESS   not-accessible
        STATUS       current
        DESCRIPTION  "reserved."
        ::= { provSCAssignV11Entry 2 }

    v11Interface OBJECT-TYPE
        SYNTAX       INTEGER { invalid(0), co(1), contra(2) }
        MAX-ACCESS   read-write
        STATUS       current
        DESCRIPTION  "V11 Interface Direction setting."
        ::= { provSCAssignV11Entry 3 }

    v11Assign OBJECT-TYPE
        SYNTAX       Integer32
        MAX-ACCESS   read-write
        STATUS       current
        DESCRIPTION  "V11 assignment."
        ::= { provSCAssignV11Entry 4 }

    provSCAssignRs232cTable OBJECT-TYPE
        SYNTAX       SEQUENCE OF ProvSCAssignRs232cEntry
        MAX-ACCESS   not-accessible
        STATUS       current
        DESCRIPTION  "This table contains RS232C Interface assignment."
        ::= { provSCAssignSetGroup 2 }

    provSCAssignRs232cEntry OBJECT-TYPE
        SYNTAX       ProvSCAssignRs232cEntry
        MAX-ACCESS   not-accessible
        STATUS       current
        DESCRIPTION  ""
        INDEX        { provSCAssignRs232cIndex }
        ::= { provSCAssignRs232cTable 1 }

    ProvSCAssignRs232cEntry ::= SEQUENCE {
        provSCAssignRs232cIndex      INTEGER,
        provSCAssignRs232cNEAddress  IpAddress,
        rs232cAssign                 Integer32
    }

    provSCAssignRs232cIndex OBJECT-TYPE
        SYNTAX       INTEGER { port1(1), port2(2) }
        MAX-ACCESS   not-accessible
        STATUS       current
        DESCRIPTION  "Index of this table."
        ::= { provSCAssignRs232cEntry 1 }

    provSCAssignRs232cNEAddress OBJECT-TYPE
        SYNTAX       IpAddress
        MAX-ACCESS   not-accessible
        STATUS       current
        DESCRIPTION  "reserved."
        ::= { provSCAssignRs232cEntry 2 }

    rs232cAssign OBJECT-TYPE
        SYNTAX       Integer32
        MAX-ACCESS   read-write
        STATUS       current
        DESCRIPTION  "RS232C assignment."
        ::= { provSCAssignRs232cEntry 3 }

    provScSohThroughSetTable OBJECT-TYPE
        SYNTAX       SEQUENCE OF ProvScSohThroughSetEntry
        MAX-ACCESS   not-accessible
        STATUS       current
        DESCRIPTION  "This table contains SOH Through setting."
        ::= { provSCAssignGroup 2 }

    provScSohThroughSetEntry OBJECT-TYPE
        SYNTAX       ProvScSohThroughSetEntry
        MAX-ACCESS   not-accessible
        STATUS       current
        DESCRIPTION  ""
        INDEX        { provScSohThroughSetIfIndex }
        ::= { provScSohThroughSetTable 1 }

    ProvScSohThroughSetEntry ::= SEQUENCE {
        provScSohThroughSetIfIndex    InterfaceIndex,
        provScSohThroughSetNEAddress  IpAddress,
        scSohThroughSetting           Integer32
    }

    provScSohThroughSetIfIndex OBJECT-TYPE
        SYNTAX       InterfaceIndex
        MAX-ACCESS   not-accessible
        STATUS       current
        DESCRIPTION  "Index of this table."
        ::= { provScSohThroughSetEntry 1 }

    provScSohThroughSetNEAddress OBJECT-TYPE
        SYNTAX       IpAddress
        MAX-ACCESS   not-accessible
        STATUS       current
        DESCRIPTION  "reserved."
        ::= { provScSohThroughSetEntry 2 }

    scSohThroughSetting OBJECT-TYPE
        SYNTAX       Integer32
        MAX-ACCESS   read-write
        STATUS       current
        DESCRIPTION  "SOH Through setting."
        ::= { provScSohThroughSetEntry 3 }

    provSCAssignNoteTable OBJECT-TYPE
        SYNTAX       SEQUENCE OF ProvSCAssignNoteEntry
        MAX-ACCESS   not-accessible
        STATUS       current
        DESCRIPTION  "This table contains V11 setting for log/trap."
        ::= { provSCAssignGroup 3 }

    provSCAssignNoteEntry OBJECT-TYPE
        SYNTAX       ProvSCAssignNoteEntry
        MAX-ACCESS   not-accessible
        STATUS       current
        DESCRIPTION  ""
        INDEX        { provSCAssignNoteIndex }
        ::= { provSCAssignNoteTable 1 }

    ProvSCAssignNoteEntry ::= SEQUENCE {
        provSCAssignNoteIndex         Integer32,
        provSCAssignNoteNEAddress     IpAddress,
        provSCAssignNoteV11Interface  DisplayString,
        provSCAssignNoteV11SCAssign   DisplayString
    }

    provSCAssignNoteIndex OBJECT-TYPE
        SYNTAX       Integer32 (1..1)
        MAX-ACCESS   not-accessible
        STATUS       current
        DESCRIPTION  "Index of this table."
        ::= { provSCAssignNoteEntry 1 }

    provSCAssignNoteNEAddress OBJECT-TYPE
        SYNTAX       IpAddress
        MAX-ACCESS   not-accessible
        STATUS       current
        DESCRIPTION  "reserved."
        ::= { provSCAssignNoteEntry 2 }

    provSCAssignNoteV11Interface OBJECT-TYPE
        SYNTAX       DisplayString (SIZE(0..32))
        MAX-ACCESS   read-write
        STATUS       current
        DESCRIPTION  "V11 Interface setting."
        ::= { provSCAssignNoteEntry 3 }

    provSCAssignNoteV11SCAssign OBJECT-TYPE
        SYNTAX       DisplayString (SIZE(0..32))
        MAX-ACCESS   read-write
        STATUS       current
        DESCRIPTION  "V11 assignment setting."
        ::= { provSCAssignNoteEntry 4 }

    provAmrOperationTable OBJECT-TYPE
        SYNTAX       SEQUENCE OF ProvAmrOperationEntry
        MAX-ACCESS   not-accessible
        STATUS       current
        DESCRIPTION  "This table contains AMR Operation control."
        ::= { provisioningGroup 18 }

    provAmrOperationEntry OBJECT-TYPE
        SYNTAX       ProvAmrOperationEntry
        MAX-ACCESS   not-accessible
        STATUS       current
        DESCRIPTION  ""
        INDEX        { provAmrOperationIfIndex }
        ::= { provAmrOperationTable 1 }

    ProvAmrOperationEntry ::= SEQUENCE {
        provAmrOperationIfIndex    InterfaceIndex,
        provAmrOperationNEAddress  IpAddress,
        cnThresholdOffset          Integer32,
        cnHysteresysOffset         Integer32,
        rslThresholdOffset         Integer32,
        rslHysteresysOffset        Integer32,
        atpcThresholdOffset        Integer32,
        decisionInterval           Integer32,
        holdProtction              Integer32,
        promoteProtection          Integer32,
        degradeProtection          Integer32
    }

    provAmrOperationIfIndex OBJECT-TYPE
        SYNTAX       InterfaceIndex
        MAX-ACCESS   not-accessible
        STATUS       current
        DESCRIPTION  "Index of this table."
        ::= { provAmrOperationEntry 1 }

    provAmrOperationNEAddress OBJECT-TYPE
        SYNTAX       IpAddress
        MAX-ACCESS   not-accessible
        STATUS       current
        DESCRIPTION  "reserved."
        ::= { provAmrOperationEntry 2 }

    cnThresholdOffset OBJECT-TYPE
        SYNTAX       Integer32 (-3..3)
        MAX-ACCESS   read-write
        STATUS       current
        DESCRIPTION  "CNR Threshold Offset"
        ::= { provAmrOperationEntry 3 }

    cnHysteresysOffset OBJECT-TYPE
        SYNTAX       Integer32 (0..9)
        MAX-ACCESS   read-write
        STATUS       current
        DESCRIPTION  "CNR Hysteresis Offset"
        ::= { provAmrOperationEntry 4 }

    rslThresholdOffset OBJECT-TYPE
        SYNTAX       Integer32 (-3..3)
        MAX-ACCESS   read-write
        STATUS       current
        DESCRIPTION  "RSL Threshold Offset"
        ::= { provAmrOperationEntry 5 }

    rslHysteresysOffset OBJECT-TYPE
        SYNTAX       Integer32 (0..9)
        MAX-ACCESS   read-write
        STATUS       current
        DESCRIPTION  "RSL Hysteresis Offset"
        ::= { provAmrOperationEntry 6 }

    atpcThresholdOffset OBJECT-TYPE
        SYNTAX       Integer32 (0..6)
        MAX-ACCESS   read-write
        STATUS       current
        DESCRIPTION  "ATPC Threshold Offset"
        ::= { provAmrOperationEntry 7 }

    decisionInterval OBJECT-TYPE
        SYNTAX       Integer32 (0..15)
        MAX-ACCESS   read-write
        STATUS       current
        DESCRIPTION  "AMR Decision Interval"
        ::= { provAmrOperationEntry 8 }

    holdProtction OBJECT-TYPE
        SYNTAX       Integer32 (1..256)
        MAX-ACCESS   read-write
        STATUS       current
        DESCRIPTION  "AMR Hold Protection"
        ::= { provAmrOperationEntry 9 }

    promoteProtection OBJECT-TYPE
        SYNTAX       Integer32 (1..65536)
        MAX-ACCESS   read-write
        STATUS       current
        DESCRIPTION  "AMR Promote Protection"
        ::= { provAmrOperationEntry 10 }

    degradeProtection OBJECT-TYPE
        SYNTAX       Integer32 (1..1024)
        MAX-ACCESS   read-write
        STATUS       current
        DESCRIPTION  "AMR Degrade Protection"
        ::= { provAmrOperationEntry 11 }

    provSoftkeyTable OBJECT-TYPE
        SYNTAX       SEQUENCE OF ProvSoftkeyEntry
        MAX-ACCESS   not-accessible
        STATUS       current
        DESCRIPTION  ""
        ::= { provisioningGroup 19 }

    provSoftkeyEntry OBJECT-TYPE
        SYNTAX       ProvSoftkeyEntry
        MAX-ACCESS   not-accessible
        STATUS       current
        DESCRIPTION  ""
        INDEX        { provSoftkeyIndex }
        ::= { provSoftkeyTable 1 }

    ProvSoftkeyEntry ::= SEQUENCE {
        provSoftkeyIndex      Integer32,
        provSoftkeyNEAddress  IpAddress,
        provRadioCapacity     INTEGER,
        provSfpUseAssign      INTEGER
    }

    provSoftkeyIndex OBJECT-TYPE
        SYNTAX       Integer32
        MAX-ACCESS   not-accessible
        STATUS       current
        DESCRIPTION  "Index of this table."
        ::= { provSoftkeyEntry 1 }

    provSoftkeyNEAddress OBJECT-TYPE
        SYNTAX       IpAddress
        MAX-ACCESS   not-accessible
        STATUS       current
        DESCRIPTION  "reserved."
        ::= { provSoftkeyEntry 2 }

    provRadioCapacity OBJECT-TYPE
        SYNTAX       INTEGER {
                         invalid(0),
                         notAssign(1),
                         slot1(2),
                         slot2(3),
                         slot3(4),
                         slot4(5),
                         slot5(6),
                         slot6(7),
                         slot7(8),
                         slot8(9),
                         slot9(10),
                         slot10(11),
                         slot11(12),
                         slot12(13),
                         slot13(14),
                         slot14(15)
                     }
        MAX-ACCESS   read-write
        STATUS       current
        DESCRIPTION  "Radio Capacity"
        ::= { provSoftkeyEntry 3 }

    provSfpUseAssign OBJECT-TYPE
        SYNTAX       INTEGER {
                         invalid(0),
                         notAssign(1),
                         slot1(2),
                         slot2(3),
                         slot3(4),
                         slot4(5),
                         slot5(6),
                         slot6(7),
                         slot7(8),
                         slot8(9),
                         slot9(10),
                         slot10(11),
                         slot11(12),
                         slot12(13),
                         slot13(14),
                         slot14(15)
                     }
        MAX-ACCESS   read-write
        STATUS       current
        DESCRIPTION  "SFP Port Usage"
        ::= { provSoftkeyEntry 4 }

    provVlanGroup OBJECT IDENTIFIER
        ::= { provisioningGroup 20 }

    provVlanEquipmentTable OBJECT-TYPE
        SYNTAX       SEQUENCE OF ProvVlanEquipmentEntry
        MAX-ACCESS   not-accessible
        STATUS       current
        DESCRIPTION  "VLAN EQUIPMENT TABLE"
        ::= { provVlanGroup 1 }

    provVlanEquipmentEntry OBJECT-TYPE
        SYNTAX       ProvVlanEquipmentEntry
        MAX-ACCESS   not-accessible
        STATUS       current
        DESCRIPTION  "VLAN EQUIPMENT ENTRY"
        INDEX        { provVlanEquipmentIndex }
        ::= { provVlanEquipmentTable 1 }

    ProvVlanEquipmentEntry ::= SEQUENCE {
        provVlanEquipmentIndex        Integer32,
        provVlanEquipmentNEAddress    IpAddress,
        provVlanEquipmentMode         INTEGER,
        provVlanEquipmentDefaultVid   Integer32,
        provVlanEquipmentDefaultTpid  OCTET STRING
    }

    provVlanEquipmentIndex OBJECT-TYPE
        SYNTAX       Integer32 (1..1)
        MAX-ACCESS   not-accessible
        STATUS       current
        DESCRIPTION  "Index of this table."
        ::= { provVlanEquipmentEntry 1 }

    provVlanEquipmentNEAddress OBJECT-TYPE
        SYNTAX       IpAddress
        MAX-ACCESS   not-accessible
        STATUS       current
        DESCRIPTION  "reserved."
        ::= { provVlanEquipmentEntry 2 }

    provVlanEquipmentMode OBJECT-TYPE
        SYNTAX       INTEGER { dot1q(1), dot1ad(2) }
        MAX-ACCESS   read-write
        STATUS       current
        DESCRIPTION
            "VLAN Mode
            1. 802.1q mode
            2. 802.1ad mode
            Note) It is possible to set in ADV/4, ADV/10(STD Read
            Only-support).
              (only 802.1q mode in STD)"
        ::= { provVlanEquipmentEntry 3 }

    provVlanEquipmentDefaultVid OBJECT-TYPE
        SYNTAX       Integer32 (1..4094)
        MAX-ACCESS   read-write
        STATUS       current
        DESCRIPTION
            "Default VLAN-ID
            value range : 1-4094
            default : 1
            FLAG=TRAP|EVLOG
            LOGITEM='%s'
            LOGSTATUS='%s'"
        ::= { provVlanEquipmentEntry 4 }

    provVlanEquipmentDefaultTpid OBJECT-TYPE
        SYNTAX       OCTET STRING (SIZE(2..2))
        MAX-ACCESS   read-write
        STATUS       current
        DESCRIPTION
            "TPID value which is used to identify the frame as an IEEE 802.1Q
            or 802.1ad tagged frame."
        ::= { provVlanEquipmentEntry 5 }

    provVlanCustomerTable OBJECT-TYPE
        SYNTAX       SEQUENCE OF ProvVlanCustomerEntry
        MAX-ACCESS   not-accessible
        STATUS       current
        DESCRIPTION  "CUSTOMER VLAN TABLE"
        ::= { provVlanGroup 2 }

    provVlanCustomerEntry OBJECT-TYPE
        SYNTAX       ProvVlanCustomerEntry
        MAX-ACCESS   not-accessible
        STATUS       current
        DESCRIPTION  "CUSTOMER VLAN PORT ENTRY"
        INDEX        { provVlanCustomerIfIndex, provVlanCustomerVlanIndex }
        ::= { provVlanCustomerTable 1 }

    ProvVlanCustomerEntry ::= SEQUENCE {
        provVlanCustomerIfIndex    InterfaceIndex,
        provVlanCustomerVlanIndex  Integer32,
        provVlanCustomerNEAddress  IpAddress,
        provVlanCustomerPort       INTEGER,
        provVlanCustomerRowstatus  RowStatus
    }

    provVlanCustomerIfIndex OBJECT-TYPE
        SYNTAX       InterfaceIndex
        MAX-ACCESS   not-accessible
        STATUS       current
        DESCRIPTION  "Index of this table."
        ::= { provVlanCustomerEntry 1 }

    provVlanCustomerVlanIndex OBJECT-TYPE
        SYNTAX       Integer32 (1..4094)
        MAX-ACCESS   not-accessible
        STATUS       current
        DESCRIPTION  "Index of this table."
        ::= { provVlanCustomerEntry 2 }

    provVlanCustomerNEAddress OBJECT-TYPE
        SYNTAX       IpAddress
        MAX-ACCESS   not-accessible
        STATUS       current
        DESCRIPTION  "reserved."
        ::= { provVlanCustomerEntry 3 }

    provVlanCustomerPort OBJECT-TYPE
        SYNTAX       INTEGER { access(1), tunnel(2), trunk(3) }
        MAX-ACCESS   read-create
        STATUS       current
        DESCRIPTION
            "VLAN TYPE
            1. Access(default)
            2. Tunnel
            3. Trunk

            FLAG=TRAP|EVLOG"
        ::= { provVlanCustomerEntry 4 }

    provVlanCustomerRowstatus OBJECT-TYPE
        SYNTAX       RowStatus { active(1), createAndGo(4), destroy(6) }
        MAX-ACCESS   read-create
        STATUS       current
        DESCRIPTION
            "Rowstatus
            1. active
            4. createAndGo
            6. destroy
            FLAG=TRAP|EVLOG"
        ::= { provVlanCustomerEntry 5 }

    provVlanServiceTable OBJECT-TYPE
        SYNTAX       SEQUENCE OF ProvVlanServiceEntry
        MAX-ACCESS   not-accessible
        STATUS       current
        DESCRIPTION  ""
        ::= { provVlanGroup 3 }

    provVlanServiceEntry OBJECT-TYPE
        SYNTAX       ProvVlanServiceEntry
        MAX-ACCESS   not-accessible
        STATUS       current
        DESCRIPTION  ""
        INDEX        { provVlanServiceIfIndex, provVlanServiceVlanIndex }
        ::= { provVlanServiceTable 1 }

    ProvVlanServiceEntry ::= SEQUENCE {
        provVlanServiceIfIndex    InterfaceIndex,
        provVlanServiceVlanIndex  Integer32,
        provVlanServiceNEAddress  IpAddress,
        provVlanServicePortType   INTEGER,
        provVlanServiceRowStatus  RowStatus
    }

    provVlanServiceIfIndex OBJECT-TYPE
        SYNTAX       InterfaceIndex
        MAX-ACCESS   not-accessible
        STATUS       current
        DESCRIPTION  "Index of this table."
        ::= { provVlanServiceEntry 1 }

    provVlanServiceVlanIndex OBJECT-TYPE
        SYNTAX       Integer32 (1..4094)
        MAX-ACCESS   not-accessible
        STATUS       current
        DESCRIPTION  "Index of this table."
        ::= { provVlanServiceEntry 2 }

    provVlanServiceNEAddress OBJECT-TYPE
        SYNTAX       IpAddress
        MAX-ACCESS   not-accessible
        STATUS       current
        DESCRIPTION  "reserved."
        ::= { provVlanServiceEntry 3 }

    provVlanServicePortType OBJECT-TYPE
        SYNTAX       INTEGER { invalid(0), cAccess(1), sTrunk(2) }
        MAX-ACCESS   read-create
        STATUS       current
        DESCRIPTION  "VLAN Port Type(VLAN ID)"
        ::= { provVlanServiceEntry 4 }

    provVlanServiceRowStatus OBJECT-TYPE
        SYNTAX       RowStatus
        MAX-ACCESS   read-create
        STATUS       current
        DESCRIPTION  "RowStatus of this table."
        ::= { provVlanServiceEntry 5 }

    provVlanCBridgeTable OBJECT-TYPE
        SYNTAX       SEQUENCE OF ProvVlanCBridgeEntry
        MAX-ACCESS   not-accessible
        STATUS       current
        DESCRIPTION  ""
        ::= { provVlanGroup 4 }

    provVlanCBridgeEntry OBJECT-TYPE
        SYNTAX       ProvVlanCBridgeEntry
        MAX-ACCESS   not-accessible
        STATUS       current
        DESCRIPTION  ""
        INDEX        {
                         provVlanCBridgeIfIndex,
                         provVlanCBridgeSVlanIndex,
                         provVlanCBridgeCVlanIndex
                     }
        ::= { provVlanCBridgeTable 1 }

    ProvVlanCBridgeEntry ::= SEQUENCE {
        provVlanCBridgeIfIndex     InterfaceIndex,
        provVlanCBridgeSVlanIndex  Integer32,
        provVlanCBridgeCVlanIndex  Integer32,
        provVlanCBridgeNEAddress   IpAddress,
        provVlanCBridgePortType    INTEGER,
        provVlanCBridgeRowStatus   RowStatus
    }

    provVlanCBridgeIfIndex OBJECT-TYPE
        SYNTAX       InterfaceIndex
        MAX-ACCESS   not-accessible
        STATUS       current
        DESCRIPTION  "Index of this table."
        ::= { provVlanCBridgeEntry 1 }

    provVlanCBridgeSVlanIndex OBJECT-TYPE
        SYNTAX       Integer32 (1..4094)
        MAX-ACCESS   not-accessible
        STATUS       current
        DESCRIPTION  "Index of this table."
        ::= { provVlanCBridgeEntry 2 }

    provVlanCBridgeCVlanIndex OBJECT-TYPE
        SYNTAX       Integer32 (1..4094)
        MAX-ACCESS   not-accessible
        STATUS       current
        DESCRIPTION  "Index of this table."
        ::= { provVlanCBridgeEntry 3 }

    provVlanCBridgeNEAddress OBJECT-TYPE
        SYNTAX       IpAddress
        MAX-ACCESS   not-accessible
        STATUS       current
        DESCRIPTION  "reserved."
        ::= { provVlanCBridgeEntry 4 }

    provVlanCBridgePortType OBJECT-TYPE
        SYNTAX       INTEGER { invalid(0), cBridge(1) }
        MAX-ACCESS   read-create
        STATUS       current
        DESCRIPTION  "VLAN Port Type(C-VLAN ID)"
        ::= { provVlanCBridgeEntry 5 }

    provVlanCBridgeRowStatus OBJECT-TYPE
        SYNTAX       RowStatus
        MAX-ACCESS   read-create
        STATUS       current
        DESCRIPTION  "RowStatus of this table."
        ::= { provVlanCBridgeEntry 6 }

    provVlanNameTable OBJECT-TYPE
        SYNTAX       SEQUENCE OF ProvVlanNameEntry
        MAX-ACCESS   not-accessible
        STATUS       current
        DESCRIPTION  "VLAN NAME TABLE"
        ::= { provVlanGroup 5 }

    provVlanNameEntry OBJECT-TYPE
        SYNTAX       ProvVlanNameEntry
        MAX-ACCESS   not-accessible
        STATUS       current
        DESCRIPTION  "VLAN NAME ENTRY"
        INDEX        { provVlanNameVlanIndex }
        ::= { provVlanNameTable 1 }

    ProvVlanNameEntry ::= SEQUENCE {
        provVlanNameVlanIndex  Integer32,
        provVlanNameNEAddress  IpAddress,
        provVlanName           DisplayString,
        provVlanNameRowstatus  RowStatus
    }

    provVlanNameVlanIndex OBJECT-TYPE
        SYNTAX       Integer32 (1..4094)
        MAX-ACCESS   not-accessible
        STATUS       current
        DESCRIPTION  "Index of this table."
        ::= { provVlanNameEntry 1 }

    provVlanNameNEAddress OBJECT-TYPE
        SYNTAX       IpAddress
        MAX-ACCESS   not-accessible
        STATUS       current
        DESCRIPTION  "reserved."
        ::= { provVlanNameEntry 2 }

    provVlanName OBJECT-TYPE
        SYNTAX       DisplayString (SIZE(0..32))
        MAX-ACCESS   read-create
        STATUS       current
        DESCRIPTION  "VLAN Service Name"
        ::= { provVlanNameEntry 3 }

    provVlanNameRowstatus OBJECT-TYPE
        SYNTAX       RowStatus { active(1), createAndGo(4), destroy(6) }
        MAX-ACCESS   read-create
        STATUS       current
        DESCRIPTION  "RowStatus of this table."
        ::= { provVlanNameEntry 4 }

    provVlanCounterTable OBJECT-TYPE
        SYNTAX       SEQUENCE OF ProvVlanCounterEntry
        MAX-ACCESS   not-accessible
        STATUS       current
        DESCRIPTION  "VLAN COUNTER TABLE"
        ::= { provVlanGroup 7 }

    provVlanCounterEntry OBJECT-TYPE
        SYNTAX       ProvVlanCounterEntry
        MAX-ACCESS   not-accessible
        STATUS       current
        DESCRIPTION  "VLAN COUNTER ENTRY"
        INDEX        { provVlanCounterIndex }
        ::= { provVlanCounterTable 1 }

    ProvVlanCounterEntry ::= SEQUENCE {
        provVlanCounterIndex      Integer32,
        provVlanCounterNEAddress  IpAddress,
        provVlanCounterEntryPort  InterfaceIndex,
        provVlanCounterEntryVid   Integer32,
        provVlanCounterRowstatus  RowStatus
    }

    provVlanCounterIndex OBJECT-TYPE
        SYNTAX       Integer32 (1..256)
        MAX-ACCESS   not-accessible
        STATUS       current
        DESCRIPTION  "Index of this table."
        ::= { provVlanCounterEntry 1 }

    provVlanCounterNEAddress OBJECT-TYPE
        SYNTAX       IpAddress
        MAX-ACCESS   not-accessible
        STATUS       current
        DESCRIPTION  "reserved."
        ::= { provVlanCounterEntry 2 }

    provVlanCounterEntryPort OBJECT-TYPE
        SYNTAX       InterfaceIndex
        MAX-ACCESS   read-create
        STATUS       current
        DESCRIPTION  "Port Number"
        ::= { provVlanCounterEntry 3 }

    provVlanCounterEntryVid OBJECT-TYPE
        SYNTAX       Integer32 (1..4094)
        MAX-ACCESS   read-create
        STATUS       current
        DESCRIPTION
            "VLAN ID which becomes a counter target
            value range : 1-4094
            Note) it is possible to set it When the specified VLAN ID exists
            in specified port.
            FLAG=TRAP|EVLOG"
        ::= { provVlanCounterEntry 4 }

    provVlanCounterRowstatus OBJECT-TYPE
        SYNTAX       RowStatus { active(1), createAndGo(4), destroy(6) }
        MAX-ACCESS   read-create
        STATUS       current
        DESCRIPTION
            "Rowstatus
            1. active
            4. createAndGo
            6. destroy
            FLAG=TRAP|EVLOG"
        ::= { provVlanCounterEntry 5 }

    provDot1qPortVlanTable OBJECT-TYPE
        SYNTAX       SEQUENCE OF ProvDot1qPortVlanEntry
        MAX-ACCESS   not-accessible
        STATUS       current
        DESCRIPTION
            "Port base VLAN Information Table for 802.1q mode.
            This table provides summarized assigned VLAN information for the
            specified port. MAX-ACCESS of the object inside of this table is
            writable. But provisioning function (VLAN assign function through
            this table) is future support. These objects act as read-only
            object currently."
        ::= { provVlanGroup 10 }

    provDot1qPortVlanEntry OBJECT-TYPE
        SYNTAX       ProvDot1qPortVlanEntry
        MAX-ACCESS   not-accessible
        STATUS       current
        DESCRIPTION  ""
        INDEX        { provDot1qPortVlanIfIndex }
        ::= { provDot1qPortVlanTable 1 }

    ProvDot1qPortVlanEntry ::= SEQUENCE {
        provDot1qPortVlanIfIndex    InterfaceIndex,
        provDot1qPortVlanNEAddress  IpAddress,
        provDot1qPortVlanPortType   INTEGER,
        provDot1qPortVlanList       IpeVlanListOrZero,
        provDot1qPortAccessVid      IpeVlanIndexOrZero
    }

    provDot1qPortVlanIfIndex OBJECT-TYPE
        SYNTAX       InterfaceIndex
        MAX-ACCESS   not-accessible
        STATUS       current
        DESCRIPTION  "Index of this table."
        ::= { provDot1qPortVlanEntry 1 }

    provDot1qPortVlanNEAddress OBJECT-TYPE
        SYNTAX       IpAddress
        MAX-ACCESS   not-accessible
        STATUS       current
        DESCRIPTION  "reserved."
        ::= { provDot1qPortVlanEntry 2 }

    provDot1qPortVlanPortType OBJECT-TYPE
        SYNTAX       INTEGER {
                         invalid(0),
                         tunnel(1),
                         trunk(2),
                         trunkWithAccess(3),
                         accessOnly(4)
                     }
        MAX-ACCESS   read-write
        STATUS       current
        DESCRIPTION
            "VLAN Port Type.
            When the port is configured as 'tunnel' port, the object returns
            value as 'tunnel'. If trunk VLANs are assigned to the port, the
            object returns value as 'trunk'. Trunk VLANs and Access VLANs are
            assigned to the port, the value becomes 'trunkWithAccess'. If the
            port has only access vlan, the value becomes 'accessOnly'."
        ::= { provDot1qPortVlanEntry 3 }

    provDot1qPortVlanList OBJECT-TYPE
        SYNTAX       IpeVlanListOrZero
        MAX-ACCESS   read-write
        STATUS       current
        DESCRIPTION
            "VLAN List.
            When the 'provDot1qPortVlanPortType' is 'tunnel' port, the object
            shows tunnel VLANs assigned to the port. The other port type, the
            object shows trunk VLANs assigned to the port."
        ::= { provDot1qPortVlanEntry 4 }

    provDot1qPortAccessVid OBJECT-TYPE
        SYNTAX       IpeVlanIndexOrZero
        MAX-ACCESS   read-write
        STATUS       current
        DESCRIPTION
            "Access VLAN ID.
            When the 'provDot1qPortVlanPortType' is 'trunkWithAccess' or
            'accessOnly', the object returns access VLAN ID. Otherwise the
            object returns '0'."
        ::= { provDot1qPortVlanEntry 5 }

    provDot1adPortVlanTable OBJECT-TYPE
        SYNTAX       SEQUENCE OF ProvDot1adPortVlanEntry
        MAX-ACCESS   not-accessible
        STATUS       current
        DESCRIPTION
            "Port base VLAN Information Table for 802.1ad mode.
            This table provides summarized assigned VLAN information for the
            specified port. MAX-ACCESS of the object inside of this table is
            writable. But provisioning function (VLAN assign function through
            this table) is future support. These objects act as read-only
            object currently."
        ::= { provVlanGroup 11 }

    provDot1adPortVlanEntry OBJECT-TYPE
        SYNTAX       ProvDot1adPortVlanEntry
        MAX-ACCESS   not-accessible
        STATUS       current
        DESCRIPTION  ""
        INDEX        { provDot1adPortVlanIfIndex }
        ::= { provDot1adPortVlanTable 1 }

    ProvDot1adPortVlanEntry ::= SEQUENCE {
        provDot1adPortVlanIfIndex    InterfaceIndex,
        provDot1adPortVlanNEAddress  IpAddress,
        provDot1adPortVlanPortType   INTEGER,
        provDot1adPortVlanList       IpeVlanListOrZero,
        provDot1adPortCAccessVid     IpeVlanIndexOrZero
    }

    provDot1adPortVlanIfIndex OBJECT-TYPE
        SYNTAX       InterfaceIndex
        MAX-ACCESS   not-accessible
        STATUS       current
        DESCRIPTION  "Index of this table."
        ::= { provDot1adPortVlanEntry 1 }

    provDot1adPortVlanNEAddress OBJECT-TYPE
        SYNTAX       IpAddress
        MAX-ACCESS   not-accessible
        STATUS       current
        DESCRIPTION  "reserved."
        ::= { provDot1adPortVlanEntry 2 }

    provDot1adPortVlanPortType OBJECT-TYPE
        SYNTAX       INTEGER {
                         invalid(0),
                         bridge(1),
                         trunk(2),
                         trunkWithAccess(3),
                         accessOnly(4)
                     }
        MAX-ACCESS   read-write
        STATUS       current
        DESCRIPTION
            "VLAN Port Type.
            When the port is configured as C-Bridge port, the object returns
            'bridge'. If s-trunk VLANs are assigned to the port, the object
            returns value as 'trunk'. S-Trunk VLANs and C-Access VLANs are
            assigned to the port, the value becomes 'trunkWithAccess'. If the
            port has only C-Access vlan, the value becomes 'accessOnly'."
        ::= { provDot1adPortVlanEntry 3 }

    provDot1adPortVlanList OBJECT-TYPE
        SYNTAX       IpeVlanListOrZero
        MAX-ACCESS   read-write
        STATUS       current
        DESCRIPTION
            "VLAN List.
            When the 'provDot1adPortVlanPortType' is 'bridge' port, the
            object returns empty value (length 0 string). The other port
            type, the object shows S-trunk VLANs assigned to the port."
        ::= { provDot1adPortVlanEntry 4 }

    provDot1adPortCAccessVid OBJECT-TYPE
        SYNTAX       IpeVlanIndexOrZero
        MAX-ACCESS   read-write
        STATUS       current
        DESCRIPTION
            "C-Access VLAN ID.
            When the 'provDot1adPortVlanPortType' is 'trunkWithAccess' or
            'accessOnly', the object returns access VLAN ID. Otherwise the
            object returns '0'."
        ::= { provDot1adPortVlanEntry 5 }

    provQosGroup OBJECT IDENTIFIER
        ::= { provisioningGroup 21 }

    provQosEquipmentTable OBJECT-TYPE
        SYNTAX       SEQUENCE OF ProvQosEquipmentEntry
        MAX-ACCESS   not-accessible
        STATUS       current
        DESCRIPTION  "QoS Equipment Table"
        ::= { provQosGroup 1 }

    provQosEquipmentEntry OBJECT-TYPE
        SYNTAX       ProvQosEquipmentEntry
        MAX-ACCESS   not-accessible
        STATUS       current
        DESCRIPTION  "QoS Equipment Entry"
        INDEX        { provQosEquipmentIndex }
        ::= { provQosEquipmentTable 1 }

    ProvQosEquipmentEntry ::= SEQUENCE {
        provQosEquipmentIndex               Integer32,
        provQosEquipmentNEAddress           IpAddress,
        provQosEquipmentClassifyProfile     Integer32,
        provQosEquipmentClassMode           INTEGER,
        provQosEquipmentClassificationMode  INTEGER
    }

    provQosEquipmentIndex OBJECT-TYPE
        SYNTAX       Integer32 (1..1)
        MAX-ACCESS   not-accessible
        STATUS       current
        DESCRIPTION  "Index of this table."
        ::= { provQosEquipmentEntry 1 }

    provQosEquipmentNEAddress OBJECT-TYPE
        SYNTAX       IpAddress
        MAX-ACCESS   not-accessible
        STATUS       current
        DESCRIPTION  "reserved."
        ::= { provQosEquipmentEntry 2 }

    provQosEquipmentClassifyProfile OBJECT-TYPE
        SYNTAX       Integer32 (0..3)
        MAX-ACCESS   read-write
        STATUS       current
        DESCRIPTION
            "Classify Profile Index
            value range : 0 - 3"
        ::= { provQosEquipmentEntry 3 }

    provQosEquipmentClassMode OBJECT-TYPE
        SYNTAX       INTEGER { invalid(0), qos4class(1), qos8class(2) }
        MAX-ACCESS   read-write
        STATUS       current
        DESCRIPTION
            "Configure the Equipment QoS Class mode.
            When the object is changed, provQosEgressPortSchedMode is
            initialized depends on the QoS Class mode.
            provQosEgressPortSchedMode is changed to sp4, when the qos
            mode is set to qos4class, and provQosEgressPortSchedMode is
            changed to sp1dwrr7, when the qos mode is set to qos8class."
        ::= { provQosEquipmentEntry 4 }

    provQosEquipmentClassificationMode OBJECT-TYPE
        SYNTAX       INTEGER {
                         invalid(0),
                         qosequipmode(1),
                         qosportmode(2),
                         qosequipvlanmode(3)
                     }
        MAX-ACCESS   read-write
        STATUS       current
        DESCRIPTION  "Classification Mode"
        ::= { provQosEquipmentEntry 5 }

    provQosClassifyTable OBJECT-TYPE
        SYNTAX       SEQUENCE OF ProvQosClassifyEntry
        MAX-ACCESS   not-accessible
        STATUS       current
        DESCRIPTION
            "Qos Classify Table. This table defines classifier for the input
            frames. The frames whose 'provQosClassifyField' is
            'provQosClassifyPriority' are mapped to Internal Priority
            'provQosClassifyPriority'."
        ::= { provQosGroup 2 }

    provQosClassifyEntry OBJECT-TYPE
        SYNTAX       ProvQosClassifyEntry
        MAX-ACCESS   not-accessible
        STATUS       current
        DESCRIPTION  ""
        INDEX        { provQosClassifyProfileIndex, provQosClassifyEntryIndex }
        ::= { provQosClassifyTable 1 }

    ProvQosClassifyEntry ::= SEQUENCE {
        provQosClassifyProfileIndex      Integer32,
        provQosClassifyEntryIndex        Integer32,
        provQosClassifyNEAddress         IpAddress,
        provQosClassifyField             INTEGER,
        provQosClassifyPriority          Integer32,
        provQosClassifyInternalPriority  Integer32,
        provQosClassifyRowstatus         RowStatus
    }

    provQosClassifyProfileIndex OBJECT-TYPE
        SYNTAX       Integer32 (1..3)
        MAX-ACCESS   not-accessible
        STATUS       current
        DESCRIPTION  "Index of this table."
        ::= { provQosClassifyEntry 1 }

    provQosClassifyEntryIndex OBJECT-TYPE
        SYNTAX       Integer32 (1..64)
        MAX-ACCESS   not-accessible
        STATUS       current
        DESCRIPTION  "Index of this table."
        ::= { provQosClassifyEntry 2 }

    provQosClassifyNEAddress OBJECT-TYPE
        SYNTAX       IpAddress
        MAX-ACCESS   not-accessible
        STATUS       current
        DESCRIPTION  "reserved."
        ::= { provQosClassifyEntry 3 }

    provQosClassifyField OBJECT-TYPE
        SYNTAX       INTEGER {
                         unuse(-1),
                         vlanCos(1),
                         ipv4Precedence(2),
                         ipv4Dscp(3),
                         ipv6Dscp(4),
                         mplsExp(5),
                         other(10)
                     }
        MAX-ACCESS   read-create
        STATUS       current
        DESCRIPTION
            "QoS Classify Field. This object specifies classify field such as
            CoS value, DSCP value. If the value of this object is 'other',
            the entry acts as default entry. i.e. the 'other' entry matches
            all frames which are not matched to the other entries. And
            'other' entry cannot be created by the manager, 'other' entry is
            created as 64th entry by the agent."
        ::= { provQosClassifyEntry 4 }

    provQosClassifyPriority OBJECT-TYPE
        SYNTAX       Integer32 (-1..63)
        MAX-ACCESS   read-create
        STATUS       current
        DESCRIPTION  "QoS Classify Priority (value)."
        ::= { provQosClassifyEntry 5 }

    provQosClassifyInternalPriority OBJECT-TYPE
        SYNTAX       Integer32 (-1..7)
        MAX-ACCESS   read-create
        STATUS       current
        DESCRIPTION
            "QoS Classify Internal Priority. The frames which are matched to
            the entry are mapped to the internal prioiry specified by this
            object."
        ::= { provQosClassifyEntry 6 }

    provQosClassifyRowstatus OBJECT-TYPE
        SYNTAX       RowStatus { active(1), createAndGo(4), destroy(6) }
        MAX-ACCESS   read-create
        STATUS       current
        DESCRIPTION
            "RowStatus of this table. The entry whose
            'provQosClassifyEntryIndex' is 64 is created automatically by the
            agent, and cannot be created and deleted by manager."
        ::= { provQosClassifyEntry 7 }

    provQosIngressPolicingProfileTable OBJECT-TYPE
        SYNTAX       SEQUENCE OF ProvQosIngressPolicingProfileEntry
        MAX-ACCESS   not-accessible
        STATUS       current
        DESCRIPTION  "QoS Ingress Policer Profile Table"
        ::= { provQosGroup 3 }

    provQosIngressPolicingProfileEntry OBJECT-TYPE
        SYNTAX       ProvQosIngressPolicingProfileEntry
        MAX-ACCESS   not-accessible
        STATUS       current
        DESCRIPTION  "QoS Ingress Policer Profile Entry"
        INDEX        { provQosIngressPolicingProfileProfileIndex }
        ::= { provQosIngressPolicingProfileTable 1 }

    ProvQosIngressPolicingProfileEntry ::= SEQUENCE {
        provQosIngressPolicingProfileProfileIndex  Integer32,
        provQosIngressPolicingProfileNEAddress     IpAddress,
        provQosIngressPolicingProfileEir           Integer32,
        provQosIngressPolicingProfileCir           Integer32,
        provQosIngressPolicingProfileEbs           Integer32,
        provQosIngressPolicingProfileCbs           Integer32
    }

    provQosIngressPolicingProfileProfileIndex OBJECT-TYPE
        SYNTAX       Integer32 (1..64)
        MAX-ACCESS   not-accessible
        STATUS       current
        DESCRIPTION  "Index of this table."
        ::= { provQosIngressPolicingProfileEntry 1 }

    provQosIngressPolicingProfileNEAddress OBJECT-TYPE
        SYNTAX       IpAddress
        MAX-ACCESS   not-accessible
        STATUS       current
        DESCRIPTION  "reserved."
        ::= { provQosIngressPolicingProfileEntry 2 }

    provQosIngressPolicingProfileEir OBJECT-TYPE
        SYNTAX       Integer32 (0..10000000)
        MAX-ACCESS   read-write
        STATUS       current
        DESCRIPTION
            "range : 0 - 1000000 (iPASOLINK200/400/1000series/EX/iX)"
        ::= { provQosIngressPolicingProfileEntry 3 }

    provQosIngressPolicingProfileCir OBJECT-TYPE
        SYNTAX       Integer32 (0..10000000)
        MAX-ACCESS   read-write
        STATUS       current
        DESCRIPTION
            "range : 0 - 1000000 (iPASOLINK200/400/1000series/EX/iX)"
        ::= { provQosIngressPolicingProfileEntry 4 }

    provQosIngressPolicingProfileEbs OBJECT-TYPE
        SYNTAX       Integer32 (0..128)
        MAX-ACCESS   read-write
        STATUS       current
        DESCRIPTION
            "EBS
            value range : 0Kbyte - 128KByte
            Default : 0KBy"
        ::= { provQosIngressPolicingProfileEntry 5 }

    provQosIngressPolicingProfileCbs OBJECT-TYPE
        SYNTAX       Integer32 (1..64)
        MAX-ACCESS   read-write
        STATUS       current
        DESCRIPTION
            "CBS
            value range : 1Kbyte - 64KByte
            Default : 24Kbyte"
        ::= { provQosIngressPolicingProfileEntry 6 }

    provQosIngressPolicingTable OBJECT-TYPE
        SYNTAX       SEQUENCE OF ProvQosIngressPolicingEntry
        MAX-ACCESS   not-accessible
        STATUS       current
        DESCRIPTION  "QoS Ingress Policer Table"
        ::= { provQosGroup 4 }

    provQosIngressPolicingEntry OBJECT-TYPE
        SYNTAX       ProvQosIngressPolicingEntry
        MAX-ACCESS   not-accessible
        STATUS       current
        DESCRIPTION  "QoS Ingress Policer Entry"
        INDEX        { provQosIngressPolicingEntryIndex }
        ::= { provQosIngressPolicingTable 1 }

    ProvQosIngressPolicingEntry ::= SEQUENCE {
        provQosIngressPolicingEntryIndex           Integer32,
        provQosIngressPolicingEntryNEAddress       IpAddress,
        provQosIngressPolicingEntryPortNumber      Integer32,
        provQosIngressPolicingEntryVlanNumber      Integer32,
        provQosIngressPolicingEntryPriorityNumber  Integer32,
        provQosIngressPolicingEntryProfileNumber   Integer32,
        provQosIngressPolicingEntryMplsLabel       Integer32,
        provQosIngressPolicingEntryReserve2        Integer32,
        provQosIngressPolicingEntryReserve3        Integer32,
        provQosIngressPolicingEntryRowstatus       RowStatus
    }

    provQosIngressPolicingEntryIndex OBJECT-TYPE
        SYNTAX       Integer32 (1..256)
        MAX-ACCESS   not-accessible
        STATUS       current
        DESCRIPTION  "Index of this table."
        ::= { provQosIngressPolicingEntry 1 }

    provQosIngressPolicingEntryNEAddress OBJECT-TYPE
        SYNTAX       IpAddress
        MAX-ACCESS   not-accessible
        STATUS       current
        DESCRIPTION  "reserved."
        ::= { provQosIngressPolicingEntry 2 }

    provQosIngressPolicingEntryPortNumber OBJECT-TYPE
        SYNTAX       Integer32 (-1..2147483647)
        MAX-ACCESS   read-create
        STATUS       current
        DESCRIPTION
            "Port Number
            value range : 0 - 0x7FFFFFFF, unuse(-1)
            FLAG=TRAP|EVLOG"
        ::= { provQosIngressPolicingEntry 3 }

    provQosIngressPolicingEntryVlanNumber OBJECT-TYPE
        SYNTAX       Integer32 (-1..-1|1..4094)
        MAX-ACCESS   read-create
        STATUS       current
        DESCRIPTION
            "VLAN Number
            value range : 1 - 4094, unuse(-1)
            FLAG=TRAP|EVLOG"
        ::= { provQosIngressPolicingEntry 4 }

    provQosIngressPolicingEntryPriorityNumber OBJECT-TYPE
        SYNTAX       Integer32 (-1..7)
        MAX-ACCESS   read-create
        STATUS       current
        DESCRIPTION
            "Internal Priority
            value range : 0 - 7, unuse(-1)
            FLAG=TRAP|EVLOG"
        ::= { provQosIngressPolicingEntry 5 }

    provQosIngressPolicingEntryProfileNumber OBJECT-TYPE
        SYNTAX       Integer32 (-1..-1|1..64)
        MAX-ACCESS   read-create
        STATUS       current
        DESCRIPTION
            "Policer Profile Number
            value range : 1 - 16    (iPASOLINK200/400/1000series/EX/iX)
                          1 - 64    (iPASOLINK VR series)
                          unuse(-1)
            FLAG=TRAP|EVLOG"
        ::= { provQosIngressPolicingEntry 6 }

    provQosIngressPolicingEntryMplsLabel OBJECT-TYPE
        SYNTAX       Integer32 (-1..1048575)
        MAX-ACCESS   read-create
        STATUS       current
        DESCRIPTION  "QoS Ingress Policing Entry MPLS Label"
        ::= { provQosIngressPolicingEntry 7 }

    provQosIngressPolicingEntryReserve2 OBJECT-TYPE
        SYNTAX       Integer32
        MAX-ACCESS   read-create
        STATUS       current
        DESCRIPTION  "reserved."
        ::= { provQosIngressPolicingEntry 8 }

    provQosIngressPolicingEntryReserve3 OBJECT-TYPE
        SYNTAX       Integer32
        MAX-ACCESS   read-create
        STATUS       current
        DESCRIPTION  "reserved."
        ::= { provQosIngressPolicingEntry 9 }

    provQosIngressPolicingEntryRowstatus OBJECT-TYPE
        SYNTAX       RowStatus { active(1), createAndGo(4), destroy(6) }
        MAX-ACCESS   read-create
        STATUS       current
        DESCRIPTION  "RowStatus of this table."
        ::= { provQosIngressPolicingEntry 10 }

    provQosEgressPortTable OBJECT-TYPE
        SYNTAX       SEQUENCE OF ProvQosEgressPortEntry
        MAX-ACCESS   not-accessible
        STATUS       current
        DESCRIPTION  "QoS Egress Port Table"
        ::= { provQosGroup 5 }

    provQosEgressPortEntry OBJECT-TYPE
        SYNTAX       ProvQosEgressPortEntry
        MAX-ACCESS   not-accessible
        STATUS       current
        DESCRIPTION  "QoS Egress Port Entry"
        INDEX        { provQosEgressPortIfIndex }
        ::= { provQosEgressPortTable 1 }

    ProvQosEgressPortEntry ::= SEQUENCE {
        provQosEgressPortIfIndex                 InterfaceIndex,
        provQosEgressPortNEAddress               IpAddress,
        provQosEgressPortSchedMode               INTEGER,
        provQosEgressPortDropMode                INTEGER,
        provQosEgressPortInternalPriority0Class  Integer32,
        provQosEgressPortInternalPriority1Class  Integer32,
        provQosEgressPortInternalPriority2Class  Integer32,
        provQosEgressPortInternalPriority3Class  Integer32,
        provQosEgressPortInternalPriority4Class  Integer32,
        provQosEgressPortInternalPriority5Class  Integer32,
        provQosEgressPortInternalPriority6Class  Integer32,
        provQosEgressPortInternalPriority7Class  Integer32,
        provQosEgressPortPortShaperRate          Integer32
    }

    provQosEgressPortIfIndex OBJECT-TYPE
        SYNTAX       InterfaceIndex
        MAX-ACCESS   not-accessible
        STATUS       current
        DESCRIPTION  "Index of this table."
        ::= { provQosEgressPortEntry 1 }

    provQosEgressPortNEAddress OBJECT-TYPE
        SYNTAX       IpAddress
        MAX-ACCESS   not-accessible
        STATUS       current
        DESCRIPTION  "FLAG=TRAP|EVLOG"
        ::= { provQosEgressPortEntry 2 }

    provQosEgressPortSchedMode OBJECT-TYPE
        SYNTAX       INTEGER {
                         sp2(1),
                         sp4(2),
                         sp1-dwrr3(3),
                         dwrr4(4),
                         sp1dwrr7(5),
                         sp2dwrr6(6),
                         sp8(7)
                     }
        MAX-ACCESS   read-write
        STATUS       current
        DESCRIPTION
            "Scheduling Mode

            Changing provQosEgressPortSchedMode, provQosEgressPort-
            InternalPriority0Class to provQosEgressPortInternal-
            Priority7Class will change.
            FLAG=TRAP|EVLOG"
        ::= { provQosEgressPortEntry 3 }

    provQosEgressPortDropMode OBJECT-TYPE
        SYNTAX       INTEGER { wtd(1), wred(2) }
        MAX-ACCESS   read-write
        STATUS       current
        DESCRIPTION
            "Egress Drop Mode
            1. WTD(Weighted Tail Drop)
            2. WRED
            FLAG=TRAP|EVLOG"
        ::= { provQosEgressPortEntry 4 }

    provQosEgressPortInternalPriority0Class OBJECT-TYPE
        SYNTAX       Integer32 (0..7)
        MAX-ACCESS   read-write
        STATUS       current
        DESCRIPTION
            "Class of internal priority 0
            value range : 0 - 7 (STD : 0 - 3)(2xSP : 0 - 1 / other : 0 - 3)
            FLAG=TRAP|EVLOG"
        ::= { provQosEgressPortEntry 5 }

    provQosEgressPortInternalPriority1Class OBJECT-TYPE
        SYNTAX       Integer32 (0..7)
        MAX-ACCESS   read-write
        STATUS       current
        DESCRIPTION
            "Class of internal priority 1
            value range : 0 - 7 (STD : 0 - 3)(2xSP : 0 - 1 / other : 0 - 3)
            FLAG=TRAP|EVLOG"
        ::= { provQosEgressPortEntry 6 }

    provQosEgressPortInternalPriority2Class OBJECT-TYPE
        SYNTAX       Integer32 (0..7)
        MAX-ACCESS   read-write
        STATUS       current
        DESCRIPTION
            "Class of internal priority 2
            value range : 0 - 7 (STD : 0 - 3)(2xSP : 0 - 1 / other : 0 - 3)
            FLAG=TRAP|EVLOG"
        ::= { provQosEgressPortEntry 7 }

    provQosEgressPortInternalPriority3Class OBJECT-TYPE
        SYNTAX       Integer32 (0..7)
        MAX-ACCESS   read-write
        STATUS       current
        DESCRIPTION
            "Class of internal priority 3
            value range : 0 - 7 (STD : 0 - 3)(2xSP : 0 - 1 / other : 0 - 3)
            FLAG=TRAP|EVLOG"
        ::= { provQosEgressPortEntry 8 }

    provQosEgressPortInternalPriority4Class OBJECT-TYPE
        SYNTAX       Integer32 (0..7)
        MAX-ACCESS   read-write
        STATUS       current
        DESCRIPTION
            "Class of internal priority 4
            value range : 0 - 7 (STD : 0 - 3)(2xSP : 0 - 1 / other : 0 - 3)
            FLAG=TRAP|EVLOG"
        ::= { provQosEgressPortEntry 9 }

    provQosEgressPortInternalPriority5Class OBJECT-TYPE
        SYNTAX       Integer32 (0..7)
        MAX-ACCESS   read-write
        STATUS       current
        DESCRIPTION
            "Class of internal priority 5
            value range : 0 - 7 (STD : 0 - 3)(2xSP : 0 - 1 / other : 0 - 3)
            FLAG=TRAP|EVLOG"
        ::= { provQosEgressPortEntry 10 }

    provQosEgressPortInternalPriority6Class OBJECT-TYPE
        SYNTAX       Integer32 (0..7)
        MAX-ACCESS   read-write
        STATUS       current
        DESCRIPTION
            "Class of internal priority 6
            value range : 0 - 7 (STD : 0 - 3)(2xSP : 0 - 1 / other : 0 - 3)
            FLAG=TRAP|EVLOG"
        ::= { provQosEgressPortEntry 11 }

    provQosEgressPortInternalPriority7Class OBJECT-TYPE
        SYNTAX       Integer32 (0..7)
        MAX-ACCESS   read-write
        STATUS       current
        DESCRIPTION
            "Class of internal priority 7
            value range : 0 - 7 (STD : 0 - 3)(2xSP : 0 - 1 / other : 0 - 3)
            FLAG=TRAP|EVLOG"
        ::= { provQosEgressPortEntry 12 }

    provQosEgressPortPortShaperRate OBJECT-TYPE
        SYNTAX       Integer32 (0..10000000)
        MAX-ACCESS   read-write
        STATUS       current
        DESCRIPTION
            "This object configures Port base shaper rate. The acceptable
            range depends on physical bandwidth."
        ::= { provQosEgressPortEntry 13 }

    provQosEgressTable OBJECT-TYPE
        SYNTAX       SEQUENCE OF ProvQosEgressEntry
        MAX-ACCESS   not-accessible
        STATUS       current
        DESCRIPTION  "QoS Egress Class Table"
        ::= { provQosGroup 6 }

    provQosEgressEntry OBJECT-TYPE
        SYNTAX       ProvQosEgressEntry
        MAX-ACCESS   not-accessible
        STATUS       current
        DESCRIPTION  "QoS Egress Class Entry"
        INDEX        { provQosEgressIfIndex, provQosEgressClassIndex }
        ::= { provQosEgressTable 1 }

    ProvQosEgressEntry ::= SEQUENCE {
        provQosEgressIfIndex                   InterfaceIndex,
        provQosEgressClassIndex                Integer32,
        provQosEgressClassNEAddress            IpAddress,
        provQosEgressClassShaperRate           Integer32,
        provQosEgressClassMinimumRate          Integer32,
        provQosEgressClassDWRRWeight           Integer32,
        provQosEgressQueueLength               Integer32,
        provQosEgressWtdYellowFrameThreshold   Integer32,
        provQosEgressWredYellowFrameThreshold  Integer32,
        provQosEgressWredGreenFrameThreshold   Integer32
    }

    provQosEgressIfIndex OBJECT-TYPE
        SYNTAX       InterfaceIndex
        MAX-ACCESS   not-accessible
        STATUS       current
        DESCRIPTION  "Index of this table."
        ::= { provQosEgressEntry 1 }

    provQosEgressClassIndex OBJECT-TYPE
        SYNTAX       Integer32 (1..8)
        MAX-ACCESS   not-accessible
        STATUS       current
        DESCRIPTION  "Index of this table."
        ::= { provQosEgressEntry 2 }

    provQosEgressClassNEAddress OBJECT-TYPE
        SYNTAX       IpAddress
        MAX-ACCESS   not-accessible
        STATUS       current
        DESCRIPTION  "reserved."
        ::= { provQosEgressEntry 3 }

    provQosEgressClassShaperRate OBJECT-TYPE
        SYNTAX       Integer32 (0..10000000)
        MAX-ACCESS   read-write
        STATUS       current
        DESCRIPTION
            "This object configures the Class based shaper rate. The
            acceptable range depends on the physical port type."
        ::= { provQosEgressEntry 4 }

    provQosEgressClassMinimumRate OBJECT-TYPE
        SYNTAX       Integer32 (0..1000000)
        MAX-ACCESS   not-accessible
        STATUS       current
        DESCRIPTION  "This object configures the Class based minimum rate."
        ::= { provQosEgressEntry 5 }

    provQosEgressClassDWRRWeight OBJECT-TYPE
        SYNTAX       Integer32 (1..127)
        MAX-ACCESS   read-write
        STATUS       current
        DESCRIPTION
            "Class Shaper Weight
            value range : 1 - 127
            Default : 1
            FLAG=TRAP|EVLOG"
        ::= { provQosEgressEntry 6 }

    provQosEgressQueueLength OBJECT-TYPE
        SYNTAX       Integer32 (16..1024)
        MAX-ACCESS   read-write
        STATUS       current
        DESCRIPTION  "Queue Length per Class."
        ::= { provQosEgressEntry 7 }

    provQosEgressWtdYellowFrameThreshold OBJECT-TYPE
        SYNTAX       Integer32 (10..100)
        MAX-ACCESS   read-write
        STATUS       current
        DESCRIPTION
            "WTD Yellow Frame Threshold
            value range : 10% - 100%
            Default : 70%
            FLAG=TRAP|EVLOG"
        ::= { provQosEgressEntry 8 }

    provQosEgressWredYellowFrameThreshold OBJECT-TYPE
        SYNTAX       Integer32 (10..100)
        MAX-ACCESS   read-write
        STATUS       current
        DESCRIPTION
            "WRED Yellow Frame Threshold
            value range : 10% - 100%
            Default : 70%
            FLAG=TRAP|EVLOG"
        ::= { provQosEgressEntry 9 }

    provQosEgressWredGreenFrameThreshold OBJECT-TYPE
        SYNTAX       Integer32 (10..100)
        MAX-ACCESS   read-write
        STATUS       current
        DESCRIPTION
            "WRED Green Frame Threshold
            value range : 10% - 100%
            Default : 70%
            FLAG=TRAP|EVLOG"
        ::= { provQosEgressEntry 10 }

    provQosFloodControlEquipmentTable OBJECT-TYPE
        SYNTAX       SEQUENCE OF ProvQosFloodControlEquipmentEntry
        MAX-ACCESS   not-accessible
        STATUS       current
        DESCRIPTION  ""
        ::= { provQosGroup 7 }

    provQosFloodControlEquipmentEntry OBJECT-TYPE
        SYNTAX       ProvQosFloodControlEquipmentEntry
        MAX-ACCESS   not-accessible
        STATUS       current
        DESCRIPTION  ""
        INDEX        { provQosFloodControlEquipmentIndex }
        ::= { provQosFloodControlEquipmentTable 1 }

    ProvQosFloodControlEquipmentEntry ::= SEQUENCE {
        provQosFloodControlEquipmentIndex      Integer32,
        provQosFloodControlEquipmentNEAddress  IpAddress,
        provQosFloodControlEquipmentFrameType  INTEGER,
        provQosFloodControlEquipmentRate       Integer32
    }

    provQosFloodControlEquipmentIndex OBJECT-TYPE
        SYNTAX       Integer32 (1..1)
        MAX-ACCESS   not-accessible
        STATUS       current
        DESCRIPTION  "Index of this table."
        ::= { provQosFloodControlEquipmentEntry 1 }

    provQosFloodControlEquipmentNEAddress OBJECT-TYPE
        SYNTAX       IpAddress
        MAX-ACCESS   not-accessible
        STATUS       current
        DESCRIPTION  "reserved."
        ::= { provQosFloodControlEquipmentEntry 2 }

    provQosFloodControlEquipmentFrameType OBJECT-TYPE
        SYNTAX       INTEGER { unknownUnicast(1), multicast(2), broadcast(3) }
        MAX-ACCESS   read-only
        STATUS       obsolete
        DESCRIPTION
            "Frame Type
            Values: unknownUnicast(1), multicast(2), broadcast(3)"
        ::= { provQosFloodControlEquipmentEntry 3 }

    provQosFloodControlEquipmentRate OBJECT-TYPE
        SYNTAX       Integer32 (1000..1000000)
        UNITS        "kbps"
        MAX-ACCESS   read-write
        STATUS       current
        DESCRIPTION
            "Class Shaper Rate
            value range : 1Mbps - 1000Mbps"
        DEFVAL       { 1000000 }
        ::= { provQosFloodControlEquipmentEntry 4 }

    provQosFloodControlTable OBJECT-TYPE
        SYNTAX       SEQUENCE OF ProvQosFloodControlEntry
        MAX-ACCESS   not-accessible
        STATUS       current
        DESCRIPTION  ""
        ::= { provQosGroup 8 }

    provQosFloodControlEntry OBJECT-TYPE
        SYNTAX       ProvQosFloodControlEntry
        MAX-ACCESS   not-accessible
        STATUS       current
        DESCRIPTION  ""
        INDEX        { provQosFloodControlIfIndex }
        ::= { provQosFloodControlTable 1 }

    ProvQosFloodControlEntry ::= SEQUENCE {
        provQosFloodControlIfIndex    InterfaceIndex,
        provQosFloodControlNEAddress  IpAddress,
        provQosFloodControlFrameType  INTEGER,
        provQosFloodControlEnabled    EnableDisableValue
    }

    provQosFloodControlIfIndex OBJECT-TYPE
        SYNTAX       InterfaceIndex
        MAX-ACCESS   not-accessible
        STATUS       current
        DESCRIPTION  "Index of this table."
        ::= { provQosFloodControlEntry 1 }

    provQosFloodControlNEAddress OBJECT-TYPE
        SYNTAX       IpAddress
        MAX-ACCESS   not-accessible
        STATUS       current
        DESCRIPTION  "reserved."
        ::= { provQosFloodControlEntry 2 }

    provQosFloodControlFrameType OBJECT-TYPE
        SYNTAX       INTEGER { unknownUnicast(1), multicast(2), broadcast(3) }
        MAX-ACCESS   read-only
        STATUS       obsolete
        DESCRIPTION
            "Frame Type
            Values: unknownUnicast(1), multicast(2), broadcast(3)"
        ::= { provQosFloodControlEntry 3 }

    provQosFloodControlEnabled OBJECT-TYPE
        SYNTAX       EnableDisableValue
        MAX-ACCESS   read-write
        STATUS       current
        DESCRIPTION
            "Flood Control Enable/Disable
            Values: invalid(0), disable(1), enable(2)"
        DEFVAL       { disable }
        ::= { provQosFloodControlEntry 4 }

    provQosPortClassifyTable OBJECT-TYPE
        SYNTAX       SEQUENCE OF ProvQosPortClassifyEntry
        MAX-ACCESS   not-accessible
        STATUS       current
        DESCRIPTION
            "This table contains the classify mode for port base QoS."
        ::= { provQosGroup 9 }

    provQosPortClassifyEntry OBJECT-TYPE
        SYNTAX       ProvQosPortClassifyEntry
        MAX-ACCESS   not-accessible
        STATUS       current
        DESCRIPTION  ""
        INDEX        { provQosPortClassifyIfIndex }
        ::= { provQosPortClassifyTable 1 }

    ProvQosPortClassifyEntry ::= SEQUENCE {
        provQosPortClassifyIfIndex    InterfaceIndex,
        provQosPortClassifyNEAddress  IpAddress,
        provQosPortClassifyField      INTEGER,
        provQosPortClassifyPriority   Integer32
    }

    provQosPortClassifyIfIndex OBJECT-TYPE
        SYNTAX       InterfaceIndex
        MAX-ACCESS   not-accessible
        STATUS       current
        DESCRIPTION  "Index of this table."
        ::= { provQosPortClassifyEntry 1 }

    provQosPortClassifyNEAddress OBJECT-TYPE
        SYNTAX       IpAddress
        MAX-ACCESS   not-accessible
        STATUS       current
        DESCRIPTION  "reserved."
        ::= { provQosPortClassifyEntry 2 }

    provQosPortClassifyField OBJECT-TYPE
        SYNTAX       INTEGER {
                         unuse(-1),
                         port(1),
                         ctagCos(2),
                         stagCos(3),
                         v4v6Dscp(4),
                         v4Precedence(5)
                     }
        MAX-ACCESS   read-write
        STATUS       current
        DESCRIPTION
            "This object configures the port base QoS mode.
            when the object is configured as 'port' mode, the system
            classifies all frames which are received on the port as
            'provQosPortClassifyPriority'.
            On 'ctagCos' mode, the system classifies received frames based on
            the CoS value of C-tag. 'stagCos' mode is similar to 'ctagCos',
            but this mode is not available on dot1q mode.
            On 'v4v6Dscp' mode, the system classifies frames based on the
            DSCP value. On the 'mplsExp' mode, the system classifies MPLS
            frames based on MPLS Exp value."
        ::= { provQosPortClassifyEntry 3 }

    provQosPortClassifyPriority OBJECT-TYPE
        SYNTAX       Integer32 (0..7)
        MAX-ACCESS   read-write
        STATUS       current
        DESCRIPTION
            "Internal Priority for port base Qos. When the classifying schema
            is not applicable to received frames, the frames are classified
            as 'provQosPortClassifyPriority'."
        ::= { provQosPortClassifyEntry 4 }

    provQosPortClassifyDscpTable OBJECT-TYPE
        SYNTAX       SEQUENCE OF ProvQosPortClassifyDscpEntry
        MAX-ACCESS   not-accessible
        STATUS       current
        DESCRIPTION
            "This table contains the mapping of DSCP value to internal
            Priority. This configuration is applicable only when the system
            is running on the port base QoS mode."
        ::= { provQosGroup 10 }

    provQosPortClassifyDscpEntry OBJECT-TYPE
        SYNTAX       ProvQosPortClassifyDscpEntry
        MAX-ACCESS   not-accessible
        STATUS       current
        DESCRIPTION  ""
        INDEX        {
                         provQosPortClassifyDscpProfileIndex,
                         provQosPortClassifyDscpEntryIndex
                     }
        ::= { provQosPortClassifyDscpTable 1 }

    ProvQosPortClassifyDscpEntry ::= SEQUENCE {
        provQosPortClassifyDscpProfileIndex      Integer32,
        provQosPortClassifyDscpEntryIndex        Integer32,
        provQosPortClassifyDscpNEAddress         IpAddress,
        provQosPortClassifyDscpPriority          Integer32,
        provQosPortClassifyDscpInternalPriority  Integer32
    }

    provQosPortClassifyDscpProfileIndex OBJECT-TYPE
        SYNTAX       Integer32
        MAX-ACCESS   not-accessible
        STATUS       current
        DESCRIPTION  "Index of this table."
        ::= { provQosPortClassifyDscpEntry 1 }

    provQosPortClassifyDscpEntryIndex OBJECT-TYPE
        SYNTAX       Integer32 (1..64)
        MAX-ACCESS   not-accessible
        STATUS       current
        DESCRIPTION  "Index of this table."
        ::= { provQosPortClassifyDscpEntry 2 }

    provQosPortClassifyDscpNEAddress OBJECT-TYPE
        SYNTAX       IpAddress
        MAX-ACCESS   not-accessible
        STATUS       current
        DESCRIPTION  "reserved."
        ::= { provQosPortClassifyDscpEntry 3 }

    provQosPortClassifyDscpPriority OBJECT-TYPE
        SYNTAX       Integer32 (0..63)
        MAX-ACCESS   read-write
        STATUS       current
        DESCRIPTION
            "This object specifies the DSCP value for DCSP to internal
            priority mapping. And this object acts as read-only object, this
            means the system cannot accept the change request to this
            object."
        ::= { provQosPortClassifyDscpEntry 4 }

    provQosPortClassifyDscpInternalPriority OBJECT-TYPE
        SYNTAX       Integer32 (0..7)
        MAX-ACCESS   read-write
        STATUS       current
        DESCRIPTION
            "Internal Priority value which is assigned to frames whose DSCP
            value is 'provQosPortClassifyPortDscpPriority'."
        ::= { provQosPortClassifyDscpEntry 5 }

    provQosVlanClassifyDefaultTable OBJECT-TYPE
        SYNTAX       SEQUENCE OF ProvQosVlanClassifyDefaultEntry
        MAX-ACCESS   not-accessible
        STATUS       current
        DESCRIPTION
            "This table contains the Default internal priority for VLAN base
            QoS mode."
        ::= { provQosGroup 11 }

    provQosVlanClassifyDefaultEntry OBJECT-TYPE
        SYNTAX       ProvQosVlanClassifyDefaultEntry
        MAX-ACCESS   not-accessible
        STATUS       current
        DESCRIPTION  ""
        INDEX        { provQosVlanClassifyDefaultIndex }
        ::= { provQosVlanClassifyDefaultTable 1 }

    ProvQosVlanClassifyDefaultEntry ::= SEQUENCE {
        provQosVlanClassifyDefaultIndex      Integer32,
        provQosVlanClassifyDefaultNEAddress  IpAddress,
        provQosVlanClassifyDefaultPriority   Integer32
    }

    provQosVlanClassifyDefaultIndex OBJECT-TYPE
        SYNTAX       Integer32 (1..1)
        MAX-ACCESS   not-accessible
        STATUS       current
        DESCRIPTION  "Index of this table."
        ::= { provQosVlanClassifyDefaultEntry 1 }

    provQosVlanClassifyDefaultNEAddress OBJECT-TYPE
        SYNTAX       IpAddress
        MAX-ACCESS   not-accessible
        STATUS       current
        DESCRIPTION  "reserved."
        ::= { provQosVlanClassifyDefaultEntry 2 }

    provQosVlanClassifyDefaultPriority OBJECT-TYPE
        SYNTAX       Integer32 (0..7)
        MAX-ACCESS   read-write
        STATUS       current
        DESCRIPTION
            "Internal priority which is assigned to the untag frames.
            Note) tagged frames whose VLAN ID is not configured in
            'provVlanClassifyTable' are assigned based on its Cos value."
        DEFVAL       { 0 }
        ::= { provQosVlanClassifyDefaultEntry 3 }

    provQosVlanClassifyTable OBJECT-TYPE
        SYNTAX       SEQUENCE OF ProvQosVlanClassifyEntry
        MAX-ACCESS   not-accessible
        STATUS       current
        DESCRIPTION
            "This table contains the mapping of VLAN ID to Internal priority.
            This configuration is applicable only when the system is running
            on VLAN base QoS mode."
        ::= { provQosGroup 12 }

    provQosVlanClassifyEntry OBJECT-TYPE
        SYNTAX       ProvQosVlanClassifyEntry
        MAX-ACCESS   not-accessible
        STATUS       current
        DESCRIPTION  ""
        INDEX        {
                         provQosVlanClassifyProfileIndex,
                         provQosVlanClassifyEntryIndex
                     }
        ::= { provQosVlanClassifyTable 1 }

    ProvQosVlanClassifyEntry ::= SEQUENCE {
        provQosVlanClassifyProfileIndex      Integer32,
        provQosVlanClassifyEntryIndex        Integer32,
        provQosVlanClassifyNEAddress         IpAddress,
        provQosVlanClassifyVlanIndex         IpeVlanIndex,
        provQosVlanClassifyInternalPriority  Integer32,
        provQosVlanClassifyRowStatus         RowStatus
    }

    provQosVlanClassifyProfileIndex OBJECT-TYPE
        SYNTAX       Integer32 (1..1)
        MAX-ACCESS   not-accessible
        STATUS       current
        DESCRIPTION  "Index of this table."
        ::= { provQosVlanClassifyEntry 1 }

    provQosVlanClassifyEntryIndex OBJECT-TYPE
        SYNTAX       Integer32 (1..128)
        MAX-ACCESS   not-accessible
        STATUS       current
        DESCRIPTION  "Index of this table."
        ::= { provQosVlanClassifyEntry 2 }

    provQosVlanClassifyNEAddress OBJECT-TYPE
        SYNTAX       IpAddress
        MAX-ACCESS   not-accessible
        STATUS       current
        DESCRIPTION  "reserved."
        ::= { provQosVlanClassifyEntry 3 }

    provQosVlanClassifyVlanIndex OBJECT-TYPE
        SYNTAX       IpeVlanIndex
        MAX-ACCESS   read-create
        STATUS       current
        DESCRIPTION
            "this object configures the VLAN ID for VLAN ID to internal
            priority mapping."
        ::= { provQosVlanClassifyEntry 4 }

    provQosVlanClassifyInternalPriority OBJECT-TYPE
        SYNTAX       Integer32 (0..7)
        MAX-ACCESS   read-create
        STATUS       current
        DESCRIPTION
            "Internal priority which is assigned to the frames whose VLAN ID
            is 'provQosVlanClassifyEntryIndex'."
        ::= { provQosVlanClassifyEntry 5 }

    provQosVlanClassifyRowStatus OBJECT-TYPE
        SYNTAX       RowStatus
        MAX-ACCESS   read-create
        STATUS       current
        DESCRIPTION
            "This object is used for create a new row or delete an existing
            row."
        ::= { provQosVlanClassifyEntry 6 }

    provRstpGroup OBJECT IDENTIFIER
        ::= { provisioningGroup 23 }

    provRstpExtBridgeTable OBJECT-TYPE
        SYNTAX       SEQUENCE OF ProvRstpExtBridgeEntry
        MAX-ACCESS   not-accessible
        STATUS       current
        DESCRIPTION  ""
        ::= { provRstpGroup 1 }

    provRstpExtBridgeEntry OBJECT-TYPE
        SYNTAX       ProvRstpExtBridgeEntry
        MAX-ACCESS   not-accessible
        STATUS       current
        DESCRIPTION  ""
        INDEX        { provRstpExtBridgeIndex }
        ::= { provRstpExtBridgeTable 1 }

    ProvRstpExtBridgeEntry ::= SEQUENCE {
        provRstpExtBridgeIndex            Integer32,
        provRstpExtBridgeNEAddress        IpAddress,
        provRstpExtBridgeEnable           EnableDisableValue,
        provRstpExtBridgeRstpMstpVersion  INTEGER,
        provRstpExtBridgeMaxAge           Integer32,
        provRstpExtBridgeHelloTime        Integer32,
        provRstpExtBridgeForwardDelay     Integer32,
        provRstpExtBridgePriority         Integer32,
        provRstpExtBridgeTxHoldCount      Integer32
    }

    provRstpExtBridgeIndex OBJECT-TYPE
        SYNTAX       Integer32 (1..1)
        MAX-ACCESS   not-accessible
        STATUS       current
        DESCRIPTION  "Index of this table."
        ::= { provRstpExtBridgeEntry 1 }

    provRstpExtBridgeNEAddress OBJECT-TYPE
        SYNTAX       IpAddress
        MAX-ACCESS   not-accessible
        STATUS       current
        DESCRIPTION  "reserved."
        ::= { provRstpExtBridgeEntry 2 }

    provRstpExtBridgeEnable OBJECT-TYPE
        SYNTAX       EnableDisableValue
        MAX-ACCESS   read-write
        STATUS       current
        DESCRIPTION  "RSTP enable/disable"
        ::= { provRstpExtBridgeEntry 3 }

    provRstpExtBridgeRstpMstpVersion OBJECT-TYPE
        SYNTAX       INTEGER { rstp(1), mstp(2) }
        MAX-ACCESS   read-write
        STATUS       current
        DESCRIPTION  "STP Mode"
        ::= { provRstpExtBridgeEntry 4 }

    provRstpExtBridgeMaxAge OBJECT-TYPE
        SYNTAX       Integer32 (6..40)
        MAX-ACCESS   read-write
        STATUS       current
        DESCRIPTION  "Max Age Timer"
        ::= { provRstpExtBridgeEntry 5 }

    provRstpExtBridgeHelloTime OBJECT-TYPE
        SYNTAX       Integer32 (1..2)
        MAX-ACCESS   read-write
        STATUS       current
        DESCRIPTION  "Hello Timer"
        ::= { provRstpExtBridgeEntry 6 }

    provRstpExtBridgeForwardDelay OBJECT-TYPE
        SYNTAX       Integer32 (4..30)
        MAX-ACCESS   read-write
        STATUS       current
        DESCRIPTION  "Forwarding Delay Timer"
        ::= { provRstpExtBridgeEntry 7 }

    provRstpExtBridgePriority OBJECT-TYPE
        SYNTAX       Integer32 (0..61440)
        MAX-ACCESS   read-write
        STATUS       current
        DESCRIPTION  "Bridgw Priority"
        ::= { provRstpExtBridgeEntry 8 }

    provRstpExtBridgeTxHoldCount OBJECT-TYPE
        SYNTAX       Integer32 (1..10)
        MAX-ACCESS   read-write
        STATUS       current
        DESCRIPTION  "STP TX Hold Count (RSTP)"
        ::= { provRstpExtBridgeEntry 9 }

    provRstpExtPortTable OBJECT-TYPE
        SYNTAX       SEQUENCE OF ProvRstpExtPortEntry
        MAX-ACCESS   not-accessible
        STATUS       current
        DESCRIPTION  ""
        ::= { provRstpGroup 2 }

    provRstpExtPortEntry OBJECT-TYPE
        SYNTAX       ProvRstpExtPortEntry
        MAX-ACCESS   not-accessible
        STATUS       current
        DESCRIPTION  ""
        INDEX        { provRstpExtPortifIndex }
        ::= { provRstpExtPortTable 1 }

    ProvRstpExtPortEntry ::= SEQUENCE {
        provRstpExtPortifIndex            InterfaceIndex,
        provRstpExtPortNEAddress          IpAddress,
        provRstpExtPortPriority           Integer32,
        provRstpExtPortEnable             EnableDisableValue,
        provRstpExtPortAdminEdgePort      EnableDisableValue,
        provRstpExtPortAdminPointToPoint  INTEGER,
        provRstpExtPortAdminPathCost      Integer32
    }

    provRstpExtPortifIndex OBJECT-TYPE
        SYNTAX       InterfaceIndex
        MAX-ACCESS   not-accessible
        STATUS       current
        DESCRIPTION  "Index of this table."
        ::= { provRstpExtPortEntry 1 }

    provRstpExtPortNEAddress OBJECT-TYPE
        SYNTAX       IpAddress
        MAX-ACCESS   not-accessible
        STATUS       current
        DESCRIPTION  "reserved."
        ::= { provRstpExtPortEntry 2 }

    provRstpExtPortPriority OBJECT-TYPE
        SYNTAX       Integer32 (0..240)
        MAX-ACCESS   read-write
        STATUS       current
        DESCRIPTION  "STP Port Priority (RSTP)"
        ::= { provRstpExtPortEntry 3 }

    provRstpExtPortEnable OBJECT-TYPE
        SYNTAX       EnableDisableValue
        MAX-ACCESS   read-write
        STATUS       current
        DESCRIPTION  "RSTP Enable"
        ::= { provRstpExtPortEntry 4 }

    provRstpExtPortAdminEdgePort OBJECT-TYPE
        SYNTAX       EnableDisableValue
        MAX-ACCESS   read-write
        STATUS       current
        DESCRIPTION  "Edge Port (RSTP)"
        ::= { provRstpExtPortEntry 5 }

    provRstpExtPortAdminPointToPoint OBJECT-TYPE
        SYNTAX       INTEGER { forceTrue(0), forceFalse(1), auto(2) }
        MAX-ACCESS   read-write
        STATUS       current
        DESCRIPTION  "PtoP Port (RSTP)"
        ::= { provRstpExtPortEntry 6 }

    provRstpExtPortAdminPathCost OBJECT-TYPE
        SYNTAX       Integer32 (0..200000000)
        MAX-ACCESS   read-write
        STATUS       current
        DESCRIPTION  "STP Port Path Cost (RSTP)"
        ::= { provRstpExtPortEntry 7 }

    provEthOamGroup OBJECT IDENTIFIER
        ::= { provisioningGroup 24 }

    provEthOamMegTable OBJECT-TYPE
        SYNTAX       SEQUENCE OF ProvEthOamMegEntry
        MAX-ACCESS   not-accessible
        STATUS       current
        DESCRIPTION  "Meg Setting Table"
        ::= { provEthOamGroup 1 }

    provEthOamMegEntry OBJECT-TYPE
        SYNTAX       ProvEthOamMegEntry
        MAX-ACCESS   not-accessible
        STATUS       current
        DESCRIPTION  ""
        INDEX        { provEthOamMegIndex }
        ::= { provEthOamMegTable 1 }

    ProvEthOamMegEntry ::= SEQUENCE {
        provEthOamMegIndex        IpeMepId,
        provEthOamMegNEAddress    IpAddress,
        provEthOamMegID           OCTET STRING,
        provEthOamMegLevel        INTEGER,
        provEthOamMegPeriod       INTEGER,
        provEthOamMegRowStatus    RowStatus,
        provEthOamMegShortID      OCTET STRING,
        provEthOamMegCcmEnabled   EnableDisableValue,
        provEthOamMegCcmPriority  Integer32
    }

    provEthOamMegIndex OBJECT-TYPE
        SYNTAX       IpeMepId
        MAX-ACCESS   not-accessible
        STATUS       current
        DESCRIPTION  "Index of this table."
        ::= { provEthOamMegEntry 1 }

    provEthOamMegNEAddress OBJECT-TYPE
        SYNTAX       IpAddress
        MAX-ACCESS   not-accessible
        STATUS       current
        DESCRIPTION  "IP Address"
        ::= { provEthOamMegEntry 2 }

    provEthOamMegID OBJECT-TYPE
        SYNTAX       OCTET STRING (SIZE(0..43))
        MAX-ACCESS   read-create
        STATUS       current
        DESCRIPTION  "Meg ID(0-43 Octet String)"
        ::= { provEthOamMegEntry 3 }

    provEthOamMegLevel OBJECT-TYPE
        SYNTAX       INTEGER {
                         level0(0),
                         level1(1),
                         level2(2),
                         level3(3),
                         level4(4),
                         level5(5),
                         level6(6),
                         level7(7)
                     }
        MAX-ACCESS   read-create
        STATUS       current
        DESCRIPTION  "Meg Level(0-7)"
        ::= { provEthOamMegEntry 4 }

    provEthOamMegPeriod OBJECT-TYPE
        SYNTAX       INTEGER {
                         invalid(0),
                         period-3ms(1),
                         period-10ms(2),
                         period-100ms(3),
                         period-1s(4),
                         period-10s(5),
                         period-1min(6)
                     }
        MAX-ACCESS   read-create
        STATUS       current
        DESCRIPTION  "CCM Frame Transmit Period(1-6)"
        ::= { provEthOamMegEntry 5 }

    provEthOamMegRowStatus OBJECT-TYPE
        SYNTAX       RowStatus {
                         active(1),
                         notInService(2),
                         notReady(3),
                         createAndGo(4),
                         createAndWait(5),
                         destroy(6)
                     }
        MAX-ACCESS   read-create
        STATUS       current
        DESCRIPTION  "Entry Status"
        ::= { provEthOamMegEntry 6 }

    provEthOamMegShortID OBJECT-TYPE
        SYNTAX       OCTET STRING (SIZE(0..43))
        MAX-ACCESS   read-create
        STATUS       current
        DESCRIPTION  "Short Meg ID(0-43 Octet String)"
        ::= { provEthOamMegEntry 7 }

    provEthOamMegCcmEnabled OBJECT-TYPE
        SYNTAX       EnableDisableValue
        MAX-ACCESS   read-create
        STATUS       current
        DESCRIPTION  "CCM Transmit/Receive Setting"
        ::= { provEthOamMegEntry 8 }

    provEthOamMegCcmPriority OBJECT-TYPE
        SYNTAX       Integer32 (0..7)
        MAX-ACCESS   read-create
        STATUS       current
        DESCRIPTION  "CCM Frame Priority"
        ::= { provEthOamMegEntry 9 }

    provEthOamMipTable OBJECT-TYPE
        SYNTAX       SEQUENCE OF ProvEthOamMipEntry
        MAX-ACCESS   not-accessible
        STATUS       current
        DESCRIPTION  "Mip Setting Table"
        ::= { provEthOamGroup 2 }

    provEthOamMipEntry OBJECT-TYPE
        SYNTAX       ProvEthOamMipEntry
        MAX-ACCESS   not-accessible
        STATUS       current
        DESCRIPTION  ""
        INDEX        {
                         provEthOamMipIndex,
                         provEthOamMipIfIndex,
                         provEthOamMipVld,
                         provEthOamMipMegLevel
                     }
        ::= { provEthOamMipTable 1 }

    ProvEthOamMipEntry ::= SEQUENCE {
        provEthOamMipIndex      Integer32,
        provEthOamMipIfIndex    InterfaceIndex,
        provEthOamMipVld        Integer32,
        provEthOamMipMegLevel   INTEGER,
        provEthOamMipNEAddress  IpAddress,
        provEthOamMipRowStatus  RowStatus
    }

    provEthOamMipIndex OBJECT-TYPE
        SYNTAX       Integer32 (1..32)
        MAX-ACCESS   not-accessible
        STATUS       current
        DESCRIPTION  "Index of this table."
        ::= { provEthOamMipEntry 1 }

    provEthOamMipIfIndex OBJECT-TYPE
        SYNTAX       InterfaceIndex
        MAX-ACCESS   not-accessible
        STATUS       current
        DESCRIPTION  "Index of this table."
        ::= { provEthOamMipEntry 2 }

    provEthOamMipVld OBJECT-TYPE
        SYNTAX       Integer32 (0..4094)
        MAX-ACCESS   not-accessible
        STATUS       current
        DESCRIPTION  "Vlan Id(1-4094, Untag=0)"
        ::= { provEthOamMipEntry 3 }

    provEthOamMipMegLevel OBJECT-TYPE
        SYNTAX       INTEGER {
                         level0(0),
                         level1(1),
                         level2(2),
                         level3(3),
                         level4(4),
                         level5(5),
                         level6(6),
                         level7(7)
                     }
        MAX-ACCESS   not-accessible
        STATUS       current
        DESCRIPTION  "Meg Level(0-7)"
        ::= { provEthOamMipEntry 4 }

    provEthOamMipNEAddress OBJECT-TYPE
        SYNTAX       IpAddress
        MAX-ACCESS   not-accessible
        STATUS       current
        DESCRIPTION  "IP Address"
        ::= { provEthOamMipEntry 5 }

    provEthOamMipRowStatus OBJECT-TYPE
        SYNTAX       RowStatus { active(1), createAndGo(4), destroy(6) }
        MAX-ACCESS   read-create
        STATUS       current
        DESCRIPTION  "Entry Status"
        ::= { provEthOamMipEntry 6 }

    provEthOamMepTable OBJECT-TYPE
        SYNTAX       SEQUENCE OF ProvEthOamMepEntry
        MAX-ACCESS   not-accessible
        STATUS       current
        DESCRIPTION  "Mep Setting Table"
        ::= { provEthOamGroup 3 }

    provEthOamMepEntry OBJECT-TYPE
        SYNTAX       ProvEthOamMepEntry
        MAX-ACCESS   not-accessible
        STATUS       current
        DESCRIPTION  ""
        INDEX        { provEthOamMepIndex }
        ::= { provEthOamMepTable 1 }

    ProvEthOamMepEntry ::= SEQUENCE {
        provEthOamMepIndex               IpeMepId,
        provEthOamMepNEAddress           IpAddress,
        provEthOamMepIfIndex             InterfaceIndex,
        provEthOamMepVld                 Integer32,
        provEthOamMepMegIndex            IpeMepId,
        provEthOamMepDirection           INTEGER,
        provEthOamMepId                  Integer32,
        provEthOamMepCcmTransmitEnabled  EnableDisableValue,
        provEthOamMepCcmReceiveEnabled   EnableDisableValue,
        provEthOamMepCcmPriority         Integer32,
        provEthOamMepAisTransmitEnabled  EnableDisableValue,
        provEthOamMepAisReceiveEnabled   EnableDisableValue,
        provEthOamMepAisPeriod           INTEGER,
        provEthOamMepAisMegIndex         IpeMepId,
        provEthOamMepAisPriority         Integer32,
        provEthOamMepRowStatus           RowStatus
    }

    provEthOamMepIndex OBJECT-TYPE
        SYNTAX       IpeMepId
        MAX-ACCESS   not-accessible
        STATUS       current
        DESCRIPTION  "Index of this table."
        ::= { provEthOamMepEntry 1 }

    provEthOamMepNEAddress OBJECT-TYPE
        SYNTAX       IpAddress
        MAX-ACCESS   not-accessible
        STATUS       current
        DESCRIPTION  "IP Address"
        ::= { provEthOamMepEntry 2 }

    provEthOamMepIfIndex OBJECT-TYPE
        SYNTAX       InterfaceIndex
        MAX-ACCESS   read-create
        STATUS       current
        DESCRIPTION  "Ifindex"
        ::= { provEthOamMepEntry 3 }

    provEthOamMepVld OBJECT-TYPE
        SYNTAX       Integer32 (0..4094)
        MAX-ACCESS   read-create
        STATUS       current
        DESCRIPTION  "Vlan Id(1-4094, Untag=0)"
        ::= { provEthOamMepEntry 4 }

    provEthOamMepMegIndex OBJECT-TYPE
        SYNTAX       IpeMepId
        MAX-ACCESS   read-create
        STATUS       current
        DESCRIPTION  "Meg Index(1-128)"
        ::= { provEthOamMepEntry 5 }

    provEthOamMepDirection OBJECT-TYPE
        SYNTAX       INTEGER { inside(0), outside(1) }
        MAX-ACCESS   read-create
        STATUS       current
        DESCRIPTION
            "Mep Direction.
            range: outside(iPASOLINK200/400/1000series/EX/iX),
            outside,inside(iPASOLINK VR series)"
        DEFVAL       { outside }
        ::= { provEthOamMepEntry 6 }

    provEthOamMepId OBJECT-TYPE
        SYNTAX       Integer32 (1..8191)
        MAX-ACCESS   read-create
        STATUS       current
        DESCRIPTION  "Mep Id(1-8191)"
        ::= { provEthOamMepEntry 7 }

    provEthOamMepCcmTransmitEnabled OBJECT-TYPE
        SYNTAX       EnableDisableValue
        MAX-ACCESS   read-create
        STATUS       obsolete
        DESCRIPTION  "CCM Transmit Setting"
        ::= { provEthOamMepEntry 8 }

    provEthOamMepCcmReceiveEnabled OBJECT-TYPE
        SYNTAX       EnableDisableValue
        MAX-ACCESS   read-create
        STATUS       obsolete
        DESCRIPTION  "CCM Receive Setting"
        ::= { provEthOamMepEntry 9 }

    provEthOamMepCcmPriority OBJECT-TYPE
        SYNTAX       Integer32 (0..7)
        MAX-ACCESS   read-create
        STATUS       obsolete
        DESCRIPTION  "CCM Frame Priority"
        ::= { provEthOamMepEntry 10 }

    provEthOamMepAisTransmitEnabled OBJECT-TYPE
        SYNTAX       EnableDisableValue
        MAX-ACCESS   read-create
        STATUS       obsolete
        DESCRIPTION  "ETH-AIS Transmit Setting"
        ::= { provEthOamMepEntry 11 }

    provEthOamMepAisReceiveEnabled OBJECT-TYPE
        SYNTAX       EnableDisableValue
        MAX-ACCESS   read-create
        STATUS       obsolete
        DESCRIPTION  "ETH-AIS Receive Setting"
        ::= { provEthOamMepEntry 12 }

    provEthOamMepAisPeriod OBJECT-TYPE
        SYNTAX       INTEGER { invalid(0), period-1s(4), period-1min(6) }
        MAX-ACCESS   read-create
        STATUS       obsolete
        DESCRIPTION  "ETH-AIS Frame Transmit Period"
        ::= { provEthOamMepEntry 13 }

    provEthOamMepAisMegIndex OBJECT-TYPE
        SYNTAX       IpeMepId
        MAX-ACCESS   read-create
        STATUS       obsolete
        DESCRIPTION  "ETH-AIS Frame Transmit MEG"
        ::= { provEthOamMepEntry 14 }

    provEthOamMepAisPriority OBJECT-TYPE
        SYNTAX       Integer32 (0..7)
        MAX-ACCESS   read-create
        STATUS       obsolete
        DESCRIPTION  "ETH-AIS Frame Priority"
        ::= { provEthOamMepEntry 15 }

    provEthOamMepRowStatus OBJECT-TYPE
        SYNTAX       RowStatus {
                         active(1),
                         notInService(2),
                         notReady(3),
                         createAndGo(4),
                         createAndWait(5),
                         destroy(6)
                     }
        MAX-ACCESS   read-create
        STATUS       current
        DESCRIPTION  "Entry Status"
        ::= { provEthOamMepEntry 16 }

    provEthOamPeerListTable OBJECT-TYPE
        SYNTAX       SEQUENCE OF ProvEthOamPeerListEntry
        MAX-ACCESS   not-accessible
        STATUS       current
        DESCRIPTION  "Peer Mep Setting Table"
        ::= { provEthOamGroup 4 }

    provEthOamPeerListEntry OBJECT-TYPE
        SYNTAX       ProvEthOamPeerListEntry
        MAX-ACCESS   not-accessible
        STATUS       current
        DESCRIPTION  ""
        INDEX        { provEthOamPeerListIndex }
        ::= { provEthOamPeerListTable 1 }

    ProvEthOamPeerListEntry ::= SEQUENCE {
        provEthOamPeerListIndex              IpeMepId,
        provEthOamPeerListNEAddress          IpAddress,
        provEthOamPeerListMepIndex           IpeMepId,
        provEthOamPeerListPeerMepId          Integer32,
        provEthOamPeerListCheckStatusEnable  EnableDisableValue,
        provEthOamPeerListRowStatus          RowStatus
    }

    provEthOamPeerListIndex OBJECT-TYPE
        SYNTAX       IpeMepId
        MAX-ACCESS   not-accessible
        STATUS       current
        DESCRIPTION  "Index of this table."
        ::= { provEthOamPeerListEntry 1 }

    provEthOamPeerListNEAddress OBJECT-TYPE
        SYNTAX       IpAddress
        MAX-ACCESS   not-accessible
        STATUS       current
        DESCRIPTION  "IP Address"
        ::= { provEthOamPeerListEntry 2 }

    provEthOamPeerListMepIndex OBJECT-TYPE
        SYNTAX       IpeMepId
        MAX-ACCESS   read-create
        STATUS       current
        DESCRIPTION  "Own Mep Index(1-128)"
        ::= { provEthOamPeerListEntry 3 }

    provEthOamPeerListPeerMepId OBJECT-TYPE
        SYNTAX       Integer32 (1..8191)
        MAX-ACCESS   read-create
        STATUS       current
        DESCRIPTION  "Peer Mep Id(1-8191)"
        ::= { provEthOamPeerListEntry 4 }

    provEthOamPeerListCheckStatusEnable OBJECT-TYPE
        SYNTAX       EnableDisableValue
        MAX-ACCESS   read-create
        STATUS       obsolete
        DESCRIPTION  "Peer Mep CCM Receive setting"
        ::= { provEthOamPeerListEntry 5 }

    provEthOamPeerListRowStatus OBJECT-TYPE
        SYNTAX       RowStatus {
                         active(1),
                         notInService(2),
                         notReady(3),
                         createAndGo(4),
                         createAndWait(5),
                         destroy(6)
                     }
        MAX-ACCESS   read-create
        STATUS       current
        DESCRIPTION  "Entry Status"
        ::= { provEthOamPeerListEntry 6 }

    provEthOamMipMappingTable OBJECT-TYPE
        SYNTAX       SEQUENCE OF ProvEthOamMipMappingEntry
        MAX-ACCESS   not-accessible
        STATUS       current
        DESCRIPTION  "MIP Mapping Table"
        ::= { provEthOamGroup 5 }

    provEthOamMipMappingEntry OBJECT-TYPE
        SYNTAX       ProvEthOamMipMappingEntry
        MAX-ACCESS   not-accessible
        STATUS       current
        DESCRIPTION  ""
        INDEX        {
                         provEthOamMipMappingIfIndex,
                         provEthOamMipMappingVld,
                         provEthOamMipMappingMegLevel
                     }
        ::= { provEthOamMipMappingTable 1 }

    ProvEthOamMipMappingEntry ::= SEQUENCE {
        provEthOamMipMappingIfIndex    InterfaceIndex,
        provEthOamMipMappingVld        Integer32,
        provEthOamMipMappingMegLevel   INTEGER,
        provEthOamMipMappingNEAddress  IpAddress,
        provEthOamMipMappingMipIndex   Integer32
    }

    provEthOamMipMappingIfIndex OBJECT-TYPE
        SYNTAX       InterfaceIndex
        MAX-ACCESS   not-accessible
        STATUS       current
        DESCRIPTION  "Index of this table."
        ::= { provEthOamMipMappingEntry 1 }

    provEthOamMipMappingVld OBJECT-TYPE
        SYNTAX       Integer32 (0..4094)
        MAX-ACCESS   not-accessible
        STATUS       current
        DESCRIPTION  "Vlan Id(1-4094, Untag=0)"
        ::= { provEthOamMipMappingEntry 2 }

    provEthOamMipMappingMegLevel OBJECT-TYPE
        SYNTAX       INTEGER {
                         level0(0),
                         level1(1),
                         level2(2),
                         level3(3),
                         level4(4),
                         level5(5),
                         level6(6),
                         level7(7)
                     }
        MAX-ACCESS   not-accessible
        STATUS       current
        DESCRIPTION  "Meg Level(0-7)"
        ::= { provEthOamMipMappingEntry 3 }

    provEthOamMipMappingNEAddress OBJECT-TYPE
        SYNTAX       IpAddress
        MAX-ACCESS   not-accessible
        STATUS       current
        DESCRIPTION  "IP Address"
        ::= { provEthOamMipMappingEntry 4 }

    provEthOamMipMappingMipIndex OBJECT-TYPE
        SYNTAX       Integer32 (1..32)
        MAX-ACCESS   read-only
        STATUS       current
        DESCRIPTION  "Mip Index(1-32)"
        ::= { provEthOamMipMappingEntry 5 }

    provEthOamMepMappingTable OBJECT-TYPE
        SYNTAX       SEQUENCE OF ProvEthOamMepMappingEntry
        MAX-ACCESS   not-accessible
        STATUS       current
        DESCRIPTION  "MEP Mapping Table"
        ::= { provEthOamGroup 6 }

    provEthOamMepMappingEntry OBJECT-TYPE
        SYNTAX       ProvEthOamMepMappingEntry
        MAX-ACCESS   not-accessible
        STATUS       current
        DESCRIPTION  ""
        INDEX        {
                         provEthOamMepMappingIfIndex,
                         provEthOamMepMappingVld,
                         provEthOamMepMappingMegIndex
                     }
        ::= { provEthOamMepMappingTable 1 }

    ProvEthOamMepMappingEntry ::= SEQUENCE {
        provEthOamMepMappingIfIndex    InterfaceIndex,
        provEthOamMepMappingVld        Integer32,
        provEthOamMepMappingMegIndex   IpeMepId,
        provEthOamMepMappingNEAddress  IpAddress,
        provEthOamMepMappingMepIndex   IpeMepId
    }

    provEthOamMepMappingIfIndex OBJECT-TYPE
        SYNTAX       InterfaceIndex
        MAX-ACCESS   not-accessible
        STATUS       current
        DESCRIPTION  "Index of this table."
        ::= { provEthOamMepMappingEntry 1 }

    provEthOamMepMappingVld OBJECT-TYPE
        SYNTAX       Integer32 (0..4094)
        MAX-ACCESS   not-accessible
        STATUS       current
        DESCRIPTION  "Vlan Id(1-4094, Untag=0)"
        ::= { provEthOamMepMappingEntry 2 }

    provEthOamMepMappingMegIndex OBJECT-TYPE
        SYNTAX       IpeMepId
        MAX-ACCESS   not-accessible
        STATUS       current
        DESCRIPTION  "Index of this table."
        ::= { provEthOamMepMappingEntry 3 }

    provEthOamMepMappingNEAddress OBJECT-TYPE
        SYNTAX       IpAddress
        MAX-ACCESS   not-accessible
        STATUS       current
        DESCRIPTION  "IP Address"
        ::= { provEthOamMepMappingEntry 4 }

    provEthOamMepMappingMepIndex OBJECT-TYPE
        SYNTAX       IpeMepId
        MAX-ACCESS   read-only
        STATUS       current
        DESCRIPTION  "Mep Index(1-128)"
        ::= { provEthOamMepMappingEntry 5 }

    provFdbGroup OBJECT IDENTIFIER
        ::= { provisioningGroup 27 }

    provFdbEquipmentTable OBJECT-TYPE
        SYNTAX       SEQUENCE OF ProvFdbEquipmentEntry
        MAX-ACCESS   not-accessible
        STATUS       current
        DESCRIPTION
            "This table contains the equipment level configuration for FDB
            learning behaviours."
        ::= { provFdbGroup 1 }

    provFdbEquipmentEntry OBJECT-TYPE
        SYNTAX       ProvFdbEquipmentEntry
        MAX-ACCESS   not-accessible
        STATUS       current
        DESCRIPTION  ""
        INDEX        { provFdbEquipmentIndex }
        ::= { provFdbEquipmentTable 1 }

    ProvFdbEquipmentEntry ::= SEQUENCE {
        provFdbEquipmentIndex                  Integer32,
        provFdbEquipmentNEAddress              IpAddress,
        provFdbEquipmentNumberOfLearningEntry  Integer32,
        provFdbEquipmentLearningLimitEnable    EnableDisableValue,
        provFdbEquipmentAgingTime              Integer32,
        provFdbEquipmentAgingEnable            EnableDisableValue,
        provFdbEquipmentLearningLimitMode      INTEGER
    }

    provFdbEquipmentIndex OBJECT-TYPE
        SYNTAX       Integer32 (1..1)
        MAX-ACCESS   not-accessible
        STATUS       current
        DESCRIPTION  "Index of this table."
        ::= { provFdbEquipmentEntry 1 }

    provFdbEquipmentNEAddress OBJECT-TYPE
        SYNTAX       IpAddress
        MAX-ACCESS   not-accessible
        STATUS       current
        DESCRIPTION  "reserved."
        ::= { provFdbEquipmentEntry 2 }

    provFdbEquipmentNumberOfLearningEntry OBJECT-TYPE
        SYNTAX       Integer32 (1..32384)
        MAX-ACCESS   read-write
        STATUS       current
        DESCRIPTION  "Number of maximum learning entries."
        ::= { provFdbEquipmentEntry 3 }

    provFdbEquipmentLearningLimitEnable OBJECT-TYPE
        SYNTAX       EnableDisableValue
        MAX-ACCESS   read-write
        STATUS       current
        DESCRIPTION  "Enabling notification for learning limit over."
        ::= { provFdbEquipmentEntry 4 }

    provFdbEquipmentAgingTime OBJECT-TYPE
        SYNTAX       Integer32 (5..163680)
        MAX-ACCESS   read-write
        STATUS       current
        DESCRIPTION
            "The aging time.
            When the aging time for the destination address is expired, the
            entry will be cleared."
        ::= { provFdbEquipmentEntry 5 }

    provFdbEquipmentAgingEnable OBJECT-TYPE
        SYNTAX       EnableDisableValue
        MAX-ACCESS   read-write
        STATUS       current
        DESCRIPTION
            "Enabling FDB Aging.
            When the object is set to 'disable', the aging function is
            disabled, and the learned entries are never aged-out. Rebooting
            agent or FDB clearing request can clear all entries."
        ::= { provFdbEquipmentEntry 6 }

    provFdbEquipmentLearningLimitMode OBJECT-TYPE
        SYNTAX       INTEGER { normal(1), protect(2) }
        MAX-ACCESS   read-write
        STATUS       current
        DESCRIPTION
            "Learning limit mode.
            On 'normal' mode, when the learned entries exceed the value of
            provFdbEquipmentNumberOfLearningEntry, the exceeded entries are
            not learned and unknown frames are flooded to all ports.
            On 'protect' mode, the unknown frames are discarded when the
            learning entries are full."
        ::= { provFdbEquipmentEntry 7 }

    provFdbVlanTable OBJECT-TYPE
        SYNTAX       SEQUENCE OF ProvFdbVlanEntry
        MAX-ACCESS   not-accessible
        STATUS       current
        DESCRIPTION  "this table contains the vlan level configurations."
        ::= { provFdbGroup 2 }

    provFdbVlanEntry OBJECT-TYPE
        SYNTAX       ProvFdbVlanEntry
        MAX-ACCESS   not-accessible
        STATUS       current
        DESCRIPTION  ""
        INDEX        { provFdbVlanIndex }
        ::= { provFdbVlanTable 1 }

    ProvFdbVlanEntry ::= SEQUENCE {
        provFdbVlanIndex                    Integer32,
        provFdbVlanNEAddress                IpAddress,
        provFdbVlanNumberOfLearningEntry    Integer32,
        provFdbVlanLearningLimitMode        INTEGER,
        provFdbVlanLearningLimitModeEnable  EnableDisableValue
    }

    provFdbVlanIndex OBJECT-TYPE
        SYNTAX       Integer32 (1..4094)
        MAX-ACCESS   not-accessible
        STATUS       current
        DESCRIPTION  "Index of this table."
        ::= { provFdbVlanEntry 1 }

    provFdbVlanNEAddress OBJECT-TYPE
        SYNTAX       IpAddress
        MAX-ACCESS   not-accessible
        STATUS       current
        DESCRIPTION  "reserved."
        ::= { provFdbVlanEntry 2 }

    provFdbVlanNumberOfLearningEntry OBJECT-TYPE
        SYNTAX       Integer32 (1..32384)
        MAX-ACCESS   read-write
        STATUS       current
        DESCRIPTION  "Number of maximum learning entries per VLAN."
        ::= { provFdbVlanEntry 3 }

    provFdbVlanLearningLimitMode OBJECT-TYPE
        SYNTAX       INTEGER { normal(1), protect(2) }
        MAX-ACCESS   read-write
        STATUS       current
        DESCRIPTION
            "Learning limit mode.
            On 'normal' mode, when the learned entries exceed the value of
            provFdbEquipmentNumberOfLearningEntry, the exceeded entries are
            not learned and unknown frames are flooded to all ports.
            On 'protect' mode, the unknown frames are discarded when the
            learning entries are full."
        ::= { provFdbVlanEntry 4 }

    provFdbVlanLearningLimitModeEnable OBJECT-TYPE
        SYNTAX       EnableDisableValue
        MAX-ACCESS   read-write
        STATUS       current
        DESCRIPTION
            "Enabling the learning limitation per VLAN.
            When the value is set to 'disable', the available learning
            entries for that VLAN are up to the amount of system entries, and
            the limit mode is configured to the 'normal' mode.

            Note) if the other limitation (per system or per port) is
            enabled, the learning limitation is performed by the
            configuration."
        ::= { provFdbVlanEntry 5 }

    provFdbStaticEntryTable OBJECT-TYPE
        SYNTAX       SEQUENCE OF ProvFdbStaticEntryEntry
        MAX-ACCESS   not-accessible
        STATUS       current
        DESCRIPTION  ""
        ::= { provFdbGroup 3 }

    provFdbStaticEntryEntry OBJECT-TYPE
        SYNTAX       ProvFdbStaticEntryEntry
        MAX-ACCESS   not-accessible
        STATUS       current
        DESCRIPTION  ""
        INDEX        {
                         provFdbStaticEntryIndex,
                         provFdbStaticVlanId,
                         provFdbStaticPortIfIndex
                     }
        ::= { provFdbStaticEntryTable 1 }

    ProvFdbStaticEntryEntry ::= SEQUENCE {
        provFdbStaticEntryIndex   Integer32,
        provFdbStaticVlanId       Integer32,
        provFdbStaticPortIfIndex  InterfaceIndex,
        provFdbStaticNEAddress    IpAddress,
        provFdbStaticMacAddress   MacAddress,
        provFdbStaticRowStatus    RowStatus
    }

    provFdbStaticEntryIndex OBJECT-TYPE
        SYNTAX       Integer32 (1..256)
        MAX-ACCESS   not-accessible
        STATUS       current
        DESCRIPTION  "Index of this table."
        ::= { provFdbStaticEntryEntry 1 }

    provFdbStaticVlanId OBJECT-TYPE
        SYNTAX       Integer32 (1..4094)
        MAX-ACCESS   not-accessible
        STATUS       current
        DESCRIPTION
            "VLAN ID
            Value Range : 1-4094
            FLAG=TRAP|EVLOG
            LOGITEM='%s'
            LOGSTATUS='%s'"
        ::= { provFdbStaticEntryEntry 2 }

    provFdbStaticPortIfIndex OBJECT-TYPE
        SYNTAX       InterfaceIndex
        MAX-ACCESS   not-accessible
        STATUS       current
        DESCRIPTION  "Index of this table."
        ::= { provFdbStaticEntryEntry 3 }

    provFdbStaticNEAddress OBJECT-TYPE
        SYNTAX       IpAddress
        MAX-ACCESS   not-accessible
        STATUS       current
        DESCRIPTION  "reserved."
        ::= { provFdbStaticEntryEntry 4 }

    provFdbStaticMacAddress OBJECT-TYPE
        SYNTAX       MacAddress
        MAX-ACCESS   read-create
        STATUS       current
        DESCRIPTION
            "MAC Address
            Valude Range : 00:00:00:00:00:00-FF:FF:FF:FF:FF:FF
            FLAG=TRAP|EVLOG
            LOGITEM='%s'
            LOGSTATUS='%s'"
        ::= { provFdbStaticEntryEntry 5 }

    provFdbStaticRowStatus OBJECT-TYPE
        SYNTAX       RowStatus { active(1), createAndGo(4), destroy(6) }
        MAX-ACCESS   read-create
        STATUS       current
        DESCRIPTION
            "Rowstatus
            1. active
            4. createAndGo
            6. destroy
            FLAG=TRAP|EVLOG
            LOGITEM='%s'
            LOGSTATUS='%s'"
        ::= { provFdbStaticEntryEntry 6 }

    provFdbPortTable OBJECT-TYPE
        SYNTAX       SEQUENCE OF ProvFdbPortEntry
        MAX-ACCESS   not-accessible
        STATUS       current
        DESCRIPTION  "this table contains the port level configurations."
        ::= { provFdbGroup 4 }

    provFdbPortEntry OBJECT-TYPE
        SYNTAX       ProvFdbPortEntry
        MAX-ACCESS   not-accessible
        STATUS       current
        DESCRIPTION  ""
        INDEX        { provFdbPortIfIndex }
        ::= { provFdbPortTable 1 }

    ProvFdbPortEntry ::= SEQUENCE {
        provFdbPortIfIndex        InterfaceIndex,
        provFdbPortNEAddress      IpAddress,
        provFdbPortLearningLimit  Integer32,
        provFdbPortLimitMode      INTEGER,
        provFdbPortLimitEnable    EnableDisableValue
    }

    provFdbPortIfIndex OBJECT-TYPE
        SYNTAX       InterfaceIndex
        MAX-ACCESS   not-accessible
        STATUS       current
        DESCRIPTION  "Index of this table."
        ::= { provFdbPortEntry 1 }

    provFdbPortNEAddress OBJECT-TYPE
        SYNTAX       IpAddress
        MAX-ACCESS   not-accessible
        STATUS       obsolete
        DESCRIPTION  "reserved."
        ::= { provFdbPortEntry 2 }

    provFdbPortLearningLimit OBJECT-TYPE
        SYNTAX       Integer32 (1..32384)
        MAX-ACCESS   read-write
        STATUS       current
        DESCRIPTION  "Number of maximum learning entries per port."
        DEFVAL       { 32384 }
        ::= { provFdbPortEntry 3 }

    provFdbPortLimitMode OBJECT-TYPE
        SYNTAX       INTEGER { normal(1), protect(2) }
        MAX-ACCESS   read-write
        STATUS       current
        DESCRIPTION
            "Learning limit mode.
            On 'normal' mode, when the learned entries exceed the value of
            provFdbEquipmentNumberOfLearningEntry, the exceeded entries are
            not learned and unknown frames are flooded to all ports.
            On 'protect' mode, the unknown frames are discarded when the
            learning entries are full."
        DEFVAL       { protect }
        ::= { provFdbPortEntry 4 }

    provFdbPortLimitEnable OBJECT-TYPE
        SYNTAX       EnableDisableValue
        MAX-ACCESS   read-write
        STATUS       current
        DESCRIPTION
            "Enabling the learning limitation per port.
            When the value is set to 'disable', the available learning
            entries for that port are up to the amount of system entries, and
            the limit mode is configured to the 'normal' mode.

            Note) if the other limitation (per system or per VLAN) is
            enabled, the learning limitation is performed by the
            configuration."
        DEFVAL       { disable }
        ::= { provFdbPortEntry 5 }

    provLlfGroup OBJECT IDENTIFIER
        ::= { provisioningGroup 28 }

    provLlfGroupTable OBJECT-TYPE
        SYNTAX       SEQUENCE OF ProvLlfGroupEntry
        MAX-ACCESS   not-accessible
        STATUS       current
        DESCRIPTION  ""
        ::= { provLlfGroup 1 }

    provLlfGroupEntry OBJECT-TYPE
        SYNTAX       ProvLlfGroupEntry
        MAX-ACCESS   not-accessible
        STATUS       current
        DESCRIPTION  ""
        INDEX        { provLlfGroupIndex, provLlfGroupIfIndex }
        ::= { provLlfGroupTable 1 }

    ProvLlfGroupEntry ::= SEQUENCE {
        provLlfGroupIndex       Integer32,
        provLlfGroupIfIndex     InterfaceIndex,
        provLlfGroupNEAddress   IpAddress,
        provLlfGroupPortEnable  INTEGER,
        provLlfGroupRowStatus   RowStatus
    }

    provLlfGroupIndex OBJECT-TYPE
        SYNTAX       Integer32 (1..16)
        MAX-ACCESS   not-accessible
        STATUS       current
        DESCRIPTION  "Index of this table."
        ::= { provLlfGroupEntry 1 }

    provLlfGroupIfIndex OBJECT-TYPE
        SYNTAX       InterfaceIndex
        MAX-ACCESS   not-accessible
        STATUS       current
        DESCRIPTION  "Index of this table."
        ::= { provLlfGroupEntry 2 }

    provLlfGroupNEAddress OBJECT-TYPE
        SYNTAX       IpAddress
        MAX-ACCESS   not-accessible
        STATUS       current
        DESCRIPTION  "IP Address"
        ::= { provLlfGroupEntry 3 }

    provLlfGroupPortEnable OBJECT-TYPE
        SYNTAX       INTEGER { disable(1), enable(2) }
        MAX-ACCESS   read-create
        STATUS       current
        DESCRIPTION
            "LLF Group Enable
            FLAG=TRAP|EVLOG
            LOGITEM='%s'
            LOGSTATUS='%s'"
        ::= { provLlfGroupEntry 4 }

    provLlfGroupRowStatus OBJECT-TYPE
        SYNTAX       RowStatus { active(1), createAndGo(4), destroy(6) }
        MAX-ACCESS   read-create
        STATUS       current
        DESCRIPTION
            "RowStatus
            1. active
            4. createAndGo
            6. destroy
            FLAG=TRAP|EVLOG
            LOGITEM='%s'
            LOGSTATUS='%s'"
        ::= { provLlfGroupEntry 5 }

    provLlfPortTable OBJECT-TYPE
        SYNTAX       SEQUENCE OF ProvLlfPortEntry
        MAX-ACCESS   not-accessible
        STATUS       current
        DESCRIPTION  ""
        ::= { provLlfGroup 2 }

    provLlfPortEntry OBJECT-TYPE
        SYNTAX       ProvLlfPortEntry
        MAX-ACCESS   not-accessible
        STATUS       current
        DESCRIPTION  ""
        INDEX        { provLlfPortIfIndex }
        ::= { provLlfPortTable 1 }

    ProvLlfPortEntry ::= SEQUENCE {
        provLlfPortIfIndex         InterfaceIndex,
        provLlfPortNEAddress       IpAddress,
        provLlfPortMode            INTEGER,
        provLlfPortInfoForwarding  INTEGER
    }

    provLlfPortIfIndex OBJECT-TYPE
        SYNTAX       InterfaceIndex
        MAX-ACCESS   not-accessible
        STATUS       current
        DESCRIPTION  "Index of this table."
        ::= { provLlfPortEntry 1 }

    provLlfPortNEAddress OBJECT-TYPE
        SYNTAX       IpAddress
        MAX-ACCESS   not-accessible
        STATUS       current
        DESCRIPTION  "IP Address"
        ::= { provLlfPortEntry 2 }

    provLlfPortMode OBJECT-TYPE
        SYNTAX       INTEGER { trunk(1), edgeShutdown(2), edgeOamSend(3) }
        MAX-ACCESS   read-write
        STATUS       current
        DESCRIPTION
            "LLF Port Mode. 'trunk' means the port is connected to the peer,
            'trunk' port only transfers the LLF request messages, the port
            status will not be changed by LLF.
            'edgeShutdown' and 'edegOamSend' means the port will be act as
            edge port of LLF group. The port which is configured as
            'edgeShutdown' will be closed when the LLF control is activated,
            on the other hand, the 'edgeOamSend' port will send the OAM
            messages when the LLF control is activated.

            The modem port cannot be configured as 'edgeShutdown' or
            'edgeOamSend', can be configured as 'trunk'. And default value
            depends on the port type. The default value of the modem port is
            'trunk', and that of the other port is 'edgeShutdown'."
        ::= { provLlfPortEntry 3 }

    provLlfPortInfoForwarding OBJECT-TYPE
        SYNTAX       INTEGER { disable(1), enable(2) }
        MAX-ACCESS   read-write
        STATUS       current
        DESCRIPTION
            "LLF Info Fowarding Enable
            Default : enable
            FLAG=TRAP|EVLOG
            LOGITEM='%s'
            LOGSTATUS='%s'"
        ::= { provLlfPortEntry 4 }

    provLlfGroupIgnoreTable OBJECT-TYPE
        SYNTAX       SEQUENCE OF ProvLlfGroupIgnoreEntry
        MAX-ACCESS   not-accessible
        STATUS       current
        DESCRIPTION  ""
        ::= { provLlfGroup 3 }

    provLlfGroupIgnoreEntry OBJECT-TYPE
        SYNTAX       ProvLlfGroupIgnoreEntry
        MAX-ACCESS   not-accessible
        STATUS       current
        DESCRIPTION  ""
        INDEX        { provLlfGroupIgnoreIndex }
        ::= { provLlfGroupIgnoreTable 1 }

    ProvLlfGroupIgnoreEntry ::= SEQUENCE {
        provLlfGroupIgnoreIndex      Integer32,
        provLlfGroupIgnoreNEAddress  IpAddress,
        provLlfGroupIgnoreEnable     INTEGER
    }

    provLlfGroupIgnoreIndex OBJECT-TYPE
        SYNTAX       Integer32 (1..16)
        MAX-ACCESS   not-accessible
        STATUS       current
        DESCRIPTION  "Index of this table."
        ::= { provLlfGroupIgnoreEntry 1 }

    provLlfGroupIgnoreNEAddress OBJECT-TYPE
        SYNTAX       IpAddress
        MAX-ACCESS   not-accessible
        STATUS       current
        DESCRIPTION  "IP Address"
        ::= { provLlfGroupIgnoreEntry 2 }

    provLlfGroupIgnoreEnable OBJECT-TYPE
        SYNTAX       INTEGER { disable(1), enable(2) }
        MAX-ACCESS   read-write
        STATUS       current
        DESCRIPTION
            "LLF Info Ignore Enable
            Default : disable
            FLAG=TRAP|EVLOG
            LOGITEM='%s'
            LOGSTATUS='%s'"
        ::= { provLlfGroupIgnoreEntry 3 }

    provFilterGroup OBJECT IDENTIFIER
        ::= { provisioningGroup 29 }

    provFilterProfileTable OBJECT-TYPE
        SYNTAX       SEQUENCE OF ProvFilterProfileEntry
        MAX-ACCESS   not-accessible
        STATUS       current
        DESCRIPTION  ""
        ::= { provFilterGroup 1 }

    provFilterProfileEntry OBJECT-TYPE
        SYNTAX       ProvFilterProfileEntry
        MAX-ACCESS   not-accessible
        STATUS       current
        DESCRIPTION  ""
        INDEX        { provFilterProfileIndex }
        ::= { provFilterProfileTable 1 }

    ProvFilterProfileEntry ::= SEQUENCE {
        provFilterProfileIndex      Integer32,
        provFilterProfileNEAddress  IpAddress,
        provFilterEntryIndex1       Integer32,
        provFilterEntryIndex2       Integer32,
        provFilterEntryIndex3       Integer32,
        provFilterEntryIndex4       Integer32,
        provFilterEntryIndex5       Integer32,
        provFilterEntryIndex6       Integer32,
        provFilterEntryIndex7       Integer32,
        provFilterEntryIndex8       Integer32,
        provFilterEntryIndex9       Integer32,
        provFilterEntryIndex10      Integer32,
        provFilterProfileName       DisplayString,
        provFilterRowStatus         RowStatus
    }

    provFilterProfileIndex OBJECT-TYPE
        SYNTAX       Integer32 (1..64)
        MAX-ACCESS   not-accessible
        STATUS       current
        DESCRIPTION  "Index of this table."
        ::= { provFilterProfileEntry 1 }

    provFilterProfileNEAddress OBJECT-TYPE
        SYNTAX       IpAddress
        MAX-ACCESS   not-accessible
        STATUS       current
        DESCRIPTION  "reserved."
        ::= { provFilterProfileEntry 2 }

    provFilterEntryIndex1 OBJECT-TYPE
        SYNTAX       Integer32 (0..256)
        MAX-ACCESS   read-create
        STATUS       current
        DESCRIPTION
            "Filter Entry number which is assigned to this profile. The value
            0 means that no Filter entry is assigned. To set the filter entry
            to the profile, set the filter entry number to this object. To
            unassign the filter entry from the profile, set 0 to the object."
        DEFVAL       { 0 }
        ::= { provFilterProfileEntry 3 }

    provFilterEntryIndex2 OBJECT-TYPE
        SYNTAX       Integer32 (0..256)
        MAX-ACCESS   read-create
        STATUS       current
        DESCRIPTION
            "Filter Entry number which is assigned to this profile. The value
            0 means that no Filter entry is assigned. To set the filter entry
            to the profile, set the filter entry number to this object. To
            unassign the filter entry from the profile, set 0 to the object."
        DEFVAL       { 0 }
        ::= { provFilterProfileEntry 4 }

    provFilterEntryIndex3 OBJECT-TYPE
        SYNTAX       Integer32 (0..256)
        MAX-ACCESS   read-create
        STATUS       current
        DESCRIPTION
            "Filter Entry number which is assigned to this profile. The value
            0 means that no Filter entry is assigned. To set the filter entry
            to the profile, set the filter entry number to this object. To
            unassign the filter entry from the profile, set 0 to the object."
        DEFVAL       { 0 }
        ::= { provFilterProfileEntry 5 }

    provFilterEntryIndex4 OBJECT-TYPE
        SYNTAX       Integer32 (0..256)
        MAX-ACCESS   read-create
        STATUS       current
        DESCRIPTION
            "Filter Entry number which is assigned to this profile. The value
            0 means that no Filter entry is assigned. To set the filter entry
            to the profile, set the filter entry number to this object. To
            unassign the filter entry from the profile, set 0 to the object."
        DEFVAL       { 0 }
        ::= { provFilterProfileEntry 6 }

    provFilterEntryIndex5 OBJECT-TYPE
        SYNTAX       Integer32 (0..256)
        MAX-ACCESS   read-create
        STATUS       current
        DESCRIPTION
            "Filter Entry number which is assigned to this profile. The value
            0 means that no Filter entry is assigned. To set the filter entry
            to the profile, set the filter entry number to this object. To
            unassign the filter entry from the profile, set 0 to the object."
        DEFVAL       { 0 }
        ::= { provFilterProfileEntry 7 }

    provFilterEntryIndex6 OBJECT-TYPE
        SYNTAX       Integer32 (0..256)
        MAX-ACCESS   read-create
        STATUS       current
        DESCRIPTION
            "Filter Entry number which is assigned to this profile. The value
            0 means that no Filter entry is assigned. To set the filter entry
            to the profile, set the filter entry number to this object. To
            unassign the filter entry from the profile, set 0 to the object."
        DEFVAL       { 0 }
        ::= { provFilterProfileEntry 8 }

    provFilterEntryIndex7 OBJECT-TYPE
        SYNTAX       Integer32 (0..256)
        MAX-ACCESS   read-create
        STATUS       current
        DESCRIPTION
            "Filter Entry number which is assigned to this profile. The value
            0 means that no Filter entry is assigned. To set the filter entry
            to the profile, set the filter entry number to this object. To
            unassign the filter entry from the profile, set 0 to the object."
        DEFVAL       { 0 }
        ::= { provFilterProfileEntry 9 }

    provFilterEntryIndex8 OBJECT-TYPE
        SYNTAX       Integer32 (0..256)
        MAX-ACCESS   read-create
        STATUS       current
        DESCRIPTION
            "Filter Entry number which is assigned to this profile. The value
            0 means that no Filter entry is assigned. To set the filter entry
            to the profile, set the filter entry number to this object. To
            unassign the filter entry from the profile, set 0 to the object."
        DEFVAL       { 0 }
        ::= { provFilterProfileEntry 10 }

    provFilterEntryIndex9 OBJECT-TYPE
        SYNTAX       Integer32 (0..256)
        MAX-ACCESS   read-create
        STATUS       current
        DESCRIPTION
            "Filter Entry number which is assigned to this profile. The value
            0 means that no Filter entry is assigned. To set the filter entry
            to the profile, set the filter entry number to this object. To
            unassign the filter entry from the profile, set 0 to the object."
        DEFVAL       { 0 }
        ::= { provFilterProfileEntry 11 }

    provFilterEntryIndex10 OBJECT-TYPE
        SYNTAX       Integer32 (0..256)
        MAX-ACCESS   read-create
        STATUS       current
        DESCRIPTION
            "Filter Entry number which is assigned to this profile. The value
            0 means that no Filter entry is assigned. To set the filter entry
            to the profile, set the filter entry number to this object. To
            unassign the filter entry from the profile, set 0 to the object."
        DEFVAL       { 0 }
        ::= { provFilterProfileEntry 12 }

    provFilterProfileName OBJECT-TYPE
        SYNTAX       DisplayString (SIZE(0..32))
        MAX-ACCESS   read-create
        STATUS       current
        DESCRIPTION  "Administrative Name for the Filter Profile"
        ::= { provFilterProfileEntry 68 }

    provFilterRowStatus OBJECT-TYPE
        SYNTAX       RowStatus { active(1), createAndGo(4), destroy(6) }
        MAX-ACCESS   read-create
        STATUS       current
        DESCRIPTION
            "RowStatus for this table. This object controls create and delete
            filter profile."
        ::= { provFilterProfileEntry 69 }

    provFilterEntryTable OBJECT-TYPE
        SYNTAX       SEQUENCE OF ProvFilterEntryEntry
        MAX-ACCESS   not-accessible
        STATUS       current
        DESCRIPTION  ""
        ::= { provFilterGroup 2 }

    provFilterEntryEntry OBJECT-TYPE
        SYNTAX       ProvFilterEntryEntry
        MAX-ACCESS   not-accessible
        STATUS       current
        DESCRIPTION  ""
        INDEX        { provFilterEntryIndex }
        ::= { provFilterEntryTable 1 }

    ProvFilterEntryEntry ::= SEQUENCE {
        provFilterEntryIndex          Integer32,
        provFilterEntryNEAddress      IpAddress,
        provFilterEntryMode           INTEGER,
        provFilterEntryTarget         INTEGER,
        provFilterEntryDestMac        MacAddress,
        provFilterEntryDestMacMask    MacAddress,
        provFilterEntrySrcMac         MacAddress,
        provFilterEntrySrcMacMask     MacAddress,
        provFilterEntryEthertype      OCTET STRING,
        provFilterEntryEthertypeMask  OCTET STRING,
        provFilterEntryCos            OCTET STRING,
        provFilterEntryCosMask        OCTET STRING,
        provFilterEntryVlan           Integer32,
        provFilterEntryVlanMask       Integer32,
        provFilterEntryRowStatus      RowStatus
    }

    provFilterEntryIndex OBJECT-TYPE
        SYNTAX       Integer32 (1..256)
        MAX-ACCESS   not-accessible
        STATUS       current
        DESCRIPTION  "Index of this table."
        ::= { provFilterEntryEntry 1 }

    provFilterEntryNEAddress OBJECT-TYPE
        SYNTAX       IpAddress
        MAX-ACCESS   not-accessible
        STATUS       current
        DESCRIPTION
            "IP Address
            FLAG=TRAP|EVLOG
            LOGITEM='%s'
            LOGSTATUS='%s'"
        ::= { provFilterEntryEntry 2 }

    provFilterEntryMode OBJECT-TYPE
        SYNTAX       INTEGER { deny(1), permit(2) }
        MAX-ACCESS   read-create
        STATUS       obsolete
        DESCRIPTION
            "Filter entry action:deny(1), permit(2)
            default:deny(1)
            FLAG=TRAP|EVLOG
            LOGITEM='%s'
            LOGSTATUS='%s'"
        DEFVAL       { deny }
        ::= { provFilterEntryEntry 3 }

    provFilterEntryTarget OBJECT-TYPE
        SYNTAX       INTEGER { invalid(0), l2filter(1) }
        MAX-ACCESS   read-create
        STATUS       obsolete
        DESCRIPTION
            "Filter Type:L2(1), L3(2)
            default:L2(1)
            FLAG=TRAP|EVLOG
            LOGITEM='%s'
            LOGSTATUS='%s'"
        DEFVAL       { l2filter }
        ::= { provFilterEntryEntry 4 }

    provFilterEntryDestMac OBJECT-TYPE
        SYNTAX       MacAddress
        MAX-ACCESS   read-create
        STATUS       current
        DESCRIPTION
            "Destination MAC Address
            FLAG=TRAP|EVLOG
            LOGITEM='%s'
            LOGSTATUS='%s'"
        DEFVAL       { '000000000000'h }
        ::= { provFilterEntryEntry 5 }

    provFilterEntryDestMacMask OBJECT-TYPE
        SYNTAX       MacAddress
        MAX-ACCESS   read-create
        STATUS       current
        DESCRIPTION
            "Destination MAC Address mask value
            FLAG=TRAP|EVLOG
            LOGITEM='%s'
            LOGSTATUS='%s'"
        DEFVAL       { '000000000000'h }
        ::= { provFilterEntryEntry 6 }

    provFilterEntrySrcMac OBJECT-TYPE
        SYNTAX       MacAddress
        MAX-ACCESS   read-create
        STATUS       current
        DESCRIPTION
            "Source MAC Address
            FLAG=TRAP|EVLOG
            LOGITEM='%s'
            LOGSTATUS='%s'"
        DEFVAL       { '000000000000'h }
        ::= { provFilterEntryEntry 7 }

    provFilterEntrySrcMacMask OBJECT-TYPE
        SYNTAX       MacAddress
        MAX-ACCESS   read-create
        STATUS       current
        DESCRIPTION
            "Source MAC Address mask value
            FLAG=TRAP|EVLOG
            LOGITEM='%s'
            LOGSTATUS='%s'"
        DEFVAL       { '000000000000'h }
        ::= { provFilterEntryEntry 8 }

    provFilterEntryEthertype OBJECT-TYPE
        SYNTAX       OCTET STRING (SIZE(2..2))
        MAX-ACCESS   read-create
        STATUS       current
        DESCRIPTION
            "EthetType
            FLAG=TRAP|EVLOG
            LOGITEM='%s'
            LOGSTATUS='%s'"
        DEFVAL       { '0000'h }
        ::= { provFilterEntryEntry 9 }

    provFilterEntryEthertypeMask OBJECT-TYPE
        SYNTAX       OCTET STRING (SIZE(2..2))
        MAX-ACCESS   read-create
        STATUS       current
        DESCRIPTION
            "EthetType mask value
            FLAG=TRAP|EVLOG
            LOGITEM='%s'
            LOGSTATUS='%s'"
        DEFVAL       { '0000'h }
        ::= { provFilterEntryEntry 10 }

    provFilterEntryCos OBJECT-TYPE
        SYNTAX       OCTET STRING (SIZE(1..1))
        MAX-ACCESS   read-create
        STATUS       current
        DESCRIPTION
            "CoS
            FLAG=TRAP|EVLOG
            LOGITEM='%s'
            LOGSTATUS='%s'"
        DEFVAL       { '00'h }
        ::= { provFilterEntryEntry 11 }

    provFilterEntryCosMask OBJECT-TYPE
        SYNTAX       OCTET STRING (SIZE(1..1))
        MAX-ACCESS   read-create
        STATUS       current
        DESCRIPTION
            "CoS mask value
            FLAG=TRAP|EVLOG
            LOGITEM='%s'
            LOGSTATUS='%s'"
        DEFVAL       { '00'h }
        ::= { provFilterEntryEntry 12 }

    provFilterEntryVlan OBJECT-TYPE
        SYNTAX       Integer32 (1..4095)
        MAX-ACCESS   read-create
        STATUS       current
        DESCRIPTION
            "VLAN-ID
            FLAG=TRAP|EVLOG
            LOGITEM='%s'
            LOGSTATUS='%s'"
        DEFVAL       { 1 }
        ::= { provFilterEntryEntry 13 }

    provFilterEntryVlanMask OBJECT-TYPE
        SYNTAX       Integer32 (0..4095)
        MAX-ACCESS   read-create
        STATUS       current
        DESCRIPTION
            "VLAN-ID mask value
            FLAG=TRAP|EVLOG
            LOGITEM='%s'
            LOGSTATUS='%s'"
        DEFVAL       { 0 }
        ::= { provFilterEntryEntry 14 }

    provFilterEntryRowStatus OBJECT-TYPE
        SYNTAX       RowStatus { active(1), createAndGo(4), destroy(6) }
        MAX-ACCESS   read-create
        STATUS       current
        DESCRIPTION
            "RowStatus
            1. active
            4. createAndGo
            6. destroy
            FLAG=TRAP|EVLOG
            LOGITEM='%s'
            LOGSTATUS='%s'"
        ::= { provFilterEntryEntry 53 }

    provFilterPortTable OBJECT-TYPE
        SYNTAX       SEQUENCE OF ProvFilterPortEntry
        MAX-ACCESS   not-accessible
        STATUS       current
        DESCRIPTION  ""
        ::= { provFilterGroup 3 }

    provFilterPortEntry OBJECT-TYPE
        SYNTAX       ProvFilterPortEntry
        MAX-ACCESS   not-accessible
        STATUS       current
        DESCRIPTION  ""
        INDEX        { provFilterPortIndex }
        ::= { provFilterPortTable 1 }

    ProvFilterPortEntry ::= SEQUENCE {
        provFilterPortIndex       Integer32,
        provFilterPortNEAddress   IpAddress,
        provFilterIngressProfile  Integer32,
        provFilterEgressProfile   Integer32
    }

    provFilterPortIndex OBJECT-TYPE
        SYNTAX       Integer32
        MAX-ACCESS   not-accessible
        STATUS       current
        DESCRIPTION  "Index of this table."
        ::= { provFilterPortEntry 1 }

    provFilterPortNEAddress OBJECT-TYPE
        SYNTAX       IpAddress
        MAX-ACCESS   not-accessible
        STATUS       current
        DESCRIPTION  "IP Address"
        ::= { provFilterPortEntry 2 }

    provFilterIngressProfile OBJECT-TYPE
        SYNTAX       Integer32 (0..64)
        MAX-ACCESS   read-write
        STATUS       current
        DESCRIPTION
            "Ingress Filter Profile Number. To assign the filter profile to
            this port, set the appropriate filter profile index to this
            object.
            To unassign the filter profile from this port, set 0.
            For iPASOLINK VR series, this object can be set to non-zero value
            up to 16 ports in total."
        DEFVAL       { 0 }
        ::= { provFilterPortEntry 3 }

    provFilterEgressProfile OBJECT-TYPE
        SYNTAX       Integer32 (0..64)
        MAX-ACCESS   read-write
        STATUS       obsolete
        DESCRIPTION
            "Egress Filter Profile Number. To assign the filter profile to
            this port, set the appropriate filter profile index to this
            object.
            To unassign the filter profile from this port, set 0.
            For iPASOLINK VR series, this object can be set to non-zero value
            up to 16 ports in total."
        DEFVAL       { 0 }
        ::= { provFilterPortEntry 4 }

    provFilterL2ProtoTable OBJECT-TYPE
        SYNTAX       SEQUENCE OF ProvFilterL2ProtoEntry
        MAX-ACCESS   not-accessible
        STATUS       current
        DESCRIPTION  ""
        ::= { provFilterGroup 4 }

    provFilterL2ProtoEntry OBJECT-TYPE
        SYNTAX       ProvFilterL2ProtoEntry
        MAX-ACCESS   not-accessible
        STATUS       current
        DESCRIPTION  ""
        INDEX        { provFilterL2ProtoIfIndex }
        ::= { provFilterL2ProtoTable 1 }

    ProvFilterL2ProtoEntry ::= SEQUENCE {
        provFilterL2ProtoIfIndex          InterfaceIndex,
        provFilterL2ProtoNEAddress        IpAddress,
        provFilterL2ProtoBpduAction       INTEGER,
        provFilterL2ProtoLacpAction       INTEGER,
        provFilterL2ProtoPortAutheAction  INTEGER,
        provFilterL2ProtoPBAction         INTEGER,
        provFilterL2ProtoLldpAction       INTEGER,
        provFilterL2ProtoOtherMacAction   INTEGER,
        provFilterL2ProtoGarpAction       INTEGER
    }

    provFilterL2ProtoIfIndex OBJECT-TYPE
        SYNTAX       InterfaceIndex
        MAX-ACCESS   not-accessible
        STATUS       current
        DESCRIPTION  "Index of this table."
        ::= { provFilterL2ProtoEntry 1 }

    provFilterL2ProtoNEAddress OBJECT-TYPE
        SYNTAX       IpAddress
        MAX-ACCESS   not-accessible
        STATUS       current
        DESCRIPTION
            "IP Address
            FLAG=TRAP|EVLOG
            LOGITEM='%s'
            LOGSTATUS='%s'"
        ::= { provFilterL2ProtoEntry 2 }

    provFilterL2ProtoBpduAction OBJECT-TYPE
        SYNTAX       INTEGER { discard(1), transparent(2) }
        MAX-ACCESS   read-write
        STATUS       current
        DESCRIPTION
            "L2 Protocol Fream(BPDU) Recive Action:discard(1),transparent(2)
            default:discard(1)
            FLAG=TRAP|EVLOG
            LOGITEM='%s'
            LOGSTATUS='%s'"
        ::= { provFilterL2ProtoEntry 3 }

    provFilterL2ProtoLacpAction OBJECT-TYPE
        SYNTAX       INTEGER { discard(1), transparent(2) }
        MAX-ACCESS   read-write
        STATUS       current
        DESCRIPTION
            "L2 Protocol Fream(LACP) Recive Action:discard(1),transparent(2)
            default:discard(1)
            FLAG=TRAP|EVLOG
            LOGITEM='%s'
            LOGSTATUS='%s'"
        ::= { provFilterL2ProtoEntry 4 }

    provFilterL2ProtoPortAutheAction OBJECT-TYPE
        SYNTAX       INTEGER { discard(1), transparent(2) }
        MAX-ACCESS   read-write
        STATUS       current
        DESCRIPTION
            "L2 Protocol Fream(Port Authe) Recive
            Action:discard(1),transparent(2)
            default:discard(1)
            FLAG=TRAP|EVLOG
            LOGITEM='%s'
            LOGSTATUS='%s'"
        ::= { provFilterL2ProtoEntry 5 }

    provFilterL2ProtoPBAction OBJECT-TYPE
        SYNTAX       INTEGER { discard(1), transparent(2) }
        MAX-ACCESS   read-write
        STATUS       current
        DESCRIPTION
            "L2 Protocol Fream(PB) Recive Action:discard(1),transparent(2)
            default:discard(1)
            FLAG=TRAP|EVLOG
            LOGITEM='%s'
            LOGSTATUS='%s'"
        ::= { provFilterL2ProtoEntry 6 }

    provFilterL2ProtoLldpAction OBJECT-TYPE
        SYNTAX       INTEGER { discard(1), transparent(2) }
        MAX-ACCESS   read-write
        STATUS       current
        DESCRIPTION
            "L2 Protocol Fream(LLDP) Recive Action:discard(1),transparent(2)
            default:discard(1)
            FLAG=TRAP|EVLOG
            LOGITEM='%s'
            LOGSTATUS='%s'"
        ::= { provFilterL2ProtoEntry 7 }

    provFilterL2ProtoOtherMacAction OBJECT-TYPE
        SYNTAX       INTEGER { discard(1), transparent(2) }
        MAX-ACCESS   read-write
        STATUS       current
        DESCRIPTION
            "L2 Protocol Fream(Other Mac) Recive
            Action:discard(1),transparent(2)
            default:discard(1)
            FLAG=TRAP|EVLOG
            LOGITEM='%s'
            LOGSTATUS='%s'"
        ::= { provFilterL2ProtoEntry 8 }

    provFilterL2ProtoGarpAction OBJECT-TYPE
        SYNTAX       INTEGER { discard(1), transparent(2) }
        MAX-ACCESS   read-write
        STATUS       current
        DESCRIPTION
            "L2 Protocol Fream(GARP) Recive Action:discard(1),transparent(2)
            default:discard(1)
            FLAG=TRAP|EVLOG
            LOGITEM='%s'
            LOGSTATUS='%s'"
        ::= { provFilterL2ProtoEntry 9 }

    provETHPortFwdTable OBJECT-TYPE
        SYNTAX       SEQUENCE OF ProvETHPortFwdEntry
        MAX-ACCESS   not-accessible
        STATUS       current
        DESCRIPTION  ""
        ::= { provFilterGroup 5 }

    provETHPortFwdEntry OBJECT-TYPE
        SYNTAX       ProvETHPortFwdEntry
        MAX-ACCESS   not-accessible
        STATUS       current
        DESCRIPTION  ""
        INDEX        { provETHPortFwdIfIndex }
        ::= { provETHPortFwdTable 1 }

    ProvETHPortFwdEntry ::= SEQUENCE {
        provETHPortFwdIfIndex    InterfaceIndex,
        provETHPortFwdNEAddress  IpAddress,
        provETHPortFwdIsolation  EnableDisableValue
    }

    provETHPortFwdIfIndex OBJECT-TYPE
        SYNTAX       InterfaceIndex
        MAX-ACCESS   not-accessible
        STATUS       current
        DESCRIPTION  "Index of this table."
        ::= { provETHPortFwdEntry 1 }

    provETHPortFwdNEAddress OBJECT-TYPE
        SYNTAX       IpAddress
        MAX-ACCESS   not-accessible
        STATUS       obsolete
        DESCRIPTION  "reserved."
        ::= { provETHPortFwdEntry 2 }

    provETHPortFwdIsolation OBJECT-TYPE
        SYNTAX       EnableDisableValue
        MAX-ACCESS   read-write
        STATUS       current
        DESCRIPTION  "Port Isolate"
        ::= { provETHPortFwdEntry 3 }

    provETHPortSetGroup OBJECT IDENTIFIER
        ::= { provisioningGroup 30 }

    provETHPortTable OBJECT-TYPE
        SYNTAX       SEQUENCE OF ProvETHPortEntry
        MAX-ACCESS   not-accessible
        STATUS       current
        DESCRIPTION  ""
        ::= { provETHPortSetGroup 1 }

    provETHPortEntry OBJECT-TYPE
        SYNTAX       ProvETHPortEntry
        MAX-ACCESS   not-accessible
        STATUS       current
        DESCRIPTION  ""
        INDEX        { provETHIfIndex }
        ::= { provETHPortTable 1 }

    ProvETHPortEntry ::= SEQUENCE {
        provETHIfIndex            InterfaceIndex,
        provETHPortNEAddress      IpAddress,
        provETHPortInterfaceType  INTEGER,
        provETHPortSpeed          INTEGER,
        provETHPortDuplex         INTEGER,
        provETHPortFlowControl    INTEGER,
        provETHPortMDIMDIX        INTEGER,
        provETHPortPortClose      INTEGER,
        provETHPortMirroring      INTEGER,
        provETHPortDirection      INTEGER,
        provETHPortName           DisplayString
    }

    provETHIfIndex OBJECT-TYPE
        SYNTAX       InterfaceIndex
        MAX-ACCESS   not-accessible
        STATUS       current
        DESCRIPTION  "Index of this table."
        ::= { provETHPortEntry 1 }

    provETHPortNEAddress OBJECT-TYPE
        SYNTAX       IpAddress
        MAX-ACCESS   not-accessible
        STATUS       current
        DESCRIPTION  "reserved."
        ::= { provETHPortEntry 2 }

    provETHPortInterfaceType OBJECT-TYPE
        SYNTAX       INTEGER { fiber(1), copper(2) }
        MAX-ACCESS   read-write
        STATUS       current
        DESCRIPTION
            "SFP type:fiber(1),copper(2)
            default:fiber(1)
            FLAG=TRAP|EVLOG
            LOGITEM='%s'
            LOGSTATUS='%s'"
        ::= { provETHPortEntry 3 }

    provETHPortSpeed OBJECT-TYPE
        SYNTAX       INTEGER { autonego(1), s10M(2), s100M(3), s1000M(4) }
        MAX-ACCESS   read-write
        STATUS       current
        DESCRIPTION
            "Setting this object to autonego will cause the interface which
            has the auto-negotiation signalling ability to be enabled.

            The other values represent the administratively-configured speed
            of the Medium."
        ::= { provETHPortEntry 4 }

    provETHPortDuplex OBJECT-TYPE
        SYNTAX       INTEGER { half(1), full(2) }
        MAX-ACCESS   read-write
        STATUS       current
        DESCRIPTION
            "This object represents the administratively-configured
            operation-mode of the Medium when auto-negotiation is disable."
        ::= { provETHPortEntry 5 }

    provETHPortFlowControl OBJECT-TYPE
        SYNTAX       INTEGER { disable(1), enable(2) }
        MAX-ACCESS   read-write
        STATUS       current
        DESCRIPTION
            "Flowcontrol setting:disable(1),enable(2)
            default:enable(2)
            FLAG=TRAP|EVLOG
            LOGITEM='%s'
            LOGSTATUS='%s'"
        ::= { provETHPortEntry 6 }

    provETHPortMDIMDIX OBJECT-TYPE
        SYNTAX       INTEGER { mdi(1), mdi-x(2) }
        MAX-ACCESS   read-write
        STATUS       current
        DESCRIPTION
            "MDI setting:mdi(1),mdi-x(2)
            default:mdi(1)


            FLAG=TRAP|EVLOG
            LOGITEM='%s'
            LOGSTATUS='%s'"
        ::= { provETHPortEntry 7 }

    provETHPortPortClose OBJECT-TYPE
        SYNTAX       INTEGER { disable(1), enable(2) }
        MAX-ACCESS   read-write
        STATUS       current
        DESCRIPTION  "The administrative state of the interface."
        ::= { provETHPortEntry 8 }

    provETHPortMirroring OBJECT-TYPE
        SYNTAX       INTEGER { none(1), monitoring(2), mirror(3) }
        MAX-ACCESS   read-write
        STATUS       current
        DESCRIPTION
            "Mirror port type:none(1),mirroring(2),mirror(3)
            default:none(1)
            FLAG=TRAP|EVLOG
            LOGITEM='%s'
            LOGSTATUS='%s'"
        ::= { provETHPortEntry 9 }

    provETHPortDirection OBJECT-TYPE
        SYNTAX       INTEGER { ingress(1), egress(2), both(3) }
        MAX-ACCESS   read-write
        STATUS       current
        DESCRIPTION
            "Mirror fream direction:ingress(1),egress(2),both(3)
            default:ingress(1)
            FLAG=TRAP|EVLOG
            LOGITEM='%s'
            LOGSTATUS='%s'"
        ::= { provETHPortEntry 10 }

    provETHPortName OBJECT-TYPE
        SYNTAX       DisplayString (SIZE(0..32))
        MAX-ACCESS   read-write
        STATUS       current
        DESCRIPTION
            "Port Name(0-32 characters)
            FLAG=TRAP|EVLOG
            LOGITEM='%s'
            LOGSTATUS='%s'"
        ::= { provETHPortEntry 11 }

    provETHPortMtuTable OBJECT-TYPE
        SYNTAX       SEQUENCE OF ProvETHPortMtuEntry
        MAX-ACCESS   not-accessible
        STATUS       current
        DESCRIPTION  ""
        ::= { provETHPortSetGroup 2 }

    provETHPortMtuEntry OBJECT-TYPE
        SYNTAX       ProvETHPortMtuEntry
        MAX-ACCESS   not-accessible
        STATUS       current
        DESCRIPTION  ""
        INDEX        { provETHPortMtuIndex }
        ::= { provETHPortMtuTable 1 }

    ProvETHPortMtuEntry ::= SEQUENCE {
        provETHPortMtuIndex            Integer32,
        provETHPortMtuNEAddress        IpAddress,
        provETHPortMtuFeMaxFrameSize   Integer32,
        provETHPortMtuGbeMaxFrameSize  Integer32
    }

    provETHPortMtuIndex OBJECT-TYPE
        SYNTAX       Integer32 (1..1)
        MAX-ACCESS   not-accessible
        STATUS       current
        DESCRIPTION  "Index of this table."
        ::= { provETHPortMtuEntry 1 }

    provETHPortMtuNEAddress OBJECT-TYPE
        SYNTAX       IpAddress
        MAX-ACCESS   not-accessible
        STATUS       current
        DESCRIPTION
            "IP Address
            FLAG=TRAP|EVLOG
            LOGITEM='%s'
            LOGSTATUS='%s'"
        ::= { provETHPortMtuEntry 2 }

    provETHPortMtuFeMaxFrameSize OBJECT-TYPE
        SYNTAX       Integer32 (64..2000)
        MAX-ACCESS   read-write
        STATUS       current
        DESCRIPTION
            "FE Port MTU size
            FLAG=TRAP|EVLOG
            LOGITEM='%s'
            LOGSTATUS='%s'"
        ::= { provETHPortMtuEntry 3 }

    provETHPortMtuGbeMaxFrameSize OBJECT-TYPE
        SYNTAX       Integer32 (64..9600)
        MAX-ACCESS   read-write
        STATUS       current
        DESCRIPTION
            "GbE/XGbE Port MTU size
            FLAG=TRAP|EVLOG
            LOGITEM='%s'
            LOGSTATUS='%s'"
        ::= { provETHPortMtuEntry 4 }

    provSyncETHSetGroup OBJECT IDENTIFIER
        ::= { provisioningGroup 31 }

    provSyncETHTable OBJECT-TYPE
        SYNTAX       SEQUENCE OF ProvSyncETHEntry
        MAX-ACCESS   not-accessible
        STATUS       current
        DESCRIPTION  ""
        ::= { provSyncETHSetGroup 1 }

    provSyncETHEntry OBJECT-TYPE
        SYNTAX       ProvSyncETHEntry
        MAX-ACCESS   not-accessible
        STATUS       current
        DESCRIPTION  ""
        INDEX        { provSyncETHIndex }
        ::= { provSyncETHTable 1 }

    ProvSyncETHEntry ::= SEQUENCE {
        provSyncETHIndex      Integer32,
        provSyncETHNEAddress  IpAddress,
        provSyncETHEnable     INTEGER
    }

    provSyncETHIndex OBJECT-TYPE
        SYNTAX       Integer32 (1..1)
        MAX-ACCESS   not-accessible
        STATUS       current
        DESCRIPTION  "Index of this table."
        ::= { provSyncETHEntry 1 }

    provSyncETHNEAddress OBJECT-TYPE
        SYNTAX       IpAddress
        MAX-ACCESS   not-accessible
        STATUS       current
        DESCRIPTION
            "IP Address
            FLAG=TRAP|EVLOG
            LOGITEM='%s'
            LOGSTATUS='%s'"
        ::= { provSyncETHEntry 2 }

    provSyncETHEnable OBJECT-TYPE
        SYNTAX       INTEGER { disable(1), enable(2) }
        MAX-ACCESS   read-write
        STATUS       current
        DESCRIPTION
            "SyncEther setting:disable(1),enable(2)
            default:disable(1)
            FLAG=TRAP|EVLOG
            LOGITEM='%s'
            LOGSTATUS='%s'"
        ::= { provSyncETHEntry 3 }

    provSyncETHPortTable OBJECT-TYPE
        SYNTAX       SEQUENCE OF ProvSyncETHPortEntry
        MAX-ACCESS   not-accessible
        STATUS       current
        DESCRIPTION  ""
        ::= { provSyncETHSetGroup 2 }

    provSyncETHPortEntry OBJECT-TYPE
        SYNTAX       ProvSyncETHPortEntry
        MAX-ACCESS   not-accessible
        STATUS       current
        DESCRIPTION  ""
        INDEX        { provSyncETHPortIfIndex }
        ::= { provSyncETHPortTable 1 }

    ProvSyncETHPortEntry ::= SEQUENCE {
        provSyncETHPortIfIndex    InterfaceIndex,
        provSyncETHPortNEAddress  IpAddress,
        provSyncETHPortEnable     INTEGER
    }

    provSyncETHPortIfIndex OBJECT-TYPE
        SYNTAX       InterfaceIndex
        MAX-ACCESS   not-accessible
        STATUS       current
        DESCRIPTION  "Index of this table."
        ::= { provSyncETHPortEntry 1 }

    provSyncETHPortNEAddress OBJECT-TYPE
        SYNTAX       IpAddress
        MAX-ACCESS   not-accessible
        STATUS       current
        DESCRIPTION  "reserved."
        ::= { provSyncETHPortEntry 2 }

    provSyncETHPortEnable OBJECT-TYPE
        SYNTAX       INTEGER {
                         invalid(0),
                         disable(1),
                         enable(2),
                         enableMaster(3),
                         enableSlave(4)
                     }
        MAX-ACCESS   read-write
        STATUS       current
        DESCRIPTION  "Sync ETHER Enable"
        DEFVAL       { disable }
        ::= { provSyncETHPortEntry 3 }

    provETHCardGroup OBJECT IDENTIFIER
        ::= { provisioningGroup 32 }

    provETHCardSetTable OBJECT-TYPE
        SYNTAX       SEQUENCE OF ProvETHCardSetEntry
        MAX-ACCESS   not-accessible
        STATUS       current
        DESCRIPTION  ""
        ::= { provETHCardGroup 1 }

    provETHCardSetEntry OBJECT-TYPE
        SYNTAX       ProvETHCardSetEntry
        MAX-ACCESS   not-accessible
        STATUS       current
        DESCRIPTION  ""
        INDEX        { provETHCardSetIndex }
        ::= { provETHCardSetTable 1 }

    ProvETHCardSetEntry ::= SEQUENCE {
        provETHCardSetIndex      Integer32,
        provETHCardSetNEAddress  IpAddress,
        ethCardLineClkSelect     Integer32
    }

    provETHCardSetIndex OBJECT-TYPE
        SYNTAX       Integer32
        MAX-ACCESS   not-accessible
        STATUS       current
        DESCRIPTION  "Index of this table."
        ::= { provETHCardSetEntry 1 }

    provETHCardSetNEAddress OBJECT-TYPE
        SYNTAX       IpAddress
        MAX-ACCESS   not-accessible
        STATUS       current
        DESCRIPTION  "reserved."
        ::= { provETHCardSetEntry 2 }

    ethCardLineClkSelect OBJECT-TYPE
        SYNTAX       Integer32 (1..4)
        MAX-ACCESS   read-write
        STATUS       current
        DESCRIPTION  "Clock Select"
        ::= { provETHCardSetEntry 3 }

    provProtectionGroup OBJECT IDENTIFIER
        ::= { provisioningGroup 33 }

    provStm1ApsTable OBJECT-TYPE
        SYNTAX       SEQUENCE OF ProvStm1ApsEntry
        MAX-ACCESS   not-accessible
        STATUS       current
        DESCRIPTION  ""
        ::= { provProtectionGroup 1 }

    provStm1ApsEntry OBJECT-TYPE
        SYNTAX       ProvStm1ApsEntry
        MAX-ACCESS   not-accessible
        STATUS       current
        DESCRIPTION  ""
        INDEX        { provStm1ApsIfIndex }
        ::= { provStm1ApsTable 1 }

    ProvStm1ApsEntry ::= SEQUENCE {
        provStm1ApsIfIndex    InterfaceIndex,
        provStm1ApsNEAddress  IpAddress,
        apsLockinSetting      UsedNotusedValue,
        apsDetectionTime      Integer32,
        apsDetectionCount     Integer32,
        apsClearLockinTime    Integer32
    }

    provStm1ApsIfIndex OBJECT-TYPE
        SYNTAX       InterfaceIndex
        MAX-ACCESS   not-accessible
        STATUS       current
        DESCRIPTION  "Index of this table."
        ::= { provStm1ApsEntry 1 }

    provStm1ApsNEAddress OBJECT-TYPE
        SYNTAX       IpAddress
        MAX-ACCESS   not-accessible
        STATUS       current
        DESCRIPTION  "reserved."
        ::= { provStm1ApsEntry 2 }

    apsLockinSetting OBJECT-TYPE
        SYNTAX       UsedNotusedValue
        MAX-ACCESS   read-write
        STATUS       current
        DESCRIPTION  "Lock-in Usage"
        ::= { provStm1ApsEntry 3 }

    apsDetectionTime OBJECT-TYPE
        SYNTAX       Integer32 (1..60)
        UNITS        "minutes"
        MAX-ACCESS   read-write
        STATUS       current
        DESCRIPTION  "Detection Time"
        ::= { provStm1ApsEntry 4 }

    apsDetectionCount OBJECT-TYPE
        SYNTAX       Integer32 (1..255)
        MAX-ACCESS   read-write
        STATUS       current
        DESCRIPTION  "Detection Count"
        ::= { provStm1ApsEntry 5 }

    apsClearLockinTime OBJECT-TYPE
        SYNTAX       Integer32 (1..288)
        UNITS        "10 minutes"
        MAX-ACCESS   read-write
        STATUS       current
        DESCRIPTION  "Clear Lock-in Timer"
        ::= { provStm1ApsEntry 6 }

    provCtrlGroup OBJECT IDENTIFIER
        ::= { provisioningGroup 34 }

    provCtrlExtTable OBJECT-TYPE
        SYNTAX       SEQUENCE OF ProvCtrlExtEntry
        MAX-ACCESS   not-accessible
        STATUS       current
        DESCRIPTION  ""
        ::= { provCtrlGroup 1 }

    provCtrlExtEntry OBJECT-TYPE
        SYNTAX       ProvCtrlExtEntry
        MAX-ACCESS   not-accessible
        STATUS       current
        DESCRIPTION  ""
        INDEX        { provCtrlExtIndex }
        ::= { provCtrlExtTable 1 }

    ProvCtrlExtEntry ::= SEQUENCE {
        provCtrlExtIndex                Integer32,
        provCtrlExtNEAddress            IpAddress,
        provCtrlExtOverTempAlarmRaise   Integer32,
        provCtrlExtOverTempAlarmClear   Integer32,
        provCtrlExtUnderTempAlarmRaise  Integer32,
        provCtrlExtUnderTempAlarmClear  Integer32
    }

    provCtrlExtIndex OBJECT-TYPE
        SYNTAX       Integer32 (1..1)
        MAX-ACCESS   not-accessible
        STATUS       current
        DESCRIPTION  "Index of this table."
        ::= { provCtrlExtEntry 1 }

    provCtrlExtNEAddress OBJECT-TYPE
        SYNTAX       IpAddress
        MAX-ACCESS   not-accessible
        STATUS       current
        DESCRIPTION  "reserved."
        ::= { provCtrlExtEntry 2 }

    provCtrlExtOverTempAlarmRaise OBJECT-TYPE
        SYNTAX       Integer32
        UNITS        "0.1 degree"
        MAX-ACCESS   read-write
        STATUS       current
        DESCRIPTION  "Upper Limit Over Temperature of Alarm Raise"
        ::= { provCtrlExtEntry 3 }

    provCtrlExtOverTempAlarmClear OBJECT-TYPE
        SYNTAX       Integer32
        UNITS        "0.1 degree"
        MAX-ACCESS   read-write
        STATUS       current
        DESCRIPTION  "Upper Limit Over Temperature of Alarm Clear"
        ::= { provCtrlExtEntry 4 }

    provCtrlExtUnderTempAlarmRaise OBJECT-TYPE
        SYNTAX       Integer32
        UNITS        "0.1 degree"
        MAX-ACCESS   read-write
        STATUS       current
        DESCRIPTION  "Lower Limit Under Temperature of Alarm Raise"
        ::= { provCtrlExtEntry 5 }

    provCtrlExtUnderTempAlarmClear OBJECT-TYPE
        SYNTAX       Integer32
        UNITS        "0.1 degree"
        MAX-ACCESS   read-write
        STATUS       current
        DESCRIPTION  "Lower Limit Under Temperature of Alarm Clear"
        ::= { provCtrlExtEntry 6 }

    provLicenseGroup OBJECT IDENTIFIER
        ::= { provisioningGroup 45 }

    provLicenseAlarmTable OBJECT-TYPE
        SYNTAX       SEQUENCE OF ProvLicenseAlarmEntry
        MAX-ACCESS   not-accessible
        STATUS       current
        DESCRIPTION
            "Configure License Alarm Detection Delay.
            This table is only for internal use."
        ::= { provLicenseGroup 1 }

    provLicenseAlarmEntry OBJECT-TYPE
        SYNTAX       ProvLicenseAlarmEntry
        MAX-ACCESS   not-accessible
        STATUS       current
        DESCRIPTION  ""
        INDEX        { provLicenseAlarmIndex }
        ::= { provLicenseAlarmTable 1 }

    ProvLicenseAlarmEntry ::= SEQUENCE {
        provLicenseAlarmIndex           Integer32,
        provLicenseAlarmNEAddress       IpAddress,
        provLicenseAlarmDetectionDelay  Integer32
    }

    provLicenseAlarmIndex OBJECT-TYPE
        SYNTAX       Integer32 (1..1)
        MAX-ACCESS   not-accessible
        STATUS       current
        DESCRIPTION  "Index of this table."
        ::= { provLicenseAlarmEntry 1 }

    provLicenseAlarmNEAddress OBJECT-TYPE
        SYNTAX       IpAddress
        MAX-ACCESS   not-accessible
        STATUS       current
        DESCRIPTION  "reserved."
        ::= { provLicenseAlarmEntry 2 }

    provLicenseAlarmDetectionDelay OBJECT-TYPE
        SYNTAX       Integer32 (0..5)
        UNITS        "minutes"
        MAX-ACCESS   read-write
        STATUS       current
        DESCRIPTION  "License Alarm Detection Delay."
        DEFVAL       { 3 }
        ::= { provLicenseAlarmEntry 3 }

-----------------------------------------------
-- maintenanceGroup Definitions
-----------------------------------------------

    maintCommonGroup OBJECT IDENTIFIER
        ::= { maintenanceGroup 1 }

    maintCommonTable OBJECT-TYPE
        SYNTAX       SEQUENCE OF MaintCommonEntry
        MAX-ACCESS   not-accessible
        STATUS       current
        DESCRIPTION  ""
        ::= { maintCommonGroup 1 }

    maintCommonEntry OBJECT-TYPE
        SYNTAX       MaintCommonEntry
        MAX-ACCESS   not-accessible
        STATUS       current
        DESCRIPTION  ""
        INDEX        { maintCommonIndex }
        ::= { maintCommonTable 1 }

    MaintCommonEntry ::= SEQUENCE {
        maintCommonIndex      Integer32,
        maintCommonNEAddress  IpAddress,
        maintMode             OffOnValue,
        maintLANDeviceReset   INTEGER,
        maintShipment         INTEGER
    }

    maintCommonIndex OBJECT-TYPE
        SYNTAX       Integer32 (1..1)
        MAX-ACCESS   not-accessible
        STATUS       current
        DESCRIPTION  "Index of this table."
        ::= { maintCommonEntry 1 }

    maintCommonNEAddress OBJECT-TYPE
        SYNTAX       IpAddress
        MAX-ACCESS   not-accessible
        STATUS       current
        DESCRIPTION  "reserved."
        ::= { maintCommonEntry 2 }

    maintMode OBJECT-TYPE
        SYNTAX       OffOnValue
        MAX-ACCESS   read-write
        STATUS       current
        DESCRIPTION
            "FLAG=TRAP|EVLOG
            LOGITEM='MAINTENANCE'
            LOGSTATUS='OFF(1),ON(2)'
            TRAP=controlEvent"
        ::= { maintCommonEntry 3 }

    maintLANDeviceReset OBJECT-TYPE
        SYNTAX       INTEGER { invalid(0), reset(1) }
        MAX-ACCESS   read-write
        STATUS       current
        DESCRIPTION
            "FLAG=TRAP|EVLOG
            LOGITEM='LAN DEVICE RESET'
            LOGSTATUS='NOT SELECTED(1),RESET(2)'
            TRAP=controlEvent"
        ::= { maintCommonEntry 4 }

    maintShipment OBJECT-TYPE
        SYNTAX       INTEGER {
                         invalid(0),
                         rfFrequencyClear(1),
                         provisioningClear(2),
                         allClearWoSoftkeyAndConfig(3),
                         allClearWoSoftkey(4),
                         allClear(5)
                     }
        MAX-ACCESS   read-write
        STATUS       current
        DESCRIPTION
            "This object provides function for restoring factory defaults.
            This object behaves as 'writeOnly', and the returned value is not
            guaranteed.
            'provisioningClear' will clear provisioning data without softkey,
            user/network config, and internal data."
        ::= { maintCommonEntry 5 }

    maintCardTable OBJECT-TYPE
        SYNTAX       SEQUENCE OF MaintCardEntry
        MAX-ACCESS   not-accessible
        STATUS       current
        DESCRIPTION  ""
        ::= { maintCommonGroup 2 }

    maintCardEntry OBJECT-TYPE
        SYNTAX       MaintCardEntry
        MAX-ACCESS   not-accessible
        STATUS       current
        DESCRIPTION  ""
        INDEX        { maintCardIndex }
        ::= { maintCardTable 1 }

    MaintCardEntry ::= SEQUENCE {
        maintCardIndex      Integer32,
        maintCardNEAddress  IpAddress,
        maintCardReset      INTEGER
    }

    maintCardIndex OBJECT-TYPE
        SYNTAX       Integer32
        MAX-ACCESS   not-accessible
        STATUS       current
        DESCRIPTION  "Index of this table."
        ::= { maintCardEntry 1 }

    maintCardNEAddress OBJECT-TYPE
        SYNTAX       IpAddress
        MAX-ACCESS   not-accessible
        STATUS       current
        DESCRIPTION  "reserved."
        ::= { maintCardEntry 2 }

    maintCardReset OBJECT-TYPE
        SYNTAX       INTEGER { invalid(0), reset(1) }
        MAX-ACCESS   read-write
        STATUS       current
        DESCRIPTION
            "Card Reset Control.
            When set 'reset' to this object, the card will reset itself. if
            the card has firmware, the card can accept the 'revert' request,
            and if set, the card will restart with the firmware installed in
            other side."
        ::= { maintCardEntry 3 }

    maintOduResetTable OBJECT-TYPE
        SYNTAX       SEQUENCE OF MaintOduResetEntry
        MAX-ACCESS   not-accessible
        STATUS       current
        DESCRIPTION  ""
        ::= { maintCommonGroup 3 }

    maintOduResetEntry OBJECT-TYPE
        SYNTAX       MaintOduResetEntry
        MAX-ACCESS   not-accessible
        STATUS       current
        DESCRIPTION  ""
        INDEX        { maintOduResetIfIndex }
        ::= { maintOduResetTable 1 }

    MaintOduResetEntry ::= SEQUENCE {
        maintOduResetIfIndex    InterfaceIndex,
        maintOduResetNEAddress  IpAddress,
        maintOduReset           INTEGER
    }

    maintOduResetIfIndex OBJECT-TYPE
        SYNTAX       InterfaceIndex
        MAX-ACCESS   not-accessible
        STATUS       current
        DESCRIPTION  "Index of this table."
        ::= { maintOduResetEntry 1 }

    maintOduResetNEAddress OBJECT-TYPE
        SYNTAX       IpAddress
        MAX-ACCESS   not-accessible
        STATUS       current
        DESCRIPTION  "reserved."
        ::= { maintOduResetEntry 2 }

    maintOduReset OBJECT-TYPE
        SYNTAX       INTEGER {
                         invalid(0),
                         resetNormal(1),
                         resetRevert(2),
                         resetNone(3)
                     }
        MAX-ACCESS   read-write
        STATUS       current
        DESCRIPTION
            "FLAG=TRAP|EVLOG
            LOGITEM='MAINTENANCE'
            LOGSTATUS='OFF(1),ON(2)'
            TRAP=controlEvent"
        ::= { maintOduResetEntry 3 }

    maintIduResetTable OBJECT-TYPE
        SYNTAX       SEQUENCE OF MaintIduResetEntry
        MAX-ACCESS   not-accessible
        STATUS       current
        DESCRIPTION  ""
        ::= { maintCommonGroup 4 }

    maintIduResetEntry OBJECT-TYPE
        SYNTAX       MaintIduResetEntry
        MAX-ACCESS   not-accessible
        STATUS       current
        DESCRIPTION  ""
        INDEX        { maintIduResetIndex }
        ::= { maintIduResetTable 1 }

    MaintIduResetEntry ::= SEQUENCE {
        maintIduResetIndex      Integer32,
        maintIduResetNEAddress  IpAddress,
        maintIduReset           INTEGER
    }

    maintIduResetIndex OBJECT-TYPE
        SYNTAX       Integer32
        MAX-ACCESS   not-accessible
        STATUS       current
        DESCRIPTION  "Index of this table."
        ::= { maintIduResetEntry 1 }

    maintIduResetNEAddress OBJECT-TYPE
        SYNTAX       IpAddress
        MAX-ACCESS   not-accessible
        STATUS       current
        DESCRIPTION  "reserved."
        ::= { maintIduResetEntry 2 }

    maintIduReset OBJECT-TYPE
        SYNTAX       INTEGER {
                         invalid(0),
                         resetNormal(1),
                         resetRevert(2),
                         resetNone(3)
                     }
        MAX-ACCESS   read-write
        STATUS       current
        DESCRIPTION
            "FLAG=TRAP|EVLOG
            LOGITEM='MAINTENANCE'
            LOGSTATUS='OFF(1),ON(2)'
            TRAP=controlEvent"
        ::= { maintIduResetEntry 3 }

    maintModemTable OBJECT-TYPE
        SYNTAX       SEQUENCE OF MaintModemEntry
        MAX-ACCESS   not-accessible
        STATUS       current
        DESCRIPTION  ""
        ::= { maintenanceGroup 2 }

    maintModemEntry OBJECT-TYPE
        SYNTAX       MaintModemEntry
        MAX-ACCESS   not-accessible
        STATUS       current
        DESCRIPTION  ""
        INDEX        { maintModemIfIndex }
        ::= { maintModemTable 1 }

    MaintModemEntry ::= SEQUENCE {
        maintModemIfIndex                    InterfaceIndex,
        maintModemNEAddress                  IpAddress,
        maintModemATPCManualControl          INTEGER,
        maintModemATPCManualContPower        Integer32,
        maintModemTxMuteControl              OffOnValue,
        maintModemTxMuteContReleaseTime      Integer32,
        maintModemCW                         OffOnValue,
        maintModemCWReleaseTime              Integer32,
        maintModemIFLoopback                 OffOnValue,
        maintModemIFLoopbackReleaseTime      Integer32,
        maintModemRFLoopback                 OffOnValue,
        maintModemRFLoopbackReleaseTime      Integer32,
        maintModemForcedXPICCont             INTEGER,
        maintModemTxModulationManualControl  INTEGER,
        maintModemRFSubBandSelect            DisplayString,
        maintModemL2Loopback1                OffOnValue,
        maintModemL2Loopback1ReleaseTime     Integer32,
        maintModemL2Loopback2                OffOnValue,
        maintModemL2Loopback2ReleaseTime     Integer32
    }

    maintModemIfIndex OBJECT-TYPE
        SYNTAX       InterfaceIndex
        MAX-ACCESS   not-accessible
        STATUS       current
        DESCRIPTION  "Index of this table."
        ::= { maintModemEntry 1 }

    maintModemNEAddress OBJECT-TYPE
        SYNTAX       IpAddress
        MAX-ACCESS   not-accessible
        STATUS       current
        DESCRIPTION  "reserved."
        ::= { maintModemEntry 2 }

    maintModemATPCManualControl OBJECT-TYPE
        SYNTAX       INTEGER { invalid(0), auto(1), manual(2) }
        MAX-ACCESS   read-write
        STATUS       current
        DESCRIPTION
            "FLAG=TRAP|EVLOG
            LOGITEM='ATPC MANUAL CONTROL'
            LOGSTATUS='AUTO(1),MANUAL(2)'
            TRAP=controlEvent"
        ::= { maintModemEntry 3 }

    maintModemATPCManualContPower OBJECT-TYPE
        SYNTAX       Integer32 (-380..400)
        MAX-ACCESS   read-write
        STATUS       current
        DESCRIPTION
            "FLAG=TRAP|EVLOG
            LOGITEM='ATPC MANUAL POWER[dB]'
            LOGSTATUS='%d'
            TRAP=controlEvent"
        ::= { maintModemEntry 4 }

    maintModemTxMuteControl OBJECT-TYPE
        SYNTAX       OffOnValue
        MAX-ACCESS   read-write
        STATUS       current
        DESCRIPTION
            "FLAG=TRAP|EVLOG
            LOGITEM='TX MUTE CONTROL'
            LOGSTATUS='OFF(1),ON(2)'
            TRAP=controlEvent"
        ::= { maintModemEntry 5 }

    maintModemTxMuteContReleaseTime OBJECT-TYPE
        SYNTAX       Integer32
        MAX-ACCESS   read-write
        STATUS       current
        DESCRIPTION
            "FLAG=TRAP|EVLOG
            LOGITEM='TX MUTE OFF TIMER'
            LOGSTATUS='%d'
            TRAP=controlEvent"
        ::= { maintModemEntry 6 }

    maintModemCW OBJECT-TYPE
        SYNTAX       OffOnValue
        MAX-ACCESS   read-write
        STATUS       current
        DESCRIPTION
            "FLAG=TRAP|EVLOG
            LOGITEM='CW CONTROL'
            LOGSTATUS='OFF(1),ON(2)'
            TRAP=controlEvent"
        ::= { maintModemEntry 7 }

    maintModemCWReleaseTime OBJECT-TYPE
        SYNTAX       Integer32
        MAX-ACCESS   read-write
        STATUS       current
        DESCRIPTION
            "FLAG=TRAP|EVLOG
            LOGITEM='TX MUTE OFF TIMER'
            LOGSTATUS='%d'
            TRAP=controlEvent"
        ::= { maintModemEntry 8 }

    maintModemIFLoopback OBJECT-TYPE
        SYNTAX       OffOnValue
        MAX-ACCESS   read-write
        STATUS       current
        DESCRIPTION
            "FLAG=TRAP|EVLOG
            LOGITEM='IF LOOPBACK'
            LOGSTATUS='OFF(1),ON(2)'
            TRAP=controlEvent"
        ::= { maintModemEntry 9 }

    maintModemIFLoopbackReleaseTime OBJECT-TYPE
        SYNTAX       Integer32
        MAX-ACCESS   read-write
        STATUS       current
        DESCRIPTION
            "FLAG=TRAP|EVLOG
            LOGITEM='TX MUTE OFF TIMER'
            LOGSTATUS='%d'
            TRAP=controlEvent"
        ::= { maintModemEntry 10 }

    maintModemRFLoopback OBJECT-TYPE
        SYNTAX       OffOnValue
        MAX-ACCESS   read-write
        STATUS       current
        DESCRIPTION
            "FLAG=TRAP|EVLOG
            LOGITEM='RF LOOPBACK'
            LOGSTATUS='OFF(1),ON(2)'
            TRAP=controlEvent"
        ::= { maintModemEntry 11 }

    maintModemRFLoopbackReleaseTime OBJECT-TYPE
        SYNTAX       Integer32
        MAX-ACCESS   read-write
        STATUS       current
        DESCRIPTION
            "FLAG=TRAP|EVLOG
            LOGITEM='TX MUTE OFF TIMER'
            LOGSTATUS='%d'
            TRAP=controlEvent"
        ::= { maintModemEntry 12 }

    maintModemForcedXPICCont OBJECT-TYPE
        SYNTAX       INTEGER { invalid(0), auto(1), forcedReset(2) }
        MAX-ACCESS   read-write
        STATUS       current
        DESCRIPTION
            "FLAG=TRAP|EVLOG
            LOGITEM='XPIC CONTROL'
            LOGSTATUS='AUTO(1),FORCED RESET(2)'
            TRAP=controlEvent"
        ::= { maintModemEntry 13 }

    maintModemTxModulationManualControl OBJECT-TYPE
        SYNTAX       INTEGER {
                         invalid(0),
                         auto(1),
                         qpsk(2),
                         qam16(3),
                         qam32(4),
                         qam64(5),
                         qam128(6),
                         qam256(7),
                         qam512(8),
                         qam1024(9),
                         qam2048(10)
                     }
        MAX-ACCESS   read-write
        STATUS       current
        DESCRIPTION
            "This object controls Tx Modulation.
            The value 'psk8' is available only for the iPASOLINK EX. This
            value is valid only when esModemChSpacing is 'cs500m'."
        ::= { maintModemEntry 14 }

    maintModemRFSubBandSelect OBJECT-TYPE
        SYNTAX       DisplayString (SIZE(1..1))
        MAX-ACCESS   read-write
        STATUS       current
        DESCRIPTION
            "FLAG=TRAP|EVLOG
            LOGITEM='RF SUB BAND SELECT'
            LOGSTATUS='A(65),B(66),C(67),D(68),E(69),F(70),G(71),H(72),J(74),K(75),L(76),M(77),N(78),P(80),R(82),X(88)'
            TRAP=controlEvent"
        ::= { maintModemEntry 15 }

    maintModemL2Loopback1 OBJECT-TYPE
        SYNTAX       OffOnValue
        MAX-ACCESS   read-write
        STATUS       current
        DESCRIPTION
            "This object controls Loopback function for L2 frames.
            When the object is set to 'On', the L2 frames received from the
            Radio Link are loopbacked."
        ::= { maintModemEntry 16 }

    maintModemL2Loopback1ReleaseTime OBJECT-TYPE
        SYNTAX       Integer32
        UNITS        "seconds"
        MAX-ACCESS   read-write
        STATUS       current
        DESCRIPTION
            "This object controls Release Time for L2 loopback1 function.
            L2 loopback function will be released automatically when the
            timer which is configured by this object is expired."
        ::= { maintModemEntry 17 }

    maintModemL2Loopback2 OBJECT-TYPE
        SYNTAX       OffOnValue
        MAX-ACCESS   read-write
        STATUS       current
        DESCRIPTION
            "This object controls Loopback function for L2 frames.
            When the object is set to 'On', the L2 frames transmitted to the
            Radio Link are loopbacked."
        ::= { maintModemEntry 18 }

    maintModemL2Loopback2ReleaseTime OBJECT-TYPE
        SYNTAX       Integer32
        UNITS        "seconds"
        MAX-ACCESS   read-write
        STATUS       current
        DESCRIPTION
            "This object controls Release Time for L2 loopback2 function.
            L2 loopback function will be released automatically when the
            timer which is configured by this object is expired."
        ::= { maintModemEntry 19 }

    maintSwGroupTable OBJECT-TYPE
        SYNTAX       SEQUENCE OF MaintSwGroupEntry
        MAX-ACCESS   not-accessible
        STATUS       current
        DESCRIPTION  ""
        ::= { maintenanceGroup 3 }

    maintSwGroupEntry OBJECT-TYPE
        SYNTAX       MaintSwGroupEntry
        MAX-ACCESS   not-accessible
        STATUS       current
        DESCRIPTION  ""
        INDEX        { maintSwGroupIfIndex }
        ::= { maintSwGroupTable 1 }

    MaintSwGroupEntry ::= SEQUENCE {
        maintSwGroupIfIndex    InterfaceIndex,
        maintSwGroupNEAddress  IpAddress,
        maintTxSWControl       INTEGER,
        maintTxSWMode          INTEGER,
        maintRxSWControl       INTEGER,
        maintRxSWMode          INTEGER,
        maintDADEAdjust        INTEGER,
        maintDADEAdjustEnable  OffOnValue
    }

    maintSwGroupIfIndex OBJECT-TYPE
        SYNTAX       InterfaceIndex
        MAX-ACCESS   not-accessible
        STATUS       current
        DESCRIPTION  "Index of this table."
        ::= { maintSwGroupEntry 1 }

    maintSwGroupNEAddress OBJECT-TYPE
        SYNTAX       IpAddress
        MAX-ACCESS   not-accessible
        STATUS       current
        DESCRIPTION  "reserved."
        ::= { maintSwGroupEntry 2 }

    maintTxSWControl OBJECT-TYPE
        SYNTAX       INTEGER { invalid(0), clear(1), forcedNo1(2), forcedNo2(3) }
        MAX-ACCESS   read-write
        STATUS       current
        DESCRIPTION  "TX SW Manual Control"
        ::= { maintSwGroupEntry 3 }

    maintTxSWMode OBJECT-TYPE
        SYNTAX       INTEGER {
                         invalid(0),
                         clear(1),
                         clear2(2),
                         forcedNo1(3),
                         forcedNo2(4)
                     }
        MAX-ACCESS   read-only
        STATUS       current
        DESCRIPTION  "TX SW Manual Control Status"
        ::= { maintSwGroupEntry 4 }

    maintRxSWControl OBJECT-TYPE
        SYNTAX       INTEGER {
                         invalid(0),
                         clear(1),
                         manualNo1(2),
                         manualNo2(3),
                         forcedNo1(4),
                         forcedNo2(5)
                     }
        MAX-ACCESS   read-write
        STATUS       current
        DESCRIPTION  "RX SW Manual Control"
        ::= { maintSwGroupEntry 5 }

    maintRxSWMode OBJECT-TYPE
        SYNTAX       INTEGER {
                         invalid(0),
                         clear(1),
                         clear2(2),
                         manualNo1(3),
                         manualNo2(4),
                         forcedNo1(5),
                         forcedNo2(6)
                     }
        MAX-ACCESS   read-only
        STATUS       current
        DESCRIPTION  "RX SW Manual Control Status"
        ::= { maintSwGroupEntry 6 }

    maintDADEAdjust OBJECT-TYPE
        SYNTAX       INTEGER { invalid(0), dade(1), offsetDade(2), dadeOff(3) }
        MAX-ACCESS   read-write
        STATUS       current
        DESCRIPTION
            "FLAG=TRAP|EVLOG
            LOGITEM='DADE ADJUST'
            LOGSTATUS='DADE(1),OFFSET DADE(2),DADE OFF(3)'
            TRAP=controlEvent"
        ::= { maintSwGroupEntry 7 }

    maintDADEAdjustEnable OBJECT-TYPE
        SYNTAX       OffOnValue
        MAX-ACCESS   read-only
        STATUS       current
        DESCRIPTION
            "FLAG=TRAP|EVLOG
            LOGITEM='DADE ADJUST ENABLE'
            LOGSTATUS='OFF(1),ON(EXECUTING)(2)'
            TRAP=statusChange"
        ::= { maintSwGroupEntry 8 }

    maintE1SystemTable OBJECT-TYPE
        SYNTAX       SEQUENCE OF MaintE1SystemEntry
        MAX-ACCESS   not-accessible
        STATUS       current
        DESCRIPTION  ""
        ::= { maintenanceGroup 4 }

    maintE1SystemEntry OBJECT-TYPE
        SYNTAX       MaintE1SystemEntry
        MAX-ACCESS   not-accessible
        STATUS       current
        DESCRIPTION  ""
        INDEX        { maintE1SystemIfIndex }
        ::= { maintE1SystemTable 1 }

    MaintE1SystemEntry ::= SEQUENCE {
        maintE1SystemIfIndex    InterfaceIndex,
        maintE1SystemNEAddress  IpAddress,
        maintE1ChLoopback1      OffOnValue,
        maintE1ChLoopback2      OffOnValue
    }

    maintE1SystemIfIndex OBJECT-TYPE
        SYNTAX       InterfaceIndex
        MAX-ACCESS   not-accessible
        STATUS       current
        DESCRIPTION  "Index of this table."
        ::= { maintE1SystemEntry 1 }

    maintE1SystemNEAddress OBJECT-TYPE
        SYNTAX       IpAddress
        MAX-ACCESS   not-accessible
        STATUS       current
        DESCRIPTION  "reserved."
        ::= { maintE1SystemEntry 2 }

    maintE1ChLoopback1 OBJECT-TYPE
        SYNTAX       OffOnValue
        MAX-ACCESS   read-write
        STATUS       current
        DESCRIPTION
            "FLAG=TRAP|EVLOG
            LOGITEM='E1 CH LOOPBACK1'
            LOGSTATUS='OFF(1),ON(2)'
            TRAP=controlEvent"
        ::= { maintE1SystemEntry 3 }

    maintE1ChLoopback2 OBJECT-TYPE
        SYNTAX       OffOnValue
        MAX-ACCESS   read-write
        STATUS       current
        DESCRIPTION
            "FLAG=TRAP|EVLOG
            LOGITEM='E1 CH LOOPBACK2'
            LOGSTATUS='OFF(1),ON(2)'
            TRAP=controlEvent"
        ::= { maintE1SystemEntry 4 }

    maintStm1Group OBJECT IDENTIFIER
        ::= { maintenanceGroup 5 }

    maintStm1PortTable OBJECT-TYPE
        SYNTAX       SEQUENCE OF MaintStm1PortEntry
        MAX-ACCESS   not-accessible
        STATUS       current
        DESCRIPTION  ""
        ::= { maintStm1Group 1 }

    maintStm1PortEntry OBJECT-TYPE
        SYNTAX       MaintStm1PortEntry
        MAX-ACCESS   not-accessible
        STATUS       current
        DESCRIPTION  ""
        INDEX        { maintStm1PortIfIndex }
        ::= { maintStm1PortTable 1 }

    MaintStm1PortEntry ::= SEQUENCE {
        maintStm1PortIfIndex        InterfaceIndex,
        maintStm1PortNEAddress      IpAddress,
        maintStm1ChLoopback1        OffOnValue,
        maintStm1ChLoopback2        OffOnValue,
        maintStm1ForcedLSCont       OffOnValue,
        maintStm1ALSMuanualRestart  INTEGER
    }

    maintStm1PortIfIndex OBJECT-TYPE
        SYNTAX       InterfaceIndex
        MAX-ACCESS   not-accessible
        STATUS       current
        DESCRIPTION  "Index of this table."
        ::= { maintStm1PortEntry 1 }

    maintStm1PortNEAddress OBJECT-TYPE
        SYNTAX       IpAddress
        MAX-ACCESS   not-accessible
        STATUS       current
        DESCRIPTION  "reserved."
        ::= { maintStm1PortEntry 2 }

    maintStm1ChLoopback1 OBJECT-TYPE
        SYNTAX       OffOnValue
        MAX-ACCESS   read-write
        STATUS       current
        DESCRIPTION
            "FLAG=TRAP|EVLOG
            LOGSTATUS='OFF(1),ON(2)'
            TRAP=controlEvent"
        ::= { maintStm1PortEntry 3 }

    maintStm1ChLoopback2 OBJECT-TYPE
        SYNTAX       OffOnValue
        MAX-ACCESS   read-write
        STATUS       current
        DESCRIPTION
            "FLAG=TRAP|EVLOG
            LOGSTATUS='OFF(1),ON(2)'
            TRAP=controlEvent"
        ::= { maintStm1PortEntry 4 }

    maintStm1ForcedLSCont OBJECT-TYPE
        SYNTAX       OffOnValue
        MAX-ACCESS   read-write
        STATUS       current
        DESCRIPTION
            "FLAG=TRAP|EVLOG
            LOGSTATUS='OFF(1),ON(2)'
            TRAP=controlEvent"
        ::= { maintStm1PortEntry 5 }

    maintStm1ALSMuanualRestart OBJECT-TYPE
        SYNTAX       INTEGER { invalid(0), off(1), shortOn(2), longOn(3) }
        MAX-ACCESS   read-write
        STATUS       current
        DESCRIPTION
            "FLAG=TRAP|EVLOG
            LOGSTATUS='OFF(1),ON(2)'
            TRAP=controlEvent"
        ::= { maintStm1PortEntry 6 }

    maintTimingSourceTable OBJECT-TYPE
        SYNTAX       SEQUENCE OF MaintTimingSourceEntry
        MAX-ACCESS   not-accessible
        STATUS       current
        DESCRIPTION  ""
        ::= { maintenanceGroup 6 }

    maintTimingSourceEntry OBJECT-TYPE
        SYNTAX       MaintTimingSourceEntry
        MAX-ACCESS   not-accessible
        STATUS       current
        DESCRIPTION  ""
        INDEX        { maintTimingSourceIndex }
        ::= { maintTimingSourceTable 1 }

    MaintTimingSourceEntry ::= SEQUENCE {
        maintTimingSourceIndex      INTEGER,
        maintTimingSourceNEAddress  IpAddress,
        maintTimingSourceSwControl  INTEGER,
        maintTimingSourceLockOut    OffOnValue
    }

    maintTimingSourceIndex OBJECT-TYPE
        SYNTAX       INTEGER {
                         timingSource1(1),
                         timingSource2(2),
                         timingSource3(3)
                     }
        MAX-ACCESS   not-accessible
        STATUS       current
        DESCRIPTION  "Index of this table."
        ::= { maintTimingSourceEntry 1 }

    maintTimingSourceNEAddress OBJECT-TYPE
        SYNTAX       IpAddress
        MAX-ACCESS   not-accessible
        STATUS       current
        DESCRIPTION  "reserved."
        ::= { maintTimingSourceEntry 2 }

    maintTimingSourceSwControl OBJECT-TYPE
        SYNTAX       INTEGER { invalid(0), normal(1), manualSw(2), forcedSw(3) }
        MAX-ACCESS   read-write
        STATUS       current
        DESCRIPTION
            "FLAG=TRAP|EVLOG
            LOGITEM='TIMING SOURCE SW CONTROL'
            LOGSTATUS='NORMAL(1),MANUAL SW(2),FORCED SW(3)'
            TRAP=controlEvent"
        ::= { maintTimingSourceEntry 3 }

    maintTimingSourceLockOut OBJECT-TYPE
        SYNTAX       OffOnValue
        MAX-ACCESS   read-write
        STATUS       current
        DESCRIPTION
            "FLAG=TRAP|EVLOG
            LOGSTATUS='OFF(1),ON(2)'
            TRAP=controlEvent"
        ::= { maintTimingSourceEntry 4 }

    maintSncpSwTable OBJECT-TYPE
        SYNTAX       SEQUENCE OF MaintSncpSwEntry
        MAX-ACCESS   not-accessible
        STATUS       current
        DESCRIPTION  ""
        ::= { maintenanceGroup 8 }

    maintSncpSwEntry OBJECT-TYPE
        SYNTAX       MaintSncpSwEntry
        MAX-ACCESS   not-accessible
        STATUS       current
        DESCRIPTION  ""
        INDEX        { maintSncpSwIndex }
        ::= { maintSncpSwTable 1 }

    MaintSncpSwEntry ::= SEQUENCE {
        maintSncpSwIndex      Integer32,
        maintSncpSwNEAddress  IpAddress,
        maintSncpSwControl    INTEGER,
        maintSncpSwMode       INTEGER
    }

    maintSncpSwIndex OBJECT-TYPE
        SYNTAX       Integer32 (1..2352)
        MAX-ACCESS   not-accessible
        STATUS       current
        DESCRIPTION  "Index of this table."
        ::= { maintSncpSwEntry 1 }

    maintSncpSwNEAddress OBJECT-TYPE
        SYNTAX       IpAddress
        MAX-ACCESS   not-accessible
        STATUS       current
        DESCRIPTION  "reserved."
        ::= { maintSncpSwEntry 2 }

    maintSncpSwControl OBJECT-TYPE
        SYNTAX       INTEGER {
                         invalid(0),
                         clear(1),
                         forcedSwToProtection(2),
                         forcedSwToWork(3),
                         manualSwToProtection(4),
                         manualSwToWork(5)
                     }
        MAX-ACCESS   read-write
        STATUS       current
        DESCRIPTION  "SNCP Manual SW Control"
        ::= { maintSncpSwEntry 3 }

    maintSncpSwMode OBJECT-TYPE
        SYNTAX       INTEGER {
                         invalid(0),
                         clear(1),
                         clear2(2),
                         forcedSwToProtection(3),
                         forcedSwToWork(4),
                         manualSwToProtection(5),
                         manualSwToWork(6)
                     }
        MAX-ACCESS   read-only
        STATUS       current
        DESCRIPTION  "SNCP Manual SW Control Status"
        ::= { maintSncpSwEntry 4 }

    maintETHGroup OBJECT IDENTIFIER
        ::= { maintenanceGroup 9 }

    maintFdbGroup OBJECT IDENTIFIER
        ::= { maintETHGroup 1 }

    maintFdbTable OBJECT-TYPE
        SYNTAX       SEQUENCE OF MaintFdbEntry
        MAX-ACCESS   not-accessible
        STATUS       current
        DESCRIPTION
            "This table contains the maintenance functions for FDB entries."
        ::= { maintFdbGroup 1 }

    maintFdbEntry OBJECT-TYPE
        SYNTAX       MaintFdbEntry
        MAX-ACCESS   not-accessible
        STATUS       current
        DESCRIPTION  ""
        INDEX        { maintFdbIndex }
        ::= { maintFdbTable 1 }

    MaintFdbEntry ::= SEQUENCE {
        maintFdbIndex                     Integer32,
        maintFdbNEAddress                 IpAddress,
        maintFdbTableClearAll             OffOnValue,
        maintFdbTableClearPort            InterfaceIndex,
        maintFdbTableClearVlan            Integer32,
        maintFdbGetLearningInfoExecute    OffOnValue,
        maintFdbClearLearningInfoExecute  OffOnValue
    }

    maintFdbIndex OBJECT-TYPE
        SYNTAX       Integer32 (1..1)
        MAX-ACCESS   not-accessible
        STATUS       current
        DESCRIPTION  "Index of this table."
        ::= { maintFdbEntry 1 }

    maintFdbNEAddress OBJECT-TYPE
        SYNTAX       IpAddress
        MAX-ACCESS   not-accessible
        STATUS       current
        DESCRIPTION  "reserved."
        ::= { maintFdbEntry 2 }

    maintFdbTableClearAll OBJECT-TYPE
        SYNTAX       OffOnValue
        MAX-ACCESS   read-write
        STATUS       current
        DESCRIPTION
            "FDB clear request.
            When the object is set to 'on', the all forwarding database
            entries will be cleared."
        ::= { maintFdbEntry 3 }

    maintFdbTableClearPort OBJECT-TYPE
        SYNTAX       InterfaceIndex
        MAX-ACCESS   read-write
        STATUS       current
        DESCRIPTION
            "FDB clear request per port.
            Setting to interface index of target port, the forwarding
            database entries for the specified port will be cleared."
        ::= { maintFdbEntry 4 }

    maintFdbTableClearVlan OBJECT-TYPE
        SYNTAX       Integer32 (0..4094)
        MAX-ACCESS   read-write
        STATUS       current
        DESCRIPTION
            "FDB clear request per VLAN.
            Setting to VLAN ID of target VLAN, the forwarding database
            entries for the specified VLAN will be cleared."
        ::= { maintFdbEntry 5 }

    maintFdbGetLearningInfoExecute OBJECT-TYPE
        SYNTAX       OffOnValue
        MAX-ACCESS   read-write
        STATUS       current
        DESCRIPTION
            "Request to export dynamic FDB entries.
            The system provides the file interface for dynamic FDB entries.
            The agent start to export dynamic FDB entries to file, when the
            object is set to 'on'. After completing to export, the object
            will be changed to 'off' and the manager can retrieve the file
            using usual file transferring method."
        ::= { maintFdbEntry 6 }

    maintFdbClearLearningInfoExecute OBJECT-TYPE
        SYNTAX       OffOnValue
        MAX-ACCESS   read-write
        STATUS       current
        DESCRIPTION
            "Request to delete the exported FDB file.
            The exported FDB file is created on the internal file system, the
            manager should delete that file using this object."
        ::= { maintFdbEntry 7 }

    maintEthOamGroup OBJECT IDENTIFIER
        ::= { maintETHGroup 2 }

    maintEthOamLbTable OBJECT-TYPE
        SYNTAX       SEQUENCE OF MaintEthOamLbEntry
        MAX-ACCESS   not-accessible
        STATUS       current
        DESCRIPTION  "ETH-LB Execution Management Table"
        ::= { maintEthOamGroup 1 }

    maintEthOamLbEntry OBJECT-TYPE
        SYNTAX       MaintEthOamLbEntry
        MAX-ACCESS   not-accessible
        STATUS       current
        DESCRIPTION  ""
        INDEX        { maintEthOamLbMepIndex }
        ::= { maintEthOamLbTable 1 }

    MaintEthOamLbEntry ::= SEQUENCE {
        maintEthOamLbMepIndex    IpeMepId,
        maintEthOamLbNEAddress   IpAddress,
        maintEthOamLbExecute     INTEGER,
        maintEthOamLbDesAddress  MacAddress,
        maintEthOamLbCount       Integer32,
        maintEthOamLbPeriod      Integer32,
        maintEthOamLbSize        Integer32,
        maintEthOamLbPriority    Integer32
    }

    maintEthOamLbMepIndex OBJECT-TYPE
        SYNTAX       IpeMepId
        MAX-ACCESS   not-accessible
        STATUS       current
        DESCRIPTION  "Index of this table."
        ::= { maintEthOamLbEntry 1 }

    maintEthOamLbNEAddress OBJECT-TYPE
        SYNTAX       IpAddress
        MAX-ACCESS   not-accessible
        STATUS       current
        DESCRIPTION  "IP Address"
        ::= { maintEthOamLbEntry 2 }

    maintEthOamLbExecute OBJECT-TYPE
        SYNTAX       INTEGER { invalid(0), run(1), stop(2) }
        MAX-ACCESS   read-write
        STATUS       current
        DESCRIPTION  "ETH-LB Execution"
        ::= { maintEthOamLbEntry 3 }

    maintEthOamLbDesAddress OBJECT-TYPE
        SYNTAX       MacAddress
        MAX-ACCESS   read-write
        STATUS       current
        DESCRIPTION  "Destination MAC Address"
        ::= { maintEthOamLbEntry 4 }

    maintEthOamLbCount OBJECT-TYPE
        SYNTAX       Integer32 (1..127)
        MAX-ACCESS   read-write
        STATUS       current
        DESCRIPTION  "Transmit Count(1-127)"
        ::= { maintEthOamLbEntry 5 }

    maintEthOamLbPeriod OBJECT-TYPE
        SYNTAX       Integer32 (1..10)
        MAX-ACCESS   read-write
        STATUS       current
        DESCRIPTION  "Transmit Period(1-10)"
        ::= { maintEthOamLbEntry 6 }

    maintEthOamLbSize OBJECT-TYPE
        SYNTAX       Integer32 (64..9600)
        MAX-ACCESS   read-write
        STATUS       current
        DESCRIPTION  "PDU Size(64-9600)"
        ::= { maintEthOamLbEntry 7 }

    maintEthOamLbPriority OBJECT-TYPE
        SYNTAX       Integer32 (0..7)
        MAX-ACCESS   read-write
        STATUS       current
        DESCRIPTION  "Priority(0-7)"
        ::= { maintEthOamLbEntry 8 }

    maintEthOamLbResultTable OBJECT-TYPE
        SYNTAX       SEQUENCE OF MaintEthOamLbResultEntry
        MAX-ACCESS   not-accessible
        STATUS       current
        DESCRIPTION  "ETH-LB Result Table"
        ::= { maintEthOamGroup 2 }

    maintEthOamLbResultEntry OBJECT-TYPE
        SYNTAX       MaintEthOamLbResultEntry
        MAX-ACCESS   not-accessible
        STATUS       current
        DESCRIPTION  ""
        INDEX        { maintEthOamLbResultMepIndex }
        ::= { maintEthOamLbResultTable 1 }

    MaintEthOamLbResultEntry ::= SEQUENCE {
        maintEthOamLbResultMepIndex    IpeMepId,
        maintEthOamLbResultNEAddress   IpAddress,
        maintEthOamLbResultIfIndex     InterfaceIndex,
        maintEthOamLbResultMacAddress  MacAddress,
        maintEthOamLbResultVid         Integer32,
        maintEthOamLbResultMegId       OCTET STRING,
        maintEthOamLbResultMepId       Integer32,
        maintEthOamLbResultMegLevel    Integer32,
        maintEthOamLbResultDaType      INTEGER,
        maintEthOamLbResultSuccess     Integer32,
        maintEthOamLbResultFail        Integer32,
        maintEthOamLbResultMinTime     Integer32,
        maintEthOamLbResultMaxTime     Integer32,
        maintEthOamLbResultAveTime     Integer32,
        maintEthOamLbResultDevTime     Integer32,
        maintEthOamLbResultLastUpTime  DateAndTime,
        maintEthOamLbResultExecStatus  INTEGER
    }

    maintEthOamLbResultMepIndex OBJECT-TYPE
        SYNTAX       IpeMepId
        MAX-ACCESS   not-accessible
        STATUS       current
        DESCRIPTION  "Index of this table."
        ::= { maintEthOamLbResultEntry 1 }

    maintEthOamLbResultNEAddress OBJECT-TYPE
        SYNTAX       IpAddress
        MAX-ACCESS   not-accessible
        STATUS       current
        DESCRIPTION  "IP Address"
        ::= { maintEthOamLbResultEntry 2 }

    maintEthOamLbResultIfIndex OBJECT-TYPE
        SYNTAX       InterfaceIndex
        MAX-ACCESS   read-only
        STATUS       current
        DESCRIPTION  "Ifindex"
        ::= { maintEthOamLbResultEntry 3 }

    maintEthOamLbResultMacAddress OBJECT-TYPE
        SYNTAX       MacAddress
        MAX-ACCESS   read-only
        STATUS       current
        DESCRIPTION  "MAC Address"
        ::= { maintEthOamLbResultEntry 4 }

    maintEthOamLbResultVid OBJECT-TYPE
        SYNTAX       Integer32 (0..4094)
        MAX-ACCESS   read-only
        STATUS       current
        DESCRIPTION  "Mep's Vlan Id"
        ::= { maintEthOamLbResultEntry 5 }

    maintEthOamLbResultMegId OBJECT-TYPE
        SYNTAX       OCTET STRING (SIZE(1..43))
        MAX-ACCESS   read-only
        STATUS       current
        DESCRIPTION  "Mep's MEG ID"
        ::= { maintEthOamLbResultEntry 6 }

    maintEthOamLbResultMepId OBJECT-TYPE
        SYNTAX       Integer32 (1..8191)
        MAX-ACCESS   read-only
        STATUS       current
        DESCRIPTION  "Mep Id"
        ::= { maintEthOamLbResultEntry 7 }

    maintEthOamLbResultMegLevel OBJECT-TYPE
        SYNTAX       Integer32 (0..7)
        MAX-ACCESS   read-only
        STATUS       current
        DESCRIPTION  "Mep's Meg Level"
        ::= { maintEthOamLbResultEntry 8 }

    maintEthOamLbResultDaType OBJECT-TYPE
        SYNTAX       INTEGER { multicast(0), unicast(1) }
        MAX-ACCESS   read-only
        STATUS       current
        DESCRIPTION  "MAC Address Type(Multicast or Unicast)"
        ::= { maintEthOamLbResultEntry 9 }

    maintEthOamLbResultSuccess OBJECT-TYPE
        SYNTAX       Integer32 (0..127)
        MAX-ACCESS   read-only
        STATUS       current
        DESCRIPTION  "ETH-LB Success Count"
        ::= { maintEthOamLbResultEntry 10 }

    maintEthOamLbResultFail OBJECT-TYPE
        SYNTAX       Integer32 (0..127)
        MAX-ACCESS   read-only
        STATUS       current
        DESCRIPTION  "ETH-LB Fail Count(for UnicastLB only)"
        ::= { maintEthOamLbResultEntry 11 }

    maintEthOamLbResultMinTime OBJECT-TYPE
        SYNTAX       Integer32 (0..5000)
        MAX-ACCESS   read-only
        STATUS       current
        DESCRIPTION  "Minimum Round Trip Time(for UnicastLB only)"
        ::= { maintEthOamLbResultEntry 12 }

    maintEthOamLbResultMaxTime OBJECT-TYPE
        SYNTAX       Integer32 (0..5000)
        MAX-ACCESS   read-only
        STATUS       current
        DESCRIPTION  "Maximum Round Trip Time(for UnicastLB only)"
        ::= { maintEthOamLbResultEntry 13 }

    maintEthOamLbResultAveTime OBJECT-TYPE
        SYNTAX       Integer32 (0..5000)
        MAX-ACCESS   read-only
        STATUS       current
        DESCRIPTION  "Average Round Trip Time(for UnicastLB only)"
        ::= { maintEthOamLbResultEntry 14 }

    maintEthOamLbResultDevTime OBJECT-TYPE
        SYNTAX       Integer32 (0..5000)
        MAX-ACCESS   read-only
        STATUS       current
        DESCRIPTION  "Deflection Round Trip Time(for UnicastLB only)"
        ::= { maintEthOamLbResultEntry 15 }

    maintEthOamLbResultLastUpTime OBJECT-TYPE
        SYNTAX       DateAndTime
        MAX-ACCESS   read-only
        STATUS       current
        DESCRIPTION  "ETH-LB Start Time"
        ::= { maintEthOamLbResultEntry 16 }

    maintEthOamLbResultExecStatus OBJECT-TYPE
        SYNTAX       INTEGER { none(0), running(1), stop(2), complete(3) }
        MAX-ACCESS   read-only
        STATUS       current
        DESCRIPTION  "ETH-LB Execution Status"
        ::= { maintEthOamLbResultEntry 17 }

    maintEthOamLbResultMacTable OBJECT-TYPE
        SYNTAX       SEQUENCE OF MaintEthOamLbResultMacEntry
        MAX-ACCESS   not-accessible
        STATUS       current
        DESCRIPTION  "ETH-LB Result MAC Address Table"
        ::= { maintEthOamGroup 3 }

    maintEthOamLbResultMacEntry OBJECT-TYPE
        SYNTAX       MaintEthOamLbResultMacEntry
        MAX-ACCESS   not-accessible
        STATUS       current
        DESCRIPTION  ""
        INDEX        {
                         maintEthOamLbResultMacMepIndex,
                         maintEthOamLbResultMacNumber
                     }
        ::= { maintEthOamLbResultMacTable 1 }

    MaintEthOamLbResultMacEntry ::= SEQUENCE {
        maintEthOamLbResultMacMepIndex    IpeMepId,
        maintEthOamLbResultMacNumber      Integer32,
        maintEthOamLbResultMacNEAddress   IpAddress,
        maintEthOamLbResultMac            INTEGER,
        maintEthOamLbResultMacSrcAddress  MacAddress,
        maintEthOamLbResultMacTime        Integer32
    }

    maintEthOamLbResultMacMepIndex OBJECT-TYPE
        SYNTAX       IpeMepId
        MAX-ACCESS   not-accessible
        STATUS       current
        DESCRIPTION  "Index of this table."
        ::= { maintEthOamLbResultMacEntry 1 }

    maintEthOamLbResultMacNumber OBJECT-TYPE
        SYNTAX       Integer32 (1..16)
        MAX-ACCESS   not-accessible
        STATUS       current
        DESCRIPTION  "ETH-LBR Receive Number"
        ::= { maintEthOamLbResultMacEntry 2 }

    maintEthOamLbResultMacNEAddress OBJECT-TYPE
        SYNTAX       IpAddress
        MAX-ACCESS   not-accessible
        STATUS       current
        DESCRIPTION  "IP Address"
        ::= { maintEthOamLbResultMacEntry 3 }

    maintEthOamLbResultMac OBJECT-TYPE
        SYNTAX       INTEGER { invalid(0), receive(1), timeout(2) }
        MAX-ACCESS   read-only
        STATUS       current
        DESCRIPTION  "ETH-LB Result(for UnicastLB only)"
        ::= { maintEthOamLbResultMacEntry 4 }

    maintEthOamLbResultMacSrcAddress OBJECT-TYPE
        SYNTAX       MacAddress
        MAX-ACCESS   read-only
        STATUS       current
        DESCRIPTION  "MAC Address"
        ::= { maintEthOamLbResultMacEntry 5 }

    maintEthOamLbResultMacTime OBJECT-TYPE
        SYNTAX       Integer32
        MAX-ACCESS   read-only
        STATUS       current
        DESCRIPTION  "Round Trip Time"
        ::= { maintEthOamLbResultMacEntry 6 }

    maintEthOamLtTable OBJECT-TYPE
        SYNTAX       SEQUENCE OF MaintEthOamLtEntry
        MAX-ACCESS   not-accessible
        STATUS       current
        DESCRIPTION  "ETH-LT Execution Management Table"
        ::= { maintEthOamGroup 4 }

    maintEthOamLtEntry OBJECT-TYPE
        SYNTAX       MaintEthOamLtEntry
        MAX-ACCESS   not-accessible
        STATUS       current
        DESCRIPTION  ""
        INDEX        { maintEthOamLtMepIndex }
        ::= { maintEthOamLtTable 1 }

    MaintEthOamLtEntry ::= SEQUENCE {
        maintEthOamLtMepIndex       IpeMepId,
        maintEthOamLtNEAddress      IpAddress,
        maintEthOamLtExecute        INTEGER,
        maintEthOamLtTargetAddress  MacAddress,
        maintEthOamLtTtl            Integer32,
        maintEthOamLtPriority       Integer32
    }

    maintEthOamLtMepIndex OBJECT-TYPE
        SYNTAX       IpeMepId
        MAX-ACCESS   not-accessible
        STATUS       current
        DESCRIPTION  "Index of this table."
        ::= { maintEthOamLtEntry 1 }

    maintEthOamLtNEAddress OBJECT-TYPE
        SYNTAX       IpAddress
        MAX-ACCESS   not-accessible
        STATUS       current
        DESCRIPTION  "IP Address"
        ::= { maintEthOamLtEntry 2 }

    maintEthOamLtExecute OBJECT-TYPE
        SYNTAX       INTEGER { invalid(0), run(1), stop(2) }
        MAX-ACCESS   read-write
        STATUS       current
        DESCRIPTION  "ETH-LT Execution"
        ::= { maintEthOamLtEntry 3 }

    maintEthOamLtTargetAddress OBJECT-TYPE
        SYNTAX       MacAddress
        MAX-ACCESS   read-write
        STATUS       current
        DESCRIPTION  "Target MAC Address"
        ::= { maintEthOamLtEntry 4 }

    maintEthOamLtTtl OBJECT-TYPE
        SYNTAX       Integer32 (1..255)
        MAX-ACCESS   read-write
        STATUS       current
        DESCRIPTION  "Time To Live(1-255)"
        ::= { maintEthOamLtEntry 5 }

    maintEthOamLtPriority OBJECT-TYPE
        SYNTAX       Integer32 (0..7)
        MAX-ACCESS   read-write
        STATUS       current
        DESCRIPTION  "Priority(0-7)"
        ::= { maintEthOamLtEntry 6 }

    maintEthOamLtResultTable OBJECT-TYPE
        SYNTAX       SEQUENCE OF MaintEthOamLtResultEntry
        MAX-ACCESS   not-accessible
        STATUS       current
        DESCRIPTION  "ETH-LT Result Table"
        ::= { maintEthOamGroup 5 }

    maintEthOamLtResultEntry OBJECT-TYPE
        SYNTAX       MaintEthOamLtResultEntry
        MAX-ACCESS   not-accessible
        STATUS       current
        DESCRIPTION  ""
        INDEX        { maintEthOamLtResultMepIndex }
        ::= { maintEthOamLtResultTable 1 }

    MaintEthOamLtResultEntry ::= SEQUENCE {
        maintEthOamLtResultMepIndex    IpeMepId,
        maintEthOamLtResultNEAddress   IpAddress,
        maintEthOamLtResultIfIndex     InterfaceIndex,
        maintEthOamLtResultMacAddress  MacAddress,
        maintEthOamLtResultVid         Integer32,
        maintEthOamLtResultMegId       OCTET STRING,
        maintEthOamLtResultMepId       Integer32,
        maintEthOamLtResultMegLevel    Integer32,
        maintEthOamLtResultTtl         Integer32,
        maintEthOamLtResultReceive     Integer32,
        maintEthOamLtResultLastUpTime  DateAndTime,
        maintEthOamLtResultExecStatus  INTEGER
    }

    maintEthOamLtResultMepIndex OBJECT-TYPE
        SYNTAX       IpeMepId
        MAX-ACCESS   not-accessible
        STATUS       current
        DESCRIPTION  "Index of this table."
        ::= { maintEthOamLtResultEntry 1 }

    maintEthOamLtResultNEAddress OBJECT-TYPE
        SYNTAX       IpAddress
        MAX-ACCESS   not-accessible
        STATUS       current
        DESCRIPTION  "IP Address"
        ::= { maintEthOamLtResultEntry 2 }

    maintEthOamLtResultIfIndex OBJECT-TYPE
        SYNTAX       InterfaceIndex
        MAX-ACCESS   read-only
        STATUS       current
        DESCRIPTION  "Ifindex"
        ::= { maintEthOamLtResultEntry 3 }

    maintEthOamLtResultMacAddress OBJECT-TYPE
        SYNTAX       MacAddress
        MAX-ACCESS   read-only
        STATUS       current
        DESCRIPTION  "MAC Address"
        ::= { maintEthOamLtResultEntry 4 }

    maintEthOamLtResultVid OBJECT-TYPE
        SYNTAX       Integer32 (0..4094)
        MAX-ACCESS   read-only
        STATUS       current
        DESCRIPTION  "Mep's Vlan Id"
        ::= { maintEthOamLtResultEntry 5 }

    maintEthOamLtResultMegId OBJECT-TYPE
        SYNTAX       OCTET STRING (SIZE(1..43))
        MAX-ACCESS   read-only
        STATUS       current
        DESCRIPTION  "Mep's MEG ID"
        ::= { maintEthOamLtResultEntry 6 }

    maintEthOamLtResultMepId OBJECT-TYPE
        SYNTAX       Integer32 (1..8191)
        MAX-ACCESS   read-only
        STATUS       current
        DESCRIPTION  "Mep Id"
        ::= { maintEthOamLtResultEntry 7 }

    maintEthOamLtResultMegLevel OBJECT-TYPE
        SYNTAX       Integer32 (0..7)
        MAX-ACCESS   read-only
        STATUS       current
        DESCRIPTION  "Mep's Meg Level"
        ::= { maintEthOamLtResultEntry 8 }

    maintEthOamLtResultTtl OBJECT-TYPE
        SYNTAX       Integer32 (0..255)
        MAX-ACCESS   read-only
        STATUS       current
        DESCRIPTION  "TTL"
        ::= { maintEthOamLtResultEntry 9 }

    maintEthOamLtResultReceive OBJECT-TYPE
        SYNTAX       Integer32 (0..16)
        MAX-ACCESS   read-only
        STATUS       current
        DESCRIPTION  "ETH-LTR Receive Count"
        ::= { maintEthOamLtResultEntry 10 }

    maintEthOamLtResultLastUpTime OBJECT-TYPE
        SYNTAX       DateAndTime
        MAX-ACCESS   read-only
        STATUS       current
        DESCRIPTION  "ETH-LT Start Time"
        ::= { maintEthOamLtResultEntry 11 }

    maintEthOamLtResultExecStatus OBJECT-TYPE
        SYNTAX       INTEGER { none(0), running(1), stop(2), complete(3) }
        MAX-ACCESS   read-only
        STATUS       current
        DESCRIPTION  "ETH-LT Execution Status"
        ::= { maintEthOamLtResultEntry 12 }

    maintEthOamLtResultMacTable OBJECT-TYPE
        SYNTAX       SEQUENCE OF MaintEthOamLtResultMacEntry
        MAX-ACCESS   not-accessible
        STATUS       current
        DESCRIPTION  "ETH-LT Result MAC Address Table"
        ::= { maintEthOamGroup 6 }

    maintEthOamLtResultMacEntry OBJECT-TYPE
        SYNTAX       MaintEthOamLtResultMacEntry
        MAX-ACCESS   not-accessible
        STATUS       current
        DESCRIPTION  ""
        INDEX        {
                         maintEthOamLtResultMacMepIndex,
                         maintEthOamLtResultMacNumber
                     }
        ::= { maintEthOamLtResultMacTable 1 }

    MaintEthOamLtResultMacEntry ::= SEQUENCE {
        maintEthOamLtResultMacMepIndex    IpeMepId,
        maintEthOamLtResultMacNumber      Integer32,
        maintEthOamLtResultMacNEAddress   IpAddress,
        maintEthOamLtResultMacTtl         Integer32,
        maintEthOamLtResultMacSrcAddress  MacAddress,
        maintEthOamLtResultMacRlyAct      INTEGER
    }

    maintEthOamLtResultMacMepIndex OBJECT-TYPE
        SYNTAX       IpeMepId
        MAX-ACCESS   not-accessible
        STATUS       current
        DESCRIPTION  "Index of this table."
        ::= { maintEthOamLtResultMacEntry 1 }

    maintEthOamLtResultMacNumber OBJECT-TYPE
        SYNTAX       Integer32 (1..16)
        MAX-ACCESS   not-accessible
        STATUS       current
        DESCRIPTION  "ETH-LTR Receive Number"
        ::= { maintEthOamLtResultMacEntry 2 }

    maintEthOamLtResultMacNEAddress OBJECT-TYPE
        SYNTAX       IpAddress
        MAX-ACCESS   not-accessible
        STATUS       current
        DESCRIPTION  "IP Address"
        ::= { maintEthOamLtResultMacEntry 3 }

    maintEthOamLtResultMacTtl OBJECT-TYPE
        SYNTAX       Integer32 (0..255)
        MAX-ACCESS   read-only
        STATUS       current
        DESCRIPTION  "Time To Live"
        ::= { maintEthOamLtResultMacEntry 4 }

    maintEthOamLtResultMacSrcAddress OBJECT-TYPE
        SYNTAX       MacAddress
        MAX-ACCESS   read-only
        STATUS       current
        DESCRIPTION  "MAC Address"
        ::= { maintEthOamLtResultMacEntry 5 }

    maintEthOamLtResultMacRlyAct OBJECT-TYPE
        SYNTAX       INTEGER {
                         invalid(0),
                         relayHit(1),
                         relayFDB(2),
                         relayNFDB(3)
                     }
        MAX-ACCESS   read-only
        STATUS       current
        DESCRIPTION  "RelayAction"
        ::= { maintEthOamLtResultMacEntry 6 }

    maintEthOamDmTable OBJECT-TYPE
        SYNTAX       SEQUENCE OF MaintEthOamDmEntry
        MAX-ACCESS   not-accessible
        STATUS       current
        DESCRIPTION  "ETH-DM Execution Management Table"
        ::= { maintEthOamGroup 7 }

    maintEthOamDmEntry OBJECT-TYPE
        SYNTAX       MaintEthOamDmEntry
        MAX-ACCESS   not-accessible
        STATUS       current
        DESCRIPTION  ""
        INDEX        { maintEthOamDmMepIndex }
        ::= { maintEthOamDmTable 1 }

    MaintEthOamDmEntry ::= SEQUENCE {
        maintEthOamDmMepIndex    IpeMepId,
        maintEthOamDmNEAddress   IpAddress,
        maintEthOamDmExecute     INTEGER,
        maintEthOamDmDesAddress  MacAddress,
        maintEthOamDmCount       Integer32,
        maintEthOamDmPeriodS     Integer32,
        maintEthOamDmPriority    Integer32
    }

    maintEthOamDmMepIndex OBJECT-TYPE
        SYNTAX       IpeMepId
        MAX-ACCESS   not-accessible
        STATUS       current
        DESCRIPTION  "Index of this table."
        ::= { maintEthOamDmEntry 1 }

    maintEthOamDmNEAddress OBJECT-TYPE
        SYNTAX       IpAddress
        MAX-ACCESS   not-accessible
        STATUS       current
        DESCRIPTION  "IP Address"
        ::= { maintEthOamDmEntry 2 }

    maintEthOamDmExecute OBJECT-TYPE
        SYNTAX       INTEGER { invalid(0), run(1), stop(2) }
        MAX-ACCESS   read-write
        STATUS       current
        DESCRIPTION  "ETH-DM Execution"
        ::= { maintEthOamDmEntry 3 }

    maintEthOamDmDesAddress OBJECT-TYPE
        SYNTAX       MacAddress
        MAX-ACCESS   read-write
        STATUS       current
        DESCRIPTION  "Destination MAC Address"
        ::= { maintEthOamDmEntry 4 }

    maintEthOamDmCount OBJECT-TYPE
        SYNTAX       Integer32 (1..500)
        MAX-ACCESS   read-write
        STATUS       current
        DESCRIPTION  "ETH-DM Transmit Count(1-500)"
        ::= { maintEthOamDmEntry 5 }

    maintEthOamDmPeriodS OBJECT-TYPE
        SYNTAX       Integer32 (1..10)
        UNITS        "seconds"
        MAX-ACCESS   read-write
        STATUS       current
        DESCRIPTION  "ETH-DM Transmit Period Second"
        ::= { maintEthOamDmEntry 6 }

    maintEthOamDmPriority OBJECT-TYPE
        SYNTAX       Integer32 (0..7)
        MAX-ACCESS   read-write
        STATUS       current
        DESCRIPTION  "Priority(0-7)"
        ::= { maintEthOamDmEntry 7 }

    maintEthOamDmResultTable OBJECT-TYPE
        SYNTAX       SEQUENCE OF MaintEthOamDmResultEntry
        MAX-ACCESS   not-accessible
        STATUS       current
        DESCRIPTION  "ETH-DM Result Table"
        ::= { maintEthOamGroup 8 }

    maintEthOamDmResultEntry OBJECT-TYPE
        SYNTAX       MaintEthOamDmResultEntry
        MAX-ACCESS   not-accessible
        STATUS       current
        DESCRIPTION  ""
        INDEX        { maintEthOamDmResultMepIndex }
        ::= { maintEthOamDmResultTable 1 }

    MaintEthOamDmResultEntry ::= SEQUENCE {
        maintEthOamDmResultMepIndex       IpeMepId,
        maintEthOamDmResultNEAddress      IpAddress,
        maintEthOamDmResultIfIndex        InterfaceIndex,
        maintEthOamDmResultSrcMacAddress  MacAddress,
        maintEthOamDmResultVid            Integer32,
        maintEthOamDmResultMegId          OCTET STRING,
        maintEthOamDmResultMepId          Integer32,
        maintEthOamDmResultMegLevel       Integer32,
        maintEthOamDmResultDesMacAddress  MacAddress,
        maintEthOamDmResultRequest        Integer32,
        maintEthOamDmResultReceive        Integer32,
        maintEthOamDmResultMinTime        Integer32,
        maintEthOamDmResultMaxTime        Integer32,
        maintEthOamDmResultAveTime        Integer32,
        maintEthOamDmResultDevTime        Integer32,
        maintEthOamDmResultErrCount       Integer32,
        maintEthOamDmResultLastUpTime     DateAndTime,
        maintEthOamDmResultExecStatus     INTEGER
    }

    maintEthOamDmResultMepIndex OBJECT-TYPE
        SYNTAX       IpeMepId
        MAX-ACCESS   not-accessible
        STATUS       current
        DESCRIPTION  "Index of this table."
        ::= { maintEthOamDmResultEntry 1 }

    maintEthOamDmResultNEAddress OBJECT-TYPE
        SYNTAX       IpAddress
        MAX-ACCESS   not-accessible
        STATUS       current
        DESCRIPTION  "IP Address"
        ::= { maintEthOamDmResultEntry 2 }

    maintEthOamDmResultIfIndex OBJECT-TYPE
        SYNTAX       InterfaceIndex
        MAX-ACCESS   read-only
        STATUS       current
        DESCRIPTION  "Ifindex"
        ::= { maintEthOamDmResultEntry 3 }

    maintEthOamDmResultSrcMacAddress OBJECT-TYPE
        SYNTAX       MacAddress
        MAX-ACCESS   read-only
        STATUS       current
        DESCRIPTION  "MAC Address"
        ::= { maintEthOamDmResultEntry 4 }

    maintEthOamDmResultVid OBJECT-TYPE
        SYNTAX       Integer32 (0..4094)
        MAX-ACCESS   read-only
        STATUS       current
        DESCRIPTION  "Mep's Vlan Id"
        ::= { maintEthOamDmResultEntry 5 }

    maintEthOamDmResultMegId OBJECT-TYPE
        SYNTAX       OCTET STRING (SIZE(0..43))
        MAX-ACCESS   read-only
        STATUS       current
        DESCRIPTION  "Mep's MEG ID"
        ::= { maintEthOamDmResultEntry 6 }

    maintEthOamDmResultMepId OBJECT-TYPE
        SYNTAX       Integer32 (1..8191)
        MAX-ACCESS   read-only
        STATUS       current
        DESCRIPTION  "MEP ID"
        ::= { maintEthOamDmResultEntry 7 }

    maintEthOamDmResultMegLevel OBJECT-TYPE
        SYNTAX       Integer32 (0..7)
        MAX-ACCESS   read-only
        STATUS       current
        DESCRIPTION  "Mep's Meg Level"
        ::= { maintEthOamDmResultEntry 8 }

    maintEthOamDmResultDesMacAddress OBJECT-TYPE
        SYNTAX       MacAddress
        MAX-ACCESS   read-only
        STATUS       current
        DESCRIPTION  "Destination MAC Address"
        ::= { maintEthOamDmResultEntry 9 }

    maintEthOamDmResultRequest OBJECT-TYPE
        SYNTAX       Integer32 (0..500)
        MAX-ACCESS   read-only
        STATUS       current
        DESCRIPTION  "ETH-DMM Transmit Count"
        ::= { maintEthOamDmResultEntry 10 }

    maintEthOamDmResultReceive OBJECT-TYPE
        SYNTAX       Integer32 (0..500)
        MAX-ACCESS   read-only
        STATUS       current
        DESCRIPTION  "ETH-DMR Receive Count"
        ::= { maintEthOamDmResultEntry 11 }

    maintEthOamDmResultMinTime OBJECT-TYPE
        SYNTAX       Integer32 (0..8388608)
        UNITS        "microseconds"
        MAX-ACCESS   read-only
        STATUS       current
        DESCRIPTION  "Minimum Round Trip Time"
        ::= { maintEthOamDmResultEntry 12 }

    maintEthOamDmResultMaxTime OBJECT-TYPE
        SYNTAX       Integer32 (0..8388608)
        UNITS        "microseconds"
        MAX-ACCESS   read-only
        STATUS       current
        DESCRIPTION  "Maximum Round Trip Time"
        ::= { maintEthOamDmResultEntry 13 }

    maintEthOamDmResultAveTime OBJECT-TYPE
        SYNTAX       Integer32 (0..8388608)
        UNITS        "microseconds"
        MAX-ACCESS   read-only
        STATUS       current
        DESCRIPTION  "Average Round Trip Time"
        ::= { maintEthOamDmResultEntry 14 }

    maintEthOamDmResultDevTime OBJECT-TYPE
        SYNTAX       Integer32 (0..8388608)
        UNITS        "microseconds"
        MAX-ACCESS   read-only
        STATUS       current
        DESCRIPTION  "Deflection Round Trip Time"
        ::= { maintEthOamDmResultEntry 15 }

    maintEthOamDmResultErrCount OBJECT-TYPE
        SYNTAX       Integer32 (0..500)
        MAX-ACCESS   read-only
        STATUS       current
        DESCRIPTION  "Error Count"
        ::= { maintEthOamDmResultEntry 16 }

    maintEthOamDmResultLastUpTime OBJECT-TYPE
        SYNTAX       DateAndTime
        MAX-ACCESS   read-only
        STATUS       current
        DESCRIPTION  "ETH-DM Start Time"
        ::= { maintEthOamDmResultEntry 17 }

    maintEthOamDmResultExecStatus OBJECT-TYPE
        SYNTAX       INTEGER { none(0), running(1), stop(2), complete(3) }
        MAX-ACCESS   read-only
        STATUS       current
        DESCRIPTION  "ETH-DM Execution Status"
        ::= { maintEthOamDmResultEntry 18 }

    maintEthOamLmTable OBJECT-TYPE
        SYNTAX       SEQUENCE OF MaintEthOamLmEntry
        MAX-ACCESS   not-accessible
        STATUS       current
        DESCRIPTION  "ETH-LM Execution Management Table"
        ::= { maintEthOamGroup 9 }

    maintEthOamLmEntry OBJECT-TYPE
        SYNTAX       MaintEthOamLmEntry
        MAX-ACCESS   not-accessible
        STATUS       current
        DESCRIPTION  ""
        INDEX        { maintEthOamLmMepIndex }
        ::= { maintEthOamLmTable 1 }

    MaintEthOamLmEntry ::= SEQUENCE {
        maintEthOamLmMepIndex           IpeMepId,
        maintEthOamLmNEAddress          IpAddress,
        maintEthOamLmExecute            INTEGER,
        maintEthOamLmDesAddress         MacAddress,
        maintEthOamLmCount              Integer32,
        maintEthOamLmPeriodS            Integer32,
        maintEthOamLmPriority           Integer32,
        maintEthOamLmTargetFrmPriority  Integer32
    }

    maintEthOamLmMepIndex OBJECT-TYPE
        SYNTAX       IpeMepId
        MAX-ACCESS   not-accessible
        STATUS       current
        DESCRIPTION  "Index of this table."
        ::= { maintEthOamLmEntry 1 }

    maintEthOamLmNEAddress OBJECT-TYPE
        SYNTAX       IpAddress
        MAX-ACCESS   not-accessible
        STATUS       current
        DESCRIPTION  "IP Address"
        ::= { maintEthOamLmEntry 2 }

    maintEthOamLmExecute OBJECT-TYPE
        SYNTAX       INTEGER { invalid(0), run(1), stop(2) }
        MAX-ACCESS   read-write
        STATUS       current
        DESCRIPTION  "ETH-DM Execution"
        ::= { maintEthOamLmEntry 3 }

    maintEthOamLmDesAddress OBJECT-TYPE
        SYNTAX       MacAddress
        MAX-ACCESS   read-write
        STATUS       current
        DESCRIPTION  "Destination MAC Address"
        ::= { maintEthOamLmEntry 4 }

    maintEthOamLmCount OBJECT-TYPE
        SYNTAX       Integer32 (1..500)
        MAX-ACCESS   read-write
        STATUS       current
        DESCRIPTION  "ETH-LM Transmit Count(1-500)"
        ::= { maintEthOamLmEntry 5 }

    maintEthOamLmPeriodS OBJECT-TYPE
        SYNTAX       Integer32 (1..10)
        MAX-ACCESS   read-write
        STATUS       current
        DESCRIPTION  "ETH-LM Transmit Period Second"
        ::= { maintEthOamLmEntry 6 }

    maintEthOamLmPriority OBJECT-TYPE
        SYNTAX       Integer32 (0..7)
        MAX-ACCESS   read-write
        STATUS       current
        DESCRIPTION  "Priority(0-7)"
        ::= { maintEthOamLmEntry 7 }

    maintEthOamLmTargetFrmPriority OBJECT-TYPE
        SYNTAX       Integer32 (-1..7)
        MAX-ACCESS   read-write
        STATUS       current
        DESCRIPTION  "Target Frame Priority"
        ::= { maintEthOamLmEntry 8 }

    maintEthOamLmResultTable OBJECT-TYPE
        SYNTAX       SEQUENCE OF MaintEthOamLmResultEntry
        MAX-ACCESS   not-accessible
        STATUS       current
        DESCRIPTION  "ETH-LM Result Table"
        ::= { maintEthOamGroup 10 }

    maintEthOamLmResultEntry OBJECT-TYPE
        SYNTAX       MaintEthOamLmResultEntry
        MAX-ACCESS   not-accessible
        STATUS       current
        DESCRIPTION  ""
        INDEX        { maintEthOamLmResultMepIndex }
        ::= { maintEthOamLmResultTable 1 }

    MaintEthOamLmResultEntry ::= SEQUENCE {
        maintEthOamLmResultMepIndex         IpeMepId,
        maintEthOamLmResultNEAddress        IpAddress,
        maintEthOamLmResultIfIndex          InterfaceIndex,
        maintEthOamLmResultSrcMacAddress    MacAddress,
        maintEthOamLmResultVid              Integer32,
        maintEthOamLmResultMegId            OCTET STRING,
        maintEthOamLmResultMepId            Integer32,
        maintEthOamLmResultMegLevel         Integer32,
        maintEthOamLmResultDesMacAddress    MacAddress,
        maintEthOamLmResultRequest          Integer32,
        maintEthOamLmResultReceive          Integer32,
        maintEthOamLmResultTxFramesNearEnd  Counter32,
        maintEthOamLmResultRxFramesFarEnd   Counter32,
        maintEthOamLmResultTxFramesFarEnd   Counter32,
        maintEthOamLmResultRxFramesNearEnd  Counter32,
        maintEthOamLmResultTxFrameLoss      Counter32,
        maintEthOamLmResultTxFLR            Integer32,
        maintEthOamLmResultRxFrameLoss      Counter32,
        maintEthOamLmResultRxFLR            Integer32,
        maintEthOamLmResultErrCount         Integer32,
        maintEthOamLmResultLastUpTime       DateAndTime,
        maintEthOamLmResultExecStatus       INTEGER
    }

    maintEthOamLmResultMepIndex OBJECT-TYPE
        SYNTAX       IpeMepId
        MAX-ACCESS   not-accessible
        STATUS       current
        DESCRIPTION  "Index of this table."
        ::= { maintEthOamLmResultEntry 1 }

    maintEthOamLmResultNEAddress OBJECT-TYPE
        SYNTAX       IpAddress
        MAX-ACCESS   not-accessible
        STATUS       current
        DESCRIPTION  "IP Address"
        ::= { maintEthOamLmResultEntry 2 }

    maintEthOamLmResultIfIndex OBJECT-TYPE
        SYNTAX       InterfaceIndex
        MAX-ACCESS   read-only
        STATUS       current
        DESCRIPTION  "Ifindex"
        ::= { maintEthOamLmResultEntry 3 }

    maintEthOamLmResultSrcMacAddress OBJECT-TYPE
        SYNTAX       MacAddress
        MAX-ACCESS   read-only
        STATUS       current
        DESCRIPTION  "MAC Address"
        ::= { maintEthOamLmResultEntry 4 }

    maintEthOamLmResultVid OBJECT-TYPE
        SYNTAX       Integer32 (0..4094)
        MAX-ACCESS   read-only
        STATUS       current
        DESCRIPTION  "Mep's Vlan Id"
        ::= { maintEthOamLmResultEntry 5 }

    maintEthOamLmResultMegId OBJECT-TYPE
        SYNTAX       OCTET STRING (SIZE(0..43))
        MAX-ACCESS   read-only
        STATUS       current
        DESCRIPTION  "Mep's MEG ID"
        ::= { maintEthOamLmResultEntry 6 }

    maintEthOamLmResultMepId OBJECT-TYPE
        SYNTAX       Integer32 (1..8191)
        MAX-ACCESS   read-only
        STATUS       current
        DESCRIPTION  "MEP ID"
        ::= { maintEthOamLmResultEntry 7 }

    maintEthOamLmResultMegLevel OBJECT-TYPE
        SYNTAX       Integer32 (0..7)
        MAX-ACCESS   read-only
        STATUS       current
        DESCRIPTION  "Mep's Meg Level"
        ::= { maintEthOamLmResultEntry 8 }

    maintEthOamLmResultDesMacAddress OBJECT-TYPE
        SYNTAX       MacAddress
        MAX-ACCESS   read-only
        STATUS       current
        DESCRIPTION  "Destination MAC Address"
        ::= { maintEthOamLmResultEntry 9 }

    maintEthOamLmResultRequest OBJECT-TYPE
        SYNTAX       Integer32 (0..500)
        MAX-ACCESS   read-only
        STATUS       current
        DESCRIPTION  "ETH-LMM Transmit Count"
        ::= { maintEthOamLmResultEntry 10 }

    maintEthOamLmResultReceive OBJECT-TYPE
        SYNTAX       Integer32 (0..500)
        MAX-ACCESS   read-only
        STATUS       current
        DESCRIPTION  "ETH-LMR Receive Count"
        ::= { maintEthOamLmResultEntry 11 }

    maintEthOamLmResultTxFramesNearEnd OBJECT-TYPE
        SYNTAX       Counter32
        MAX-ACCESS   read-only
        STATUS       current
        DESCRIPTION  "Transmit Frame Near Count"
        ::= { maintEthOamLmResultEntry 12 }

    maintEthOamLmResultRxFramesFarEnd OBJECT-TYPE
        SYNTAX       Counter32
        MAX-ACCESS   read-only
        STATUS       current
        DESCRIPTION  "Receive Frame Far Count"
        ::= { maintEthOamLmResultEntry 13 }

    maintEthOamLmResultTxFramesFarEnd OBJECT-TYPE
        SYNTAX       Counter32
        MAX-ACCESS   read-only
        STATUS       current
        DESCRIPTION  "Transmit Frame Far Count"
        ::= { maintEthOamLmResultEntry 14 }

    maintEthOamLmResultRxFramesNearEnd OBJECT-TYPE
        SYNTAX       Counter32
        MAX-ACCESS   read-only
        STATUS       current
        DESCRIPTION  "Receive Frame Near Count"
        ::= { maintEthOamLmResultEntry 15 }

    maintEthOamLmResultTxFrameLoss OBJECT-TYPE
        SYNTAX       Counter32
        MAX-ACCESS   read-only
        STATUS       current
        DESCRIPTION  "Transmit Frame Loss Count"
        ::= { maintEthOamLmResultEntry 16 }

    maintEthOamLmResultTxFLR OBJECT-TYPE
        SYNTAX       Integer32 (0..1000)
        UNITS        "0.1 percent"
        MAX-ACCESS   read-only
        STATUS       current
        DESCRIPTION  "Transmit Frame Loss Rate"
        ::= { maintEthOamLmResultEntry 17 }

    maintEthOamLmResultRxFrameLoss OBJECT-TYPE
        SYNTAX       Counter32
        MAX-ACCESS   read-only
        STATUS       current
        DESCRIPTION  "Receive Frame Loss Count"
        ::= { maintEthOamLmResultEntry 18 }

    maintEthOamLmResultRxFLR OBJECT-TYPE
        SYNTAX       Integer32 (0..1000)
        UNITS        "0.1 percent"
        MAX-ACCESS   read-only
        STATUS       current
        DESCRIPTION  "Receive Frame Loss Rate"
        ::= { maintEthOamLmResultEntry 19 }

    maintEthOamLmResultErrCount OBJECT-TYPE
        SYNTAX       Integer32 (0..500)
        MAX-ACCESS   read-only
        STATUS       current
        DESCRIPTION  "Error Count"
        ::= { maintEthOamLmResultEntry 20 }

    maintEthOamLmResultLastUpTime OBJECT-TYPE
        SYNTAX       DateAndTime
        MAX-ACCESS   read-only
        STATUS       current
        DESCRIPTION  "ETH-LM Start Time"
        ::= { maintEthOamLmResultEntry 21 }

    maintEthOamLmResultExecStatus OBJECT-TYPE
        SYNTAX       INTEGER { none(0), running(1), stop(2), complete(3) }
        MAX-ACCESS   read-only
        STATUS       current
        DESCRIPTION  "ETH-LM Execution Status"
        ::= { maintEthOamLmResultEntry 22 }

    maintEthOamExecutionHistoryTable OBJECT-TYPE
        SYNTAX       SEQUENCE OF MaintEthOamExecutionHistoryEntry
        MAX-ACCESS   not-accessible
        STATUS       current
        DESCRIPTION  "Execution History Table"
        ::= { maintEthOamGroup 11 }

    maintEthOamExecutionHistoryEntry OBJECT-TYPE
        SYNTAX       MaintEthOamExecutionHistoryEntry
        MAX-ACCESS   not-accessible
        STATUS       current
        DESCRIPTION  ""
        INDEX        { maintEthOamExecutionHistoryIndex }
        ::= { maintEthOamExecutionHistoryTable 1 }

    MaintEthOamExecutionHistoryEntry ::= SEQUENCE {
        maintEthOamExecutionHistoryIndex      Integer32,
        maintEthOamExecutionHistoryNEAddress  IpAddress,
        maintEthOamExecutionMepIndex          IpeMepId,
        maintEthOamExecutionType              INTEGER,
        maintEthOamExecutionDesAddress        MacAddress,
        maintEthOamExecutionCount             Integer32,
        maintEthOamExecutionPduSize           Integer32,
        maintEthOamExecutionTtl               Integer32,
        maintEthOamExecutionPeriodS           Integer32,
        maintEthOamExecutionPriority          Integer32,
        maintEthOamExecutionTime              DateAndTime
    }

    maintEthOamExecutionHistoryIndex OBJECT-TYPE
        SYNTAX       Integer32 (1..15)
        MAX-ACCESS   not-accessible
        STATUS       current
        DESCRIPTION  "Index of this table."
        ::= { maintEthOamExecutionHistoryEntry 1 }

    maintEthOamExecutionHistoryNEAddress OBJECT-TYPE
        SYNTAX       IpAddress
        MAX-ACCESS   not-accessible
        STATUS       current
        DESCRIPTION  "IP Address"
        ::= { maintEthOamExecutionHistoryEntry 2 }

    maintEthOamExecutionMepIndex OBJECT-TYPE
        SYNTAX       IpeMepId
        MAX-ACCESS   read-only
        STATUS       current
        DESCRIPTION  "Mep Index(1-128) 0 is Non use."
        ::= { maintEthOamExecutionHistoryEntry 3 }

    maintEthOamExecutionType OBJECT-TYPE
        SYNTAX       INTEGER {
                         invalid(0),
                         loop-back(1),
                         link-trace(2),
                         delay-measurement(3),
                         loss-measurement(4)
                     }
        MAX-ACCESS   read-only
        STATUS       current
        DESCRIPTION  "Execution Type(1:LB, 2:LT, 3:DM, 4:LM)"
        ::= { maintEthOamExecutionHistoryEntry 4 }

    maintEthOamExecutionDesAddress OBJECT-TYPE
        SYNTAX       MacAddress
        MAX-ACCESS   read-only
        STATUS       current
        DESCRIPTION  "Destination MAC Address"
        ::= { maintEthOamExecutionHistoryEntry 5 }

    maintEthOamExecutionCount OBJECT-TYPE
        SYNTAX       Integer32 (0..500)
        MAX-ACCESS   read-only
        STATUS       current
        DESCRIPTION
            "Transmit Count(LB:1-127, LT:Not Use, DM:1-500, LM:1-500)"
        ::= { maintEthOamExecutionHistoryEntry 6 }

    maintEthOamExecutionPduSize OBJECT-TYPE
        SYNTAX       Integer32 (0..9600)
        MAX-ACCESS   read-only
        STATUS       current
        DESCRIPTION  "PDU Size(LB:60-9600, LT/DM/LM:Not Use)"
        ::= { maintEthOamExecutionHistoryEntry 7 }

    maintEthOamExecutionTtl OBJECT-TYPE
        SYNTAX       Integer32 (0..255)
        MAX-ACCESS   read-only
        STATUS       current
        DESCRIPTION  "Time To live(LT:1-255, LB/DM/LM:Not Use)"
        ::= { maintEthOamExecutionHistoryEntry 8 }

    maintEthOamExecutionPeriodS OBJECT-TYPE
        SYNTAX       Integer32 (0..10)
        MAX-ACCESS   read-only
        STATUS       current
        DESCRIPTION  "Transmit Period Second(LB/DM/LM:1-10, LT:Not Use)"
        ::= { maintEthOamExecutionHistoryEntry 9 }

    maintEthOamExecutionPriority OBJECT-TYPE
        SYNTAX       Integer32 (0..7)
        MAX-ACCESS   read-only
        STATUS       current
        DESCRIPTION  "Priority(0-7)"
        ::= { maintEthOamExecutionHistoryEntry 10 }

    maintEthOamExecutionTime OBJECT-TYPE
        SYNTAX       DateAndTime
        MAX-ACCESS   read-only
        STATUS       current
        DESCRIPTION  "Execution Start Time"
        ::= { maintEthOamExecutionHistoryEntry 11 }

    maintRstpGroup OBJECT IDENTIFIER
        ::= { maintETHGroup 3 }

    maintRstpTable OBJECT-TYPE
        SYNTAX       SEQUENCE OF MaintRstpEntry
        MAX-ACCESS   not-accessible
        STATUS       current
        DESCRIPTION  ""
        ::= { maintRstpGroup 1 }

    maintRstpEntry OBJECT-TYPE
        SYNTAX       MaintRstpEntry
        MAX-ACCESS   not-accessible
        STATUS       current
        DESCRIPTION  ""
        INDEX        { maintRstpBridgeIndex }
        ::= { maintRstpTable 1 }

    MaintRstpEntry ::= SEQUENCE {
        maintRstpBridgeIndex      Integer32,
        maintRstpNEAddress        IpAddress,
        maintRstpModeClearStatus  Integer32
    }

    maintRstpBridgeIndex OBJECT-TYPE
        SYNTAX       Integer32 (1..1)
        MAX-ACCESS   not-accessible
        STATUS       current
        DESCRIPTION  "Index of this table."
        ::= { maintRstpEntry 1 }

    maintRstpNEAddress OBJECT-TYPE
        SYNTAX       IpAddress
        MAX-ACCESS   not-accessible
        STATUS       current
        DESCRIPTION  "reserved."
        ::= { maintRstpEntry 2 }

    maintRstpModeClearStatus OBJECT-TYPE
        SYNTAX       Integer32
        MAX-ACCESS   read-write
        STATUS       current
        DESCRIPTION  "mode clear"
        ::= { maintRstpEntry 3 }

    maintLogGroup OBJECT IDENTIFIER
        ::= { maintenanceGroup 10 }

    maintClearLogTable OBJECT-TYPE
        SYNTAX       SEQUENCE OF MaintClearLogEntry
        MAX-ACCESS   not-accessible
        STATUS       current
        DESCRIPTION  ""
        ::= { maintLogGroup 1 }

    maintClearLogEntry OBJECT-TYPE
        SYNTAX       MaintClearLogEntry
        MAX-ACCESS   not-accessible
        STATUS       current
        DESCRIPTION  ""
        INDEX        { maintClearLogIndex }
        ::= { maintClearLogTable 1 }

    MaintClearLogEntry ::= SEQUENCE {
        maintClearLogIndex      Integer32,
        maintLogGroupNEAddress  IpAddress,
        localLogClear           INTEGER
    }

    maintClearLogIndex OBJECT-TYPE
        SYNTAX       Integer32 (1..1)
        MAX-ACCESS   not-accessible
        STATUS       current
        DESCRIPTION  "Index of this table."
        ::= { maintClearLogEntry 1 }

    maintLogGroupNEAddress OBJECT-TYPE
        SYNTAX       IpAddress
        MAX-ACCESS   not-accessible
        STATUS       current
        DESCRIPTION  "reserved."
        ::= { maintClearLogEntry 2 }

    localLogClear OBJECT-TYPE
        SYNTAX       INTEGER { cmd(0), evt(1), alm(2), all(3) }
        MAX-ACCESS   read-write
        STATUS       current
        DESCRIPTION
            "FLAG=TRAP|EVLOG
            LOGSTATUS='OFF(1),ON(2)'
            TRAP=controlEvent"
        ::= { maintClearLogEntry 3 }

    maintModemCardGroup OBJECT IDENTIFIER
        ::= { maintenanceGroup 12 }

    maintModemCardTable OBJECT-TYPE
        SYNTAX       SEQUENCE OF MaintModemCardEntry
        MAX-ACCESS   not-accessible
        STATUS       current
        DESCRIPTION  ""
        ::= { maintModemCardGroup 1 }

    maintModemCardEntry OBJECT-TYPE
        SYNTAX       MaintModemCardEntry
        MAX-ACCESS   not-accessible
        STATUS       current
        DESCRIPTION  ""
        INDEX        { maintModemCardIndex }
        ::= { maintModemCardTable 1 }

    MaintModemCardEntry ::= SEQUENCE {
        maintModemCardIndex          Integer32,
        maintModemCardNEAddress      IpAddress,
        maintModemCardLockinRequest  INTEGER
    }

    maintModemCardIndex OBJECT-TYPE
        SYNTAX       Integer32
        MAX-ACCESS   not-accessible
        STATUS       current
        DESCRIPTION  "Index of this table."
        ::= { maintModemCardEntry 1 }

    maintModemCardNEAddress OBJECT-TYPE
        SYNTAX       IpAddress
        MAX-ACCESS   not-accessible
        STATUS       current
        DESCRIPTION  "reserved."
        ::= { maintModemCardEntry 2 }

    maintModemCardLockinRequest OBJECT-TYPE
        SYNTAX       INTEGER { invalid(0), none(1), lockin(2) }
        MAX-ACCESS   read-write
        STATUS       current
        DESCRIPTION  "Lock-in Control"
        ::= { maintModemCardEntry 3 }

    maintEOWGroup OBJECT IDENTIFIER
        ::= { maintenanceGroup 16 }

    maintEOWTable OBJECT-TYPE
        SYNTAX       SEQUENCE OF MaintEOWEntry
        MAX-ACCESS   not-accessible
        STATUS       current
        DESCRIPTION  "This table contains EOW Call SW Control."
        ::= { maintEOWGroup 1 }

    maintEOWEntry OBJECT-TYPE
        SYNTAX       MaintEOWEntry
        MAX-ACCESS   not-accessible
        STATUS       current
        DESCRIPTION  ""
        INDEX        { maintEOWIndex }
        ::= { maintEOWTable 1 }

    MaintEOWEntry ::= SEQUENCE {
        maintEOWIndex       Integer32,
        maintEOWNEAddress   IpAddress,
        maintCallSwControl  INTEGER
    }

    maintEOWIndex OBJECT-TYPE
        SYNTAX       Integer32
        MAX-ACCESS   not-accessible
        STATUS       current
        DESCRIPTION  "Index of this table."
        ::= { maintEOWEntry 1 }

    maintEOWNEAddress OBJECT-TYPE
        SYNTAX       IpAddress
        MAX-ACCESS   not-accessible
        STATUS       current
        DESCRIPTION  "reserved."
        ::= { maintEOWEntry 2 }

    maintCallSwControl OBJECT-TYPE
        SYNTAX       INTEGER {
                         off(0),
                         modemSlotNo1(1),
                         modemSlotNo2(2),
                         modemSlotNo3(3),
                         modemSlotNo4(4),
                         modemSlotNo5(5),
                         modemSlotNo6(6),
                         modemSlotNo7(7),
                         modemSlotNo8(8),
                         modemSlotNo9(9),
                         modemSlotNo10(10),
                         modemSlotNo11(11),
                         modemSlotNo12(12),
                         modemSlotNo13(13),
                         modemSlotNo14(14)
                     }
        MAX-ACCESS   read-write
        STATUS       current
        DESCRIPTION  "Call SW Control."
        ::= { maintEOWEntry 3 }

    maintEOWIfTable OBJECT-TYPE
        SYNTAX       SEQUENCE OF MaintEOWIfEntry
        MAX-ACCESS   not-accessible
        STATUS       current
        DESCRIPTION  "This table contains EOW Buzzer Contorl."
        ::= { maintEOWGroup 2 }

    maintEOWIfEntry OBJECT-TYPE
        SYNTAX       MaintEOWIfEntry
        MAX-ACCESS   not-accessible
        STATUS       current
        DESCRIPTION  ""
        INDEX        { maintEOWIfIndex }
        ::= { maintEOWIfTable 1 }

    MaintEOWIfEntry ::= SEQUENCE {
        maintEOWIfIndex      InterfaceIndex,
        maintEOWIfNEAddress  IpAddress,
        maintEOWIfSwControl  INTEGER
    }

    maintEOWIfIndex OBJECT-TYPE
        SYNTAX       InterfaceIndex
        MAX-ACCESS   not-accessible
        STATUS       current
        DESCRIPTION  "Index of this table."
        ::= { maintEOWIfEntry 1 }

    maintEOWIfNEAddress OBJECT-TYPE
        SYNTAX       IpAddress
        MAX-ACCESS   not-accessible
        STATUS       current
        DESCRIPTION  "reserved."
        ::= { maintEOWIfEntry 2 }

    maintEOWIfSwControl OBJECT-TYPE
        SYNTAX       INTEGER { off(0), call(1) }
        MAX-ACCESS   read-write
        STATUS       current
        DESCRIPTION  "EOW Buzzer Contorl"
        ::= { maintEOWIfEntry 3 }

    maintProtectionGroup OBJECT IDENTIFIER
        ::= { maintenanceGroup 33 }

    maintStm1ApsTable OBJECT-TYPE
        SYNTAX       SEQUENCE OF MaintStm1ApsEntry
        MAX-ACCESS   not-accessible
        STATUS       current
        DESCRIPTION  ""
        ::= { maintProtectionGroup 1 }

    maintStm1ApsEntry OBJECT-TYPE
        SYNTAX       MaintStm1ApsEntry
        MAX-ACCESS   not-accessible
        STATUS       current
        DESCRIPTION  ""
        INDEX        { maintStm1ApsIfIndex }
        ::= { maintStm1ApsTable 1 }

    MaintStm1ApsEntry ::= SEQUENCE {
        maintStm1ApsIfIndex    InterfaceIndex,
        maintStm1ApsNEAddress  IpAddress,
        maintApsSwControl      INTEGER,
        maintApsSwMode         INTEGER
    }

    maintStm1ApsIfIndex OBJECT-TYPE
        SYNTAX       InterfaceIndex
        MAX-ACCESS   not-accessible
        STATUS       current
        DESCRIPTION  "Index of this table."
        ::= { maintStm1ApsEntry 1 }

    maintStm1ApsNEAddress OBJECT-TYPE
        SYNTAX       IpAddress
        MAX-ACCESS   not-accessible
        STATUS       current
        DESCRIPTION  "reserved."
        ::= { maintStm1ApsEntry 2 }

    maintApsSwControl OBJECT-TYPE
        SYNTAX       INTEGER {
                         clear(1),
                         forcedSwToProtection(2),
                         forcedSwToWork(3),
                         manualSwToProtection(4),
                         manualSwToWork(5)
                     }
        MAX-ACCESS   read-write
        STATUS       current
        DESCRIPTION  "APS Manual SW Control"
        ::= { maintStm1ApsEntry 3 }

    maintApsSwMode OBJECT-TYPE
        SYNTAX       INTEGER {
                         clear(1),
                         forcedSwToProtection(2),
                         forcedSwToWork(3),
                         manualSwToProtection(4),
                         manualSwToWork(5)
                     }
        MAX-ACCESS   read-only
        STATUS       current
        DESCRIPTION  "APS Manual SW Control Status"
        ::= { maintStm1ApsEntry 4 }

-----------------------------------------------
-- inventoryGroup Definitions
-----------------------------------------------

    invCardInfoGroup OBJECT IDENTIFIER
        ::= { inventoryGroup 1 }

    invMainInfoTable OBJECT-TYPE
        SYNTAX       SEQUENCE OF InvMainInfoEntry
        MAX-ACCESS   not-accessible
        STATUS       current
        DESCRIPTION
            "Equipment Inventory Information (IDU) - Main Board / Ctrl Card"
        ::= { invCardInfoGroup 1 }

    invMainInfoEntry OBJECT-TYPE
        SYNTAX       InvMainInfoEntry
        MAX-ACCESS   not-accessible
        STATUS       current
        DESCRIPTION  ""
        INDEX        { invMainInfoIndex }
        ::= { invMainInfoTable 1 }

    InvMainInfoEntry ::= SEQUENCE {
        invMainInfoIndex             Integer32,
        invMainInfoNEAddress         IpAddress,
        invMainName                  DisplayString,
        invMainCodeNo                DisplayString,
        invMainSerialNo              DisplayString,
        invMainManufacturedDate      DisplayString,
        invMainFirmVersion           DisplayString,
        invMainFirmVersionUncurrent  DisplayString,
        invMainCardHardVersion       DisplayString
    }

    invMainInfoIndex OBJECT-TYPE
        SYNTAX       Integer32 (1..1|17..18)
        MAX-ACCESS   not-accessible
        STATUS       current
        DESCRIPTION  "Index of this table."
        ::= { invMainInfoEntry 1 }

    invMainInfoNEAddress OBJECT-TYPE
        SYNTAX       IpAddress
        MAX-ACCESS   not-accessible
        STATUS       current
        DESCRIPTION  "reserved."
        ::= { invMainInfoEntry 2 }

    invMainName OBJECT-TYPE
        SYNTAX       DisplayString
        MAX-ACCESS   read-only
        STATUS       current
        DESCRIPTION  "Main Board / Ctrl Card Name."
        ::= { invMainInfoEntry 3 }

    invMainCodeNo OBJECT-TYPE
        SYNTAX       DisplayString
        MAX-ACCESS   read-only
        STATUS       current
        DESCRIPTION  "Main Board / Ctrl Card Code No."
        ::= { invMainInfoEntry 4 }

    invMainSerialNo OBJECT-TYPE
        SYNTAX       DisplayString (SIZE(1..8))
        MAX-ACCESS   read-write
        STATUS       current
        DESCRIPTION  "Main Board / Ctrl Card Serial No."
        ::= { invMainInfoEntry 5 }

    invMainManufacturedDate OBJECT-TYPE
        SYNTAX       DisplayString
        MAX-ACCESS   read-only
        STATUS       current
        DESCRIPTION  "Main Board / Ctrl Card Manufactured Date"
        ::= { invMainInfoEntry 6 }

    invMainFirmVersion OBJECT-TYPE
        SYNTAX       DisplayString
        MAX-ACCESS   read-only
        STATUS       current
        DESCRIPTION  "Main Board / Ctrl Card Firmware Version."
        ::= { invMainInfoEntry 7 }

    invMainFirmVersionUncurrent OBJECT-TYPE
        SYNTAX       DisplayString
        MAX-ACCESS   read-only
        STATUS       current
        DESCRIPTION  "Main Board / Ctrl Card Firmware Version (Uncurrent)."
        ::= { invMainInfoEntry 8 }

    invMainCardHardVersion OBJECT-TYPE
        SYNTAX       DisplayString
        MAX-ACCESS   read-only
        STATUS       current
        DESCRIPTION  "Main Board / Ctrl Card Hardware Version."
        ::= { invMainInfoEntry 9 }

    invCardInfoTable OBJECT-TYPE
        SYNTAX       SEQUENCE OF InvCardInfoEntry
        MAX-ACCESS   not-accessible
        STATUS       current
        DESCRIPTION
            "Equipment Inventory Information (IDU) - Option / Universal Card"
        ::= { invCardInfoGroup 2 }

    invCardInfoEntry OBJECT-TYPE
        SYNTAX       InvCardInfoEntry
        MAX-ACCESS   not-accessible
        STATUS       current
        DESCRIPTION  ""
        INDEX        { invCardInfoIndex }
        ::= { invCardInfoTable 1 }

    InvCardInfoEntry ::= SEQUENCE {
        invCardInfoIndex         Integer32,
        invCardInfoNEAddress     IpAddress,
        invCardName              DisplayString,
        invCardCodeNo            DisplayString,
        invCardSerialNo          DisplayString,
        invCardManufacturedDate  DisplayString,
        invCardFirmVersion       DisplayString,
        invCardHardVersion       DisplayString
    }

    invCardInfoIndex OBJECT-TYPE
        SYNTAX       Integer32
        MAX-ACCESS   not-accessible
        STATUS       current
        DESCRIPTION  "Index of this table."
        ::= { invCardInfoEntry 1 }

    invCardInfoNEAddress OBJECT-TYPE
        SYNTAX       IpAddress
        MAX-ACCESS   not-accessible
        STATUS       current
        DESCRIPTION  "reserved."
        ::= { invCardInfoEntry 2 }

    invCardName OBJECT-TYPE
        SYNTAX       DisplayString
        MAX-ACCESS   read-only
        STATUS       current
        DESCRIPTION
            "Card Name. when the card is removed, the value will be changed
            to '**'."
        ::= { invCardInfoEntry 3 }

    invCardCodeNo OBJECT-TYPE
        SYNTAX       DisplayString
        MAX-ACCESS   read-only
        STATUS       current
        DESCRIPTION
            "Card Code No. when the card is removed, the value will be
            changed to '**'."
        ::= { invCardInfoEntry 4 }

    invCardSerialNo OBJECT-TYPE
        SYNTAX       DisplayString
        MAX-ACCESS   read-only
        STATUS       current
        DESCRIPTION
            "Card Serial No. when the card is removed, the value will be
            changed to '**'."
        ::= { invCardInfoEntry 5 }

    invCardManufacturedDate OBJECT-TYPE
        SYNTAX       DisplayString
        MAX-ACCESS   read-only
        STATUS       current
        DESCRIPTION
            "Card Manufactured Date. when the card is removed, the value will
            be changed to '**'."
        ::= { invCardInfoEntry 6 }

    invCardFirmVersion OBJECT-TYPE
        SYNTAX       DisplayString
        MAX-ACCESS   read-only
        STATUS       current
        DESCRIPTION
            "Card Firmware Version. when the card is removed, the value will
            be changed to '**'."
        ::= { invCardInfoEntry 7 }

    invCardHardVersion OBJECT-TYPE
        SYNTAX       DisplayString
        MAX-ACCESS   read-only
        STATUS       current
        DESCRIPTION
            "Card Hardware Version. when the card is removed, the value will
            be changed to '**'."
        ::= { invCardInfoEntry 8 }

    invFPGAInfoTable OBJECT-TYPE
        SYNTAX       SEQUENCE OF InvFPGAInfoEntry
        MAX-ACCESS   not-accessible
        STATUS       current
        DESCRIPTION  "Equipment Inventory Information (IDU) - FPGA"
        ::= { inventoryGroup 2 }

    invFPGAInfoEntry OBJECT-TYPE
        SYNTAX       InvFPGAInfoEntry
        MAX-ACCESS   not-accessible
        STATUS       current
        DESCRIPTION  ""
        INDEX        { invFPGAInfoIndex }
        ::= { invFPGAInfoTable 1 }

    InvFPGAInfoEntry ::= SEQUENCE {
        invFPGAInfoIndex      Integer32,
        invFPGAInfoNEAddress  IpAddress,
        invFPGAName           DisplayString,
        invFPGACodeNo         DisplayString,
        invFPGAHardVersion    DisplayString
    }

    invFPGAInfoIndex OBJECT-TYPE
        SYNTAX       Integer32
        MAX-ACCESS   not-accessible
        STATUS       current
        DESCRIPTION  "Index of this table."
        ::= { invFPGAInfoEntry 1 }

    invFPGAInfoNEAddress OBJECT-TYPE
        SYNTAX       IpAddress
        MAX-ACCESS   not-accessible
        STATUS       current
        DESCRIPTION  "reserved."
        ::= { invFPGAInfoEntry 2 }

    invFPGAName OBJECT-TYPE
        SYNTAX       DisplayString
        MAX-ACCESS   read-only
        STATUS       current
        DESCRIPTION
            "FPGA Name. when the card is removed, the value will be changed
            to '**'."
        ::= { invFPGAInfoEntry 3 }

    invFPGACodeNo OBJECT-TYPE
        SYNTAX       DisplayString
        MAX-ACCESS   read-only
        STATUS       current
        DESCRIPTION
            "FPGA Code No. when the card is removed, the value will be
            changed to '**'."
        ::= { invFPGAInfoEntry 4 }

    invFPGAHardVersion OBJECT-TYPE
        SYNTAX       DisplayString
        MAX-ACCESS   read-only
        STATUS       current
        DESCRIPTION
            "FPGA Version. when the card is removed, the value will be
            changed to '**'."
        ::= { invFPGAInfoEntry 5 }

    invModuleInfoOduTable OBJECT-TYPE
        SYNTAX       SEQUENCE OF InvModuleInfoOduEntry
        MAX-ACCESS   not-accessible
        STATUS       current
        DESCRIPTION  "Equipment Inventory Information (ODU)"
        ::= { inventoryGroup 3 }

    invModuleInfoOduEntry OBJECT-TYPE
        SYNTAX       InvModuleInfoOduEntry
        MAX-ACCESS   not-accessible
        STATUS       current
        DESCRIPTION  ""
        INDEX        { invModuleInfoOduIfIndex }
        ::= { invModuleInfoOduTable 1 }

    InvModuleInfoOduEntry ::= SEQUENCE {
        invModuleInfoOduIfIndex          InterfaceIndex,
        invModuleInfoOduNEAddress        IpAddress,
        invOduCardName                   DisplayString,
        invOduCardCodeNo                 DisplayString,
        invOduCardHardVersion            DisplayString,
        invOduCardSerialNo               DisplayString,
        invOduCardManufacturedDate       DisplayString,
        invOduCardFirmCurrentVersion     DisplayString,
        invOduCardFirmUncurrentVersion   DisplayString,
        invOduProvRangeATPCMax           Integer32,
        invOduProvRangeATPCMin           Integer32,
        invOduProvRangeMTPCMax           Integer32,
        invOduProvRangeMTPCMin           Integer32,
        invOduProvRangeRxThresholdMax    Integer32,
        invOduProvRangeRxThresholdMin    Integer32,
        invOduProvRangeHysteresisPermit  INTEGER,
        invOduProvRangeHysteresisMax     Integer32,
        invOduProvRangeHysteresisMin     Integer32,
        invOduFreqInfoTxStartFrequency   DisplayString,
        invOduFreqInfoTxStopFrequency    DisplayString,
        invOduFreqInfoRxStartFrequency   DisplayString,
        invOduFreqInfoRxStopFrequency    DisplayString,
        invOduFreqInfoFrequencyStep      DisplayString,
        invOduFreqInfoShiftFrequency     DisplayString,
        invOduFreqInfoUpperLower         INTEGER,
        invOduFreqInfoTxPhase            INTEGER,
        invOduFreqInfoRxPhase            INTEGER,
        invOduFreqInfoSubBand            DisplayString,
        invOduFreqInfoTxRxIndependence   INTEGER,
        invOduFreqInfoSupportedIpe       INTEGER,
        invOduFreqInfoSubBand1           DisplayString,
        invOduFreqInfoSubBand2           DisplayString,
        invOduFreqInfoSubBand3           DisplayString,
        invOduFreqInfoSubBand4           DisplayString,
        invOduFreqInfoSubBand5           DisplayString,
        invOduFreqInfoSubBand6           DisplayString,
        invOduFreqInfoSubBand7           DisplayString,
        invOduFreqInfoSubBand8           DisplayString,
        invOduFreqInfoSubBand9           DisplayString,
        invOduFreqInfoSubBand10          DisplayString
    }

    invModuleInfoOduIfIndex OBJECT-TYPE
        SYNTAX       InterfaceIndex
        MAX-ACCESS   not-accessible
        STATUS       current
        DESCRIPTION  "Index of this table."
        ::= { invModuleInfoOduEntry 1 }

    invModuleInfoOduNEAddress OBJECT-TYPE
        SYNTAX       IpAddress
        MAX-ACCESS   not-accessible
        STATUS       current
        DESCRIPTION  "reserved."
        ::= { invModuleInfoOduEntry 2 }

    invOduCardName OBJECT-TYPE
        SYNTAX       DisplayString
        MAX-ACCESS   read-only
        STATUS       current
        DESCRIPTION
            "ODU Name. when the ODU is removed or disconnected, the value
            will be changed to '**'."
        ::= { invModuleInfoOduEntry 3 }

    invOduCardCodeNo OBJECT-TYPE
        SYNTAX       DisplayString
        MAX-ACCESS   read-only
        STATUS       current
        DESCRIPTION
            "ODU Code Name. when the ODU is removed or disconnected, the
            value will be changed to '**'."
        ::= { invModuleInfoOduEntry 4 }

    invOduCardHardVersion OBJECT-TYPE
        SYNTAX       DisplayString
        MAX-ACCESS   read-only
        STATUS       current
        DESCRIPTION
            "ODU Hardware version. when the ODU is removed or disconnected,
            the value will be changed to '**'."
        ::= { invModuleInfoOduEntry 5 }

    invOduCardSerialNo OBJECT-TYPE
        SYNTAX       DisplayString
        MAX-ACCESS   read-only
        STATUS       current
        DESCRIPTION
            "ODU Serial No. when the ODU is removed or disconnected, the
            value will be changed to '**'."
        ::= { invModuleInfoOduEntry 6 }

    invOduCardManufacturedDate OBJECT-TYPE
        SYNTAX       DisplayString
        MAX-ACCESS   read-only
        STATUS       current
        DESCRIPTION
            "ODU Manufactured Date. when the ODU is removed or disconnected,
            the value will be changed to '**'."
        ::= { invModuleInfoOduEntry 7 }

    invOduCardFirmCurrentVersion OBJECT-TYPE
        SYNTAX       DisplayString
        MAX-ACCESS   read-only
        STATUS       current
        DESCRIPTION
            "ODU Firmware information (current). when the ODU is removed or
            disconnected, the value will be changed to '**'."
        ::= { invModuleInfoOduEntry 8 }

    invOduCardFirmUncurrentVersion OBJECT-TYPE
        SYNTAX       DisplayString
        MAX-ACCESS   read-only
        STATUS       current
        DESCRIPTION
            "ODU Firmware information (uncurrent). when the ODU is removed or
            disconnected, the value will be changed to '**'."
        ::= { invModuleInfoOduEntry 9 }

    invOduProvRangeATPCMax OBJECT-TYPE
        SYNTAX       Integer32
        MAX-ACCESS   read-only
        STATUS       current
        DESCRIPTION  "ODU Frequency Information - Range ATPC MAX (dbm)"
        ::= { invModuleInfoOduEntry 10 }

    invOduProvRangeATPCMin OBJECT-TYPE
        SYNTAX       Integer32
        MAX-ACCESS   read-only
        STATUS       current
        DESCRIPTION  "ODU Frequency Information - Range ATPC MIN (dbm)"
        ::= { invModuleInfoOduEntry 11 }

    invOduProvRangeMTPCMax OBJECT-TYPE
        SYNTAX       Integer32
        MAX-ACCESS   read-only
        STATUS       current
        DESCRIPTION  "ODU Frequency Information - Range MTPC MAX (dbm)"
        ::= { invModuleInfoOduEntry 12 }

    invOduProvRangeMTPCMin OBJECT-TYPE
        SYNTAX       Integer32
        MAX-ACCESS   read-only
        STATUS       current
        DESCRIPTION  "ODU Frequency Information - Range MTPC MIN (dbm)"
        ::= { invModuleInfoOduEntry 13 }

    invOduProvRangeRxThresholdMax OBJECT-TYPE
        SYNTAX       Integer32
        MAX-ACCESS   read-only
        STATUS       current
        DESCRIPTION
            "ODU Frequency Information - Range RX Threshold MAX (dbm)"
        ::= { invModuleInfoOduEntry 14 }

    invOduProvRangeRxThresholdMin OBJECT-TYPE
        SYNTAX       Integer32
        MAX-ACCESS   read-only
        STATUS       current
        DESCRIPTION
            "ODU Frequency Information - Range RX Threshold MIN (dbm)"
        ::= { invModuleInfoOduEntry 15 }

    invOduProvRangeHysteresisPermit OBJECT-TYPE
        SYNTAX       INTEGER { deny(0), permit(255) }
        MAX-ACCESS   read-only
        STATUS       current
        DESCRIPTION  "ODU Frequency Information - Range Hysteresis Permit"
        ::= { invModuleInfoOduEntry 16 }

    invOduProvRangeHysteresisMax OBJECT-TYPE
        SYNTAX       Integer32
        MAX-ACCESS   read-only
        STATUS       current
        DESCRIPTION  "ODU Range Hysteresis MAX (dB)"
        ::= { invModuleInfoOduEntry 17 }

    invOduProvRangeHysteresisMin OBJECT-TYPE
        SYNTAX       Integer32
        MAX-ACCESS   read-only
        STATUS       current
        DESCRIPTION  "ODU Range Hysteresis MIN (dB)"
        ::= { invModuleInfoOduEntry 18 }

    invOduFreqInfoTxStartFrequency OBJECT-TYPE
        SYNTAX       DisplayString
        MAX-ACCESS   read-only
        STATUS       current
        DESCRIPTION  "ODU Frequency Information - TX Start Frequency (MHz)"
        ::= { invModuleInfoOduEntry 19 }

    invOduFreqInfoTxStopFrequency OBJECT-TYPE
        SYNTAX       DisplayString
        MAX-ACCESS   read-only
        STATUS       current
        DESCRIPTION  "ODU Frequency Information - TX Stop Frequency (MHz)"
        ::= { invModuleInfoOduEntry 20 }

    invOduFreqInfoRxStartFrequency OBJECT-TYPE
        SYNTAX       DisplayString
        MAX-ACCESS   read-only
        STATUS       current
        DESCRIPTION  "ODU Frequency Information - RX Start Frequency (MHz)"
        ::= { invModuleInfoOduEntry 21 }

    invOduFreqInfoRxStopFrequency OBJECT-TYPE
        SYNTAX       DisplayString
        MAX-ACCESS   read-only
        STATUS       current
        DESCRIPTION  "ODU Frequency Information - RX Stop Frequency (MHz)"
        ::= { invModuleInfoOduEntry 22 }

    invOduFreqInfoFrequencyStep OBJECT-TYPE
        SYNTAX       DisplayString
        MAX-ACCESS   read-only
        STATUS       current
        DESCRIPTION  "ODU Frequency Information - Frequency Step (MHz)"
        ::= { invModuleInfoOduEntry 23 }

    invOduFreqInfoShiftFrequency OBJECT-TYPE
        SYNTAX       DisplayString
        MAX-ACCESS   read-only
        STATUS       current
        DESCRIPTION  "ODU Frequency Information - Shift Frequency (MHz)"
        ::= { invModuleInfoOduEntry 24 }

    invOduFreqInfoUpperLower OBJECT-TYPE
        SYNTAX       INTEGER { lower(1), upper(2) }
        MAX-ACCESS   read-only
        STATUS       current
        DESCRIPTION  "ODU Frequency Information - Upper / Lower"
        ::= { invModuleInfoOduEntry 25 }

    invOduFreqInfoTxPhase OBJECT-TYPE
        SYNTAX       INTEGER { forward(1), reverse(2) }
        MAX-ACCESS   read-only
        STATUS       current
        DESCRIPTION  "ODU Frequency Information - TX Phase"
        ::= { invModuleInfoOduEntry 26 }

    invOduFreqInfoRxPhase OBJECT-TYPE
        SYNTAX       INTEGER { forward(1), reverse(2) }
        MAX-ACCESS   read-only
        STATUS       current
        DESCRIPTION  "ODU Frequency Information - RX Phase"
        ::= { invModuleInfoOduEntry 27 }

    invOduFreqInfoSubBand OBJECT-TYPE
        SYNTAX       DisplayString
        MAX-ACCESS   read-only
        STATUS       current
        DESCRIPTION  "ODU Frequency Information - Sub Band"
        ::= { invModuleInfoOduEntry 28 }

    invOduFreqInfoTxRxIndependence OBJECT-TYPE
        SYNTAX       INTEGER { notIndependence(1), independence(2) }
        MAX-ACCESS   read-only
        STATUS       current
        DESCRIPTION  "ODU Frequency Information - TX / RX Independence"
        ::= { invModuleInfoOduEntry 29 }

    invOduFreqInfoSupportedIpe OBJECT-TYPE
        SYNTAX       INTEGER { notSupported(1), supported(2) }
        MAX-ACCESS   read-only
        STATUS       current
        DESCRIPTION  "ODU Frequency Information - Supported iPASOLINK"
        ::= { invModuleInfoOduEntry 30 }

    invOduFreqInfoSubBand1 OBJECT-TYPE
        SYNTAX       DisplayString
        MAX-ACCESS   read-only
        STATUS       current
        DESCRIPTION  "ODU Frequency Information - Sub Band 01"
        ::= { invModuleInfoOduEntry 31 }

    invOduFreqInfoSubBand2 OBJECT-TYPE
        SYNTAX       DisplayString
        MAX-ACCESS   read-only
        STATUS       current
        DESCRIPTION  "ODU Frequency Information - Sub Band 02"
        ::= { invModuleInfoOduEntry 32 }

    invOduFreqInfoSubBand3 OBJECT-TYPE
        SYNTAX       DisplayString
        MAX-ACCESS   read-only
        STATUS       current
        DESCRIPTION  "ODU Frequency Information - Sub Band 03"
        ::= { invModuleInfoOduEntry 33 }

    invOduFreqInfoSubBand4 OBJECT-TYPE
        SYNTAX       DisplayString
        MAX-ACCESS   read-only
        STATUS       current
        DESCRIPTION  "ODU Frequency Information - Sub Band 04"
        ::= { invModuleInfoOduEntry 34 }

    invOduFreqInfoSubBand5 OBJECT-TYPE
        SYNTAX       DisplayString
        MAX-ACCESS   read-only
        STATUS       current
        DESCRIPTION  "ODU Frequency Information - Sub Band 05"
        ::= { invModuleInfoOduEntry 35 }

    invOduFreqInfoSubBand6 OBJECT-TYPE
        SYNTAX       DisplayString
        MAX-ACCESS   read-only
        STATUS       current
        DESCRIPTION  "ODU Frequency Information - Sub Band 06"
        ::= { invModuleInfoOduEntry 36 }

    invOduFreqInfoSubBand7 OBJECT-TYPE
        SYNTAX       DisplayString
        MAX-ACCESS   read-only
        STATUS       current
        DESCRIPTION  "ODU Frequency Information - Sub Band 07"
        ::= { invModuleInfoOduEntry 37 }

    invOduFreqInfoSubBand8 OBJECT-TYPE
        SYNTAX       DisplayString
        MAX-ACCESS   read-only
        STATUS       current
        DESCRIPTION  "ODU Frequency Information - Sub Band 08"
        ::= { invModuleInfoOduEntry 38 }

    invOduFreqInfoSubBand9 OBJECT-TYPE
        SYNTAX       DisplayString
        MAX-ACCESS   read-only
        STATUS       current
        DESCRIPTION  "ODU Frequency Information - Sub Band 09"
        ::= { invModuleInfoOduEntry 39 }

    invOduFreqInfoSubBand10 OBJECT-TYPE
        SYNTAX       DisplayString
        MAX-ACCESS   read-only
        STATUS       current
        DESCRIPTION  "ODU Frequency Information - Sub Band 10"
        ::= { invModuleInfoOduEntry 40 }

    invUpdateInfoTable OBJECT-TYPE
        SYNTAX       SEQUENCE OF InvUpdateInfoEntry
        MAX-ACCESS   not-accessible
        STATUS       current
        DESCRIPTION  "Inventory Update Information"
        ::= { inventoryGroup 4 }

    invUpdateInfoEntry OBJECT-TYPE
        SYNTAX       InvUpdateInfoEntry
        MAX-ACCESS   not-accessible
        STATUS       current
        DESCRIPTION  ""
        INDEX        { invUpdateInfoIndex }
        ::= { invUpdateInfoTable 1 }

    InvUpdateInfoEntry ::= SEQUENCE {
        invUpdateInfoIndex      Integer32,
        invUpdateInfoNEAddress  IpAddress,
        invUpdateInfoSummary    OCTET STRING
    }

    invUpdateInfoIndex OBJECT-TYPE
        SYNTAX       Integer32 (1..1)
        MAX-ACCESS   not-accessible
        STATUS       current
        DESCRIPTION  "Index of this table."
        ::= { invUpdateInfoEntry 1 }

    invUpdateInfoNEAddress OBJECT-TYPE
        SYNTAX       IpAddress
        MAX-ACCESS   not-accessible
        STATUS       current
        DESCRIPTION  "reserved."
        ::= { invUpdateInfoEntry 2 }

    invUpdateInfoSummary OBJECT-TYPE
        SYNTAX       OCTET STRING (SIZE(12..12|20..20))
        MAX-ACCESS   read-only
        STATUS       current
        DESCRIPTION  "Inventory Update Information Summary"
        ::= { invUpdateInfoEntry 3 }

    invSfpInfoTable OBJECT-TYPE
        SYNTAX       SEQUENCE OF InvSfpInfoEntry
        MAX-ACCESS   not-accessible
        STATUS       current
        DESCRIPTION  "SFP / XFP Information"
        ::= { inventoryGroup 5 }

    invSfpInfoEntry OBJECT-TYPE
        SYNTAX       InvSfpInfoEntry
        MAX-ACCESS   not-accessible
        STATUS       current
        DESCRIPTION  ""
        INDEX        { invSfpInfoIfIndex }
        ::= { invSfpInfoTable 1 }

    InvSfpInfoEntry ::= SEQUENCE {
        invSfpInfoIfIndex          InterfaceIndex,
        invSfpInfoNEAddress        IpAddress,
        invSfpVendorName           DisplayString,
        invSfpVendorPn             DisplayString,
        invSfpVendorVer            DisplayString,
        invSfpVendorSn             DisplayString,
        invSfpType                 DisplayString,
        invSfpManufacturedDate     DisplayString,
        invSfpSupportedWavelength  DisplayString,
        invSfpSupportedLinkLength  DisplayString
    }

    invSfpInfoIfIndex OBJECT-TYPE
        SYNTAX       InterfaceIndex
        MAX-ACCESS   not-accessible
        STATUS       current
        DESCRIPTION  "Index of this table."
        ::= { invSfpInfoEntry 1 }

    invSfpInfoNEAddress OBJECT-TYPE
        SYNTAX       IpAddress
        MAX-ACCESS   not-accessible
        STATUS       current
        DESCRIPTION  "reserved."
        ::= { invSfpInfoEntry 2 }

    invSfpVendorName OBJECT-TYPE
        SYNTAX       DisplayString
        MAX-ACCESS   read-only
        STATUS       current
        DESCRIPTION  "Vendor Name"
        ::= { invSfpInfoEntry 3 }

    invSfpVendorPn OBJECT-TYPE
        SYNTAX       DisplayString
        MAX-ACCESS   read-only
        STATUS       current
        DESCRIPTION  "Part Number"
        ::= { invSfpInfoEntry 4 }

    invSfpVendorVer OBJECT-TYPE
        SYNTAX       DisplayString
        MAX-ACCESS   read-only
        STATUS       current
        DESCRIPTION  "Vendor Revision Number"
        ::= { invSfpInfoEntry 5 }

    invSfpVendorSn OBJECT-TYPE
        SYNTAX       DisplayString
        MAX-ACCESS   read-only
        STATUS       current
        DESCRIPTION  "Vendor Serial Number"
        ::= { invSfpInfoEntry 6 }

    invSfpType OBJECT-TYPE
        SYNTAX       DisplayString
        MAX-ACCESS   read-only
        STATUS       current
        DESCRIPTION  "SFP Type"
        ::= { invSfpInfoEntry 7 }

    invSfpManufacturedDate OBJECT-TYPE
        SYNTAX       DisplayString
        MAX-ACCESS   read-only
        STATUS       current
        DESCRIPTION  "SFP Manufactured Date"
        ::= { invSfpInfoEntry 8 }

    invSfpSupportedWavelength OBJECT-TYPE
        SYNTAX       DisplayString
        UNITS        "nm"
        MAX-ACCESS   read-only
        STATUS       current
        DESCRIPTION
            "Wavelength supported by SFP/XFP/SFP+.
            If the SFP media type is not optical, this object will show the
            value '0'."
        ::= { invSfpInfoEntry 9 }

    invSfpSupportedLinkLength OBJECT-TYPE
        SYNTAX       DisplayString
        UNITS        "km"
        MAX-ACCESS   read-only
        STATUS       current
        DESCRIPTION  "Link length supported by SFP/XFP/SFP+."
        ::= { invSfpInfoEntry 10 }

    invSoftkeyInfoTable OBJECT-TYPE
        SYNTAX       SEQUENCE OF InvSoftkeyInfoEntry
        MAX-ACCESS   not-accessible
        STATUS       current
        DESCRIPTION  "Software Key Information."
        ::= { inventoryGroup 6 }

    invSoftkeyInfoEntry OBJECT-TYPE
        SYNTAX       InvSoftkeyInfoEntry
        MAX-ACCESS   not-accessible
        STATUS       current
        DESCRIPTION  ""
        INDEX        { invSoftkeyInfoIndex }
        ::= { invSoftkeyInfoTable 1 }

    InvSoftkeyInfoEntry ::= SEQUENCE {
        invSoftkeyInfoIndex          Integer32,
        invSoftkeyInfoNEAddress      IpAddress,
        invSoftkeySerialNo           DisplayString,
        invSupportabilityInfoFw      OCTET STRING,
        invSupportabilityInfoKey     OCTET STRING,
        invSupportabilityInfoValid   OCTET STRING,
        invCapa10MaxE1Rst            OCTET STRING,
        invCapa20MaxE1Rst            OCTET STRING,
        invCapa50MaxE1Rst            OCTET STRING,
        invCapa100MaxE1Rst           OCTET STRING,
        invCapa150MaxE1Rst           OCTET STRING,
        invCapa200MaxE1Rst           OCTET STRING,
        invCapa300MaxE1Rst           OCTET STRING,
        invCapa400MaxE1Rst           OCTET STRING,
        invSoftkeyEquipmentSerialNo  DisplayString
    }

    invSoftkeyInfoIndex OBJECT-TYPE
        SYNTAX       Integer32 (1..1)
        MAX-ACCESS   not-accessible
        STATUS       current
        DESCRIPTION  "Index of this table."
        ::= { invSoftkeyInfoEntry 1 }

    invSoftkeyInfoNEAddress OBJECT-TYPE
        SYNTAX       IpAddress
        MAX-ACCESS   not-accessible
        STATUS       current
        DESCRIPTION  "reserved."
        ::= { invSoftkeyInfoEntry 2 }

    invSoftkeySerialNo OBJECT-TYPE
        SYNTAX       DisplayString
        MAX-ACCESS   read-only
        STATUS       current
        DESCRIPTION  "Software Key Serial No."
        ::= { invSoftkeyInfoEntry 3 }

    invSupportabilityInfoFw OBJECT-TYPE
        SYNTAX       OCTET STRING (SIZE(32..32|40..40|52..52|68..68))
        MAX-ACCESS   read-only
        STATUS       current
        DESCRIPTION  "Supportability (Firmware)"
        ::= { invSoftkeyInfoEntry 4 }

    invSupportabilityInfoKey OBJECT-TYPE
        SYNTAX       OCTET STRING (SIZE(32..32|40..40|52..52|68..68))
        MAX-ACCESS   read-only
        STATUS       current
        DESCRIPTION  "Supportability (Software Key)"
        ::= { invSoftkeyInfoEntry 5 }

    invSupportabilityInfoValid OBJECT-TYPE
        SYNTAX       OCTET STRING (SIZE(32..32|40..40|52..52|68..68))
        MAX-ACCESS   read-only
        STATUS       current
        DESCRIPTION  "Supportability (Current)"
        ::= { invSoftkeyInfoEntry 6 }

    invCapa10MaxE1Rst OBJECT-TYPE
        SYNTAX       OCTET STRING (SIZE(160..160|192..192))
        MAX-ACCESS   read-only
        STATUS       current
        DESCRIPTION
            "Maximum Available E1/RST Connections for 10M Capacity."
        ::= { invSoftkeyInfoEntry 7 }

    invCapa20MaxE1Rst OBJECT-TYPE
        SYNTAX       OCTET STRING (SIZE(160..160|192..192))
        MAX-ACCESS   read-only
        STATUS       current
        DESCRIPTION
            "Maximum Available E1/RST Connections for 20M Capacity."
        ::= { invSoftkeyInfoEntry 8 }

    invCapa50MaxE1Rst OBJECT-TYPE
        SYNTAX       OCTET STRING (SIZE(160..160|192..192))
        MAX-ACCESS   read-only
        STATUS       current
        DESCRIPTION
            "Maximum Available E1/RST Connections for 50M Capacity."
        ::= { invSoftkeyInfoEntry 9 }

    invCapa100MaxE1Rst OBJECT-TYPE
        SYNTAX       OCTET STRING (SIZE(160..160|192..192))
        MAX-ACCESS   read-only
        STATUS       current
        DESCRIPTION
            "Maximum Available E1/RST Connections for 100M Capacity."
        ::= { invSoftkeyInfoEntry 10 }

    invCapa150MaxE1Rst OBJECT-TYPE
        SYNTAX       OCTET STRING (SIZE(160..160|192..192))
        MAX-ACCESS   read-only
        STATUS       current
        DESCRIPTION
            "Maximum Available E1/RST Connections for 150M Capacity."
        ::= { invSoftkeyInfoEntry 11 }

    invCapa200MaxE1Rst OBJECT-TYPE
        SYNTAX       OCTET STRING (SIZE(160..160|192..192))
        MAX-ACCESS   read-only
        STATUS       current
        DESCRIPTION
            "Maximum Available E1/RST Connections for 200M Capacity."
        ::= { invSoftkeyInfoEntry 12 }

    invCapa300MaxE1Rst OBJECT-TYPE
        SYNTAX       OCTET STRING (SIZE(160..160|192..192))
        MAX-ACCESS   read-only
        STATUS       current
        DESCRIPTION
            "Maximum Available E1/RST Connections for 300M Capacity."
        ::= { invSoftkeyInfoEntry 13 }

    invCapa400MaxE1Rst OBJECT-TYPE
        SYNTAX       OCTET STRING (SIZE(160..160|192..192))
        MAX-ACCESS   read-only
        STATUS       current
        DESCRIPTION
            "Maximum Available E1/RST Connections for 400M Capacity."
        ::= { invSoftkeyInfoEntry 14 }

    invSoftkeyEquipmentSerialNo OBJECT-TYPE
        SYNTAX       DisplayString
        MAX-ACCESS   read-only
        STATUS       current
        DESCRIPTION  "Equipment Serial Number."
        ::= { invSoftkeyInfoEntry 15 }

    invClk2mInfoTable OBJECT-TYPE
        SYNTAX       SEQUENCE OF InvClk2mInfoEntry
        MAX-ACCESS   not-accessible
        STATUS       current
        DESCRIPTION
            "Equipment Inventory Information (IDU) - Main Board / Ctrl Card
            (EXT CLK)"
        ::= { inventoryGroup 7 }

    invClk2mInfoEntry OBJECT-TYPE
        SYNTAX       InvClk2mInfoEntry
        MAX-ACCESS   not-accessible
        STATUS       current
        DESCRIPTION  ""
        INDEX        { invClk2mInfoIndex }
        ::= { invClk2mInfoTable 1 }

    InvClk2mInfoEntry ::= SEQUENCE {
        invClk2mInfoIndex             INTEGER,
        invClk2mInfoNEAddress         IpAddress,
        invClk2mCardName              DisplayString,
        invClk2mCardCodeNo            DisplayString,
        invClk2mCardSerialNo          DisplayString,
        invClk2mCardManufacturedDate  DisplayString,
        invClk2mFPGAName              DisplayString,
        invClk2mFPGACodeNo            DisplayString,
        invClk2mFPGAHardVersion       DisplayString,
        invClk2mCardHardVersion       DisplayString
    }

    invClk2mInfoIndex OBJECT-TYPE
        SYNTAX       INTEGER { extclk(1), extclk2(2) }
        MAX-ACCESS   not-accessible
        STATUS       current
        DESCRIPTION  "Index of this table."
        ::= { invClk2mInfoEntry 1 }

    invClk2mInfoNEAddress OBJECT-TYPE
        SYNTAX       IpAddress
        MAX-ACCESS   not-accessible
        STATUS       current
        DESCRIPTION  "reserved."
        ::= { invClk2mInfoEntry 2 }

    invClk2mCardName OBJECT-TYPE
        SYNTAX       DisplayString
        MAX-ACCESS   read-only
        STATUS       current
        DESCRIPTION  "Name"
        ::= { invClk2mInfoEntry 3 }

    invClk2mCardCodeNo OBJECT-TYPE
        SYNTAX       DisplayString
        MAX-ACCESS   read-only
        STATUS       current
        DESCRIPTION  "Code No."
        ::= { invClk2mInfoEntry 4 }

    invClk2mCardSerialNo OBJECT-TYPE
        SYNTAX       DisplayString
        MAX-ACCESS   read-only
        STATUS       current
        DESCRIPTION  "Serial No."
        ::= { invClk2mInfoEntry 5 }

    invClk2mCardManufacturedDate OBJECT-TYPE
        SYNTAX       DisplayString
        MAX-ACCESS   read-only
        STATUS       current
        DESCRIPTION  "Manufactured Date"
        ::= { invClk2mInfoEntry 6 }

    invClk2mFPGAName OBJECT-TYPE
        SYNTAX       DisplayString
        MAX-ACCESS   read-only
        STATUS       current
        DESCRIPTION  "FPGA Name"
        ::= { invClk2mInfoEntry 7 }

    invClk2mFPGACodeNo OBJECT-TYPE
        SYNTAX       DisplayString
        MAX-ACCESS   read-only
        STATUS       current
        DESCRIPTION  "FPGA Code No."
        ::= { invClk2mInfoEntry 8 }

    invClk2mFPGAHardVersion OBJECT-TYPE
        SYNTAX       DisplayString
        MAX-ACCESS   read-only
        STATUS       current
        DESCRIPTION  "FPGA Version."
        ::= { invClk2mInfoEntry 9 }

    invClk2mCardHardVersion OBJECT-TYPE
        SYNTAX       DisplayString
        MAX-ACCESS   read-only
        STATUS       current
        DESCRIPTION  "Hardware Version."
        ::= { invClk2mInfoEntry 10 }

    invMacAddressInfoTable OBJECT-TYPE
        SYNTAX       SEQUENCE OF InvMacAddressInfoEntry
        MAX-ACCESS   not-accessible
        STATUS       current
        DESCRIPTION
            "Equipment Inventory Information - Mac Address Information"
        ::= { inventoryGroup 8 }

    invMacAddressInfoEntry OBJECT-TYPE
        SYNTAX       InvMacAddressInfoEntry
        MAX-ACCESS   not-accessible
        STATUS       current
        DESCRIPTION  ""
        INDEX        { invMacAddressInfoIfIndex }
        ::= { invMacAddressInfoTable 1 }

    InvMacAddressInfoEntry ::= SEQUENCE {
        invMacAddressInfoIfIndex    InterfaceIndex,
        invMacAddressInfoNEAddress  IpAddress,
        invMacAddress               MacAddress
    }

    invMacAddressInfoIfIndex OBJECT-TYPE
        SYNTAX       InterfaceIndex
        MAX-ACCESS   not-accessible
        STATUS       current
        DESCRIPTION  "Index of this table."
        ::= { invMacAddressInfoEntry 1 }

    invMacAddressInfoNEAddress OBJECT-TYPE
        SYNTAX       IpAddress
        MAX-ACCESS   not-accessible
        STATUS       current
        DESCRIPTION  "reserved."
        ::= { invMacAddressInfoEntry 2 }

    invMacAddress OBJECT-TYPE
        SYNTAX       MacAddress
        MAX-ACCESS   read-only
        STATUS       current
        DESCRIPTION  "Mac Address which assigned to that port."
        ::= { invMacAddressInfoEntry 3 }

    invModemParamInfoTable OBJECT-TYPE
        SYNTAX       SEQUENCE OF InvModemParamInfoEntry
        MAX-ACCESS   not-accessible
        STATUS       current
        DESCRIPTION
            "Equipment Inventory Information (IDU) - MODEM Parameter"
        ::= { inventoryGroup 9 }

    invModemParamInfoEntry OBJECT-TYPE
        SYNTAX       InvModemParamInfoEntry
        MAX-ACCESS   not-accessible
        STATUS       current
        DESCRIPTION  ""
        INDEX        { invModemParamInfoIfIndex }
        ::= { invModemParamInfoTable 1 }

    InvModemParamInfoEntry ::= SEQUENCE {
        invModemParamInfoIfIndex    InterfaceIndex,
        invModemParamInfoNEAddress  IpAddress,
        invModemParamVersion        DisplayString
    }

    invModemParamInfoIfIndex OBJECT-TYPE
        SYNTAX       InterfaceIndex
        MAX-ACCESS   not-accessible
        STATUS       current
        DESCRIPTION  "Index of this table."
        ::= { invModemParamInfoEntry 1 }

    invModemParamInfoNEAddress OBJECT-TYPE
        SYNTAX       IpAddress
        MAX-ACCESS   not-accessible
        STATUS       current
        DESCRIPTION  "reserved."
        ::= { invModemParamInfoEntry 2 }

    invModemParamVersion OBJECT-TYPE
        SYNTAX       DisplayString
        MAX-ACCESS   read-only
        STATUS       current
        DESCRIPTION
            "Parameter Information
            MIB format of invModemParamVersion is xx.yy."
        ::= { invModemParamInfoEntry 3 }

    invChassisInfoTable OBJECT-TYPE
        SYNTAX       SEQUENCE OF InvChassisInfoEntry
        MAX-ACCESS   not-accessible
        STATUS       current
        DESCRIPTION  "Equipment Inventory Information (IDU) - Chassis"
        ::= { inventoryGroup 10 }

    invChassisInfoEntry OBJECT-TYPE
        SYNTAX       InvChassisInfoEntry
        MAX-ACCESS   not-accessible
        STATUS       current
        DESCRIPTION  ""
        INDEX        { invChassisInfoIndex }
        ::= { invChassisInfoTable 1 }

    InvChassisInfoEntry ::= SEQUENCE {
        invChassisInfoIndex         Integer32,
        invChassisInfoNEAddress     IpAddress,
        invChassisName              DisplayString,
        invChassisCodeNo            DisplayString,
        invChassisSerialNo          DisplayString,
        invChassisManufacturedDate  DisplayString,
        invChassisFirmVersion       DisplayString,
        invChassisHardVersion       DisplayString
    }

    invChassisInfoIndex OBJECT-TYPE
        SYNTAX       Integer32 (1..1)
        MAX-ACCESS   not-accessible
        STATUS       current
        DESCRIPTION  "Index of this table."
        ::= { invChassisInfoEntry 1 }

    invChassisInfoNEAddress OBJECT-TYPE
        SYNTAX       IpAddress
        MAX-ACCESS   not-accessible
        STATUS       current
        DESCRIPTION  "reserved."
        ::= { invChassisInfoEntry 2 }

    invChassisName OBJECT-TYPE
        SYNTAX       DisplayString
        MAX-ACCESS   read-only
        STATUS       current
        DESCRIPTION  "Name"
        ::= { invChassisInfoEntry 3 }

    invChassisCodeNo OBJECT-TYPE
        SYNTAX       DisplayString
        MAX-ACCESS   read-only
        STATUS       current
        DESCRIPTION  "Code No."
        ::= { invChassisInfoEntry 4 }

    invChassisSerialNo OBJECT-TYPE
        SYNTAX       DisplayString (SIZE(1..8))
        MAX-ACCESS   read-write
        STATUS       current
        DESCRIPTION
            "Serial No.
            Note: For VR 2, this object cannot be modified, acting as
            read-only object."
        ::= { invChassisInfoEntry 5 }

    invChassisManufacturedDate OBJECT-TYPE
        SYNTAX       DisplayString (SIZE(1..7))
        MAX-ACCESS   read-write
        STATUS       current
        DESCRIPTION
            "Manufactured Date
            Note: For VR 2, this object cannot be modified, acting as
            read-only object."
        ::= { invChassisInfoEntry 6 }

    invChassisFirmVersion OBJECT-TYPE
        SYNTAX       DisplayString
        MAX-ACCESS   read-only
        STATUS       current
        DESCRIPTION  "Firmware Version"
        ::= { invChassisInfoEntry 7 }

    invChassisHardVersion OBJECT-TYPE
        SYNTAX       DisplayString
        MAX-ACCESS   read-only
        STATUS       current
        DESCRIPTION  "Hardware Version"
        ::= { invChassisInfoEntry 8 }

    meteringTable OBJECT-TYPE
        SYNTAX       SEQUENCE OF MeteringEntry
        MAX-ACCESS   not-accessible
        STATUS       current
        DESCRIPTION  "MODEM TX / RX Metering Table."
        ::= { meteringGroup 1 }

    meteringEntry OBJECT-TYPE
        SYNTAX       MeteringEntry
        MAX-ACCESS   not-accessible
        STATUS       current
        DESCRIPTION  ""
        INDEX        { meteringIfIndex }
        ::= { meteringTable 1 }

    MeteringEntry ::= SEQUENCE {
        meteringIfIndex           InterfaceIndex,
        meteringNEAddress         IpAddress,
        metSysTxPowerStatus       ValidInvalidValue,
        metSysTxPowerValue        DisplayString,
        metSysRxLevelStatus       ValidInvalidValue,
        metSysRxLevelValue        DisplayString,
        metSysPSVoltageStatus     ValidInvalidValue,
        metSysPSVoltageValue      DisplayString,
        metSysTempODUStatus       ValidInvalidValue,
        metSysTempODUValue        DisplayString,
        metSysTempIDUStatus       ValidInvalidValue,
        metSysTempIDUValue        DisplayString,
        metSysBitErrorRateStatus  Integer32,
        metSysBitErrorRateValue   DisplayString
    }

    meteringIfIndex OBJECT-TYPE
        SYNTAX       InterfaceIndex
        MAX-ACCESS   not-accessible
        STATUS       current
        DESCRIPTION  "Index of this table."
        ::= { meteringEntry 1 }

    meteringNEAddress OBJECT-TYPE
        SYNTAX       IpAddress
        MAX-ACCESS   not-accessible
        STATUS       current
        DESCRIPTION  "reserved."
        ::= { meteringEntry 2 }

    metSysTxPowerStatus OBJECT-TYPE
        SYNTAX       ValidInvalidValue
        MAX-ACCESS   read-only
        STATUS       current
        DESCRIPTION  "MODEM TX Power Status."
        ::= { meteringEntry 3 }

    metSysTxPowerValue OBJECT-TYPE
        SYNTAX       DisplayString
        MAX-ACCESS   read-only
        STATUS       current
        DESCRIPTION  "MODEM TX Power"
        ::= { meteringEntry 4 }

    metSysRxLevelStatus OBJECT-TYPE
        SYNTAX       ValidInvalidValue
        MAX-ACCESS   read-only
        STATUS       current
        DESCRIPTION  "MODEM RX Power Status"
        ::= { meteringEntry 5 }

    metSysRxLevelValue OBJECT-TYPE
        SYNTAX       DisplayString
        MAX-ACCESS   read-only
        STATUS       current
        DESCRIPTION  "MODEM RX Power"
        ::= { meteringEntry 6 }

    metSysPSVoltageStatus OBJECT-TYPE
        SYNTAX       ValidInvalidValue
        MAX-ACCESS   read-only
        STATUS       current
        DESCRIPTION  "MODEM ODU Power Supply Status"
        ::= { meteringEntry 7 }

    metSysPSVoltageValue OBJECT-TYPE
        SYNTAX       DisplayString
        MAX-ACCESS   read-only
        STATUS       current
        DESCRIPTION  "MODEM ODU Power Supply"
        ::= { meteringEntry 8 }

    metSysTempODUStatus OBJECT-TYPE
        SYNTAX       ValidInvalidValue
        MAX-ACCESS   read-only
        STATUS       current
        DESCRIPTION  "MODEM ODU Temperature Status"
        ::= { meteringEntry 9 }

    metSysTempODUValue OBJECT-TYPE
        SYNTAX       DisplayString
        MAX-ACCESS   read-only
        STATUS       current
        DESCRIPTION  "MODEM ODU Temperature"
        ::= { meteringEntry 10 }

    metSysTempIDUStatus OBJECT-TYPE
        SYNTAX       ValidInvalidValue
        MAX-ACCESS   read-only
        STATUS       current
        DESCRIPTION  "IDU Temperature Status"
        ::= { meteringEntry 11 }

    metSysTempIDUValue OBJECT-TYPE
        SYNTAX       DisplayString
        MAX-ACCESS   read-only
        STATUS       current
        DESCRIPTION  "IDU Temperature"
        ::= { meteringEntry 12 }

    metSysBitErrorRateStatus OBJECT-TYPE
        SYNTAX       Integer32
        MAX-ACCESS   read-only
        STATUS       current
        DESCRIPTION  "MODEM BER Status"
        ::= { meteringEntry 13 }

    metSysBitErrorRateValue OBJECT-TYPE
        SYNTAX       DisplayString
        MAX-ACCESS   read-only
        STATUS       current
        DESCRIPTION  "MODEM BER"
        ::= { meteringEntry 14 }

    meteringFanTable OBJECT-TYPE
        SYNTAX       SEQUENCE OF MeteringFanEntry
        MAX-ACCESS   not-accessible
        STATUS       current
        DESCRIPTION  "FAN Metering Table."
        ::= { meteringGroup 3 }

    meteringFanEntry OBJECT-TYPE
        SYNTAX       MeteringFanEntry
        MAX-ACCESS   not-accessible
        STATUS       current
        DESCRIPTION  ""
        INDEX        { meteringFanSlotIndex }
        ::= { meteringFanTable 1 }

    MeteringFanEntry ::= SEQUENCE {
        meteringFanSlotIndex     Integer32,
        meteringFanNEAddress     IpAddress,
        meteringFanSpeed1        DisplayString,
        meteringFanSpeed1Status  ValidInvalidValue,
        meteringFanSpeed2        DisplayString,
        meteringFanSpeed2Status  ValidInvalidValue,
        meteringFanSpeed3        DisplayString,
        meteringFanSpeed3Status  ValidInvalidValue
    }

    meteringFanSlotIndex OBJECT-TYPE
        SYNTAX       Integer32 (8..8|22..23)
        MAX-ACCESS   not-accessible
        STATUS       current
        DESCRIPTION  "Index of this table."
        ::= { meteringFanEntry 1 }

    meteringFanNEAddress OBJECT-TYPE
        SYNTAX       IpAddress
        MAX-ACCESS   not-accessible
        STATUS       current
        DESCRIPTION  "reserved."
        ::= { meteringFanEntry 2 }

    meteringFanSpeed1 OBJECT-TYPE
        SYNTAX       DisplayString
        MAX-ACCESS   read-only
        STATUS       current
        DESCRIPTION  "FAN1 Rotation Speed"
        ::= { meteringFanEntry 3 }

    meteringFanSpeed1Status OBJECT-TYPE
        SYNTAX       ValidInvalidValue
        MAX-ACCESS   read-only
        STATUS       current
        DESCRIPTION  "FAN1 Rotation Speed Status"
        ::= { meteringFanEntry 4 }

    meteringFanSpeed2 OBJECT-TYPE
        SYNTAX       DisplayString
        MAX-ACCESS   read-only
        STATUS       current
        DESCRIPTION  "FAN2 Rotation Speed"
        ::= { meteringFanEntry 5 }

    meteringFanSpeed2Status OBJECT-TYPE
        SYNTAX       ValidInvalidValue
        MAX-ACCESS   read-only
        STATUS       current
        DESCRIPTION  "FAN2 Rotation Speed Status"
        ::= { meteringFanEntry 6 }

    meteringFanSpeed3 OBJECT-TYPE
        SYNTAX       DisplayString
        MAX-ACCESS   read-only
        STATUS       current
        DESCRIPTION  "FAN3 Rotation Speed"
        ::= { meteringFanEntry 7 }

    meteringFanSpeed3Status OBJECT-TYPE
        SYNTAX       ValidInvalidValue
        MAX-ACCESS   read-only
        STATUS       current
        DESCRIPTION  "FAN3 Rotation Speed Status"
        ::= { meteringFanEntry 8 }

-----------------------------------------------
-- pmonGroup Definitions
-----------------------------------------------

    pmon15minDataRadioGroup OBJECT IDENTIFIER
        ::= { pmonGroup 1 }

    pmon15minDataRadioTable OBJECT-TYPE
        SYNTAX       SEQUENCE OF Pmon15minDataRadioEntry
        MAX-ACCESS   not-accessible
        STATUS       current
        DESCRIPTION  "PMON MODEM 15min RF Monitoring Table"
        ::= { pmon15minDataRadioGroup 1 }

    pmon15minDataRadioEntry OBJECT-TYPE
        SYNTAX       Pmon15minDataRadioEntry
        MAX-ACCESS   not-accessible
        STATUS       current
        DESCRIPTION  ""
        INDEX        {
                         pmon15minDataModemIfIndex,
                         pmon15minDataModemMonitorName
                     }
        ::= { pmon15minDataRadioTable 1 }

    Pmon15minDataRadioEntry ::= SEQUENCE {
        pmon15minDataModemIfIndex      InterfaceIndex,
        pmon15minDataModemMonitorName  INTEGER,
        pmon15minDataRadioNEAddress    IpAddress,
        pmon15minDataModemStatusInfo   IpeStatsInfo,
        pmon15minDataRfValue           Integer32
    }

    pmon15minDataModemIfIndex OBJECT-TYPE
        SYNTAX       InterfaceIndex
        MAX-ACCESS   not-accessible
        STATUS       current
        DESCRIPTION  "Index of this table."
        ::= { pmon15minDataRadioEntry 1 }

    pmon15minDataModemMonitorName OBJECT-TYPE
        SYNTAX       INTEGER {
                         pmonBBE(1),
                         pmonES(2),
                         pmonSES(3),
                         pmonSEF(4),
                         pmonUAS(5),
                         pmonOFS(6)
                     }
        MAX-ACCESS   not-accessible
        STATUS       current
        DESCRIPTION
            "Index of this table. The value represents the monitoring item."
        ::= { pmon15minDataRadioEntry 2 }

    pmon15minDataRadioNEAddress OBJECT-TYPE
        SYNTAX       IpAddress
        MAX-ACCESS   not-accessible
        STATUS       current
        DESCRIPTION  "reserved."
        ::= { pmon15minDataRadioEntry 3 }

    pmon15minDataModemStatusInfo OBJECT-TYPE
        SYNTAX       IpeStatsInfo
        MAX-ACCESS   read-only
        STATUS       current
        DESCRIPTION  "PMON MODEM 15min RF Monitoring Status"
        ::= { pmon15minDataRadioEntry 4 }

    pmon15minDataRfValue OBJECT-TYPE
        SYNTAX       Integer32
        MAX-ACCESS   read-only
        STATUS       current
        DESCRIPTION  "PMON MODEM 15min RF Monitoring Value"
        ::= { pmon15minDataRadioEntry 5 }

    pmon15minDataCableGroup OBJECT IDENTIFIER
        ::= { pmonGroup 2 }

    pmon15minDataThroughModeGroup OBJECT IDENTIFIER
        ::= { pmon15minDataCableGroup 1 }

    pmon15minDataTmRsTable OBJECT-TYPE
        SYNTAX       SEQUENCE OF Pmon15minDataTmRsEntry
        MAX-ACCESS   not-accessible
        STATUS       current
        DESCRIPTION  "PMON STM-1 15min (Through Mode) RS Monitoring Table"
        ::= { pmon15minDataThroughModeGroup 1 }

    pmon15minDataTmRsEntry OBJECT-TYPE
        SYNTAX       Pmon15minDataTmRsEntry
        MAX-ACCESS   not-accessible
        STATUS       current
        DESCRIPTION  ""
        INDEX        { pmon15minDataTmRsIfIndex, pmon15minDataTmRsMonitorName }
        ::= { pmon15minDataTmRsTable 1 }

    Pmon15minDataTmRsEntry ::= SEQUENCE {
        pmon15minDataTmRsIfIndex      InterfaceIndex,
        pmon15minDataTmRsMonitorName  INTEGER,
        pmon15minDataTmRsNEAddress    IpAddress,
        pmon15minDataTmRsStatusInfo   IpeStatsInfo,
        pmon15minDataTmRsValue        Integer32
    }

    pmon15minDataTmRsIfIndex OBJECT-TYPE
        SYNTAX       InterfaceIndex
        MAX-ACCESS   not-accessible
        STATUS       current
        DESCRIPTION  "Index of this table."
        ::= { pmon15minDataTmRsEntry 1 }

    pmon15minDataTmRsMonitorName OBJECT-TYPE
        SYNTAX       INTEGER {
                         pmonBBE(1),
                         pmonES(2),
                         pmonSES(3),
                         pmonSEF(4),
                         pmonUAS(5),
                         pmonOFS(6)
                     }
        MAX-ACCESS   not-accessible
        STATUS       current
        DESCRIPTION
            "index of this table. The value represents the monitoring item."
        ::= { pmon15minDataTmRsEntry 2 }

    pmon15minDataTmRsNEAddress OBJECT-TYPE
        SYNTAX       IpAddress
        MAX-ACCESS   not-accessible
        STATUS       current
        DESCRIPTION  "reserved."
        ::= { pmon15minDataTmRsEntry 3 }

    pmon15minDataTmRsStatusInfo OBJECT-TYPE
        SYNTAX       IpeStatsInfo
        MAX-ACCESS   read-only
        STATUS       current
        DESCRIPTION
            "PMON STM-1 15min (Through Mode) RS Monitoring Status."
        ::= { pmon15minDataTmRsEntry 4 }

    pmon15minDataTmRsValue OBJECT-TYPE
        SYNTAX       Integer32
        MAX-ACCESS   read-only
        STATUS       current
        DESCRIPTION  "PMON STM-1 15min (Through Mode) RS Monitoring Status"
        ::= { pmon15minDataTmRsEntry 5 }

    pmon15minDataTmDMRRsTable OBJECT-TYPE
        SYNTAX       SEQUENCE OF Pmon15minDataTmDMRRsEntry
        MAX-ACCESS   not-accessible
        STATUS       current
        DESCRIPTION
            "PMON STM-1 15min (Through Mode) DMR RS Monitoring Table"
        ::= { pmon15minDataThroughModeGroup 2 }

    pmon15minDataTmDMRRsEntry OBJECT-TYPE
        SYNTAX       Pmon15minDataTmDMRRsEntry
        MAX-ACCESS   not-accessible
        STATUS       current
        DESCRIPTION  ""
        INDEX        {
                         pmon15minDataTmDMRRsIfIndex,
                         pmon15minDataTmDMRRsMonitorName
                     }
        ::= { pmon15minDataTmDMRRsTable 1 }

    Pmon15minDataTmDMRRsEntry ::= SEQUENCE {
        pmon15minDataTmDMRRsIfIndex      InterfaceIndex,
        pmon15minDataTmDMRRsMonitorName  INTEGER,
        pmon15minDataTmDMRRsNEAddress    IpAddress,
        pmon15minDataTmDMRRsStatusInfo   IpeStatsInfo,
        pmon15minDataTmDMRRsValue        Integer32
    }

    pmon15minDataTmDMRRsIfIndex OBJECT-TYPE
        SYNTAX       InterfaceIndex
        MAX-ACCESS   not-accessible
        STATUS       current
        DESCRIPTION  "Index of this table."
        ::= { pmon15minDataTmDMRRsEntry 1 }

    pmon15minDataTmDMRRsMonitorName OBJECT-TYPE
        SYNTAX       INTEGER {
                         pmonBBE(1),
                         pmonES(2),
                         pmonSES(3),
                         pmonSEF(4),
                         pmonUAS(5),
                         pmonOFS(6)
                     }
        MAX-ACCESS   not-accessible
        STATUS       current
        DESCRIPTION
            "Index of this table. The value represents the monitoring item."
        ::= { pmon15minDataTmDMRRsEntry 2 }

    pmon15minDataTmDMRRsNEAddress OBJECT-TYPE
        SYNTAX       IpAddress
        MAX-ACCESS   not-accessible
        STATUS       current
        DESCRIPTION  "reserved."
        ::= { pmon15minDataTmDMRRsEntry 3 }

    pmon15minDataTmDMRRsStatusInfo OBJECT-TYPE
        SYNTAX       IpeStatsInfo
        MAX-ACCESS   read-only
        STATUS       current
        DESCRIPTION
            "PMON STM-1 15min (Through Mode) DMR RS Monitoring Status"
        ::= { pmon15minDataTmDMRRsEntry 4 }

    pmon15minDataTmDMRRsValue OBJECT-TYPE
        SYNTAX       Integer32
        MAX-ACCESS   read-only
        STATUS       current
        DESCRIPTION
            "PMON STM-1 15min (Through Mode) DMR RS Monitoring Value"
        ::= { pmon15minDataTmDMRRsEntry 5 }

    pmon15minDataChannelizedModeGroup OBJECT IDENTIFIER
        ::= { pmon15minDataCableGroup 2 }

    pmon15minDataChRsTable OBJECT-TYPE
        SYNTAX       SEQUENCE OF Pmon15minDataChRsEntry
        MAX-ACCESS   not-accessible
        STATUS       current
        DESCRIPTION
            "PMON STM-1 15min (Channelized Mode) RS Monitoring Table"
        ::= { pmon15minDataChannelizedModeGroup 1 }

    pmon15minDataChRsEntry OBJECT-TYPE
        SYNTAX       Pmon15minDataChRsEntry
        MAX-ACCESS   not-accessible
        STATUS       current
        DESCRIPTION  ""
        INDEX        { pmon15minDataChRsIfIndex, pmon15minDataChRsMonitorName }
        ::= { pmon15minDataChRsTable 1 }

    Pmon15minDataChRsEntry ::= SEQUENCE {
        pmon15minDataChRsIfIndex      InterfaceIndex,
        pmon15minDataChRsMonitorName  INTEGER,
        pmon15minDataChRsNEAddress    IpAddress,
        pmon15minDataChRsStatusInfo   IpeStatsInfo,
        pmon15minDataChRsValue        Integer32
    }

    pmon15minDataChRsIfIndex OBJECT-TYPE
        SYNTAX       InterfaceIndex
        MAX-ACCESS   not-accessible
        STATUS       current
        DESCRIPTION  "Index of this table."
        ::= { pmon15minDataChRsEntry 1 }

    pmon15minDataChRsMonitorName OBJECT-TYPE
        SYNTAX       INTEGER {
                         pmonBBE(1),
                         pmonES(2),
                         pmonSES(3),
                         pmonSEF(4),
                         pmonUAS(5),
                         pmonOFS(6)
                     }
        MAX-ACCESS   not-accessible
        STATUS       current
        DESCRIPTION
            "Index of this table. The value represents the monitoring item."
        ::= { pmon15minDataChRsEntry 2 }

    pmon15minDataChRsNEAddress OBJECT-TYPE
        SYNTAX       IpAddress
        MAX-ACCESS   not-accessible
        STATUS       current
        DESCRIPTION  "reserved."
        ::= { pmon15minDataChRsEntry 3 }

    pmon15minDataChRsStatusInfo OBJECT-TYPE
        SYNTAX       IpeStatsInfo
        MAX-ACCESS   read-only
        STATUS       current
        DESCRIPTION
            "PMON STM-1 15min (Channelized Mode) RS Monitoring Status"
        ::= { pmon15minDataChRsEntry 4 }

    pmon15minDataChRsValue OBJECT-TYPE
        SYNTAX       Integer32
        MAX-ACCESS   read-only
        STATUS       current
        DESCRIPTION
            "PMON STM-1 15min (Channelized Mode) RS Monitoring Value"
        ::= { pmon15minDataChRsEntry 5 }

    pmon15minDataChMsTable OBJECT-TYPE
        SYNTAX       SEQUENCE OF Pmon15minDataChMsEntry
        MAX-ACCESS   not-accessible
        STATUS       current
        DESCRIPTION
            "PMON STM-1 15min (Channelized Mode) MS Monitoring Table."
        ::= { pmon15minDataChannelizedModeGroup 2 }

    pmon15minDataChMsEntry OBJECT-TYPE
        SYNTAX       Pmon15minDataChMsEntry
        MAX-ACCESS   not-accessible
        STATUS       current
        DESCRIPTION  ""
        INDEX        { pmon15minDataChMsIfIndex, pmon15minDataChMsMonitorName }
        ::= { pmon15minDataChMsTable 1 }

    Pmon15minDataChMsEntry ::= SEQUENCE {
        pmon15minDataChMsIfIndex      InterfaceIndex,
        pmon15minDataChMsMonitorName  INTEGER,
        pmon15minDataChMsNEAddress    IpAddress,
        pmon15minDataChMsStatusInfo   IpeStatsInfo,
        pmon15minDataChMsValue        Integer32
    }

    pmon15minDataChMsIfIndex OBJECT-TYPE
        SYNTAX       InterfaceIndex
        MAX-ACCESS   not-accessible
        STATUS       current
        DESCRIPTION  "Index of this table."
        ::= { pmon15minDataChMsEntry 1 }

    pmon15minDataChMsMonitorName OBJECT-TYPE
        SYNTAX       INTEGER {
                         pmonBBE(1),
                         pmonES(2),
                         pmonSES(3),
                         pmonSEP(4),
                         pmonUAS(5)
                     }
        MAX-ACCESS   not-accessible
        STATUS       current
        DESCRIPTION
            "Index of this table. The value represents the monitoring item"
        ::= { pmon15minDataChMsEntry 2 }

    pmon15minDataChMsNEAddress OBJECT-TYPE
        SYNTAX       IpAddress
        MAX-ACCESS   not-accessible
        STATUS       current
        DESCRIPTION  "reserved."
        ::= { pmon15minDataChMsEntry 3 }

    pmon15minDataChMsStatusInfo OBJECT-TYPE
        SYNTAX       IpeStatsInfo
        MAX-ACCESS   read-only
        STATUS       current
        DESCRIPTION
            "PMON STM-1 15min (Channelized Mode) MS Monitoring Status."
        ::= { pmon15minDataChMsEntry 4 }

    pmon15minDataChMsValue OBJECT-TYPE
        SYNTAX       Integer32
        MAX-ACCESS   read-only
        STATUS       current
        DESCRIPTION
            "PMON STM-1 15min (Channelized Mode) MS Monitoring Value"
        ::= { pmon15minDataChMsEntry 5 }

    pmon15minData16E1Group OBJECT IDENTIFIER
        ::= { pmon15minDataCableGroup 3 }

    pmon15minData16E1PdhTable OBJECT-TYPE
        SYNTAX       SEQUENCE OF Pmon15minData16E1PdhEntry
        MAX-ACCESS   not-accessible
        STATUS       current
        DESCRIPTION  "PMON E1 15min Monitoring Table"
        ::= { pmon15minData16E1Group 1 }

    pmon15minData16E1PdhEntry OBJECT-TYPE
        SYNTAX       Pmon15minData16E1PdhEntry
        MAX-ACCESS   not-accessible
        STATUS       current
        DESCRIPTION  ""
        INDEX        {
                         pmon15minData16E1PdhIfIndex,
                         pmon15minData16E1PdhMonitorName
                     }
        ::= { pmon15minData16E1PdhTable 1 }

    Pmon15minData16E1PdhEntry ::= SEQUENCE {
        pmon15minData16E1PdhIfIndex      InterfaceIndex,
        pmon15minData16E1PdhMonitorName  INTEGER,
        pmon15minData16E1PdhNEAddress    IpAddress,
        pmon15minData16E1PdhStatusInfo   IpeStatsInfo,
        pmon15minData16E1PdhValue        Counter32
    }

    pmon15minData16E1PdhIfIndex OBJECT-TYPE
        SYNTAX       InterfaceIndex
        MAX-ACCESS   not-accessible
        STATUS       current
        DESCRIPTION  "Index of this table."
        ::= { pmon15minData16E1PdhEntry 1 }

    pmon15minData16E1PdhMonitorName OBJECT-TYPE
        SYNTAX       INTEGER { pmonCV(1) }
        MAX-ACCESS   not-accessible
        STATUS       current
        DESCRIPTION
            "Index of this table. The value represents the monitoring item"
        ::= { pmon15minData16E1PdhEntry 2 }

    pmon15minData16E1PdhNEAddress OBJECT-TYPE
        SYNTAX       IpAddress
        MAX-ACCESS   not-accessible
        STATUS       current
        DESCRIPTION  "reserved."
        ::= { pmon15minData16E1PdhEntry 3 }

    pmon15minData16E1PdhStatusInfo OBJECT-TYPE
        SYNTAX       IpeStatsInfo
        MAX-ACCESS   read-only
        STATUS       current
        DESCRIPTION  "PMON E1 15min Monitoring Status"
        ::= { pmon15minData16E1PdhEntry 4 }

    pmon15minData16E1PdhValue OBJECT-TYPE
        SYNTAX       Counter32
        MAX-ACCESS   read-only
        STATUS       current
        DESCRIPTION  "PMON E1 15min Monitoring Value"
        ::= { pmon15minData16E1PdhEntry 5 }

    pmon1dayDataRadioGroup OBJECT IDENTIFIER
        ::= { pmonGroup 3 }

    pmon1dayDataRadioTable OBJECT-TYPE
        SYNTAX       SEQUENCE OF Pmon1dayDataRadioEntry
        MAX-ACCESS   not-accessible
        STATUS       current
        DESCRIPTION  "PMON MODEM 1 day RF Monitoring Table"
        ::= { pmon1dayDataRadioGroup 1 }

    pmon1dayDataRadioEntry OBJECT-TYPE
        SYNTAX       Pmon1dayDataRadioEntry
        MAX-ACCESS   not-accessible
        STATUS       current
        DESCRIPTION  ""
        INDEX        { pmon1dayDataModemIfIndex, pmon1dayDataModemMonitorName }
        ::= { pmon1dayDataRadioTable 1 }

    Pmon1dayDataRadioEntry ::= SEQUENCE {
        pmon1dayDataModemIfIndex      InterfaceIndex,
        pmon1dayDataModemMonitorName  INTEGER,
        pmon1dayDataRadioNEAddress    IpAddress,
        pmon1dayDataModemStatusInfo   IpeStatsInfo,
        pmon1dayDataRfValue           Integer32
    }

    pmon1dayDataModemIfIndex OBJECT-TYPE
        SYNTAX       InterfaceIndex
        MAX-ACCESS   not-accessible
        STATUS       current
        DESCRIPTION  "Index of this table."
        ::= { pmon1dayDataRadioEntry 1 }

    pmon1dayDataModemMonitorName OBJECT-TYPE
        SYNTAX       INTEGER {
                         pmonBBE(1),
                         pmonES(2),
                         pmonSES(3),
                         pmonSEF(4),
                         pmonUAS(5),
                         pmonOFS(6)
                     }
        MAX-ACCESS   not-accessible
        STATUS       current
        DESCRIPTION
            "Index of this table. The value represents the monitoring item"
        ::= { pmon1dayDataRadioEntry 2 }

    pmon1dayDataRadioNEAddress OBJECT-TYPE
        SYNTAX       IpAddress
        MAX-ACCESS   not-accessible
        STATUS       current
        DESCRIPTION  "reserved."
        ::= { pmon1dayDataRadioEntry 3 }

    pmon1dayDataModemStatusInfo OBJECT-TYPE
        SYNTAX       IpeStatsInfo
        MAX-ACCESS   read-only
        STATUS       current
        DESCRIPTION  "PMON MODEM 1 day RF Monitoring Status."
        ::= { pmon1dayDataRadioEntry 4 }

    pmon1dayDataRfValue OBJECT-TYPE
        SYNTAX       Integer32
        MAX-ACCESS   read-only
        STATUS       current
        DESCRIPTION  "PMON MODEM 1 day RF Monitoring Value"
        ::= { pmon1dayDataRadioEntry 5 }

    pmon1dayDataCableGroup OBJECT IDENTIFIER
        ::= { pmonGroup 4 }

    pmon1dayDataThroughModeGroup OBJECT IDENTIFIER
        ::= { pmon1dayDataCableGroup 1 }

    pmon1dayDataTmRsTable OBJECT-TYPE
        SYNTAX       SEQUENCE OF Pmon1dayDataTmRsEntry
        MAX-ACCESS   not-accessible
        STATUS       current
        DESCRIPTION  "PMON STM-1 1day (Through Mode) RS Monitoring Table"
        ::= { pmon1dayDataThroughModeGroup 1 }

    pmon1dayDataTmRsEntry OBJECT-TYPE
        SYNTAX       Pmon1dayDataTmRsEntry
        MAX-ACCESS   not-accessible
        STATUS       current
        DESCRIPTION  ""
        INDEX        { pmon1dayDataTmRsIfIndex, pmon1dayDataTmRsMonitorName }
        ::= { pmon1dayDataTmRsTable 1 }

    Pmon1dayDataTmRsEntry ::= SEQUENCE {
        pmon1dayDataTmRsIfIndex      InterfaceIndex,
        pmon1dayDataTmRsMonitorName  INTEGER,
        pmon1dayDataTmRsNEAddress    IpAddress,
        pmon1dayDataTmRsStatusInfo   IpeStatsInfo,
        pmon1dayDataTmRsValue        Integer32
    }

    pmon1dayDataTmRsIfIndex OBJECT-TYPE
        SYNTAX       InterfaceIndex
        MAX-ACCESS   not-accessible
        STATUS       current
        DESCRIPTION  "Index of this table."
        ::= { pmon1dayDataTmRsEntry 1 }

    pmon1dayDataTmRsMonitorName OBJECT-TYPE
        SYNTAX       INTEGER {
                         pmonBBE(1),
                         pmonES(2),
                         pmonSES(3),
                         pmonSEF(4),
                         pmonUAS(5),
                         pmonOFS(6)
                     }
        MAX-ACCESS   not-accessible
        STATUS       current
        DESCRIPTION
            "Index of this table. The value represents the monitoring item"
        ::= { pmon1dayDataTmRsEntry 2 }

    pmon1dayDataTmRsNEAddress OBJECT-TYPE
        SYNTAX       IpAddress
        MAX-ACCESS   not-accessible
        STATUS       current
        DESCRIPTION  "reserved."
        ::= { pmon1dayDataTmRsEntry 3 }

    pmon1dayDataTmRsStatusInfo OBJECT-TYPE
        SYNTAX       IpeStatsInfo
        MAX-ACCESS   read-only
        STATUS       current
        DESCRIPTION  "PMON STM-1 1day (Through Mode) RS Monitoring Status"
        ::= { pmon1dayDataTmRsEntry 4 }

    pmon1dayDataTmRsValue OBJECT-TYPE
        SYNTAX       Integer32
        MAX-ACCESS   read-only
        STATUS       current
        DESCRIPTION  "PMON STM-1 1day (Through Mode) RS Monitoring Value"
        ::= { pmon1dayDataTmRsEntry 5 }

    pmon1dayDataTmDMRRsTable OBJECT-TYPE
        SYNTAX       SEQUENCE OF Pmon1dayDataTmDMRRsEntry
        MAX-ACCESS   not-accessible
        STATUS       current
        DESCRIPTION
            "PMON STM-1 1day (Through Mode) DMR RS Monitoring Table"
        ::= { pmon1dayDataThroughModeGroup 2 }

    pmon1dayDataTmDMRRsEntry OBJECT-TYPE
        SYNTAX       Pmon1dayDataTmDMRRsEntry
        MAX-ACCESS   not-accessible
        STATUS       current
        DESCRIPTION  ""
        INDEX        {
                         pmon1dayDataTmDMRRsIfIndex,
                         pmon1dayDataTmDMRRsMonitorName
                     }
        ::= { pmon1dayDataTmDMRRsTable 1 }

    Pmon1dayDataTmDMRRsEntry ::= SEQUENCE {
        pmon1dayDataTmDMRRsIfIndex      InterfaceIndex,
        pmon1dayDataTmDMRRsMonitorName  INTEGER,
        pmon1dayDataTmDMRRsNEAddress    IpAddress,
        pmon1dayDataTmDMRRsStatusInfo   IpeStatsInfo,
        pmon1dayDataTmDMRRsValue        Integer32
    }

    pmon1dayDataTmDMRRsIfIndex OBJECT-TYPE
        SYNTAX       InterfaceIndex
        MAX-ACCESS   not-accessible
        STATUS       current
        DESCRIPTION  "Index of this table."
        ::= { pmon1dayDataTmDMRRsEntry 1 }

    pmon1dayDataTmDMRRsMonitorName OBJECT-TYPE
        SYNTAX       INTEGER {
                         pmonBBE(1),
                         pmonES(2),
                         pmonSES(3),
                         pmonSEF(4),
                         pmonUAS(5),
                         pmonOFS(6)
                     }
        MAX-ACCESS   not-accessible
        STATUS       current
        DESCRIPTION
            "Index of this table. The value represents the monitoring item."
        ::= { pmon1dayDataTmDMRRsEntry 2 }

    pmon1dayDataTmDMRRsNEAddress OBJECT-TYPE
        SYNTAX       IpAddress
        MAX-ACCESS   not-accessible
        STATUS       current
        DESCRIPTION  "reserved."
        ::= { pmon1dayDataTmDMRRsEntry 3 }

    pmon1dayDataTmDMRRsStatusInfo OBJECT-TYPE
        SYNTAX       IpeStatsInfo
        MAX-ACCESS   read-only
        STATUS       current
        DESCRIPTION
            "PMON STM-1 1day (Through Mode) DMR RS Monitoring Status"
        ::= { pmon1dayDataTmDMRRsEntry 4 }

    pmon1dayDataTmDMRRsValue OBJECT-TYPE
        SYNTAX       Integer32
        MAX-ACCESS   read-only
        STATUS       current
        DESCRIPTION
            "PMON STM-1 1day (Through Mode) DMR RS Monitoring Value"
        ::= { pmon1dayDataTmDMRRsEntry 5 }

    pmon1dayDataChannelizedModeGroup OBJECT IDENTIFIER
        ::= { pmon1dayDataCableGroup 2 }

    pmon1dayDataChRsTable OBJECT-TYPE
        SYNTAX       SEQUENCE OF Pmon1dayDataChRsEntry
        MAX-ACCESS   not-accessible
        STATUS       current
        DESCRIPTION
            "PMON STM-1 1day (Channelized Mode) RS Monitoring Table"
        ::= { pmon1dayDataChannelizedModeGroup 1 }

    pmon1dayDataChRsEntry OBJECT-TYPE
        SYNTAX       Pmon1dayDataChRsEntry
        MAX-ACCESS   not-accessible
        STATUS       current
        DESCRIPTION  ""
        INDEX        { pmon1dayDataChRsIfIndex, pmon1dayDataChRsMonitorName }
        ::= { pmon1dayDataChRsTable 1 }

    Pmon1dayDataChRsEntry ::= SEQUENCE {
        pmon1dayDataChRsIfIndex      InterfaceIndex,
        pmon1dayDataChRsMonitorName  INTEGER,
        pmon1dayDataChRsNEAddress    IpAddress,
        pmon1dayDataChRsStatusInfo   IpeStatsInfo,
        pmon1dayDataChRsValue        Integer32
    }

    pmon1dayDataChRsIfIndex OBJECT-TYPE
        SYNTAX       InterfaceIndex
        MAX-ACCESS   not-accessible
        STATUS       current
        DESCRIPTION  "Index of this table."
        ::= { pmon1dayDataChRsEntry 1 }

    pmon1dayDataChRsMonitorName OBJECT-TYPE
        SYNTAX       INTEGER {
                         pmonBBE(1),
                         pmonES(2),
                         pmonSES(3),
                         pmonSEF(4),
                         pmonUAS(5),
                         pmonOFS(6)
                     }
        MAX-ACCESS   not-accessible
        STATUS       current
        DESCRIPTION
            "Index of this table. The value represents the monitoring item"
        ::= { pmon1dayDataChRsEntry 2 }

    pmon1dayDataChRsNEAddress OBJECT-TYPE
        SYNTAX       IpAddress
        MAX-ACCESS   not-accessible
        STATUS       current
        DESCRIPTION  "reserved."
        ::= { pmon1dayDataChRsEntry 3 }

    pmon1dayDataChRsStatusInfo OBJECT-TYPE
        SYNTAX       IpeStatsInfo
        MAX-ACCESS   read-only
        STATUS       current
        DESCRIPTION
            "PMON STM-1 1day (Channelized Mode) RS Monitoring Status"
        ::= { pmon1dayDataChRsEntry 4 }

    pmon1dayDataChRsValue OBJECT-TYPE
        SYNTAX       Integer32
        MAX-ACCESS   read-only
        STATUS       current
        DESCRIPTION
            "PMON STM-1 1day (Channelized Mode) RS Monitoring Value"
        ::= { pmon1dayDataChRsEntry 5 }

    pmon1dayDataChMsTable OBJECT-TYPE
        SYNTAX       SEQUENCE OF Pmon1dayDataChMsEntry
        MAX-ACCESS   not-accessible
        STATUS       current
        DESCRIPTION
            "PMON STM-1 1day (Channelized Mode) MS Monitoring Table"
        ::= { pmon1dayDataChannelizedModeGroup 2 }

    pmon1dayDataChMsEntry OBJECT-TYPE
        SYNTAX       Pmon1dayDataChMsEntry
        MAX-ACCESS   not-accessible
        STATUS       current
        DESCRIPTION  ""
        INDEX        { pmon1dayDataChMsIfIndex, pmon1dayDataChMsMonitorName }
        ::= { pmon1dayDataChMsTable 1 }

    Pmon1dayDataChMsEntry ::= SEQUENCE {
        pmon1dayDataChMsIfIndex      InterfaceIndex,
        pmon1dayDataChMsMonitorName  INTEGER,
        pmon1dayDataChMsNEAddress    IpAddress,
        pmon1dayDataChMsStatusInfo   IpeStatsInfo,
        pmon1dayDataChMsValue        Integer32
    }

    pmon1dayDataChMsIfIndex OBJECT-TYPE
        SYNTAX       InterfaceIndex
        MAX-ACCESS   not-accessible
        STATUS       current
        DESCRIPTION  "Index of this table."
        ::= { pmon1dayDataChMsEntry 1 }

    pmon1dayDataChMsMonitorName OBJECT-TYPE
        SYNTAX       INTEGER {
                         pmonBBE(1),
                         pmonES(2),
                         pmonSES(3),
                         pmonSEP(4),
                         pmonUAS(5)
                     }
        MAX-ACCESS   not-accessible
        STATUS       current
        DESCRIPTION
            "Index of this table. The value represents the monitoring item"
        ::= { pmon1dayDataChMsEntry 2 }

    pmon1dayDataChMsNEAddress OBJECT-TYPE
        SYNTAX       IpAddress
        MAX-ACCESS   not-accessible
        STATUS       current
        DESCRIPTION  "reserved."
        ::= { pmon1dayDataChMsEntry 3 }

    pmon1dayDataChMsStatusInfo OBJECT-TYPE
        SYNTAX       IpeStatsInfo
        MAX-ACCESS   read-only
        STATUS       current
        DESCRIPTION
            "PMON STM-1 1day (Channelized Mode) MS Monitoring Status"
        ::= { pmon1dayDataChMsEntry 4 }

    pmon1dayDataChMsValue OBJECT-TYPE
        SYNTAX       Integer32
        MAX-ACCESS   read-only
        STATUS       current
        DESCRIPTION
            "PMON STM-1 1day (Channelized Mode) MS Monitoring Value"
        ::= { pmon1dayDataChMsEntry 5 }

    pmon1dayData16E1Group OBJECT IDENTIFIER
        ::= { pmon1dayDataCableGroup 3 }

    pmon1dayData16E1PdhTable OBJECT-TYPE
        SYNTAX       SEQUENCE OF Pmon1dayData16E1PdhEntry
        MAX-ACCESS   not-accessible
        STATUS       current
        DESCRIPTION  "PMON E1 1day Monitoring Table"
        ::= { pmon1dayData16E1Group 1 }

    pmon1dayData16E1PdhEntry OBJECT-TYPE
        SYNTAX       Pmon1dayData16E1PdhEntry
        MAX-ACCESS   not-accessible
        STATUS       current
        DESCRIPTION  ""
        INDEX        {
                         pmon1dayData16E1PdhIfIndex,
                         pmon1dayData16E1PdhMonitorName
                     }
        ::= { pmon1dayData16E1PdhTable 1 }

    Pmon1dayData16E1PdhEntry ::= SEQUENCE {
        pmon1dayData16E1PdhIfIndex      InterfaceIndex,
        pmon1dayData16E1PdhMonitorName  INTEGER,
        pmon1dayData16E1PdhNEAddress    IpAddress,
        pmon1dayData16E1PdhStatusInfo   IpeStatsInfo,
        pmon1dayData16E1PdhValue        Counter32
    }

    pmon1dayData16E1PdhIfIndex OBJECT-TYPE
        SYNTAX       InterfaceIndex
        MAX-ACCESS   not-accessible
        STATUS       current
        DESCRIPTION  "Index of this table."
        ::= { pmon1dayData16E1PdhEntry 1 }

    pmon1dayData16E1PdhMonitorName OBJECT-TYPE
        SYNTAX       INTEGER { pmonCV(1) }
        MAX-ACCESS   not-accessible
        STATUS       current
        DESCRIPTION
            "Index of this table. The value represents the monitoring item."
        ::= { pmon1dayData16E1PdhEntry 2 }

    pmon1dayData16E1PdhNEAddress OBJECT-TYPE
        SYNTAX       IpAddress
        MAX-ACCESS   not-accessible
        STATUS       current
        DESCRIPTION  "reserved."
        ::= { pmon1dayData16E1PdhEntry 3 }

    pmon1dayData16E1PdhStatusInfo OBJECT-TYPE
        SYNTAX       IpeStatsInfo
        MAX-ACCESS   read-only
        STATUS       current
        DESCRIPTION  "PMON E1 1day Monitoring Status"
        ::= { pmon1dayData16E1PdhEntry 4 }

    pmon1dayData16E1PdhValue OBJECT-TYPE
        SYNTAX       Counter32
        MAX-ACCESS   read-only
        STATUS       current
        DESCRIPTION  "PMON E1 1day Monitoring Value"
        ::= { pmon1dayData16E1PdhEntry 5 }

    pmonTxRxLev15minCurrentDataTable OBJECT-TYPE
        SYNTAX       SEQUENCE OF PmonTxRxLev15minCurrentDataEntry
        MAX-ACCESS   not-accessible
        STATUS       current
        DESCRIPTION  "PMON ODU 15min Tx/RX Level Monitoring Table"
        ::= { pmonTxRxLevGroup 1 }

    pmonTxRxLev15minCurrentDataEntry OBJECT-TYPE
        SYNTAX       PmonTxRxLev15minCurrentDataEntry
        MAX-ACCESS   not-accessible
        STATUS       current
        DESCRIPTION  ""
        INDEX        { pmonTxRxLev15minCurrentDataIfIndex }
        ::= { pmonTxRxLev15minCurrentDataTable 1 }

    PmonTxRxLev15minCurrentDataEntry ::= SEQUENCE {
        pmonTxRxLev15minCurrentDataIfIndex     InterfaceIndex,
        pmonTxRxLev15minCurrentDataNEAddress   IpAddress,
        pmonTxRxLev15minCurrentDataStatusInfo  IpeStatsInfo,
        pmonTxRxLev15minRxLevelMaxCurrentData  DisplayString,
        pmonTxRxLev15minRxLevelMinCurrentData  DisplayString
    }

    pmonTxRxLev15minCurrentDataIfIndex OBJECT-TYPE
        SYNTAX       InterfaceIndex
        MAX-ACCESS   not-accessible
        STATUS       current
        DESCRIPTION  "Index of this table."
        ::= { pmonTxRxLev15minCurrentDataEntry 1 }

    pmonTxRxLev15minCurrentDataNEAddress OBJECT-TYPE
        SYNTAX       IpAddress
        MAX-ACCESS   not-accessible
        STATUS       current
        DESCRIPTION  "reserved."
        ::= { pmonTxRxLev15minCurrentDataEntry 2 }

    pmonTxRxLev15minCurrentDataStatusInfo OBJECT-TYPE
        SYNTAX       IpeStatsInfo
        MAX-ACCESS   read-only
        STATUS       current
        DESCRIPTION  "PMON ODU 15min RX Level Status"
        ::= { pmonTxRxLev15minCurrentDataEntry 3 }

    pmonTxRxLev15minRxLevelMaxCurrentData OBJECT-TYPE
        SYNTAX       DisplayString
        MAX-ACCESS   read-only
        STATUS       current
        DESCRIPTION  "PMON ODU 15min RX Level (MAX)"
        ::= { pmonTxRxLev15minCurrentDataEntry 4 }

    pmonTxRxLev15minRxLevelMinCurrentData OBJECT-TYPE
        SYNTAX       DisplayString
        MAX-ACCESS   read-only
        STATUS       current
        DESCRIPTION  "PMON ODU 15min RX Level (MIN)"
        ::= { pmonTxRxLev15minCurrentDataEntry 5 }

    pmonTxRxLev1dayCurrentDataTable OBJECT-TYPE
        SYNTAX       SEQUENCE OF PmonTxRxLev1dayCurrentDataEntry
        MAX-ACCESS   not-accessible
        STATUS       current
        DESCRIPTION  "PMON ODU 1day Tx/RX Level Monitoring Table"
        ::= { pmonTxRxLevGroup 2 }

    pmonTxRxLev1dayCurrentDataEntry OBJECT-TYPE
        SYNTAX       PmonTxRxLev1dayCurrentDataEntry
        MAX-ACCESS   not-accessible
        STATUS       current
        DESCRIPTION  ""
        INDEX        { pmonTxRxLev1dayCurrentDataIfIndex }
        ::= { pmonTxRxLev1dayCurrentDataTable 1 }

    PmonTxRxLev1dayCurrentDataEntry ::= SEQUENCE {
        pmonTxRxLev1dayCurrentDataIfIndex     InterfaceIndex,
        pmonTxRxLev1dayCurrentDataNEAddress   IpAddress,
        pmonTxRxLev1dayCurrentDataStatusInfo  IpeStatsInfo,
        pmonTxRxLev1dayRxLevelMaxCurrentData  DisplayString,
        pmonTxRxLev1dayRxLevelMinCurrentData  DisplayString
    }

    pmonTxRxLev1dayCurrentDataIfIndex OBJECT-TYPE
        SYNTAX       InterfaceIndex
        MAX-ACCESS   not-accessible
        STATUS       current
        DESCRIPTION  "Index of this table."
        ::= { pmonTxRxLev1dayCurrentDataEntry 1 }

    pmonTxRxLev1dayCurrentDataNEAddress OBJECT-TYPE
        SYNTAX       IpAddress
        MAX-ACCESS   not-accessible
        STATUS       current
        DESCRIPTION  "reserved."
        ::= { pmonTxRxLev1dayCurrentDataEntry 2 }

    pmonTxRxLev1dayCurrentDataStatusInfo OBJECT-TYPE
        SYNTAX       IpeStatsInfo
        MAX-ACCESS   read-only
        STATUS       current
        DESCRIPTION  "PMON ODU 1day RX Level Status"
        ::= { pmonTxRxLev1dayCurrentDataEntry 3 }

    pmonTxRxLev1dayRxLevelMaxCurrentData OBJECT-TYPE
        SYNTAX       DisplayString
        MAX-ACCESS   read-only
        STATUS       current
        DESCRIPTION  "PMON ODU 1day RX Level (MAX)"
        ::= { pmonTxRxLev1dayCurrentDataEntry 4 }

    pmonTxRxLev1dayRxLevelMinCurrentData OBJECT-TYPE
        SYNTAX       DisplayString
        MAX-ACCESS   read-only
        STATUS       current
        DESCRIPTION  "PMON ODU 1day RX Level (MIN)"
        ::= { pmonTxRxLev1dayCurrentDataEntry 5 }

-----------------------------------------------
-- rmonGroup Definitions
-----------------------------------------------

    rmonEthGroup OBJECT IDENTIFIER
        ::= { rmonGroup 1 }

    rmon15minPortGroup OBJECT IDENTIFIER
        ::= { rmonEthGroup 1 }

    rmon15minPortTable OBJECT-TYPE
        SYNTAX       SEQUENCE OF Rmon15minPortEntry
        MAX-ACCESS   not-accessible
        STATUS       current
        DESCRIPTION  "RMON 15min Port Monitoring Table."
        ::= { rmon15minPortGroup 1 }

    rmon15minPortEntry OBJECT-TYPE
        SYNTAX       Rmon15minPortEntry
        MAX-ACCESS   not-accessible
        STATUS       current
        DESCRIPTION  ""
        INDEX        { rmon15minIfIndex }
        ::= { rmon15minPortTable 1 }

    Rmon15minPortEntry ::= SEQUENCE {
        rmon15minIfIndex                                   InterfaceIndex,
        rmon15minNEAddress                                 IpAddress,
        rmon15minHCRxEthStatsOctets                        Counter64,
        rmon15minHCRxEthStatsOctetsStatusInfo              INTEGER,
        rmon15minHCTxEthStatsOctets                        Counter64,
        rmon15minHCTxEthStatsOctetsStatusInfo              INTEGER,
        rmon15minRxEthStatsPkts                            Counter32,
        rmon15minRxEthStatsPktsStatusInfo                  INTEGER,
        rmon15minTxEthStatsPkts                            Counter32,
        rmon15minTxEthStatsPktsStatusInfo                  INTEGER,
        rmon15minRxEthStatsDropEvents                      Counter32,
        rmon15minRxEthStatsDropEventsStatusInfo            INTEGER,
        rmon15minRxEthStatsUndersizePkts                   Counter32,
        rmon15minRxEthStatsUndersizePktsStatusInfo         INTEGER,
        rmon15minRxEthStatsFragments                       Counter32,
        rmon15minRxEthStatsFragmentsStatusInfo             INTEGER,
        rmon15minRxEthStatsPkts64Octets                    Counter32,
        rmon15minRxEthStatsPkts64OctetsStatusInfo          INTEGER,
        rmon15minTxEthStatsPkts64Octets                    Counter32,
        rmon15minTxEthStatsPkts64OctetsStatusInfo          INTEGER,
        rmon15minRxEthStatsPkts65to127Octets               Counter32,
        rmon15minRxEthStatsPkts65to127OctetsStatusInfo     INTEGER,
        rmon15minTxEthStatsPkts65to127Octets               Counter32,
        rmon15minTxEthStatsPkts65to127OctetsStatusInfo     INTEGER,
        rmon15minRxEthStatsPkts128to255Octets              Counter32,
        rmon15minRxEthStatsPkts128to255OctetsStatusInfo    INTEGER,
        rmon15minTxEthStatsPkts128to255Octets              Counter32,
        rmon15minTxEthStatsPkts128to255OctetsStatusInfo    INTEGER,
        rmon15minRxEthStatsPkts256to511Octets              Counter32,
        rmon15minRxEthStatsPkts256to511OctetsStatusInfo    INTEGER,
        rmon15minTxEthStatsPkts256to511Octets              Counter32,
        rmon15minTxEthStatsPkts256to511OctetsStatusInfo    INTEGER,
        rmon15minRxEthStatsPkts512to1023Octets             Counter32,
        rmon15minRxEthStatsPkts512to1023OctetsStatusInfo   INTEGER,
        rmon15minTxEthStatsPkts512to1023Octets             Counter32,
        rmon15minTxEthStatsPkts512to1023OctetsStatusInfo   INTEGER,
        rmon15minRxEthStatsPkts1024to1518Octets            Counter32,
        rmon15minRxEthStatsPkts1024to1518OctetsStatusInfo  INTEGER,
        rmon15minTxEthStatsPkts1024to1518Octets            Counter32,
        rmon15minTxEthStatsPkts1024to1518OctetsStatusInfo  INTEGER,
        rmon15minRxEthStatsCRCAlignErrors                  Counter32,
        rmon15minRxEthStatsCRCAlignErrorsStatusInfo        INTEGER,
        rmon15minRxEthStatsOversizePkts                    Counter32,
        rmon15minRxEthStatsOversizePktsStatusInfo          INTEGER,
        rmon15minRxEthStatsJabbers                         Counter32,
        rmon15minRxEthStatsJabbersStatusInfo               INTEGER,
        rmon15minRxEthStatsMulticastPkts                   Counter32,
        rmon15minRxEthStatsMulticastPktsStatusInfo         INTEGER,
        rmon15minTxEthStatsMulticastPkts                   Counter32,
        rmon15minTxEthStatsMulticastPktsStatusInfo         INTEGER,
        rmon15minRxEthStatsBroadcastPkts                   Counter32,
        rmon15minRxEthStatsBroadcastPktsStatusInfo         INTEGER,
        rmon15minTxEthStatsBroadcastPkts                   Counter32,
        rmon15minTxEthStatsBroadcastPktsStatusInfo         INTEGER,
        rmon15minTxEthStatsCollisions                      Counter32,
        rmon15minTxEthStatsCollisionsStatusInfo            INTEGER,
        rmon15minHCRxUnknownTPID                           Counter64,
        rmon15minHCRxUnknownTPIDStatusInfo                 INTEGER,
        rmon15minHCRxUnknownVID                            Counter64,
        rmon15minHCRxUnknownVIDStatusInfo                  INTEGER,
        rmon15minHCRxMAClimit                              Counter64,
        rmon15minHCRxMAClimitStatusInfo                    INTEGER,
        rmon15minHCRxFilterDiscard                         Counter64,
        rmon15minHCRxFilterDiscardStatusInfo               INTEGER,
        rmon15minHCRxQoSDiscard                            Counter64,
        rmon15minHCRxQoSDiscardStatusInfo                  INTEGER,
        rmon15minHCTxQueue0Discard                         Counter64,
        rmon15minHCTxQueue0DiscardStatusInfo               INTEGER,
        rmon15minHCTxQueue1Discard                         Counter64,
        rmon15minHCTxQueue1DiscardStatusInfo               INTEGER,
        rmon15minHCTxQueue2Discard                         Counter64,
        rmon15minHCTxQueue2DiscardStatusInfo               INTEGER,
        rmon15minHCTxQueue3Discard                         Counter64,
        rmon15minHCTxQueue3DiscardStatusInfo               INTEGER,
        rmon15minHCTxQueue4Discard                         Counter64,
        rmon15minHCTxQueue4DiscardStatusInfo               INTEGER,
        rmon15minHCTxQueue5Discard                         Counter64,
        rmon15minHCTxQueue5DiscardStatusInfo               INTEGER,
        rmon15minHCTxQueue6Discard                         Counter64,
        rmon15minHCTxQueue6DiscardStatusInfo               INTEGER,
        rmon15minHCTxQueue7Discard                         Counter64,
        rmon15minHCTxQueue7DiscardStatusInfo               INTEGER,
        rmon15minTxEthStatsOversizePkts                    Counter32,
        rmon15minTxEthStatsOversizePktsStatusInfo          INTEGER
    }

    rmon15minIfIndex OBJECT-TYPE
        SYNTAX       InterfaceIndex
        MAX-ACCESS   not-accessible
        STATUS       current
        DESCRIPTION  "Index of this table."
        ::= { rmon15minPortEntry 1 }

    rmon15minNEAddress OBJECT-TYPE
        SYNTAX       IpAddress
        MAX-ACCESS   not-accessible
        STATUS       current
        DESCRIPTION  "reserved."
        ::= { rmon15minPortEntry 2 }

    rmon15minHCRxEthStatsOctets OBJECT-TYPE
        SYNTAX       Counter64
        MAX-ACCESS   read-only
        STATUS       current
        DESCRIPTION  "RMON 15min RX Octs"
        ::= { rmon15minPortEntry 3 }

    rmon15minHCRxEthStatsOctetsStatusInfo OBJECT-TYPE
        SYNTAX       INTEGER {
                         invalid(0),
                         valid-no-maintenance(1),
                         valid-maintenance(2),
                         invalid-no-maintenance(3),
                         invalid-maintenance(4)
                     }
        MAX-ACCESS   read-only
        STATUS       current
        DESCRIPTION
            "RMON 15min RX Octs Status. 'invalid' means the corresponding
            monitoring value is not reliable because of the alarm or other
            reasons. 'maintenance' means that some maintenance functions are
            executed on the current interval."
        ::= { rmon15minPortEntry 4 }

    rmon15minHCTxEthStatsOctets OBJECT-TYPE
        SYNTAX       Counter64
        MAX-ACCESS   read-only
        STATUS       current
        DESCRIPTION  "RMON 15min TX Octs"
        ::= { rmon15minPortEntry 5 }

    rmon15minHCTxEthStatsOctetsStatusInfo OBJECT-TYPE
        SYNTAX       INTEGER {
                         invalid(0),
                         valid-no-maintenance(1),
                         valid-maintenance(2),
                         invalid-no-maintenance(3),
                         invalid-maintenance(4)
                     }
        MAX-ACCESS   read-only
        STATUS       current
        DESCRIPTION
            "RMON 15min TX Octs Status. 'invalid' means the corresponding
            monitoring value is not reliable because of the alarm or other
            reasons. 'maintenance' means that some maintenance functions are
            executed on the current interval."
        ::= { rmon15minPortEntry 6 }

    rmon15minRxEthStatsPkts OBJECT-TYPE
        SYNTAX       Counter32
        MAX-ACCESS   read-only
        STATUS       current
        DESCRIPTION  "RMON 15min RX Pkts"
        ::= { rmon15minPortEntry 7 }

    rmon15minRxEthStatsPktsStatusInfo OBJECT-TYPE
        SYNTAX       INTEGER {
                         invalid(0),
                         valid-no-maintenance(1),
                         valid-maintenance(2),
                         invalid-no-maintenance(3),
                         invalid-maintenance(4)
                     }
        MAX-ACCESS   read-only
        STATUS       current
        DESCRIPTION
            "RMON 15min RX Pkts Status. 'invalid' means the corresponding
            monitoring value is not reliable because of the alarm or other
            reasons. 'maintenance' means that some maintenance functions are
            executed on the current interval."
        ::= { rmon15minPortEntry 8 }

    rmon15minTxEthStatsPkts OBJECT-TYPE
        SYNTAX       Counter32
        MAX-ACCESS   read-only
        STATUS       current
        DESCRIPTION  "RMON 15min TX Pkts"
        ::= { rmon15minPortEntry 9 }

    rmon15minTxEthStatsPktsStatusInfo OBJECT-TYPE
        SYNTAX       INTEGER {
                         invalid(0),
                         valid-no-maintenance(1),
                         valid-maintenance(2),
                         invalid-no-maintenance(3),
                         invalid-maintenance(4)
                     }
        MAX-ACCESS   read-only
        STATUS       current
        DESCRIPTION
            "RMON 15min TX Pkts Status. 'invalid' means the corresponding
            monitoring value is not reliable because of the alarm or other
            reasons. 'maintenance' means that some maintenance functions are
            executed on the current interval."
        ::= { rmon15minPortEntry 10 }

    rmon15minRxEthStatsDropEvents OBJECT-TYPE
        SYNTAX       Counter32
        MAX-ACCESS   read-only
        STATUS       current
        DESCRIPTION  "RMON 15min RX Drop Events"
        ::= { rmon15minPortEntry 11 }

    rmon15minRxEthStatsDropEventsStatusInfo OBJECT-TYPE
        SYNTAX       INTEGER {
                         invalid(0),
                         valid-no-maintenance(1),
                         valid-maintenance(2),
                         invalid-no-maintenance(3),
                         invalid-maintenance(4)
                     }
        MAX-ACCESS   read-only
        STATUS       current
        DESCRIPTION
            "RMON 15min RX Drop Events Status. 'invalid' means the
            corresponding monitoring value is not reliable because of the
            alarm or other reasons. 'maintenance' means that some maintenance
            functions are executed on the current interval."
        ::= { rmon15minPortEntry 12 }

    rmon15minRxEthStatsUndersizePkts OBJECT-TYPE
        SYNTAX       Counter32
        MAX-ACCESS   read-only
        STATUS       current
        DESCRIPTION  "RMON 15min RX Undersize Pkts"
        ::= { rmon15minPortEntry 13 }

    rmon15minRxEthStatsUndersizePktsStatusInfo OBJECT-TYPE
        SYNTAX       INTEGER {
                         invalid(0),
                         valid-no-maintenance(1),
                         valid-maintenance(2),
                         invalid-no-maintenance(3),
                         invalid-maintenance(4)
                     }
        MAX-ACCESS   read-only
        STATUS       current
        DESCRIPTION
            "RMON 15min RX Undersize Pkts Status. 'invalid' means the
            corresponding monitoring value is not reliable because of the
            alarm or other reasons. 'maintenance' means that some maintenance
            functions are executed on the current interval."
        ::= { rmon15minPortEntry 14 }

    rmon15minRxEthStatsFragments OBJECT-TYPE
        SYNTAX       Counter32
        MAX-ACCESS   read-only
        STATUS       current
        DESCRIPTION  "RMON 15min RX Fragments"
        ::= { rmon15minPortEntry 15 }

    rmon15minRxEthStatsFragmentsStatusInfo OBJECT-TYPE
        SYNTAX       INTEGER {
                         invalid(0),
                         valid-no-maintenance(1),
                         valid-maintenance(2),
                         invalid-no-maintenance(3),
                         invalid-maintenance(4)
                     }
        MAX-ACCESS   read-only
        STATUS       current
        DESCRIPTION
            "RMON 15min RX Fragments Status. 'invalid' means the
            corresponding monitoring value is not reliable because of the
            alarm or other reasons. 'maintenance' means that some maintenance
            functions are executed on the current interval."
        ::= { rmon15minPortEntry 16 }

    rmon15minRxEthStatsPkts64Octets OBJECT-TYPE
        SYNTAX       Counter32
        MAX-ACCESS   read-only
        STATUS       current
        DESCRIPTION  "RMON 15min RX 64 Octs"
        ::= { rmon15minPortEntry 17 }

    rmon15minRxEthStatsPkts64OctetsStatusInfo OBJECT-TYPE
        SYNTAX       INTEGER {
                         invalid(0),
                         valid-no-maintenance(1),
                         valid-maintenance(2),
                         invalid-no-maintenance(3),
                         invalid-maintenance(4)
                     }
        MAX-ACCESS   read-only
        STATUS       current
        DESCRIPTION
            "RMON 15min RX 64 Octs Status. 'invalid' means the corresponding
            monitoring value is not reliable because of the alarm or other
            reasons. 'maintenance' means that some maintenance functions are
            executed on the current interval."
        ::= { rmon15minPortEntry 18 }

    rmon15minTxEthStatsPkts64Octets OBJECT-TYPE
        SYNTAX       Counter32
        MAX-ACCESS   read-only
        STATUS       current
        DESCRIPTION  "RMON 15min TX 64 Octs"
        ::= { rmon15minPortEntry 19 }

    rmon15minTxEthStatsPkts64OctetsStatusInfo OBJECT-TYPE
        SYNTAX       INTEGER {
                         invalid(0),
                         valid-no-maintenance(1),
                         valid-maintenance(2),
                         invalid-no-maintenance(3),
                         invalid-maintenance(4)
                     }
        MAX-ACCESS   read-only
        STATUS       current
        DESCRIPTION
            "RMON 15min TX 64 Octs Status. 'invalid' means the corresponding
            monitoring value is not reliable because of the alarm or other
            reasons. 'maintenance' means that some maintenance functions are
            executed on the current interval."
        ::= { rmon15minPortEntry 20 }

    rmon15minRxEthStatsPkts65to127Octets OBJECT-TYPE
        SYNTAX       Counter32
        MAX-ACCESS   read-only
        STATUS       current
        DESCRIPTION  "RMON 15min RX 65 to 127 Octs"
        ::= { rmon15minPortEntry 21 }

    rmon15minRxEthStatsPkts65to127OctetsStatusInfo OBJECT-TYPE
        SYNTAX       INTEGER {
                         invalid(0),
                         valid-no-maintenance(1),
                         valid-maintenance(2),
                         invalid-no-maintenance(3),
                         invalid-maintenance(4)
                     }
        MAX-ACCESS   read-only
        STATUS       current
        DESCRIPTION
            "RMON 15min RX 65 to 127 Octs Status. 'invalid' means the
            corresponding monitoring value is not reliable because of the
            alarm or other reasons. 'maintenance' means that some maintenance
            functions are executed on the current interval."
        ::= { rmon15minPortEntry 22 }

    rmon15minTxEthStatsPkts65to127Octets OBJECT-TYPE
        SYNTAX       Counter32
        MAX-ACCESS   read-only
        STATUS       current
        DESCRIPTION  "RMON 15min TX 65 to 127 Octs"
        ::= { rmon15minPortEntry 23 }

    rmon15minTxEthStatsPkts65to127OctetsStatusInfo OBJECT-TYPE
        SYNTAX       INTEGER {
                         invalid(0),
                         valid-no-maintenance(1),
                         valid-maintenance(2),
                         invalid-no-maintenance(3),
                         invalid-maintenance(4)
                     }
        MAX-ACCESS   read-only
        STATUS       current
        DESCRIPTION
            "RMON 15min TX 65 to 127 Octs Status. 'invalid' means the
            corresponding monitoring value is not reliable because of the
            alarm or other reasons. 'maintenance' means that some maintenance
            functions are executed on the current interval."
        ::= { rmon15minPortEntry 24 }

    rmon15minRxEthStatsPkts128to255Octets OBJECT-TYPE
        SYNTAX       Counter32
        MAX-ACCESS   read-only
        STATUS       current
        DESCRIPTION  "RMON 15min RX 128 to 255 Octs"
        ::= { rmon15minPortEntry 25 }

    rmon15minRxEthStatsPkts128to255OctetsStatusInfo OBJECT-TYPE
        SYNTAX       INTEGER {
                         invalid(0),
                         valid-no-maintenance(1),
                         valid-maintenance(2),
                         invalid-no-maintenance(3),
                         invalid-maintenance(4)
                     }
        MAX-ACCESS   read-only
        STATUS       current
        DESCRIPTION
            "RMON 15min RX 128 to 255 Octs Status. 'invalid' means the
            corresponding monitoring value is not reliable because of the
            alarm or other reasons. 'maintenance' means that some maintenance
            functions are executed on the current interval."
        ::= { rmon15minPortEntry 26 }

    rmon15minTxEthStatsPkts128to255Octets OBJECT-TYPE
        SYNTAX       Counter32
        MAX-ACCESS   read-only
        STATUS       current
        DESCRIPTION  "RMON 15min TX 128 to 255 Octs"
        ::= { rmon15minPortEntry 27 }

    rmon15minTxEthStatsPkts128to255OctetsStatusInfo OBJECT-TYPE
        SYNTAX       INTEGER {
                         invalid(0),
                         valid-no-maintenance(1),
                         valid-maintenance(2),
                         invalid-no-maintenance(3),
                         invalid-maintenance(4)
                     }
        MAX-ACCESS   read-only
        STATUS       current
        DESCRIPTION
            "RMON 15min TX 128 to 255 Octs Status. 'invalid' means the
            corresponding monitoring value is not reliable because of the
            alarm or other reasons. 'maintenance' means that some maintenance
            functions are executed on the current interval."
        ::= { rmon15minPortEntry 28 }

    rmon15minRxEthStatsPkts256to511Octets OBJECT-TYPE
        SYNTAX       Counter32
        MAX-ACCESS   read-only
        STATUS       current
        DESCRIPTION  "RMON 15min RX 256 to 511 Octs"
        ::= { rmon15minPortEntry 29 }

    rmon15minRxEthStatsPkts256to511OctetsStatusInfo OBJECT-TYPE
        SYNTAX       INTEGER {
                         invalid(0),
                         valid-no-maintenance(1),
                         valid-maintenance(2),
                         invalid-no-maintenance(3),
                         invalid-maintenance(4)
                     }
        MAX-ACCESS   read-only
        STATUS       current
        DESCRIPTION
            "RMON 15min RX 256 to 511 Octs Status. 'invalid' means the
            corresponding monitoring value is not reliable because of the
            alarm or other reasons. 'maintenance' means that some maintenance
            functions are executed on the current interval."
        ::= { rmon15minPortEntry 30 }

    rmon15minTxEthStatsPkts256to511Octets OBJECT-TYPE
        SYNTAX       Counter32
        MAX-ACCESS   read-only
        STATUS       current
        DESCRIPTION  "RMON 15min TX 256 to 511 Octs"
        ::= { rmon15minPortEntry 31 }

    rmon15minTxEthStatsPkts256to511OctetsStatusInfo OBJECT-TYPE
        SYNTAX       INTEGER {
                         invalid(0),
                         valid-no-maintenance(1),
                         valid-maintenance(2),
                         invalid-no-maintenance(3),
                         invalid-maintenance(4)
                     }
        MAX-ACCESS   read-only
        STATUS       current
        DESCRIPTION
            "RMON 15min TX 256 to 511 Octs Status. 'invalid' means the
            corresponding monitoring value is not reliable because of the
            alarm or other reasons. 'maintenance' means that some maintenance
            functions are executed on the current interval."
        ::= { rmon15minPortEntry 32 }

    rmon15minRxEthStatsPkts512to1023Octets OBJECT-TYPE
        SYNTAX       Counter32
        MAX-ACCESS   read-only
        STATUS       current
        DESCRIPTION  "RMON 15min RX 512 to 1023 Octs"
        ::= { rmon15minPortEntry 33 }

    rmon15minRxEthStatsPkts512to1023OctetsStatusInfo OBJECT-TYPE
        SYNTAX       INTEGER {
                         invalid(0),
                         valid-no-maintenance(1),
                         valid-maintenance(2),
                         invalid-no-maintenance(3),
                         invalid-maintenance(4)
                     }
        MAX-ACCESS   read-only
        STATUS       current
        DESCRIPTION
            "RMON 15min RX 512 to 1023 Octs Status. 'invalid' means the
            corresponding monitoring value is not reliable because of the
            alarm or other reasons. 'maintenance' means that some maintenance
            functions are executed on the current interval."
        ::= { rmon15minPortEntry 34 }

    rmon15minTxEthStatsPkts512to1023Octets OBJECT-TYPE
        SYNTAX       Counter32
        MAX-ACCESS   read-only
        STATUS       current
        DESCRIPTION  "RMON 15min TX 512 to 1023 Octs"
        ::= { rmon15minPortEntry 35 }

    rmon15minTxEthStatsPkts512to1023OctetsStatusInfo OBJECT-TYPE
        SYNTAX       INTEGER {
                         invalid(0),
                         valid-no-maintenance(1),
                         valid-maintenance(2),
                         invalid-no-maintenance(3),
                         invalid-maintenance(4)
                     }
        MAX-ACCESS   read-only
        STATUS       current
        DESCRIPTION
            "RMON 15min TX 512 to 1023 Octs Status. 'invalid' means the
            corresponding monitoring value is not reliable because of the
            alarm or other reasons. 'maintenance' means that some maintenance
            functions are executed on the current interval."
        ::= { rmon15minPortEntry 36 }

    rmon15minRxEthStatsPkts1024to1518Octets OBJECT-TYPE
        SYNTAX       Counter32
        MAX-ACCESS   read-only
        STATUS       current
        DESCRIPTION  "RMON 15min RX 1024 to 1518 Octs"
        ::= { rmon15minPortEntry 37 }

    rmon15minRxEthStatsPkts1024to1518OctetsStatusInfo OBJECT-TYPE
        SYNTAX       INTEGER {
                         invalid(0),
                         valid-no-maintenance(1),
                         valid-maintenance(2),
                         invalid-no-maintenance(3),
                         invalid-maintenance(4)
                     }
        MAX-ACCESS   read-only
        STATUS       current
        DESCRIPTION
            "RMON 15min RX 1024 to 1518 Octs Status. 'invalid' means the
            corresponding monitoring value is not reliable because of the
            alarm or other reasons. 'maintenance' means that some maintenance
            functions are executed on the current interval."
        ::= { rmon15minPortEntry 38 }

    rmon15minTxEthStatsPkts1024to1518Octets OBJECT-TYPE
        SYNTAX       Counter32
        MAX-ACCESS   read-only
        STATUS       current
        DESCRIPTION  "RMON 15min TX 1024 to 1518 Octs"
        ::= { rmon15minPortEntry 39 }

    rmon15minTxEthStatsPkts1024to1518OctetsStatusInfo OBJECT-TYPE
        SYNTAX       INTEGER {
                         invalid(0),
                         valid-no-maintenance(1),
                         valid-maintenance(2),
                         invalid-no-maintenance(3),
                         invalid-maintenance(4)
                     }
        MAX-ACCESS   read-only
        STATUS       current
        DESCRIPTION
            "RMON 15min TX 1024 to 1518 Octs Status. 'invalid' means the
            corresponding monitoring value is not reliable because of the
            alarm or other reasons. 'maintenance' means that some maintenance
            functions are executed on the current interval."
        ::= { rmon15minPortEntry 40 }

    rmon15minRxEthStatsCRCAlignErrors OBJECT-TYPE
        SYNTAX       Counter32
        MAX-ACCESS   read-only
        STATUS       current
        DESCRIPTION  "RMON 15min RX CRC Alignment Errors"
        ::= { rmon15minPortEntry 41 }

    rmon15minRxEthStatsCRCAlignErrorsStatusInfo OBJECT-TYPE
        SYNTAX       INTEGER {
                         invalid(0),
                         valid-no-maintenance(1),
                         valid-maintenance(2),
                         invalid-no-maintenance(3),
                         invalid-maintenance(4)
                     }
        MAX-ACCESS   read-only
        STATUS       current
        DESCRIPTION
            "RMON 15min RX CRC Alignment Errors Status. 'invalid' means the
            corresponding monitoring value is not reliable because of the
            alarm or other reasons. 'maintenance' means that some maintenance
            functions are executed on the current interval."
        ::= { rmon15minPortEntry 42 }

    rmon15minRxEthStatsOversizePkts OBJECT-TYPE
        SYNTAX       Counter32
        MAX-ACCESS   read-only
        STATUS       current
        DESCRIPTION  "RMON 15min RX Oversize Pkts"
        ::= { rmon15minPortEntry 43 }

    rmon15minRxEthStatsOversizePktsStatusInfo OBJECT-TYPE
        SYNTAX       INTEGER {
                         invalid(0),
                         valid-no-maintenance(1),
                         valid-maintenance(2),
                         invalid-no-maintenance(3),
                         invalid-maintenance(4)
                     }
        MAX-ACCESS   read-only
        STATUS       current
        DESCRIPTION
            "RMON 15min RX Oversize Pkts Status. 'invalid' means the
            corresponding monitoring value is not reliable because of the
            alarm or other reasons. 'maintenance' means that some maintenance
            functions are executed on the current interval."
        ::= { rmon15minPortEntry 44 }

    rmon15minRxEthStatsJabbers OBJECT-TYPE
        SYNTAX       Counter32
        MAX-ACCESS   read-only
        STATUS       current
        DESCRIPTION  "RMON 15min RX Jabbers"
        ::= { rmon15minPortEntry 45 }

    rmon15minRxEthStatsJabbersStatusInfo OBJECT-TYPE
        SYNTAX       INTEGER {
                         invalid(0),
                         valid-no-maintenance(1),
                         valid-maintenance(2),
                         invalid-no-maintenance(3),
                         invalid-maintenance(4)
                     }
        MAX-ACCESS   read-only
        STATUS       current
        DESCRIPTION
            "RMON 15min RX Jabbers Status. 'invalid' means the corresponding
            monitoring value is not reliable because of the alarm or other
            reasons. 'maintenance' means that some maintenance functions are
            executed on the current interval."
        ::= { rmon15minPortEntry 46 }

    rmon15minRxEthStatsMulticastPkts OBJECT-TYPE
        SYNTAX       Counter32
        MAX-ACCESS   read-only
        STATUS       current
        DESCRIPTION  "RMON 15min RX Multicast Pkts"
        ::= { rmon15minPortEntry 47 }

    rmon15minRxEthStatsMulticastPktsStatusInfo OBJECT-TYPE
        SYNTAX       INTEGER {
                         invalid(0),
                         valid-no-maintenance(1),
                         valid-maintenance(2),
                         invalid-no-maintenance(3),
                         invalid-maintenance(4)
                     }
        MAX-ACCESS   read-only
        STATUS       current
        DESCRIPTION
            "RMON 15min RX Multicast Pkts Status. 'invalid' means the
            corresponding monitoring value is not reliable because of the
            alarm or other reasons. 'maintenance' means that some maintenance
            functions are executed on the current interval."
        ::= { rmon15minPortEntry 48 }

    rmon15minTxEthStatsMulticastPkts OBJECT-TYPE
        SYNTAX       Counter32
        MAX-ACCESS   read-only
        STATUS       current
        DESCRIPTION  "RMON 15min TX Multicast Pkts"
        ::= { rmon15minPortEntry 49 }

    rmon15minTxEthStatsMulticastPktsStatusInfo OBJECT-TYPE
        SYNTAX       INTEGER {
                         invalid(0),
                         valid-no-maintenance(1),
                         valid-maintenance(2),
                         invalid-no-maintenance(3),
                         invalid-maintenance(4)
                     }
        MAX-ACCESS   read-only
        STATUS       current
        DESCRIPTION
            "RMON 15min TX Multicast Pkts Status. 'invalid' means the
            corresponding monitoring value is not reliable because of the
            alarm or other reasons. 'maintenance' means that some maintenance
            functions are executed on the current interval."
        ::= { rmon15minPortEntry 50 }

    rmon15minRxEthStatsBroadcastPkts OBJECT-TYPE
        SYNTAX       Counter32
        MAX-ACCESS   read-only
        STATUS       current
        DESCRIPTION  "RMON 15min RX Broadcast Pkts"
        ::= { rmon15minPortEntry 51 }

    rmon15minRxEthStatsBroadcastPktsStatusInfo OBJECT-TYPE
        SYNTAX       INTEGER {
                         invalid(0),
                         valid-no-maintenance(1),
                         valid-maintenance(2),
                         invalid-no-maintenance(3),
                         invalid-maintenance(4)
                     }
        MAX-ACCESS   read-only
        STATUS       current
        DESCRIPTION
            "RMON 15min RX Broadcast Pkts Status. 'invalid' means the
            corresponding monitoring value is not reliable because of the
            alarm or other reasons. 'maintenance' means that some maintenance
            functions are executed on the current interval."
        ::= { rmon15minPortEntry 52 }

    rmon15minTxEthStatsBroadcastPkts OBJECT-TYPE
        SYNTAX       Counter32
        MAX-ACCESS   read-only
        STATUS       current
        DESCRIPTION  "RMON 15min TX Broadcast Pkts"
        ::= { rmon15minPortEntry 53 }

    rmon15minTxEthStatsBroadcastPktsStatusInfo OBJECT-TYPE
        SYNTAX       INTEGER {
                         invalid(0),
                         valid-no-maintenance(1),
                         valid-maintenance(2),
                         invalid-no-maintenance(3),
                         invalid-maintenance(4)
                     }
        MAX-ACCESS   read-only
        STATUS       current
        DESCRIPTION
            "RMON 15min TX Broadcast Pkts Status. 'invalid' means the
            corresponding monitoring value is not reliable because of the
            alarm or other reasons. 'maintenance' means that some maintenance
            functions are executed on the current interval."
        ::= { rmon15minPortEntry 54 }

    rmon15minTxEthStatsCollisions OBJECT-TYPE
        SYNTAX       Counter32
        MAX-ACCESS   read-only
        STATUS       current
        DESCRIPTION  "RMON 15min TX Collisions"
        ::= { rmon15minPortEntry 55 }

    rmon15minTxEthStatsCollisionsStatusInfo OBJECT-TYPE
        SYNTAX       INTEGER {
                         invalid(0),
                         valid-no-maintenance(1),
                         valid-maintenance(2),
                         invalid-no-maintenance(3),
                         invalid-maintenance(4)
                     }
        MAX-ACCESS   read-only
        STATUS       current
        DESCRIPTION
            "RMON 15min TX Collisions Status. 'invalid' means the
            corresponding monitoring value is not reliable because of the
            alarm or other reasons. 'maintenance' means that some maintenance
            functions are executed on the current interval."
        ::= { rmon15minPortEntry 56 }

    rmon15minHCRxUnknownTPID OBJECT-TYPE
        SYNTAX       Counter64
        MAX-ACCESS   read-only
        STATUS       current
        DESCRIPTION  "RMON 15min Unknown TPID"
        ::= { rmon15minPortEntry 57 }

    rmon15minHCRxUnknownTPIDStatusInfo OBJECT-TYPE
        SYNTAX       INTEGER {
                         invalid(0),
                         valid-no-maintenance(1),
                         valid-maintenance(2),
                         invalid-no-maintenance(3),
                         invalid-maintenance(4)
                     }
        MAX-ACCESS   read-only
        STATUS       current
        DESCRIPTION
            "RMON 15min Unknown TPID Status. 'invalid' means the
            corresponding monitoring value is not reliable because of the
            alarm or other reasons. 'maintenance' means that some maintenance
            functions are executed on the current interval."
        ::= { rmon15minPortEntry 58 }

    rmon15minHCRxUnknownVID OBJECT-TYPE
        SYNTAX       Counter64
        MAX-ACCESS   read-only
        STATUS       current
        DESCRIPTION  "RMON 15min Unknown VID"
        ::= { rmon15minPortEntry 59 }

    rmon15minHCRxUnknownVIDStatusInfo OBJECT-TYPE
        SYNTAX       INTEGER {
                         invalid(0),
                         valid-no-maintenance(1),
                         valid-maintenance(2),
                         invalid-no-maintenance(3),
                         invalid-maintenance(4)
                     }
        MAX-ACCESS   read-only
        STATUS       current
        DESCRIPTION
            "RMON 15min Unknown VID Status. 'invalid' means the corresponding
            monitoring value is not reliable because of the alarm or other
            reasons. 'maintenance' means that some maintenance functions are
            executed on the current interval."
        ::= { rmon15minPortEntry 60 }

    rmon15minHCRxMAClimit OBJECT-TYPE
        SYNTAX       Counter64
        MAX-ACCESS   read-only
        STATUS       current
        DESCRIPTION  "RMON 15min RX MAC Limit"
        ::= { rmon15minPortEntry 61 }

    rmon15minHCRxMAClimitStatusInfo OBJECT-TYPE
        SYNTAX       INTEGER {
                         invalid(0),
                         valid-no-maintenance(1),
                         valid-maintenance(2),
                         invalid-no-maintenance(3),
                         invalid-maintenance(4)
                     }
        MAX-ACCESS   read-only
        STATUS       current
        DESCRIPTION
            "RMON 15min RX MAC Limit Status. 'invalid' means the
            corresponding monitoring value is not reliable because of the
            alarm or other reasons. 'maintenance' means that some maintenance
            functions are executed on the current interval."
        ::= { rmon15minPortEntry 62 }

    rmon15minHCRxFilterDiscard OBJECT-TYPE
        SYNTAX       Counter64
        MAX-ACCESS   read-only
        STATUS       current
        DESCRIPTION  "RMON 15min RX Filter Discard"
        ::= { rmon15minPortEntry 63 }

    rmon15minHCRxFilterDiscardStatusInfo OBJECT-TYPE
        SYNTAX       INTEGER {
                         invalid(0),
                         valid-no-maintenance(1),
                         valid-maintenance(2),
                         invalid-no-maintenance(3),
                         invalid-maintenance(4)
                     }
        MAX-ACCESS   read-only
        STATUS       current
        DESCRIPTION
            "RMON 15min RX Filter Discard Status. 'invalid' means the
            corresponding monitoring value is not reliable because of the
            alarm or other reasons. 'maintenance' means that some maintenance
            functions are executed on the current interval."
        ::= { rmon15minPortEntry 64 }

    rmon15minHCRxQoSDiscard OBJECT-TYPE
        SYNTAX       Counter64
        MAX-ACCESS   read-only
        STATUS       current
        DESCRIPTION  "RMON 15min RX QoS Discard"
        ::= { rmon15minPortEntry 65 }

    rmon15minHCRxQoSDiscardStatusInfo OBJECT-TYPE
        SYNTAX       INTEGER {
                         invalid(0),
                         valid-no-maintenance(1),
                         valid-maintenance(2),
                         invalid-no-maintenance(3),
                         invalid-maintenance(4)
                     }
        MAX-ACCESS   read-only
        STATUS       current
        DESCRIPTION
            "RMON 15min RX QoS Discard Status. 'invalid' means the
            corresponding monitoring value is not reliable because of the
            alarm or other reasons. 'maintenance' means that some maintenance
            functions are executed on the current interval."
        ::= { rmon15minPortEntry 66 }

    rmon15minHCTxQueue0Discard OBJECT-TYPE
        SYNTAX       Counter64
        MAX-ACCESS   read-only
        STATUS       current
        DESCRIPTION  "RMON 15min TX Queue0 Discard"
        ::= { rmon15minPortEntry 67 }

    rmon15minHCTxQueue0DiscardStatusInfo OBJECT-TYPE
        SYNTAX       INTEGER {
                         invalid(0),
                         valid-no-maintenance(1),
                         valid-maintenance(2),
                         invalid-no-maintenance(3),
                         invalid-maintenance(4)
                     }
        MAX-ACCESS   read-only
        STATUS       current
        DESCRIPTION
            "RMON 15min TX Queue0 Discard Status. 'invalid' means the
            corresponding monitoring value is not reliable because of the
            alarm or other reasons. 'maintenance' means that some maintenance
            functions are executed on the current interval."
        ::= { rmon15minPortEntry 68 }

    rmon15minHCTxQueue1Discard OBJECT-TYPE
        SYNTAX       Counter64
        MAX-ACCESS   read-only
        STATUS       current
        DESCRIPTION  "RMON 15min TX Queue1 Discard"
        ::= { rmon15minPortEntry 69 }

    rmon15minHCTxQueue1DiscardStatusInfo OBJECT-TYPE
        SYNTAX       INTEGER {
                         invalid(0),
                         valid-no-maintenance(1),
                         valid-maintenance(2),
                         invalid-no-maintenance(3),
                         invalid-maintenance(4)
                     }
        MAX-ACCESS   read-only
        STATUS       current
        DESCRIPTION
            "RMON 15min TX Queue1 Discard Status. 'invalid' means the
            corresponding monitoring value is not reliable because of the
            alarm or other reasons. 'maintenance' means that some maintenance
            functions are executed on the current interval."
        ::= { rmon15minPortEntry 70 }

    rmon15minHCTxQueue2Discard OBJECT-TYPE
        SYNTAX       Counter64
        MAX-ACCESS   read-only
        STATUS       current
        DESCRIPTION  "RMON 15min TX Queue2 Discard"
        ::= { rmon15minPortEntry 71 }

    rmon15minHCTxQueue2DiscardStatusInfo OBJECT-TYPE
        SYNTAX       INTEGER {
                         invalid(0),
                         valid-no-maintenance(1),
                         valid-maintenance(2),
                         invalid-no-maintenance(3),
                         invalid-maintenance(4)
                     }
        MAX-ACCESS   read-only
        STATUS       current
        DESCRIPTION
            "RMON 15min TX Queue2 Discard Status. 'invalid' means the
            corresponding monitoring value is not reliable because of the
            alarm or other reasons. 'maintenance' means that some maintenance
            functions are executed on the current interval."
        ::= { rmon15minPortEntry 72 }

    rmon15minHCTxQueue3Discard OBJECT-TYPE
        SYNTAX       Counter64
        MAX-ACCESS   read-only
        STATUS       current
        DESCRIPTION  "RMON 15min TX Queue3 Discard"
        ::= { rmon15minPortEntry 73 }

    rmon15minHCTxQueue3DiscardStatusInfo OBJECT-TYPE
        SYNTAX       INTEGER {
                         invalid(0),
                         valid-no-maintenance(1),
                         valid-maintenance(2),
                         invalid-no-maintenance(3),
                         invalid-maintenance(4)
                     }
        MAX-ACCESS   read-only
        STATUS       current
        DESCRIPTION
            "RMON 15min TX Queue3 Discard Status. 'invalid' means the
            corresponding monitoring value is not reliable because of the
            alarm or other reasons. 'maintenance' means that some maintenance
            functions are executed on the current interval."
        ::= { rmon15minPortEntry 74 }

    rmon15minHCTxQueue4Discard OBJECT-TYPE
        SYNTAX       Counter64
        MAX-ACCESS   read-only
        STATUS       current
        DESCRIPTION
            "RMON 15min TX Queue4 Discard. If the equipment is running on 4
            class QoS mode. The value of this object is always 0."
        ::= { rmon15minPortEntry 75 }

    rmon15minHCTxQueue4DiscardStatusInfo OBJECT-TYPE
        SYNTAX       INTEGER {
                         invalid(0),
                         valid-no-maintenance(1),
                         valid-maintenance(2),
                         invalid-no-maintenance(3),
                         invalid-maintenance(4)
                     }
        MAX-ACCESS   read-only
        STATUS       current
        DESCRIPTION
            "RMON 15min TX Queue4 Discard Status. 'invalid' means the
            corresponding monitoring value is not reliable because of the
            alarm or other reasons. 'maintenance' means that some maintenance
            functions are executed on the current interval."
        ::= { rmon15minPortEntry 76 }

    rmon15minHCTxQueue5Discard OBJECT-TYPE
        SYNTAX       Counter64
        MAX-ACCESS   read-only
        STATUS       current
        DESCRIPTION
            "RMON 15min TX Queue5 Discard. If the equipment is running on 4
            class QoS mode. The value of this object is always 0."
        ::= { rmon15minPortEntry 77 }

    rmon15minHCTxQueue5DiscardStatusInfo OBJECT-TYPE
        SYNTAX       INTEGER {
                         invalid(0),
                         valid-no-maintenance(1),
                         valid-maintenance(2),
                         invalid-no-maintenance(3),
                         invalid-maintenance(4)
                     }
        MAX-ACCESS   read-only
        STATUS       current
        DESCRIPTION
            "RMON 15min TX Queue5 Discard Status. 'invalid' means the
            corresponding monitoring value is not reliable because of the
            alarm or other reasons. 'maintenance' means that some maintenance
            functions are executed on the current interval."
        ::= { rmon15minPortEntry 78 }

    rmon15minHCTxQueue6Discard OBJECT-TYPE
        SYNTAX       Counter64
        MAX-ACCESS   read-only
        STATUS       current
        DESCRIPTION
            "RMON 15min TX Queue6 Discard. If the equipment is running on 4
            class QoS mode. The value of this object is always 0."
        ::= { rmon15minPortEntry 79 }

    rmon15minHCTxQueue6DiscardStatusInfo OBJECT-TYPE
        SYNTAX       INTEGER {
                         invalid(0),
                         valid-no-maintenance(1),
                         valid-maintenance(2),
                         invalid-no-maintenance(3),
                         invalid-maintenance(4)
                     }
        MAX-ACCESS   read-only
        STATUS       current
        DESCRIPTION
            "RMON 15min TX Queue6 Discard Status. 'invalid' means the
            corresponding monitoring value is not reliable because of the
            alarm or other reasons. 'maintenance' means that some maintenance
            functions are executed on the current interval."
        ::= { rmon15minPortEntry 80 }

    rmon15minHCTxQueue7Discard OBJECT-TYPE
        SYNTAX       Counter64
        MAX-ACCESS   read-only
        STATUS       current
        DESCRIPTION
            "RMON 15min TX Queue7 Discard. If the equipment is running on 4
            class QoS mode. The value of this object is always 0."
        ::= { rmon15minPortEntry 81 }

    rmon15minHCTxQueue7DiscardStatusInfo OBJECT-TYPE
        SYNTAX       INTEGER {
                         invalid(0),
                         valid-no-maintenance(1),
                         valid-maintenance(2),
                         invalid-no-maintenance(3),
                         invalid-maintenance(4)
                     }
        MAX-ACCESS   read-only
        STATUS       current
        DESCRIPTION
            "RMON 15min TX Queue7 Discard Status. 'invalid' means the
            corresponding monitoring value is not reliable because of the
            alarm or other reasons. 'maintenance' means that some maintenance
            functions are executed on the current interval."
        ::= { rmon15minPortEntry 82 }

    rmon15minTxEthStatsOversizePkts OBJECT-TYPE
        SYNTAX       Counter32
        MAX-ACCESS   read-only
        STATUS       current
        DESCRIPTION  "RMON 15min TX Oversize Pkts."
        ::= { rmon15minPortEntry 83 }

    rmon15minTxEthStatsOversizePktsStatusInfo OBJECT-TYPE
        SYNTAX       INTEGER {
                         invalid(0),
                         valid-no-maintenance(1),
                         valid-maintenance(2),
                         invalid-no-maintenance(3),
                         invalid-maintenance(4)
                     }
        MAX-ACCESS   read-only
        STATUS       current
        DESCRIPTION
            "RMON 15min TX Oversize Pkts Status. 'invalid' means the
            corresponding monitoring value is not reliable because of the
            alarm or other reasons. 'maintenance' means that some maintenance
            functions are executed on the current interval."
        ::= { rmon15minPortEntry 84 }

    rmon15minPort2Table OBJECT-TYPE
        SYNTAX       SEQUENCE OF Rmon15minPort2Entry
        MAX-ACCESS   not-accessible
        STATUS       current
        DESCRIPTION  "RMON 15min Port Monitoring Table."
        ::= { rmon15minPortGroup 2 }

    rmon15minPort2Entry OBJECT-TYPE
        SYNTAX       Rmon15minPort2Entry
        MAX-ACCESS   not-accessible
        STATUS       current
        DESCRIPTION  ""
        INDEX        { rmon15minPort2IfIndex }
        ::= { rmon15minPort2Table 1 }

    Rmon15minPort2Entry ::= SEQUENCE {
        rmon15minPort2IfIndex                             InterfaceIndex,
        rmon15minPort2NEAddress                           IpAddress,
        rmon15minHCRxEthStatsOctets2                      Counter64,
        rmon15minHCRxEthStatsOctets2Status                IpeStatsInfo,
        rmon15minHCTxEthStatsOctets2                      Counter64,
        rmon15minHCTxEthStatsOctets2Status                IpeStatsInfo,
        rmon15minHCRxEthStatsPkts2                        Counter64,
        rmon15minHCRxEthStatsPkts2Status                  IpeStatsInfo,
        rmon15minHCTxEthStatsPkts2                        Counter64,
        rmon15minHCTxEthStatsPkts2Status                  IpeStatsInfo,
        rmon15minRxEthStatsDropEvents2                    Counter32,
        rmon15minRxEthStatsDropEvents2Status              IpeStatsInfo,
        rmon15minRxEthStatsUndersizePkts2                 Counter32,
        rmon15minRxEthStatsUndersizePkts2Status           IpeStatsInfo,
        rmon15minRxEthStatsFragments2                     Counter32,
        rmon15minRxEthStatsFragments2Status               IpeStatsInfo,
        rmon15minHCRxEthStatsPkts64Octets2                Counter64,
        rmon15minHCRxEthStatsPkts64Octets2Status          IpeStatsInfo,
        rmon15minHCTxEthStatsPkts64Octets2                Counter64,
        rmon15minHCTxEthStatsPkts64Octets2Status          IpeStatsInfo,
        rmon15minHCRxEthStatsPkts65to127Octets2           Counter64,
        rmon15minHCRxEthStatsPkts65to127Octets2Status     IpeStatsInfo,
        rmon15minHCTxEthStatsPkts65to127Octets2           Counter64,
        rmon15minHCTxEthStatsPkts65to127Octets2Status     IpeStatsInfo,
        rmon15minHCRxEthStatsPkts128to255Octets2          Counter64,
        rmon15minHCRxEthStatsPkts128to255Octets2Status    IpeStatsInfo,
        rmon15minHCTxEthStatsPkts128to255Octets2          Counter64,
        rmon15minHCTxEthStatsPkts128to255Octets2Status    IpeStatsInfo,
        rmon15minHCRxEthStatsPkts256to511Octets2          Counter64,
        rmon15minHCRxEthStatsPkts256to511Octets2Status    IpeStatsInfo,
        rmon15minHCTxEthStatsPkts256to511Octets2          Counter64,
        rmon15minHCTxEthStatsPkts256to511Octets2Status    IpeStatsInfo,
        rmon15minHCRxEthStatsPkts512to1023Octets2         Counter64,
        rmon15minHCRxEthStatsPkts512to1023Octets2Status   IpeStatsInfo,
        rmon15minHCTxEthStatsPkts512to1023Octets2         Counter64,
        rmon15minHCTxEthStatsPkts512to1023Octets2Status   IpeStatsInfo,
        rmon15minHCRxEthStatsPkts1024to1518Octets2        Counter64,
        rmon15minHCRxEthStatsPkts1024to1518Octets2Status  IpeStatsInfo,
        rmon15minHCTxEthStatsPkts1024to1518Octets2        Counter64,
        rmon15minHCTxEthStatsPkts1024to1518Octets2Status  IpeStatsInfo,
        rmon15minRxEthStatsCRCAlignErrors2                Counter32,
        rmon15minRxEthStatsCRCAlignErrors2Status          IpeStatsInfo,
        rmon15minRxEthStatsOversizePkts2                  Counter32,
        rmon15minRxEthStatsOversizePkts2Status            IpeStatsInfo,
        rmon15minRxEthStatsJabbers2                       Counter32,
        rmon15minRxEthStatsJabbers2Status                 IpeStatsInfo,
        rmon15minRxEthStatsMulticastPkts2                 Counter32,
        rmon15minRxEthStatsMulticastPkts2Status           IpeStatsInfo,
        rmon15minTxEthStatsMulticastPkts2                 Counter32,
        rmon15minTxEthStatsMulticastPkts2Status           IpeStatsInfo,
        rmon15minRxEthStatsBroadcastPkts2                 Counter32,
        rmon15minRxEthStatsBroadcastPkts2Status           IpeStatsInfo,
        rmon15minTxEthStatsBroadcastPkts2                 Counter32,
        rmon15minTxEthStatsBroadcastPkts2Status           IpeStatsInfo,
        rmon15minTxEthStatsCollisions2                    Counter32,
        rmon15minTxEthStatsCollisions2Status              IpeStatsInfo,
        rmon15minHCRxUnknownTPID2                         Counter64,
        rmon15minHCRxUnknownTPID2Status                   IpeStatsInfo,
        rmon15minHCRxUnknownVID2                          Counter64,
        rmon15minHCRxUnknownVID2Status                    IpeStatsInfo,
        rmon15minHCRxMAClimit2                            Counter64,
        rmon15minHCRxMAClimit2Status                      IpeStatsInfo,
        rmon15minHCRxFilterDiscard2                       Counter64,
        rmon15minHCRxFilterDiscard2Status                 IpeStatsInfo,
        rmon15minHCRxQoSDiscard2                          Counter64,
        rmon15minHCRxQoSDiscard2Status                    IpeStatsInfo,
        rmon15minHCTxQueue0Discard2                       Counter64,
        rmon15minHCTxQueue0Discard2Status                 IpeStatsInfo,
        rmon15minHCTxQueue1Discard2                       Counter64,
        rmon15minHCTxQueue1Discard2Status                 IpeStatsInfo,
        rmon15minHCTxQueue2Discard2                       Counter64,
        rmon15minHCTxQueue2Discard2Status                 IpeStatsInfo,
        rmon15minHCTxQueue3Discard2                       Counter64,
        rmon15minHCTxQueue3Discard2Status                 IpeStatsInfo,
        rmon15minHCTxQueue4Discard2                       Counter64,
        rmon15minHCTxQueue4Discard2Status                 IpeStatsInfo,
        rmon15minHCTxQueue5Discard2                       Counter64,
        rmon15minHCTxQueue5Discard2Status                 IpeStatsInfo,
        rmon15minHCTxQueue6Discard2                       Counter64,
        rmon15minHCTxQueue6Discard2Status                 IpeStatsInfo,
        rmon15minHCTxQueue7Discard2                       Counter64,
        rmon15minHCTxQueue7Discard2Status                 IpeStatsInfo,
        rmon15minTxEthStatsOversizePkts2                  Counter32,
        rmon15minTxEthStatsOversizePkts2Status            IpeStatsInfo
    }

    rmon15minPort2IfIndex OBJECT-TYPE
        SYNTAX       InterfaceIndex
        MAX-ACCESS   not-accessible
        STATUS       current
        DESCRIPTION  "Index of this table."
        ::= { rmon15minPort2Entry 1 }

    rmon15minPort2NEAddress OBJECT-TYPE
        SYNTAX       IpAddress
        MAX-ACCESS   not-accessible
        STATUS       current
        DESCRIPTION  "reserved."
        ::= { rmon15minPort2Entry 2 }

    rmon15minHCRxEthStatsOctets2 OBJECT-TYPE
        SYNTAX       Counter64
        MAX-ACCESS   read-only
        STATUS       current
        DESCRIPTION  "RMON 15min RX Octs"
        ::= { rmon15minPort2Entry 3 }

    rmon15minHCRxEthStatsOctets2Status OBJECT-TYPE
        SYNTAX       IpeStatsInfo
        MAX-ACCESS   read-only
        STATUS       current
        DESCRIPTION
            "RMON 15min RX Octs Status. 'invalid' means the corresponding
            monitoring value is not reliable because of the alarm or other
            reasons. 'maintenance' means that some maintenance functions are
            executed on the current interval."
        ::= { rmon15minPort2Entry 4 }

    rmon15minHCTxEthStatsOctets2 OBJECT-TYPE
        SYNTAX       Counter64
        MAX-ACCESS   read-only
        STATUS       current
        DESCRIPTION  "RMON 15min TX Octs"
        ::= { rmon15minPort2Entry 5 }

    rmon15minHCTxEthStatsOctets2Status OBJECT-TYPE
        SYNTAX       IpeStatsInfo
        MAX-ACCESS   read-only
        STATUS       current
        DESCRIPTION
            "RMON 15min TX Octs Status. 'invalid' means the corresponding
            monitoring value is not reliable because of the alarm or other
            reasons. 'maintenance' means that some maintenance functions are
            executed on the current interval."
        ::= { rmon15minPort2Entry 6 }

    rmon15minHCRxEthStatsPkts2 OBJECT-TYPE
        SYNTAX       Counter64
        MAX-ACCESS   read-only
        STATUS       current
        DESCRIPTION  "RMON 15min RX Pkts"
        ::= { rmon15minPort2Entry 7 }

    rmon15minHCRxEthStatsPkts2Status OBJECT-TYPE
        SYNTAX       IpeStatsInfo
        MAX-ACCESS   read-only
        STATUS       current
        DESCRIPTION
            "RMON 15min RX Pkts Status. 'invalid' means the corresponding
            monitoring value is not reliable because of the alarm or other
            reasons. 'maintenance' means that some maintenance functions are
            executed on the current interval."
        ::= { rmon15minPort2Entry 8 }

    rmon15minHCTxEthStatsPkts2 OBJECT-TYPE
        SYNTAX       Counter64
        MAX-ACCESS   read-only
        STATUS       current
        DESCRIPTION  "RMON 15min TX Pkts"
        ::= { rmon15minPort2Entry 9 }

    rmon15minHCTxEthStatsPkts2Status OBJECT-TYPE
        SYNTAX       IpeStatsInfo
        MAX-ACCESS   read-only
        STATUS       current
        DESCRIPTION
            "RMON 15min TX Pkts Status. 'invalid' means the corresponding
            monitoring value is not reliable because of the alarm or other
            reasons. 'maintenance' means that some maintenance functions are
            executed on the current interval."
        ::= { rmon15minPort2Entry 10 }

    rmon15minRxEthStatsDropEvents2 OBJECT-TYPE
        SYNTAX       Counter32
        MAX-ACCESS   read-only
        STATUS       current
        DESCRIPTION  "RMON 15min RX Drop Events"
        ::= { rmon15minPort2Entry 11 }

    rmon15minRxEthStatsDropEvents2Status OBJECT-TYPE
        SYNTAX       IpeStatsInfo
        MAX-ACCESS   read-only
        STATUS       current
        DESCRIPTION
            "RMON 15min RX Drop Events Status. 'invalid' means the
            corresponding monitoring value is not reliable because of the
            alarm or other reasons. 'maintenance' means that some maintenance
            functions are executed on the current interval."
        ::= { rmon15minPort2Entry 12 }

    rmon15minRxEthStatsUndersizePkts2 OBJECT-TYPE
        SYNTAX       Counter32
        MAX-ACCESS   read-only
        STATUS       current
        DESCRIPTION  "RMON 15min RX Undersize Pkts"
        ::= { rmon15minPort2Entry 13 }

    rmon15minRxEthStatsUndersizePkts2Status OBJECT-TYPE
        SYNTAX       IpeStatsInfo
        MAX-ACCESS   read-only
        STATUS       current
        DESCRIPTION
            "RMON 15min RX Undersize Pkts Status. 'invalid' means the
            corresponding monitoring value is not reliable because of the
            alarm or other reasons. 'maintenance' means that some maintenance
            functions are executed on the current interval."
        ::= { rmon15minPort2Entry 14 }

    rmon15minRxEthStatsFragments2 OBJECT-TYPE
        SYNTAX       Counter32
        MAX-ACCESS   read-only
        STATUS       current
        DESCRIPTION  "RMON 15min RX Fragments"
        ::= { rmon15minPort2Entry 15 }

    rmon15minRxEthStatsFragments2Status OBJECT-TYPE
        SYNTAX       IpeStatsInfo
        MAX-ACCESS   read-only
        STATUS       current
        DESCRIPTION
            "RMON 15min RX Fragments Status. 'invalid' means the
            corresponding monitoring value is not reliable because of the
            alarm or other reasons. 'maintenance' means that some maintenance
            functions are executed on the current interval."
        ::= { rmon15minPort2Entry 16 }

    rmon15minHCRxEthStatsPkts64Octets2 OBJECT-TYPE
        SYNTAX       Counter64
        MAX-ACCESS   read-only
        STATUS       current
        DESCRIPTION  "RMON 15min RX 64 Octs"
        ::= { rmon15minPort2Entry 17 }

    rmon15minHCRxEthStatsPkts64Octets2Status OBJECT-TYPE
        SYNTAX       IpeStatsInfo
        MAX-ACCESS   read-only
        STATUS       current
        DESCRIPTION
            "RMON 15min RX 64 Octs Status. 'invalid' means the corresponding
            monitoring value is not reliable because of the alarm or other
            reasons. 'maintenance' means that some maintenance functions are
            executed on the current interval."
        ::= { rmon15minPort2Entry 18 }

    rmon15minHCTxEthStatsPkts64Octets2 OBJECT-TYPE
        SYNTAX       Counter64
        MAX-ACCESS   read-only
        STATUS       current
        DESCRIPTION  "RMON 15min TX 64 Octs"
        ::= { rmon15minPort2Entry 19 }

    rmon15minHCTxEthStatsPkts64Octets2Status OBJECT-TYPE
        SYNTAX       IpeStatsInfo
        MAX-ACCESS   read-only
        STATUS       current
        DESCRIPTION
            "RMON 15min TX 64 Octs Status. 'invalid' means the corresponding
            monitoring value is not reliable because of the alarm or other
            reasons. 'maintenance' means that some maintenance functions are
            executed on the current interval."
        ::= { rmon15minPort2Entry 20 }

    rmon15minHCRxEthStatsPkts65to127Octets2 OBJECT-TYPE
        SYNTAX       Counter64
        MAX-ACCESS   read-only
        STATUS       current
        DESCRIPTION  "RMON 15min RX 65 to 127 Octs"
        ::= { rmon15minPort2Entry 21 }

    rmon15minHCRxEthStatsPkts65to127Octets2Status OBJECT-TYPE
        SYNTAX       IpeStatsInfo
        MAX-ACCESS   read-only
        STATUS       current
        DESCRIPTION
            "RMON 15min RX 65 to 127 Octs Status. 'invalid' means the
            corresponding monitoring value is not reliable because of the
            alarm or other reasons. 'maintenance' means that some maintenance
            functions are executed on the current interval."
        ::= { rmon15minPort2Entry 22 }

    rmon15minHCTxEthStatsPkts65to127Octets2 OBJECT-TYPE
        SYNTAX       Counter64
        MAX-ACCESS   read-only
        STATUS       current
        DESCRIPTION  "RMON 15min TX 65 to 127 Octs"
        ::= { rmon15minPort2Entry 23 }

    rmon15minHCTxEthStatsPkts65to127Octets2Status OBJECT-TYPE
        SYNTAX       IpeStatsInfo
        MAX-ACCESS   read-only
        STATUS       current
        DESCRIPTION
            "RMON 15min TX 65 to 127 Octs Status. 'invalid' means the
            corresponding monitoring value is not reliable because of the
            alarm or other reasons. 'maintenance' means that some maintenance
            functions are executed on the current interval."
        ::= { rmon15minPort2Entry 24 }

    rmon15minHCRxEthStatsPkts128to255Octets2 OBJECT-TYPE
        SYNTAX       Counter64
        MAX-ACCESS   read-only
        STATUS       current
        DESCRIPTION  "RMON 15min RX 128 to 255 Octs"
        ::= { rmon15minPort2Entry 25 }

    rmon15minHCRxEthStatsPkts128to255Octets2Status OBJECT-TYPE
        SYNTAX       IpeStatsInfo
        MAX-ACCESS   read-only
        STATUS       current
        DESCRIPTION
            "RMON 15min RX 128 to 255 Octs Status. 'invalid' means the
            corresponding monitoring value is not reliable because of the
            alarm or other reasons. 'maintenance' means that some maintenance
            functions are executed on the current interval."
        ::= { rmon15minPort2Entry 26 }

    rmon15minHCTxEthStatsPkts128to255Octets2 OBJECT-TYPE
        SYNTAX       Counter64
        MAX-ACCESS   read-only
        STATUS       current
        DESCRIPTION  "RMON 15min TX 128 to 255 Octs"
        ::= { rmon15minPort2Entry 27 }

    rmon15minHCTxEthStatsPkts128to255Octets2Status OBJECT-TYPE
        SYNTAX       IpeStatsInfo
        MAX-ACCESS   read-only
        STATUS       current
        DESCRIPTION
            "RMON 15min TX 128 to 255 Octs Status. 'invalid' means the
            corresponding monitoring value is not reliable because of the
            alarm or other reasons. 'maintenance' means that some maintenance
            functions are executed on the current interval."
        ::= { rmon15minPort2Entry 28 }

    rmon15minHCRxEthStatsPkts256to511Octets2 OBJECT-TYPE
        SYNTAX       Counter64
        MAX-ACCESS   read-only
        STATUS       current
        DESCRIPTION  "RMON 15min RX 256 to 511 Octs"
        ::= { rmon15minPort2Entry 29 }

    rmon15minHCRxEthStatsPkts256to511Octets2Status OBJECT-TYPE
        SYNTAX       IpeStatsInfo
        MAX-ACCESS   read-only
        STATUS       current
        DESCRIPTION
            "RMON 15min RX 256 to 511 Octs Status. 'invalid' means the
            corresponding monitoring value is not reliable because of the
            alarm or other reasons. 'maintenance' means that some maintenance
            functions are executed on the current interval."
        ::= { rmon15minPort2Entry 30 }

    rmon15minHCTxEthStatsPkts256to511Octets2 OBJECT-TYPE
        SYNTAX       Counter64
        MAX-ACCESS   read-only
        STATUS       current
        DESCRIPTION  "RMON 15min TX 256 to 511 Octs"
        ::= { rmon15minPort2Entry 31 }

    rmon15minHCTxEthStatsPkts256to511Octets2Status OBJECT-TYPE
        SYNTAX       IpeStatsInfo
        MAX-ACCESS   read-only
        STATUS       current
        DESCRIPTION
            "RMON 15min TX 256 to 511 Octs Status. 'invalid' means the
            corresponding monitoring value is not reliable because of the
            alarm or other reasons. 'maintenance' means that some maintenance
            functions are executed on the current interval."
        ::= { rmon15minPort2Entry 32 }

    rmon15minHCRxEthStatsPkts512to1023Octets2 OBJECT-TYPE
        SYNTAX       Counter64
        MAX-ACCESS   read-only
        STATUS       current
        DESCRIPTION  "RMON 15min RX 512 to 1023 Octs"
        ::= { rmon15minPort2Entry 33 }

    rmon15minHCRxEthStatsPkts512to1023Octets2Status OBJECT-TYPE
        SYNTAX       IpeStatsInfo
        MAX-ACCESS   read-only
        STATUS       current
        DESCRIPTION
            "RMON 15min RX 512 to 1023 Octs Status. 'invalid' means the
            corresponding monitoring value is not reliable because of the
            alarm or other reasons. 'maintenance' means that some maintenance
            functions are executed on the current interval."
        ::= { rmon15minPort2Entry 34 }

    rmon15minHCTxEthStatsPkts512to1023Octets2 OBJECT-TYPE
        SYNTAX       Counter64
        MAX-ACCESS   read-only
        STATUS       current
        DESCRIPTION  "RMON 15min TX 512 to 1023 Octs"
        ::= { rmon15minPort2Entry 35 }

    rmon15minHCTxEthStatsPkts512to1023Octets2Status OBJECT-TYPE
        SYNTAX       IpeStatsInfo
        MAX-ACCESS   read-only
        STATUS       current
        DESCRIPTION
            "RMON 15min TX 512 to 1023 Octs Status. 'invalid' means the
            corresponding monitoring value is not reliable because of the
            alarm or other reasons. 'maintenance' means that some maintenance
            functions are executed on the current interval."
        ::= { rmon15minPort2Entry 36 }

    rmon15minHCRxEthStatsPkts1024to1518Octets2 OBJECT-TYPE
        SYNTAX       Counter64
        MAX-ACCESS   read-only
        STATUS       current
        DESCRIPTION  "RMON 15min RX 1024 to 1518 Octs"
        ::= { rmon15minPort2Entry 37 }

    rmon15minHCRxEthStatsPkts1024to1518Octets2Status OBJECT-TYPE
        SYNTAX       IpeStatsInfo
        MAX-ACCESS   read-only
        STATUS       current
        DESCRIPTION
            "RMON 15min RX 1024 to 1518 Octs Status. 'invalid' means the
            corresponding monitoring value is not reliable because of the
            alarm or other reasons. 'maintenance' means that some maintenance
            functions are executed on the current interval."
        ::= { rmon15minPort2Entry 38 }

    rmon15minHCTxEthStatsPkts1024to1518Octets2 OBJECT-TYPE
        SYNTAX       Counter64
        MAX-ACCESS   read-only
        STATUS       current
        DESCRIPTION  "RMON 15min TX 1024 to 1518 Octs"
        ::= { rmon15minPort2Entry 39 }

    rmon15minHCTxEthStatsPkts1024to1518Octets2Status OBJECT-TYPE
        SYNTAX       IpeStatsInfo
        MAX-ACCESS   read-only
        STATUS       current
        DESCRIPTION
            "RMON 15min TX 1024 to 1518 Octs Status. 'invalid' means the
            corresponding monitoring value is not reliable because of the
            alarm or other reasons. 'maintenance' means that some maintenance
            functions are executed on the current interval."
        ::= { rmon15minPort2Entry 40 }

    rmon15minRxEthStatsCRCAlignErrors2 OBJECT-TYPE
        SYNTAX       Counter32
        MAX-ACCESS   read-only
        STATUS       current
        DESCRIPTION  "RMON 15min RX CRC Alignment Errors"
        ::= { rmon15minPort2Entry 41 }

    rmon15minRxEthStatsCRCAlignErrors2Status OBJECT-TYPE
        SYNTAX       IpeStatsInfo
        MAX-ACCESS   read-only
        STATUS       current
        DESCRIPTION
            "RMON 15min RX CRC Alignment Errors Status. 'invalid' means the
            corresponding monitoring value is not reliable because of the
            alarm or other reasons. 'maintenance' means that some maintenance
            functions are executed on the current interval."
        ::= { rmon15minPort2Entry 42 }

    rmon15minRxEthStatsOversizePkts2 OBJECT-TYPE
        SYNTAX       Counter32
        MAX-ACCESS   read-only
        STATUS       current
        DESCRIPTION  "RMON 15min RX Oversize Pkts"
        ::= { rmon15minPort2Entry 43 }

    rmon15minRxEthStatsOversizePkts2Status OBJECT-TYPE
        SYNTAX       IpeStatsInfo
        MAX-ACCESS   read-only
        STATUS       current
        DESCRIPTION
            "RMON 15min RX Oversize Pkts Status. 'invalid' means the
            corresponding monitoring value is not reliable because of the
            alarm or other reasons. 'maintenance' means that some maintenance
            functions are executed on the current interval."
        ::= { rmon15minPort2Entry 44 }

    rmon15minRxEthStatsJabbers2 OBJECT-TYPE
        SYNTAX       Counter32
        MAX-ACCESS   read-only
        STATUS       current
        DESCRIPTION  "RMON 15min RX Jabbers"
        ::= { rmon15minPort2Entry 45 }

    rmon15minRxEthStatsJabbers2Status OBJECT-TYPE
        SYNTAX       IpeStatsInfo
        MAX-ACCESS   read-only
        STATUS       current
        DESCRIPTION
            "RMON 15min RX Jabbers Status. 'invalid' means the corresponding
            monitoring value is not reliable because of the alarm or other
            reasons. 'maintenance' means that some maintenance functions are
            executed on the current interval."
        ::= { rmon15minPort2Entry 46 }

    rmon15minRxEthStatsMulticastPkts2 OBJECT-TYPE
        SYNTAX       Counter32
        MAX-ACCESS   read-only
        STATUS       current
        DESCRIPTION  "RMON 15min RX Multicast Pkts"
        ::= { rmon15minPort2Entry 47 }

    rmon15minRxEthStatsMulticastPkts2Status OBJECT-TYPE
        SYNTAX       IpeStatsInfo
        MAX-ACCESS   read-only
        STATUS       current
        DESCRIPTION
            "RMON 15min RX Multicast Pkts Status. 'invalid' means the
            corresponding monitoring value is not reliable because of the
            alarm or other reasons. 'maintenance' means that some maintenance
            functions are executed on the current interval."
        ::= { rmon15minPort2Entry 48 }

    rmon15minTxEthStatsMulticastPkts2 OBJECT-TYPE
        SYNTAX       Counter32
        MAX-ACCESS   read-only
        STATUS       current
        DESCRIPTION  "RMON 15min TX Multicast Pkts"
        ::= { rmon15minPort2Entry 49 }

    rmon15minTxEthStatsMulticastPkts2Status OBJECT-TYPE
        SYNTAX       IpeStatsInfo
        MAX-ACCESS   read-only
        STATUS       current
        DESCRIPTION
            "RMON 15min TX Multicast Pkts Status. 'invalid' means the
            corresponding monitoring value is not reliable because of the
            alarm or other reasons. 'maintenance' means that some maintenance
            functions are executed on the current interval."
        ::= { rmon15minPort2Entry 50 }

    rmon15minRxEthStatsBroadcastPkts2 OBJECT-TYPE
        SYNTAX       Counter32
        MAX-ACCESS   read-only
        STATUS       current
        DESCRIPTION  "RMON 15min RX Broadcast Pkts"
        ::= { rmon15minPort2Entry 51 }

    rmon15minRxEthStatsBroadcastPkts2Status OBJECT-TYPE
        SYNTAX       IpeStatsInfo
        MAX-ACCESS   read-only
        STATUS       current
        DESCRIPTION
            "RMON 15min RX Broadcast Pkts Status. 'invalid' means the
            corresponding monitoring value is not reliable because of the
            alarm or other reasons. 'maintenance' means that some maintenance
            functions are executed on the current interval."
        ::= { rmon15minPort2Entry 52 }

    rmon15minTxEthStatsBroadcastPkts2 OBJECT-TYPE
        SYNTAX       Counter32
        MAX-ACCESS   read-only
        STATUS       current
        DESCRIPTION  "RMON 15min TX Broadcast Pkts"
        ::= { rmon15minPort2Entry 53 }

    rmon15minTxEthStatsBroadcastPkts2Status OBJECT-TYPE
        SYNTAX       IpeStatsInfo
        MAX-ACCESS   read-only
        STATUS       current
        DESCRIPTION
            "RMON 15min TX Broadcast Pkts Status. 'invalid' means the
            corresponding monitoring value is not reliable because of the
            alarm or other reasons. 'maintenance' means that some maintenance
            functions are executed on the current interval."
        ::= { rmon15minPort2Entry 54 }

    rmon15minTxEthStatsCollisions2 OBJECT-TYPE
        SYNTAX       Counter32
        MAX-ACCESS   read-only
        STATUS       current
        DESCRIPTION  "RMON 15min TX Collisions"
        ::= { rmon15minPort2Entry 55 }

    rmon15minTxEthStatsCollisions2Status OBJECT-TYPE
        SYNTAX       IpeStatsInfo
        MAX-ACCESS   read-only
        STATUS       current
        DESCRIPTION
            "RMON 15min TX Collisions Status. 'invalid' means the
            corresponding monitoring value is not reliable because of the
            alarm or other reasons. 'maintenance' means that some maintenance
            functions are executed on the current interval."
        ::= { rmon15minPort2Entry 56 }

    rmon15minHCRxUnknownTPID2 OBJECT-TYPE
        SYNTAX       Counter64
        MAX-ACCESS   read-only
        STATUS       current
        DESCRIPTION  "RMON 15min Unknown TPID"
        ::= { rmon15minPort2Entry 57 }

    rmon15minHCRxUnknownTPID2Status OBJECT-TYPE
        SYNTAX       IpeStatsInfo
        MAX-ACCESS   read-only
        STATUS       current
        DESCRIPTION
            "RMON 15min Unknown TPID Status. 'invalid' means the
            corresponding monitoring value is not reliable because of the
            alarm or other reasons. 'maintenance' means that some maintenance
            functions are executed on the current interval."
        ::= { rmon15minPort2Entry 58 }

    rmon15minHCRxUnknownVID2 OBJECT-TYPE
        SYNTAX       Counter64
        MAX-ACCESS   read-only
        STATUS       current
        DESCRIPTION  "RMON 15min Unknown VID"
        ::= { rmon15minPort2Entry 59 }

    rmon15minHCRxUnknownVID2Status OBJECT-TYPE
        SYNTAX       IpeStatsInfo
        MAX-ACCESS   read-only
        STATUS       current
        DESCRIPTION
            "RMON 15min Unknown VID Status. 'invalid' means the corresponding
            monitoring value is not reliable because of the alarm or other
            reasons. 'maintenance' means that some maintenance functions are
            executed on the current interval."
        ::= { rmon15minPort2Entry 60 }

    rmon15minHCRxMAClimit2 OBJECT-TYPE
        SYNTAX       Counter64
        MAX-ACCESS   read-only
        STATUS       current
        DESCRIPTION  "RMON 15min RX MAC Limit"
        ::= { rmon15minPort2Entry 61 }

    rmon15minHCRxMAClimit2Status OBJECT-TYPE
        SYNTAX       IpeStatsInfo
        MAX-ACCESS   read-only
        STATUS       current
        DESCRIPTION
            "RMON 15min RX MAC Limit Status. 'invalid' means the
            corresponding monitoring value is not reliable because of the
            alarm or other reasons. 'maintenance' means that some maintenance
            functions are executed on the current interval."
        ::= { rmon15minPort2Entry 62 }

    rmon15minHCRxFilterDiscard2 OBJECT-TYPE
        SYNTAX       Counter64
        MAX-ACCESS   read-only
        STATUS       current
        DESCRIPTION  "RMON 15min RX Filter Discard"
        ::= { rmon15minPort2Entry 63 }

    rmon15minHCRxFilterDiscard2Status OBJECT-TYPE
        SYNTAX       IpeStatsInfo
        MAX-ACCESS   read-only
        STATUS       current
        DESCRIPTION
            "RMON 15min RX Filter Discard Status. 'invalid' means the
            corresponding monitoring value is not reliable because of the
            alarm or other reasons. 'maintenance' means that some maintenance
            functions are executed on the current interval."
        ::= { rmon15minPort2Entry 64 }

    rmon15minHCRxQoSDiscard2 OBJECT-TYPE
        SYNTAX       Counter64
        MAX-ACCESS   read-only
        STATUS       current
        DESCRIPTION  "RMON 15min RX QoS Discard"
        ::= { rmon15minPort2Entry 65 }

    rmon15minHCRxQoSDiscard2Status OBJECT-TYPE
        SYNTAX       IpeStatsInfo
        MAX-ACCESS   read-only
        STATUS       current
        DESCRIPTION
            "RMON 15min RX QoS Discard Status. 'invalid' means the
            corresponding monitoring value is not reliable because of the
            alarm or other reasons. 'maintenance' means that some maintenance
            functions are executed on the current interval."
        ::= { rmon15minPort2Entry 66 }

    rmon15minHCTxQueue0Discard2 OBJECT-TYPE
        SYNTAX       Counter64
        MAX-ACCESS   read-only
        STATUS       current
        DESCRIPTION  "RMON 15min TX Queue0 Discard"
        ::= { rmon15minPort2Entry 67 }

    rmon15minHCTxQueue0Discard2Status OBJECT-TYPE
        SYNTAX       IpeStatsInfo
        MAX-ACCESS   read-only
        STATUS       current
        DESCRIPTION
            "RMON 15min TX Queue0 Discard Status. 'invalid' means the
            corresponding monitoring value is not reliable because of the
            alarm or other reasons. 'maintenance' means that some maintenance
            functions are executed on the current interval."
        ::= { rmon15minPort2Entry 68 }

    rmon15minHCTxQueue1Discard2 OBJECT-TYPE
        SYNTAX       Counter64
        MAX-ACCESS   read-only
        STATUS       current
        DESCRIPTION  "RMON 15min TX Queue1 Discard"
        ::= { rmon15minPort2Entry 69 }

    rmon15minHCTxQueue1Discard2Status OBJECT-TYPE
        SYNTAX       IpeStatsInfo
        MAX-ACCESS   read-only
        STATUS       current
        DESCRIPTION
            "RMON 15min TX Queue1 Discard Status. 'invalid' means the
            corresponding monitoring value is not reliable because of the
            alarm or other reasons. 'maintenance' means that some maintenance
            functions are executed on the current interval."
        ::= { rmon15minPort2Entry 70 }

    rmon15minHCTxQueue2Discard2 OBJECT-TYPE
        SYNTAX       Counter64
        MAX-ACCESS   read-only
        STATUS       current
        DESCRIPTION  "RMON 15min TX Queue2 Discard"
        ::= { rmon15minPort2Entry 71 }

    rmon15minHCTxQueue2Discard2Status OBJECT-TYPE
        SYNTAX       IpeStatsInfo
        MAX-ACCESS   read-only
        STATUS       current
        DESCRIPTION
            "RMON 15min TX Queue2 Discard Status. 'invalid' means the
            corresponding monitoring value is not reliable because of the
            alarm or other reasons. 'maintenance' means that some maintenance
            functions are executed on the current interval."
        ::= { rmon15minPort2Entry 72 }

    rmon15minHCTxQueue3Discard2 OBJECT-TYPE
        SYNTAX       Counter64
        MAX-ACCESS   read-only
        STATUS       current
        DESCRIPTION  "RMON 15min TX Queue3 Discard"
        ::= { rmon15minPort2Entry 73 }

    rmon15minHCTxQueue3Discard2Status OBJECT-TYPE
        SYNTAX       IpeStatsInfo
        MAX-ACCESS   read-only
        STATUS       current
        DESCRIPTION
            "RMON 15min TX Queue3 Discard Status. 'invalid' means the
            corresponding monitoring value is not reliable because of the
            alarm or other reasons. 'maintenance' means that some maintenance
            functions are executed on the current interval."
        ::= { rmon15minPort2Entry 74 }

    rmon15minHCTxQueue4Discard2 OBJECT-TYPE
        SYNTAX       Counter64
        MAX-ACCESS   read-only
        STATUS       current
        DESCRIPTION
            "RMON 15min TX Queue4 Discard. If the equipment is running on 4
            class QoS mode. The value of this object is always 0."
        ::= { rmon15minPort2Entry 75 }

    rmon15minHCTxQueue4Discard2Status OBJECT-TYPE
        SYNTAX       IpeStatsInfo
        MAX-ACCESS   read-only
        STATUS       current
        DESCRIPTION
            "RMON 15min TX Queue4 Discard Status. 'invalid' means the
            corresponding monitoring value is not reliable because of the
            alarm or other reasons. 'maintenance' means that some maintenance
            functions are executed on the current interval."
        ::= { rmon15minPort2Entry 76 }

    rmon15minHCTxQueue5Discard2 OBJECT-TYPE
        SYNTAX       Counter64
        MAX-ACCESS   read-only
        STATUS       current
        DESCRIPTION
            "RMON 15min TX Queue5 Discard. If the equipment is running on 4
            class QoS mode. The value of this object is always 0."
        ::= { rmon15minPort2Entry 77 }

    rmon15minHCTxQueue5Discard2Status OBJECT-TYPE
        SYNTAX       IpeStatsInfo
        MAX-ACCESS   read-only
        STATUS       current
        DESCRIPTION
            "RMON 15min TX Queue5 Discard Status. 'invalid' means the
            corresponding monitoring value is not reliable because of the
            alarm or other reasons. 'maintenance' means that some maintenance
            functions are executed on the current interval."
        ::= { rmon15minPort2Entry 78 }

    rmon15minHCTxQueue6Discard2 OBJECT-TYPE
        SYNTAX       Counter64
        MAX-ACCESS   read-only
        STATUS       current
        DESCRIPTION
            "RMON 15min TX Queue6 Discard. If the equipment is running on 4
            class QoS mode. The value of this object is always 0."
        ::= { rmon15minPort2Entry 79 }

    rmon15minHCTxQueue6Discard2Status OBJECT-TYPE
        SYNTAX       IpeStatsInfo
        MAX-ACCESS   read-only
        STATUS       current
        DESCRIPTION
            "RMON 15min TX Queue6 Discard Status. 'invalid' means the
            corresponding monitoring value is not reliable because of the
            alarm or other reasons. 'maintenance' means that some maintenance
            functions are executed on the current interval."
        ::= { rmon15minPort2Entry 80 }

    rmon15minHCTxQueue7Discard2 OBJECT-TYPE
        SYNTAX       Counter64
        MAX-ACCESS   read-only
        STATUS       current
        DESCRIPTION
            "RMON 15min TX Queue7 Discard. If the equipment is running on 4
            class QoS mode. The value of this object is always 0."
        ::= { rmon15minPort2Entry 81 }

    rmon15minHCTxQueue7Discard2Status OBJECT-TYPE
        SYNTAX       IpeStatsInfo
        MAX-ACCESS   read-only
        STATUS       current
        DESCRIPTION
            "RMON 15min TX Queue7 Discard Status. 'invalid' means the
            corresponding monitoring value is not reliable because of the
            alarm or other reasons. 'maintenance' means that some maintenance
            functions are executed on the current interval."
        ::= { rmon15minPort2Entry 82 }

    rmon15minTxEthStatsOversizePkts2 OBJECT-TYPE
        SYNTAX       Counter32
        MAX-ACCESS   read-only
        STATUS       current
        DESCRIPTION  "RMON 15min TX Oversize Pkts."
        ::= { rmon15minPort2Entry 83 }

    rmon15minTxEthStatsOversizePkts2Status OBJECT-TYPE
        SYNTAX       IpeStatsInfo
        MAX-ACCESS   read-only
        STATUS       current
        DESCRIPTION
            "RMON 15min TX Oversize Pkts Status. 'invalid' means the
            corresponding monitoring value is not reliable because of the
            alarm or other reasons. 'maintenance' means that some maintenance
            functions are executed on the current interval."
        ::= { rmon15minPort2Entry 84 }

    rmon1dayportGroup OBJECT IDENTIFIER
        ::= { rmonEthGroup 2 }

    rmon1dayPortTable OBJECT-TYPE
        SYNTAX       SEQUENCE OF Rmon1dayPortEntry
        MAX-ACCESS   not-accessible
        STATUS       current
        DESCRIPTION  "RMON 1day Port Monitoring Table."
        ::= { rmon1dayportGroup 1 }

    rmon1dayPortEntry OBJECT-TYPE
        SYNTAX       Rmon1dayPortEntry
        MAX-ACCESS   not-accessible
        STATUS       current
        DESCRIPTION  ""
        INDEX        { rmon1dayIfIndex }
        ::= { rmon1dayPortTable 1 }

    Rmon1dayPortEntry ::= SEQUENCE {
        rmon1dayIfIndex                                   InterfaceIndex,
        rmon1dayNEAddress                                 IpAddress,
        rmon1dayHCRxEthStatsOctets                        Counter64,
        rmon1dayHCRxEthStatsOctetsStatusInfo              INTEGER,
        rmon1dayHCTxEthStatsOctets                        Counter64,
        rmon1dayHCTxEthStatsOctetsStatusInfo              INTEGER,
        rmon1dayRxEthStatsPkts                            Counter32,
        rmon1dayRxEthStatsPktsStatusInfo                  INTEGER,
        rmon1dayTxEthStatsPkts                            Counter32,
        rmon1dayTxEthStatsPktsStatusInfo                  INTEGER,
        rmon1dayRxEthStatsDropEvents                      Counter32,
        rmon1dayRxEthStatsDropEventsStatusInfo            INTEGER,
        rmon1dayRxEthStatsUndersizePkts                   Counter32,
        rmon1dayRxEthStatsUndersizePktsStatusInfo         INTEGER,
        rmon1dayRxEthStatsFragments                       Counter32,
        rmon1dayRxEthStatsFragmentsStatusInfo             INTEGER,
        rmon1dayRxEthStatsPkts64Octets                    Counter32,
        rmon1dayRxEthStatsPkts64OctetsStatusInfo          INTEGER,
        rmon1dayTxEthStatsPkts64Octets                    Counter32,
        rmon1dayTxEthStatsPkts64OctetsStatusInfo          INTEGER,
        rmon1dayRxEthStatsPkts65to127Octets               Counter32,
        rmon1dayRxEthStatsPkts65to127OctetsStatusInfo     INTEGER,
        rmon1dayTxEthStatsPkts65to127Octets               Counter32,
        rmon1dayTxEthStatsPkts65to127OctetsStatusInfo     INTEGER,
        rmon1dayRxEthStatsPkts128to255Octets              Counter32,
        rmon1dayRxEthStatsPkts128to255OctetsStatusInfo    INTEGER,
        rmon1dayTxEthStatsPkts128to255Octets              Counter32,
        rmon1dayTxEthStatsPkts128to255OctetsStatusInfo    INTEGER,
        rmon1dayRxEthStatsPkts256to511Octets              Counter32,
        rmon1dayRxEthStatsPkts256to511OctetsStatusInfo    INTEGER,
        rmon1dayTxEthStatsPkts256to511Octets              Counter32,
        rmon1dayTxEthStatsPkts256to511OctetsStatusInfo    INTEGER,
        rmon1dayRxEthStatsPkts512to1023Octets             Counter32,
        rmon1dayRxEthStatsPkts512to1023OctetsStatusInfo   INTEGER,
        rmon1dayTxEthStatsPkts512to1023Octets             Counter32,
        rmon1dayTxEthStatsPkts512to1023OctetsStatusInfo   INTEGER,
        rmon1dayRxEthStatsPkts1024to1518Octets            Counter32,
        rmon1dayRxEthStatsPkts1024to1518OctetsStatusInfo  INTEGER,
        rmon1dayTxEthStatsPkts1024to1518Octets            Counter32,
        rmon1dayTxEthStatsPkts1024to1518OctetsStatusInfo  INTEGER,
        rmon1dayRxEthStatsCRCAlignErrors                  Counter32,
        rmon1dayRxEthStatsCRCAlignErrorsStatusInfo        INTEGER,
        rmon1dayRxEthStatsOversizePkts                    Counter32,
        rmon1dayRxEthStatsOversizePktsStatusInfo          INTEGER,
        rmon1dayRxEthStatsJabbers                         Counter32,
        rmon1dayRxEthStatsJabbersStatusInfo               INTEGER,
        rmon1dayRxEthStatsMulticastPkts                   Counter32,
        rmon1dayRxEthStatsMulticastPktsStatusInfo         INTEGER,
        rmon1dayTxEthStatsMulticastPkts                   Counter32,
        rmon1dayTxEthStatsMulticastPktsStatusInfo         INTEGER,
        rmon1dayRxEthStatsBroadcastPkts                   Counter32,
        rmon1dayRxEthStatsBroadcastPktsStatusInfo         INTEGER,
        rmon1dayTxEthStatsBroadcastPkts                   Counter32,
        rmon1dayTxEthStatsBroadcastPktsStatusInfo         INTEGER,
        rmon1dayTxEthStatsCollisions                      Counter32,
        rmon1dayTxEthStatsCollisionsStatusInfo            INTEGER,
        rmon1dayHCRxUnknownTPID                           Counter64,
        rmon1dayHCRxUnknownTPIDStatusInfo                 INTEGER,
        rmon1dayHCRxUnknownVID                            Counter64,
        rmon1dayHCRxUnknownVIDStatusInfo                  INTEGER,
        rmon1dayHCRxMAClimit                              Counter64,
        rmon1dayHCRxMAClimitStatusInfo                    INTEGER,
        rmon1dayHCRxFilterDiscard                         Counter64,
        rmon1dayHCRxFilterDiscardStatusInfo               INTEGER,
        rmon1dayHCRxQoSDiscard                            Counter64,
        rmon1dayHCRxQoSDiscardStatusInfo                  INTEGER,
        rmon1dayHCTxQueue0Discard                         Counter64,
        rmon1dayHCTxQueue0DiscardStatusInfo               INTEGER,
        rmon1dayHCTxQueue1Discard                         Counter64,
        rmon1dayHCTxQueue1DiscardStatusInfo               INTEGER,
        rmon1dayHCTxQueue2Discard                         Counter64,
        rmon1dayHCTxQueue2DiscardStatusInfo               INTEGER,
        rmon1dayHCTxQueue3Discard                         Counter64,
        rmon1dayHCTxQueue3DiscardStatusInfo               INTEGER,
        rmon1dayHCTxQueue4Discard                         Counter64,
        rmon1dayHCTxQueue4DiscardStatusInfo               INTEGER,
        rmon1dayHCTxQueue5Discard                         Counter64,
        rmon1dayHCTxQueue5DiscardStatusInfo               INTEGER,
        rmon1dayHCTxQueue6Discard                         Counter64,
        rmon1dayHCTxQueue6DiscardStatusInfo               INTEGER,
        rmon1dayHCTxQueue7Discard                         Counter64,
        rmon1dayHCTxQueue7DiscardStatusInfo               INTEGER,
        rmon1dayTxEthStatsOversizePkts                    Counter32,
        rmon1dayTxEthStatsOversizePktsStatusInfo          INTEGER
    }

    rmon1dayIfIndex OBJECT-TYPE
        SYNTAX       InterfaceIndex
        MAX-ACCESS   not-accessible
        STATUS       current
        DESCRIPTION  "Index of this table."
        ::= { rmon1dayPortEntry 1 }

    rmon1dayNEAddress OBJECT-TYPE
        SYNTAX       IpAddress
        MAX-ACCESS   not-accessible
        STATUS       current
        DESCRIPTION  "reserved."
        ::= { rmon1dayPortEntry 2 }

    rmon1dayHCRxEthStatsOctets OBJECT-TYPE
        SYNTAX       Counter64
        MAX-ACCESS   read-only
        STATUS       current
        DESCRIPTION  "RMON 1day RX Octs"
        ::= { rmon1dayPortEntry 3 }

    rmon1dayHCRxEthStatsOctetsStatusInfo OBJECT-TYPE
        SYNTAX       INTEGER {
                         invalid(0),
                         valid-no-maintenance(1),
                         valid-maintenance(2),
                         invalid-no-maintenance(3),
                         invalid-maintenance(4)
                     }
        MAX-ACCESS   read-only
        STATUS       current
        DESCRIPTION
            "RMON 1day RX Octs Status. 'invalid' means the corresponding
            monitoring value is not reliable because of the alarm or other
            reasons. 'maintenance' means that some maintenance functions are
            executed on the current interval."
        ::= { rmon1dayPortEntry 4 }

    rmon1dayHCTxEthStatsOctets OBJECT-TYPE
        SYNTAX       Counter64
        MAX-ACCESS   read-only
        STATUS       current
        DESCRIPTION  "RMON 1day TX Octs"
        ::= { rmon1dayPortEntry 5 }

    rmon1dayHCTxEthStatsOctetsStatusInfo OBJECT-TYPE
        SYNTAX       INTEGER {
                         invalid(0),
                         valid-no-maintenance(1),
                         valid-maintenance(2),
                         invalid-no-maintenance(3),
                         invalid-maintenance(4)
                     }
        MAX-ACCESS   read-only
        STATUS       current
        DESCRIPTION
            "RMON 1day TX Octs Status. 'invalid' means the corresponding
            monitoring value is not reliable because of the alarm or other
            reasons. 'maintenance' means that some maintenance functions are
            executed on the current interval."
        ::= { rmon1dayPortEntry 6 }

    rmon1dayRxEthStatsPkts OBJECT-TYPE
        SYNTAX       Counter32
        MAX-ACCESS   read-only
        STATUS       current
        DESCRIPTION  "RMON 1day RX Pkts"
        ::= { rmon1dayPortEntry 7 }

    rmon1dayRxEthStatsPktsStatusInfo OBJECT-TYPE
        SYNTAX       INTEGER {
                         invalid(0),
                         valid-no-maintenance(1),
                         valid-maintenance(2),
                         invalid-no-maintenance(3),
                         invalid-maintenance(4)
                     }
        MAX-ACCESS   read-only
        STATUS       current
        DESCRIPTION
            "RMON 1day RX Pkts Status. 'invalid' means the corresponding
            monitoring value is not reliable because of the alarm or other
            reasons. 'maintenance' means that some maintenance functions are
            executed on the current interval."
        ::= { rmon1dayPortEntry 8 }

    rmon1dayTxEthStatsPkts OBJECT-TYPE
        SYNTAX       Counter32
        MAX-ACCESS   read-only
        STATUS       current
        DESCRIPTION  "RMON 1day TX Pkts"
        ::= { rmon1dayPortEntry 9 }

    rmon1dayTxEthStatsPktsStatusInfo OBJECT-TYPE
        SYNTAX       INTEGER {
                         invalid(0),
                         valid-no-maintenance(1),
                         valid-maintenance(2),
                         invalid-no-maintenance(3),
                         invalid-maintenance(4)
                     }
        MAX-ACCESS   read-only
        STATUS       current
        DESCRIPTION
            "RMON 1day TX Pkts Status. 'invalid' means the corresponding
            monitoring value is not reliable because of the alarm or other
            reasons. 'maintenance' means that some maintenance functions are
            executed on the current interval."
        ::= { rmon1dayPortEntry 10 }

    rmon1dayRxEthStatsDropEvents OBJECT-TYPE
        SYNTAX       Counter32
        MAX-ACCESS   read-only
        STATUS       current
        DESCRIPTION  "RMON 1day RX Drop Events"
        ::= { rmon1dayPortEntry 11 }

    rmon1dayRxEthStatsDropEventsStatusInfo OBJECT-TYPE
        SYNTAX       INTEGER {
                         invalid(0),
                         valid-no-maintenance(1),
                         valid-maintenance(2),
                         invalid-no-maintenance(3),
                         invalid-maintenance(4)
                     }
        MAX-ACCESS   read-only
        STATUS       current
        DESCRIPTION
            "RMON 1day RX Drop Events Status. 'invalid' means the
            corresponding monitoring value is not reliable because of the
            alarm or other reasons. 'maintenance' means that some maintenance
            functions are executed on the current interval."
        ::= { rmon1dayPortEntry 12 }

    rmon1dayRxEthStatsUndersizePkts OBJECT-TYPE
        SYNTAX       Counter32
        MAX-ACCESS   read-only
        STATUS       current
        DESCRIPTION  "RMON 1day RX Undersize Pkts"
        ::= { rmon1dayPortEntry 13 }

    rmon1dayRxEthStatsUndersizePktsStatusInfo OBJECT-TYPE
        SYNTAX       INTEGER {
                         invalid(0),
                         valid-no-maintenance(1),
                         valid-maintenance(2),
                         invalid-no-maintenance(3),
                         invalid-maintenance(4)
                     }
        MAX-ACCESS   read-only
        STATUS       current
        DESCRIPTION
            "RMON 1day RX Undersize Pkts Status. 'invalid' means the
            corresponding monitoring value is not reliable because of the
            alarm or other reasons. 'maintenance' means that some maintenance
            functions are executed on the current interval."
        ::= { rmon1dayPortEntry 14 }

    rmon1dayRxEthStatsFragments OBJECT-TYPE
        SYNTAX       Counter32
        MAX-ACCESS   read-only
        STATUS       current
        DESCRIPTION  "RMON 1day RX Fragments"
        ::= { rmon1dayPortEntry 15 }

    rmon1dayRxEthStatsFragmentsStatusInfo OBJECT-TYPE
        SYNTAX       INTEGER {
                         invalid(0),
                         valid-no-maintenance(1),
                         valid-maintenance(2),
                         invalid-no-maintenance(3),
                         invalid-maintenance(4)
                     }
        MAX-ACCESS   read-only
        STATUS       current
        DESCRIPTION
            "RMON 1day RX Fragments Status. 'invalid' means the corresponding
            monitoring value is not reliable because of the alarm or other
            reasons. 'maintenance' means that some maintenance functions are
            executed on the current interval."
        ::= { rmon1dayPortEntry 16 }

    rmon1dayRxEthStatsPkts64Octets OBJECT-TYPE
        SYNTAX       Counter32
        MAX-ACCESS   read-only
        STATUS       current
        DESCRIPTION  "RMON 1day RX 64 Octs"
        ::= { rmon1dayPortEntry 17 }

    rmon1dayRxEthStatsPkts64OctetsStatusInfo OBJECT-TYPE
        SYNTAX       INTEGER {
                         invalid(0),
                         valid-no-maintenance(1),
                         valid-maintenance(2),
                         invalid-no-maintenance(3),
                         invalid-maintenance(4)
                     }
        MAX-ACCESS   read-only
        STATUS       current
        DESCRIPTION
            "RMON 1day RX 64 Octs Status. 'invalid' means the corresponding
            monitoring value is not reliable because of the alarm or other
            reasons. 'maintenance' means that some maintenance functions are
            executed on the current interval."
        ::= { rmon1dayPortEntry 18 }

    rmon1dayTxEthStatsPkts64Octets OBJECT-TYPE
        SYNTAX       Counter32
        MAX-ACCESS   read-only
        STATUS       current
        DESCRIPTION  "RMON 1day TX 64 Octs"
        ::= { rmon1dayPortEntry 19 }

    rmon1dayTxEthStatsPkts64OctetsStatusInfo OBJECT-TYPE
        SYNTAX       INTEGER {
                         invalid(0),
                         valid-no-maintenance(1),
                         valid-maintenance(2),
                         invalid-no-maintenance(3),
                         invalid-maintenance(4)
                     }
        MAX-ACCESS   read-only
        STATUS       current
        DESCRIPTION
            "RMON 1day TX 64 Octs Status. 'invalid' means the corresponding
            monitoring value is not reliable because of the alarm or other
            reasons. 'maintenance' means that some maintenance functions are
            executed on the current interval."
        ::= { rmon1dayPortEntry 20 }

    rmon1dayRxEthStatsPkts65to127Octets OBJECT-TYPE
        SYNTAX       Counter32
        MAX-ACCESS   read-only
        STATUS       current
        DESCRIPTION  "RMON 1day RX 65 to 127 Octs"
        ::= { rmon1dayPortEntry 21 }

    rmon1dayRxEthStatsPkts65to127OctetsStatusInfo OBJECT-TYPE
        SYNTAX       INTEGER {
                         invalid(0),
                         valid-no-maintenance(1),
                         valid-maintenance(2),
                         invalid-no-maintenance(3),
                         invalid-maintenance(4)
                     }
        MAX-ACCESS   read-only
        STATUS       current
        DESCRIPTION
            "RMON 1day RX 65 to 127 Octs Status. 'invalid' means the
            corresponding monitoring value is not reliable because of the
            alarm or other reasons. 'maintenance' means that some maintenance
            functions are executed on the current interval."
        ::= { rmon1dayPortEntry 22 }

    rmon1dayTxEthStatsPkts65to127Octets OBJECT-TYPE
        SYNTAX       Counter32
        MAX-ACCESS   read-only
        STATUS       current
        DESCRIPTION  "RMON 1day TX 65 to 127 Octs"
        ::= { rmon1dayPortEntry 23 }

    rmon1dayTxEthStatsPkts65to127OctetsStatusInfo OBJECT-TYPE
        SYNTAX       INTEGER {
                         invalid(0),
                         valid-no-maintenance(1),
                         valid-maintenance(2),
                         invalid-no-maintenance(3),
                         invalid-maintenance(4)
                     }
        MAX-ACCESS   read-only
        STATUS       current
        DESCRIPTION
            "RMON 1day TX 65 to 127 Octs Status. 'invalid' means the
            corresponding monitoring value is not reliable because of the
            alarm or other reasons. 'maintenance' means that some maintenance
            functions are executed on the current interval."
        ::= { rmon1dayPortEntry 24 }

    rmon1dayRxEthStatsPkts128to255Octets OBJECT-TYPE
        SYNTAX       Counter32
        MAX-ACCESS   read-only
        STATUS       current
        DESCRIPTION  "RMON 1day RX 128 to 255 Octs."
        ::= { rmon1dayPortEntry 25 }

    rmon1dayRxEthStatsPkts128to255OctetsStatusInfo OBJECT-TYPE
        SYNTAX       INTEGER {
                         invalid(0),
                         valid-no-maintenance(1),
                         valid-maintenance(2),
                         invalid-no-maintenance(3),
                         invalid-maintenance(4)
                     }
        MAX-ACCESS   read-only
        STATUS       current
        DESCRIPTION
            "RMON 1day RX 128 to 255 Octs Status. 'invalid' means the
            corresponding monitoring value is not reliable because of the
            alarm or other reasons. 'maintenance' means that some maintenance
            functions are executed on the current interval."
        ::= { rmon1dayPortEntry 26 }

    rmon1dayTxEthStatsPkts128to255Octets OBJECT-TYPE
        SYNTAX       Counter32
        MAX-ACCESS   read-only
        STATUS       current
        DESCRIPTION  "RMON 1day TX 128 to 255 Octs"
        ::= { rmon1dayPortEntry 27 }

    rmon1dayTxEthStatsPkts128to255OctetsStatusInfo OBJECT-TYPE
        SYNTAX       INTEGER {
                         invalid(0),
                         valid-no-maintenance(1),
                         valid-maintenance(2),
                         invalid-no-maintenance(3),
                         invalid-maintenance(4)
                     }
        MAX-ACCESS   read-only
        STATUS       current
        DESCRIPTION
            "RMON 1day TX 128 to 255 Octs Status. 'invalid' means the
            corresponding monitoring value is not reliable because of the
            alarm or other reasons. 'maintenance' means that some maintenance
            functions are executed on the current interval."
        ::= { rmon1dayPortEntry 28 }

    rmon1dayRxEthStatsPkts256to511Octets OBJECT-TYPE
        SYNTAX       Counter32
        MAX-ACCESS   read-only
        STATUS       current
        DESCRIPTION  "RMON 1day RX 256 to 511 Octs."
        ::= { rmon1dayPortEntry 29 }

    rmon1dayRxEthStatsPkts256to511OctetsStatusInfo OBJECT-TYPE
        SYNTAX       INTEGER {
                         invalid(0),
                         valid-no-maintenance(1),
                         valid-maintenance(2),
                         invalid-no-maintenance(3),
                         invalid-maintenance(4)
                     }
        MAX-ACCESS   read-only
        STATUS       current
        DESCRIPTION
            "RMON 1day RX 256 to 511 Octs Status. 'invalid' means the
            corresponding monitoring value is not reliable because of the
            alarm or other reasons. 'maintenance' means that some maintenance
            functions are executed on the current interval."
        ::= { rmon1dayPortEntry 30 }

    rmon1dayTxEthStatsPkts256to511Octets OBJECT-TYPE
        SYNTAX       Counter32
        MAX-ACCESS   read-only
        STATUS       current
        DESCRIPTION  "RMON 1day TX 256 to 511 Octs."
        ::= { rmon1dayPortEntry 31 }

    rmon1dayTxEthStatsPkts256to511OctetsStatusInfo OBJECT-TYPE
        SYNTAX       INTEGER {
                         invalid(0),
                         valid-no-maintenance(1),
                         valid-maintenance(2),
                         invalid-no-maintenance(3),
                         invalid-maintenance(4)
                     }
        MAX-ACCESS   read-only
        STATUS       current
        DESCRIPTION
            "RMON 1day TX 256 to 511 Octs Status. 'invalid' means the
            corresponding monitoring value is not reliable because of the
            alarm or other reasons. 'maintenance' means that some maintenance
            functions are executed on the current interval."
        ::= { rmon1dayPortEntry 32 }

    rmon1dayRxEthStatsPkts512to1023Octets OBJECT-TYPE
        SYNTAX       Counter32
        MAX-ACCESS   read-only
        STATUS       current
        DESCRIPTION  "RMON 1day RX 512 to 1023 Octs"
        ::= { rmon1dayPortEntry 33 }

    rmon1dayRxEthStatsPkts512to1023OctetsStatusInfo OBJECT-TYPE
        SYNTAX       INTEGER {
                         invalid(0),
                         valid-no-maintenance(1),
                         valid-maintenance(2),
                         invalid-no-maintenance(3),
                         invalid-maintenance(4)
                     }
        MAX-ACCESS   read-only
        STATUS       current
        DESCRIPTION
            "RMON 1day RX 512 to 1023 Octs Status. 'invalid' means the
            corresponding monitoring value is not reliable because of the
            alarm or other reasons. 'maintenance' means that some maintenance
            functions are executed on the current interval."
        ::= { rmon1dayPortEntry 34 }

    rmon1dayTxEthStatsPkts512to1023Octets OBJECT-TYPE
        SYNTAX       Counter32
        MAX-ACCESS   read-only
        STATUS       current
        DESCRIPTION  "RMON 1day TX 512 to 1023 Octs"
        ::= { rmon1dayPortEntry 35 }

    rmon1dayTxEthStatsPkts512to1023OctetsStatusInfo OBJECT-TYPE
        SYNTAX       INTEGER {
                         invalid(0),
                         valid-no-maintenance(1),
                         valid-maintenance(2),
                         invalid-no-maintenance(3),
                         invalid-maintenance(4)
                     }
        MAX-ACCESS   read-only
        STATUS       current
        DESCRIPTION
            "RMON 1day TX 512 to 1023 Octs Status. 'invalid' means the
            corresponding monitoring value is not reliable because of the
            alarm or other reasons. 'maintenance' means that some maintenance
            functions are executed on the current interval."
        ::= { rmon1dayPortEntry 36 }

    rmon1dayRxEthStatsPkts1024to1518Octets OBJECT-TYPE
        SYNTAX       Counter32
        MAX-ACCESS   read-only
        STATUS       current
        DESCRIPTION  "RMON 1day RX 1024 to 1518 Octs."
        ::= { rmon1dayPortEntry 37 }

    rmon1dayRxEthStatsPkts1024to1518OctetsStatusInfo OBJECT-TYPE
        SYNTAX       INTEGER {
                         invalid(0),
                         valid-no-maintenance(1),
                         valid-maintenance(2),
                         invalid-no-maintenance(3),
                         invalid-maintenance(4)
                     }
        MAX-ACCESS   read-only
        STATUS       current
        DESCRIPTION
            "RMON 1day RX 1024 to 1518 Octs Status. 'invalid' means the
            corresponding monitoring value is not reliable because of the
            alarm or other reasons. 'maintenance' means that some maintenance
            functions are executed on the current interval."
        ::= { rmon1dayPortEntry 38 }

    rmon1dayTxEthStatsPkts1024to1518Octets OBJECT-TYPE
        SYNTAX       Counter32
        MAX-ACCESS   read-only
        STATUS       current
        DESCRIPTION  "RMON 1day TX 1024 to 1518 Octs."
        ::= { rmon1dayPortEntry 39 }

    rmon1dayTxEthStatsPkts1024to1518OctetsStatusInfo OBJECT-TYPE
        SYNTAX       INTEGER {
                         invalid(0),
                         valid-no-maintenance(1),
                         valid-maintenance(2),
                         invalid-no-maintenance(3),
                         invalid-maintenance(4)
                     }
        MAX-ACCESS   read-only
        STATUS       current
        DESCRIPTION
            "RMON 1day TX 1024 to 1518 Octs Status. 'invalid' means the
            corresponding monitoring value is not reliable because of the
            alarm or other reasons. 'maintenance' means that some maintenance
            functions are executed on the current interval."
        ::= { rmon1dayPortEntry 40 }

    rmon1dayRxEthStatsCRCAlignErrors OBJECT-TYPE
        SYNTAX       Counter32
        MAX-ACCESS   read-only
        STATUS       current
        DESCRIPTION  "RMON 1day RX CRC Alignment Errors"
        ::= { rmon1dayPortEntry 41 }

    rmon1dayRxEthStatsCRCAlignErrorsStatusInfo OBJECT-TYPE
        SYNTAX       INTEGER {
                         invalid(0),
                         valid-no-maintenance(1),
                         valid-maintenance(2),
                         invalid-no-maintenance(3),
                         invalid-maintenance(4)
                     }
        MAX-ACCESS   read-only
        STATUS       current
        DESCRIPTION
            "RMON 1day RX CRC Alignment Errors Status. 'invalid' means the
            corresponding monitoring value is not reliable because of the
            alarm or other reasons. 'maintenance' means that some maintenance
            functions are executed on the current interval."
        ::= { rmon1dayPortEntry 42 }

    rmon1dayRxEthStatsOversizePkts OBJECT-TYPE
        SYNTAX       Counter32
        MAX-ACCESS   read-only
        STATUS       current
        DESCRIPTION  "RMON 1day RX Oversize Pkts"
        ::= { rmon1dayPortEntry 43 }

    rmon1dayRxEthStatsOversizePktsStatusInfo OBJECT-TYPE
        SYNTAX       INTEGER {
                         invalid(0),
                         valid-no-maintenance(1),
                         valid-maintenance(2),
                         invalid-no-maintenance(3),
                         invalid-maintenance(4)
                     }
        MAX-ACCESS   read-only
        STATUS       current
        DESCRIPTION
            "RMON 1day RX Oversize Pkts Status. 'invalid' means the
            corresponding monitoring value is not reliable because of the
            alarm or other reasons. 'maintenance' means that some maintenance
            functions are executed on the current interval."
        ::= { rmon1dayPortEntry 44 }

    rmon1dayRxEthStatsJabbers OBJECT-TYPE
        SYNTAX       Counter32
        MAX-ACCESS   read-only
        STATUS       current
        DESCRIPTION  "RMON 1day RX Jabbers"
        ::= { rmon1dayPortEntry 45 }

    rmon1dayRxEthStatsJabbersStatusInfo OBJECT-TYPE
        SYNTAX       INTEGER {
                         invalid(0),
                         valid-no-maintenance(1),
                         valid-maintenance(2),
                         invalid-no-maintenance(3),
                         invalid-maintenance(4)
                     }
        MAX-ACCESS   read-only
        STATUS       current
        DESCRIPTION
            "RMON 1day RX Jabbers Status. 'invalid' means the corresponding
            monitoring value is not reliable because of the alarm or other
            reasons. 'maintenance' means that some maintenance functions are
            executed on the current interval."
        ::= { rmon1dayPortEntry 46 }

    rmon1dayRxEthStatsMulticastPkts OBJECT-TYPE
        SYNTAX       Counter32
        MAX-ACCESS   read-only
        STATUS       current
        DESCRIPTION  "RMON 1day RX Multicast Pkts"
        ::= { rmon1dayPortEntry 47 }

    rmon1dayRxEthStatsMulticastPktsStatusInfo OBJECT-TYPE
        SYNTAX       INTEGER {
                         invalid(0),
                         valid-no-maintenance(1),
                         valid-maintenance(2),
                         invalid-no-maintenance(3),
                         invalid-maintenance(4)
                     }
        MAX-ACCESS   read-only
        STATUS       current
        DESCRIPTION
            "RMON 1day RX Multicast Pkts Status. 'invalid' means the
            corresponding monitoring value is not reliable because of the
            alarm or other reasons. 'maintenance' means that some maintenance
            functions are executed on the current interval."
        ::= { rmon1dayPortEntry 48 }

    rmon1dayTxEthStatsMulticastPkts OBJECT-TYPE
        SYNTAX       Counter32
        MAX-ACCESS   read-only
        STATUS       current
        DESCRIPTION  "RMON 1day TX Multicast Pkts."
        ::= { rmon1dayPortEntry 49 }

    rmon1dayTxEthStatsMulticastPktsStatusInfo OBJECT-TYPE
        SYNTAX       INTEGER {
                         invalid(0),
                         valid-no-maintenance(1),
                         valid-maintenance(2),
                         invalid-no-maintenance(3),
                         invalid-maintenance(4)
                     }
        MAX-ACCESS   read-only
        STATUS       current
        DESCRIPTION
            "RMON 1day TX Multicast Pkts Status. 'invalid' means the
            corresponding monitoring value is not reliable because of the
            alarm or other reasons. 'maintenance' means that some maintenance
            functions are executed on the current interval."
        ::= { rmon1dayPortEntry 50 }

    rmon1dayRxEthStatsBroadcastPkts OBJECT-TYPE
        SYNTAX       Counter32
        MAX-ACCESS   read-only
        STATUS       current
        DESCRIPTION  "RMON 1day RX Broadcast Pkts."
        ::= { rmon1dayPortEntry 51 }

    rmon1dayRxEthStatsBroadcastPktsStatusInfo OBJECT-TYPE
        SYNTAX       INTEGER {
                         invalid(0),
                         valid-no-maintenance(1),
                         valid-maintenance(2),
                         invalid-no-maintenance(3),
                         invalid-maintenance(4)
                     }
        MAX-ACCESS   read-only
        STATUS       current
        DESCRIPTION
            "RMON 1day RX Broadcast Pkts Status. 'invalid' means the
            corresponding monitoring value is not reliable because of the
            alarm or other reasons. 'maintenance' means that some maintenance
            functions are executed on the current interval."
        ::= { rmon1dayPortEntry 52 }

    rmon1dayTxEthStatsBroadcastPkts OBJECT-TYPE
        SYNTAX       Counter32
        MAX-ACCESS   read-only
        STATUS       current
        DESCRIPTION  "RMON 1day TX Broadcast Pkts."
        ::= { rmon1dayPortEntry 53 }

    rmon1dayTxEthStatsBroadcastPktsStatusInfo OBJECT-TYPE
        SYNTAX       INTEGER {
                         invalid(0),
                         valid-no-maintenance(1),
                         valid-maintenance(2),
                         invalid-no-maintenance(3),
                         invalid-maintenance(4)
                     }
        MAX-ACCESS   read-only
        STATUS       current
        DESCRIPTION
            "RMON 1day TX Broadcast Pkts Status. 'invalid' means the
            corresponding monitoring value is not reliable because of the
            alarm or other reasons. 'maintenance' means that some maintenance
            functions are executed on the current interval."
        ::= { rmon1dayPortEntry 54 }

    rmon1dayTxEthStatsCollisions OBJECT-TYPE
        SYNTAX       Counter32
        MAX-ACCESS   read-only
        STATUS       current
        DESCRIPTION  "RMON 1day TX Collisions."
        ::= { rmon1dayPortEntry 55 }

    rmon1dayTxEthStatsCollisionsStatusInfo OBJECT-TYPE
        SYNTAX       INTEGER {
                         invalid(0),
                         valid-no-maintenance(1),
                         valid-maintenance(2),
                         invalid-no-maintenance(3),
                         invalid-maintenance(4)
                     }
        MAX-ACCESS   read-only
        STATUS       current
        DESCRIPTION
            "RMON 1day TX Collistions Status. 'invalid' means the
            corresponding monitoring value is not reliable because of the
            alarm or other reasons. 'maintenance' means that some maintenance
            functions are executed on the current interval."
        ::= { rmon1dayPortEntry 56 }

    rmon1dayHCRxUnknownTPID OBJECT-TYPE
        SYNTAX       Counter64
        MAX-ACCESS   read-only
        STATUS       current
        DESCRIPTION  "RMON 1day RX Unknown TPID."
        ::= { rmon1dayPortEntry 57 }

    rmon1dayHCRxUnknownTPIDStatusInfo OBJECT-TYPE
        SYNTAX       INTEGER {
                         invalid(0),
                         valid-no-maintenance(1),
                         valid-maintenance(2),
                         invalid-no-maintenance(3),
                         invalid-maintenance(4)
                     }
        MAX-ACCESS   read-only
        STATUS       current
        DESCRIPTION
            "RMON 1day RX Unknown TPID Status. 'invalid' means the
            corresponding monitoring value is not reliable because of the
            alarm or other reasons. 'maintenance' means that some maintenance
            functions are executed on the current interval."
        ::= { rmon1dayPortEntry 58 }

    rmon1dayHCRxUnknownVID OBJECT-TYPE
        SYNTAX       Counter64
        MAX-ACCESS   read-only
        STATUS       current
        DESCRIPTION  "RMON 1day RX Unknown VID."
        ::= { rmon1dayPortEntry 59 }

    rmon1dayHCRxUnknownVIDStatusInfo OBJECT-TYPE
        SYNTAX       INTEGER {
                         invalid(0),
                         valid-no-maintenance(1),
                         valid-maintenance(2),
                         invalid-no-maintenance(3),
                         invalid-maintenance(4)
                     }
        MAX-ACCESS   read-only
        STATUS       current
        DESCRIPTION
            "RMON 1day RX Unknown VID Status. 'invalid' means the
            corresponding monitoring value is not reliable because of the
            alarm or other reasons. 'maintenance' means that some maintenance
            functions are executed on the current interval."
        ::= { rmon1dayPortEntry 60 }

    rmon1dayHCRxMAClimit OBJECT-TYPE
        SYNTAX       Counter64
        MAX-ACCESS   read-only
        STATUS       current
        DESCRIPTION  "RMON 1day RX MAC Limit."
        ::= { rmon1dayPortEntry 61 }

    rmon1dayHCRxMAClimitStatusInfo OBJECT-TYPE
        SYNTAX       INTEGER {
                         invalid(0),
                         valid-no-maintenance(1),
                         valid-maintenance(2),
                         invalid-no-maintenance(3),
                         invalid-maintenance(4)
                     }
        MAX-ACCESS   read-only
        STATUS       current
        DESCRIPTION
            "RMON 1day RX MAC Limit Status. 'invalid' means the corresponding
            monitoring value is not reliable because of the alarm or other
            reasons. 'maintenance' means that some maintenance functions are
            executed on the current interval."
        ::= { rmon1dayPortEntry 62 }

    rmon1dayHCRxFilterDiscard OBJECT-TYPE
        SYNTAX       Counter64
        MAX-ACCESS   read-only
        STATUS       current
        DESCRIPTION  "RMON 1day RX Filter Discard."
        ::= { rmon1dayPortEntry 63 }

    rmon1dayHCRxFilterDiscardStatusInfo OBJECT-TYPE
        SYNTAX       INTEGER {
                         invalid(0),
                         valid-no-maintenance(1),
                         valid-maintenance(2),
                         invalid-no-maintenance(3),
                         invalid-maintenance(4)
                     }
        MAX-ACCESS   read-only
        STATUS       current
        DESCRIPTION
            "RMON 1day RX Filter Discard Status. 'invalid' means the
            corresponding monitoring value is not reliable because of the
            alarm or other reasons. 'maintenance' means that some maintenance
            functions are executed on the current interval."
        ::= { rmon1dayPortEntry 64 }

    rmon1dayHCRxQoSDiscard OBJECT-TYPE
        SYNTAX       Counter64
        MAX-ACCESS   read-only
        STATUS       current
        DESCRIPTION  "RMON 1day RX QoS Discard."
        ::= { rmon1dayPortEntry 65 }

    rmon1dayHCRxQoSDiscardStatusInfo OBJECT-TYPE
        SYNTAX       INTEGER {
                         invalid(0),
                         valid-no-maintenance(1),
                         valid-maintenance(2),
                         invalid-no-maintenance(3),
                         invalid-maintenance(4)
                     }
        MAX-ACCESS   read-only
        STATUS       current
        DESCRIPTION
            "RMON 1day RX QoS Discard Status. 'invalid' means the
            corresponding monitoring value is not reliable because of the
            alarm or other reasons. 'maintenance' means that some maintenance
            functions are executed on the current interval."
        ::= { rmon1dayPortEntry 66 }

    rmon1dayHCTxQueue0Discard OBJECT-TYPE
        SYNTAX       Counter64
        MAX-ACCESS   read-only
        STATUS       current
        DESCRIPTION  "RMON 1day TX Queue0 Discard."
        ::= { rmon1dayPortEntry 67 }

    rmon1dayHCTxQueue0DiscardStatusInfo OBJECT-TYPE
        SYNTAX       INTEGER {
                         invalid(0),
                         valid-no-maintenance(1),
                         valid-maintenance(2),
                         invalid-no-maintenance(3),
                         invalid-maintenance(4)
                     }
        MAX-ACCESS   read-only
        STATUS       current
        DESCRIPTION
            "RMON 1day TX Queue0 Discard Status. 'invalid' means the
            corresponding monitoring value is not reliable because of the
            alarm or other reasons. 'maintenance' means that some maintenance
            functions are executed on the current interval."
        ::= { rmon1dayPortEntry 68 }

    rmon1dayHCTxQueue1Discard OBJECT-TYPE
        SYNTAX       Counter64
        MAX-ACCESS   read-only
        STATUS       current
        DESCRIPTION  "RMON 1day TX Queue1 Discard."
        ::= { rmon1dayPortEntry 69 }

    rmon1dayHCTxQueue1DiscardStatusInfo OBJECT-TYPE
        SYNTAX       INTEGER {
                         invalid(0),
                         valid-no-maintenance(1),
                         valid-maintenance(2),
                         invalid-no-maintenance(3),
                         invalid-maintenance(4)
                     }
        MAX-ACCESS   read-only
        STATUS       current
        DESCRIPTION
            "RMON 1day TX Queue1 Discard Status. 'invalid' means the
            corresponding monitoring value is not reliable because of the
            alarm or other reasons. 'maintenance' means that some maintenance
            functions are executed on the current interval."
        ::= { rmon1dayPortEntry 70 }

    rmon1dayHCTxQueue2Discard OBJECT-TYPE
        SYNTAX       Counter64
        MAX-ACCESS   read-only
        STATUS       current
        DESCRIPTION  "RMON 1day TX Queue2 Discard."
        ::= { rmon1dayPortEntry 71 }

    rmon1dayHCTxQueue2DiscardStatusInfo OBJECT-TYPE
        SYNTAX       INTEGER {
                         invalid(0),
                         valid-no-maintenance(1),
                         valid-maintenance(2),
                         invalid-no-maintenance(3),
                         invalid-maintenance(4)
                     }
        MAX-ACCESS   read-only
        STATUS       current
        DESCRIPTION
            "RMON 1day TX Queue2 Discard Status. 'invalid' means the
            corresponding monitoring value is not reliable because of the
            alarm or other reasons. 'maintenance' means that some maintenance
            functions are executed on the current interval."
        ::= { rmon1dayPortEntry 72 }

    rmon1dayHCTxQueue3Discard OBJECT-TYPE
        SYNTAX       Counter64
        MAX-ACCESS   read-only
        STATUS       current
        DESCRIPTION  "RMON 1day TX Queue3 Discard."
        ::= { rmon1dayPortEntry 73 }

    rmon1dayHCTxQueue3DiscardStatusInfo OBJECT-TYPE
        SYNTAX       INTEGER {
                         invalid(0),
                         valid-no-maintenance(1),
                         valid-maintenance(2),
                         invalid-no-maintenance(3),
                         invalid-maintenance(4)
                     }
        MAX-ACCESS   read-only
        STATUS       current
        DESCRIPTION
            "RMON 1day TX Queue3 Discard Status. 'invalid' means the
            corresponding monitoring value is not reliable because of the
            alarm or other reasons. 'maintenance' means that some maintenance
            functions are executed on the current interval."
        ::= { rmon1dayPortEntry 74 }

    rmon1dayHCTxQueue4Discard OBJECT-TYPE
        SYNTAX       Counter64
        MAX-ACCESS   read-only
        STATUS       current
        DESCRIPTION
            "RMON 1day TX Queue4 Discard. If the equipment is running on 4
            class QoS mode. The value of this object is always 0."
        ::= { rmon1dayPortEntry 75 }

    rmon1dayHCTxQueue4DiscardStatusInfo OBJECT-TYPE
        SYNTAX       INTEGER {
                         invalid(0),
                         valid-no-maintenance(1),
                         valid-maintenance(2),
                         invalid-no-maintenance(3),
                         invalid-maintenance(4)
                     }
        MAX-ACCESS   read-only
        STATUS       current
        DESCRIPTION
            "RMON 1day TX Queue4 Discard Status. 'invalid' means the
            corresponding monitoring value is not reliable because of the
            alarm or other reasons. 'maintenance' means that some maintenance
            functions are executed on the current interval."
        ::= { rmon1dayPortEntry 76 }

    rmon1dayHCTxQueue5Discard OBJECT-TYPE
        SYNTAX       Counter64
        MAX-ACCESS   read-only
        STATUS       current
        DESCRIPTION
            "RMON 1day TX Queue5 Discard. If the equipment is running on 4
            class QoS mode. The value of this object is always 0."
        ::= { rmon1dayPortEntry 77 }

    rmon1dayHCTxQueue5DiscardStatusInfo OBJECT-TYPE
        SYNTAX       INTEGER {
                         invalid(0),
                         valid-no-maintenance(1),
                         valid-maintenance(2),
                         invalid-no-maintenance(3),
                         invalid-maintenance(4)
                     }
        MAX-ACCESS   read-only
        STATUS       current
        DESCRIPTION
            "RMON 1day TX Queue5 Discard Status. 'invalid' means the
            corresponding monitoring value is not reliable because of the
            alarm or other reasons. 'maintenance' means that some maintenance
            functions are executed on the current interval."
        ::= { rmon1dayPortEntry 78 }

    rmon1dayHCTxQueue6Discard OBJECT-TYPE
        SYNTAX       Counter64
        MAX-ACCESS   read-only
        STATUS       current
        DESCRIPTION
            "RMON 1day TX Queue6 Discard. If the equipment is running on 4
            class QoS mode. The value of this object is always 0."
        ::= { rmon1dayPortEntry 79 }

    rmon1dayHCTxQueue6DiscardStatusInfo OBJECT-TYPE
        SYNTAX       INTEGER {
                         invalid(0),
                         valid-no-maintenance(1),
                         valid-maintenance(2),
                         invalid-no-maintenance(3),
                         invalid-maintenance(4)
                     }
        MAX-ACCESS   read-only
        STATUS       current
        DESCRIPTION
            "RMON 1day TX Queue6 Discard Status. 'invalid' means the
            corresponding monitoring value is not reliable because of the
            alarm or other reasons. 'maintenance' means that some maintenance
            functions are executed on the current interval."
        ::= { rmon1dayPortEntry 80 }

    rmon1dayHCTxQueue7Discard OBJECT-TYPE
        SYNTAX       Counter64
        MAX-ACCESS   read-only
        STATUS       current
        DESCRIPTION
            "RMON 1day TX Queue7 Discard. If the equipment is running on 4
            class QoS mode. The value of this object is always 0."
        ::= { rmon1dayPortEntry 81 }

    rmon1dayHCTxQueue7DiscardStatusInfo OBJECT-TYPE
        SYNTAX       INTEGER {
                         invalid(0),
                         valid-no-maintenance(1),
                         valid-maintenance(2),
                         invalid-no-maintenance(3),
                         invalid-maintenance(4)
                     }
        MAX-ACCESS   read-only
        STATUS       current
        DESCRIPTION
            "RMON 1day TX Queue7 Discard Status. 'invalid' means the
            corresponding monitoring value is not reliable because of the
            alarm or other reasons. 'maintenance' means that some maintenance
            functions are executed on the current interval."
        ::= { rmon1dayPortEntry 82 }

    rmon1dayTxEthStatsOversizePkts OBJECT-TYPE
        SYNTAX       Counter32
        MAX-ACCESS   read-only
        STATUS       current
        DESCRIPTION  "RMON 1day TX Oversize Pkts."
        ::= { rmon1dayPortEntry 83 }

    rmon1dayTxEthStatsOversizePktsStatusInfo OBJECT-TYPE
        SYNTAX       INTEGER {
                         invalid(0),
                         valid-no-maintenance(1),
                         valid-maintenance(2),
                         invalid-no-maintenance(3),
                         invalid-maintenance(4)
                     }
        MAX-ACCESS   read-only
        STATUS       current
        DESCRIPTION
            "RMON 1day TX Oversize Pkts Status. 'invalid' means the
            corresponding monitoring value is not reliable because of the
            alarm or other reasons. 'maintenance' means that some maintenance
            functions are executed on the current interval."
        ::= { rmon1dayPortEntry 84 }

    rmon1dayPort2Table OBJECT-TYPE
        SYNTAX       SEQUENCE OF Rmon1dayPort2Entry
        MAX-ACCESS   not-accessible
        STATUS       current
        DESCRIPTION  "RMON 1day Port Monitoring Table."
        ::= { rmon1dayportGroup 2 }

    rmon1dayPort2Entry OBJECT-TYPE
        SYNTAX       Rmon1dayPort2Entry
        MAX-ACCESS   not-accessible
        STATUS       current
        DESCRIPTION  ""
        INDEX        { rmon1dayPort2IfIndex }
        ::= { rmon1dayPort2Table 1 }

    Rmon1dayPort2Entry ::= SEQUENCE {
        rmon1dayPort2IfIndex                             InterfaceIndex,
        rmon1dayPort2NEAddress                           IpAddress,
        rmon1dayHCRxEthStatsOctets2                      Counter64,
        rmon1dayHCRxEthStatsOctets2Status                IpeStatsInfo,
        rmon1dayHCTxEthStatsOctets2                      Counter64,
        rmon1dayHCTxEthStatsOctets2Status                IpeStatsInfo,
        rmon1dayHCRxEthStatsPkts2                        Counter64,
        rmon1dayHCRxEthStatsPkts2Status                  IpeStatsInfo,
        rmon1dayHCTxEthStatsPkts2                        Counter64,
        rmon1dayHCTxEthStatsPkts2Status                  IpeStatsInfo,
        rmon1dayRxEthStatsDropEvents2                    Counter32,
        rmon1dayRxEthStatsDropEvents2Status              IpeStatsInfo,
        rmon1dayRxEthStatsUndersizePkts2                 Counter32,
        rmon1dayRxEthStatsUndersizePkts2Status           IpeStatsInfo,
        rmon1dayRxEthStatsFragments2                     Counter32,
        rmon1dayRxEthStatsFragments2Status               IpeStatsInfo,
        rmon1dayHCRxEthStatsPkts64Octets2                Counter64,
        rmon1dayHCRxEthStatsPkts64Octets2Status          IpeStatsInfo,
        rmon1dayHCTxEthStatsPkts64Octets2                Counter64,
        rmon1dayHCTxEthStatsPkts64Octets2Status          IpeStatsInfo,
        rmon1dayHCRxEthStatsPkts65to127Octets2           Counter64,
        rmon1dayHCRxEthStatsPkts65to127Octets2Status     IpeStatsInfo,
        rmon1dayHCTxEthStatsPkts65to127Octets2           Counter64,
        rmon1dayHCTxEthStatsPkts65to127Octets2Status     IpeStatsInfo,
        rmon1dayHCRxEthStatsPkts128to255Octets2          Counter64,
        rmon1dayHCRxEthStatsPkts128to255Octets2Status    IpeStatsInfo,
        rmon1dayHCTxEthStatsPkts128to255Octets2          Counter64,
        rmon1dayHCTxEthStatsPkts128to255Octets2Status    IpeStatsInfo,
        rmon1dayHCRxEthStatsPkts256to511Octets2          Counter64,
        rmon1dayHCRxEthStatsPkts256to511Octets2Status    IpeStatsInfo,
        rmon1dayHCTxEthStatsPkts256to511Octets2          Counter64,
        rmon1dayHCTxEthStatsPkts256to511Octets2Status    IpeStatsInfo,
        rmon1dayHCRxEthStatsPkts512to1023Octets2         Counter64,
        rmon1dayHCRxEthStatsPkts512to1023Octets2Status   IpeStatsInfo,
        rmon1dayHCTxEthStatsPkts512to1023Octets2         Counter64,
        rmon1dayHCTxEthStatsPkts512to1023Octets2Status   IpeStatsInfo,
        rmon1dayHCRxEthStatsPkts1024to1518Octets2        Counter64,
        rmon1dayHCRxEthStatsPkts1024to1518Octets2Status  IpeStatsInfo,
        rmon1dayHCTxEthStatsPkts1024to1518Octets2        Counter64,
        rmon1dayHCTxEthStatsPkts1024to1518Octets2Status  IpeStatsInfo,
        rmon1dayRxEthStatsCRCAlignErrors2                Counter32,
        rmon1dayRxEthStatsCRCAlignErrors2Status          IpeStatsInfo,
        rmon1dayRxEthStatsOversizePkts2                  Counter32,
        rmon1dayRxEthStatsOversizePkts2Status            IpeStatsInfo,
        rmon1dayRxEthStatsJabbers2                       Counter32,
        rmon1dayRxEthStatsJabbers2Status                 IpeStatsInfo,
        rmon1dayRxEthStatsMulticastPkts2                 Counter32,
        rmon1dayRxEthStatsMulticastPkts2Status           IpeStatsInfo,
        rmon1dayTxEthStatsMulticastPkts2                 Counter32,
        rmon1dayTxEthStatsMulticastPkts2Status           IpeStatsInfo,
        rmon1dayRxEthStatsBroadcastPkts2                 Counter32,
        rmon1dayRxEthStatsBroadcastPkts2Status           IpeStatsInfo,
        rmon1dayTxEthStatsBroadcastPkts2                 Counter32,
        rmon1dayTxEthStatsBroadcastPkts2Status           IpeStatsInfo,
        rmon1dayTxEthStatsCollisions2                    Counter32,
        rmon1dayTxEthStatsCollisions2Status              IpeStatsInfo,
        rmon1dayHCRxUnknownTPID2                         Counter64,
        rmon1dayHCRxUnknownTPID2Status                   IpeStatsInfo,
        rmon1dayHCRxUnknownVID2                          Counter64,
        rmon1dayHCRxUnknownVID2Status                    IpeStatsInfo,
        rmon1dayHCRxMAClimit2                            Counter64,
        rmon1dayHCRxMAClimit2Status                      IpeStatsInfo,
        rmon1dayHCRxFilterDiscard2                       Counter64,
        rmon1dayHCRxFilterDiscard2Status                 IpeStatsInfo,
        rmon1dayHCRxQoSDiscard2                          Counter64,
        rmon1dayHCRxQoSDiscard2Status                    IpeStatsInfo,
        rmon1dayHCTxQueue0Discard2                       Counter64,
        rmon1dayHCTxQueue0Discard2Status                 IpeStatsInfo,
        rmon1dayHCTxQueue1Discard2                       Counter64,
        rmon1dayHCTxQueue1Discard2Status                 IpeStatsInfo,
        rmon1dayHCTxQueue2Discard2                       Counter64,
        rmon1dayHCTxQueue2Discard2Status                 IpeStatsInfo,
        rmon1dayHCTxQueue3Discard2                       Counter64,
        rmon1dayHCTxQueue3Discard2Status                 IpeStatsInfo,
        rmon1dayHCTxQueue4Discard2                       Counter64,
        rmon1dayHCTxQueue4Discard2Status                 IpeStatsInfo,
        rmon1dayHCTxQueue5Discard2                       Counter64,
        rmon1dayHCTxQueue5Discard2Status                 IpeStatsInfo,
        rmon1dayHCTxQueue6Discard2                       Counter64,
        rmon1dayHCTxQueue6Discard2Status                 IpeStatsInfo,
        rmon1dayHCTxQueue7Discard2                       Counter64,
        rmon1dayHCTxQueue7Discard2Status                 IpeStatsInfo,
        rmon1dayTxEthStatsOversizePkts2                  Counter32,
        rmon1dayTxEthStatsOversizePkts2Status            IpeStatsInfo
    }

    rmon1dayPort2IfIndex OBJECT-TYPE
        SYNTAX       InterfaceIndex
        MAX-ACCESS   not-accessible
        STATUS       current
        DESCRIPTION  "Index of this table."
        ::= { rmon1dayPort2Entry 1 }

    rmon1dayPort2NEAddress OBJECT-TYPE
        SYNTAX       IpAddress
        MAX-ACCESS   not-accessible
        STATUS       current
        DESCRIPTION  "reserved."
        ::= { rmon1dayPort2Entry 2 }

    rmon1dayHCRxEthStatsOctets2 OBJECT-TYPE
        SYNTAX       Counter64
        MAX-ACCESS   read-only
        STATUS       current
        DESCRIPTION  "RMON 1day RX Octs"
        ::= { rmon1dayPort2Entry 3 }

    rmon1dayHCRxEthStatsOctets2Status OBJECT-TYPE
        SYNTAX       IpeStatsInfo
        MAX-ACCESS   read-only
        STATUS       current
        DESCRIPTION
            "RMON 1day RX Octs Status. 'invalid' means the corresponding
            monitoring value is not reliable because of the alarm or other
            reasons. 'maintenance' means that some maintenance functions are
            executed on the current interval."
        ::= { rmon1dayPort2Entry 4 }

    rmon1dayHCTxEthStatsOctets2 OBJECT-TYPE
        SYNTAX       Counter64
        MAX-ACCESS   read-only
        STATUS       current
        DESCRIPTION  "RMON 1day TX Octs"
        ::= { rmon1dayPort2Entry 5 }

    rmon1dayHCTxEthStatsOctets2Status OBJECT-TYPE
        SYNTAX       IpeStatsInfo
        MAX-ACCESS   read-only
        STATUS       current
        DESCRIPTION
            "RMON 1day TX Octs Status. 'invalid' means the corresponding
            monitoring value is not reliable because of the alarm or other
            reasons. 'maintenance' means that some maintenance functions are
            executed on the current interval."
        ::= { rmon1dayPort2Entry 6 }

    rmon1dayHCRxEthStatsPkts2 OBJECT-TYPE
        SYNTAX       Counter64
        MAX-ACCESS   read-only
        STATUS       current
        DESCRIPTION  "RMON 1day RX Pkts"
        ::= { rmon1dayPort2Entry 7 }

    rmon1dayHCRxEthStatsPkts2Status OBJECT-TYPE
        SYNTAX       IpeStatsInfo
        MAX-ACCESS   read-only
        STATUS       current
        DESCRIPTION
            "RMON 1day RX Pkts Status. 'invalid' means the corresponding
            monitoring value is not reliable because of the alarm or other
            reasons. 'maintenance' means that some maintenance functions are
            executed on the current interval."
        ::= { rmon1dayPort2Entry 8 }

    rmon1dayHCTxEthStatsPkts2 OBJECT-TYPE
        SYNTAX       Counter64
        MAX-ACCESS   read-only
        STATUS       current
        DESCRIPTION  "RMON 1day TX Pkts"
        ::= { rmon1dayPort2Entry 9 }

    rmon1dayHCTxEthStatsPkts2Status OBJECT-TYPE
        SYNTAX       IpeStatsInfo
        MAX-ACCESS   read-only
        STATUS       current
        DESCRIPTION
            "RMON 1day TX Pkts Status. 'invalid' means the corresponding
            monitoring value is not reliable because of the alarm or other
            reasons. 'maintenance' means that some maintenance functions are
            executed on the current interval."
        ::= { rmon1dayPort2Entry 10 }

    rmon1dayRxEthStatsDropEvents2 OBJECT-TYPE
        SYNTAX       Counter32
        MAX-ACCESS   read-only
        STATUS       current
        DESCRIPTION  "RMON 1day RX Drop Events"
        ::= { rmon1dayPort2Entry 11 }

    rmon1dayRxEthStatsDropEvents2Status OBJECT-TYPE
        SYNTAX       IpeStatsInfo
        MAX-ACCESS   read-only
        STATUS       current
        DESCRIPTION
            "RMON 1day RX Drop Events Status. 'invalid' means the
            corresponding monitoring value is not reliable because of the
            alarm or other reasons. 'maintenance' means that some maintenance
            functions are executed on the current interval."
        ::= { rmon1dayPort2Entry 12 }

    rmon1dayRxEthStatsUndersizePkts2 OBJECT-TYPE
        SYNTAX       Counter32
        MAX-ACCESS   read-only
        STATUS       current
        DESCRIPTION  "RMON 1day RX Undersize Pkts"
        ::= { rmon1dayPort2Entry 13 }

    rmon1dayRxEthStatsUndersizePkts2Status OBJECT-TYPE
        SYNTAX       IpeStatsInfo
        MAX-ACCESS   read-only
        STATUS       current
        DESCRIPTION
            "RMON 1day RX Undersize Pkts Status. 'invalid' means the
            corresponding monitoring value is not reliable because of the
            alarm or other reasons. 'maintenance' means that some maintenance
            functions are executed on the current interval."
        ::= { rmon1dayPort2Entry 14 }

    rmon1dayRxEthStatsFragments2 OBJECT-TYPE
        SYNTAX       Counter32
        MAX-ACCESS   read-only
        STATUS       current
        DESCRIPTION  "RMON 1day RX Fragments"
        ::= { rmon1dayPort2Entry 15 }

    rmon1dayRxEthStatsFragments2Status OBJECT-TYPE
        SYNTAX       IpeStatsInfo
        MAX-ACCESS   read-only
        STATUS       current
        DESCRIPTION
            "RMON 1day RX Fragments Status. 'invalid' means the corresponding
            monitoring value is not reliable because of the alarm or other
            reasons. 'maintenance' means that some maintenance functions are
            executed on the current interval."
        ::= { rmon1dayPort2Entry 16 }

    rmon1dayHCRxEthStatsPkts64Octets2 OBJECT-TYPE
        SYNTAX       Counter64
        MAX-ACCESS   read-only
        STATUS       current
        DESCRIPTION  "RMON 1day RX 64 Octs"
        ::= { rmon1dayPort2Entry 17 }

    rmon1dayHCRxEthStatsPkts64Octets2Status OBJECT-TYPE
        SYNTAX       IpeStatsInfo
        MAX-ACCESS   read-only
        STATUS       current
        DESCRIPTION
            "RMON 1day RX 64 Octs Status. 'invalid' means the corresponding
            monitoring value is not reliable because of the alarm or other
            reasons. 'maintenance' means that some maintenance functions are
            executed on the current interval."
        ::= { rmon1dayPort2Entry 18 }

    rmon1dayHCTxEthStatsPkts64Octets2 OBJECT-TYPE
        SYNTAX       Counter64
        MAX-ACCESS   read-only
        STATUS       current
        DESCRIPTION  "RMON 1day TX 64 Octs"
        ::= { rmon1dayPort2Entry 19 }

    rmon1dayHCTxEthStatsPkts64Octets2Status OBJECT-TYPE
        SYNTAX       IpeStatsInfo
        MAX-ACCESS   read-only
        STATUS       current
        DESCRIPTION
            "RMON 1day TX 64 Octs Status. 'invalid' means the corresponding
            monitoring value is not reliable because of the alarm or other
            reasons. 'maintenance' means that some maintenance functions are
            executed on the current interval."
        ::= { rmon1dayPort2Entry 20 }

    rmon1dayHCRxEthStatsPkts65to127Octets2 OBJECT-TYPE
        SYNTAX       Counter64
        MAX-ACCESS   read-only
        STATUS       current
        DESCRIPTION  "RMON 1day RX 65 to 127 Octs"
        ::= { rmon1dayPort2Entry 21 }

    rmon1dayHCRxEthStatsPkts65to127Octets2Status OBJECT-TYPE
        SYNTAX       IpeStatsInfo
        MAX-ACCESS   read-only
        STATUS       current
        DESCRIPTION
            "RMON 1day RX 65 to 127 Octs Status. 'invalid' means the
            corresponding monitoring value is not reliable because of the
            alarm or other reasons. 'maintenance' means that some maintenance
            functions are executed on the current interval."
        ::= { rmon1dayPort2Entry 22 }

    rmon1dayHCTxEthStatsPkts65to127Octets2 OBJECT-TYPE
        SYNTAX       Counter64
        MAX-ACCESS   read-only
        STATUS       current
        DESCRIPTION  "RMON 1day TX 65 to 127 Octs"
        ::= { rmon1dayPort2Entry 23 }

    rmon1dayHCTxEthStatsPkts65to127Octets2Status OBJECT-TYPE
        SYNTAX       IpeStatsInfo
        MAX-ACCESS   read-only
        STATUS       current
        DESCRIPTION
            "RMON 1day TX 65 to 127 Octs Status. 'invalid' means the
            corresponding monitoring value is not reliable because of the
            alarm or other reasons. 'maintenance' means that some maintenance
            functions are executed on the current interval."
        ::= { rmon1dayPort2Entry 24 }

    rmon1dayHCRxEthStatsPkts128to255Octets2 OBJECT-TYPE
        SYNTAX       Counter64
        MAX-ACCESS   read-only
        STATUS       current
        DESCRIPTION  "RMON 1day RX 128 to 255 Octs."
        ::= { rmon1dayPort2Entry 25 }

    rmon1dayHCRxEthStatsPkts128to255Octets2Status OBJECT-TYPE
        SYNTAX       IpeStatsInfo
        MAX-ACCESS   read-only
        STATUS       current
        DESCRIPTION
            "RMON 1day RX 128 to 255 Octs Status. 'invalid' means the
            corresponding monitoring value is not reliable because of the
            alarm or other reasons. 'maintenance' means that some maintenance
            functions are executed on the current interval."
        ::= { rmon1dayPort2Entry 26 }

    rmon1dayHCTxEthStatsPkts128to255Octets2 OBJECT-TYPE
        SYNTAX       Counter64
        MAX-ACCESS   read-only
        STATUS       current
        DESCRIPTION  "RMON 1day TX 128 to 255 Octs"
        ::= { rmon1dayPort2Entry 27 }

    rmon1dayHCTxEthStatsPkts128to255Octets2Status OBJECT-TYPE
        SYNTAX       IpeStatsInfo
        MAX-ACCESS   read-only
        STATUS       current
        DESCRIPTION
            "RMON 1day TX 128 to 255 Octs Status. 'invalid' means the
            corresponding monitoring value is not reliable because of the
            alarm or other reasons. 'maintenance' means that some maintenance
            functions are executed on the current interval."
        ::= { rmon1dayPort2Entry 28 }

    rmon1dayHCRxEthStatsPkts256to511Octets2 OBJECT-TYPE
        SYNTAX       Counter64
        MAX-ACCESS   read-only
        STATUS       current
        DESCRIPTION  "RMON 1day RX 256 to 511 Octs."
        ::= { rmon1dayPort2Entry 29 }

    rmon1dayHCRxEthStatsPkts256to511Octets2Status OBJECT-TYPE
        SYNTAX       IpeStatsInfo
        MAX-ACCESS   read-only
        STATUS       current
        DESCRIPTION
            "RMON 1day RX 256 to 511 Octs Status. 'invalid' means the
            corresponding monitoring value is not reliable because of the
            alarm or other reasons. 'maintenance' means that some maintenance
            functions are executed on the current interval."
        ::= { rmon1dayPort2Entry 30 }

    rmon1dayHCTxEthStatsPkts256to511Octets2 OBJECT-TYPE
        SYNTAX       Counter64
        MAX-ACCESS   read-only
        STATUS       current
        DESCRIPTION  "RMON 1day TX 256 to 511 Octs."
        ::= { rmon1dayPort2Entry 31 }

    rmon1dayHCTxEthStatsPkts256to511Octets2Status OBJECT-TYPE
        SYNTAX       IpeStatsInfo
        MAX-ACCESS   read-only
        STATUS       current
        DESCRIPTION
            "RMON 1day TX 256 to 511 Octs Status. 'invalid' means the
            corresponding monitoring value is not reliable because of the
            alarm or other reasons. 'maintenance' means that some maintenance
            functions are executed on the current interval."
        ::= { rmon1dayPort2Entry 32 }

    rmon1dayHCRxEthStatsPkts512to1023Octets2 OBJECT-TYPE
        SYNTAX       Counter64
        MAX-ACCESS   read-only
        STATUS       current
        DESCRIPTION  "RMON 1day RX 512 to 1023 Octs"
        ::= { rmon1dayPort2Entry 33 }

    rmon1dayHCRxEthStatsPkts512to1023Octets2Status OBJECT-TYPE
        SYNTAX       IpeStatsInfo
        MAX-ACCESS   read-only
        STATUS       current
        DESCRIPTION
            "RMON 1day RX 512 to 1023 Octs Status. 'invalid' means the
            corresponding monitoring value is not reliable because of the
            alarm or other reasons. 'maintenance' means that some maintenance
            functions are executed on the current interval."
        ::= { rmon1dayPort2Entry 34 }

    rmon1dayHCTxEthStatsPkts512to1023Octets2 OBJECT-TYPE
        SYNTAX       Counter64
        MAX-ACCESS   read-only
        STATUS       current
        DESCRIPTION  "RMON 1day TX 512 to 1023 Octs"
        ::= { rmon1dayPort2Entry 35 }

    rmon1dayHCTxEthStatsPkts512to1023Octets2Status OBJECT-TYPE
        SYNTAX       IpeStatsInfo
        MAX-ACCESS   read-only
        STATUS       current
        DESCRIPTION
            "RMON 1day TX 512 to 1023 Octs Status. 'invalid' means the
            corresponding monitoring value is not reliable because of the
            alarm or other reasons. 'maintenance' means that some maintenance
            functions are executed on the current interval."
        ::= { rmon1dayPort2Entry 36 }

    rmon1dayHCRxEthStatsPkts1024to1518Octets2 OBJECT-TYPE
        SYNTAX       Counter64
        MAX-ACCESS   read-only
        STATUS       current
        DESCRIPTION  "RMON 1day RX 1024 to 1518 Octs."
        ::= { rmon1dayPort2Entry 37 }

    rmon1dayHCRxEthStatsPkts1024to1518Octets2Status OBJECT-TYPE
        SYNTAX       IpeStatsInfo
        MAX-ACCESS   read-only
        STATUS       current
        DESCRIPTION
            "RMON 1day RX 1024 to 1518 Octs Status. 'invalid' means the
            corresponding monitoring value is not reliable because of the
            alarm or other reasons. 'maintenance' means that some maintenance
            functions are executed on the current interval."
        ::= { rmon1dayPort2Entry 38 }

    rmon1dayHCTxEthStatsPkts1024to1518Octets2 OBJECT-TYPE
        SYNTAX       Counter64
        MAX-ACCESS   read-only
        STATUS       current
        DESCRIPTION  "RMON 1day TX 1024 to 1518 Octs."
        ::= { rmon1dayPort2Entry 39 }

    rmon1dayHCTxEthStatsPkts1024to1518Octets2Status OBJECT-TYPE
        SYNTAX       IpeStatsInfo
        MAX-ACCESS   read-only
        STATUS       current
        DESCRIPTION
            "RMON 1day TX 1024 to 1518 Octs Status. 'invalid' means the
            corresponding monitoring value is not reliable because of the
            alarm or other reasons. 'maintenance' means that some maintenance
            functions are executed on the current interval."
        ::= { rmon1dayPort2Entry 40 }

    rmon1dayRxEthStatsCRCAlignErrors2 OBJECT-TYPE
        SYNTAX       Counter32
        MAX-ACCESS   read-only
        STATUS       current
        DESCRIPTION  "RMON 1day RX CRC Alignment Errors"
        ::= { rmon1dayPort2Entry 41 }

    rmon1dayRxEthStatsCRCAlignErrors2Status OBJECT-TYPE
        SYNTAX       IpeStatsInfo
        MAX-ACCESS   read-only
        STATUS       current
        DESCRIPTION
            "RMON 1day RX CRC Alignment Errors Status. 'invalid' means the
            corresponding monitoring value is not reliable because of the
            alarm or other reasons. 'maintenance' means that some maintenance
            functions are executed on the current interval."
        ::= { rmon1dayPort2Entry 42 }

    rmon1dayRxEthStatsOversizePkts2 OBJECT-TYPE
        SYNTAX       Counter32
        MAX-ACCESS   read-only
        STATUS       current
        DESCRIPTION  "RMON 1day RX Oversize Pkts"
        ::= { rmon1dayPort2Entry 43 }

    rmon1dayRxEthStatsOversizePkts2Status OBJECT-TYPE
        SYNTAX       IpeStatsInfo
        MAX-ACCESS   read-only
        STATUS       current
        DESCRIPTION
            "RMON 1day RX Oversize Pkts Status. 'invalid' means the
            corresponding monitoring value is not reliable because of the
            alarm or other reasons. 'maintenance' means that some maintenance
            functions are executed on the current interval."
        ::= { rmon1dayPort2Entry 44 }

    rmon1dayRxEthStatsJabbers2 OBJECT-TYPE
        SYNTAX       Counter32
        MAX-ACCESS   read-only
        STATUS       current
        DESCRIPTION  "RMON 1day RX Jabbers"
        ::= { rmon1dayPort2Entry 45 }

    rmon1dayRxEthStatsJabbers2Status OBJECT-TYPE
        SYNTAX       IpeStatsInfo
        MAX-ACCESS   read-only
        STATUS       current
        DESCRIPTION
            "RMON 1day RX Jabbers Status. 'invalid' means the corresponding
            monitoring value is not reliable because of the alarm or other
            reasons. 'maintenance' means that some maintenance functions are
            executed on the current interval."
        ::= { rmon1dayPort2Entry 46 }

    rmon1dayRxEthStatsMulticastPkts2 OBJECT-TYPE
        SYNTAX       Counter32
        MAX-ACCESS   read-only
        STATUS       current
        DESCRIPTION  "RMON 1day RX Multicast Pkts"
        ::= { rmon1dayPort2Entry 47 }

    rmon1dayRxEthStatsMulticastPkts2Status OBJECT-TYPE
        SYNTAX       IpeStatsInfo
        MAX-ACCESS   read-only
        STATUS       current
        DESCRIPTION
            "RMON 1day RX Multicast Pkts Status. 'invalid' means the
            corresponding monitoring value is not reliable because of the
            alarm or other reasons. 'maintenance' means that some maintenance
            functions are executed on the current interval."
        ::= { rmon1dayPort2Entry 48 }

    rmon1dayTxEthStatsMulticastPkts2 OBJECT-TYPE
        SYNTAX       Counter32
        MAX-ACCESS   read-only
        STATUS       current
        DESCRIPTION  "RMON 1day TX Multicast Pkts."
        ::= { rmon1dayPort2Entry 49 }

    rmon1dayTxEthStatsMulticastPkts2Status OBJECT-TYPE
        SYNTAX       IpeStatsInfo
        MAX-ACCESS   read-only
        STATUS       current
        DESCRIPTION
            "RMON 1day TX Multicast Pkts Status. 'invalid' means the
            corresponding monitoring value is not reliable because of the
            alarm or other reasons. 'maintenance' means that some maintenance
            functions are executed on the current interval."
        ::= { rmon1dayPort2Entry 50 }

    rmon1dayRxEthStatsBroadcastPkts2 OBJECT-TYPE
        SYNTAX       Counter32
        MAX-ACCESS   read-only
        STATUS       current
        DESCRIPTION  "RMON 1day RX Broadcast Pkts."
        ::= { rmon1dayPort2Entry 51 }

    rmon1dayRxEthStatsBroadcastPkts2Status OBJECT-TYPE
        SYNTAX       IpeStatsInfo
        MAX-ACCESS   read-only
        STATUS       current
        DESCRIPTION
            "RMON 1day RX Broadcast Pkts Status. 'invalid' means the
            corresponding monitoring value is not reliable because of the
            alarm or other reasons. 'maintenance' means that some maintenance
            functions are executed on the current interval."
        ::= { rmon1dayPort2Entry 52 }

    rmon1dayTxEthStatsBroadcastPkts2 OBJECT-TYPE
        SYNTAX       Counter32
        MAX-ACCESS   read-only
        STATUS       current
        DESCRIPTION  "RMON 1day TX Broadcast Pkts."
        ::= { rmon1dayPort2Entry 53 }

    rmon1dayTxEthStatsBroadcastPkts2Status OBJECT-TYPE
        SYNTAX       IpeStatsInfo
        MAX-ACCESS   read-only
        STATUS       current
        DESCRIPTION
            "RMON 1day TX Broadcast Pkts Status. 'invalid' means the
            corresponding monitoring value is not reliable because of the
            alarm or other reasons. 'maintenance' means that some maintenance
            functions are executed on the current interval."
        ::= { rmon1dayPort2Entry 54 }

    rmon1dayTxEthStatsCollisions2 OBJECT-TYPE
        SYNTAX       Counter32
        MAX-ACCESS   read-only
        STATUS       current
        DESCRIPTION  "RMON 1day TX Collisions."
        ::= { rmon1dayPort2Entry 55 }

    rmon1dayTxEthStatsCollisions2Status OBJECT-TYPE
        SYNTAX       IpeStatsInfo
        MAX-ACCESS   read-only
        STATUS       current
        DESCRIPTION
            "RMON 1day TX Collistions Status. 'invalid' means the
            corresponding monitoring value is not reliable because of the
            alarm or other reasons. 'maintenance' means that some maintenance
            functions are executed on the current interval."
        ::= { rmon1dayPort2Entry 56 }

    rmon1dayHCRxUnknownTPID2 OBJECT-TYPE
        SYNTAX       Counter64
        MAX-ACCESS   read-only
        STATUS       current
        DESCRIPTION  "RMON 1day RX Unknown TPID."
        ::= { rmon1dayPort2Entry 57 }

    rmon1dayHCRxUnknownTPID2Status OBJECT-TYPE
        SYNTAX       IpeStatsInfo
        MAX-ACCESS   read-only
        STATUS       current
        DESCRIPTION
            "RMON 1day RX Unknown TPID Status. 'invalid' means the
            corresponding monitoring value is not reliable because of the
            alarm or other reasons. 'maintenance' means that some maintenance
            functions are executed on the current interval."
        ::= { rmon1dayPort2Entry 58 }

    rmon1dayHCRxUnknownVID2 OBJECT-TYPE
        SYNTAX       Counter64
        MAX-ACCESS   read-only
        STATUS       current
        DESCRIPTION  "RMON 1day RX Unknown VID."
        ::= { rmon1dayPort2Entry 59 }

    rmon1dayHCRxUnknownVID2Status OBJECT-TYPE
        SYNTAX       IpeStatsInfo
        MAX-ACCESS   read-only
        STATUS       current
        DESCRIPTION
            "RMON 1day RX Unknown VID Status. 'invalid' means the
            corresponding monitoring value is not reliable because of the
            alarm or other reasons. 'maintenance' means that some maintenance
            functions are executed on the current interval."
        ::= { rmon1dayPort2Entry 60 }

    rmon1dayHCRxMAClimit2 OBJECT-TYPE
        SYNTAX       Counter64
        MAX-ACCESS   read-only
        STATUS       current
        DESCRIPTION  "RMON 1day RX MAC Limit."
        ::= { rmon1dayPort2Entry 61 }

    rmon1dayHCRxMAClimit2Status OBJECT-TYPE
        SYNTAX       IpeStatsInfo
        MAX-ACCESS   read-only
        STATUS       current
        DESCRIPTION
            "RMON 1day RX MAC Limit Status. 'invalid' means the corresponding
            monitoring value is not reliable because of the alarm or other
            reasons. 'maintenance' means that some maintenance functions are
            executed on the current interval."
        ::= { rmon1dayPort2Entry 62 }

    rmon1dayHCRxFilterDiscard2 OBJECT-TYPE
        SYNTAX       Counter64
        MAX-ACCESS   read-only
        STATUS       current
        DESCRIPTION  "RMON 1day RX Filter Discard."
        ::= { rmon1dayPort2Entry 63 }

    rmon1dayHCRxFilterDiscard2Status OBJECT-TYPE
        SYNTAX       IpeStatsInfo
        MAX-ACCESS   read-only
        STATUS       current
        DESCRIPTION
            "RMON 1day RX Filter Discard Status. 'invalid' means the
            corresponding monitoring value is not reliable because of the
            alarm or other reasons. 'maintenance' means that some maintenance
            functions are executed on the current interval."
        ::= { rmon1dayPort2Entry 64 }

    rmon1dayHCRxQoSDiscard2 OBJECT-TYPE
        SYNTAX       Counter64
        MAX-ACCESS   read-only
        STATUS       current
        DESCRIPTION  "RMON 1day RX QoS Discard."
        ::= { rmon1dayPort2Entry 65 }

    rmon1dayHCRxQoSDiscard2Status OBJECT-TYPE
        SYNTAX       IpeStatsInfo
        MAX-ACCESS   read-only
        STATUS       current
        DESCRIPTION
            "RMON 1day RX QoS Discard Status. 'invalid' means the
            corresponding monitoring value is not reliable because of the
            alarm or other reasons. 'maintenance' means that some maintenance
            functions are executed on the current interval."
        ::= { rmon1dayPort2Entry 66 }

    rmon1dayHCTxQueue0Discard2 OBJECT-TYPE
        SYNTAX       Counter64
        MAX-ACCESS   read-only
        STATUS       current
        DESCRIPTION  "RMON 1day TX Queue0 Discard."
        ::= { rmon1dayPort2Entry 67 }

    rmon1dayHCTxQueue0Discard2Status OBJECT-TYPE
        SYNTAX       IpeStatsInfo
        MAX-ACCESS   read-only
        STATUS       current
        DESCRIPTION
            "RMON 1day TX Queue0 Discard Status. 'invalid' means the
            corresponding monitoring value is not reliable because of the
            alarm or other reasons. 'maintenance' means that some maintenance
            functions are executed on the current interval."
        ::= { rmon1dayPort2Entry 68 }

    rmon1dayHCTxQueue1Discard2 OBJECT-TYPE
        SYNTAX       Counter64
        MAX-ACCESS   read-only
        STATUS       current
        DESCRIPTION  "RMON 1day TX Queue1 Discard."
        ::= { rmon1dayPort2Entry 69 }

    rmon1dayHCTxQueue1Discard2Status OBJECT-TYPE
        SYNTAX       IpeStatsInfo
        MAX-ACCESS   read-only
        STATUS       current
        DESCRIPTION
            "RMON 1day TX Queue1 Discard Status. 'invalid' means the
            corresponding monitoring value is not reliable because of the
            alarm or other reasons. 'maintenance' means that some maintenance
            functions are executed on the current interval."
        ::= { rmon1dayPort2Entry 70 }

    rmon1dayHCTxQueue2Discard2 OBJECT-TYPE
        SYNTAX       Counter64
        MAX-ACCESS   read-only
        STATUS       current
        DESCRIPTION  "RMON 1day TX Queue2 Discard."
        ::= { rmon1dayPort2Entry 71 }

    rmon1dayHCTxQueue2Discard2Status OBJECT-TYPE
        SYNTAX       IpeStatsInfo
        MAX-ACCESS   read-only
        STATUS       current
        DESCRIPTION
            "RMON 1day TX Queue2 Discard Status. 'invalid' means the
            corresponding monitoring value is not reliable because of the
            alarm or other reasons. 'maintenance' means that some maintenance
            functions are executed on the current interval."
        ::= { rmon1dayPort2Entry 72 }

    rmon1dayHCTxQueue3Discard2 OBJECT-TYPE
        SYNTAX       Counter64
        MAX-ACCESS   read-only
        STATUS       current
        DESCRIPTION  "RMON 1day TX Queue3 Discard."
        ::= { rmon1dayPort2Entry 73 }

    rmon1dayHCTxQueue3Discard2Status OBJECT-TYPE
        SYNTAX       IpeStatsInfo
        MAX-ACCESS   read-only
        STATUS       current
        DESCRIPTION
            "RMON 1day TX Queue3 Discard Status. 'invalid' means the
            corresponding monitoring value is not reliable because of the
            alarm or other reasons. 'maintenance' means that some maintenance
            functions are executed on the current interval."
        ::= { rmon1dayPort2Entry 74 }

    rmon1dayHCTxQueue4Discard2 OBJECT-TYPE
        SYNTAX       Counter64
        MAX-ACCESS   read-only
        STATUS       current
        DESCRIPTION
            "RMON 1day TX Queue4 Discard. If the equipment is running on 4
            class QoS mode. The value of this object is always 0."
        ::= { rmon1dayPort2Entry 75 }

    rmon1dayHCTxQueue4Discard2Status OBJECT-TYPE
        SYNTAX       IpeStatsInfo
        MAX-ACCESS   read-only
        STATUS       current
        DESCRIPTION
            "RMON 1day TX Queue4 Discard Status. 'invalid' means the
            corresponding monitoring value is not reliable because of the
            alarm or other reasons. 'maintenance' means that some maintenance
            functions are executed on the current interval."
        ::= { rmon1dayPort2Entry 76 }

    rmon1dayHCTxQueue5Discard2 OBJECT-TYPE
        SYNTAX       Counter64
        MAX-ACCESS   read-only
        STATUS       current
        DESCRIPTION
            "RMON 1day TX Queue5 Discard. If the equipment is running on 4
            class QoS mode. The value of this object is always 0."
        ::= { rmon1dayPort2Entry 77 }

    rmon1dayHCTxQueue5Discard2Status OBJECT-TYPE
        SYNTAX       IpeStatsInfo
        MAX-ACCESS   read-only
        STATUS       current
        DESCRIPTION
            "RMON 1day TX Queue5 Discard Status. 'invalid' means the
            corresponding monitoring value is not reliable because of the
            alarm or other reasons. 'maintenance' means that some maintenance
            functions are executed on the current interval."
        ::= { rmon1dayPort2Entry 78 }

    rmon1dayHCTxQueue6Discard2 OBJECT-TYPE
        SYNTAX       Counter64
        MAX-ACCESS   read-only
        STATUS       current
        DESCRIPTION
            "RMON 1day TX Queue6 Discard. If the equipment is running on 4
            class QoS mode. The value of this object is always 0."
        ::= { rmon1dayPort2Entry 79 }

    rmon1dayHCTxQueue6Discard2Status OBJECT-TYPE
        SYNTAX       IpeStatsInfo
        MAX-ACCESS   read-only
        STATUS       current
        DESCRIPTION
            "RMON 1day TX Queue6 Discard Status. 'invalid' means the
            corresponding monitoring value is not reliable because of the
            alarm or other reasons. 'maintenance' means that some maintenance
            functions are executed on the current interval."
        ::= { rmon1dayPort2Entry 80 }

    rmon1dayHCTxQueue7Discard2 OBJECT-TYPE
        SYNTAX       Counter64
        MAX-ACCESS   read-only
        STATUS       current
        DESCRIPTION
            "RMON 1day TX Queue7 Discard. If the equipment is running on 4
            class QoS mode. The value of this object is always 0."
        ::= { rmon1dayPort2Entry 81 }

    rmon1dayHCTxQueue7Discard2Status OBJECT-TYPE
        SYNTAX       IpeStatsInfo
        MAX-ACCESS   read-only
        STATUS       current
        DESCRIPTION
            "RMON 1day TX Queue7 Discard Status. 'invalid' means the
            corresponding monitoring value is not reliable because of the
            alarm or other reasons. 'maintenance' means that some maintenance
            functions are executed on the current interval."
        ::= { rmon1dayPort2Entry 82 }

    rmon1dayTxEthStatsOversizePkts2 OBJECT-TYPE
        SYNTAX       Counter32
        MAX-ACCESS   read-only
        STATUS       current
        DESCRIPTION  "RMON 1day TX Oversize Pkts."
        ::= { rmon1dayPort2Entry 83 }

    rmon1dayTxEthStatsOversizePkts2Status OBJECT-TYPE
        SYNTAX       IpeStatsInfo
        MAX-ACCESS   read-only
        STATUS       current
        DESCRIPTION
            "RMON 1day TX Oversize Pkts Status. 'invalid' means the
            corresponding monitoring value is not reliable because of the
            alarm or other reasons. 'maintenance' means that some maintenance
            functions are executed on the current interval."
        ::= { rmon1dayPort2Entry 84 }

    rmon15minVlanGroup OBJECT IDENTIFIER
        ::= { rmonEthGroup 3 }

    rmon15minVlanTable OBJECT-TYPE
        SYNTAX       SEQUENCE OF Rmon15minVlanEntry
        MAX-ACCESS   not-accessible
        STATUS       current
        DESCRIPTION  "RMON 15min VLAN Counter Table."
        ::= { rmon15minVlanGroup 1 }

    rmon15minVlanEntry OBJECT-TYPE
        SYNTAX       Rmon15minVlanEntry
        MAX-ACCESS   not-accessible
        STATUS       current
        DESCRIPTION  ""
        INDEX        { rmon15minVlanCounterIndex }
        ::= { rmon15minVlanTable 1 }

    Rmon15minVlanEntry ::= SEQUENCE {
        rmon15minVlanCounterIndex               Integer32,
        rmon15minVlanCounterNEAddress           IpAddress,
        rmon15minHCRxFrame                      Counter64,
        rmon15minHCRxFrameStatusInfo            INTEGER,
        rmon15minHCTxFrame                      Counter64,
        rmon15minHCTxFrameStatusInfo            INTEGER,
        rmon15minHCRxQoSDiscardFrame            Counter64,
        rmon15minHCRxQoSDiscardFrameStatusInfo  INTEGER
    }

    rmon15minVlanCounterIndex OBJECT-TYPE
        SYNTAX       Integer32 (1..256)
        MAX-ACCESS   not-accessible
        STATUS       current
        DESCRIPTION  "Index of this table."
        ::= { rmon15minVlanEntry 1 }

    rmon15minVlanCounterNEAddress OBJECT-TYPE
        SYNTAX       IpAddress
        MAX-ACCESS   not-accessible
        STATUS       current
        DESCRIPTION  "reserved."
        ::= { rmon15minVlanEntry 2 }

    rmon15minHCRxFrame OBJECT-TYPE
        SYNTAX       Counter64
        MAX-ACCESS   read-only
        STATUS       current
        DESCRIPTION  "RMON 15min VLAN RX Frames"
        ::= { rmon15minVlanEntry 3 }

    rmon15minHCRxFrameStatusInfo OBJECT-TYPE
        SYNTAX       INTEGER {
                         invalid(0),
                         valid-no-maintenance(1),
                         valid-maintenance(2),
                         invalid-no-maintenance(3),
                         invalid-maintenance(4)
                     }
        MAX-ACCESS   read-only
        STATUS       current
        DESCRIPTION
            "RMON 15min VLAN RX Frames Status. 'invalid' means the
            corresponding monitoring value is not reliable because of the
            alarm or other reasons. 'maintenance' means that some maintenance
            functions are executed on the current interval."
        ::= { rmon15minVlanEntry 4 }

    rmon15minHCTxFrame OBJECT-TYPE
        SYNTAX       Counter64
        MAX-ACCESS   read-only
        STATUS       current
        DESCRIPTION  "RMON 15min VLAN TX Frames"
        ::= { rmon15minVlanEntry 5 }

    rmon15minHCTxFrameStatusInfo OBJECT-TYPE
        SYNTAX       INTEGER {
                         invalid(0),
                         valid-no-maintenance(1),
                         valid-maintenance(2),
                         invalid-no-maintenance(3),
                         invalid-maintenance(4)
                     }
        MAX-ACCESS   read-only
        STATUS       current
        DESCRIPTION
            "RMON 15min VLAN TX Frames Status. 'invalid' means the
            corresponding monitoring value is not reliable because of the
            alarm or other reasons. 'maintenance' means that some maintenance
            functions are executed on the current interval."
        ::= { rmon15minVlanEntry 6 }

    rmon15minHCRxQoSDiscardFrame OBJECT-TYPE
        SYNTAX       Counter64
        MAX-ACCESS   read-only
        STATUS       current
        DESCRIPTION  "RMON 15min RX QoS Discard Frames"
        ::= { rmon15minVlanEntry 7 }

    rmon15minHCRxQoSDiscardFrameStatusInfo OBJECT-TYPE
        SYNTAX       INTEGER {
                         invalid(0),
                         valid-no-maintenance(1),
                         valid-maintenance(2),
                         invalid-no-maintenance(3),
                         invalid-maintenance(4)
                     }
        MAX-ACCESS   read-only
        STATUS       current
        DESCRIPTION
            "RMON 15min RX QoS Discard Frames Status. 'invalid' means the
            corresponding monitoring value is not reliable because of the
            alarm or other reasons. 'maintenance' means that some maintenance
            functions are executed on the current interval."
        ::= { rmon15minVlanEntry 8 }

    rmon15minVlanPortMappingTable OBJECT-TYPE
        SYNTAX       SEQUENCE OF Rmon15minVlanPortMappingEntry
        MAX-ACCESS   not-accessible
        STATUS       current
        DESCRIPTION
            "If the VLAN Counter is enabled to the port, this object will
            show the corresponding VLAN Counter Index."
        ::= { rmon15minVlanGroup 2 }

    rmon15minVlanPortMappingEntry OBJECT-TYPE
        SYNTAX       Rmon15minVlanPortMappingEntry
        MAX-ACCESS   not-accessible
        STATUS       current
        DESCRIPTION  ""
        INDEX        {
                         rmon15minVlanPortMappingIfIndex,
                         rmon15minVlanMappingVlanIndex
                     }
        ::= { rmon15minVlanPortMappingTable 1 }

    Rmon15minVlanPortMappingEntry ::= SEQUENCE {
        rmon15minVlanPortMappingIfIndex  InterfaceIndex,
        rmon15minVlanMappingVlanIndex    Integer32,
        rmon15minVlanMappingNEAddress    IpAddress,
        rmon15minVlanCounterId           Integer32
    }

    rmon15minVlanPortMappingIfIndex OBJECT-TYPE
        SYNTAX       InterfaceIndex
        MAX-ACCESS   not-accessible
        STATUS       current
        DESCRIPTION  "Index of this table."
        ::= { rmon15minVlanPortMappingEntry 1 }

    rmon15minVlanMappingVlanIndex OBJECT-TYPE
        SYNTAX       Integer32 (1..4094)
        MAX-ACCESS   not-accessible
        STATUS       current
        DESCRIPTION  "Index of this table."
        ::= { rmon15minVlanPortMappingEntry 2 }

    rmon15minVlanMappingNEAddress OBJECT-TYPE
        SYNTAX       IpAddress
        MAX-ACCESS   not-accessible
        STATUS       current
        DESCRIPTION  "reserved."
        ::= { rmon15minVlanPortMappingEntry 3 }

    rmon15minVlanCounterId OBJECT-TYPE
        SYNTAX       Integer32 (1..256)
        MAX-ACCESS   read-only
        STATUS       current
        DESCRIPTION
            "VLAN Counter ID which is assigned to the port.
            value range : 1 -   8 (iPASOLINK200/400/1000series/EX/iX)
                        : 1 - 256 (iPASOLINK VR 2/VR 4/VR 10)"
        ::= { rmon15minVlanPortMappingEntry 4 }

    rmon1dayVlanGroup OBJECT IDENTIFIER
        ::= { rmonEthGroup 4 }

    rmon1dayVlanTable OBJECT-TYPE
        SYNTAX       SEQUENCE OF Rmon1dayVlanEntry
        MAX-ACCESS   not-accessible
        STATUS       current
        DESCRIPTION  "RMON 1day VLAN Counter Table."
        ::= { rmon1dayVlanGroup 1 }

    rmon1dayVlanEntry OBJECT-TYPE
        SYNTAX       Rmon1dayVlanEntry
        MAX-ACCESS   not-accessible
        STATUS       current
        DESCRIPTION  ""
        INDEX        { rmon1dayVlanCounterIndex }
        ::= { rmon1dayVlanTable 1 }

    Rmon1dayVlanEntry ::= SEQUENCE {
        rmon1dayVlanCounterIndex               Integer32,
        rmon1dayVlanCounterNEAddress           IpAddress,
        rmon1dayHCRxFrame                      Counter64,
        rmon1dayHCRxFrameStatusInfo            INTEGER,
        rmon1dayHCTxFrame                      Counter64,
        rmon1dayHCTxFrameStatusInfo            INTEGER,
        rmon1dayHCRxQoSDiscardFrame            Counter64,
        rmon1dayHCRxQoSDiscardFrameStatusInfo  INTEGER
    }

    rmon1dayVlanCounterIndex OBJECT-TYPE
        SYNTAX       Integer32 (1..256)
        MAX-ACCESS   not-accessible
        STATUS       current
        DESCRIPTION  "Index of this table."
        ::= { rmon1dayVlanEntry 1 }

    rmon1dayVlanCounterNEAddress OBJECT-TYPE
        SYNTAX       IpAddress
        MAX-ACCESS   not-accessible
        STATUS       current
        DESCRIPTION  "reserved."
        ::= { rmon1dayVlanEntry 2 }

    rmon1dayHCRxFrame OBJECT-TYPE
        SYNTAX       Counter64
        MAX-ACCESS   read-only
        STATUS       current
        DESCRIPTION  "RMON 1day VLAN RX Frames"
        ::= { rmon1dayVlanEntry 3 }

    rmon1dayHCRxFrameStatusInfo OBJECT-TYPE
        SYNTAX       INTEGER {
                         invalid(0),
                         valid-no-maintenance(1),
                         valid-maintenance(2),
                         invalid-no-maintenance(3),
                         invalid-maintenance(4)
                     }
        MAX-ACCESS   read-only
        STATUS       current
        DESCRIPTION
            "RMON 1day VLAN RX Frames Status. 'invalid' means the
            corresponding monitoring value is not reliable because of the
            alarm or other reasons. 'maintenance' means that some maintenance
            functions are executed on the current interval."
        ::= { rmon1dayVlanEntry 4 }

    rmon1dayHCTxFrame OBJECT-TYPE
        SYNTAX       Counter64
        MAX-ACCESS   read-only
        STATUS       current
        DESCRIPTION  "RMON 1day VLAN TX Frames"
        ::= { rmon1dayVlanEntry 5 }

    rmon1dayHCTxFrameStatusInfo OBJECT-TYPE
        SYNTAX       INTEGER {
                         invalid(0),
                         valid-no-maintenance(1),
                         valid-maintenance(2),
                         invalid-no-maintenance(3),
                         invalid-maintenance(4)
                     }
        MAX-ACCESS   read-only
        STATUS       current
        DESCRIPTION
            "RMON 1day VLAN TX Frames Status. 'invalid' means the
            corresponding monitoring value is not reliable because of the
            alarm or other reasons. 'maintenance' means that some maintenance
            functions are executed on the current interval."
        ::= { rmon1dayVlanEntry 6 }

    rmon1dayHCRxQoSDiscardFrame OBJECT-TYPE
        SYNTAX       Counter64
        MAX-ACCESS   read-only
        STATUS       current
        DESCRIPTION  "RMON 1day RX QoS Discard Frames"
        ::= { rmon1dayVlanEntry 7 }

    rmon1dayHCRxQoSDiscardFrameStatusInfo OBJECT-TYPE
        SYNTAX       INTEGER {
                         invalid(0),
                         valid-no-maintenance(1),
                         valid-maintenance(2),
                         invalid-no-maintenance(3),
                         invalid-maintenance(4)
                     }
        MAX-ACCESS   read-only
        STATUS       current
        DESCRIPTION
            "RMON 1day RX QoS Discard Frames Status. 'invalid' means the
            corresponding monitoring value is not reliable because of the
            alarm or other reasons. 'maintenance' means that some maintenance
            functions are executed on the current interval."
        ::= { rmon1dayVlanEntry 8 }

    rmon1dayVlanPortMappingTable OBJECT-TYPE
        SYNTAX       SEQUENCE OF Rmon1dayVlanPortMappingEntry
        MAX-ACCESS   not-accessible
        STATUS       current
        DESCRIPTION
            "If the VLAN Counter is enabled to the port, this object will
            show the corresponding VLAN Counter Index."
        ::= { rmon1dayVlanGroup 2 }

    rmon1dayVlanPortMappingEntry OBJECT-TYPE
        SYNTAX       Rmon1dayVlanPortMappingEntry
        MAX-ACCESS   not-accessible
        STATUS       current
        DESCRIPTION  ""
        INDEX        {
                         rmon1dayVlanPortMappingIfIndex,
                         rmon1dayVlanMappingVlanIndex
                     }
        ::= { rmon1dayVlanPortMappingTable 1 }

    Rmon1dayVlanPortMappingEntry ::= SEQUENCE {
        rmon1dayVlanPortMappingIfIndex  InterfaceIndex,
        rmon1dayVlanMappingVlanIndex    Integer32,
        rmon1dayVlanMappingNEAddress    IpAddress,
        rmon1dayVlanCounterId           Integer32
    }

    rmon1dayVlanPortMappingIfIndex OBJECT-TYPE
        SYNTAX       InterfaceIndex
        MAX-ACCESS   not-accessible
        STATUS       current
        DESCRIPTION  "Index of this table."
        ::= { rmon1dayVlanPortMappingEntry 1 }

    rmon1dayVlanMappingVlanIndex OBJECT-TYPE
        SYNTAX       Integer32 (1..4094)
        MAX-ACCESS   not-accessible
        STATUS       current
        DESCRIPTION  "Index of this table."
        ::= { rmon1dayVlanPortMappingEntry 2 }

    rmon1dayVlanMappingNEAddress OBJECT-TYPE
        SYNTAX       IpAddress
        MAX-ACCESS   not-accessible
        STATUS       current
        DESCRIPTION  "reserved."
        ::= { rmon1dayVlanPortMappingEntry 3 }

    rmon1dayVlanCounterId OBJECT-TYPE
        SYNTAX       Integer32 (1..256)
        MAX-ACCESS   read-only
        STATUS       current
        DESCRIPTION
            "VLAN Counter ID which is assigned to the port.
            value range : 1 -   8 (iPASOLINK200/400/1000series/EX/iX)
                        : 1 - 256 (iPASOLINK VR 2/VR 4/VR 10)"
        ::= { rmon1dayVlanPortMappingEntry 4 }

-----------------------------------------------
-- End User MIB Object Definitions
-----------------------------------------------

END
