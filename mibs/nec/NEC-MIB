-- "@(#)NEC-MIB.txt 7.1.2.2 98/03/11 18:15:10"	sccs ident
-- NEC-MIB { iso org(3) dod(6) internet(1) private(4) enterprises(1) 119 }

NEC-MIB DEFINITIONS ::= BEGIN
	IMPORTS
        enterprises, Counter, IpAddress, Opaque
                FROM RFC1155-SMI
        OBJECT-TYPE
                FROM RFC-1212
        DisplayString, ifIndex
                FROM RFC1213-MIB
	DateAndTime, TruthValue
		FROM SNMPv2-TC-v1;

	nec		OBJECT IDENTIFIER ::= { enterprises 119 }
	necProduct	OBJECT IDENTIFIER ::= { nec 1 }
	atomis		OBJECT IDENTIFIER ::= { necProduct 14 }
	m7-phase2	OBJECT IDENTIFIER ::= { atomis 9 }
	m7-corporate	OBJECT IDENTIFIER ::= { atomis 12 }
	nec-mib			OBJECT IDENTIFIER ::= { nec 2 }
	necProductDepend        OBJECT IDENTIFIER ::= { nec-mib 3 }
	atomis-mib          	OBJECT IDENTIFIER ::= { necProductDepend 14 }
	m7-phase2-mib		OBJECT IDENTIFIER ::= { atomis-mib 9 }
		node		OBJECT IDENTIFIER ::= { m7-phase2-mib 1 }
		slot		OBJECT IDENTIFIER ::= { m7-phase2-mib 2 }
		linf		OBJECT IDENTIFIER ::= { m7-phase2-mib 3 }
		conn		OBJECT IDENTIFIER ::= { m7-phase2-mib 4 }
		perf		OBJECT IDENTIFIER ::= { m7-phase2-mib 5 }
		scale		OBJECT IDENTIFIER ::= { m7-phase2-mib 6 }
		card		OBJECT IDENTIFIER ::= { m7-phase2-mib 7 }
		clock		OBJECT IDENTIFIER ::= { m7-phase2-mib 8 }
		diag		OBJECT IDENTIFIER ::= { m7-phase2-mib 9 }
		pnni		OBJECT IDENTIFIER ::= { m7-phase2-mib 10 }
		matCmd		OBJECT IDENTIFIER ::= { m7-phase2-mib 11 }
--		bill		OBJECT IDENTIFIER ::= { m7-phase2-mib 100 }
--		user		OBJECT IDENTIFIER ::= { m7-phase2-mib 101 }
	m7-corporate-mib	OBJECT IDENTIFIER ::= { atomis-mib 12 }

--	The Node Group

nodeStatus	OBJECT IDENTIFIER ::= { node 1 }

nodeStatusOperStatus OBJECT-TYPE
	SYNTAX  INTEGER {
			down (1),
			active (2),
			installing(3)
		}
	ACCESS  read-only
	STATUS  mandatory
	DESCRIPTION
		"Indicate operational status of the equipment."
	--	本装置の運転状態を表す.
	::= { nodeStatus 1 }

nodeStatusStartTime OBJECT-TYPE
	SYNTAX	DateAndTime
	ACCESS	read-only
	STATUS	mandatory
	DESCRIPTION
		"Date and Time when the equipment was last restarted"
	--	本装置が再開した時刻
	::= { nodeStatus 2 }

nodeStatusNodeId OBJECT-TYPE
	SYNTAX  OCTET STRING
	ACCESS  read-only
	STATUS  mandatory
	DESCRIPTION
		"Node ID of the equipment"
	--	本装置の Node ID
	::= { nodeStatus 3 }

nodeStatusSelfSystem OBJECT-TYPE
	SYNTAX	INTEGER {
			system-0 (1),
			system-1 (2)
		}
	ACCESS	read-only
	STATUS	mandatory
	DESCRIPTION
		"Indicate which system of the SW-Engine the NMS is
		connected with."
	--	NMS がどちらの系の SW-Engine につながっているかを示す.
	::= { nodeStatus 4  }

nodeStatusSwitchType OBJECT-TYPE
	SYNTAX	INTEGER {
			sw-Engine-5G (1),
			sw-Engine-10G (2)
		}
	ACCESS	read-only
	STATUS	mandatory
	DESCRIPTION
		"Indicate the type of SW-Engine."
	--	SW-Engine の種別を示す.
	::= { nodeStatus 5 }

nodeStatusFan OBJECT-TYPE
	SYNTAX	INTEGER {
			normal (1),
			failure (2)
		}
	ACCESS	read-only
	STATUS	mandatory
	DESCRIPTION
		"Indicate operational status of the FAN of the equipment."
	--	本装置の FAN の運転状態
	::= { nodeStatus 6 }

nodeStatusEnvironment OBJECT-TYPE
	SYNTAX  INTEGER {
			good (1),
			noGood (2)
		}
	ACCESS  read-only
	STATUS  mandatory
	DESCRIPTION
		"Peripheral temperature environment of the equipment.
		If the peripheral temperature exceeds 50 C, this object
		enters noGood(2)."
	--	本装置の周辺温度環境.
	--	周辺温度が50℃以上になった場合 noGood(2) となる.
	::= { nodeStatus 7 }

nodeStatusTable OBJECT-TYPE
	SYNTAX	SEQUENCE OF NodeStatusEntry
	ACCESS	not-accessible
	STATUS	mandatory
	DESCRIPTION
		"Table which indicates the status of each part of the
		equipment."
	--	本装置の各部の状態を示すテーブル.
	::= { node 2 }

nodeStatusEntry OBJECT-TYPE
	SYNTAX	NodeStatusEntry
	ACCESS	not-accessible
	STATUS	mandatory
	DESCRIPTION
		"Entry of the configuration of the table. "
	--	本装置の構成のエントリ
	INDEX	{ nodeStatusIndex }
	::= { nodeStatusTable 1 }

NodeStatusEntry ::=
	SEQUENCE {
		nodeStatusIndex
			INTEGER,
		nodeStatusPower
			INTEGER,
		nodeStatusSwitchMode
			INTEGER,
		nodeStatusSwitch
			INTEGER
	}

nodeStatusIndex OBJECT-TYPE
	SYNTAX	INTEGER
	ACCESS	not-accessible
	STATUS	mandatory
	DESCRIPTION
		"Index of the system configuration of the equipment "
	--	本装置の系構成のインデックス
	::= { nodeStatusEntry 1 }

nodeStatusPower OBJECT-TYPE
	SYNTAX	INTEGER {
			normal (1),
			failure (2),
			notInstalled (99)
		}
	ACCESS  read-only
	STATUS  mandatory
	DESCRIPTION
		"Indicate the status of the Power Unit of the equipment."
	--	本装置の PowerUnit の状態を表す.
	::= { nodeStatusEntry 2 }

nodeStatusSwitchMode OBJECT-TYPE
	SYNTAX  INTEGER {
			act (1),
			sby (2),
			notInstalled (99)
		}
	ACCESS  read-only
	STATUS  mandatory
	DESCRIPTION
		"Indicate operational mode of SW-Engine of the equipment."
	--	本装置の SW-Engine の運転モードを表す.
	::= { nodeStatusEntry 3 }

nodeStatusSwitch OBJECT-TYPE
	SYNTAX  INTEGER {
			normal (1),
			failure (2),
			diagnostics (3),
			diagnosis-status-NG (4),
			initializing (5),
			notInstalled (99)
		}
	ACCESS  read-only
	STATUS  mandatory
	DESCRIPTION
		"Indicate the status of the SW-Engine of the equipment."
	--	本装置の SW-Engine の状態を表す.
	::= { nodeStatusEntry 4 }

nodePCMCIATable OBJECT-TYPE
	SYNTAX  SEQUENCE OF NodePCMCIAEntry
	ACCESS  not-accessible
	STATUS  mandatory
	DESCRIPTION
		"Table which indicates the status of the PCMCIA card.
		Every PCMCIA slot is provided with an entry."
	--	PCMCIA card の状態を示すテーブル.
	--	PCMCIA スロット毎に １つのエントリを持つ.
	::= { node 3 }

nodePCMCIAEntry OBJECT-TYPE
	SYNTAX  NodePCMCIAEntry
	ACCESS  not-accessible
	STATUS  mandatory
	DESCRIPTION
		"Entry of nodePCMCIATable"
	--	nodePCMCIATable のエントリ
	INDEX	{ nodeStatusIndex, nodePCMCIAIndex }
	::= { nodePCMCIATable 1 }

NodePCMCIAEntry ::=
	SEQUENCE {
		nodePCMCIAIndex
			INTEGER,
		nodePCMCIAStatus
			INTEGER,
		nodePCMCIAType
			INTEGER
	}

nodePCMCIAIndex OBJECT-TYPE
	SYNTAX  INTEGER (1..2)
	ACCESS  not-accessible
	STATUS  mandatory
	DESCRIPTION
		"PCMCIA slot number per SW-Engine"
	--	SW-Engine 毎の PCMCIA スロット番号
	::= { nodePCMCIAEntry 1 }

nodePCMCIAStatus OBJECT-TYPE
	SYNTAX  INTEGER {
			normal (1),
			failure (2),
			initializing (3),
			busy (4),		-- Access in progress
			unknown (5),
			notInstalled (99)
		}
	ACCESS  read-only
	STATUS  mandatory
	DESCRIPTION
		"Status of PCMCIA card"
	--	PCMCIA card の状態
	::= { nodePCMCIAEntry 2 }

nodePCMCIAType OBJECT-TYPE
	SYNTAX  INTEGER {
			lan-card (1),
			ata-card (2),
			unknown (3),
			notInstalled (99)
	}
	ACCESS  read-only
	STATUS  mandatory
	DESCRIPTION
		"Type of installed PCMCIA card"
	--	実装されている PCMCIA card の種類
	::= { nodePCMCIAEntry 3 }

nodeOpe		OBJECT IDENTIFIER ::= { node 4 }

nodeOpeSave OBJECT-TYPE
	SYNTAX	INTEGER {
			noOperation(1),	--	None
			save(2)		--	Save processing
		}
	ACCESS	read-write
	STATUS  mandatory
	DESCRIPTION
		"Save processing.
		Save System Configuration information in FROM.
		The result is indicated in nodeOpeSaveResult.
		The value at read is always noOperation (1)."
	--	SAVE 処理.
	--	System Configuration 情報を FROM に SAVE する.
	--	結果はnodeOpeSaveResultに表示する.
	--	読み込み時の値は,いつも noOperation (1) である.
	::= { nodeOpe 1 }

nodeOpeSaveResult OBJECT-TYPE
	SYNTAX	INTEGER {			-- ACT/SBY
			succeed (1),		-- OK/OK
			succeed-0 (2),		-- OK/NG
			succeed-1 (3),		-- NG/OK
			temporaryFailure (4),	-- NG/NG
			nearend (5),		-- OK(NearEND)/OK(NearEND)
			nearend-0 (6),		-- OK(NearEND)/OK
			nearend-0-failure-1 (7),-- OK(NearEND)/NG
			nearend-1 (8),		-- OK/OK(NearEND)
			nearend-1-failure-0 (9),-- NG/OK(NearEND)
			notReady (10),		-- SAVE cannot be performed
			ready (11)		-- SAVE is in preparation
		}
	ACCESS	read-only
	STATUS	mandatory
	DESCRIPTION
		"The result of SAVE processing
		OK/NG indicate that SAVE processing completed/failed,
		respectively.
		(NearEND) indicates that the number of write counts
		approaches to the limit."
	--	SAVE 処理の結果
	--	OK/NG は SAVE 処理の成功 / 失敗を示す.
	--	(NearEND) は FROM への書き込み回数が限界に近付いた
	--	ことをを示す.
	::= { nodeOpe 2 }

nodeOpeCopy OBJECT-TYPE
	SYNTAX  INTEGER	{
			noOperation (1),	-- None.
			copy-all-from-act (2),	-- ACT->SBY
						-- Copy office data and LM.
			copy-all-from-sby (3),	-- SBY->ACT
						-- Copy office data and LM.
			copy-config-from-act (4),-- ACT->SBY Copy office data.
			copy-config-from-sby (5),-- SBY->ACT Copy office data.
			copy-system-from-act (6),-- ACT->SBY Copy LM.
			copy-system-from-sby (7) -- SBY->ACT Copy LM.
		}
	ACCESS	read-write
	STATUS  mandatory
	DESCRIPTION
		"Copy the system configuration information/LM to the FROM
		of other system.
		The result is indicated in nodeOpeCopyResult.
		The value at read is always noOperation(1)."
	--	System Configuration 情報 / ＬＭ を他系 FROM にコピーする.
	--	結果は nodeOpeCopyResult に表示する.
	--	読み込み時の値は,いつも noOperation(1) である.
	::= { nodeOpe 3 }

nodeOpeCopyResult OBJECT-TYPE
	SYNTAX	INTEGER {
			succeed (1), 		-- COPY completed.
			temporaryFailure (2), 	-- COPY failed.
			nearend (3), 		-- The number of write counts
						-- into FROM at the copy
						-- destination approaches to
						-- the limit.
			notReady (4), 		-- COPY cannot be performed.
			ready (5) 		-- Copy is in preparation.
		}
	ACCESS	read-only
	STATUS  mandatory
	DESCRIPTION
		"Result of the copy processing."
	--	Copy 処理の結果.
	::= { nodeOpe 4 }

nodeOpeReset OBJECT-TYPE
	SYNTAX	INTEGER {
			noOperation (1), 	-- None.
			reset-act (2),		-- Restart ACT system SW-Engine.
			reset-sby (3),		-- Restart SBY system SW-Engine.
			ach (4)			-- Switch ACT system.
		}
	ACCESS	read-write
	STATUS  mandatory
	DESCRIPTION
		"System Reset processing
		The value at read is always noOperation(1)."
	--	System Reset 処理.
	--	読み込み時の値は,いつも noOperation(1) である.
	::= { nodeOpe 5 }

--	The Slot Group

slotIfConfTable OBJECT-TYPE
        SYNTAX  SEQUENCE OF SlotIfConfEntry
        ACCESS  not-accessible
        STATUS  mandatory
        DESCRIPTION
                "Table which indicates the line card configuration
		of the equipment"
	--	本装置の回線パッケージの構成を示すテーブル.
        ::= { slot 1 }

slotIfConfEntry OBJECT-TYPE
        SYNTAX  SlotIfConfEntry
        ACCESS  not-accessible
        STATUS  mandatory
        DESCRIPTION
                "Entry of the line card configuration"
	--	回線パッケージの構成のエントリ
        INDEX   { slotIfConfIndex }
        ::= { slotIfConfTable 1 }

SlotIfConfEntry ::=
        SEQUENCE {
                slotIfConfIndex
                        INTEGER,
                slotIfConfPhysType
                        INTEGER,
                slotIfConfRev
                        DisplayString,
                slotIfConfStatus
                        INTEGER,
                slotIfConfBufferType
                        INTEGER,
                slotIfConfBufferRev
                        DisplayString,
		slotIfConfReset
			INTEGER,
		slotIfConfResetResult
			INTEGER
        }

slotIfConfIndex OBJECT-TYPE
        SYNTAX  INTEGER (1..16)
        ACCESS  read-only
        STATUS  mandatory
        DESCRIPTION
                "Index of line card configuration"
	--	回線パッケージの構成のインデックス
	::= { slotIfConfEntry 1 }

slotIfConfPhysType OBJECT-TYPE
        SYNTAX  INTEGER {
                        other (1),
                        taxi-100M (2),
                        oc3c-SMF-Long (3),
                        oc3c-SMF-Short (4),
                        oc3c-MMF (5),
                        relay-6Mcel (6),
                        j2-6M-4M-3M (7),
                        utp-5 (8),
                        oc12c-SMF-Type-A (9),
                        oc12c-SMF-Type-B (10),
                        ds3 (11),
                        e3 (12),
                        bts-1 (13),
                        bts-4 (14),
			primary-1536K-1152K-768K-512K-384K-256K-192K (15),
			ds1 (16),
			e1 (17),
			oc3c-POF (18),
			sts3c-COAXIAL (19),
                        vod-RxHFC4M (50),
                        vod-TxHFC27M (51),
			svr (52),
			fr-ds1 (53),
			fr-e1 (54),
			dcs (55),
			ce-ds3 (56),
			ce-ds1 (57),
			ce-e1 (58),
			ce-J2 (59),
			svr2 (60),
			notInstalled (99)
                }
        ACCESS  read-only
        STATUS  mandatory
        DESCRIPTION
                "PMD layer/physical layer format of the line card.
		Above stated [oc3c], [oc12c] are ATM Form conformed names.
		They are corresponding to the ITU-T conformed names as follows:
		oc3c - STM1
		oc12 - STM4
		sts3c - STM1"
	--	回線カードのPMDレイヤおよび物理レイヤフォーマット.
	--	上記は,[oc3c],[oc12c]はATM Form準拠の名称である.
	--	ITUーT準拠の場合は以下のように対応する.
	--	oc3c - STM1
	--	oc12 - STM4
	--	sts3c - STM1
        ::= { slotIfConfEntry 2 }

slotIfConfRev OBJECT-TYPE
        SYNTAX  DisplayString
        ACCESS  read-only
        STATUS  mandatory
        DESCRIPTION
                "The revision of the line cards.
		JpnToEng[パッケージ未実装時は,0 length.]"
	--	回線パッケージのリビジョン
	--	パッケージ未実装時は,0 length.
        ::= { slotIfConfEntry 3 }

slotIfConfStatus OBJECT-TYPE
        SYNTAX  INTEGER {
                        other (1),
                        inService (2),
                        outOfService (3),
                        testing (4),
                        initializing (5),
                        installing (6),
                        notInstalled (99)
                }
        ACCESS  read-only
        STATUS  mandatory
        DESCRIPTION
                "Operational status of the line cards."
	--	回線パッケージの運転状態
        ::= { slotIfConfEntry 4 }

slotIfConfBufferType OBJECT-TYPE
        SYNTAX  INTEGER {
			other (1),
			ph1-buffer (2),
			ph2-buffer (3),
			fr-buffer (4),
			fr-buffer2 (5),
			notInstalled (99)
                }
        ACCESS  read-only
        STATUS  mandatory
        DESCRIPTION
                "The Buffer ID of the line cards."
	--	回線カードのBuffer ID
        ::= { slotIfConfEntry 5 }

slotIfConfBufferRev OBJECT-TYPE
        SYNTAX  DisplayString
        ACCESS  read-only
        STATUS  mandatory
        DESCRIPTION
                "The revision of the line card's buffers.
		JpnToEng[パッケージ未実装時は,0 length.]"
	--	回線パッケージのBufferのリビジョン.
	--	パッケージ未実装時は,0 length.
        ::= { slotIfConfEntry 6 }

slotIfConfReset OBJECT-TYPE
	SYNTAX  INTEGER {
			noOperation(1),	-- None
			reset(2),	-- Reset order
			notInstalled(99)
		}
	ACCESS  read-write
	STATUS  mandatory
	DESCRIPTION
		"Line card reset.
		The result of the reset order is indicated in
		slotIfConfResetResult.
		JpnToEng[PKG未実装時以外の読み込み時の値は,いつも
		noOperation(1)である.]"
	--	回線パッケージのリセット.
	--	リセット指示結果は slotIfConfResetResult で表す.
	--	PKG未実装時以外の読み込み時の値は,いつもnoOperation(1)である.
	::= { slotIfConfEntry 7 }

slotIfConfResetResult OBJECT-TYPE
	SYNTAX  INTEGER {
			succeed(1),	-- Normal end (initial value).
			other(2),	-- NG other than below stated values.
			diagnostics (3),	-- Diagnostic test in progress.
			unchangeableSlaveLine (4),	-- Slave line cannot
							-- be switched.
			notInstalled(99)
		}
	ACCESS  read-only
	STATUS  mandatory
	DESCRIPTION
		"The current result of the reset order by slotIfConfReset."
	--	 slotIfConfReset によるリセット指示の最新結果.
	::= { slotIfConfEntry 8 }

--	The Linf Group

LinfFilterMaskVpi	::= INTEGER (-1|0..12)
	--	Filter mask VPI.
	--	JpnToEng[実装bufferにより無効な場合は -1.]
	--	実装bufferにより無効な場合は -1.

LinfFilterMaskVci	::= INTEGER (-1|0..14)
	--	Filter mask VCI.
	--	JpnToEng[実装bufferにより無効な場合は -1.]
	--	実装bufferにより無効な場合は -1.

LinfCellMappingMode	::= INTEGER { direct(1), plcp(2) }
	--	Cell mapping mode.

LinfScramble		::= INTEGER { on(1), off(2) }
	--	Scramble.

LinfLBO			::= INTEGER {
					low(1),
					hi(2),
					length-0-110(3),
					length-110-220(4),
					length-220-330(5),
					length-330-440(6),
					length-440-550(7),
					length-550-660(8),
					length-over660(9)
				}
	--	Line Build Out.

LinfFrameMode		::= INTEGER {
					c-bit(1),
					m23(2),
					g832-g804(3),
					g751(4),
					m13(5),
					esf(6),
					sf(7)
				}
	--	Frame mode.

LinfMinVci		::= INTEGER (0..16383)
	--	JpnToEng[使用可能な最小VCI.]
	--	使用可能な最小VCI.

LinfMaxVci		::= INTEGER (0..16383)
	--	JpnToEng[使用可能な最大VCI.]
	--	使用可能な最大VCI.

LinfService		::= INTEGER { unstructured(1), structured(2) }
	--	Service.

LinfInterWorking	::= INTEGER { network(1), service(2) }
	--	Type of Interworking.

LinfVendor		::= INTEGER {
					notApplicable(1),
					stratacom(2),
					digital-equipment(3),
					northan-telecom(4),
					cisco-systems(5)
				}
	--	JpnToEng[4社スペック個別仕様.
	--	linfRecommendation が fourVendor 以外のとき無効.]
	--	4社スペック個別仕様.
	--	linfRecommendation が fourVendor 以外のとき無効.

LinfFractionalType	::= INTEGER { unstructured(1), fractional(2) }
	--	Fractional type.
	--	JpnToEng[fr-ds1の場合, unstructured は Unchannelizedの意味.]
	--	fr-ds1の場合, unstructured は Unchannelizedの意味.

LinfFractionalSet	::= INTEGER
	--	JpnToEng(次行から6行分)
	--	帯域設定(設定する fractional 番号)
	--	32ビットコードの最下位ビットが, fractional 番号 0 を表し,
	--	設定する fractional 番号に対応するビットをセットする.
	--	例えば, fractional 番号 1, 10, 31 を設定した場合は,
	--	10000000000000000000010000000010 (=2147484674=2^31+2^10+2^1)
	--	LinfFractionalType が unstructured(1) の場合は,無効(0xfffffffe).

LinfCasMode		::= INTEGER { notApplicable(1), basic(2), cas(3) }
	--	This parameter selects which AAL1 Format shoud be used.
	--	Basic dose not carry CAS bits, and use a single 125 usec frame.
	--	cas(3) carry CAS bits in a multiframe structure for E1,
	--	DS1 SF and DS1 ESF respoectively.
	--	This applies to structured interface only.
	--	Default is basic(2).
	--	CAS( Channel Assosiated Signaling )モード
	--	CE-DS1, CE-E1のLinfServiceがstructured(2)のときのみ有効。
	--	Defaultは、notApplicable(1)( Defaultがunstructured(1)の為.)

LinfCodingMode		::= INTEGER { hdb3(1), ami(2) }
	--	JpnToEng[物理レベルの符号化方式.]
	--	物理レベルの符号化方式.

LinfUnUsedParam	::= INTEGER { unused(-1) }
	--	Unused parameter.
	--	使用しないパラメータ

	--	JpnToEng(次行から2行分)
	--	linfPhysType の値によって linfParam1~7 の意味は
	--	次のとおり異なる.

	--	For fr-e1, fr-ds1
	--	Param1	LinfMinVci
	--	Param2	LinfMaxVci
	--	Param3	LinfInterWorking
	--	Param4	LinfVendor
	--	Param5	LinfFractionalType
	--	Param6	LinfFractionalSet
	--	Param7	LinfLBO		JpnToEng[fr-ds1 以外はLinfUnUsedParam]

	--	For ce-e1, ce-ds1, ce-ds3, ce-J2
	--	Param1	LinfMinVci
	--	Param2	LinfMaxVci
	--	Param3	LinfService
	--	Param4	LinfLBO		JpnToEng[ce-ds1, ce-ds3 以外は LinfUnUsedParam]
	--	Param5	LinfFrameMode	JpnToEng[ce-ds1, ce-ds3 以外はLinfUnUsedParam]
	--	Param6	LinfCasMode	JpnToEng[ce-ds1, ce-e1 以外はLinfUnUsedParam]
	--	Param7	LinfCodingMode	JpnToEng[ce-e1 以外はLinfUnUsedParam]

	--	For e1, e3, ds1, ds3
	--	Param1	LinfFilterMaskVpi
	--	Param2	LinfFilterMaskVci
	--	Param3	LinfCellMappingMode
	--	Param4	LinfScramble
	--	Param5	LinfLBO		JpnToEng[ds1, ds3 以外は LinfUnUsedParam]
	--	Param6	LinfFrameMode	JpnToEng[e3, ds3 以外はLinfUnUsedParam]
	--	Param7	LinfUnUsedParam

	--	For JpnToEng[パッケージ未実装]
	--	Param1	LinfUnUsedParam
	--	Param2	LinfUnUsedParam
	--	Param3	LinfUnUsedParam
	--	Param4	LinfUnUsedParam
	--	Param5	LinfUnUsedParam
	--	Param6	LinfUnUsedParam
	--	Param7	LinfUnUsedParam

	--	For JpnToEng[上記以外]
	--	Param1	LinfFilterMaskVpi
	--	Param2	LinfFilterMaskVci
	--	Param3	LinfUnUsedParam
	--	Param4	LinfUnUsedParam
	--	Param5	LinfUnUsedParam
	--	Param6	LinfUnUsedParam
	--	Param7	LinfUnUsedParam

linfStatusTable OBJECT-TYPE
	SYNTAX	SEQUENCE OF LinfStatusEntry
	ACCESS	not-accessible
	STATUS	mandatory
	DESCRIPTION
		"Table related to the ATM specific lines which could not be
		defined by MIB-II.
		The table includes the configuration information,
		operational status and error types of lines."
	--	MIB-IIにて定義できなかった回線に関するテーブル.
	--	構成情報,運用状態,回線のエラー種別等を含む.
	::= { linf 1 }

linfStatusEntry OBJECT-TYPE
	SYNTAX	LinfStatusEntry
	ACCESS	not-accessible
	STATUS	mandatory
	DESCRIPTION
		"Entry of the line interface status indication."
	--	回線インタフェース状態表示のエントリ
	INDEX	{ linfIndex }
	::= { linfStatusTable 1 }

LinfStatusEntry ::=
	SEQUENCE {
		linfIndex
			INTEGER ,
		linfStatus
			INTEGER,
		linfLoopBack
			INTEGER,
		linfConf
			INTEGER,
		linfFwdAvailableBandWidth
			INTEGER,
		linfBkwdAvailableBandWidth
			INTEGER,
                linfJ2Rate
                        INTEGER,
                linfCacFactor
                        INTEGER,
                linfLoopBackCause
                        INTEGER,
		linfBandWidth
                        INTEGER,
		linfRecommendation
			INTEGER,
		linfUnassignedIdle
			INTEGER,
		linfMaxActiveVpiBits
			INTEGER,
		linfMaxActiveVciBits
			INTEGER,
		linfPhysType
			INTEGER,
		linfParam1
			INTEGER,
		linfParam2
			INTEGER,
		linfParam3
			INTEGER,
		linfParam4
			INTEGER,
		linfParam5
			INTEGER,
		linfParam6
			INTEGER,
		linfParam7
			INTEGER
	}

linfIndex OBJECT-TYPE
	SYNTAX	INTEGER(1..64)
	ACCESS	read-only
	STATUS	mandatory
	DESCRIPTION
		"Index of the line interface status indication"
	--	回線インタフェース状態表示のインデックス.
	::= { linfStatusEntry 1 }

linfStatus OBJECT-TYPE
	SYNTAX	INTEGER {
			normal (1),
			los (2),
			lof (3),
			loc (4),
			ais-path (5),
			ais-section (6),
			yellow-section (7),
			yellow-path (8),
			lop (9),
			ais (10),
			payload-all-one (11),
			rai (12),
			oof (13) ,
			idle (14),
			rdi (15),
			plcp-oof (16),
			plcp-lof (17),
			plcp-yellow (18),
			red(19),
			loss-of-64K-clock(80),
			loss-of-8K-clock(81),
			frequency-out-of-range(82),
			failure(97),
			administratively-down (98),
			notInstalled (99)
		}
	ACCESS	read-only
	STATUS	mandatory
	DESCRIPTION
		"Status of the line interface or the receive clock"
	--	回線インタフェースの状態または受信クロック状態
	::= { linfStatusEntry 2 }

linfLoopBack OBJECT-TYPE
	SYNTAX	INTEGER {
			others (1),	-- not used
			normal (2),
			localLoopBack (3),
			remoteLoopBack (4),
			notInstalled (99)
		}
	ACCESS	read-write
	STATUS	mandatory
	DESCRIPTION
		"Loop back status"
	--	ループバック状態
	::= { linfStatusEntry 3 }

linfConf OBJECT-TYPE
	SYNTAX	INTEGER {
			others (1),
			private-UNI (2),
			private-NNI (3),
			public-UNI  (4),
--			gate-NNI    (5),
--		Only interface customized version is used.
--		Line interface type Add gate_NNI so that SW would be
--		considered as Gateway in the customized configuration.
--		カスタマイズの構成としてSWをGatewayとして意識させる為に
--		gate_NNI を追加
			uni	    (6),
			nni	    (7),
			notInstalled (99)
		}
	ACCESS	read-only
	STATUS	mandatory
	DESCRIPTION
		"Line card type."
	--	回線インタフェースの種別.
	::= {  linfStatusEntry  4 }

linfFwdAvailableBandWidth OBJECT-TYPE
	SYNTAX	INTEGER
	ACCESS	read-only
	STATUS	mandatory
	DESCRIPTION
		"Forward Available BandWidth(Mbps).
		JpnToEng[PKG未実装時は,0]"
	--	Forwardの残帯域 (Mbps).
	--	PKG未実装時は,0.
	::= {  linfStatusEntry  5 }

linfBkwdAvailableBandWidth OBJECT-TYPE
	SYNTAX	INTEGER
	ACCESS	read-only
	STATUS	mandatory
	DESCRIPTION
		"Backward Available BandWidth(Mbps).
		JpnToEng[PKG未実装時は,0]"
	--	Backwardの残帯域(Mbps).
	--	PKG未実装時は,0.
	::= {  linfStatusEntry  6 }

linfJ2Rate OBJECT-TYPE
	SYNTAX	INTEGER {
			not-leased-line (1),
			type-3-Mbps (2),
			type-4point5-Mbps (3),
			type-6point3-Mbps (4),
			notInstalled (99)
		}
	ACCESS	not-accessible
	STATUS	mandatory
	DESCRIPTION
		"Indicate the line rate of the J2-dedicated line service."
	--	J2専用線サービスの回線速度を示す.
	::= { linfStatusEntry  7 }

linfCacFactor OBJECT-TYPE
	SYNTAX  INTEGER(0|10..1000)
	ACCESS  read-write
	STATUS  mandatory
	DESCRIPTION
		"JpnToEng(次行から7行分)"
	--	CAC Overbooking機能を実現するため,回線の仮想的な
	--	使用可能帯域を求めるために使用するFactor(係数).
	--	但し,トンネリングが登録されている場合,この係数は
	--	トンネリング登録VPIに対しては適用されない.
	--	0は未設定を意味する.
	--	設定時にパスが存在すると設定NGになる.
	--	PKG未実装時は,0.
	::= { linfStatusEntry 8 }

linfLoopBackCause OBJECT-TYPE
	SYNTAX  INTEGER {
			succeed (1),
			diagnosis (2),          -- Diagnostic test in progress.
			failure (3),            -- JpnToEng[設定不可能な装置状態]
			notSupportedByPkg (4),  -- JpnToEng[機能未サポートパッケージ]
			alreadyRegistered (5),  -- JpnToEng[登録済み]
			adminDown (6),          -- admin down
			initializing (7),        -- JpnToEng[初期化中]
			notInstalled (99)
		}
	ACCESS  read-only
	STATUS  mandatory
	DESCRIPTION
		"JpnToEng[物理ループバックの設定結果.]"
	--	物理ループバックの設定結果.
	::= { linfStatusEntry 9 }

linfBandWidth OBJECT-TYPE
	SYNTAX	INTEGER
	ACCESS	read-only
	STATUS	mandatory
	DESCRIPTION
		"BandWidth[cell/s].JpnToEng[無効またはPKG未実装時は値 0.]"
	--	帯域[cell/s]. 無効またはPKG未実装時は値 0.
	::= {  linfStatusEntry  10 }

linfRecommendation	OBJECT-TYPE
	SYNTAX	INTEGER {
			other (1),
			atmForum (2),
			itu (3),
			ttc (4),
			frameRelayForum (5),
			itu-t (6),
			ansi (7),
			fourVendor (8),
			notInstalled (99)
		}
	ACCESS	read-only
	STATUS	mandatory
	DESCRIPTION
	 	"JpnToEng[対応勧告]"
	 --	対応勧告
	::= { linfStatusEntry 11 }

linfUnassignedIdle	OBJECT-TYPE
	SYNTAX	INTEGER {
			notApplicable (1),
			unAssigned (2),
			idle (3),
			notInstalled (99)
		}
	ACCESS	read-only
	STATUS	mandatory
	DESCRIPTION
		"Unassigned/Idle"
	::= { linfStatusEntry 12 }

linfMaxActiveVpiBits	OBJECT-TYPE
	SYNTAX	INTEGER (0..12)
	ACCESS	read-only
	STATUS	mandatory
	DESCRIPTION
	 	"The length of valid VPI bits.JpnToEng[PKG未実装時は0.]"
	--	VPI有効Bit長.PKG未実装時は0.
	::= { linfStatusEntry 13 }

linfMaxActiveVciBits	OBJECT-TYPE
	SYNTAX	INTEGER (0..14)
	ACCESS	read-only
	STATUS	mandatory
	DESCRIPTION
	 	"The length of valid VCI bits.JpnToEng[PKG未実装時は0.]"
	--	VCI有効Bit長.PKG未実装時は0.
	::= { linfStatusEntry 14 }

linfPhysType	OBJECT-TYPE
	SYNTAX	INTEGER
	ACCESS	read-only
	STATUS	mandatory
	DESCRIPTION
		"JpnToEng[この回線が属するスロットの slotIfConfPhysType 値]"
	--	この回線が属するスロットの slotIfConfPhysType 値.
	::= { linfStatusEntry 15 }

linfParam1		OBJECT-TYPE
	SYNTAX	INTEGER
	ACCESS	read-only
	STATUS	mandatory
	DESCRIPTION
		"JpnToEng(次の２行分)"
	--	回線のコンフィグレーション.
	--	linfPhysType の値によって意味が異なる.
	::= { linfStatusEntry 16 }

linfParam2		OBJECT-TYPE
	SYNTAX	INTEGER
	ACCESS	read-only
	STATUS	mandatory
	DESCRIPTION
		"JpnToEng(次の２行分)"
	--	回線のコンフィグレーション.
	--	linfPhysType の値によって意味が異なる.
	::= { linfStatusEntry 17 }

linfParam3		OBJECT-TYPE
	SYNTAX	INTEGER
	ACCESS	read-only
	STATUS	mandatory
	DESCRIPTION
		"JpnToEng(次の２行分)"
	--	回線のコンフィグレーション.
	--	linfPhysType の値によって意味が異なる.
	::= { linfStatusEntry 18 }

linfParam4		OBJECT-TYPE
	SYNTAX	INTEGER
	ACCESS	read-only
	STATUS	mandatory
	DESCRIPTION
		"JpnToEng(次の２行分)"
	--	回線のコンフィグレーション.
	--	linfPhysType の値によって意味が異なる.
	::= { linfStatusEntry 19 }

linfParam5		OBJECT-TYPE
	SYNTAX	INTEGER
	ACCESS	read-only
	STATUS	mandatory
	DESCRIPTION
		"JpnToEng(次の２行分)"
	--	回線のコンフィグレーション.
	--	linfPhysType の値によって意味が異なる.
	::= { linfStatusEntry 20 }

linfParam6		OBJECT-TYPE
	SYNTAX	INTEGER
	ACCESS	read-only
	STATUS	mandatory
	DESCRIPTION
		"JpnToEng(次の２行分)"
	--	回線のコンフィグレーション.
	--	linfPhysType の値によって意味が異なる.
	::= { linfStatusEntry 21 }

linfParam7		OBJECT-TYPE
	SYNTAX	INTEGER
	ACCESS	read-only
	STATUS	mandatory
	DESCRIPTION
		"JpnToEng(次の２行分)"
	--	回線のコンフィグレーション.
	--	linfPhysType の値によって意味が異なる.
	::= { linfStatusEntry 22 }

linfFifoConfTable OBJECT-TYPE
        SYNTAX  SEQUENCE OF LinfFifoConfEntry
        ACCESS  not-accessible
        STATUS  mandatory
        DESCRIPTION
                "Indicate status of FIFO on the shaper-line card.
 	         	* JpnToEng[SCR, MBSを省略したときはCBRとみなし,
			 PCRだけを元にシェーピングレートの設定を行なう.]

                  	* Relationship between PCR, SCR and MBS value.
				PCR >= SCR
				PCR >= MBS "
	--	シェーパカードのFIFOの状態を示す.
	--
	--		* SCR, MBSを省略したときはCBRとみなし,
	--			PCRだけを元にシェーピングレートの設定を行なう.
	--
	--
	--		* PCR, SCR, MBSの値の関係
	--			PCR >= SCR
	--			PCR >= MBS
        ::= { linf 2 }

linfFifoConfEntry OBJECT-TYPE
        SYNTAX  LinfFifoConfEntry
        ACCESS  not-accessible
        STATUS  mandatory
        DESCRIPTION
                "Entry of FIFO status indication "
	--	FIFO状態表示のエントリ
        INDEX   { linfFifoConfifIndex , linfFifoConfIndex }
        ::= { linfFifoConfTable 1 }

LinfFifoConfEntry ::=
        SEQUENCE {
                linfFifoConfifIndex
                        INTEGER ,
                linfFifoConfIndex
                        INTEGER ,
                linfFifoConfStatus
                        INTEGER,
                linfFifoConfPeekRate
                        INTEGER,
                linfFifoConfSustainRate
                        INTEGER,
                linfFifoConfMaxBurstSize
                        INTEGER,
		linfFifoConfRowStatus
			INTEGER
        }

linfFifoConfifIndex OBJECT-TYPE
        SYNTAX  INTEGER
        ACCESS  not-accessible
        STATUS  mandatory
        DESCRIPTION
                " Line Interface Index "
	--	回線インタフェースインデックス
        ::= { linfFifoConfEntry 1 }

linfFifoConfIndex OBJECT-TYPE
        SYNTAX  INTEGER
        ACCESS  not-accessible
        STATUS  mandatory
        DESCRIPTION
                " Index of FIFO "
	--	FIFOのインデックス
        ::= { linfFifoConfEntry 2 }

linfFifoConfStatus OBJECT-TYPE
        SYNTAX  INTEGER {
                        normal (1),
                        overflow (2)
                }
        ACCESS  not-accessible
        STATUS  mandatory
        DESCRIPTION
                " Status of FIFO "
	--	FIFOの状態
        ::= { linfFifoConfEntry 3 }

linfFifoConfPeekRate OBJECT-TYPE
        SYNTAX  INTEGER (1..1412830)
        ACCESS  not-accessible
        STATUS  mandatory
        DESCRIPTION
                "Peak Cell rate (PCR) for shaper-line card."
	--	シェーパーカードのピークセルレート(PCR).
        ::= { linfFifoConfEntry 4 }

linfFifoConfSustainRate OBJECT-TYPE
        SYNTAX  INTEGER (1..1412830)
        ACCESS  not-accessible
        STATUS  mandatory
        DESCRIPTION
              " Sustainable Cell Rate ( SCR)  for shaper-line card."
	--	シェーパーカードの平均セルレート(SCR).
        ::= { linfFifoConfEntry 5 }

linfFifoConfMaxBurstSize OBJECT-TYPE
        SYNTAX  INTEGER (1..1412830)
        ACCESS  not-accessible
        STATUS  mandatory
        DESCRIPTION
              "Maximum Burst Size (MBS) for the shaper-line card."
	--	シェーパーカードの最大バーストサイズ(MBS).
        ::= { linfFifoConfEntry 6 }

linfFifoConfRowStatus OBJECT-TYPE
        SYNTAX  INTEGER {
                        active(1),
                        notInService(2),
                        notReady(3),
                        createAndGo(4),         -- notSupported
                        createAndWait(5),
                        destroy(6)
                }
        ACCESS  not-accessible
        STATUS  mandatory
        DESCRIPTION
            " This object is used to designate the setting method for
		the shaping rate from the manager.
		Also, this object returns the reply to the shaping rate
		setting request from the agent side.

                           - 'active', which indicates that the
                           conceptual row is available for use by the
                           managed device;

                           - 'notInService', which indicates that the
                           conceptual row exists in the agent, but is
                           unavailable for use by the managed device;

                           - 'notReady', which indicates that the
                           conceptual row exists in the agent, but is
                           missing information necessary in order to be
                           available for use by the managed device;

                           - 'createAndGo', which is supplied by a
                           management station wishing to create a new
                           instance of a conceptual row and to have it
                           available for use by the managed device;

                           - 'createAndWait', which is supplied by a
                           management station wishing to create a new
                           instance of a conceptual row but not to have
                           it available for use by the managed device;
                           and,

                           - 'destroy', which is supplied by a
                           management station wishing to delete all of
                           the instances associated with an existing
                           conceptual row.
			"
	--	マネージャからはshapingレートの設定方法指定のために
	--	用いられる.またエージェント側からはshapingレートの設定要求
	--	に対する結果を返す.
        ::= { linfFifoConfEntry 7 }

--	The Conn (Connection & Traffic for accounting) Group

--	connPvc			OBJECT IDENTIFIER ::= { conn  1 }
--	connConf		OBJECT IDENTIFIER ::= { conn  2 }
--	connRoute		OBJECT IDENTIFIER ::= { conn  3 }
--	connSoftPvcIndexNext	OBJECT IDENTIFIER ::= { conn  4 }
--	connSoftPvcTable	OBJECT IDENTIFIER ::= { conn  5 }
--	connSoftPvcEstablishedSrcInfTable
--				OBJECT IDENTIFIER ::= { conn  6 }
--	connOam			OBJECT IDENTIFIER ::= { conn  7 }
--	connLoop		OBJECT IDENTIFIER ::= { conn  8 }
--	connProfile		OBJECT IDENTIFIER ::= { conn  9 }
--	connSvcTable		OBJECT IDENTIFIER ::= { conn 10 }
--	connCe			OBJECT IDENTIFIER ::= { conn 11 }
--	connFr			OBJECT IDENTIFIER ::= { conn 12 }


connPvc		OBJECT IDENTIFIER ::= { conn 1 }

connPvcOpe	OBJECT IDENTIFIER ::= { connPvc 1 }

	--	JpnToEng(次の５行分)
	--	connPvcOpeLowVpi, connPvcOpeLowVci,
	--	connPvcOpeHighVpi, connPvcOpeHighVci に -1 を指定した場合は,
	--	agent側で 空きVPI,VCI を選択し, PVCを設定する.
	--	PVC設定成功の場合は,これらのオブジェクト値は選択された
	--	VPI,VCIに更新される.

connPvcOpeLowPort	OBJECT-TYPE
	SYNTAX	INTEGER (1..65|-1)	-- default value is -1.
	ACCESS	read-write
	STATUS	mandatory
	DESCRIPTION
		"Low-side line port number. "
	--	Low側回線ポート番号.
	::= { connPvcOpe 1 }

connPvcOpeLowVpi	OBJECT-TYPE
	SYNTAX	INTEGER (0..16383|-1)	-- default value is -1.
	ACCESS	read-write
	STATUS	mandatory
	DESCRIPTION
		" Low-side VPI number."
	--	Low側VPI番号.
	::= { connPvcOpe 2 }

connPvcOpeLowVci	OBJECT-TYPE
	SYNTAX	INTEGER (0..16383|-1)	-- default value is -1.
	ACCESS	read-write
	STATUS	mandatory
	DESCRIPTION
		" Low-side VCI number."
	--	Low側VCI番号.
	::= { connPvcOpe 3 }

connPvcOpeHighPort	OBJECT-TYPE
	SYNTAX	INTEGER (1..65|-1)	-- default value is -1.
	ACCESS	read-write
	STATUS	mandatory
	DESCRIPTION
		" High-side line port number."
	--	High側回線のポート番号.
	::= { connPvcOpe 4 }

connPvcOpeHighVpi	OBJECT-TYPE
	SYNTAX	INTEGER (0..16383|-1)	-- default value is -1.
	ACCESS	read-write
	STATUS	mandatory
	DESCRIPTION
		" High-side VPI number."
	--	High側のVPI番号.
	::= { connPvcOpe 5 }

connPvcOpeHighVci	OBJECT-TYPE
	SYNTAX	INTEGER (0..16383|-1)	-- default value is -1.
	ACCESS	read-write
	STATUS	mandatory
	DESCRIPTION
		" High-side VCI number."
	--	High側のVCI番号.
	::= { connPvcOpe 6 }

connPvcOpeTopology	OBJECT-TYPE
	SYNTAX	INTEGER {
			uni-directional-VCC (1),	-- default value
			bi-directional-VCC  (2),
			uni-directional-VPC (3),
			bi-directional-VPC  (4),
			broadcast-VPC       (5),
			broadcast-VCC       (6)
		}
	ACCESS  read-write
	STATUS  mandatory
	DESCRIPTION
		"Topology of the Connection."
	--	コネクション形態.
	::= { connPvcOpe 7 }

connPvcOpeTrafficType OBJECT-TYPE
	SYNTAX  INTEGER {
		traffic-CBR (1),
		traffic-rt-VBR (2),
		traffic-nrt-VBR (3),
		traffic-ABR (4),
		traffic-UBR (5)		-- default value
	}
	ACCESS  read-write
	STATUS  mandatory
	DESCRIPTION
		"Traffic Type."
	--	トラヒックタイプ.
	::= { connPvcOpe 8 }

connPvcOpeStatus OBJECT-TYPE
	SYNTAX	INTEGER {
			allocate(1),	-- JpnToEng[managerにPVC操作の権利を
					-- 与える.]
			establish(2),	-- JpnToEng[point-to-point,
					-- point-to-multi PVCの設定指示.]
			add(3),		-- JpnToEng[multicastコネクションに
					-- 対してのPVCエンドポイント追加指示.]
			delete(4),	-- JpnToEng[point-to-point,
					-- point-to-multi PVCのルート削除指示.]
			remove(5),	-- JpnToEng[multicastコネクションに
					-- 対してのPVCエンドポイント削除指示.]
			free(6)		-- JpnToEng[managerからPVC操作の権利
					-- を解放.]
					-- default value

		}
	ACCESS	read-write
	STATUS	mandatory
	DESCRIPTION
		"JpnToEng[PVC設定/削除の制御を行なう.]"
	--	PVC設定/削除の制御を行なう.
	::= { connPvcOpe 9 }

connPvcOpeCause OBJECT-TYPE
	SYNTAX	INTEGER {
			rowExisting(1),		-- default value
			allocateSucceed(2),
			vpivciLowBusy(3),
			vpivciHighBusy(4),
			vpivciOutOfRange(5),
			rateLowOverFlow(6),
			rateHighOverFlow(7),
			broadcastTableFull(8),
			inconsistentVPVC(9),
			lineDiagnosis(10),
			missMatchTrfType(11),
			illegalLowFileName(12),
			illegalHighFileName(13),
			illegalLowShaper(14),
			illegalHighShaper(15),
			illegalOperation(16),
			parameterIsNotEnough(17),
			diagnostics(18),
			otherFailure(19),
 			illegalLowRateForUPC(20),
 			illegalHighRateForUPC(21),
			noSpecifiedConnection(22),
			noCevc(23),
			noDlci(24),
			illegalTopology(25),
			noLowShaperForGateway(26),
			noHighShaperForGateway(27),
			noPvcLowShaperForGateway(28),
			noPvcHighShaperForGateway(29),
			missMatchTrfTypeLowShaperForGateway(30),
			missMatchTrfTypeHighShaperForGateway(31),
			leafSetAnotherLine(32),
			insusfficientPCRofProfile(33)
		}
	ACCESS	read-only
	STATUS	mandatory
	DESCRIPTION
		"The result of the connection operation."
	--	コネクション操作の結果を表示するためのオブジェクト.
	::= { connPvcOpe 10 }

connPvcOpeLowFifoIndex		OBJECT-TYPE
	SYNTAX	INTEGER (0..16)		-- default value is 0.
	ACCESS	read-write
	STATUS	mandatory
	DESCRIPTION
		"Shaper number of Forward.
		If shaping is not performed, designate 0."
	--	ForwardのShaper番号.
	--	shapingしないときは,０指定.
        ::= { connPvcOpe 11 }

connPvcOpeHighFifoIndex		OBJECT-TYPE
	SYNTAX	INTEGER (0..16)		-- default value is 0.
	ACCESS	read-write
	STATUS	mandatory
	DESCRIPTION
		"Shaper number of Backward.
		If shaping is not performed, designate 0."
	--	BackwardのShaper番号.
	--	shapingしないときは,０指定.
        ::= { connPvcOpe 12 }

connPvcOpeLowParam1	OBJECT-TYPE
	SYNTAX	INTEGER {
			off(1),		-- default value
			mode1(2),
			mode2(3),
			mode3(4),
			mode4(5),
			mode5(6)
	}
	ACCESS	read-write
	STATUS	mandatory
	DESCRIPTION
		"UPC mode of Forward."
	--	ForwardのUPCモード
	::= { connPvcOpe 13 }

connPvcOpeHighParam1	OBJECT-TYPE
	SYNTAX	INTEGER {
			off(1),		-- default value
			mode1(2),
			mode2(3),
			mode3(4),
			mode4(5),
			mode5(6)
	}
	ACCESS	read-write
	STATUS	mandatory
	DESCRIPTION
		"UPC mode of Backward."
	--	BackwardのUPCモード
	::= { connPvcOpe 14 }

--	connPvcOpeLowParam1/connPvcOpeHighParam1
--	If ABR is designated, only off/mode1 can be designated.
--	If UBR is designated, only mode1/mode5/off can be designated.
--	If nrt-VBR is designated, only mode2/mode3/mode4/off can
--	be designated.
--	If rt-VBR is designated, only mode2/mode3/mode4/off can
--	be designated.
--	If CBR is designated, only mode1/off can be designated.
--	 制限事項
--	 ABR     指定時 は off/mode1
--	 UBR     指定時 は mode1/mode5/off
--	 nrt-VBR 指定時 は mode2/mode3/mode4/off
--	 rt-VBR  指定時 は mode2/mode3/mode4/off
--	 CBR     指定時 は mode1/off
--	 しか指定できない.

connPvcOpeLowParam2	OBJECT-TYPE
	SYNTAX	DisplayString (SIZE(1..10|0))	-- default value is size(0).
	ACCESS	read-write
	STATUS	mandatory
	DESCRIPTION
		"Profile name of Forward.
		If nothing is designated, the string of size(0) is designated."
	--	Forwardのプロファイル名
	--	指定しない場合はsize 0の文字列を設定する.
	::= { connPvcOpe 15 }

connPvcOpeHighParam2	OBJECT-TYPE
	SYNTAX	DisplayString (SIZE(1..10|0))	-- default value is size(0).
	ACCESS	read-write
	STATUS	mandatory
	DESCRIPTION
		"Profile name of Backward.
		If nothing is designated, the string of size(0) is designated."
	--	Backwardのプロファイル名
	--	指定しない場合はsize 0の文字列を設定する.
	::= { connPvcOpe 16 }

connPvcTable	OBJECT-TYPE
	SYNTAX	SEQUENCE OF ConnPvcEntry
	ACCESS	not-accessible
	STATUS	mandatory
	DESCRIPTION
		"JpnToEng(次の４行分を)"
	--	本装置に設定される PVC の情報を表すテーブル.
	--	PVCのエンドポイント毎に１つのエントリーを持つ.
	--	ただし,multicastの入り側は,そのleaf数だけの
	--	エントリーが存在し,connPvcIndexにより区別される.
	::= { connPvc 2 }

connPvcEntry	OBJECT-TYPE
	SYNTAX	ConnPvcEntry
	ACCESS	not-accessible
	STATUS	mandatory
	DESCRIPTION
		"Entry of connPvcTable.
		e.g.
		receive +----------------------------------+transmit
		=======>|   ---- uni-directional-VCC ----  |=======>
		(1/0/32)|                                  |(2/0/32)
		=======>|   ---- bi-directional-VCC  ----  |=======>
		(1/0/33)|                                  |(2/0/33)
		=======>|   ---- broadcast - VCC ---+----  |=======>
		(1/0/34)|                           |      |(2/0/34)
		        |                           +----  |=======>
		        |                                  |(3/0/34)
		        +----------------------------------+
		                                            (line/vpi/vci)
		 connPvcContrastPort.1.0.32.1.1=2
		 connPvcContrastPort.2.0.32.2.1=1
		 connPvcContrastPort.1.0.33.3.1=2
		 connPvcContrastPort.2.0.33.3.1=1
		 connPvcContrastPort.1.0.34.5.1=2
		 connPvcContrastPort.1.0.34.5.2=3
		 connPvcContrastPort.2.0.34.4.1=1
		 connPvcContrastPort.3.0.34.4.1=1"
	INDEX{ connPvcPort, connPvcVpi, connPvcVci, connPvcDirection, connPvcIndex }
	::=	{ connPvcTable 1 }

ConnPvcEntry ::=
	SEQUENCE	{
		connPvcPort
			INTEGER,
		connPvcVpi
			INTEGER,
		connPvcVci
			INTEGER,
		connPvcDirection
			INTEGER,
		connPvcIndex
			INTEGER,
		connPvcContrastPort
			INTEGER,
		connPvcContrastVpi
			INTEGER,
		connPvcContrastVci
			INTEGER,
		connPvcTopology
			INTEGER,
		connPvcTrafficType
			INTEGER,
		connPvcFifoIndex
			INTEGER,
		connPvcContrastFifoIndex
			INTEGER,
		connPvcTrfConf
			INTEGER,
		connPvcTrfResult
			INTEGER,
		connPvcParam1
			INTEGER,
		connPvcContrastParam1
			INTEGER,
		connPvcParam2
			DisplayString,
		connPvcContrastParam2
			DisplayString,
		connPvcParam3
			INTEGER,
		connPvcContrastParam3
			INTEGER,
		connPvcParam4
			INTEGER,
		connPvcContrastParam4
			INTEGER,
		connPvcParam5
			INTEGER,
		connPvcContrastParam5
			INTEGER,
		connPvcParam6
			INTEGER,
		connPvcContrastParam6
			INTEGER,
		connPvcParam7
			INTEGER,
		connPvcContrastParam7
			INTEGER
	}

connPvcPort	OBJECT-TYPE
	SYNTAX	INTEGER
	ACCESS	not-accessible
	STATUS	mandatory
	DESCRIPTION
		"Line port number"
	--	回線番号
	::= { connPvcEntry 1 }

connPvcVpi	OBJECT-TYPE
	SYNTAX	INTEGER
	ACCESS	not-accessible
	STATUS	mandatory
	DESCRIPTION
		"VPI number"
	--	VPI番号
	::= { connPvcEntry 2 }

connPvcVci	OBJECT-TYPE
	SYNTAX	INTEGER
	ACCESS	not-accessible
	STATUS	mandatory
	DESCRIPTION
		"VCI number"
	--	VCI番号
	::= { connPvcEntry 3 }

connPvcDirection	OBJECT-TYPE
	SYNTAX	INTEGER {
			in(1),		-- On the low side of UNI/Gateway.
			out(2),		-- On the high side of UNI/Gateway.
			in-out(3),	-- Bi.
			multi-out(4),	-- On the high side of multicast.
			multi-in(5)	-- On the low side of multicast.
	}
	ACCESS  not-accessible
	STATUS  mandatory
	DESCRIPTION
		"Indicate cell flow."
	--	セルの流れを示す
	::= { connPvcEntry 4 }

connPvcIndex	OBJECT-TYPE
	SYNTAX	INTEGER
	ACCESS	not-accessible
	STATUS	mandatory
	DESCRIPTION
		"JpnToEng[スイッチングするエンドポイントを
		識別するインデックス.]"
	--	スイッチングするエンドポイントを識別するインデックス.
	::= { connPvcEntry 5 }

connPvcContrastPort	OBJECT-TYPE
	SYNTAX	INTEGER
	ACCESS	read-only
	STATUS	mandatory
	DESCRIPTION
		"JpnToEng[スイッチングするエンドポイントの回線番号.]"
	--	スイッチングするエンドポイントの回線番号.
	::= { connPvcEntry 6 }

connPvcContrastVpi	OBJECT-TYPE
	SYNTAX	INTEGER
	ACCESS	read-only
	STATUS	mandatory
	DESCRIPTION
		"JpnToEng[スイッチングするエンドポイントのVPI番号.]"
	--	スイッチングするエンドポイントのVPI番号.
	::= { connPvcEntry 7 }

connPvcContrastVci	OBJECT-TYPE
	SYNTAX	INTEGER
	ACCESS	read-only
	STATUS	mandatory
	DESCRIPTION
		"JpnToEng[スイッチングするエンドポイントのVCI番号.]"
	--	スイッチングするエンドポイントのVCI番号.
	::= { connPvcEntry 8 }

connPvcTopology	OBJECT-TYPE
	SYNTAX	INTEGER {
			uni-directional-VCC (1),
			bi-directional-VCC  (2),
			uni-directional-VPC (3),
			bi-directional-VPC  (4),
			broadcast-VPC       (5),
			broadcast-VCC       (6),
			gateway             (7)
		}
	ACCESS  read-only
	STATUS  mandatory
	DESCRIPTION
		"Topology of the Connection."
	--	コネクション形態.
	::= { connPvcEntry 9 }

connPvcTrafficType	OBJECT-TYPE
	SYNTAX	INTEGER {
				traffic-CBR (1),
				traffic-rt-VBR (2),
				traffic-nrt-VBR (3),
				traffic-ABR (4),
				traffic-UBR (5)
	}
	ACCESS  read-only
	STATUS  mandatory
	DESCRIPTION
		"Traffic Type."
	--	トラヒックタイプ.
	::= { connPvcEntry 10 }

connPvcFifoIndex	OBJECT-TYPE
	SYNTAX	INTEGER (0..16)
	ACCESS	read-only
	STATUS	mandatory
	DESCRIPTION
		"The Shaper numbers of the direction from this endpoint to
		the endpoint to be switched.
		Value 0 means that Shaping will not be performed."
	--	このエンドポイントからスイッチングする
	--	エンドポイント方向へのShaper番号
	--	値０はShapingしないことを表す.
	::= { connPvcEntry 11 }

connPvcContrastFifoIndex	OBJECT-TYPE
	SYNTAX	INTEGER (0..16)
	ACCESS	read-only
	STATUS	mandatory
	DESCRIPTION
		"The Shaper number of the direction from the endpoint to
		be switched to this end point.
		Value 0 means that Shaping will not be performed."
	--	スイッチングするエンドポイントからこのエンドポイント
	--	方向へのShaper番号
	--	値０はShapingしないことを表す.
	::= { connPvcEntry 12 }

connPvcTrfConf OBJECT-TYPE
	SYNTAX  INTEGER {
			entry(1),
			remove(2)
		}
	ACCESS  read-write
	STATUS  mandatory
	DESCRIPTION
		" Indicate Traffic control/status.
		 If a path does not exist, noSuchName.
		 1. Indicate Traffic status
		    1) entry...registered
 		    2) remove...not registered(initial status)
	 	 2. Register Traffic
		    1) Set connPvcTrfConf to 'entry', to perform the
			registration process.
		    2) Then, get connPvcTrfResult. For normal end,
		       it contains entrySucceed, for abnormal end,
		       it contains other value.
		 3. Delete Traffic
		    1) Set connPvcTrfConf to 'remove', to perform the
			deletion process.
		    2) Then, get connPvTrfResult.  For normal end, it
			contains entrySucceed, for abnormal end, it contains
			other value. "
	--	Traffic制御／状態表示を行う.
	--	パスがない場合は,noSuchName.
	--	1. Traffic状態表示
	--	    1) entry ... 登録中
	--	    2) remove... 未登録(初期状態)
	--	2. Traffic登録
	--	    1) connPvcTrfConfにentryをSetすると登録処理を行う.
	--	    2) その後,connPvcTrfResultをGetする.
	--	        正常終了だとentrySucceedとなっている.異常終了は,
	--	       それ以外となる.
	--	3. Traffic削除
	--	    1) connPvcTrfConfにremoveをSetすると登録削除処理を行う.
	--	    2) その後,connPvcTrfResultをGetする.
	--	        正常終了だとentrySucceedとなっている.異常終了は,
	--	       それ以外となる.
	::= { connPvcEntry 13 }

connPvcTrfResult OBJECT-TYPE
	SYNTAX  INTEGER {
			other(1),
			entrySucceed(2),	-- entry
			alreadyEntry(3),	-- entry
			tableOverflow(4),	-- entry
			removeSucceed(5),	-- remove
			notEntry(6) 		-- remove
		}
	ACCESS  read-only
	STATUS  mandatory
	DESCRIPTION
		"Indicate the processing result after Traffic control.
		 If the path does not exist, noSuchName.
		 The result of the registration
			EntrySucceed  (2) --- Normal end of the registration
			AlreadyEntry  (3) --- Double registration
			tableOverflow (4) --- The number of registration is
					      over the limit.
		The result of the deletion
			RemoveSucceed (5) --- Normal end of the deletion
			notEntry      (6) --- Non-registration
		Normally, other (1) is indicated.  It is the current status
		just after the traffic control.  Once, the traffic control
		is got, then it returns to other (1). "
	--	Traffic制御後の処理結果を表示する.
	--	パスがない場合は,noSuchName.
	--	登録時の結果
	--	    entrySucceed(2)     - 登録の正常終了
	--	    alreadyEntry(3)     - 二重登録
	--	    tableOverflow(4)    - 登録数オーバー
	--	削除時の結果
	--	    removeSucceed(5)    - 削除の正常終了
	--	    notEntry(6)         - 未登録
	--	通常は,other(1)で見えます.トラヒック制御直後の最新状態を
	--	もち,１度Getされると,other(1)になる.
	::= { connPvcEntry 14 }

connPvcParam1	OBJECT-TYPE
	SYNTAX	INTEGER {
			off(1),
			mode1(2),
			mode2(3),
			mode3(4),
			mode4(5),
			mode5(6)
	}
	ACCESS	read-only
	STATUS	mandatory
	DESCRIPTION
		"UPC mode of the direction from this endpoint to
		the endpoint to be switched.
		If nothing is designated, or the designation is invalid,
		off (1) is indicated."
	--	このエンドポイントからスイッチングする
	--	エンドポイント方向へのUPCモード.
	--	指定していない場合,指定が無効の場合は,off(1)表示.
	::= { connPvcEntry 15 }

connPvcContrastParam1	OBJECT-TYPE
	SYNTAX	INTEGER {
			off(1),
			mode1(2),
			mode2(3),
			mode3(4),
			mode4(5),
			mode5(6)
	}
	ACCESS	read-only
	STATUS	mandatory
	DESCRIPTION
		"UPC mode of the direction from the endpoint to
		be switched to this end point.
		If nothing is designated, or the designation is invalid,
		off (1) is indicated."
	--	スイッチングするエンドポイントから
	--	このエンドポイント方向へのUPCモード.
	--	指定していない場合,指定が無効の場合は,off(1)表示.
	::= { connPvcEntry 16 }

connPvcParam2	OBJECT-TYPE
	SYNTAX	DisplayString (SIZE(1..10|0))
	ACCESS	read-only
	STATUS	mandatory
	DESCRIPTION
		"Profile name of the direction from this endpoint to
		the endpoint to be switched.
		If nothing is designated, or the designation is invalid,
		the string of size(0) is indicated."
	--	このエンドポイントからスイッチングする
	--	エンドポイント方向へのプロファイル名.
	--	指定していない場合,指定が無効だった場合,size 0の文字列
	--	を表示する.
	::= { connPvcEntry 17 }

connPvcContrastParam2	OBJECT-TYPE
	SYNTAX	DisplayString (SIZE(1..10|0))
	ACCESS	read-only
	STATUS	mandatory
	DESCRIPTION
		"Profile name of the direction from the endpoint to
		be switched to this end point.
		If nothing is designated, or the designation is invalid,
		the string of size(0) is indicated."
	--	スイッチングするエンドポイントから
	--	このエンドポイント方向へのプロファイル名.
	--	指定していない場合,指定が無効だった場合,size 0の文字列
	--	を表示する.
	::= { connPvcEntry 18 }

connPvcParam3	OBJECT-TYPE
	SYNTAX	INTEGER
	ACCESS	read-only
	STATUS	mandatory
	DESCRIPTION
		"PCR[cell/s] of the direction from this endpoint to
		the endpoint to be switched.
		If the value is invalid, -1 is indicated."
	--	このエンドポイントからスイッチングする
	--	エンドポイント方向へのＰＣＲ[cell/s].
	--	値が無効の場合 -1を表示する.
	::= { connPvcEntry 19 }

connPvcContrastParam3	OBJECT-TYPE
	SYNTAX	INTEGER
	ACCESS	read-only
	STATUS	mandatory
	DESCRIPTION
		"PCR[cell/s] of the direction from the endpoint to
		be switched to this end point.
		If the value is invalid, -1 is indicated."
	--	スイッチングするエンドポイントから
	--	このエンドポイント方向へのＰＣＲ[cell/s].
	--	値が無効の場合 -1を表示する.
	::= { connPvcEntry 20 }

connPvcParam4	OBJECT-TYPE
	SYNTAX	INTEGER
	ACCESS	read-only
	STATUS	mandatory
	DESCRIPTION
		"SCR[cell/s] of the direction from this endpoint to
		the endpoint to be switched.
		If the value is invalid, -1 is indicated."
	--	このエンドポイントからスイッチングする
	--	エンドポイント方向へのＳＣＲ[cell/s].
	--	値が無効の場合 -1を表示する.
	::= { connPvcEntry 21 }

connPvcContrastParam4	OBJECT-TYPE
	SYNTAX	INTEGER
	ACCESS	read-only
	STATUS	mandatory
	DESCRIPTION
		"SCR[cell/s] of the direction from the endpoint to
		be switched to this end point.
		If the value is invalid, -1 is indicated."
	--	スイッチングするエンドポイントから
	--	このエンドポイント方向へのＳＣＲ[cell/s].
	--	値が無効の場合 -1を表示する.
	::= { connPvcEntry 22 }

connPvcParam5	OBJECT-TYPE
	SYNTAX	INTEGER
	ACCESS	read-only
	STATUS	mandatory
	DESCRIPTION
		"MBS[cell] of the direction from this endpoint to
		the endpoint to be switched.
		If the value is invalid, -1 is indicated."
	--	このエンドポイントからスイッチングする
	--	エンドポイント方向へのMBS[cell].
	--	値が無効の場合 -1を表示する.
	::= { connPvcEntry 23 }

connPvcContrastParam5	OBJECT-TYPE
	SYNTAX	INTEGER
	ACCESS	read-only
	STATUS	mandatory
	DESCRIPTION
		"MBS[cell] of the direction from the endpoint to
		be switched to this end point.
		If the value is invalid, -1 is indicated."
	--	スイッチングするエンドポイントから
	--	このエンドポイント方向へのMBS[cell].
	--	値が無効の場合 -1を表示する.
	::= { connPvcEntry 24 }

connPvcParam6	OBJECT-TYPE
	SYNTAX	INTEGER {
			off(1),
			on(2)
	}
	ACCESS	read-only
	STATUS	mandatory
	DESCRIPTION
		"EPD(Early Packet Discard) of the direction from this endpoint
		to the endpoint to be switched.
		Indicate if the discard processing in the unit of AAL5
		packet should be performed or not when the threshold is
		exceeded.
		If the value is invalid, off(1) is indicated."
	--	このエンドポイントからスイッチングする
	--	エンドポイント方向へのEPD(Early Packet Discard).
	--	しきい値を超えたときのAAL５パケット単位
	--	の廃棄処理を行なうかを表示.
	--	値が無効の場合 off(1)を表示する.
	::= { connPvcEntry 25 }

connPvcContrastParam6	OBJECT-TYPE
	SYNTAX	INTEGER {
			off(1),
			on(2)
	}
	ACCESS	read-only
	STATUS	mandatory
	DESCRIPTION
		"EPD(Early Packet Discard) of the direction from the endpoint
		to be switched to this end point.
		Indicate if the discard processing in the unit of AAL5
		packet should be performed or not when the threshold is
		exceeded.
		If the value is invalid, off(1) is indicated."
	--	スイッチングするエンドポイントから
	--	このエンドポイント方向へのEPD((Early Packet Discard)..
	--	しきい値を超えたときのAAL５パケット単位
	--	の廃棄処理を行なうかを表示.
	--	値が無効の場合 off(1)を表示する.
	::= { connPvcEntry 26 }

connPvcParam7	OBJECT-TYPE
	SYNTAX	INTEGER
	ACCESS	not-accessible
	STATUS	mandatory
	DESCRIPTION
		"MCR[cell/s]. Not supported here."
	--	MCR[cell/s]. 今回未サポート.
	::= { connPvcEntry 27 }

connPvcContrastParam7	OBJECT-TYPE
	SYNTAX	INTEGER
	ACCESS	not-accessible
	STATUS	mandatory
	DESCRIPTION
		"MCR[cell/s]. Not supported here."
	--	MCR[cell/s]. 今回未サポート.
	::= { connPvcEntry 28 }

connPvcTrfTable	OBJECT-TYPE
	SYNTAX	SEQUENCE OF ConnPvcTrfEntry
	ACCESS	not-accessible
	STATUS	mandatory
	DESCRIPTION
		" Indicate traffic counter information per connection."
	--	コネクション毎のトラヒックカウンタ情報表示を行なう.
	::= { connPvc 3 }

connPvcTrfEntry	OBJECT-TYPE
 	SYNTAX	ConnPvcTrfEntry
 	ACCESS	not-accessible
 	STATUS	mandatory
 	DESCRIPTION
 		" Entry of traffic per connection.
		  Every INDEX is equivalent to the one defined in connPvcEntry."
	--	コネクション毎のトラヒックのエントリ
	--	各INDEXは,connPvcEntryで定義されているものと同じ.
 	INDEX{ connPvcPort, connPvcVpi, connPvcVci, connPvcDirection, connPvcIndex }
 	::= { connPvcTrfTable 1 }

ConnPvcTrfEntry ::=
	SEQUENCE	{
		connPvcTrfInCells
			OCTET STRING,
		connPvcTrfInCellsCounters
			Counter,
		connPvcTrfOutCells
			OCTET STRING,
		connPvcTrfOutCellsCounters
			Counter,
		connPvcTrfInDropCells
			OCTET STRING,
		connPvcTrfInDropCellsCounters
			Counter
 	}

connPvcTrfInCells	OBJECT-TYPE
	SYNTAX	OCTET STRING
	ACCESS	read-only
	STATUS	mandatory
	DESCRIPTION
		" The number of receive cells  64 bit counter"
	--	受信セル数 64ビットカウンタ
	::= { connPvcTrfEntry 1 }

connPvcTrfInCellsCounters	OBJECT-TYPE
	SYNTAX	Counter
	ACCESS	read-only
	STATUS	mandatory
	DESCRIPTION
		" The number of receive cells  32 bit counter"
	--	受信セル数 32ビットカウンタ
	::= { connPvcTrfEntry 2 }

connPvcTrfOutCells	OBJECT-TYPE
	SYNTAX	OCTET STRING
	ACCESS  read-only
	STATUS  mandatory
	DESCRIPTION
		" The number of transmit cells  64 bit counter"
	--	送信セル数 64ビットカウンタ
	::= { connPvcTrfEntry 3 }

connPvcTrfOutCellsCounters	OBJECT-TYPE
	SYNTAX  Counter
	ACCESS  read-only
	STATUS  mandatory
	DESCRIPTION
		" The number of transmit cells  32 bit counter"
	--	送信セル数 32ビットカウンタ
	::= { connPvcTrfEntry 4 }

connPvcTrfInDropCells	OBJECT-TYPE
	SYNTAX  OCTET STRING
	ACCESS  read-only
	STATUS  mandatory
	DESCRIPTION
		" The number of receive drop cells  64 bit counter "
	--	受信廃棄セル数 64ビットカウンタ
	::= { connPvcTrfEntry 5 }

connPvcTrfInDropCellsCounters	OBJECT-TYPE
	SYNTAX  Counter
	ACCESS  read-only
	STATUS  mandatory
	DESCRIPTION
		" The number of receive drop cells  32 bit counter"
	--	受信廃棄セル数 32ビットカウンタ
	::= { connPvcTrfEntry 6 }

connConf	OBJECT IDENTIFIER ::= { conn 2 }

connConfNode	OBJECT IDENTIFIER ::= { connConf 1 }

connConfNodePvcs	OBJECT-TYPE
	SYNTAX  INTEGER (0..32000)
	ACCESS	read-only
	STATUS	mandatory
	DESCRIPTION
		"The number of current established PVCs in this switch."
	--	スイッチで設定中のPVC数 .
	::= { connConfNode 1 }

connConfNodeSvcs	OBJECT-TYPE
	SYNTAX  INTEGER (0..4096)
	ACCESS	read-only
	STATUS	mandatory
	DESCRIPTION
		"The number of current established SVCs in this switch."
	--	スイッチで設定中のSVC数 .
	::= { connConfNode 2 }

connConfNodeSoftPvcs	OBJECT-TYPE
	SYNTAX  INTEGER (0..4096)
	ACCESS	read-only
	STATUS	mandatory
	DESCRIPTION
		"The number of current established Soft PVPCs/PVCCs in
		 this switch."
	--	スイッチで設定中のSoft PVPCs/PVCCs数 .
	::= { connConfNode 3 }

connConfNodeTrafClear	OBJECT-TYPE
	SYNTAX	INTEGER {
			allClear(1),
			noOperation(2)
		}
	ACCESS	read-write
	STATUS	mandatory
	DESCRIPTION
		"Set allClear (1) to clear all traffic registration information.
		If noOperation (2) is written, nothing will be performed.
		The value at read is always noOperation (2)."
	--	トラヒック登録情報を全クリアするには,allClear(1)を設定する.
	--	noOperation(2)を書き込んだ場合は, 何も行なわない.
	--	読み込み時の値は, いつもnoOperation(2)である.
	::= { connConfNode 4 }

connConfNodeTrafs	OBJECT-TYPE
	SYNTAX	INTEGER (0..1024)
	ACCESS	read-only
	STATUS	mandatory
	DESCRIPTION
		" The number of traffic registrations which are being set
		in the switch. "
	--	スイッチで設定中のトラヒック登録数 .
	::= { connConfNode 5 }

connConfNodeCompleteSvcs	OBJECT-TYPE
	SYNTAX	Counter
	ACCESS	read-only
	STATUS	mandatory
	DESCRIPTION
		" The number of SVC complete calls "
	--	SVC 完了呼数.
	::= { connConfNode 6 }

connConfNodeUnCompleteSvcs	OBJECT-TYPE
	SYNTAX	Counter
	ACCESS	read-only
	STATUS	mandatory
	DESCRIPTION
		" The number of SVC incomplete calls "
	--	SVC 不完了呼数.
	::= { connConfNode 7 }

connConfIfTable	OBJECT-TYPE
	SYNTAX	SEQUENCE OF ConnConfIfEntry
	ACCESS	not-accessible
	STATUS	mandatory
	DESCRIPTION
		" The table is used to show the information of current
		 established connections on the interface."
	::= { connConf 2 }

connConfIfEntry OBJECT-TYPE
	SYNTAX	ConnConfIfEntry
	ACCESS	not-accessible
	STATUS	mandatory
	DESCRIPTION
		"Entry of connConfIfTable."
	INDEX	{ ifIndex }
	::= { connConfIfTable 1}

ConnConfIfEntry ::=
	SEQUENCE {
		connConfIfPvcs		INTEGER,
		connConfIfSvcs		INTEGER,
		connConfIfSoftPvcs	INTEGER
	}

connConfIfPvcs	OBJECT-TYPE
	SYNTAX  INTEGER (0..16384)
	ACCESS	read-only
	STATUS	mandatory
	DESCRIPTION
		" The number of current established PVCs
		on the interface."
	::= { connConfIfEntry 1 }

connConfIfSvcs	OBJECT-TYPE
	SYNTAX  INTEGER (0..4096)
	ACCESS	read-only
	STATUS	mandatory
	DESCRIPTION
		" The number of current established SVCs
		on the interface."
	::= { connConfIfEntry 2 }

connConfIfSoftPvcs	OBJECT-TYPE
	SYNTAX  INTEGER (0..4096)
	ACCESS	read-only
	STATUS	mandatory
	DESCRIPTION
		" The number of current established Soft PVPCs/PVCCs
		on the interface."
	::= { connConfIfEntry 3 }


connRoute	OBJECT IDENTIFIER ::= { conn 3 }

DstAtmAddressFormat ::= INTEGER	{
				noWriting(-1),	-- read only
				e-164	(1),
				nsap	(2)
			}
	--	DstAtmAddress format.

DstAtmAddressLength ::= INTEGER(4..160|-1)
	--	The valid bit length of DstAtmAddress.
	--	The value(-1) is read-only.
	--	The value(4..160) must be a multiple of 4.

DstAtmAddress ::= OCTET STRING(SIZE(0..20))
	--	Called Party Address.
	--	Its maximum length is either 20 bytes (NSAP) or 8
	--	bytes (E.164).
	--	If the last semi OCTET is invalid, it is padded
	--	with 0xf.
	--	The value of size(0) is read-only.

DstPrimaryIfIndex ::= INTEGER(1..99|-1)
	--	The outgoing port number selected first.
	--	The value(-1) is read-only.

DstPrimaryVPI ::= INTEGER(0..4095|-1)
	--	The outgoing VPI number for tunneling selected first.
	--	The value(-1) shows that this is not used for routing.

DstSecondaryIfIndex ::= INTEGER(1..99|-1)
	--	The outgoing port number selected secondly or after.
	--	The value(-1) shows that this is not used for routing.

DstSecondaryVPI ::= INTEGER(0..4095|-1)
	--	The outgoing VPI number for tunneling selected secondly or
	--	after.
	--	The value(-1) shows that this is not used for routing.

connRouteOpe	OBJECT IDENTIFIER ::= { connRoute 1 }

	--	The connRouteOpe module defines the way to operate(add or
	--	delete) the static routing information which connRouteTable
	--	shows.

	--	the Procedure of operating the static routing information

	--	1.Get connRouteOpeStatus

	--		Get connRouteOpeStatus to check if it is "free".

	--		If it is, managers can set "allocate" to it.

	--		If not, try again after a while.
	--		If it has been the same value other than "free" for a
	--		long time, set it "free" judging that the allocating
	--		manager failed. But the other managers which did set
	--		"allocate" cannot set "free" for 60sec after the
	--		allocating manager has last requested the agent to
	--		set objects under connRouteOpe module.
	--
	--	2.Set "allocate" to connRouteOpeStatus.

	--		Set "allocate" to connRouteOpeStatus, then
	--		the agent sets the default value to the parameter
	--		objects.

	--		i)The default values of parameters

	--		connRouteOpeAddressFormat	-1
	--		connRouteOpeAddressLength	-1
	--		connRouteOpeAddress		 0 length string
	--		connRouteOpePrimaryIfIndex	-1
	--		connRouteOpePrimaryVPI		-1
	--		connRouteOpeSecondaryIfIndex	-1
	--		connRouteOpeSecondaryVPI	-1
	--		connRouteOpeTertiaryIfIndex	-1
	--		connRouteOpeTertiaryVPI		-1
	--		connRouteOpeFourthryIfIndex	-1
	--		connRouteOpeFourthryVPI		-1
	--		connRouteOpeFifthryIfIndex	-1
	--		connRouteOpeFifthryVPI		-1
	--		connRouteOpeSixthryIfIndex	-1
	--		connRouteOpeSixthryVPI		-1
	--		connRouteOpeSeventhryIfIndex	-1
	--		connRouteOpeSeventhryVPI	-1

	--	In 3. and 4., parameter objects cannot be set by the managers
	--	which have not set "allocate".

	--	3.Set the value to parameter objects.

	--		i)"add" parameters

	--		connRouteOpeAddressFormat
	--		connRouteOpeAddressLength
	--		connRouteOpeAddress
	--		connRouteOpePrimaryIfIndex
	--		connRouteOpePrimaryVPI		*
	--		connRouteOpeSecondaryIfIndex	*
	--		connRouteOpeSecondaryVPI	*
	--		connRouteOpeTertiaryIfIndex	*
	--		connRouteOpeTertiaryVPI		*
	--		connRouteOpeFourthryIfIndex	*
	--		connRouteOpeFourthryVPI		*
	--		connRouteOpeFifthryIfIndex	*
	--		connRouteOpeFifthryVPI		*
	--		connRouteOpeSixthryIfIndex	*
	--		connRouteOpeSixthryVPI		*
	--		connRouteOpeSeventhryIfIndex	*
	--		connRouteOpeSeventhryVPI	*

	--		*)If these parameters are not necessary
	--		a manager does not have to set them( or
	--		sets the value(-1) to them).
	--		But the following pattern of parameters	is not allowed.

	--		connRouteOpeSecondary(〜Seventhry)IfIndex   - not set
	--				(i.e This object value is(-1))
	--		connRouteOpeSecondary(〜Seventhry)VPI	- set
	--				(i.e This object value is not (-1))

	--		ii)"delete" parameters

	--		connRouteOpeAddressFormat
	--		connRouteOpeAddressLength
	--		connRouteOpeAddress

	--	4.Set "add"/"delete" to connRouteOpeStatus.
	--		( No other objects should be set together with
	--		connRouteOpeStatus in this operation.)

	--		If the error status of the response is "noError", it
	--		means that connRouteOpeStatus is set successfully.
	--		Otherwise, get connRouteOpeFailureCause to see the
	--		cause.

	--	5.Set "free" to connRouteOpeStatus
	--		Set "free" to connRouteOpeStatus for the next
	--		operation.

connRouteOpeStatus	OBJECT-TYPE
		SYNTAX  INTEGER {
				allocate(1),
				add	(2),
				delete	(3),
				free	(4)
			}
		ACCESS  read-write
		STATUS  mandatory
		DESCRIPTION
			"
		allocate	: allocate the right to operate the routing
				information to a manager.

		add		: add the routing information
				to static routing table.


		delete		: delete the routing information
				from static routing table.

		free		: free the right to operate the routing
				information from a manager.

			    +-------------+
			    |		  |
			    +---+----+<---+
		    ----------->|free|<-----------------
		   |		+----+   		|
		   |	    		     		|
		   |     +--------+        +----------+	|
		    ---->|allocate| -----> |add/delete|-
			 +--------+        +----------+
			"
		::= { connRouteOpe 1 }

ConnRouteOpeFailureCause ::= INTEGER	{
			noWriting			 (-1),
			other				  (1), -- add,delete
			allocateSucceed			  (2),
			tableIsFull			  (3), -- add
			parameterIsNotEnough		  (4), -- add,delete
			specifiedAddressIsIllegal	  (5), -- add,delete
			specifiedAddressIsAlreadyExisting (6), -- add
			specifiedAddressIsNotExisting	  (7)  -- delete
			}

connRouteOpeFailureCause OBJECT-TYPE
		SYNTAX	ConnRouteOpeFailureCause
		ACCESS  read-only
		STATUS  mandatory
		DESCRIPTION
			"The result of the operation."
		::= { connRouteOpe 2 }

connRouteOpeAddressFormat OBJECT-TYPE
		SYNTAX  DstAtmAddressFormat
		ACCESS	read-write
		STATUS	mandatory
		::= { connRouteOpe 3 }

connRouteOpeAddressLength OBJECT-TYPE
		SYNTAX  DstAtmAddressLength
		ACCESS	read-write
		STATUS	mandatory
		::= { connRouteOpe 4 }

connRouteOpeAddress	OBJECT-TYPE
		SYNTAX	DstAtmAddress
		ACCESS  read-write
		STATUS  mandatory
		::= { connRouteOpe 5 }

connRouteOpePrimaryIfIndex OBJECT-TYPE
		SYNTAX  DstPrimaryIfIndex
		ACCESS  read-write
		STATUS  mandatory
		::= { connRouteOpe 6 }

connRouteOpePrimaryVPI OBJECT-TYPE
		SYNTAX  DstPrimaryVPI
		ACCESS  read-write
		STATUS	mandatory
		::= { connRouteOpe 7 }

connRouteOpeSecondaryIfIndex OBJECT-TYPE
		SYNTAX  DstSecondaryIfIndex
		ACCESS  read-write
		STATUS  mandatory
		::= { connRouteOpe 8 }

connRouteOpeSecondaryVPI OBJECT-TYPE
		SYNTAX	DstSecondaryVPI
		ACCESS  read-write
		STATUS  mandatory
		::= { connRouteOpe 9 }

connRouteOpeTertiaryIfIndex OBJECT-TYPE
                SYNTAX  DstSecondaryIfIndex
                ACCESS  read-write
                STATUS  mandatory
                ::= { connRouteOpe 10 }

connRouteOpeTertiaryVPI OBJECT-TYPE
                SYNTAX  DstSecondaryVPI
                ACCESS  read-write
                STATUS  mandatory
                ::= { connRouteOpe 11 }

connRouteOpeFourthryIfIndex OBJECT-TYPE
                SYNTAX  DstSecondaryIfIndex
                ACCESS  read-write
                STATUS  mandatory
                ::= { connRouteOpe 12 }

connRouteOpeFourthryVPI OBJECT-TYPE
                SYNTAX  DstSecondaryVPI
                ACCESS  read-write
                STATUS  mandatory
                ::= { connRouteOpe 13 }

connRouteOpeFifthryIfIndex OBJECT-TYPE
                SYNTAX  DstSecondaryIfIndex
                ACCESS  read-write
                STATUS  mandatory
                ::= { connRouteOpe 14 }

connRouteOpeFifthryVPI OBJECT-TYPE
                SYNTAX  DstSecondaryVPI
                ACCESS  read-write
                STATUS  mandatory
                ::= { connRouteOpe 15 }

connRouteOpeSixthryIfIndex OBJECT-TYPE
                SYNTAX  DstSecondaryIfIndex
                ACCESS  read-write
                STATUS  mandatory
                ::= { connRouteOpe 16 }

connRouteOpeSixthryVPI OBJECT-TYPE
                SYNTAX  DstSecondaryVPI
                ACCESS  read-write
                STATUS  mandatory
                ::= { connRouteOpe 17 }

connRouteOpeSeventhryIfIndex OBJECT-TYPE
                SYNTAX  DstSecondaryIfIndex
                ACCESS  read-write
                STATUS  mandatory
                ::= { connRouteOpe 18 }

connRouteOpeSeventhryVPI OBJECT-TYPE
                SYNTAX  DstSecondaryVPI
                ACCESS  read-write
                STATUS  mandatory
                ::= { connRouteOpe 19 }

connRouteTable	OBJECT-TYPE
	SYNTAX	SEQUENCE OF ConnRouteEntry
	ACCESS	not-accessible
	STATUS  mandatory
	DESCRIPTION
		"This table is used to show the static routing table for SVC."
	::= { connRoute 2 }

connRouteEntry	OBJECT-TYPE
	SYNTAX	ConnRouteEntry
	ACCESS	not-accessible
	STATUS	mandatory
	DESCRIPTION
		"Entry of connRouteTable."
	--	 connRouteTableのエントリ.
	INDEX	{ connRouteAtmAddressFormat,
			connRouteAtmAddressLength, connRouteAtmAddress }
	::= { connRouteTable 1}

ConnRouteEntry ::=
	SEQUENCE {
		connRouteType
			INTEGER,
		connRoutePrimaryIfIndex
			INTEGER,
		connRoutePrimaryVPI
			INTEGER,
		connRouteSecondaryIfIndex
			INTEGER,
		connRouteSecondaryVPI
			INTEGER,
                connRouteTertiaryIfIndex
                        INTEGER,
                connRouteTertiaryVPI
                        INTEGER,
                connRouteFourthryIfIndex
                        INTEGER,
                connRouteFourthryVPI
                        INTEGER,
                connRouteFifthryIfIndex
                        INTEGER,
                connRouteFifthryVPI
                        INTEGER,
                connRouteSixthryIfIndex
                        INTEGER,
                connRouteSixthryVPI
                        INTEGER,
                connRouteSeventhryIfIndex
                        INTEGER,
                connRouteSeventhryVPI
                        INTEGER,
                connRoutePrimaryStatus
                        INTEGER,
                connRoutePrimaryCause
                        INTEGER,
		connRouteAtmAddressFormat
			DstAtmAddressFormat,
		connRouteAtmAddressLength
			DstAtmAddressLength,
		connRouteAtmAddress
			DstAtmAddress
	}

connRouteType OBJECT-TYPE
		SYNTAX  INTEGER {
				static	(1),
				dynamic	(2)
			}
		ACCESS	read-only
		STATUS	mandatory
		DESCRIPTION
			"The value of this object shows the routing type."
		::= { connRouteEntry 1 }

connRoutePrimaryIfIndex OBJECT-TYPE
		SYNTAX  DstPrimaryIfIndex
		ACCESS  read-only
		STATUS  mandatory
		::= { connRouteEntry 2 }

connRoutePrimaryVPI OBJECT-TYPE
		SYNTAX  DstPrimaryVPI
		ACCESS  read-only
		STATUS	mandatory
		::= { connRouteEntry 3 }

connRouteSecondaryIfIndex OBJECT-TYPE
		SYNTAX  DstSecondaryIfIndex
		ACCESS  read-only
		STATUS  mandatory
		::= { connRouteEntry 4 }

connRouteSecondaryVPI OBJECT-TYPE
		SYNTAX	DstSecondaryVPI
		ACCESS  read-only
		STATUS  mandatory
		::= { connRouteEntry 5 }

connRouteTertiaryIfIndex OBJECT-TYPE
                SYNTAX  DstSecondaryIfIndex
                ACCESS  read-only
                STATUS  mandatory
                ::= { connRouteEntry 6 }

connRouteTertiaryVPI OBJECT-TYPE
                SYNTAX  DstSecondaryVPI
                ACCESS  read-only
                STATUS  mandatory
                ::= { connRouteEntry 7 }

connRouteFourthryIfIndex OBJECT-TYPE
                SYNTAX  DstSecondaryIfIndex
                ACCESS  read-only
                STATUS  mandatory
                ::= { connRouteEntry 8 }

connRouteFourthryVPI OBJECT-TYPE
                SYNTAX  DstSecondaryVPI
                ACCESS  read-only
                STATUS  mandatory
                ::= { connRouteEntry 9 }

connRouteFifthryIfIndex OBJECT-TYPE
                SYNTAX  DstSecondaryIfIndex
                ACCESS  read-only
                STATUS  mandatory
                ::= { connRouteEntry 10 }

connRouteFifthryVPI OBJECT-TYPE
                SYNTAX  DstSecondaryVPI
                ACCESS  read-only
                STATUS  mandatory
                ::= { connRouteEntry 11 }

connRouteSixthryIfIndex OBJECT-TYPE
                SYNTAX  DstSecondaryIfIndex
                ACCESS  read-only
                STATUS  mandatory
                ::= { connRouteEntry 12 }

connRouteSixthryVPI OBJECT-TYPE
                SYNTAX  DstSecondaryVPI
                ACCESS  read-only
                STATUS  mandatory
                ::= { connRouteEntry 13 }

connRouteSeventhryIfIndex OBJECT-TYPE
                SYNTAX  DstSecondaryIfIndex
                ACCESS  read-only
                STATUS  mandatory
                ::= { connRouteEntry 14 }

connRouteSeventhryVPI OBJECT-TYPE
                SYNTAX  DstSecondaryVPI
                ACCESS  read-only
                STATUS  mandatory
                ::= { connRouteEntry 15 }

connRoutePrimaryStatus OBJECT-TYPE
                SYNTAX  INTEGER {
                        disable (1),
                        enable  (2)
                        }
                ACCESS  read-only
                STATUS  mandatory
                DESCRIPTION
		"Operational status of the primary routing.
		If the primary route of the routing table of the
		equipment is valid, enable(2), if not valid, disable(1)."
	--	本装置のルーチングテーブルの基本ルートが有効の場合は
	--	enable(2) 有効でない場合はdisable(1).
                ::= { connRouteEntry 16 }

connRoutePrimaryCause OBJECT-TYPE
                SYNTAX  INTEGER {
                                normal (0),
                                other (1),
                                outOfService (2),
                                testing (3),
                                lineInterface-Down  (4),
                                lineInterface-Failure (5),
                                sw-Engine-Failure (6),
                                sw-Engine-SwapOUT (7),
                                notInstalled (99)
                        }
                ACCESS  read-only
                STATUS  mandatory
                DESCRIPTION
		"Cause of the switching from the primary route."
	--	基本ルートから切り替わった時の要因.
                ::= { connRouteEntry 17 }

connRouteAtmAddressFormat	OBJECT-TYPE
		SYNTAX	DstAtmAddressFormat
		ACCESS	not-accessible
		STATUS	mandatory
		::= { connRouteEntry 18 }

connRouteAtmAddressLength	OBJECT-TYPE
		SYNTAX	DstAtmAddressLength
		ACCESS	not-accessible
		STATUS	mandatory
		::= { connRouteEntry 19 }

connRouteAtmAddress	OBJECT-TYPE
		SYNTAX	DstAtmAddress
		ACCESS	not-accessible
		STATUS	mandatory
		::= { connRouteEntry 20 }

connSoftPvcIndexNext	OBJECT-TYPE
	SYNTAX  INTEGER (1..128)
	ACCESS	read-only
	STATUS	mandatory
	DESCRIPTION
		"This object returns the empty index of the call management
		table, required to access to connSoftPvcTable. "
	--	本オブジェクトは, connSoftPvcTableをアクセスする時に,
	--	必要となる呼管理テーブルの空きindex値を返す.
	::= { conn 4 }

connSoftPvcTable OBJECT-TYPE
	SYNTAX	SEQUENCE OF ConnSoftPvcEntry
	ACCESS	not-accessible
	STATUS	mandatory
	DESCRIPTION
		" This table include all entries to Soft-PVPC/PVCC
		currently available between the lines or the line and
		CPU port of the switch.  Also, this table is used to
		set or delete Soft-PVPC/PVCC.  The operable
		connection form between Soft-PVPC/PVCC is bi-
		directional point-to-point only.

	The procedure to set the connection is as follows:

		1. Acquire connSoftPvcIndex
		To set the connection, read connSoftPvcIndexNext and
		obtain an index of the Soft-PVPC/PVCC table.  The
		index must be managed by NMS. (The index is required
		to take an action to the connection.)

		2. Set createAndWait
		Set connSoftPvcRowStatus to CreateAndWait, using the
		obtained connSoftPvcIndex as index.  If the agent
		will set the parameter for the Soft-PVPC/PVCC
		setting to the default value and make
		connSoftRowStatus to notReady.

		However, the same manager cannot create another row
		while creating a row (the status of the row is notRedy
		or notInService).

		3. Get the default value
		Get the default value of the object which serves as
		parameter for the connection setting. (The agent
		shall return -1 if it does not have a default value.)

		Default values are as follows:

			connSoftPvcTopology		bi-directional-VCC(2)
			connSoftPvcTrafficType		traffic-UBR(5)
			connSoftPvcEndpointType		calling(1)
			connSoftPvcRetry		2
			connSoftPvcSrcAtmAddressFormat	nsap(2)
			connSoftPvcSrcAtmAddressLength	None
			connSoftPvcSrcAtmAddress	0 length string
			connSoftPvcSrcIfIndex		None
			connSoftPvcSrcVPI		None
			connSoftPvcSrcVCI		None
			connSoftPvcDstAtmAddressFormat	nsap(2)
			connSoftPvcDstAtmAddressLength	None
			connSoftPvcDstAtmAddress	0 length string
			connSoftPvcDstIfIndex		None
			connSoftPvcDstVPI		None
			connSoftPvcDstVCI		None
			connSoftPvcSrcFifoIndex		0
			connSoftPvcDstFifoIndex		0
			connSoftPvcNodeKind		model5(1)
			connSoftPvcSrcParam1		off(1)
			connSoftPvcDstParam1		off(1)
			connSoftPvcSrcParam2		0 length string
			connSoftPvcDstParam2		0 length string
			connSoftPvcSrcParam3		-1
			connSoftPvcDstParam3		-1
			connSoftPvcSrcParam4		-1
			connSoftPvcDstParam4		-1
			connSoftPvcSrcParam5		-1
			connSoftPvcDstParam5		-1
			connSoftPvcSrcParam6		off(2)
			connSoftPvcDstParam6		off(2)
			connSoftPvcSrcParam7		None (not installed)
			connSoftPvcDstParam7		None (not installed)

		4. Set parameter
		If a parameter does not have a default value, or the
		default value should not be used, set the parameter to
		a value.
		If all parameters are set, the agent shall make
		connSoftPvcRowStatus to notInService.

		5. Set active
		By doing so, the agent checks parameters, resources and
		establishes the connection.

		6. Get connSoftPvcRowStatus
		If connSoftPvcRowStatus is active, the connection
		setting completed successfully, if notInService,the
		connection setting failed.  For the cause, refer to
		connSoftPvcCause.
		(Note) When the connection setting has failed, if the
		connection is not released, the row will remain.

		7. Get connSoftPvcRestRetry
		Remaining counts of retry are contained.  If it is
		positive value, the retry is in progress.  If
		connSoftPvcRestRetry is 0, the retry completed.  The
		result of the connection setting should be seen, when
		this object is 0.
		-1 means that infinite retry is in progress.

		***Special pattern***
		(1) If connSoftPvcTopology is bi-directional-VPC, set
		connSoftPvcSrcVCI, connSoftPvcDstVCI to 0.

	The procedure to release the connection is as follows:

		1. Set 'destroy'
		Set connSoftPvcRowStatus to 'destroy', using
		connSoftPvcIndex of the connection to be deleted as
		index.
		The agent will delete the connection, referring to
		it.
		(Note) 'destroy' can also be set during the bypass
		processing.

		2. Get the result
		If the connection is deleted, 'get' of
		connSoftPvcTable of the designated index becomes
		NoSuchName.

	The bypass processing of connection

		1. Set notInService
		When the agent executes the bypass processing of
		connection, set connSoftPvcRowStatus to
		notInService, and then establish the connection.

		2. Get connSoftPvcRowStatus
		If connSoftPvcRowStatus is 'active', the bypass
		connection setting has completed successfully.
		If connSoftPvcRowStatus remains 'notInService',
		the connection setting has failed.

	Others

		1. The cut and recovery processing of connection is
		performed, following the delete and set procedures
		of the concerned connection.
		Each procedure is as stated before."

	--	このテーブルは交換機の回線間や回線とCPUポート間で
	--	現在張られている全てのSoft-PVPC/PVCCへのエントリを含む.
	--	また, Soft-PVPC/PVCCの設定・削除にも使われる.
	--	操作できるSoft-PVPC/PVCCのコネクション形態は
	--	bi-directional point-to-pointのみである.
	--
	--	コネクション設定の手順は以下のとおり.
	--	1.connSoftPvcIndexの取得
	--	  コネクションを設定する場合にはconnSoftPvcIndexNextを
	--	  読み, Soft-PVPC/PVCCテーブルのインデックスを得る。
	--	  ここで得たインデックスはNMSで管理する必要がある。
	--	  (以後このコネクションに対するアクションを起こす場合
	--	  には必要となる。)
	--
	--	2.createAndWaitのset
	--	  取得したconnSoftPvcIndexをインデックスとして,
	--	  connSoftPvcRowStatusにcreateAndWaitをセットする.
	--	  エージェントはこれによりSoft-PVPC/PVCC設定の為の
	--	  パラメータにデフォルト値を設定し,
	--	  connSoftPvcRowStatusをnotReadyにする.
	--
	--	  ただし, 同一のマネージャはrowを生成している最中に
	--	  (rowのstatusはnotReady, またはnotInService),
	--	  さらに別のrowを生成することはできない.
	--
	--	3.デフォルト値のget
	--	  コネクション設定時のパラメータとなるオブジェクトの
	--	  デフォルト値をgetする. (エージェントは,デフォルト値
	--	  がないものに関しては-1を返す)
	--
	--	  デフォルト値を以下に示す。
	--		connSoftPvcTopology		bi-directional-VCC(2)
	--		connSoftPvcTrafficType		traffic-UBR(5)
	--		connSoftPvcEndpointType		calling(1)
	--		connSoftPvcRetry		2
	--		connSoftPvcSrcAtmAddressFormat	nsap(2)
	--		connSoftPvcSrcAtmAddressLength	なし
	--		connSoftPvcSrcAtmAddress	0 length string
	--		connSoftPvcSrcIfIndex		なし
	--		connSoftPvcSrcVPI		なし
	--		connSoftPvcSrcVCI		なし
	--		connSoftPvcDstAtmAddressFormat	nsap(2)
	--		connSoftPvcDstAtmAddressLength	なし
	--		connSoftPvcDstAtmAddress	0 length string
	--		connSoftPvcDstIfIndex		なし
	--		connSoftPvcDstVPI		なし
	--		connSoftPvcDstVCI		なし
	--		connSoftPvcSrcFifoIndex		0
	--		connSoftPvcDstFifoIndex		0
	--		connSoftPvcNodeKind		model5(1)
	--		connSoftPvcSrcParam1		off(1)
	--		connSoftPvcDstParam1		off(1)
	--		connSoftPvcSrcParam2		0 length string
	--		connSoftPvcDstParam2		0 length string
	--		connSoftPvcSrcParam3		-1
	--		connSoftPvcDstParam3		-1
	--		connSoftPvcSrcParam4		-1
	--		connSoftPvcDstParam4		-1
	--		connSoftPvcSrcParam5		-1
	--		connSoftPvcDstParam5		-1
	--		connSoftPvcSrcParam6		off(2)
	--		connSoftPvcDstParam6		off(2)
	--		connSoftPvcSrcParam7		なし (未実装の為)
	--		connSoftPvcDstParam7		なし (未実装の為)
	--
	--	4.パラメータのset
	--	  デフォルト値がないもの,デフォルト値を使用したくない
	--	  ものに関して, 値をsetする.
	--	  全てのパラメータが設定されたならば,エージェントは
	--	  connSoftPvcRowStatusをnotInServiceにする.
	--
	--	5.activeのset
	--	  エージェントはこれによりパラメータのチェック,
	--	  リソースのチェックを行ない,コネクションを張りにいく.
	--
	--	6.connSoftPvcRowStatusのget
	--	  connSoftPvcRowStatusがactiveならば,コネクション設定
	--	  成功. notInServiceのままのときは, コネクション設定
	--	  失敗. 要因は,connSoftPvcCauseを見る.
	--	  (注)コネクション設定失敗時は,コネクション解除を行わ
	--	      ないと,rowが残ることになる.
	--
	--	7.connSoftPvcRestRetryのget
	--	  残りリトライ回数がはいっている. 正の値ならばリトライ
	--	  処理中. connSoftPvcRestRetryが0ならばリトライ完了.
	--	  コネクション設定の結果を見る時は, このオブジェクトが
	--	  0の時に行うべきである.
	--	  -1は,無限リトライ中である.
	--
	--	**** 特殊なパターン ****
	--	 (1)connSoftPvcTopologyが
	--		bi-directional-VPC
	--	    の場合
	--	    	connSoftPvcSrcVCI,
	--	    	connSoftPvcDstVCI
	--	    には０を設定して下さい.
	--
	--	コネクション解除の手順は以下のとおり.
	--	1.destroyのset
	--	  削除したいコネクションのconnSoftPvcIndexをインデックスとし,
	--	  connSoftPvcRowStatusにdestroyをセットする.
	--	  エージェントはこれによりコネクションを削除しにいく.
	--	  (注)迂回処理中もdestroyの設定は可能とする.
	--
	--	2.結果のget
	--	  コネクションが,削除出来た場合は,指定インデックスの
	--	  connSoftPvcTableのgetはNoSuchNameとなる.
	--
	--	コネクションの迂回処理
	--	1.notInServiceのset
	--	  エージェントはコネクションの迂回処理を行う場合,
	--	  connSoftPvcRowStatusにnotInServiceをセットしてから,
	--	  コネクションを張りにいく.
	--	2.connSoftPvcRowStatusのget
	--	  connSoftPvcRowStatusがactiveならば,迂回コネクション
	--	  設定成功.
	--	  connSoftPvcRowStatusがnotInServiceのままのときは
	--	  コネクション設定失敗.
	--
	--	その他
	--	1.コネクションの切り戻し処理は, 対象のコネクション
	--	  に対して, 削除＆設定の手順を踏んで行う.
	--	  それぞれの処理手順は前述の通り.
	::= { conn 5 }

connSoftPvcEntry OBJECT-TYPE
	SYNTAX	ConnSoftPvcEntry
	ACCESS	not-accessible
	STATUS	mandatory
	DESCRIPTION
		" Entry of ATMSoft-PVPC/PVCC connection "
	--	ATMSoft-PVPC/PVCCコネクションのエントリ
	INDEX	{ connSoftPvcIndex }
	::= { connSoftPvcTable 1 }

ConnSoftPvcEntry ::=
	SEQUENCE {
		connSoftPvcIndex
			INTEGER,
		connSoftPvcTopology
			INTEGER,
		connSoftPvcTrafficType
			INTEGER,
		connSoftPvcEndpointType
			INTEGER,
		connSoftPvcRetry
			INTEGER,
		connSoftPvcSrcAtmAddressFormat
			INTEGER,
		connSoftPvcSrcAtmAddressLength
			INTEGER,
		connSoftPvcSrcAtmAddress
			OCTET STRING,
		connSoftPvcSrcIfIndex
			INTEGER,
		connSoftPvcSrcVPI
			INTEGER,
		connSoftPvcSrcVCI
			INTEGER,
		connSoftPvcDstAtmAddressFormat
			INTEGER,
		connSoftPvcDstAtmAddressLength
			INTEGER,
		connSoftPvcDstAtmAddress
			OCTET STRING,
		connSoftPvcDstIfIndex
			INTEGER,
		connSoftPvcDstVPI
			INTEGER,
		connSoftPvcDstVCI
			INTEGER,
		connSoftPvcRowStatus
			INTEGER,
		connSoftPvcCause
			INTEGER,
		connSoftPvcRestRetry
			INTEGER,
		connSoftPvcSrcFifoIndex
			INTEGER,
		connSoftPvcDstFifoIndex
			INTEGER,
		connSoftPvcNodeKind
			INTEGER,
		connSoftPvcSrcParam1
			INTEGER,
		connSoftPvcDstParam1
			INTEGER,
		connSoftPvcSrcParam2
			DisplayString,
		connSoftPvcDstParam2
			DisplayString,
		connSoftPvcSrcParam3
			INTEGER,
		connSoftPvcDstParam3
			INTEGER,
		connSoftPvcSrcParam4
			INTEGER,
		connSoftPvcDstParam4
			INTEGER,
		connSoftPvcSrcParam5
			INTEGER,
		connSoftPvcDstParam5
			INTEGER,
		connSoftPvcSrcParam6
			INTEGER,
		connSoftPvcDstParam6
			INTEGER,
		connSoftPvcSrcParam7
			INTEGER,
		connSoftPvcDstParam7
			INTEGER
	}

connSoftPvcIndex	OBJECT-TYPE
	SYNTAX  INTEGER (1..128)
	ACCESS	read-only
	STATUS	mandatory
	DESCRIPTION
		"The value of this object is equal to the
		 connSoftPvcIndexNext.
		1	-	128	:	Soft PVPCs/PVCCs"
	::= { connSoftPvcEntry 1 }

connSoftPvcTopology OBJECT-TYPE
	SYNTAX	INTEGER {
			bi-directional-VCC  (2),
			bi-directional-VPC  (4)
		}
	ACCESS	read-write
	STATUS	mandatory
	DESCRIPTION
		"Topology of the Connection."
	--	 コネクション形態.
	::= { connSoftPvcEntry 2 }

connSoftPvcTrafficType OBJECT-TYPE
	SYNTAX	INTEGER {
			traffic-CBR (1),
			traffic-rt-VBR (2),
			traffic-nrt-VBR (3),
			traffic-ABR (4),
			traffic-UBR (5)
		}
	ACCESS	read-write
	STATUS	mandatory
	DESCRIPTION
		"Traffic Type."
	--	トラヒックタイプ.
	::= { connSoftPvcEntry 3 }

connSoftPvcEndpointType OBJECT-TYPE
	SYNTAX	INTEGER {
			calling(1),	-- Calling side.
			called(2)	-- Called side. notSupported.
		}
	ACCESS	read-only
	STATUS	mandatory
	DESCRIPTION
		"Type of Endpoint."
	--	エンドポイントの種類.
	::= { connSoftPvcEntry 4 }

connSoftPvcRetry OBJECT-TYPE
	SYNTAX  INTEGER (0..15|-1)
	ACCESS	read-write
	STATUS	mandatory
	DESCRIPTION
		"Number of retry.
		0	-	15	:	Number of retry
		-1			:	Infinite retry"
	--	リトライ回数.
	::= { connSoftPvcEntry 5 }

ConnSoftPvcSrcAtmAddressFormat ::= INTEGER	{
		noWriting(-1),	-- read only
		e-164	 (1),
		nsap	 (2)
	}

connSoftPvcSrcAtmAddressFormat OBJECT-TYPE
	SYNTAX  ConnSoftPvcSrcAtmAddressFormat
	ACCESS	read-write
	STATUS	mandatory
	DESCRIPTION
		"AtmAdress format. "
	::= { connSoftPvcEntry 6 }

connSoftPvcSrcAtmAddressLength OBJECT-TYPE
	SYNTAX  INTEGER (4..160|-1)
	ACCESS	read-write
	STATUS	mandatory
	DESCRIPTION
		"The valid bit length of connSoftPvcSrcAtmAddress.
		 The value(-1) is read-only.
		 The value(4..160) must be a multiple of 4."
	::= { connSoftPvcEntry 7 }

connSoftPvcSrcAtmAddress OBJECT-TYPE
	SYNTAX  OCTET STRING (SIZE(0..20))
	ACCESS	read-write
	STATUS	mandatory
	DESCRIPTION
		"NodeId of source node.
		 Its maximum length is 13 bytes.
		 This object length is 20 bytes in case AtmAddress is
		 setting.
		 If the last semi OCTET is invalid, it is padded
		 with 0xf.
		 The value of size(0) is read-only."
	::= { connSoftPvcEntry 8 }

connSoftPvcSrcIfIndex OBJECT-TYPE
	SYNTAX	INTEGER (1..99|-1)
	ACCESS	read-write
	STATUS	mandatory
	DESCRIPTION
		"The number of the calling line.
		(ifIndex of ifEntry)"
	--	発呼側回線番号.
	::= { connSoftPvcEntry 9 }

connSoftPvcSrcVPI OBJECT-TYPE
	SYNTAX	INTEGER
	ACCESS	read-write
	STATUS	mandatory
	DESCRIPTION
		"VPI value of the calling line."
	--	発呼側回線VPI番号.
	::= { connSoftPvcEntry 10 }

connSoftPvcSrcVCI OBJECT-TYPE
	SYNTAX	INTEGER
	ACCESS	read-write
	STATUS	mandatory
	DESCRIPTION
		"VCI value of the calling line."
	--	発呼側回線VCI番号.
	::= { connSoftPvcEntry 11 }

ConnSoftPvcDstAtmAddressFormat ::= INTEGER {
		noWriting(-1),    -- read only
		e-164    (1),
		nsap     (2)
		}

connSoftPvcDstAtmAddressFormat OBJECT-TYPE
	SYNTAX  ConnSoftPvcDstAtmAddressFormat
	ACCESS	read-write
	STATUS	mandatory
	DESCRIPTION
		"AtmAdress format. "
	::= { connSoftPvcEntry 12 }

connSoftPvcDstAtmAddressLength OBJECT-TYPE
	SYNTAX  INTEGER (4..160|-1)
	ACCESS	read-write
	STATUS	mandatory
	DESCRIPTION
		"The valid bit length of connSoftPvcDstAtmAddress.
		 The value(-1) is read-only.
		 The value(4..160) must be a multiple of 4."
	::= { connSoftPvcEntry 13 }

connSoftPvcDstAtmAddress OBJECT-TYPE
	SYNTAX  OCTET STRING (SIZE(0..20))
	ACCESS	read-write
	STATUS	mandatory
	DESCRIPTION
		"NodeId of destination node.
		 Its maximum length is 13 bytes.
		 This object length is 20 bytes in case AtmAddress is
		 setting.
		 If the last semi OCTET is invalid, it is padded
		 with 0xf.
		 The value of size(0) is read-only."
	::= { connSoftPvcEntry 14 }

connSoftPvcDstIfIndex OBJECT-TYPE
	SYNTAX	INTEGER (1..99|-1)
	ACCESS	read-write
	STATUS	mandatory
	DESCRIPTION
		"The number of the called line.
		(ifIndex of ifEntry)65 is GateWay."
	--	着呼側回線番号.
	--	(ifEntryのifIndex)65はGateWay.
	::= { connSoftPvcEntry 15 }

connSoftPvcDstVPI OBJECT-TYPE
	SYNTAX	INTEGER
	ACCESS	read-write
	STATUS	mandatory
	DESCRIPTION
		"VPI value of the called line."
	--	着呼側回線VPI番号.
	::= { connSoftPvcEntry 16 }

connSoftPvcDstVCI OBJECT-TYPE
	SYNTAX	INTEGER
	ACCESS	read-write
	STATUS	mandatory
	DESCRIPTION
		"VCI value of the called line."
	--	着呼側回線VCI番号.
	::= { connSoftPvcEntry 17 }

connSoftPvcRowStatus OBJECT-TYPE
	SYNTAX	INTEGER {
			active(1),
			notInService(2),
			notReady(3),
			createAndGo(4),		-- notSupported
			createAndWait(5),
			destroy(6)
		}
	ACCESS	read-write
	STATUS	mandatory
	DESCRIPTION
		"It is used from the manager to order the setting method
		of the Soft PVC connection.  It is used from the agent side
		to return the result of the connection setting request.

			   - 'active', which indicates that the
			   conceptual row is available for use by the
			   managed device;

			   - 'notInService', which indicates that the
			   conceptual row exists in the agent, but is
			   unavailable for use by the managed device;

			   - 'notReady', which indicates that the
			   conceptual row exists in the agent, but is
			   missing information necessary in order to be
			   available for use by the managed device;

			   - 'createAndGo', which is supplied by a
			   management station wishing to create a new
			   instance of a conceptual row and to have it
			   available for use by the managed device;

			   - 'createAndWait', which is supplied by a
			   management station wishing to create a new
			   instance of a conceptual row but not to have
			   it available for use by the managed device;
			   and,

			   - 'destroy', which is supplied by a
			   management station wishing to delete all of
			   the instances associated with an existing
			   conceptual row.
			"
	--	マネージャからはSoft PVCコネクションの設定方法指定のために
	--	用いられる。またエージェント側からはコネクション設定要求に
	--	対する結果を返す。
	::= { connSoftPvcEntry 18 }

connSoftPvcCause OBJECT-TYPE
	SYNTAX	INTEGER {
			rowExisting(1),		-- default value
			vpivciSrcBusy(2),
			vpivciDstBusy(3),
			vpivciOutOfRange(4),
			rateSrcOverFlow(5),
			rateDstOverFlow(6),
			dataTableFull(7),
			inconsistentVPVC(8),
			lineDiagnosis(9),
			missMatchTrfType(10),
			illegalSrcFileName(11),
			illegalDstFileName(12),
			lineOutOfOrder(13),
			illegalSrcShaper(14),
			illegalOperation(15),
			parameterIsNotEnough(16),
			diagnostics(17),
			otherFailure(18),
			illegalSrcRateForUPC(19),
			noCevc(20),
			noDlci(21),
			noSrcShaperForGateway(22),
			noPvcSrcShaperForGateway(23),
			missMatchTrfTypeSrcShaperForGateway(24),
			insusfficientPCRofProfile(25)
		}
	ACCESS	read-only
	STATUS	mandatory
	DESCRIPTION
		"Object to indicate the result of the connection setting."
	--	コネクション設定の結果を表示するためのオブジェクト.
	::= { connSoftPvcEntry 19 }

connSoftPvcRestRetry OBJECT-TYPE
	SYNTAX	INTEGER (0..15|-1)
	ACCESS	read-only
	STATUS	mandatory
	DESCRIPTION
		"Remaining number of retry
		 0  -  15  :  Remaining number of retry
		 -1        :  Infinite retry in progress"
	--	残りリトライ回数.
	::= { connSoftPvcEntry 20 }

connSoftPvcSrcFifoIndex		OBJECT-TYPE
	SYNTAX	INTEGER (0..16)
	ACCESS  read-write
	STATUS  mandatory
	DESCRIPTION
		" Designate the Shaper number of the calling line.
		 If the Shaping is not performed, designate 0. "
	--	発呼側回線のShaper番号の指定
	--	Ｓｈａｐｉｎｇしないときは,０指定
	::= { connSoftPvcEntry 21 }

connSoftPvcDstFifoIndex		OBJECT-TYPE
	SYNTAX	INTEGER (0..16)
	ACCESS  read-write
	STATUS  mandatory
	DESCRIPTION
		" Designate the Shaper number of the called line.
		  If the Shaping is not performed, designate 0.
		  However, if the called sw is not furnished with the shaping
		  function, this value has no meaning.
		  Since it cannot be recognized if this value is set on the
		  called side, the value is regarded as 'the value set by
		  the calling side'."
	--	着呼側回線のShaper 番号の指定
	--	Ｓｈａｐｉｎｇしないときは,０指定
	--	ただし,着呼側SWにシェーピング機能が実装されて
	--	いない場合は,この値は意味をなさない。
	--	現状は,着呼側に値が設定できたかどうか認識できない
	--	為,この値は『発呼側が設定した値』という位置付けになる.
	::= { connSoftPvcEntry 22 }

connSoftPvcNodeKind	OBJECT-TYPE
	SYNTAX	INTEGER {
			model5(1),
			model7(2),
			model5E(3)
	}
	ACCESS	read-write
	STATUS	mandatory
	DESCRIPTION
		"Designate/indicate the machine type on the called side. "
	--	着呼側のマシン種別を指定／表示
	::= { connSoftPvcEntry 23 }

connSoftPvcSrcParam1	OBJECT-TYPE
	SYNTAX	INTEGER {
			off(1),
			mode1(2),
			mode2(3),
			mode3(4),
			mode4(5),
			mode5(6)
	}
	ACCESS	read-write
	STATUS	mandatory
	DESCRIPTION
		"UPC mode of the calling line."
	--	発呼側回線のUPCモード.
	::= { connSoftPvcEntry 24 }

connSoftPvcDstParam1	OBJECT-TYPE
	SYNTAX	INTEGER {
			off(1),
			mode1(2),
			mode2(3),
			mode3(4),
			mode4(5),
			mode5(6)
	}
	ACCESS	read-write
	STATUS	mandatory
	DESCRIPTION
		"UPC mode of the called line."
	--	着呼側回線のUPCモード.
	::= { connSoftPvcEntry 25 }

--	connSoftPvcSrcParam1/connSoftPvcDstParam1
--	The restrictions of UPC mode settings
--	If ABR is designated, only off/mode1 can be designated.
--	If UBR is designated, only mode1/mode5/off can be
--	designated.
--	If nrt-VBR is designated, only mode2/mode3/mode4/off
--	can be designated.
--	If rt-VBR is designated, only mode2/mode3/mode4/off can
--	be designated.
--	If CBR is designated, only mode1/off can be designated.
--	UPCモードの設定
--	制限事項
--	ABR     指定時 は off/mode1
--	UBR     指定時 は mode1/mode5/off
--	nrt-VBR指定時  は mode2/mode3/mode4/off
--	rt-VBR 指定時  は mode2/mode3/mode4/off
--	CBR     指定時 は mode1/off
--	しか指定できない.

connSoftPvcSrcParam2	OBJECT-TYPE
	SYNTAX	DisplayString (SIZE(1..10|0))
	ACCESS	read-write
	STATUS	mandatory
	DESCRIPTION
		"Profile name of Forward.
		If nothing is designated, the string of size(0) is designated."
	--	Forwardのプロファイル名
	--	指定しない場合はsize 0の文字列を設定する.
	::= { connSoftPvcEntry 26 }

connSoftPvcDstParam2	OBJECT-TYPE
	SYNTAX	DisplayString (SIZE(1..10|0))
	ACCESS	read-write
	STATUS	mandatory
	DESCRIPTION
		"Profile name of Backward.
		If nothing is designated, the string of size(0) is designated."
	--	Backwardのプロファイル名
	--	指定しない場合はsize 0の文字列を設定する.
	::= { connSoftPvcEntry 27 }

connSoftPvcSrcParam3	OBJECT-TYPE
	SYNTAX	INTEGER
	ACCESS	read-only
	STATUS	mandatory
	DESCRIPTION
		"PCR[cell/s] of Forward.
		If the value is invalid, -1 is indicated."
	--	ForwardのPCR[cell/s].
	--	値が無効の場合 -1を表示する.
	::= { connSoftPvcEntry 28 }

connSoftPvcDstParam3	OBJECT-TYPE
	SYNTAX	INTEGER
	ACCESS	read-only
	STATUS	mandatory
	DESCRIPTION
		"PCR[cell/s] of Backward.
		If the value is invalid, -1 is indicated."
	--	BackwardのPCR[cell/s].
	--	値が無効の場合 -1を表示する.
	::= { connSoftPvcEntry 29 }

connSoftPvcSrcParam4	OBJECT-TYPE
	SYNTAX	INTEGER
	ACCESS	read-only
	STATUS	mandatory
	DESCRIPTION
		"SCR[cell/s] of Forward.
		If the value is invalid, -1 is indicated."
	--	ForwardのSCR[cell/s].
	--	値が無効の場合 -1を表示する.
	::= { connSoftPvcEntry 30 }

connSoftPvcDstParam4	OBJECT-TYPE
	SYNTAX	INTEGER
	ACCESS	read-only
	STATUS	mandatory
	DESCRIPTION
		"SCR[cell/s] of Backward.
		If the value is invalid, -1 is indicated."
	--	BackwardのSCR[cell/s].
	--	値が無効の場合 -1を表示する.
	::= { connSoftPvcEntry 31 }

connSoftPvcSrcParam5	OBJECT-TYPE
	SYNTAX	INTEGER
	ACCESS	read-only
	STATUS	mandatory
	DESCRIPTION
		"MBS[cell] of Forward.
		If the value is invalid, -1 is indicated."
	--	ForwardのMBS[cell].
	--	値が無効の場合 -1を表示する.
	::= { connSoftPvcEntry 32 }

connSoftPvcDstParam5	OBJECT-TYPE
	SYNTAX	INTEGER
	ACCESS	read-only
	STATUS	mandatory
	DESCRIPTION
		"MBS[cell] of Backward.
		If the value is invalid, -1 is indicated."
	--	BackwardのMBS[cell].
	--	値が無効の場合 -1を表示する.
	::= { connSoftPvcEntry 33 }

connSoftPvcSrcParam6	OBJECT-TYPE
	SYNTAX	INTEGER {
			on(1),
			off(2)
	}
	ACCESS	read-only
	STATUS	mandatory
	DESCRIPTION
		"EPD(Early Packet Discard) of Forward.
		Indicate if the discard processing in the unit of AAL5
		packet should be performed or not when the threshold is
		exceeded.
		If the value is invalid, off(2) is indicated."
	--	Forward方向のEPD(Early Packet Discard).
	--	しきい値を超えたときのAAL５パケット単位
	--	の廃棄処理を行なうかを表示.
	--	値が無効な場合は, off(2)を表示.
	::= { connSoftPvcEntry 34 }

connSoftPvcDstParam6	OBJECT-TYPE
	SYNTAX	INTEGER {
			on(1),
			off(2)
	}
	ACCESS	read-only
	STATUS	mandatory
	DESCRIPTION
		"EPD(Early Packet Discard) of Backward.
		Indicate if the discard processing in the unit of AAL5
		packet should be performed or not when the threshold is
		exceeded.
		If the value is invalid, off(2) is indicated."
	--	Backward方向のEPD(Early Packet Discard).
	--	しきい値を超えたときのAAL５パケット単位
	--	の廃棄処理を行なうかを表示.
	--	値が無効な場合は, off(2)を表示.
	::= { connSoftPvcEntry 35 }

connSoftPvcSrcParam7	OBJECT-TYPE
	SYNTAX	INTEGER
	ACCESS	not-accessible
	STATUS	mandatory
	DESCRIPTION
		"MCR[cell/s]. Not supported here."
	--	MCR[cell/s]. 今回未サポート.
	::= { connSoftPvcEntry 36 }

connSoftPvcDstParam7	OBJECT-TYPE
	SYNTAX	INTEGER
	ACCESS	not-accessible
	STATUS	mandatory
	DESCRIPTION
		"MCR[cell/s]. Not supported here."
	--	MCR[cell/s]. 今回未サポート.
	::= { connSoftPvcEntry 37 }

ConnSoftPvcEstSrcInfIndex ::= INTEGER (1..128)

connSoftPvcEstablishedSrcInfTable OBJECT-TYPE
	SYNTAX	SEQUENCE OF ConnSoftPvcEstablishedSrcInfEntry
	ACCESS	not-accessible
	STATUS	mandatory
	DESCRIPTION
		" The table regarding the calling node of the Soft
		PVPC/PVCC established as called side office by the local node"
	--	自ノードが着側局として確立しているSoft PVPC/PVCCの
	--	発側ノードに関するテーブル.
	::= { conn 6 }

connSoftPvcEstablishedSrcInfEntry OBJECT-TYPE
	SYNTAX	ConnSoftPvcEstablishedSrcInfEntry
	ACCESS	not-accessible
	STATUS	mandatory
	DESCRIPTION
		" The entry of the calling side node information of the
		Soft PVPC/PVCC established as the called side office by
		the local node"
	--	自ノードが着側局として確立しているSoft PVPC/PVCCの
	--	発側ノード情報のエントリ.
	INDEX	{ connSoftPvcEstSrcInfIndex }
	::= { connSoftPvcEstablishedSrcInfTable 1 }

ConnSoftPvcEstablishedSrcInfEntry ::=
	SEQUENCE {
		connSoftPvcEstablishedSrcInf
			Opaque,
		connSoftPvcEstSrcInfIndex
			ConnSoftPvcEstSrcInfIndex
	}

connSoftPvcEstablishedSrcInf OBJECT-TYPE
	SYNTAX	Opaque
	ACCESS	read-only
	STATUS	mandatory
	DESCRIPTION
	" The calling node information of the Soft PVPC/PVCC
	  established as called side office by the node.
	  The structure of the entry is as follows
			 struct {
				long	SrcAtmAddressFormat;
				long	SrcAtmAddressLength;
				char	SrcAtmAddress[20];
			 };
	(*1) 'long' data should be stored with 'big endian'.
	(*2) For SrcAtmAddress data, if it is less than 20 byte,
	the data padded by '0xf' shall be stored.
	This information is divided into up to 32 pieces, and each
	piece is put into the head 4 bytes (count) of an entry.  The
	data which contains the number of the entries is described
	below.

			+-----------------+
			|      count      | (= n)
			+-----------------+
			|   EstSrcInf 1   |
			|.................|
			|   EstSrcInf 2   |
			|.................|
			|        .        |
			|        .        |
			|        .        |
			|.................|
			|   EstSrcInf n   | ( 1 <= n <= 32 )
			+-----------------+
		"
	--	ノードが着側局として確立しているSoft PVPC/PVCCの
	--	 発側ノード情報.
	--	 エントリの構造は以下の通り.
	--
	--	 struct {
	--		long	SrcAtmAddressFormat;
	--		long	SrcAtmAddressLength;
	--		char	SrcAtmAddress[20];
	--	 };
	--	 (*1) longデータはbig endianで格納すること.
	--	 (*2) SrcAtmAddressデータは, 20byteに満たない場合,
	--	      0xfでpaddingしたデータを格納すること.
	--
	--	 この情報を最大３２個ずつまとめ, 先頭4byte(count)に
	--	 まとめたエントリの個数を格納したデータ.
	::= { connSoftPvcEstablishedSrcInfEntry 1 }

connSoftPvcEstSrcInfIndex	OBJECT-TYPE
	SYNTAX	ConnSoftPvcEstSrcInfIndex
	ACCESS	not-accessible
	STATUS	mandatory
	::= { connSoftPvcEstablishedSrcInfEntry 2 }


connOam			OBJECT IDENTIFIER ::= { conn 7 }

	--	<< OAM-END-Point/connection-point setting/procedure of delete >>

	-- 1. Set allocate
  	-- 	The manager acquires the right to set OAM
	--	End-point/Connecting-point, by setting
	--	connOamOpeStatus to 'allocate'.  Then, the agent
	--	sets each parameter to the default value.
	--	The default values are described below.

	--		connOamOpeCause    : succeed(2)
	--		connOamOpePoint    : end-point(1)
	--		connOamOpeMode     : f4(1)
	--		connOamOpeSection  : segment(1)
	--		connOamOpePort1    : None (-1)
	--		connOamOpePort2    : None (-1)
	--		connOamOpeVpi1     : None (-1)
	--		connOamOpeVpi2     : None (-1)
	--		connOamOpeVci1     : None (-1)
	--		connOamOpeVci2     : None (-1)

	--	2. Set each parameter
	--		Set each parameter to a proper value.

	--	3. Set add/delete
	--	Set connOamOpeStatus to 'add'/'delete'.
	--	Then, the agent checks each parameter and sets/deletes
	--	End-point/Connecting-point.  Also the result will be
	--	reflected in connOamOpeCause.

	--	4. Get the result
	--		The manager gets connOamOpeCause.

	--	5. Set 'free'
	--		When the above states processing ends, the manager must
	--		set connOamOpeStatus to 'free' and release the right to
	--		set/delete.

	--	<< OAM End-point / Connecting-point 設定/削除手順 >>

	--	1. allocate の SET
	--		Manager は connOamOpeStatus に allocate を SET
	--		することにより, OAM End-point / Connecting-point
	--		を設定するための権利を取得する.
	--		これにより Agent は各パラメータに Default 値を設定する.

	--		Default 値は以下の通りである.
	--		connOamOpeCause    : succeed(2)
	--		connOamOpePoint    : end-point(1)
	--		connOamOpeMode     : f4(1)
	--		connOamOpeSection  : segment(1)
	--		connOamOpePort1    : なし(-1)
	--		connOamOpePort2    : なし(-1)
	--		connOamOpeVpi1     : なし(-1)
	--		connOamOpeVpi2     : なし(-1)
	--		connOamOpeVci1     : なし(-1)
	--		connOamOpeVci2     : なし(-1)

	--	2. 各パラメータの SET
	--		各パラメータに値を SET する.

	--	3. add / delete の SET
	--		connOamOpeStatus に add (追加時) / delete (削除時) を
	--		SET する. これにより Agent は各パラメータのチェックを
	--		行い, End-point / Connecting-point の設定 / 削除処理を
	--		行う. また, connOamOpeCause に結果を反映させる.

	--	4. 結果の GET
	--		Manager は connOamOpeCause を GET する.

	--	5. free の SET
	--		Manager は上記処理の終了時には connOamOpeStatus に
	--		free を SET し, 設定/削除処理を行う権利を必ず解放
	--		しなければならない.

connOamOpe	OBJECT IDENTIFIER ::= { connOam 1 }

connOamOpeStatus	OBJECT-TYPE
	SYNTAX	INTEGER {
			allocate (1),	-- acquire the right to set/delete.
			add      (2),	-- order to add.
			delete   (3),	-- order to delete.
			free     (4)	-- release the right to set/delete.
		}
	ACCESS	read-write
	STATUS	mandatory
	DESCRIPTION
		" Used to set/delete OAM End-point, Connecting-point."
	--	OAM End-point, Connecting-point 設定/削除処理の操作に使用.
	::= { connOamOpe 1 }

connOamOpeCause	OBJECT-TYPE
	SYNTAX	INTEGER {
			other                (1), -- Error other than
						  -- below stated.
			succeed              (2), -- Set/delete processing
						  -- completed successfully.
			parameterIsNotEnough (3), -- Parameter is not enough.
			tableIsFull          (4), -- Table overflow.
			illegalPoint         (5), -- Illegal point.
			illegalMode          (6), -- Illegal mode.
			illegalSection       (7), -- Illegal section.
						  -- notSupported.
			illegalPort          (8), -- Illegal line number.
			illegalVpiVci        (9), -- Illegal VPI/VCI.
			invalidBufferType   (10), -- Buffer of the designated
						  -- line is no supported in
						  -- this function.
			noSuchConnection    (11), -- Designated connection does
						  -- not exist.
			alreadyRegistered   (12), -- Already registered.
			notExisting         (13)  -- Not registered.
		}
	ACCESS	read-only
	STATUS	mandatory DESCRIPTION
		" The result of the processing to set/delete OAM End-point,
		Connecting-point."
	--	OAM End-point, Connecting-point 設定/削除処理の結果.
	::= { connOamOpe 2 }

connOamOpePoint	OBJECT-TYPE
	SYNTAX	INTEGER {
			end-point        (1),
			connecting-point (2)
		}
	ACCESS	read-write
	STATUS	mandatory
	DESCRIPTION
		"End-point / Connecting-point."
	::= { connOamOpe 3 }

connOamOpeMode	OBJECT-TYPE
	SYNTAX	INTEGER {
			f4 (1),
			f5 (2)
		}
	ACCESS	read-write
	STATUS	mandatory
	DESCRIPTION
		" Mode. F4 (VP level)/f5 (VC level) "
	--	Mode. f4 (VPレベル) / f5 (VCレベル).
	::= { connOamOpe 4 }

connOamOpeSection	OBJECT-TYPE
	SYNTAX	INTEGER {
			segment    (1),
			end-to-end (2)
		}
	ACCESS	read-write
	STATUS	mandatory
	DESCRIPTION
		" Point between segments/End-to-End point."
	--	Segment 間の Point / End-to-End 間の Point.
	::= { connOamOpe 5 }

connOamOpePort1	OBJECT-TYPE
	SYNTAX	INTEGER
	ACCESS	read-write
	STATUS	mandatory
	DESCRIPTION
		" Line number"
	--	回線番号.
	::= { connOamOpe 6 }

connOamOpePort2	OBJECT-TYPE
	SYNTAX	INTEGER
	ACCESS	read-write
	STATUS	mandatory
	DESCRIPTION
		" Line number.  Upon setting/deleting end-point, don't
		care about it."
	--	回線番号. End-point の設定/削除時は Don't care.
	::= { connOamOpe 7 }

connOamOpeVpi1	OBJECT-TYPE
	SYNTAX	INTEGER
	ACCESS	read-write
	STATUS	mandatory
	DESCRIPTION
		"VPI."
	::= { connOamOpe 8 }

connOamOpeVpi2	OBJECT-TYPE
	SYNTAX	INTEGER
	ACCESS	read-write
	STATUS	mandatory
	DESCRIPTION
		" VPI.  Upon setting/deleting end-point, don't care about it. "
	--	VPI. End-point の設定/削除時は Don't care.
	::= { connOamOpe 9 }

connOamOpeVci1	OBJECT-TYPE
	SYNTAX	INTEGER
	ACCESS	read-write
	STATUS	mandatory
	DESCRIPTION
		" VCI. JpnToEng[f4 レベル の設定/削除時は Don't care.]"
	--	VCI. f4 レベル の設定/削除時は Don't care.
	::= { connOamOpe 10 }

connOamOpeVci2	OBJECT-TYPE
	SYNTAX	INTEGER
	ACCESS	read-write
	STATUS	mandatory
	DESCRIPTION
		" VCI. JpnToEng[End-point または f4 レベル の設定/削除時は
		Don't care.]"
	--	VCI. End-point または f4 レベル の設定/削除時は Don't care.
	::= { connOamOpe 11 }

connOamTable	OBJECT-TYPE
	SYNTAX	SEQUENCE OF ConnOamEntry
	ACCESS	not-accessible
	STATUS	mandatory
	DESCRIPTION
		" OAM End-point, Connecting-point indication table "
	--	OAM End-point, Connecting-point 表示テーブル.
	::= { connOam 2 }

connOamEntry	OBJECT-TYPE
	SYNTAX	ConnOamEntry
	ACCESS	not-accessible
	STATUS	mandatory
	DESCRIPTION
		" OAM End-point, Connecting-point indication entry "
	--	OAM End-point, Connecting-point 表示テーブルのエントリ.
	INDEX	{ connOamPort, connOamIndex }
	::= { connOamTable 1 }

ConnOamEntry ::=
	SEQUENCE {
		connOamPort		INTEGER,
		connOamIndex		INTEGER,
		connOamContrastPort	INTEGER,
		connOamVpi		INTEGER,
		connOamContrastVpi	INTEGER,
		connOamVci		INTEGER,
		connOamContrastVci	INTEGER,
		connOamPoint		INTEGER,
		connOamMode		INTEGER,
		connOamSection		INTEGER,
		connOamStatus		INTEGER,
		connOamDefectType	INTEGER,
		connOamDefectNodeID	OCTET STRING
	}

connOamPort	OBJECT-TYPE
	SYNTAX	INTEGER
	ACCESS	not-accessible
	STATUS	mandatory
	DESCRIPTION
		" Line number"
	--	回線番号.
	::= { connOamEntry 1 }

connOamIndex	OBJECT-TYPE
	SYNTAX	INTEGER (1..144)
	ACCESS	not-accessible
	STATUS	mandatory
	DESCRIPTION
		"OAM End-point / Connecting-point Index."
	::= { connOamEntry 2 }

connOamContrastPort	OBJECT-TYPE
	SYNTAX	INTEGER
	ACCESS	read-only
	STATUS	mandatory
	DESCRIPTION
		" Line number of the opposite line. For End-point, -1."
	--	対照の回線番号. End-point の場合は -1.
	::= { connOamEntry 3 }

connOamVpi	OBJECT-TYPE
	SYNTAX	INTEGER
	ACCESS	read-only
	STATUS	mandatory
	DESCRIPTION
		"VPI."
	::= { connOamEntry 4 }

connOamContrastVpi	OBJECT-TYPE
	SYNTAX	INTEGER
	ACCESS	read-only
	STATUS	mandatory
	DESCRIPTION
		" Opposite VPI.  For End-point, -1. "
	--	対照の VPI. End-point の場合は -1.
	::= { connOamEntry 5 }

connOamVci	OBJECT-TYPE
	SYNTAX	INTEGER
	ACCESS	read-only
	STATUS	mandatory
	DESCRIPTION
		" VCI.  For the f4 level, -1."
	--	VCI. f4 レベルの 場合は,-1.
	::= { connOamEntry 6 }

connOamContrastVci	OBJECT-TYPE
	SYNTAX	INTEGER
	ACCESS	read-only
	STATUS	mandatory
	DESCRIPTION
		" Opposite VCI. JpnToEng[End-point または
		f4レベルの場合は -1.]"
	--	対照の VCI. End-point または f4レベルの場合は -1.
	::= { connOamEntry 7 }

connOamPoint	OBJECT-TYPE
	SYNTAX	INTEGER {
			end-point        (1),
			connecting-point (2)
		}
	ACCESS	read-only
	STATUS	mandatory
	DESCRIPTION
		"End-point / Connecting-point."
	::= { connOamEntry 8 }

connOamMode	OBJECT-TYPE
	SYNTAX	INTEGER {
			f4 (1),
			f5 (2)
		}
	ACCESS	read-only
	STATUS	mandatory
	DESCRIPTION
		" Mode. F4 (VP level)/f5 (VC level). "
	--	Mode. f4 (VPレベル) / f5 (VCレベル).
	::= { connOamEntry 9 }

connOamSection	OBJECT-TYPE
	SYNTAX	INTEGER {
			segment    (1),
			end-to-end (2)
		}
	ACCESS	read-only
	STATUS	mandatory
	DESCRIPTION
		" Point between segments/End-to-End point."
	--	Segment 間の Point / End-to-End 間の Point.
	::= { connOamEntry 10 }

connOamStatus	OBJECT-TYPE
	SYNTAX	INTEGER {
			other (1),	-- Not related status indication.
					-- (The connection is connecting-point)
			normal (2),	-- Normal line.
			receive-AIS (3),-- AIS cell is received.
			receive-RDI (4),-- RDI cell is received.
			failure (5)	-- Receive fault occurred.
		}
	ACCESS	read-only
	STATUS	mandatory
	DESCRIPTION
		" Receive status of end-point."
	--	End-point の受信状態.
	::= { connOamEntry 11 }

connOamDefectType	OBJECT-TYPE
	SYNTAX	INTEGER {
			normal (1),
			los (2),
			lof (3),
			loc (4),
			ais-path (5),
			ais-section (6),
			yellow-section (7),	-- notSupported
			yellow-path (8),	-- notSupported
			lop (9),
			ais (10),
			payload-all-one (11),
			rai (12),		-- notSupported
			oof (13) ,
			idle (14),		-- notSupported
			rdi (15),		-- notSupported
			plcp-oof (16),
			plcp-lof (17),
			plcp-yellow (18),	-- notSupported
			red(19)
		}
	ACCESS	read-only
	STATUS	mandatory
	DESCRIPTION
		" Fault cause in the receive cell.
		For Connecting-point, return 'normal (1)'."
	--	受信セル内の故障要因.
	--	Connecting-point の場合は常に normal(1) を返す.
	::= { connOamEntry 12 }

connOamDefectNodeID	OBJECT-TYPE
	SYNTAX	OCTET STRING( SIZE (13) )
	ACCESS	read-only
	STATUS	mandatory
	DESCRIPTION
		" Node ID of the Switch which sends alarm transfer cells.
		For connecting-point, return '0 length string'."
	--	警報転送セル送出元 Switch の Node ID.
	--	Connecting-point の場合は常に 0 length string を返す.
	::= { connOamEntry 13 }

connLoop		OBJECT IDENTIFIER ::= { conn 8 }

connLoopOpe	OBJECT IDENTIFIER ::= { connLoop 1 }

	--	JpnToEng(次から９３行分を)
	--	<< ループバック試験実施の手順 >>

	--	1. allocate の SET
	--		Manager は connLoopOpeStatus に allocate を SET
	--		することにより, ループバック試験を行うための権利
	--		を取得する.
	--		これにより Agent は以下の Object に Default 値を
	--		設定する. Default 値は
	--			connLoopOpeCause                  1
	--			connLoopOpeMode                   1
	--			connLoopOpeBase                   1
	--			connLoopOpeLoopBackPointNodeId    0 length string
	--			connLoopOpeCorrelationTag         0 length string
	--			connLoopOpeCount                  1
	--			connLoopOpePort                  -1
	--			connLoopOpeVpi                   -1
	--			connLoopOpeVci                   -1
	--			connLoopOpeNormalEndCount        -1
	--			connLoopOpeAbnormalEndCount      -1
	--			connLoopOpeAbortCount            -1
	--			connLoopOpeLoopBackPointIdLength -1
	--		である.

	--	2. 各パラメータ の SET
	--		各パラメータに値を SET する.

	--	3. action の SET
	--		connLoopOpeStatus に action を SET する.
	--		これにより Agent はパラメータやリソースのチェックを
	--		行い, 問題がなければループバック試験を開始する.
	--		パラメータやリソースに問題があった場合は,
	--		connLoopOpeStatus を endtest に変更し, 要因を
	--		connLoopOpeCause に反映させる.

	--	4. connLoopOpeStatus の GET
	--		Manager は connLoopOpeStatus が action ならば
	--		ループバック試験実行中, endtest ならばループバック
	--		試験終了と判断する.
	--		正常終了時, Agent は connLoopOpeCause に succeed を
	--		設定する.
	--		異常終了時は要因を connLoopOpeCause に設定する.

	--	5. 試験結果の GET
	--		Agent は connLoopOpeCount に SET された回数分
	--		ループバック試験を行い, 結果を以下にカウントする.
	--		正常終了 : connLoopOpeNormalEndCount   (A)
	--		異常終了 : connLoopOpeAbnormalEndCount (B)
	--		試験中断 : connLoopOpeAbortCount       (C)
	--		connLoopOpeCause が succeed のときは
	--			connLoopOpeCount = (A) + (B) + (C)
	--		となる.

	--		ループバック試験中の中断は,サポートしていない.

	--	6. free の SET
	--		Manager は上記処理の終了時には connLoopOpeStatus に
	--		free を SET し, ループバック試験を行う権利を必ず解放
	--		しなければならない.

	--	<< 制限事項 >>

	--	1. 排他制御

	--		connLoopOpe 配下の Object への SET に対して以下
	--		のような排他制御を行っている.

	--	  1-1. connLoopOpeStatus

	--		以下の条件を満たす場合のみ SET 可能である.
	--		条件を満たさない場合は genErr を返す.

	--		<< 条件 >>
	--		allocate (1) : connLoopOpeStatus が free である.
	--		action   (2) : allocate した Manager である, かつ
	--		               connLoopOpeStatus が allocate である.
	--		endtest  (3) : allocate した Manager である, かつ
	--		               connLoopOpeStatus が action である.
	--		free     (4) : a. b. c. の何れかである.
	--		               a. connLoopOpeStatus が free である.
	--		               b. allocate した Manager である, かつ
	--		                  connLoopOpeStatus が allocate,
	--		                  endtest の何れかである.
	--		               c. allocate した Manager でない, かつ
	--		                  allocate した Manager の connLoopOpe
	--		                  配下の Object への最後の Access から
	--		                  60 秒以上経過している, かつ
	--		                  connLoopOpeStatus が allocate,
	--		                  endtest の何れかである.

	--	  1-2. connLoopOpeStatus 以外

	--		allocate した Manager のみ SET 可能である.
	--		それ以外の Manager からの SET に対しては genErr を返す.

connLoopOpeStatus	OBJECT-TYPE
	SYNTAX	INTEGER	{
			allocate (1),	-- JpnToEng[ループバック試験を行う権利の取得.]
			action   (2),	-- JpnToEng[ループバック試験の実行.]
			endtest  (3),	-- JpnToEng[ループバック試験の終了.]
			free     (4)	-- JpnToEng[ループバック試験を行う権利の解放]
		}
	ACCESS	read-write
	STATUS	mandatory
	DESCRIPTION
		"JpnToEng[ループバック試験の操作.]"
	--	ループバック試験の操作.
	::= { connLoopOpe 1 }

connLoopOpeCause	OBJECT-TYPE
	SYNTAX	INTEGER	{
			succeed          (1), -- JpnToEng[ループバック試験終了(SWでの中断も含む).]
			abort            (2), -- JpnToEng[Manager からの中断要求によるテスト終了.]
			other            (3), -- JpnToEng[下記以外の NG 要因.]
			vpivciOutOfRange (4), -- JpnToEng[VPI/VCI値異常.]
			parameterFailed  (5), -- JpnToEng[以下のパラメータの何れかが異常. Mode, Base, Count, Port.]
			admindown        (6), -- JpnToEng[指定回線が Admin-down 状態.]
			nonePkg          (7), -- JpnToEng[指定回線ＰＫＧが抜出状態.]
			noneBuffer2      (8), -- JpnToEng[指定回線ＰＫＧが Buffer2 でない.]
			lineLoopback     (9), -- JpnToEng[指定回線がＰＫＧ内部で LoopBack 状態.]
			resetSlot        (10), -- JpnToEng[指定回線ＰＫＧが RESET 中.]
			noneLoopBackId   (11), -- JpnToEng[Switch に LoopBack ID が設定されていない.]
			execute          (12) -- JpnToEng[既にループバック試験実行中.]
		}
	ACCESS	read-only
	STATUS	mandatory
	DESCRIPTION
		"JpnToEng[ループバック試験の結果.]"
	--	ループバック試験の結果.
	::= { connLoopOpe 2 }

connLoopOpeMode	OBJECT-TYPE
	SYNTAX	INTEGER	{
			f4 (1),
			f5 (2)
		}
	ACCESS	read-write
	STATUS	mandatory
	DESCRIPTION
		"F4 (VP level)/f5 (VC level)."
	--	f4 (VPレベル) / f5 (VCレベル).
	::= { connLoopOpe 3 }

connLoopOpeBase	OBJECT-TYPE
	SYNTAX	INTEGER	{
			segment (1),
			end-end (2)
		}
	ACCESS	read-write
	STATUS	mandatory
	DESCRIPTION
		"JpnToEng[テストベースのフロー.]"
	--	テストベースのフロー.
	::= { connLoopOpe 4 }

connLoopOpeLoopBackPointNodeId	OBJECT-TYPE
	SYNTAX	OCTET STRING ( SIZE (16) )
	ACCESS	read-write
	STATUS	mandatory
	DESCRIPTION
		"JpnToEng[ループバックセルを折り返す Switch の LoopBackID.]"
	--	ループバックセルを折り返す Switch の LoopBackID.
	::= { connLoopOpe 5 }

connLoopOpeCorrelationTag	OBJECT-TYPE
	SYNTAX	OCTET STRING ( SIZE (4) )
	ACCESS	read-write
	STATUS	mandatory
	DESCRIPTION
		"JpnToEng[送信したセルと受信したセルを
		 対応付けるための情報.]"
	--	送信したセルと受信したセルを対応付けるための情報.
	::= { connLoopOpe 6 }

connLoopOpeCount	OBJECT-TYPE
	SYNTAX	INTEGER (1..16)
	ACCESS	read-write
	STATUS	mandatory
	DESCRIPTION
		"JpnToEng[ループバック試験の実施回数.]"
	--	ループバック試験の実施回数.
	::= { connLoopOpe 7 }

connLoopOpePort	OBJECT-TYPE
	SYNTAX	INTEGER
	ACCESS	read-write
	STATUS	mandatory
	DESCRIPTION
		"JpnToEng[送出元の回線番号.]"
	--	送出元の回線番号.
	::= { connLoopOpe 8 }

connLoopOpeVpi	OBJECT-TYPE
	SYNTAX	INTEGER
	ACCESS	read-write
	STATUS	mandatory
	DESCRIPTION
		"JpnToEng[送出元の VPI.]"
	--	送出元の VPI.
	::= { connLoopOpe 9 }

connLoopOpeVci	OBJECT-TYPE
	SYNTAX	INTEGER
	ACCESS	read-write
	STATUS	mandatory
	DESCRIPTION
		"JpnToEng[送出元の VCI.
		f4 (VPレベル) での処理時は Don't care とする.]"
	--	送出元の VCI.
	--	f4 (VPレベル) での処理時は Don't care とする.
	::= { connLoopOpe 10 }

connLoopOpeNormalEndCount	OBJECT-TYPE
	SYNTAX	INTEGER
	ACCESS	read-only
	STATUS	mandatory
	DESCRIPTION
		"JpnToEng[ループバック試験正常終了回数.]"
	--	ループバック試験正常終了回数.
	::= { connLoopOpe 11 }

connLoopOpeAbnormalEndCount	OBJECT-TYPE
	SYNTAX	INTEGER
	ACCESS	read-only
	STATUS	mandatory
	DESCRIPTION
		"JpnToEng[ループバック試験異常終了回数.]"
	--	ループバック試験異常終了回数.
	::= { connLoopOpe 12 }

connLoopOpeAbortCount	OBJECT-TYPE
	SYNTAX	INTEGER
	ACCESS	read-only
	STATUS	mandatory
	DESCRIPTION
		"JpnToEng[ループバック試験中断回数.]"
	--	ループバック試験中断回数.
	::= { connLoopOpe 13 }

connLoopOpeLoopBackPointIdLength	OBJECT-TYPE
	SYNTAX	INTEGER
	ACCESS	read-write
	STATUS	mandatory
	DESCRIPTION
		"JpnToEng[ループバックセルを折り返す Switch の LoopBack Location ID
		 の入力サイズ(bit長).ただし,4ビット単位できりあげ.]"
	--	ループバックセルを折り返す Switch の LoopBack Location ID
	--	の入力サイズ(bit長).ただし,4ビット単位できりあげ.
	::= { connLoopOpe 14 }

connProfile		OBJECT IDENTIFIER ::= { conn 9 }

	--	Type used for connProfile.

		ConnProfileIndex ::= INTEGER
		--	Index of connProfileTable.
		--	connProfileTable の インデックス.

	--	<>

	--	1. Get connProfileIndex
        --	The manager obtains the Index of connProfileTable
	--	(connProfileIndex), by getting connProfileIndexNext.

	--	2. Set createAndWait
	--	Set connProfileRowStatus to createAndWait, using the
	--	obtained connProfileIndex as Index.  Then, the agent set
	--	each parameter to the default value and make
	--	connProfileRowStatus to notRedy.
	--	Default values are stated below.
	--		connProfileTrafficType : traffic-UBR(5)
	--		connProfileName        : None (0 length string)
	--		connProfileParam1      : None (-1)
	--		connProfileParam2      : None (-1)
	--		connProfileParam3      : None (-1)
	--		connProfileParam4      : off(1)
	--		In this table, only one non-active row (i.e., a row
	--		whose status is notReady or notInservice) can exist
	--		at a time.
	--	3. Set each parameter
	--	For parameters which don't have default values or default
	--	values should not be set to, set them to proper values.
	--	The agent changes connProfileRowStatus to notInService, if
	--	connProfileTrafficType, connProfileName and
	--	connProfileParam4 have been set.
	--	Required parameters differ according to the traffic type.
	--	The traffic types and the required parameters are stated
	--	as below.
	--	("connProfile" part is omitted.)

	--	 =======================================================
	--	|TrafficType	||Name	|Param1	|Param2	|Param3	|Param4	|
	--	|=======================================================|
	--	|CBR		||  *	|   *	|	|	|   *	|
	--	|- - - - - - - - - - - - - - - - - - - - - - - - - - - -|
	--	|rt-VBR		||  *	|   *	|   *	|   *	|   *	|
	--	|- - - - - - - - - - - - - - - - - - - - - - - - - - - -|
	--	|nrt-VBR	||  *	|   *	|   *	|   *	|   *	|
	--	|- - - - - - - - - - - - - - - - - - - - - - - - - - - -|
	--	|ABR		||  *	|   *	|	|	|   *   |
	--	|- - - - - - - - - - - - - - - - - - - - - - - - - - - -|
	--	|UBR		||  *	|   *	|	|	|   *	|
	--	 =======================================================
	--	* column: mandatory(JpnToEng[ただし, ABRの Param1 は 値無し(-1)にも対応する.])


	--	4. Set active
	--	The manager sets connProfileRowStatus to active.  Then,
	--	the agent checks parameters and resources and registers
	--	the profiles.

	--	5. Get the result
	--	Get connProfileRowStatus, and if it is active, the profile
	--	setting has successfully completed.  If it is notInService,
	--	the setting has failed.  Get connProfileCause and see the cause.

	--	<>

	--	1. Set "destroy"
	--	Set connProfileRowStatus of the profile to be deleted,
	--	to "destroy".
	--	Then, the agent will delete the profile.

	--	2. Get the result
	--	If the deletion has successfully completed, the object of
	--	"get" subordinate to the connProfileTable of the designated
	--	index becomes noSuchName.

	--	<< Profile 設定手順 >>

	--	1. connProfileIndex の GET
	--		Manager は connProfileIndexNext を GET すること
	--		により, connProfileTable の Index (connProfileIndex)
	--		を得る.

	--	2. createAndWait の SET
	--		取得した connProfileIndex を Index として
	--		connProfileRowStatus に createAndWait を SET する.
	--		これにより Agent は各パラメータに Default 値を設定し,
	--		connProfileRowStatus を notReady にする.

	--		Default 値は以下の通りである.
	--		connProfileTrafficType : traffic-UBR(5)
	--		connProfileName        : なし(0 length string)
	--		connProfileParam1      : なし(-1)
	--		connProfileParam2      : なし(-1)
	--		connProfileParam3      : なし(-1)
	--		connProfileParam4      : off(1)

	--		このテーブルでは,  非active な row ( i.e. Row の
	--		Status が notReady か notInService である row )
	--		は, 同時に 1 つのみ 存在可能.

	--	3. 各パラメータの SET
	--		デフォルト値がないもの,デフォルト値を使用したくないも
	--		のに関して,値をsetする.
	--		Agent は connProfileTrafficType, connProfileName そして
	--		connProfileParam4が設定されたならば,connProfileRowStatus
	--		を notInService に変更する.

	--		必要なパラメータはトラヒックタイプにより異なる.
	--		その対応を以下に示す.

	--		TrafficTypeと必要なパラメータの対応
	--				("connProfile"部分は省略)
	--	 =======================================================
	--	|TrafficType	||Name	|Param1	|Param2	|Param3	|Param4	|
	--	|=======================================================|
	--	|CBR		||  *	|   *	|	|	|   *	|
	--	|- - - - - - - - - - - - - - - - - - - - - - - - - - - -|
	--	|rt-VBR		||  *	|   *	|   *	|   *	|   *	|
	--	|- - - - - - - - - - - - - - - - - - - - - - - - - - - -|
	--	|nrt-VBR	||  *	|   *	|   *	|   *	|   *	|
	--	|- - - - - - - - - - - - - - - - - - - - - - - - - - - -|
	--	|ABR		||  *	|   *	|	|	|   *   |
	--	|- - - - - - - - - - - - - - - - - - - - - - - - - - - -|
	--	|UBR		||  *	|   *	|	|	|   *	|
	--	 =======================================================
	--	*印欄: 	必要 (ただし, ABRの Param1 は 値無し(-1)にも対応する)

	--	4. active の SET
	--		Manager は connProfileRowStatus に active を SET する.
	--		これにより Agent はパラメータやリソースのチェックを行い,
	--		Profile の登録処理を行う.

	--	5. 結果の GET
	--		connProfileRowStatus の GET を行い, active ならば
	--		Profile 設定成功である. notInService ならば設定失敗
	--		であるので connProfileCause を GET して要因を見る.

	--	<< Profile 削除手順 >>

	--	1. destroy の SET
	--		削除したい Profile の connProfileRowStatus に
	--		destroy を SET する.
	--		これにより Agent は Profile の削除処理を行う.

	--	2. 結果の GET
	--		削除成功の場合は, 指定 Index の connProfileTable 配下
	--		の Object の GET は noSuchName となる.

connProfileIndexNext	OBJECT-TYPE
		SYNTAX	ConnProfileIndex
		ACCESS	read-only
		STATUS	mandatory
		DESCRIPTION
		"Shows the empty index value of connProfileTable(including
		row of notReady, notInService).
		If the number of profiles reaches the registration limit, 0. "
	--	connProfileTable の空き(notReady,notInServiceのrowを含む)
	--	Index 値を表す.
	--	既に登録可能な Profile 数を満たしている場合の値は 0.
	::= { connProfile 1 }

connProfileTable	OBJECT-TYPE
	SYNTAX	SEQUENCE OF ConnProfileEntry
	ACCESS	not-accessible
	STATUS	mandatory
	DESCRIPTION
		" Table to set/indicate the profile. "
	--	Profile の設定 / 表示を行うためのテーブル.
	::= { connProfile 2 }

connProfileEntry	OBJECT-TYPE
	SYNTAX	ConnProfileEntry
	ACCESS	not-accessible
	STATUS	mandatory
	DESCRIPTION
		" Entry of connProfileTable."
	--	connProfileTable のエントリ.
	INDEX	{ connProfileIndex }
	::= { connProfileTable 1 }

ConnProfileEntry ::=
	SEQUENCE {
		connProfileIndex        ConnProfileIndex,
		connProfileRowStatus    INTEGER,
		connProfileCause        INTEGER,
		connProfileTrafficType  INTEGER,
		connProfileName         DisplayString,
		connProfileParam1       INTEGER,
		connProfileParam2       INTEGER,
		connProfileParam3       INTEGER,
		connProfileParam4       INTEGER
	}

connProfileIndex	OBJECT-TYPE
	SYNTAX	ConnProfileIndex
	ACCESS	not-accessible
	STATUS	mandatory
	DESCRIPTION
		" Index value of connProfileTable."
	--	connProfileTableの Index 値.
	::= { connProfileEntry 1 }

connProfileRowStatus	OBJECT-TYPE
	SYNTAX	INTEGER	{
			active        (1),
			notInService  (2),	-- read-only
			notReady      (3),	-- read-only
			createAndGo   (4),	-- notSupported
			createAndWait (5),
			destroy       (6)
		}
	ACCESS	read-write
	STATUS	mandatory
	DESCRIPTION
		" Used to control rows of the table."
	--	このテーブルのrow を制御するために使用される.
	::= { connProfileEntry 2 }

connProfileCause	OBJECT-TYPE
	SYNTAX	INTEGER	{
			rowExisting(1),	    -- default value
			otherFailure(2),    -- NG cause other than stated below.
			inconsistentEpd(3), -- Traffic type is inconsistent
					    -- with EPD value.
			parameterNotEnough(4), -- Parameter is not enough.
			alreadyExist(5),    -- Duplicate profile name exist.
					    -- (content is same)
			duplicateName(6),   -- Duplicate profile name exist.
					    -- (content is different)
			inconsistentRate(7) -- Rate designation is inconsistent.
		}
	ACCESS	read-only
	STATUS	mandatory
	DESCRIPTION
		" The result of Profile setting processing."
	--	Profile 設定処理の結果.
	::= { connProfileEntry 3 }

connProfileTrafficType	OBJECT-TYPE
	SYNTAX	INTEGER	{
			traffic-CBR     (1),
			traffic-rt-VBR  (2),
			traffic-nrt-VBR (3),
			traffic-ABR     (4),
			traffic-UBR     (5)
		}
	ACCESS	read-write
	STATUS	mandatory
	DESCRIPTION
		"Traffic Type."
	::= { connProfileEntry 4 }

connProfileName	OBJECT-TYPE
	SYNTAX	DisplayString (SIZE(0|1..10))
	ACCESS	read-write
	STATUS	mandatory
	DESCRIPTION
		" Profile name.
		Available characters: alphanumeric characters
		0 length string is only read."
	--	Profile 名.
	--	使用可能文字: 英数字.
	--	0 length string は readのみ.
	::= { connProfileEntry 5 }

--	The meanings of the subsequent connProfileParam1~4 are
--	different according to the buffer type of the line
--	(slotIfConfBufferType) which the calls are set to.

--	以下に続く connProfileParam1~4 は, 呼が設定される回線の
--	バッファータイプ( slotIfConfBufferType で表される )に
--	よって意味が異なる.

connProfileParam1	OBJECT-TYPE
	SYNTAX	INTEGER (-1|1..1412830)
	ACCESS	read-write
	STATUS	mandatory
	DESCRIPTION
		" For ph1/2-buffer, peek cell rate [cell/sec].
		If it is invalid, -1.
		JpnToEng[ABR で -1 の場合は, 帯域確保/UPCの設定をしないことを示す.]"
	--	ph1/2-bufferの場合, Peek cell rate [cell/sec].
	--	無効な場合の値は -1.
	--	ABR で -1 の場合は, 帯域確保/UPCの設定をしないことを示す.
	::= { connProfileEntry 6 }

connProfileParam2	OBJECT-TYPE
	SYNTAX	INTEGER (-1|1..1412830)
	ACCESS	read-write
	STATUS	mandatory
	DESCRIPTION
		" For ph1/2-buffer, Sustainable cell rate [cell/sec].
		Only nrt-VBR, and rt-VBR are valid.
		If it is invalid, -1. "
	--	ph1/2-bufferの場合, Sustainable cell rate [cell/sec].
	--	nrt-VBR, rt-VBR のみ有効.
	--	無効な場合の値は -1.
	::= { connProfileEntry 7 }

connProfileParam3	OBJECT-TYPE
	SYNTAX	INTEGER (-1|1..1412830)
	ACCESS	read-write
	STATUS	mandatory
	DESCRIPTION
		" For ph1/2-buffer, Maximum burst size [cell].
		Only nrt-VBR, and rt-VBR are valid.
		If it is invalid, -1. "
	--	ph1/2-bufferの場合, Maximum burst size [cell].
	--	nrt-VBR, rt-VBR のみ有効.
	--	無効な場合の値は -1.
	::= { connProfileEntry 8 }

connProfileParam4	OBJECT-TYPE
	SYNTAX	INTEGER	{
			off  (1),
			on (2)
		}
	ACCESS	read-write
	STATUS	mandatory
	DESCRIPTION
		" For ph1/2-buffer, EPD function flag.
		  If it is other than ABR, UBR, off, only. "
	--	ph1/2-bufferの場合, EPD機能フラグ.
	--	ABR, UBR 以外は off のみ.
	::= { connProfileEntry 9 }

connProfileName2Index	OBJECT-TYPE
	SYNTAX	DisplayString (SIZE(0|1..10))
	ACCESS	read-write
	STATUS	mandatory
	DESCRIPTION
		" Equivalent to connProfileName "
	--	connProfileName と同意.
	::= { connProfile 3 }

connProfileName2IndexResult	OBJECT-TYPE
	SYNTAX	ConnProfileIndex
	ACCESS	read-only
	STATUS	mandatory
	DESCRIPTION
		" Shows the index of the row whose connProfileRowStatus in
		connProfileTable, corresponding to connProfileName2Index,
		is active.  If the corresponding row does not exist, 0. "
	--	connProfileName2Indexに対応する,connProfileTable内の
	--	connProfileRowStatusがactiveであるrowのインデックスを表す.
	--	対応するrowが存在しない場合の値は0.
	::= { connProfile 4 }

connSvcTable	OBJECT-TYPE
	SYNTAX	SEQUENCE OF ConnSvcEntry
	ACCESS	not-accessible
	STATUS	mandatory
	DESCRIPTION
		"JpnToEng[本装置に設定される SVC 情報のテーブル.]"
	--	本装置に設定される SVC 情報のテーブル.
	::= { conn 10 }

connSvcEntry	OBJECT-TYPE
	SYNTAX	ConnSvcEntry
	ACCESS	not-accessible
	STATUS	mandatory
	DESCRIPTION
		"JpnToEng[本装置に設定される SVC 情報のエントリ.]"
	--	本装置に設定される SVC 情報のエントリ.
	INDEX	{ ifIndex, connSvcIndex }
	::= { connSvcTable 1 }

ConnSvcEntry ::=
	SEQUENCE {
		connSvcIndex
			INTEGER,
		connSvcInf
			Opaque
	}

connSvcIndex	OBJECT-TYPE
	SYNTAX	INTEGER
	ACCESS	not-accessible
	STATUS	mandatory
	DESCRIPTION
		"JpnToEng[SVC 情報の Index.]"
	--	SVC 情報の Index.
	::= { connSvcEntry 1 }

connSvcInf	OBJECT-TYPE
	SYNTAX	Opaque
	ACCESS	read-only
	STATUS	mandatory
	DESCRIPTION
		"JpnToEng(次の１３５行分を)
-- 		SVC の情報.
-- 		エントリの構造は以下の通り.
-- 		                       Bits
-- 		   8     7     6     5     4     3     2     1
-- 		+-----+-----+-----+-----+-----+-----+-----+-----+
-- 		| 格納されている SVC 数                         |  1 -  4 Octets
-- 		+===============================================+
-- 		| 入側回線番号                                  |  1 -  2
-- 		+-----+-----+-----+-----+-----+-----+-----+-----+
-- 		| 入側 VPI 番号                                 |  3 -  4
-- 		+-----+-----+-----+-----+-----+-----+-----+-----+
-- 		| 入側 VCI 番号                                 |  5 -  6
-- 		+-----+-----+-----+-----+-----+-----+-----+-----+
-- 		| 出側回線番号                                  |  7 -  8
-- 		+-----+-----+-----+-----+-----+-----+-----+-----+
-- 		| 出側 VPI 番号                                 |  9 - 10
-- 		+-----+-----+-----+-----+-----+-----+-----+-----+
-- 		| 出側 VCI 番号                                 | 11 - 12
-- 		+-----+-----+-----+-----+-----+-----+-----+-----+
-- 		| 方向      | 種別      | Traffic Type          | 13
-- 		| (注1)     | (注2)     | (注3)                 |
-- 		+-----+-----+-----+-----+-----+-----+-----+-----+
-- 		| Calling Party         | Called Party          | 14
-- 		| Address Format        | Address Format        |
-- 		| (注4)                 | (注4)                 |
-- 		+-----+-----+-----+-----+-----+-----+-----+-----+
-- 		| Calling Party Address Length [bits]           | 15
-- 		+-----+-----+-----+-----+-----+-----+-----+-----+
-- 		| Called Party Address Length [bits]            | 16
-- 		+-----+-----+-----+-----+-----+-----+-----+-----+
-- 		| Calling Party Address                         | 17 - 36
-- 		+-----+-----+-----+-----+-----+-----+-----+-----+
-- 		| Called Party Address                          | 37 - 56
-- 		+-----+-----+-----+-----+-----+-----+-----+-----+
-- 		| 入側 Shaper 番号 (注5)                        | 57
-- 		+-----+-----+-----+-----+-----+-----+-----+-----+
-- 		| 出側 Shaper 番号 (注5)                        | 58
-- 		+-----+-----+-----+-----+-----+-----+-----+-----+
-- 		| 入側 UPC Mode   | 出側 UPC Mode   | Tag-| Tag-| 59
-- 		| (注6)           | (注6)           | ging| ging|
-- 		|                 |                 | Fwd | Bwd |
-- 		|                 |                 |(注7)|(注7)|
-- 		+-----+-----+-----+-----+-----+-----+-----+-----+
-- 		| Fwd | Bwd |                                   | 60
-- 		| EPD | EPD |             Dummy1                |
-- 		|(注8)|(注8)|                                   |
-- 		+-----+-----+-----+-----+-----+-----+-----+-----+
-- 		| Forward PCR [cell/s]                          | 61 - 64
-- 		+-----+-----+-----+-----+-----+-----+-----+-----+
-- 		| Backward PCR [cell/s]                         | 65 - 68
-- 		+-----+-----+-----+-----+-----+-----+-----+-----+
-- 		| Forward SCR [cell/s]                          | 69 - 72
-- 		+-----+-----+-----+-----+-----+-----+-----+-----+
-- 		| Backward SCR [cell/s]                         | 73 - 76
-- 		+-----+-----+-----+-----+-----+-----+-----+-----+
-- 		| Forward MBS [cells]                           | 77 - 80
-- 		+-----+-----+-----+-----+-----+-----+-----+-----+
-- 		| Backward MBS [cells]                          | 81 - 84
-- 		+===============================================+
-- 		| 入側回線番号                                  |
-- 		+-----+-----+-----+-----+-----+-----+-----+-----+
-- 		| 入側 VPI 番号                                 |
-- 		+-----+-----+-----+-----+-----+-----+-----+-----+
-- 		| 入側 VCI 番号                                 |
-- 		+-----+-----+-----+-----+-----+-----+-----+-----+
-- 		:                                               :
-- 		:                                               :
-- 		+-----+-----+-----+-----+-----+-----+-----+-----+
-- 		| Backward MBS                                  |
-- 		+-----------------------------------------------+
--
-- 		(注1) 方向
-- 			1: PtoP, 2: PtoMP-out, 3: PtoMP-in
-- 		(注2) 種別
-- 			0: PtoP, 1: PtoMP
-- 		(注3) Traffic Type
-- 			1: CBR, 2: rt-VBR, 3: nrt-VBR, 4: ABR, 5: UBR
-- 		(注4) Calling/Called Party Address Format
-- 			1: E.164, 2: NSAP
-- 		(注5) 入/出側 Shaper 番号
-- 			0: Shaping OFF, 1-16: Shaper 番号
-- 		(注6) 入/出側 UPC Mode
-- 			0: UPC OFF, 1-5: mode1-mode5
-- 		(注7) Tagging Forward/Backward
-- 			0: OFF, 1: ON
-- 		(注8) EPD
-- 			0: OFF, 1: ON
--
-- 		struct atmSvc {
-- 			unsigned short	AtmSvcIncomingPort	;
-- 			unsigned short	AtmSvcIncomingVpi	;
-- 			unsigned short	AtmSvcIncomingVci	;
-- 			unsigned short	AtmSvcOutgoingPort	;
-- 			unsigned short	AtmSvcOutgoingVpi	;
-- 			unsigned short	AtmSvcOutgoingVci	;
-- 			unsigned char	AtmSvcDirection   : 2	;
-- 			unsigned char	AtmSvcTopology    : 2	;
-- 			unsigned char	AtmSvcTrafficType : 4 	;
-- 			unsigned char	AtmSvcCallingAddressFormat : 4	;
-- 			unsigned char	AtmSvcCalledAddressFormat  : 4	;
-- 			unsigned char	AtmSvcCallingAddressLength	;
-- 			unsigned char	AtmSvcCalledAddressLength	;
-- 			unsigned char	AtmSvcCallingAddress[ 20 ]	;
-- 			unsigned char	AtmSvcCalledAddress[ 20 ]	;
-- 			unsigned char	AtmSvcIncomingShaper	;
-- 			unsigned char	AtmSvcOutgoingShaper	;
-- 			unsigned char	AtmSvcIncomingUpcMode : 3	;
-- 			unsigned char	AtmSvcOutgoingUpcMode : 3	;
-- 			unsigned char	AtmSvcForwardTagging  : 1	;
-- 			unsigned char	AtmSvcBackwardTagging : 1	;
-- 			unsigned char	AtmSvcForwardEpd  : 1	;
-- 			unsigned char	AtmSvcBackwardEpd : 1	;
-- 			unsigned char	Dummy1            : 6	;
-- 			long	AtmSvcForwardPcr	;
-- 			long	AtmSvcBackwardPcr	;
-- 			long	AtmSvcForwardScr	;
-- 			long	AtmSvcBackwardScr	;
-- 			long	AtmSvcForwardMbs	;
-- 			long	AtmSvcBackwardMbs	;
-- 		} ;
--
-- 		struct opaqueSvc {
-- 			long		count		;
-- 			struct atmSvc	atmSvc[ 16 ]	;
-- 		} ;
--
-- 		各データは Big Endian で格納される.
-- 		AtmSvcCallingAddress/CalledAddress が 20 byte に満たない場合,
-- 		不足部分は 0 で padding される.
--
-- 		SVC 情報は, 最大 16 個ずつまとめられ, 先頭に格納データ数を
-- 		表す 4 byte のデータが付与される.
--
-- 		SVC 情報は動的なデータであるため, 情報を参照するときは
-- 		連続的に最初から参照しないと情報の正確性は保証できない.
		"
	--	SVC の情報.
	--	各データは Big Endian で格納される.
	--	AtmSvcCallingAddress/CalledAddress が 20 byte に満たない場合,
	--	不足部分は 0 で padding される.
	--
	--	SVC 情報は, 最大 16 個ずつまとめられ, 先頭に格納データ数を
	--	表す 4 byte のデータが付与される.
	--
	--	SVC 情報は動的なデータであるため, 情報を参照するときは
	--	連続的に最初から参照しないと情報の正確性は保証できない.

	::= { connSvcEntry 2 }


connCe			OBJECT IDENTIFIER ::= { conn 11 }

connCeVc		OBJECT IDENTIFIER ::= { connCe 1 }

	--	JpnToEng(次の１０４行分を)
--  connCeVc	Circuit Emulation コネクション(CEVC)設定データ

	--	設定手順

	--	1. createAndWait の SET
	--		connCeVcRowStatus に createAndWait を SET する．
	--		これにより Agent は各パラメータに Default 値を設定し
	--		connCeVcRowStatus を notReady にする．

	--		このテーブルでは,  非active な row ( つまり Row の
	--		Status が notReady か notInService である row )
	--		は, 同時に 1 つのみ 存在可能.

	--	2. 各パラメータの SET
	--		デフォルト値がないもの,デフォルト値を使用したくないも
	--		のに関して値をsetする.
	--		Agent は
	--			connCeVcDirection
	--		が設定されたならば,
	--		connCeVcRowStatus を notInService に変更する.

	--		必要なパラメータは,pkg種別,structure mode(set interface)
	--		Direction により異なる.
	--		その対応を以下に示す.

	--                          設定パラメータ分岐一覧表
	--  ==================================================================
	-- |                     |   CE-J2   |   CE-DS1  |   CE-E1   | CE-DS3 |
	-- |                     |- - - - - -|- - - - - -|- - - - - -|- - - - |
	-- |  パラメータ         | uns | str | uns | str | uns | str | uns    |
	-- |==================================================================|
	-- | UpPartialFillSize   | −  | −  | *1  | *1  | *1  | *1  | *1     |
	-- |- - - - - - - - - - - - - - - - - - - - - - - - - - - - - - - - - |
	-- | DownPartialFillSize | −  | −  | *1  | *1  | *1  | *1  | *1     |
	-- |- - - - - - - - - - - - - - - - - - - - - - - - - - - - - - - - - |
	-- | ConditionData       | −  | −  | −  | ○  | −  | ○  | −     |
	-- |- - - - - - - - - - - - - - - - - - - - - - - - - - - - - - - - - |
	-- | CDVT                | *2  | *2  | *2  | *2  | *2  | *2  | *2     |
	-- |- - - - - - - - - - - - - - - - - - - - - - - - - - - - - - - - - |
	-- | UpTimeSlot1         | −  | *1  | −  | *1  | −  | *1  | −     |
	-- |- - - - - - - - - - - - - - - - - - - - - - - - - - - - - - - - - |
	-- | downTimeSlot1       | −  | *1  | −  | *1  | −  | *1  | −     |
	-- |- - - - - - - - - - - - - - - - - - - - - - - - - - - - - - - - - |
	-- | UpTimeSlot2         | −  | *1  | −  | −  | −  | −  | −     |
	-- |- - - - - - - - - - - - - - - - - - - - - - - - - - - - - - - - - |
	-- | downTimeSlot2       | −  | *1  | −  | −  | −  | −  | −     |
	-- |- - - - - - - - - - - - - - - - - - - - - - - - - - - - - - - - - |
	-- | UpTimeSlot3         | −  | *1  | −  | −  | −  | −  | −     |
	-- |- - - - - - - - - - - - - - - - - - - - - - - - - - - - - - - - - |
	-- | downTimeSlot3       | −  | *1  | −  | −  | −  | −  | −     |
	--  ==================================================================
	--						"uns" :Unstructure mode
	--						"str" :Structure mode
	--			*1  PartialFillSize, Timeslot1-3 の設定は,
	--			    connCeVcDirection の方向により Up, Down
	--			    の必要パラメーターが異なる．
	--				 =========================
	--				| Direction |  Up  | Down |
	--				|=========================|
	--				|    Bi     |  ○  |  ○  |
	--				|- - - - - - - - - - - - -|
	--				|    Up     |  ○  |  −  |
	--				|- - - - - - - - - - - - -|
	--				|   Down    |  −  |  ○  |
	--				 =========================
	--			*2  CDVT は,Direction が Down の時のみ有効．

	--		※  structure時は,最低1つのTimeSlotを設定しなければなら
	--		    ない.(Timeslot1-3の内1つはbitが登録されていなければ
	--		    ならない.)

	--	3. active の SET
	--		Manager は connCeVcRowStatus に active を SET する.
	--		これにより Agent はパラメータやリソースのチェックを行い,
	--		cevc の設定処理を行う.

	--			structure時のpkg種別による
	--			１PORT当たりの最大チャンネル数
	--			（unstructure時は,1channel）
	--			 ===============================
	--			| pkg種別   |  最大チャンネル数 |
	--			|================================
	--			| CE-J2     |      ４channel    |
	--			|- - - - - - - - - - - - - - - -|
	--			| CE-DS1    |    ２４channel    |
	--			|- - - - - - - - - - - - - - - -|
	--			| CE-E1     |    ３０channel    |
	--			 ===============================

	--	4. 結果の GET
	--		connCeVcRowStatus の GET を行い, active ならば
	--		cevc 設定成功である. notInService ならば設定失敗
	--		であるので connCeVcCause を GET して要因を見る.

	--	削除手順

	--	1. destroy の SET
	--		削除したい cevc の connCeVcRowStatus に destroy を
	--		 SET する.
	--		これにより Agent は cevc の削除処理を行う.

	--	2. 結果の GET
	--		削除成功の場合は, 指定 Index の connCeVcTable 配下
	--		の Object の GET は noSuchName となる.


connCeVcTable			OBJECT-TYPE
	SYNTAX SEQUENCE OF ConnCeVcEntry
	ACCESS not-accessible
	STATUS mandatory
	DESCRIPTION
		"JpnToEng[CESカードに設定されたCEVCの情報表示を行なう.]"
	--	CESカードに設定されたCEVCの情報表示を行なう.
	::= { connCeVc 1 }

connCeVcEntry			OBJECT-TYPE
	SYNTAX ConnCeVcEntry
	ACCESS not-accessible
	STATUS mandatory
	DESCRIPTION
		"JpnToEng[本装置に設定される全てのCEVCのエントリー.]"
	--	本装置に設定される全てのCEVCのエントリー.
	INDEX{ connCeVcPort, connCeVcVci }
	::= { connCeVcTable 1 }

ConnCeVcEntry ::=
	SEQUENCE	{
		connCeVcPort			INTEGER,
		connCeVcVci			INTEGER,
		connCeVcRowStatus		INTEGER,
		connCeVcCause			INTEGER,
		connCeVcDirection		INTEGER,
		connCeVcUpPartialFillSize	INTEGER,
		connCeVcDownPartialFillSize	INTEGER,
		connCeVcCondition		INTEGER,
		connCeVcCDVT			INTEGER,
		connCeVcUpPCR			INTEGER,
		connCeVcDownPCR			INTEGER,
		connCeVcUpTimeSlot1		INTEGER,
		connCeVcDownTimeSlot1		INTEGER,
		connCeVcUpTimeSlot2		INTEGER,
		connCeVcDownTimeSlot2		INTEGER,
		connCeVcUpTimeSlot3		INTEGER,
		connCeVcDownTimeSlot3		INTEGER
	}

connCeVcPort			OBJECT-TYPE
	SYNTAX INTEGER
	ACCESS not-accessible
	STATUS mandatory
	DESCRIPTION
		"Line number."
	--	回線番号.
	::= { connCeVcEntry 1 }

connCeVcVci			OBJECT-TYPE
	SYNTAX INTEGER	(32..383)
	ACCESS not-accessible
	STATUS mandatory
	DESCRIPTION
		"VCI value.
		JpnToEng[使用可能範位はlinfStatusTable 参照.]"
	--	VCI番号.
	--	使用可能範位はlinfStatusTable 参照.
	::= { connCeVcEntry 2 }

connCeVcRowStatus			OBJECT-TYPE
	SYNTAX INTEGER	{
			active		(1),
			notInService	(2),	-- read-only
			notReady	(3),	-- read-only
			createAndGo	(4),	-- notSupported
			createAndWait	(5),
			destroy		(6)
	}
	ACCESS read-write
	STATUS mandatory
	DESCRIPTION
		" Used to control rows of the table."
	--	このテーブルの row を制御するために使用される.
	::= { connCeVcEntry 3 }

connCeVcCause			OBJECT-TYPE
	SYNTAX INTEGER	{
		rowExisting(1),		-- default
		otherFailure(2),	-- NG cause other than stated below.
		parameterNotEnough(3),	-- Parameter is not enough.
		illegalpkg(4),		-- pkg other than CES.
		vcsOverFllow(5),	-- The number of registration of Vc is
                                        -- over the limit.
		tssOverFllow(6),	-- The number of registration of TS is
                                        -- over the limit.
		alreadyAssignedTs(7),	-- JpnToEng[同一TSを異なるvcに登録.]
		inconsistentTss(8),	-- JpnToEng[J2 BI時にUPとDOWNでTS数
					-- 異なる.]
		illegalTimeslot(9),	-- JpnToEng[TS登録が１つも無し.
					-- E1 未サポートTS(0,16)を指定.]
		illegalPort(10),	-- Illegal line number.
		illegalVci(11),		-- Illegal VCI value.
		illegalUpPartialFillSize(12),	-- JpnToEng[Up側PartialFillSize
						-- が範囲外.]
		illegalDownPartialFillSize(13),	-- JpnToEng[Down側PartialFillSize
						-- が範囲外.]
		illegalCdvt(14)		-- JpnToEng[CDVT が範囲外.]
	}
	ACCESS read-only
	STATUS mandatory
	DESCRIPTION
		" The result of CEVC setting processing."
	--	CEVC設定処理の結果.
	::= { connCeVcEntry 4 }

connCeVcDirection		OBJECT-TYPE
	SYNTAX INTEGER {
			bi	(1),	-- default
			up	(2),
			down	(3)
	}
	ACCESS read-write
	STATUS mandatory
	DESCRIPTION
		"JpnToEng[設定方向]"
	--	設定方向
	::= { connCeVcEntry 5 }

connCeVcUpPartialFillSize	OBJECT-TYPE
	SYNTAX INTEGER (-1|0..47)	-- default -1
	ACCESS read-write
	STATUS mandatory
	DESCRIPTION
		"JpnToEng[UP方向のセル当たりの満たされた平均ユーザオクテット数
		0 の場合は full 設定(structure の時は46.875になる)
		0 以外の最小値は,設定TS数+1.]"
	--	UP方向のセル当たりの満たされた平均ユーザオクテット数
	--	0 の場合は full 設定(structure の時は46.875になる)
	--	0 以外の最小値は,設定TS数+1.
	::= { connCeVcEntry 6 }

connCeVcDownPartialFillSize	OBJECT-TYPE
	SYNTAX INTEGER (-1|0..47)	-- default -1
	ACCESS read-write
	STATUS mandatory
	DESCRIPTION
		"JpnToEng[DOWN方向のセル当たりの満たされた平均ユーザオクテット数
		0 の場合は full 設定(structure の時は46.875になる)
		0 以外の最小値は,設定TS数+1.]"
	--	DOWN方向のセル当たりの満たされた平均ユーザオクテット数
	--	0 の場合は full 設定(structure の時は46.875になる)
	--	0 以外の最小値は,設定TS数+1.
	::= { connCeVcEntry 7 }

connCeVcCondition		OBJECT-TYPE
	SYNTAX INTEGER	(-1|0..255)	-- default -1
	ACCESS read-write
	STATUS mandatory
	DESCRIPTION
		"Condtion date."
	--	コンディションデータ.
	::= { connCeVcEntry 8 }

connCeVcCDVT			OBJECT-TYPE
	SYNTAX INTEGER	(-1|1..7218)	-- default -1
	ACCESS read-write
	STATUS mandatory
	DESCRIPTION
		"CDVT value.
			JpnToEng[pkg種別によるCDVT範囲]
		+----------------------+----------+------------+
		|pkg type| str mode    |CDVT range| unit of    |
		|        |             |          |  setting   |
		================================================
		| CE-J2  | unstructure | 1..73    | 125μsec   |
		|        +-------------+----------+------------+
		|        | structure   | 1..7218  | 125μsec   |
		+--------+-------------+----------+------------+
		| CE-DS1 | unstructure | 1..255   | 165.8μsec |
		|        +-------------+----------+------------+
		|        | structure   | 1..191   | 125μsec   |
		+--------+-------------+----------+------------+
		| CE-E1  | unstructure | 1..255   | 124.5μsec |
		|        +-------------+----------+------------+
		|        | structure   | 1..255   | 125μsec   |
		+--------+-------------+----------+------------+
		| CE-DS3 | unstructure | 1..255   | 5.7μsec   |
		+--------+-------------+----------+------------+
		"
	--	CDVT値.
	::= { connCeVcEntry 9 }

connCeVcUpPCR			OBJECT-TYPE
	SYNTAX INTEGER	(-1|0..118979)	-- default -1
	ACCESS read-only
	STATUS mandatory
	DESCRIPTION
		"JpnToEng[CEVC設定時のUP方向のPCR値.]"
	--	CEVC設定時のUP方向のPCR値.
	::= { connCeVcEntry 10 }

connCeVcDownPCR			OBJECT-TYPE
	SYNTAX INTEGER	(-1|0..118979)	-- default -1
	ACCESS read-only
	STATUS mandatory
	DESCRIPTION
		"JpnToEng[CEVC設定時のDOWN方向のPCR値.]"
	--	CEVC設定時のDOWN方向のPCR値.
	::= { connCeVcEntry 11 }

connCeVcUpTimeSlot1		OBJECT-TYPE
	SYNTAX INTEGER
	ACCESS read-write
	STATUS mandatory
	DESCRIPTION
		"JpnToEng(次の１２行分)"
	--	Up方向のタイムスロット(1-32) をビットで指定する.
	--	32ビットコードの最下位ビットが,TS1を表し,設定する
	--	TS に対応するビットをセットする．
	--	例えば,TS1,TS10,TS32 を設定した場合は
	--	10000000000000000000001000000001(b)
	--	( 80000201(h) = 2^(32-1)+2^(10-1)+2^(1-1) )
	--	default 0.
	--
	--	CE-DS1/J2/E1でbitと呼び名の対応が違います。
        --	CE-J2  bit0 = TS1, bit23 = TS24, bit31 = TS32
        --	CE-DS1 bit0 = TS1, bit23 = TS24, bit31 = 未使用
        --	CE-E1  bit0 = TS0, bit23 = TS23, bit31 = TS31
	::= { connCeVcEntry 12 }

connCeVcDownTimeSlot1		OBJECT-TYPE
	SYNTAX INTEGER
	ACCESS read-write
	STATUS mandatory
	DESCRIPTION
		"JpnToEng(次の2行分)"
	--	Down方向のタイムスロット(1-32) をビットで指定する.
	--	default 0.
	::= { connCeVcEntry 13 }

connCeVcUpTimeSlot2		OBJECT-TYPE
	SYNTAX INTEGER
	ACCESS read-write
	STATUS mandatory
	DESCRIPTION
		"JpnToEng(次の2行分)"
	--	Up方向のタイムスロット(33-64) をビットで指定する.
	--	default 0.
	::= { connCeVcEntry 14 }

connCeVcDownTimeSlot2		OBJECT-TYPE
	SYNTAX INTEGER
	ACCESS read-write
	STATUS mandatory
	DESCRIPTION
		"JpnToEng(次の2行分)"
	--	Down方向のタイムスロット(33-64) をビットで指定する.
	--	default 0.
	::= { connCeVcEntry 15 }

connCeVcUpTimeSlot3		OBJECT-TYPE
	SYNTAX INTEGER
	ACCESS read-write
	STATUS mandatory
	DESCRIPTION
		"JpnToEng(次の2行分)"
	--	Up方向のタイムスロット(65-96) をビットで指定する.
	--	default 0.
	::= { connCeVcEntry 16 }

connCeVcDownTimeSlot3		OBJECT-TYPE
	SYNTAX INTEGER
	ACCESS read-write
	STATUS mandatory
	DESCRIPTION
		"JpnToEng(次の2行分)"
	--	Down方向のタイムスロット(65-96) をビットで指定する.
	--	default 0.
	::= { connCeVcEntry 17 }



connFr			OBJECT IDENTIFIER ::= { conn 12 }

connFrDlci		OBJECT IDENTIFIER ::= { connFr 1 }

	--	JpnToEng(次の39行分)
	--	connFrDlci	Frame Relay コネクション(DLCI) 設定データ
	--
	--	設定手順
	--
	--	1. createAndWait の SET
	--		connFrDlciRowStatus に createAndWait を SET する.
	--		これにより Agent は各パラメータに Default 値を設定し,
	--		connFrDlciRowStatus を notReady にする.
	--
	--
	--		このテーブルでは,  非active な row ( i.e. Row の
	--		Status が notReady か notInService である row )
	--		は, 同時に 1 つのみ 存在可能.
	--
	--	2.パラメータの SET
	--		パラメータ connFrDlciFrProfile に値を SET する.
	--		Agent は connFrDlciFrProfile が設定されたならば,
	--		connFrDlciRowStatus を notInService に変更する.
	--
	--	4. active の set
	--		Manager は connFrDlciRowStatus に active を SET する.
	--		これにより Agent はパラメータやリソースのチェックを
	--		行い コネクション(DLCI) 設定データの登録処理を行う.
	--
	--	5. 結果の GET
	--		connFrDlciRowStatus の GET を行い, active ならば
	--		設定成功である. notInService ならば設定失敗であるので
	--		connFrDlciCause を GET して要因を見る.
	--
	--	削除手順
	--
	--	1. destroy の SET
	--		connFrDlciRowStatus に destroy を SET する.
	--		これにより Agent は コネクション(DLCI) 設定データの
	--		削除処理を行う.
	--
	--	2. 結果の GET
	--		削除成功の場合は, 指定 Index の connFrDlciTable 配下
	--		の Object の GET は noSuchName となる.

connFrDlciTable		OBJECT-TYPE
	SYNTAX	SEQUENCE OF ConnFrDlciEntry
	ACCESS	not-accessible
	STATUS	mandatory
	DESCRIPTION
		"JpnToEng(次の2行分)"
	--	Frame Relay コネクション(DLCI) 設定データを表すテーブル.
	--	コネクション(DLCI) 設定データ毎に,1つのエントリを持つ.
	::= { connFrDlci 1 }

connFrDlciEntry		OBJECT-TYPE
	SYNTAX ConnFrDlciEntry
	ACCESS not-accessible
	STATUS mandatory
	DESCRIPTION
		"Entry of connFrDlciTable."
	--	connFrDlciTable のエントリ.
	INDEX{ connFrDlciPort , connFrDlciIndex }
	::= { connFrDlciTable 1 }

ConnFrDlciEntry ::=
	SEQUENCE	{
		connFrDlciPort		INTEGER,
		connFrDlciIndex		INTEGER,
		connFrDlciRowStatus	INTEGER,
		connFrDlciCause		INTEGER,
		connFrDlciFrProfile	DisplayString,
		connFrDlciPCR		INTEGER,
		connFrDlciSCR		INTEGER,
		connFrDlciMBS		INTEGER
	}

connFrDlciPort		OBJECT-TYPE
	SYNTAX	INTEGER (1..64)
	ACCESS	not-accessible
	STATUS	mandatory
	DESCRIPTION
		"Line number."
	--	回線番号.
	::= { connFrDlciEntry 1 }

connFrDlciIndex		OBJECT-TYPE
	SYNTAX	INTEGER (16..1007)
	ACCESS	not-accessible
	STATUS	mandatory
	DESCRIPTION
		"DLCI number."
	--	DLCI番号.
	::= { connFrDlciEntry 2 }

connFrDlciRowStatus	OBJECT-TYPE
	SYNTAX	INTEGER {
		active (1),
		notInService (2),	-- read-only
		notReady (3),		-- read-only
		createAndGo(4),		-- notSupported
		createAndWait(5),
		destroy(6)
	}
	ACCESS	read-write
	STATUS	mandatory
	DESCRIPTION
		" Used to control rows of the table."
	--	このテーブルのrow を制御するために使用される.
	::= { connFrDlciEntry 3 }

connFrDlciCause		OBJECT-TYPE
	SYNTAX	INTEGER {
		rowExisting (1),	-- default value.
		otherFailure (2),	-- NG cause other than stated below.
		noFrProfile (3),	-- JpnToEng[指定FrProfileが未登録.]
		inconsistentInterWorking (4),
					-- JpnToEng[Frprofileと 回線のインター
					--	ワーキングが不一致.]
		totalCIROverFlow (5),	-- JpnToEng[指定Frprodileの合計CIRが
					--	オーバーフロー.]
		lineDiagnosticsFailure (6),
					-- JpnToEng[診断障害発生.]
		illegalPort (7),	-- Illegal Line number.
		illegalDlci (8),	-- Illegal DLCI number.
		pvcsOverFlow (9)	-- JpnToEng[PVC数超過.]
	}
	ACCESS	read-only
	STATUS	mandatory
	DESCRIPTION
		"JpnToEng[コネクション(DLCI) 設定データ 設定処理の結果.]"
	--	コネクション(DLCI) 設定データ 設定処理の結果.
	::= { connFrDlciEntry 4 }

connFrDlciFrProfile	OBJECT-TYPE
	SYNTAX	DisplayString (SIZE(0|1..10))
	ACCESS	read-write
	STATUS	mandatory
	DESCRIPTION
		"JpnToEng(次の2行分)"
	--	connFrProfile で設定しているFrame Relay 用プロファイル名.
	--	0 length string (デフォルト値) は readのみ.
	::= { connFrDlciEntry 5 }

connFrDlciPCR	OBJECT-TYPE
	SYNTAX	INTEGER
	ACCESS	read-only
	STATUS	mandatory
	DESCRIPTION
		"Peak Cell Rate[cell/sec].
		JpnToEng[rowがactiveでない場合の値は -1(デフォルト値).]"
	--	rowがactiveでない場合の値は -1(デフォルト値).
	::= { connFrDlciEntry 6 }

connFrDlciSCR	OBJECT-TYPE
	SYNTAX	INTEGER
	ACCESS	read-only
	STATUS	mandatory
	DESCRIPTION
		"Sustainable Cell Rate[cell/sec].
		JpnToEng[rowがactiveでない場合の値は -1(デフォルト値).]"
	--	rowがactiveでない場合の値は -1(デフォルト値).
	::= { connFrDlciEntry 7 }

connFrDlciMBS	OBJECT-TYPE
	SYNTAX	INTEGER
	ACCESS	read-only
	STATUS	mandatory
	DESCRIPTION
		"Maximum Burst Size[cell].
		JpnToEng[rowがactiveでない場合の値は -1(デフォルト値).]"
	--	rowがactiveでない場合の値は -1(デフォルト値).
	::= { connFrDlciEntry 8 }


--	connFrProfle	Frame Relay Profile

connFrProfile		OBJECT IDENTIFIER ::= { connFr 2 }

	ConnFrProfileIndex ::= INTEGER
	--	Index of connFrProfileTable.


	--	JpnToEng(次の76行分)
	--	設定手順
	--
	--	1. connFrProfileIndex の GET
	--		Manager は connFrProfileIndexNext を GET すること
	--		により, connFrProfileTable の Index (connFrProfileIndex)
	--		を得る.
	--
	--	2. createAndWait の SET
	--		取得した connFrProfileIndex を Index として
	--		connFrProfileRowStatus に createAndWait を SET する.
	--		これにより Agent は各パラメータに Default 値を設定し,
	--		connFrProfileRowStatus を notReady にする.
	--
	--		このテーブルでは,  非active な row ( i.e. Row の
	--		Status が notReady か notInService である row )
	--		は, 同時に 1 つのみ 存在可能.
	--
	--	3. 各パラメータの SET
	--		デフォルト値がないもの,デフォルト値を使用したくないも
	--		のに関して値をsetする.
	--		Agent は
	--			connFrProfileName,
	--			connFrProfileInterworkingType,
	--			connFrProfileCIR,
	--			connFrProfileDEtoCLP,
	--			connFrProfileCLPtoDE
	--		が設定されたならば,
	--		connFrProfileRowStatus を notInService に変更する.
	--
	--		必要なパラメータはconnFrProfileInterworkingType,
	--		connFrProfileDEtoCLP, connFrProfileCLPtoDE,により異なる.
	--		その対応を以下に示す.
	--
	--			設定パラメータ分岐一覧表
	-- ================================================================
	--| パラメータ     |   a   |   b   |   c   |   d   |   e   |   f   |
	--|================================================================|
	--|InterworkingType|Network|Network|Service|Service|Service|Service|
	--|- - - - - - - - - - - - - - - - - - - - - - - - - - - - - - - - |
	--|CIR             |  xxx  |  xxx  |  xxx  |  xxx  |  xxx  |  xxx  |
	--|- - - - - - - - - - - - - - - - - - - - - - - - - - - - - - - - |
	--|DEtoCLP         | Mode1 | Mode2 | Mode1 | Mode1 | Mode2 | Mode2 |
	--|- - - - - - - - - - - - - - - - - - - - - - - - - - - - - - - - |
	--|CLPValue        |   -   |on/off |   -   |   -   |on/off |on/off |
	--|- - - - - - - - - - - - - - - - - - - - - - - - - - - - - - - - |
	--|CLPtoDE         |Mode1/2|Mode1/2| Mode1 | Mode2 | Mode1 | Mode2 |
	--|- - - - - - - - - - - - - - - - - - - - - - - - - - - - - - - - |
	--|DEValue         |   -   |   -   |   -   |on/off |   -   |on/off |
	--|- - - - - - - - - - - - - - - - - - - - - - - - - - - - - - - - |
	--|CapsulationMode |   -   |   -   |Mode1/2|Mode1/2|Mode1/2|Mode1/2|
	--|- - - - - - - - - - - - - - - - - - - - - - - - - - - - - - - - |
	--|CongestionMode  |   -   |   -   |Mode1/2|Mode1/2|Mode1/2|Mode1/2|
	-- ================================================================
	--		*1 "xxx":数値設定
	--		*2 "-"	:無効パラメーター
	--
	--	4. active の SET
	--		Manager は connFrProfileRowStatus に active を SET する.
	--		これにより Agent はパラメータやリソースのチェックを行い,
	--		Frprofile の登録処理を行う.
	--
	--	5. 結果の GET
	--		connFrProfileRowStatus の GET を行い, active ならば
	--		Frprofile 設定成功である. notInService ならば設定失敗
	--		であるので connFrProfileCause を GET して要因を見る.
	--
	--	削除手順
	--
	--	1. destroy の SET
	--		削除したい Frprofile の connFrProfileRowStatus に
	--		destroy を SET する.
	--		これにより Agent は Frprofile の削除処理を行う.
	--
	--	2. 結果の GET
	--		削除成功の場合は, 指定 Index の connFrProfileTable 配下
	--		の Object の GET は noSuchName となる.


connFrProfileIndexNext	OBJECT-TYPE
	SYNTAX ConnFrProfileIndex
	ACCESS read-only
	STATUS mandatory
	DESCRIPTION
		"JpnToEng(次の2行分)"
	--	connFrProfileTable の空きIndex値を表す.
	--	既に最大登録されている場合は０.
	::= { connFrProfile 1 }

connFrProfileTable		OBJECT-TYPE
	SYNTAX SEQUENCE  OF  ConnFrProfileEntry
	ACCESS not-accessible
	STATUS mandatory
	DESCRIPTION
		"JpnToEng[Frprofile の設定 / 表示を行なうためのテーブル.]"
	--	Frprofile の設定 / 表示を行なうためのテーブル.
	::= { connFrProfile 2 }

connFrProfileEntry		OBJECT-TYPE
	SYNTAX ConnFrProfileEntry
	ACCESS not-accessible
	STATUS mandatory
	DESCRIPTION
		"Entry of connFrProfileTable."
	--	connFrProfileTableのエントリ.
	INDEX { connFrProfileIndex }
	::= { connFrProfileTable 1 }

ConnFrProfileEntry ::=
	SEQUENCE {
		connFrProfileIndex		ConnFrProfileIndex,
		connFrProfileRowStatus		INTEGER,
		connFrProfileCause		INTEGER,
		connFrProfileName		DisplayString,
		connFrProfileInterworkingType	INTEGER,
		connFrProfileCIR		INTEGER,
		connFrProfileDEtoCLP		INTEGER,
		connFrProfileCLPValue		INTEGER,
		connFrProfileCLPtoDE		INTEGER,
		connFrProfileDEValue		INTEGER,
		connFrProfileCapsulationMode	INTEGER,
		connFrProfileCongestionMode	INTEGER
	}

connFrProfileIndex			OBJECT-TYPE
	SYNTAX ConnFrProfileIndex
	ACCESS not-accessible
	STATUS mandatory
	DESCRIPTION
		"Index of connFrProfileTable."
	--	connFrProfileTableの Index 値.
	::= { connFrProfileEntry 1 }

connFrProfileRowStatus		OBJECT-TYPE
	SYNTAX INTEGER {
			active		(1),
			notInService	(2),	-- read-only
			notReady	(3),	-- read-only
			createAndGo	(4),	-- notSupported
			createAndWait	(5),
			destroy		(6)
	}
	ACCESS read-write
	STATUS mandatory
	DESCRIPTION
		" Used to control rows of the table."
	--	このテーブルの row を制御するために使用される.
	::= { connFrProfileEntry 2 }

connFrProfileCause		OBJECT-TYPE
	SYNTAX INTEGER {
			rowExisting(1),	-- default
			otherFailure(2), -- NG cause other than stated below.
			parameterNotEnough(3), -- Parameter is not enough.
			alreadyExist(4), -- Duplicate Frprofile name exist.
						-- (content is same)
			duplicateName(5) -- Duplicate Frprofile name exist.
						-- (content is different)
		}
	ACCESS	read-only
	STATUS	mandatory
	DESCRIPTION
		" The result of Frprofile setting processing."
	--	Frprofile 設定処理の結果.
	::= { connFrProfileEntry 3 }

connFrProfileName		OBJECT-TYPE
	SYNTAX DisplayString (SIZE(0|1..10)) -- default 0 length string
	ACCESS read-write
	STATUS mandatory
	DESCRIPTION
		"Frprofile name.
		Available characters: alphanumeric characters
		0 length string is only read."
	--	Frprofile 名.
	--	使用可能文字: 英数字.
	--	0 length string は readのみ.
	::= { connFrProfileEntry 4 }

connFrProfileInterworkingType	OBJECT-TYPE
	SYNTAX INTEGER {
		network	(1),	-- default
		service	(2)
	}
	ACCESS read-write
	STATUS mandatory
	DESCRIPTION
		"Interworking Type"
	::= { connFrProfileEntry 5 }

connFrProfileCIR		OBJECT-TYPE
	SYNTAX INTEGER (-1|1..1984)	-- default -1(read-olny)
	ACCESS read-write
	STATUS mandatory
	DESCRIPTION
		"CIR value."
	--	CIR 値.
	::= { connFrProfileEntry 6 }

connFrProfileDEtoCLP		OBJECT-TYPE
	SYNTAX INTEGER {
		mode1		(1),	--default
		mode2		(2)
	}
	ACCESS read-write
	STATUS mandatory
	DESCRIPTION
		"DE to CLP mapping mode"
	--	セル損失優先モード.
	::= { connFrProfileEntry 7 }

connFrProfileCLPValue		OBJECT-TYPE
	SYNTAX INTEGER {
		notApplicable	(1),	--default, read-only
		on		(2),
		off		(3)
	}
	ACCESS read-write
	STATUS mandatory
	DESCRIPTION
		"CLP Value.
		It's valid when connFrProfileDEtoCLP is mode2."
	--	connFrProfileDEtoCLP が mode2 の場合有効.
	::= { connFrProfileEntry 8 }

connFrProfileCLPtoDE		OBJECT-TYPE
	SYNTAX INTEGER {
		mode1		(1),	--default
		mode2		(2)
	}
	ACCESS read-write
	STATUS mandatory
	DESCRIPTION
		"CLP to DE mapping mode."
	--	フレーム廃棄優先モード.
	::= { connFrProfileEntry 9 }

connFrProfileDEValue		OBJECT-TYPE
	SYNTAX INTEGER {
		notApplicable	(1),	--default, read-only
		on		(2),
		off		(3)
	}
	ACCESS read-write
	STATUS mandatory
	DESCRIPTION
		"DE Value.
		It's valid when connFrProfileInterworkingType is service
		and connFrProfileCLPtoDE is mode2."
	--	connFrProfileInterworkingType が service でかつ
	--	connFrProfileCLPtoDE が mode2 の場合有効.
	::= { connFrProfileEntry 10 }

connFrProfileCapsulationMode	OBJECT-TYPE
	SYNTAX INTEGER {
		notApplicable	(1),	--default, read-only
		transparent 	(2),
		translation	(3)
	}
	ACCESS read-write
	STATUS mandatory
	DESCRIPTION
		"Protocol encapsulation mode.
		It's valid when connFrProfileInterworkingType is service."
	--	カプセル化モード
	--	connFrProfileInterworkingType が Service の時有効.
	::= { connFrProfileEntry 11 }

connFrProfileCongestionMode	OBJECT-TYPE
	SYNTAX INTEGER {
		notApplicable	(1),	--default, read-only
		mode1		(2),
		mode2		(3)
	}
	ACCESS read-write
	STATUS mandatory
	DESCRIPTION
		"Congestion indication(Forward) mode.
		It's valid when connFrProfileInterworkingType is service."
	--	順方向輻輳(FECN)モード
	--	connFrProfileInterworkingType が Service の時有効.
	::= { connFrProfileEntry 12 }

connFrProfileName2Index           OBJECT-TYPE
	SYNTAX	DisplayString (SIZE(0|1..10))
	ACCESS	read-write
	STATUS	mandatory
	DESCRIPTION
		"Equivalent to connProfileName."
	--	connFrProfileName と同意．
	::= { connFrProfile 3 }

connFrProfileName2IndexResult           OBJECT-TYPE
	SYNTAX	ConnFrProfileIndex
	ACCESS	read-only
	STATUS	mandatory
	DESCRIPTION
		" Shows the index of the row whose connFrProfileRowStatus in
		connFrProfileTable, corresponding to connFrProfileName2Index,
		is active.  If the corresponding row does not exist, 0. "
	--	connFrProfileName2Indexに対応する,connFrProfileTable内の
	--	connFrProfileRowStatusがactiveであるrowのインデックスを表す.
	--	対応するrowが存在しない場合の値は0.
	::= { connFrProfile 4 }

--	The Perf (Performance) Group

perfTrapEnable OBJECT-TYPE
	SYNTAX	INTEGER {
			enable(1),	-- default
			disable(2)
		}
	ACCESS	read-write
	STATUS	mandatory
	DESCRIPTION
		"This object is used for disabling/enabling trap messages
		regarding the enterprise specific traps."
	--	enterprise specific trap に関するＴｒａｐ送信
	--	の規制を示す.
	::= { perf 1 }

perfIfTable OBJECT-TYPE
	SYNTAX	SEQUENCE OF PerfIfEntry
	ACCESS	not-accessible
	STATUS	mandatory
	DESCRIPTION
		"Table for showing the result of the performance monitoring
		per line of the equipment. Up to 64 tables are available for
		entry.
		Every line whose traffic is managed per line is provided with
		an entry. "
	--	本装置の回線毎のパフォーマンスモニタ結果を示すテーブル.
	--	64までエントリ可能.
	--	回線単位でトラヒック管理している回線毎に1つのエントリを持つ.
	::= { perf 2 }

perfIfEntry OBJECT-TYPE
	SYNTAX	PerfIfEntry
	ACCESS	not-accessible
	STATUS	mandatory
	DESCRIPTION
		"Entry of the line performance monitoring."
	--	回線のパフォーマンスモニタのエントリ.
	INDEX	{ perfIfIndex }
	::= { perfIfTable 1 }

PerfIfEntry ::=
	SEQUENCE {
		perfIfIndex
			INTEGER,
		perfIfReceivedCells
			OCTET STRING,
		perfIfReceivedCellsCounters
			Counter,
		perfIfTransmittedCells
			OCTET STRING,
		perfIfTransmittedCellsCounters
			Counter,
		perfIfMisDelivdCells
			OCTET STRING,
		perfIfMisDelivdCellsCounters
			Counter,
		perfIfThresholdExcessCells
			OCTET STRING,
		perfIfThresholdExcessCellsCounters
			Counter,
		perfIfUpcErrorCells
			OCTET STRING,
		perfIfUpcErrorCellsCounters
			Counter
	}

perfIfIndex OBJECT-TYPE
	SYNTAX	INTEGER
	ACCESS	not-accessible
	STATUS	mandatory
	DESCRIPTION
		"Line number."
	--	回線番号.
	::= { perfIfEntry 1 }

perfIfReceivedCells OBJECT-TYPE
        SYNTAX  OCTET STRING (SIZE(8))
        ACCESS  read-only
        STATUS  mandatory
        DESCRIPTION
                "The Number of the receive cells of line port.
		(64 bit applicable)"
	--	回線ポートの受信セル数(64bit対応).
        ::= { perfIfEntry 2 }

perfIfReceivedCellsCounters OBJECT-TYPE
        SYNTAX  Counter
        ACCESS  read-only
        STATUS  mandatory
        DESCRIPTION
                "The Number of the receive cells of line port.
		(32 bit applicable)."
	--	回線ポートの受信セル数(32bit対応).
        ::= { perfIfEntry 3 }

perfIfTransmittedCells OBJECT-TYPE
        SYNTAX  OCTET STRING (SIZE(8))
        ACCESS  read-only
        STATUS  mandatory
        DESCRIPTION
                "The Number of the transmit cells of line port.
		(64 bit applicable)."
	--	回線ポートの送信セル数(64bit対応)
        ::= { perfIfEntry 4 }

perfIfTransmittedCellsCounters OBJECT-TYPE
        SYNTAX  Counter
        ACCESS  read-only
        STATUS  mandatory
        DESCRIPTION
                "The Number of the transmit cells of line port.
		(32 bit applicable)."
	--	回線ポートの送信セル数(32bit対応).
        ::= { perfIfEntry 5 }

perfIfMisDelivdCells OBJECT-TYPE
        SYNTAX  OCTET STRING (SIZE(8))
        ACCESS  read-only
        STATUS  mandatory
        DESCRIPTION
		"The Number of the undefined cells of line port.
		(64 bit applicable)."
	--	回線ポートの未定義セル数(64bit対応).
        ::= { perfIfEntry 8 }

perfIfMisDelivdCellsCounters OBJECT-TYPE
        SYNTAX  Counter
        ACCESS  read-only
        STATUS  mandatory
        DESCRIPTION
		"The Number of the undefined cells of line port.
		(32 bit applicable)."
	--	回線ポートの未定義セル数(32bit対応).
        ::= { perfIfEntry 9 }

perfIfThresholdExcessCells OBJECT-TYPE
        SYNTAX  OCTET STRING (SIZE(8))
        ACCESS  read-only
        STATUS  mandatory
        DESCRIPTION
                "Number of the threshold excess cells (64 bit applicable)."
	--	回線ポートの閾値超過セル数(64bit対応).
        ::= { perfIfEntry 10 }

perfIfThresholdExcessCellsCounters OBJECT-TYPE
        SYNTAX  Counter
        ACCESS  read-only
        STATUS  mandatory
        DESCRIPTION
                "Number of the threshold excess cells (32 bit applicable)."
	--	回線ポートの閾値超過セル数(32bit対応).
        ::= { perfIfEntry 11 }

perfIfUpcErrorCells OBJECT-TYPE
        SYNTAX  OCTET STRING (SIZE(8))
        ACCESS  read-only
        STATUS  mandatory
        DESCRIPTION
                "Number of the UPC error cells (64 bit applicable)."
	--	回線ポートのＵＰＣエラーセル数(64bit対応).
        ::= { perfIfEntry 12 }

perfIfUpcErrorCellsCounters OBJECT-TYPE
        SYNTAX  Counter
        ACCESS  read-only
        STATUS  mandatory
        DESCRIPTION
                "Number of the UPC error cells (32 bit applicable)."
	--	回線ポートのＵＰＣエラーセル数(32bit対応).
        ::= { perfIfEntry 13 }

perfIfSlotTable	OBJECT-TYPE
	SYNTAX	SEQUENCE OF PerfIfSlotEntry
	ACCESS	not-accessible
	STATUS	mandatory
	DESCRIPTION
		 "Table for showing the number of cells of the traffic and
		 performance per line card of the equipment.
		 Up to 16 tables are available for entry.
		 Every line whose traffic is managed per slot is provided
		 with an entry.
		 The object which becomes invalid by the line card is always 0."
	--	本装置の回線カード毎のトラヒック/パフォーマンスのセル数を示す
	--	テーブル.
	--	16までエントリ可能。
	--	スロット単位でトラヒック管理している回線カード毎に1つの
	--	エントリを持つ.
	--	回線カードによって無効となるオブジェクトは常に値 0 である.
	::= { perf 3 }

perfIfSlotEntry	OBJECT-TYPE
	SYNTAX	PerfIfSlotEntry
	ACCESS	not-accessible
	STATUS	mandatory
	DESCRIPTION
		"Entry of traffic/performance per line card."
	--	回線カード毎のトラヒック/パフォーマンスのエントリ.
	INDEX	{ slotIfConfIndex }
	::= { perfIfSlotTable 1 }

PerfIfSlotEntry ::=
	SEQUENCE {
		perfIfSlotReceivedCells
			OCTET STRING,
		perfIfSlotTransmittedCells
			OCTET STRING,
		perfIfSlotInDropCells
			OCTET STRING,
		perfIfSlotReceivedCellsCounters
			Counter,
		perfIfSlotTransmittedCellsCounters
			Counter,
		perfIfSlotInDropCellsCounters
			Counter,
		perfIfSlotHCThresholdExcessCells
			OCTET STRING,
		perfIfSlotThresholdExcessCells
			Counter,
		perfIfSlotHCUpcErrorCells
			OCTET STRING,
		perfIfSlotUpcErrorCells
			Counter

	}

perfIfSlotReceivedCells OBJECT-TYPE
	SYNTAX	OCTET STRING (SIZE(8))
	ACCESS	read-only
	STATUS	mandatory
	DESCRIPTION
		"The number of receive cells."
	--	 受信セル数.
	::= { perfIfSlotEntry 1 }

perfIfSlotTransmittedCells OBJECT-TYPE
	SYNTAX	OCTET STRING (SIZE(8))
	ACCESS	read-only
	STATUS	mandatory
	DESCRIPTION
		"The number of transmit cells."
	--	 送信セル数.
	::= { perfIfSlotEntry 2 }

perfIfSlotInDropCells OBJECT-TYPE
	SYNTAX	OCTET STRING (SIZE(8))
	ACCESS	read-only
	STATUS	mandatory
	DESCRIPTION
		"The number of receive drop cells."
	--	 受信廃棄セル数.
	::= { perfIfSlotEntry 3 }

	-- perfIfSlotEntry4 shall be absent.
	-- perfIfSlotEntry 4 は欠番とする

perfIfSlotReceivedCellsCounters OBJECT-TYPE
	SYNTAX	Counter
	ACCESS	read-only
	STATUS	mandatory
	DESCRIPTION
		"The number of receive cells."
	--	 受信セル数.
	::= { perfIfSlotEntry 5 }

perfIfSlotTransmittedCellsCounters OBJECT-TYPE
	SYNTAX	Counter
	ACCESS	read-only
	STATUS	mandatory
	DESCRIPTION
		"The number of transmit cells."
	--	 送信セル数.
	::= { perfIfSlotEntry 6 }

perfIfSlotInDropCellsCounters OBJECT-TYPE
	SYNTAX	Counter
	ACCESS	read-only
	STATUS	mandatory
	DESCRIPTION
		"The number of receive drop cells."
	--	 受信廃棄セル数.
	::= { perfIfSlotEntry 7 }

	-- perfIfSlotEntry8 shall be absent.
	-- perfIfSlotEntry 8 は欠番とする

perfIfSlotHCThresholdExcessCells OBJECT-TYPE
        SYNTAX  OCTET STRING (SIZE(8))
        ACCESS  read-only
        STATUS  mandatory
        DESCRIPTION
		"The number of threshold excess cells"
	--	閾値超過セル数.
        ::= { perfIfSlotEntry 9 }

perfIfSlotThresholdExcessCells OBJECT-TYPE
        SYNTAX  Counter
        ACCESS  read-only
        STATUS  mandatory
        DESCRIPTION
		"The number of threshold excess cells"
	--	閾値超過セル数.
        ::= { perfIfSlotEntry 10 }

perfIfSlotHCUpcErrorCells OBJECT-TYPE
        SYNTAX  OCTET STRING (SIZE(8))
        ACCESS  read-only
        STATUS  mandatory
        DESCRIPTION
		"Number of UPC error cells."
	--	ＵＰＣエラーセル数.
        ::= { perfIfSlotEntry 11 }

perfIfSlotUpcErrorCells OBJECT-TYPE
        SYNTAX  Counter
        ACCESS  read-only
        STATUS  mandatory
        DESCRIPTION
		"Number of UPC error cells."
	--	ＵＰＣエラーセル数.
        ::= { perfIfSlotEntry 12 }

perfIfPhysTable	OBJECT-TYPE
	SYNTAX	SEQUENCE OF PerfIfPhysEntry
	ACCESS	not-accessible
	STATUS	mandatory
	DESCRIPTION
		"JpnToEng[物理層パフォーマンスモニタを示すテーブル.]"
	--	物理層パフォーマンスモニタを示すテーブル.
	::= { perf 4 }

perfIfPhysEntry	OBJECT-TYPE
	SYNTAX	PerfIfPhysEntry
	ACCESS	not-accessible
	STATUS	mandatory
	DESCRIPTION
		"JpnToEng[物理層パフォーマンスモニタのエントリ.]"
	--	物理層パフォーマンスモニタのエントリ.
	INDEX	{ perfIfPhysPort }
	::= { perfIfPhysTable 1 }

PerfIfPhysEntry ::=
	SEQUENCE {
		perfIfPhysPort
			INTEGER,
		perfIfPhysHCHecErorrs
			OCTET STRING,
		perfIfPhysHecErorrs
			INTEGER,
		perfIfPhysHCHecDropCells
			OCTET STRING,
		perfIfPhysHecDropCells
			INTEGER,
		perfIfPhysHCB1Errors
			OCTET STRING,
		perfIfPhysB1Errors
			INTEGER,
		perfIfPhysHCB2Errors
			OCTET STRING,
		perfIfPhysB2Errors
			INTEGER,
		perfIfPhysHCB3Errors
			OCTET STRING,
		perfIfPhysHCB3Errors
			INTEGER,
		perfIfPhysHCPathFEBEs
			OCTET STRING,
		perfIfPhysPathFEBEs
			INTEGER,
		perfIfPhysHCLineFEBEs
			OCTET STRING,
		perfIfPhysLineFEBEs
			INTEGER,
		perfIfPhysHCFramingErrors
			OCTET STRING,
		perfIfPhysFramingErrors
			INTEGER,
		perfIfPhysHCReceivedCells
			OCTET STRING,
		perfIfPhysReceivedCells
			INTEGER,
		perfIfPhysHCTransmittedCells
			OCTET STRING,
		perfIfPhysTransmittedCells
			INTEGER,
		perfIfPhysHCIdelUnassignedCells
			OCTET STRING,
		perfIfPhysIdelUnassignedCells
			INTEGER,
		perfIfPhysHCFEBEErrors
			OCTET STRING,
		perfIfPhysFEBEErrors
			INTEGER,
		perfIfPhysHCFEBEs
			OCTET STRING,
		perfIfPhysFEBEs
			INTEGER,
		perfIfPhysHCPathParityErrors
			OCTET STRING,
		perfIfPhysPathParityErrors
			INTEGER,
		perfIfPhysHCParityErrors
			OCTET STRING,
		perfIfPhysParityErrors
			INTEGER,
		perfIfPhysHCSEZs
			OCTET STRING,
		perfIfPhysSEZs
			INTEGER,
		perfIfPhysHCBitErrors
			OCTET STRING,
		perfIfPhysBitErrors
			INTEGER,
		perfIfPhysHCLcvErrors
			OCTET STRING,
		perfIfPhysLcvErrors
			INTEGER,
		perfIfPhysHCBip8Errors
			OCTET STRING,
		perfIfPhysBip8Errors
			INTEGER,
		perfIfPhysHCIecErrors
			OCTET STRING,
		perfIfPhysIecErrors
			INTEGER,
		perfIfPhysHCFramingPatternErrors
			OCTET STRING,
		perfIfPhysFramingPatternErrors
			INTEGER,
		perfIfPhysHCFramingBitErrors
			OCTET STRING,
		perfIfPhysFramingBitErrors
			INTEGER,
		perfIfPhysHCCrcErrors
			OCTET STRING,
		perfIfPhysCrcErrors
			INTEGER
	}

perfIfPhysPort	OBJECT-TYPE
	SYNTAX	INTEGER
	ACCESS	not-accessible
	STATUS	mandatory
	DESCRIPTION
		"Line number."
	--	回線番号.
	::= { perfIfPhysEntry 1 }

perfIfPhysHCHecErorrs	OBJECT-TYPE
	SYNTAX	OCTET STRING
	ACCESS	read-only
	STATUS	mandatory
	DESCRIPTION
		"Number of HEC error cells(64 bit applicable).
		On the line card other than OC12, J2 and PR-1.5M,
		the value of this object is 0."
	--	HEC エラーセル数 (64bit対応)
	--	Line Card が OC12, J2, PR-1.5M 以外の場合は 0 を返す.
	::= { perfIfPhysEntry 2 }

perfIfPhysHecErorrs	OBJECT-TYPE
	SYNTAX	INTEGER
	ACCESS	read-only
	STATUS	mandatory
	DESCRIPTION
		"Number of HEC error cells(32 bit applicable).
		On the line card other than OC12, J2 and PR-1.5M,
		the value of this object is 0."
	--	HEC エラーセル数 (32bit対応)
	--	Line Card が OC12, J2, PR-1.5M 以外の場合は 0 を返す.
	::= { perfIfPhysEntry 3 }

perfIfPhysHCHecDropCells	OBJECT-TYPE
	SYNTAX	OCTET STRING
	ACCESS	read-only
	STATUS	mandatory
	DESCRIPTION
		"Number of uncorrectable HEC error cells(64 bit applicable).
		On the line card other than OC3, OC12, OC12PMC, J2,
		PR-1.5, DS3, E3, DS1 and E1, the value of this object is 0."
	--	訂正不可能セル数 (64bit対応).
	--	Line Card が OC3, OC12, OC12PMC, J2, PR-1.5, DS3, E3,
	--	DS1, E1 以外の場合は 0 を返す.
	::= { perfIfPhysEntry 4 }

perfIfPhysHecDropCells	OBJECT-TYPE
	SYNTAX	INTEGER
	ACCESS	read-only
	STATUS	mandatory
	DESCRIPTION
		"Number of uncorrectable HEC error cells(32 bit applicable).
		On the line card other than OC3, OC12, OC12PMC, J2,
		PR-1.5, DS3, E3, DS1 and E1, the value of this object is 0."
	--	訂正不可能セル数 (32bit対応).
	--	Line Card が OC3, OC12, OC12PMC, J2, PR-1.5, DS3, E3,
	--	DS1, E1 以外の場合は 0 を返す.
	::= { perfIfPhysEntry 5 }

perfIfPhysHCB1Errors	OBJECT-TYPE
	SYNTAX	OCTET STRING
	ACCESS	read-only
	STATUS	mandatory
	DESCRIPTION
		"Number of B1 errors(64 bit applicable).
		On the line card other than OC3, OC12, OC12PMC,
		DS3, E3, DS1 and E1,
		the value of this object is 0."
	--	B1 エラー数 (64bit対応).
	--	Line Card が OC3, OC12, OC12PMC, DS3, E3, DS1, E1 以外
	--	の場合は 0 を返す.
	::= { perfIfPhysEntry 6 }

perfIfPhysB1Errors	OBJECT-TYPE
	SYNTAX	INTEGER
	ACCESS	read-only
	STATUS	mandatory
	DESCRIPTION
		"Number of B1 errors(32 bit applicable).
		On the line card other than OC3, OC12, OC12PMC,
		DS3, E3, DS1 and E1,
		the value of this object is 0."
	--	B1 エラー数 (32bit対応).
	--	Line Card が OC3, OC12, OC12PMC, DS3, E3, DS1, E1 以外
	--	の場合は 0 を返す.
	::= { perfIfPhysEntry 7 }

perfIfPhysHCB2Errors	OBJECT-TYPE
	SYNTAX	OCTET STRING
	ACCESS	read-only
	STATUS	mandatory
	DESCRIPTION
		"Number of B2 errors(64 bit applicable).
		On the line card other than OC3, OC12 and OC12PMC,
		the value of this object is 0."
	--	B2 エラー数 (64bit対応).
	--	Line Card が OC3, OC12, OC12PMC 以外
	--	の場合は 0 を返す.
	::= { perfIfPhysEntry 8 }

perfIfPhysB2Errors	OBJECT-TYPE
	SYNTAX	INTEGER
	ACCESS	read-only
	STATUS	mandatory
	DESCRIPTION
		"Number of B2 errors(32 bit applicable).
		On the line card other than OC3, OC12 and OC12PMC,
		the value of this object is 0."
	--	B2 エラー数 (32bit対応).
	--	Line Card が OC3, OC12, OC12PMC 以外
	--	の場合は 0 を返す.
	::= { perfIfPhysEntry 9 }

perfIfPhysHCB3Errors	OBJECT-TYPE
	SYNTAX	OCTET STRING
	ACCESS	read-only
	STATUS	mandatory
	DESCRIPTION
		"Number of B3 errors(64 bit applicable).
		On the line card other than OC3, OC12 and OC12PMC,
		the value of this object is 0."
	--	B3 エラー数 (64bit対応)
	--	Line Card が OC3, OC12, OC12PMC 以外
	--	の場合は 0 を返す.
	::= { perfIfPhysEntry 10 }

perfIfPhysB3Errors	OBJECT-TYPE
	SYNTAX	INTEGER
	ACCESS	read-only
	STATUS	mandatory
	DESCRIPTION
		"Number of B3 errors(32 bit applicable).
		On the line card other than OC3, OC12 and OC12PMC,
		the value of this object is 0."
	--	B3 エラー数 (32bit対応)
	--	Line Card が OC3, OC12, OC12PMC 以外
	--	の場合は 0 を返す.
	::= { perfIfPhysEntry 11 }

perfIfPhysHCPathFEBEs	OBJECT-TYPE
	SYNTAX	OCTET STRING
	ACCESS	read-only
	STATUS	mandatory
	DESCRIPTION
		"Number of Path FEBEs(64 bit applicable).
		On the line card other than OC3, OC12 and OC12PMC,
		the value of this object is 0."
	--	Path FEBE 数 (64bit対応)
	--	Line Card が OC3, OC12, OC12PMC 以外
	--	の場合は 0 を返す.
	::= { perfIfPhysEntry 12 }

perfIfPhysPathFEBEs	OBJECT-TYPE
	SYNTAX	INTEGER
	ACCESS	read-only
	STATUS	mandatory
	DESCRIPTION
		"Number of Path FEBEs(32 bit applicable).
		On the line card other than OC3, OC12 and OC12PMC,
		the value of this object is 0."
	--	Path FEBE 数 (32bit対応)
	--	Line Card が OC3, OC12, OC12PMC 以外
	--	の場合は 0 を返す.
	::= { perfIfPhysEntry 13 }

perfIfPhysHCLineFEBEs	OBJECT-TYPE
	SYNTAX	OCTET STRING
	ACCESS	read-only
	STATUS	mandatory
	DESCRIPTION
		"Number of Line (Section) FEBEs(64 bit applicable).
		On the line card other than OC3, OC12 and OC12PMC,
		the value of this object is 0."
	--	Line (Section) FEBE 数 (64bit対応)
	--	Line Card が OC3, OC12, OC12PMC 以外
	--	の場合は 0 を返す.
	::= { perfIfPhysEntry 14 }

perfIfPhysLineFEBEs	OBJECT-TYPE
	SYNTAX	INTEGER
	ACCESS	read-only
	STATUS	mandatory
	DESCRIPTION
		"Number of Line (Section) FEBEs(32 bit applicable).
		On the line card other than OC3, OC12 and OC12PMC,
		the value of this object is 0."
	--	Line (Section) FEBE 数 (32bit対応)
	--	Line Card が OC3, OC12, OC12PMC 以外
	--	の場合は 0 を返す.
	::= { perfIfPhysEntry 15 }

perfIfPhysHCFramingErrors	OBJECT-TYPE
	SYNTAX	OCTET STRING
	ACCESS	read-only
	STATUS	mandatory
	DESCRIPTION
		"Number of Framing errors(64 bit applicable).
		On the line card other than DS1, E1, DS3 and E3,
		the value of this object is 0."
	--	Framing エラー数 (64bit対応)
	--	Line Card が DS1, E1, DS3, E3 以外の場合は 0 を返す.
	::= { perfIfPhysEntry 16 }

perfIfPhysFramingErrors	OBJECT-TYPE
	SYNTAX	INTEGER
	ACCESS	read-only
	STATUS	mandatory
	DESCRIPTION
		"Number of Framing errors(32 bit applicable).
		On the line card other than DS1, E1, DS3 and E3,
		the value of this object is 0."
	--	Framing エラー数 (32bit対応)
	--	Line Card が DS1, E1, DS3, E3 以外の場合は 0 を返す.
	::= { perfIfPhysEntry 17 }

perfIfPhysHCReceivedCells	OBJECT-TYPE
	SYNTAX	OCTET STRING
	ACCESS	read-only
	STATUS	mandatory
	DESCRIPTION
		"The Number of the receive cells(64 bit applicable).
		On the line card other than DS3, E3 and OC12PMC,
		the value of this object is 0."
	--	受信セル数 (64bit対応)
	--	Line Card が DS3, E3, OC12PMC 以外の場合は 0 を返す.
	::= { perfIfPhysEntry 18 }

perfIfPhysReceivedCells	OBJECT-TYPE
	SYNTAX	INTEGER
	ACCESS	read-only
	STATUS	mandatory
	DESCRIPTION
		"The Number of the receive cells(32 bit applicable).
		On the line card other than DS3, E3 and OC12PMC,
		the value of this object is 0."
	--	受信セル数 (32bit対応)
	--	Line Card が DS3, E3, OC12PMC 以外の場合は 0 を返す.
	::= { perfIfPhysEntry 19 }

perfIfPhysHCTransmittedCells	OBJECT-TYPE
	SYNTAX	OCTET STRING
	ACCESS	read-only
	STATUS	mandatory
	DESCRIPTION
		"The Number of the transmit cells(64 bit applicable).
		On the line card other than DS3, E3 and OC12PMC,
		the value of this object is 0."
	--	送信セル数 (64bit対応)
	--	Line Card が DS3, E3, OC12PMC 以外の場合は 0 を返す.
	::= { perfIfPhysEntry 20 }

perfIfPhysTransmittedCells	OBJECT-TYPE
	SYNTAX	INTEGER
	ACCESS	read-only
	STATUS	mandatory
	DESCRIPTION
		"The Number of the transmit cells(32 bit applicable).
		On the line card other than DS3, E3 and OC12PMC,
		the value of this object is 0."
	--	送信セル数 (32bit対応)
	--	Line Card が DS3, E3, OC12PMC 以外の場合は 0 を返す.
	::= { perfIfPhysEntry 21 }

perfIfPhysHCIdelUnassignedCells	OBJECT-TYPE
	SYNTAX	OCTET STRING
	ACCESS	read-only
	STATUS	mandatory
	DESCRIPTION
		"The Number of Idle/Unassigned cells(64 bit applicable).
		On the line card other than DS3 and E3,
		the value of this object is 0."
	--	Idle/Unassigned セル数 (64bit対応)
	--	Line Card が DS3, E3 以外の場合は 0 を返す.
	::= { perfIfPhysEntry 22 }

perfIfPhysIdelUnassignedCells	OBJECT-TYPE
	SYNTAX	INTEGER
	ACCESS	read-only
	STATUS	mandatory
	DESCRIPTION
		"The Number of Idle/Unassigned cells(32 bit applicable).
		On the line card other than DS3 and E3,
		the value of this object is 0."
	--	Idle/Unassigned セル数 (32bit対応)
	--	Line Card が DS3, E3 以外の場合は 0 を返す.
	::= { perfIfPhysEntry 23 }

perfIfPhysHCFEBEErrors	OBJECT-TYPE
	SYNTAX	OCTET STRING
	ACCESS	read-only
	STATUS	mandatory
	DESCRIPTION
		"Number of FEBE errors(64 bit applicable).
		On the line card other than DS3, E3, DS1 and E1,
		the value of this object is 0."
	--	FEBE エラー数 (64bit対応).
	--	Line Card が DS3, E3, DS1, E1 以外の場合は 0 を返す.
	::= { perfIfPhysEntry 24 }

perfIfPhysFEBEErrors	OBJECT-TYPE
	SYNTAX	INTEGER
	ACCESS	read-only
	STATUS	mandatory
	DESCRIPTION
		"Number of FEBEs errors(32 bit applicable).
		On the line card other than DS3, E3, DS1 and E1,
		the value of this object is 0."
	--	FEBE エラー数 (32bit対応).
	--	Line Card が DS3, E3, DS1, E1 以外の場合は 0 を返す.
	::= { perfIfPhysEntry 25 }

perfIfPhysHCFEBEs	OBJECT-TYPE
	SYNTAX	OCTET STRING
	ACCESS	read-only
	STATUS	mandatory
	DESCRIPTION
		"Number of FEBEs(64 bit applicable).
		On the line card other than DS3, E3, E1 and CE-E1,
		the value of this object is 0."
	--	FEBE 数 (64bit対応).
	--	Line Card が DS3, E3, E1, FR-E1, CE-E1 以外の場合は 0 を返す.
	::= { perfIfPhysEntry 26 }

perfIfPhysFEBEs	OBJECT-TYPE
	SYNTAX	INTEGER
	ACCESS	read-only
	STATUS	mandatory
	DESCRIPTION
		"Number of FEBEs(32 bit applicable).
		On the line card other than DS3, E3, E1 and CE-E1,
		the value of this object is 0."
	--	FEBE 数 (32bit対応).
	--	Line Card が DS3, E3, E1, FR-E1, CE-E1 以外の場合は 0 を返す.
	::= { perfIfPhysEntry 27 }

perfIfPhysHCPathParityErrors	OBJECT-TYPE
	SYNTAX	OCTET STRING
	ACCESS	read-only
	STATUS	mandatory
	DESCRIPTION
		"Number of path parity errors(64 bit applicable).
		On the line card other than DS3,
		the value of this object is 0."
	--	パスパリティエラー数 (64bit対応)
	--	Line Card が DS3 以外の場合は 0 を返す.
	::= { perfIfPhysEntry 28 }

perfIfPhysPathParityErrors	OBJECT-TYPE
	SYNTAX	INTEGER
	ACCESS	read-only
	STATUS	mandatory
	DESCRIPTION
		"Number of path parity errors(32 bit applicable).
		On the line card other than DS3,
		the value of this object is 0."
	--	パスパリティエラー数 (32bit対応)
	--	Line Card が DS3 以外の場合は 0 を返す.
	::= { perfIfPhysEntry 29 }

perfIfPhysHCParityErrors	OBJECT-TYPE
	SYNTAX	OCTET STRING
	ACCESS	read-only
	STATUS	mandatory
	DESCRIPTION
		"Number of parity errors(64 bit applicable).
		On the line card other than DS3,
		the value of this object is 0."
	--	パリティエラー数 (64bit対応)
	--	Line Card が DS3 以外の場合は 0 を返す.
	::= { perfIfPhysEntry 30 }

perfIfPhysParityErrors	OBJECT-TYPE
	SYNTAX	INTEGER
	ACCESS	read-only
	STATUS	mandatory
	DESCRIPTION
		"Number of parity errors(32 bit applicable).
		On the line card other than DS3,
		the value of this object is 0."
	--	パリティエラー数 (32bit対応)
	--	Line Card が DS3 以外の場合は 0 を返す.
	::= { perfIfPhysEntry 31 }

perfIfPhysHCSEZs	OBJECT-TYPE
	SYNTAX	OCTET STRING
	ACCESS	read-only
	STATUS	mandatory
	DESCRIPTION
		"Number of detections of Summed excessive Zero
		(64 bit applicable).
		On the line card other than DS3,
		the value of this object is 0."
	--	Summed excessive Zero 検出数 (64bit対応)
	--	Line Card が DS3 以外の場合は 0 を返す.
	::= { perfIfPhysEntry 32 }

perfIfPhysSEZs	OBJECT-TYPE
	SYNTAX	INTEGER
	ACCESS	read-only
	STATUS	mandatory
	DESCRIPTION
		"Number of detections of Summed excessive Zero
		(32 bit applicable).
		On the line card other than DS3,
		the value of this object is 0."
	--	Summed excessive Zero 検出数 (32bit対応)
	--	Line Card が DS3 以外の場合は 0 を返す.
	::= { perfIfPhysEntry 33 }

perfIfPhysHCBitErrors	OBJECT-TYPE
	SYNTAX	OCTET STRING
	ACCESS	read-only
	STATUS	mandatory
	DESCRIPTION
		"Number of Bit errors(64 bit applicable).
		On the line card other than DS3 and CE-DS1(SF mode),
		the value of this object is 0."
	--	Bit エラー数 (64bit対応)
	--	Line Card が DS3, CE-DS1(SFモード) 以外の場合は 0 を返す.
	::= { perfIfPhysEntry 34 }

perfIfPhysBitErrors	OBJECT-TYPE
	SYNTAX	INTEGER
	ACCESS	read-only
	STATUS	mandatory
	DESCRIPTION
		"Number of Bit errors(32 bit applicable).
		On the line card other than DS3 and CE-DS1(SF mode),
		the value of this object is 0."
	--	Bit エラー数 (32bit対応)
	--	Line Card が DS3, CE-DS1(SFモード) 以外の場合は 0 を返す.
	::= { perfIfPhysEntry 35 }

perfIfPhysHCLcvErrors	OBJECT-TYPE
	SYNTAX	OCTET STRING
	ACCESS	read-only
	STATUS	mandatory
	DESCRIPTION
		"Number of LCV errors(64 bit applicable).
		On the line card other than DS3, E3, DS1, E1,
		FR-E1, CE-DS1, FR-DS1 and CE-E1,
		the value of this object is 0."
	--	LCV エラー数 (64bit対応)
	--	Line Card が DS3, E3, DS1, E1, FR-E1, CE-DS1, FR-DS1, CE-E1
	--	以外の場合は 0 を返す.
	::= { perfIfPhysEntry 36 }

perfIfPhysLcvErrors	OBJECT-TYPE
	SYNTAX	INTEGER
	ACCESS	read-only
	STATUS	mandatory
	DESCRIPTION
		"Number of LCV errors(32 bit applicable).
		On the line card other than DS3, E3, DS1, E1,
		FR-E1, CE-DS1, FR-DS1 and CE-E1,
		the value of this object is 0."
	--	LCV エラー数 (32bit対応)
	--	Line Card が DS3, E3, DS1, E1, FR-E1, CE-DS1, FR-DS1, CE-E1
	--	以外の場合は 0 を返す.
	::= { perfIfPhysEntry 37 }

perfIfPhysHCBip8Errors	OBJECT-TYPE
	SYNTAX	OCTET STRING
	ACCESS	read-only
	STATUS	mandatory
	DESCRIPTION
		"Number of BIP-8 errors(64 bit applicable).
		On the line card other than E3,
		the value of this object is 0."
	--	BIP-8 エラー数 (64bit対応)
	--	Line Card が E3 以外の場合は 0 を返す.
	::= { perfIfPhysEntry 38 }

perfIfPhysBip8Errors	OBJECT-TYPE
	SYNTAX	INTEGER
	ACCESS	read-only
	STATUS	mandatory
	DESCRIPTION
		"Number of BIP-8 errors(32 bit applicable).
		On the line card other than E3,
		the value of this object is 0."
	--	BIP-8 エラー数 (32bit対応)
	--	Line Card が E3 以外の場合は 0 を返す.
	::= { perfIfPhysEntry 39 }

perfIfPhysHCIecErrors	OBJECT-TYPE
	SYNTAX	OCTET STRING
	ACCESS	read-only
	STATUS	mandatory
	DESCRIPTION
		"Number of IEC errors(64 bit applicable).
		On the line card other than E3,
		the value of this object is 0."
	--	IEC エラー数 (64bit対応)
	--	Line Card が E3 以外の場合は 0 を返す.
	::= { perfIfPhysEntry 40 }

perfIfPhysIecErrors	OBJECT-TYPE
	SYNTAX	INTEGER
	ACCESS	read-only
	STATUS	mandatory
	DESCRIPTION
		"Number of IEC errors(32 bit applicable).
		On the line card other than E3,
		the value of this object is 0."
	--	IEC エラー数 (32bit対応)
	--	Line Card が E3 以外の場合は 0 を返す.
	::= { perfIfPhysEntry 41 }

perfIfPhysHCFramingPatternErrors	OBJECT-TYPE
	SYNTAX	OCTET STRING
	ACCESS	read-only
	STATUS	mandatory
	DESCRIPTION
		"Number of Framing pattern errors(64 bit applicable).
		On the line card other than E3,
		the value of this object is 0."
	--	Framing pattern エラー数 (64bit対応)
	--	Line Card が E3 以外の場合は 0 を返す.
	::= { perfIfPhysEntry 42 }

perfIfPhysFramingPatternErrors	OBJECT-TYPE
	SYNTAX	INTEGER
	ACCESS	read-only
	STATUS	mandatory
	DESCRIPTION
		"Number of Framing pattern errors(32 bit applicable).
		On the line card other than E3,
		the value of this object is 0."
	--	Framing pattern エラー数 (32bit対応)
	--	Line Card が E3 以外の場合は 0 を返す.
	::= { perfIfPhysEntry 43 }

perfIfPhysHCFramingBitErrors	OBJECT-TYPE
	SYNTAX	OCTET STRING
	ACCESS	read-only
	STATUS	mandatory
	DESCRIPTION
		"Number of Framing bit errors(64 bit applicable).
		On the line card other than DS1, E1, FR-E1, CE-DS1, FR-DS1
		and CE-E1, the value of this object is 0."
	--	Framing bit エラー数 (64bit対応)
	--	Line Card が DS1,E1,FR-E1,CE-DS1,FR-DS1, CE-E1 以外
	--	の場合は 0 を返す.
	::= { perfIfPhysEntry 44 }

perfIfPhysFramingBitErrors	OBJECT-TYPE
	SYNTAX	INTEGER
	ACCESS	read-only
	STATUS	mandatory
	DESCRIPTION
		"Number of Framing bit errors(32 bit applicable).
		On the line card other than DS1, E1, FR-E1, CE-DS1, FR-DS1
		and CE-E1, the value of this object is 0."
	--	Framing bit エラー数 (32bit対応)
	--	Line Card が DS1,E1,FR-E1,CE-DS1,FR-DS1,CE-E1 以外
	--	の場合は 0 を返す.
	::= { perfIfPhysEntry 45 }

perfIfPhysHCCrcErrors	OBJECT-TYPE
	SYNTAX	OCTET STRING
	ACCESS	read-only
	STATUS	mandatory
	DESCRIPTION
		"Number of CRC errors(64 bit applicable).
		On the line card other than DS1, E1, FR-E1, FR-DS1,
		CE-DS1(ESF mode) and CE-E1, the value of this object is 0."
	--	CRC エラー数 (64bit対応)
	--	Line Card が DS1,E1,FR-E1,FR-DS1,CE-DS1(ESFモード),CE-E1
	--	以外の場合は 0 を返す.
	::= { perfIfPhysEntry 46 }

perfIfPhysCrcErrors	OBJECT-TYPE
	SYNTAX	INTEGER
	ACCESS	read-only
	STATUS	mandatory
	DESCRIPTION
		"Number of CRC errors(32 bit applicable).
		On the line card other than DS1, E1, FR-E1, FR-DS1,
		CE-DS1(ESF mode) and CE-E1, the value of this object is 0."
	--	CRC エラー数 (32bit対応)
	--	Line Card が DS1,E1,FR-E1,FR-DS1,CE-DS1(ESFモード),CE-E1
	--	以外の場合は 0 を返す.
	::= { perfIfPhysEntry 47 }



--	The Scalability Group

--	scale	OBJECT IDENTIFIER ::= { m7-phase2-mib 6 }
	--	JpnToEng(次の６１行分を)
	--	<< tftp 実行手順 >>
	--
	--	1. allocate の SET
	--		Manager は scaleStatus に allocate を SET することに
	--		より tftp を実行する権利を取得する.
	--		これにより Agent は以下の Object に Default 値を
	--		設定する. Default 値は以下の通りである.
	--
	--		scaleCause    : succeed (3)
	--		scaleDataType : system (1)
	--		scaleTarget   : 0.0.0.0
	--		scaleFileName : zero length string
	--		scaleSwSide   : act (1)
	--
	--		scale 配下の Object に SET 出来るのは scaleStatus への
	--		allocate の SET に成功した Manager のみであり,
	--		allocate の SET に成功するのは scaleStatus が free
	--		の場合のみか,もしくはallocateの状態が１０分以上続いた
	--		場合のみである.
	--
	--	2. 各パラメータの SET
	--		Manager は各パラメータ(データ種別, Target-IP-Address,
	--		ファイル名)に値を SET する.
	--
	--	3. 実行指示
	--		scaleStatus に install / backup の何れかを SET する.
	--		これにより Agent は各パラメータのチェックを行う.
	--		問題がなければ scaleCause を start に変更した後,
	--		tftp の開始を通知する Trap を Manager に送信し,
	--		tftp を開始する.
	--		問題があれば scaleStatus を allocate に変更し, 要因を
	--		scaleCause に設定する.
	--
	--	4. 結果の GET
	--		Agent は tftp 終了時, scaleStatus を allocate に変更し,
	--		結果を scaleCause に設定する. 更に Manager に対して
	--		tftp の終了を通知する Trap を送信する.
	--
	--		但し, Software の install が正常終了した場合は Trap は
	--		発行されない.
	--
	--		scaleStatus を allocate に戻す場合には, 各パラメータへの
	--		Default 値の設定は行わない.
	--
	--	5. 必要に応じて 2. から 4. までの手順を繰り返す
	--		( allocate の SET に成功した Manager は scaleStatus
	--		に free を SET することなく, 連続して tftp を実行
	--		することが可能である. )
	--
	--	6. free の SET.
	--		Manager は tftp を終了する場合には scaleStatus に
	--              free を SET し, tftp を行う権利を解放しなければ
	--              ならない.
	--
	--		(注) allocate した Manager が free を SET する前に
	--		Manager-Agent 間の通信に問題が発生した等の理由によって
	--		実行権が永久に確保されたままになるという状況を回避する
	--		ために以下の条件を設ける. (FINNETカスタマイズ版のみ)
	--
	--		<< 条件 >>
	--		allocate 状態が 10 分以上続いた場合, Agent 側は
	--		scaleStatus を強制的に free に変更する.

scaleStatus	OBJECT-TYPE
	SYNTAX	INTEGER {
			allocate (1),	-- Acquire the right to execute tftp.
			install  (2),	-- Order to execute tftp (install).
			backup   (3),	-- Order to execute tftp (backup).
			free     (4)	-- Release the right to execute tftp.
		}
	ACCESS	read-write
	STATUS	mandatory
	DESCRIPTION
		"Order to execute and state."
	--	実行指示および状態.
	::= { scale 1 }

scaleCause	OBJECT-TYPE
	SYNTAX	INTEGER {
			other         (1),	-- other than stated below.
			start         (2),	-- in execution.
			succeed       (3),	-- normal end. Default.
			nearend       (4),	-- normal end.
						-- the number of write counts
						-- approaches to the limit.
			timeOut       (5),	-- connection time out.
			fileNotFound  (6),	-- file not found.
			accessViolate (7),	-- memory access error.
			checksumError (8),	-- crc check error.
			noData        (9),	-- JpnToEng[CDR収集件数が0.]
						-- notSupported.
                        sbyAccessError(10)      -- SBY system access error.
		}
	ACCESS	read-only
	STATUS	mandatory
	DESCRIPTION
		"The result of execution."
	--	実行結果.
	::= { scale 2 }

scaleDataType	OBJECT-TYPE
	SYNTAX	INTEGER {
			system   (1),	-- software
			config   (2),	-- office data
			bill-cdr (3)	-- JpnToEng[課金情報]
					-- notSupported
		}
	ACCESS	read-write
	STATUS	mandatory
	DESCRIPTION
		"Data type."
	--	データ種別.
	::= { scale 3 }

scaleTarget	OBJECT-TYPE
	SYNTAX	IpAddress
	ACCESS	read-write
	STATUS	mandatory
	DESCRIPTION
		"IP address of the target."
	--	Target の IP address.
	::= { scale 4 }

scaleFileName	OBJECT-TYPE
	SYNTAX	DisplayString
	ACCESS	read-write
	STATUS	mandatory
	DESCRIPTION
		"File name(up to 127 characters)."
	--	ファイル名 ( 最大 127 文字 ).
	::= { scale 5 }

scaleSwSide     OBJECT-TYPE
	SYNTAX  INTEGER {
			act   (1),	-- ACT system
			sby   (2)	-- SBY system
	}
	ACCESS  read-write
	STATUS  mandatory
	DESCRIPTION
		"Indicate which system of the SW-Engine."
	--	系.
	::= { scale 6 }

--	The Card Group

cardStatusTable	OBJECT-TYPE
	SYNTAX	SEQUENCE OF CardStatusEntry
	ACCESS	not-accessible
	STATUS	mandatory
	DESCRIPTION
		"Table showing the configuration information of the line
		card with CPU."
	--	CPU 付き Line Card の Configration 情報を示すテーブル.
	::= { card 1 }

cardStatusEntry	OBJECT-TYPE
	SYNTAX	CardStatusEntry
	ACCESS	not-accessible
	STATUS	mandatory
	DESCRIPTION
		"Entry of the configuration nformation of the line card
		with CPU."
	--	CPU 付き Line Card の Configration 情報のエントリ.
	INDEX	{ slotIfConfIndex }
	::= { cardStatusTable 1 }

CardStatusEntry ::=
	SEQUENCE {
		cardStatusServerType            INTEGER,
		cardStatusRevision              DisplayString,
		cardStatusMateSlotNumber        INTEGER,
		cardStatusMode                  INTEGER,
		cardStatusPriority		INTEGER,
		cardStatusAtmAddr		OCTET STRING,
		cardStatusMateAtmAddr		OCTET STRING
	}

cardStatusServerType	OBJECT-TYPE
	SYNTAX	INTEGER
	ACCESS	read-only
	STATUS	mandatory
	DESCRIPTION
		"Indicate the types of the server installed in
		the line card with CPU:
			other (1) ...other than the below stated types
			LANE  (2)
			ARP   (4)
			NHRP  (8)
			MPOA  (16)
		If more than one server type is installed, return the sum
		of their values.
		e.g.
			Only NHRP           is installed ---> 8
			ARP and NHRP       are installed ---> 4 + 8 = 12
			LANE, ARP and NHRP are installed ---> 2 + 4 + 8 = 14"
	--	CPU 付き Line Card に実装されている Server の種別を表す.
	--	複数の ServerType を実装している場合は,それぞれの値の
	--	和で返す.
	::= { cardStatusEntry 1 }

cardStatusRevision	OBJECT-TYPE
	SYNTAX	DisplayString
	ACCESS	read-only
	STATUS	mandatory
	DESCRIPTION
		"The revision of the software installed in the line card
		with CPU.
		e.g., ...X means the number of revision.
		Software Version X.X(X)  Boot ROM Version KXX"
	--	CPU 付き Line Card に搭載されるソフトウェアのリビジョン.
	::= { cardStatusEntry 2 }

cardStatusMateSlotNumber	OBJECT-TYPE
	SYNTAX	INTEGER (0..16)
	ACCESS	read-only
	STATUS	mandatory
	DESCRIPTION
		"The slot number of the card with double configuration
		(including itself).
		If it is single configuration/although it is of double
		configuration, SBY system is not implemented, return zero."
	--	自分と 2 重化構成になっている Card の Slot 番号.
	--	1 重化の場合 / 2 重化に configuration されているが
	--	SBY 系が未実装の場合は 0 を返す.
	::= { cardStatusEntry 3 }

cardStatusMode	OBJECT-TYPE
	SYNTAX	INTEGER	{
			act (1),
			sby (2),
			single (3),
			other (4)
		}
	ACCESS	read-only
	STATUS	mandatory
	DESCRIPTION
		"Operational mode of the card."
	--	Card の動作モード.
	::= { cardStatusEntry 4 }

cardStatusPriority	OBJECT-TYPE
	SYNTAX	INTEGER	{
			local (1),		-- JpnToEng[同一筐体での二重化 または、Singleモード]
			remotePrimary (2),	-- JpnToEng[リモート二重化時のプライマリ]
			remoteSecoundary (3)	-- JpnToEng[リモート二重か時のセカンダリ]
		}
	ACCESS	read-only
	STATUS	mandatory
	DESCRIPTION
		"JpnToEng(次の1行分)"
	--	リモート二重化時の再開優先順位を示す.
	::= { cardStatusEntry 5 }

cardStatusAtmAddr	OBJECT-TYPE
	SYNTAX	OCTET STRING(SIZE(0 | 20))
	ACCESS	read-only
	STATUS	mandatory
	DESCRIPTION
		"JpnToEng(次の2行分)"
	--	二重化時の自系 card を実装している switch の ATM アドレス.
	--	Singleモードの時は, 0 length.
	::= { cardStatusEntry 6 }

cardStatusMateAtmAddr	OBJECT-TYPE
	SYNTAX	OCTET STRING(SIZE(0 | 20))
	ACCESS	read-only
	STATUS	mandatory
	DESCRIPTION
		"JpnToEng(次の2行分)"
	--	二重化時の他系 card を実装している switch の ATM アドレス.
	--	Singleモードの時は, 0 length.
	::= { cardStatusEntry 7 }

cardOpeTable	OBJECT-TYPE
	SYNTAX	SEQUENCE OF CardOpeEntry
	ACCESS	not-accessible
	STATUS	mandatory
	DESCRIPTION
		"The table showing the command operations to the line
		card with CPU.
		If the card configured on SBY system is indicated,
		return noSuchName."
	--	CPU 付き Line Card へのコマンド操作を定義したテーブル.
	--	SBY 系に configuration されている Card を指定した場合は
	--	noSuchName を返す.
	::= { card 2 }

cardOpeEntry	OBJECT-TYPE
	SYNTAX	CardOpeEntry
	ACCESS	not-accessible
	STATUS	mandatory
	DESCRIPTION
		"Entry of command operation to the line card with CPU."
	--	CPU 付き Line Card へのコマンド操作のエントリ.
	INDEX	{ slotIfConfIndex }
	::= { cardOpeTable 1 }

CardOpeEntry ::=
	SEQUENCE {
		cardOpeReset            INTEGER,
		cardOpeDiagnosis        INTEGER,
		cardOpeSave             INTEGER,
		cardOpeSaveResult       INTEGER,
		cardOpeCopy             INTEGER,
		cardOpeCopyResult       INTEGER
	}

cardOpeReset	OBJECT-TYPE
	SYNTAX	INTEGER {
			noOperation (1),	-- None.
			reset (2),		-- Restart the system.
			ach (3)			-- Switch to the ACT system.
		}
	ACCESS	read-write
	STATUS	mandatory
	DESCRIPTION
		"Card Reset processing.
		Return noOperation(1) at read.
		JpnToEng[リモート二重化構成時は設定不可とし,
		genErrorを返却する.]"
	--	Card Reset 処理.
	--	Read 時は常に noOperation (1) を返す.
	--	リモート二重化構成時は設定不可とし,genErrorを返却する.
	::= { cardOpeEntry 1 }

cardOpeDiagnosis	OBJECT-TYPE
	SYNTAX	INTEGER {
			noOperation (1),
			diagnosis (2)
		}
	ACCESS	not-accessible
	STATUS	mandatory
	DESCRIPTION
		"Card diagnostic processing.
		Diagnose the SBY system card of double configuration with
		(the ACT system card).
		Return noOperation (1) at read.
		JpnToEng[リモート二重化構成時は設定不可とし,
		genErrorを返却する.]"
	--	Card 診断処理.
	--	自分 ( ACT 系 Card ) と 2 重化構成に configuration されている
	--	SBY 系 Card の診断を行う.
	--	Read 時は常に noOperation (1) を返す.
	--	リモート二重化構成時は設定不可とし,genErrorを返却する.
	::= { cardOpeEntry 2 }

cardOpeSave	OBJECT-TYPE
	SYNTAX	INTEGER {
			noOperation (1),
			save (2)
		}
	ACCESS	read-write
	STATUS	mandatory
	DESCRIPTION
		"Card Save processing.
		Save the system configuration information in FROM.
		If it is of double configuration, save it in SBY
		system FROM as well.
		Return noOperation (1) at read."
	--	Card Save 処理.
	--	System Configuration 情報を FROM に SAVE する.
	--	2 重化に configuration されている場合は SBY 系の FROM
	--	にも SAVE する.
	--	Read 時は常に noOperation (1) を返す.
	::= { cardOpeEntry 3 }

cardOpeSaveResult	OBJECT-TYPE
	SYNTAX	INTEGER {			    -- ACT/SBY
			succeed (1),		    -- OK/OK
			succeed-act (2),	    -- OK/NG
			succeed-sby (3),	    -- NG/OK
			temporaryFailure (4),	    -- NG/NG
			nearend (5),		    -- OK(NearEND)/OK(NearEND)
			nearend-act (6),	    -- OK(NearEND)/OK
			nearend-act-failure-sby (7),-- OK(NearEND)/NG
			nearend-sby (8),	    -- OK/OK(NearEND)
			nearend-sby-failure-act (9),-- NG/OK(NearEND)
			notReady (10),		    -- SAVE cannot be performed.
			ready (11)		    -- SAVE is in preparation.
		}
	ACCESS	read-only
	STATUS	mandatory
	DESCRIPTION
		"The result of card save processing.
		OK /NG indicate that SAVE processing completed/failed,
		respectively.
		(NearEND) indicates that the number of writes into FROM
		approaches to the limit."
	--	Card Save 処理の結果.
	--	OK/NG は, SAVE 処理の成功 / 失敗を示す.
	--	(NearEND) は FROM への書き込み回数が限界に近付いた
	--	ことをを示す.
	::= { cardOpeEntry 4 }

cardOpeCopy	OBJECT-TYPE
	SYNTAX	INTEGER {
			noOperation (1),
			copy-all-from-act (2),
			copy-all-from-sby (3),
			copy-config-from-act (4),
			copy-config-from-sby (5),
			copy-system-from-act (6),
			copy-system-from-sby (7)
		}
	ACCESS	read-write
	STATUS	mandatory
	DESCRIPTION
		"Card Copy processing.
		Return noOperation (1) at read."
	--	Card Copy 処理.
	--	Read 時は常に noOperation (1) を返す.
	::= { cardOpeEntry 5 }

cardOpeCopyResult	OBJECT-TYPE
	SYNTAX	INTEGER {
			succeed (1),	-- COPY completed.
			temporaryFailure (2),	-- COPY failed.
			nearend (3),	-- The number of writes into FROM
					-- at the copy destination
					-- approaches to the limit.
			notReady (4),	-- COPY cannot be performed.
			ready (5)	-- Copy is in preparation.
		}
	ACCESS	read-only
	STATUS	mandatory
	DESCRIPTION
		"Result of Card Copy processing."
	--	Card Copy 処理の結果.
	::= { cardOpeEntry 6 }

--	The Clock Group

clockOpe	OBJECT IDENTIFIER ::= { clock 1 }
	--	JpnToEng(次の５４行分を)
	--	<< クロック設定手順 >>
	--
	--	1. allocate の SET.
	--		Manager は clockOpeStatusに allocate をSETすることに
	--		より, クロックモードの設定をする権利を取得する.
	--		これにより Agentは以下の Object に Default 値を
	--		設定する. Default 値は以下の通りである.
	--
	--		clockOpeCause		: noWriting (1)
	--		clockOpeMode		: master (1)
	--		clockOpeAccuracy	: -1
	--		clockOpeSlaveLine1	: -1
	--		clockOpeSlaveLine2	: -1
	--		clockOpeSlaveLine3	: -1
	--		clockOpeSlaveLine4	: -1
	--
	--		clockOpe 配下の Objectに SET出来るのはclockOpeStatus
	--		への allocate のSETに成功したManagerのみであり,
	--		allocate の SETに成功するのは clockOpeStatusが free
	--		の場合のみである.
	--
	--	2. 各パラメータの SET
	--		各パラメータに値を SET する.
	--
	--	3. 設定指示
	--		clockOpeStatusに set を設定する.
	--		これにより Agentはパラメータのチェックを行い,
	--		問題がなければクロックの設定を行う.
	--		パラメータに問題があった場合は, 要因をclockOpeCauseに
	--		反映させる.
	--		クロックの設定が正常に終了した場合(succeed,setWarning)
	--		は,Agentは実際に装置に登録された内容にパラメータを
	--		変更する.
	--
	--	4. 結果の GET
	--		clockOpeStatusに set を設定した後, Agentは
	--		クロック設定処理を行い, 設定結果をclockOpeCauseに
	--		反映させる.
	--		Managerは clockOpeCauseをGETし 設定結果を取得する.
	--
	--	5. free の SET
	--		Managerはクロック設定を終了する場合は clockOpeStatusに
	--		free を SETし, クロック設定を行う権利を解放しなければ
	--		ならない. また,２重freeも可能とする.
	--
	--		(注) allocate した Manager が free を SET する前に
	--		Manager-Agent 間の通信に問題が発生した等の理由によって
	--		実行権が永久に確保されたままになるという状況を回避する
	--		ために以下の条件を設ける.
	--
	--		<< 条件 >>
	--		allocate した Manager からの最後の clockOpe 配下の
	--		Object へのAccessから60秒以上経過している場合,
	--		他のManager が free を SET することを可能とする.


clockOpeStatus	OBJECT-TYPE
	SYNTAX	INTEGER	{
			allocate (1),	-- Acquire the right to set Clock Mode.
			set      (2),	-- Designate the Clock Mode setting.
			free     (3)	-- Release the right to set Clock Mode.
		}
	ACCESS	read-write
	STATUS	mandatory
	DESCRIPTION
		"Used to control Clock setting processing."
	--	クロック設定処理の制御に使用される.
	::= { clockOpe 1 }

clockOpeCause	OBJECT-TYPE
	SYNTAX	INTEGER	{
			noWriting          (1),	-- initial value. default
			other              (2),	-- system error.
			succeed            (3),	-- normal end.
			setWarning         (4),	-- normal end.
						-- JpnToEng[(一部のポートでエラー)]
			parameterNotEnough (5),	-- parameter error.
						-- JpnToEng[(ポート重複指定含む)]
			portNotExist       (6),	-- Slot(port) is not installed.
			portOutOfRange     (7),	-- Port is out of range.
			allPortFailure     (8)	-- All ports cannot be set.
		}
	ACCESS	read-only
	STATUS	mandatory
	DESCRIPTION
		"Result of Clock setting processing."
	--	Clock Mode 設定処理の結果.
	::= { clockOpe 2 }

clockOpeMode	OBJECT-TYPE
	SYNTAX	INTEGER	{
			master (1),	-- Default
			slave  (2)
		}
	ACCESS	read-write
	STATUS	mandatory
	DESCRIPTION
		"Clock Mode."
	::= { clockOpe 3 }

clockOpeAccuracy	OBJECT-TYPE
	SYNTAX	INTEGER (0..255|-1)
	ACCESS	read-write
	STATUS	mandatory
	DESCRIPTION
		"Accuracy[ppm] of clock.
		JpnToEng[(SLAVEモード設定時のみ有効)]
		If no set, value is -1."
	--	クロックの精度[ppm].
	--	SLAVEモード設定時のみ有効.
	--	未設定の場合(-1).
	::= { clockOpe 4 }

clockOpeSlaveLine1	OBJECT-TYPE
	SYNTAX	INTEGER	(1..32|-1)
	ACCESS	read-write
	STATUS	mandatory
	DESCRIPTION
		"Slave line number 1.
		JpnToEng[(SLAVEモード設定時のみ有効)]
		If no set, value is -1."
	--	従属回線番号１.
	--	SLAVEモード設定時のみ有効.
	--	未設定の場合(-1).
	::= { clockOpe 5 }

clockOpeSlaveLine2	OBJECT-TYPE
	SYNTAX	INTEGER	(1..32|-1)
	ACCESS	read-write
	STATUS	mandatory
	DESCRIPTION
		"Slave line number 2.
		JpnToEng[(SLAVEモード設定時のみ有効)]
		Slave line number 1 shall be set already.
		If no set, value is -1."
	--	従属回線番号２.
	--	SLAVEモード設定時のみ有効.
	--	従属回線番号１が設定済であること.
	--	未設定の場合(-1).
	::= { clockOpe 6 }

clockOpeSlaveLine3	OBJECT-TYPE
	SYNTAX	INTEGER	(1..32|-1)
	ACCESS	read-write
	STATUS	mandatory
	DESCRIPTION
		"Slave line number 3.
		JpnToEng[(SLAVEモード設定時のみ有効)]
		Slave line number 1~2 shall be set already.
		If no set, value is -1."
	--	従属回線番号３.
	--	SLAVEモード設定時のみ有効.
	--	従属回線番号１〜２が設定済であること.
	--	未設定の場合(-1).
	::= { clockOpe 7 }

clockOpeSlaveLine4	OBJECT-TYPE
	SYNTAX	INTEGER (1..32|-1)
	ACCESS	read-write
	STATUS	mandatory
	DESCRIPTION
		"Slave line number 4.
		JpnToEng[(SLAVEモード設定時のみ有効)]
		Slave line number 1~3 shall be set already.
		If no set, value is -1."
	--	従属回線番号４.
	--	SLAVEモード設定時のみ有効.
	--	従属回線番号１〜３が設定済であること.
	--	未設定の場合(-1).
	::= { clockOpe 8 }

ClockSlaveLineStatus	::= INTEGER {
			notApplicable        (1), -- for master mode or
						  -- no set
			active               (2), -- JpnToEng[従属中]
			standby              (3), -- JpnToEng[従属待ち]
			hardError            (4), -- hardware fault
			adminDown            (5), -- in AdminDown status
			notExist             (6), -- not installed
			linfDown             (7), -- line fault
			testing              (8), -- diagnostic test in progress
			notSupported         (9), -- PKG not supported
			syncronizedFailure  (10), -- Synchronized failure
			lossOf64kClock      (11), -- loss of 64k clock(DCS)
			lossOf8kClock       (12), -- loss of 8k clock(DCS)
			frequencyOutOfRange (13)  -- Frequency out of range(DCS)
		}
	--	State of slave line
	--	従属回線の状態.

clockMode	OBJECT-TYPE
	SYNTAX	INTEGER	{
			master (1),
			slave  (2)
		}
	ACCESS	read-only
	STATUS	mandatory
	DESCRIPTION
		"Clock Mode."
	::= { clock 2 }

clockAccuracy	OBJECT-TYPE
	SYNTAX	INTEGER (0..255|-1)
	ACCESS	read-only
	STATUS	mandatory
	DESCRIPTION
		"Accuracy[ppm] of clock."
	--	クロックの精度 [ppm].
	::= { clock 3 }

clockSlaveLine	OBJECT-TYPE
	SYNTAX	INTEGER
	ACCESS	read-only
	STATUS	mandatory
	DESCRIPTION
		"The number of the actually slaved line.
		If mode is master (1), it is -1. "
	--	実際に従属している回線番号.
	--	Mode が master(1) の場合は -1.
	::= { clock 4 }

clockSlaveLine1	OBJECT-TYPE
	SYNTAX	INTEGER
	ACCESS	read-only
	STATUS	mandatory
	DESCRIPTION
		"Slave line number 1.
		If no set, value is -1."
	--	従属回線番号１.
	--	未設定の場合(-1).
	::= { clock 5 }

clockSlaveLine1Status	OBJECT-TYPE
	SYNTAX	ClockSlaveLineStatus
	ACCESS	read-only
	STATUS	mandatory
	DESCRIPTION
		"State of slave line 1."
	--	従属回線番号１の状態.
	::= { clock 6 }

clockSlaveLine2	OBJECT-TYPE
	SYNTAX	INTEGER
	ACCESS	read-only
	STATUS	mandatory
	DESCRIPTION
		"Slave line number 2.
		If no set, value is -1."
	--	従属回線番号２.
	--	未設定の場合(-1).
	::= { clock 7 }

clockSlaveLine2Status	OBJECT-TYPE
	SYNTAX	ClockSlaveLineStatus
	ACCESS	read-only
	STATUS	mandatory
	DESCRIPTION
		"State of slave line 2."
	--	従属回線番号２の状態.
	::= { clock 8 }

clockSlaveLine3	OBJECT-TYPE
	SYNTAX	INTEGER
	ACCESS	read-only
	STATUS	mandatory
	DESCRIPTION
		"Slave line number 3.
		If no set, value is -1."
	--	従属回線番号３.
	--	未設定の場合(-1).
	::= { clock 9 }

clockSlaveLine3Status	OBJECT-TYPE
	SYNTAX	ClockSlaveLineStatus
	ACCESS	read-only
	STATUS	mandatory
	DESCRIPTION
		"State of slave line 3."
	--	従属回線番号３の状態.
	::= { clock 10 }

clockSlaveLine4	OBJECT-TYPE
	SYNTAX	INTEGER
	ACCESS	read-only
	STATUS	mandatory
	DESCRIPTION
		"Slave line number 4.
		If no set, value is -1."
	--	従属回線番号４.
	--	未設定の場合(-1).
	::= { clock 11 }

clockSlaveLine4Status	OBJECT-TYPE
	SYNTAX	ClockSlaveLineStatus
	ACCESS	read-only
	STATUS	mandatory
	DESCRIPTION
		"State of slave line 4."
	--	従属回線番号４の状態.
	::= { clock 12 }

--	The Diag Group

	--	JpnToEng(次の６５行分を)
	--	<< 診断実行手順 >>
	--
	--	1. allocate の SET.
	--		allocate を SET することにより, 診断処理を実行する
	--		権利を取得する.
	--		診断処理を実行出来るのは allocate の SET に成功した
	--		Manager のみであり, diagActionStatus が free の
	--		ときのみ allocate 可能である.
	--		allocate の SET 時に Agent 側は各パラメータに初期値
	--		を設定する.
	--		初期値は以下の通りである.
	--
	--		diagActionKind : 1  ( switch )
	--		diagCause      : 1  ( normal )
	--		diagParam1     : -1
	--
	--	2. 各パラメータの SET.
	--		diagActionKind に値を SET することで診断部位を特定する.
	--		diagActionKind に slot を指定した場合は diagParam1
	--		に対象 Slot 番号を指定しなければならない.
	--
	--	3. start の SET.
	--		Manager が start を SET することにより Agent は
	--		各パラメータのチェックを行い, 問題がなければ
	--		diagActionStatus を execute に変更した後, 診断処理を
	--		開始する.
	--		問題があった場合は, 結果を diagPreCause に反映させ,
	--		diagActionStatus を end に変更する.
	--
	--		診断処理を行っている間は diagActionStatus の値は
	--		execute のままである.
	--		start を SET 出来るのは diagActionStatus が
	--		allocate の場合のみである.
	--
	--	4. 結果の GET.
	--		診断終了時, Agent は diagCause に結果を反映させて
	--		diagActionStatus を end に変更する.
	--		これにより Manager は diagCause の取得を行い, 結果を
	--		認識する.
	--
	--		allocate した Manager が diagCause を GET した時点で
	--		diagActionStatus が end であれば, Agent 側は
	--		diagActionStatus を allocate に戻し, 各パラメータに
	--		初期値を設定する.
	--
	--	5. 必要に応じて 2. から 4. までの手順を繰り返す.
	--		( allocate を SET した Manager は diagActionStatus
	--		に free を SET することなく, 複数の部位を連続して
	--		診断することが可能である. )
	--
	--	6. free (5) の SET.
	--		Manager 側は診断処理を終了する場合には diagActionStatus
	--		に free を SET し, 診断処理を行う権利を解放しなければ
	--		ならない.
	--
	--		(注) allocate した Manager が free を SET する前に
	--		Manager-Agent 間の通信に問題が発生した等の理由によって
	--		実行権が永久に確保されたままになるという状況を回避する
	--		ために以下の条件を設ける.
	--
	--		<< 条件 >>
	--		allocate した Manager からの最後の diag 配下の
	--		Object への Access から 60 秒以上経過している場合,
	--		diagActionStatus が allocate か end であれば, 他の
	--		Manager が free を SET することを可能とする.

diagActionStatus	OBJECT-TYPE
	SYNTAX	INTEGER	{
			allocate (1),	-- acquire the right to diagnostics test
			start    (2),	-- order to execute diagnostics test
			execute  (3),	-- in execution of diagnostics test
			end      (4),	-- end of diagnostics test
			free     (5)	-- release the right to diagnostics test
		}
	ACCESS	read-write
	STATUS	mandatory
	DESCRIPTION
		"Used to control diagnostics test processing."
	--	診断処理の制御に使用される.
	::= { diag 1 }

diagActionKind	OBJECT-TYPE
	SYNTAX	INTEGER	{
			switch (1),
			cpu    (2),
			slot   (3)
		}
	ACCESS	read-write
	STATUS	mandatory
	DESCRIPTION
		"JpnToEng(次の４行分を)"
	--	診断対象部位.
	--	switch (1), cpu (2) はSBYのSW,CPUに対しての診断(２重化時のみ).
	--	slot (3) を指定した場合は diagParam1 に対象 Slot 番号を
	--	設定しなければならない.
	::= { diag 2 }

diagPreCause	OBJECT-TYPE
	SYNTAX	INTEGER	{
			other              (1),	-- NG other than stated below
			succeed            (2),	-- normal end of parameter check
			parameterNotEnough (3),	-- Parameter is not enough.
			notInstalled       (4),	-- SW-Engine/CPU/LineBoard
						-- is not installed.
			notSupport	   (5), -- JpnToEng[診断機能をSupport
						-- してないPKG]
			diagnostics	   (6), -- JpnToEng[指定装置が診断中]
			clkChgError	   (7), -- JpnToEng[従属回線が切り替え
						-- れない]
			initializing	   (8), -- JpnToEng[SW-Engine初期化中
						-- の為診断不可能]
			sbyAccessError	   (9)  -- JpnToEng[SBY系にアクセス
						-- できない]
		}
	ACCESS	read-only
	STATUS	mandatory
	DESCRIPTION
		"JpnToEng[診断処理実行前のパラメータチェックの結果.]"
	--	診断処理実行前のパラメータチェックの結果.
	::= { diag 3 }

diagCause	OBJECT-TYPE
	SYNTAX	INTEGER	{
			normal   (1),
--	Switch Engine	(01xxyyzz)
			diagNG-SC  (1020004),
			diagNG-BF  (1030004),
			diagNG-ES0 (1040007),
			diagNG-ES1 (1040107),
			diagNG-SAR (1050005),
			diagNG-DI  (1060010),
			diagNG-CPU (1070002),
			diagNG-CPU-Register           (1600201),
			diagNG-CPU-Timer-Test         (1600202),
			diagNG-CPU-MM-Test            (1600203),
			diagNG-CPU-DRAM-Partial-Write (1600204),
			diagNG-CPU-Memory-Machining   (1600205),
			diagNG-CPU-Cash-Test          (1600206),
			diagNG-CPU-BSN-Parity         (1600207),
			diagNG-CPU-LANCE-LoopBack     (1600208),
			diagNG-Local-Memory       (1600301),
			diagNG-DMAC-Register      (1600302),
			diagNG-MISCEMA-Register   (1600303),
			diagNG-XACK-Interrupt     (1600304),
			diagNG-ASW-Register       (1600401),
			diagNG-BMT                (1600402),
			diagNG-Failer-Detect      (1600403),
			diagNG-SAR-Register       (1600501),
			diagNG-SAR-Control-Memory (1600502),
			diagNG-SAR-Packet-Memory  (1600503),
			diagNG-DI-Register        (1600504),
			diagNG-DI-Memory          (1600505),
			diagNG-ES-LoopBack                 (1600601),
			diagNG-ES-Own-LoopBack             (1600602),
			diagNG-ES-Other-LoopBack           (1600603),
			diagNG-ES-Own-Broadcast-LoopBack   (1600604),
			diagNG-ES-Other-Broadcast-LoopBack (1600605),
			diagNG-ES-Nto1-Test                (1600606),
			diagNG-ATOM-Buffer-OVF     (1600607),
			diagNG-BackPressure        (1600608),
			diagNG-RICEtoCell-Compete  (1600609),
			diagNG-SAR-LoopBack        (1600701),
			diagNG-DI-LoopBack         (1600702),
			diagNG-SW-Own-LoopBack     (1600703),
			diagNG-SW-Other-LoopBack   (1600704),
			diagNG-Illegal-Cell-Detect (1600705),
			diagNG-SARtoPacket-Compete (1600706),
			diagNG-PCMCIA-Register     (1601101),
--	Line Buffer	(02xxyyzz)
			diagNG-IXB-Register   (2010002),
			diagNG-OXB-Register   (2020003),
			diagNG-UHT-Register   (2030003),
			diagNG-IBC-Register   (2040008),
			diagNG-IBC-RIRO-SGRAM (2040009),
			diagNG-IBC-HT-i-SGRAM (2040010),
			diagNG-IBC-RIRO-SRAM  (2040011),
			diagNG-OBC-Register   (2040012),
			diagNG-OBC-CellBuffer (2040013),
			diagNG-OBC-HT-o       (2040014),
			diagNG-OBC-BCI-BMT    (2040015),
			diagNG-FR-SDRAM       (2090006),
--	Line Card	(03xxyyzz)
			diagNG-PHY0         (3010002),
			diagNG-PHY1         (3010102),
			diagNG-PHY2         (3010202),
			diagNG-PHY3         (3010302),
			diagNG-MUX          (3020012),
			diagNG-CU2INF       (3030002),
			diagNG-UNIC         (3040003),
			diagNG-CFAD         (3050003),
			diagNG-PLD          (3060003),
			diagNG-FPGA         (3070004),
			diagNG-FRM0         (3080004),
			diagNG-FRM1         (3080104),
			diagNG-S-UNI622     (3120004),
			diagNG-TAC0         (3130001),
			diagNG-TAC1         (3130101),
			diagNG-TAC2         (3130201),
			diagNG-TAC3         (3130301),
			diagNG-LCA-Common   (3150001),
			diagNG-LCA-Separate (3150002),
			diagNG-UCFAD2       (3160001),
			diagNG-PM7345-0     (3140005),
			diagNG-PM7345-1     (3140105),
			diagNG-PM7345-2     (3140205),
			diagNG-PM7345-3     (3140305),
			diagNG-PM4341A-0    (3170001),
			diagNG-PM4341A-1    (3170101),
			diagNG-PM4341A-2    (3170201),
			diagNG-PM4341A-3    (3170301),
			diagNG-PM6341-0     (3180001),
			diagNG-PM6341-1     (3180101),
			diagNG-PM6341-2     (3180201),
			diagNG-PM6341-3     (3180301),
			diagNG-DCS-LCA      (3230003),
			diagNG-ALARM        (3190001),
			diagNG-FRAME        (3190002),
			diagNG-TS-CTL       (3190003),
			diagNG-FIFO-CTL     (3190004),
			diagNG-AAL1-SAR     (3200001),
			diagNG-FPGA-CE-DS1  (3210003),
			diagNG-FPGA-CE-E1   (3220004),
			diagNG-WAC-021      (3240001),
			diagNG-CPU-DRAM     (3250001),
			diagNG-CPU-Tout     (3250002)
		}
	ACCESS	read-only
	STATUS	mandatory
	DESCRIPTION
		"Result of diagnostics test processing."
	--	診断処理の結果.
	::= { diag 4 }

diagParam1	OBJECT-TYPE
	SYNTAX	INTEGER
	ACCESS	read-write
	STATUS	mandatory
	DESCRIPTION
		"JpnToEng[次の２行分]"
	--	診断する Slot の番号.
	--	diagActionKind が slot (3) 以外の場合は Don't care.
	::= { diag 5 }

--	The PNNI Group

--	pnni group で使用する type

	PnniAtmAddr ::= OCTET STRING (SIZE(20))
	--	ATM address.

	PnniNodeId ::= OCTET STRING (SIZE(22))
	--	PNNI node ID.

	PnniPeerGroupId ::= OCTET STRING (SIZE(14))
	--	PNNI peer group ID.

	PnniLevel ::= INTEGER (0..104)
	--	PNNI routing level indicator.


--	the pnni node group

pnniNode	OBJECT IDENTIFIER ::= { pnni 1 }

pnniNodeOpe	OBJECT IDENTIFIER ::= { pnniNode 1 }
	-- Object identifier reserved to add pnniNodeTable operation definition.
	-- pnniNodeTable操作定義追加の為に予約されている object identifier.

pnniNodeTable	OBJECT-TYPE
	SYNTAX	SEQUENCE OF PnniNodeEntry
	ACCESS	not-accessible
	STATUS	mandatory
	DESCRIPTION
		"Table of PNNI Logical node attributes.
		A row exist every PNNI peer group which the managed system
		belongs to."
	--	PNNI logical node 属性のテーブル.
	--	管理されるシステムが属する PNNI peer group 毎に,
	--	1つのrowが存在する.
	::= { pnniNode 2 }

pnniNodeEntry	OBJECT-TYPE
	SYNTAX	PnniNodeEntry
	ACCESS	not-accessible
	STATUS	mandatory
	DESCRIPTION
		"Entry of pnniNodeTable."
	--	pnniNodeTableのエントリ.
	INDEX	{ pnniNodeLevel }
	::= { pnniNodeTable 1 }

PnniNodeEntry ::=
	SEQUENCE {
		pnniNodeLevel			PnniLevel,
		pnniNodeId			PnniNodeId,
		pnniNodeAtmAddress		PnniAtmAddr,
		pnniNodePeerGroupId		PnniPeerGroupId,
		pnniNodeRestrictedTransit	TruthValue,
		pnniNodeRestrictedBranching	TruthValue,
		pnniNodeLeadershipPriority	INTEGER
	}

pnniNodeLevel OBJECT-TYPE
	SYNTAX	PnniLevel
	ACCESS	not-accessible
	STATUS	mandatory
	DESCRIPTION
		"PNNI hierarchy level where node(s) reside."
	--	ノードが存在する PNNI hierarchy の level.
	::= { pnniNodeEntry 1 }

pnniNodeId OBJECT-TYPE
	SYNTAX	PnniNodeId
	ACCESS	read-only
	STATUS	mandatory
	DESCRIPTION
		"Node ID."
	--	ノードID.
	::= { pnniNodeEntry 2 }

pnniNodeAtmAddress OBJECT-TYPE
	SYNTAX	PnniAtmAddr
	ACCESS	read-only
	STATUS	mandatory
	DESCRIPTION
		"ATM End System Address of node."
	--	ノードの ATM End System Address.
	::= { pnniNodeEntry 3 }

pnniNodePeerGroupId OBJECT-TYPE
	SYNTAX	PnniPeerGroupId
	ACCESS	read-only
	STATUS	mandatory
	DESCRIPTION
		"Peer Group Identifier of the peer group which a node
		belongs to."
	--	ノードが属する peer group の Peer Group Identifier.
	::= { pnniNodeEntry 4 }

pnniNodeRestrictedTransit OBJECT-TYPE
	SYNTAX	TruthValue
	ACCESS	read-only
	STATUS	mandatory
	DESCRIPTION
		"Restrict a node to be used as a transit route."
	--	ノードを中継路とすることを制限する.
	::= { pnniNodeEntry 5 }

pnniNodeRestrictedBranching OBJECT-TYPE
	SYNTAX	TruthValue
	ACCESS	read-only
	STATUS	mandatory
	DESCRIPTION
		"Restrict a node to be used as a branch point of
		point-to-multipoint."
	--	ノードを point-to-multipoint の 分岐点とすることを制限する.
	::= { pnniNodeEntry 6 }

pnniNodeLeadershipPriority OBJECT-TYPE
	SYNTAX	INTEGER (0..255)
	ACCESS	read-only
	STATUS	mandatory
	DESCRIPTION
		"Leadership priority which a node notifies of."
	--	ノードが通知する Leadership priority.
	::= { pnniNodeEntry 7 }

--	The MAT Command Group

matCmdStatus	OBJECT-TYPE
	SYNTAX	INTEGER	{
			allocate (1),
			inActive (2),	-- read-only
			active (3),	-- read-only
			free (4)
		}
	ACCESS	read-write
	STATUS	mandatory
	DESCRIPTION
		"JpnToEng(次の5行分)"
	--	SNMPによるMATコマンドの制御を行う.
	--	allocate : コマンド実行権の取得
	--	inActive : コマンド入力待ち
	--	active   : コマンド実行中
	--	free     : コマンド実行権の解放
	::= { matCmd 1 }

matCmdInput	OBJECT-TYPE
	SYNTAX	DisplayString
	ACCESS	read-write
	STATUS	mandatory
	DESCRIPTION
		"JpnToEng(次の1行分)"
	--	入力文字列.
	::= { matCmd 2 }

matCmdOutput	OBJECT-TYPE
	SYNTAX	DisplayString
	ACCESS	read-only
	STATUS	mandatory
	DESCRIPTION
		"JpnToEng(次の1行分)"
	--	出力文字列.
	::= { matCmd 3 }

matCmdOutputType	OBJECT-TYPE
	SYNTAX	INTEGER	{
			normal (1),
			continued (2),
			interactive (3)
		}
	ACCESS	read-only
	STATUS	mandatory
	DESCRIPTION
		"JpnToEng(次の4行分)"
	--	出力文字列 type.
	--	normal      : 通常の応答(最後の応答).
	--	continued   : 応答に続きがある.
	--	interactive : 応答に対して次の要求を入力する必要がある.
	::= { matCmd 4 }

matCmdStop	OBJECT-TYPE
	SYNTAX	INTEGER	{
			noOperation (1),
			stop (2)
		}
	ACCESS	read-write
	STATUS	mandatory
	DESCRIPTION
		"When the value is set to 'stop', the MAT command is stopped.
		When the value is set to 'noOperation', no operation is
		performed. When read, the value 'noOperation' is returned."
	::= { matCmd 5 }

matCmdTimeOut	OBJECT-TYPE
	SYNTAX	INTEGER(1..180)
--	Units
--		seconds
	ACCESS	read-write
	STATUS	mandatory
	DESCRIPTION
		"JpnToEng(次の1行分)"
	--	Timeout値.
	DEFVAL	{ 60 }
	::= { matCmd 6 }
END
