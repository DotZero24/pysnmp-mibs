-- ************************************************************************************************
-- FileName    :mpFrppMIB.my
-- Description :MultiMedia Platform private MIB
-- Revision History     :
--   Ver.     mark   date
--   01.06    @007   07/31/2001
-- ************************************************************************************************
--


MP-FRPP-MIB DEFINITIONS ::= BEGIN

   IMPORTS
      mgmt, NetworkAddress, IpAddress, Counter, Gauge, TimeTicks
      FROM RFC1155-SMI

      ifIndex
      FROM RFC1213-MIB

      OBJECT-TYPE
      FROM RFC-1212

--      DisplayString
--      FROM RFC1155-SMI

      TRAP-TYPE
      FROM RFC-1215

      RowStatus
        FROM SNMPv2-TC;

   NetPrefix ::= OCTET STRING (SIZE (13))

   DisplayString ::= OCTET STRING

-- The following definition was gotten from rfc1514
   DateAndTime ::= OCTET STRING (SIZE (8 | 11))
-- in OpenView , DateAndTime must be comment   98/12/15 YI
   --        A date-time specification for the local time of day.
   --        This data type is intended to provide a consistent
   --        method of reporting date information.
   --
   --            field  octets  contents                  range
   --            _____  ______  ________                  _____
   --              1      1-2   year                      0..65536
   --                           (in network byte order)
   --              2       3    month                     1..12
   --              3       4    day                       1..31
   --              4       5    hour                      0..23
   --              5       6    minutes                   0..59
   --              6       7    seconds                   0..60
   --                           (use 60 for leap-second)
   --              7       8    deci-seconds              0..9
   --              8       9    direction from UTC        "+" / "-"
   --                           (in ascii notation)
   --              9      10    hours from UTC            0..11
   --             10      11    minutes from UTC          0..59
   --
   --            Note that if only local time is known, then
   --            timezone information (fields 8-10) is not present.

-- The following definition was cadged from the Bridge MIB
      MacAddress ::= OCTET STRING (SIZE (6))
                                                -- a 6 octet address
                                                -- in the
                                                -- "canonical"
                                                -- order
      -- defined by IEEE 802.1a, i.e., as if it were transmitted
      -- least significant bit first, even though 802.5 (in
      -- contrast to other n802.x protocols) requires MAC
      -- addresses to be transmitted most significant bit first.
      --
      -- 16-bit addresses, if needed, are represented by setting
      -- their upper 4 octets to all 0's, i.e., AAFF would be
      -- represented as 00000000AAFF.

-- The following definition is privately defined for Sanfran Private MIB
      PhysAddress ::= OCTET STRING (SIZE (6))


--   nec               OBJECT IDENTIFIER ::= { enterprises 119}

--   necProduct        OBJECT IDENTIFIER ::= { nec 1 }
--   nec-mib           OBJECT IDENTIFIER ::= { nec 2 }
--   necExperimental   OBJECT IDENTIFIER ::= { nec 3 }

--   datax             OBJECT IDENTIFIER ::= { necProduct 3 }
--   ether-sw          OBJECT IDENTIFIER ::= { datax 10 }
--   sf                OBJECT IDENTIFIER ::= { ether-sw 3 }

--   necCommon         OBJECT IDENTIFIER ::= { nec-mib 1 }
--   necFunction       OBJECT IDENTIFIER ::= { nec-mib 2 }
--   necProductDepend  OBJECT IDENTIFIER ::= { nec-mib 3 }

--   datax-mib         OBJECT IDENTIFIER ::= { necProductDepend 3 }
--   ether-sw-mib      OBJECT IDENTIFIER ::= { datax-mib 10 }
--   ether-sw          OBJECT IDENTIFIER ::= { datax 10 }




  org         OBJECT IDENTIFIER     ::= { iso 3 }
  dod         OBJECT IDENTIFIER     ::= { org 6 }
  internet    OBJECT IDENTIFIER     ::= { dod 1 }
  private     OBJECT IDENTIFIER     ::= { internet 4 }
  enterprises OBJECT IDENTIFIER     ::= { private 1 }
  nec               OBJECT IDENTIFIER ::= { enterprises 119}


-- 98/12/15 YI mmpf => mmpf-mib CHG start
-- sysObjectID
   necProduct        OBJECT IDENTIFIER ::= { nec 1 }
   datax             OBJECT IDENTIFIER ::= { necProduct 3 }
   mmpf              OBJECT IDENTIFIER ::= { datax 13 }
   mmn9110           OBJECT IDENTIFIER ::= { mmpf 1 }
   mmn9120           OBJECT IDENTIFIER ::= { mmpf 2 }
-- [sysObjectID]  MM-Node9110/MM-Node9120
--  mmn9110           OBJECT IDENTIFIER ::= { nec necProduct(1) datax(3) mmpf(13) mmn9110(1) }
--  mmn9120           OBJECT IDENTIFIER ::= { nec necProduct(1) datax(3) mmpf(13) mmn9110(2) }


   nec-mib           OBJECT IDENTIFIER ::= { nec 2 }
   necProductDepend  OBJECT IDENTIFIER ::= { nec-mib 3 }
   datax-mib         OBJECT IDENTIFIER ::= { necProductDepend 3 }
   mmpf-mib          OBJECT IDENTIFIER ::= { datax-mib 13 }

   mpSystem                 OBJECT IDENTIFIER ::= { mmpf-mib 1 }
   mpIfCard                 OBJECT IDENTIFIER ::= { mmpf-mib 2 }
   mpEtherPort              OBJECT IDENTIFIER ::= { mmpf-mib 3 }
   mpVlan                   OBJECT IDENTIFIER ::= { mmpf-mib 4 }
   mpBridge                 OBJECT IDENTIFIER ::= { mmpf-mib 5 }
   mpDbAccess               OBJECT IDENTIFIER ::= { mmpf-mib 6 }
   mpEventLog               OBJECT IDENTIFIER ::= { mmpf-mib 7 }
   mpUiSession              OBJECT IDENTIFIER ::= { mmpf-mib 8 }
   mpFtp                    OBJECT IDENTIFIER ::= { mmpf-mib 9 }
   mpDhcp                   OBJECT IDENTIFIER ::= { mmpf-mib 10 }
   mpIp                     OBJECT IDENTIFIER ::= { mmpf-mib 11 }
   mpRip                    OBJECT IDENTIFIER ::= { mmpf-mib 12 }
   mpSnmp                   OBJECT IDENTIFIER ::= { mmpf-mib 13 }
   mpStats                  OBJECT IDENTIFIER ::= { mmpf-mib 14 }
   mpCli                    OBJECT IDENTIFIER ::= { mmpf-mib 15 }
   mpAtm                    OBJECT IDENTIFIER ::= { mmpf-mib 16 }
   mpLis                    OBJECT IDENTIFIER ::= { mmpf-mib 17 }
   mpDns                    OBJECT IDENTIFIER ::= { mmpf-mib 18 }
   mpLec                    OBJECT IDENTIFIER ::= { mmpf-mib 19 }
   mpMpc                    OBJECT IDENTIFIER ::= { mmpf-mib 20 }
   mpStp                    OBJECT IDENTIFIER ::= { mmpf-mib 21 }
   mpLlc                    OBJECT IDENTIFIER ::= { mmpf-mib 22 }
   mpOspf                   OBJECT IDENTIFIER ::= { mmpf-mib 23 }

   mpObsCtl                 OBJECT IDENTIFIER ::= { mmpf-mib 101 }
   mpCardInfo               OBJECT IDENTIFIER ::= { mmpf-mib 102 }
   mpInterface              OBJECT IDENTIFIER ::= { mmpf-mib 103 }
   mpPvoice                 OBJECT IDENTIFIER ::= { mmpf-mib 104 }
-- 98/12/15 YI mmpf => mmpf-mib CHG end

   mpAtmCallCtl             OBJECT IDENTIFIER ::= { mmpf-mib 110 }
   mpCes                    OBJECT IDENTIFIER ::= { mmpf-mib 111 }
   mpIpsw                   OBJECT IDENTIFIER ::= { mmpf-mib 112 }
   mpInsCtl                 OBJECT IDENTIFIER ::= { mmpf-mib 113 }
   mpFfr                    OBJECT IDENTIFIER ::= { mmpf-mib 114 }
   mpIpswAtm                OBJECT IDENTIFIER ::= { mmpf-mib 115 }

   mpPpp                    OBJECT IDENTIFIER ::= { mmpf-mib 120 }
   mpPos                    OBJECT IDENTIFIER ::= { mmpf-mib 121 }
   mpFrpp                   OBJECT IDENTIFIER ::= { mmpf-mib 123 }

--
--  ＦＲＰＰ  ＴＲＡＰ用のＭＩＢ
--

        mpFrppTrapInfo        OBJECT IDENTIFIER ::= { mpFrpp 1 }

        mpFrppTrapInfoMccid  OBJECT-TYPE
                SYNTAX  INTEGER
                ACCESS  read-only
                STATUS  mandatory
                DESCRIPTION
                     "A unique value to identify a multi channel(MCC-ID)."--                   MCC IDを得るObject。
                ::= { mpFrppTrapInfo 1 }

        mpFrppTrapInfoDlci  OBJECT-TYPE
                SYNTAX  INTEGER
                ACCESS  read-only
                STATUS  mandatory
                DESCRIPTION
                     "A unique value to identify a data link(DLCI)."
--                   DLCIを得るObject。
                ::= { mpFrppTrapInfo 2 }


-- MCC FrameRelay プライベートＭＩＢ   @001追加

-- MCC FrameRelay Chanel Configuration MIB

        mpFrppMccCfgTable OBJECT-TYPE
                SYNTAX SEQUENCE OF MpFrppMccCfgEntry
                ACCESS  not-accessible
                STATUS  mandatory
                DESCRIPTION "This is the table type object of the Mcc FrameRelay Chanel configuration."
                ::= { mpFrpp 2 }

        mpFrppMccCfgEntry OBJECT-TYPE
                SYNTAX  MpFrppMccCfgEntry
                ACCESS  not-accessible
                STATUS  mandatory
                DESCRIPTION "This is the table entry of mpFrppMccCfgTable."
                INDEX { mpFrppMccCfgIfIndex }
                ::= { mpFrppMccCfgTable 1 }

        MpFrppMccCfgEntry ::=
                 SEQUENCE {
                   mpFrppMccCfgIfIndex          INTEGER,
                   mpFrppMccCfgL2Status         INTEGER,
                   mpFrppMccCfgLmiProtocol      INTEGER,
                   mpFrppMccCfgUniType          INTEGER,
                   mpFrppMccCfgMonitoredEvents  INTEGER,
                   mpFrppMccCfgErrorThreshold   INTEGER,
                   mpFrppMccCfgFullEnqInterval  INTEGER,
                   mpFrppMccCfgLmiProcedure     INTEGER,
                   mpFrppMccCfgNetPollInterval  INTEGER,
                   mpFrppMccCfgUsrPollInterval  INTEGER,
--                 mpFrppMccCfgMtuSize          INTEGER,                @006
                   mpFrppMccCfgAsync            INTEGER,
--                 mpFrppMccCfgCllm             INTEGER,                @006
--                 mpFrppMccCfgCllmTim          INTEGER,                @006
                   mpFrppMccCfgRowStatus        RowStatus,
                   mpFrppMccCfgErrInfo          INTEGER
               }

        mpFrppMccCfgIfIndex  OBJECT-TYPE
                SYNTAX  INTEGER
                ACCESS  read-only
                STATUS  mandatory
                DESCRIPTION "The value of this object identifies
                             the MCC-ID (Mcc Channel number) ."
                         -- ＭＣＣ－ＩＤを示す。
                ::= { mpFrppMccCfgEntry 1 }

        mpFrppMccCfgL2Status OBJECT-TYPE
                SYNTAX   INTEGER {
                                up(1),
                                down(2),
                                testing(3)
                                }
                ACCESS  read-only
                STATUS  mandatory
                DESCRIPTION "The value of this object identifies the
                             layer 2 status."
                          -- レイヤー２の状態を示す。
                DEFVAL { down }
                ::= { mpFrppMccCfgEntry 2 }

        mpFrppMccCfgLmiProtocol OBJECT-TYPE
                SYNTAX  INTEGER {
                                ansi(1),   -- ANSI 91
                                itu(2),    -- ITU or FRF
                                noLmi(3)   -- LMI無し
                               }
                ACCESS  read-write
                STATUS  mandatory
                DESCRIPTION "The value of this object identifies the
                             link management interface protocol."
                          -- リンク管理インターフェース(LMI)のプロトコルタイプ
                          -- を示す。
                DEFVAL { ansi }
                ::= { mpFrppMccCfgEntry 3 }

        mpFrppMccCfgUniType OBJECT-TYPE
                SYNTAX  INTEGER {
                                dte(1),       -- DTE
                                dce(2)        -- DCE
                               }
                ACCESS  read-write
                STATUS  mandatory
                DESCRIPTION "The value of this object identifies
                             the frame relay user Network Interface type."
                          -- フレームリレーのユーザネットワークインタフェース
                          -- タイプを示す。
                DEFVAL { dte }
                ::= { mpFrppMccCfgEntry 4 }

        mpFrppMccCfgMonitoredEvents OBJECT-TYPE
                SYNTAX  INTEGER (1..10)
                ACCESS  read-write
                STATUS  mandatory
                DESCRIPTION "The value of this object identifies
                             the monitored events count(N393)."
                          -- 観測イベントカウント(N393)を示す。
                DEFVAL { 4 }
                ::= { mpFrppMccCfgEntry 5 }

        mpFrppMccCfgErrorThreshold OBJECT-TYPE
                SYNTAX  INTEGER (1..10)
                ACCESS  read-write
                STATUS  mandatory
                DESCRIPTION "The value of this object identifies
                             the error threshold(N392)."
                          -- エラーしきい値(N392)を示す。
                DEFVAL { 3 }
                ::= { mpFrppMccCfgEntry 6 }

        mpFrppMccCfgFullEnqInterval OBJECT-TYPE
                SYNTAX  INTEGER (1..255)
                ACCESS  read-write
                STATUS  mandatory
                DESCRIPTION "The value of this object identifies the i
                             full status (status of all PVCs) polling counter(N391)."
                          -- フルステータス問い合わせ(Full Status Enquiry)行う
                          -- タイミングを決定するカウンタ値を示す
                          -- (フルステータスポーリング(N391))
                DEFVAL { 6 }
                ::= { mpFrppMccCfgEntry 7 }

        mpFrppMccCfgLmiProcedure OBJECT-TYPE
               SYNTAX  INTEGER {
                                uniDirectional(1),   -- 単方向LMI
                                biDirectional(2)     -- 双方向LMI
                               }
               ACCESS  read-write
               STATUS  mandatory
               DESCRIPTION "The value of this object identifies the
                            link management interface (LMI) procedure."
                         -- リンク管理インターフェース(LMI)手順を示す。
               DEFVAL { uniDirectional }
               ::= { mpFrppMccCfgEntry 8 }

        mpFrppMccCfgNetPollInterval OBJECT-TYPE
               SYNTAX  INTEGER (5..30)
               ACCESS  read-write
               STATUS  mandatory
               DESCRIPTION "The value of this object identifies the
                            polling verification timer(T392)."
                         -- ステータス問い合わせ(Status Enquiry)の受信待ち
                         -- タイマー(T392)。
                         -- (ポーリング検証タイマ(T392))
               DEFVAL { 15 }
               ::= { mpFrppMccCfgEntry 9 }

        mpFrppMccCfgUsrPollInterval OBJECT-TYPE
               SYNTAX  INTEGER (5..30)
               ACCESS  read-write
               STATUS  mandatory
               DESCRIPTION "The value of this object identifies the
                           link integrity verification polling timer(T391)."
                         -- ステータス問い合わせ(Status Enquiry)のポーリング
                         -- 周期タイマーを示す
                         -- (リンク完全性確認ポーリングタイマ(T391))
               DEFVAL { 10 }
               ::= { mpFrppMccCfgEntry 10 }

        mpFrppMccCfgAsync OBJECT-TYPE
               SYNTAX  INTEGER {
                                enable(1),
                                disable(2)
                               }
               ACCESS  read-write
               STATUS  mandatory
               DESCRIPTION "The value of this object identifies the Async Flag."
                         -- 単一PVC非同期通知実行フラグ。
               DEFVAL { disable }
               ::= { mpFrppMccCfgEntry 11 }

        mpFrppMccCfgRowStatus OBJECT-TYPE
               SYNTAX  RowStatus
               ACCESS  read-write
               STATUS  mandatory
               DESCRIPTION "An entry in MCC Channel management table."
                         -- createAndGo(4)でtableの新規作成を行い
                         -- tableのコンフィグにデフォルト値を設定する
                         -- notInService(2)でtableへの変更を行い
                         -- 変更が終了したらactive(1)をSETする
                         -- active(1)をSETされるとMCC-FRへコンフィグダウンロード
                         -- 要求を行う
                         -- destroy(6)でtableを削除し、MCC-FRにコンフィグ削除を
                         -- 行う
               ::= { mpFrppMccCfgEntry 12 }

        mpFrppMccCfgErrInfo OBJECT-TYPE
               SYNTAX  INTEGER {
                                normal(1),                      -- 正常
                                parameterNotEnough(2),          -- パラメータ不足
                                badValue(3),                    -- 設定値異常
                                badIndexValue(4),               -- INDEX値異常
                                correlationError(5),            -- 相関関係NG
                                memoryAllocateFailure(6),       -- Memoryハント失敗
                                mbufHuntFailure(7),             -- MBUFハント失敗
                                relationalConfigExist(8),       -- 関連するConfigが存在
                                lowLayerConfigNotRegistered(9), -- 下位レイヤConfig未実装
                                mappingDataAlreadyExist(10),    -- マッピングデータが存在する
                                ipAddressNotDeleted(11),        -- ＩＰアドレステーブルは削除されていない
                                mccIdHuntFailure(12)            -- MCC ID生成失敗
                               }
               ACCESS  read-only
               STATUS  mandatory
               DESCRIPTION "The value of this object indicates error
                            information that became an error set to MIB
                            in this table."
                         -- Table内の各MIBへのSETでエラーとなった場合の、詳細
                         -- エラー情報を示す。
               ::= { mpFrppMccCfgEntry 13 }

-- ・MCC FrameRelay FRPP Configuration MIB                      @006

        mpFrppFrppCfgTable OBJECT-TYPE
               SYNTAX SEQUENCE OF MpFrppFrppCfgEntry
               ACCESS  not-accessible
               STATUS  mandatory
               DESCRIPTION "This is the table type object of the
                            Mcc FrameRelay FRPP configuration."
               ::= { mpFrpp 3 }

        mpFrppFrppCfgEntry OBJECT-TYPE
               SYNTAX  MpFrppFrppCfgEntry
               ACCESS  not-accessible
               STATUS  mandatory
               DESCRIPTION "This is the table entry of mpFrppFrppCfgTable."
               INDEX { mpFrppFrppCfgIfIndex, mpFrppFrppCfgMccidIndex,
                       mpFrppFrppCfgDlciIndex }                         --@006変更
               ::= { mpFrppFrppCfgTable 1 }

        MpFrppFrppCfgEntry ::=
                 SEQUENCE {
                   mpFrppFrppCfgIfIndex            INTEGER,
                   mpFrppFrppCfgMccidIndex         INTEGER,             --@006変更
                   mpFrppFrppCfgDlciIndex          INTEGER,             --@006変更
                   mpFrppFrppCfgFrppName           DisplayString,
                   mpFrppFrppCfgIpadd              IpAddress,
                   mpFrppFrppCfgSubnet             IpAddress,
                   mpFrppFrppCfgMtuSize            INTEGER,
                   mpFrppFrppCfgInterWorkType      INTEGER,
                   mpFrppFrppCfgCrtpSupport        INTEGER,             --003@追加
                   mpFrppFrppCfgCrtpLimit          INTEGER,             --003@追加
                   mpFrppFrppCfgCrtpMode           INTEGER,             --003@追加
                   mpFrppFrppCfgCrtpAging          INTEGER,             --003@追加
                   mpFrppFrppCfgCtcpSupport        INTEGER,             --003@追加
                   mpFrppFrppCfgCtcpLimit          INTEGER,             --003@追加
                   mpFrppFrppCfgCtcpMode           INTEGER,             --003@追加
                   mpFrppFrppCfgCtcpAging          INTEGER,             --003@追加
                   mpFrppFrppCfgHwSticFlag         INTEGER,             --005@追加
                   mpFrppDlciCfgMtuSize            INTEGER,
                   mpFrppDlciCfgBecn               INTEGER,
                   mpFrppDlciCfgEncap              INTEGER,
                   mpFrppDlciCfgDe                 INTEGER,
                   mpFrppDlciCfgPln                INTEGER,
                   mpFrppDlciCfgFragSize           INTEGER,
                   mpFrppDlciCfgMir                INTEGER,
                   mpFrppDlciCfgPerInc             INTEGER,
                   mpFrppDlciCfgPerDec             INTEGER,
                   mpFrppDlciCfgMincir             INTEGER,
                   mpFrppDlciCfgCir                INTEGER,
                   mpFrppDlciCfgSnapFlg            INTEGER,
                   mpFrppDlciQueueLenH             INTEGER,
                   mpFrppDlciQueueLenU             INTEGER,
                   mpFrppDlciQueueLenL             INTEGER,
                   mpFrppDlciQueueLenN             INTEGER,
                   mpFrppDlciQueueByteH            INTEGER,
                   mpFrppDlciQueueByteU            INTEGER,
                   mpFrppDlciQueueByteL            INTEGER,
                   mpFrppDlciQueueByteN            INTEGER,
                   mpFrppDlciIpQosClassAf3         INTEGER,
                   mpFrppDlciIpQosClassAf2         INTEGER,
                   mpFrppDlciIpQosClassAf1         INTEGER,
                   mpFrppDlciIpQosClassBe          INTEGER,
                   mpFrppDlciIpQosClassEf3         INTEGER,
                   mpFrppDlciIpQosClassEf2         INTEGER,
                   mpFrppDlciIpQosClassEf1         INTEGER,
                   mpFrppDlciIpQosClassAf4         INTEGER,
                   mpFrppDlciCfgInarpMode          INTEGER,
                   mpFrppDlciCfgTrapFilter         INTEGER,       --@002追加
                   mpFrppFrppCfgRowStatus          RowStatus,
                   mpFrppFrppCfgErrInfo            INTEGER
               }

        mpFrppFrppCfgIfIndex  OBJECT-TYPE
               SYNTAX  INTEGER
               ACCESS  read-only
               STATUS  mandatory
               DESCRIPTION "The value of this object identifies the
                            FRPP_NO (FRPP number) ."
                         -- ＦＲＰＰ番号を示す。
               ::= { mpFrppFrppCfgEntry 1 }

        mpFrppFrppCfgMccidIndex OBJECT-TYPE             --@006変更
               SYNTAX  INTEGER (0..2147483647)                  --003@変更
               ACCESS  read-only                        --003@変更 @006変更
               STATUS  mandatory
               DESCRIPTION "The value of this object is the mccid for
                            this entry."
                         -- FRPPインタフェースにマッピングされているmccid
                         -- を示す
               ::= { mpFrppFrppCfgEntry 2 }

       mpFrppFrppCfgDlciIndex OBJECT-TYPE               --@006変更
               SYNTAX  INTEGER (16..991)                --003@変更 @006変更
               ACCESS  read-only                        --003@変更 @006変更
               STATUS  mandatory
               DESCRIPTION "The value of this object is the Dlci for
                            this entry."
                         -- FrppインタフェースにマッピングされているDLCI
                         -- 番号を示す
               ::= { mpFrppFrppCfgEntry 3 }

        mpFrppFrppCfgFrppName    OBJECT-TYPE
               SYNTAX  DisplayString
               ACCESS  read-write
               STATUS  mandatory
               DESCRIPTION
                     "The textual name of the interface on the Frpp."
                        -- FRPP名
               ::= { mpFrppFrppCfgEntry 4 }

        mpFrppFrppCfgIpadd OBJECT-TYPE
               SYNTAX   IpAddress
               ACCESS   read-only
               STATUS   mandatory
               DESCRIPTION
                     "The value of this object is the FRPP IP address
                      for this entry."
                      -- クライアントIPアドレス
               ::= { mpFrppFrppCfgEntry 5 }

        mpFrppFrppCfgSubnet OBJECT-TYPE
               SYNTAX   IpAddress
               ACCESS   read-only
               STATUS   mandatory
               DESCRIPTION
                     "The value of this object is the FRPP IP address
                      for this entry."
                      -- クライアントサブネットマスク
               ::= { mpFrppFrppCfgEntry 6 }

        mpFrppFrppCfgMtuSize OBJECT-TYPE
               SYNTAX  INTEGER (1280..9180)                     --004@変更
               ACCESS  read-write
               STATUS  mandatory
               DESCRIPTION "The value of this object identifies the max frame
                            length on this port."
                         -- ルータからFRPPインタフェースまでのポート上で転送する
                         -- フレームの最大フレーム長を示す
               DEFVAL { 9180 }
               ::= { mpFrppFrppCfgEntry 7 }

        mpFrppFrppCfgInterWorkType OBJECT-TYPE
               SYNTAX  INTEGER {
                                ipoverfr(1),  -- IPoverFR
                                macoverfr(2)  -- MACoverFR
                               }
               ACCESS  read-write
               STATUS  mandatory
               DESCRIPTION "The value of this object indicates the
                            FRPP InterWorkType."
                         -- FRPPインタフェースのインタワーキング情報を示す。
               DEFVAL { ipoverfr }
               ::= { mpFrppFrppCfgEntry 8 }

        mpFrppFrppCfgCrtpSupport OBJECT-TYPE                    -- @003
               SYNTAX  INTEGER {
                                no(1),
                                support(2)
                               }
               ACCESS  read-write
               STATUS  mandatory
               DESCRIPTION "The value of this object indicates the
                            CRTP Support Flag."
                         -- CRTPサポート情報を示す。
               DEFVAL { no }
               ::= { mpFrppFrppCfgEntry 9 }

        mpFrppFrppCfgCrtpLimit OBJECT-TYPE
               SYNTAX  INTEGER (1..128)
               ACCESS  read-write
               STATUS  mandatory
               DESCRIPTION "The value of this object indicates the
                            CRTP Limit."
                         -- CRTP同時圧縮最大数を示す。
               DEFVAL { 128 }
               ::= { mpFrppFrppCfgEntry 10 }

        mpFrppFrppCfgCrtpMode OBJECT-TYPE
               SYNTAX  INTEGER {
                                through(1),
                                discard(2)
                               }
               ACCESS  read-write
               STATUS  mandatory
               DESCRIPTION "The value of this object indicates the
                            CRTP Mode."
                         -- CRTP同時圧縮最大数超の動作を示す。
               DEFVAL { through }
               ::= { mpFrppFrppCfgEntry 11}

        mpFrppFrppCfgCrtpAging OBJECT-TYPE
               SYNTAX  INTEGER (1..120)
               ACCESS  read-write
               STATUS  mandatory
               DESCRIPTION "The value of this object indicates the
                            CRTP Aging Time."
                         -- CRTPでのエージングタイマーを示す。
               DEFVAL { 5 }
               ::= { mpFrppFrppCfgEntry 12 }

        mpFrppFrppCfgCtcpSupport OBJECT-TYPE
               SYNTAX  INTEGER {
                                no(1),
                                support(2)
                               }
               ACCESS  read-write
               STATUS  mandatory
               DESCRIPTION "The value of this object indicates the
                            CTCP Support Flag."
                         -- CTCPサポート情報を示す。
               DEFVAL { no }
               ::= { mpFrppFrppCfgEntry 13 }

        mpFrppFrppCfgCtcpLimit OBJECT-TYPE
               SYNTAX  INTEGER (1..128)
               ACCESS  read-write
               STATUS  mandatory
               DESCRIPTION "The value of this object indicates the
                            CTCP Limit."
                         -- CTCP同時圧縮最大数を示す。
               DEFVAL { 128 }
               ::= { mpFrppFrppCfgEntry 14 }

        mpFrppFrppCfgCtcpMode OBJECT-TYPE
               SYNTAX  INTEGER {
                                through(1),
                                discard(2)
                               }
               ACCESS  read-write
               STATUS  mandatory
               DESCRIPTION "The value of this object indicates the
                            CTCP Mode."
                         -- CTCP同時圧縮最大数超の動作を示す。
               DEFVAL { through }
               ::= { mpFrppFrppCfgEntry 15}

        mpFrppFrppCfgCtcpAging OBJECT-TYPE
               SYNTAX  INTEGER (1..120)
               ACCESS  read-write
               STATUS  mandatory
               DESCRIPTION "The value of this object indicates the
                            CTCP Aging Time."
                         -- CTCPでのエージングタイマーを示す。
               DEFVAL { 30 }
               ::= { mpFrppFrppCfgEntry 16 }

        mpFrppFrppCfgHwSticFlag OBJECT-TYPE
               SYNTAX  INTEGER {
                                enable(1),
                                disable(2)
                               }
               ACCESS  read-write
               STATUS  mandatory
               DESCRIPTION "The value of this object indicates the
                            Statistics Request Flag."
                         -- 統計情報取得オプション。
               DEFVAL { enable }
               ::= { mpFrppFrppCfgEntry 17}

        mpFrppDlciCfgMtuSize OBJECT-TYPE
               SYNTAX  INTEGER
               ACCESS  read-only                                --@004変更
               STATUS  mandatory
               DESCRIPTION "The value of this object identifies the
                            inside maximum frame size(Mtu) in octets for
                            this frame relay logical port(DLCI).
                            This value shall not exceed the value of
                            mpFrCktMtuSize."
                         -- DLCI単位の入側最大フレーム長を示す
                         -- 本MIBに設定する値は、チャネルの最大フレーム長
                         -- (mpFrppMccCfgMtuSize)以下でなくてはならない
               ::= { mpFrppFrppCfgEntry 18 }

        mpFrppDlciCfgBecn OBJECT-TYPE
               SYNTAX  INTEGER {
                                enable(1),
                                disable(2)
                               }
               ACCESS  read-write
               STATUS  mandatory
               DESCRIPTION "The value of this object indicates mode of BECN."
                         -- BECN/CLLMフレーム受信時の輻輳回避動作モード。
               DEFVAL { disable }
               ::= { mpFrppFrppCfgEntry 19 }

        mpFrppDlciCfgEncap OBJECT-TYPE                          --@007
               SYNTAX  INTEGER {
                                nec(1),                         --@003変更
                                cisco(2)
                               }
               ACCESS  read-write
               STATUS  mandatory
               DESCRIPTION "The value of this object identifies the
                            Mode of VoIp."
                         -- VoIPルータ収容モード。
               DEFVAL { nec }                                   --@006変更
               ::= { mpFrppFrppCfgEntry 20 }

        mpFrppDlciCfgDe OBJECT-TYPE
               SYNTAX  INTEGER {
                                enable(1),
                                disable(2)
                               }
               ACCESS  read-write
               STATUS  mandatory
               DESCRIPTION "The value of this object identifies the DE bit
                            marking."
                         -- DEビットマーキング。
               DEFVAL { disable }
               ::= { mpFrppFrppCfgEntry 21 }

        mpFrppDlciCfgPln OBJECT-TYPE
               SYNTAX  INTEGER {
                                ipv4(1),
                                ipv6(2)
                               }
               ACCESS  read-only
               STATUS  mandatory
               DESCRIPTION "The value of this object identifies the protocol
                            addressing."
                         -- IPアドレス長。
               ::= { mpFrppFrppCfgEntry 22 }

        mpFrppDlciCfgFragSize OBJECT-TYPE
               SYNTAX  INTEGER (0..1600)
               ACCESS  read-write
               STATUS  mandatory
               DESCRIPTION "The value of this object identifies the
                           FRF.12 flagment size. within the range of
                           0,16 - 1600."
                         -- FRF.12フラグメントサイズ（byte）
               DEFVAL { 0 }
               ::= { mpFrppFrppCfgEntry 23 }

        mpFrppDlciCfgMir OBJECT-TYPE
               SYNTAX  INTEGER (0..2048)
               ACCESS  read-write
               STATUS  mandatory
               DESCRIPTION "The value of this object identifies the
                            Mir ."
                         -- 最大送信レート数
               DEFVAL { 0 }                                     --@006変更
               ::= { mpFrppFrppCfgEntry 24 }

        mpFrppDlciCfgPerInc OBJECT-TYPE
               SYNTAX  INTEGER (1..100)
               ACCESS  read-write
               STATUS  mandatory
               DESCRIPTION "The value of this object identifies the
                            percent increment."
                         -- スループット増速ステップレート
               DEFVAL { 12 }
               ::= { mpFrppFrppCfgEntry 25 }

        mpFrppDlciCfgPerDec OBJECT-TYPE
               SYNTAX  INTEGER (1..100)
               ACCESS  read-write
               STATUS  mandatory
               DESCRIPTION "The value of this object identifies the
                            percent decrement."
                         -- スループット減速ステップルート
               DEFVAL { 25 }
               ::= { mpFrppFrppCfgEntry 26 }

        mpFrppDlciCfgMincir OBJECT-TYPE
               SYNTAX  INTEGER (1..2048)                        --@006変更
               ACCESS  read-write
               STATUS  mandatory
               DESCRIPTION "The value of this object identifies the
                            MinCir."
                         -- 最低保障rate(Kbps)
               DEFVAL { 64 }
              ::= { mpFrppFrppCfgEntry 27 }

        mpFrppDlciCfgCir  OBJECT-TYPE
               SYNTAX  INTEGER (1..2048)                        --@006変更
               ACCESS  read-write
               STATUS  mandatory
               DESCRIPTION "The value of this object identifies the
                            Committed Information Rate (CIR) is rate
                            (expressed in bits/second) that the network
                            commits to deliver under normal network conditions.
                           "
                         -- 契約情報速度(CIR)を示す。
                         -- 契約情報速度(CIR)は、通常状態下のネットワーク
                         -- が転送を保証する速度(bits/秒で表現される）。
               DEFVAL { 64 }
               ::= { mpFrppFrppCfgEntry 28 }

        mpFrppDlciCfgSnapFlg OBJECT-TYPE
               SYNTAX  INTEGER {
                                off(1),
                                on(2)
                               }
               ACCESS  read-write
               STATUS  mandatory
               DESCRIPTION "The value of this object identifies configration
                            status for this table."
                         -- SNAPフラグ（ＦＲ送信時）
               DEFVAL { off }
               ::= { mpFrppFrppCfgEntry 29 }

        mpFrppDlciQueueLenH OBJECT-TYPE
               SYNTAX  INTEGER (0..255)
               ACCESS  read-write
               STATUS  mandatory
               DESCRIPTION "The value of this object identifies configration
                            High queue length.
                           "
                         -- High送信フレームキュー長（フレーム）
               DEFVAL { 40 }
               ::= { mpFrppFrppCfgEntry 30 }

        mpFrppDlciQueueLenU OBJECT-TYPE
               SYNTAX  INTEGER (0..255)
               ACCESS  read-write
               STATUS  mandatory
               DESCRIPTION "The value of this object identifies configration
                            Urgent queue length.
                           "
                         -- Urgent送信フレームキュー長（フレーム）
               DEFVAL { 20 }
               ::= { mpFrppFrppCfgEntry 31 }

        mpFrppDlciQueueLenL OBJECT-TYPE
               SYNTAX  INTEGER (0..255)
               ACCESS  read-write
               STATUS  mandatory
               DESCRIPTION "The value of this object identifies configration
                            Low queue length.
                           "
                         -- Low送信フレームキュー長（フレーム）
               DEFVAL { 80 }
               ::= { mpFrppFrppCfgEntry 32 }

        mpFrppDlciQueueLenN OBJECT-TYPE
               SYNTAX  INTEGER (0..255)
               ACCESS  read-write
               STATUS  mandatory
               DESCRIPTION "The value of this object identifies configration
                            Normal queue length.
                           "
                         -- Normal送信フレームキュー長（フレーム）
               DEFVAL { 60 }
               ::= { mpFrppFrppCfgEntry 33 }

        mpFrppDlciQueueByteH OBJECT-TYPE
               SYNTAX  INTEGER (0..65535)
               ACCESS  read-write
               STATUS  mandatory
               DESCRIPTION "The value of this object identifies configration
                            High queue length. within the range of 0,16 - 1600."
                         -- High 送信フレームキュー長（バイト）
               DEFVAL { 0 }                             --@006変更
               ::= { mpFrppFrppCfgEntry 34 }

        mpFrppDlciQueueByteU OBJECT-TYPE
               SYNTAX  INTEGER (0..65535)
               ACCESS  read-write
               STATUS  mandatory
               DESCRIPTION "The value of this object identifies configration
                            Urgent queue length. within the range of 0,16 - 1600
."
                         -- Urgent 送信フレームキュー長（バイト）
               DEFVAL { 0 }                             --@006変更
               ::= { mpFrppFrppCfgEntry 35 }

        mpFrppDlciQueueByteL OBJECT-TYPE
               SYNTAX  INTEGER (0..65535)
               ACCESS  read-write
               STATUS  mandatory
               DESCRIPTION "The value of this object identifies configration
                            Low queue length. within the range of 0,16 - 1600."
                         -- Low 送信フレームキュー長（バイト）
               DEFVAL { 0 }                             --@006変更
               ::= { mpFrppFrppCfgEntry 36 }

        mpFrppDlciQueueByteN OBJECT-TYPE
               SYNTAX  INTEGER (0..65535)
               ACCESS  read-write
               STATUS  mandatory
               DESCRIPTION "The value of this object identifies configration
                            Normal queue length. within the range of 0,16 - 1600
."
                         -- Normal 送信フレームキュー長（バイト）
               DEFVAL { 0 }                             --@006変更
               ::= { mpFrppFrppCfgEntry 37 }


        mpFrppDlciIpQosClassAf3 OBJECT-TYPE
               SYNTAX  INTEGER {
                                urgent(1),
                                high(2),
                                normal(3),
                                low(4)
                               }
               ACCESS  read-write
               STATUS  mandatory
               DESCRIPTION "The value of this object identifies configration
                            IP-Qos/AF3 mapping Class .
                           "
                         -- IP-Qos/AF3クラスマッピング
               DEFVAL { high }
               ::= { mpFrppFrppCfgEntry 38 }

        mpFrppDlciIpQosClassAf2 OBJECT-TYPE
               SYNTAX  INTEGER {
                                urgent(1),
                                high(2),
                                normal(3),
                                low(4)
                               }
               ACCESS  read-write
               STATUS  mandatory
               DESCRIPTION "The value of this object identifies configration
                            IP-Qos/AF2 mapping Class .
                           "
                         -- IP-Qos/AF2クラスマッピング
               DEFVAL { normal }
               ::= { mpFrppFrppCfgEntry 39 }

        mpFrppDlciIpQosClassAf1 OBJECT-TYPE
               SYNTAX  INTEGER {
                                urgent(1),
                                high(2),
                                normal(3),
                                low(4)
                               }
               ACCESS  read-write
               STATUS  mandatory
               DESCRIPTION "The value of this object identifies configration
                            IP-Qos/AF1 mapping Class .
                           "
                         -- IP-Qos/AF1クラスマッピング
               DEFVAL { normal }
               ::= { mpFrppFrppCfgEntry 40 }

        mpFrppDlciIpQosClassBe OBJECT-TYPE
               SYNTAX  INTEGER {
                                urgent(1),
                                high(2),
                                normal(3),
                                low(4)
                               }
               ACCESS  read-write
               STATUS  mandatory
               DESCRIPTION "The value of this object identifies configration
                            IP-Qos/Be mapping Class .
                           "
                         -- IP-Qos/Beクラスマッピング
               DEFVAL { low }
               ::= { mpFrppFrppCfgEntry 41 }

        mpFrppDlciIpQosClassEf3 OBJECT-TYPE
               SYNTAX  INTEGER {
                                urgent(1),
                                high(2),
                                normal(3),
                                low(4)
                               }
               ACCESS  read-write
               STATUS  mandatory
               DESCRIPTION "The value of this object identifies configration
                            IP-Qos/Ef3 mapping Class .
                           "
                         -- IP-Qos/Ef3クラスマッピング
               DEFVAL { urgent }
               ::= { mpFrppFrppCfgEntry 42 }

        mpFrppDlciIpQosClassEf2 OBJECT-TYPE
               SYNTAX  INTEGER {
                                urgent(1),
                                high(2),
                                normal(3),
                                low(4)
                               }
               ACCESS  read-write
              STATUS  mandatory
               DESCRIPTION "The value of this object identifies configration
                            IP-Qos/EF2 mapping Class .
                           "
                         -- IP-Qos/EF2クラスマッピング
               DEFVAL { urgent }
               ::= { mpFrppFrppCfgEntry 43 }

        mpFrppDlciIpQosClassEf1 OBJECT-TYPE
               SYNTAX  INTEGER {
                                urgent(1),
                                high(2),
                                normal(3),
                                low(4)
                               }
               ACCESS  read-write
               STATUS  mandatory
               DESCRIPTION "The value of this object identifies configration
                            IP-Qos/Ef1 mapping Class .
                           "
                         -- IP-Qos/Ef1クラスマッピング
               DEFVAL { urgent }
               ::= { mpFrppFrppCfgEntry 44 }

        mpFrppDlciIpQosClassAf4 OBJECT-TYPE
               SYNTAX  INTEGER {
                                urgent(1),
                                high(2),
                                normal(3),
                                low(4)
                               }
               ACCESS  read-write
               STATUS  mandatory
               DESCRIPTION "The value of this object identifies configration
                            IP-Qos/AF4 mapping Class .
                           "
                         -- IP-Qos/AF4クラスマッピング
               DEFVAL { high }
               ::= { mpFrppFrppCfgEntry 45 }

        mpFrppDlciCfgInarpMode OBJECT-TYPE
               SYNTAX  INTEGER {
                                no(1),
                                passive(2)
                               }
               ACCESS  read-write
               STATUS  mandatory
               DESCRIPTION "The value of this object identifies configration
                            Inverse Arp mode ."
                         -- Inverse Arp モード
               DEFVAL { passive }
               ::= { mpFrppFrppCfgEntry 46 }

        mpFrppDlciCfgTrapFilter OBJECT-TYPE
               SYNTAX  INTEGER {
                                no(1),     -- No
                                up(2),     -- UP
                                down(3),   -- Down
                                up-down(4) -- Up-Down
                               }
               ACCESS  read-write
               STATUS  mandatory
               DESCRIPTION "The value of this object indicates the
                            DLCi Trap Filter status."
                         -- DLCIのTrapFilter設定状態を示す。
               DEFVAL { no }
               ::= { mpFrppFrppCfgEntry 47 }

        mpFrppFrppCfgRowStatus OBJECT-TYPE
               SYNTAX  RowStatus
               ACCESS  read-write
               STATUS  mandatory
               DESCRIPTION "An entry in MCC Channel management table."
                         -- createAndGo(4)でtableの新規作成を行い
                         -- tableのコンフィグにデフォルト値を設定する
                         -- notInService(2)でtableへの変更を行い
                         -- 変更が終了したらactive(1)をSETする
                         -- active(1)をSETされるとMCC-FRへコンフィグダウンロード
                         -- 要求を行う
                         -- destroy(6)でtableを削除し、MCC-FRにコンフィグ削除を
                         -- 行う
               ::= { mpFrppFrppCfgEntry 48 }

        mpFrppFrppCfgErrInfo OBJECT-TYPE
               SYNTAX  INTEGER {
                                normal(1),                      -- 正常
                                parameterNotEnough(2),          -- パラメータ不足
                                badValue(3),                    -- 設定値異常
                                badIndexValue(4),               -- INDEX値異常
                                correlationError(5),            -- 相関関係NG
                                memoryAllocateFailure(6),       -- Memoryハント失敗
                                mbufHuntFailure(7),             -- MBUFハント失敗
                                relationalConfigExist(8),       -- 関連するConfigが存在
                                lowLayerConfigNotRegistered(9), -- 下位レイヤConfig未実装
                                mappingDataAlreadyExist(10),    -- マッピングデータが存在する
                                ipAddressNotDeleted(11),        -- ＩＰアドレステーブルは削除されていない
                                mccIdHuntFailure(12)            -- MCC ID生成失敗
                               }
               ACCESS  read-only
               STATUS  mandatory
               DESCRIPTION "The value of this object indicates error
                            information that became an error set to MIB
                            in this table."
                         -- Table内の各MIBへのSETでエラーとなった場合の、詳細
                         -- エラー情報を示す。
               ::= { mpFrppFrppCfgEntry 49 }


--- FRPP Admin Information MIB
        mpFrppInfoTable OBJECT-TYPE
               SYNTAX  SEQUENCE OF MpFrppInfoEntry
               ACCESS  not-accessible
               STATUS  mandatory
               DESCRIPTION "This is the table type object of the
                            FRPP information."
                         -- FRPP Admin 情報Table
               ::= { mpFrpp 4 }

        mpFrppInfoEntry OBJECT-TYPE
               SYNTAX  MpFrppInfoEntry
               ACCESS  not-accessible
               STATUS  mandatory
               DESCRIPTION "This is the table entry of mpFrppInfoTable."
                         -- FRPP Admin情報Tableエントリ
               INDEX { mpFrppInfoIndex }
               ::= { mpFrppInfoTable 1 }

        MpFrppInfoEntry ::=
                 SEQUENCE {
                   mpFrppInfoIndex                 INTEGER,
                   mpFrppInfoFrppAdminStatus       INTEGER,
                   mpFrppInfoFrppOperStatus        INTEGER,
                   mpFrppInfoFrppLastChange        TimeTicks,
                   mpFrppInfoDlci                  INTEGER,     --@006追加
                   mpFrppInfoDlciAdminStatus       INTEGER,     --@006追加
                   mpFrppInfoDlciOperStatus        INTEGER,     --@006追加
                   mpFrppInfoDlciLastChange        TimeTicks,   --@006追加
                   mpFrppInfoDlciOperDownEvent     INTEGER      --@006追加
                 }

        mpFrppInfoIndex  OBJECT-TYPE
               SYNTAX  INTEGER
               ACCESS  read-only
               STATUS  mandatory
               DESCRIPTION "The value of this object identifies the
                            Frpp No (Frpp number) ."
                         -- ＦＲＰＰ番号を示す。
               ::= { mpFrppInfoEntry 1 }

        mpFrppInfoFrppAdminStatus OBJECT-TYPE
               SYNTAX  INTEGER {
                                active(1),   -- Active
                                inactive(2)  -- Inactive
                               }
               ACCESS  read-write
               STATUS  mandatory
               DESCRIPTION "The value of this object indicates the
                            Frpp administration status."
                         -- FrppのAdmin状態を示す。
               DEFVAL { active }
               ::= { mpFrppInfoEntry 2 }

        mpFrppInfoFrppOperStatus OBJECT-TYPE
               SYNTAX  INTEGER {
                                active(1),
                                inactive(2)
                               }
               ACCESS  read-only
               STATUS  mandatory
               DESCRIPTION "The value of this object indicates the
                            Frpp operational status."
                         -- FrppのOperaation状態を示す。
               ::= { mpFrppInfoEntry 3 }

        mpFrppInfoFrppLastChange OBJECT-TYPE
               SYNTAX  TimeTicks
               ACCESS  read-only
               STATUS  mandatory
               DESCRIPTION "The value of sysUpTime at the time the Frpp
                            entered its current operational state."
                         -- FRPPのOper Status変化時刻を示す。
                         -- 値は、sysUpTime
               ::= { mpFrppInfoEntry 4 }

        mpFrppInfoDlci OBJECT-TYPE                      -- @006
               SYNTAX  INTEGER (16..991)
               ACCESS  read-only
               STATUS  mandatory
               DESCRIPTION "The value of this object is equal to the
                            Data Link Connection Identifer(DLCi) value
                            for index to this mpFrDlcStatisticsTable table."
                         -- データリンクコネクション識別子(DLCi)の値を示す。
               ::= { mpFrppInfoEntry 5 }

        mpFrppInfoDlciAdminStatus OBJECT-TYPE                   -- @006
               SYNTAX  INTEGER {
                                active(1),   -- Active
                                inactive(2)  -- Inactive
                               }
               ACCESS  read-only                        --@004変更
               STATUS  mandatory
               DESCRIPTION "The value of this object indicates the
                            Dlci administration status."
                         -- DLCIのAdmin状態を示す。
               ::= { mpFrppInfoEntry 6 }

        mpFrppInfoDlciOperStatus OBJECT-TYPE                    -- @006
               SYNTAX  INTEGER {
                                active(1),
                                inactive(2)
                               }
               ACCESS  read-only
               STATUS  mandatory
               DESCRIPTION "The value of this object indicates the
                            DLCi operational status."
                         -- DLCIのOperaation状態を示す。
               ::= { mpFrppInfoEntry 7 }

        mpFrppInfoDlciLastChange OBJECT-TYPE                    -- @006
               SYNTAX  TimeTicks
               ACCESS  read-only
               STATUS  mandatory
               DESCRIPTION "The value of sysUpTime at the time the DLCI
                            entered its current operational state."
                         -- DLCIのOper Status変化時刻を示す。
                         -- 値は、sysUpTime
               ::= { mpFrppInfoEntry 8 }

        mpFrppInfoDlciOperDownEvent OBJECT-TYPE                 -- @006
               SYNTAX  INTEGER {
                                normal(1),
                                dlcidown(2),
                                lmierror(3),
                                lmiStatusInactiveReceived(4),
                                unknown(5)
                               }
               ACCESS  read-only
               STATUS  mandatory
               DESCRIPTION "The value of this object indicates error
                            information that became an error set to MIB
                            in this table."
                         -- Table内の各MIBへのSETでエラーとなった場合の、詳細
                         -- エラー情報を示す。
               ::= { mpFrppInfoEntry 9 }


-- Frpp Mccid Statistics Information MIB

        mpFrppMccIdStatTable OBJECT-TYPE
               SYNTAX SEQUENCE OF MpFrppMccIdStatEntry
               ACCESS  not-accessible
               STATUS  mandatory
               DESCRIPTION "This is the table type object of the
                            Frpp Mccid statistics information."
               ::= { mpFrpp 5 }

        mpFrppMccIdStatEntry OBJECT-TYPE
               SYNTAX  MpFrppMccIdStatEntry
               ACCESS  not-accessible
               STATUS  mandatory
               DESCRIPTION "This is the table entry of mpFrppMccIdStatTable."
               INDEX { mpFrppMccIdStatIfIndex }
               ::= { mpFrppMccIdStatTable 1 }

        MpFrppMccIdStatEntry ::=
                 SEQUENCE {
                   mpFrppMccIdStatIfIndex       INTEGER,
                   mpFrppMccIdRcvOctets         Counter,
                   mpFrppMccIdRcvFrames         Counter,
                   mpFrppMccIdRcvFrameMinSize   INTEGER,
                   mpFrppMccIdRcvFrameMaxSize   INTEGER,
                   mpFrppMccIdRcvDiscardFrames  Counter,
                   mpFrppMccIdRcvFecnFrames     Counter,
                   mpFrppMccIdRcvBecnFrames     Counter,
                   mpFrppMccIdRcvDeFrames       Counter,
                   mpFrppMccIdRcvInvalidFrames  Counter,
                   mpFrppMccIdRcvLongFrames     Counter,
                   mpFrppMccIdRcvShortFrames    Counter,
                   mpFrppMccIdXmtOctets         Counter,
                   mpFrppMccIdXmtFrames         Counter,
                   mpFrppMccIdXmtFrameMinSize   INTEGER,
                   mpFrppMccIdXmtFrameMaxSize   INTEGER,
                   mpFrppMccIdXmtDiscardFrames  Counter,
                   mpFrppMccIdXmtFecnFrames     Counter,
                   mpFrppMccIdXmtBecnFrames     Counter,
                   mpFrppMccIdXmtDeFrames       Counter,
                   mpFrppMccIdRcvCllmFrames     Counter
               }

        mpFrppMccIdStatIfIndex OBJECT-TYPE
               SYNTAX  INTEGER
               ACCESS  read-only
               STATUS  mandatory
               DESCRIPTION "The value of this object identifies the mccid
                            number."
                         -- mccid番号を示す。
               ::= { mpFrppMccIdStatEntry 1 }

        mpFrppMccIdRcvOctets OBJECT-TYPE
               SYNTAX  Counter
               ACCESS  read-only
               STATUS  mandatory
               DESCRIPTION "The value of this object indicates the total
                            number of octets received on this port."
                         -- 受信バイト数を示す
               ::= { mpFrppMccIdStatEntry 2 }

        mpFrppMccIdRcvFrames OBJECT-TYPE
               SYNTAX  Counter
               ACCESS  read-only
               STATUS  mandatory
               DESCRIPTION "The value of this object indicates the total
                            number of frames received on this port."
                         -- 受信フレーム数を示す
               ::= { mpFrppMccIdStatEntry 3 }

        mpFrppMccIdRcvFrameMinSize OBJECT-TYPE
               SYNTAX  INTEGER
               ACCESS  read-only
               STATUS  mandatory
               DESCRIPTION "The value of this object indicates the minimum
                            size of frames received on this port."
                         -- 受信フレーム最小サイズを示す
               ::= { mpFrppMccIdStatEntry 4 }

        mpFrppMccIdRcvFrameMaxSize OBJECT-TYPE
               SYNTAX  INTEGER
               ACCESS  read-only
               STATUS  mandatory
               DESCRIPTION "The value of this object indicates the maximum
                            size of frames received on this port."
                         -- 受信フレーム最大サイズを示す
               ::= { mpFrppMccIdStatEntry 5 }

        mpFrppMccIdRcvDiscardFrames OBJECT-TYPE
               SYNTAX  Counter
               ACCESS  read-only
               STATUS  mandatory
               DESCRIPTION "The value of this object indicates the total
                            number of discard frames received on this port."
                         -- 受信廃棄フレーム数を示す
               ::= { mpFrppMccIdStatEntry 6 }

        mpFrppMccIdRcvFecnFrames OBJECT-TYPE
               SYNTAX  Counter
               ACCESS  read-only
               STATUS  mandatory
               DESCRIPTION "The value of this object indicates the number
                            of frames received with the FECN bit set."
                         -- 受信FECN設定フレーム数を示す
               ::= { mpFrppMccIdStatEntry 7 }

        mpFrppMccIdRcvBecnFrames OBJECT-TYPE
               SYNTAX  Counter
               ACCESS  read-only
               STATUS  mandatory
               DESCRIPTION "The value of this object indicates the number
                            of frames received with the BECN bit set."
                         -- 受信BECN設定フレーム数を示す
               ::= { mpFrppMccIdStatEntry 8 }

        mpFrppMccIdRcvDeFrames OBJECT-TYPE
               SYNTAX  Counter
               ACCESS  read-only
               STATUS  mandatory
               DESCRIPTION "The value of this object indicates the number
                            of frames received with the DE bit set."
                         -- 受信DE設定フレーム数を示す
               ::= { mpFrppMccIdStatEntry 9 }

        mpFrppMccIdRcvInvalidFrames OBJECT-TYPE
               SYNTAX  Counter
               ACCESS  read-only
               STATUS  mandatory
               DESCRIPTION "The value of this object indicates the total
                            number of invalid frames received on this port."
                         -- 受信無効フレーム数を示す
               ::= { mpFrppMccIdStatEntry 10 }

        mpFrppMccIdRcvLongFrames OBJECT-TYPE
               SYNTAX  Counter
               ACCESS  read-only
               STATUS  mandatory
               DESCRIPTION "The value of this object indicates the total
                            number of long frames received on this port."
                         -- 受信Longフレーム数を示す
               ::= { mpFrppMccIdStatEntry 11 }

        mpFrppMccIdRcvShortFrames OBJECT-TYPE
               SYNTAX  Counter
               ACCESS  read-only
               STATUS  mandatory
               DESCRIPTION "The value of this object indicates the total
                            number of short frames received on this port."
                         -- 受信shortフレーム数を示す
               ::= { mpFrppMccIdStatEntry 12 }

        mpFrppMccIdXmtOctets OBJECT-TYPE
               SYNTAX  Counter
               ACCESS  read-only
               STATUS  mandatory
               DESCRIPTION "The value of this object indicates the total
                            number of octets sent on this port."
                         -- 送信バイト数を示す
               ::= { mpFrppMccIdStatEntry 13 }

        mpFrppMccIdXmtFrames OBJECT-TYPE
               SYNTAX  Counter
               ACCESS  read-only
               STATUS  mandatory
               DESCRIPTION "The value of this object indicates the total
                            number of frames sent on this port."
                         -- 送信フレーム数を示す
               ::= { mpFrppMccIdStatEntry 14 }

        mpFrppMccIdXmtFrameMinSize OBJECT-TYPE
               SYNTAX  INTEGER
               ACCESS  read-only
               STATUS  mandatory
               DESCRIPTION "The value of this object indicates the minimum
                            size of frames sent on this port."
                         -- 送信フレーム最小サイズを示す
               ::= { mpFrppMccIdStatEntry 15 }

        mpFrppMccIdXmtFrameMaxSize OBJECT-TYPE
               SYNTAX  INTEGER
               ACCESS  read-only
               STATUS  mandatory
               DESCRIPTION "The value of this object indicates the maximum
                            size of frames sent on this port."
                         -- 送信フレーム最大サイズを示す
               ::= { mpFrppMccIdStatEntry 16 }

        mpFrppMccIdXmtDiscardFrames OBJECT-TYPE
               SYNTAX  Counter
               ACCESS  read-only
               STATUS  mandatory
               DESCRIPTION "The value of this object indicates the total
                            number of discard frames sent on this port."
                         -- 送信廃棄フレーム数を示す
               ::= { mpFrppMccIdStatEntry 17 }

        mpFrppMccIdXmtFecnFrames OBJECT-TYPE
               SYNTAX  Counter
               ACCESS  read-only
               STATUS  mandatory
               DESCRIPTION "The value of this object indicates the number
                            of frames sent with the FECN bit set."
                         -- 送信FECN設定フレーム数を示す
               ::= { mpFrppMccIdStatEntry 18 }

        mpFrppMccIdXmtBecnFrames OBJECT-TYPE
               SYNTAX  Counter
               ACCESS  read-only
               STATUS  mandatory
               DESCRIPTION "The value of this object indicates the number
                            of frames sent with the BECN bit set."
                         -- 送信BECN設定フレーム数を示す
               ::= { mpFrppMccIdStatEntry 19 }

        mpFrppMccIdXmtDeFrames OBJECT-TYPE
               SYNTAX  Counter
               ACCESS  read-only
               STATUS  mandatory
               DESCRIPTION "The value of this object indicates the number
                            of frames sent with the DE bit set."
                         -- 送信DE設定フレーム数を示す
               ::= { mpFrppMccIdStatEntry 20 }

        mpFrppMccIdRcvCllmFrames OBJECT-TYPE
               SYNTAX  Counter
               ACCESS  read-only
               STATUS  mandatory
               DESCRIPTION "The value of this object indicates the total
                            number of CLLM frames received on this port."
                         -- 受信CLLMフレーム数を示す
               ::= { mpFrppMccIdStatEntry 21 }


-- ・Frpp Port LMI Statistics Information MIB

        mpFrppMccIdLmiStatTable OBJECT-TYPE
               SYNTAX SEQUENCE OF MpFrppMccIdLmiStatEntry
               ACCESS  not-accessible
               STATUS  mandatory
               DESCRIPTION "This is the table type object of the
                            Frpp Port LMI statitics information."
               ::= { mpFrpp 6 }

        mpFrppMccIdLmiStatEntry OBJECT-TYPE
               SYNTAX  MpFrppMccIdLmiStatEntry
               ACCESS  not-accessible
               STATUS  mandatory
               DESCRIPTION "This is the table entry
                            of mpFrppMccIdLmiStatTable."
               INDEX { mpFrppMccIdLmiStatIfIndex }
               ::= { mpFrppMccIdLmiStatTable 1 }

        MpFrppMccIdLmiStatEntry ::=
                 SEQUENCE {
                   mpFrppMccIdLmiStatIfIndex      INTEGER,
                   mpFrppMccIdRcvLmiStatEnqs      Counter,
                   mpFrppMccIdXmtLmiStatEnqs      Counter,
                   mpFrppMccIdRcvLmiStats         Counter,
                   mpFrppMccIdXmtLmiStats         Counter,
                   mpFrppMccIdUsrLmiLinkRelErrs   Counter,
                   mpFrppMccIdUsrLmiT391Tos       Counter,
                   mpFrppMccIdUsrLmiSeqErrs       Counter,
                   mpFrppMccIdUsrLmiProtErrs      Counter,
                   mpFrppMccIdUsrLmiChInacts      Counter,
                   mpFrppMccIdNetLmiLinkRelErrs   Counter,
                   mpFrppMccIdNetLmiT392Tos       Counter,
                   mpFrppMccIdNetLmiSeqErrs       Counter,
                   mpFrppMccIdNetLmiErrs          Counter,
                   mpFrppMccIdNetChInacts         Counter,
                   mpFrppMccIdRcvAsyncFrms        Counter
               }

        mpFrppMccIdLmiStatIfIndex OBJECT-TYPE
               SYNTAX  INTEGER
               ACCESS  read-only
               STATUS  mandatory
               DESCRIPTION "The value of this object identifies the mccid
                            number."
                         -- Mccid番号を示す。
               ::= { mpFrppMccIdLmiStatEntry 1 }

        mpFrppMccIdRcvLmiStatEnqs OBJECT-TYPE
               SYNTAX  Counter
               ACCESS  read-only
               STATUS  mandatory
               DESCRIPTION "The value of this object indicates the total
                            number of status enquiry frames received on
                            this port."
                         -- 受信StatusEnqフレーム数を示す
               ::= { mpFrppMccIdLmiStatEntry 2 }

        mpFrppMccIdXmtLmiStatEnqs OBJECT-TYPE
               SYNTAX  Counter
               ACCESS  read-only
               STATUS  mandatory
               DESCRIPTION "The value of this object indicates the total
                            number of status enquiry frames sent on this port."
                         -- 送信StatusEnqフレーム数を示す
               ::= { mpFrppMccIdLmiStatEntry 3 }

        mpFrppMccIdRcvLmiStats OBJECT-TYPE
               SYNTAX  Counter
               ACCESS  read-only
               STATUS  mandatory
               DESCRIPTION "The value of this object indicates the total
                            number of status frames received on this port."
                         -- 受信Statusフレーム数を示す
               ::= { mpFrppMccIdLmiStatEntry 4 }

        mpFrppMccIdXmtLmiStats OBJECT-TYPE
               SYNTAX  Counter
               ACCESS  read-only
               STATUS  mandatory
               DESCRIPTION "The value of this object indicates the total
                            number of status frames sent on this port."
                         -- 送信Statusフレーム数を示す
               ::= { mpFrppMccIdLmiStatEntry 5 }

        mpFrppMccIdUsrLmiLinkRelErrs OBJECT-TYPE
               SYNTAX  Counter
               ACCESS  read-only
               STATUS  mandatory
               DESCRIPTION "The value of this object indicates the number
                            of user-side local in-channel signaling link
                            reliability errors for this port."
                         -- リンク完全性確認エラー数(DTE)を示す
               ::= { mpFrppMccIdLmiStatEntry 6 }

        mpFrppMccIdUsrLmiT391Tos OBJECT-TYPE
               SYNTAX  Counter
               ACCESS  read-only
               STATUS  mandatory
               DESCRIPTION "The value of this object indicates the number
                            of user-side not receive status for this port."
                         -- Status未受信回数(DTE)を示す
               ::= { mpFrppMccIdLmiStatEntry 7 }

        mpFrppMccIdUsrLmiSeqErrs OBJECT-TYPE
               SYNTAX  Counter
               ACCESS  read-only
               STATUS  mandatory
               DESCRIPTION "The value of this object indicates the number
                            of Sequens Errors."
                         -- 受信STATUSシーケンス番号異常検出回数を示す
               ::= { mpFrppMccIdLmiStatEntry 8 }

        mpFrppMccIdUsrLmiProtErrs OBJECT-TYPE
               SYNTAX  Counter
               ACCESS  read-only
               STATUS  mandatory
               DESCRIPTION "The value of this object indicates the number
                            of network-side local in-channel signaling protocol
                            errors for this port."
                         -- 無効LMIフレーム受信数(DCE)を示す
               ::= { mpFrppMccIdLmiStatEntry 9 }

        mpFrppMccIdUsrLmiChInacts OBJECT-TYPE
               SYNTAX  Counter
               ACCESS  read-only
               STATUS  mandatory
               DESCRIPTION "The value of this object indicates the number
                            of times the network-side channel was declared
                            inactive (i.e., N392 errors in N393 events)
                            for this port."
                         -- N393 Event中のN392エラー発生回数(DCE)を示す
               ::= { mpFrppMccIdLmiStatEntry 10 }

        mpFrppMccIdNetLmiLinkRelErrs OBJECT-TYPE
               SYNTAX  Counter
               ACCESS  read-only
               STATUS  mandatory
               DESCRIPTION "The value of this object indicates the number
                            of user-side local in-channel signaling link
                            reliability errors for this port."
                         -- リンク完全性確認エラー数(DTE)を示す
               ::= { mpFrppMccIdLmiStatEntry 11 }

        mpFrppMccIdNetLmiT392Tos OBJECT-TYPE
               SYNTAX  Counter
               ACCESS  read-only
               STATUS  mandatory
               DESCRIPTION "The value of this object indicates the number
                            of user-side not receive status for this port."
                         -- Status未受信回数(DTE)を示す
               ::= { mpFrppMccIdLmiStatEntry 12 }

        mpFrppMccIdNetLmiSeqErrs OBJECT-TYPE
               SYNTAX  Counter
               ACCESS  read-only
               STATUS  mandatory
               DESCRIPTION "The value of this object indicates the number
                            of Sequens Errors."
                         -- 受信STATUSシーケンス番号異常検出回数を示す
               ::= { mpFrppMccIdLmiStatEntry 13 }

        mpFrppMccIdNetLmiErrs OBJECT-TYPE
               SYNTAX  Counter
               ACCESS  read-only
               STATUS  mandatory
               DESCRIPTION "The value of this object indicates the number
                            of network-side local in-channel signaling protocol
                            errors for this port."
                         -- 無効LMIフレーム受信数(DCE)を示す
               ::= { mpFrppMccIdLmiStatEntry 14 }

        mpFrppMccIdNetChInacts OBJECT-TYPE
               SYNTAX  Counter
               ACCESS  read-only
               STATUS  mandatory
               DESCRIPTION "The value of this object indicates the number
                            of times the network-side channel was declared
                            inactive (i.e., N392 errors in N393 events)
                            for this port."
                         -- N393 Event中のN392エラー発生回数(DCE)を示す
               ::= { mpFrppMccIdLmiStatEntry 15 }

        mpFrppMccIdRcvAsyncFrms OBJECT-TYPE
               SYNTAX  Counter
               ACCESS  read-only
               STATUS  mandatory
               DESCRIPTION "The value of this object indicates the number
                            of Async Frames for this port."
                         -- 受信単一ＰＶＣ非同期フレーム
               ::= { mpFrppMccIdLmiStatEntry 16 }


-- ・Frpp Frpp Statistics Information MIB                       @006 追加

        mpFrppFrppStatTable OBJECT-TYPE
               SYNTAX SEQUENCE OF MpFrppFrppStatEntry
               ACCESS  not-accessible
               STATUS  mandatory
               DESCRIPTION "This is the table type object of the
                            Frpp Frpp statistics information."
               ::= { mpFrpp 7 }

        mpFrppFrppStatEntry OBJECT-TYPE
               SYNTAX  MpFrppFrppStatEntry
               ACCESS  not-accessible
               STATUS  mandatory
               DESCRIPTION "This is the table entry of mpFrppFrppStatTable."
               INDEX { mpFrppFrppStatIndex }
               ::= { mpFrppFrppStatTable 1 }

        MpFrppFrppStatEntry ::=
                 SEQUENCE {
                   mpFrppFrppStatIndex              INTEGER,
                   mpFrppFrppStatRcvFrames          Counter,
                   mpFrppFrppStatXmtFrames          Counter,
                   mpFrppFrppStatRcvDiscardFrames   Counter,
                   mpFrppFrppStatXmtDiscardFrames   Counter,
                   mpFrppFrppStatRcvEncapErrors     Counter,
                   mpFrppFrppStatXmtEncapErrors     Counter,
                   mpFrppFrppStatRcvArpTransErrors  Counter,
                   mpFrppFrppStatXmtArpTransErrors  Counter,
                   mpFrppFrppStatReassembleErrors   Counter,
                   mpFrppFrppStatPriorityQueues     Counter,
                   mpFrppFrppStatPriorityBytes      Counter
               }

        mpFrppFrppStatIndex OBJECT-TYPE
               SYNTAX  INTEGER
               ACCESS  read-only
               STATUS  mandatory
               DESCRIPTION "The value of this object identifies the Frpp
                            number."
                         -- Frpp 番号を示す。
               ::= { mpFrppFrppStatEntry 1 }

        mpFrppFrppStatRcvFrames OBJECT-TYPE
               SYNTAX  Counter
               ACCESS  read-only
               STATUS  mandatory
               DESCRIPTION "The value of this object indicates the total
                            number of frames received on this port."
                         -- 受信フレーム総数を示す
               ::= { mpFrppFrppStatEntry 2 }

        mpFrppFrppStatXmtFrames OBJECT-TYPE
               SYNTAX  Counter
               ACCESS  read-only
               STATUS  mandatory
               DESCRIPTION "The value of this object indicates the total
                            number of frames sent on this port."
                         -- 送信フレーム総数を示す
               ::= { mpFrppFrppStatEntry 3 }

        mpFrppFrppStatRcvDiscardFrames OBJECT-TYPE
               SYNTAX  Counter
               ACCESS  read-only
               STATUS  mandatory
               DESCRIPTION "The value of this object indicates the total
                            number of discarded frames received
                            on this port."
                         -- 受信で廃棄されたフレーム総数を示す
               ::= { mpFrppFrppStatEntry 4 }

        mpFrppFrppStatXmtDiscardFrames OBJECT-TYPE
               SYNTAX  Counter
               ACCESS  read-only
               STATUS  mandatory
               DESCRIPTION "The value of this object indicates the total
                            number of discarded frames sent on this port."
                         -- 送信で廃棄されたフレーム総数を示す
               ::= { mpFrppFrppStatEntry 5 }

        mpFrppFrppStatRcvEncapErrors OBJECT-TYPE
               SYNTAX  Counter
               ACCESS  read-only
               STATUS  mandatory
               DESCRIPTION "The value of this object indicates the total
                            number of Payload header conversion errors
                            received on this port."
                         -- 受信で発生したペイロードヘッダ変換エラーの
                         -- 総数を示す
               ::= { mpFrppFrppStatEntry 6 }

        mpFrppFrppStatXmtEncapErrors OBJECT-TYPE
               SYNTAX  Counter
               ACCESS  read-only
               STATUS  mandatory
               DESCRIPTION "The value of this object indicates the total
                            number of Payload header conversion errors
                            sent on this port."
                         -- 送信で発生したペイロードヘッダ変換エラーの
                         -- 総数を示す
               ::= { mpFrppFrppStatEntry 7 }

        mpFrppFrppStatRcvArpTransErrors OBJECT-TYPE
               SYNTAX  Counter
               ACCESS  read-only
               STATUS  mandatory
               DESCRIPTION "The value of this object indicates the number
                            of APR packet conversion error sends received
                            on this port."
                         -- 受信で発生したARPパケット変換エラー送信数を示す
               ::= { mpFrppFrppStatEntry 8 }

        mpFrppFrppStatXmtArpTransErrors OBJECT-TYPE
               SYNTAX  Counter
               ACCESS  read-only
               STATUS  mandatory
               DESCRIPTION "The value of this object indicates the number
                            of ARP packet conversion error sends sent on
                            this port."
                         -- 送信で発生したARPパケット変換エラー送信数を示す
               ::= { mpFrppFrppStatEntry 9 }

        mpFrppFrppStatReassembleErrors OBJECT-TYPE
               SYNTAX  Counter
               ACCESS  read-only
               STATUS  mandatory
               DESCRIPTION "The value of this object indicates the total
                            number of Reassemble conversion errors."
                         -- フラグメント・リアセンブリの変換エラー総数を示す
               ::= { mpFrppFrppStatEntry 10 }

        mpFrppFrppStatPriorityQueues OBJECT-TYPE
               SYNTAX  Counter
               ACCESS  read-only
               STATUS  mandatory
               DESCRIPTION "The value of this object indicates the total
                            number of priority queue length excess frames."
                         -- プライオリティーキュー長超過フレーム総数を示す
               ::= { mpFrppFrppStatEntry 11 }

        mpFrppFrppStatPriorityBytes OBJECT-TYPE
               SYNTAX  Counter
               ACCESS  read-only
               STATUS  mandatory
               DESCRIPTION "The value of this object indicates the total
                            number of priority byte length excess frames."
                         -- プリオリティーバイト長超過フレーム総数を示す
               ::= { mpFrppFrppStatEntry 12 }


-- ・Frpp DLCI Statistics Information MIB

        mpFrppDlcStatTable OBJECT-TYPE
               SYNTAX SEQUENCE OF MpFrppDlcStatEntry
               ACCESS  not-accessible
               STATUS  mandatory
               DESCRIPTION "This is the table type object of the
                            Frpp DLCI statistics information."
               ::= { mpFrpp 8 }

        mpFrppDlcStatEntry OBJECT-TYPE
               SYNTAX  MpFrppDlcStatEntry
               ACCESS  not-accessible
               STATUS  mandatory
               DESCRIPTION "This is the table entry of mpFrppDlcStatTable."
               INDEX { mpFrppDlciStatIfIndex }
               ::= { mpFrppDlcStatTable 1 }

        MpFrppDlcStatEntry ::=
                 SEQUENCE {
                   mpFrppDlciStatIfIndex                    INTEGER,
--                 mpFrppDlciStatDlciIndex                  INTEGER,    @006削除
                   mpFrppDlciStatRcvOctets                  Counter,
                   mpFrppDlciStatRcvFrames                  Counter,
                   mpFrppDlciStatRcvFrameMinSize            INTEGER,
                   mpFrppDlciStatRcvFrameMaxSize            INTEGER,
                   mpFrppDlciStatRcvFECNFrames              Counter,
                   mpFrppDlciStatRcvBECNFrames              Counter,
                   mpFrppDlciStatRcvDEFrames                Counter,
                   mpFrppDlciStatRcvTaggedDEFrames          Counter,
                   mpFrppDlciStatXmtOctets                  Counter,
                   mpFrppDlciStatXmtFrames                  Counter,
                   mpFrppDlciStatXmtFrameMinSize            INTEGER,
                   mpFrppDlciStatXmtFrameMaxSize            INTEGER,
                   mpFrppDlciStatXmtDEDiscardFrames         Counter,
                   mpFrppDlciStatXmtFECNFrames              Counter,
                   mpFrppDlciStatXmtBECNFrames              Counter,
                   mpFrppDlciStatXmtDEFrames                Counter,
                   mpFrppDlciStatXmtTaggedDEFrames          Counter,
                   mpFrppDlciStatRcvInArpReqFrms            Counter,
                   mpFrppDlciStatXmtInArpReqFrms            Counter,
                   mpFrppDlciStatRcvInArpRlyFrms            Counter,
                   mpFrppDlciStatXmtInArpRlyFrms            Counter,
                   mpFrppDlciStatFNUnrecognizHeaders        Counter,
                   mpFrppDlciStatNFUnrecognizHeaders        Counter,
                   mpFrppDlciStatFNArpTranslationErrs       Counter,
                   mpFrppDlciStatNFArpTranslationErrs       Counter,
                   mpFrppDlciStatXmtVQFrms                  Counter,
                   mpFrppDlciStatXmtUQFrms                  Counter,
                   mpFrppDlciStatXmtXceedUQLenFrms          Counter,
                   mpFrppDlciStatXmtXceedUQByteFrms         Counter,
                   mpFrppDlciStatXmtHQFrms                  Counter,
                   mpFrppDlciStatXmtXceedHQLenFrms          Counter,
                   mpFrppDlciStatXmtXceedHQByteFrms         Counter,
                   mpFrppDlciStatXmtNQFrms                  Counter,
                   mpFrppDlciStatXmtXceedNQLenFrms          Counter,
                   mpFrppDlciStatXmtXceedNQByteFrms         Counter,
                   mpFrppDlciStatXmtLQFrms                  Counter,
                   mpFrppDlciStatXmtXceedLQLenFrms          Counter,
                   mpFrppDlciStatXmtXceedLQByteFrms         Counter,
                   mpFrppDlciStatRcvNPBDe0Frms              Counter,
                   mpFrppDlciStatRcvNPBDe1Frms              Counter,
                   mpFrppDlciStatRcvNPBDiscardFrms          Counter,
                   mpFrppDlciStatXmtNPBFrms                 Counter,
                   mpFrppDlciStatXmtNPBDiscardFrms          Counter
               }

        mpFrppDlciStatIfIndex OBJECT-TYPE
               SYNTAX  INTEGER
               ACCESS  read-only
               STATUS  mandatory
               DESCRIPTION "The value of this object identifies the frpp
                            number."
                         -- Frpp 番号を示す。
               ::= { mpFrppDlcStatEntry 1 }

        mpFrppDlciStatRcvOctets OBJECT-TYPE
               SYNTAX  Counter
               ACCESS  read-only
               STATUS  mandatory
               DESCRIPTION "The value of this object indicates the total
                            number of octets received for this Dlci."
                         -- 受信バイト数を示す
               ::= { mpFrppDlcStatEntry 2 }

        mpFrppDlciStatRcvFrames OBJECT-TYPE
               SYNTAX  Counter
               ACCESS  read-only
               STATUS  mandatory
               DESCRIPTION "The value of this object indicates the total
                            number of frames received for this Dlci."
                         -- 受信フレーム数を示す
               ::= { mpFrppDlcStatEntry 3 }

        mpFrppDlciStatRcvFrameMinSize OBJECT-TYPE
               SYNTAX  INTEGER
               ACCESS  read-only
               STATUS  mandatory
               DESCRIPTION "The value of this object indicates the minimum
                            size of frames received for this Dlci."
                         -- 受信フレーム最小サイズを示す
               ::= { mpFrppDlcStatEntry 4 }

        mpFrppDlciStatRcvFrameMaxSize OBJECT-TYPE
               SYNTAX  INTEGER
               ACCESS  read-only
               STATUS  mandatory
               DESCRIPTION "The value of this object indicates the maximum
                            size of frames received for this Dlci."
                         -- 受信フレーム最大サイズを示す
               ::= { mpFrppDlcStatEntry 5 }

        mpFrppDlciStatRcvFECNFrames OBJECT-TYPE
               SYNTAX  Counter
               ACCESS  read-only
               STATUS  mandatory
               DESCRIPTION "The value of this object indicates the number
                            of frames received with the FECN bit set."
                         -- 受信FECN設定フレーム数を示す
               ::= { mpFrppDlcStatEntry 6 }

        mpFrppDlciStatRcvBECNFrames OBJECT-TYPE
               SYNTAX  Counter
               ACCESS  read-only
               STATUS  mandatory
               DESCRIPTION "The value of this object indicates the number
                            of frames received with the BECN bit set."
                         -- 受信BECN設定フレーム数を示す
               ::= { mpFrppDlcStatEntry 7 }

        mpFrppDlciStatRcvDEFrames OBJECT-TYPE
               SYNTAX  Counter
               ACCESS  read-only
               STATUS  mandatory
               DESCRIPTION "The value of this object indicates the number
                            of frames received with the DE bit set."
                         -- 受信DE設定フレーム数を示す
               ::= { mpFrppDlcStatEntry 8 }


        mpFrppDlciStatRcvTaggedDEFrames OBJECT-TYPE
               SYNTAX  Counter
               ACCESS  read-only
               STATUS  mandatory
               DESCRIPTION "The value of this object indicates the number
                            of DE tagged frames received from this port."
                         -- 受信DEタギングフレーム数を示す
               ::= { mpFrppDlcStatEntry 9 }

        mpFrppDlciStatXmtOctets OBJECT-TYPE
               SYNTAX  Counter
               ACCESS  read-only
               STATUS  mandatory
               DESCRIPTION "The value of this object indicates the total
                            number of octets sent for this DLci."
                         -- 送信バイト数を示す
               ::= { mpFrppDlcStatEntry 10 }

        mpFrppDlciStatXmtFrames OBJECT-TYPE
               SYNTAX  Counter
               ACCESS  read-only
               STATUS  mandatory
               DESCRIPTION "The value of this object indicates the total
                            number of frames sent for this dlci."
                         -- 送信フレーム数を示す
               ::= { mpFrppDlcStatEntry 11 }

        mpFrppDlciStatXmtFrameMinSize OBJECT-TYPE
               SYNTAX  INTEGER
               ACCESS  read-only
               STATUS  mandatory
               DESCRIPTION "The value of this object indicates the minimum
                            size of frames sent for this dlci."
                         -- 送信フレーム最小サイズを示す
               ::= { mpFrppDlcStatEntry 12 }

        mpFrppDlciStatXmtFrameMaxSize OBJECT-TYPE
               SYNTAX  INTEGER
               ACCESS  read-only
               STATUS  mandatory
               DESCRIPTION "The value of this object indicates the maximum
                            size of frames sent for this dlci."
                         -- 送信フレーム最大サイズを示す
               ::= { mpFrppDlcStatEntry 13 }

        mpFrppDlciStatXmtDEDiscardFrames OBJECT-TYPE
               SYNTAX  Counter
               ACCESS  read-only
               STATUS  mandatory
               DESCRIPTION "The value of this object indicates the total
                            number of discard DE frames sent for this dlci."
                         -- 送信DE廃棄フレーム数を示す
               ::= { mpFrppDlcStatEntry 14 }

        mpFrppDlciStatXmtFECNFrames OBJECT-TYPE
               SYNTAX  Counter
               ACCESS  read-only
               STATUS  mandatory
               DESCRIPTION "The value of this object indicates the number
                            of frames sent with the FECN bit set."
                         -- 送信FECN設定フレーム数を示す
               ::= { mpFrppDlcStatEntry 15 }

        mpFrppDlciStatXmtBECNFrames OBJECT-TYPE
               SYNTAX  Counter
               ACCESS  read-only
               STATUS  mandatory
               DESCRIPTION "The value of this object indicates the number
                            of frames sent with the BECN bit set."
                         -- 送信BECN設定フレーム数を示す
               ::= { mpFrppDlcStatEntry 16 }

        mpFrppDlciStatXmtDEFrames OBJECT-TYPE
               SYNTAX  Counter
               ACCESS  read-only
               STATUS  mandatory
               DESCRIPTION "The value of this object indicates the number
                            of frames sent with the DE bit set."
                         -- 送信DE設定フレーム数を示す
               ::= { mpFrppDlcStatEntry 17 }

        mpFrppDlciStatXmtTaggedDEFrames OBJECT-TYPE
               SYNTAX  Counter
               ACCESS  read-only
               STATUS  mandatory
               DESCRIPTION "The value of this object indicates the number
                            of DE tagged frames sent to this port."
                         -- 送信DEタギングフレーム数を示す
               ::= { mpFrppDlcStatEntry 18 }

       mpFrppDlciStatRcvInArpReqFrms OBJECT-TYPE
               SYNTAX  Counter
               ACCESS  read-only
               STATUS  mandatory
               DESCRIPTION "The value of this object indicates the number
                            of frames sent with the InArp."
                         -- 受信InArpリクエストフレ－ム数を示す
               ::= { mpFrppDlcStatEntry 19 }

       mpFrppDlciStatXmtInArpReqFrms OBJECT-TYPE
               SYNTAX  Counter
               ACCESS  read-only
               STATUS  mandatory
               DESCRIPTION "The value of this object indicates the number
                            of frames sent with the InArp."
                         -- 送信InArpリクエストフレ－ム数を示す
               ::= { mpFrppDlcStatEntry 20 }

       mpFrppDlciStatRcvInArpRlyFrms OBJECT-TYPE
               SYNTAX  Counter
               ACCESS  read-only
               STATUS  mandatory
               DESCRIPTION "The value of this object indicates the number
                            of frames sent with the InArp."
                         -- 受信InARPリプライ数を示す
               ::= { mpFrppDlcStatEntry 21 }

       mpFrppDlciStatXmtInArpRlyFrms OBJECT-TYPE
               SYNTAX  Counter
               ACCESS  read-only
               STATUS  mandatory
               DESCRIPTION "The value of this object indicates the number
                            of frames sent with the InArp."
                         -- 送信InARPリプライ数を示す
               ::= { mpFrppDlcStatEntry 22 }

       mpFrppDlciStatFNUnrecognizHeaders OBJECT-TYPE
               SYNTAX  Counter
               ACCESS  read-only
               STATUS  mandatory
               DESCRIPTION "The value of this object indicates the number
                            of frames sent with the InArp."
                         -- RFC1490ヘッダ変換失敗数(FR->NPB)を示す
               ::= { mpFrppDlcStatEntry 23 }

       mpFrppDlciStatNFUnrecognizHeaders OBJECT-TYPE
               SYNTAX  Counter
               ACCESS  read-only
               STATUS  mandatory
               DESCRIPTION "The value of this object indicates the number
                            of frames sent with the InArp."
                         -- RFC1490ヘッダ変換失敗数(NPB->FR)を示す
               ::= { mpFrppDlcStatEntry 24 }

       mpFrppDlciStatFNArpTranslationErrs OBJECT-TYPE
               SYNTAX  Counter
               ACCESS  read-only
               STATUS  mandatory
               DESCRIPTION "The value of this object indicates the number
                            of frames sent with the InArp."
                         -- 未定義ヘッダエラ－(FR->NPB)を示す
               ::= { mpFrppDlcStatEntry 25 }

       mpFrppDlciStatNFArpTranslationErrs OBJECT-TYPE
               SYNTAX  Counter
               ACCESS  read-only
               STATUS  mandatory
               DESCRIPTION "The value of this object indicates the number
                            of frames sent with the InArp."
                         -- 未定義ヘッダエラ－(NPB->FR)を示す
               ::= { mpFrppDlcStatEntry 26 }

       mpFrppDlciStatXmtVQFrms OBJECT-TYPE
               SYNTAX  Counter
               ACCESS  read-only
               STATUS  mandatory
               DESCRIPTION "The value of this object indicates the number
                            of frames sent with the InArp."
                         -- 送信PQ(Voice)フレ－ム数(正常送信)を示す
               ::= { mpFrppDlcStatEntry 27 }

       mpFrppDlciStatXmtUQFrms OBJECT-TYPE
               SYNTAX  Counter
               ACCESS  read-only
               STATUS  mandatory
               DESCRIPTION "The value of this object indicates the number
                            of frames sent with the InArp."
                         -- 送信PQ(Urgent)フレ－ム数(正常送信)を示す
               ::= { mpFrppDlcStatEntry 28 }

       mpFrppDlciStatXmtXceedUQLenFrms OBJECT-TYPE
               SYNTAX  Counter
               ACCESS  read-only
               STATUS  mandatory
               DESCRIPTION "The value of this object indicates the number
                            of frames sent with the InArp."
                         -- 送信PQ(Urgent)Que長超過廃棄フレ－ム数を示す
               ::= { mpFrppDlcStatEntry 29 }

       mpFrppDlciStatXmtXceedUQByteFrms OBJECT-TYPE
               SYNTAX  Counter
               ACCESS  read-only
               STATUS  mandatory
               DESCRIPTION "The value of this object indicates the number
                            of frames sent with the InArp."
                         -- 送信PQ(Urgent)QueByte長超過廃棄フレ－ム数を示す
               ::= { mpFrppDlcStatEntry 30 }

        mpFrppDlciStatXmtHQFrms OBJECT-TYPE
               SYNTAX  Counter
               ACCESS  read-only
               STATUS  mandatory
               DESCRIPTION "The value of this object indicates the number
                            of frames sent with the InArp."
                         -- 送信PQ(High)フレ－ム数(正常送信)を示す
               ::= { mpFrppDlcStatEntry 31 }

        mpFrppDlciStatXmtXceedHQLenFrms OBJECT-TYPE
               SYNTAX  Counter
               ACCESS  read-only
               STATUS  mandatory
               DESCRIPTION "The value of this object indicates the number
                            of frames sent with the InArp."
                         -- 送信PQ(High)Que長超過廃棄フレ－ム数を示す
               ::= { mpFrppDlcStatEntry 32 }

        mpFrppDlciStatXmtXceedHQByteFrms OBJECT-TYPE
               SYNTAX  Counter
               ACCESS  read-only
               STATUS  mandatory
               DESCRIPTION "The value of this object indicates the number
                            of frames sent with the InArp."
                         -- 送信PQ(High)QueByte長超過廃棄フレ－ム数を示す
               ::= { mpFrppDlcStatEntry 33 }

        mpFrppDlciStatXmtNQFrms OBJECT-TYPE
               SYNTAX  Counter
               ACCESS  read-only
               STATUS  mandatory
               DESCRIPTION "The value of this object indicates the number
                            of frames sent with the InArp."
                         -- 送信PQ(Normal)フレ－ム数(正常送信)を示す
               ::= { mpFrppDlcStatEntry 34 }

        mpFrppDlciStatXmtXceedNQLenFrms OBJECT-TYPE
               SYNTAX  Counter
               ACCESS  read-only
               STATUS  mandatory
               DESCRIPTION "The value of this object indicates the number
                            of frames sent with the InArp."
                         -- 送信PQ(Normal)Que長超過廃棄フレ－ム数を示す
               ::= { mpFrppDlcStatEntry 35 }

        mpFrppDlciStatXmtXceedNQByteFrms OBJECT-TYPE
               SYNTAX  Counter
               ACCESS  read-only
               STATUS  mandatory
               DESCRIPTION "The value of this object indicates the number
                            of frames sent with the InArp."
                         -- 送信PQ(Normal)QueByte長超過廃棄フレ－ム数を示す
               ::= { mpFrppDlcStatEntry 36 }

        mpFrppDlciStatXmtLQFrms OBJECT-TYPE
               SYNTAX  Counter
               ACCESS  read-only
               STATUS  mandatory
               DESCRIPTION "The value of this object indicates the number
                            of frames sent with the InArp."
                         -- 送信PQ(Low)フレ－ム数(正常送信)を示す
               ::= { mpFrppDlcStatEntry 37 }

        mpFrppDlciStatXmtXceedLQLenFrms OBJECT-TYPE
               SYNTAX  Counter
               ACCESS  read-only
               STATUS  mandatory
               DESCRIPTION "The value of this object indicates the number
                            of frames sent with the InArp."
                         -- 送信PQ(Low)Que長超過廃棄フレ－ム数を示す
               ::= { mpFrppDlcStatEntry 38 }

        mpFrppDlciStatXmtXceedLQByteFrms OBJECT-TYPE
               SYNTAX  Counter
               ACCESS  read-only
               STATUS  mandatory
               DESCRIPTION "The value of this object indicates the number
                            of frames sent with the InArp."
                         -- 送信PQ(Low)QueByte長超過廃棄フレ－ム数を示す
               ::= { mpFrppDlcStatEntry 39 }

        mpFrppDlciStatRcvNPBDe0Frms OBJECT-TYPE
               SYNTAX  Counter
               ACCESS  read-only
               STATUS  mandatory
               DESCRIPTION "The value of this object indicates the number
                            of frames received from SAR with the CLP bit set
                            to 0."
                         -- 受信DE=0フレ－ム数(NPBから受信)を示す
               ::= { mpFrppDlcStatEntry 40 }

        mpFrppDlciStatRcvNPBDe1Frms OBJECT-TYPE
               SYNTAX  Counter
               ACCESS  read-only
               STATUS  mandatory
               DESCRIPTION "The value of this object indicates the number
                            of frames received from SAR with the CLP bit set
                            to 1."
                         -- 受信DE=0フレ－ム数(NPBから受信)を示す
               ::= { mpFrppDlcStatEntry 41 }

        mpFrppDlciStatRcvNPBDiscardFrms OBJECT-TYPE
               SYNTAX  Counter
               ACCESS  read-only
               STATUS  mandatory
               DESCRIPTION "The value of this object indicates the total
                            number of discard frames sent on this port."
                         -- 受信廃棄フレ－ム数(NPBから受信)を示す
               ::= { mpFrppDlcStatEntry 42 }

        mpFrppDlciStatXmtNPBFrms OBJECT-TYPE
               SYNTAX  Counter
               ACCESS  read-only
               STATUS  mandatory
               DESCRIPTION "The value of this object indicates the total
                            number of discard frames sent on this port."
                         -- 送信フレ－ム数(NPBへ送信)を示す
               ::= { mpFrppDlcStatEntry 43 }

        mpFrppDlciStatXmtNPBDiscardFrms OBJECT-TYPE
               SYNTAX  Counter
               ACCESS  read-only
               STATUS  mandatory
               DESCRIPTION "The value of this object indicates the total
                            number of discard frames sent on this port."
                         -- 送信廃棄フレ－ム数を示す
               ::= { mpFrppDlcStatEntry 44 }

-- ・Frpp DLCI Work Statistics Information MIB  @002追加

        mpFrppDlciWkStatTable OBJECT-TYPE
               SYNTAX SEQUENCE OF MpFrppDlciWkStatEntry
               ACCESS  not-accessible
               STATUS  mandatory
               DESCRIPTION "This is the table type object of the
                            Frpp DLCI Work statistics information."
               ::= { mpFrpp 9 }

        mpFrppDlciWkStatEntry OBJECT-TYPE
               SYNTAX  MpFrppDlciWkStatEntry
               ACCESS  not-accessible
               STATUS  mandatory
               DESCRIPTION "This is the table entry of mpFrppDlciWkStatTable."
               INDEX { mpFrppDlciWkStatIfIndex }
               ::= { mpFrppDlciWkStatTable 1 }

        MpFrppDlciWkStatEntry ::=
                 SEQUENCE {
                   mpFrppDlciWkStatIfIndex                  INTEGER,
--                 mpFrppDlciWkStatDlciIndex                INTEGER,    @006削除
                   mpFrppDlciWkStatFNEncapNones             Counter,
                   mpFrppDlciWkStatFNEncapBridgeds          Counter,
                   mpFrppDlciWkStatFNEncapBridgedFCSs       Counter,
                   mpFrppDlciWkStatFNEncapBPDUs             Counter,
                   mpFrppDlciWkStatFNEncapRoutedIPs         Counter,
                   mpFrppDlciWkStatFNEncapRoutedIPSNAPs     Counter,
                   mpFrppDlciWkStatFNEncapVOIP0s            Counter,
                   mpFrppDlciWkStatFNEncapVOIP1s            Counter,
                   mpFrppDlciWkStatFNEncapVOIP2s            Counter,
                   mpFrppDlciWkStatFNEncapVOIP3s            Counter,
                   mpFrppDlciWkStatFNEncapVOIP4s            Counter,
                   mpFrppDlciWkStatFNEncapVOIP5s            Counter,
                   mpFrppDlciWkStatFNEncapVOIP6s            Counter,
                   mpFrppDlciWkStatFNEncapVOIP7s            Counter,
                   mpFrppDlciWkStatFNEncapVOIP8s            Counter,
                   mpFrppDlciWkStatFNEncapVOIP9s            Counter,
                   mpFrppDlciWkStatNFEncapNones             Counter,
                   mpFrppDlciWkStatNFEncapBridgeds          Counter,
                   mpFrppDlciWkStatNFEncapBridgedFCSs       Counter,
                   mpFrppDlciWkStatNFEncapBPDUs             Counter,
                   mpFrppDlciWkStatNFEncapRoutedIPs         Counter,
                   mpFrppDlciWkStatNFEncapRoutedIPSNAPs     Counter,
                   mpFrppDlciWkStatNFEncapVOIP0s            Counter,
                   mpFrppDlciWkStatNFEncapVOIP1s            Counter,
                   mpFrppDlciWkStatNFEncapVOIP2s            Counter,
                   mpFrppDlciWkStatNFEncapVOIP3s            Counter,
                   mpFrppDlciWkStatNFEncapVOIP4s            Counter,
                   mpFrppDlciWkStatNFEncapVOIP5s            Counter,
                   mpFrppDlciWkStatNFEncapVOIP6s            Counter,
                   mpFrppDlciWkStatNFEncapVOIP7s            Counter,
                   mpFrppDlciWkStatNFEncapVOIP8s            Counter,
                   mpFrppDlciWkStatNFEncapVOIP9s            Counter,
                   mpFrppDlciWkStatRcvFragFrms              Counter,
                   mpFrppDlciWkStatRasmCompleteds           Counter,
                   mpFrppDlciWkStatFragSequenceErrs         Counter,
                   mpFrppDlciWkStatFragBitErrs              Counter,
                   mpFrppDlciWkStatRasmFrmSizeErrs          Counter,
                   mpFrppDlciWkStatInvalidFragFrms          Counter,
                   mpFrppDlciWkStatFragBufhuntNgs           Counter,
                   mpFrppDlciWkStatFragSndNgs               Counter,
                   mpFrppDlciWkStatXmtFrames                Counter,
                   mpFrppDlciWkStatXmtDiscardFrms           Counter
               }

        mpFrppDlciWkStatIfIndex OBJECT-TYPE
               SYNTAX  INTEGER
               ACCESS  read-only
               STATUS  mandatory
               DESCRIPTION "The value of this object identifies the frpp
                            number."
                         -- Frpp 番号を示す。
               ::= { mpFrppDlciWkStatEntry 1 }

        mpFrppDlciWkStatFNEncapNones OBJECT-TYPE
               SYNTAX  Counter
               ACCESS  read-only
               STATUS  mandatory
               DESCRIPTION "The value of this object indicates the total
                            number of non capsule for this Dlci."
                         -- capsule化なし　フレーム数
               ::= { mpFrppDlciWkStatEntry 2 }

        mpFrppDlciWkStatFNEncapBridgeds  OBJECT-TYPE
               SYNTAX  Counter
               ACCESS  read-only
               STATUS  mandatory
               DESCRIPTION "The value of this object indicates the total
                            number of MACoFR(802.3/ETHER) non FCS for this Dlci."
                         -- MACoFR(802.3/ETHER) FCS無しフレームレーム数
                ::= { mpFrppDlciWkStatEntry 3 }

        mpFrppDlciWkStatFNEncapBridgedFCSs    OBJECT-TYPE
               SYNTAX  Counter
               ACCESS  read-only
               STATUS  mandatory
               DESCRIPTION "The value of this object indicates the total
                            number of MACoFR(802.3/ETHER) for this Dlci."
                         -- MACoFR(802.3/ETHER) FCS有り　フレーム数
                ::= { mpFrppDlciWkStatEntry 4 }

        mpFrppDlciWkStatFNEncapBPDUs  OBJECT-TYPE
               SYNTAX  Counter
               ACCESS  read-only
               STATUS  mandatory
               DESCRIPTION "The value of this object indicates the total
                            number of MACoFR(802.3d/802.3g) for this dlci."
                         -- MACoFR(802.3d/802.3g) フレーム数
                ::= { mpFrppDlciWkStatEntry 5 }

        mpFrppDlciWkStatFNEncapRoutedIPs  OBJECT-TYPE
               SYNTAX  Counter
               ACCESS  read-only
               STATUS  mandatory
               DESCRIPTION "The value of this object indicates the total
                            number of IPoFR(NLPID) for this dlci."
                         -- IPoFR(NLPID) フレーム数
                ::= { mpFrppDlciWkStatEntry 6 }

        mpFrppDlciWkStatFNEncapRoutedIPSNAPs  OBJECT-TYPE
               SYNTAX  Counter
               ACCESS  read-only
               STATUS  mandatory
               DESCRIPTION "The value of this object indicates the total
                            number of IPoFR with SNAP for this dlci."
                         -- IPoFR with SNAP フレーム数
                ::= { mpFrppDlciWkStatEntry 7 }

        mpFrppDlciWkStatFNEncapVOIP0s     OBJECT-TYPE
               SYNTAX  Counter
               ACCESS  read-only
               STATUS  mandatory
               DESCRIPTION "The value of this object indicates the total
                            number of VoIP (cmp udp) for this dlci."
                         -- 951収容 0x03 20(cmp udp) フレーム数
                ::= { mpFrppDlciWkStatEntry 8 }

        mpFrppDlciWkStatFNEncapVOIP1s   OBJECT-TYPE
               SYNTAX  Counter
               ACCESS  read-only
               STATUS  mandatory
               DESCRIPTION "The value of this object indicates the total
                            number of VoIP (cmp rtp) for this dlci."
                         -- 951収容 0x03 21(cmp rtp)  フレーム数
                ::= { mpFrppDlciWkStatEntry 9 }

        mpFrppDlciWkStatFNEncapVOIP2s  OBJECT-TYPE
               SYNTAX  Counter
               ACCESS  read-only
               STATUS  mandatory
               DESCRIPTION "The value of this object indicates the total
                            number of VoIP (ful hdr)for this dlci."
                         -- 951収容 0x03 22(ful hdr) フレーム数
                ::= { mpFrppDlciWkStatEntry 10 }

        mpFrppDlciWkStatFNEncapVOIP3s  OBJECT-TYPE
               SYNTAX  Counter
               ACCESS  read-only
               STATUS  mandatory
               DESCRIPTION "The value of this object indicates the total
                            number of VoIP (ful ctx) for this dlci."
                         -- 951収容 0x03 23(ful ctx) フレーム数
                ::= { mpFrppDlciWkStatEntry 11 }

        mpFrppDlciWkStatFNEncapVOIP4s   OBJECT-TYPE
               SYNTAX  Counter
               ACCESS  read-only
               STATUS  mandatory
               DESCRIPTION "The value of this object indicates the total
                            number of VoIP (cmp rtp) for this dlci."
                         -- cso収容 0x20 07(cmp rtp) フレーム数
                ::= { mpFrppDlciWkStatEntry 12 }

        mpFrppDlciWkStatFNEncapVOIP5s    OBJECT-TYPE
               SYNTAX  Counter
               ACCESS  read-only
               STATUS  mandatory
               DESCRIPTION "The value of this object indicates the total
                            number of VoIP (ful hdr) for this dlci."
                         -- cso収容 0x20 09(ful hdr) フレーム数
                ::= { mpFrppDlciWkStatEntry 13 }

        mpFrppDlciWkStatFNEncapVOIP6s   OBJECT-TYPE
               SYNTAX  Counter
               ACCESS  read-only
               STATUS  mandatory
               DESCRIPTION "The value of this object indicates the total
                            number of VoIP(ful ctx) for this dlci."
                         -- cso収容 0x20 0A(ful ctx) フレーム数
                ::= { mpFrppDlciWkStatEntry 14 }

        mpFrppDlciWkStatFNEncapVOIP7s  OBJECT-TYPE
               SYNTAX  Counter
               ACCESS  read-only
               STATUS  mandatory
               DESCRIPTION "The value of this object indicates the total
                            number of VoIP for this dlci.(reserve)"
                         -- 951収容 0x03 31(cmp tcp) フレーム数
                ::= { mpFrppDlciWkStatEntry 15 }

        mpFrppDlciWkStatFNEncapVOIP8s  OBJECT-TYPE
               SYNTAX  Counter
               ACCESS  read-only
               STATUS  mandatory
               DESCRIPTION "The value of this object indicates the total
                            number of VoIP for this dlci.(reserve)"
                         -- 951収容 0x03 32(cmp tcp nodelta) フレーム数
                ::= { mpFrppDlciWkStatEntry 16 }

        mpFrppDlciWkStatFNEncapVOIP9s  OBJECT-TYPE
               SYNTAX  Counter
               ACCESS  read-only
               STATUS  mandatory
               DESCRIPTION "The value of this object indicates the total
                            number of VoIP for this dlci.(reserve)"
                         -- cso収容 0x20 08(full ctx) フレーム数
                ::= { mpFrppDlciWkStatEntry 17 }

        mpFrppDlciWkStatNFEncapNones   OBJECT-TYPE
               SYNTAX  Counter
               ACCESS  read-only
               STATUS  mandatory
               DESCRIPTION "The value of this object indicates the total
                            number of None capsulation for this dlci."
                         -- capsule化無し　フレーム数
                ::= { mpFrppDlciWkStatEntry 18 }

        mpFrppDlciWkStatNFEncapBridgeds  OBJECT-TYPE
               SYNTAX  Counter
               ACCESS  read-only
               STATUS  mandatory
               DESCRIPTION "The value of this object indicates the total
                            number of MACoFR(802.3/ETHER) non FSC for this dlci."
                         -- MACoFR(802.3/ETHER) FCS無し フレーム数
                ::= { mpFrppDlciWkStatEntry 19 }

        mpFrppDlciWkStatNFEncapBridgedFCSs  OBJECT-TYPE
               SYNTAX  Counter
               ACCESS  read-only
               STATUS  mandatory
               DESCRIPTION "The value of this object indicates the total
                            number of MACoFR(802.3/ETHER) for this dlci."
                         -- MACoFR(802.3/ETHER) フレーム数
                ::= { mpFrppDlciWkStatEntry 20 }

        mpFrppDlciWkStatNFEncapBPDUs   OBJECT-TYPE
               SYNTAX  Counter
               ACCESS  read-only
               STATUS  mandatory
               DESCRIPTION "The value of this object indicates the total
                            number of MACoFR(802.3d/802.3g) for this dlci."
                         -- MACoFR(802.3d/802.3g) フレーム数
                ::= { mpFrppDlciWkStatEntry 21 }

        mpFrppDlciWkStatNFEncapRoutedIPs  OBJECT-TYPE
               SYNTAX  Counter
               ACCESS  read-only
               STATUS  mandatory
               DESCRIPTION "The value of this object indicates the total
                            number of IPoFR(NLPID) for this dlci."
                         -- IPoFR(NLPID) フレーム数
                ::= { mpFrppDlciWkStatEntry 22 }

        mpFrppDlciWkStatNFEncapRoutedIPSNAPs  OBJECT-TYPE
               SYNTAX  Counter
               ACCESS  read-only
               STATUS  mandatory
               DESCRIPTION "The value of this object indicates the total
                            number of IPoFR with SNAP for this dlci."
                         -- IPoFR with SNAP フレーム数
                ::= { mpFrppDlciWkStatEntry 23 }

        mpFrppDlciWkStatNFEncapVOIP0s  OBJECT-TYPE
               SYNTAX  Counter
               ACCESS  read-only
               STATUS  mandatory
               DESCRIPTION "The value of this object indicates the total
                            number of VoIP (cmp udp) for this dlci."
                         -- 951収容 0x03 20(cmp udp) フレーム数
                ::= { mpFrppDlciWkStatEntry 24 }

        mpFrppDlciWkStatNFEncapVOIP1s OBJECT-TYPE
               SYNTAX  Counter
               ACCESS  read-only
               STATUS  mandatory
               DESCRIPTION "The value of this object indicates the total
                            number of VoIP (cmp rtp) for this dlci."
                         -- 951収容 0x03 21(cmp rtp) フレーム数
                ::= { mpFrppDlciWkStatEntry 25 }

        mpFrppDlciWkStatNFEncapVOIP2s   OBJECT-TYPE
               SYNTAX  Counter
               ACCESS  read-only
               STATUS  mandatory
               DESCRIPTION "The value of this object indicates the total
                            number of VoIP (ful hdr) for this dlci."
                         -- 951収容 0x03 22(ful hdr) フレーム数
                ::= { mpFrppDlciWkStatEntry 26 }

        mpFrppDlciWkStatNFEncapVOIP3s  OBJECT-TYPE
               SYNTAX  Counter
               ACCESS  read-only
               STATUS  mandatory
               DESCRIPTION "The value of this object indicates the total
                            number of VoIP (ful ctx) for this dlci."
                         -- 951収容 0x03 23(ful ctx) フレーム数
                ::= { mpFrppDlciWkStatEntry 27 }

        mpFrppDlciWkStatNFEncapVOIP4s  OBJECT-TYPE
               SYNTAX  Counter
               ACCESS  read-only
               STATUS  mandatory
               DESCRIPTION "The value of this object indicates the total
                            number of VoIP (cmp rtp) for this dlci."
                         -- cso収容 0x20 07(cmp rtp) フレーム数
                ::= { mpFrppDlciWkStatEntry 28  }

        mpFrppDlciWkStatNFEncapVOIP5s  OBJECT-TYPE
               SYNTAX  Counter
               ACCESS  read-only
               STATUS  mandatory
               DESCRIPTION "The value of this object indicates the total
                            number of VoIP (ful hdr) for this dlci."
                         -- cso収容 0x20 09(ful hdr) フレーム数
                ::= { mpFrppDlciWkStatEntry 29 }

        mpFrppDlciWkStatNFEncapVOIP6s  OBJECT-TYPE
               SYNTAX  Counter
               ACCESS  read-only
               STATUS  mandatory
               DESCRIPTION "The value of this object indicates the total
                            number of VoIP (ful ctx) for this dlci."
                         -- cso収容 0x20 0A(ful ctx) フレーム数
                ::= { mpFrppDlciWkStatEntry 30 }

        mpFrppDlciWkStatNFEncapVOIP7s   OBJECT-TYPE
               SYNTAX  Counter
               ACCESS  read-only
               STATUS  mandatory
               DESCRIPTION "The value of this object indicates the total
                            number of VoIP for this dlci."
                         -- 951収容 0x03 31(cmp tcp) フレーム数
                ::= { mpFrppDlciWkStatEntry 31 }

        mpFrppDlciWkStatNFEncapVOIP8s   OBJECT-TYPE
               SYNTAX  Counter
               ACCESS  read-only
               STATUS  mandatory
               DESCRIPTION "The value of this object indicates the total
                            number of VoIP for this dlci."
                         -- 951収容 0x03 32(cmp tcp nodelta) フレーム数
                ::= { mpFrppDlciWkStatEntry 32 }

        mpFrppDlciWkStatNFEncapVOIP9s  OBJECT-TYPE
               SYNTAX  Counter
               ACCESS  read-only
               STATUS  mandatory
               DESCRIPTION "The value of this object indicates the total
                            number of VoIP for this dlci."
                         -- cso収容 0x20 08(full ctx) フレーム数
                ::= { mpFrppDlciWkStatEntry 33 }

        mpFrppDlciWkStatRcvFragFrms   OBJECT-TYPE
               SYNTAX  Counter
               ACCESS  read-only
               STATUS  mandatory
               DESCRIPTION "The value of this object indicates the total
                            number of FRF.12 Fragment for this dlci."
                         -- 受信Fragmentフレーム数
                ::= { mpFrppDlciWkStatEntry 34 }

        mpFrppDlciWkStatRasmCompleteds   OBJECT-TYPE
               SYNTAX  Counter
               ACCESS  read-only
               STATUS  mandatory
               DESCRIPTION "The value of this object indicates the total
                            number of FRF.12 RasmCompleted for this dlci."
                         -- リアセンブリ完了数
                ::= { mpFrppDlciWkStatEntry 35 }

        mpFrppDlciWkStatFragSequenceErrs  OBJECT-TYPE
               SYNTAX  Counter
               ACCESS  read-only
               STATUS  mandatory
               DESCRIPTION "The value of this object indicates the total
                            number of FRF.12 FragSequenceErr for this dlci."
                         -- SEQ No.異常 によりリアセンブリに失敗した回数
                ::= { mpFrppDlciWkStatEntry 36 }

        mpFrppDlciWkStatFragBitErrs  OBJECT-TYPE
               SYNTAX  Counter
               ACCESS  read-only
               STATUS  mandatory
               DESCRIPTION "The value of this object indicates the total
                            number of FRF.12 BitErr for this dlci."
                         -- リアセンブリ中に開始Fragment bit(Begin bit)を受信した数
                ::= { mpFrppDlciWkStatEntry 37 }

        mpFrppDlciWkStatRasmFrmSizeErrs  OBJECT-TYPE
               SYNTAX  Counter
               ACCESS  read-only
               STATUS  mandatory
               DESCRIPTION "The value of this object indicates the total
                            number of FRF.12 SizeErr for this dlci."
                         -- リアセンブリ後のMTUサイズOver
                ::= { mpFrppDlciWkStatEntry 38 }

        mpFrppDlciWkStatInvalidFragFrms   OBJECT-TYPE
               SYNTAX  Counter
               ACCESS  read-only
               STATUS  mandatory
               DESCRIPTION "The value of this object indicates the total
                            number of FRF.12 InvalidFragFrms  for this dlci."
                         -- 無効Fragmentフレーム数
                ::= { mpFrppDlciWkStatEntry 39 }

        mpFrppDlciWkStatFragBufhuntNgs   OBJECT-TYPE
               SYNTAX  Counter
               ACCESS  read-only
               STATUS  mandatory
               DESCRIPTION "The value of this object indicates the total
                            number of FRF.12 Buffer Hunt NG for this dlci."
                         -- Fragmentバッファハント失敗回数
                ::= { mpFrppDlciWkStatEntry 40 }

        mpFrppDlciWkStatFragSndNgs  OBJECT-TYPE
               SYNTAX  Counter
               ACCESS  read-only
               STATUS  mandatory
               DESCRIPTION "The value of this object indicates the total
                            number of FRF.12 send flg err for this dlci."
                         -- Fragmentフレーム送信失敗回数
                ::= { mpFrppDlciWkStatEntry 41 }

        mpFrppDlciWkStatXmtFrames  OBJECT-TYPE
               SYNTAX  Counter
               ACCESS  read-only
               STATUS  mandatory
               DESCRIPTION "The value of this object indicates the total
                            number of FRF.12 rev flg ng for this dlci."
                         -- 送信Fragmentフレーム数
                ::= { mpFrppDlciWkStatEntry 42 }

        mpFrppDlciWkStatXmtDiscardFrms  OBJECT-TYPE
               SYNTAX  Counter
               ACCESS  read-only
               STATUS  mandatory
               DESCRIPTION "The value of this object indicates the total
                            number of FRF.12 DiscardFrms for this dlci."
                         -- 送信廃棄Fragmentフレーム数
                ::= { mpFrppDlciWkStatEntry 43 }

END
