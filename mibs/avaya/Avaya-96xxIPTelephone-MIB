Avaya-96xxIPTelephone-MIB
DEFINITIONS ::= BEGIN
IMPORTS
        	enterprises, OBJECT-TYPE, MODULE-IDENTITY, Integer32, IpAddress
              		FROM SNMPv2-SMI
   		DisplayString
		FROM RFC1213-MIB ;

avaya96xxMIB MODULE-IDENTITY
	     	LAST-UPDATED     "0908052000Z"
    	     	ORGANIZATION     "avaya"
             		CONTACT-INFO     "Avaya Customer Services
		      	 Avaya, Inc.
		    	 211 Mt. Airy Road
		       	Basking Ridge, NJ 07920 US (A
	    	                   WWW: www.avaya.com
        		                  Tel: +1 908 953 6000"

		 DESCRIPTION     "MIB Module for 96xx IP Telephones as of Release S3.1
			in accordance with 96xx IP RFS 110716, Issue 3.1.
			Copyright 2009 by Avaya Inc.  All rights reserved."
	            ::= { ipEndpointMIBs 2 }

avaya                   OBJECT IDENTIFIER ::= { enterprises 6889 }
products                OBJECT IDENTIFIER ::= { avaya 1 }
avayaMibs               OBJECT IDENTIFIER ::= { avaya 2 }
avayaipEndpointProd     OBJECT IDENTIFIER ::= { products 69 }
ipEndpointMIBs          OBJECT IDENTIFIER ::= { avayaMibs 69 }


endptID         OBJECT IDENTIFIER ::= { avaya96xxMIB 1 }
endptAGCHAND    OBJECT-TYPE
                    SYNTAX      INTEGER
                    MAX-ACCESS  read-only
                    STATUS      current
                    DESCRIPTION "Handset AGC status. This variable returns 1
                        if the endpoint's handset Automatic Gain Control
                        capability is currently enabled, else 0."
                    ::= { endptID 1 }
endptAGCHEAD    OBJECT-TYPE
                    SYNTAX      INTEGER
                    MAX-ACCESS  read-only
                    STATUS      current
                    DESCRIPTION "Headset AGC status. This variable returns 1
                        if the endpoint's headset Automatic Gain Control
                        capability is currently enabled, else 0."
                    ::= { endptID 2 }
endptAGCSPKR    OBJECT-TYPE
                    SYNTAX      INTEGER
                    MAX-ACCESS  read-only
                    STATUS      current
                    DESCRIPTION "Speakerphone AGC status. This variable returns
                        1 if the endpoint's speakerphone Automatic Gain Control
                        capability is currently enabled, else 0."
                    ::= { endptID 3 }
endptAPPINUSE   OBJECT-TYPE
                    SYNTAX      DisplayString
                    MAX-ACCESS  read-only
                    STATUS      current
                    DESCRIPTION "Application file name.  This variable returns
                        the name of the application file in the endpoint."
                    ::= { endptID 4 }
endptAPPNAME    OBJECT-TYPE
                    SYNTAX      DisplayString
                    MAX-ACCESS  read-only
                    STATUS      current
                    DESCRIPTION "Application file ID. This variable returns
                        a string specifying the system-specific application
                        file that should be used for telephone operation."
                    ::= { endptID 5 }
endptBAKLIGHTOFF OBJECT-TYPE
                    SYNTAX      INTEGER
                    MAX-ACCESS  read-only
                    STATUS      current
                    DESCRIPTION "Backlight idle timer setting. This variable returns
	    the number of minutes of idle time, after which the
	    telephone backlightis turned off. Range is 0-999, with a
	    default of 120.  Used in phones with backlit displays."
                    ::= { endptID 6 }
endptBOOTNAME   OBJECT-TYPE
                    SYNTAX      DisplayString
                    MAX-ACCESS  read-only
                    STATUS      current
                    DESCRIPTION "Boot code file ID. This variable returns a string
                        specifying the boot code
                        file used to initiate telephone operation."
                    ::= { endptID 7 }
endptBRURI      OBJECT-TYPE
                    SYNTAX      DisplayString
                    MAX-ACCESS  read-only
                    STATUS      current
                    DESCRIPTION "Backup and restore URI. This variable returns
		a string specifying the URI used for backup and restore files."
                    ::= { endptID 8 }
endptCNAPORT    OBJECT-TYPE
                    SYNTAX      INTEGER
                    MAX-ACCESS  read-only
                    STATUS      current
                    DESCRIPTION "Chatter server port. This variable returns the
		Chatter server registration transport-layer port number
		(from 0 to 65535; default is 8888)."
                    ::= { endptID 9 }
endptCNASRVR    OBJECT-TYPE
                    SYNTAX      DisplayString
                    MAX-ACCESS  read-only
                    STATUS      current
                    DESCRIPTION "CNA server addresses. This variable returns zero
		or more Chatter server addresses for network analysis, in
		dotted decimal or DNS format."
                    ::= { endptID 10 }
endptCODECR     OBJECT-TYPE
                    SYNTAX      DisplayString
                    MAX-ACCESS  read-only
                    STATUS      current
                    DESCRIPTION "Receive codec. This variable returns the
                        designation of the Receive codec currently in use."
                    ::= { endptID 11 }
endptCODECT     OBJECT-TYPE
                    SYNTAX      DisplayString
                    MAX-ACCESS  read-only
                    STATUS      current
                    DESCRIPTION "Transmit codec. This variable returns the
                        designation of the Transmit codec currently in use."
                    ::= { endptID 12 }
endptDHCPLEASEREBIND     OBJECT-TYPE
                    SYNTAX      Integer32
                    MAX-ACCESS  read-only
                    STATUS      current
                    DESCRIPTION "Rebind time of IPADD lease. This
                        variable returns an unsigned integer specifying
                        the length of time at which to rebind the IPADD
	    lease, in seconds as received by DHCP option 59
	    or as computed from the lease time if option 59 is
	     is not received."
                    ::= { endptID 13 }
endptDHCPLEASERENEW     OBJECT-TYPE
                    SYNTAX      Integer32
                    MAX-ACCESS  read-only
                    STATUS      current
                    DESCRIPTION "Renewal time of IPADD lease. This
                        variable returns an unsigned integer specifying
                        the length of time at which to renew the IPADD
	    lease, in seconds as received by DHCP option 58
	    or as computed from the lease time if option 58 is
	     is not received."
                    ::= { endptID 14 }
endptDHCPLEASETIME      OBJECT-TYPE
                    SYNTAX      Integer32
                    MAX-ACCESS  read-only
                    STATUS      current
                    DESCRIPTION "Duration of IPADD lease. This variable
                        returns an unsigned integer specifying the length
                        of time of the IPADD lease, in seconds as received
                        by DHCP option 51."
                    ::= { endptID 15 }
endptDNSSRVR    OBJECT-TYPE
                    SYNTAX      DisplayString
                    MAX-ACCESS  read-only
                    STATUS      current
                    DESCRIPTION "List of DNS server addresses.  This variable
		returns a sequence of IP addresses, in dotted-decimal
		format and separated by commas, of DNS servers
		available for use."
                    ::= { endptID 16 }
endptDOMAIN     OBJECT-TYPE
                    SYNTAX      DisplayString
                    MAX-ACCESS  read-only
                    STATUS      current
                    DESCRIPTION "List of DNS domain labels.  This variable
		returns a sequence of labels, separated by periods, for
                        use as the highest-level domain in resolving DNS names
		in system values."
                    ::= { endptID 17 }
endptDOT1X      OBJECT-TYPE
                    SYNTAX      INTEGER
                    MAX-ACCESS  read-only
                    STATUS      current
                    DESCRIPTION "Current value for 802.1X handling. This variable returns
		0 if  Supplicant operation is Enabled,  1 if Supplicant operation is
                        Enabled with proxy Logoff, and 2 if Supplicant operation is Disabled.
	     The default is 0."
                    ::= { endptID 18 }
endptDSCPAUD    OBJECT-TYPE
                    SYNTAX      INTEGER
                    MAX-ACCESS  read-only
                    STATUS      current
                    DESCRIPTION "DSCP for audio. This variable specifies the
                        Differentiated Services Code Point for audio
                        currently in use (between 0 and 63 inclusive)."
                    ::= { endptID 19 }
endptDSCPBBE    OBJECT-TYPE
                    SYNTAX      INTEGER
                    MAX-ACCESS  read-only
                    STATUS      current
                    DESCRIPTION "DSCP BBE priority value. This variable returns
                        an integer between 0 and 7 inclusive specifying the
                        far-end endpoint's DiffServ Better than Best Effort audio
                        priority value."
                    ::= { endptID 20 }
endptDSCPSIG    OBJECT-TYPE
                    SYNTAX      INTEGER
                    MAX-ACCESS  read-only
                    STATUS      current
                    DESCRIPTION " DSCP for signaling. This variable specifies
                        the Differentiated Services Code Point for signaling
                        currently in use (between 0 and 63 inclusive)."
                    ::= { endptID 21 }
endptDSPVERSION  OBJECT-TYPE
                    SYNTAX      DisplayString
                    MAX-ACCESS  read-only
                    STATUS      current
                    DESCRIPTION "DSP Version.  This variable returns a string
		of up to 10 characters, that identifies the version of
		the DSP firmware in the endpoint."
                    ::= { endptID 22 }
endptFEIPADD    OBJECT-TYPE
                    SYNTAX      IpAddress
                    MAX-ACCESS  read-only
                    STATUS      current
                    DESCRIPTION "Audio endpoint address. This variable returns
                        a 4-octet string specifying the address of the far-end
                        audio endpoint currently in use."
                    ::= { endptID 23 }
endptFEPORT     OBJECT-TYPE
                    SYNTAX      INTEGER
                    MAX-ACCESS  read-only
                    STATUS      current
                    DESCRIPTION "Audio endpoint port number. This variable returns
                        the far-end endpoint's transport layer port number for
                        audio, currently in use."
                    ::= { endptID 24 }
endptGIPADD     OBJECT-TYPE
                    SYNTAX      DisplayString
                    MAX-ACCESS  read-only
                    STATUS      current
                    DESCRIPTION "List of router addresses.  This variable returns a
		sequence of IP addresses, in dotted-decimal format and
		separated by commas, of routers available for use."
                    ::= { endptID 25 }
endptGIPINUSE   OBJECT-TYPE
                    SYNTAX      IpAddress
                    MAX-ACCESS  read-only
                    STATUS      current
                    DESCRIPTION "Router address.  This variable returns
                        a 4-octet string specifying the IP address of
                        the router currently in use."
                    ::= { endptID 26 }
endptGROUP      OBJECT-TYPE
                    SYNTAX      INTEGER
                    MAX-ACCESS  read-only
                    STATUS      current
                    DESCRIPTION "Group identifier. This variable returns the
                        integer corresponding to the current group identifier."
                    ::= { endptID 27 }
endptHTTPDIR    OBJECT-TYPE
                    SYNTAX      DisplayString
                    MAX-ACCESS  read-only
                    STATUS      current
                    DESCRIPTION "HTTP server Directory.  This variable returns
		the path used in formation of the URI for HTTP GET
                        operations."
                    ::= { endptID 28 }
endptHTTPSRVR   OBJECT-TYPE
                    SYNTAX      DisplayString
                    MAX-ACCESS  read-only
                    STATUS      current
                    DESCRIPTION "HTTP server IP addresses.  This variable
		returns a comma-separated list of HTTP server IP
		addresses available  for use, in dotted-decimal or
                        DNS format."
                    ::= { endptID 29 }
endptHTTPUSED   OBJECT-TYPE
                    SYNTAX      IpAddress
                    MAX-ACCESS  read-only
                    STATUS      current
                    DESCRIPTION "HTTP initialization server IP address.  This
		variable returns a 4-octet IP address for the HTTP server
		used during initialization (all zeroes if no server
		successfully used during initialization)."
                    ::= { endptID 30 }
endptICMPDU     OBJECT-TYPE
                    SYNTAX      INTEGER
                    MAX-ACCESS  read-only
                    STATUS      current
                    DESCRIPTION "Current value for ICMP Destination message handling.
                        This variable returns 0 if the telephone does not transmit ICMP
                        Destination Unreachable messages are not transmitted; 1 if such
                        messages are transmitted only in response to datagrams that
                        designate closed UDP ports or if the designated transport
                        protocol is not supported, and 2 if such such messages are
                        sent only in response to datagrams that designate closed UDP
                        or TCP ports or if the designated transport protocol is not
                        supported.  The default is 1."
                    ::= { endptID 31 }
endptICMPRED    OBJECT-TYPE
                    SYNTAX      INTEGER
                    MAX-ACCESS  read-only
                    STATUS      current
                    DESCRIPTION "Current value for ICMP Redirect message handling. This
                        variable returns 1 if received Redict messages are handled as
                        specified in RFC 1122, Sections 3.2.2.2 and 3.3.1.2, else 0.
		The default is 0."
                    ::= { endptID 32 }
endptIPADD      OBJECT-TYPE
                    SYNTAX      IpAddress
                    MAX-ACCESS  read-only
                    STATUS      current
                    DESCRIPTION "Endpoint IP address. This variable returns a 4-octet string
		specifying the endpoint's current IP address."
                    ::= { endptID 33 }
endptJMSEC      OBJECT-TYPE
                    SYNTAX      INTEGER
                    MAX-ACCESS  read-only
                    STATUS      current
                    DESCRIPTION "Jitter buffer size. This variable returns the number of
                        milliseconds of delay added to compensate for network jitter, from
                        0-300 milliseconds.  The default is 10."
                    ::= { endptID 34 }
endptL2Q        OBJECT-TYPE
                    SYNTAX      INTEGER
                    MAX-ACCESS  read-only
                    STATUS      current
                    DESCRIPTION "802.1Q framing flag. This variable returns 0
		if the Layer 2 802.1Q framing parameter is set to
		'auto', 1 if it is set to on/enabled, else 2 for
                        off/disabled."
                    ::= { endptID 35 }
endptL2QAUD     OBJECT-TYPE
                    SYNTAX      INTEGER
                    MAX-ACCESS  read-only
                    STATUS      current
                    DESCRIPTION "Audio priority. This variable returns an
                        integer between 0 and 7 inclusive specifying the
                        current Layer 2 802.1Q audio priority value."
                    ::= { endptID 36 }
endptL2QSIG     OBJECT-TYPE
                    SYNTAX      INTEGER
                    MAX-ACCESS  read-only
                    STATUS      current
                    DESCRIPTION "Signaling priority. This variable returns
                        an integer between 0 and 7 inclusive specifying the
                        current Layer 2 802.1Q signaling priority value."
                    ::= { endptID 37 }
endptL2QSTAT    OBJECT-TYPE
                    SYNTAX      INTEGER
                    MAX-ACCESS  read-only
                    STATUS      current
                    DESCRIPTION "802.1Q tagging flag. This variable returns 0
                        if the Layer 2 802.1Q tagging parameter is currently
                        OFF, else 1."
                    ::= { endptID 38 }
endptL2QVLAN    OBJECT-TYPE
                    SYNTAX      INTEGER
                    MAX-ACCESS  read-only
                    STATUS      current
                    DESCRIPTION "Administered Telephone VLAN Identifier. This variable
                        returns an integer between 0 and 4094 inclusive specifying the
                        administered Layer 2 802.1Q VLAN Identifier value."
                    ::= { endptID 39 }
endptL2QVLANINUSE OBJECT-TYPE
                    SYNTAX      INTEGER
                    MAX-ACCESS  read-only
                    STATUS      current
                    DESCRIPTION "Telephone VLAN Identifier in use. This variable
                        returns an integer between 0 and 4094 inclusive specifying
                        the current Layer 2 802.1Q VLAN Identifier value."
                    ::= { endptID 40 }
endptLOGSRVR    OBJECT-TYPE
                    SYNTAX      DisplayString
                    MAX-ACCESS  read-only
                    STATUS      current
                    DESCRIPTION "Event Log server address.  This variable
		returns at most one IP address, in dotted-decimal
		or DNS format, of the server to be used for event
		logging.  This function is intended for Avaya use,
                        in debugging if necessary."
                    ::= { endptID 41 }
endptMACADDR    OBJECT-TYPE
                    SYNTAX      DisplayString
                    MAX-ACCESS  read-only
                    STATUS      current
                    DESCRIPTION "MAC address. This variable returns a 6-octet
                        string specifying the endpoint's MAC address."
                    ::= { endptID 42 }
endptMODEL      OBJECT-TYPE
                    SYNTAX      DisplayString
                    MAX-ACCESS  read-only
                    STATUS      current
                    DESCRIPTION "Model identifier. This variable returns
		a string of up to 8 ASCII characters."
                    ::= { endptID 43 }
endptNETMASK    OBJECT-TYPE
                    SYNTAX      IpAddress
                    MAX-ACCESS  read-only
                    STATUS      current
                    DESCRIPTION "Subnet mask. This variable returns a
                        4-octet string specifying the subnet mask
                        currently in use."
                    ::= { endptID 44 }
endptPHONECC     OBJECT-TYPE
                    SYNTAX      DisplayString
                    MAX-ACCESS  read-only
                    STATUS      current
                    DESCRIPTION "Phone comcode. This variable returns a string
		of up to 9 numerical characters, specifying the comcode
                        of the endpoint itself."
                    ::= { endptID 45 }
endptPHONESN    OBJECT-TYPE
                    SYNTAX      DisplayString
                    MAX-ACCESS  read-only
                    STATUS      current
                    DESCRIPTION "Housing serial number. This variable
		returns a string of up to 18 ASCII characters,
		specifying the serial number on the outside
                        of the endpoint's housing."
                    ::= { endptID 46 }
endptPHY1DUPLEX OBJECT-TYPE
                    SYNTAX      INTEGER
                    MAX-ACCESS  read-only
                    STATUS      current
                    DESCRIPTION "Ethernet line interface duplex setting. This variable
		returns 1 if the interface is half-duplex and 2 if the interface
                        is full duplex."
                    ::= { endptID 47 }
endptPHY1SPEED  OBJECT-TYPE
                    SYNTAX      INTEGER
                    MAX-ACCESS  read-only
                    STATUS      current
                    DESCRIPTION "Ethernet interface speed. This variable
		returns a string specifying the endpoint's Ethernet
		interface speed in Mbps: '100' or '10'."
                    ::= { endptID 48 }
endptPHY1STAT   OBJECT-TYPE
                    SYNTAX      INTEGER
                    MAX-ACCESS  read-only
                    STATUS      current
                    DESCRIPTION "Ethernet line interface status.  This
		variable returns 0 if the endpoint's Ethernet line
                        interface is currently NOT enabled, 1 if the Ethernet
		line interface is currently for auto-negotiation, 2 for
		10Mbps half-duplex, 3 for 10Mbps full-duplex, 4 for
		100Mbps half-duplex, and 5 for 100Mbps full-duplex."
                    ::= { endptID 49 }
endptPHY2DUPLEX OBJECT-TYPE
                    SYNTAX      INTEGER
                    MAX-ACCESS  read-only
                    STATUS      current
                    DESCRIPTION "Secondary Ethernet interface duplex setting. This
		variable returns 0 if no link is established, 1 if the interface
                        is half-duplex,and 2 if the interface is full duplex."
                    ::= { endptID 50 }
endptPHY2PRIO   OBJECT-TYPE
                    SYNTAX      INTEGER
                    MAX-ACCESS  read-only
                    STATUS      current
                    DESCRIPTION "Secondary Ethernet interface Layer 2 priority.  This
		variable returns 0 through 7, and is used with endptVLANSEP.
                        The default is 0."
                    ::= { endptID 51 }
endptPHY2SPEED  OBJECT-TYPE
                    SYNTAX      INTEGER
                    MAX-ACCESS  read-only
                    STATUS      current
                    DESCRIPTION "Secondary Ethernet speed. This variable
		returns a string specifying the endpoint's Ethernet
		interface speed in Mbps: '100' or '10' or '0'."
                    ::= { endptID 52 }
endptPHY2STAT   OBJECT-TYPE
                    SYNTAX      INTEGER
                    MAX-ACCESS  read-only
                    STATUS      current
                    DESCRIPTION "Secondary Ethernet interface status.  This
		variable returns 0 if the endpoint's Secondary Ethernet
                        interface is currently NOT enabled, 1 if the Secondary Ethernet
                        interface is currently for auto-negotiation, 2 for
		10Mbps half-duplex, 3 for 10Mbps full-duplex, 4 for
		100Mbps half-duplex, and 5 for 100Mbps full-duplex."
                    ::= { endptID 53 }
endptPHY2VLAN   OBJECT-TYPE
                    SYNTAX      INTEGER
                    MAX-ACCESS  read-only
                    STATUS      current
                    DESCRIPTION "Secondary Ethernet interface VLAN ID.  This
		variable returns an integer between 0 and 4094 inclusive
                        specifying the current Layer 2 802.1Q VLAN Identifier
                        value for tagged frames received on the secondary Ethernet
                        interface while VLAN separation is enabled."
                    ::= { endptID 54 }
endptPORTAUD    OBJECT-TYPE
                    SYNTAX      INTEGER
                    MAX-ACCESS  read-only
                    STATUS      current
                    DESCRIPTION "Transport-layer audio port. This variable returns
                        the endpoint's transport layer port number for audio,
                        currently in use."
                    ::= { endptID 55 }
endptPROCPSWD   OBJECT-TYPE
                    SYNTAX      INTEGER
                    MAX-ACCESS  read-only
                    STATUS      current
                    DESCRIPTION "Local Procedure Password. This variable returns
                        0 if the Local Procedure Password is null, else 1."
                    ::= { endptID 56 }
endptPROCSTAT   OBJECT-TYPE
                    SYNTAX      INTEGER
                    MAX-ACCESS  read-only
                    STATUS      current
                    DESCRIPTION "Local Procedure flag. This variable returns 0 if
                        Local Procedures are currently allowed for this telephone,
                        else 1."
                    ::= { endptID 57 }
endptPWBCC      OBJECT-TYPE
                    SYNTAX      DisplayString
                    MAX-ACCESS  read-only
                    STATUS      current
                    DESCRIPTION "PWB comcode. This variable returns
                        a string of up to 9 numerical characters,
                        specifying the comcode or version number of
                        the printed wiring board of the endpoint."
                    ::= { endptID 58 }
endptPWBSN      OBJECT-TYPE
                    SYNTAX      DisplayString
                    MAX-ACCESS  read-only
                    STATUS      current
                    DESCRIPTION "PWB serial number. This variable
		returns a string of up to 18 ASCII characters,
		specifying the serial number on the endpoint's
		printed wiring board, or N/A if the board has
                        no serial number."
                    ::= { endptID 59 }
endptRTCPCONT   OBJECT-TYPE
                    SYNTAX      INTEGER
                    MAX-ACCESS  read-only
                    STATUS      current
                    DESCRIPTION "RTCP Control flag. This variable returns
                        0 if the RTCP control status is off/disabled, else 1."
                    ::= { endptID 60 }
endptRTCPFLOW   OBJECT-TYPE
                    SYNTAX      INTEGER
                    MAX-ACCESS  read-only
                    STATUS      current
                    DESCRIPTION "RTCP Flowrate. This variable returns
                        an integer between 5 and 30 inclusive specifying the
                        RTCP flowrate in milliseconds."
                    ::= { endptID 61 }
endptRTCPMON    OBJECT-TYPE
                    SYNTAX      IpAddress
                    MAX-ACCESS  read-only
                    STATUS      current
                    DESCRIPTION "RTCP Monitor address.  This variable returns a
                        4-octet string specifying the IP address of the RTCP
                        monitor currently in use."
                    ::= { endptID 62 }
endptRSVPCONT   OBJECT-TYPE
                    SYNTAX      INTEGER
                    MAX-ACCESS  read-only
                    STATUS      current
                    DESCRIPTION "RSVP Control flag. This variable returns
                        0 if the RSVP control status is off/disabled, else 1."
                    ::= { endptID 63 }
endptRSVPRFRSH  OBJECT-TYPE
                    SYNTAX      INTEGER
                    MAX-ACCESS  read-only
                    STATUS      current
                    DESCRIPTION "RSVP Refresh rate. This variable returns
                        an integer between 1 and 3600 inclusive specifying the
                        RSVP refresh rate in milliseconds."
                    ::= { endptID 64 }
endptRSVPRTRY   OBJECT-TYPE
                    SYNTAX      INTEGER
                    MAX-ACCESS  read-only
                    STATUS      current
                    DESCRIPTION "RSVP Failed Retry flag. This variable returns
                        0 if the RSVP Failed Retry Reservation control status is
                        off/disabled, else 1."
                    ::= { endptID 65 }
endptRSVPPROF   OBJECT-TYPE
                    SYNTAX      INTEGER
                    MAX-ACCESS  read-only
                    STATUS      current
                    DESCRIPTION "RSVP profile flag. This variable returns
                        0 if the RSVP profile is guaranteed, else 1 for controlled
                        load."
                    ::= { endptID 66 }
endptSIG	    OBJECT-TYPE
                    SYNTAX      INTEGER
                    MAX-ACCESS  read-only
                    STATUS      current
                    DESCRIPTION "Signaling protocol download flag. This variable
                        returns the integer corresponding to the current
                        signaling protocol."
                    ::= { endptID 67 }
endptSNMPADD    OBJECT-TYPE
                    SYNTAX      DisplayString
                    MAX-ACCESS  read-only
                    STATUS      current
                    DESCRIPTION "SNMP source addresses. This variable returns
		one or more allowable source IP addresses for SNMP queries,
                        in dotted decimal or DNS format."
                    ::= { endptID 68 }
endptSTATIC     OBJECT-TYPE
                    SYNTAX      INTEGER
                    MAX-ACCESS  read-only
                    STATUS      current
                    DESCRIPTION "Static programming override flag. This variable
                        returns the integer corresponding to the current level of
		 override permissions for static programming."
                    ::= { endptID 69 }
endptTLSSRVR    OBJECT-TYPE
                    SYNTAX      DisplayString
                    MAX-ACCESS  read-only
                    STATUS      current
                    DESCRIPTION "TLS server addresses. This variable returns zero
		or more Transport Layer Security server addresses for
                        software download, in dotted decimal or DNS format."
                    ::= { endptID 70 }
endptTLSUSED    OBJECT-TYPE
                    SYNTAX      IpAddress
                    MAX-ACCESS  read-only
                    STATUS      current
                    DESCRIPTION "TLS server address used. This variable returns the
		TLS server address from TLSSRVR used, if any, during
		initialization, or all zeroes if no TLS server was used."
                    ::= { endptID 71 }
endptTMSEC      OBJECT-TYPE
                    SYNTAX      INTEGER
                    MAX-ACCESS  read-only
                    STATUS      current
                    DESCRIPTION "Transmit buffer fill level. This variable returns
                        the transmit buffer minimum fill level, in msec, currently
                        in use."
                    ::= { endptID 72 }
endptVLANLIST    OBJECT-TYPE
                    SYNTAX      DisplayString
                    MAX-ACCESS  read-only
                    STATUS      current
                    DESCRIPTION "VLAN ID list. This variable returns a list of
                        zero or more VLAN IDs."
                    ::= { endptID 73 }
endptVLANSEP    OBJECT-TYPE
                    SYNTAX      INTEGER
                    MAX-ACCESS  read-only
                    STATUS      current
                    DESCRIPTION "VLAN separation value. This variable returns 0
		 if frames received on the secondary Ethernet interface are
                         unchanged before forwarding; else 1, which is the default."
                    ::= { endptID 74 }
endptFONT       OBJECT-TYPE
                    SYNTAX      DisplayString
                    MAX-ACCESS  read-only
                    STATUS      current
                    DESCRIPTION "Font file identifier. This variable returns a text string
		with the name of the font file stored in the phone, if any."
                    ::= { endptID 75 }
endptLANGFILES   OBJECT-TYPE
                    SYNTAX      DisplayString
                    MAX-ACCESS  read-only
                    STATUS      current
                    DESCRIPTION "Language file list. This variable returns a comma-separated
		text string listing the language files stored in the phone,
		if any."
                    ::= { endptID 76 }
endptPHNEMERGNUM   OBJECT-TYPE
                    SYNTAX      DisplayString
                    MAX-ACCESS  read-only
                    STATUS      current
                    DESCRIPTION "Emergency Number. This variable returns a telephone number
		to be dialed when an Emergency softkey is pressed."
                    ::= { endptID 77}
endptAUDIOENV OBJECT-TYPE
                    SYNTAX      INTEGER
                    MAX-ACCESS  read-only
                    STATUS      current
                    DESCRIPTION "Audio Environment parameter. This variable returns the current value
		of AUDIOENV."
                    ::= { endptID 78}
endptAUDIOSTHD OBJECT-TYPE
                    SYNTAX      INTEGER
                    MAX-ACCESS  read-only
                    STATUS      current
                    DESCRIPTION "Audio Handset Sidetone parameter. This variable returns the current
		value  of AUDIOSTHD."
                    ::= { endptID 79}
endptAUDIOSTHS OBJECT-TYPE
                    SYNTAX      INTEGER
                    MAX-ACCESS  read-only
                    STATUS      current
                    DESCRIPTION "Audio Headset Sidetone parameter. This variable returns the current
		value of AUDIOSTHS."
                    ::= { endptID 80}
endptBRAUTH  OBJECT-TYPE
                    SYNTAX      INTEGER
                    MAX-ACCESS  read-only
                    STATUS      current
                    DESCRIPTION "Backup/Restore authentication control. This variable returns  0
	       if the call server IP address and telephone's registration password is NOT
	      not included as credentials in an Authentication request-header; 1 (the default) if that
	      data is included and the telephone will accept the server's digital certificate if signed by
	      Avaya, or 2 if that data is included and the telephone will accept the server's
	      digital certificate if signed by Avaya or a trusted certificate based on TRUSTCERTS."
                    ::= { endptID 81}
endptDHCPINUSE  OBJECT-TYPE
                    SYNTAX      IpAddress
                    MAX-ACCESS  read-only
                    STATUS      current
                    DESCRIPTION "IP address of DHCP server from which phone's IP address was obtained.  This
		variable returns four zeroes by default or when the telephone is manually programmed."
                    ::= { endptID 82 }
endptDHCPLEASEEXP  OBJECT-TYPE
                    SYNTAX      Integer32
                    MAX-ACCESS  read-only
                    STATUS      current
                    DESCRIPTION "DHCP lease expiration. This variable returns the time (in seconds) remaining
		until the expiration of the current DHCP lease; or 0 if the lease has expired."
                   ::= { endptID 83 }
endptDHCPSTD  OBJECT-TYPE
                    SYNTAX      INTEGER
                    MAX-ACCESS  read-only
                    STATUS      current
                    DESCRIPTION "DHCP compliance flag. This variable returns  0 (the default) if the
	      telephone ignores the DHCP standard and continues using its IP address after its
	      lease has expired, assuming the DHCP server cannot be reached.  The value 1 is returned
	      if the DHCP standard is followed and the telephone stops using its IP address (IPADD)."
                    ::= { endptID 84}
endptDHCPT1REM  OBJECT-TYPE
                    SYNTAX      Integer32
                    MAX-ACCESS  read-only
                    STATUS      current
                    DESCRIPTION "DHCP lease renewal expiration. This variable returns the time (in seconds) until
		the start of IP address lease renewal, -1 if the lease is infinite, or 0 if the timer has expired."
                   ::= { endptID 85 }
endptDHCPT2REM  OBJECT-TYPE
                    SYNTAX      Integer32
                    MAX-ACCESS  read-only
                    STATUS      current
                    DESCRIPTION "DHCP lease rebinding expiration. This variable returns the time (in seconds) remaining
		until the start of IP address lease renewal, -1 if the lease is infinite, or 0 if the timer has expired."
                   ::= { endptID 86 }
endptDOT1XSTAT  OBJECT-TYPE
                    SYNTAX      INTEGER
                    MAX-ACCESS  read-only
                    STATUS      current
                    DESCRIPTION "802.1X Supplicant status. This variable returns  0 if 802.1X Supplicant mode is
	      Disabled; 1 (the default) if the supplicant mode is set to Unicast-only, and 2 if the supplicant
	      mode is set to Unicast/Multicast."
                    ::= { endptID 87}
endptHTTPPORT  OBJECT-TYPE
                    SYNTAX      INTEGER
                    MAX-ACCESS  read-only
                    STATUS      current
                    DESCRIPTION "HTTP port number. This variable returns the TCP port number used for HTTP file downloading."
                    ::= { endptID 88}
endptTLSDIR  OBJECT-TYPE
                    SYNTAX      DisplayString
                    MAX-ACCESS  read-only
                    STATUS      current
                    DESCRIPTION "TLS Server Directory.  This variable returns the path that
		 is prepended to all file names used in HTTPS GET operations."
                    ::= { endptID 89}
endptTLSPORT  OBJECT-TYPE
                    SYNTAX      DisplayString
                    MAX-ACCESS  read-only
                    STATUS      current
                    DESCRIPTION "TLS server port number. This variable returns
                        the TCP port number used for HTTPS file downloading."
                    ::= { endptID 90}
endptMEMHEAPFREE  OBJECT-TYPE
                    SYNTAX      Integer32
                    MAX-ACCESS  read-only
                    STATUS      current
                    DESCRIPTION "Heap allocation. This variable returns the number of bytes of
		volatile memory currently allocated for, but unused by, the Heap."
                   ::= { endptID 91}
endptSSONCONTENT  OBJECT-TYPE
                    SYNTAX      DisplayString
                    MAX-ACCESS  read-only
                    STATUS      current
                    DESCRIPTION "SSON Content. This variable returns the data portion of the
		DHCP site-specific option designated by NVSSON, exactly as received."
                    ::= { endptID 92}
endptTLSSRVRID  OBJECT-TYPE
                    SYNTAX      INTEGER
                    MAX-ACCESS  read-only
                    STATUS      current
                    DESCRIPTION "TLS server ID flag. This variable returns 1 if the TLS server
		identity is to be checked against its certificate, otherwise 0."
                    ::= { endptID 93}
endptTRUSTCERTS  OBJECT-TYPE
                    SYNTAX      DisplayString
                    MAX-ACCESS  read-only
                    STATUS      current
                    DESCRIPTION "Trusted Certificates list. This variable returns the current
		 trusted certificates to be downloaded; 0-255 ASCII
		characters, 0 or more filenames or URLs separated by commas."
                    ::= { endptID 94}
endptVOXFILES  OBJECT-TYPE
                    SYNTAX      DisplayString
                    MAX-ACCESS  read-only
                    STATUS      current
                    DESCRIPTION "Voice language files list. This variable returns the current
		 list of voice langauge files to be downloaded; 0-255 ASCII
		characters, 0 or more filenames separated by commas."
                    ::= { endptID 95}
endptGRATARP      OBJECT-TYPE
                    SYNTAX      INTEGER
                    MAX-ACCESS  read-only
                    STATUS      current
                    DESCRIPTION "Gratuitous ARP flag. This variable returns 1 oif gratuitous ARP messages
		are to be process; else 0."
                    ::= { endptID 96 }


endptNVM        OBJECT IDENTIFIER ::= { avaya96xxMIB 2 }
endptNVAGCHAND  OBJECT-TYPE
                    SYNTAX      INTEGER
                    MAX-ACCESS  read-only
                    STATUS      current
                    DESCRIPTION "Non-Volatile Memory (NVM)Handset AGC status. This
                        variable returns 1 if the endpoint's handset Automatic
		Gain Control capability in NVM is currently enabled, else 0."
                    ::= { endptNVM 1 }
endptNVAGCHEAD  OBJECT-TYPE
                    SYNTAX      INTEGER
                    MAX-ACCESS  read-only
                    STATUS      current
                    DESCRIPTION "NVM Headset AGC status. This variable returns 1
                        if the endpoint's headset Automatic Gain Control capability
		in NVM is currently enabled, else 0."
                    ::= { endptNVM 2 }
endptNVAGCSPKR    OBJECT-TYPE
                    SYNTAX      INTEGER
                    MAX-ACCESS  read-only
                    STATUS      current
                    DESCRIPTION "Speakerphone AGC status. This variable returns 1
                        if the endpoint's speakerphone Automatic Gain Control
                        capability in NVM is currently enabled, else 0."
                    ::= { endptNVM 3 }
endptNVALERT    OBJECT-TYPE
                    SYNTAX      INTEGER
                    MAX-ACCESS  read-only
                    STATUS      obsolete
                    DESCRIPTION "Alerting Mode flag. This variable returns 1 if
		the alerting mode setting in non-volatile memory is
		enabled, else 0."
                    ::= { endptNVM 4 }
endptNVAUTH     OBJECT-TYPE
                    SYNTAX      INTEGER
                    MAX-ACCESS  read-only
                    STATUS      current
                    DESCRIPTION "Script file authentication flag. This variable
		returns 1 if the endpoint must authenticate script files,
                      	else 0."
                    ::= { endptNVM 5 }
endptNVBRIGHTNESS OBJECT-TYPE
                    SYNTAX      INTEGER
                    MAX-ACCESS  read-only
                    STATUS      current
                    DESCRIPTION "Display Brightness setting. This variable returns
		the value of the display contrast setting in non-volatile
		memory.  Range is 0-5, with 4 the default."
                    ::= { endptNVM 6 }
endptNVCALLSRVR OBJECT-TYPE
                    SYNTAX      IpAddress
                    MAX-ACCESS  read-only
                    STATUS      obsolete
                    DESCRIPTION "NVM IP address of call server if manually entered.
                        	Default is four zeroes."
                    ::= { endptNVM 7 }
endptNVCHADDR   OBJECT-TYPE
                    SYNTAX      Integer32
                    MAX-ACCESS  read-only
                    STATUS      current
                    DESCRIPTION "Manually-entered DHCP chaddr value. This
		variable returns a manually-entered value for the DHCP
		chaddr field as stored in non-volatile memory, if any.
		A Hexadecimal value with range of 0 (the default) to
                        999999."
                    ::= { endptNVM 8 }
endptNVCONTRAST OBJECT-TYPE
                    SYNTAX      INTEGER
                    MAX-ACCESS  read-only
                    STATUS      current
                    DESCRIPTION "Display Contrast setting. This variable returns
		the value of the display contrast setting in non-volatile
		memory.  Range is 0-15, with 8 the default."
                    ::= { endptNVM 9 }
endptNVFILESRVR OBJECT-TYPE
                    SYNTAX      IpAddress
                    MAX-ACCESS  read-only
                    STATUS      obsolete
                    DESCRIPTION "NVM File server address. This variable returns
                        a 4-octet string specifying the IP address of the file
                        server as stored in NVM."
                    ::= { endptNVM 10 }
endptNVGIPADD   OBJECT-TYPE
                    SYNTAX      IpAddress
                    MAX-ACCESS  read-only
                    STATUS      current
                    DESCRIPTION "NVM Router address.  This variable returns a 4-
                        octet string specifying the IP address of the router as
                        stored in NVM."
                    ::= { endptNVM 11 }
endptNVIPADD    OBJECT-TYPE
                    SYNTAX      IpAddress
                    MAX-ACCESS  read-only
                    STATUS      current
                    DESCRIPTION "NVM IP address. This variable returns a 4-octet
                        string specifying the endpoint's IP address stored in
                        NVM."
                    ::= { endptNVM 12 }
endptNVL2Q      OBJECT-TYPE
                    SYNTAX      INTEGER
                    MAX-ACCESS  read-only
                    STATUS      current
                    DESCRIPTION "NVM 802.1Q flag. This variable returns 0 if
		the Layer 2 802.1Q framing parameter in NVM is set to
		'auto', 1 if it is set to on/enabled, else 2 for
                        off/disabled."
                    ::= { endptNVM 13 }
endptNVL2QVLAN  OBJECT-TYPE
                    SYNTAX      INTEGER
                    MAX-ACCESS  read-only
                    STATUS      current
                    DESCRIPTION "NVM VLAN Identifier. This variable returns an
                        integer between 0 and 4094 inclusive specifying the Layer
                        2 802.1Q VLAN Identifier value stored in NVM."
                    ::= { endptNVM 14 }
endptNVLOGSTAT  OBJECT-TYPE
                    SYNTAX      INTEGER
                    MAX-ACCESS  read-only
                    STATUS      current
                    DESCRIPTION "NVM Event Log flag. This variable returns 0 if the
                        endpoint's event logging capability in NVM is currently
                        NOT enabled, else 1."
                    ::= { endptNVM 15 }
endptNVNETMASK  OBJECT-TYPE
                    SYNTAX      IpAddress
                    MAX-ACCESS  read-only
                    STATUS      current
                    DESCRIPTION "NVM Subnet mask. This variable returns a 4-octet
                        string specifying the subnet mask as stored in NVM."
                    ::= { endptNVM 16 }
endptNVPHY1STAT OBJECT-TYPE
                    SYNTAX      INTEGER
                    MAX-ACCESS  read-only
                    STATUS      current
                    DESCRIPTION "NVM Ethernet line interface status.  This
                        variable returns 0 if the endpoint's Ethernet line
                        interface in NVM iscurrently NOT enabled, 1 if the
                        Ethernet line interface in NVM is currently for
                        auto-negotiation, 2 for 10Mbps half-duplex, 3 for
                        10Mbps full-duplex, 4 for 100Mbps half-duplex, and
                        5 for 100Mbps full-duplex."
                    ::= { endptNVM 17 }
endptNVPHY2STAT OBJECT-TYPE
                    SYNTAX      INTEGER
                    MAX-ACCESS  read-only
                    STATUS      current
                    DESCRIPTION "NVM Secondary Ethernet interface setting.  This
		variable returns 0 if the endpoint's secondary Ethernet
		interface in NVM is currently NOT enabled(or none exists),
		1 if the hub is set for auto-negotiation, 2 for 10Mbps
		half-duplex, 3 for 10Mbps full-duplex, 4 for 100Mbps
                        half-duplex, and 5 for 100Mbps full-duplex."
                    ::= { endptNVM 18 }
endptNVSSON     OBJECT-TYPE
                    SYNTAX      INTEGER
                    MAX-ACCESS  read-only
                    STATUS      current
                    DESCRIPTION "NVM Site-specific option number. This variable
                        returns an integer between 128 and 254 inclusive,
                        specifying the SSON stored in NVM.  The default is 176."
                    ::= { endptNVM 19 }
endptNVVLANTEST    OBJECT-TYPE
                    SYNTAX      INTEGER
                    MAX-ACCESS  read-only
                    STATUS      current
                    DESCRIPTION "NVM VLAN pause parameter. This variable returns
                        the number of seconds stored in NVM for the endppoint to
                        wait for a DHCPOFFER message when using a non-zero VLAN ID.
                        Valid values are integers from 0 to 999 inclusive."
                    ::= { endptNVM 20 }
endptNVLANGFILE OBJECT-TYPE
                    SYNTAX      DisplayString
                    MAX-ACCESS  read-only
                    STATUS      current
                    DESCRIPTION "Language file. This variable returns the name
                        of the language file in non-volatile memory."
                    ::= { endptNVM 21 }
endptNVTRUSTLIST OBJECT-TYPE
                    SYNTAX      DisplayString
                    MAX-ACCESS  read-only
                    STATUS      current
                    DESCRIPTION "List of trusted certificates. This variable returns 0-255
	      ASCII characters: 0 or more filenames or URLs separated by commas
	     and without intervening spaces, containing the list of
                        downloaded trusted certificates in non-volatile memory."
                    ::= { endptNVM 22 }
endptNVVOXFILE OBJECT-TYPE
                    SYNTAX      DisplayString
                    MAX-ACCESS  read-only
                    STATUS      current
                    DESCRIPTION "Voice language file. This variable returns 0-32
	      ASCII characters: 0 or 1filename, identifying the voice language file,
                         if any, in non-volatile memory."
                    ::= { endptNVM 23 }
endptNVRINGTONESTYLE 	OBJECT-TYPE
                    SYNTAX      INTEGER
                    MAX-ACCESS  read-only
                    STATUS      current
                    DESCRIPTION "Ringing style identifier.  This variable returns
                        the number of seconds stored in NVM for the endppoint to
                        wait for a DHCPOFFER message when using a non-zero VLAN ID.
                        Valid values are integers from 0 to 999 inclusive."
                    ::= { endptNVM 24 }
endptNVSBM24BRIGHTNESS1	OBJECT-TYPE
                    SYNTAX      INTEGER
                    MAX-ACCESS  read-only
                    STATUS      current
                    DESCRIPTION "SBM24 backlight level. This variable returns
                        the value of the backlight brightness for the first SBM24 attached,
                        to the telephone, if any.  Valid values are integers from 1 to 5 inclusive."
                    ::= { endptNVM 25 }
endptNVSBM24BRIGHTNESS2	OBJECT-TYPE
                    SYNTAX      INTEGER
                    MAX-ACCESS  read-only
                    STATUS      current
                    DESCRIPTION "SBM24 backlight level. This variable returns
                        the value of the backlight brightness for the second SBM24 attached,
                        to the telephone, if any.  Valid values are integers from 1 to 5 inclusive."
                    ::= { endptNVM 26 }
endptNVSBM24BRIGHTNESS3	OBJECT-TYPE
                    SYNTAX      INTEGER
                    MAX-ACCESS  read-only
                    STATUS      current
                    DESCRIPTION "SBM24 backlight level. This variable returns
                        the value of the backlight brightness for the third SBM24 attached,
                        to the telephone, if any.  Valid values are integers from 1 to 5 inclusive."
                    ::= { endptNVM 27 }


endptMaintenance        OBJECT IDENTIFIER ::= { avaya96xxMIB 3 }
endptAPPSTAT    OBJECT-TYPE
                    SYNTAX      INTEGER
                    MAX-ACCESS  read-only
                    STATUS      current
                    DESCRIPTION "Application download flag. This variable
	      returns '0' if the most recent attempt to download
 	     and store an application file was successful. This
	      variable returns '1' if the most recent attempt to
	     download an application file was successful but the
	     file was not successfully stored in NVM.  This variable
	     returns '2' if the most recent attempt to download an
	     application file was NOT successful."
	::= { endptMaintenance 1 }
endptUPGRADESTAT OBJECT-TYPE
                    SYNTAX      INTEGER
                    MAX-ACCESS  read-only
                    STATUS      current
                    DESCRIPTION "Script loading status flag. This variable
                        returns '0' if a 96xxupgrade.txt file was successfully
                        obtained and interpreted since the last power-up or reset.
                        This variable returns '1' if the file was successfully
                        obtained but NOT successfully interpreted since the last
                        power-up or reset. This variable returns '2' if the file
                        was NOT successfully obtained since the last
                        power-up or reset."
                    ::= { endptMaintenance 2 }
endptRecentLog  OBJECT-TYPE
	  SYNTAX SEQUENCE OF EndptRecentLogEntry
	  MAX-ACCESS	not-accessible
	  STATUS		current
	  DESCRIPTION	"Each entry is one of up to 75 syslog event
		messages added since last reset or power-up, each of
		which has severity code less than the value of NVLOGLOCAL.
		Entries are in chronological order, oldest first."
	  ::= { endptMaintenance 3 }
endptRecentLogEntry	OBJECT-TYPE
	  SYNTAX EndptRecentLogEntry
	  MAX-ACCESS	not-accessible
	  STATUS		current
	  DESCRIPTION	"Each entry is one of up to 75 syslog event
		messages added since last reset or power-up, each of
		which has severity code less than the value of NVLOGLOCAL.
		Entries are in chronological order, oldest first."
	  INDEX		{ endptRecentLogText }
	  ::= { endptRecentLog 1 }
EndptRecentLogEntry	    ::=
	SEQUENCE {
		endptRecentLogText
		DisplayString
	}
endptRecentLogText	OBJECT-TYPE
	  SYNTAX		DisplayString
	  MAX-ACCESS	read-only
	  STATUS		current
	  DESCRIPTION	"Syslog event message."
	  ::= { endptRecentLogEntry 1 }
endptResetLog   OBJECT-TYPE
	  SYNTAX SEQUENCE OF EndptResetLogEntry
	  MAX-ACCESS	not-accessible
	  STATUS		current
	  DESCRIPTION	"Each entry is one of up to 75 syslog event
		messages added before the last reset or power-up, each of
		which has severity code less than the value of NVLOGLOCAL.
		Entries are in chronological order, oldest first."
	  ::= { endptMaintenance 4 }
endptResetLogEntry	OBJECT-TYPE
	  SYNTAX EndptResetLogEntry
	  MAX-ACCESS	not-accessible
	  STATUS		current
	  DESCRIPTION	"Each entry is one of up to 75 syslog event
		messages added before the last reset or power-up, each of
		which has severity code less than the value of NVLOGLOCAL.
		Entries are in chronological order, oldest first."
	  INDEX		{ endptResetLogText }
	  ::= { endptResetLog 1 }
EndptResetLogEntry	    ::=
	SEQUENCE {
		endptResetLogText
		DisplayString
	}
endptResetLogText	OBJECT-TYPE
	  SYNTAX		DisplayString
	  MAX-ACCESS	read-only
	  STATUS		current
	  DESCRIPTION	"Syslog event message."
	  ::= { endptResetLogEntry 1 }


endptApps    OBJECT IDENTIFIER ::= { avaya96xxMIB 4 }
endptAUDIOPATH  OBJECT-TYPE
                    SYNTAX      INTEGER
                    MAX-ACCESS  read-only
                    STATUS      current
                    DESCRIPTION "User audio path.  This variable returns 0 if the
	     telephone does not support a 2-way speaker or does not
                        have a headset jack; 1 if the user audio path is with the
                        speakerphone, and 2 if the user audio path is with the headset."
                    ::= { endptApps 1 }
endptENHDIALSTAT OBJECT-TYPE
                    SYNTAX      INTEGER
                    MAX-ACCESS  read-only
                    STATUS      current
                    DESCRIPTION "Enhanced Local Dialing status.  This variable
		returns 0 if the Enhanced Local Dialing status is
                     	off/disabled, else 1."
                    ::= { endptApps 2 }
endptSUBSCRIBELIST    OBJECT-TYPE
                    SYNTAX      DisplayString
                    MAX-ACCESS  read-only
                    STATUS      current
                    DESCRIPTION "96xx Web push subscription list. This
                       variable returns a string containing one or more fully
                       qualified URLs to which the phone's Browser application
                       subscribes for potential pushed content."
                    ::= { endptApps 3 }
endptTPSLIST    OBJECT-TYPE
                    SYNTAX      DisplayString
                    MAX-ACCESS  read-only
                    STATUS      current
                    DESCRIPTION "96xxWeb Trusted Push Server list. This
                       variable returns a string containing one or more domains
                       and paths in DNS format, used to determine for
                       validation of push requests."
                    ::= { endptApps 4 }
endptWMLEXCEPT  OBJECT-TYPE
                    SYNTAX      DisplayString
                    MAX-ACCESS  read-only
                    STATUS      current
                    DESCRIPTION "96xx Web Proxy Server Exception List. This
                       variable returns a string specifying a list of one or
                       more HTTP proxy server Exception domains, separated by
                       commas with no intervening spaces, up to 127 total
	       characters. Used by the 96xx Browser application."
                    ::= { endptApps 5 }
endptWMLHOME    OBJECT-TYPE
                    SYNTAX      DisplayString
                    MAX-ACCESS  read-only
                    STATUS      current
                    DESCRIPTION "96xx Web application URL. This variable returns
                        a URL of the Home page for the 96xx Browser application."
                    ::= { endptApps 6 }
endptWMLIDLETIME    OBJECT-TYPE
                    SYNTAX      INTEGER
                    MAX-ACCESS  read-only
                    STATUS      current
                    DESCRIPTION "Web Idle Timer. This variable returns the number
                       of minutes, from 1 to 60 inclusive, of idle activity on the
                       telephone before the Web Idle Timer URI is displayed."
                    ::= { endptApps 7 }
endptWMLIDLEURI    OBJECT-TYPE
                    SYNTAX      DisplayString
                    MAX-ACCESS  read-only
                    STATUS      current
                    DESCRIPTION "Web Idle Timer URI. This variable returns the
                        URI of the WML page displayed after the 96xxWeb
                        Idle Timer expires."
                    ::= { endptApps 8 }
endptWMLPORT    OBJECT-TYPE
                    SYNTAX      INTEGER
                    MAX-ACCESS  read-only
                    STATUS      current
                    DESCRIPTION "96xx Browser application TCP port. This variable
                        returns an integer specifying the TCP port most recently
                        used for the HTTP proxy server.  Used by the 96xx
                        Browser application."
                    ::= { endptApps 9 }
endptWMLPROXY   OBJECT-TYPE
                    SYNTAX      IpAddress
                    MAX-ACCESS  read-only
                    STATUS      current
                    DESCRIPTION "96xx Web Proxy Server. This variable returns
                        an IP addresses, in dotted-decimal or DNS format, of an
                        HTTP proxy server.  Used by the 96xx Browser application."
                    ::= { endptApps 10 }
endptGUESTDURATION  OBJECT-TYPE
                    SYNTAX      INTEGER
                    MAX-ACCESS  read-only
                    STATUS      current
                    DESCRIPTION "96xx Guest Login Duration. This variable
                        returns an integer specifying the number of hours from 1-12
                        for the Guest Login duration.  The default is 2."
                    ::= { endptApps 11 }
endptGUESTLOGINSTAT  OBJECT-TYPE
                    SYNTAX      INTEGER
                    MAX-ACCESS  read-only
                    STATUS      current
                    DESCRIPTION "96xx Guest Login permission flag.  This variable
                        returns 1 if the user is allowed to initiate a Guest Login,
                        otherwise 0."
                    ::= { endptApps 12 }
endptGUESTWARNING  OBJECT-TYPE
                    SYNTAX      INTEGER
                    MAX-ACCESS  read-only
                    STATUS      current
                    DESCRIPTION "96xx Guest Login Warning interval.  This variable
                        returns an integer specifying the number of minutes from 1-15
                        before the expiration of a Guest Login that a warnign screen
	     is displayed.  The default is 5."
                    ::= { endptApps 13 }
endptPUSHCAP  OBJECT-TYPE
                    SYNTAX      DisplayString
                    MAX-ACCESS  read-only
                    STATUS      current
                    DESCRIPTION "Push capabilities. This variable returns a
                       4-digit integer specifying the phone administration for audio transmit,
                        audi receive, display (web), and Top Line pushes, respectively.
                        The valid digits are 0 (Disabled), 1 (barge-in onl ypushes of the given
	      type Enabled) and 2 (both barge-in and normal pushes of the given
	      type Enabled).  The default is 2222."
                    ::= { endptApps 14 }
endptPUSHPORT  OBJECT-TYPE
                    SYNTAX      INTEGER
                    MAX-ACCESS  read-only
                    STATUS      current
                    DESCRIPTION "Push listening port. This variable returns an
                       integer specifying the TCP listening port most recently
                        used for the HTTP server.."
                    ::= { endptApps 15 }
endptQKLOGINSTAT  OBJECT-TYPE
                    SYNTAX      INTEGER
                    MAX-ACCESS  read-only
                    STATUS      current
                    DESCRIPTION "Quick Login permission flag. This variable
                        returns 1 (the default) if users are permitted to use the # button
                        to use a previous login and password during registration, else 0."
                    ::= { endptApps 16 }
endptSCREENSAVER  OBJECT-TYPE
                    SYNTAX      DisplayString
                    MAX-ACCESS  read-only
                    STATUS      current
                    DESCRIPTION "Custom screen saver URL.  This variable returns
	      a filename from 0-32 characters that specifies an image displayed
                        in lieu of the Avaya screen saver."
                    ::= {endptApps 17 }
endptWMLSMALL    OBJECT-TYPE
                    SYNTAX      DisplayString
                    MAX-ACCESS  read-only
                    STATUS      current
                    DESCRIPTION "9610 Web application URL. This variable returns
                        a URL of the Home page for the 9610 Browser application."
                    ::= { endptApps 18 }
endptCLDELCALLBK  OBJECT-TYPE
                    SYNTAX      INTEGER
                    MAX-ACCESS  read-only
                    STATUS      current
                    DESCRIPTION "Call Log Callback Deletion flag. This variable
                        returns 1 if a Missed Call Log entry is deleted from the Call Log
	     if the user Calls that entry from the Call Log, else 0 (the default) ."
                    ::= { endptApps 19 }
endptFBONCASCREEN  OBJECT-TYPE
                    SYNTAX      INTEGER
                    MAX-ACCESS  read-only
                    STATUS      current
                    DESCRIPTION "Feature Buttons on Call Appearance List flag. This
                        variable returns 1 if administered feature buttons are allowed to be
                        listed on the Call Appearance Screen, else 0 (the default) ."
                    ::= { endptApps 20 }
endptLOGBACKUP  OBJECT-TYPE
                    SYNTAX      INTEGER
                    MAX-ACCESS  read-only
                    STATUS      current
                    DESCRIPTION "Call Log backup permission flag. This variable
                        returns 1 (the default) if the telephone is to automatically store and
	     retrieve a file of Call Log entries, else 0."
                    ::= { endptApps 21 }
endptLOGMISSEDONCE  OBJECT-TYPE
                    SYNTAX      INTEGER
                    MAX-ACCESS  read-only
                    STATUS      current
                    DESCRIPTION "Missed Call Log Counter flag. This variable
                        returns 1 if the telephone keeps only one Missed Call Log record for
                        a given Name and Number, as well as a counter of Missed calls from
	     that Name and Number, else 0 (the default)."
                    ::= { endptApps 22 }
endptLOGUNSEEN  OBJECT-TYPE
                    SYNTAX      INTEGER
                    MAX-ACCESS  read-only
                    STATUS      current
                    DESCRIPTION "Log redirected calls permission flag. This variable
                        returns 1 if the telephone is to create Call Log entries for calls that
                        are redirected from the physical telephone, else 0 (the default)."
                    ::= { endptApps 23 }
endptAPPSTATVALUE  OBJECT-TYPE
                    SYNTAX      INTEGER
                    MAX-ACCESS  read-only
                    STATUS      current
                    DESCRIPTION "Applications permission status.  This variable returns the
	     current value of the APPSTAT parameter, which can restrict the
                        availability of some of the telephone applications, as documented in
                        the 9600 Series Admin Guide."
                    ::= { endptApps 24 }
endptOPSTAT  OBJECT-TYPE
                    SYNTAX      INTEGER
                    MAX-ACCESS  read-only
                    STATUS      current
                    DESCRIPTION "Options permission status.  This variable returns the
	     current value of the OPSTAT parameter, which can restrict the
                        availability of some of the telephone options, as documented in
                        the 9600 Series Admin Guide."
                    ::= { endptApps 25}
endptOPSTAT2  OBJECT-TYPE
                    SYNTAX      INTEGER
                    MAX-ACCESS  read-only
                    STATUS      current
                    DESCRIPTION "Options permission override parameter.  This variable returns
	     the current value of the OPSTAT2 parameter, which can override specific
                        functionality of the OPSTAT parameter, as documented in the 9600
                        Series Admin Guide."
                    ::= { endptApps 26 }


endptAdjuncts   OBJECT IDENTIFIER ::= { avaya96xxMIB 5 }
endptBMODS      OBJECT-TYPE
                    SYNTAX      INTEGER
                    MAX-ACCESS  read-only
                    STATUS      current
                    DESCRIPTION "Button Module interface usage. This variable returns
                        the number of devicess attached (or daisy-chained) to the
                         endpoint through the button module interface."
                    ::= { endptAdjuncts 1}
endptBTADHWVER  OBJECT-TYPE
                    SYNTAX      DisplayString
                    MAX-ACCESS  read-only
                    STATUS      current
                    DESCRIPTION "Bluetooth adapter hardware version. This variable returns
                        the hardware version of an attached Bluetooth Adapter, if any.
	     If none, null is returned."
                    ::= {endptAdjuncts 2}
endptBTADSTAT  OBJECT-TYPE
                    SYNTAX      INTEGER
                    MAX-ACCESS  read-only
                    STATUS      current
                    DESCRIPTION "Bluetooth adapter presence. This variable returns
                        1 if the presence. of a Bluetooth adapter is detected, else 0."
                    ::= { endptAdjuncts 3}
endptBTADSWVER  OBJECT-TYPE
                    SYNTAX      DisplayString
                    MAX-ACCESS  read-only
                    STATUS      current
                    DESCRIPTION "Bluetooth adapter software version. This variable returns
                        the software version of an attached Bluetooth Adapter, if any.
	     If none, null is returned."
                    ::= {endptAdjuncts 4}
endptGIGEHWVER  OBJECT-TYPE
                    SYNTAX      DisplayString
                    MAX-ACCESS  read-only
                    STATUS      current
                    DESCRIPTION "GigE adapter hardware version. This variable returns
                        the hardware version of an attached GigE Adapter, if any.
	     If none, null is returned."
                    ::= {endptAdjuncts 5}
endptGIGESTAT  OBJECT-TYPE
                    SYNTAX      INTEGER
                    MAX-ACCESS  read-only
                    STATUS      current
                    DESCRIPTION "GigE adapter presence. This variable returns
                        1 if the presence. of a GigE adapter is detected, else 0."
                    ::= { endptAdjuncts 6}
endptGIGESWVER  OBJECT-TYPE
                    SYNTAX      DisplayString
                    MAX-ACCESS  read-only
                    STATUS      current
                    DESCRIPTION "GigE adapter software version. This variable returns
                        the software version of an attached GigE Adapter, if any.
	     If none, null is returned."
                    ::= {endptAdjuncts 7}
endptSBM1HWVER  OBJECT-TYPE
                    SYNTAX      DisplayString
                    MAX-ACCESS  read-only
                    STATUS      current
                    DESCRIPTION "SBM #1 hardware version. This variable returns
                        the hardware version of the first button module, if any.
	     If none, null is returned."
                    ::= {endptAdjuncts 8}
endptSBM1SWVER  OBJECT-TYPE
                    SYNTAX      DisplayString
                    MAX-ACCESS  read-only
                    STATUS      current
                    DESCRIPTION "SBM #1 software version. This variable returns
                        the software version of the first button module, if any.
	     If none, null is returned."
                    ::= {endptAdjuncts 9}
endptSBM2HWVER  OBJECT-TYPE
                    SYNTAX      DisplayString
                    MAX-ACCESS  read-only
                    STATUS      current
                    DESCRIPTION "SBM #2 hardware version. This variable returns
                        the hardware version of the second button module, if any.
	     If none, null is returned."
                    ::= {endptAdjuncts 10}
endptSBM2SWVER  OBJECT-TYPE
                    SYNTAX      DisplayString
                    MAX-ACCESS  read-only
                    STATUS      current
                    DESCRIPTION "SBM #2 software version. This variable returns
                        the software version of the second button module, if any."
                    ::= {endptAdjuncts 11}
endptSBM3HWVER  OBJECT-TYPE
                    SYNTAX      DisplayString
                    MAX-ACCESS  read-only
                    STATUS      current
                    DESCRIPTION "SBM #3 hardware version. This variable returns
                        the hardware version of the third button module, if any.
	     If none, null is returned."
                    ::= {endptAdjuncts 12}
endptSBM3SWVER  OBJECT-TYPE
                    SYNTAX      DisplayString
                    MAX-ACCESS  read-only
                    STATUS      current
                    DESCRIPTION "SBM #3 software version. This variable returns
                        the software version of the third button module, if any."
                    ::= {endptAdjuncts 13}
endptSBMSTAT  OBJECT-TYPE
                    SYNTAX      INTEGER
                    MAX-ACCESS  read-only
                    STATUS      current
                    DESCRIPTION "Button Modules attached. This variable returns
                        the number of Button Modules attached (or daisy-chained)
                        to the endpoint."
                    ::= { endptAdjuncts 14}
endptUSBPOWER  OBJECT-TYPE
                    SYNTAX      INTEGER
                    MAX-ACCESS  read-only
                    STATUS      current
                    DESCRIPTION "USB Power Provision. This variable returns 0 if
                        the telephone is to disable USB power, 1 if USB power is enabled
	     only if the telephone is Aux powered, 2 if USB power is enabled
	     regardless of the power source, or 3 if USB power is enabled if
	     the telephone is Aux powered or PoE Class 3."
                    ::= { endptAdjuncts 15}


endptH323   OBJECT IDENTIFIER ::= { avaya96xxMIB 6 }
endptMCIPADD    OBJECT-TYPE
                    SYNTAX      DisplayString
                    MAX-ACCESS  read-only
                    STATUS      current
                    DESCRIPTION "List of call server addresses.  This
		variable returns a sequence of IP addresses, in
		dotted-decimal or DNS format and separated by
		commas, of call server IP addresses available
                        for use."
                    ::= { endptH323 1 }
endptGKINUSE    OBJECT-TYPE
                    SYNTAX      IpAddress
                    MAX-ACCESS  read-only
                    STATUS      current
                    DESCRIPTION "Gatekeeper in use address.  This variable
                        returns a 4-octet string specifying the IP
                        address of the gatekeeper currently in use."
                    ::= { endptH323 2 }
endptNVPHONEXT      OBJECT-TYPE
                    SYNTAX      DisplayString
                    MAX-ACCESS  read-only
                    STATUS      current
                    DESCRIPTION "Endpoint's phone extension.  This variable
		returns a text string identifying the endpoint's extension,
		in free text format.  The default value is NULL. "
                    ::= { endptH323 3 }
endptRASGkList	OBJECT-TYPE
		  SYNTAX SEQUENCE OF EndptRASGkEntry
		  MAX-ACCESS	not-accessible
		  STATUS		current
		  DESCRIPTION	"Each entry is one of up to 75 gatekeeper
			addresses in dotted-decimal or DNS format, as downloaded from
			the call server during RAS.  Entries are listed in the order received."
			  ::= { endptH323 4 }
endptRASGkEntry   OBJECT-TYPE
		  SYNTAX EndptRASGkEntry
		  MAX-ACCESS	not-accessible
		  STATUS		current
		  DESCRIPTION	"Each entry is one of up to 75 gatekeeper
			addresses in dotted-decimal or DNS format, as downloaded from
			the call server during RAS.  Entries are listed in the order  received."
		  INDEX		{ endptRASGkEntryData}
		  ::= { endptRASGkList 1 }
EndptRASGkEntry	  ::=
		SEQUENCE {
				endptRASGkEntryData
				DisplayString
				}
endptRASGkEntryData OBJECT-TYPE
		  SYNTAX		DisplayString
		  MAX-ACCESS	read-only
		  STATUS		current
		  DESCRIPTION	"Data for an individual RAS-provided Gatekeeper."
		  ::= { endptRASGkEntry 1 }
endptREREGISTER OBJECT-TYPE
                   SYNTAX      INTEGER
                   MAX-ACCESS  read-only
                   STATUS      current
                   DESCRIPTION "Reregistration Timer value. This variable returns
                       the number of minutes from 1 to 120 inclusive the telephone
                       waits between re-registration attempts if unnamed registration
                       is not in effect.  The default is 20 minutes."
                   ::= { endptH323 5 }

endptSERVICESTAT OBJECT-TYPE
                   SYNTAX      INTEGER
                   MAX-ACCESS  read-only
                   STATUS      current
                   DESCRIPTION "Status of phone in service. This variable returns
                       0 if the phone is not in service nor is attempting to register,
                       1 if the telephone has failed Gatekeeper Discovery, 2 if the
                       telephone has successfully completed Gatekeeper Discovery but
                       has not successfully completed registration, 3 if the telephone
                       has successfully registered but does not have a TCP connection,
                       and 4 if the telephone is registered and has a TCP connection."
                   ::= { endptH323 6 }
endptGKTCPPORT  OBJECT-TYPE
                    SYNTAX      INTEGER
                    MAX-ACCESS  read-only
                    STATUS      current
                    DESCRIPTION "Gatekeeper Port. This variable returns 0 if the
                        telephone is not currently registered, otherwise it returns the
                       TCP port number on the gatekeeper with which the telephone
	    has a signaling connection established."
                    ::= { endptH323 7 }

endptCERT   OBJECT IDENTIFIER ::= { avaya96xxMIB 8 }
endptMYCERTCAID    OBJECT-TYPE
                    SYNTAX      DisplayString
                    MAX-ACCESS  read-only
                    STATUS      current
                    DESCRIPTION "Certificate Authority ID.  This variable returns the
		Certificate Authority Identifier to be used in a certificate request."
                    ::= { endptCERT 1 }
endptMYCERTCN    OBJECT-TYPE
                    SYNTAX      DisplayString
                    MAX-ACCESS  read-only
                    STATUS      current
                    DESCRIPTION "Certificate Common Name.  This variable returns the
		Common Name of the Subject of a certificate request."
                    ::= { endptCERT 2 }
endptMYCERTDN    OBJECT-TYPE
                    SYNTAX      DisplayString
                    MAX-ACCESS  read-only
                    STATUS      current
                    DESCRIPTION "Certificate Distinguished Name. This variable returns additional information (sometimes
		common country and organizational information) that, together with the Common
		Name, is used to create a Distinguished Name."
                    ::= { endptCERT 3 }
endptMYCERTKEYLEN    OBJECT-TYPE
                    SYNTAX      INTEGER
                    MAX-ACCESS  read-only
                    STATUS      current
                    DESCRIPTION "Key length. This variable returns the bit length of the public and private keys generated
		for a certificate request"
                    ::= { endptCERT 4 }
endptMYCERTRENEW    OBJECT-TYPE
                    SYNTAX      INTEGER
                    MAX-ACCESS  read-only
                    STATUS      current
                    DESCRIPTION "Certificate Renewal interval. This variable returns the percentage of a certificate Validity
		interval after which renewal procedures will be initiated."
                    ::= { endptCERT 5 }
endptMYCERTURL    OBJECT-TYPE
                    SYNTAX      DisplayString
                    MAX-ACCESS  read-only
                    STATUS      current
                    DESCRIPTION "SCEP URL.  This variable returns the URL to be used
		to contact an SCEP server."
                    ::= { endptCERT 6 }
endptMYCERTWAIT    OBJECT-TYPE
                    SYNTAX      INTEGER
                    MAX-ACCESS  read-only
                    STATUS      current
                    DESCRIPTION "Certificate wait flag. This variable returns 0 if the
		telephone will wait until a pending certificate request is
		complete, else 1 if it will periodically check in the background."
                    ::= { endptCERT 7 }


endptVPN   OBJECT IDENTIFIER ::= { avaya96xxMIB 9 }
endptALWCLRNOTIFY    OBJECT-TYPE
                    SYNTAX      INTEGER
                    MAX-ACCESS  read-only
                    STATUS      current
                    DESCRIPTION "ISAKP Notification flag.  This variable returns 1 if
		unencrypted ISAKMP Notification Payloads will be accepted, else 0."
                    ::= { endptVPN 1 }
endptAUTHTYPE    OBJECT-TYPE
                    SYNTAX      INTEGER
                    MAX-ACCESS  read-only
                    STATUS      current
                    DESCRIPTION "VPN Authentication Method.  This variable returns 3 if the VPN authentication
		method is Pre-Shared Key (PSK); 4 if the method is PSK with XAUTH, 5 if the method is RSA
		signatures with XAUTH, 6 if the method is Hybrid XAUTH, and 7 if the method is RSA
		signatures."
                    ::= { endptVPN 2 }
endptCFGPROF   OBJECT-TYPE
                    SYNTAX      INTEGER
                    MAX-ACCESS  read-only
                    STATUS      current
                    DESCRIPTION "VPN Configuration Profile.  This variable returns 2 if the VPN Configuration Profile
		is based on Checkpoint Security Gateway, 3 if the profile is based on Cisco PSK with XAUTH,
		5 if the profile is based on Juniper PSK with XAUTH, 6 if the profile is based on Generic PSK,
		8 if the profile is based on Cisco Cert. with XAUTH, 9 if the profile is based on Juniper Cert.
		with XAUTH, or 11 if the profile is based on Nortel Contivity."
                    ::= { endptVPN 3 }
endptCOPYTOS    OBJECT-TYPE
                    SYNTAX      INTEGER
                    MAX-ACCESS  read-only
                    STATUS      current
                    DESCRIPTION "TOS Copy flag.  This variable returns 1 if the value of the TOS bits will be copied
		from the inner IP header to the outer IP header, else this variable returns 2 and the TOS
		bits of the outer IP header will be set to 0."
                    ::= { endptVPN 4 }
endptDHCPSRVR    OBJECT-TYPE
                    SYNTAX      DisplayString
                    MAX-ACCESS  read-only
                    STATUS      current
                    DESCRIPTION "List of DHCP server addresses.  This variable returns a sequence of zero or more
		IP addresses, in dotted-decimal format and separated by commas, of enterprise DHCP
		servers from which configuration parameters may be requested through a VPN tunnel
		via a DHCPINFORM message."
                    ::= { endptVPN 5 }
endptDROPCLEAR    OBJECT-TYPE
                    SYNTAX      INTEGER
                    MAX-ACCESS  read-only
                    STATUS      current
                    DESCRIPTION "Clear IPSec packet treatment.  This variable returns 1 if received unencrypted
		(clear) IPsec packets are to be dropped, else 0"
                    ::= { endptVPN 6 }
endptENCAPS    OBJECT-TYPE
                    SYNTAX      INTEGER
                    MAX-ACCESS  read-only
                    STATUS      current
                    DESCRIPTION "Encapsulation Port Numbers.  This variable returns 0 if negotiation of NAT
		traversal is as specified in IETF RFC 3947 (except that IKE negotiation begins with a
		source port of 2070 and that source port continues to be used unless the source and
		destination port numbers are changed to 4500, 1 if UDP encapsulation of the inner IP
		layer will not be provided and negotiation of NAT traversal as specified in IETF RFC 3947
		is not supported, 2 if  negotiation of NAT traversal is as specified in IETF RFC 3947
		(except IKE uses source port 2070 and the source and destination port numbers are not
		subsequently changed), or 4 if  negotiation of NAT traversal is as specified in IETF RFC 3947."
                    ::= { endptVPN 7 }
endptEXTDNSSRVR    OBJECT-TYPE
                    SYNTAX      DisplayString
                    MAX-ACCESS  read-only
                    STATUS      current
                    DESCRIPTION "List of external DNS server addresses.  This variable returns a sequence of IP
		addresses, in dotted-decimal format and separated by commas, of DNS servers available for
		use outside of the VPN tunnel when in VPN mode."
                    ::= { endptVPN 8 }
endptEXTGIPADD    OBJECT-TYPE
                    SYNTAX      DisplayString
                    MAX-ACCESS  read-only
                    STATUS      current
                    DESCRIPTION "List of external router addresses.  This variable returns a sequence of IP addresses,
		in dotted-decimal format and separated by commas, of routers available for use outside of
		the VPN tunnel when in VPN mode."
                    ::= { endptVPN 9 }
endptEXTIPADD    OBJECT-TYPE
                    SYNTAX      DisplayString
                    MAX-ACCESS  read-only
                    STATUS      current
                    DESCRIPTION "Endpoint External IP address. This variable returns a 4-octet string specifying the
		endpoint's current outer IP address when in VPN mode."
                    ::= { endptVPN 10 }
endptEXTNETMASK    OBJECT-TYPE
                    SYNTAX      DisplayString
                    MAX-ACCESS  read-only
                    STATUS      current
                    DESCRIPTION "External Subnet mask. This variable returns a  4-octet string specifying the subnet
		mask to be used outside of the VPN tunnel when in VPN mode."
                    ::= { endptVPN 11 }
endptIKECONFIGMODE    OBJECT-TYPE
                    SYNTAX      INTEGER
                    MAX-ACCESS  read-only
                    STATUS      current
                    DESCRIPTION "IKE Configuration flag.  This variable returns 1 if the ISAKMP configuration method
		to be used, else 2.."
                    ::= { endptVPN 12 }
endptIKEDH    OBJECT-TYPE
                    SYNTAX      INTEGER
                    MAX-ACCESS  read-only
                    STATUS      current
                    DESCRIPTION "In-Use Diffie-Hellman Group for IKE SA.  This variable returns the negotiated IKE Phase 1
		DH Group number."
                    ::= { endptVPN 13 }
endptIKEDHGRP    OBJECT-TYPE
                    SYNTAX      INTEGER
                    MAX-ACCESS  read-only
                    STATUS      current
                    DESCRIPTION "Proposed Diffie-Hellman Group for IKE SA.  This variable returns 1 if the DH Group
		Description proposed for IKE Phase 1 is the First Oakley Group, 2 if the proposal is for the
		Second Oakley Group, 5 if the proposal is for the 1536-bit MODP Group, 14 if the proposal is
		for the 2048-bit MODP Group, and 15 if the proposal is for the 3072-bit MODP Group, else 0."
                    ::= { endptVPN 14 }
endptIKEID    OBJECT-TYPE
                    SYNTAX      DisplayString
                    MAX-ACCESS  read-only
                    STATUS      current
                    DESCRIPTION "IKE Phase 1 identity,  This variable returns the identity (also known as in XAUTH as
		group name) used during IKE Phase 1 negotiation."
                    ::= { endptVPN 15 }
endptIKEIDTYPE    OBJECT-TYPE
                    SYNTAX      INTEGER
                    MAX-ACCESS  read-only
                    STATUS      current
                    DESCRIPTION "IKE SA identification type.  This varable returns 1 if the Identification Type used for
		IKE Phase 1 is ID_IPV4_ADDR, 2 if the ID Type is ID_FQDN, 3 if the ID Type is ID_USER_FQDN,
		9 if the ID Type is ID_DER_ASN1_DN, and 11 if the ID Type is ID_KEY_ID."
                    ::= { endptVPN 16 }
endptIKEOVERTCP    OBJECT-TYPE
                    SYNTAX      INTEGER
                    MAX-ACCESS  read-only
                    STATUS      current
                    DESCRIPTION "IKE TCP usage policy. This variable returns 0 if IKE is only to use UDP, 1 if TCP is to be
		tried after an IKE times out using UDP, or 2 if only TCP is to be used."
                    ::= { endptVPN 17 }
endptIKEP1AUTH    OBJECT-TYPE
                    SYNTAX      INTEGER
                    MAX-ACCESS  read-only
                    STATUS      current
                    DESCRIPTION "In-Use IKE Phase 1 authentication algorithm. This variable returns 1 if MD5 was negotiated,
		and 2 if SHA was negotiated."
                    ::= { endptVPN 18 }
endptIKEP1AUTHALG    OBJECT-TYPE
                    SYNTAX      INTEGER
                    MAX-ACCESS  read-only
                    STATUS      current
                    DESCRIPTION "Proposed IKE Phase 1 authentication algorithm.  This variable returns 0 if if either hash
		algorithm is acceptable for IKE Phase 1, 1 if MD5 is proposed, or 2 if SHA is proposed:."
                    ::= { endptVPN 19 }
endptIKEP1ENC    OBJECT-TYPE
                    SYNTAX      INTEGER
                    MAX-ACCESS  read-only
                    STATUS      current
                    DESCRIPTION "In-Use IKE Phase 1 encryption algorithm. This variable returns 1 if AES-CBC-128 was
		negotiated, 2 if 3DES-CBC was negotiated, 3 if DES-CBC was negotiated, 4 if AES-CBC-192 was
		negotiated, or 5 if AES-CBC-256 was negotiated."
                    ::= { endptVPN 20 }
endptIKEP1ENCALG    OBJECT-TYPE
                    SYNTAX      INTEGER
                    MAX-ACCESS  read-only
                    STATUS      current
                    DESCRIPTION "IKE Phase 1 encryption algorithm.  This variable returns.0 if any encryption algoithm
		is acceptable for IKE Phase 1, 1 if AES-CBC-128 is proposed, 2 if 3DES-CBC is proposed, 3 if
		DES-CBC is proposed, 4 if AES-CBC-192  is proposed, and 5 if AES-CBC-256 is proposed."
                    ::= { endptVPN 21 }
endptIKEP1LIFESEC    OBJECT-TYPE
                    SYNTAX      Integer32
                    MAX-ACCESS  read-only
                    STATUS      current
                    DESCRIPTION "IKE Security Association lifetime.  This variable returns the proposed number of seconds
		for the SA Life Duration for IKE Phase 1."
                    ::= { endptVPN 22 }
endptIKEP2AUTH    OBJECT-TYPE
                    SYNTAX      INTEGER
                    MAX-ACCESS  read-only
                    STATUS      current
                    DESCRIPTION "In-Use IKE Phase 2 authentication algorithm. This variable returns 1 if MD5 was
		negotiated, and 2 if SHA was negotiated."
                    ::= { endptVPN 23 }
endptIKEP2AUTHALG    OBJECT-TYPE
                    SYNTAX      INTEGER
                    MAX-ACCESS  read-only
                    STATUS      current
                    DESCRIPTION "IKE Phase 2 authentication algorithm.  This variable returns 0 if either hash algorithm
		is acceptable for IKE Phase 1, 1 if MD5 is proposed, or 2 if SHA is proposed:."
                    ::= { endptVPN 24 }
endptIKEP2ENC    OBJECT-TYPE
                    SYNTAX      INTEGER
                    MAX-ACCESS  read-only
                    STATUS      current
                    DESCRIPTION "In-Use IKE Phase 2 encryption algorithm. This variable returns 1 if AES-CBC-128 was
		negotiated, 2 if 3DES-CBC was negotiated, 3 if DES-CBC was negotiated, 4 if AES-CBC-192
		was negotiated, 5 if AES-CBC-256 was negotiated, or 6 if NULL encryption was negotiated."
                    ::= { endptVPN 25 }
endptIKEP2ENCALG    OBJECT-TYPE
                    SYNTAX      INTEGER
                    MAX-ACCESS  read-only
                    STATUS      current
                    DESCRIPTION "IKE Phase 1 encryption algorithm.  This variable returns.0 if any encryption algoithm
		is acceptable for IKE Phase 1, 1 if AES-CBC-128 is proposed, 2 if 3DES-CBC is proposed, 3 if
		DES-CBC is proposed, 4 if AES-CBC-192  is proposed, 5 if AES-CBC-256 is proposed, and 6 if
		NULLencryption is proposed."
                    ::= { endptVPN 26 }
endptIKEP2LIFESEC    OBJECT-TYPE
                    SYNTAX      Integer32
                    MAX-ACCESS  read-only
                    STATUS      current
                    DESCRIPTION "IPsec Security Association lifetime.  This variable returns the proposed number of seconds
		for the SA Life Duration for IKE Phase 2."
                    ::= { endptVPN 27 }
endptIKESALIFEKB    OBJECT-TYPE
                    SYNTAX      Integer32
                    MAX-ACCESS  read-only
                    STATUS      current
                    DESCRIPTION "IKE Security Association KB Lifetime.  This variable returns the IKE SA lifetime in kilobytes."
                    ::= { endptVPN 28 }
endptIKESALIFESEC    OBJECT-TYPE
                    SYNTAX      Integer32
                    MAX-ACCESS  read-only
                    STATUS      current
                    DESCRIPTION "IKE Security Association time Lifetime.  This variable returns the IKE SA lifetime in seconds."
                    ::= { endptVPN 29 }
endptIKETRANSPORT    OBJECT-TYPE
                    SYNTAX      INTEGER
                    MAX-ACCESS  read-only
                    STATUS      current
                    DESCRIPTION "In-Use IKE transport protocol.  This variable returns 0 if IKE is not in use, 1 if UDP is being
		used for IKE transport, or 2 if TCP is being used for IKE transport."
                    ::= { endptVPN 30 }
endptIKEXCHGMODE    OBJECT-TYPE
                    SYNTAX      INTEGER
                    MAX-ACCESS  read-only
                    STATUS      current
                    DESCRIPTION "IKE Phase 1 negotiation mode.  This variable returns 1 if the IKE Phase 1 exchange usesd is
		Aggressive Mode, else 2 for Main Mode. "
                    ::= { endptVPN 31 }
endptIPSECSALIFEKB    OBJECT-TYPE
                    SYNTAX      Integer32
                    MAX-ACCESS  read-only
                    STATUS      current
                    DESCRIPTION "IPsec Security Association KB Lifetime.  This variable returns the IPsec SA lifetime in
		kilobytes."
                    ::= { endptVPN 32 }
endptIPSECSALIFESEC    OBJECT-TYPE
                    SYNTAX      Integer32
                    MAX-ACCESS  read-only
                    STATUS      current
                    DESCRIPTION "IPsec Security Association time Lifetime.  This variable returns the IPsec SA lifetime
		in seconds."
                    ::= { endptVPN 33 }
endptIPSECSUBNET    OBJECT-TYPE
                    SYNTAX      DisplayString
                    MAX-ACCESS  read-only
                    STATUS      current
                    DESCRIPTION "VPN Tunnel IP Address ranges.  This variable returns the IP address ranges that will use
		the VPN tunnel, with 0.0.0.0/0 meaning all IP addresses."
                    ::= { endptVPN 34 }
endptNORTELAUTH    OBJECT-TYPE
                    SYNTAX      INTEGER
                    MAX-ACCESS  read-only
                    STATUS      current
                    DESCRIPTION "Nortel gateway authentication method.  If Nortel gateway user authentication is to
		be used, this variable returns 1 if a local username and password are to be used; 2 if a RADIUS
		username and password are to be used, 3 if RADIUS SecurID is to be used, and 4 if RADIUS Axent
		is to be used.."
                    ::= { endptVPN 35 }
endptPFSDH    OBJECT-TYPE
                    SYNTAX      INTEGER
                    MAX-ACCESS  read-only
                    STATUS      current
                    DESCRIPTION "In-Use Diffie-Hellman Group for IPsec SA.  This variable returns the negotiated IKE PFS
		DH Group number."
                    ::= { endptVPN 36 }
endptPFSDHGRP    OBJECT-TYPE
                    SYNTAX      INTEGER
                    MAX-ACCESS  read-only
                    STATUS      current
                    DESCRIPTION "Diffie-Hellman Group for IPsec SA.  This variable returns 1 if the DH Group Description
		proposed for IPSec SA is the First Oakley Group, 2 if the proposal is for the Second Oakley Group,
		5 if the proposal is for the 1536-bit MODP Group, 14 if the proposal is for the 2048-bit MODP Group,
		and 15 if the proposal is for the 3072-bit MODP Group, else 0."
                    ::= { endptVPN 37 }
endptPSWDTYPE    OBJECT-TYPE
                    SYNTAX      INTEGER
                    MAX-ACCESS  read-only
                    STATUS      current
                    DESCRIPTION "VPN Password Permissions.  This variable returns 1 if the password may be alphanumeric
		and is to be stored in non-volatile memory as the value of NVVPNPSWD, 2 if the password may be
		alphanumeric and is to be stored in volatile memory that will be cleared when the telephone resets,
		3 if the password may be numeric-only and is to be stored in volatile memory that will be cleared
		mmediately after the first time the password is used (this is for use with numeric-only one-time token
		devices), 4 if the password may be alphanumeric and is to be stored in volatile memory that will be
		cleared immediately after the first time the password is used, and 5 if the password may be
		alphanumeric and is to be stored in volatile memory that is cleared when the user invokes VPN
		Sleep Mode and when the telephone resets."
                    ::= { endptVPN 38 }
endptSGINUSE    OBJECT-TYPE
                    SYNTAX      DisplayString
                    MAX-ACCESS  read-only
                    STATUS      current
                    DESCRIPTION "VPN Security Gateway address.  This variable returns a 4-octet string specifying the IP
		address of the VPN Security Gateway in use, else 0.0.0.0."
                    ::= { endptVPN 39 }
endptSGIP    OBJECT-TYPE
                    SYNTAX      DisplayString
                    MAX-ACCESS  read-only
                    STATUS      current
                    DESCRIPTION "VPN Security Gateway list.  This variable returns the list of VPN security gateway IP
		addresses available to the telephone."
                    ::= { endptVPN 40}
endptSGVENDOR    OBJECT-TYPE
                    SYNTAX      INTEGER
                    MAX-ACCESS  read-only
                    STATUS      current
                    DESCRIPTION "VPN Security Gateway Vendor.  This variable returns 1 if the IKE implementation matches
		Juniper/NetScreen, 2 if it matches Cisco, 3 if it matches Check Point/Nokia, 5 if it matches
		Nortel, otherwise 4."
                    ::= { endptVPN 41 }
endptSGVERSION    OBJECT-TYPE
                    SYNTAX      DisplayString
                    MAX-ACCESS  read-only
                    STATUS      current
                    DESCRIPTION "Security Gateway Version.  This variable returns the version information, if any,
		of the Security Gateway with wich the telephone has a VPN tunnel established, else NULL."
                    ::= { endptVPN 42 }
endptVPNMODE    OBJECT-TYPE
                    SYNTAX      INTEGER
                    MAX-ACCESS  read-only
                    STATUS      current
                    DESCRIPTION "VPN Support Specification.  This variable returns 1 if VPN functionality is enabled, else 0."
                    ::= { endptVPN 43 }
endptVPNUSER    OBJECT-TYPE
                    SYNTAX      DisplayString
                    MAX-ACCESS  read-only
                    STATUS      current
                    DESCRIPTION "VPN User Name.  This variable returns the user name to be used during authentication. "
                    ::= { endptVPN 44 }
endptVPNUSERTYPE    OBJECT-TYPE
                    SYNTAX      INTEGER
                    MAX-ACCESS  read-only
                    STATUS      current
                    DESCRIPTION "VPN User Name Permissions.  This variable returns 1 if  the user can change the VPN username,
		else 0."
                    ::= { endptVPN 45 }
endptXAUTH    OBJECT-TYPE
                    SYNTAX      INTEGER
                    MAX-ACCESS  read-only
                    STATUS      current
                    DESCRIPTION "XAUTH status. This variable returns 2 if XAUTH is disabled, else 1."
                    ::= { endptVPN 46 }

END
