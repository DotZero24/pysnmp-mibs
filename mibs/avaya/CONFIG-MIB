-- ==========================================================
--
-- MIB      : Config                              Avaya Inc.
--
-- Version  : 10.3.44                             19 Nov 2008
--
-- ==========================================================
--
-- ==========================================================
--  SourceSafe Version Information:
--  $Revision: 59 $
--  Check in $Date: 11/19/08 7:03p $
--  $Author: Sbiton $
--  $Archive: /MIBs/Version 1.0/Source/Lannet/CONFIG-MIB.MY $
-- ==========================================================
--
-- Copyright 1999-2007 Avaya Inc.
-- All Rights Reserved.
--
-- Reproduction of this document is authorized on condition
-- that the foregoing copyright notice is included.
--
-- This Avaya SNMP Management Information Base
-- Specification embodies Avaya confidential and
-- proprietary intellectual property.  Avaya Inc. retains all
-- title and ownership in the Specification, including any revisions
--
-- It is Avaya intent to encourage the widespread use of this
-- Specification in connection with the management of Avaya
-- products.
--
-- Avaya grants vendors, end-users, and other interested parties
-- a non-exclusive license to use this Specification in connection
-- with the management of Avaya products.
--
-- This Specification is supplied "as is," and Avaya makes
-- no warranty, either express or implied, as to the use,
-- operation, condition, or performance of the Specification.
--
-- ==========================================================
--
-- Version 10.3.45
--  19 Nov June 2008
--   1.) Change Distributed Office names to Communication Manager Branch Edition.
--   2.) Change i40-14A to i40-A14 and G250-14A to G250-A14
-- Shlomi Biton
--
--
-- Version 10.3.44
--  02 Nov June 2008
--   1.) Add chApplicationBladeStatus mib item to indicate that application blade as S8300D
--       undergoes reset phase and now it is up again.
-- Shlomi Biton
--
--
-- Version 10.3.43
-- 11 Sep 2008
-- 1. Add new enumerations for the G430 H.248.
--	a. chHwType - avayaG430(41).
--  b. genGroupType - avayaG430-motherboard(5014),
-- 2. Update genGroupType of avayaG430-motherboard(5013)
--    to avayaDistributedOfficeG430-motherboard(5013).
-- 3. Update genPortType - 	avayaG450-10or100or1000TPort(4014),
--    						avayaG450-10or100TPort(4015),
--     						avayaG430-10or100Tport(4017),
-- 							avayaG430-10or100TPortAndInPWR(4019),
-- TO:
--  						avayaDistributedOfficeG450-10or100or1000TPort(4014),
--    						avayaDistributedOfficeG450-10or100TPort(4015),
--     						avayaDistributedOfficeG430-10or100Tport(4017),
-- 							avayaDistributedOfficeG430-10or100TPortAndInPWR(4019),
-- 4. Add new enumerations to genPortType:
--    avayaG430-10or100Tport(4020),
--    avayaG430-10or100TPortAndInPWR(4021)
-- Shlomi Biton
--
-- Version 10.3.42
-- 21 May 2008
-- 1. Update Product Name G450.
-- Shlomi Biton
--
-- Version 10.3.41
-- 27 Mar 2008
-- 1. Update Products Names G430 and G450 in the relevant MIBs.
-- Shlomi Biton
--
-- Version 10.3.40
-- 31 January 2008
-- 1. Add the following values to genGroupType
--		a. avayaDistributedOfficei40VirtualApplicationServer(4211)
--    	b. avayaDistributedOfficei120VirtualApplicationServer(4212)
--    	c. avayaDistributedOfficeVenusVirtualApplicationServer(4214)
--    	d.  avayaDistributedOfficeJupiterVirtualApplicationServer(4215)
-- 2. Add Venus and Jupiter enumerations to chHwType.
-- 		a. avayaDistributedOfficeiJupiter(38)
-- 		b. avayaDistributedOfficeiVenus(40)
-- 3. Add Venus and Jupiter enumerations to genGroupType.
--		a. avayaJupiter-motherboard(5011)
--		b. avayaVenus-motherboard(5013)
-- 4. Add Venus and Jupiter enumerations to genPortType.
-- 		a. avayaJupiter-10or100or1000TPort(4014)
--		b. avayaJupiter-10or100TPort(4015)
--		c. avayaVenus-10or100Tport(4017)
-- 5. Add MM118 enumerations to genGroupType.
--		a. avayaMM118(4113)
-- 6. Add MM118 enumerations to genPortType.
-- 		a. avayaVenus-10or100TPortAndInPWR(4019)
-- Shlomi Biton
--
-- Version 10.3.39
-- 02 October 2007
-- 1. Add avayaG250-14A(28) to chHWType.
-- 2. Add avayaG250-14A-motherboard(2854) and avayaG250-int-analog-6L8T(4010)
--	  to genGroupType.
-- 3. Change avayaG450-Supervisor(4050) to avayaG450-Mainboard(4050) in genGroupType.
-- Shlomi Biton
--
-- Version 10.3.38
-- 08 July 2007
-- 1. Add avayaDistributedOfficei40-14A(37) to chHWType.
-- 2. Add avayai40-14A-motherboard(5009) and avayai40-14A-int-analog-6L8T(5010)
--	  to genGroupType.
-- Shlomi Biton
--
-- Version 10.3.37
-- 28 May 2007
-- 1. Add avayaTRM480(36) to chHWType.
-- 2. Add avayaTRM480(5100) to genGroupType.
-- Shlomi Biton
--
-- Version 10.3.36
-- 26 Feb 2007
-- Use shorter enumerations for ADO devices in genGroupType and in genPortType.
-- Shlomi Biton
--
-- Version 10.3.35
-- 06 Feb 2007
-- Add the following enumerations to genGroupType:
-- 1. avayaDistributedOfficei40-Analog-motherboard(5000),
-- 2. avayaDistributedOfficei40-BRI-motherboard(5001),
-- 3. avayaDistributedOfficei40-DS1-motherboard(5002),
-- 4. avayaDistributedOfficei120(5003),
-- 5. avayaDistributedOfficei120-int-analog(5004),
-- 6. avayaDistributedOfficei40-int-analog-2L4T(5005),
-- 7. avayaDistributedOfficei40-int-analog-2L1T(5006),
-- 8. avayaDistributedOfficei40-int-BRI(5007),
-- 9. avayaDistributedOfficei40-int-DS1(5008)
-- Add the following enumerations to genPortType:
-- 1. avayaDistributedOfficei40-10or100TPortAndInPWR(4000),
-- 2. avayaDistributedOfficei40-10or100TPort(4001),
-- 3. avayaDistributedOfficei120-LAG(4002),
-- 4. avayaDistributedOfficei120-1000SX-SFP(4003),
-- 5. avayaDistributedOfficei120-1000LX-SFP(4004),
-- 6. avayaDistributedOfficei120-LAG100(4005),
-- 7. avayaDistributedOfficei120-LAG1000(4006),
-- 8. avayaDistributedOfficei120-100or1000TPort(4007),
-- 9. avayaDistributedOfficei120-10or100TPort(4008),
-- 10. avayaDistributedOfficei120-SFP-NotPresent(4009),
-- 11. avayaDistributedOfficei120-SFP-NotSupported(4010),
-- 12. avayaDistributedOfficei120-10or100TPortAndInPWR(4011),
-- 13. avayaDistributedOfficei120-1000TX-SFP(4012),
-- 14. avayaDistributedOfficei120-10or100or1000TPort(4013)
-- Shlomi Biton
--
--
-- Version 10.3.34
-- 14 Jan 2007
-- Add chHwType for G450
-- Meir Deutsch
--
-- RCS
-- Version 10.3.33
-- 01 Jan 2007
--   1.) Rename avayaLSB(4210) to avayaAM110ApplicationModule(4210).
--   2.) Rename avayaG350-L(31) to  avayaDistributedOfficei120(31).
--   3.) Rename avayaG250-L(32) to avayaDistributedOfficei40-Analog(32).
--   4.) Rename avayaG250-BRI-L(33) to avayaDistributedOfficei40-BRI(33).
--	 5.) Rename avayaG250-DS1-L(34) to avayaDistributedOfficei40-DS1(34).
--   6.) Add avayaG450-Supervisor(4050) to genGroupType.
-- Shlomi Biton
--
-- Version 10.3.32
-- 17 Oct 2006
--   1.) Add 4155(TIM508), 4156(TIM516)	and 4157(TIM518) values to genGroupType.
-- Shlomi Biton
--
-- Version 10.3.31
--  07 Aug 2006
--   1.) Add avayaLSB(4210) to genGroupType for Liverpool Server Blade.
--   2.) Add avayaG350-L(31), avayaG250-L(32), avayaG250-BRI-L(33) and avayaG250-DS1-L(34)
--		 to chHwType.
-- Shlomi Biton
--
-- Version 10.3.30
--  27 June 2006
--   1.) Add chStatus mib item to indicate that the chassis undergoes reset phase and now it is up
--       again.
-- Shlomi Biton
--
-- Version 10.3.29
--  26 January 2006
--   1.) Add genGroupType and chHwType for TGM550/TIM514/TIM521/TIM510
-- Meir Deutsch

-- Version 10.3.28
-- 20 December 2005
-- Changing the genGroupConfigurationSymbol to be R/O instead of R/W.
--
-- Version 10.3.27
-- 21 June 2005
-- Adding new enumeration for genGroupType of avayaMM314cr(4112) for the
-- 24 Ports PoE cost reduction HDMM for G350.
--
-- Version 10.3.26
-- 07 April 2005
-- Adding new enumerations of avayaG350-10or100or1000TPort(2913) to GenPortType.
--
-- Shlomi Biton
--
-- Version 10.3.25
-- 5 January 2005
-- Add genGroupType, genPortType and chHwType for G250-DS1/DCP and change object names for G250/G250-BRI
-- Meir Deutsch
--
-- Version 10.3.24
-- 24 October 2004   	Shlomi Biton
-- Adding new enumeration for genGroupType of avayaMM316(4111) for the
-- new 40 Ports PoE HDMM for G350.
--
-- Version 10.3.23
-- 24 October 2004   	Shlomi Biton
-- Updating the default of chStackHealthRxListen to be stop instead of 2 (compiler problem).
--
-- Version 10.3.22
-- 5 October 2004   	Meir Deutsch
-- Added chLldpSystemControl and update values for the G250-BRI

--
-- Version 10.3.21
-- 21 September 2004   	Pesah Spector
-- Added to genGroup object genGroupFips140Ready
--
-- Version 10.3.20
-- 20 June 2004   	Meir Deutsch
-- Added to genGroupFaultMask bit 21 indication PoE consumption above thershold
--
-- Version 10.3.19
-- 19 Feb 2004
-- Added to genGroupType
-- 			avayaMM716(4110)
-- Shlomi Biton
--
--  Version 10.3.18
--  15 January 2004
--   1.) Add genGroupType, genPortType and chHwType for G250
-- Meir Deutsch
--
-- Version 10.3.17
--  1 January 2004
--   1.) Add genGroupType for invalid blade (invalid)
-- Dan Gluskin
--
-- Version 10.3.16
--  Add chHwType for G350 (22) and change Cayenne (W310) chHwType to 23.
--
-- Version 10.3.15
-- 10 Nov 2003
-- Added to genGroupType
-- 			avayaMM717(4109
-- Shlomi Biton
--
-- Version 10.3.14
-- 4 Aug 2003
-- Fix a bug in AgType definition forr W310L3
-- Meir Deutsch

-- Version 10.3.13
-- 3 Aug 2003
-- Document old changes in PortFaultMask and GroupFaultMask - relating to POE
-- Meir Deutsch

-- Version 10.3.12
-- 23 July 2003
-- Added changes for W310
-- Meir Deutsch

-- Version 10.3.11
-- 30 June 2003
-- Added to genPortType
--          avayaG350-1000TX-SFP(2912)
-- Dan Gluskin
--
-- Version 10.3.10
-- 19 June 2003
-- Added to genGroupReset value (3) indicating module reset including PoE supply
-- Meir Deutsch
--
-- Version 10.3.9
-- 8 June 2003
-- Added to genPortType
--          cajunP330-ML-1000TX-SFP(2550)
--          avayaC360-1000TX-SFP(2650)
--
--
-- Version 10.3.8
-- 2 June 2003
-- Add avayaG350 media modules enums to genGroupType
-- The vaules are 0x1000 + Module's HW type
-- Change Boxster to avayaG350 in all places
-- Dan Gluskin
--
--
-- Version 10.3.7
-- 25 May 2003
--
-- 1. Added to chHWType
--          avayaC360(20)
--
-- 2. Added to chGenAgType
--          avayaC360(60)
--          avayaC360L3(61)
--
-- 3. Added to genGroupType
--          avayaC363T(2700)
--          avayaC364T(2701)
--          avayaC363T-PWR(2702)
--          avayaC364T-PWR(2703)
--
-- 4. Added to genPortType
--          avayaC360-LAG(2640)
--          avayaC360-1000SX-SFP(2641)
--          avayaC360-1000LX-SFP(2642)
--          avayaC360-LAG100(2643)
--          avayaC360-LAG1000(2644)
--          avayaC360-100or1000Tport(2645)
--          avayaC360-10or100Tport(2646)
--          avayaC360-SFP-NotPresent(2647)
--          avayaC360-SFP-NotSupported(2648)
--          avayaC360-10or100TPortAndInPWR(2649)
--
-- Igor Umansky
--
--
-- Version 10.3.6
-- 10 Mar 2003
-- 1. Added to genGroupType
--          avayaC460-M4648ML-T-PWR(2604)
--          avayaC460-M4648ML-T-PWR-2G(2605)
-- 2. Added to genPortType
--          avayaC460-10or100TPortAndInPWR(3509)
-- 3. Added to chHWPowerModType
--          avayaC460-M4648ML-T-PWR(2604)
--          avayaC460-M4648ML-T-PWR-2G(2605)
-- 4. Added to chHWPowerTable
--          chHWPowerPriority
--          chHWPowerPoEBudget
--          chHWPowerPoEDemand
-- 5. Added to chHWPSUType
--          avayaC460-MPS4610-AC(2)
-- 6. Added to chHWPSUTable
--          chHWPSUPoECapacity
--          chHWPSUPoEConsumption
-- 7. Added to chHWPower
--          chHWPowerConfigurationAdmin
--          chHWPoECapacity
--          chHWPoEConsumption
--          chHWPoERemain
--          chHWPoEBudgetRecalc
--
-- Igor Umansky
--
-- Version 10.3.5
-- 18 Feb 2003
-- Changes for Boxster
-- genGroupType 'boxster' added
-- genPortType 'boxster' types added
--
-- Version 10.3.4
-- 26 Dec 2002
-- 1. Added chStackHealthTxDstAddress to chStackHealthTable
-- Pesah Spector
--
-- Version 10.3.3
-- 25 Nov 2002
-- 1. Added chHWPowerFans to chHWPower
-- Igor Umansky
--
-- Version 10.3.2
-- 17 Nov 2002
-- 1. Added cajunX330W-2DS1-B(2519) to genGroupType
--
-- Igor Umansky
--
-- Version 10.3.1
-- 7 Nov 2002
--
-- 1. Added to chHWFans:
--          oneFanFailed(3),
--          moreThanOneFanFailed(4)
-- 2. Added to chGenAgType:
--          avayaC460L3(59)
-- 3. Added chHWPower group
-- 4. Added chSpv group
-- 5. Added to chHWPSUTable:
--          chHWPSUCapacity,
--          chHWPSUConsumption,
--          chHWPSUType,
--          chHWPSUTypeName,
--          chHWPSUDescr
-- 6. Added to chHWPSUId description for modular switches.
--
-- Igor Umansky
--
--
-- Version 10.2.15
-- 21 Aug 2002
-- policyType item added for P334T-ML RL3/L3 policy selection
-- Dan Gluskin
--
-- Version 10.2.14
-- 15 Aug 2002
-- Revert changes made by MG soft MIB Browser
-- Replace all under-scores with '-'
-- Dan Gluskin
--
-- Version 10.2.13
-- 4 August 2002
-- Software port-redundancy enhancements:
-- - softRedundancyDumpingInterval
-- - softRedundancySwitchoverInterval
-- Dan Gluskin
--
-- Version 10.2.12
-- 14 July 2002
-- stackHealth group revised (changed to chStackHealthTable)
-- Dan Gluskin
--
-- Version 10.2.11
-- 4 July 2002
-- stackHealth group added
-- Dan Gluskin
--
-- Version 10.2.10
-- 30 Apr 2002
-- 1. Added genGroupType cajunX330W-2USP (2518) - Igor Umansky.
--
-- Version 10.2.9
-- 10 Feb 2002
-- 1. Added genGroupType
--     avayaC460-M460ML-SPV(2600),
--     avayaC460-M4648ML-T(2601),
--     avayaC460-M4648ML-T-2G(2602),
--     avayaC460-M4612ML-G(2603),
--     By Yaron pdut
-- 2. Added genGroupPSUType for the p333 - Yaron Pdut
-- 3. Added avayaC460 type for chHwType
-- 4. Added avayaC460 type for chGenAgType
--
-- Version 10.2.8
-- 25 Dec. 2001
-- 1. Added genGroupType cajunX330W-2DS1 (2517) - Michael W.
--
-- Version 10.2.7
-- 10 Dec. 2001
-- 1. Added genGroupType cajunP133GT2(2516) for the p130 family - Yigal N.
--
-- Version 10.2.6
-- 31 Oct 2001, ItaiZ
-- Fixed genPortVlanBindingMode to be as Kernel and NMS use it.
--
-- Version 10.2.5
-- 29 Oct. 2001
-- 1. Added genGroupType cajunP133T(2515) for the p130 family - Yigal N.
--
-- Version 10.2.4
-- 15 Oct. 2001
-- 1. Added chGenAgType x330wan(57) for the P330 WAN uplink - Michael W.
-- 2. Added chGenAgReset for supporting the 'boot from bank a'
--    and 'reset' cli commands. - Michael W.
--
-- Version 10.2.3
-- 9 Sept. 2001
-- 1. Added genGroupType x330W-4DS1(2514) for the P330 WAN uplink
--
-- Version 10.2.2
-- 20 Feb. 2001
-- 1. Add new module C-hawk chGenAgType(56) & genGroupType(2800) - Ran I.
-- 2. Copyright changed from Lucent/Lannet to Avaya.
-- 3. Delete the following modules from chHWType - Yigal
--    cajunP332G-ML(20), cajunP332GT-ML(21), cajunP334T-ML(22),
--    cajunP333T-PWR(23),
--
-- Version 10.2.1
-- 12 Dec. 2000
-- 1. Add new module P333T-PWR to chHWType & genGroupType - Ran I.
-- 2. Add new functionality eth10BaseTwInPWR(57) & eth100BaseTXwInPWR(58)&
--    port type cajunP330-10or100TPort+InPWR(2549) - Ran I.
--
-- Version 10.2.0
-- 22 Oct. 2000
-- 1. Add new item genPortVLANBindingMode to genPort table - Ygdal N.
-- 2. Add new item genGroupPortClassificationMask to genGroup table - Smadar B.
--
-- Version 10.1.6
-- 19 Sep. 2000
-- 1. Added new HW - P333RLB to chGenAgType, genGroupType - Itai Z.
-- 2. Add new item genGroupCascadingUpFault,
--    genGroupCascadingDownFault to genGroup table - Yigdal N.
--
-- Version 10.1.5
-- 05 July 2000
-- 1. Change name of M2-2400 to M2-2400I in group and port types - Michal R.
--
-- Version 10.1.4
-- 27 June 2000
-- 1. Change name of cajunP332AG  to cajunP332G-ML and add new HW types
--    cajunP332GT-ML & cajunP334T-ML - Ran I.
-- 2. Change the names in chGenAgType, genGroupType & genPortType to ML - Ran I.
--
-- Version 10.1.3
-- 19 June 2000
-- 1. Move m-acc155or622MMFPort & m- acc155or622SMFPort from
--    range 3000 to range 2000 - Michal R.
-- 2. Add new port types m2-2400Port, m4-DS3Port &m4-E3Port - Michal R
--
-- Version 10.1.2
-- 13 June 2000
-- 1. Change the group type of P133T to P133G2R - Yaron N.
-- 2. Add new group types P133F2 and P134G2 - Yaron N.
--
-- Version 10.1.1
-- 1 June 2000
-- 1. Change the group type of m2-2400IR to m2-2400 - Michal R.
-- 2. Add new enumeration (blocked) to genGroupCascadUpStatus &
--    genGroupCascadDownStatus - Ygdal N.
-- 3. Add new item genGroupShowModuleInformation to genGroup table - Yaron N.
--
-- Version 10.1.0
-- 16 May 2000
-- 1. Add fast SW redundancy table - Ygdal N.
--
-- Version 10.0.1
-- 16 May 2000
-- 1. Move m-accf & m-accsf from range 3000 to range 2000 - Michal R.
-- 2. Add new modules m2-2400IR(3005), m4-DS3(3009), m4-E3(3010)
--    for wizard - Michal R.
-- 3. Change the type CajunP332F to CajunP332MF - Ygdal N.
-- 4. Add new types to genPortType for P340 - Ran I.
--     cajunP330A-100Fport(2540) , cajunP330A-1000SX-SFP(2541),
--     cajunP330A-1000LX-SFP(2542), cajunP330A-LAG100(2543),
--     cajunP330A-LAG1000(2544), cajunP330A-1000TPort(2545),
--     cajunP330A-10-100TPort(2546), cajunP330A-SFP-NotPresent(2547),
--     cajunP330A-SFP-NotSupported(2548)
-- 5. Add new type to genPortFunctionality - Ran I.
--     sFP-NotPresent(55), sFP-NotSupported(56).
-- 6. Change the name of cajunP130 to cajunP133T - Yaron N.
-- 7. Add cajunP332AG to chHWType, chGenAgType, genGroupType - Ran I.
--
-- Version 10.0.0
-- 14 Apr. 2000
-- 1. Add new mib genPortClassification to genPort table - Ygdal N.
-- 2. Add cajunP130 to chHWType, chGenAgType, genGroupType - Yaron N.
-- 3. Add new value eth1000BaseX-Proprietary to genPortFunctionality - Yaron N.
-- 4. Add new values to genPortType - Yaron N.
--     cajunP130-10or100BaseTXPort(2530), cajunP130-100BaseFXPort(2531),
--     cajunP130-1000BaseSX-GBICPort(2532), cajunP130-1000BaseLX-GBICPort(2533),
--     cajunP130-1000BaseX-Proprietary-GBICPort(2534),
--     cajunP130-GBIC-NotSupported (2535),
--     cajunP130-GBIC-NotPresent(2536), cajunP130-LAG100(2537),
--     cajunP130-LAG1000(2538), cajunP130-1000BaseTPort(2539)
-- 5. Add new mib item genGroupSerialNumber to genGroup table - Yaron N.
-- 6. Add m-acc to chGenAgType and m-accf, m-accsf to genGroupType - Yaron N.
-- 7. Add new value oc12 to genPortFunctionality - Yaron N.
-- 8. Add new values to genPortType - Yaron N.
--     m-acc155or622MMFPort(3005), m-acc155or622SMFPort(3006)
--
-- Version 9.9.1
-- 6 Mar. 2000
-- 1. Update the list of occupied bits in genGroupFaultMask
--    (13,14,15,16) - Ygdal N.
--
-- Version 9.9.0
-- 14 Feb 2000
-- 1. Add new MIB item chLicenseKey to chassis. - Gidi N.
--
-- Version 9.8.1
-- 23 Dec. 1999
-- 1. Add new group type CajunP332F(2505). - Ygdal N.
-- 2. Add new enumeration eth1000BaseCX(50), gBICNotPresent(51),
--     gBICNotSupported(52) to genPortFunctionality - Ygdal N.
-- 3. Add new enumeration cajunP330-1000SX-GBIC(2523),
--     cajunP330-1000LX-GBIC(2524), cajunP330-1000T-GBIC(2525),
--     cajunP330-1000CX-GBIC(2526), cajunP330-GBIC-NotPresent(2527),
--     cajunP330-GBIC-NotSupported (2528) to genPortType - Ygdal N.
--
-- Version 9.8.0
-- 29 Nov. 1999
-- 1. Udate description of chSlotLastChange to be update when a module
--    is reset. - Yigal N.
-- 2. Add new mib genGroupResetLastStamp in group level
--    to indicate last module reset. - Yigal N.
-- 3. Add new mib genGroupBootVersion for display - Yigal N.
--
-- Version 9.7.4
-- 26 Oct. 1999
-- 1. Add new agent type cajunX330ATM for the P330 ATM
--    plug-in modules - Yaron N.
--
-- Version 9.7.3
-- 29 Sep. 1999
-- 1. Add new port type for the P330 plug-in modules - Ygdal N.
--     cajunP330-1000TXPort(2522)
-- 2. Add new group functionality - Ygdal N.
--     eth1000BaseTX(49)
--
-- Version 9.7.2
-- 14 Sep. 1999
-- 1. Add new port type for the P120 plug-in modules and change
--    the number of others - Ran I.
--     cajunP120-1000BaseT-GBIC(2516)
--     cajunP120-GBIC-NotPresent(2517),
--     cajunP120-GBIC-Unknown(2518), cajunP120-GBIC-Other(2519),
--     cajunP120-FibreChannel-GBIC(25120),cajunP120-1000BaseTX(2521),
--
-- Version 9.7.1
-- 9 Sep. 1999
-- 1. Add new port types for the P120 plug-in modules - Ran I.
--     cajunP120-1000BaseCX-GBIC(2513), cajunP120-1000BaseSX-GBIC(2514),
--     cajunP120-1000BaseLX-GBIC(2515), cajunP120-GBIC-NotPresent(2516),
--     cajunP120-GBIC-Unknown(2517), cajunP120-GBIC-Other(2518),
--     cajunP120-FibreChannel-GBIC(2519),	cajunP120-1000BaseTX(2520),
--
-- Version 9.7.0
-- 22 Aug. 1999
-- 1. Add genGroupLicenseKey mib item to genGroup table. - Ygdal N.
-- 2. Add new module CajunP334T to genGroupType - Ygdal N.
-- 3. Add genGroupLogFileClear mib item to genGroup table. - Ygdal N.
-- 4. Add new module CajunP333R to chGenAgType - Yigal N.
--
-- Version 9.6.1
-- 20 July 1999
--  1. Add new group type M15-155MS to genGroupType 3004 - Gidi N.
--  2. Add new port type M15-155MSPort to genPortType 3004 - Gidi N.
--
-- Version 9.6.0
-- 29 June 1999
--  1. Add 2 new mib items to genGroup table. genGroupSTARootPortID &
--      genGroupCopyPortInstruction - Ygdal N.
--
-- Version 9.5.4
-- 13 June 1999
-- 1. Change the numbers of group types P117S&P117SR - Yaron N.
-- 2. Change the numbers of port types P117SPort&P117SRPort - Yaron N.
--
-- Version 9.5.3
-- 10 June 1999
-- 1. Add new group types P117S&P117SR to genGroupType - Yaron N.
-- 2. Add new port types P117SPort&P117SRPort to genPortType - Yaron N.
--
-- Version 9.5.2
-- 7 June 1999
-- 1. Add new group cajunP122 to chGenAgType & genGroupType - Ran B.
--
-- Version 9.5.1
-- 19 May 1999
-- 1. Add new groups to chGenAgType: m-sps-T, m-sps-ER and m-sps-EB - Gidi N.
-- 2. Add new modules to genGroupType: m-sps-T, m-sps-ER and m-sps-EB - Gidi N.
-- 3. Add module M32-100T and port type m10or100BaseTXdot1Qport - Yaron N.
--
-- Version 9.5.0
-- 13 May 1999
-- 1. Add new group type lfe8008S to genGroup table - Yigdal N.
-- 2. Add new port type lfe8008S-UTPPort to genPort table - Yigdal N.
-- 3. Add two new items genGroupCascadUpStatus and
--     genGroupCascadDownStatus to genGroup table - Yigdal N.
--
-- Version 9.4.3
-- 30 Apr. 1999
-- 1. Add new port types P330-LAG and P110-LAG to genPortType - Yaron N.
-- 2. Add new functionality LAF-100 and LAG-1000 to genPortFunc - Yaron N.
-- 3. Add module type P333R for to genGroupType - Yigal N.
--
-- Version 9.4.2
-- 27 Apr. 1999
-- 1. Change the SYNTAX of chLogFileAbsoluteTime from INTEGER to
--    Counter - Yigal N.
--
-- Version 9.4.1
-- 20 Apr. 1999
-- 1. Change the name of the chLogReset table to a generic
--    name chLogFile - Yigal N.
-- 2. Add new item chLogFileName to chLogFile table - Yigal N.
--
-- Version 9.4.0
-- 19 Apr. 1999
-- 1. Add new table chLogReset for P330 family to support log files - Ygdal N.
-- 2. Add new item genGroupNumberOfInterfaces to genGroup table - Gidi N.
--
-- Version 9.3.0
-- 23 Mar. 1999
-- 1. Add new mib genPortName for P330 family - Ygdal N.
--
-- Version 9.2.2
-- 22 Mar. 1999
-- 1. Add new module type m15-155SF and port type m15-155SFPort
--    to M770(meritage) family - Gidi N.
-- 2. Add new mib chPluginList for P330 family - Ygdal N.
-- 3. Add new port type cajunP330-LAG for P330 family - Ygdal N.
-- 4. Add new port functionality ethLAG for P330 family - Ygdal N.
--
-- Version 9.2.1
-- 11 Mar. 1999
-- 1. Add new module (P333T) for P330 family in genGroup table - Ygdal N.
-- 2. Add new agent (P330) for P330 family in chHWType - Ygdal N.
-- 3. Add new port types for P330 family in genPort table - Ygdal N.
--
-- Version 9.2
-- 07 Jan. 1999
-- 1. Add new item genGroupNumberOfLogicalPorts to genGroup table - Yaron N.
--
-- Version 9.1
-- 12 Dec. 1998
-- 1. Change enumeration of let36-01 in chHWType to let36-01-02 - Dan R.
-- 2. Move softRedundancy table from module.mib file to this file - Yigal N.
-- 3. Add new mib softRedundancyGlobalStatus to Soft Redundancy
--    application - Yaron N.
--
-- Version 9.0.2
-- 24 Nov. 1998
-- 1. Add new type cajun210 to chHWType - Ygdal N.
--
-- Version 9.0.1
-- 16 Nov. 1998
-- 1. Change the groupType and portType m3-622SF to m3-622F- Gidi N.
-- 2. Add new groupType and new portType m3-622SF - Gidi N.
--
-- Version 9.0
-- 9 Nov. 1998
-- 1. Cancel bit 13 in genGroupFaultMask - Ygdal N.
-- 2. Replace - with - or & - Yigal N.
-- 3. Add new groupType and new portType m3-622SF - Gidi N.
-- 4. Change meritage to m770 in chHWType. - Gdi N.
--
-- Version 8.9.1
-- 7 Oct. 1998
-- 1. A new module cajunP210(44) was added to chGenAgType - Ygdal N.
-- 2. A new module cajunP210(2500) was added to genGroupType - Ygdal N.
-- 3. A new port cajunP210-10&100TPort(2500), cajunP210-100FPort(2501),
--     cajunP210-1000SXPort(2502), cajunP210-1000LXport(2503)
--     was added to genPortType - Ygdal N.
-- 4. Add new bit to genGroupFaultMask (bit 13) - Ygdal N.
--
-- Version 8.9.0
-- 23 Sep. 1998
-- 1. A new module lge-2000LX (191) was added to genGroupType - Yaron N.
-- 2. A new port type lge-2000LXPort (195) was added to genPortType - Yaron N.
-- 3. A new mib item genPortAdminPermission was added to genPortTable - Zion S.
--
-- Version 8.8.4
-- 16 Aug. 1998
-- 1. A new module lge-2000SX (190) was added to genGroupType - Yaron N.
-- 2. A new port type lge-2000SXPort (194) was added to genPortType - Yaron N.
--
-- Version 8.8.3
-- 05 July 1998
-- 1. Add enumeration notPresent(3) to genGroupBUPSActivityStatus - Zion S.
--
-- Version 8.8.2
-- 03 July 1998
-- 1. Add new group types visage26Plus, visage26PlusFxMM,
--    visage26PlusFxSM and visage26PlusTx to genGroupType - Zion S.
-- 2. Add new group types visage1000SX and visage1000LX to
--    genGroupType - Zion S.
-- 1. Change m-mls group type number from 2400 to 2200.
--
-- Version 8.8.1
-- 08 June 1998
-- 1. Add new group types visage2000SX and visage2000LX to genGroupType - Zion S.
--
-- Version 8.8.0
-- 04 June 1998
-- 1. Add new mib genPortVLANMode to genPort table - Yaron N.
-- 2. Add new group types m2-1000SX, m2-1000LX, m14-10F, m24-10T to genGroupType
--    Yaron N.
-- 3. Add new type of port functionality eth10BaseFL, eth1000BaseSX,
--    eth1000BaseLX to genPortFunctionlity - Yaron N.
-- 4. Add new port types m10/100BaseTXPort (2000), m100BaseFXPort (2001),
--     m1000BaseSXPort (2002), m1000BaseLXPort(2003)
--     m10BaseFLPort (2004), m10BaseTPort (2005) - Yaron N.
--
-- Version 8.7.1
-- 19 May 1998
-- 1. Change m-mls group type number from 2006 to 2400.
--
-- Version 8.7.0
-- 23 Apr. 1998
-- 1. Add new mib genPortIfMap to genPort table - Dan R.
-- 2. Change description of genGroupConfigurationSymbol and genGroupHWVersion
--
-- Version 8.6.4
-- 12 Apr. 1998
-- 1. Add groupType of m-mls(2006) - Yigal N.
-- 2. Add port type m15-155Fport (3000) - Gidi N.
-- 3. Add meritageAtm (16) to chHWType - Gidi N.
--
-- Version 8.6.3
-- 24 Feb. 1998
-- 1. Change groupType name of lbt3(187) to lbt155+ - Dan R..
-- 2. Delete groupType name of lbt2(184) - Dan R.
--
-- Version 8.6.2
-- 18 Jan. 1998
-- 1. Delete groupType/ portType(1002) for visage16TR module - Zion S.
-- 2. Change groupType/ portType of visage3LS from 1011 to 1012 - Zion S.
-- 3. Change groupType/ portType of visage1600T from 1003 to 1013 - Zion S.
--
-- Version 8.6.1
-- 12 Jan. 1998
-- 1. Add agent type m-spx to chGenAgType and genGroupType. - Yaron N.
-- 2. Change description of chGenAgId. - Yigal N.
--
-- Version 8.6.0
-- 28 Dec. 1997
-- 1. Change groupType(1010) and portType(1010) for visage2500 module - Gidi N.
-- 2. Add groupType(1011) and portType(1011) for visage3LS module - Yigal N.
-- 3. A new item genPortFunctionalStatus was added to genPort table. - Gidi N.
-- 4. Update description of genPortFaultMask item - Yigal N.
--
-- Version 8.5.5
-- 2 Dec. 1997
-- 1. Add new groupType(1010) and portType(1010) for visage3LS module - Benny R.
-- 2. Add new mib item chGenAgIpAddr was added to chGenAg Table. - Gidi N.
--
-- Version 8.5.4
-- 25 Oct. 1997
-- 1. Add new groupType(1003) and portType(1003) for visage1600T
--    module - Zion S.
--
-- Version 8.5.3
-- 05 Oct. 1997
-- 1. Change precedence of chLntAgSetup subtree from chSetupAg back to chLntAg.
-- 2. Add 2 group types for Legacy Meritag nma-rs(2003) and
--    nma-re(2004) - Yigal N.
--
-- Version 8.5.2
-- 26 Aug. 1997
-- 1. Change the access of chAgHubAddr from read-only to read-write.
--
-- Version 8.5.1
-- 26 Aug. 1997
-- 1. Add group type m15-155F to genGroupType
-- 2. Add agent type mAtm and m-3ls to chGenAgType
-- 3. Change description and Type of chGenAgEntMngVersion
-- 4. Change precedence of chLntAgSetup subtree from chLntAg to chSetupAg
--
-- Version 8.5.0
-- 18 Aug. 1997
-- 1. Delete relations to meritage. A new mib file was added (mritag.mib)
-- 2. Change convention of version numbering.
--
-- Version 8.5
-- Revision A. -	1. Add two group types m12-100T and m12-100F to genGroupType and the
-- 10-Apr-1997	    related port type to genPortType. - Yaron N.
-- 	2. New description to chNumOfXswitch which defins the default values.
-- 	3. Add new item chGenAgXswitchBridging to chGenAg table. -Yaron N.
-- 	4. Add new item genGroupRedundancyStatus to genGroup table.
-- 	5. Add 3 items to PSU table. The otems are:
-- 	     chHWPSUConfigurationSymbol
-- 	     chHWPSURatedPower
-- 	     chHWPSUType
-- 	6. Add chassis HW Fans table
--
-- Revision B. -	1. Add the enum sdh-stm1(42) to genPortFunctionality - Zion S.
-- 4 - May-1997
--
-- Revision C. -	1. Add the enum letMeritage, meritage to chHWType - Yaron N.
-- 18- May-1997 2. Add the enum m-spv to chGenAgType - Yaron N.
-- 	3. Add the enum middle to chHWPSULocation - Yaron N.
-- 	4. Add the enum m-spv to genGroupType - Yaron N.
--
-- Revision D. -	1. Change groups type visage16200F-Plus(1001) to visage16200F and
-- 9-June-1997	    16200F(1005) to 16200F/C
-- 	2. Change genPortType
-- 	    visage16200FPlusPort(1001) to visage16200FPort(1001)
-- 	    and visage16200FPort(1005) to visage16200F/CPort(1005)
-- 	Note: See 8.1 revision B.
--
-- Revision E. -	1. Change the enumeration of lfe4004SF in genGroupType mib item,
-- 20-July-1997     from 187 to 189. The enumeration 187 was occupied by lbt3.
-- 	Note: See 8.1.1 revision A.
-- 	2. Add new type visage16TR to chGenAgType, genGroupType and
-- 	    genPortType.
--
-- Version 8.1
-- Revision A. -	1. Add two groups type lfe4004SF and lfe4004ST to genGroupType - Ronen
-- 10-Apr-1997	    Bar-Tal.
-- 	2. Add two ports type lfe4004SFPort and lfe4004STPort to genPortType - -//-
-- 	3. Change the text for the genPortFunctionality: lse10baseT(20) to
-- 	    eth10baseTx(20). - Zion S.
-- 	4. add new item genGroupTempExceed to genGroupTable.- Zion S./Yaron N.
--
-- Version 8.0.1
-- Revision A. -  1. Change Enumaration of Visage products in genGroupType 1001-16200F,
-- 20-Feb-1997	    1002 - free, 1003 - free. - Zion S.
-- Revision B. -  1. Change Enumaration of Visage products in genPortType 1001-16200F,
-- 26-Feb-1997	    1002 - free, 1003 - free. - Zion S.
--
-- Version 8.0
-- Revision A. -  1. spliting lannt80.mib into 3 files config, moduls and applic files
-- 15-Nov-1996	    config file contains the chassis, genGroup, genPort and
-- 		      genIntPort sub-trees. - Yigal N.
-- 		  2. Change lre to lns in genGroupType & genAgType -Rafi H.
-- 		  3. Delete all Meritage Hubs from chHwType - Rafi H.
-- 		  4. Add new 3 items genGroupTypeName, genGroupAgentSlot,
-- 		      and genGroupMngType - Rafi H.
-- 		  5. Add visage16200ST and visage 16200SF to genGroupType
-- 		      and to genPortType. - Zvika M.
-- Revision B. -  1. Change lns to 3ls in genGroupType & genAgType - Yigal N.
-- 21-Nov-1996	2. Add new genGroupType - leb200n(174) - Zion S.
--
-- Revision C. -  1. Change the enumeration of genGroupType & genPortType
-- 11-Dec-1996	    for visage products - Gidi N.
--
-- Revision D. -  1. Change the enumeration of LSA2 genGroupType from 183 to 186
-- 		 2. Add genPortFunctionality for  sonet(40), fimVoice(41)
-- 		 3. Change 3LS to ls3LS
-- 31-Dec-1996	    - Yigal N.
--
-- ==========================================================

	CONFIG-MIB DEFINITIONS ::= BEGIN

		IMPORTS
			lannet
				FROM GEN-MIB
			OBJECT-TYPE
				FROM RFC-1212
			TimeTicks, IpAddress, Counter
				FROM RFC1155-SMI
			DisplayString
				FROM RFC1213-MIB;



--
-- Node definitions
--

--  Node definitions
--
-- Node definitions
--
-- Node definitions
--
-- Node definitions
--
-- 1.3.6.1.4.1.81.7
		chassis OBJECT IDENTIFIER ::= { lannet 7 }

--     Chassis group
-- Implementation of this group is mandatory for all  box agents.
-- 1.3.6.1.4.1.81.7.1
		chHWType OBJECT-TYPE
			SYNTAX INTEGER
				{
				let18(1),
				let3(2),
				let36(3),
				let18Extended(4),
				lert40(5),
				let10(6),
				fdx100(7),
				stack(8),
				let20(9),
				let36-01-02(10),
				lea(11),
				lac(12),
				visage(13),
				letM770(14),
				m770(15),
				m770Atm(16),
				cajunP120(17),
				cajunP330(18),
				cajunP130(19),
				avayaC360(20),
				avayaC460(21),
				avayaG350(22),
				avayaW310(23),
				avayaG250(24),
				avayaG250-BRI(25),
				avayaG250-DS1(26),
				avayaG250-DCP(27),
				avayaG250-A14(28),
				avayaTGM550(30),
				avayaCommunicationManagerBranchEditioni120(31),
				avayaCommunicationManagerBranchEditioni40-Analog(32),
				avayaCommunicationManagerBranchEditioni40-BRI(33),
				avayaCommunicationManagerBranchEditioni40-DS1(34),
				avayaG450(35),
				avayaTRM480(36),
				avayaCommunicationManagerBranchEditioni40-A14(37),
				avayaCommunicationManagerBranchEditionG450(38),
				avayaCommunicationManagerBranchEditionG430(40),
				avayaG430(41),
				unknown(255)
				}
			ACCESS read-write
			STATUS mandatory
			DESCRIPTION
				"Indicates type of enclosure in which the SNMP agent operates."
			::= { chassis 1 }

--     1.3.6.1.4.1.81.7.2
		chNumberOfSlots OBJECT-TYPE
			SYNTAX INTEGER (1..255)
			ACCESS read-only
			STATUS mandatory
			DESCRIPTION
				"Number of manageable slots in the chassis.
				In implementation it describes the number of manageable slots
				in the chassis (not all slots should be occupied)."
			::= { chassis 2 }

--     1.3.6.1.4.1.81.7.3
		chNumberOfEthernetBuses OBJECT-TYPE
			SYNTAX INTEGER (0..255)
			ACCESS read-only
			STATUS mandatory
			DESCRIPTION
				"Indicates the number of internal Ethernet buses provided by the box."
			::= { chassis 3 }

--     1.3.6.1.4.1.81.7.4
		chNumberOfTRBuses OBJECT-TYPE
			SYNTAX INTEGER (0..255)
			ACCESS read-only
			STATUS mandatory
			DESCRIPTION
				"Indicates the number of internal Token Ring buses provided by the box."
			::= { chassis 4 }

--     1.3.6.1.4.1.81.7.5
		chNumberOfFDDIBuses OBJECT-TYPE
			SYNTAX INTEGER (0..255)
			ACCESS read-only
			STATUS mandatory
			DESCRIPTION
				"Indicates the number of internal FDDI buses provided by the box."
			::= { chassis 5 }

--     1.3.6.1.4.1.81.7.6
		chNumberOfLocalTalkBuses OBJECT-TYPE
			SYNTAX INTEGER (0..255)
			ACCESS read-only
			STATUS mandatory
			DESCRIPTION
				"Indicates the number of internal Local Talk buses provided by the box."
			::= { chassis 6 }

--     1.3.6.1.4.1.81.7.7
		chReset OBJECT-TYPE
			SYNTAX INTEGER
				{
				on(1),
				off(2)
				}
			ACCESS read-write
			STATUS mandatory
			DESCRIPTION
				"Setting the value of this attribute to ON is interpreted as a reset
				command for the whole chassis.
				It initiates a complete reinitialisation of the chassis and of all
				the devices incorporated inside the chassis."
			::= { chassis 7 }

--     1.3.6.1.4.1.81.7.8
		chFullConfig OBJECT-TYPE
			SYNTAX OCTET STRING
			ACCESS read-only
			STATUS deprecated
			DESCRIPTION
				"Full configuration message retrieved by	management stations
				at periodic interrogation times. Coded in compact internal application format."
			::= { chassis 8 }

--     Agent Group - attributes of SNMP agents
-- 1.3.6.1.4.1.81.7.9
		chAg OBJECT IDENTIFIER ::= { chassis 9 }

--     1.3.6.1.4.1.81.7.9.1
		chGenAgTable OBJECT-TYPE
			SYNTAX SEQUENCE OF ChGenAgEntry
			ACCESS not-accessible
			STATUS mandatory
			DESCRIPTION
				"Table of configuration attributes common to all SNMP agents in hubs."
			::= { chAg 1 }

--     1.3.6.1.4.1.81.7.9.1.1
		chGenAgEntry OBJECT-TYPE
			SYNTAX ChGenAgEntry
			ACCESS not-accessible
			STATUS mandatory
			DESCRIPTION
				"An entry in the table, containing configuration attributes for a single agent."
			INDEX { chGenAgId }
			::= { chGenAgTable 1 }

		ChGenAgEntry ::=
			SEQUENCE {
				chGenAgId
					INTEGER,
				chGenAgType
					INTEGER,
				chGenAgMgmtIfType
					INTEGER,
				chGenAgAddr
					OCTET STRING,
				chGenAgSpecificOID
					OBJECT IDENTIFIER,
				chGenAgSLIPAddress
					IpAddress,
				chGenAgTypeName
					DisplayString,
				chGenAgEntMngVersion
					DisplayString,
				chGenAgIpAddr
					IpAddress,
				chGenAgReset
					INTEGER
			 }

--     1.3.6.1.4.1.81.7.9.1.1.1
		chGenAgId OBJECT-TYPE
			SYNTAX INTEGER (1..255)
			ACCESS read-only
			STATUS mandatory
			DESCRIPTION
				"Agent index for identifying the agent. Takes the value of the slot number where
				the agent card is inserted. For box agents which are not managed as Group the value
				of chGenAgId is chNumberOfSlots+1. For box agents which are managed as Group
				the value in not greater then chNumberOfSlots"
			::= { chGenAgEntry 1 }

--     1.3.6.1.4.1.81.7.9.1.1.2
		chGenAgType OBJECT-TYPE
			SYNTAX INTEGER
				{
				nma1-et(1),
				nma1-et-e(2),
				nma1-tr(3),
				nma2-et(4),
				nma2-tr(5),
				nma2-fddi(6),
				ielb(7),
				itlb(8),
				lts16(9),
				ierp(10),
				iefn(11),
				itfn(12),
				sh-ema(13),
				nma-rt(14),
				sh-tma(15),
				nma-re(16),
				ietlb(17),
				nma2-fddi-rad(18),
				iefr-mc(19),
				iefr-utp(20),
				ieqr(21),
				iere(22),
				itre(23),
				las(24),
				lsa(26),
				lsf100(27),
				nma-rs(28),
				lea(29),
				itrp(30),
				ls3ls(31),
				visageNMA(32),
				fat-pipe-fddi(33),
				visage16200(34),
				visage16TR(35),
				visage16155(36),
				lsa2(39),
				m-spv(40),
				m-mls(41),
				m-atm(42),
				m-spx(43),
				cajunP120(44),
				cajunP330(45),
				m-sps-T(46),
				m-sps-ER(47),
				m-sps-EB(48),
				cajunP122(49),
				cajunP333R(50),
				cajunX330ATM(51),
				cajunP130(52),
				m-acc(53),
				cajunP332-ML(54),
				cajunP333RLB(55),
				c-Hawk(56),
				x330wan(57),
				avayaC460(58),
				avayaC460L3(59),
				avayaC360(60),
				avayaC360L3(61),
				avayaW310(62),
				avayaW310L3(63),
				unknown(255)
				}
			ACCESS read-only
			STATUS mandatory
			DESCRIPTION
				"Defines the type of the card whose management
				attributes are described by the SNMP agent."
			::= { chGenAgEntry 2 }

--     1.3.6.1.4.1.81.7.9.1.1.3
		chGenAgMgmtIfType OBJECT-TYPE
			SYNTAX INTEGER
				{
				none(1),
				regular1822(2),
				hdh1822(3),
				ddn-x25(4),
				rfc877-x25(5),
				ethernet-csmacd(6),
				iso88023-csmacd(7),
				iso88024-tokenBus(8),
				iso88025-tokenRing(9),
				iso88026-man(10),
				starLan(11),
				proteon-10MBit(12),
				proteon-80MBit(13),
				hyperchannel(14),
				fddi(15),
				lapb(16),
				sdlc(17),
				t1-carrier(18),
				cept(19),
				basicIsdn(20),
				primaryIsdn(21),
				propPointToPointSerial(22),
				ppp(23),
				softwareLoopback(24),
				eon(25),
				ethernet-3Mbit(26),
				nsip(27),
				slip(28),
				ultra(29),
				ds3(30),
				sip(31),
				frameRelay(32),
				rs232(33),
				para(34),
				arcnet(35),
				arcnetPlus(36),
				atm(37),
				miox25(38),
				sonet(39),
				x25ple(40),
				iso88022llc(41),
				localTalk(42),
				smdsDxi(43),
				frameRelayService(44),
				v35(45),
				hssi(46),
				hippi(47),
				modem(48),
				aal5(49),
				sonetPath(50),
				sonetVT(51),
				smdsIcip(52),
				propVirtual(53),
				propMultiplexor(54),
				aflane8023(59),
				ip(255)
				}
			ACCESS read-only
			STATUS mandatory
			DESCRIPTION
				"This attribute describes one of the interfaces of agents existing on
				modules and their type. Value 'none' defines the lack of
				an interface whose type is recognized by the management console.
				Any other value defines an interface whose type is recognized by
				the management console and may be used as a management channel."
			::= { chGenAgEntry 3 }

--     1.3.6.1.4.1.81.7.9.1.1.4
		chGenAgAddr OBJECT-TYPE
			SYNTAX OCTET STRING (SIZE (0..20))
			ACCESS read-only
			STATUS mandatory
			DESCRIPTION
				"This attribute defines an unique address by which the agent may be
				addressed by the management console. The address format should be
				consistent with the type defined by chGenAgMgmtIfType."
			::= { chGenAgEntry 4 }

--     1.3.6.1.4.1.81.7.9.1.1.5
		chGenAgSpecificOID OBJECT-TYPE
			SYNTAX OBJECT IDENTIFIER
			ACCESS read-only
			STATUS mandatory
			DESCRIPTION
				"This attribute provides the OID of another group containing
				additional more specific information regarding this instance."
			::= { chGenAgEntry 5 }

--     1.3.6.1.4.1.81.7.9.1.1.6
		chGenAgSLIPAddress OBJECT-TYPE
			SYNTAX IpAddress
			ACCESS read-only
			STATUS mandatory
			DESCRIPTION
				"IP address of the SLIP channel of the agent"
			::= { chGenAgEntry 6 }

--     1.3.6.1.4.1.81.7.9.1.1.7
		chGenAgTypeName OBJECT-TYPE
			SYNTAX DisplayString (SIZE (0..32))
			ACCESS read-only
			STATUS mandatory
			DESCRIPTION
				"String with the Agent name."
			::= { chGenAgEntry 7 }

--     1.3.6.1.4.1.81.7.9.1.1.8
		chGenAgEntMngVersion OBJECT-TYPE
			SYNTAX DisplayString
			ACCESS read-only
			STATUS mandatory
			DESCRIPTION
				"The entity management version supported by the specific Agent.
				In the format: X.Y.Z (using numbers):
					1st byte - major version number
					2nd byte - '.'
					3rd byte - minor version number
					4th byte - '.'
					5th byte - debug version number."
			::= { chGenAgEntry 8 }

--     1.3.6.1.4.1.81.7.9.1.1.9
		chGenAgIpAddr OBJECT-TYPE
			SYNTAX IpAddress
			ACCESS read-only
			STATUS mandatory
			DESCRIPTION
				"This attribute defines the Ip address by which the agent may be
				addressed by the management console.
				For NMA-RX this should include the IP address of the Side Band interface."
			::= { chGenAgEntry 9 }

--     1.3.6.1.4.1.81.7.9.1.1.10
		chGenAgReset OBJECT-TYPE
			SYNTAX INTEGER
				{
				noReset(0),
				warmReset(1),
				coldReset(2),
				resetAndSwitchToBackupBank(3)
				}
			ACCESS read-write
			STATUS mandatory
			DESCRIPTION
				"This attribute asks that the agent with the specified index reset
				itself, according to the value of the enum"
			DEFVAL { noReset }
			::= { chGenAgEntry 10 }

--     1.3.6.1.4.1.81.7.9.2
		chLntAgTable OBJECT-TYPE
			SYNTAX SEQUENCE OF ChLntAgEntry
			ACCESS not-accessible
			STATUS mandatory
			DESCRIPTION
				"Table of configuration attributes of  SNMP box agents in hubs."
			::= { chAg 2 }

--     1.3.6.1.4.1.81.7.9.2.1
		chLntAgEntry OBJECT-TYPE
			SYNTAX ChLntAgEntry
			ACCESS not-accessible
			STATUS mandatory
			DESCRIPTION
				"An entry in the table, containing configuration attributes for a single box agent."
			INDEX { chLntAgId }
			::= { chLntAgTable 1 }

		ChLntAgEntry ::=
			SEQUENCE {
				chLntAgId
					INTEGER,
				chLntAgSLIPAddress
					IpAddress,
				chLntAgSWVersion
					DisplayString,
				chLntAgKernelVersion
					DisplayString,
				chLntAgCoprocSWVersion
					DisplayString,
				chLntAgSWFault
					DisplayString,
				chLntAgMgmtBusSelection
					INTEGER,
				chLntAgCoprocCommStatus
					INTEGER,
				chLntAgCommDebugMode
					INTEGER,
				chLntAgConfigChangeTraps
					INTEGER,
				chLntAgFaultTraps
					INTEGER,
				chLntAgTrafficThreshTraps
					INTEGER,
				chLntAgGroupEnrollDeenrollTraps
					INTEGER,
				chLntAgSoftFaultTraps
					INTEGER,
				chLntAgHubEnrollTraps
					INTEGER,
				chLntAgTempThreshTraps
					INTEGER,
				chLntAgSpecificOID
					OBJECT IDENTIFIER,
				chLntAgLastAddrConfig
					OCTET STRING,
				chLntAgSecAddrConfig
					OCTET STRING,
				chLntAgSoftwareStatus
					INTEGER,
				chLntAgConfigurationSymbol
					DisplayString,
				chLntAgIntTemp
					INTEGER,
				chLntAgBootVersion
					DisplayString,
				chLntAgSensorFault
					INTEGER,
				chLntAgSensorFaultTraps
					INTEGER,
				chLntAgInterProcFault
					INTEGER,
				chLntAgInterProcFaultTraps
					INTEGER,
				chLntAgPSUVoltThrsTraps
					INTEGER,
				chLntAgHardwareVersion
					DisplayString,
				chLntAgSoftwareDscr
					DisplayString,
				chLntAgCAMChangeTraps
					INTEGER,
				chLntAgAppVersion
					DisplayString
			 }

--     1.3.6.1.4.1.81.7.9.2.1.1
		chLntAgId OBJECT-TYPE
			SYNTAX INTEGER (1..255)
			ACCESS read-only
			STATUS mandatory
			DESCRIPTION
				"Agent index for identifying the agent. Identical to the index in
				chGenAgTable for the described agent."
			::= { chLntAgEntry 1 }

--     1.3.6.1.4.1.81.7.9.2.1.2
		chLntAgSLIPAddress OBJECT-TYPE
			SYNTAX IpAddress
			ACCESS read-only
			STATUS mandatory
			DESCRIPTION
				"IP address of the SLIP channel of the agent"
			::= { chLntAgEntry 2 }

--     1.3.6.1.4.1.81.7.9.2.1.3
		chLntAgSWVersion OBJECT-TYPE
			SYNTAX DisplayString
			ACCESS read-only
			STATUS mandatory
			DESCRIPTION
				"ASCII string for description and display of the agent software version."
			::= { chLntAgEntry 3 }

--     1.3.6.1.4.1.81.7.9.2.1.4
		chLntAgKernelVersion OBJECT-TYPE
			SYNTAX DisplayString
			ACCESS read-only
			STATUS mandatory
			DESCRIPTION
				"ASCII string for description and display of the agent operating system
				(kernel) version."
			::= { chLntAgEntry 4 }

--     1.3.6.1.4.1.81.7.9.2.1.5
		chLntAgCoprocSWVersion OBJECT-TYPE
			SYNTAX DisplayString
			ACCESS read-only
			STATUS mandatory
			DESCRIPTION
				"ASCII string describing the software version of the agent's coprocessor."
			::= { chLntAgEntry 5 }

--     1.3.6.1.4.1.81.7.9.2.1.6
		chLntAgSWFault OBJECT-TYPE
			SYNTAX DisplayString
			ACCESS read-only
			STATUS mandatory
			DESCRIPTION
				"System fault emitted by agent software. It covers faults detected
				by the agent operating system and drivers. EnterpriseSpecific traps
				mechanism is used for transfering these traps to the management
				system."
			::= { chLntAgEntry 6 }

--     1.3.6.1.4.1.81.7.9.2.1.7
		chLntAgMgmtBusSelection OBJECT-TYPE
			SYNTAX INTEGER
			ACCESS read-only
			STATUS mandatory
			DESCRIPTION
				"Attribute describing the number of the bus on which management data
				are reported."
			::= { chLntAgEntry 7 }

--     1.3.6.1.4.1.81.7.9.2.1.8
		chLntAgCoprocCommStatus OBJECT-TYPE
			SYNTAX INTEGER
				{
				ok(1),
				commProblems(2),
				timeout(3),
				notSupported(255)
				}
			ACCESS read-only
			STATUS mandatory
			DESCRIPTION
				"Attribute describing the status of the communication between the
				agent and its coprocessor."
			::= { chLntAgEntry 8 }

--     1.3.6.1.4.1.81.7.9.2.1.9
		chLntAgCommDebugMode OBJECT-TYPE
			SYNTAX INTEGER
				{
				on(1),
				off(2)
				}
			ACCESS read-write
			STATUS deprecated
			DESCRIPTION
				"Attribute describing the agent mode in which communication problem
				traps are sent to managers (value 'on') or are not sent to managers
				(value 'off')."
			DEFVAL { off }
			::= { chLntAgEntry 9 }

--     1.3.6.1.4.1.81.7.9.2.1.10
		chLntAgConfigChangeTraps OBJECT-TYPE
			SYNTAX INTEGER
				{
				enabled(1),
				disabled(2)
				}
			ACCESS read-write
			STATUS mandatory
			DESCRIPTION
				"The value of this attributes determines whether or not the agent
				sends Configuration Change traps to the manager."
			DEFVAL { enabled }
			::= { chLntAgEntry 10 }

--     1.3.6.1.4.1.81.7.9.2.1.11
		chLntAgFaultTraps OBJECT-TYPE
			SYNTAX INTEGER
				{
				enabled(1),
				disabled(2)
				}
			ACCESS read-write
			STATUS mandatory
			DESCRIPTION
				"The value of this attributes determines whether or not the agent
				sends Fault traps to the manager."
			DEFVAL { enabled }
			::= { chLntAgEntry 11 }

--     1.3.6.1.4.1.81.7.9.2.1.12
		chLntAgTrafficThreshTraps OBJECT-TYPE
			SYNTAX INTEGER
				{
				enabled(1),
				disabled(2)
				}
			ACCESS read-write
			STATUS mandatory
			DESCRIPTION
				"The value of this attributes determines whether or not the agent
				sends Traffic Threshold traps to the manager."
			DEFVAL { enabled }
			::= { chLntAgEntry 12 }

--     1.3.6.1.4.1.81.7.9.2.1.13
		chLntAgGroupEnrollDeenrollTraps OBJECT-TYPE
			SYNTAX INTEGER
				{
				enabled(1),
				disabled(2)
				}
			ACCESS read-write
			STATUS mandatory
			DESCRIPTION
				"The value of this attributes determines whether or not the agent
				sends Group Enrollment and Group Deenrollment traps to the manager."
			DEFVAL { enabled }
			::= { chLntAgEntry 13 }

--     1.3.6.1.4.1.81.7.9.2.1.14
		chLntAgSoftFaultTraps OBJECT-TYPE
			SYNTAX INTEGER
				{
				enabled(1),
				disabled(2)
				}
			ACCESS read-write
			STATUS mandatory
			DESCRIPTION
				"The value of this attributes determines whether or not the agent
				sends Software Fault traps to the manager."
			::= { chLntAgEntry 14 }

--     1.3.6.1.4.1.81.7.9.2.1.15
		chLntAgHubEnrollTraps OBJECT-TYPE
			SYNTAX INTEGER
				{
				enabled(1),
				disabled(2)
				}
			ACCESS read-write
			STATUS obsolete
			DESCRIPTION
				"The value of this attributes determines whether or not the agent
				sends periodic Hub Enrollment traps to the manager."
			DEFVAL { enabled }
			::= { chLntAgEntry 15 }

--     1.3.6.1.4.1.81.7.9.2.1.16
		chLntAgTempThreshTraps OBJECT-TYPE
			SYNTAX INTEGER
				{
				enabled(1),
				disabled(2)
				}
			ACCESS read-write
			STATUS mandatory
			DESCRIPTION
				"The value of this attributes determines whether or not the agent
				sends Temperature Threshold traps to the manager."
			DEFVAL { disabled }
			::= { chLntAgEntry 16 }

--     1.3.6.1.4.1.81.7.9.2.1.17
		chLntAgSpecificOID OBJECT-TYPE
			SYNTAX OBJECT IDENTIFIER
			ACCESS read-only
			STATUS mandatory
			DESCRIPTION
				"This attribute provides the OID of another group containing
				additional more specific information regarding this instance."
			::= { chLntAgEntry 17 }

--     1.3.6.1.4.1.81.7.9.2.1.18
		chLntAgLastAddrConfig OBJECT-TYPE
			SYNTAX OCTET STRING
			ACCESS read-only
			STATUS deprecated
			DESCRIPTION
				"Configuration attribute describing the last physical address detected
				at each port. Coded in internal	application format. "
			::= { chLntAgEntry 18 }

--     1.3.6.1.4.1.81.7.9.2.1.19
		chLntAgSecAddrConfig OBJECT-TYPE
			SYNTAX OCTET STRING
			ACCESS read-only
			STATUS deprecated
			DESCRIPTION
				"Configuration attribute describing the configuration of the secure
				addresses. Coded in internal  application format. "
			::= { chLntAgEntry 19 }

--     1.3.6.1.4.1.81.7.9.2.1.20
		chLntAgSoftwareStatus OBJECT-TYPE
			SYNTAX INTEGER
				{
				unLoadable(1),
				loaded(2),
				downLoading(3),
				downLoadOfDownload(4),
				notSupported(255)
				}
			ACCESS read-write
			STATUS mandatory
			DESCRIPTION
				"Describes configuration of the firmware on this agent.
				unLoadable(1) - is returned by agents which do not support the Software
				Download feature;
				loaded(2) - is returned by agents with loaded software;
				downLoading(3) - when the attribute is set to this value by manager,
				it triggers the Software Download procedure. When procedure finished,
				agent software will reestablish value 'loaded(2)'.
				downLoadOfDownload (4) - when the attribute is set to this value by manager,
				it causes the Agent to download the new download software.
				When procedure finished, agent software will reestablish value 'loaded(2)'."
			::= { chLntAgEntry 20 }

--     1.3.6.1.4.1.81.7.9.2.1.21
		chLntAgConfigurationSymbol OBJECT-TYPE
			SYNTAX DisplayString (SIZE (1))
			ACCESS read-write
			STATUS mandatory
			DESCRIPTION
				"Defines the Configuration Symbol attached to any hardware module
				manufactured. One single character A..Z defines the CS
				version. For older modules which did not support this option on
				SNMP character '*' will be returned."
			::= { chLntAgEntry 21 }

--     1.3.6.1.4.1.81.7.9.2.1.22
		chLntAgIntTemp OBJECT-TYPE
			SYNTAX INTEGER
			ACCESS read-only
			STATUS mandatory
			DESCRIPTION
				"Internal temperature measured by the temperature sensor placed on the
				agent card. Expressed in Celsius degrees.Value  '999' means not supported."
			::= { chLntAgEntry 22 }

--     1.3.6.1.4.1.81.7.9.2.1.23
		chLntAgBootVersion OBJECT-TYPE
			SYNTAX DisplayString
			ACCESS read-only
			STATUS mandatory
			DESCRIPTION
				"ASCII string for description and display of the agent boot software
				version."
			::= { chLntAgEntry 23 }

--     Agent 6.0
-- 1.3.6.1.4.1.81.7.9.2.1.24
		chLntAgSensorFault OBJECT-TYPE
			SYNTAX INTEGER
			ACCESS read-only
			STATUS deprecated
			DESCRIPTION
				"A code of a sensor fault discovered by the agent."
			::= { chLntAgEntry 24 }

--     1.3.6.1.4.1.81.7.9.2.1.25
		chLntAgSensorFaultTraps OBJECT-TYPE
			SYNTAX INTEGER
				{
				enabled(1),
				disabled(2)
				}
			ACCESS read-write
			STATUS deprecated
			DESCRIPTION
				"This attribute enables/disables generation of the sensor fault
				trap."
			::= { chLntAgEntry 25 }

--     1.3.6.1.4.1.81.7.9.2.1.26
		chLntAgInterProcFault OBJECT-TYPE
			SYNTAX INTEGER
			ACCESS read-only
			STATUS deprecated
			DESCRIPTION
				"A code of intercommunication fault between Main - Master processors."
			::= { chLntAgEntry 26 }

--     1.3.6.1.4.1.81.7.9.2.1.27
		chLntAgInterProcFaultTraps OBJECT-TYPE
			SYNTAX INTEGER
				{
				enabled(1),
				disabled(2)
				}
			ACCESS read-write
			STATUS deprecated
			DESCRIPTION
				"This attribute enables/disables generation of the intercommunication
				fault trap."
			::= { chLntAgEntry 27 }

--     1.3.6.1.4.1.81.7.9.2.1.28
		chLntAgPSUVoltThrsTraps OBJECT-TYPE
			SYNTAX INTEGER
				{
				enabled(1),
				disabled(2)
				}
			ACCESS read-write
			STATUS mandatory
			DESCRIPTION
				"The value of this attribute determines whether or not the agent sends PSU
				voltage threshold traps to the manager."
			DEFVAL { enabled }
			::= { chLntAgEntry 28 }

--     1.3.6.1.4.1.81.7.9.2.1.29
		chLntAgHardwareVersion OBJECT-TYPE
			SYNTAX DisplayString
			ACCESS read-only
			STATUS mandatory
			DESCRIPTION
				"ASCII string for description and display of the agent hardware
				version."
			::= { chLntAgEntry 29 }

--     1.3.6.1.4.1.81.7.9.2.1.30
		chLntAgSoftwareDscr OBJECT-TYPE
			SYNTAX DisplayString
			ACCESS read-only
			STATUS mandatory
			DESCRIPTION
				"ASCII string for description and display of the agent software
				information."
			::= { chLntAgEntry 30 }

--     1.3.6.1.4.1.81.7.9.2.1.31
		chLntAgCAMChangeTraps OBJECT-TYPE
			SYNTAX INTEGER
				{
				enabled(1),
				disabled(2)
				}
			ACCESS read-write
			STATUS mandatory
			DESCRIPTION
				"The value of this attribute determines whether or not the agent sends CAM
				last change traps to the manager."
			DEFVAL { enabled }
			::= { chLntAgEntry 31 }

--     1.3.6.1.4.1.81.7.9.2.1.32
		chLntAgAppVersion OBJECT-TYPE
			SYNTAX DisplayString
			ACCESS read-only
			STATUS mandatory
			DESCRIPTION
				"ASCII string for description and display of the agent's
				application version. e.g. software running top of the Kernel"
			::= { chLntAgEntry 32 }

--     Agent 6.0
-- 1.3.6.1.4.1.81.7.9.3
		chLntAgSetup OBJECT IDENTIFIER ::= { chAg 3 }

--     1.3.6.1.4.1.81.7.9.3.1
		chLntAgMaxNmbOfMngrs OBJECT-TYPE
			SYNTAX INTEGER
			ACCESS read-only
			STATUS mandatory
			DESCRIPTION
				"Maximum number of permanent managers."
			::= { chLntAgSetup 1 }

--     1.3.6.1.4.1.81.7.9.3.2
		chLntAgPermMngrTable OBJECT-TYPE
			SYNTAX SEQUENCE OF ChLntAgPermMngrEntry
			ACCESS not-accessible
			STATUS mandatory
			DESCRIPTION
				"Table of permanent managers.
				The Agent will send Traps to managers listed in the
				chLntAgPermMngrTable. A Trap will be send to the manager
				according to the Trap Enable/Disable flag related to the Trap.
				A permanent manager will be defined by the user, through the
				Agent setup procedure, or by SNMP request. "
			::= { chLntAgSetup 2 }

--     1.3.6.1.4.1.81.7.9.3.2.1
		chLntAgPermMngrEntry OBJECT-TYPE
			SYNTAX ChLntAgPermMngrEntry
			ACCESS not-accessible
			STATUS mandatory
			DESCRIPTION
				"An entry in the permanent managers table."
			INDEX { chLntAgPermMngrId }
			::= { chLntAgPermMngrTable 1 }

		ChLntAgPermMngrEntry ::=
			SEQUENCE {
				chLntAgPermMngrId
					INTEGER,
				chLntAgPermMngrAddr
					IpAddress,
				chLntAgMngrTraps
					INTEGER
			 }

--     1.3.6.1.4.1.81.7.9.3.2.1.1
		chLntAgPermMngrId OBJECT-TYPE
			SYNTAX INTEGER (1..65535)
			ACCESS read-only
			STATUS mandatory
			DESCRIPTION
				"Index in the permanent managers table. It ranges from 1 to chLntAgMaxNmbOfMngrs"
			::= { chLntAgPermMngrEntry 1 }

--     1.3.6.1.4.1.81.7.9.3.2.1.2
		chLntAgPermMngrAddr OBJECT-TYPE
			SYNTAX IpAddress
			ACCESS read-write
			STATUS mandatory
			DESCRIPTION
				"IP address of a permanent manager."
			::= { chLntAgPermMngrEntry 2 }

--     7.0 item
-- 1.3.6.1.4.1.81.7.9.3.2.1.3
		chLntAgMngrTraps OBJECT-TYPE
			SYNTAX INTEGER
				{
				on(1),
				off(2)
				}
			ACCESS read-write
			STATUS mandatory
			DESCRIPTION
				"Value 'on' indicates that SNMP agent should send SNMP traps (traffic
				excluded) to the manager."
			::= { chLntAgPermMngrEntry 3 }

--     1.3.6.1.4.1.81.7.9.3.3
		chLntAgMaxNmbOfNets OBJECT-TYPE
			SYNTAX INTEGER
			ACCESS read-only
			STATUS deprecated
			DESCRIPTION
				"Maximum number of remote networks."
			::= { chLntAgSetup 3 }

--     1.3.6.1.4.1.81.7.9.3.4
		chLntAgRmtNetTable OBJECT-TYPE
			SYNTAX SEQUENCE OF ChLntAgRmtNetEntry
			ACCESS not-accessible
			STATUS deprecated
			DESCRIPTION
				"Remote networks table."
			::= { chLntAgSetup 4 }

--     1.3.6.1.4.1.81.7.9.3.4.1
		chLntAgRmtNetEntry OBJECT-TYPE
			SYNTAX ChLntAgRmtNetEntry
			ACCESS not-accessible
			STATUS deprecated
			DESCRIPTION
				"Entry in the remote networks table."
			INDEX { chLntAgRmtNetId }
			::= { chLntAgRmtNetTable 1 }

		ChLntAgRmtNetEntry ::=
			SEQUENCE {
				chLntAgRmtNetId
					INTEGER,
				chLntAgRmtNetAddr
					IpAddress,
				chLntAgRmtNetMask
					IpAddress
			 }

--     1.3.6.1.4.1.81.7.9.3.4.1.1
		chLntAgRmtNetId OBJECT-TYPE
			SYNTAX INTEGER (1..65535)
			ACCESS read-only
			STATUS deprecated
			DESCRIPTION
				"Index of a remote network. It ranges from 1 to chLntAgMaxNmbOfNets."
			::= { chLntAgRmtNetEntry 1 }

--     1.3.6.1.4.1.81.7.9.3.4.1.2
		chLntAgRmtNetAddr OBJECT-TYPE
			SYNTAX IpAddress
			ACCESS read-write
			STATUS deprecated
			DESCRIPTION
				"Address of a remote network. The host portion is always 0."
			::= { chLntAgRmtNetEntry 2 }

--     1.3.6.1.4.1.81.7.9.3.4.1.3
		chLntAgRmtNetMask OBJECT-TYPE
			SYNTAX IpAddress
			ACCESS read-write
			STATUS deprecated
			DESCRIPTION
				"Subnet mask for the remote network."
			::= { chLntAgRmtNetEntry 3 }

--     1.3.6.1.4.1.81.7.9.3.5
		chLntAgDateTime OBJECT-TYPE
			SYNTAX DisplayString (SIZE (13))
			ACCESS read-write
			STATUS deprecated
			DESCRIPTION
				"Current date and time for NMA-TR.
				The format is YYMMDDhhmmssw,
				where w - day of the week e.g., 1=Mon, 2=Tue,..., 7=Sun."
			::= { chLntAgSetup 5 }

--     1.3.6.1.4.1.81.7.9.3.6
		chLntAgReset OBJECT-TYPE
			SYNTAX INTEGER
				{
				on(1),
				off(2)
				}
			ACCESS read-write
			STATUS mandatory
			DESCRIPTION
				"This attribute enables the user to reset the agent."
			::= { chLntAgSetup 6 }

--     1.3.6.1.4.1.81.7.9.3.7
		chLntAgTrapsTable OBJECT-TYPE
			SYNTAX SEQUENCE OF ChLntAgTrapsEntry
			ACCESS not-accessible
			STATUS mandatory
			DESCRIPTION
				"Table of traps for each permanent manager.
				A Trap will be send to the manager according to the Trap
				Enable/Disable flag related to the Trap ID.
				When adding a new manager to the permanent managers
				table, the Agent will set its entry in this table with the
				default value for each trap flag. "
			::= { chLntAgSetup 7 }

--     1.3.6.1.4.1.81.7.9.3.7.1
		chLntAgTrapsEntry OBJECT-TYPE
			SYNTAX ChLntAgTrapsEntry
			ACCESS not-accessible
			STATUS mandatory
			DESCRIPTION
				"An entry in the permanent managers table."
			INDEX { chLntAgPermMngrId, chLntAgTrapsId }
			::= { chLntAgTrapsTable 1 }

		ChLntAgTrapsEntry ::=
			SEQUENCE {
				chLntAgTrapsPermMngrId
					INTEGER,
				chLntAgTrapsId
					INTEGER,
				chLntAgTrapsEnableFlag
					INTEGER
			 }

--     1.3.6.1.4.1.81.7.9.3.7.1.1
		chLntAgTrapsPermMngrId OBJECT-TYPE
			SYNTAX INTEGER
			ACCESS read-only
			STATUS mandatory
			DESCRIPTION
				"Index in the permanent managers traps table.
				It ranges from 1 to chLntAgMaxNmbOfMngrs"
			::= { chLntAgTrapsEntry 1 }

--     1.3.6.1.4.1.81.7.9.3.7.1.2
		chLntAgTrapsId OBJECT-TYPE
			SYNTAX INTEGER (1..65535)
			ACCESS read-only
			STATUS mandatory
			DESCRIPTION
				"The trap number is the second index in the table.
				The following list conclude the available traps numbers to be
				configured by the manager:
				1: Configuration Change Traps. Default = enabled(1).
				2: Fault Traps. Default = enabled(1).
				3: Traffic Threshold Exceeded Traps. Default = enabled(1).
				4:  Group DeEnrollment Trap. Default = enabled(1).
				6: Agent SW Fault Trap. Default = enabled(1).
				8: Hub Enrollment Trap. Default = enabled(1).
				14: Temperature Warning Traps. Default = disabled(2).
				19: PSU Existance Trap. Default = disabled(2).
				22: VNS. Default = disabled(2).
				"
			::= { chLntAgTrapsEntry 2 }

--     1.3.6.1.4.1.81.7.9.3.7.1.3
		chLntAgTrapsEnableFlag OBJECT-TYPE
			SYNTAX INTEGER
				{
				enabled(1),
				disabled(2)
				}
			ACCESS read-write
			STATUS mandatory
			DESCRIPTION
				"The value of this attributes determines whether or not the agent
				sends the traps to the manager."
			::= { chLntAgTrapsEntry 3 }

--     1.3.6.1.4.1.81.7.9.3.8
		chLntAgTicksPerSecond OBJECT-TYPE
			SYNTAX INTEGER
			ACCESS read-only
			STATUS mandatory
			DESCRIPTION
				" defines how many ticks are counted in one second."
			::= { chLntAgSetup 8 }

--     1.3.6.1.4.1.81.7.9.3.100
		chLntAgMaxTrapsNumber OBJECT-TYPE
			SYNTAX INTEGER
			ACCESS read-write
			STATUS mandatory
			DESCRIPTION
				"This attribute define the muximum trap number supported by the agent."
			::= { chLntAgSetup 100 }

--     1.3.6.1.4.1.81.7.9.4
		chAgHubMgmtIfType OBJECT-TYPE
			SYNTAX INTEGER
				{
				none(1),
				regular1822(2),
				hdh1822(3),
				ddn-x25(4),
				rfc877-x25(5),
				ethernet-csmacd(6),
				iso88023-csmacd(7),
				iso88024-tokenBus(8),
				iso88025-tokenRing(9),
				iso88026-man(10),
				starLan(11),
				proteon-10MBit(12),
				proteon-80MBit(13),
				hyperchannel(14),
				fddi(15),
				lapb(16),
				sdlc(17),
				t1-carrier(18),
				cept(19),
				basicIsdn(20),
				primaryIsdn(21),
				propPointToPointSerial(22),
				ppp(23),
				softwareLoopback(24),
				eon(25),
				ethernet-3Mbit(26),
				nsip(27),
				slip(28),
				ultra(29),
				ds3(30),
				sip(31),
				frameRelay(32),
				rs232(33),
				para(34),
				arcnet(35),
				arcnetPlus(36),
				atm(37),
				miox25(38),
				sonet(39),
				x25ple(40),
				iso88022llc(41),
				localTalk(42),
				smdsDxi(43),
				frameRelayService(44),
				v35(45),
				hssi(46),
				hippi(47),
				modem(48),
				aal5(49),
				sonetPath(50),
				sonetVT(51),
				smdsIcip(52),
				propVirtual(53),
				propMultiplexor(54),
				ip(255)
				}
			ACCESS read-only
			STATUS mandatory
			DESCRIPTION
				"This attribute describes one of the interfaces of agents existing on
				modules and their type. Value 'none' defines the lack of
				an interface whose type is recognized by the management console.
				Any other value defines an interface whose type is recognized by
				the management console and may be used as a management channel."
			::= { chAg 4 }

--     1.3.6.1.4.1.81.7.9.5
		chAgHubAddr OBJECT-TYPE
			SYNTAX OCTET STRING (SIZE (0..20))
			ACCESS read-write
			STATUS mandatory
			DESCRIPTION
				"This attribute defines an unique address by which the agent may be
				addressed by the management console. The address format should be
				consistent with the type defined by chAgHubMgmtIfType."
			::= { chAg 5 }

--     Managers group
-- includes attributes which define the manager stations for the agent software
-- while internally organized as a table, only one row (its own) is visible
-- for each manager, so, externally, from SNMP point of view it is not
-- represented as a table.
-- 1.3.6.1.4.1.81.7.10
		chMgr OBJECT IDENTIFIER ::= { chassis 10 }

--     1.3.6.1.4.1.81.7.10.1
		chMgrTrapRepStatus OBJECT-TYPE
			SYNTAX INTEGER
				{
				on(1),
				off(2)
				}
			ACCESS read-write
			STATUS deprecated
			DESCRIPTION
				"Value 'on' indicates that SNMP agent should send SNMP traps (traffic ex-
				cluded) to the manager."
			::= { chMgr 1 }

--     1.3.6.1.4.1.81.7.10.2
		chMgrContPerfRep OBJECT-TYPE
			SYNTAX INTEGER
				{
				on(1),
				off(2)
				}
			ACCESS read-write
			STATUS deprecated
			DESCRIPTION
				"Value 'on' indicates that the SNMP agent should send traffic SNMP traps
				to the manager."
			::= { chMgr 2 }

--     1.3.6.1.4.1.81.7.10.3
		chMgrMngmtState OBJECT-TYPE
			SYNTAX INTEGER
				{
				on(1),
				off(2)
				}
			ACCESS read-write
			STATUS deprecated
			DESCRIPTION
				"Attribute to be set by manager in order to instruct the agent
				to enter into a management session with the console.
				Setting this value to 'on' has the effect of performing
				an 'I am your manager' action upon the agent."
			::= { chMgr 3 }

--     1.3.6.1.4.1.81.7.10.4
		chMgrPollInterval OBJECT-TYPE
			SYNTAX INTEGER
			ACCESS read-write
			STATUS deprecated
			DESCRIPTION
				"The attribute defines an interval during which the agent is waiting
				for the manager's requests. Default value 5 minutes."
			DEFVAL { 5 }
			::= { chMgr 4 }

--     Chassis Hardware group
-- This group defines the Hardware capability of the Hubs (PSU, Temprature and FANs)
-- 1.3.6.1.4.1.81.7.11
		chHW OBJECT IDENTIFIER ::= { chassis 11 }

--     1.3.6.1.4.1.81.7.11.1
		chHWPSUTable OBJECT-TYPE
			SYNTAX SEQUENCE OF ChHWPSUEntry
			ACCESS not-accessible
			STATUS mandatory
			DESCRIPTION
				"Table of configuration attributes for Power Supply Units.
				This table can be retrieved only from agents equipped with adequate hardware."
			::= { chHW 1 }

--     1.3.6.1.4.1.81.7.11.1.1
		chHWPSUEntry OBJECT-TYPE
			SYNTAX ChHWPSUEntry
			ACCESS not-accessible
			STATUS mandatory
			DESCRIPTION
				"An entry in the table, containing configuration attributes for a single
				Power Supply Unit."
			INDEX { chHWPSUId }
			::= { chHWPSUTable 1 }

		ChHWPSUEntry ::=
			SEQUENCE {
				chHWPSUId
					INTEGER,
				chHWPSUActivityStatus
					INTEGER,
				chHWPSULocation
					INTEGER,
				chHWPSUVoltage
					INTEGER,
				chHWPSUVoltHighThresh
					INTEGER,
				chHWPSUVoltLowThresh
					INTEGER,
				chHWPSUCapacity
					INTEGER,
				chHWPSUConsumption
					INTEGER,
				chHWPSUType
					INTEGER,
				chHWPSUTypeName
					DisplayString,
				chHWPSUDescr
					DisplayString,
				chHWPSUPoECapacity
					INTEGER,
				chHWPSUPoEConsumption
					INTEGER
			 }

--     1.3.6.1.4.1.81.7.11.1.1.1
		chHWPSUId OBJECT-TYPE
			SYNTAX INTEGER (1..255)
			ACCESS read-only
			STATUS mandatory
			DESCRIPTION
				"PSU index for identifying the PSU.
				The index for each hub:
				Stackable: odd number - internal, even number - backup
				LET 36: 1 - lower; 2 - higher,
				LET 20: 1 - right; 2 - left,
				LET 10: 1 - main; 2 - backup.

				For modular switches this attribute displays the PSU number."
			::= { chHWPSUEntry 1 }

--     1.3.6.1.4.1.81.7.11.1.1.2
		chHWPSUActivityStatus OBJECT-TYPE
			SYNTAX INTEGER
				{
				notActive(1),
				dormant(2),
				active(3),
				failed(4),
				unknown(5),
				notExist(6),
				noBackupPS(7)
				}
			ACCESS read-only
			STATUS mandatory
			DESCRIPTION
				"This attribute defines the status of the PSU in what concerns
				supplying power to the chassis.
				NotActive(1) - indicates a disabled or defective PSU which cannot supply
				 power to the chassis.
				Dormant(2) - indicates a functional PSU which is installed for backup
				  purposes and can at any moment supply power to the devices in the chassis.
				Active(3) - indicates that the PSU supplies power to the chassis.
				Failed(4) - indicates PSU failure (new LET-36 and LET-20).
				Unknown(5) - when the PSU activity is not readable or unknown.
				NotExist(6) - indicates absence of PSU from the configuration.
				NoBackupPS(7) - indicates absence of  Backup PSU from the configuration.
				The following values are supported for each hub:
				Stack: active, failed, notExist, noBackupPS
				LET-36: active, failed, notExist.
				LET-20: active, failed, notExist.
				LET-10: active, failed, unknown."
			::= { chHWPSUEntry 2 }

--     1.3.6.1.4.1.81.7.11.1.1.3
		chHWPSULocation OBJECT-TYPE
			SYNTAX INTEGER
				{
				other(1),
				internal(2),
				external(3),
				right(4),
				left(5),
				lower(6),
				upper(7),
				unknown(8),
				notExist(9),
				middle(10)
				}
			ACCESS read-only
			STATUS mandatory
			DESCRIPTION
				"Describes the location of the PSU:
				LET-36: lower, upper.
				LET-20: right, left.
				LET-10: unknown."
			::= { chHWPSUEntry 3 }

--     1.3.6.1.4.1.81.7.11.1.1.4
		chHWPSUVoltage OBJECT-TYPE
			SYNTAX INTEGER
			ACCESS read-only
			STATUS mandatory
			DESCRIPTION
				"Indicates voltage of PSU expressed in milliVolts."
			::= { chHWPSUEntry 4 }

--     1.3.6.1.4.1.81.7.11.1.1.5
		chHWPSUVoltHighThresh OBJECT-TYPE
			SYNTAX INTEGER
			ACCESS read-only
			STATUS mandatory
			DESCRIPTION
				"Indicates voltage High threshold of the PSU in the HUB.
				The PSU output working voltage needed to support a module
				in the HUB should be V +/- 5%. This value is hard-coded.
				The Agent will Trap the manager when the PSU will exceed
				the chHWPSUVoltHighThresh."
			::= { chHWPSUEntry 5 }

--     1.3.6.1.4.1.81.7.11.1.1.6
		chHWPSUVoltLowThresh OBJECT-TYPE
			SYNTAX INTEGER
			ACCESS read-only
			STATUS mandatory
			DESCRIPTION
				"Indicates voltage Low threshold of the PSU in the HUB.
				The PSU output working voltage needed to support a module
				in the HUB should be V +/- 5%. This value is hard-coded.
				The Agent will Trap the manager when the PSU will 'dive' lower
				than the chHWPSUVoltLowThresh ."
			::= { chHWPSUEntry 6 }

--     1.3.6.1.4.1.81.7.11.1.1.7
		chHWPSUCapacity OBJECT-TYPE
			SYNTAX INTEGER
			ACCESS read-only
			STATUS mandatory
			DESCRIPTION
				"Indicates the maximum of electrical power of PSU
				expressed in milliWatts."
			::= { chHWPSUEntry 7 }

--     1.3.6.1.4.1.81.7.11.1.1.8
		chHWPSUConsumption OBJECT-TYPE
			SYNTAX INTEGER
			ACCESS read-only
			STATUS mandatory
			DESCRIPTION
				"Indicates the consumption of electrical power of PSU
				expressed in milliWatts."
			::= { chHWPSUEntry 8 }

--     1.3.6.1.4.1.81.7.11.1.1.9
		chHWPSUType OBJECT-TYPE
			SYNTAX INTEGER
				{
				avayaC460-MPS4603-AC(1),
				avayaC460-MPS4610-AC(2),
				unknown(255)
				}
			ACCESS read-only
			STATUS mandatory
			DESCRIPTION
				"Attribute describing the type of the PSU."
			::= { chHWPSUEntry 9 }

--     1.3.6.1.4.1.81.7.11.1.1.10
		chHWPSUTypeName OBJECT-TYPE
			SYNTAX DisplayString (SIZE (0..32))
			ACCESS read-only
			STATUS mandatory
			DESCRIPTION
				"String with the power supply name."
			::= { chHWPSUEntry 10 }

--     1.3.6.1.4.1.81.7.11.1.1.11
		chHWPSUDescr OBJECT-TYPE
			SYNTAX DisplayString
			ACCESS read-only
			STATUS mandatory
			DESCRIPTION
				"Descriptor of the PSU in ASCII format."
			::= { chHWPSUEntry 11 }

--     1.3.6.1.4.1.81.7.11.1.1.12
		chHWPSUPoECapacity OBJECT-TYPE
			SYNTAX INTEGER
			ACCESS read-only
			STATUS mandatory
			DESCRIPTION
				"Indicates the maximum PoE power in milliwatts
				provided by this PSU."
			::= { chHWPSUEntry 12 }

--     1.3.6.1.4.1.81.7.11.1.1.13
		chHWPSUPoEConsumption OBJECT-TYPE
			SYNTAX INTEGER
			ACCESS read-only
			STATUS mandatory
			DESCRIPTION
				"Indicates the PoE power consumption in milliwatts
				drawn from this PSU."
			::= { chHWPSUEntry 13 }

--     1.3.6.1.4.1.81.7.11.2
		chHWIntTempWarning OBJECT-TYPE
			SYNTAX INTEGER
				{
				ok(1),
				exceeded(2)
				}
			ACCESS read-only
			STATUS mandatory
			DESCRIPTION
				"Fault condition indicating that the temperature measured by one of the
				sensors internal to the box exceeded chHWIntTempThresh."
			::= { chHW 2 }

--     1.3.6.1.4.1.81.7.11.3
		chHWIntTempThresh OBJECT-TYPE
			SYNTAX INTEGER
			ACCESS read-only
			STATUS mandatory
			DESCRIPTION
				"Internal enclosure temperature threshold value, expressed in
				degrees Celsius.  When exceeded, a trap is sent to the management console. "
			::= { chHW 3 }

--     1.3.6.1.4.1.81.7.11.4
		chHWPeakIntTemp OBJECT-TYPE
			SYNTAX INTEGER
			ACCESS read-only
			STATUS mandatory
			DESCRIPTION
				"Maximum internal temperature inside the chassis. It is the maximum
				of the temperature values detected by different temperature sensors
				inside the box. "
			::= { chHW 4 }

--     1.3.6.1.4.1.81.7.11.5
		chHWFans OBJECT-TYPE
			SYNTAX INTEGER
				{
				exist(1),
				notExist(2),
				oneFanFailed(3),
				moreThanOneFanFailed(4),
				notSupported(255)
				}
			ACCESS read-only
			STATUS mandatory
			DESCRIPTION
				"This attribute describes the existence/absence and
				status of the fans in a hub."
			::= { chHW 5 }

--     1.3.6.1.4.1.81.7.11.6
		chHWPower OBJECT IDENTIFIER ::= { chHW 6 }

--     1.3.6.1.4.1.81.7.11.6.1
		chHWPowerTable OBJECT-TYPE
			SYNTAX SEQUENCE OF ChHWPowerEntry
			ACCESS not-accessible
			STATUS mandatory
			DESCRIPTION
				"Table of configuration attributes for power
				management."
			::= { chHWPower 1 }

--     1.3.6.1.4.1.81.7.11.6.1.1
		chHWPowerEntry OBJECT-TYPE
			SYNTAX ChHWPowerEntry
			ACCESS not-accessible
			STATUS mandatory
			INDEX { chHWPowerSlotId }
			::= { chHWPowerTable 1 }

		ChHWPowerEntry ::=
			SEQUENCE {
				chHWPowerSlotId
					INTEGER,
				chHWPowerModType
					INTEGER,
				chHWPowerModTypeName
					DisplayString,
				chHWPowerActive
					INTEGER,
				chHWPowerEnable
					INTEGER,
				chHWPowerHistory
					INTEGER,
				chHWPowerDemand
					INTEGER,
				chHWPowerPriority
					INTEGER,
				chHWPowerPoEBudget
					INTEGER,
				chHWPowerPoEDemand
					INTEGER
			 }

--     1.3.6.1.4.1.81.7.11.6.1.1.1
		chHWPowerSlotId OBJECT-TYPE
			SYNTAX INTEGER (1..16)
			ACCESS read-only
			STATUS mandatory
			DESCRIPTION
				"Index, which identifies the slot inside the chassis
				for which this entry contains information.
				The number of entries in this table is equal to
				chNumberOfSlots."
			::= { chHWPowerEntry 1 }

--     1.3.6.1.4.1.81.7.11.6.1.1.2
		chHWPowerModType OBJECT-TYPE
			SYNTAX INTEGER
				{
				emptySlot(254),
				unknown(255),
				avayaC460-M460ML-SPV(2600),
				avayaC460-M4648ML-T(2601),
				avayaC460-M4648ML-T-2G(2602),
				avayaC460-M4612ML-G(2603),
				avayaC460-M4648ML-T-PWR(2604),
				avayaC460-M4648ML-T-PWR-2G(2605)
				}
			ACCESS read-only
			STATUS mandatory
			DESCRIPTION
				"Attribute describing the type of the module.
				Values in this attribute are the same as genGroupType
				but applicable also for un-powered modules and empty
				slots."
			::= { chHWPowerEntry 2 }

--     1.3.6.1.4.1.81.7.11.6.1.1.3
		chHWPowerModTypeName OBJECT-TYPE
			SYNTAX DisplayString (SIZE (0..32))
			ACCESS read-only
			STATUS mandatory
			DESCRIPTION
				"String with the module name the same as
				genGroupTypeName but applicable also for
				un-powered modules and empty slots."
			::= { chHWPowerEntry 3 }

--     1.3.6.1.4.1.81.7.11.6.1.1.4
		chHWPowerActive OBJECT-TYPE
			SYNTAX INTEGER
				{
				yes(1),
				no(2)
				}
			ACCESS read-only
			STATUS mandatory
			DESCRIPTION
				"This object has a value of yes(1) if the module
				installed in this slot is powered up.

				This object has a value of no(2) when the module is
				powered down or the slot is empty."
			::= { chHWPowerEntry 4 }

--     1.3.6.1.4.1.81.7.11.6.1.1.5
		chHWPowerEnable OBJECT-TYPE
			SYNTAX INTEGER
				{
				enable(1),
				disable(2)
				}
			ACCESS read-write
			STATUS mandatory
			DESCRIPTION
				"Setting the value of this attribute to enable(1)
				enables the power for this slot.
				When this attribute is set to disable(2),
				the power for this slot is disabled."
			::= { chHWPowerEntry 5 }

--     1.3.6.1.4.1.81.7.11.6.1.1.6
		chHWPowerHistory OBJECT-TYPE
			SYNTAX INTEGER
				{
				yes(1),
				no(2)
				}
			ACCESS read-write
			STATUS mandatory
			DESCRIPTION
				"This object has a value of yes(1) if the module
				installed in this slot has power history.

				This object has a value of no(2) when the module has not
				power history.

				Modules with power history set to on have higher
				priority than modules with power history set to off."
			::= { chHWPowerEntry 6 }

--     1.3.6.1.4.1.81.7.11.6.1.1.7
		chHWPowerDemand OBJECT-TYPE
			SYNTAX INTEGER
			ACCESS read-only
			STATUS mandatory
			DESCRIPTION
				"Indicates total electrical power consumption for the
				module installed in this slot expressed in milliWatts.

				Returns zero if the slot is empty."
			::= { chHWPowerEntry 7 }

--     1.3.6.1.4.1.81.7.11.6.1.1.8
		chHWPowerPriority OBJECT-TYPE
			SYNTAX INTEGER
				{
				critical(1),
				high(2),
				low(3)
				}
			ACCESS read-write
			STATUS mandatory
			DESCRIPTION
				"This parameter controls the powering priority of the module
				and is used by power budget management algorithm."
			::= { chHWPowerEntry 8 }

--     1.3.6.1.4.1.81.7.11.6.1.1.9
		chHWPowerPoEBudget OBJECT-TYPE
			SYNTAX INTEGER
			ACCESS read-only
			STATUS mandatory
			DESCRIPTION
				"This parameter indicates the PoE budget in milliwatts
				allocated for this module."
			::= { chHWPowerEntry 9 }

--     1.3.6.1.4.1.81.7.11.6.1.1.10
		chHWPowerPoEDemand OBJECT-TYPE
			SYNTAX INTEGER
			ACCESS read-only
			STATUS mandatory
			DESCRIPTION
				"This parameter indicates the PoE power consumption
				in milliwatts for this module."
			::= { chHWPowerEntry 10 }

--     1.3.6.1.4.1.81.7.11.6.2
		chHWPowerConfiguration OBJECT-TYPE
			SYNTAX INTEGER
				{
				redundant(1),
				noRedundancy(2),
				unknown(3)
				}
			ACCESS read-only
			STATUS mandatory
			DESCRIPTION
				"Indicates the redundancy configuration
				of power supplies installed in the switch."
			::= { chHWPower 2 }

--     1.3.6.1.4.1.81.7.11.6.3
		chHWPowerCapacity OBJECT-TYPE
			SYNTAX INTEGER
			ACCESS read-only
			STATUS mandatory
			DESCRIPTION
				"Indicates total electrical power available
				for the switch expressed in milliWatts."
			::= { chHWPower 3 }

--     1.3.6.1.4.1.81.7.11.6.4
		chHWPowerConsumption OBJECT-TYPE
			SYNTAX INTEGER
			ACCESS read-only
			STATUS mandatory
			DESCRIPTION
				"Indicates total electrical power consumption
				for the switch expressed in milliWatts."
			::= { chHWPower 4 }

--     1.3.6.1.4.1.81.7.11.6.5
		chHWPowerRemain OBJECT-TYPE
			SYNTAX INTEGER
			ACCESS read-only
			STATUS mandatory
			DESCRIPTION
				"Indicates total electrical power remaining
				for the switch expressed in milliWatts."
			::= { chHWPower 5 }

--     1.3.6.1.4.1.81.7.11.6.6
		chHWPowerFans OBJECT-TYPE
			SYNTAX INTEGER
			ACCESS read-only
			STATUS mandatory
			DESCRIPTION
				"Indicates the consumption of electrical power
				for the chassis fans expressed in milliWatts."
			::= { chHWPower 6 }

--     1.3.6.1.4.1.81.7.11.6.7
		chHWPowerConfigurationAdmin OBJECT-TYPE
			SYNTAX INTEGER
				{
				redundant(1),
				noRedundancy(2)
				}
			ACCESS read-write
			STATUS mandatory
			DESCRIPTION
				"Defines the desired redundancy configuration
				of power supplies installed in the switch."
			::= { chHWPower 7 }

--     1.3.6.1.4.1.81.7.11.6.8
		chHWPoECapacity OBJECT-TYPE
			SYNTAX INTEGER
			ACCESS read-only
			STATUS mandatory
			DESCRIPTION
				"Indicates total PoE power available for the switch
				expressed in milliWatts."
			::= { chHWPower 8 }

--     1.3.6.1.4.1.81.7.11.6.9
		chHWPoEConsumption OBJECT-TYPE
			SYNTAX INTEGER
			ACCESS read-only
			STATUS mandatory
			DESCRIPTION
				"Indicates total PoE power consumption for the switch
				expressed in milliWatts."
			::= { chHWPower 9 }

--     1.3.6.1.4.1.81.7.11.6.10
		chHWPoERemain OBJECT-TYPE
			SYNTAX INTEGER
			ACCESS read-only
			STATUS mandatory
			DESCRIPTION
				"Indicates total PoE power remaining for the switch
				expressed in milliWatts."
			::= { chHWPower 10 }

--     1.3.6.1.4.1.81.7.11.6.11
		chHWPoEBudgetRecalc OBJECT-TYPE
			SYNTAX INTEGER
				{
				on(1),
				off(2)
				}
			ACCESS read-write
			STATUS mandatory
			DESCRIPTION
				"Setting the value of this attribute to on(1) initiates
				the PoE budget recalculation for entire switch.

				Always returns off(2) on get instruction."
			::= { chHWPower 11 }

--     1.3.6.1.4.1.81.7.12
		chSlotLastChange OBJECT-TYPE
			SYNTAX TimeTicks
			ACCESS read-only
			STATUS mandatory
			DESCRIPTION
				"This attribute contains the value of sysUpTime at the time any
				of the modules in the hub was enrolled/deenrolled.
				In addition it will be updated when a module is reset"
			::= { chassis 12 }

--     Alarms Group  new for 7.0
-- 1.3.6.1.4.1.81.7.13
		chAlarms OBJECT IDENTIFIER ::= { chassis 13 }

--     1.3.6.1.4.1.81.7.13.1
		alarmPolicyTable OBJECT-TYPE
			SYNTAX SEQUENCE OF AlarmPolicyEntry
			ACCESS not-accessible
			STATUS mandatory
			DESCRIPTION
				"A table containing the parameters that define the alarm policies."
			::= { chAlarms 1 }

--     1.3.6.1.4.1.81.7.13.1.1
		alarmPolicyEntry OBJECT-TYPE
			SYNTAX AlarmPolicyEntry
			ACCESS not-accessible
			STATUS mandatory
			DESCRIPTION
				"An entry that contains the definition of an alarm: threshold
				value, threshold type (rising/falling), sample time interval,
				sample type (delta or absolute value), and action policy."
			INDEX { alarmPolicyIndex }
			::= { alarmPolicyTable 1 }

		AlarmPolicyEntry ::=
			SEQUENCE {
				alarmPolicyIndex
					INTEGER,
				alarmPolicyParameterOID
					OBJECT IDENTIFIER,
				alarmPolicyRisingFalling
					INTEGER,
				alarmPolicyThresholdValue
					INTEGER,
				alarmPolicySampleTimeInterval
					INTEGER,
				alarmPolicySampleType
					INTEGER,
				alarmPolicyActionPolicy
					INTEGER,
				alarmPolicyBitmap
					OCTET STRING,
				alarmPolicyStatus
					INTEGER
			 }

--     1.3.6.1.4.1.81.7.13.1.1.1
		alarmPolicyIndex OBJECT-TYPE
			SYNTAX INTEGER (1..65535)
			ACCESS read-only
			STATUS mandatory
			DESCRIPTION
				"The value of this object identifies the alarmPolicy.
				It is also used in the VariableTable as a pointer from
				the sampled OID to the alarmPolicy defined on that
				item. This item uniquely identifies the policy and has
				a value between 1 and the maximum size of the table."
			::= { alarmPolicyEntry 1 }

--     1.3.6.1.4.1.81.7.13.1.1.2
		alarmPolicyParameterOID OBJECT-TYPE
			SYNTAX OBJECT IDENTIFIER
			ACCESS read-write
			STATUS mandatory
			DESCRIPTION
				"This variable defines the type of variable that this policy
				monitors. The value of the item is an non-instanciated OID
				from the following list:
					- chHWPeakIntTemp.
					- ethPortFramesReceivedOK.
					- ethPortRunts.
					- ethPortPacketErrors.
					- ethPortCollisions.
					- ethPortPartitions.
					- ethPortPygmys.
					- ethGroupTotalErrors.
					- ethBusTotalCollisions.
					- ethBusTotalPackets.
					- ethBusTotalErrors.
					- ethBusUtilization.
					- tokRingUtilization.
					- dot5StatsLostFrameErrors.
					- dot5StatsSoftErrors.
					- dot5StatsHardErrors.
					- lsBusStatsPkts.
					- lsBusStatsUtilization.
					- lsBusStatsEthBroadcastPkts.
					- lsBusStatsEthMulticastPkts.
					- lsBusStatsGoodEthPkts.
					- lsBusStatsBadEthPkts.
					- lsBusStatsNonEthPkts
					- lsBusStatsPriorityPkts	(1-4)
					- portInPkts.
					- portInTotalErrors.
				If the value of this item is not one of the above, or if it is
				one of the above but the item is not supported by the
				agent (such as a TR counter for a hub managed by an
				Ethernet agent), then when the row's status is changed
				to valid(1) a genErr will be returned."
			::= { alarmPolicyEntry 2 }

--     1.3.6.1.4.1.81.7.13.1.1.3
		alarmPolicyRisingFalling OBJECT-TYPE
			SYNTAX INTEGER
				{
				rising(1),
				falling(2)
				}
			ACCESS read-write
			STATUS mandatory
			DESCRIPTION
				"This value defines whether the policy is a rising alarm or
				a falling alarm. If the value of this item is rising(1), then
				the actionPolicy is executed if the value of the sampled variable
				is larger than the threshold. If the value of this item is
				falling(2), the actionPolicy is executed if the value of the
				sampled OID is smaller than or equal to the threshold."
			::= { alarmPolicyEntry 3 }

--     1.3.6.1.4.1.81.7.13.1.1.4
		alarmPolicyThresholdValue OBJECT-TYPE
			SYNTAX INTEGER
			ACCESS read-write
			STATUS mandatory
			DESCRIPTION
				"The threshold value of the alarmPolicy. If the reading of
				the sampled instance (according to the alarmPolicyType:
				delta or absolute value) is above or below the value of this
				item (according to alarmPolicyRisingFalling), the
				alarmPolicyActionPolicy is carried out."
			::= { alarmPolicyEntry 4 }

--     1.3.6.1.4.1.81.7.13.1.1.5
		alarmPolicySampleTimeInterval OBJECT-TYPE
			SYNTAX INTEGER
			ACCESS read-write
			STATUS mandatory
			DESCRIPTION
				"The time interval between two subsequent samples of the
				data, in seconds. All instances that are assigned to this policy
				are sampled once every TimeInterval. The value of this item
				must be a multiple of 10 and smaller than 10,000. The agent
				will truncate values within the range to multiples of 10. An
				attempt to write values that are out of range will result in a
				badValue error."
			::= { alarmPolicyEntry 5 }

--     1.3.6.1.4.1.81.7.13.1.1.6
		alarmPolicySampleType OBJECT-TYPE
			SYNTAX INTEGER
				{
				delta(1),
				absoluteValue(2)
				}
			ACCESS read-write
			STATUS mandatory
			DESCRIPTION
				"This item defines the type of sample that is compared to the
				threshold. If the value of this item is delta(1), then the threshold
				is compared to the difference between every two consecutive
				samples of the variable. If the value is absoluteValue(2), it is
				compared to the value of the variable.
				The default value is delta(1)."
			::= { alarmPolicyEntry 6 }

--     1.3.6.1.4.1.81.7.13.1.1.7
		alarmPolicyActionPolicy OBJECT-TYPE
			SYNTAX INTEGER
				{
				trap(1),
				trapAndDisconnectPort(2),
				none(3)
				}
			ACCESS read-write
			STATUS mandatory
			DESCRIPTION
				"This item defines the action taken by the agent upon
				detection of a variable larger or smaller than threshold
				(according to the value of alarmPolicyRisingFalling). If the
				value is trap(1) a trap is sent to all managers. If the value is
				trapAndDisconnectPort(2) and the OID in variableSampledOID
				points to a port then the port is disconnected. A value of (2)
				on a non-port item is legal, and will have the same effect as (1).
				Traps are sent only once, upon detection of the threshold crossing."
			::= { alarmPolicyEntry 7 }

--     1.3.6.1.4.1.81.7.13.1.1.8
		alarmPolicyBitmap OBJECT-TYPE
			SYNTAX OCTET STRING
			ACCESS read-only
			STATUS mandatory
			DESCRIPTION
				"This item describes the relationship between the policy table
				and the variable table. It is coded in proprietary coding."
			::= { alarmPolicyEntry 8 }

--     1.3.6.1.4.1.81.7.13.1.1.9
		alarmPolicyStatus OBJECT-TYPE
			SYNTAX INTEGER
				{
				active(1),
				notInService(2),
				notReady(3),
				createAndWait(4),
				destroy(5)
				}
			ACCESS read-write
			STATUS mandatory
			DESCRIPTION
				"This variable defines the status of the row.
				The values of this variables are defined and handled,
				according to the definitions in the  IETF draft:
				Row creation with SNMPv1, from 19 October 1993.
				The createAndGo value is not supported."
			::= { alarmPolicyEntry 9 }

--     1.3.6.1.4.1.81.7.13.2
		alarmPolicyNextFree OBJECT-TYPE
			SYNTAX INTEGER
			ACCESS read-only
			STATUS mandatory
			DESCRIPTION
				"An entry that points to the first available row in the policy
				table. If no rows are available, the value of the item is 0."
			::= { chAlarms 2 }

--     1.3.6.1.4.1.81.7.13.3
		variableTable OBJECT-TYPE
			SYNTAX SEQUENCE OF VariableEntry
			ACCESS not-accessible
			STATUS mandatory
			DESCRIPTION
				"This table contains the instances to be sampled by the agent
				and a pointer to the relevant policy in the policyTable for each instance."
			::= { chAlarms 3 }

--     1.3.6.1.4.1.81.7.13.3.1
		variableEntry OBJECT-TYPE
			SYNTAX VariableEntry
			ACCESS not-accessible
			STATUS mandatory
			DESCRIPTION
				"An entry that contains a single variable and the pointer to the
				policy by which it is monitored."
			INDEX { variablePolicy, variableInstance1, variableInstance2 }
			::= { variableTable 1 }

		VariableEntry ::=
			SEQUENCE {
				variablePolicy
					INTEGER,
				variableInstance1
					INTEGER,
				variableInstance2
					INTEGER,
				variableStatus
					INTEGER
			 }

--     1.3.6.1.4.1.81.7.13.3.1.1
		variablePolicy OBJECT-TYPE
			SYNTAX INTEGER (1..65535)
			ACCESS read-only
			STATUS mandatory
			DESCRIPTION
				"This item points to the alarm policy that is executed on the
				variable defined in this row. There is no limitation on the
				number of variables that are assigned a given policy. It is
				possible to create rows in the	variable table only if the policy
				pointed to is either active or	notInService.
				  When a row in the policy table is destroyed, all rows in the
				variable  table that point to it will also be destroyed."
			::= { variableEntry 1 }

--     1.3.6.1.4.1.81.7.13.3.1.2
		variableInstance1 OBJECT-TYPE
			SYNTAX INTEGER (1..65535)
			ACCESS read-only
			STATUS mandatory
			DESCRIPTION
				"This item defines the first index of the variable to be sampled.
				The combination of this item with variableInstance2 and with
				the alarmPolicyParameterOID (pointed to by variablePolicy)
				defines the instance to be sampled by the agent."
			::= { variableEntry 2 }

--     1.3.6.1.4.1.81.7.13.3.1.3
		variableInstance2 OBJECT-TYPE
			SYNTAX INTEGER (1..65535)
			ACCESS read-only
			STATUS mandatory
			DESCRIPTION
				"This item is the second index of the variable to be sampled."
			::= { variableEntry 3 }

--     1.3.6.1.4.1.81.7.13.3.1.4
		variableStatus OBJECT-TYPE
			SYNTAX INTEGER
				{
				active(1),
				notInService(2),
				notReady(3),
				createAndWait(4),
				destroy(5)
				}
			ACCESS read-write
			STATUS mandatory
			DESCRIPTION
				"This variable defines the status of the row.
				The values of this variables are defined and handled,
				according to the definitions in the  IETF draft:
				Row creation with SNMPv1, from 19 October 1993.
				The createAndGo value is not supported."
			::= { variableEntry 4 }

--     1.3.6.1.4.1.81.7.13.4
		variableNumOfEntries OBJECT-TYPE
			SYNTAX INTEGER
			ACCESS read-only
			STATUS mandatory
			DESCRIPTION
				"The number of entries in the table."
			::= { chAlarms 4 }

--     1.3.6.1.4.1.81.7.13.5
		alarmPolicyLastChange OBJECT-TYPE
			SYNTAX TimeTicks
			ACCESS read-only
			STATUS mandatory
			DESCRIPTION
				"This attribute contains the value of sysUpTime
				at the last time any of the following changes were
				made to one of the alarm tables:
				- a policy's state was changed to or from 'active';
				- a variable's state was changed to or from 'active'."
			::= { chAlarms 5 }

--     1.3.6.1.4.1.81.7.14
		chThresholdStatus OBJECT-TYPE
			SYNTAX OCTET STRING (SIZE (4))
			ACCESS read-only
			STATUS mandatory
			DESCRIPTION
				"This item is a bitmap that defines the threshold status of the
				hub, in relation to the alarmPolicyTable. If the hub is
				monitored by the agent according to policy number x in the
				alarmPolicyTable, and the threshold condition has occurred,
				then the bit #x in this item will have the value '1'. Otherwise
				it will be '0'. For x-186 based agents all bits of this item are '0'."
			::= { chassis 14 }

--     1.3.6.1.4.1.81.7.15
		chLsPortList OBJECT-TYPE
			SYNTAX OCTET STRING (SIZE (112))
			ACCESS read-only
			STATUS mandatory
			DESCRIPTION
				"A list of all LANswitch ports in the hub.
				16 bits in the bitmap are allocated for each slot in
				the hub. The MSB is for port 1 of slot 1, and the
				LSB is for port 16 of slot 16. For ports which
				are in the hub the value of the bit is 1,
				otherwise 0.
				For XSwitches, 64 bits will be reserved for each slot."
			::= { chassis 15 }

--     1.3.6.1.4.1.81.7.16
		chLsCAMPortList OBJECT-TYPE
			SYNTAX OCTET STRING (SIZE (32))
			ACCESS read-only
			STATUS mandatory
			DESCRIPTION
				"A list of all LANswitch ports in the hub for
				which the contents of the CAM (list of MAC
				addresses detected at the LANSwitch Port) are currently
				available.
				16 bits in the bitmap are allocated for each slot in
				the hub.  The MSB is for port 1 of slot 1, and the
				LSB is for port 16 of slot 16. For ports which
				report the CAM the value of the bit is 1,
				otherwise 0."
			::= { chassis 16 }

--     1.3.6.1.4.1.81.7.17
		chNumberOfHighSpeedBuses OBJECT-TYPE
			SYNTAX INTEGER (0..255)
			ACCESS read-only
			STATUS mandatory
			DESCRIPTION
				"Indicates the number of internal highspeed buses provided by the box."
			DEFVAL { 1 }
			::= { chassis 17 }

--     1.3.6.1.4.1.81.7.18
		chGroupList OBJECT-TYPE
			SYNTAX OCTET STRING
			ACCESS read-only
			STATUS mandatory
			DESCRIPTION
				"The function of this variable is to summarize the information concerning the
				presence of the module and the module type for each slot of the hub.
				The information is coded as follows:
				First Octet: number of slots
				Second Octet: SNMP Type of information: Integer = 2, OctetString = 4.
				Third Octet: length of each field
				Fourth Octet: if no module in slot #1 so '0', else the module type i.e, the integer
				conrresponding to genGroupType.
				Last Octet: represents last slot and should contain the agent type."
			::= { chassis 18 }

--     1.3.6.1.4.1.81.7.19
		chNumberOfXSwitches OBJECT-TYPE
			SYNTAX INTEGER (0..255)
			ACCESS read-only
			STATUS mandatory
			DESCRIPTION
				"Indicats the number of XSwitches provided by the box.
				Default value for Visage hub is 1. Default value for Meritage hub is 2"
			DEFVAL { 1 }
			::= { chassis 19 }

--     1.3.6.1.4.1.81.7.20
		lsBusThresholdStatus OBJECT-TYPE
			SYNTAX OCTET STRING (SIZE (4))
			ACCESS read-only
			STATUS mandatory
			DESCRIPTION
				"This item is a bitmap that defines the threshold status of the highspeed
				bus, in relation to the alarmPolicyTable. If the bus is monitored
				by the agent according to policy number x in the alarmPolicyTable, and the threshold
				condition has occured, then the bit #x in this item will have the value '1'. Otherwise it
				will be '0'. For Agent other than NMA-RS, the value of this item is always 0."
			::= { chassis 20 }

--     1.3.6.1.4.1.81.7.21
		chPluginList OBJECT-TYPE
			SYNTAX OCTET STRING
			ACCESS read-only
			STATUS mandatory
			DESCRIPTION
				"The function of this variable is to summarize the information concerning the presence of the expansion 	module and the expansion module type for each slot of the stack. The information is coded as follow:
				First Octet: number of slots
				Second Octet: SNMP Type of information: Integer=2, OctetString=4
				Third Octet: Length of each field
				Last Octets: For each slot, if no expansion module is present, the value will be 0; otherwise, the	plug-in-type-number (written in number of octets described in the 3rd octet)"
			::= { chassis 21 }

--     1.3.6.1.4.1.81.7.22
		chLogFileTable OBJECT-TYPE
			SYNTAX SEQUENCE OF ChLogFileEntry
			ACCESS not-accessible
			STATUS mandatory
			DESCRIPTION
				"Table describing all the reset occurrences in a switch,
				doubly indexed by the group number and the sequential number of the reset event"
			::= { chassis 22 }

--     1.3.6.1.4.1.81.7.22.1
		chLogFileEntry OBJECT-TYPE
			SYNTAX ChLogFileEntry
			ACCESS not-accessible
			STATUS mandatory
			DESCRIPTION
				"An entry in the table, containing data on a single reset event that occurred to a single group."
			INDEX { chLogFileGroupId, chLogFileIndex }
			::= { chLogFileTable 1 }

		ChLogFileEntry ::=
			SEQUENCE {
				chLogFileGroupId
					INTEGER,
				chLogFileIndex
					INTEGER,
				chLogFileName
					INTEGER,
				chLogFileAbsoluteTime
					Counter,
				chLogFileMessage
					DisplayString,
				chLogFileEncryptedMessage
					DisplayString
			 }

--     1.3.6.1.4.1.81.7.22.1.1
		chLogFileGroupId OBJECT-TYPE
			SYNTAX INTEGER (1..255)
			ACCESS read-only
			STATUS mandatory
			DESCRIPTION
				"Index which identifies the group or slot number."
			::= { chLogFileEntry 1 }

--     1.3.6.1.4.1.81.7.22.1.2
		chLogFileIndex OBJECT-TYPE
			SYNTAX INTEGER (1..65535)
			ACCESS read-only
			STATUS mandatory
			DESCRIPTION
				"Index which identifies the sequential number of a reset event.
				Index #1 always represents the last recent reset event that occurred.
				Every new reset event causes a shift in the table entries.
				When the maximum storage capacity of the switch is reached,
				the oldest entry is shifted out of the table (FIFO)"
			::= { chLogFileEntry 2 }

--     1.3.6.1.4.1.81.7.22.1.3
		chLogFileName OBJECT-TYPE
			SYNTAX INTEGER
				{
				reset(1),
				other(255)
				}
			ACCESS read-only
			STATUS mandatory
			DESCRIPTION
				"An enumeration which identifies the type of the log file we fetch."
			::= { chLogFileEntry 3 }

--     1.3.6.1.4.1.81.7.22.1.4
		chLogFileAbsoluteTime OBJECT-TYPE
			SYNTAX Counter
			ACCESS read-only
			STATUS mandatory
			DESCRIPTION
				"Absolute time in seconds at which the reset occurred.
				The absolute time is retrieved by the Agent from the net,
				in a standard format.
				In the case where the reset occurred before the Agent was
				already able to retrieve the absolute time, it should indicate 0."
			::= { chLogFileEntry 4 }

--     1.3.6.1.4.1.81.7.22.1.5
		chLogFileMessage OBJECT-TYPE
			SYNTAX DisplayString (SIZE (0..600))
			ACCESS read-only
			STATUS mandatory
			DESCRIPTION
				"Readable text message, which will contain a full description of the reset event and its cause."
			::= { chLogFileEntry 5 }

--     1.3.6.1.4.1.81.7.22.1.6
		chLogFileEncryptedMessage OBJECT-TYPE
			SYNTAX DisplayString (SIZE (0..600))
			ACCESS read-only
			STATUS mandatory
			DESCRIPTION
				"Encrypted message saved in the Flash memory, which will contain
				a full description of the reset event, that is understandable to the Technician only."
			::= { chLogFileEntry 6 }

--     1.3.6.1.4.1.81.7.23
		chLicenseKey OBJECT-TYPE
			SYNTAX OCTET STRING (SIZE (12))
			ACCESS read-write
			STATUS mandatory
			DESCRIPTION
				"This MIB item contains the authorization key for SMON application,
				and for other applications in the future."
			::= { chassis 23 }

--     1.3.6.1.4.1.81.7.24
		chStackHealthTable OBJECT-TYPE
			SYNTAX SEQUENCE OF ChStackHealthEntry
			ACCESS not-accessible
			STATUS mandatory
			DESCRIPTION
				"This table controls the stackHealth verification procedure -
				cascading modules and cables integrity test."
			::= { chassis 24 }

--     1.3.6.1.4.1.81.7.24.1
		chStackHealthEntry OBJECT-TYPE
			SYNTAX ChStackHealthEntry
			ACCESS not-accessible
			STATUS mandatory
			INDEX { chStackHealthGroupId }
			::= { chStackHealthTable 1 }

		ChStackHealthEntry ::=
			SEQUENCE {
				chStackHealthGroupId
					INTEGER,
				chStackHealthTxDstModule
					INTEGER,
				chStackHealthTxPktLen
					INTEGER,
				chStackHealthTxDirection
					INTEGER,
				chStackHealthTx
					INTEGER,
				chStackHealthRx
					INTEGER,
				chStackHealthRxListen
					INTEGER,
				chStackHealthTxDstAddress
					OCTET STRING
			 }

--     1.3.6.1.4.1.81.7.24.1.1
		chStackHealthGroupId OBJECT-TYPE
			SYNTAX INTEGER (1..255)
			ACCESS read-only
			STATUS mandatory
			DESCRIPTION
				"The module number"
			::= { chStackHealthEntry 1 }

--     1.3.6.1.4.1.81.7.24.1.2
		chStackHealthTxDstModule OBJECT-TYPE
			SYNTAX INTEGER
			ACCESS read-write
			STATUS mandatory
			DESCRIPTION
				"The test destination module"
			::= { chStackHealthEntry 2 }

--     1.3.6.1.4.1.81.7.24.1.3
		chStackHealthTxPktLen OBJECT-TYPE
			SYNTAX INTEGER (28..1500)
			ACCESS read-write
			STATUS mandatory
			DESCRIPTION
				"The size of the UDP test packets"
			DEFVAL { 64 }
			::= { chStackHealthEntry 3 }

--     1.3.6.1.4.1.81.7.24.1.4
		chStackHealthTxDirection OBJECT-TYPE
			SYNTAX INTEGER (1..255)
			ACCESS read-write
			STATUS mandatory
			DESCRIPTION
				"The direction for sending test frames."
			DEFVAL { 1 }
			::= { chStackHealthEntry 4 }

--     1.3.6.1.4.1.81.7.24.1.5
		chStackHealthTx OBJECT-TYPE
			SYNTAX INTEGER
			ACCESS read-write
			STATUS mandatory
			DESCRIPTION
				"The number of packet to send. When greater than zero,
				the agent at module chStackHealthGroupID
				send a UDP packet to chStackHealthTxModule,
				port 5090, size chStackHealthTxPktLen via cascading
				port stackHealthTxPhyPort.
				The agent decrements this leaf by one for each packet
				it sends. "
			DEFVAL { 0 }
			::= { chStackHealthEntry 5 }

--     1.3.6.1.4.1.81.7.24.1.6
		chStackHealthRx OBJECT-TYPE
			SYNTAX INTEGER
			ACCESS read-only
			STATUS mandatory
			DESCRIPTION
				"This item counts the number of received packets."
			::= { chStackHealthEntry 6 }

--     1.3.6.1.4.1.81.7.24.1.7
		chStackHealthRxListen OBJECT-TYPE
			SYNTAX INTEGER
				{
				start(1),
				stop(2)
				}
			ACCESS read-write
			STATUS mandatory
			DESCRIPTION
				"When set to start(1) the subagent start listening on
				UDP port 5090. Writing to this item resets stackHealthRx.
				When set to stop(2), the agent close the UDP port."
			DEFVAL { stop }
			::= { chStackHealthEntry 7 }

--     1.3.6.1.4.1.81.7.24.1.8
		chStackHealthTxDstAddress OBJECT-TYPE
			SYNTAX OCTET STRING (SIZE (0..6))
			ACCESS read-write
			STATUS mandatory
			DESCRIPTION
				"The test destination module address"
			::= { chStackHealthEntry 8 }

--     This group contains information about the status
-- of the supervisors in the chassis.
-- 1.3.6.1.4.1.81.7.25
		chSpv OBJECT IDENTIFIER ::= { chassis 25 }

--     1.3.6.1.4.1.81.7.25.1
		chSpvTable OBJECT-TYPE
			SYNTAX SEQUENCE OF ChSpvEntry
			ACCESS not-accessible
			STATUS mandatory
			DESCRIPTION
				"This table contains entries for each slot
				in the chassis intended for installation
				of the supervisor's."
			::= { chSpv 1 }

--     1.3.6.1.4.1.81.7.25.1.1
		chSpvEntry OBJECT-TYPE
			SYNTAX ChSpvEntry
			ACCESS not-accessible
			STATUS mandatory
			INDEX { chSpvId }
			::= { chSpvTable 1 }

		ChSpvEntry ::=
			SEQUENCE {
				chSpvId
					INTEGER,
				chSpvStatus
					INTEGER,
				chSpvSyncStatus
					INTEGER,
				chSpvEwVersion
					DisplayString,
				chSpvBankASwVersion
					DisplayString,
				chSpvBankBSwVersion
					DisplayString,
				chSpvBankPref
					INTEGER,
				chSpvSerialNumber
					DisplayString,
				chSpvConfigurationSymbol
					DisplayString,
				chSpvRunningSwVersion
					DisplayString,
				chSpvBootedFrom
					INTEGER
			 }

--     1.3.6.1.4.1.81.7.25.1.1.1
		chSpvId OBJECT-TYPE
			SYNTAX INTEGER (1..2)
			ACCESS read-only
			STATUS mandatory
			DESCRIPTION
				"Identifies the SPV's slot number."
			::= { chSpvEntry 1 }

--     1.3.6.1.4.1.81.7.25.1.1.2
		chSpvStatus OBJECT-TYPE
			SYNTAX INTEGER
				{
				active(1),
				standby(2),
				halted(3),
				warmReset(4),
				inElection(5),
				unknown(255)
				}
			ACCESS read-only
			STATUS mandatory
			DESCRIPTION
				"Indicates the status of the SPV:
				active(1) -     the SPV operates as master SPV
				standby(2) -    the SPV may replace the active SPV in
				                case of failure.
				halted(3) -     the SPV is unable to act as a standby
				                SPV.
				warmReset(4) -  the SPV performs warm reset.
				inElection(5) - the SPV performs election process.
				unknown (255) - the SPV status is unknown."
			::= { chSpvEntry 2 }

--     1.3.6.1.4.1.81.7.25.1.1.3
		chSpvSyncStatus OBJECT-TYPE
			SYNTAX INTEGER
				{
				yes(1),
				no(2),
				unknown(255)
				}
			ACCESS read-only
			STATUS mandatory
			DESCRIPTION
				"Indicates whether SPV is synchronized with the chassis."
			::= { chSpvEntry 3 }

--     1.3.6.1.4.1.81.7.25.1.1.4
		chSpvEwVersion OBJECT-TYPE
			SYNTAX DisplayString
			ACCESS read-only
			STATUS mandatory
			DESCRIPTION
				"Describes the version number of Embedded Web software."
			::= { chSpvEntry 4 }

--     1.3.6.1.4.1.81.7.25.1.1.5
		chSpvBankASwVersion OBJECT-TYPE
			SYNTAX DisplayString
			ACCESS read-only
			STATUS mandatory
			DESCRIPTION
				"Describes the version number of software
				contained in Bank A."
			::= { chSpvEntry 5 }

--     1.3.6.1.4.1.81.7.25.1.1.6
		chSpvBankBSwVersion OBJECT-TYPE
			SYNTAX DisplayString
			ACCESS read-only
			STATUS mandatory
			DESCRIPTION
				"Describes the version number of software
				contained in Bank B."
			::= { chSpvEntry 6 }

--     1.3.6.1.4.1.81.7.25.1.1.7
		chSpvBankPref OBJECT-TYPE
			SYNTAX INTEGER
				{
				bankA(1),
				bankB(2),
				unknown(255)
				}
			ACCESS read-only
			STATUS mandatory
			DESCRIPTION
				"Indicates which bank is preferred for boot up."
			::= { chSpvEntry 7 }

--     1.3.6.1.4.1.81.7.25.1.1.8
		chSpvSerialNumber OBJECT-TYPE
			SYNTAX DisplayString
			ACCESS read-only
			STATUS mandatory
			DESCRIPTION
				"Describes SPV's serial number."
			::= { chSpvEntry 8 }

--     1.3.6.1.4.1.81.7.25.1.1.9
		chSpvConfigurationSymbol OBJECT-TYPE
			SYNTAX DisplayString
			ACCESS read-only
			STATUS mandatory
			DESCRIPTION
				"Describes SPV's Configuration Symbol."
			::= { chSpvEntry 9 }

--     1.3.6.1.4.1.81.7.25.1.1.10
		chSpvRunningSwVersion OBJECT-TYPE
			SYNTAX DisplayString
			ACCESS read-only
			STATUS mandatory
			DESCRIPTION
				"Describes the SPV's running software version."
			::= { chSpvEntry 10 }

--     1.3.6.1.4.1.81.7.25.1.1.11
		chSpvBootedFrom OBJECT-TYPE
			SYNTAX INTEGER
				{
				bankA(1),
				bankB(2),
				network(3),
				unknown(255)
				}
			ACCESS read-only
			STATUS mandatory
			DESCRIPTION
				"Indicated from which bank SPV was booted."
			::= { chSpvEntry 11 }

--     1.3.6.1.4.1.81.7.25.2
		chSpvActive OBJECT-TYPE
			SYNTAX INTEGER
			ACCESS read-only
			STATUS mandatory
			DESCRIPTION
				"Indicates the chSpvId of avtive SPV.
				Only one SPV can be active at the time."
			::= { chSpv 2 }

--     1.3.6.1.4.1.81.7.26
		chLldpSystemControl OBJECT-TYPE
			SYNTAX INTEGER
				{
				enabled(1),
				disabled(2)
				}
			ACCESS read-write
			STATUS mandatory
			DESCRIPTION
				"The administrative enable/disable state for LLDP
				 application in a System."
			DEFVAL { disabled }
			::= { chassis 26 }

--     1.3.6.1.4.1.81.7.27
		chStatus OBJECT-TYPE
			SYNTAX INTEGER
				{
				idle(1),
				up(2)
				}
			ACCESS read-write
			STATUS mandatory
			DESCRIPTION
				"Chassis informs the Server that it is up. This is internal MIB
				for gateway use to indicate the server that the gateway undergoes reset and now
				it is up. The chassis set this mib to up(2). The MIB always returns idle(1)."
			DEFVAL { idle }
			::= { chassis 27 }

		chApplicationBladeStatus OBJECT-TYPE
			SYNTAX INTEGER
				{
				idle(1),
				up(2)
				}
			ACCESS read-write
			STATUS mandatory
			DESCRIPTION
				"Chassis informs that application server blade is up. This is internal MIB
				for gateway use to indicate the DO Telephony server that the application module
				undergoes reset and now it is up. The chassis set this mib to up(2).
				The MIB always returns idle(1)."
			DEFVAL { idle }
			::= { chassis 28 }


--     Generic Group group
-- mandatory for all managed  modules (groups)
-- 1.3.6.1.4.1.81.8
		genGroup OBJECT IDENTIFIER ::= { lannet 8 }

--     1.3.6.1.4.1.81.8.1
		genGroupTable OBJECT-TYPE
			SYNTAX SEQUENCE OF GenGroupEntry
			ACCESS not-accessible
			STATUS mandatory
			DESCRIPTION
				"Table of configuration attributes for managed  modules.
				Includes configuration data which are independent of the
				specific functionality of the module."
			::= { genGroup 1 }

--     1.3.6.1.4.1.81.8.1.1
		genGroupEntry OBJECT-TYPE
			SYNTAX GenGroupEntry
			ACCESS not-accessible
			STATUS mandatory
			DESCRIPTION
				"An entry in the table, containing data about a single group."
			INDEX { genGroupId }
			::= { genGroupTable 1 }

		GenGroupEntry ::=
			SEQUENCE {
				genGroupId
					INTEGER,
				genGroupSWVersion
					DisplayString,
				genGroupKernelVersion
					DisplayString,
				genGroupType
					INTEGER,
				genGroupDescr
					DisplayString,
				genGroupNumberOfPorts
					INTEGER,
				genGroupNumberOfIntPorts
					INTEGER,
				genGroupReset
					INTEGER,
				genGroupAutoMan
					INTEGER,
				genGroupFullConfig
					OCTET STRING,
				genGroupRedun12
					INTEGER,
				genGroupRedun34
					INTEGER,
				genGroupRedun13-14
					INTEGER,
				genGroupStandAloneMode
					INTEGER,
				genGroupInterProcCommStatus
					INTEGER,
				genGroupCommStatus
					INTEGER,
				genGroupHWStatus
					INTEGER,
				genGroupSupplyVoltageFault
					INTEGER,
				genGroupIntTemp
					INTEGER,
				genGroupSpecificOID
					OBJECT IDENTIFIER,
				genGroupConfigurationSymbol
					DisplayString,
				genGroupLastChange
					TimeTicks,
				genGroupRedunRecovery
					INTEGER,
				genGroupHWVersion
					DisplayString,
				genGroupHeight
					INTEGER,
				genGroupWidth
					INTEGER,
				genGroupIntrusionControl
					OCTET STRING,
				genGroupThresholdStatus
					OCTET STRING,
				genGroupEavesdropping
					OCTET STRING,
				genGroupMainSWVersion
					DisplayString,
				genGroupMPSActivityStatus
					INTEGER,
				genGroupBUPSActivityStatus
					INTEGER,
				genGroupPrepareCounters
					INTEGER,
				genGroupPortLastChange
					OCTET STRING,
				genGroupIntPortLastChange
					OCTET STRING,
				genGroupFaultMask
					OCTET STRING,
				genGroupTypeName
					DisplayString,
				genGroupAgentSlot
					INTEGER,
				genGroupMngType
					INTEGER,
				genGroupNumberOfLogicalPorts
					INTEGER,
				genGroupNumberOfInterfaces
					INTEGER,
				genGroupCascadUpStatus
					INTEGER,
				genGroupCascadDownStatus
					INTEGER,
				genGroupSTARootPortID
					INTEGER,
				genGroupCopyPortInstruction
					OCTET STRING,
				genGroupLicenseKey
					OCTET STRING,
				genGroupLogFileClear
					INTEGER,
				genGroupBootVersion
					DisplayString,
				genGroupResetLastStamp
					TimeTicks,
				genGroupSerialNumber
					DisplayString,
				genGroupShowModuleInformation
					DisplayString,
				genGroupCascadingUpFault
					INTEGER,
				genGroupCascadingDownFault
					INTEGER,
				genGroupPortClassificationMask
					OCTET STRING,
				genGroupPSUType
					INTEGER,
				genGroupPolicyType
					INTEGER,
				genGroupFips140Ready
					INTEGER
			 }

--     1.3.6.1.4.1.81.8.1.1.1
		genGroupId OBJECT-TYPE
			SYNTAX INTEGER (1..255)
			ACCESS read-only
			STATUS mandatory
			DESCRIPTION
				"Index which identifies the group inside the chassis for which this
				entry contains information. Equals the number of the slot by which
				the group is accessed. This value is never greater than chNumberOfSlots."
			::= { genGroupEntry 1 }

--     1.3.6.1.4.1.81.8.1.1.2
		genGroupSWVersion OBJECT-TYPE
			SYNTAX DisplayString
			ACCESS read-only
			STATUS mandatory
			DESCRIPTION
				"ASCII string for description and display of the group software version."
			::= { genGroupEntry 2 }

--     1.3.6.1.4.1.81.8.1.1.3
		genGroupKernelVersion OBJECT-TYPE
			SYNTAX DisplayString
			ACCESS read-only
			STATUS mandatory
			DESCRIPTION
				"ASCII string for description and display of the group kernel version."
			::= { genGroupEntry 3 }

--     1.3.6.1.4.1.81.8.1.1.4
		genGroupType OBJECT-TYPE
			SYNTAX INTEGER
				{
				le10b(1),
				le10b-2(2),
				le10c(3),
				le10c-2(4),
				le15(5),
				le15-2(6),
				le20(7),
				le30x(8),
				le30x-2(9),
				le30xd(10),
				le40x(11),
				le40xt(12),
				ltr4-RJ45(13),
				ltr4-D9(14),
				ltr4-D25(15),
				ltr4-FO(16),
				ltrio-RJ45(19),
				ltrio-D9(20),
				ltrio-D25(21),
				ltrio-FO(22),
				ltrio-Con1(23),
				ltrio-Con2(24),
				le10b-2r(25),
				le10c-2r(26),
				le80xt(27),
				le140xt(28),
				ielb(29),
				ltrf4(30),
				ltrf16(31),
				lts16(32),
				le20n(33),
				ltr104-RJ45(34),
				le20r(35),
				llt8(36),
				le20s(37),
				le10b2n(38),
				ltr104-D9(39),
				ltr104-D25(40),
				ltrt-RJ45(41),
				ltrt-D9(42),
				ltr104f(43),
				itlb(44),
				le140xtf(45),
				le120r(46),
				le120r-2(47),
				le140xtc(48),
				le110b(49),
				le110bq(50),
				lcl100(51),
				le140xtq(52),
				le20n-fb(53),
				le20s-fb(54),
				le140xtf-fb(55),
				ltr104s(56),
				lert40-AUI(57),
				lert40-10BASET(58),
				lfd104-mic(59),
				lfd104-stm(60),
				lfd104-stl(61),
				lfd104-stp(62),
				lfd104-utp(63),
				lfd102-mic(64),
				lfd102-stm(65),
				lfd102-sts(66),
				le140xtn(67),
				ltr104a(68),
				le120q(69),
				le120sq2(70),
				le120sq5(71),
				le120q-fb(72),
				le120sq2-fb(73),
				le120sq5-fb(74),
				ltr108t(75),
				ltr108f(76),
				lse808(77),
				lhs(78),
				iefn(80),
				itfn(81),
				ierp(86),
				lse108(87),
				lse208(88),
				le110cq(89),
				itre2(90),
				sh-e16(92),
				le115q(93),
				sh-t16(94),
				sh-e8(95),
				lhb(96),
				sh-efn(97),
				sh-tfn(98),
				lace100(100),
				le140xts(101),
				le40xtn(102),
				le80xtn(103),
				itrp(104),
				lfd104-lcf(105),
				lfd104-sts(106),
				lfd102-lcf(107),
				lfd102-stl(108),
				lfd102-stp(109),
				lfd102-utp(110),
				phy4-mic(111),
				phy4-stm(112),
				phy4-stl(113),
				phy4-stp(114),
				phy4-utp(115),
				phy4-lcf(116),
				phy4-sts(117),
				phy2-mic(118),
				phy2-stm(119),
				phy2-stl(120),
				phy2-stp(121),
				phy2-utp(122),
				phy2-lcf(123),
				phy2-sts(124),
				sh-t16io-c(126),
				sh-t16io-fr(127),
				lse404(128),
				sh-t16io-cr(129),
				sh-e8fb(131),
				sh-e8fl(132),
				iefr-mc(134),
				ieqr(136),
				iere2(138),
				ltr104sn(139),
				le240xtc(140),
				le280xt(141),
				sh-e16fb(143),
				sh-e16fl(144),
				lse404s(145),
				lse404s-fb(146),
				lse404srj(147),
				le240xtcs(148),
				le280xts(149),
				lsa(150),
				lfe100n(151),
				lsf100(152),
				lfe100(153),
				lst168(154),
				lea10BT(155),
				lea10BTRed(156),
				leaFl(157),
				leaFlRed(158),
				sh-e24(159),
				sh-e24s(160),
				lfe1008(161),
				le180xt(163),
				sh-e24fl(164),
				sh-e24fb(165),
				sh-e24sfl(166),
				sh-e24sfb(167),
				sh-40sf(168),
				sh-80rj(169),
				lse-pm(170),
				lsf100n(171),
				ls3ls(172),
				las(173),
				leb200n(174),
				leb200(175),
				fat-pipe-fddi(176),
				lfe4004(178),
				lbt155(185),
				lsa2(186),
				lbt155Plus(187),
				lfe4004ST(188),
				lfe4004SF(189),
				lge-2000SX(190),
				lge-2000LX(191),
				lfe8008S(192),
				invalid(253),
				emptySlot(254),
				unknown(255),
				visage24T(1000),
				visage16200F(1001),
				visage16200T(1004),
				visage16200FC(1005),
				visage800T(1006),
				visage800F(1007),
				visage16155FR(1008),
				visage16155F(1009),
				visage2500(1010),
				visage3LS(1012),
				visage1600T(1013),
				visage2008SX(1014),
				visage2008LX(1015),
				visage1008SX(1016),
				visage1008LX(1017),
				visage26Plus(1025),
				visage26PlusFxMM(1026),
				visage26PlusFxSM(1027),
				visage26PlusTx(1028),
				cajunP117S(1029),
				cajunP117SR(1030),
				m12-100T(2000),
				m12-100F(2001),
				m-spv(2002),
				nma-rs(2003),
				nma-re(2004),
				m-spx(2005),
				m2-1000SX(2006),
				m2-1000LX(2007),
				m14-10F(2008),
				m24-10T(2009),
				m-sps-T(2010),
				m-sps-ER(2011),
				m-sps-EB(2012),
				m32-100T(2013),
				m-accf(2014),
				m-accsf(2015),
				m-mls(2200),
				cajunP120(2500),
				cajunP333T(2501),
				cajunP333R(2502),
				cajunP122(2503),
				cajunP334T(2504),
				cajunP332MF(2505),
				cajunP133G2(2506),
				cajunP332G-ML(2507),
				cajunP133F2(2508),
				cajunP134G2(2509),
				cajunP332GT-ML(2510),
				cajunP334T-ML(2511),
				cajunP333RLB(2512),
				cajunP333T-PWR(2513),
				cajunX330W-4DS1(2514),
				cajunP133T(2515),
				cajunP133GT2(2516),
				cajunX330W-2DS1(2517),
				cajunX330W-2USP(2518),
				cajunX330W-2DS1-B(2519),
				avayaC460-M460ML-SPV(2600),
				avayaC460-M4648ML-T(2601),
				avayaC460-M4648ML-T-2G(2602),
				avayaC460-M4612ML-G(2603),
				avayaC460-M4648ML-T-PWR(2604),
				avayaC460-M4648ML-T-2G-PWR(2605),
				avayaC363T(2700),
				avayaC364T(2701),
				avayaC363T-PWR(2702),
				avayaC364T-PWR(2703),
				c-Hawk(2800),
				avayaG250-motherboard(2850),
				avayaG250-BRI-motherboard(2851),
				avayaG250-DS1-motherboard(2852),
				avayaG250-DCP-motherboard(2853),
				avayaG250-A14-motherboard(2854),
				avayaG350(2900),
				m15-155F(3000),
				m3-622F(3001),
				m3-622SF(3002),
				m15-155SF(3003),
				m15-155MS(3004),
				m2-2400I(3005),
				m4-DS3(3009),
				m4-E3(3010),
				avayaW310(3100),
				avayaG250-int-analog-2L4T(4005),
				avayaG250-int-analog-2L1T(4006),
				avayaG250-int-BRI(4007),
				avayaG250-int-DS1(4008),
				avayaG250-int-12pDCP(4009),
				avayaG250-int-analog-6L8T(4010),
				avayaG450-Mainboard(4050),
				avayaMM720(4098),
				avayaMM712(4099),
				avayaMM711(4100),
				avayaMM710(4101),
				avayaMM760(4102),
				avayaMM714(4103),
				avayaMM722(4104),
				avayaG350-int-analog(4105),
				avayaMM314(4106),
				avayaMM340(4107),
				avayaMM342(4108),
				avayaMM717(4109),
				avayaMM716(4110),
				avayaMM316(4111),
				avayaMM314cr(4112),
				avayaMM118(4113),
				avayaMM312(4128),
				avayaTGM550(4150),
				avayaTGM550-int-analog-2L2T(4151),
				avayaTIM514(4152),
				avayaTIM510(4153),
				avayaTIM521(4154),
				avayaTIM508(4155),
				avayaTIM516(4156),
				avayaTIM518(4157),
				avayaS8300(4200),
				avayaAM110ApplicationModule(4210),
				avayaCommunicationManagerBranchEditioni40TelephonyServer(4211),
				avayaCommunicationManagerBranchEditioni120TelephonyServer(4212),
				avayaCommunicationManagerBranchEditionG430TelephonyServer(4214),
				avayaCommunicationManagerBranchEditionG450TelephonyServer(4215),
				avayaMMtst(4351),
				avayai40-Analog-motherboard(5000),
				avayai40-BRI-motherboard(5001),
				avayai40-DS1-motherboard(5002),
				avaya120(5003),
				avayai120-int-analog(5004),
				avayai40-int-analog-2L4T(5005),
				avayai40-int-analog-2L1T(5006),
				avayai40-int-BRI(5007),
				avayai40-int-DS1(5008),
				avayai40-A14-motherboard(5009),
				avayai40-A14-int-analog-6L8T(5010),
				avayaCommunicationManagerBranchEditionG450-Mainboard(5011),
				avayaCommunicationManagerBranchEditionG430-motherboard(5013),
				avayaG430-motherboard(5014),
				avayaTRM480(5100)
				}
			ACCESS read-only
			STATUS mandatory
			DESCRIPTION
				"Attribute describing the type of the group (module)."
			::= { genGroupEntry 4 }

--     1.3.6.1.4.1.81.8.1.1.5
		genGroupDescr OBJECT-TYPE
			SYNTAX DisplayString (SIZE (0..32))
			ACCESS read-only
			STATUS mandatory
			DESCRIPTION
				"Descriptor of the group in ASCII (readable) format, mainly for use with
				generic management applications."
			::= { genGroupEntry 5 }

--     1.3.6.1.4.1.81.8.1.1.6
		genGroupNumberOfPorts OBJECT-TYPE
			SYNTAX INTEGER (0..255)
			ACCESS read-only
			STATUS mandatory
			DESCRIPTION
				"Number of ports in group. It is assumed that on each group the ports
				are assigned unique numbers in the range from 1 to genGroupNumberOfPorts.
				They correspond to the number of ports on the module (FRU)"
			::= { genGroupEntry 6 }

--     1.3.6.1.4.1.81.8.1.1.7
		genGroupNumberOfIntPorts OBJECT-TYPE
			SYNTAX INTEGER (0..255)
			ACCESS read-only
			STATUS mandatory
			DESCRIPTION
				"Number of internal ports (ports connected to the chassis buses) on
				the module."
			::= { genGroupEntry 7 }

--     1.3.6.1.4.1.81.8.1.1.8
		genGroupReset OBJECT-TYPE
			SYNTAX INTEGER
				{
				on(1),
				off(2),
				onWithPoE(3),
				notSupported(255)
				}
			ACCESS read-write
			STATUS mandatory
			DESCRIPTION
				"Setting the value of this attribute to 'on' is interpreted as a software
				RESET command. Sensor software is reinitialized and according to the
				sensor specifications, partial or total reset of the module hardware may
				be performed. 'onWithPoE' will RESET also the Power over Ethernet
				circuitry thus dropping the power to attached PD"
			::= { genGroupEntry 8 }

--     1.3.6.1.4.1.81.8.1.1.9
		genGroupAutoMan OBJECT-TYPE
			SYNTAX INTEGER
				{
				auto(1),
				man(2)
				}
			ACCESS read-only
			STATUS mandatory
			DESCRIPTION
				"This attribute reflects the status of the Auto/Manual switch which
				defines the working mode of  sensors. In the MANUAL mode no set
				operations may be performed on attributes related to the sensor. The
				sensor works according to configuration switches set by hardware and
				transmits all configuration information to the agent. In the AUTO mode,
				hardware switches are overridden by set commands."
			::= { genGroupEntry 9 }

--     1.3.6.1.4.1.81.8.1.1.10
		genGroupFullConfig OBJECT-TYPE
			SYNTAX OCTET STRING
			ACCESS read-only
			STATUS deprecated
			DESCRIPTION
				"Attribute describing the full configuration of a group in internal
				application format."
			::= { genGroupEntry 10 }

--     MIB 7.0
-- 1.3.6.1.4.1.81.8.1.1.11
		genGroupRedun12 OBJECT-TYPE
			SYNTAX INTEGER
				{
				on(1),
				off(2),
				blocked(3),
				notSupported(255)
				}
			ACCESS read-write
			STATUS mandatory
			DESCRIPTION
				"Value on(1) of this attribute defines a redundancy (backup) relationship
				between synchronous external ports 1 and 2 on a  module.
				Value blocked(3) of this attribute defines that the module is in the
				redundancy block mode used by IMR based modules."
			::= { genGroupEntry 11 }

--     1.3.6.1.4.1.81.8.1.1.12
		genGroupRedun34 OBJECT-TYPE
			SYNTAX INTEGER
				{
				on(1),
				off(2),
				notSupported(255)
				}
			ACCESS read-write
			STATUS mandatory
			DESCRIPTION
				"Value ON of this attribute defines a redundancy (backup) relationship
				between synchronous external ports 3 and 4 on a  module."
			::= { genGroupEntry 12 }

--     1.3.6.1.4.1.81.8.1.1.13
		genGroupRedun13-14 OBJECT-TYPE
			SYNTAX INTEGER
				{
				on(1),
				off(2),
				notSupported(255)
				}
			ACCESS read-write
			STATUS mandatory
			DESCRIPTION
				"Value ON of this attribute defines a redundancy (backup) relationship
				between synchronous external ports 13 and 14 on a  module."
			::= { genGroupEntry 13 }

--     1.3.6.1.4.1.81.8.1.1.14
		genGroupStandAloneMode OBJECT-TYPE
			SYNTAX INTEGER
				{
				on(1),
				off(2),
				notSupported(255)
				}
			ACCESS read-write
			STATUS mandatory
			DESCRIPTION
				"Value ON of this attribute indicates the sensor's operation Stand Alone
				mode . Internal ports are disabled and the card functions in a local
				star configuration toward its external ports."
			::= { genGroupEntry 14 }

--     1.3.6.1.4.1.81.8.1.1.15
		genGroupInterProcCommStatus OBJECT-TYPE
			SYNTAX INTEGER
				{
				ok(1),
				commProblems(2),
				noCommunication(3),
				notSupported(255)
				}
			ACCESS read-only
			STATUS mandatory
			DESCRIPTION
				"This attribute describes the status of the communication between the
				microprocessor of the sensor and the microprocessor of the agent on cards
				with embedded agents."
			::= { genGroupEntry 15 }

--     1.3.6.1.4.1.81.8.1.1.16
		genGroupCommStatus OBJECT-TYPE
			SYNTAX INTEGER
				{
				ok(1),
				commProblems(2),
				noCommunication(3),
				notSupported(255)
				}
			ACCESS read-only
			STATUS mandatory
			DESCRIPTION
				"This attribute describes the communication status of the group with
				the SNMP Agent as detected and reported by the agent."
			::= { genGroupEntry 16 }

--     1.3.6.1.4.1.81.8.1.1.17
		genGroupHWStatus OBJECT-TYPE
			SYNTAX INTEGER
				{
				ok(1),
				hardwareProblems(2),
				notSupported(255)
				}
			ACCESS read-only
			STATUS mandatory
			DESCRIPTION
				"This attribute describes the status of the group hardware as detected
				by the sensors software."
			::= { genGroupEntry 17 }

--     1.3.6.1.4.1.81.8.1.1.18
		genGroupSupplyVoltageFault OBJECT-TYPE
			SYNTAX INTEGER
				{
				on(1),
				off(2),
				notSupported(255)
				}
			ACCESS read-only
			STATUS mandatory
			DESCRIPTION
				"A value 'on' of this attribute informs of a 'voltage supply
				out-of-range' error condition on sensor equipped with
				hardware which checks this condition."
			::= { genGroupEntry 18 }

--     1.3.6.1.4.1.81.8.1.1.19
		genGroupIntTemp OBJECT-TYPE
			SYNTAX INTEGER
			ACCESS read-only
			STATUS mandatory
			DESCRIPTION
				"Internal temperature of the enclosure as measured by the
				specific module instance.Value	'999' means not supported."
			::= { genGroupEntry 19 }

--     1.3.6.1.4.1.81.8.1.1.20
		genGroupSpecificOID OBJECT-TYPE
			SYNTAX OBJECT IDENTIFIER
			ACCESS read-only
			STATUS mandatory
			DESCRIPTION
				"This attribute provides the OID of another group containing
				additional more specific information regarding this instance."
			::= { genGroupEntry 20 }

--     1.3.6.1.4.1.81.8.1.1.21
		genGroupConfigurationSymbol OBJECT-TYPE
			SYNTAX DisplayString
			ACCESS read-only
			STATUS mandatory
			DESCRIPTION
				"Defines the Configuration Symbol attached to any hardware module manufactured.
				One single character A..Z defines the CS version. For older modules which did not
				support this option on	SNMP character '*' will be returned.

				Meritage modules will use a new format
				X.Y - where X & Y are integers:
					1st byte (X) - Major version number
					2nd byte - '.'
					3rd byte (Y) - minor version number "
			::= { genGroupEntry 21 }

--     1.3.6.1.4.1.81.8.1.1.22
		genGroupLastChange OBJECT-TYPE
			SYNTAX TimeTicks
			ACCESS read-only
			STATUS mandatory
			DESCRIPTION
				"This attribute contains the value of sysUpTime at the time any change
				pertaining to the specified group occurred."
			::= { genGroupEntry 22 }

--     1.3.6.1.4.1.81.8.1.1.23
		genGroupRedunRecovery OBJECT-TYPE
			SYNTAX INTEGER
				{
				on(1),
				off(2),
				notSupported(255)
				}
			ACCESS read-only
			STATUS mandatory
			DESCRIPTION
				"This attribute is relevant for the cards with redundancy feature (LTR-108F).
				It defines the behaviour in case of main port failure:
				on(1) - the data path returns to the main port when
					   its correct functionality is recovered.
				off(2) - the data path stays with  the redundant port."
			::= { genGroupEntry 23 }

--     1.3.6.1.4.1.81.8.1.1.24
		genGroupHWVersion OBJECT-TYPE
			SYNTAX DisplayString
			ACCESS read-only
			STATUS mandatory
			DESCRIPTION
				"Defines the Hardware version of the module.
				Current modules use a single character A - D.
				Very old modules which do not support this mib will be returned an asterisk '*' "
			::= { genGroupEntry 24 }

--     1.3.6.1.4.1.81.8.1.1.25
		genGroupHeight OBJECT-TYPE
			SYNTAX INTEGER
			ACCESS read-only
			STATUS mandatory
			DESCRIPTION
				"This item describes the physical height of the module in Us (1U=1.75'')."
			::= { genGroupEntry 25 }

--     1.3.6.1.4.1.81.8.1.1.26
		genGroupWidth OBJECT-TYPE
			SYNTAX INTEGER
			ACCESS read-only
			STATUS mandatory
			DESCRIPTION
				"This item describes the physical width of the module in HP units (1HP=0.5 mm)."
			::= { genGroupEntry 26 }

--     1.3.6.1.4.1.81.8.1.1.27
		genGroupIntrusionControl OBJECT-TYPE
			SYNTAX OCTET STRING
			ACCESS read-write
			STATUS mandatory
			DESCRIPTION
				"Group intrusion security mode (not supported or
				Security Bypass or Secure) assigned to this module.
				Security Bypass - all ports in this group are not secure.
				Secure - ports in this group will perform security as defined
				per port, in the port level.
				The information is coded in internal  format."
			::= { genGroupEntry 27 }

--     1.3.6.1.4.1.81.8.1.1.28
		genGroupThresholdStatus OBJECT-TYPE
			SYNTAX OCTET STRING (SIZE (4))
			ACCESS read-only
			STATUS mandatory
			DESCRIPTION
				"This item is a bitmap that defines the threshold status of the
				module, in relation to the alarmPolicyTable. If the ring is
				monitored by the agent according to policy number x in the
				alarmPolicyTable, and the threshold condition has occured, then
				the bit #x in this item will have the value '1'. Otherwise it will be  '0'.
				For x-186 based agents all bits of this item are '0'."
			::= { genGroupEntry 28 }

--     1.3.6.1.4.1.81.8.1.1.29
		genGroupEavesdropping OBJECT-TYPE
			SYNTAX OCTET STRING
			ACCESS read-write
			STATUS mandatory
			DESCRIPTION
				"Group eavesdropping security mode (not supported or
				Security Bypass or Secure) assigned to this module.
				Security Bypass - all ports in this group are not secure.
				Secure - ports in this group will perform security as defined
				per port, in the port level.
				This attribute can be assigned to security modules.
				The information is coded in internal proprierty format."
			::= { genGroupEntry 29 }

--     1.3.6.1.4.1.81.8.1.1.30
		genGroupMainSWVersion OBJECT-TYPE
			SYNTAX DisplayString
			ACCESS read-only
			STATUS mandatory
			DESCRIPTION
				"ASCII string for description and display of the main CPU software
				version in modules that utilize more than one management processor."
			::= { genGroupEntry 30 }

--     1.3.6.1.4.1.81.8.1.1.31
		genGroupMPSActivityStatus OBJECT-TYPE
			SYNTAX INTEGER
				{
				notActive(1),
				active(2),
				notSupported(255)
				}
			ACCESS read-only
			STATUS mandatory
			DESCRIPTION
				"This attribute defines the status of the main
				PS inside the stackable hub."
			::= { genGroupEntry 31 }

--     1.3.6.1.4.1.81.8.1.1.32
		genGroupBUPSActivityStatus OBJECT-TYPE
			SYNTAX INTEGER
				{
				notActive(1),
				active(2),
				notPresent(3),
				notSupported(255)
				}
			ACCESS read-only
			STATUS mandatory
			DESCRIPTION
				"This attribute defines the status of the backup PS
				externally connected to the module."
			::= { genGroupEntry 32 }

--     1.3.6.1.4.1.81.8.1.1.33
		genGroupPrepareCounters OBJECT-TYPE
			SYNTAX INTEGER
				{
				none(1),
				ethPortCounters(2),
				ethPortErrCounters(3),
				ethPortSWCounters(4),
				fethPortSWCounters(5),
				ethGroupCounters(6),
				fethGroupCounters(7),
				scEthCounters(8),
				notSupported(255)
				}
			ACCESS read-write
			STATUS mandatory
			DESCRIPTION
				"This item should help the agent to prepare
				a large amount of counters. The agent should
				reset this value to none(1), when it has terminated
				to prepare the counters.
				fethGroupCounters(7) - This counters are only supported by RISC agents for LFE1008."
			DEFVAL { none }
			::= { genGroupEntry 33 }

--     1.3.6.1.4.1.81.8.1.1.34
		genGroupPortLastChange OBJECT-TYPE
			SYNTAX OCTET STRING
			ACCESS read-only
			STATUS mandatory
			DESCRIPTION
				"This item contains the last two bytes of the TimeStamp of
				the last change of each port as follows:
				Bytes 0 -1: port 1,
				Bytes 2 -3: port 2,
				Bytes 4 -5: port 3, and so on.
				No trap should be sent on the item change."
			::= { genGroupEntry 34 }

--     1.3.6.1.4.1.81.8.1.1.35
		genGroupIntPortLastChange OBJECT-TYPE
			SYNTAX OCTET STRING
			ACCESS read-only
			STATUS mandatory
			DESCRIPTION
				"This item contains the last two bytes of the TimeStamp of
				the last change of each internal port as follows:
				Bytes 0 -1: internal port 1,
				Bytes 2 -3: internal port 2,
				Bytes 4 -5: internal port 3, and so on.
				No trap should be sent on the item change."
			::= { genGroupEntry 35 }

--     1.3.6.1.4.1.81.8.1.1.36
		genGroupFaultMask OBJECT-TYPE
			SYNTAX OCTET STRING
			ACCESS read-only
			STATUS mandatory
			DESCRIPTION
				"Each bit of this item describes the situation of the
				group regarding specific fault.
				For example:
				bit 1: on indicates 'module internal
					communication problem'
				bit 2 : on indicates 'module hardware problem'
					and so on.

				The fault traps will be sent.

				1   genGroupInterProcCommStatus =commProblems(2) or
				    genGroupInterProcCommStatus =noCommunication(3), or
				    genGroupCommStatus = commProblems(2) or
				    genGroupCommStatus = noCommunication(3)
				2   genGroupSupplyVoltageFault = on(1) or
				    genGroupHWStatus = hardwareProblems(2) or
				    fethGroupFunctionalStatus = malfunctioning(3)
				3   ethGroupFIFO = on(1)
				4   ethGroupWrongPortSelection = on(1)
				5   radFddiGroupTestResult= faulty(2)
				6   iwrPMState = fail(2) or iwrIOMState = fail(2)
				7   genGroupMPSActivityStatus = notActive(1)
				8   genGroupBUPSActivityStatus = notActive(1)
				9   lntAtmGroupBITResult = faulty(2)
				10  tokGroupLSTBeaconing = on(1)
				11  genCTIGroupCellLossAlarm=cellLossAlarm(2)
				12  scGenGroupStatus=loadsBudgetProblem(2)
				13  scGenGroupFansStatus=oneFanFailed(2)
				14  scGenGroupBUPSFansStatus=oneFanFailed(2)
				15  genGroupCascadUpStatus=rld(2)
				16  genGroupCascadDownStatus=rld(2)
				17  genGroupCascadUpStatus=blocked(3)
				18  genGroupCascadDownStatus=blocked(3)
				19  pethMainPseOperStatus=OFF(2) Inline Power Supply failure
				20  Inline software download failure (No MIB value)
				21  Powerinline consumption crossed the usage threshold
				"
			::= { genGroupEntry 36 }

--     1.3.6.1.4.1.81.8.1.1.37
		genGroupTypeName OBJECT-TYPE
			SYNTAX DisplayString (SIZE (0..32))
			ACCESS read-only
			STATUS mandatory
			DESCRIPTION
				"String with the module name."
			::= { genGroupEntry 37 }

--     1.3.6.1.4.1.81.8.1.1.38
		genGroupAgentSlot OBJECT-TYPE
			SYNTAX INTEGER (1..255)
			ACCESS read-write
			STATUS mandatory
			DESCRIPTION
				"This attribute defines the slot number of the Agent supporting this group.
				If there is multiplexor, than the value will be the multiplxor slot number.
				If there is no multiplexor, the value will be the mudule's slot number.
				The default value is the module's slot number."
			::= { genGroupEntry 38 }

--     1.3.6.1.4.1.81.8.1.1.39
		genGroupMngType OBJECT-TYPE
			SYNTAX INTEGER
				{
				agent(1),
				subAgent(2),
				sensor(3),
				notSupported(255)
				}
			ACCESS read-only
			STATUS mandatory
			DESCRIPTION
				"This attribute defines the management type of the module."
			::= { genGroupEntry 39 }

--     1.3.6.1.4.1.81.8.1.1.40
		genGroupNumberOfLogicalPorts OBJECT-TYPE
			SYNTAX INTEGER (0..255)
			ACCESS read-only
			STATUS mandatory
			DESCRIPTION
				"Number of logical ports in group.
				The logical ports represent the Link Aggregation Groups (LAGs) associated with
				that module/switch. It is assumed that on each group the logical ports are assigned
				unique numbers in the range from (genGroupNumberOfPorts+1) to
				(genGroupNumberOfPorts+genGroupNumberOf LogicalPorts)."
			::= { genGroupEntry 40 }

--     1.3.6.1.4.1.81.8.1.1.41
		genGroupNumberOfInterfaces OBJECT-TYPE
			SYNTAX INTEGER
			ACCESS read-only
			STATUS mandatory
			DESCRIPTION
				"The number of network interfaces (regardless of their current state)
				present on this module. This will help determined the ifNumber for the entire system"
			::= { genGroupEntry 41 }

--     1.3.6.1.4.1.81.8.1.1.42
		genGroupCascadUpStatus OBJECT-TYPE
			SYNTAX INTEGER
				{
				ok(1),
				rld(2),
				blocked(3),
				notSupported(255)
				}
			ACCESS read-only
			STATUS mandatory
			DESCRIPTION
				"The functional status of the P330 two cascading-up ports:
				ok(1) - fully functional ports, transmitting and receiving packets.
				rld(2) - receive link down condition on at least one of the ports.
				blocked(3) - stacking up problem"
			::= { genGroupEntry 42 }

--     1.3.6.1.4.1.81.8.1.1.43
		genGroupCascadDownStatus OBJECT-TYPE
			SYNTAX INTEGER
				{
				ok(1),
				rld(2),
				blocked(3),
				notSupported(255)
				}
			ACCESS read-only
			STATUS mandatory
			DESCRIPTION
				"The functional status of the P330 two cascading-down ports:
				ok(1) - fully functional ports, transmitting and receiving packets.
				rld(2) - receive link down condition on at least one of the ports.
				blocked(3) - stacking down problem"
			::= { genGroupEntry 43 }

--     1.3.6.1.4.1.81.8.1.1.44
		genGroupSTARootPortID OBJECT-TYPE
			SYNTAX INTEGER
			ACCESS read-only
			STATUS mandatory
			DESCRIPTION
				"The port ID. Number through which the STA Root bridge can be reached.
				If it is one of the P330 backplane port, its port id. will be from 201 to 204,
				as referring to backplane Guitar ports, numbered from 0 to 3 respectively.
				This will help the STA to run in a distributed environment, i.e. as for P330.
				Note that internally, STA function will use only one port id.
				for the backplane ports, that is 120. For this reason, port id. 120 should not be used in the future. "
			::= { genGroupEntry 44 }

--     1.3.6.1.4.1.81.8.1.1.45
		genGroupCopyPortInstruction OBJECT-TYPE
			SYNTAX OCTET STRING
			ACCESS read-write
			STATUS mandatory
			DESCRIPTION
				"This variable is used internally by the P330 Master for sending a contracted instruction code to
				every Slave agent of the stack. The instruction is coded as follows:
				1st Octet:	0 - reset the following port mirroring
						1 - set the following port mirroring
				2nd to 5th:	mirroring source port id.
				6th to 9th:	mirroring destination port id.
				10th Octet:	mirroring direction:
					1 - Rx only
					2 - Tx only
					3 - both
				Ports id. 201 to 204 refer to the P330 backplane Guitar ports, 0 to 3 respectively.
				Port id. 301, 302, 303 refer to P330 backplane LAGs, down, up,
				and fat (a single four ports LAG) respectively."
			::= { genGroupEntry 45 }

--     1.3.6.1.4.1.81.8.1.1.46
		genGroupLicenseKey OBJECT-TYPE
			SYNTAX OCTET STRING (SIZE (12))
			ACCESS read-write
			STATUS mandatory
			DESCRIPTION
				"This MIB item contains the authorization key for SMON application,
				and for other applications in the future."
			::= { genGroupEntry 46 }

--     1.3.6.1.4.1.81.8.1.1.47
		genGroupLogFileClear OBJECT-TYPE
			SYNTAX INTEGER
				{
				on(1),
				off(2)
				}
			ACCESS read-write
			STATUS mandatory
			DESCRIPTION
				"This attribute enables the user to clear all the log files attached of a specific module."
			::= { genGroupEntry 47 }

--     1.3.6.1.4.1.81.8.1.1.48
		genGroupBootVersion OBJECT-TYPE
			SYNTAX DisplayString
			ACCESS read-only
			STATUS mandatory
			DESCRIPTION
				"ASCII string for description and display of the booter version of the module."
			::= { genGroupEntry 48 }

--     1.3.6.1.4.1.81.8.1.1.49
		genGroupResetLastStamp OBJECT-TYPE
			SYNTAX TimeTicks
			ACCESS read-only
			STATUS mandatory
			DESCRIPTION
				"This attribute contains the value of sysUpTime at the time it polled"
			::= { genGroupEntry 49 }

--     1.3.6.1.4.1.81.8.1.1.50
		genGroupSerialNumber OBJECT-TYPE
			SYNTAX DisplayString
			ACCESS read-only
			STATUS mandatory
			DESCRIPTION
				" The burnt-in identifier of the device. This is a unique 7-digits number"
			::= { genGroupEntry 50 }

--     1.3.6.1.4.1.81.8.1.1.51
		genGroupShowModuleInformation OBJECT-TYPE
			SYNTAX DisplayString
			ACCESS read-only
			STATUS mandatory
			DESCRIPTION
				"String that includes all information of the Show Module CLI Command.
				TAB String indicates new column, while CR String indicates new line."
			::= { genGroupEntry 51 }

--     1.3.6.1.4.1.81.8.1.1.52
		genGroupCascadingUpFault OBJECT-TYPE
			SYNTAX INTEGER
				{
				enable(1),
				disable(2),
				notSupported(255)
				}
			ACCESS read-write
			STATUS mandatory
			DESCRIPTION
				" Enable /Disable the sending of cascading up fault traps for this module."
			DEFVAL { enable }
			::= { genGroupEntry 52 }

--     1.3.6.1.4.1.81.8.1.1.53
		genGroupCascadingDownFault OBJECT-TYPE
			SYNTAX INTEGER
				{
				enable(1),
				disable(2),
				notSupported(255)
				}
			ACCESS read-write
			STATUS mandatory
			DESCRIPTION
				" Enable /Disable the sending of cascading down fault traps for this module."
			DEFVAL { enable }
			::= { genGroupEntry 53 }

--     1.3.6.1.4.1.81.8.1.1.54
		genGroupPortClassificationMask OBJECT-TYPE
			SYNTAX OCTET STRING
			ACCESS read-only
			STATUS mandatory
			DESCRIPTION
				"This is a mask of the port classification values of all ports of this module.
				The index of the bits starts from 0, where bit 0 is unused.
				If the n bit has value of 1 - it means that the n port
				has valuable port classification.
				If the value of the n bit is 0 then either there is
				no such port or its port classification is 0.
				For example:
				If the first 10 ports of a module are valuable ports and
				there is no plugin then the value of this MIB is:
				7f e0
				If a module has 10 regular ports and there is a plugin
				with 2 valuable ports (which are considered as ports
				51, 52) then the value of this MIB is:
				00 00 00 00 00 00 18"
			::= { genGroupEntry 54 }

--     1.3.6.1.4.1.81.8.1.1.55
		genGroupPSUType OBJECT-TYPE
			SYNTAX INTEGER
				{
				ac(1),
				dc(2),
				notSupported(255)
				}
			ACCESS read-write
			STATUS mandatory
			DESCRIPTION
				"This attribute defines the type main PSU of each module."
			::= { genGroupEntry 55 }

--     1.3.6.1.4.1.81.8.1.1.56
		genGroupPolicyType OBJECT-TYPE
			SYNTAX INTEGER
				{
				router(1),
				all(2),
				notSupported(255)
				}
			ACCESS read-write
			STATUS mandatory
			DESCRIPTION
				"This attribute defines whether the module active
				policy-list is enforced on all packets or only on routed
				packets."
			DEFVAL { router }
			::= { genGroupEntry 56 }
 --     1.3.6.1.4.1.81.8.1.1.57
         	genGroupFips140Ready OBJECT-TYPE
                 	SYNTAX INTEGER
                 	{
                      	   on(1),
                   	   off(2)
                 	}
                 	ACCESS read-only
                 	STATUS mandatory
                 	DESCRIPTION
 				"This attribute reports on when module was manufactured compliant
 				 to FIPS 140-2 standard. When reports off the module
 				 is not FIPS compliant and cannot operate in FIPS approved
				 mode as defined by the standard. "
                 	DEFVAL { off }
                 ::= { genGroupEntry 57 }

--     Generic Port group
-- mandatory for all managed  ports
-- 1.3.6.1.4.1.81.9
		genPort OBJECT IDENTIFIER ::= { lannet 9 }

--     1.3.6.1.4.1.81.9.1
		genPortTable OBJECT-TYPE
			SYNTAX SEQUENCE OF GenPortEntry
			ACCESS not-accessible
			STATUS mandatory
			DESCRIPTION
				"Table of configuration attributes for managed	ports.
				Includes configuration data which are independent of the
				specific functionality of the port."
			::= { genPort 1 }

--     1.3.6.1.4.1.81.9.1.1
		genPortEntry OBJECT-TYPE
			SYNTAX GenPortEntry
			ACCESS not-accessible
			STATUS mandatory
			DESCRIPTION
				"An entry in the table, containing data about a single port."
			INDEX { genPortGroupId, genPortId }
			::= { genPortTable 1 }

		GenPortEntry ::=
			SEQUENCE {
				genPortGroupId
					INTEGER,
				genPortId
					INTEGER,
				genPortFunctionality
					INTEGER,
				genPortType
					INTEGER,
				genPortDescr
					DisplayString,
				genPortActivityStatus
					INTEGER,
				genPortSecurityPolicy
					OCTET STRING,
				genPortSecureAddresses
					OCTET STRING,
				genPortIntPortConnection
					INTEGER,
				genPortAdminStatus
					INTEGER,
				genPortSpecificOID
					OBJECT IDENTIFIER,
				genPortThresholdStatus
					OCTET STRING,
				genPortEavesdropping
					OCTET STRING,
				genPortFaultMask
					OCTET STRING,
				genPortSWRdFault
					INTEGER,
				genPortActivation
					INTEGER,
				genPortFunctionalStatus
					INTEGER,
				genPortIfMap
					INTEGER,
				genPortVLANMode
					INTEGER,
				genPortAdminPermission
					INTEGER,
				genPortName
					DisplayString,
				genPortClassification
					INTEGER,
				genPortVLANBindingMode
					INTEGER
			 }

--     1.3.6.1.4.1.81.9.1.1.1
		genPortGroupId OBJECT-TYPE
			SYNTAX INTEGER (1..255)
			ACCESS read-only
			STATUS mandatory
			DESCRIPTION
				"Index which identifies the group inside the chassis for which this
				entry contains information. Equals the number of the slot by which
				the group containing the port is accessed. This value is never greater
				than chNumberOfSlots."
			::= { genPortEntry 1 }

--     1.3.6.1.4.1.81.9.1.1.2
		genPortId OBJECT-TYPE
			SYNTAX INTEGER (1..255)
			ACCESS read-only
			STATUS mandatory
			DESCRIPTION
				"Index which identifies the port inside the group for which this
				entry contains information. It generally corresponds with the number
				by which the port is identified and is marked on the module.
				This value is never greater than genGroupNumberOfPorts of the group
				to which the port belongs."
			::= { genPortEntry 2 }

--     34 - 39 free
-- 1.3.6.1.4.1.81.9.1.1.3
		genPortFunctionality OBJECT-TYPE
			SYNTAX INTEGER
				{
				private(1),
				repeaterAUI(2),
				repeaterThin(3),
				repeater10BaseT(4),
				tenBaseFSyncAct(5),
				foirl(6),
				xcvr(7),
				lobe(8),
				ri(9),
				ro(10),
				serial(11),
				localTalk(12),
				fddi(13),
				clock(14),
				genTokenRing(15),
				dte(16),
				activeLobe(17),
				genActiveTokenRing(18),
				tenBaseFB(19),
				eth10BaseT(20),
				fiber(21),
				wan(22),
				star(23),
				activeRI(24),
				activeRO(25),
				fl(26),
				sonet-oc3(27),
				a100BaseTX(28),
				a100BaseFX(29),
				oc3(30),
				anATM-Main(31),
				anATM-Secondary(32),
				a1000BaseFX(33),
				sonet(40),
				fimVoice(41),
				sdh-stm1(42),
				eth1000BaseSX(43),
				eth1000BaseLX(44),
				eth10BaseFL(45),
				ethLAG(46),
				lag100(47),
				lag1000(48),
				eth1000BaseTX(49),
				eth1000BaseCX(50),
				gBICNotPresent(51),
				gBICNotSupported(52),
				eth1000BaseX-Proprietary(53),
				oc12(54),
				sFP-NotPresent(55),
				sFP-NotSupported(56),
				eth10BaseTwInPWR(57),
				eth100BaseTXwInPWR(58)
				}
			ACCESS read-only
			STATUS mandatory
			DESCRIPTION
				"Describes the functionality of the port according to international standards."
			::= { genPortEntry 3 }

--     Agent 5.1
-- Agent 6.0
-- 97 free
-- 101-106 free
-- 125 free
-- Agent 7.0
-- was ieqr and iefr
-- 143 free
-- Agent 7.1
-- 149-151 free
-- Agent 7.0
-- 1002 free
-- 1003 free
-- 1011 free
-- 3006-3008 free
-- 1.3.6.1.4.1.81.9.1.1.4
		genPortType OBJECT-TYPE
			SYNTAX INTEGER
				{
				le10bPort(1),
				le10cPort(2),
				le15Port(3),
				le20Port(4),
				le30xPort(5),
				le30xdPort(6),
				le40xPort(7),
				le40xtPort(8),
				lobeRJ45(9),
				lobeD9(10),
				lobeD25(11),
				lobeFO(12),
				ri104D25(13),
				ro104D25(14),
				riRJ45(15),
				riD9(16),
				riD25(17),
				riFO(18),
				ri104RJ45(19),
				ri104D9(20),
				roRJ45(21),
				roD9(22),
				roD25(23),
				roFO(24),
				ro104RJ45(25),
				ro104D9(26),
				le80xtPort(27),
				le140xtPort(28),
				ielb-AUIPort(29),
				ielb-10btPort(30),
				ltrf4Port(31),
				ltrf16Port(32),
				lts16Port(33),
				llt8Port(34),
				le20rPort(35),
				itlbRoPort(36),
				itlbRiPort(37),
				itlbDTEPort(38),
				starFO(39),
				le10bnPort(40),
				le120rPort(41),
				le140xtf-foPort(42),
				le140xtf-10btPort(43),
				le140xtcPort(44),
				le110bPort(45),
				le110bqPort(46),
				le140xtqPort(47),
				lert40-AUIPort(48),
				lert40-10btPort(49),
				clock-int(50),
				clock-ext(51),
				ri104RJ45S(52),
				ro104RJ45S(53),
				lobe104RJ45S(54),
				le20fbPort(55),
				le140xtf-fofbPort(56),
				fddi-micPort1(57),
				fddi-micPort2(58),
				fddi-micPort3(59),
				fddi-stmPort1(60),
				fddi-stmPort2(61),
				fddi-stmPort3(62),
				fddi-stlPort1(63),
				fddi-stlPort2(64),
				fddi-stlPort3(65),
				fddi-stpPort1(66),
				fddi-stpPort2(67),
				fddi-stpPort3(68),
				fddi-utpPort1(69),
				fddi-utpPort2(70),
				fddi-utpPort3(71),
				fddi-stsPort1(72),
				fddi-stsPort2(73),
				fddi-stsPort3(74),
				le140xtnPort(75),
				ltr104a-lobePort(76),
				ltr104a-riPort(77),
				ltr104a-roPort(78),
				le120qPort(79),
				le120sq2PortS(80),
				le120sq2PortM(81),
				le120sq5Port(82),
				le120q-fbPort(83),
				le120sq2-fbPortS(84),
				le120sq2-fbPortM(85),
				le120sq5-fbPort(86),
				ltr108t-lobePort1(87),
				ltr108t-riPort1(88),
				ltr108t-roPort1(89),
				ltr108t-lobePort(90),
				ltr108f-lobePort(91),
				ltr108f-starPortFO(92),
				ltr108f-riPortFO(93),
				ltr108f-roPortFO(94),
				lse808Port(95),
				lhsPort(96),
				iefnPort(98),
				itfnPort(99),
				itrePort(100),
				ierpPort(107),
				lse108Port(108),
				lse208Port(109),
				le110cqPort(110),
				ltr108t-starPort1(111),
				she-10btPort(112),
				she-AUIPort(113),
				she-FOPort(114),
				she-FOSyncPort(115),
				le115qPort(116),
				sht-lobePort(117),
				sht-riRJ45Port(118),
				sht-riD9Port(119),
				sht-riFOPort(120),
				sht-roRJ45Port(121),
				sht-roD9Port(122),
				sht-roFOPort(123),
				lhbPort(124),
				le140xtsPort(126),
				le40xtnPort(127),
				le80xtnPort(128),
				itrpPort(129),
				fddi-lcfPort1(130),
				fddi-lcfPort2(131),
				fddi-lcfPort3(132),
				ltr108f-lobeRJ45(133),
				lse404Port(134),
				star104RJ45S(135),
				she-10bfbPort(136),
				sht-starPort(137),
				le240xtcPort(138),
				le280xtPort(139),
				iefrMICPort(140),
				ri104RJ45SN(141),
				iwr10BaseTPort(142),
				ro104RJ45SN(144),
				sh-efn-AUIPort(145),
				lobe104RJ45SN(146),
				sh-efnPort(147),
				sh-tfnPort(148),
				ierePort(152),
				lse404sPort(153),
				lse404s-fbPort(154),
				le240xtcsPort(155),
				le280xtsPort(156),
				atmMMFPort(157),
				lsaPort(158),
				atmUTPPort(159),
				sh-elbAUIPort(160),
				sh-elb10btPort(161),
				lse404srjPort(162),
				lfe100Port(163),
				lsf100Port(164),
				lst-lobeRJ45Port(165),
				lst-starRJ45Port(166),
				lst-riRJ45Port(167),
				lst-roRJ45Port(168),
				tenBaseTPort(169),
				flPort(170),
				shes-10btPort(171),
				shes-AUIPort(172),
				shes-FOPort(173),
				shes-10bfbPort(174),
				le180xtPort(175),
				lfe1008Port(177),
				lse-pmPort(178),
				sh-40sfPort(179),
				sh-80rjPort(180),
				ls3ls-WAN(181),
				leb200Port(183),
				fat-pipe-fddiPort(184),
				lfe4004Port(186),
				sonetPort(190),
				fimVoicePort(191),
				lfe4004SFPort(192),
				lfe4004STPort(193),
				lge-2000SXPort(194),
				lge-2000LXPort(195),
				lfe8008SUTPPort(196),
				unknownPort(255),
				visage10BTPort(1000),
				visage16200FPort(1001),
				visage16200TPort(1004),
				visage16200FCPort(1005),
				visage800TPort(1006),
				visage800FPort(1007),
				visage16155FRPort(1008),
				visage16155FPort(1009),
				visage2500Port(1010),
				visage3LSPort(1012),
				visage1600TPort(1013),
				visage1000BaseSXPort(1014),
				visage1000BaseLXPort(1015),
				cajunP117SPort(1016),
				cajunP117SRPort(1017),
				m10or100BaseTXPort(2000),
				m100BaseFXPort(2001),
				m1000BaseSXPort(2002),
				m1000BaseLXPort(2003),
				m10BaseFLPort(2004),
				m10BaseTPort(2005),
				m10or100BaseTXdot1QPort(2006),
				m-acc155or622MMFPort(2007),
				m-acc155or622SMFPort(2008),
				cajunP120-10or100TPort(2500),
				cajunP120-100FPort(2501),
				cajunP120-1000SXPort(2502),
				cajunP120-1000LXPort(2503),
				cajunP330-10or100TPort(2504),
				cajunP330-100FPort(2505),
				cajunP330-1000SXPort(2506),
				cajunP330-1000LXPort(2507),
				cajunP330-LAG(2508),
				cajunP330-LAG100(2509),
				cajunP330-LAG1000(2510),
				cajunP110-LAG100(2511),
				cajunP110-LAG1000(2512),
				cajunP120-1000BaseCX-GBIC(2513),
				cajunP120-1000BaseSX-GBIC(2514),
				cajunP120-1000BaseLX-GBIC(2515),
				cajunP120-1000BaseT-GBIC(2516),
				cajunP120-GBIC-NotPresent(2517),
				cajunP120-GBIC-Unknown(2518),
				cajunP120-GBIC-Other(2519),
				cajunP120-FibreChannel-GBIC(2520),
				cajunP120-1000BaseTX(2521),
				cajunP330-1000TXPort(2522),
				cajunP330-1000SX-GBIC(2523),
				cajunP330-1000LX-GBIC(2524),
				cajunP330-1000T-GBIC(2525),
				cajunP330-1000CX-GBIC(2526),
				cajunP330-GBIC-NotPresent(2527),
				cajunP330-GBIC-NotSupported(2528),
				cajunP130-10or100BaseTXPort(2530),
				cajunP130-100BaseFXPort(2531),
				cajunP130-1000BaseSX-GBICPort(2532),
				cajunP130-1000BaseLX-GBICPort(2533),
				cajunP130-1000BaseX-Proprietary-GBICPort(2534),
				cajunP130-GBIC-NotSupported(2535),
				cajunP130-GBIC-NotPresent(2536),
				cajunP130-LAG100(2537),
				cajunP130-LAG1000(2538),
				cajunP130-1000BaseTPort(2539),
				cajunP330-ML-LAG(2540),
				cajunP330-ML-1000SX-SFP(2541),
				cajunP330-ML-1000LX-SFP(2542),
				cajunP330-ML-LAG100(2543),
				cajunP330-ML-LAG1000(2544),
				cajunP330-ML-100or1000TPort(2545),
				cajunP330-ML-10or100TPort(2546),
				cajunP330-ML-SFP-NotPresent(2547),
				cajunP330-ML-SFP-NotSupported(2548),
				cajunP330-10or100TPortAndInPWR(2549),
				cajunP330-ML-1000TX-SFP(2550),
				avayaC360-LAG(2640),
				avayaC360-1000SX-SFP(2641),
				avayaC360-1000LX-SFP(2642),
				avayaC360-LAG100(2643),
				avayaC360-LAG1000(2644),
				avayaC360-100or1000Tport(2645),
				avayaC360-10or100Tport(2646),
				avayaC360-SFP-NotPresent(2647),
				avayaC360-SFP-NotSupported(2648),
				avayaC360-10or100TPortAndInPWR(2649),
				avayaC360-1000TX-SFP(2650),
				avayaG250-10or100TPortAndInPWR(2811),
				avayaG250-10or100TPort(2812),
				avayaG350-LAG(2902),
				avayaG350-1000SX-SFP(2903),
				avayaG350-1000LX-SFP(2904),
				avayaG350-LAG100(2905),
				avayaG350-LAG1000(2906),
				avayaG350-100or1000TPort(2907),
				avayaG350-10or100TPort(2908),
				avayaG350-SFP-NotPresent(2909),
				avayaG350-SFP-NotSupported(2910),
				avayaG350-10or100TPortAndInPWR(2911),
				avayaG350-1000TX-SFP(2912),
				avayaG350-10or100or1000TPort(2913),
				m15-155FPort(3000),
				m3-622FPort(3001),
				m3-622SFPort(3002),
				m15-155SFPort(3003),
				m15-155MSPort(3004),
				m2-2400IPort(3005),
				m4-DS3Port(3009),
				m4-E3Port(3010),
				avayaC460-100Fport(3500),
				avayaC460-1000SX-SFP(3501),
				avayaC460-1000LX-SFP(3502),
				avayaC460-LAG100(3503),
				avayaC460-LAG1000(3504),
				avayaC460-1000TPort(3505),
				avayaC460-10or100Tport(3506),
				avayaC460-SFP-NotPresent(3507),
				avayaC460-SFP-NotSupported(3508),
				avayaC460-10or100TPortAndInPWR(3509),
				avayaW310-LAG(3640),
				avayaW310-1000SX-SFP(3641),
				avayaW310-1000LX-SFP(3642),
				avayaW310-LAG100(3643),
				avayaW310-LAG1000(3644),
				avayaW310-SFP-NotPresent(3647),
				avayaW310-SFP-NotSupported(3648),
				avayaW310-10or100TPortAndInPWR(3649),
				avayaW310-1000TX-SFP(3650),
				avayaCommunicationManagerBranchEditioni40-10or100TPortAndInPWR(4000),
				avayaCommunicationManagerBranchEditioni40-10or100TPort(4001),
				avayaCommunicationManagerBranchEditioni120-LAG(4002),
				avayaCommunicationManagerBranchEditioni120-1000SX-SFP(4003),
				avayaCommunicationManagerBranchEditioni120-1000LX-SFP(4004),
				avayaCommunicationManagerBranchEditioni120-LAG100(4005),
				avayaCommunicationManagerBranchEditioni120-LAG1000(4006),
				avayaCommunicationManagerBranchEditioni120-100or1000TPort(4007),
				avayaCommunicationManagerBranchEditioni120-10or100TPort(4008),
				avayaCommunicationManagerBranchEditioni120-SFP-NotPresent(4009),
				avayaCommunicationManagerBranchEditioni120-SFP-NotSupported(4010),
				avayaCommunicationManagerBranchEditioni120-10or100TPortAndInPWR(4011),
				avayaCommunicationManagerBranchEditioni120-1000TX-SFP(4012),
				avayaCommunicationManagerBranchEditioni120-10or100or1000TPort(4013),
			    avayaCommunicationManagerBranchEditionG450-10or100or1000TPort(4014),
				avayaCommunicationManagerBranchEditionG450-10or100TPort(4015),
				avayaCommunicationManagerBranchEditionG430-10or100Tport(4017),
				avayaCommunicationManagerBranchEditionG430-10or100TPortAndInPWR(4019),
				avayaG430-10or100Tport(4020),
				avayaG430-10or100TPortAndInPWR(4021)
				}
			ACCESS read-only
			STATUS mandatory
			DESCRIPTION
				"Attribute describing the type of  port."
			::= { genPortEntry 4 }

--     1.3.6.1.4.1.81.9.1.1.5
		genPortDescr OBJECT-TYPE
			SYNTAX DisplayString (SIZE (0..32))
			ACCESS read-only
			STATUS mandatory
			DESCRIPTION
				"Descriptor of the port in ASCII (readable) format, mainly for use with
				generic management applications."
			::= { genPortEntry 5 }

--     1.3.6.1.4.1.81.9.1.1.6
		genPortActivityStatus OBJECT-TYPE
			SYNTAX INTEGER
				{
				notActive(1),
				dormant(2),
				active(3),
				notSupported(255)
				}
			ACCESS read-only
			STATUS mandatory
			DESCRIPTION
				"This attribute defines the status of ports that may be part of a redundancy scheme.
				notActive(1) - indicates a disabled port which cannot transmit or receive
				packets even if included in a redundancy scheme.
				dormant(2) - indicates an enabled port which does not transmit or receive
				packets, but because it is included in a redundancy scheme, it may at
				any moment become responsible packet transmission and reception.
				active(3) - indicates that the port transmits and receives packets, serving
				as the main path in the redundant configuration."
			::= { genPortEntry 6 }

--     1.3.6.1.4.1.81.9.1.1.7
		genPortSecurityPolicy OBJECT-TYPE
			SYNTAX OCTET STRING
			ACCESS read-write
			STATUS mandatory
			DESCRIPTION
				"Security policy (noPolicy or Trap Only or Trap and Close) assigned to this port.
				noPolicy - do not perform intrusion control security mechanism.
				Trap Only - perform intrusion control security mechanism and trap
					the console, in case of  security violation.
				Trap and Close - perform intrusion control security mechanism, trap
					the console and close this port, in case of  security violation.
				The information is coded in internal  format."
			::= { genPortEntry 7 }

--     1.3.6.1.4.1.81.9.1.1.8
		genPortSecureAddresses OBJECT-TYPE
			SYNTAX OCTET STRING
			ACCESS read-write
			STATUS mandatory
			DESCRIPTION
				"This attribute defines the security information (physical addresses)
				relevant for the entry. Coded in internal format, cryptographic
				methods may be used for privacy purposes."
			::= { genPortEntry 8 }

--     1.3.6.1.4.1.81.9.1.1.9
		genPortIntPortConnection OBJECT-TYPE
			SYNTAX INTEGER (0..255)
			ACCESS read-only
			STATUS mandatory
			DESCRIPTION
				"The value of this attribute defines the internal port to which the port
				is connected. A value 0 of this attribute would indicate no internal
				port connection (stand-alone mode). Any other positive value equals
				the number of the internal port."
			::= { genPortEntry 9 }

--     1.3.6.1.4.1.81.9.1.1.10
		genPortAdminStatus OBJECT-TYPE
			SYNTAX INTEGER
				{
				enabled(1),
				disabled(2)
				}
			ACCESS read-write
			STATUS mandatory
			DESCRIPTION
				"A disabled port neither transmits nor receives. The port must be explicitly
				enabled to restore operation. For token ring ports, this attribute is read-only."
			::= { genPortEntry 10 }

--     1.3.6.1.4.1.81.9.1.1.11
		genPortSpecificOID OBJECT-TYPE
			SYNTAX OBJECT IDENTIFIER
			ACCESS read-only
			STATUS mandatory
			DESCRIPTION
				"This attribute provides the OID of another group containing
				additional more specific information regarding this instance."
			::= { genPortEntry 11 }

--     1.3.6.1.4.1.81.9.1.1.12
		genPortThresholdStatus OBJECT-TYPE
			SYNTAX OCTET STRING (SIZE (4))
			ACCESS read-only
			STATUS mandatory
			DESCRIPTION
				"This item is a bitmap that defines the threshold status of
				the port, in relation to the alarmPolicyTable. If the port is
				monitored by the agent according to policy number x in the
				alarmPolicyTable, and the threshold condition has occurred,
				then the bit #x in this item will have the value '1'. Otherwise
				it will be '0'. For x-186 based agents all bits of this item are '0'."
			::= { genPortEntry 12 }

--     1.3.6.1.4.1.81.9.1.1.13
		genPortEavesdropping OBJECT-TYPE
			SYNTAX OCTET STRING
			ACCESS read-write
			STATUS mandatory
			DESCRIPTION
				"Eavesdropping security mechanism (Off or On) assigned to this port.
				On - perform Eavesdropping security mechanism in the port.
				The information is coded in internal format."
			::= { genPortEntry 13 }

--     1.3.6.1.4.1.81.9.1.1.14
		genPortFaultMask OBJECT-TYPE
			SYNTAX OCTET STRING
			ACCESS read-only
			STATUS mandatory
			DESCRIPTION
				"Each bit of this item describes the situation of the port
				regarding specific fault. For example:
				bit 1: on indicates 'port autopartition fault'
				bit4 : on indicates 'Ethernet port connection problem'
				and so on.
				The fault trap will be sent contains the genPortFaultMask item.

				0 Don't care
				1   ethPortAutoPartitionState = autoPartition(1) or
				     fethPortAutoPartitionState = autoPartition(1) or
				     scEthPortFunctionalStatus = partition(8) or
				     genPortFunctionalStatus = partition(8)
				4   ethPortNoAUILoop = on(1) or
				     ethPortJabber = on(1) or
				     ethPortMJLP = on(1) or
				     ethPortFunctionalStatus = localJabber(3) or
				     ethPortFunctionalStatus = illSeq(6) or
				     ethPortFunctionalStatus = shortCirc(7) or
				     ethPortFunctionalStatus = partitionOrLocalJabber(8) or
				     ethPortFIFO = on(1) or
				     fethPortFIFO = on(1) or
				     fethPortFunctionalStatus = localJabber(3) or
				     scEthPortAutoNegotiationStatus = fail(2)
				7   ethPortFunctionalStatus = rld(2) or
				     fethPortFunctionalStatus = rld(2) or
				     scEthPortFunctionalStatus = rld(2) or
				     genPortFunctionalStatus = rld(2)
				10 ethPortFunctionalStatus = tld(4) or
				     ethPortFunctionalStatus = remoteJabber(5) or
				     ethPortFunctionalStatus = remoteFaultOrLockLost(9) or
				     ethPortFunctionalStatus = remoteFault(10) or
				     ethPortFunctionalStatus = lockLost(11) or
				     fethPortFunctionalStatus = remoteFault(10)
				11 tokPortRingSpeedError= on(1)
				12 tokPortFunctionalStatus = rld(2) or tld(4) or
				     tokPortConnected = notConnected(2)
				15 tokPortCableFault =	on(1)
				16 radFddiPortTestResult= faulty(2)
				17 radFddiPortFunctionalStatus=  lerAlarm(2)
				18 radFddiPortFunctionalStatus= lerCutoff(3)
				19 ltalkPortJam = on(1)
				20 ltalkPortTestResult = faulty(2)
				21 clPortFunctionalStatus = faulty(2)
				22 itrLinkFunctionalStatus = fail(2) or  noRxClk(3)
				23 fethPortFunctionalStatus = wrongSpeed(12)
				24 lhsLinkStatus = linkFailure(2)
				25 lntFddiPortRingConfiguration = isolate(5)
				26 lntFddiPortRingConfiguration = wrap-a(2) or wrap-b(3) or wrap-s(4)
				27 atmEdgePortHealthStatus = atmError(2) or
				     atmInterfaceTCAlarmState = lcdFailure
				28 fethPortDormantLinkFunctionalStatus = rld(2) or
				     atmEdgePortDormantHealthStatus = atmError(2)
				29 sonetSectionCurrentStatus = sonetSectionLOS or sonetSectionLOF or
				     sonetLineCurrentStatus = sonetLineAIS or
				     sonetPathCurrentStatus = sonetPathSTSLOP or sonetPathSTSAIS or
									      sonetPathUnequipped or sonetPathSignalLabelMismatch
				30 sonetLineCurrentStatus = sonetLineRDI or
				     sonetPathCurrentStatus = sonetPathSTSRDI
				31 genCTIPortSync = not ok(1)
				32 genCTIPortRxAlarm = not ok(1)
				33 genCTIPortTxAlarm = not ok(1)
				34 atmEdgePortILMIStatus = down(2)
				35 atmEdgePortSignalStatus = down(2)
				37 pethPsePortDetectionStatus = fault or otherFault
				"
			::= { genPortEntry 14 }

--     1.3.6.1.4.1.81.9.1.1.15
		genPortSWRdFault OBJECT-TYPE
			SYNTAX INTEGER
				{
				ok(1),
				fault(2)
				}
			ACCESS read-only
			STATUS mandatory
			DESCRIPTION
				"Attribute that reports to the Agent of any fault occurs in the
				port for the Soft Redundancy application"
			::= { genPortEntry 15 }

--     1.3.6.1.4.1.81.9.1.1.16
		genPortActivation OBJECT-TYPE
			SYNTAX INTEGER
				{
				enabled(1),
				disabled(2)
				}
			ACCESS read-write
			STATUS mandatory
			DESCRIPTION
				"A disabled port neither transmits nor receives. The port must be
				Explicitly enabled to restore operation."
			::= { genPortEntry 16 }

--     1.3.6.1.4.1.81.9.1.1.17
		genPortFunctionalStatus OBJECT-TYPE
			SYNTAX INTEGER
				{
				ok(1),
				rld(2),
				rxJabber(3),
				partition(8),
				remoteFault(10),
				notSupported(255)
				}
			ACCESS read-only
			STATUS mandatory
			DESCRIPTION
				"The functional status of the port:
				ok(1) - fully functional port, transmitting and receiving packets.
				rld(2) - receive link down condition on the port - Indicates
				a cable  or connector failure detected by the port H/W.
				rxJabber(3) -
				partition(8) - the port is in partition state.
				RemoteFault(10) - "
			::= { genPortEntry 17 }

--     1.3.6.1.4.1.81.9.1.1.18
		genPortIfMap OBJECT-TYPE
			SYNTAX INTEGER
			ACCESS read-only
			STATUS mandatory
			DESCRIPTION
				"This MIB object defines the mapping of the LANNET box port to a
				MIB-II interface. If the port corresponds to a stack of interfaces - like
				the case of ATM ports, the interface number of this port shows the lowest
				interface in the ifStack, the one that typically has a connector present.
				If value zero is returned, the mapping is impossible or unknown for this
				type of port."
			DEFVAL { 0 }
			::= { genPortEntry 18 }

--     1.3.6.1.4.1.81.9.1.1.19
		genPortVLANMode OBJECT-TYPE
			SYNTAX INTEGER
				{
				perPortOnly(1),
				dot1QTagging(2),
				plusTagging(3),
				islTagging(4),
				dot1QTaggingButPVID(5),
				notSupported(255)
				}
			ACCESS read-write
			STATUS mandatory
			DESCRIPTION
				"This item defines the VLAN operation mode of the port:

				perPortOnly(1)	- indicates that all received packets are mapped to the VLAN, defined on the
				port, and packets are transmitted in untagged format;

				dot1QTagging(2) - indicates that all received packets are mapped to VLANs according to
				802.1Q standard. All transmitted packets are tagged according to the standard 802.1Q tagging;

				plusTagging(3)	- indicates that all packets recieved and transmitted on that port are tagged
				according to Lannet-s PlusTagging	scheme. This mode is used when inter-VLAN bridging
				should be supported;

				islTagging(4)	- indicates that all packets recieved and transmitted on that port are tagged
				according to the proprietary ISL mode of Lannet;

				dot1QTaggingButPVID(5) - indicates that all received packets are mapped to VLANs
				according to 802.1Q standard. All transmitted packets are tagged according to the standard
				802.1Q tagging, exluding packets that belong to the port-s VLAN,which are transmitted untagged."
			DEFVAL { dot1QTagging }
			::= { genPortEntry 19 }

--     1.3.6.1.4.1.81.9.1.1.20
		genPortAdminPermission OBJECT-TYPE
			SYNTAX INTEGER
				{
				permit(1),
				notPermit(2),
				notSupported(255)
				}
			ACCESS read-write
			STATUS mandatory
			DESCRIPTION
				"This item defines whether or not the Agent is permitted to change a
				Port Status from Disable to Enable.
					Permit(1) - The agent is permitted to do so.
					NotPermit(2) - The agent is not permitted to do so.
					Default value is: permit(1)."
			DEFVAL { permit }
			::= { genPortEntry 20 }

--     1.3.6.1.4.1.81.9.1.1.21
		genPortName OBJECT-TYPE
			SYNTAX DisplayString (SIZE (0..16))
			ACCESS read-write
			STATUS mandatory
			DESCRIPTION
				"Name of the port in ASCII format, mainly filled by network
				managers for easily recognize the specific use of a switched port."
			::= { genPortEntry 21 }

--     1.3.6.1.4.1.81.9.1.1.22
		genPortClassification OBJECT-TYPE
			SYNTAX INTEGER
				{
				regular(1),
				valuable(2),
				notSupported(255)
				}
			ACCESS read-write
			STATUS mandatory
			DESCRIPTION
				"Classification assigned to this port.
				regular - this port is connected to regular stations.
				Topology changes that may occur on it will not generate the
				sending of topology change (notification) BPDUs,
				will not generate a fast aging on the local forwarding database,
				and will not be signaled by console if the port administrative status is disabled.
				valuable - this port is used as a backbone link or is connected to a valuable server.
				Topology changes that may occur on it will generate a fast aging on the local forwarding database,
				and if STA is enabled on the stack, the sending of topology change (notification) BPDUs.
				It will also be signaled and propagated by console even if the port administrative
				status is disabled or if STA is disabled on this port."
			::= { genPortEntry 22 }

--     1.3.6.1.4.1.81.9.1.1.23
		genPortVLANBindingMode OBJECT-TYPE
			SYNTAX INTEGER
				{
				static(1),
				bindToAll(2),
				bindToConfigured(3),
				gVRP(4),
				notSupported(255)
				}
			ACCESS read-write
			STATUS mandatory
			DESCRIPTION
				"VLAN binding mode assigned to this port.
				static - this port supports only the egress VLAN list as configured
					manually in its corresponding
					dot1qVlanStaticEgressPort. This is the default VLAN
					Binding mode.
				bindToAll - this port supports the whole range of VLANs from VLAN
					ID 1 to the max VLAN ID supported by the device.
				bindToConfigured - this port supports the egress VLAN IDs for
					which dot1qVlanStaticTable rows exist.
				GVRP - this port supports the egress VLAN IDs configured
					manually in its corresponding
					dot1qVlanStaticEgressPort as well as VLAN IDs requested by
					 the GVRP link partner."
			::= { genPortEntry 23 }

--     Generic Internal Port group
-- Implementation of this group is mandatory for all
-- SNMP agents.
-- 1.3.6.1.4.1.81.10
		genIntPort OBJECT IDENTIFIER ::= { lannet 10 }

--     1.3.6.1.4.1.81.10.1
		genIntPortTable OBJECT-TYPE
			SYNTAX SEQUENCE OF GenIntPortEntry
			ACCESS not-accessible
			STATUS mandatory
			DESCRIPTION
				"Table of configuration attributes of  internal ports.
				Internal ports are physical and/or logical entities which
				transfer information and connect modules to the internal
				networks (buses)."
			::= { genIntPort 1 }

--     1.3.6.1.4.1.81.10.1.1
		genIntPortEntry OBJECT-TYPE
			SYNTAX GenIntPortEntry
			ACCESS not-accessible
			STATUS mandatory
			DESCRIPTION
				"An entry in the table, containing data about a single port."
			INDEX { genIntPortGroupId, genIntPortId }
			::= { genIntPortTable 1 }

		GenIntPortEntry ::=
			SEQUENCE {
				genIntPortGroupId
					INTEGER,
				genIntPortId
					INTEGER,
				genIntPortAdminStatus
					INTEGER,
				genIntPortActivityStatus
					INTEGER,
				genIntPortBusConnNumber
					INTEGER,
				genIntPortBusConnType
					INTEGER,
				genIntPortSpecificOID
					OBJECT IDENTIFIER,
				genIntPortMonitorMode
					INTEGER
			 }

--     Agent 6.0
-- 1.3.6.1.4.1.81.10.1.1.1
		genIntPortGroupId OBJECT-TYPE
			SYNTAX INTEGER (1..255)
			ACCESS read-only
			STATUS mandatory
			DESCRIPTION
				"Index which identifies the group inside the chassis for which this
				entry contains information. Equals the number of the slot by which
				the group containing the internal port is accessed. This value is
				never greater than chNumberOfSlots."
			::= { genIntPortEntry 1 }

--     1.3.6.1.4.1.81.10.1.1.2
		genIntPortId OBJECT-TYPE
			SYNTAX INTEGER (1..255)
			ACCESS read-only
			STATUS mandatory
			DESCRIPTION
				"Index which identifies the port inside the group for which this
				entry contains information.
				This value is never greater than genGroupNumberOfIntPorts
				of the group to which the port belongs."
			::= { genIntPortEntry 2 }

--     1.3.6.1.4.1.81.10.1.1.3
		genIntPortAdminStatus OBJECT-TYPE
			SYNTAX INTEGER
				{
				enabled(1),
				disabled(2)
				}
			ACCESS read-write
			STATUS mandatory
			DESCRIPTION
				"Defines the capability of the internal port to transmit or receive data.
				A disabled internal port neither transmits or receives. The port must be
				explicitly enabled to restore operation."
			::= { genIntPortEntry 3 }

--     1.3.6.1.4.1.81.10.1.1.4
		genIntPortActivityStatus OBJECT-TYPE
			SYNTAX INTEGER
				{
				notActive(1),
				dormant(2),
				active(3),
				notSupported(255)
				}
			ACCESS read-only
			STATUS mandatory
			DESCRIPTION
				"This attribute defines the status of internal ports that may be part of
				a redundancy scheme.
				notActive(1) - indicates a disabled port which cannot transmit or receive
				packets even if included in a redundancy scheme.
				dormant(2) - indicates an enabled port which does not transmit or receive
				packets, but because it is included in a redundancy scheme, it may at
				any moment become responsible packet transmission and reception.
				active(3) - indicates that the port transmits and receives packets, serving
				as the main path in the redundant configuration."
			::= { genIntPortEntry 4 }

--     1.3.6.1.4.1.81.10.1.1.5
		genIntPortBusConnNumber OBJECT-TYPE
			SYNTAX INTEGER (0..255)
			ACCESS read-write
			STATUS mandatory
			DESCRIPTION
				"The value of this attribute defines the shared bus or virtual network
				to which the internal port is connected. The value '0' indicates that
				the port is disconnected from the bus. In switch environments
				(virtual net) 0 and 255 are read only values"
			::= { genIntPortEntry 5 }

--     Agent 6.0
-- Agent 7.1
-- 1.3.6.1.4.1.81.10.1.1.6
		genIntPortBusConnType OBJECT-TYPE
			SYNTAX INTEGER
				{
				ethernet(1),
				token-ring(2),
				local-talk(3),
				fddi(4),
				high-speed(5),
				fastEthernet(6),
				xSwitch(7),
				atm(8),
				other(255)
				}
			ACCESS read-only
			STATUS mandatory
			DESCRIPTION
				"The value of this attribute defines the type of the bus to which
				the internal port is connected."
			::= { genIntPortEntry 6 }

--     1.3.6.1.4.1.81.10.1.1.7
		genIntPortSpecificOID OBJECT-TYPE
			SYNTAX OBJECT IDENTIFIER
			ACCESS read-only
			STATUS mandatory
			DESCRIPTION
				"This attribute provides the OID of another group containing
				additional more specific information regarding this instance."
			::= { genIntPortEntry 7 }

--     1.3.6.1.4.1.81.10.1.1.8
		genIntPortMonitorMode OBJECT-TYPE
			SYNTAX INTEGER
				{
				on(1),
				off(2),
				notSupported(255)
				}
			ACCESS read-write
			STATUS mandatory
			DESCRIPTION
				"This attribute enables monitoring of a specified bus (RMON)."
			::= { genIntPortEntry 8 }

--     Software Redundancy Group
-- Implementation of this group is mandatory for all chassis
-- SNMP agents.
-- 1.3.6.1.4.1.81.11
		softRedundancy OBJECT IDENTIFIER ::= { lannet 11 }

--     1.3.6.1.4.1.81.11.1
		softRedundancyTable OBJECT-TYPE
			SYNTAX SEQUENCE OF SoftRedundancyEntry
			ACCESS not-accessible
			STATUS mandatory
			DESCRIPTION
				"Table of attributes which define software redundancy links
				defined by means of the  chassis SNMP agents."
			::= { softRedundancy 1 }

--     1.3.6.1.4.1.81.11.1.1
		softRedundancyEntry OBJECT-TYPE
			SYNTAX SoftRedundancyEntry
			ACCESS not-accessible
			STATUS mandatory
			DESCRIPTION
				"An entry in the table, containing data about a single
				software redundancy link."
			INDEX { softRedundancyId }
			::= { softRedundancyTable 1 }

		SoftRedundancyEntry ::=
			SEQUENCE {
				softRedundancyId
					INTEGER,
				softRedundancyName
					DisplayString,
				softRedundancyGroupId1
					INTEGER,
				softRedundancyPortId1
					INTEGER,
				softRedundancyGroupId2
					INTEGER,
				softRedundancyPortId2
					INTEGER,
				softRedundancyStatus
					INTEGER
			 }

--     1.3.6.1.4.1.81.11.1.1.1
		softRedundancyId OBJECT-TYPE
			SYNTAX INTEGER (1..255)
			ACCESS read-only
			STATUS mandatory
			DESCRIPTION
				"Index which identifies the software redundancy link which for
				which the current entry provides information."
			::= { softRedundancyEntry 1 }

--     1.3.6.1.4.1.81.11.1.1.2
		softRedundancyName OBJECT-TYPE
			SYNTAX DisplayString (SIZE (1..15))
			ACCESS read-write
			STATUS mandatory
			DESCRIPTION
				"Logical name of the software redundancy link"
			::= { softRedundancyEntry 2 }

--     1.3.6.1.4.1.81.11.1.1.3
		softRedundancyGroupId1 OBJECT-TYPE
			SYNTAX INTEGER (1..255)
			ACCESS read-write
			STATUS mandatory
			DESCRIPTION
				"ID of the group to which the main port on the software redundancy
				link belongs. This value is never greater than chNumberOfSlots."
			::= { softRedundancyEntry 3 }

--     1.3.6.1.4.1.81.11.1.1.4
		softRedundancyPortId1 OBJECT-TYPE
			SYNTAX INTEGER (1..255)
			ACCESS read-write
			STATUS mandatory
			DESCRIPTION
				"ID of the main port on the software redundancy link."
			::= { softRedundancyEntry 4 }

--     1.3.6.1.4.1.81.11.1.1.5
		softRedundancyGroupId2 OBJECT-TYPE
			SYNTAX INTEGER (1..255)
			ACCESS read-write
			STATUS mandatory
			DESCRIPTION
				"ID of the group to which the secondary port on the software redundancy
				link belongs. This value is never greater than chNumberOfSlots."
			::= { softRedundancyEntry 5 }

--     1.3.6.1.4.1.81.11.1.1.6
		softRedundancyPortId2 OBJECT-TYPE
			SYNTAX INTEGER (1..255)
			ACCESS read-write
			STATUS mandatory
			DESCRIPTION
				"ID of the secondary port on the software redundancy link."
			::= { softRedundancyEntry 6 }

--     1.3.6.1.4.1.81.11.1.1.7
		softRedundancyStatus OBJECT-TYPE
			SYNTAX INTEGER
				{
				valid(1),
				createRequest(2),
				underCreation(3),
				invalid(4)
				}
			ACCESS read-write
			STATUS mandatory
			DESCRIPTION
				"Status of the entry in the softRedundancy Table:
				valid(1) indicates that row is busy with meaningful values;
				createRequest(2) will be set by manager when creating a new row;
				underCreation(3) indicates that agent accepts create command and performs it;
				invalid(4) indicates that no meaningful values are present in the row.
				Managers set this value in order to transmit a 'Delete row' command to agent."
			::= { softRedundancyEntry 7 }

--     1.3.6.1.4.1.81.11.2
		softRedundancyGlobalStatus OBJECT-TYPE
			SYNTAX INTEGER
				{
				enable(1),
				disable(2),
				notSupported(255)
				}
			ACCESS read-write
			STATUS mandatory
			DESCRIPTION
				" This attribute is used to allow the user to preserve the information,
				configured in the SWRedundancy table, although not activating it.
				The user can disable it when STA is enable in the switch."
			DEFVAL { enable }
			::= { softRedundancy 2 }

--     1.3.6.1.4.1.81.11.3
		fastRedundancyTable OBJECT-TYPE
			SYNTAX SEQUENCE OF FastRedundancyEntry
			ACCESS not-accessible
			STATUS mandatory
			DESCRIPTION
				"Table of attributes which define the unique fast redundancy link
				defined by means of the  chassis SNMP agents."
			::= { softRedundancy 3 }

--     1.3.6.1.4.1.81.11.3.1
		fastRedundancyEntry OBJECT-TYPE
			SYNTAX FastRedundancyEntry
			ACCESS not-accessible
			STATUS mandatory
			DESCRIPTION
				"The unique entry in the table, containing data about the
				fast redundancy link."
			INDEX { fastRedundancyId }
			::= { fastRedundancyTable 1 }

		FastRedundancyEntry ::=
			SEQUENCE {
				fastRedundancyId
					INTEGER,
				fastRedundancyName
					DisplayString,
				fastRedundancyGroupId1
					INTEGER,
				fastRedundancyPortId1
					INTEGER,
				fastRedundancyGroupId2
					INTEGER,
				fastRedundancyPortId2
					INTEGER,
				fastRedundancyStatus
					INTEGER
			 }

--     1.3.6.1.4.1.81.11.3.1.1
		fastRedundancyId OBJECT-TYPE
			SYNTAX INTEGER (1..255)
			ACCESS read-only
			STATUS mandatory
			DESCRIPTION
				"Index which identifies the fast redundancy link for
				which the current entry provides information.
				Since only a single entry is supported, it will be always 1."
			::= { fastRedundancyEntry 1 }

--     1.3.6.1.4.1.81.11.3.1.2
		fastRedundancyName OBJECT-TYPE
			SYNTAX DisplayString (SIZE (1..15))
			ACCESS read-write
			STATUS mandatory
			DESCRIPTION
				"Logical name of the fast redundancy link.
				The default value for this item is 'fast'"
			::= { fastRedundancyEntry 2 }

--     1.3.6.1.4.1.81.11.3.1.3
		fastRedundancyGroupId1 OBJECT-TYPE
			SYNTAX INTEGER (1..255)
			ACCESS read-write
			STATUS mandatory
			DESCRIPTION
				"ID of the group to which the main port on the fast redundancy
				link belongs. This value is never greater than chNumberOfSlots."
			::= { fastRedundancyEntry 3 }

--     1.3.6.1.4.1.81.11.3.1.4
		fastRedundancyPortId1 OBJECT-TYPE
			SYNTAX INTEGER (1..255)
			ACCESS read-write
			STATUS mandatory
			DESCRIPTION
				"ID of the main port on the fast redundancy link."
			::= { fastRedundancyEntry 4 }

--     1.3.6.1.4.1.81.11.3.1.5
		fastRedundancyGroupId2 OBJECT-TYPE
			SYNTAX INTEGER (1..255)
			ACCESS read-write
			STATUS mandatory
			DESCRIPTION
				"ID of the group to which the secondary port on the fast redundancy
				link belongs. This value is never greater than chNumberOfSlots."
			::= { fastRedundancyEntry 5 }

--     1.3.6.1.4.1.81.11.3.1.6
		fastRedundancyPortId2 OBJECT-TYPE
			SYNTAX INTEGER (1..255)
			ACCESS read-write
			STATUS mandatory
			DESCRIPTION
				"ID of the secondary port on the fast redundancy link."
			::= { fastRedundancyEntry 6 }

--     1.3.6.1.4.1.81.11.3.1.7
		fastRedundancyStatus OBJECT-TYPE
			SYNTAX INTEGER
				{
				valid(1),
				createRequest(2),
				underCreation(3),
				invalid(4)
				}
			ACCESS read-write
			STATUS mandatory
			DESCRIPTION
				"Status of the entry in the fastRedundancy Table:
				valid(1) indicates that the row is set with meaningful values;
				createRequest(2) will be set by Console when creating the row;
				underCreation(3) indicates that agent accepts create command and performs it;
				invalid(4) indicates that no meaningful values are present in the row.
				Console will set this value in order to transmit a 'Delete row' command to agent."
			::= { fastRedundancyEntry 7 }

--     1.3.6.1.4.1.81.11.4
		softRedundancyMinTimeBetweenSwitchOvers OBJECT-TYPE
			SYNTAX INTEGER
			ACCESS read-write
			STATUS mandatory
			DESCRIPTION
				"The minimum gap between redundancy-switchovers in primary/secondary
				pairs (in milliseconds)."
			DEFVAL { 60000 }
			::= { softRedundancy 4 }

--     1.3.6.1.4.1.81.11.5
		softRedundancySwitchBackInterval OBJECT-TYPE
			SYNTAX INTEGER
			ACCESS read-write
			STATUS mandatory
			DESCRIPTION
				"The period the primary port link has to be 'up' before the system
				switches back (in milliseconds).
				If switchback interval is zero, the system never switches back.
				     	 If it is one, the system switches back immediately."
			DEFVAL { 0 }
			::= { softRedundancy 5 }


	END

--
-- CONFIG-MIB.my
--
