--========================================================
--
-- MIB      : Application               Madge Networks Ltd
--
-- Version  : 8.9.0                            12 May 2003
--
--
-- ========================================================
-- Source Safe data:
-- $Revision: 1.1 $
-- Check In: $Date: 2005/03/03 12:50:48 $
-- $Author: llevinsk $
-- $Archive:  $
-- ========================================================
--
-- Copyright 1992,1993, 1994, 1995, 1996, 1997,1998,1999,2000
-- 2001,2002,2003 Avaya Inc.
-- All Rights Reserved.
--
-- Reproduction of this document is authorized on condition
-- that the foregoing copyright notice is included.
--
-- This Avaya Inc. SNMP Management Information Base Specification
-- (Specification) embodies Avaya Inc.  confidential and
-- proprietary intellectual property.  MADGE retains all
-- title and ownership in the Specification, including any revisions
--
-- It is MADGE's intent to encourage the widespread use of this
-- Specification in connection with the management of MADGE products.
-- MADGE grants vendors, end-users, and other interested parties
-- a non-exclusive license to use this Specification in connection
-- with the management of MADGE products.
--
-- This Specification is supplied "as is," and MADGE makes
-- no warranty, either express or implied, as to the use,
-- operation, condition, or performance of the Specification.
--
--========================================================
--
-- RCS
--
-- Version 8.9.0
-- 12 May 2003 - Itai Z
-- Added  vnsPacketExpectedIfName, vnsPacketDetectedIfName
--   for supporting routers with physical interfaces
-- Version 8.8.0
-- 7 Apr. 1998
-- 1. Replace scPortHistoryGoodBroadcastPktsRec and scPortHistoryGoodMulticastPktsRec
--     mib items in the scPortHistoryTable with scPortHistoryGoodNonUnicastPktsRec - Dan R.
-- 2. Add new item portHistoryMemoryAvailability to portHistory sub-tree. - Dan R.
--
-- Version 8.7.0
-- 1 Feb. 1998
-- 1. Delete lsHistoryNumberOfBuckets mib item (un-used) - Rafi H.
-- 2. Move portHistoryExtendedControlTable from lsMonitor sub-tree to smon sub-tree
--     under portHistory and add portHistoryExtendedControlName item to this table - Dan R.
-- 3. Move lsPortHistoryTable from lsMonitor sub-tree to smon sub-tree under portHistory - Dan R.
-- 4. Add scPortHistoryTable to smon sub-tree under portHistory. - Dan R.
--
-- Version 8.6.0
-- 23 December 1997
-- 1. Change INDEX of lsHistoryExtendedControlTable to standard RMON index - Dan R.
-- 2. Add new item lsHistoryExtendedControlCreateTime to lsHistoryExtendedControlTable. - Dan R.
-- 3. Add new table lsPortHistory - Dan R.
--
-- Version 8.5.1
-- 19 December 1997
-- 1. Change SYNTAX of lsPortInTotalErrors from INTEGER to Counter
--     and its description - Rafi H.
-- 2. Add new mib lsPortInCollisions to ls Port table - Rafi H.
-- 3. Change Header of this file - Yigal N.
--
-- Version 8.5
-- Revision A. -	1. Change the description of lseGroupHSBMonStatus mib item to use bits
-- 15-Jun.-1997		    D3-D7.
--
-- Revision B. -	1. Change the STATUS of lseIntPortRxReject and lseIntPortTxReject from
-- 21-July-1997	    mandatory to obsolete.
--
--
-- Version 8.0
-- Revision A. -   1. Splitting lannet80.mib into 3 files, this file contains the lan switch
-- 15-Nov.-1996       modules, SMON application, VNS application and TerrainMaster
--                             application.
-- Revision B. -   1. Add new mib items for smon application, history and alarms
-- 21-Nov.-1996  2. For history application lsHistoryExtendedControlTable with three mib items
--                            lsHistoryExtendedControlIndex, lsHistoryExtendedControlLastBucketIndex,
--                            lsHistoryExtendedControlNumberOfBuckets
--                         3. For alarms application alarmMonitorStatusTable with 2 mib items
--                             alarmMonitorStatusIndex and alarmMonitorStatus.
--                             more new item is alarmUtilitiesCommand.
--
-- Revision C. -   1. add new mib item for leb200 in lse group - lseGroupAssignSlots - Zion S.
-- 11-Dec-1996   2. add more 2 new mib items for leb200n in lse group -
--                             lseGroupHSBMonStatus,  lseGroupEnableHSBReset - Zion S.
--
-- Revision D. -   1. Change the enumaration of alarmUtilitiesCommand parameter to
-- 31-Dec-1996	     idle(1), clearAll(2).
--
--========================================================

APPLIC-MIB DEFINITIONS ::= BEGIN

IMPORTS
      IpAddress, Counter, TimeTicks
    FROM RFC1155-SMI
      OBJECT-TYPE
    FROM RFC-1212
      DisplayString, ifIndex
    FROM RFC1213-MIB
      historyControlIndex
    FROM RMON-MIB
      lannet
    FROM GEN-MIB;


-- Some MIB Compilers need these two lines:
--  enterprises  OBJECT IDENTIFIER ::=
--                { iso org(3) dod(6) internet(1) private(4) 1 }

lntLanSwitch   OBJECT IDENTIFIER ::= { lannet 19 } -- switch group
lntTopology    OBJECT IDENTIFIER ::= { lannet 23 }
smon OBJECT IDENTIFIER ::= { lannet 30 }

lse                OBJECT IDENTIFIER ::= { lntLanSwitch 1 } -- mandatory for LANswitch modules
lhs                OBJECT IDENTIFIER ::= { lntLanSwitch 2 } --
lsMonitor      OBJECT IDENTIFIER ::= { lntLanSwitch 3 } -- LANswitch Monitoring Group
lst                 OBJECT IDENTIFIER ::= { lntLanSwitch 4 } -- TR switch module

lsVNChange OBJECT IDENTIFIER ::=  { lntLanSwitch 6 } -- VNS application
vnsPacket    OBJECT IDENTIFIER ::=  { lntLanSwitch 7 }  -- VNS application


--    This MIB group defines the attributes specific to the Ethernet LANswitch modules

lseGroupTable OBJECT-TYPE
      SYNTAX  SEQUENCE OF LseGroupEntry
      ACCESS  not-accessible
      STATUS  mandatory
      ::= { lse 1 }

lseGroupEntry OBJECT-TYPE
      SYNTAX  LseGroupEntry
      ACCESS  not-accessible
      STATUS  mandatory
      INDEX  { lseGroupId }
      ::= { lseGroupTable 1 }

LseGroupEntry  ::=
      SEQUENCE  {
	lseGroupId
	  INTEGER,
	lseGroupFastOpen
	  INTEGER,
	lseGroup10MSqlt
	  INTEGER,
	lseGroupSmartSqlt
	  INTEGER,
	lseGroupCParameter
	  INTEGER,
	lseGroupIPGJamLength
	  INTEGER,
	lseGroupJamLength
	  INTEGER,
	lseGroupDataBlinderLength
	  INTEGER,
	lseGroupIPGDataLength
	  INTEGER,
	lseGroupActiveMonitor
	  INTEGER,
	lseGroupBackbone12
	  INTEGER,
	lseGroupSetDefaults
	  INTEGER,
	lseGroupBackbone34
	  INTEGER,
	lseGroupBackboneRedun12
	  INTEGER,
	lseGroupBackoffFromJam
	  INTEGER,
	lseGroupCAMClear
	  INTEGER,
             lseGroupJamPrevent
               INTEGER,
             lseGroupNormOpCl
               INTEGER,
	lseGroupNormOpDelay
	  INTEGER,
	lseGroupAutoPartitionEnable
	  INTEGER,
	lseGroupWorkState
	  INTEGER,
	lseGroupBITResult
	  INTEGER,
	lseGroupAssignSlots
	  OCTET STRING,
	lseGroupHSBMonStatus
	  INTEGER,
	lseGroupEnableHSBReset
	  INTEGER
      }

lseGroupId OBJECT-TYPE
      SYNTAX  INTEGER
      ACCESS  read-only
      STATUS  mandatory
      DESCRIPTION
      "Slot number in which the group is installed."
      ::= { lseGroupEntry 1 }

lseGroupFastOpen OBJECT-TYPE
      SYNTAX  INTEGER {
	on(1),
	off(2),
	notSupported(255)
	}
      ACCESS read-write
      STATUS mandatory
      DESCRIPTION
      "Setting the value of this attribute to ON activates the port for short idle time
      when code violation was detected."
      ::= { lseGroupEntry 2 }

lseGroup10MSqlt OBJECT-TYPE
      SYNTAX  INTEGER {
	on(1),
	off(2),
	notSupported(255)
	}
      ACCESS read-write
      STATUS mandatory
      DESCRIPTION
      "Setting the value of this attribute to ON activates the mechanism of detection
      preamble of 10Mhz."
      ::= { lseGroupEntry 3 }

lseGroupSmartSqlt OBJECT-TYPE
      SYNTAX  INTEGER {
	on(1),
	off(2),
	notSupported(255)
	}
      ACCESS read-write
      STATUS deprecated
      DESCRIPTION
      "Control the mechnism of the input sensitivity of the port."
      ::= { lseGroupEntry 4 }

lseGroupCParameter OBJECT-TYPE
     SYNTAX  INTEGER  (1..7)
     ACCESS read-write
     STATUS mandatory
     DESCRIPTION
     "Defines the number of consecutive collisions the port waits before it ceases transmitting
     of 512 bits time toward the station."
      ::= { lseGroupEntry 5 }

lseGroupIPGJamLength OBJECT-TYPE
      SYNTAX  INTEGER (16..124)
      ACCESS read-write
      STATUS mandatory
      DESCRIPTION
"Defines the IPG jam length in Ethernet bit time (100nS) start at 16 bit time in
steps of 16, to 112 bit time.
For LFE-100, (Fast Ethernet bit time (10nS))  values are from 48 bit times (480nano-seconds)
 in step of 4, to 124 (1240nano-seconds).
Any number between the defined values will take to nearest smaller value."
      ::= { lseGroupEntry 6 }

lseGroupJamLength OBJECT-TYPE
      SYNTAX  INTEGER (8..120)
      ACCESS read-write
      STATUS mandatory
      DESCRIPTION
"Defines the Jam Length in time starting from 8 (800micro-seconds) to
120 (12mili-seconds). Each step of 8 is equal 800micro-seconds.
For LFE-100, values are from 8 (80micro-seconds) to 32 (320micro-seconds),
each step of 8 is equal 800micro-seconds.
Any number between the defined values will take to nearest smaller value."
      ::= { lseGroupEntry 7 }

lseGroupDataBlinderLength OBJECT-TYPE
      SYNTAX  INTEGER (0..124)
      ACCESS read-write
      STATUS mandatory
      DESCRIPTION
"Defines the Data Blinder Length in Ethernet bit time (100nS) start at 16 bit time in steps of
16 to 112 bit time.
For LFE-100, (Fast Ethernet bit time (10nS))  values are from 0  bit times
 in step of 4, to 124 (1240nano-seconds).
Any number between the defined values will take to nearest smaller value."
      ::= { lseGroupEntry 8 }

lseGroupIPGDataLength OBJECT-TYPE
      SYNTAX  INTEGER (16..124)
      ACCESS read-write
      STATUS mandatory
      DESCRIPTION
"Defines the IPG (Inter Packet Gap) length in Ethernet bit time
(100nS) starting at 16 bit time in steps of 16 to 112 bit time.
For LFE-100, (Fast Ethernet bit time (10nS))  values are from 48 bit times
(480nano-seconds)  in step of 4, to 124 (1240 nano-seconds).
Any number between the defined values will take to nearest smaller value."
      ::= { lseGroupEntry 9 }

lseGroupActiveMonitor OBJECT-TYPE
      SYNTAX  INTEGER {
	on(1),
	off(2),
	notSupported(255)
	}
      ACCESS read-only
      STATUS mandatory
      DESCRIPTION
      "This attribute defines the  module which is the high-speed bus active monitor."
      ::= { lseGroupEntry 10 }

lseGroupBackbone12 OBJECT-TYPE
     SYNTAX  INTEGER {
	on(1),
	off(2),
	notSupported(255)
	}
     ACCESS  read-write
     STATUS  mandatory
     DESCRIPTION
"Port 1 and 2 in the board perform as Backbone link.
lse208 - upper cluster is RX only and lower cluster is TX only.
lse404 - upper port is Rx only and second port is Tx only. Two remains port are performed as regular foirl interfaces.
lse808 - the first port is RX from line only, the second - TX to line only, the rest are in regular10BaseT mode."
     ::= { lseGroupEntry 11 }

lseGroupSetDefaults OBJECT-TYPE
    SYNTAX  INTEGER {
	on(1),
	off(2),
	notSupported(255)
	}
   ACCESS  read-write
   STATUS  mandatory
   DESCRIPTION
   "Set all hardware parameters to their default values. This item will
     always return a value of off(2), since it acts like a toggle switch."
   ::= { lseGroupEntry 12 }

lseGroupBackbone34 OBJECT-TYPE
     SYNTAX  INTEGER {
	on(1),
	off(2),
	notSupported(255)
	}
     ACCESS  read-write
     STATUS  mandatory
     DESCRIPTION
	"Port 3 and 4 in the board performed as Backbone link.
	lse404 - Third port is Rx only and forth port is Tx only.
	Two remaining ports performed as regular foirl interfaces."
     ::= { lseGroupEntry 13 }

lseGroupBackboneRedun12 OBJECT-TYPE
     SYNTAX  INTEGER    {
			on(1),
			off(2),
			notSupported(255)
			}
     ACCESS  read-write
     STATUS  mandatory
     DESCRIPTION
     "Value on(1) of this attribute defines a redundancy (backup)
     relationship between Backbone port 1 and backbone port 2
     on a  LANswiltch module."
     ::= { lseGroupEntry 14 }

lseGroupBackoffFromJam  OBJECT-TYPE
     SYNTAX  INTEGER    {
			on(1),
			off(2),
			notSupported(255)
			}
     ACCESS  read-write
     STATUS  mandatory
     DESCRIPTION
"Value on(1) of this attribute defines non-consecutive
jam after a collision has occured   in  LANswitch modules."
     ::= { lseGroupEntry 15 }

lseGroupCAMClear  OBJECT-TYPE
     SYNTAX  INTEGER    {
			on(1),
			off(2),
			notSupported(255)
			}
     ACCESS  read-write
     STATUS  mandatory
     DESCRIPTION
"Value on(1) of this attribute causes the LANSwitch
module to clear the CAM tables."
     ::= { lseGroupEntry 16 }

lseGroupJamPrevent  OBJECT-TYPE
     SYNTAX INTEGER 	{
			on(1),
			off(2),
			notSupported(255)
			}
     ACCESS  read-write
     STATUS  mandatory
     DESCRIPTION
"Jam prevent flag.
       Functionaly, Jam prevent is a back-pressure into the line direction.
       There are two modes of opration:
       1) automatic - the sensor gets the items status from HW
       2) manual      - the sensor gets the items status from user."
     ::= { lseGroupEntry 17 }


lseGroupNormOpCl  OBJECT-TYPE
     SYNTAX  INTEGER 	{
			open(1),
			closed(2),
			notSupported(255)
			}
     ACCESS  read-write
     STATUS  mandatory
     DESCRIPTION
"Normaly Open/Close flag.
       When open(1) state is set, the sensor should activate
       a delay mechanism for the module to operate at Normaly-Closed
       mode for 30 seconds in order to enable the port's CAM to learn the
       current segmentation"
::= { lseGroupEntry 18 }

lseGroupNormOpDelay OBJECT-TYPE
      SYNTAX  INTEGER (0..600000)
      ACCESS  read-write
      STATUS  mandatory
      DESCRIPTION
      "When sets to a value greater than 0 (zero) and the MIB item
      lseGroupNormOpCl is equal to closed(2), this item define the time
      delay that the module will remain in normally open mode before
      it will move to normaly close mode. This will be activated after
      the user will reset the module.
      The value is in seconds."
      DEFVAL {30}
      ::= { lseGroupEntry 19 }

lseGroupAutoPartitionEnable OBJECT-TYPE
      SYNTAX  INTEGER {
		enable(1),
		disable(2),
		notSupported(255)
    }
      ACCESS  read-write
      STATUS  mandatory
      DESCRIPTION
      " Enables autopartition mechanism support in the group level for each port of the group."
      DEFVAL { disable}
      ::= { lseGroupEntry 20}

lseGroupWorkState OBJECT-TYPE
	SYNTAX  INTEGER {
		run(1),
		boot(2),
		runAndBoot(3),
		none(4),
		notSupported(255)
	}
	ACCESS  read-only
	STATUS  mandatory
	DESCRIPTION
	"One of the possible states of the module: this item
	indicates if the module is runing or booting. The value
	runAndBoot(3) indicates a serious software problem."
	::= { lseGroupEntry 21 }


lseGroupBITResult OBJECT-TYPE
	SYNTAX  INTEGER {
		ok(1),
		faulty(2),
		notSupported(255)
	}
	ACCESS  read-only
	STATUS  mandatory
	DESCRIPTION
	"The  Bit Indication Test in state 'faulty' indicates a problem.
	The agent should send a fault trap in this case."
	::= { lseGroupEntry 22 }

lseGroupAssignSlots OBJECT-TYPE
	SYNTAX  OCTET STRING ( SIZE (2))
	ACCESS  read-write
	STATUS mandatory
	DESCRIPTION
	"In a multi-backbone configuration within a single HUB, this item enables to  assign
              backbone module with specific slot numbers. Only packets from these slots should be
              handled by the backbone module, Packets from other slots are ignored.
              The 16-bit string represents the slots in the hub, a Bit per slot. Bit 0 (LSB) corresponds
              to slot 1, Bit 15 (MSB) corresponds to slot 16.
	A Bit set to '1' indicates that the corresponding slot is assigned to this backbone module.
	A clear Bit '0', indicates that the corresponding slot is ignored by this module.
	Todate, only the LEB200 module supports this capability.
	The string is expressed in Hex.
	Default value is FF, i.e., all slots are assigned to module."
	::= {lseGroupEntry 23}

lseGroupHSBMonStatus OBJECT-TYPE
	SYNTAX  INTEGER
	ACCESS  read-only
	STATUS mandatory
	DESCRIPTION
	"This is a bit-masked attribute which displays events which may cause HSB Reset.
	When a bit is '1', the relevant evet may cause HSB Reset.
	When a bit is '0', the relevant evet will not cause HSB Reset.
	The following are the events:
	  LSB	 D0 - Too many packets were discarded from a queue.
		 D1 - One of the Tx buffers to HSB is full for more than a default period.
		 D2 - Token has not been available for more than a default period.
		 D3 - RX Buffer full in one of the ports.
		 D4 -'1' HSB Reset has been occured , '0'- HSB reset hadn't occured since last
                                    time this MIB has been read.
		 D5 - '0' - the ram of the relevant port is O.K. (the port is decode in D6-D7) , '1'
                                   The ram is not O.K.
		 D6-  D7  Decode the relevant port that It's ram is not O.K
			00 - Port  no'0
			01 - Port  no' 1
			10 - Port  no' 2
			11 - Port  no' 3."
	::= {lseGroupEntry 24}

lseGroupEnableHSBReset OBJECT-TYPE
	SYNTAX  INTEGER {
		enable (1),
		disable (2),
		notSupported (255)
	}
	ACCESS  read-write
	STATUS mandatory
	DESCRIPTION
	"This item enables/disables the HSB Reset mechanism in  the module."
	::= {lseGroupEntry 25}


-- This MIB group contains the attributes of the LANswitch internal port,
-- i.e., the connection of the LANswitch to the highspeed bus.

lseIntPort OBJECT IDENTIFIER ::= {lse 2}

lseIntPortTable OBJECT-TYPE
      SYNTAX  SEQUENCE OF LseIntPortEntry
      ACCESS  not-accessible
      STATUS  mandatory
      ::= { lseIntPort 1 }

lseIntPortEntry OBJECT-TYPE
      SYNTAX  LseIntPortEntry
      ACCESS  not-accessible
      STATUS  mandatory
      DESCRIPTION
      "An entry in the table, containing data about a single internal LanSwitch bank."
      INDEX  { lseIntPortGroupId, lseIntPortId }
      ::= { lseIntPortTable 1 }

LseIntPortEntry  ::=
      SEQUENCE  {
	lseIntPortGroupId
	  INTEGER,
	lseIntPortId
	  INTEGER,
	lseIntPortIOMode
	  INTEGER,
	lseIntPortResetSwitchCAM
	  INTEGER,
	lseIntPortVideoPacket
	  INTEGER,
	lseIntPortPriorityStateMachine
	  INTEGER,
	lseIntPortActiveBroadcastPriority
	  INTEGER,
	lseIntPortPriorityLevel
	  INTEGER,
	lseIntPortSuperPriorityEnable
	  INTEGER,
	lseIntPortRoutingMode
	  INTEGER,
	lseIntPortGlobal
	  INTEGER,
	lseIntPortLearnIOCAM
	  INTEGER,
	lseIntPortSecurity
	  INTEGER,
	lseIntPortIgnoreBusy
	  INTEGER,
	lseIntPortRetryPriorityLevel1
	  INTEGER,
	lseIntPortRetryPriorityLevel2
	  INTEGER,
	lseIntPortRetryPriorityLevel3
	  INTEGER,
	lseIntPortIgnoreProtocolType
	  INTEGER,
	lseIntPortCompanyMAC
	  OCTET STRING,
	lseIntPortTxSafetyZone
	  INTEGER,
	lseIntPortRxSafetyZone
	  INTEGER,
	lseIntPortTxBurstLength
	  INTEGER,
	lseIntPortSecurityIntruder
	  INTEGER,
	lseIntPortJabber
	  INTEGER,
	lseIntPortCAM
	  OCTET STRING,
	lseIntPortVideoStateMachine
	  INTEGER,
	lseIntPortTransmitWeight
	  INTEGER,
	lseIntPortSuperPriority
	  INTEGER,
	lseIntPortAlignment
	 Counter,
	lseIntPortRxReject
	 Counter,
	lseIntPortTxReject
	 Counter,
	lseIntPortRxEmpty0
	 INTEGER,
	lseIntPortRxEmpty1
	 INTEGER,
	lseIntPortRxEmpty2
	 INTEGER,
	lseIntPortSuperNetNumber
	 INTEGER,
	lseIntPortGlobalSuperNet
	 INTEGER,
	lseIntPortMACAddress
	 OCTET STRING,
	lseIntPortIgnoreRoutingMode
	 INTEGER,
	lseIntPortCAMLastChange
	 TimeTicks,
	lseIntPortCopiedPort
	  INTEGER,
	lseIntPortBroadcastBehavior
	  INTEGER,
	lseIntPortFilteringMethod
	  INTEGER,
	lseIntPortSetFilter
	  OCTET STRING,
	lseIntPortRemoveFilter
	  OCTET STRING,
	lseIntPortClearFilter
	   INTEGER,
	lseIntPortMonitorMissedEvents
	  Counter
    }

lseIntPortGroupId OBJECT-TYPE
      SYNTAX  INTEGER (1..255)
      ACCESS  read-only
      STATUS  mandatory
      DESCRIPTION
      "Id of the group to which the port belongs."
      ::= { lseIntPortEntry 1 }

lseIntPortId OBJECT-TYPE
      SYNTAX  INTEGER (1..255)
      ACCESS  read-only
      STATUS  mandatory
      DESCRIPTION
      "Number of LanSwitch port in the board."
      ::= { lseIntPortEntry 2 }

lseIntPortIOMode OBJECT-TYPE
      SYNTAX  INTEGER {
	on(1),
	off(2),
	notSupported(255)
	}
      ACCESS read-write
      STATUS mandatory
      DESCRIPTION
      "on(1) activates IO mode in which all packets on the
        high-speed bus that were not captured by any regular
        port are captured by the I/O port."
      ::= { lseIntPortEntry 3 }

lseIntPortResetSwitchCAM OBJECT-TYPE
      SYNTAX  INTEGER {
	on(1),
	off(2),
	notSupported(255)
	}
      ACCESS read-write
      STATUS mandatory
      DESCRIPTION
      "Acting like toggle switch thus always returns off(2)
       on read. When set to on(1), causes the reset of the
       LANswitch CAM (addresses) memory."
      ::= { lseIntPortEntry 4 }

lseIntPortVideoPacket OBJECT-TYPE
      SYNTAX  INTEGER {
	on(1),
	off(2),
	notSupported(255)
	}
      ACCESS read-write
      STATUS mandatory
      DESCRIPTION
      "When set to on(1), all Tx packets toward the
      high-speed bus to video type packets."
      ::= { lseIntPortEntry 5 }

lseIntPortPriorityStateMachine OBJECT-TYPE
      SYNTAX  INTEGER {
	on(1),
	off(2),
	notSupported(255)
	}
      ACCESS read-write
      STATUS mandatory
      DESCRIPTION
      "Setting the value of this attribute to on(1) activates
       the priority mechanism."
      ::= { lseIntPortEntry 6 }

lseIntPortActiveBroadcastPriority OBJECT-TYPE
      SYNTAX  INTEGER {
	on(1),
	off(2),
	notSupported(255)
	}
      ACCESS read-write
      STATUS mandatory
      DESCRIPTION
      "Setting the value of this attribute to on(1) activates
      the active broadcast mode in priority mechanism."
      ::= { lseIntPortEntry 7 }

lseIntPortPriorityLevel OBJECT-TYPE
      SYNTAX  INTEGER {
	broadcast(1),
	multicast(2),
	video(3),
	regular(4),
	default(5),
	mngrTerminal(6),
	notSupported(255)
	}
      ACCESS read-write
      STATUS mandatory
      DESCRIPTION
      "This attribute defines the priority levels of
       Tx packets toward the high-speed bus.
      The highest priority is broadcast(1)."
      ::= { lseIntPortEntry 8 }

lseIntPortSuperPriorityEnable OBJECT-TYPE
      SYNTAX  INTEGER {
	on(1),
	off(2),
	notSupported(255)
	}
      ACCESS read-write
      STATUS mandatory
      DESCRIPTION
 " When limited space is left in Tx buffer, only the highest priority
packets are accepted. This in turn  can create a situation in  which one
port tries to  send  a packet and never gets its chance  to be accepted. In
order to prevent it the  destination port counts  the  successive  number
of tries of  the  low priority   port,  and  when a  certain (8)  number is
reached, it accepts the packet anyhow.
The value on(1) defines the retry parameter for the priority level mechanism."
      ::= { lseIntPortEntry 9 }

lseIntPortRoutingMode OBJECT-TYPE
      SYNTAX  INTEGER {
	generic(1),
	net(2),
	dst-port(3),
	allPackets(4),
	notSupported(255)
	}
      ACCESS read-write
      STATUS mandatory
      DESCRIPTION
      "generic(1) - examines all the packets that are
        not members of any virtual network.
        net(2) - examines only the packets that have
        the port's network number.
       allPackets(4) - examine all packets regardless
       of their routing mode."
      ::= { lseIntPortEntry 10 }

lseIntPortGlobal OBJECT-TYPE
      SYNTAX  INTEGER {
	on(1),
	off(2),
	notSupported(255)
	}
      ACCESS read-write
      STATUS mandatory
      DESCRIPTION
      "Setting the global mode to on(1) sets the
       port in a network routing mode that examines
       all packets that are not members of all  virtual networks."
      ::= { lseIntPortEntry 11 }

lseIntPortLearnIOCAM OBJECT-TYPE
      SYNTAX  INTEGER {
	on(1),
	off(2),
	notSupported(255)
	}
      ACCESS read-write
      STATUS mandatory
      DESCRIPTION
      "Setting this parameter to on(1) enables an I/O port to
       learn incoming MAC addresses received in its port and
      store them in its CAM. Packets with destination address
      that match the CAM addresses are not transferred to the high speed bus."
      ::= { lseIntPortEntry 12 }

lseIntPortSecurity OBJECT-TYPE
      SYNTAX  INTEGER {
	on(1),
	off(2),
	notSupported(255)
	}
      ACCESS read-write
      STATUS mandatory
      DESCRIPTION
      "Setting the value of this attribute to on(1) activates the security mode."
      ::= { lseIntPortEntry 13 }

lseIntPortIgnoreBusy OBJECT-TYPE
      SYNTAX  INTEGER {
	on(1),
	off(2),
	notSupported(255)
	}
      ACCESS read-write
      STATUS mandatory
      DESCRIPTION
      "Setting the value of this attribute to on(1) activates the ignore busy mode.
      The busy signal toward the high-speed bus is not activated even though the TX buffer is full."
      ::= { lseIntPortEntry 14 }

lseIntPortRetryPriorityLevel1 OBJECT-TYPE
      SYNTAX  INTEGER (0..31)
      ACCESS read-write
      STATUS mandatory
      DESCRIPTION
      "The port increases the priority level of the high-speed bus packets after the defined number
      (0..31) trials."
      ::= { lseIntPortEntry 15 }

lseIntPortRetryPriorityLevel2 OBJECT-TYPE
      SYNTAX  INTEGER (0..255)
      ACCESS read-write
      STATUS mandatory
      DESCRIPTION
      "The port increases the priority level of the high-speed bus packets after the defined number
      (0..255) trials."
      ::= { lseIntPortEntry 16 }

lseIntPortRetryPriorityLevel3 OBJECT-TYPE
      SYNTAX  INTEGER (0..255)
      ACCESS read-write
      STATUS mandatory
      DESCRIPTION
      "The port increases the priority level of the high-speed bus packets after the defined number
      (0..255) trials."
      ::= { lseIntPortEntry 17 }

lseIntPortIgnoreProtocolType OBJECT-TYPE
      SYNTAX  INTEGER {
	ignore(1),
	not-ignore(2),
	notSupported(255)
	}
      ACCESS read-write
      STATUS mandatory
      DESCRIPTION
      "Any packet regardless of the protocol type is received from the high-speed bus."
      ::= { lseIntPortEntry 18 }

lseIntPortCompanyMAC  OBJECT-TYPE
      SYNTAX  OCTET STRING
      ACCESS read-write
      STATUS mandatory
      DESCRIPTION
      "The attribute defines the first three bytes of the MAC address of the video host server."
      ::= { lseIntPortEntry 19 }

lseIntPortTxSafetyZone OBJECT-TYPE
      SYNTAX   INTEGER (0..510)
      ACCESS read-write
      STATUS mandatory
      DESCRIPTION
      "Defines the Tx Safety Zone in bits."
      ::= { lseIntPortEntry 20 }

lseIntPortRxSafetyZone OBJECT-TYPE
      SYNTAX  INTEGER (0..510)
      ACCESS read-write
      STATUS mandatory
      DESCRIPTION
      "Defines the Rx Safety Zone in bits."
      ::= { lseIntPortEntry 21 }

lseIntPortTxBurstLength OBJECT-TYPE
      SYNTAX  INTEGER (0..510)
      ACCESS read-write
      STATUS mandatory
      DESCRIPTION
      "Defines the TX Burst Length in bits."
      ::= { lseIntPortEntry 22 }

lseIntPortSecurityIntruder OBJECT-TYPE
      SYNTAX  INTEGER {
	on(1),
	off(2),
	notSupported(255)
	}
      ACCESS read-only
      STATUS mandatory
      DESCRIPTION
      "The value on(1) of this attribute reflects a security violation occurrence."
      ::= { lseIntPortEntry 23 }

lseIntPortJabber OBJECT-TYPE
     SYNTAX  INTEGER {
	on(1),
	off(2),
	notSupported(255)
	}
     ACCESS  read-only
     STATUS  mandatory
     DESCRIPTION
     "Value on(1) of this attribute reflects that jabber was transmitted
     to the port by the high-speed bus."
     ::= { lseIntPortEntry 24 }

lseIntPortCAM OBJECT-TYPE
	SYNTAX  OCTET STRING ( SIZE (0..112))
 	ACCESS  read-write
	STATUS  mandatory
	DESCRIPTION
		"112 bytes of MAC addresses. Each contains one
		byte of  the port number and six bytes of the MAC
		address. This enables to send 16 MAC Addresses
		( 16*7=112 bytes)"
	::= { lseIntPortEntry 25 }

lseIntPortVideoStateMachine OBJECT-TYPE
      SYNTAX  INTEGER {
	on(1),
	off(2),
	notSupported(255)
	}
      ACCESS  read-write
      STATUS  mandatory
      DESCRIPTION
      "Setting the value of this attribute to on(1) activates the video state machine mode.
      Received packets are filtered by demand from the station."
      ::= { lseIntPortEntry 26 }

lseIntPortTransmitWeight  OBJECT-TYPE
     SYNTAX  INTEGER (0..127)
     ACCESS  read-write
     STATUS  mandatory
     DESCRIPTION
	"Defines the Transmit Weight of the frames for the current LANswitch port toward
	the high - speed bus."
     ::= { lseIntPortEntry 27 }

lseIntPortSuperPriority OBJECT-TYPE
     SYNTAX  INTEGER {
	on(1),
	off(2),
	notSupported(255)
	}
     ACCESS  read-write
     STATUS  mandatory
     DESCRIPTION
	"Setting the value of this attribute to on(1) activates the retry priority functions."
     ::= { lseIntPortEntry 28 }

lseIntPortAlignment OBJECT-TYPE
	SYNTAX  Counter
	ACCESS  read-only
	STATUS  mandatory
	DESCRIPTION
	"The number of alignment errors observed on a specified port."
	::= { lseIntPortEntry 29 }

lseIntPortRxReject OBJECT-TYPE
	SYNTAX  Counter
	ACCESS  read-only
	STATUS  obsolete
	DESCRIPTION
	"The number of Rx buffer full observed on a specified port, from the line toward the
	High-speed bus."
	::= { lseIntPortEntry 30 }

lseIntPortTxReject OBJECT-TYPE
	SYNTAX  Counter
	ACCESS  read-only
	STATUS  obsolete
	DESCRIPTION
	"The number of Tx buffer full observed on a specified port, from the line toward the
	High-speed bus."
	::= { lseIntPortEntry 31 }

lseIntPortRxEmpty0  OBJECT-TYPE
	 SYNTAX  INTEGER
	ACCESS  read-write
	STATUS  mandatory
	DESCRIPTION
	"Define the highest threshold to receive packets from the HSB.
	This parameter is relevant when the receive buffer is full.
	When the buffer reached this threshold, all packets will be rejected.
	Version 7.0"
	::= { lseIntPortEntry 32 }

lseIntPortRxEmpty1  OBJECT-TYPE
	 SYNTAX  INTEGER
	ACCESS  read-write
	STATUS  mandatory
	DESCRIPTION
	"Define the middle threshold to receive packets from the HSB.
	This parameter is relevant when the receive buffer is almost full.
	When the buffer reached this threshold, the only packets that the port
	will receive will be those with the highest priority (1) who were already
	written in the priority machine. All other packets will be rejected.
	The space between empty1 to empty0 is reserved to packets with
	the highest priority (1) who were already written in the priority machine.
	Version 7.0 "
	::= { lseIntPortEntry 33 }

lseIntPortRxEmpty2  OBJECT-TYPE
	 SYNTAX  INTEGER
	ACCESS  read-write
	STATUS  mandatory
	DESCRIPTION
	"Define the lowest threshold to receive packets from the HSB.
	This parameter is relevant when the receive buffer is almost full.
	When the buffer reached this threshold, the only packets that the port
	will receive will be those with at least middle priority (2) who were
	already written in the priority machine. All other packets will be rejected.
	The space between empty2 to empty1 is reserved to packets with at least
	middle priority (2) who were already written in the priority machine.
	When the buffer did not reached this lowest priority, no packet will be
	rejected for empty space. Version 7.0 "
	::= { lseIntPortEntry 34 }

lseIntPortSuperNetNumber OBJECT-TYPE
	SYNTAX   INTEGER (0..14)
	ACCESS  read-write
	STATUS  mandatory
	DESCRIPTION
	"If the internal port supports SuperNet mode, the user
	have to define the supernet number. Default value is 0.
	Change of this number  when the internal port is Generic,
	Global or Global SuperNet must be blocked by the sensor."
	DEFVAL { 0}
	::= { lseIntPortEntry 35 }

lseIntPortGlobalSuperNet OBJECT-TYPE
	SYNTAX   INTEGER {
			on(1),
			off(2),
			notSupported(255)
	}
	ACCESS  read-write
	STATUS  mandatory
	DESCRIPTION
	"An internal port that is part of all SuperNets is set to
	Global SuperNet routing. The SuperNet number is 15
	in this case. "
	DEFVAL { off }
	::= { lseIntPortEntry 36 }

lseIntPortMACAddress OBJECT-TYPE
	 SYNTAX  OCTET STRING
	ACCESS  read-only
	STATUS  mandatory
	DESCRIPTION
	" The MAC address of the port, if it has. If not, an octet
	string of length 0. "
	::= { lseIntPortEntry 37 }


lseIntPortIgnoreRoutingMode OBJECT-TYPE
	 SYNTAX  INTEGER {
			ignore(1),
			notIgnore(2),
			notSupported(255)
	}
	ACCESS  read-write
	STATUS  mandatory
	DESCRIPTION
	" When this parameter is 'ignore', the LANSwitch
	port monitors all packets without paying attention
	to the virtual net assignment."
	DEFVAL { notIgnore }
	::= { lseIntPortEntry 38 }

lseIntPortCAMLastChange OBJECT-TYPE
	 SYNTAX  TimeTicks
	ACCESS  read-only
	STATUS  mandatory
	DESCRIPTION
	"This attribute contains the value of sysUpTime
	at the time any change occured to the
	content of the specific CAM."
	::= { lseIntPortEntry 39 }

lseIntPortCopiedPort  OBJECT-TYPE
	SYNTAX INTEGER
	ACCESS read-write
	STATUS mandatory
	DESCRIPTION
"The port monitored on the LANswitch bus by the
LSE-PM module. The value of this item is: 32*(S-1)+P,
where S is the slot number in the hub and P the port
within the slot (1.. 32).
When the value of this item is 0, the Copy Port function
 is disabled and the port is in Host Filter mode. For
modules that do not support this functionality, this
item  will have the value 65,535."
	::= { lseIntPortEntry  40 }

lseIntPortBroadcastBehavior   OBJECT-TYPE
	SYNTAX INTEGER {
			normal(1),
			selective(2),
			receiveAll(3),
			notSupported(255)
      		         }
	ACCESS read-write
	STATUS mandatory
	DESCRIPTION
"This item relates only to LSE-PM modules. The value of
this item defines the method by which the module treats
broadcast and multicast packets."
	::= { lseIntPortEntry 41}


lseIntPortFilteringMethod  OBJECT-TYPE
	SYNTAX INTEGER {
		source(1),
		destination(2),
		sourceOrDestination(3),
		group(4),
		notSupported(255)
      	         }
	ACCESS read-write
	STATUS mandatory
	DESCRIPTION
"This item is relevant only to the LSE-PM module.
The value of this item defines the filtering method
used to capture packets from the Cellenium bus to
the Ethernet connection."
	::= { lseIntPortEntry 42 }

lseIntPortSetFilter  OBJECT-TYPE
	SYNTAX  OCTET STRING ( SIZE (0..452))
	ACCESS read-write
	STATUS mandatory
	DESCRIPTION
"This item is relevant only to the LSE-PM module.
The item is used to add new addresses to the module's
filtering table. The string is a sequence of MAC addresses,
6 bytes each. When the item is set, each address in the list
is added to the filtering table, and related packets are then
captured.
This item always returns an empty string in response to
get requests."
	::= { lseIntPortEntry 43 }


lseIntPortRemoveFilter  OBJECT-TYPE
	SYNTAX  OCTET STRING ( SIZE (0..452))
	ACCESS read-write
	STATUS mandatory
	DESCRIPTION
"This item is relevant only to the LSE-PM module.
The item is used to remove existing addresses from
the module's filtering table. The string is a sequence of
MAC addresses, 6 bytes each. When the item is set, all
addresses in the list are removed from the filtering table,
and the module stops capturing related packets ."
	::= { lseIntPortEntry 44 }

lseIntPortClearFilter  OBJECT-TYPE
	SYNTAX   INTEGER {
		idle(1),
		clear(2),
		notSupported(255)
      	         }
	ACCESS read-write
	STATUS mandatory
	DESCRIPTION
"This item is relevant only to the LSE-PM module.
The item acts as a toggle switch: when its value is set
to clear(2), the contents of the module's filtering
tables are cleared.
This item always returns an empty string in response to
get requests."
	::= { lseIntPortEntry 45 }

lseIntPortMonitorMissedEvents OBJECT-TYPE
	SYNTAX Counter
	ACCESS read-only
	STATUS mandatory
	DESCRIPTION
"This item is relevant only to LSE-PM modules. The value
of the counter is the number of packets that were not
captured by the port as a result of overload on the
Ethernet line, though the port's filter was configured
to capture these packets."
	::= { lseIntPortEntry 46}

-- This MIB group contains the variables used in transferring the MAC
-- addresses lists of the LANswitch ports to a management application.

lseIntPortMACAdd OBJECT IDENTIFIER
      ::= {lseIntPort  2 }

lseIntPortMACAddTable OBJECT-TYPE
      SYNTAX  SEQUENCE OF LseIntPortMACAddEntry
      ACCESS  not-accessible
      STATUS  mandatory
      ::= { lseIntPortMACAdd 1 }

lseIntPortMACAddEntry OBJECT-TYPE
      SYNTAX  LseIntPortMACAddEntry
      ACCESS  not-accessible
      STATUS  mandatory
      DESCRIPTION
      "An entry in the table containing data about a single internal switch port."
      INDEX  { lseIntPortMACAddGroupId, lseIntPortMACAddPortId, lseIntPortMACAddLAId }
      ::= { lseIntPortMACAddTable 1 }

LseIntPortMACAddEntry  ::=
      SEQUENCE  {
	lseIntPortMACAddGroupId
	  INTEGER,
	lseIntPortMACAddPortId
	  INTEGER,
	lseIntPortMACAddLAId
	  INTEGER,
	lseIntPortMACAddList
	 OCTET STRING
      }

lseIntPortMACAddGroupId OBJECT-TYPE
      SYNTAX  INTEGER (1..255)
      ACCESS  read-only
      STATUS  mandatory
      DESCRIPTION
      "Id of the group to which the port belongs."
      ::= { lseIntPortMACAddEntry 1 }

lseIntPortMACAddPortId OBJECT-TYPE
      SYNTAX  INTEGER (1..255)
      ACCESS  read-only
      STATUS  mandatory
      DESCRIPTION
      "The LANswitch port number in the board."
      ::= { lseIntPortMACAddEntry 2 }

lseIntPortMACAddLAId OBJECT-TYPE
      SYNTAX  INTEGER
      ACCESS  read-only
      STATUS  mandatory
      DESCRIPTION
"The lower 2 bytes of the Last MAC Address on the previous
list. Use the 0 value to start from the beginning of the list."
      ::= { lseIntPortMACAddEntry 3 }

lseIntPortMACAddList OBJECT-TYPE
      SYNTAX  OCTET STRING ( SIZE (0..452))
      ACCESS  read-only
      STATUS  mandatory
      DESCRIPTION
"This item contains  MAC address (source addresses) of the port.
Each MAC address is 6 bytes long. The list is started with the MAC address
that follows the lseIntPortMACAddLAId."
      ::= { lseIntPortMACAddEntry 4 }

lseIntPortFilter OBJECT IDENTIFIER
      ::= {lseIntPort  3 }

lseIntPortFilterTable OBJECT-TYPE
      SYNTAX  SEQUENCE OF LseIntPortFilterEntry
      ACCESS  not-accessible
      STATUS  mandatory
      ::= { lseIntPortFilter 1 }

lseIntPortFilterEntry OBJECT-TYPE
      SYNTAX  LseIntPortFilterEntry
      ACCESS  not-accessible
      STATUS  mandatory
      DESCRIPTION
"This table is supported only for the LSE-PM module.
The table reports the contents of the port's filtering
mechanism."
     INDEX  { lseIntPortFilterGroupId, lseIntPortFilterPortId, lseIntPortFilterLAId }
      ::= { lseIntPortFilterTable 1 }

LseIntPortFilterEntry  ::=
      SEQUENCE  {
	lseIntPortFilterGroupId
	  INTEGER,
	lseIntPortFilterPortId
	  INTEGER,
	lseIntPortFilterLAId
	  INTEGER,
	lseIntPortFilterList
	 OCTET STRING
      }

lseIntPortFilterGroupId OBJECT-TYPE
      SYNTAX  INTEGER (1..255)
      ACCESS  read-only
      STATUS  mandatory
      DESCRIPTION
"This item is relevant only for the LSE-PM module. The
item defines the group to which the port belongs (i.e.,
the module number)."
      ::= { lseIntPortFilterEntry 1 }

lseIntPortFilterPortId OBJECT-TYPE
      SYNTAX  INTEGER (1..255)
      ACCESS  read-only
      STATUS  mandatory
      DESCRIPTION
"This item is relevant only for the LSE-PM module. The
item defines the number of the LANswitch port in the
board."
      ::= { lseIntPortFilterEntry 2 }

lseIntPortFilterLAId OBJECT-TYPE
      SYNTAX  INTEGER
      ACCESS  read-only
      STATUS  mandatory
      DESCRIPTION
"This item is relevant only for the LSE-PM module. The
item contains the lower 2 bytes of the Last MAC Address
on the previous list. Use the 0 value to start from the
beginning of the list."
      ::= { lseIntPortFilterEntry 3 }

lseIntPortFilterList OBJECT-TYPE
      SYNTAX  OCTET STRING ( SIZE (0..452))
      ACCESS  read-only
      STATUS  mandatory
      DESCRIPTION
"This item is relevant only for the LSE-PM module. The
item contains the  MAC addresses in the filter. Each
MAC address is 6 bytes long. The list is started with the
MAC address that follows the lseIntPortFilterLAId."
      ::= { lseIntPortFilterEntry 4 }

     lseIntPortMACVlanTable OBJECT-TYPE
            SYNTAX SEQUENCE OF LseIntPortMACVlanEntry
            ACCESS not-accessible
            STATUS mandatory
            DESCRIPTION
                "This table extends the lseIntPortMACAddTable table with VLAN support
                providing mirrow of CAM content arranged by port and Vlan. The table
                supports the show cam commands for stack switch products.
                "
            ::= { lseIntPort 4 }

        lseIntPortMACVlanEntry OBJECT-TYPE
            SYNTAX LseIntPortMACVlanEntry
            ACCESS not-accessible
            STATUS mandatory
            INDEX { lseIntPortMACVlanGroupId, lseIntPortMACAddPortId, lseIntPortMACVlanVlan, lseIntPortMACVlanLAId }
            ::= { lseIntPortMACVlanTable 1 }

        LseIntPortMACVlanEntry ::=
            SEQUENCE {
                lseIntPortMACVlanGroupId
                    INTEGER,
                lseIntPortMACVlanPortId
                    INTEGER,
                lseIntPortMACVlanVlan
                    INTEGER,
                lseIntPortMACVlanLAId
                    INTEGER,
                lseIntPortMACVlanMAClist
                    OCTET STRING
             }

        lseIntPortMACVlanGroupId OBJECT-TYPE
            SYNTAX INTEGER (1..255)
            ACCESS not-accessible
            STATUS mandatory
            DESCRIPTION
                "Id of the group to which the port belongs."
            ::= { lseIntPortMACVlanEntry 1 }

        lseIntPortMACVlanPortId OBJECT-TYPE
            SYNTAX INTEGER (1..255)
            ACCESS read-only
            STATUS mandatory
            DESCRIPTION
                "The LANswitch port number in the board."
            ::= { lseIntPortMACVlanEntry 2 }

        lseIntPortMACVlanVlan OBJECT-TYPE
            SYNTAX INTEGER (1..4095)
            ACCESS read-only
            STATUS mandatory
            DESCRIPTION
                "Id of the Vlan "
            ::= { lseIntPortMACVlanEntry 3 }

        lseIntPortMACVlanLAId OBJECT-TYPE
            SYNTAX INTEGER (1..10)
            ACCESS read-only
            STATUS mandatory
            DESCRIPTION
                "The lower 2 bytes of the Last MAC Address on the previous
                list. Use the 0 value to start from the beginning of the list."
            ::= { lseIntPortMACVlanEntry 4 }

        lseIntPortMACVlanMAClist OBJECT-TYPE
            SYNTAX OCTET STRING (SIZE (1..452))
            ACCESS read-only
            STATUS mandatory
            DESCRIPTION
                "This item contains  MAC address (source addresses) of the port.
                Each MAC address is 6 bytes long. The list is started with the MAC address
                that follows the lseIntPortMACVlanLAId."
            ::= { lseIntPortMACVlanEntry 5 }


lsePort OBJECT IDENTIFIER
      ::= {lse 3}


lsePortTable OBJECT-TYPE
      SYNTAX  SEQUENCE OF LsePortEntry
      ACCESS  not-accessible
      STATUS  mandatory
      ::= { lsePort 1 }

lsePortEntry OBJECT-TYPE
      SYNTAX  LsePortEntry
      ACCESS  not-accessible
      STATUS  mandatory
      DESCRIPTION
      "An entry in the table containing data about a single external switch port."
      INDEX  { lsePortGroupId, lsePortId }
      ::= { lsePortTable 1 }

LsePortEntry  ::=
      SEQUENCE  {
	lsePortGroupId
	  INTEGER,
	lsePortId
	  INTEGER,
	lsePortPolarity
	  INTEGER,
	lsePortBackboneStatus
	  INTEGER
     }

lsePortGroupId OBJECT-TYPE
      SYNTAX  INTEGER (1..255)
      ACCESS  read-only
      STATUS  mandatory
      DESCRIPTION
      "Id of the group to which the port belongs."
      ::= { lsePortEntry 1 }

lsePortId OBJECT-TYPE
      SYNTAX  INTEGER (1..255)
      ACCESS  read-only
      STATUS  mandatory
      DESCRIPTION
      "Number of LanSwitch port in the board."
      ::= { lsePortEntry 2 }

lsePortPolarity OBJECT-TYPE
      SYNTAX  INTEGER {
	on(1),
	off(2),
	notSupported(255)
	}
      ACCESS read-write
      STATUS mandatory
      DESCRIPTION
      "Setting the value of this attribute to ON activates the automatic port polarity
      detection mode."
      ::= { lsePortEntry 3 }

 lsePortBackboneStatus OBJECT-TYPE
      SYNTAX  INTEGER {
	     ok(1),
	     fault(2),
	     notSupported(255)
	     }
      ACCESS read-write
      STATUS mandatory
      DESCRIPTION
      "It is the status of a single port that associated with a particular
	Backbone port.
	It is utilized by the Agent in the Soft Redundancy algorithm between
	Backbone ports in LANswitch environment"
      ::= { lsePortEntry 4 }


-- ***********     LHS/LHB  Attributes   *************


lhsGroupTable  OBJECT-TYPE
	SYNTAX  SEQUENCE OF LhsGroupEntry
	ACCESS  not-accessible
	STATUS  mandatory
	DESCRIPTION
	"Table with group-related parameters."
	::= { lhs 1 }

lhsGroupEntry  OBJECT-TYPE
	SYNTAX  LhsGroupEntry
	ACCESS  not-accessible
	STATUS  mandatory
	DESCRIPTION
	"Entry in the table."
	INDEX { lhsGroupId }
	::= { lhsGroupTable 1 }

LhsGroupEntry ::=
	SEQUENCE {
	     lhsGroupId
		INTEGER,
	     lhsGroupMainSWVersion
		DisplayString,
	     lhsGroupProtocolType
		INTEGER
	}

lhsGroupId  OBJECT-TYPE
	SYNTAX  INTEGER
	ACCESS  read-only
	STATUS  mandatory
	DESCRIPTION
	"Unique slot identifier in which the module is located."
	::= { lhsGroupEntry 1 }

lhsGroupMainSWVersion OBJECT-TYPE
	SYNTAX  DisplayString
	ACCESS  read-only
	STATUS  mandatory
	DESCRIPTION
	"Software version of the main CPU."
	::= { lhsGroupEntry 2 }

lhsGroupProtocolType OBJECT-TYPE
      SYNTAX  INTEGER {
	other(1),
	ethernet(2),
	tokenring(3),
	ethernet-tokenring(4),
	notSupported(255)
      }
      ACCESS  read-write
      STATUS  mandatory
      DESCRIPTION
      "This attribute set the protocol type in which the LHB is collecting from
	the high-speed bus."
      ::= { lhsGroupEntry 3 }


lhsPortTable  OBJECT-TYPE
	SYNTAX  SEQUENCE OF LhsPortEntry
	ACCESS  not-accessible
	STATUS  mandatory
	DESCRIPTION
	"Table with port-related parameters."
	::= { lhs 2 }

lhsPortEntry  OBJECT-TYPE
	SYNTAX  LhsPortEntry
	ACCESS  not-accessible
	STATUS  mandatory
	DESCRIPTION
	"Entry in the table."
	INDEX           { lhsPortGroupId, lhsPortId }
	::= { lhsPortTable 1 }

LhsPortEntry ::=
	SEQUENCE {
	     lhsPortGroupId
		INTEGER,
	     lhsPortId
		INTEGER,
	     lhsTxUCast
		Counter,
	     lhsTxBCast
		Counter,
	     lhsTxMCast
		Counter,
	     lhsTxUrunErr
		Counter,
	     lhsTxParErr
		Counter,
	     lhsRxUCast
		Counter,
	     lhsRxBCast
		Counter,
	     lhsRxMCast
		Counter,
	     lhsRxOrunErr
		Counter,
	     lhsRxParErr
		Counter,
	     lhsRxRscErr
		Counter,
	     lhsRxBadTypeErr
		Counter,
	     lhsLinkStatus
		INTEGER
	}

lhsPortGroupId  OBJECT-TYPE
	SYNTAX  INTEGER
	ACCESS  read-only
	STATUS  mandatory
	DESCRIPTION
	"Slot index in which the module is located."
	::= { lhsPortEntry 1 }

lhsPortId  OBJECT-TYPE
	SYNTAX  INTEGER
	ACCESS  read-only
	STATUS  mandatory
	DESCRIPTION
	"Port number to which the data is related."
	::= { lhsPortEntry 2 }

lhsTxUCast  OBJECT-TYPE
	SYNTAX  Counter
	ACCESS  read-only
	STATUS  mandatory
	DESCRIPTION
	" Number of unicast packets transmitted."
	::= { lhsPortEntry 3 }

lhsTxBCast  OBJECT-TYPE
	SYNTAX  Counter
	ACCESS  read-only
	STATUS  mandatory
	DESCRIPTION
	" Number of broadcast packets transmitted."
	::= { lhsPortEntry 4 }

lhsTxMCast  OBJECT-TYPE
	SYNTAX  Counter
	ACCESS  read-only
	STATUS  mandatory
	DESCRIPTION
	" Number of multicast packets transmitted."
	::= { lhsPortEntry 5 }

lhsTxUrunErr  OBJECT-TYPE
	SYNTAX  Counter
	ACCESS  read-only
	STATUS  mandatory
	DESCRIPTION
	" Number of transmit packet underruns."
	::= { lhsPortEntry 6 }

lhsTxParErr  OBJECT-TYPE
	SYNTAX  Counter
	ACCESS  read-only
	STATUS  mandatory
	DESCRIPTION
	" Number of transmit packet parity errors."
	::= { lhsPortEntry 7 }

lhsRxUCast  OBJECT-TYPE
	SYNTAX  Counter
	ACCESS  read-only
	STATUS  mandatory
	DESCRIPTION
	" Number of unicast packets received."
	::= { lhsPortEntry 8 }

lhsRxBCast  OBJECT-TYPE
	SYNTAX  Counter
	ACCESS  read-only
	STATUS  mandatory
	DESCRIPTION
	" Number of broadcast packets received."
	::= { lhsPortEntry 9 }

lhsRxMCast  OBJECT-TYPE
	SYNTAX  Counter
	ACCESS  read-only
	STATUS  mandatory
	DESCRIPTION
	" Number of multicast packets received."
	::= { lhsPortEntry 10 }

lhsRxOrunErr  OBJECT-TYPE
	SYNTAX  Counter
	ACCESS  read-only
	STATUS  mandatory
	DESCRIPTION
	" Number of receive overrun errors."
	::= { lhsPortEntry 11 }

lhsRxParErr  OBJECT-TYPE
	SYNTAX  Counter
	ACCESS  read-only
	STATUS  mandatory
	DESCRIPTION
	" Number of receive parity errors."
	::= { lhsPortEntry 12 }

lhsRxRscErr  OBJECT-TYPE
	SYNTAX  Counter
	ACCESS  read-only
	STATUS  mandatory
	DESCRIPTION
	" Number of receive resource errors. "
	::= { lhsPortEntry 13 }

lhsRxBadTypeErr  OBJECT-TYPE
	SYNTAX  Counter
	ACCESS  read-only
	STATUS  mandatory
	DESCRIPTION
	" Number of bad frame type packets received."
	::= { lhsPortEntry 14 }

lhsLinkStatus OBJECT-TYPE
	SYNTAX  INTEGER {
		ok(1),
		linkFailure(2),
		notSupported(255)
		}
	ACCESS  read-only
	STATUS  mandatory
	DESCRIPTION
	"This attribute describes the status of the optical link as detected
	by the sensor software."
	::= { lhsPortEntry 15}

lsMonitorResourceAllocation OBJECT-TYPE
	SYNTAX    INTEGER 	{
			none(1),
			hostStats(2),
			portExtendedStats(3),
			hostMatrix(4)
				}
	ACCESS read-only
	STATUS mandatory
	DESCRIPTION
	"This item reports for which of the listed
	 monitoring activity CPU resources are
	being allocated at this time. Activities that
	are not in the above list are allocated resources at all times."
	::= { lsMonitor 1 }


lsBusStats OBJECT IDENTIFIER ::= { lsMonitor 2 }        -- LANswitch Bus Statistics

lsBusStatsDropEvents OBJECT-TYPE
	SYNTAX Counter
	ACCESS read-only
	STATUS mandatory
	DESCRIPTION
	"The total number of events in which packets
	were dropped by the probe due to lack of resources.
	Note that this number is not necessarily the number of packets dropped;
	 it is just the number of times this condition has been detected."
	::= { lsBusStats 1 }

lsBusStatsPkts OBJECT-TYPE
	SYNTAX Counter
	ACCESS read-only
	STATUS mandatory
	DESCRIPTION
	"The total number of packets (including error packets)
	received on the LANswitch bus."
	::= { lsBusStats 2 }

lsBusStatsOctets OBJECT-TYPE
	SYNTAX Counter
	ACCESS read-only
	STATUS mandatory
	DESCRIPTION
	"The total number of octets of data (including
	those in bad packets) received on the
	LANswitch bus (excluding framing bits but including
	FCS octets)."
	::= { lsBusStats 3 }

lsBusStatsUtilization OBJECT-TYPE
	SYNTAX INTEGER
	ACCESS read-only
	STATUS mandatory
	DESCRIPTION
	"The utilization of the LANswitch bus, expressed in percents
	of the maximum possible LANswitch traffic."
	::= { lsBusStats 4 }

lsBusStatsEthBroadcastPkts OBJECT-TYPE
	SYNTAX Counter
	ACCESS read-only
	STATUS mandatory
	DESCRIPTION
	"The total number of good Ethernet packets received that were
	 directed to the broadcast address."
	::= { lsBusStats 5 }

lsBusStatsMulticastPkts OBJECT-TYPE
	SYNTAX Counter
	ACCESS read-only
	STATUS mandatory
	DESCRIPTION
	"The total number of good packets received that were
	directed to a multicast address.  Note that this
	number does not include packets directed to the
	broadcast address."
	::= { lsBusStats 6 }

lsBusStatsGoodEthPkts OBJECT-TYPE
	SYNTAX Counter
	ACCESS read-only
	STATUS mandatory
	DESCRIPTION
"The total number of good Ethernet packets received on the LANswitch bus."
	::= { lsBusStats 7 }

lsBusStatsGoodEthOctets OBJECT-TYPE
	SYNTAX Counter
	ACCESS read-only
	STATUS mandatory
	DESCRIPTION
	"The total number of octets that were received on the
	LANswitch bus in good Ethernet packets (excluding framing bits but including FCS octets)."
	::= { lsBusStats 8 }

lsBusStatsBadEthPkts OBJECT-TYPE
	SYNTAX Counter
	ACCESS read-only
	STATUS mandatory
	DESCRIPTION
"The total number of bad Ethernet packets received on the LANswitch bus."
	::= { lsBusStats 9 }

lsBusStatsBadEthOctets OBJECT-TYPE
	SYNTAX Counter
	ACCESS read-only
	STATUS mandatory
	DESCRIPTION
	"The total number of octets that were received on the
	LANswitch bus in bad Ethernet packets (excluding framing
	bits but including FCS octets)."
	::= { lsBusStats 10 }

lsBusStatsNonEthPkts OBJECT-TYPE
	SYNTAX Counter
	ACCESS read-only
	STATUS mandatory
	DESCRIPTION
	"The total number of packets received on the LANswitch
	bus in non Ethernet packets."
	::= { lsBusStats 11 }

lsBusStatsNonEthOctets OBJECT-TYPE
	SYNTAX Counter
	ACCESS read-only
	STATUS mandatory
	DESCRIPTION
	"The total number of octets that were received on the
	LANswitch bus in non Ethernet packets (excluding framing bits but including FCS octets)."
	::= { lsBusStats 12 }

lsBusStatsPriorityTable OBJECT-TYPE
	SYNTAX SEQUENCE OF LsBusStatsPriorityEntry
	ACCESS not-accessible
	STATUS mandatory
	DESCRIPTION
	"A list of priority count entries."
	::= { lsBusStats 13 }

lsBusStatsPriorityEntry OBJECT-TYPE
	SYNTAX LsBusStatsPriorityEntry
	ACCESS not-accessible
	STATUS mandatory
	DESCRIPTION
	"A list of statistics related to a specific priority level on
	the LANswitch bus."
	INDEX { lsBusStatsPriorityIndex }
	::= { lsBusStatsPriorityTable 1 }

LsBusStatsPriorityEntry ::= SEQUENCE {
		lsBusStatsPriorityIndex	INTEGER,
		lsBusStatsPriorityPkts	Counter,
		lsBusStatsPriorityOctets	Counter
				}

lsBusStatsPriorityIndex OBJECT-TYPE
	SYNTAX INTEGER (1..4)
	ACCESS read-only
	STATUS mandatory
	DESCRIPTION
	"The priority for which this entry reports statistics ."
	::= { lsBusStatsPriorityEntry 1 }


lsBusStatsPriorityPkts  OBJECT-TYPE
	SYNTAX Counter
	ACCESS read-only
	STATUS mandatory
	DESCRIPTION
	"The total number of packets (including error packets)
	received on the LANswitch bus whose priority is that defined for this entry."
	::= { lsBusStatsPriorityEntry 2 }

lsBusStatsPriorityOctets  OBJECT-TYPE
	SYNTAX Counter
	ACCESS read-only
	STATUS mandatory
	DESCRIPTION
	"The total number of octets (including error packets)
	received on the LANswitch bus whose packets have the
	priority defined for this entry."
	::= { lsBusStatsPriorityEntry 3 }

lsBusStatsVirtualNetList OBJECT-TYPE
	SYNTAX OCTET STRING (SIZE (32))
	ACCESS read-only
	STATUS mandatory
	DESCRIPTION
	"A bitmap defining the status of the virtual nets in the
	Virtual NetTable. The first bit is for Virtual Net 0 and so
	on. For existing virtual nets the bit is 1, otherwise 0."
	::= { lsBusStats 14 }

lsBusStatsVirtualNetTable OBJECT-TYPE
	SYNTAX SEQUENCE OF LsBusStatsVirtualNetEntry
	ACCESS not-accessible
	STATUS mandatory
	DESCRIPTION
"A list of virtual net statistics."
	::= { lsBusStats 15 }

lsBusStatsVirtualNetEntry  OBJECT-TYPE
	SYNTAX LsBusStatsVirtualNetEntry
	ACCESS not-accessible
	STATUS mandatory
	DESCRIPTION
	"A list of staistics related to a specific virtual net which
	exists on the LANswitch bus."
	INDEX { lsBusStatsVirtualNet }
	::= { lsBusStatsVirtualNetTable 1 }

LsBusStatsVirtualNetEntry   ::= SEQUENCE {
		lsBusStatsVirtualNet	INTEGER,
		lsBusStatsVirtualNetPackets	Counter,
		lsBusStatsVirtualNetOctets	Counter
		}

lsBusStatsVirtualNet  OBJECT-TYPE
	SYNTAX INTEGER
	ACCESS read-only
	STATUS mandatory
	DESCRIPTION
	"The virtual net for which this entry reports statistics ."
	::= { lsBusStatsVirtualNetEntry 1 }

lsBusStatsVirtualNetPackets  OBJECT-TYPE
	SYNTAX Counter
	ACCESS read-only
	STATUS mandatory
	DESCRIPTION
	"The number of good packets that were
	transmitted to this virtual net by ports in this hub."
	::= { lsBusStatsVirtualNetEntry 2 }

lsBusStatsVirtualNetOctets  OBJECT-TYPE
	SYNTAX Counter
	ACCESS read-only
	STATUS mandatory
	DESCRIPTION
	"The number of octets in good packets that
	were transmitted to this virtual net by ports in this hub."
	::= { lsBusStatsVirtualNetEntry 3 }

lsPortStats  OBJECT IDENTIFIER ::= { lsMonitor 3 }  -- LANswitch Port Monitoring Group

lsPortControlTable OBJECT-TYPE
	SYNTAX SEQUENCE OF LsPortControlEntry
	ACCESS not-accessible
	STATUS mandatory
	DESCRIPTION
	"A list of port control entries."
	::= { lsPortStats 1 }

lsPortControlEntry OBJECT-TYPE
	SYNTAX LsPortControlEntry
	ACCESS not-accessible
	STATUS mandatory
	DESCRIPTION
	"A list of parameters that set up the collection
	of extended statistics related to LANswitch ports.
	Data is collected in the lsPortExtendedStatsTable."
	INDEX { lsPortControlIndex }
	::= { lsPortControlTable 1 }

LsPortControlEntry ::= SEQUENCE {
		lsPortControlIndex         INTEGER (1..65535),
		lsPortControlDataSource  OBJECT IDENTIFIER,
		lsPortControlTableSize     INTEGER,
		lsPortControlLastDeleteTime   TimeTicks,
		lsPortControlOwner          DisplayString,
		lsPortControlStatus           INTEGER
	         }

lsPortControlIndex OBJECT-TYPE
	SYNTAX INTEGER (1..65535)
	ACCESS read-only
	STATUS mandatory
	DESCRIPTION
	"An index that uniquely identifies an entry in
	the lsPortControlTable.  Each such entry defines
	a function that monitors ports and places
	statistics about them in the portTable on behalf
	of this lsPortControlEntry."
	::= { lsPortControlEntry 1 }

lsPortControlDataSource OBJECT-TYPE
	SYNTAX OBJECT IDENTIFIER
	ACCESS read-write
	STATUS mandatory
	DESCRIPTION
	"This object identifies the source of the data for
	this instance of the port function.
	The statistics in this group reflect all packets
	on the LANswitch bus that are trasferred by the lsPortFilterTable.
	This object may not be modified if the
	associated lsPortControlStatus object is equal to valid(1)."
	::= { lsPortControlEntry 2 }

lsPortControlTableSize OBJECT-TYPE
	SYNTAX INTEGER
	ACCESS read-only
	STATUS mandatory
	DESCRIPTION
	"The number of ports for which SW counters are
	collected by the agent. This number is limited to 5."
	::= { lsPortControlEntry 3 }

lsPortControlLastDeleteTime OBJECT-TYPE
	SYNTAX TimeTicks
	ACCESS read-only
	STATUS mandatory
	DESCRIPTION
	"The value of sysUpTime when the last entry
	was deleted from the portion of the portTable
	associated with this lsPortControlEntry.  If no
	deletions have occurred, this value shall be zero."
	::= { lsPortControlEntry 4 }

lsPortControlOwner OBJECT-TYPE
	SYNTAX DisplayString
	ACCESS read-write
	STATUS mandatory
	DESCRIPTION
	"The entity that configured this entry and is
	therefore using the resources assigned to it."
	::= { lsPortControlEntry 5 }

lsPortControlStatus OBJECT-TYPE
	SYNTAX INTEGER {
		valid(1),
                           	createRequest(2),
                           	underCreation(3),
                          	 invalid(4)
                         }
	ACCESS read-write
	STATUS mandatory
	DESCRIPTION
	"The status of this lsPortControl entry.
	If this object is not equal to valid(1), all
	associated entries in the lsPortTable, shall be deleted by the agent."
	::= { lsPortControlEntry 6 }

lsPortFilterTable OBJECT-TYPE
	SYNTAX SEQUENCE OF LsPortFilterEntry
	ACCESS not-accessible
	STATUS mandatory
	DESCRIPTION
	"A list of LANswitch ports to be monitored on the high-speed bus.
	The OID of this table is a legitimate value for the
	lsPortControlDataSource.
	When this OID is a source for the host table, a port in the
	table has the same meaning as an instruction to the agent
	to collect statistics for all the hosts connected to that port.
	The maximum size of this table is 5 entries"
	::= { lsPortStats 2 }

lsPortFilterEntry OBJECT-TYPE
	SYNTAX LsPortFilterEntry
	ACCESS not-accessible
	STATUS mandatory
	DESCRIPTION
	"An entry in the filter table."
	INDEX { lsPortFilter }
	::= { lsPortFilterTable 1 }

LsPortFilterEntry ::= SEQUENCE {
		lsPortFilter	INTEGER,
		lsPortFilterStatus	INTEGER
		}

lsPortFilter OBJECT-TYPE
	SYNTAX INTEGER
	ACCESS read-only
	STATUS mandatory
	DESCRIPTION
	"The port monitored on the LANswitch bus. The value
	of  this item is: (16*S-1)+P, where S is the slot number in
	the hub (1..16) and P the port within the slot (1..N)."
	::= { lsPortFilterEntry 1 }

lsPortFilterStatus OBJECT-TYPE
	SYNTAX INTEGER {
			valid(1),
			invalid(4)
      		         }
	ACCESS read-write
	STATUS mandatory
	DESCRIPTION
	"The status of this lsPortFilter entry. When the status is
	valid, the port defined in the corresponding lsPortFilter is
	a part of the filter."
	::= { lsPortFilterEntry 2 }


lsPortFilterTableClear OBJECT-TYPE
	SYNTAX INTEGER {
			idle(1),
			clear(2)
      		         }
	ACCESS read-write
	STATUS mandatory
	DESCRIPTION
	"Setting the value of this item to clear(2) causes the
	agent to clear all entries in the PortFilterTable."
	::= { lsPortStats 3 }


lsPortTable OBJECT-TYPE
	SYNTAX SEQUENCE OF LsPortEntry
	ACCESS not-accessible
	STATUS mandatory
	DESCRIPTION
	"A list of port entries. Each entry contains statistical
	data pertaining to a single port. An entry is
	maintained at all times for each of the LANswitch
	ports that exist in the hub. This table is not controlled
	by the lsPortControlTable."
	::= { lsPortStats 4 }

lsPortEntry OBJECT-TYPE
	SYNTAX LsPortEntry
	ACCESS not-accessible
	STATUS mandatory
	DESCRIPTION
	"A collection of statistics for a particular LANswitch port."
	INDEX { lsPortNumber }
	::= { lsPortTable 1 }

LsPortEntry ::= SEQUENCE {
	lsPortNumber		INTEGER,
	lsPortInPkts             	Counter,
	lsPortInFCSErrors        	Counter,
	lsPortInTooLongPkts	Counter,
	lsPortInOctets           	Counter,
	lsPortInTotalErrors  	Counter,
	lsPortInCollisions 	Counter
}

lsPortNumber OBJECT-TYPE
	SYNTAX INTEGER
	ACCESS read-only
	STATUS mandatory
	DESCRIPTION
	"The monitored port. The value of this item is:
	16*(S-1)+P, where S is the slot number in the hub (1..16)
	and P the port within the slot (1..N)."
	::= { lsPortEntry 1 }

lsPortInPkts OBJECT-TYPE
	SYNTAX Counter
	ACCESS read-only
	STATUS mandatory
	DESCRIPTION
	"The number of good packets transmitted through
	  this port into the LANswitch bus ."
	::= { lsPortEntry 2 }

lsPortInFCSErrors OBJECT-TYPE
	SYNTAX Counter
	ACCESS read-only
	STATUS mandatory
	DESCRIPTION
	"The number of packets with FCS errors transmitted
	  through this port into the LANswitch bus ."
	::= { lsPortEntry 3 }

lsPortInTooLongPkts  OBJECT-TYPE
	SYNTAX Counter
	ACCESS read-only
	STATUS mandatory
	DESCRIPTION
	"The number of packets longer than 1518 bytes
	 transmitted through this port into the LANswitch bus ."
	::= { lsPortEntry 4 }

lsPortInOctets OBJECT-TYPE
	SYNTAX Counter
	ACCESS read-only
	STATUS mandatory
	DESCRIPTION
	"The number of octets in good packets
	(excluding framing bits but including FCS octets)
	transmitted  through this port into the LANswitch bus ."
	::= { lsPortEntry 5 }

lsPortInTotalErrors  OBJECT-TYPE
	SYNTAX	Counter
	ACCESS	read-only
	STATUS	mandatory
	DESCRIPTION
	"This item is a summation of all errors on this port.
	It contains the total hardware errors related to a specific port."
	::= { lsPortEntry 6}

lsPortInCollisions  OBJECT-TYPE
	SYNTAX	Counter
	ACCESS	read-only
	STATUS	mandatory
	DESCRIPTION
	"This counter is incremented by one for any
	 CarrierEvent signal on the port for which the
	 CollisionEvent signal on this port is also asserted."
	::= { lsPortEntry 7}


lsPortExtendedReportingList OBJECT-TYPE
	SYNTAX OCTET STRING (SIZE (32))
	ACCESS read-only
	STATUS mandatory
	DESCRIPTION
	"A list of all ports in the hub for which
	Extended  statistics are currently reported. 16
	bits in the bitmap are allocated for each slot in
	the hub.  The MSB is for port 1 of slot 1, and the
	LSB is for port 16 of slot 16. The bit representing
	ports for which extended statistics are now
	reported has the value of 1, otherwise 0."
	::= { lsPortStats 5 }


lsPortExtendedStatsTable OBJECT-TYPE
	SYNTAX SEQUENCE OF LsPortExtendedStatsEntry
	ACCESS not-accessible
	STATUS mandatory
	DESCRIPTION
	"A list of port entries."
	::= { lsPortStats 6 }

lsPortExtendedStatsEntry OBJECT-TYPE
	SYNTAX LsPortExtendedStatsEntry
	ACCESS not-accessible
	STATUS mandatory
	DESCRIPTION
	"A collection of statistics for a particular
	LANswitch port."
	INDEX { lsPortExtendedStatsNumber }
	::= { lsPortExtendedStatsTable 1 }

LsPortExtendedStatsEntry ::= SEQUENCE {
	lsPortExtendedStatsNumber 	INTEGER,
	lsPortCreationOrder		INTEGER (1..65535),
	lsPortIndex 			INTEGER (1..65535),
	lsPortOutPkts              		Counter,
	lsPortInBroadcastPkts  		Counter,
	lsPortInMulticastPkts   		Counter
}

lsPortExtendedStatsNumber  OBJECT-TYPE
	SYNTAX INTEGER
	ACCESS read-only
	STATUS mandatory
	DESCRIPTION
	"The monitored port.The value of this item is:
	16*(S-1)+P, where S is the slot number in the
	hub (1..16) and P the port within the slot (1..N)."
	::= { lsPortExtendedStatsEntry  1 }

lsPortCreationOrder OBJECT-TYPE
	SYNTAX INTEGER (1..65535)
	ACCESS read-only
	STATUS mandatory
	DESCRIPTION
	"An index that defines the relative ordering of
	the discovery time of ports captured for a
	particular lsPortControlEntry.  This index shall
	be between 1 and N, where N is the value of
	the associated lsPortControlTableSize.  The
	ordering of the indexes is based on the order of
	each entry's insertion into the table, in which
	entries added earlier have a lower index value
	than entries added later.
	It is important to note that the order for a
	particular entry may change as an (earlier) entry
	is deleted from the table.  Because this order may
	change, management stations should make use of
	the lsPortControlLastDeleteTime variable in the
	lsPortControlEntry associated with the relevant
	portion of the lsPortTable.  By observing
	this variable, the management station may
	detect the circumstances where a previous
	association between a value of
	lsPortCreationOrder and a lsPortEntry may no
	longer hold."
	::= { lsPortExtendedStatsEntry 2 }

lsPortIndex OBJECT-TYPE
	SYNTAX INTEGER (1..65535)
	ACCESS read-only
	STATUS mandatory
	DESCRIPTION
	"The set of collected port statistics of which
	this entry is a part. The set of ports
	identified by a particular value of this
	index is associated with the lsPortControlEntry
	as identified by the same value of
	lsPortControlIndex."
	::= { lsPortExtendedStatsEntry 3 }

lsPortOutPkts OBJECT-TYPE
	SYNTAX Counter
	ACCESS read-only
	STATUS mandatory
	DESCRIPTION
	"The number of packets without errors
	transmitted from the LANswitch bus to this port."
	::= { lsPortExtendedStatsEntry 4 }

lsPortInBroadcastPkts  OBJECT-TYPE
	SYNTAX Counter
	ACCESS read-only
	STATUS mandatory
	DESCRIPTION
	"The number of good Ethernet packets directed
	towards the broadcast address that were
	transmitted to the LANswitch bus through this port."
	::= { lsPortExtendedStatsEntry  5 }

lsPortInMulticastPkts OBJECT-TYPE
	SYNTAX Counter
	ACCESS read-only
	STATUS mandatory
	DESCRIPTION
	"The number of good Ethernet packets
	directed to a multicast address that were
	transmitted to the LANswitch bus through this port."
	::= { lsPortExtendedStatsEntry  6 }

lsHostFilterTable OBJECT-TYPE
	SYNTAX SEQUENCE OF LsHostFilterEntry
	ACCESS not-accessible
	STATUS mandatory
	DESCRIPTION
	"A list of hosts to be monitored on the high-speed
	bus by the RMON MIB hosts group. The OID of this
	table is a legitimate value for the hostControlDataSource.
	The size of the table is limited to 200 entries."
	::= { lsMonitor 4 }

lsHostFilterEntry OBJECT-TYPE
	SYNTAX LsHostFilterEntry
	ACCESS not-accessible
	STATUS mandatory
	DESCRIPTION
	"An entry in the filter table."
	INDEX { lsHostFilterAddress }
	::= { lsHostFilterTable 1 }

LsHostFilterEntry ::= SEQUENCE {
		              lsHostFilterAddress   OCTET STRING,
		              lsHostFilterStatus      INTEGER
		              }

lsHostFilterAddress OBJECT-TYPE
	SYNTAX OCTET STRING
	ACCESS read-only
	STATUS mandatory
	DESCRIPTION
"The MAC address of a host monitored on the
high-speed bus."
	::= { lsHostFilterEntry 1 }

lsHostFilterStatus OBJECT-TYPE
	SYNTAX INTEGER {
			valid(1),
			invalid(4)
      		         }
	ACCESS read-write
	STATUS mandatory
	DESCRIPTION
"The status of this lsHostFilter entry. When the status is
valid, the host defined in the corresponding lsHostFilter is
a part of the filter."
	::= { lsHostFilterEntry 2 }

lsHostFilterTableClear OBJECT-TYPE
	SYNTAX INTEGER {
			idle(1),
			clear(2)
      		         }
	ACCESS read-write
	STATUS mandatory
	DESCRIPTION
"Setting the value of this item to clear(2) causes the
agent to clear all entries in the HostFilterTable."
	::= { lsMonitor 5 }

lsHostPortFilterTable OBJECT-TYPE
	SYNTAX SEQUENCE OF LsHostPortFilterEntry
	ACCESS not-accessible
	STATUS mandatory
	DESCRIPTION
"A list of ports to be monitored on the high-speed bus.
The OID of this table is a legitimate value for the
hostControlDataSource.
When this OID is a source for the host table, a port in the
table has the same meaning as an instruction to the agent to
collect statistics for all the hosts connected to that port.
The size of this table is limited to 5 entries."
	::= { lsMonitor 6 }

lsHostPortFilterEntry OBJECT-TYPE
	SYNTAX LsHostPortFilterEntry
	ACCESS not-accessible
	STATUS mandatory
	DESCRIPTION
"An entry in the filter table."
	INDEX { lsHostPortFilter }
	::= { lsHostPortFilterTable 1 }

LsHostPortFilterEntry ::= SEQUENCE {
		lsHostPortFilter 		INTEGER,
		lsHostPortFilterStatus	INTEGER
}

lsHostPortFilter OBJECT-TYPE
	SYNTAX INTEGER
	ACCESS read-only
	STATUS mandatory
	DESCRIPTION
"The port monitored on the LANswitch bus. The value
of this item is: 16*(S-1)+P, where S is the slot number in
the hub (1..16) and P the port within the slot (1..N)."
	::= { lsHostPortFilterEntry 1 }


lsHostPortFilterStatus OBJECT-TYPE
	SYNTAX INTEGER {
			valid(1),
			invalid(4)
      		         }
	ACCESS read-write
	STATUS mandatory
	DESCRIPTION
"The status of this lsHostPortFilter entry. When the
status is valid, the hosts defined by the corresponding
lsHostPortFilter are a part of the filter."
	::= { lsHostPortFilterEntry 2 }

lsHostPortFilterTableClear OBJECT-TYPE
	SYNTAX INTEGER {
			idle(1),
			clear(2)
      		         }
	ACCESS read-write
	STATUS mandatory
	DESCRIPTION
"Setting the value of this item to clear(2) causes the
agent to clear all entries in the HostPortFilterTable."
	::= { lsMonitor 7 }

lsMatrixFilterTable OBJECT-TYPE
	SYNTAX SEQUENCE OF LsMatrixFilterEntry
	ACCESS not-accessible
	STATUS mandatory
	DESCRIPTION
"A list of hosts to be monitored on the high-speed bus
by the RMON MIB matrix group. The OID of this table is a
legitimate value for the hostControlDataSource.
The size of the table is limited to 200 entries."
	::= { lsMonitor 8 }


lsMatrixFilterEntry OBJECT-TYPE
	SYNTAX LsMatrixFilterEntry
	ACCESS not-accessible
	STATUS mandatory
	DESCRIPTION
"An entry in the filter table."
	INDEX { lsMatrixFilterAddress }
	::= { lsMatrixFilterTable 1 }

LsMatrixFilterEntry ::= SEQUENCE {
		     lsMatrixFilterAddress       OCTET STRING,
		     lsMatrixFilterStatus          INTEGER
		              }

lsMatrixFilterAddress OBJECT-TYPE
	SYNTAX OCTET STRING
	ACCESS read-only
	STATUS mandatory
	DESCRIPTION
"The MAC address of a host monitored on the
high-speed bus."
	::= { lsMatrixFilterEntry 1 }

lsMatrixFilterStatus OBJECT-TYPE
	SYNTAX INTEGER {
			valid(1),
			invalid(4)
      		         }
	ACCESS read-write
	STATUS mandatory
	DESCRIPTION
"The status of this lsMatrixFilter entry. When the status
is valid, the hosts defined by the corresponding
lsMatrixFilter are a part of the filter."
	::= { lsMatrixFilterEntry 2 }

lsMatrixFilterTableClear OBJECT-TYPE
	SYNTAX INTEGER {
			idle(1),
			clear(2)
      		         }
	ACCESS read-write
	STATUS mandatory
	DESCRIPTION
"Setting the value of this item to clear(2) causes the
agent to clear all entries in the MatrixFilterTable."
	::= { lsMonitor 9 }

lsHostTimePortCorrTable   OBJECT-TYPE
	SYNTAX   SEQUENCE OF   LsHostTimePortCorrEntry
	ACCESS not-accessible
	STATUS mandatory
	DESCRIPTION
        "An addition to the RMON MIBs hostTimeTable. This table contains
        a list of MAC addresses that were monitored on the high-speed bus
        and the switch ports to which they are connected.
        The index of this table is the same as for the standard RMON
        hostTimeTable. Indexes are hostTimeCreationOrder and hostTimeIndex.
        The MAC address is stored in hostTimeAddress.
        The port to which the MAC address is connected
hostTimePortConnection."
	::= { lsMonitor 10 }

lsHostTimePortCorrEntry   OBJECT-TYPE
	SYNTAX   LsHostTimePortCorrEntry
	ACCESS   not-accessible
	STATUS   mandatory
	DESCRIPTION
       "An entry in the MAC to port correlation table."
       INDEX { hostTimeIndex, hostTimeCreationOrder }
       ::= { lsHostTimePortCorrTable 1 }

LsHostTimePortCorrEntry ::= SEQUENCE {
              hostTimeAddress                 OCTET STRING,
              hostTimeCreationOrder       INTEGER (1..65535),
              hostTimeIndex                      INTEGER (1..65535),
              hostTimePortConnection          INTEGER
}

hostTimeAddress OBJECT-TYPE
              SYNTAX OCTET STRING
              ACCESS read-only
              STATUS mandatory
              DESCRIPTION
                  "The physical address of this host."
              ::= { lsHostTimePortCorrEntry 1 }

hostTimeCreationOrder OBJECT-TYPE
              SYNTAX INTEGER (1..65535)
              ACCESS read-only
              STATUS mandatory
              DESCRIPTION
                  "An index that uniquely identifies an entry in
                  the hostTime table among those entries associated
                  with the same hostControlEntry.  This index shall
                  be between 1 and N, where N is the value of
                  the associated hostControlTableSize.  The ordering
                  of the indexes is based on the order of each entry's
                  insertion into the table, in which entries added
                  earlier have a lower index value than entries added
                  later. Thus the management station has the ability to
                  learn of new entries added to this table without
                  downloading the entire table.

                  It is important to note that the index for a
                  particular entry may change as an (earlier) entry
                  is deleted from the table.  Because this order may
                  change, management stations should make use of the
                  hostControlLastDeleteTime variable in the
                  hostControlEntry associated with the relevant
                  portion of the hostTimeTable.  By observing
                  this variable, the management station may detect
                  the circumstances where a download of the table
                  may have missed entries, and where a previous
                  association between a value of hostTimeCreationOrder
                  and a hostTimeEntry may no longer hold."
              ::= { lsHostTimePortCorrEntry 2 }

--  When the Agent creates the control word for this purpose, the value of
--  hostTimeIndex is constant '999'.
hostTimeIndex OBJECT-TYPE
              SYNTAX INTEGER (1..65535)
              ACCESS read-only
              STATUS mandatory
              DESCRIPTION
                  "The set of collected host statistics of which
                  this entry is a part.  The set of hosts
                  identified by a particular value of this
                  index is associated with the hostControlEntry
                  as identified by the same value of hostControlIndex."
              ::= { lsHostTimePortCorrEntry 3 }

hostTimePortConnection OBJECT-TYPE
	SYNTAX   INTEGER
	ACCESS   read-only
	STATUS   mandatory
	DESCRIPTION
        "The switch port to which this hostTimeAddress is connected.
        The coding of the port number varies for different hubs and
        packplanes.
        For the LANSwitch HSB the value of this item is:
            The value of this item is: 32*(S-1)+P, where S is
            the slot number in the hub and P the LANswitch
            port within the slot (1.. 32).
        For hosts whose port connection is not identified by the agent, the
        value of this item will be 65,535 "
	::= { lsHostTimePortCorrEntry 4 }

lsHistoryTable OBJECT-TYPE
	SYNTAX SEQUENCE OF LsHistoryEntry
	ACCESS not-accessible
	STATUS mandatory
	DESCRIPTION
	"A list of High Speed Bus history entries."
	::= {lsMonitor 11 }

lsHistoryEntry OBJECT-TYPE
	SYNTAX LsHistoryEntry
	ACCESS not-accessible
	STATUS mandatory
	DESCRIPTION
	"An historical sample of LANswitch statistics on a HSB.
	This sample is associated with the historyControlEntry which set up
	the parameters for a regular collection of these samples. "
	INDEX { lsHistoryIndex , lsHistorySampleIndex }
	::= { lsHistoryTable 1 }

LsHistoryEntry ::= SEQUENCE {
		lsHistoryIndex                 		INTEGER,
		lsHistorySampleIndex           	INTEGER,
		lsHistoryIntervalTime        	TimeTicks,
 		lsHistoryStatsDropEvents		Counter,
		lsHistoryStatsPkts		Counter,
		lsHistoryStatsOctets		Counter,
		lsHistoryStatsEthBroadcastPkts	Counter,
		lsHistoryStatsEthMulticastPkts	Counter,
		lsHistoryStatsGoodEthPkts	Counter,
		lsHistoryStatsGoodEthOctets	Counter,
		lsHistoryStatsBadEthPkts		Counter,
		lsHistoryStatsBadEthOctets	Counter,
		lsHistoryStatsNonEthPkts		Counter,
		lsHistoryStatsNonEthOctets	Counter,
		lsHistoryStatsPriority1Pkts	Counter,
		lsHistoryStatsPriority1Octets	Counter,
		lsHistoryStatsPriority2Pkts	Counter,
		lsHistoryStatsPriority2Octets	Counter,
		lsHistoryStatsPriority3Pkts	Counter,
		lsHistoryStatsPriority3Octets	Counter,
		lsHistoryStatsPriority4Pkts	Counter,
		lsHistoryStatsPriority4Octets	Counter,
		lsHistoryBusUtilization           	INTEGER (0..100)
         }

lsHistoryIndex OBJECT-TYPE
              SYNTAX INTEGER
              ACCESS read-only
              STATUS mandatory
              DESCRIPTION
              "The history of which this entry is a part.  The history identified by a particular value of this
	index is the same history as identified by the same value of  historyControlIndex."
              ::= { lsHistoryEntry 1 }

lsHistorySampleIndex OBJECT-TYPE
              SYNTAX INTEGER (1..2147483647)
              ACCESS read-only
              STATUS mandatory
              DESCRIPTION
	"An index that uniquely identifies the particular
	sample this entry represents among all samples
	associated with the same lshistoryControlEntry.
	This index starts at 1 and increases by one as each new sample is taken."
              ::= { lsHistoryEntry 2 }

lsHistoryIntervalTime OBJECT-TYPE
              SYNTAX TimeTicks
              ACCESS read-only
              STATUS mandatory
              DESCRIPTION
	"The value of sysUpTime when this bucket was sampled ."
	::= { lsHistoryEntry 3 }

lsHistoryStatsDropEvents OBJECT-TYPE
	SYNTAX Counter
	ACCESS read-only
	STATUS mandatory
	DESCRIPTION
	"The total number of events in which packets were dropped by the probe due to lack of
	resources. Note that this number is not necessarily the number of packets dropped; it is
	just the number of times this condition has been detected."
	::= { lsHistoryEntry 4 }

lsHistoryStatsPkts OBJECT-TYPE
	SYNTAX Counter
	ACCESS read-only
	STATUS mandatory
	DESCRIPTION
	"The total number of packets (including error packets) received on the LANswitch 	bus."
	::= { lsHistoryEntry 5 }

lsHistoryStatsOctets OBJECT-TYPE
	SYNTAX Counter
	ACCESS read-only
	STATUS mandatory
	DESCRIPTION
	"The total number of octets of data (including those in bad packets) received on the
	LANswitch bus (excluding framing bits but including FCS octets)."
	::= { lsHistoryEntry 6 }


lsHistoryStatsEthBroadcastPkts OBJECT-TYPE
	SYNTAX Counter
	ACCESS read-only
	STATUS mandatory
	DESCRIPTION
	"The total number of good Ethernet packets received that were directed to the broadcast
	address."
	::= { lsHistoryEntry 7 }

lsHistoryStatsEthMulticastPkts OBJECT-TYPE
	SYNTAX Counter
	ACCESS read-only
	STATUS mandatory
	DESCRIPTION
	"The total number of good packets received that were directed to a multicast address.
	Note that this number does not include packets directed to the broadcast address."
	::= { lsHistoryEntry 8 }

lsHistoryStatsGoodEthPkts OBJECT-TYPE
	SYNTAX Counter
	ACCESS read-only
	STATUS mandatory
	DESCRIPTION
	"The total number of good Ethernet packets received on the LANswitch bus."
	::= { lsHistoryEntry 9 }

lsHistoryStatsGoodEthOctets OBJECT-TYPE
	SYNTAX Counter
	ACCESS read-only
	STATUS mandatory
	DESCRIPTION
	"The total number of octets that were received on the LANswitch bus in good
	Ethernet packets (excluding framing bits but including FCS octets)."
	::= { lsHistoryEntry 10 }

lsHistoryStatsBadEthPkts OBJECT-TYPE
	SYNTAX Counter
	ACCESS read-only
	STATUS mandatory
	DESCRIPTION
	"The total number of bad Ethernet packets received on the LANswitch bus."
	::= { lsHistoryEntry 11 }

lsHistoryStatsBadEthOctets OBJECT-TYPE
	SYNTAX Counter
	ACCESS read-only
	STATUS mandatory
	DESCRIPTION
	"The total number of octets that were received on the LANswitch bus in bad Ethernet 	packets (excluding framing bits but including FCS octets)."
	::= { lsHistoryEntry 12 }

lsHistoryStatsNonEthPkts OBJECT-TYPE
	SYNTAX Counter
	ACCESS read-only
	STATUS mandatory
	DESCRIPTION
	"The total number of packets received on the LANswitch bus in non Ethernet packets."
	::= { lsHistoryEntry 13 }

lsHistoryStatsNonEthOctets OBJECT-TYPE
	SYNTAX Counter
	ACCESS read-only
	STATUS mandatory
	DESCRIPTION
	"The total number of octets that were received on the LANswitch bus in non Ethernet 	packets (excluding framing bits but including FCS octets)."
	::= { lsHistoryEntry 14 }

lsHistoryStatsPriority1Pkts  OBJECT-TYPE
	SYNTAX Counter
	ACCESS read-only
	STATUS mandatory
	DESCRIPTION
	"The total number of packets (including error packets) received on the LANswitch
	bus whose priority is that defined for this entry."
	::= { lsHistoryEntry 15 }

lsHistoryStatsPriority1Octets  OBJECT-TYPE
	SYNTAX Counter
	ACCESS read-only
	STATUS mandatory
	DESCRIPTION
	"The total number of octets (including error packets) received on the LANswitch bus 	whose packets have the priority defined for this entry."
	::= { lsHistoryEntry 16 }

lsHistoryStatsPriority2Pkts  OBJECT-TYPE
	SYNTAX Counter
	ACCESS read-only
	STATUS mandatory
	DESCRIPTION
	"The total number of packets (including error packets) received on the LANswitch 	bus whose priority is that defined for this entry."
	::= { lsHistoryEntry 17 }

lsHistoryStatsPriority2Octets  OBJECT-TYPE
	SYNTAX Counter
	ACCESS read-only
	STATUS mandatory
	DESCRIPTION
	"The total number of octets (including error packets) received on the LANswitch bus 	whose packets have the priority defined for this entry."
	::= { lsHistoryEntry 18 }

lsHistoryStatsPriority3Pkts  OBJECT-TYPE
	SYNTAX Counter
	ACCESS read-only
	STATUS mandatory
	DESCRIPTION
	"The total number of packets (including error packets) received on the LANswitch 	bus whose priority is that defined for this entry."
	::= { lsHistoryEntry 19}

lsHistoryStatsPriority3Octets  OBJECT-TYPE
	SYNTAX Counter
	ACCESS read-only
	STATUS mandatory
	DESCRIPTION
	"The total number of octets (including error packets) received on the LANswitch bus 	whose packets have the priority defined for this entry."
	::= { lsHistoryEntry 20 }

lsHistoryStatsPriority4Pkts  OBJECT-TYPE
	SYNTAX Counter
	ACCESS read-only
	STATUS mandatory
	DESCRIPTION
	"The total number of packets (including error packets) received on the LANswitch 	bus whose priority is that defined for this entry."
	::= { lsHistoryEntry 21 }

lsHistoryStatsPriority4Octets  OBJECT-TYPE
	SYNTAX Counter
	ACCESS read-only
	STATUS mandatory
	DESCRIPTION
	"The total number of octets (including error packets) received on the LANswitch bus 	whose packets have the priority defined for this entry."
	::= { lsHistoryEntry 22 }

lsHistoryBusUtilization OBJECT-TYPE
	SYNTAX INTEGER (0..100)
	ACCESS read-only
	STATUS mandatory
	DESCRIPTION
	"The utilization of the LANswitch bus, expressed in percents of the maximum  	LANswitch traffic possible."
	::= { lsHistoryEntry 23 }



--    This MIB group defines the attributes specific to the TokenRing LANswitch modules
--
lstIntPort OBJECT IDENTIFIER 	::= { lst 1 }

lstIntPortTable OBJECT-TYPE
	SYNTAX SEQUENCE OF LstIntPortEntry
	ACCESS not-accessible
	STATUS mandatory
	DESCRIPTION ""
	::= { lstIntPort 1 }

lstIntPortEntry OBJECT-TYPE
	SYNTAX LstIntPortEntry
	ACCESS not-accessible
	STATUS mandatory
	DESCRIPTION
	"An entry in the table, containing data about
	a LANswitch port of LANswitch Token-Ring modules."
	INDEX { lstIntPortGroupId, lstIntPortId }
	::= { lstIntPortTable 1 }

LstIntPortEntry ::=
	SEQUENCE {
		lstIntPortGroupId
			INTEGER,
		lstIntPortId
			INTEGER,
		lstIntPortSidebandMode
			INTEGER,
		lstIntPortTotalOctets
			Counter,
		lstIntPortTotalTraffic
			INTEGER,
		lstIntPortLocalOctets
			Counter,
		lstIntPortLocalTraffic
			INTEGER,
		lstIntPortInOctets
			Counter,
		lstIntPortInTraffic
			INTEGER,
		lstIntPortOutOctets
			Counter,
		lstIntPortOutTraffic
			INTEGER,
		lstIntPortTotalFrames
			Counter,
		lstIntPortLostFrames
			Counter,
		lstIntPortClaimFrames
			Counter,
		lstIntPortPurgeFrames
			Counter,
		lstIntPortNormallyCloseOpen
			INTEGER,
		lstIntPortSlicingEnable
			INTEGER,
		lstIntPortSliceLength
			INTEGER,
		lstIntPortUNAddr
			OCTET STRING,
		lstIntPortMACAddress
			OCTET STRING,
		lstIntPortSMPTransmitEnable
			INTEGER,
		lstIntPortIPGLength
			INTEGER,
		lstIntPortBPDummyWindow
			INTEGER,
		lstIntPortBPTokenWindow
			INTEGER,
		lstIntPortTransmitWindow
			INTEGER,
		lstIntPortBlockingPriority
			INTEGER,
		lstIntPortNormalPriority
			INTEGER,
		lstIntPortDummyMV
			INTEGER,
		lstIntPortTxConsecutiveBusiesThresh
			INTEGER,
		lstIntPortTxBufFullThresh
			INTEGER,
		lstIntPortRxEmpty0
			INTEGER,
		lstIntPortRxEmpty1
			INTEGER,
		lstIntPortRxEmpty2
			INTEGER,
		lstIntPortRxFull
			INTEGER,
		lstIntPortBPEnable
			INTEGER,
		lstIntPortRouteSideband
			INTEGER
	}

lstIntPortGroupId OBJECT-TYPE
	SYNTAX 	INTEGER (1..255)
	ACCESS	read-only
	STATUS	mandatory
	DESCRIPTION
	"Id of the group to which the switch port belongs."
	::= { lstIntPortEntry 1 }

lstIntPortId OBJECT-TYPE
	SYNTAX 	INTEGER (1..255)
	ACCESS	read-only
	STATUS	mandatory
	DESCRIPTION
	"Switch port Id in module"
	::= { lstIntPortEntry 2 }

lstIntPortSidebandMode OBJECT-TYPE
	SYNTAX 	INTEGER {
		on(1),
		off(2),
		notSupported(255)
		}
	ACCESS	read-write
	STATUS	mandatory
	DESCRIPTION
	"Enable Sideband mode on internal port. In this mode,
	MAC level management of all rings can be 	done."
	::= { lstIntPortEntry 3 }

lstIntPortTotalOctets OBJECT-TYPE
	SYNTAX 	Counter
	ACCESS	read-only
	STATUS	mandatory
	DESCRIPTION
	"Total  number of octets circling in the ring. It is the
	sum of local octets, in octets and out octets."
	::= { lstIntPortEntry 4 }

lstIntPortTotalTraffic OBJECT-TYPE
	SYNTAX 	INTEGER (0..100)
	ACCESS	read-only
	STATUS	mandatory
	DESCRIPTION
	"Total  traffic in ring as part of the maximum possible
	utilization, 4Mbps or 16Mbps, expressed in 	percents.
	It is the sum of local traffic, in traffic and out traffic."
	::= { lstIntPortEntry 5 }

lstIntPortLocalOctets OBJECT-TYPE
	SYNTAX 	Counter
	ACCESS	read-only
	STATUS	mandatory
	DESCRIPTION
	"Number of octets local to the ring. The local traffic
	 includes only traffic between stations on the local ring."
	::= { lstIntPortEntry 6 }

lstIntPortLocalTraffic OBJECT-TYPE
	SYNTAX 	INTEGER (0..100)
	ACCESS	read-only
	STATUS	mandatory
	DESCRIPTION
	"Local traffic in ring as part of the maximum possible
	utilization, 4Mbps or 16Mbps, expressed in 	percents.
	The local traffic includes only traffic between stations
	on the local ring."
	::= { lstIntPortEntry 7 }

lstIntPortInOctets OBJECT-TYPE
	SYNTAX 	Counter
	ACCESS	read-only
	STATUS	mandatory
	DESCRIPTION
	"Number of octets passing in to the HSB from the ring.
	The In traffic includes only traffic going from stations
	on the local ring to stations on other rings."
	::= { lstIntPortEntry 8 }

lstIntPortInTraffic OBJECT-TYPE
	SYNTAX 	INTEGER (0..100)
	ACCESS	read-only
	STATUS	mandatory
	DESCRIPTION
	"In traffic to the HSB from the ring as part of the
	maximum possible utilization, 4Mbps or 16Mbps,
	expressed in percents. The In traffic includes only
	traffic going from stations on the 	local ring to
	stations on other rings."
	::= { lstIntPortEntry 9 }

lstIntPortOutOctets OBJECT-TYPE
	SYNTAX 	Counter
	ACCESS	read-only
	STATUS	mandatory
	DESCRIPTION
	"Number of octets passing out from the HSB to
	the ring. The Out traffic includes only traffic
	going to stations on the local ring from stations
	on other rings."
	::= { lstIntPortEntry 10 }

lstIntPortOutTraffic OBJECT-TYPE
	SYNTAX 	INTEGER (0..100)
	ACCESS	read-only
	STATUS	mandatory
	DESCRIPTION
	"Out traffic from the HSB to the ring as part
	of the maximum possible utilization, 4Mbps or
	16Mbps, expressed in percents. The Out traffic
	 includes only traffic going to stations on the
	local ring from stations on other rings."
	::= { lstIntPortEntry 11 }

lstIntPortTotalFrames OBJECT-TYPE
	SYNTAX 	Counter
	ACCESS	read-only
	STATUS	mandatory
	DESCRIPTION
	"Total number of frames in the ring."
	::= { lstIntPortEntry 12 }

lstIntPortLostFrames OBJECT-TYPE
	SYNTAX 	Counter
	ACCESS	read-only
	STATUS	mandatory
	DESCRIPTION
	"Number of lost frames because of Back Pressure."
	::= { lstIntPortEntry 13 }

lstIntPortClaimFrames OBJECT-TYPE
	SYNTAX	Counter
	ACCESS	read-only
	STATUS	mandatory
	DESCRIPTION
	"Number of Claim-Token frames in the ring."
	::= { lstIntPortEntry 16 }

lstIntPortPurgeFrames OBJECT-TYPE
	SYNTAX	Counter
	ACCESS	read-only
	STATUS	mandatory
	DESCRIPTION
	"Number of Ring-Purge frames in the ring."
	::= { lstIntPortEntry 17 }

lstIntPortNormallyCloseOpen OBJECT-TYPE
	SYNTAX 	INTEGER {
		normallyClose(1),
		normallyOpen(2),
		notSupported(255)
		}
	ACCESS	read-write
	STATUS	mandatory
	DESCRIPTION
	"Defines the IO mode of the switch port:
	normally close or normally open. When the
	 port is in 'normallyOpen' mode, all packets
	enter the port regardless to CAM content."
	::= { lstIntPortEntry 18 }

lstIntPortSlicingEnable OBJECT-TYPE
	SYNTAX 	INTEGER {
		on(1),
		off(2),
		notSupported(255)
		}
	ACCESS	read-write
	STATUS	mandatory
	DESCRIPTION
	"Packet slicing mechanism for decreasing
	the delay of packets transmission in the HSB.
	 Value 'on' enables the slicing mechanism."
	::= { lstIntPortEntry 19 }

lstIntPortSliceLength OBJECT-TYPE
	SYNTAX	INTEGER
	ACCESS	read-write
	STATUS	mandatory
	DESCRIPTION
	"The slice length in bytes. It determines
	the delay of packet's transmission through
	the HSB."
	::= { lstIntPortEntry 20 }

lstIntPortUNAddr OBJECT-TYPE
	SYNTAX	OCTET STRING (SIZE (6))
	ACCESS	read-only
	STATUS	mandatory
	DESCRIPTION
	"MAC address of the Upstream Neighbor
	of the line interface."
	::= { lstIntPortEntry 21 }

lstIntPortMACAddress OBJECT-TYPE
	SYNTAX	OCTET STRING (SIZE (6))
	ACCESS	read-only
	STATUS	mandatory
	DESCRIPTION
	"MAC address of the line interface."
	::= { lstIntPortEntry 22 }

lstIntPortSMPTransmitEnable OBJECT-TYPE
	SYNTAX 	INTEGER {
		on(1),
		off(2),
		notSupported(255)
		}
	ACCESS	read-write
	STATUS	mandatory
	DESCRIPTION
	"Enable SMP MAC frame transmission by line
	 interface during single-station situation."
	::= { lstIntPortEntry 23 }

lstIntPortIPGLength OBJECT-TYPE
	SYNTAX 	INTEGER (1..255)
	ACCESS	read-write
	STATUS	mandatory
	DESCRIPTION
	"Number of bytes interval between frames
	transmission of the line interface to the ring."
	::= { lstIntPortEntry 24 }

lstIntPortBPDummyWindow OBJECT-TYPE
	SYNTAX 	INTEGER (1..255)
	ACCESS	read-write
	STATUS	mandatory
	DESCRIPTION
	"The time (in 0.25ms) between Dummy frames
	sendings during Back Pressure situation of the
	line interface."
	::= { lstIntPortEntry 25 }

lstIntPortBPTokenWindow OBJECT-TYPE
	SYNTAX 	INTEGER
	ACCESS	read-write
	STATUS	mandatory
	DESCRIPTION
	"The time (in 0.25ms) until Token release
	during Back Pressure situation of the line
	interface."
	::= { lstIntPortEntry 26 }

lstIntPortTransmitWindow OBJECT-TYPE
	SYNTAX 	INTEGER
	ACCESS	read-write
	STATUS	mandatory
	DESCRIPTION
	"The time (in 0.25ms) of line interface
	transmission until Token release."
	::= { lstIntPortEntry 27 }

lstIntPortBlockingPriority OBJECT-TYPE
	SYNTAX 	INTEGER (0..7)
	ACCESS	read-write
	STATUS	mandatory
	DESCRIPTION
	"The priority of the line interface during
	Back Pressure situation."
	::= { lstIntPortEntry 28 }

lstIntPortNormalPriority OBJECT-TYPE
	SYNTAX 	INTEGER (0..7)
	ACCESS	read-write
	STATUS	mandatory
	DESCRIPTION
	"The priority of the line interface for HSB
	packets transmission into the ring."
	::= { lstIntPortEntry 29 }

lstIntPortDummyMV OBJECT-TYPE
	SYNTAX 	INTEGER (1..255)
	ACCESS	read-write
	STATUS	mandatory
	DESCRIPTION
	"Content of MV (Major Vector) field in Dummy
	 frame during Back Pressure of line interface."
	::= { lstIntPortEntry 30 }

lstIntPortTxConsecutiveBusiesThresh OBJECT-TYPE
	SYNTAX	INTEGER
	ACCESS	read-write
	STATUS	mandatory
	DESCRIPTION
	"The threshold of the number of consecutive
	 busies counter."
	::= { lstIntPortEntry 31 }

lstIntPortTxBufFullThresh OBJECT-TYPE
	SYNTAX	INTEGER
	ACCESS	read-write
	STATUS	mandatory
	DESCRIPTION
	"Threshold indicator for frames buffer full."
	::= { lstIntPortEntry 32 }

lstIntPortRxEmpty0  OBJECT-TYPE
	SYNTAX	INTEGER
	ACCESS	read-write
	STATUS	mandatory
	DESCRIPTION
	"Upper threshold pointer of Rx buffer.
	Determines the degree of buffer overflow
	and back pressure efficiency."
	::= { lstIntPortEntry 33 }

lstIntPortRxEmpty1  OBJECT-TYPE
	SYNTAX	INTEGER
	ACCESS	read-write
	STATUS	mandatory
	DESCRIPTION
	"Middle threshold pointer of Rx buffer.
	 Determines the degree of buffer overflow
	and back  pressure efficiency.."
	::= { lstIntPortEntry 34 }

lstIntPortRxEmpty2  OBJECT-TYPE
	SYNTAX	INTEGER
	ACCESS	read-write
	STATUS	mandatory
	DESCRIPTION
	"Lower threshold pointer of Rx buffer. Determines
	the degree of buffer overflow and back  pressure efficiency."
	::= { lstIntPortEntry 35 }

lstIntPortRxFull  OBJECT-TYPE
	SYNTAX	INTEGER
	ACCESS	read-write
	STATUS	mandatory
	DESCRIPTION
	"Rx full threshold pointer. Determines the degree
	of buffer overflow and back pressure efficiency."
	::= { lstIntPortEntry 36 }

lstIntPortBPEnable OBJECT-TYPE
	SYNTAX 	INTEGER {
		enable(1),
		disable(2),
		notSupported(255)
		}
	ACCESS	read-write
	STATUS	mandatory
	DESCRIPTION
	"Enable/disable the Back Pressure mechanism."
	::= { lstIntPortEntry  37 }

lstIntPortRouteSideband OBJECT-TYPE
	SYNTAX 	INTEGER {
		on(1),
		off(2),
		notSupported(255)
		}
	ACCESS	read-write
	STATUS	mandatory
	DESCRIPTION
	"Set the internal port ability to get from the HSB sideband packets. The
	value 'on' enables the
	routing of sideband packet from the HSB into the internal port."
	::= { lstIntPortEntry  38 }

-- This group should be supported by LANswitch modules with WAN ports.

lseWANTable OBJECT-TYPE
	SYNTAX  SEQUENCE OF LseWANEntry
	ACCESS  not-accessible
	STATUS  mandatory
	DESCRIPTION
	"LAN Switch WAN data table. Implementation of this table is
	mandatory for all LANswitch modules with WAN ports."
	::= { lntLanSwitch 5 }

lseWANEntry OBJECT-TYPE
	SYNTAX  LseWANEntry
	ACCESS  not-accessible
	STATUS  mandatory
	DESCRIPTION
	"Entry in the table."
	INDEX           { lseWANGroupId, lseWANPortId }
	::= { lseWANTable 1 }

LseWANEntry ::=
	SEQUENCE {
	     lseWANGroupId
		INTEGER,
	     lseWANPortId
		INTEGER,
	     lseWANConnection
		INTEGER
	}

lseWANGroupId OBJECT-TYPE
	SYNTAX  INTEGER
	ACCESS  read-only
	STATUS  mandatory
	DESCRIPTION
	"Slot number in which the module is located."
	::= { lseWANEntry 1 }

lseWANPortId OBJECT-TYPE
	SYNTAX  INTEGER
	ACCESS  read-only
	STATUS  mandatory
	DESCRIPTION
	"WAN port index."
	::= { lseWANEntry 2 }

lseWANConnection OBJECT-TYPE
	SYNTAX  INTEGER { connected(1), disconnected(2) }
	ACCESS  read-only
	STATUS  mandatory
	DESCRIPTION
	"WAN connection status."
	::= { lseWANEntry 3 }


-- This MIB Group provides the MIB items required for the identification
-- of the last change in the Virtual Networks configuration detected by the agent.
-- The value is internally filled by the agent and sent to the management applications
-- via Enterprise specific traps. Such a trap may be sent when an address appears at
-- a switch port with a virtual network number that does not fit the third layer address
-- Implementation of this group is mandatory for the third layer switching devices that
-- have the capability of detecting situations of unmatching between the Virtual Net #
-- and the third layer network address.

lsVNChangeMACAddress OBJECT-TYPE
	SYNTAX	OCTET STRING (SIZE (6))
	ACCESS read-only
	STATUS mandatory
	DESCRIPTION
		"MAC Address that was detected with at
		a switch port and its mapping to a Virtual
		Network does not fit with the third layer
		address."
	::= { lsVNChange 1 }

lsVNChangeDetected	OBJECT-TYPE
	SYNTAX	INTEGER (1..4095)
	ACCESS read-only
	STATUS mandatory
	DESCRIPTION
		"Virtual Network number detected at the switch
		port when a VN change is reported."
	::= { lsVNChange 2 }

lsVNChangeExpected	OBJECT-TYPE
	SYNTAX	INTEGER (1..4095)
	ACCESS read-only
	STATUS mandatory
	DESCRIPTION
		"Virtual Network number detected at the switch
		port when a VN change is reported."
	::= { lsVNChange 3 }

lsVNChangeGroup	OBJECT-TYPE
	SYNTAX	INTEGER
	ACCESS read-only
	STATUS mandatory
	DESCRIPTION
		"The slot number of the card where the Vitual
		Network change was detected."
	::= { lsVNChange 4 }

lsVNChangePort		OBJECT-TYPE
	SYNTAX	INTEGER
	ACCESS read-only
	STATUS mandatory
	DESCRIPTION
		"The port number where the Vitual
		Network change was detected."
	::= { lsVNChange 5 }


-- This group should be supported by 3LS (3rd layer switch) routing module
-- The table will use as source information for the VNS and
-- for sending TRAPs to VNS.

vnsPacketTable OBJECT-TYPE
	SYNTAX  SEQUENCE OF VnsPacketEntry
	ACCESS  not-accessible
	STATUS  mandatory
	DESCRIPTION
	"VNS packets data table. Implementation of this table is
	mandatory for 3LS (3rd layer switch) module."
	::= { vnsPacket 1 }

vnsPacketEntry OBJECT-TYPE
	SYNTAX  VnsPacketEntry
	ACCESS  not-accessible
	STATUS  mandatory
	DESCRIPTION
	"Entry in the table."
	INDEX           { vnsPacketMACAddress }
	::= { vnsPacketTable 1 }

VnsPacketEntry ::=
	SEQUENCE {
	     vnsPacketMACAddress
		OCTET STRING,
	     vnsPacketProtocolTypeMask
		OCTET STRING,
	     vnsPacketIPAddress
		IpAddress,
	     vnsPacketIPNetMask
		IpAddress,
	     vnsPacketIPXnetwork
		OCTET STRING,
	     vnsPacketStationType
		INTEGER,
	     vnsPacketPortGroupId
		INTEGER,
	     vnsPacketPortId
		INTEGER,
	     vnsPacketBackbonePort
		INTEGER,
	     vnsPacketExpectedVLAN
		INTEGER,
	     vnsPacketDetectedVLAN
		INTEGER,
	     vnsPacketBoxAgentIP
		IpAddress,
	     vnsPacketExpectedIfName
	        DisplayString,
	     vnsPacketDetectedIfName
	        DisplayString
	}

vnsPacketMACAddress OBJECT-TYPE
	SYNTAX  OCTET STRING ( SIZE (6))
	ACCESS  read-only
	STATUS  mandatory
	DESCRIPTION
	"The Mac Address of the sending station."
	::= { vnsPacketEntry 1 }

vnsPacketProtocolTypeMask	OBJECT-TYPE
	SYNTAX OCTET STRING ( SIZE (1))
	ACCESS read-only
	STATUS mandatory
	DESCRIPTION
		"This is a mask of the exising protocols.
		 Bit(0)='1' when IP protocol exist and '0' otherwise,
		 Bit(1)='1' when IPX protocol exist and '0' otherwise,
		 all other bits are '0' for the moment."
	::= { vnsPacketEntry 2 }

vnsPacketIPAddress OBJECT-TYPE
	SYNTAX IpAddress
	ACCESS read-only
	STATUS mandatory
	DESCRIPTION
		"The IP address of the packet's sending station.
		In case the typeaddress is not IP this field will be 0.0.0.0."
	::= { vnsPacketEntry 3 }

vnsPacketIPNetMask OBJECT-TYPE
	SYNTAX  IpAddress
	ACCESS  read-only
	STATUS  mandatory
	DESCRIPTION
	"The IP Address Mask from the IP Interface Table."
	::= { vnsPacketEntry 4 }

vnsPacketIPXnetwork OBJECT-TYPE
	SYNTAX OCTET STRING ( SIZE (4))
	ACCESS  read-only
	STATUS  mandatory
	DESCRIPTION
	"The IPX NetWork Address of the packet's sending station.
	In case that the typeaddress is not IPX this field will be 0.0.0.0."
	::= { vnsPacketEntry 5 }

vnsPacketStationType OBJECT-TYPE
	SYNTAX INTEGER  {
		unknown(1),
		client(2),
		server(3),
		notSupported(255)
		}
	ACCESS read-only
	STATUS mandatory
	DESCRIPTION
		"The Station Type indicates from where comes the packets
		 in the case of the IPX protocol."
	DEFVAL { notSupported }
	::= { vnsPacketEntry 6 }

vnsPacketPortGroupId OBJECT-TYPE
      SYNTAX  INTEGER (1..255)
      ACCESS  read-only
      STATUS  mandatory
      DESCRIPTION
      "Index which identifies the group inside the chassis for which this
      entry contains information. It equals with the slot number."
      ::= { vnsPacketEntry 7 }

vnsPacketPortId OBJECT-TYPE
      SYNTAX  INTEGER (1..255)
      ACCESS  read-only
      STATUS  mandatory
      DESCRIPTION
      "Index which identifies the port inside the group for which this
      entry contains information. It equals  with the port number."
      ::= { vnsPacketEntry 8 }

 vnsPacketBackbonePort	OBJECT-TYPE
	SYNTAX INTEGER  {
		unknown(1),
		backbone(2),
		noBackbone(3),
		notSupported(255)
		}
	ACCESS read-only
	STATUS mandatory
	DESCRIPTION
		"The value 2 indicates that the port source of the packet is a
		  backbone port."
	::= { vnsPacketEntry 9 }

vnsPacketExpectedVLAN OBJECT-TYPE
	SYNTAX  INTEGER
	ACCESS read-only
	STATUS  mandatory
	DESCRIPTION
	"The value of this item is the VLAN number that the packet had to have
	 according to it's address."
	::= { vnsPacketEntry 10 }

vnsPacketDetectedVLAN OBJECT-TYPE
	SYNTAX  INTEGER
	ACCESS read-only
	STATUS  mandatory
	DESCRIPTION
	"The value of this item is the detected VLAN number of the arrived packet."
	::= { vnsPacketEntry 11 }

 vnsPacketBoxAgentIP OBJECT-TYPE
	SYNTAX  IpAddress
	ACCESS  read-only
	STATUS  mandatory
	DESCRIPTION
	"The IP Address of the Hub's BoxAgent where the 3LS (3rd layer switch) module exist."
	::= { vnsPacketEntry 12 }

vnsPacketExpectedIfName OBJECT-TYPE
	SYNTAX  DisplayString
	ACCESS read-only
	STATUS  mandatory
	DESCRIPTION
	"The value of this item is the name of the interface the packet was expected to be received on according to it's address."
	::= { vnsPacketEntry 13 }

vnsPacketDetectedIfName OBJECT-TYPE
	SYNTAX  DisplayString
	ACCESS read-only
	STATUS  mandatory
	DESCRIPTION
	"The value of this item is the name of the interface the packet was actually received on."
	::= { vnsPacketEntry 14 }


--  Topology group
--  This MIB group provides information used for the physical
--  topology applications of LANNET. This MIB group is
--  supported by Ethernet agents, released 7.0 and higher.

topDiscovery OBJECT-TYPE
	SYNTAX  INTEGER 	{
		idle(1),
		topoMessages(2),
		macFind(3),
		swBackboneMsgMonitor(4),
		notSupported(255)
		}
	ACCESS  read-write
	STATUS  mandatory
	DESCRIPTION
	"The value of this item defines the activity status of the  agent's discovery algorithm.
	When its value is set to topoMessages(2), the agent searches for the topology messages
	(interhub and bridge messages).
	When  the value  is macFind(3), the agent searches for the MAC addresses defined in
	the item ethTopMACFindList. The results of the search are then reported in
	ethTopMACResultTable.
	When  the value  is swBackboneMsgMonitor(4), the agent monitors messages with
	specific destination address. The result of monitoring is reported in 	ethTopMessageResultEntry.
	The value of this item cannot be changed from one state to another without being
	first changed to idle(1).
	This item is timed by TopDiscoveryTimeOut (return back to idle(1))."
	DEFVAL  { idle }
	::= {lntTopology 1 }


topDiscoveryTimeOut OBJECT-TYPE
	SYNTAX  INTEGER
	ACCESS  read-write
	STATUS  mandatory
	DESCRIPTION
	"The value of this item defines the maximal time (in seconds) that an agent can remain in 	the non-idle toplogy discovery mode. When the agent is set to the topology mode 	(TopDiscovery=topoDiscovery(2) or macFind(3)) the counter is started. If the manager 	doesn't return the agent back to normal operation mode within the timeOut, the agent will 	automatically return to normal operation (TopDiscovery=idle(1)) and stop searching for 	the special messages.
	The value of this item can be changed only when TopDiscovery=idle(1)."
	DEFVAL  { 3 }
	::= {lntTopology 2 }

ethTop OBJECT IDENTIFIER
      ::= { lntTopology 3 }

ethTopDiscoveryTx  OBJECT-TYPE
	SYNTAX  INTEGER {
		idle(1),
		txInterhubMsg(2),
		txBridgeMsg(3),
		txAckMsg(4)
		}
	ACCESS  read-write
	STATUS  mandatory
	DESCRIPTION
	"This item is a switch that activates the inter-agent topology messages.
	txInterhubMsg(2) - the agent transmits interhub discovery messages.
	txBridgeMsg(3) - the agent transmits bridge discovery messages.
	txAckMsg(4) - the agent transmits acknowledgment messages."
	DEFVAL  {idle }
	::= {ethTop 1 }

ethTopClearMessageResult  OBJECT-TYPE
	SYNTAX  INTEGER 	{
				 idle(1),
				 clear(2)
				}
      	ACCESS  read-write
      	STATUS  mandatory
      	DESCRIPTION
	 "When this item is set to clear(2), the agent sets the values of all ethTopMessageResult 	items to '0'. When finished the 'clear' process the Agent sets the variable to idle(1)."
	DEFVAL  {idle }
      	::= { ethTop 2 }

ethTopNumOfMessageResults  OBJECT-TYPE
	SYNTAX  INTEGER
      	ACCESS  read-write
      	STATUS  mandatory
      	DESCRIPTION
	"This item contains the number of messages
	currently stored in the ethTopMessageResultTable."
     ::= { ethTop 3 }

ethTopMessageResultTable OBJECT-TYPE
      SYNTAX  SEQUENCE OF EthTopMessageResultEntry
      ACCESS  not-accessible
      STATUS  mandatory
      DESCRIPTION
        "A table that contains 3 items with the results of the topology messages received by the  agent."
      ::= { ethTop 4 }

ethTopMessageResultEntry OBJECT-TYPE
      SYNTAX  EthTopMessageResultEntry
      ACCESS  not-accessible
      STATUS  mandatory
      DESCRIPTION
      "An entry in the table, containing part of the received data."
      INDEX  { ethTopMessageResultId }
      ::= { ethTopMessageResultTable 1 }

EthTopMessageResultEntry  ::=
      SEQUENCE  	{
			 ethTopMessageResultId
			    INTEGER,
			 ethTopMessageResult
			    OCTET STRING
      		}

ethTopMessageResultId OBJECT-TYPE
	SYNTAX  INTEGER
      	ACCESS  read-only
      	STATUS  mandatory
      	DESCRIPTION
	"The table's index. Can assume the values 1,2, or 3."
      	::= { ethTopMessageResultEntry 1 }

ethTopMessageResult  OBJECT-TYPE
	SYNTAX  OCTET STRING (SIZE (0..440))
      	ACCESS  read-only
      	STATUS  mandatory
      	DESCRIPTION
	"A row in the Topology Messages result table. Each row contains up to 44 elements."
	::= { ethTopMessageResultEntry 2 }

ethTopMACFindList  OBJECT-TYPE
      	SYNTAX  OCTET STRING  ( SIZE (0..36))
      	ACCESS  read-write
      	STATUS  mandatory
      	DESCRIPTION
      	"Up to 6 MAC addresses to be searched for by the Agent."
      	::= { ethTop 5}

ethTopMACFindResultTable  OBJECT-TYPE
      SYNTAX  SEQUENCE OF EthTopMACFindResultEntry
      ACCESS  not-accessible
      STATUS  mandatory
      DESCRIPTION
	"A table that contains 4 rows with the results of the MACFind process. Each row contains 	the results for one of the hub's buses. The number of items supported is equal to the 	number of buses supported by the agent."
      ::= { ethTop 6 }

ethTopMACFindResultEntry OBJECT-TYPE
      SYNTAX  EthTopMACFindResultEntry
      ACCESS  not-accessible
      STATUS  mandatory
      DESCRIPTION
      "An entry in the table, containing one LSA item."
      INDEX  { ethTopMACFindBus }
      ::= { ethTopMACFindResultTable 1 }

EthTopMACFindResultEntry  ::=
      SEQUENCE  	{
			 ethTopMACFindBus
			    INTEGER,
			 ethTopMACFindResult
			    OCTET STRING
      		}

ethTopMACFindBus  OBJECT-TYPE
	SYNTAX  INTEGER
	ACCESS  read-only
	STATUS  mandatory
	DESCRIPTION
	"The bus for which the results are reported."
	::= {ethTopMACFindResultEntry 1 }


ethTopMACFindResult  OBJECT-TYPE
      	SYNTAX  OCTET STRING  ( SIZE (0..48))
      	ACCESS  read-only
      	STATUS  mandatory
      	DESCRIPTION
	"The results of the search for the requested MAC addresses fo the relevant bus. The 	format is: MAC (6 bytes), slot (1 byte), port (1 byte).
	If the Agent doesn't find a MAC's correlation, the slot and port will be '0'."
    	::= { ethTopMACFindResultEntry 2}


ethTopLSATable OBJECT-TYPE
      SYNTAX  SEQUENCE OF EthTopLSAEntry
      ACCESS  not-accessible
      STATUS  mandatory
      DESCRIPTION
	"A table that contains 8 rows with the last source addresses found on the hub's ports.
	Each row in the table reports the last source addresses for specific slots in the hub:
	#1: modules 1,2,17,18;	#5: modules 9,10,25, 26;
	#2: modules 3,4,19,20;	#6: modules 11,12,27, 28;
	#3: modules 5,6,21,22;	#7: modules 13,14,29,30;
	#4: modules 7,8,23,24;	#8: modules 15,16,31,32;
	The data in the items appears by the slot order defined above. All 8 items exist even if 	some of them are empty."
      ::= { ethTop 7 }

ethTopLSAEntry OBJECT-TYPE
      SYNTAX  EthTopLSAEntry
      ACCESS  not-accessible
      STATUS  mandatory
      DESCRIPTION
      "An entry in the table, containing one LSA item."
      INDEX  { ethTopLSAId }
      ::= { ethTopLSATable 1 }

EthTopLSAEntry  ::=
      SEQUENCE  	{
			 ethTopLSAId
			    INTEGER,
			 ethTopLSA
			    OCTET STRING
      		}

ethTopLSAId  OBJECT-TYPE
	SYNTAX  INTEGER
	ACCESS  read-only
	STATUS  mandatory
	DESCRIPTION
"The table's index. Assumes values 1,2,3,...,8."
	::= {ethTopLSAEntry 1 }

ethTopLSA  OBJECT-TYPE
	SYNTAX  OCTET STRING (SIZE (384))
	ACCESS  read-only
	STATUS  mandatory
	DESCRIPTION
"This item contains the last source addresses for modules in related slots. For each port the data is: slot (one byte), port (one byte), address (6 bytes). For none existing ports the LSA will be 0.
The first bit (MSB) of the slot byte defines the user status:
'0' - single user; '1' - multi user."
	::= {ethTopLSAEntry 2 }


ethTopAddressTable OBJECT-TYPE
      SYNTAX  SEQUENCE OF EthTopAddressEntry
      ACCESS  not-accessible
      STATUS  mandatory
      DESCRIPTION
"A table that contains the MAC addresses used by the agent for the topology
messages."
      ::= { ethTop 8 }

ethTopAddressEntry OBJECT-TYPE
      SYNTAX  EthTopAddressEntry
      ACCESS  not-accessible
      STATUS  mandatory
      DESCRIPTION
      "An entry in the topology address table. The number of entries is
equal to the number of Ethernet
buses supported by the agent."
      INDEX  { ethTopBus }
      ::= { ethTopAddressTable 1 }

EthTopAddressEntry  ::=
      SEQUENCE  	{
			 ethTopBus
			    INTEGER,
			 ethTopAddress
			    OCTET STRING
      		}

ethTopBus OBJECT-TYPE
	SYNTAX  INTEGER
      	ACCESS  read-only
      	STATUS  mandatory
      	DESCRIPTION
"The bus for which this address is defined."
      	::= { ethTopAddressEntry 1 }

ethTopAddress  OBJECT-TYPE
	SYNTAX  OCTET STRING (SIZE(6))
	ACCESS  read-write
	STATUS  mandatory
	DESCRIPTION
"The MAC address used by the agent for the topology discovery
process on the related bus."
	::= {ethTopAddressEntry 2 }


ethTopHSBMonitor OBJECT-TYPE
	SYNTAX  INTEGER         {
		idle(1),
		startMonitor(2),
		notSupported(255)
		}
	ACCESS  read-write
	STATUS  mandatory
	DESCRIPTION
    	"This item ask for monitoring the LANSwitch bus by the NMA-RS.
	startMonitor(2) value, is used to start monitor the LANSwitch bus
     	collect the lsHostTimePortCorrTable. "
	DEFVAL  { idle }
	::= {ethTop 9}

-- SMON Group
-- This group is used by SMON application
-- The first group of smon sub-tree is alarms

alarms  OBJECT IDENTIFIER ::= { smon 1 }

alarmMonitorStatusTable OBJECT-TYPE
	SYNTAX SEQUENCE OF AlarmMonitorStatusEntry
 	ACCESS not-accessible
 	STATUS mandatory
	DESCRIPTION
                "A list of alarms status for Alarm entries."
	::= { alarms 1 }

alarmMonitorStatusEntry OBJECT-TYPE
	SYNTAX AlarmMonitorStatusEntry
	ACCESS not-accessible
	STATUS mandatory
 	DESCRIPTION
                "Each entry contains an index (appropriate to specific alarmIndex item)
                 and the alarmed status of this alarm entry "
	INDEX { alarmMonitorStatusIndex }
	::= { alarmMonitorStatusTable 1 }

AlarmMonitorStatusEntry ::= SEQUENCE {
	alarmMonitorStatusIndex	INTEGER,
	alarmMonitorStatus		INTEGER
             }

alarmMonitorStatusIndex OBJECT-TYPE
	SYNTAX INTEGER (1..65535)
	ACCESS read-only
	STATUS mandatory
	DESCRIPTION
	    "An index that uniquely identifies an entry in the alarmMonitorStatusTable.
	     This index is the same as the appropriate alarm Table."
	::= { alarmMonitorStatusEntry 1 }

alarmMonitorStatus OBJECT-TYPE
	SYNTAX INTEGER {
		ok(1),
		alarmState(2)
		}
 	ACCESS read-only
	STATUS mandatory
 	DESCRIPTION
                  "The alarms' status for the appropriate alarm table
		1 - ok
		2 - alarmState."
	::= { alarmMonitorStatusEntry 2 }

alarmUtilitiesCommand OBJECT-TYPE
	SYNTAX INTEGER {
		idle(1),
		clearAll(2),
		notSupported(255)
		}
	ACCESS read-write
	STATUS mandatory
	DESCRIPTION
             "The alarms command can be one of the follows:
		1 - idle - idle state.
		2 - clearAll - clear all alarms and events in the Agent tables.
		254 - failed - If the Agent does not succeed to perform the command,
		         the alarmUtilitiesCommand will be changed to failed,
 		         to indicate the fail of performing the last Command."
	::= { alarms 2 }


portHistory OBJECT IDENTIFIER ::= {smon 3 }

portHistoryExtendedControlTable OBJECT-TYPE
	SYNTAX SEQUENCE OF PortHistoryExtendedControlEntry
	ACCESS not-accessible
	STATUS mandatory
	DESCRIPTION
	"A list of extended history control entries."
	::= {portHistory 1 }

portHistoryExtendedControlEntry OBJECT-TYPE
	SYNTAX PortHistoryExtendedControlEntry
	ACCESS not-accessible
	STATUS mandatory
	DESCRIPTION
	"A list of extended parameters that set up a periodic sampling of statistics. "
	INDEX { historyControlIndex }
	::= { portHistoryExtendedControlTable 1 }

PortHistoryExtendedControlEntry ::= SEQUENCE {
	portHistoryExtendedControlCreateTime		TimeTicks, 	portHistoryExtendedControlLastBucketIndex	INTEGER,
	portHistoryExtendedControlNumberOfBuckets	INTEGER,
	portHistoryExtendedControlName			DisplayString
	}

portHistoryExtendedControlCreateTime OBJECT-TYPE
	SYNTAX TimeTicks
	ACCESS read-only
	STATUS mandatory
	DESCRIPTION
	"The value of sysUpTime at the creation of the control row and start of the history
	collection index with the same value of the historyControlIndex."
	::= { portHistoryExtendedControlEntry 1 }

portHistoryExtendedControlLastBucketIndex OBJECT-TYPE
	SYNTAX INTEGER
	ACCESS read-only
	STATUS mandatory
	DESCRIPTION
	"The index of the last bucket that was stored to the history table."
	::= { portHistoryExtendedControlEntry 2 }

portHistoryExtendedControlNumberOfBuckets OBJECT-TYPE
	SYNTAX INTEGER (0.. 2147483647)
	ACCESS read-only
	STATUS mandatory
	DESCRIPTION
	" The number of buckets stored in the probe."
	::= { portHistoryExtendedControlEntry 3 }

portHistoryExtendedControlName OBJECT-TYPE
	SYNTAX DisplayString
	ACCESS read-write
	STATUS mandatory
	DESCRIPTION
	" The name of the this history collection."
	::= { portHistoryExtendedControlEntry 4 }


lsPortHistoryTable OBJECT-TYPE
	SYNTAX SEQUENCE OF LsPortHistoryEntry
	ACCESS not-accessible
	STATUS mandatory
	DESCRIPTION
	"A list of LANswitch port history entries."
	::= {portHistory 2 }

lsPortHistoryEntry OBJECT-TYPE
	SYNTAX LsPortHistoryEntry
	ACCESS not-accessible
	STATUS mandatory
	DESCRIPTION
	"An historical sample of port switch statistics  with the historyControlEntry,
	which set up the parameters for a regular collection of these samples. "
              	INDEX {lsPortHistoryIndex,
		 lsPortHistorySampleIndex,
		 lsPortNumber }
              ::= { lsPortHistoryTable 1 }

LsPortHistoryEntry ::= SEQUENCE {
	lsPortHistoryIndex		INTEGER (1..65535),
	lsPortHistorySampleIndex		INTEGER (1..2147483647),
	lsPortHistoryIntervalTime		TimeTicks,
	lsPortHistoryBoxConfiguration	OCTET STRING,
	lsPortHistoryPkts			Counter,
	lsPortHistoryCollisions		Counter,
	lsPortHistoryTotalErrors		Counter
	}

lsPortHistoryIndex OBJECT-TYPE
	SYNTAX INTEGER (1..65535)
	ACCESS read-only
	STATUS mandatory
	DESCRIPTION
	"The history of which this entry is a part.  The history identified by a particular value of this
	index is the same history as identified by the same value of historyControlIndex."
	::= { lsPortHistoryEntry 1 }

lsPortHistorySampleIndex OBJECT-TYPE
	SYNTAX INTEGER (1..2147483647)
	ACCESS read-only
	STATUS mandatory
	DESCRIPTION
	"An index that uniquely identifies the particular sample,
	this entry represents among all samples associated with the same lshistoryControlEntry.
	This index starts at 1 and increases by one as each new sample is taken."
	::= { lsPortHistoryEntry 2 }

lsPortHistoryIntervalTime OBJECT-TYPE
	SYNTAX TimeTicks
	ACCESS read-only
	STATUS mandatory
	DESCRIPTION
	"The value of sysUpTime at the start of the interval
	over which this sample was measured."
	::= { lsPortHistoryEntry 3 }

lsPortHistoryBoxConfiguration OBJECT-TYPE
	SYNTAX OCTET STRING
	ACCESS read-only
	STATUS mandatory
	DESCRIPTION
	" Octet String build by concatenating the genGroupType of the
	maximum 16 modules in the LANSwitch box. By reading this
	variable a management application can draw a list of the LANSwitch
	modules and ports configuration relevant for the application. "
	::= { lsPortHistoryEntry 4 }

lsPortHistoryPkts OBJECT-TYPE
	SYNTAX Counter
	ACCESS read-only
	STATUS mandatory
	DESCRIPTION
	"The total number of good packets received on the port."
	::= { lsPortHistoryEntry 5 }

lsPortHistoryCollisions OBJECT-TYPE
	SYNTAX Counter
	ACCESS read-only
	STATUS mandatory
	DESCRIPTION
	" The best estimate of the total number of collisions
	on this port during this sampling interval."
	::= { lsPortHistoryEntry 6 }

lsPortHistoryTotalErrors OBJECT-TYPE
	SYNTAX Counter
	ACCESS read-only
	STATUS mandatory
	DESCRIPTION
	"The total number of errors detected by the switching hardware on this port,
	including FCS errors and too long packets."
	::= { lsPortHistoryEntry 7 }


scPortHistoryTable OBJECT-TYPE
	SYNTAX SEQUENCE OF ScPortHistoryEntry
	ACCESS not-accessible
	STATUS mandatory
	DESCRIPTION
	"A list of Xswitch port history entries."
	::= {portHistory 3 }

scPortHistoryEntry OBJECT-TYPE
	SYNTAX ScPortHistoryEntry
	ACCESS not-accessible
	STATUS mandatory
	DESCRIPTION
	"An historical sample of port switch statistics  with the historyControlEntry,
	which set up the parameters for a regular collection of these samples. "
              	INDEX {scPortHistoryIndex,
		 scPortHistorySampleIndex,
		 ifIndex }
              ::= { scPortHistoryTable 1 }

ScPortHistoryEntry ::= SEQUENCE {
	scPortHistoryIndex	 		INTEGER (1..65535),
	scPortHistorySampleIndex			INTEGER (1..2147483647),
	scPortHistoryIntervalTime			TimeTicks,
	scPortHistoryBoxConfiguration		OCTET STRING,
	scPortHistoryGoodPktsRec		Counter,
	scPortHistoryGoodNonUnicastPktsRec	Counter,
	scPortHistoryCollisions			Counter,
	scPortHistoryBadPkts			Counter,
	scPortHistoryGoodPktsSent		Counter
	}


scPortHistoryIndex OBJECT-TYPE
	SYNTAX INTEGER (1..65535)
	ACCESS read-only
	STATUS mandatory
	DESCRIPTION
	"The history of which this entry is a part.  The history identified by a particular value of this
	index is the same history as identified by the same value of historyControlIndex."
	::= { scPortHistoryEntry 1 }

scPortHistorySampleIndex OBJECT-TYPE
	SYNTAX INTEGER (1..2147483647)
	ACCESS read-only
	STATUS mandatory
	DESCRIPTION
	"An index that uniquely identifies the particular sample,
	this entry represents among all samples associated with the same scHistoryControlEntry.
	This index starts at 1 and increases by one as each new sample is taken."
	::= { scPortHistoryEntry 2 }

scPortHistoryIntervalTime OBJECT-TYPE
	SYNTAX TimeTicks
	ACCESS read-only
	STATUS mandatory
	DESCRIPTION
	"The value of sysUpTime at the start of the interval
	over which this sample was measured."
	::= { scPortHistoryEntry 3 }

scPortHistoryBoxConfiguration OBJECT-TYPE
	SYNTAX OCTET STRING
	ACCESS read-only
	STATUS mandatory
	DESCRIPTION
	" Octet String build by concatenating the genGroupType of the
	maximum 14 modules in the Meritage box or 4 boxes in the
	Visage stack. By reading this variable a management application
	can draw a list of the modules (boxes) and ports configuration
	relevant for the application. "
	::= { scPortHistoryEntry 4 }

scPortHistoryGoodPktsRec OBJECT-TYPE
	SYNTAX Counter
	ACCESS read-only
	STATUS mandatory
	DESCRIPTION
	"The total number of good packets  received by the port."
	::= { scPortHistoryEntry 5 }

scPortHistoryGoodNonUnicastPktsRec OBJECT-TYPE
	SYNTAX Counter
	ACCESS read-only
	STATUS mandatory
	DESCRIPTION
	"The total number of good packets received that were
	directed to multicat or broadcast address."
	::= { scPortHistoryEntry 6 }

scPortHistoryCollisions OBJECT-TYPE
	SYNTAX Counter
	ACCESS read-only
	STATUS mandatory
	DESCRIPTION
	"The best estimate of the total number of collisions on the
	Ethernet segment connected to the port."
	::= { scPortHistoryEntry 7 }


scPortHistoryBadPkts OBJECT-TYPE
	SYNTAX Counter
	ACCESS read-only
	STATUS mandatory
	DESCRIPTION
	"The total number of bad packets filtered by the port.
	This item is the summation of:
	scEthPortCRCAlignErrors, scEthPortOversizePkts,
	scEthPortFragments	and scEthPortJabber. "
	::= { scPortHistoryEntry 8 }

scPortHistoryGoodPktsSent OBJECT-TYPE
	SYNTAX Counter
	ACCESS read-only
	STATUS mandatory
	DESCRIPTION
	"The total number of good packets sent by the port."
	::= { scPortHistoryEntry 9 }

portHistoryMemoryAvailability OBJECT-TYPE
	SYNTAX  INTEGER         {
		standard(1),
		limited1(2),
		limited2(3),
		notSupported(255)
		}
	ACCESS  read-only
	STATUS  mandatory
	DESCRIPTION
    	"This item reflect the status of available Port History.
	standard(1) value, is used when there are no memory limitations.
               limited1(2) value, is used when the limitation is 3 MB.
 limited1(3) value, is used when the limitation is 2 MB."
	DEFVAL  { standard }
	::= {portHistory 4 }

END
