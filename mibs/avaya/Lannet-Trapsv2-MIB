--
-- ========================================================
-- Source Safe data:
-- $Revision: 16 $
-- Check In: $Date: 19/04/09 6:06p $
-- $Author: Sbiton $
-- $Archive: /MIBs/Version 1.0/Source/Lannet/Lannet-Trapsv2-MIB.my $
-- ========================================================
--
-- ===================================================================================================
--  MIB      : Lannet Traps                  Avaya Communication
--
--  Version  : 2.0.19                          19 June 2005
--
-- ===================================================================================================
--
--  Copyright 1999, 2000, 2001, 2002 Avaya  Ltd.
--  All Rights Reserved.
--
--  Reproduction of this document is authorized on condition
--  that the foregoing copyright notice is included.
--
--  This Avaya SNMP Management Information Base
--  Specification embodies Avaya confidential and
--  proprietary intellectual property.  Lucent Technologies retains all
--  title and ownership in the Specification, including any revisions
--
--  It is Avaya intent to encourage the widespread use of this
--  Specification in connection with the management of Avaya
--  products.
--
--  Avaya grants vendors, end-users, and other interested parties
--  a non-exclusive license to use this Specification in connection
--  with the management of Avaya products.
--
--  This Specification is supplied "as is," and Avaya makes
--  no warranty, either express or implied, as to the use,
--  operation, condition, or performance of the Specification.
-- **************************************************************************
-- **************************************************************************
--  Version 2.0.1
--  This MIB describe using SMIv2 traps generated by ITC P330, P130 devices . This file is
--  based on the SMIv2 "P330-TRAPS" MIB group. Migrating from SMIv1 to SMIv2 was exploited for
--  improvement in trap structure. List of changes found below
--
--  * All traps were positioned under . . .enterprises.lannet.lntTraps OID as mandates SMIv2 trap format
--  * The Fault trap (2) was reassembled and now each fault bit is mapped to a dedicate trap
--     New faults' traps are assigned trap ids in Range 3000-4000. These trap numbers are consistent with
--     the trap translations done by Faultmon service.
--  * Fault traps include the module id and port id in varbind list, which significantly
--    simplifying trap formatting for trap collectors.
--  * "Config change" trap varbind list was enhanced - it was extended to include the OID
--    of variable changed and also formatted text value of the changed variable. This chnage
--    makes the trap consistent with SMIv2 interpreters/compilers that do not allow type
--    changes in varbinds
--  * For all other traps the old trap numbering and varbind content was preserved.
--
-- **************************************************************************
--  Version 2.0.2
--  Changes
--  Related traps have been grouped under individual branches
--  Notification renamed to user notification phrasing instead of trap
--  Supported standard traps have been  added to agent capabilities
-- **************************************************************************
--   Version 2.0.3
--   Changes
--
--   * New Prefix nodes was added to all Trap nodes in order to achieve compatibility with RFC 2578
--     that requires that the next to last sub- identifier in the name of any newly-defined notification
--     must have the value zero
--   * All description that ware scrumbled by the MG-SOft builder were restored
--   * All unrefernced MIB objects were eliminated from the include list
-- **************************************************************************  Version 2.0.4
--   Version 2.0.4
--   Changes
--
--   * Corrected lntPolicyEvent varbind list
-- **************************************************************************  Version 2.0.5
--   Version 2.0.5
--   Changes
--
--   * lntMACSecurityEvent notification was added - reports on MAC security violation
--   * lntUnAuthAccessEvent notification was added - reports on unauthorized attempt to
--                                                   to get access to device management.
-- **************************************************************************  Version 2.0.6
--   Version 2.0.6
--   Changes
--
--  * Traps have been remapped to different specific numbers because of
--  we found that the numbers defined were marked as "logONLY" in the
--  trapd.conf file
--  * lntMACSecurityEvent - corrected varbind list
-- **************************************************************************  Version 2.0.7
--   Version 2.0.7
--   Changes
--
--  * All notifications under lntEthPortFaultEvents group has been updated because
--    of wrong definitions of varbind parameters
--  * The access violation trap, lntUnAuthAccessEvent was renumbered to allow
--    Boxster control security trap generation in v1 environment. The
--    trap oid suffix was chnaged from 1001 to 68
--
-- **************************************************************************
--  Version 2.0.8
--   Changes
--
--  * There was a mixup in the definitions of the lntCascadDownConnOk (1.3.6.1.4.1.81.38.10.0.2317) and the lntCascadDownConnFlt (1.3.6.1.4.1.81.38.10.0.2318)
--    ans as a result lntCascadDownConnOk was changed to be 2318 and the lntCascadDownConnFlt 2317.
-- 68
--
-- **************************************************************************
--   Version 2.0.9
--   Changes
--
--  *  nodlntPSUEvents object id was erroneosly renamed  - changed back to lntPSUEvents
--  *  The ipPolicyActivationSubContext was erroneosly replaced by ipPolicyAccessControlViolationSubCtxt in
-- **************************************************************************
--   Version 2.0.10
--    Changes
--   * CamChange trap was obsoleted - it is not supported in any of ITC devices. Has been removed from
--     groups definitions and agent capabilities.
-- **************************************************************************
--
-- **************************************************************************
--   Version 2.0.11
--    Changes
--   * Add more access prorocold identifiers as per Cid 101994 -
--     rasaccess(6889) console (6890) ppp(6891).
-- **************************************************************************
-- **************************************************************************
--  Version 2.0.12   P. Spector
--  Chnages
--  * New lntAcountLockoutEvent
-- **************************************************************************
-- **************************************************************************
--  Version 2.0.13          M. Deutsch
-- * Add lntPortInlinePowerFlt and lntPortInlinePowerOK
-- **************************************************************************
-- **************************************************************************
--  Version 2.0.14          P. Spector
-- * Add new licence related traps - lntLicenseStartupValidationFlt, lntLicenseDownloadValidationFlt
-- **************************************************************************
-- **************************************************************************
--  Version 2.0.15          Shlomi Biton
-- * Add new varbind (ipPolicyRuleDescription) to LntPolicyAccessControlViolationFlt
-- **************************************************************************
-- **************************************************************************
--  Version 2.0.16          Nimrod Dezent
-- * Added enum value lntIKEAccess(500) to lntUnauthProtocol.
-- **************************************************************************
-- **************************************************************************
--  Version 2.0.17          Shlomi Biton
-- * Add 802.1x multi-supplicant traps.
--  1. lntDot1xMaxAuthRateReachedEvent - This trap notifies the management station
--     that maximum rate of 802.1x authentications has been reached in module $1.
--  2. lntDot1xAuthFailureEvent - This trap notifies the management station that
--     device with MAC address $1 failed to authenticate module/port $2/$3 due to $4.
--     A new varbind is added of scGenPortDot1xFailureString to support $4. The possible
--  	values for scGenPortDot1xFailureString are:
--		1. "Timeout, No response from Radius Server"
--		2. "Wrong Username"
--		3. "Wrong Password"
--		4. "Not enough Place in Layer 2 table for the authenitcated station."
--		The trap will be generated only when the Radius server response with FAILURE or
--		there is timeout while accessing the Radius server or when the RADIUS response with
--		SUCCESS and there is no place in layer 2 table for this Authenticated STATION MAC.
--  3. lntDot1xMaxAuthModuleNumReachedEvent - This trap notifies the management
--     station that Authentication denied due to maximum number of authentication
--     of 802.1x $1 per module $2 has been reached.
--  4. lntDot1xMaxAuthPortNumReachedEvent - This trap notifies the management station
--     that Authentication denied due to maximum number of authentication of 802.1x $1
--     per module/port $2/$3 has been reached.
-- **************************************************************************
-- **************************************************************************
--  Version 2.0.18          Meir Deutsch
--     change name of ipPolicyAccessControlListLvlRuleTrap to lntPolicyAccessControlListLvlRuleTrap
-- **************************************************************************
--  Version 2.0.19          Shlomi Biton
--  Rename scGenGroupDot1xPortMaxSuppNum to scGenSwitchDot1xPortMaxSuppNum.
-- **************************************************************************
--  Version 2.0.20          Shlomi Biton
--  Fix syntax of lntAccountLockoutEvent.
-- **************************************************************************


    Lannet-Trapsv2-MIB DEFINITIONS ::= BEGIN

        IMPORTS
            lseIntPortCAMLastChange, vnsPacketMACAddress, vnsPacketIPAddress, vnsPacketIPNetMask, vnsPacketExpectedVLAN,
            vnsPacketDetectedVLAN, vnsPacketBoxAgentIP, vnsPacketExpectedIfName, vnsPacketDetectedIfName
                FROM APPLIC-MIB
            chLntAgIntTemp, chHWIntTempWarning, chHWIntTempThresh, genGroupId, genGroupMPSActivityStatus,
            genGroupBUPSActivityStatus, genGroupFaultMask, genGroupCascadUpStatus, genGroupCascadDownStatus, genPortGroupId,
            genPortId, genPortFaultMask, genPortFunctionalStatus, softRedundancyName, softRedundancyGroupId1,
            softRedundancyPortId1, softRedundancyGroupId2, softRedundancyPortId2, softRedundancyStatus
                FROM CONFIG-MIB
            dsx1LineStatus
                FROM DS1-MIB
            lannet
                FROM GEN-MIB
            ifName, ifAlias
                FROM IF-MIB
            ipPolicyListID, ipPolicyRuleListID, ipPolicyRuleID, ipPolicyRuleDescription, ipPolicyControlSlot, ipPolicyAccessControlViolationEntID,
            ipPolicyAccessControlViolationSrcAddr, ipPolicyAccessControlViolationDstAddr, ipPolicyAccessControlViolationProtocol, ipPolicyAccessControlViolationL4SrcPort, ipPolicyAccessControlViolationL4DstPort,
            ipPolicyAccessControlViolationEstablished, ipPolicyAccessControlViolationIfIndex, ipPolicyAccessControlViolationSubCtxt, ipPolicyAccessControlViolationTime, ipPolicyAccessControlViolationRuleType,
            ipPolicyActivationEntID, ipPolicyActivationifIndex, ipPolicyActivationSubContext, ipPolicyActivationList
                FROM POLICY-MIB
            ifIndex, ifAdminStatus, ifOperStatus, ipNetToMediaPhysAddress, ipNetToMediaNetAddress,
            DisplayString
                FROM RFC1213-MIB
            rmonNotificationGroup
                FROM RMON-MIB
            OBJECT-GROUP, AGENT-CAPABILITIES, NOTIFICATION-GROUP
                FROM SNMPv2-CONF
            coldStart, warmStart, authenticationFailure
                FROM SNMPv2-MIB
            IpAddress, OBJECT-TYPE, MODULE-IDENTITY, OBJECT-IDENTITY, NOTIFICATION-TYPE
                FROM SNMPv2-SMI
            scGenGroupBUPSFansStatus, scGenGroupFansStatus, scGenPortGroupId, scGenPortId, scGenPortLastIntruderSourceAddr,
            scGenLinkAggregationId, scGenLinkAggregationName, scGenLinkAggregationFunctionalStatus, scGenLinkAggregationAutoNegResults, scGenLinkAggregationFaultMask,
            scGenLinkAggregationStatus, scEthPortGroupId, scEthPortId, scEthPortFunctionalStatus, scGenPortDot1xMAC,
            scGenGroupDot1xSystemMaxNumSupplicant, scGenSwitchDot1xPortMaxSuppNum
                FROM XSWITCH-MIB;


        lntTraps MODULE-IDENTITY
            LAST-UPDATED "200903180953Z"		-- Mar 18, 2009 at 09:53
            ORGANIZATION
                "Avaya"
            CONTACT-INFO
                "Pesah Spector
                Avaya
                E-Mail: pspector@avaya.com

                "
            DESCRIPTION
                "SMIv2 definition of p330/P130 traps"
            ::= { lannet 38 }

-- 1.3.6.1.4.1.81.38.1
        lntConfigChangeEvents OBJECT-IDENTITY
            STATUS current
            DESCRIPTION
                "Groups together all configuration change related events"
            ::= { lntTraps 1 }

--      1.3.6.1.4.1.81.38.1.0
        lntConfigChangePrefix OBJECT-IDENTITY
            STATUS current
            DESCRIPTION
                "The next to last sub- identifier in the name of any newly-defined notification
                must have the value zero"
            ::= { lntConfigChangeEvents 0 }

--      1.3.6.1.4.1.81.38.1.0.1
        lntConfigChangeEvent NOTIFICATION-TYPE
            OBJECTS { lntConfigChangeOID, lntConfigChangeValue }
            STATUS current
            DESCRIPTION
                "Notification generated in case of configuration change.
                List of events triggering notitication is TBD"
            ::= { lntConfigChangePrefix 1 }

        lntStackMasterReelection NOTIFICATION-TYPE
            OBJECTS { genGroupId }
            STATUS current
            DESCRIPTION
                "The trap should be triggered in an event that an election process
                leads to selection of a different module as a Stack Master"
            ::= { lntConfigChangePrefix 82 }

--      1.3.6.1.4.1.81.38.2
        lntSWRedundancyEvents OBJECT-IDENTITY
            STATUS current
            DESCRIPTION
                "Groups together all software redundancy related events"
            ::= { lntTraps 2 }

--      1.3.6.1.4.1.81.38.2.0
        lntSWRedundancyPrefix OBJECT-IDENTITY
            STATUS current
            DESCRIPTION
                "The next to last sub- identifier in the name of any newly-defined notification
                must have the value zero"
            ::= { lntSWRedundancyEvents 0 }

--      1.3.6.1.4.1.81.38.2.0.12
        lntSoftRedDelEvent NOTIFICATION-TYPE
            OBJECTS { softRedundancyStatus }
            STATUS current
            DESCRIPTION
                "The trap notifies the manager of the deletion of the specified
                redundant link, which is identified by the softRedundancyId. "
            ::= { lntSWRedundancyPrefix 12 }

--      1.3.6.1.4.1.81.38.2.0.13
        lntSoftRedNewEvent NOTIFICATION-TYPE
            OBJECTS { softRedundancyName, softRedundancyGroupId1, softRedundancyPortId1, softRedundancyGroupId2, softRedundancyPortId2,
                softRedundancyStatus }
            STATUS current
            DESCRIPTION
                "The trap is generated on the creation of the redundant links for the
                specified ports. It gives the logical name of the redundant link the
                identification of the main and secondary ports and the status of the
                link. The softRedundancyId defines the instances of the above-
                mentioned variables. "
            ::= { lntSWRedundancyPrefix 13 }

--      1.3.6.1.4.1.81.38.3
        lntTempratureEvents OBJECT-IDENTITY
            STATUS current
            DESCRIPTION
                "Groups together all temprature related events"
            ::= { lntTraps 3 }

--      1.3.6.1.4.1.81.38.3.0
        lntTempratureWarningPrefix OBJECT-IDENTITY
            STATUS current
            DESCRIPTION
                "The next to last sub- identifier in the name of any newly-defined notification
                must have the value zero"
            ::= { lntTempratureEvents 0 }

--      1.3.6.1.4.1.81.38.3.0.14
        lntTempratureWarning NOTIFICATION-TYPE
            OBJECTS { chHWIntTempWarning, chHWIntTempThresh, chLntAgIntTemp }
            STATUS current
            DESCRIPTION
                "This trap notifies the management station of the internal
                board/enclosure temperature fluctuations. It is generated when
                the temperature exceeds the threshold chHWIntTempThresh. "
            ::= { lntTempratureWarningPrefix 14 }

--      1.3.6.1.4.1.81.38.3.0.23
        lntTempratureOk NOTIFICATION-TYPE
            OBJECTS { chHWIntTempWarning, chHWIntTempThresh, chLntAgIntTemp }
            STATUS current
            DESCRIPTION
                "This trap notifies the management station that the internal
                board/enclosure temperature fluctuations situation is back to normal.
                "
            ::= { lntTempratureWarningPrefix 23 }

--      1.3.6.1.4.1.81.38.4
        lntCAMChangeEvents OBJECT-IDENTITY
            STATUS current
            DESCRIPTION
                "Groups together all CAM related events"
            ::= { lntTraps 4 }

--      1.3.6.1.4.1.81.38.4.0
        lntCAMChangePrefix OBJECT-IDENTITY
            STATUS current
            DESCRIPTION
                "The next to last sub- identifier in the name of any newly-defined notification
                must have the value zero"
            ::= { lntCAMChangeEvents 0 }

--      1.3.6.1.4.1.81.38.4.0.22
        lntPortCAMLastChange NOTIFICATION-TYPE
            OBJECTS { lseIntPortCAMLastChange }
            STATUS obsolete
            DESCRIPTION
                "This trap reports of the occurred CAM changes"
            ::= { lntCAMChangePrefix 22 }

--      1.3.6.1.4.1.81.38.5
        lntPSUEvents OBJECT-IDENTITY
            STATUS current
            DESCRIPTION
                "Groups together all Power supply related events"
            ::= { lntTraps 5 }

--      1.3.6.1.4.1.81.38.5.0
        lntPSUPrefix OBJECT-IDENTITY
            STATUS current
            DESCRIPTION
                "The next to last sub- identifier in the name of any newly-defined notification
                must have the value zero"
            ::= { lntPSUEvents 0 }

--      1.3.6.1.4.1.81.38.5.0.79
        lntMainPSUFlt NOTIFICATION-TYPE
            OBJECTS { genGroupFaultMask, genGroupId, genGroupMPSActivityStatus }
            STATUS current
            DESCRIPTION
                "An error was reported concerning the Main Power Supply.
                Urgent intervention is required by the network administrator
                in order to replace the faulty module, or take any other
                necessary measures in order to ensure the uninterrupted
                operation of the network"
            ::= { lntPSUPrefix 2303 }

--      1.3.6.1.4.1.81.38.5.0.81
        lntMainPSUOk NOTIFICATION-TYPE
            OBJECTS { genGroupFaultMask, genGroupId, genGroupMPSActivityStatus }
            STATUS current
            DESCRIPTION
                "The network device recovered after a previously reported problem
                in the operation of the box Main Power Supply"
            ::= { lntPSUPrefix 2304 }

--      1.3.6.1.4.1.81.38.5.0.83
        lntBackupPSUFlt NOTIFICATION-TYPE
            OBJECTS { genGroupFaultMask, genGroupId, genGroupBUPSActivityStatus }
            STATUS current
            DESCRIPTION
                "An error was reported concerning the Backup Power Supply.
                Urgent intervention is required by the network
                administrator in order to replace the faulty module, or
                take any other necessary measures in order to ensure the
                uninterrupted operation of the network."
            ::= { lntPSUPrefix 2305 }

--      1.3.6.1.4.1.81.38.5.0.85
        lntBackupPSUOk NOTIFICATION-TYPE
            OBJECTS { genGroupFaultMask, genGroupId, genGroupMPSActivityStatus }
            STATUS current
            DESCRIPTION
                "The network device recovered after a previously reported problem
                in the operation of the box Backup Power Supply."
            ::= { lntPSUPrefix 2306 }

--      1.3.6.1.4.1.81.38.6
        lntL3Events OBJECT-IDENTITY
            STATUS current
            DESCRIPTION
                "Groups together  routing( L3) related events."
            ::= { lntTraps 6 }

--      1.3.6.1.4.1.81.38.6.0
        lntL3FaultsPrefix OBJECT-IDENTITY
            STATUS current
            DESCRIPTION
                "The next to last sub- identifier in the name of any newly-defined notification
                must have the value zero"
            ::= { lntL3Events 0 }

--      1.3.6.1.4.1.81.38.6.0.27
        lntDuplicateIPFlt NOTIFICATION-TYPE
            OBJECTS { ipNetToMediaPhysAddress, ipNetToMediaNetAddress }
            STATUS current
            DESCRIPTION
                "This trap reports to the Management station on Duplicate IP
                identification.  CRP identify the new IP on the network.
                If it similar to one of its IP interfaces, the CRP will issue a
                SNMP trap, containing the MAC of the intruder."
            ::= { lntL3FaultsPrefix 27 }

--      1.3.6.1.4.1.81.38.6.0.28
        lntVLANViolationEvent NOTIFICATION-TYPE
            OBJECTS { vnsPacketMACAddress, vnsPacketIPAddress, vnsPacketIPNetMask, vnsPacketExpectedVLAN, vnsPacketDetectedVLAN,
                vnsPacketBoxAgentIP }
            STATUS current
            DESCRIPTION
                "This trap reports to the Management station on IP VLAN violation.
                CRP verify the VLAN of the incoming packets. If there is any
                inconsistency between the configured VLAN and the VLAN number
                found in the IP packet, the CRP will issue a SNMP trap."
            ::= { lntL3FaultsPrefix 28 }

--       1.3.6.1.4.1.81.38.6.0.70
        lntARPViolationEvent NOTIFICATION-TYPE
            OBJECTS { vnsPacketMACAddress, vnsPacketIPAddress, vnsPacketIPNetMask, vnsPacketExpectedVLAN, vnsPacketDetectedVLAN,
                vnsPacketBoxAgentIP, vnsPacketExpectedIfName, vnsPacketDetectedIfName }
            STATUS current
            DESCRIPTION
                "This trap reports to the Management station when a Sourec IP in an
                ARP response does not match the subnets configured on the router
                interface through which it has been received.
                The trap returns details of the offending packet, as welll as the
                       expected vs. detected VLAN IDs and interface Names"
            ::= { lntL3FaultsPrefix 70 }

--      1.3.6.1.4.1.81.38.7
        lntLinkEvents OBJECT-IDENTITY
            STATUS current
            DESCRIPTION
                "Groups together  port link up/down  related events."
            ::= { lntTraps 7 }

--      1.3.6.1.4.1.81.38.7.0
        lntLinkEventsPrefix OBJECT-IDENTITY
            STATUS current
            DESCRIPTION
                "The next to last sub- identifier in the name of any newly-defined notification
                must have the value zero"
            ::= { lntLinkEvents 0 }

--      1.3.6.1.4.1.81.38.7.0.3039
        lntPortLinkDownEvent NOTIFICATION-TYPE
            OBJECTS { genPortFaultMask, genPortGroupId, genPortId }
            STATUS current
            DESCRIPTION
                "The port hardware detects loss of connectivity to
                an end station or to another hub or switch. This is not
                necessarily a fault condition, as the same signaling is
                reported by the port hardware in usual operational cases,
                for example, of a non-critical station being
                disconnected or turned off at the end of the work day.
                (Bit 7 in the genPortFaultMask set to on, genPortFunctionalStatus = rld(2)
                )"
            ::= { lntLinkEventsPrefix 3039 }

--      1.3.6.1.4.1.81.38.7.0.3040
        lntPortLinkUpEvent NOTIFICATION-TYPE
            OBJECTS { genPortFaultMask, genPortGroupId, genPortId }
            STATUS current
            DESCRIPTION
                "The port recovered from a previously reported
                connectivity problem.
                (Bit 7 in the genPortFaultMask set to off,
                genPortFunctionalStatus = ok)"
            ::= { lntLinkEventsPrefix 3040 }

--      1.3.6.1.4.1.81.38.7.0.3041
        lntVPortLinkDownEvent NOTIFICATION-TYPE
            OBJECTS { genPortFaultMask, genPortGroupId, genPortId }
            STATUS current
            DESCRIPTION
                "The port hardware detects the lack of a connection
                to an end station or to another hub or switch. While this
                may not be necessarily a fault condition, the network
                administrator's attention is recommended, because the port
                was defined as a valuable port. (Bit 7 in the genPortFaultMask set
                to on, genPortFunctionalStatus = rld(2))"
            ::= { lntLinkEventsPrefix 3041 }

--      1.3.6.1.4.1.81.38.7.0.3042
        lntVPortLinkUpEvent NOTIFICATION-TYPE
            OBJECTS { genPortFaultMask, genPortGroupId, genPortId }
            STATUS current
            DESCRIPTION
                "Acknowledegs link up condition on a valuable port.
                (Bit 7 in the genPortFaultMask set to off,
                genPortFunctionalStatus = ok)"
            ::= { lntLinkEventsPrefix 3042 }

--      1.3.6.1.4.1.81.38.8
        lntLAGEvents OBJECT-IDENTITY
            STATUS current
            DESCRIPTION
                "Groups together  LAG related events."
            ::= { lntTraps 8 }

--      1.3.6.1.4.1.81.38.8.0
        lntLAGPrefix OBJECT-IDENTITY
            STATUS current
            DESCRIPTION
                "The next to last sub- identifier in the name of any newly-defined notification
                must have the value zero"
            ::= { lntLAGEvents 0 }

--      1.3.6.1.4.1.81.38.8.0.44
        lntLAGConnLostFlt NOTIFICATION-TYPE
            OBJECTS { scGenLinkAggregationFaultMask, scGenLinkAggregationId, scGenLinkAggregationName, scGenLinkAggregationFunctionalStatus }
            STATUS current
            DESCRIPTION
                "The trap reports on a LAG connection lost. It is sent when
                scGenLinkAggregationFunctionalStatus changed to fail (2).  "
            ::= { lntLAGPrefix 44 }

--      1.3.6.1.4.1.81.38.8.0.46
        lntLAGConnLostOk NOTIFICATION-TYPE
            OBJECTS { scGenLinkAggregationFaultMask, scGenLinkAggregationId, scGenLinkAggregationName, scGenLinkAggregationFunctionalStatus }
            STATUS current
            DESCRIPTION
                "The trap reports that the LAG connection lost was cleared.
                It is sent when scGenLinkAggregationFunctionalStatus changed
                from fail(2) to to ok(1).
                "
            ::= { lntLAGPrefix 46 }

--      1.3.6.1.4.1.81.38.8.0.48
        lntLAGPartialConnLostFlt NOTIFICATION-TYPE
            OBJECTS { scGenLinkAggregationFaultMask, scGenLinkAggregationId, scGenLinkAggregationName, scGenLinkAggregationFunctionalStatus }
            STATUS current
            DESCRIPTION
                "The trap reports on a LAG partial connection, where some of the ports
                are in fault but some are ok. It is sent when
                scGenLinkAggregationFunctionalStatus changed to partialFail (3)."
            ::= { lntLAGPrefix 48 }

--
--
-- 1.3.6.1.4.1.81.38.8.0.50
        lntLAGPartialConnLostOk NOTIFICATION-TYPE
            OBJECTS { scGenLinkAggregationFaultMask, scGenLinkAggregationId, scGenLinkAggregationName, scGenLinkAggregationFunctionalStatus }
            STATUS current
            DESCRIPTION
                "The trap reports that the LAG partial connection was cleared.
                It is sent when scGenLinkAggregationFunctionalStatus
                changed from partialFail (3)to to ok(1).
                "
            ::= { lntLAGPrefix 50 }

--      1.3.6.1.4.1.81.38.8.0.52
        lntLAGAutoNegFlt NOTIFICATION-TYPE
            OBJECTS { scGenLinkAggregationFaultMask, scGenLinkAggregationId, scGenLinkAggregationName, scGenLinkAggregationAutoNegResults }
            STATUS current
            DESCRIPTION
                "The trap reports on a auto-negotiation results on the LAG ports.
                It is sent when scGenLinkAggregationAutoNegResults
                changed to autoNegInconsistantResults (2)."
            ::= { lntLAGPrefix 52 }

--      1.3.6.1.4.1.81.38.8.0.54
        lntLAGAutoNegOk NOTIFICATION-TYPE
            OBJECTS { scGenLinkAggregationFaultMask, scGenLinkAggregationId, scGenLinkAggregationName, scGenLinkAggregationAutoNegResults }
            STATUS current
            DESCRIPTION
                "The trap reports that the auto-negotiation results on the LAG ports was cleared.
                It is sent when this trap is enabled and when scGenLinkAggregationAutoNegResults
                changed to ok(1)."
            ::= { lntLAGPrefix 54 }

--      1.3.6.1.4.1.81.38.8.0.56
        lntLAGDeleteEvent NOTIFICATION-TYPE
            OBJECTS { scGenLinkAggregationId, scGenLinkAggregationName, scGenLinkAggregationStatus }
            STATUS current
            DESCRIPTION
                "The trap notifies the manager of the deletion of the specified LAG,
                which is identified by the scGenLinkAggregationId."
            ::= { lntLAGPrefix 56 }

--      1.3.6.1.4.1.81.38.8.0.58
        lntLAGCreateEvent NOTIFICATION-TYPE
            OBJECTS { scGenLinkAggregationId, scGenLinkAggregationName, scGenLinkAggregationStatus }
            STATUS current
            DESCRIPTION
                "The trap is generated on the creation of a new LAG,
                which is identified by the scGenLinkAggregationId."
            ::= { lntLAGPrefix 58 }

--      1.3.6.1.4.1.81.38.9
        lntFansEvents OBJECT-IDENTITY
            STATUS current
            DESCRIPTION
                "Groups together  fans related events."
            ::= { lntTraps 9 }

--      1.3.6.1.4.1.81.38.9.0
        lntFansPrefix OBJECT-IDENTITY
            STATUS current
            DESCRIPTION
                "The next to last sub- identifier in the name of any newly-defined notification
                must have the value zero"
            ::= { lntFansEvents 0 }

--      1.3.6.1.4.1.81.38.9.0.91
        lntMainFansFlt NOTIFICATION-TYPE
            OBJECTS { genGroupFaultMask, genGroupId, scGenGroupFansStatus }
            STATUS current
            DESCRIPTION
                "The trap reports the failure of one (or more)
                module's Fan. It is sent when scGenGroupFansStatus changed
                to oneFanFailed(2)"
            ::= { lntFansPrefix 2307 }

--      1.3.6.1.4.1.81.38.9.0.93
        lntMainFansOK NOTIFICATION-TYPE
            OBJECTS { genGroupFaultMask, genGroupId, scGenGroupFansStatus }
            STATUS current
            DESCRIPTION
                "The trap reports that the module's Fan failure
                was cleared. It is sent when this trap is
                enabled and when scGenGroupFansStatus changed
                from oneFanFailed(2) to allFansOK(1). "
            ::= { lntFansPrefix 2308 }

--      1.3.6.1.4.1.81.38.9.0.87
        lntBackupFansFlt NOTIFICATION-TYPE
            OBJECTS { genGroupFaultMask, genGroupId, scGenGroupBUPSFansStatus }
            STATUS current
            DESCRIPTION
                "The trap reports the failure of one
                (or more) BUPS module's Fan. It is sent when
                scGenGroupBUPSFansStatus changed to
                oneFanFailed(2). "
            ::= { lntFansPrefix 2309 }

--      1.3.6.1.4.1.81.38.9.0.89
        lntBackupFansOK NOTIFICATION-TYPE
            OBJECTS { genGroupFaultMask, genGroupId, scGenGroupBUPSFansStatus }
            STATUS current
            DESCRIPTION
                "The trap reports that the BUPS module's Fan
                failure was cleared. It is sent when this trap is
                enabled and when scGenGroupBUPSFansStatus changed
                from oneFanFailed(2) to allFansOK(1). "
            ::= { lntFansPrefix 2310 }

--      1.3.6.1.4.1.81.38.10
        lntCascadeEvents OBJECT-IDENTITY
            STATUS current
            DESCRIPTION
                "Groups together  stakc module cascading related events."
            ::= { lntTraps 10 }

--      1.3.6.1.4.1.81.38.10.0
        lntCascadeFaultsPrefix OBJECT-IDENTITY
            STATUS current
            DESCRIPTION
                "The next to last sub- identifier in the name of any newly-defined notification
                must have the value zero"
            ::= { lntCascadeEvents 0 }

--      1.3.6.1.4.1.81.38.10.0.95
        lntCascadUpConnFlt NOTIFICATION-TYPE
            OBJECTS { genGroupFaultMask, genGroupId, genGroupCascadUpStatus }
            STATUS current
            DESCRIPTION
                "The trap reports on a cascading up connection lost.
                It is sent when genGroupCascadUpStatus changed to rld(2). "
            ::= { lntCascadeFaultsPrefix 2315 }

--      1.3.6.1.4.1.81.38.10.0.97
        lntCascadUpConnOk NOTIFICATION-TYPE
            OBJECTS { genGroupFaultMask, genGroupId, genGroupCascadUpStatus }
            STATUS current
            DESCRIPTION
                "The trap reports that the cascading up connection lost
                was cleared. It is sent when genGroupCascadUpStatus changed from rld(2) to ok(1).
                "
            ::= { lntCascadeFaultsPrefix 2316 }

--      1.3.6.1.4.1.81.38.10.0.99
        lntCascadDownConnFlt NOTIFICATION-TYPE
            OBJECTS { genGroupFaultMask, genGroupId, genGroupCascadDownStatus }
            STATUS current
            DESCRIPTION
                "The trap reports on a cascading down connection lost.
                It is sent when genGroupCascadDownStatus changed to rld(2)."
            ::= { lntCascadeFaultsPrefix 2317 }

--      1.3.6.1.4.1.81.38.10.0.98
        lntCascadDownConnOk NOTIFICATION-TYPE
            OBJECTS { genGroupFaultMask, genGroupId, genGroupCascadDownStatus }
            STATUS current
            DESCRIPTION
                "The trap reports that the cascading down connection lost
                was cleared. It is sent when genGroupCascadDownStatus
                changed from rld(2) to ok(1)."
            ::= { lntCascadeFaultsPrefix 2318 }

--      1.3.6.1.4.1.81.38.11
        lntPolicyEvents OBJECT-IDENTITY
            STATUS current
            DESCRIPTION
                "Groups together  policy related events."
            ::= { lntTraps 11 }

--      1.3.6.1.4.1.81.38.11.0
        lntPolicyPrefix OBJECT-IDENTITY
            STATUS current
            DESCRIPTION
                "The next to last sub- identifier in the name of any newly-defined notification
                must have the value zero"
            ::= { lntPolicyEvents 0 }

--      1.3.6.1.4.1.81.38.11.0.60
        lntPolicyChangeEvent NOTIFICATION-TYPE
            OBJECTS { ipPolicyActivationEntID, ipPolicyActivationList, ipPolicyActivationifIndex, ipPolicyActivationSubContext }
            STATUS current
            DESCRIPTION
                "The trap reports a change in the active list specific for a
                policy-enabled box or module"
            ::= { lntPolicyPrefix 60 }

--    Sent by G350 Media Gateway
        lntPolicyAccessControlListLvlRuleTrap NOTIFICATION-TYPE
            OBJECTS { ipPolicyAccessControlViolationEntID, ipPolicyAccessControlViolationSrcAddr, ipPolicyAccessControlViolationDstAddr, ipPolicyAccessControlViolationProtocol, ipPolicyAccessControlViolationL4SrcPort,
                ipPolicyAccessControlViolationL4DstPort, ipPolicyAccessControlViolationEstablished, ipPolicyAccessControlViolationRuleType, ipPolicyListID, ipPolicyAccessControlViolationIfIndex,
                ipPolicyAccessControlViolationSubCtxt, ipPolicyAccessControlViolationTime }
            STATUS current
            DESCRIPTION
                "This trap reports to the Management station when a list-level
                Policy rule (e.g., ipPolicyListIpOptionOperation)
                specifies an operation that includes a 'notify' action.
                The trap includes in its varbind information about:
                - The entity (slot) where the event occurred,
                - The type  of the list-level  rule that was matched,
                - The quintuplet that identifies the matching packet.
                - The policy interface on which the event occurred.
                - The policy interface sub-context (e.g., the direction)
                - sysUpTime at the time the event occured.
                A management application would display this trap and the relevant
                information in a log entry.
                This trap will not be sent at intervals smaller than one
                minute for identical information in the varbinds list variables.
                "
            ::= { lntPolicyPrefix 62 }

--      1.3.6.1.4.1.81.38.11.0.64
        lntPolicyAccessControlViolationFlt NOTIFICATION-TYPE
            OBJECTS { ipPolicyAccessControlViolationEntID, ipPolicyAccessControlViolationSrcAddr, ipPolicyAccessControlViolationDstAddr, ipPolicyAccessControlViolationProtocol, ipPolicyAccessControlViolationL4SrcPort,
                ipPolicyAccessControlViolationL4DstPort, ipPolicyAccessControlViolationEstablished, ipPolicyRuleID, ipPolicyRuleListID, ipPolicyAccessControlViolationIfIndex,
                ipPolicyAccessControlViolationSubCtxt, ipPolicyAccessControlViolationTime, ipPolicyRuleDescription }
            STATUS current
            DESCRIPTION
                "This trap reports to the Management station on IP  PolicyAccess Control violation.
                The trap includes in its varbind information about the slot where the event occurred,
                The id of the rule that was violated in the current rules table,
                and the quintuplet that identifies the faulty packet.
                A management application would display this trap and the relevant information in a log entry.
                This trap will not be sent at intervals smaller than one minute for identical information in the
                varbinds list variables
                "
            ::= { lntPolicyPrefix 64 }

--      1.3.6.1.4.1.81.38.12
        lntEthPortFaultEvents OBJECT-IDENTITY
            STATUS current
            DESCRIPTION
                "Groups together Etherent port related events."
            ::= { lntTraps 12 }

--      1.3.6.1.4.1.81.38.12.0
        lntEthPortFaultPrefix OBJECT-IDENTITY
            STATUS current
            DESCRIPTION
                "The next to last sub- identifier in the name of any newly-defined notification
                must have the value zero"
            ::= { lntEthPortFaultEvents 0 }

--      1.3.6.1.4.1.81.38.12.0.3001
        lntEthPortAutoNegotiationFlt NOTIFICATION-TYPE
            OBJECTS { genPortFaultMask, genPortGroupId, genPortId }
            STATUS current
            DESCRIPTION
                "The port recovered from a previously reported
                connectivity problem. (Bit 4 in the genPortFaultMask set to off,
                scEthPortAutoNegotiationStatus = ok)"
            ::= { lntEthPortFaultPrefix 3001 }

--      Resets fault situation because of abnormal
-- situations in the hub's valuable ports.
--
--
-- 1.3.6.1.4.1.81.38.12.0.3002
        lntEthPortAutoNegotiationOK NOTIFICATION-TYPE
            OBJECTS { genPortFaultMask, genPortGroupId, genPortId }
            STATUS current
            DESCRIPTION
                "The port recovered from a previously reported
                connectivity problem. (Bit 4 in the genPortFaultMask set to off,
                scEthPortAutoNegotiationStatus = ok)"
            ::= { lntEthPortFaultPrefix 3002 }

--      1.3.6.1.4.1.81.38.12.0.3005
        lntPortFEFlt NOTIFICATION-TYPE
            OBJECTS { genPortFaultMask, genPortGroupId, genPortId }
            STATUS current
            DESCRIPTION
                "The port hardware detects a loss of connectivity
                reported by the remote extremity of the link connected to
                the port. This indication shows that though the cabling is
                at least partially operative, the information transmitted
                through the port may not arrive in all its integrity at the
                other side of the link. It is recommended that the network
                administrator check the link in order to detect the origin
                of the problem and prevent its aggravation.
                (Bit 10 in the genPortFaultMask set to on)

                "
            ::= { lntEthPortFaultPrefix 3005 }

--      1.3.6.1.4.1.81.38.12.0.3006
        lntPortFEOk NOTIFICATION-TYPE
            OBJECTS { genPortFaultMask, genPortGroupId, genPortId }
            STATUS current
            DESCRIPTION
                "A previously detected problem in the integrity of the link,
                reported by the remote link circuitry was solved.
                (Bit 10 in the genPortFaultMask set to off,
                scEthPortFunctionalStatus = ok(1))
                "
            ::= { lntEthPortFaultPrefix 3006 }

--      1.3.6.1.4.1.81.38.12.0.3015
        lntVPortFEFlt NOTIFICATION-TYPE
            OBJECTS { genPortFaultMask, genPortGroupId, genPortId }
            STATUS current
            DESCRIPTION
                "The valuable port hardware detects a loss of connectivity
                reported by the remote extremity of the link connected to
                the port. This indication shows that though the cabling is
                at least partially operative, the information transmitted
                through the port may not arrive in all its integrity at the
                other side of the link. It is recommended that the network
                administrator check the link in order to detect the origin
                of the problem and prevent its aggravation.
                (Bit 10 in the genPortFaultMask set to on,
                scEthPortFunctionalStatus = fail(2))"
            ::= { lntEthPortFaultPrefix 3015 }

--      1.3.6.1.4.1.81.38.12.0.3016
        lntVPortFEOk NOTIFICATION-TYPE
            OBJECTS { genPortFaultMask, genPortGroupId, genPortId }
            STATUS current
            DESCRIPTION
                "A previously detected problem in the integrity of the link
                to a valuable port, reported by the remote
                link circuitry was solved.
                (Bit 10 in the genPortFaultMask set to off,
                scEthPortFunctionalStatus = ok(1))"
            ::= { lntEthPortFaultPrefix 3016 }

--      1.3.6.1.4.1.81.38.12.0.3023
        lntPortAutoPartFlt NOTIFICATION-TYPE
            OBJECTS { genPortFaultMask, genPortGroupId, genPortId }
            STATUS current
            DESCRIPTION
                "The port on the module reports the activation of the auto
                partition mechanism. This event means that an excessive
                number of errors occurred on the port, and the port is
                disconnected from the repeater or switch unit. The network
                administrator should check the segment and/or end stations
                connected to the port for hardware or misconfiguration problems.
                (Bit 1 in the genPortFaultMask set to on,
                genPortFunctionalStatus = partition(8))
                "
            ::= { lntEthPortFaultPrefix 3023 }

--      1.3.6.1.4.1.81.38.12.0.3024
        lntPortAutoPartOk NOTIFICATION-TYPE
            OBJECTS { genPortFaultMask, genPortGroupId, genPortId }
            STATUS current
            DESCRIPTION
                "The port recovered from a previously reported auto
                partition fault.
                (Bit 1 in the genPortFaultMask set to off,
                genPortFunctionalStatus = ok)"
            ::= { lntEthPortFaultPrefix 3024 }

--      1.3.6.1.4.1.81.38.12.0.3025
        lntVPortAutoPartFlt NOTIFICATION-TYPE
            OBJECTS { genPortFaultMask, genPortGroupId, genPortId }
            STATUS current
            DESCRIPTION
                "The valuable port on the module reports the activation of the
                autopartition mechanism. This event means that an
                excessive number of errors occurred on the port, and the
                port is disconnected from the repeater or switch unit. The
                network administrator should check the segment and/or end
                stations connected to the port for hardware or
                misconfiguration problems.
                (Bit 1 in the genPortFaultMask set to on,
                genPortFunctionalStatus = partition(8))"
            ::= { lntEthPortFaultPrefix 3025 }

--      1.3.6.1.4.1.81.38.12.0.3026
        lntVPortAutoPartOK NOTIFICATION-TYPE
            OBJECTS { genPortFaultMask, genPortGroupId, genPortId }
            STATUS current
            DESCRIPTION
                "The valuable port recovered from a previously
                reported auto partition fault.
                (Bit 1 in the genPortFaultMask set to off,
                genPortFunctionalStatus = ok)"
            ::= { lntEthPortFaultPrefix 3026 }

--      1.3.6.1.4.1.81.38.12.0.3031
        lntEthVPortAutoNegotiationFlt NOTIFICATION-TYPE
            OBJECTS { genPortFaultMask, genPortGroupId, genPortId }
            STATUS current
            DESCRIPTION
                "The valuable port hardware detects the lack of a connection
                to an end station or to another hub or switch. While this
                is may not be necessarily a fault condition, the network
                administrator's attention is recommended, because the port
                was defined as a port.
                (Bit 4 in the genPortFaultMask set to on,
                scEthPortAutoNegotiationStatus = fail(2))

                "
            ::= { lntEthPortFaultPrefix 3031 }

--      1.3.6.1.4.1.81.38.12.0.3032
        lntEthVPortAutoNegotiationOK NOTIFICATION-TYPE
            OBJECTS { genPortFaultMask, genPortGroupId, genPortId }
            STATUS current
            DESCRIPTION
                "The port hardware detects the lack of a connection
                to an end station or to another hub or switch. While this
                is may not be necessarily a fault condition, the network
                administrator's attention is recommended, because the port
                was defined as a valuable port.
                (Bit 4 in the genPortFaultMask set to on,
                scEthPortAutoNegotiationStatus = fail(2))"
            ::= { lntEthPortFaultPrefix 3032 }

--      1.3.6.1.4.1.81.38.12.0.3933
        lntPortInlinePowerFlt NOTIFICATION-TYPE
            OBJECTS { genPortFaultMask, genPortGroupId, genPortId }
            STATUS current
            DESCRIPTION
                "The Inline Power (Power-over-Ethernet) port hardware reports that the PD (Powered device)
                connected to that port is not receiving Inline Power due to a fault condition.
                (Bit 37 in the genPortFaultMask set to on,
                pethPsePortDetectionStatus = fault(4) or otherfault(6))"
            ::= { lntEthPortFaultPrefix 3933 }

--      1.3.6.1.4.1.81.38.12.0.3934
        lntPortInlinePowerOK NOTIFICATION-TYPE
            OBJECTS { genPortFaultMask, genPortGroupId, genPortId }
            STATUS current
            DESCRIPTION
                "The Inline Power (Power-over-Ethernet) port hardware reports that the PD (Powered device)
                connected to that port is not in a fault condition. It may or not be delievering Inline Power
                to the PD.
                (Bit 37 in the genPortFaultMask set to on,
                pethPsePortDetectionStatus = fault(4) or otherfault(6))"
            ::= { lntEthPortFaultPrefix 3934 }

--      1.3.6.1.4.1.81.38.13
        lntSecurityEvents OBJECT-IDENTITY
            STATUS current
            DESCRIPTION
                "Description."
            ::= { lntTraps 13 }

--      1.3.6.1.4.1.81.38.13.0
        lntSecurityPrefix OBJECT-IDENTITY
            STATUS current
            DESCRIPTION
                "Description."
            ::= { lntSecurityEvents 0 }

--      1.3.6.1.4.1.81.38.13.0.1001
        lntUnAuthAccessEvent NOTIFICATION-TYPE
            OBJECTS { lntUnauthUserName, lntUnauthIpAddress, lntUnauthProtocol }
            STATUS current
            DESCRIPTION
                "Notification on unauthorized login attempts.
                o For CLI and SNMP login failures:
                  Both SNMP SSH and WEB management interfaces shall identify
                  situation and alert.
                  The reported information should include wrong user name,
                  host name and IP address of remote host. Passwords is not
                  reported because of the possibility to reveal password.
                o For pre-shared-key (PSK) authentication failure in IKE:
                  *	lntUnauthUserName -
                    - In IKE AM: the ID sent by the remote peer in the ID
                      payload.
                    - In IKE MM: the ID associated with the remote peer IP
                      in the running configuration.
                  * lntUnauthIpAddress - the source IP of the packet sent
                    by the remote peer.
                  * lntUnauthProtocol - lntIKEAccess(500)"
            ::= { lntSecurityPrefix 68 }

--      1.3.6.1.4.1.81.38.13.0.11
        lntMACSecurityEvent NOTIFICATION-TYPE
            OBJECTS { scGenPortLastIntruderSourceAddr, scGenPortGroupId, scGenPortId }
            STATUS current
            DESCRIPTION
                "This trap notifies the management station of the security violation.
                It gives the slot number of the board, the port on the board and the
                source MAC address extracted from the frame that has violated
                the security policy. The slot and the port numbers, genPortGroupId
                and genPortId respectively, define an instance of the appropriate
                source address.For the ring security violation the trap contains the ring ID and the
                intruder's MAC address. The trap was previously assigned the specific number 11.
                "
            ::= { lntSecurityPrefix 104 }

--      1.3.6.1.4.1.81.38.13.0.1002
        lntUnknownHostCopyEvent NOTIFICATION-TYPE
            OBJECTS { lntUnauthUserName, lntUnauthIpAddress, lntSCPStrictCheckingMode }
            STATUS current
            DESCRIPTION
                "Event generated on attempt to accomplish download/upload file
                transfer using SCP/SFTP protocol to unknown host. "
            ::= { lntSecurityPrefix 1002 }

        lntAccountLockoutEvent NOTIFICATION-TYPE
            OBJECTS { lntUnauthUserName, lntUnauthIpAddress, lntUnauthProtocol }
            STATUS current
            DESCRIPTION
                "After configurable number of failed attempts to authenticate a user, device
                penalized by locking them out for a pre-specified amount of time."
            ::= { lntSecurityPrefix 1003 }

--      1.3.6.1.4.1.81.38.1.0.1
        lntLicenseStartupValidationFlt NOTIFICATION-TYPE
            OBJECTS { lntLicenseErrorCodes }
            STATUS current
            DESCRIPTION
                "At start-up, the product validates the license file
                scheme and the license signature. On inconsistency the product
                issues this tarp and then returns to the factory-default feature activation
                settings."
            ::= { lntSecurityPrefix 1004 }

        lntLicenseDownloadValidationFlt NOTIFICATION-TYPE
            OBJECTS { lntLicenseErrorCodes }
            STATUS current
            DESCRIPTION
                "During the license file download, the product validates the license file
                scheme and the license signature. On inconsistency the product
                aborts download process, sends this notification and
                stay with the existing feature activation settings"
            ::= { lntSecurityPrefix 1005 }

		lntDot1xMaxAuthRateReachedEvent NOTIFICATION-TYPE
            OBJECTS { scGenPortGroupId }
            STATUS current
            DESCRIPTION
                "This trap notifies the management station that maximum rate of 802.1x
                authentications has been reached in module $1 .
                "
            ::= { lntSecurityPrefix 1006 }

        lntDot1xAuthFailureEvent NOTIFICATION-TYPE
            OBJECTS { scGenPortDot1xMAC, scGenPortGroupId, scGenPortId, scGenPortDot1xFailureString }
            STATUS current
            DESCRIPTION
                "This trap notifies the management station that device with MAC address
                $1 failed to authenticate module/port $2/$3 due to $4
                "
            ::= { lntSecurityPrefix 1007 }

        lntDot1xMaxAuthModuleNumReachedEvent NOTIFICATION-TYPE
            OBJECTS { scGenGroupDot1xSystemMaxNumSupplicant, scGenPortGroupId  }
            STATUS current
            DESCRIPTION
                "This trap notifies the management station that Authentication denied due to
                maximum number of authentication of 802.1x $1 per module $2 has been reached.
                "
            ::= { lntSecurityPrefix 1008 }


        lntDot1xMaxAuthPortNumReachedEvent NOTIFICATION-TYPE
            OBJECTS { scGenSwitchDot1xPortMaxSuppNum, scGenPortGroupId, scGenPortId  }
            STATUS current
            DESCRIPTION
                "This trap notifies the management station that Authentication denied due to
                maximum number of authentication of 802.1x $1 per module/port $2/$3 has been reached.
                "
            ::= { lntSecurityPrefix 1009 }



--      1.3.6.1.4.1.81.38.14
        lntNotificationVarbinds OBJECT-IDENTITY
            STATUS current
            DESCRIPTION
                "Description."
            ::= { lntTraps 14 }

--      1.3.6.1.4.1.81.38.14.1
        lntConfigChangeValue OBJECT-TYPE
            SYNTAX DisplayString
            MAX-ACCESS accessible-for-notify
            STATUS current
            DESCRIPTION
                "The text formatted value of MIB object at the time change
                configuration has occured"
            ::= { lntNotificationVarbinds 1 }

--      1.3.6.1.4.1.81.38.14.2
        lntConfigChangeOID OBJECT-TYPE
            SYNTAX OBJECT IDENTIFIER
            MAX-ACCESS accessible-for-notify
            STATUS current
            DESCRIPTION
                "This variable used to signal the OID of MIB object that had changed
                its status and triggered the Change Configuration event
                "
            ::= { lntNotificationVarbinds 2 }

--      1.3.6.1.4.1.81.38.14.3
        lntUnauthUserName OBJECT-TYPE
            SYNTAX OCTET STRING (SIZE (0..32))
            MAX-ACCESS accessible-for-notify
            STATUS current
            DESCRIPTION
                "The name of the user who's attempt to access device was identified as unauthorized.
                "
            ::= { lntNotificationVarbinds 3 }

--      1.3.6.1.4.1.81.38.14.4
        lntUnauthIpAddress OBJECT-TYPE
            SYNTAX IpAddress
            MAX-ACCESS accessible-for-notify
            STATUS current
            DESCRIPTION
                "The IP address of access violating station"
            ::= { lntNotificationVarbinds 4 }

--      1.3.6.1.4.1.81.38.14.5
        lntUnauthProtocol OBJECT-TYPE
            SYNTAX INTEGER
                {
                lntSSHAccess(22),
                lntTELNETAccess(23),
                lntHTTPAccess(80),
                lntSNMPAccess(161),
                lntHTTPSAccess(443),
                lntIKEAccess(500),
                lntRASAccess(6889),
                lntConsoleAccess(6890),
                lntPPPAccess(6891)
                }
            MAX-ACCESS accessible-for-notify
            STATUS current
            DESCRIPTION
                "The management protocol  employed for the unauthorized access -

                lntSSHAccess(22) --   SSH protocol
                lntTELNETAccess(23),  --Telnet protocol
                lntHTTPAccess(80),    --  HTTP protocol
                lntSNMPAccess(161),   --  SNMP protocol
                lntHTTPSAccess(443),  --  HTTPS protocol over TLS sockets
                lntIKEAccess(500),    --  IKE protocol - PSK authentication failure
                lntRASAccess(6889),   --  RAS access over dial-up connection
                lntConsoleAccess(6890), -- Access from the Console port
                lntPPPAccess(6891)      -- Access to PPP over modem
                "
            ::= { lntNotificationVarbinds 5 }

--      1.3.6.1.4.1.81.38.14.6
        lntSCPStrictCheckingMode OBJECT-TYPE
            SYNTAX INTEGER
                {
                yes(1),
                no(2),
                ask(3)
                }
            MAX-ACCESS accessible-for-notify
            STATUS current
            DESCRIPTION
                "The SCP setting on validity of the public key reported by the SCP server.
                If strict setting is yes - then new keys not registered already in hosts file will
                be discard and copy operation is aborted. No - device registers new hosts and proceded with copy operation,
                ask - requires interactive sessions with the operator ( must fail the SNMP non interactive request)"
            ::= { lntNotificationVarbinds 6 }

        lntLicenseErrorCodes OBJECT-TYPE
            SYNTAX INTEGER
                {
                lntSerialNumMismatch(1),
                lntInvalidSignature(2),
                lntPlatformTypeMismatch(3),
                lntInvalidLicFeture(4)
                }
            MAX-ACCESS  accessible-for-notify
            STATUS current
            DESCRIPTION
                "Product reports following errors if license validations fails

                   lntSerialNumMismatch(1), - Serial number mismatch between license file
                                              and gateway hardware
                   lntInvalidSignature(2), - Invalid digital signature on the license file

                   lntPlatformTypeMismatch(3), - Mismatch between product platform type defined in
                            license file (for example G250) and the gateway type (e.g. G350).

                   lntInvalidLicFeture(4) - Invalid feature setting."
            ::= { lntNotificationVarbinds 7 }

        scGenPortDot1xFailureString OBJECT-TYPE
            SYNTAX DisplayString
            MAX-ACCESS accessible-for-notify
            STATUS current
            DESCRIPTION
                "The text formatted value of MIB object at the time when 802.1x authentication
                is failed."
            ::= { lntNotificationVarbinds 8 }



        lntWanEvents OBJECT-IDENTITY
            STATUS current
            DESCRIPTION
                "Description."
            ::= { lntTraps 15 }

        lntWanPrefix OBJECT-IDENTITY
            STATUS current
            DESCRIPTION
                "Description."
            ::= { lntWanEvents 0 }

        lntWanPhysicalAlarmOn NOTIFICATION-TYPE
            OBJECTS { ifIndex, ifAdminStatus, ifOperStatus, ifName, ifAlias,
                dsx1LineStatus }
            STATUS current
            DESCRIPTION
                "Description."
            ::= { lntWanPrefix 30 }

        lntWanPhysicalAlarmOff NOTIFICATION-TYPE
            OBJECTS { ifIndex, ifAdminStatus, ifOperStatus, ifName, ifAlias,
                dsx1LineStatus }
            STATUS current
            DESCRIPTION
                "Description."
            ::= { lntWanPrefix 31 }

        lntWanLocalAlarmOn NOTIFICATION-TYPE
            OBJECTS { ifIndex, ifAdminStatus, ifOperStatus, ifName, ifAlias,
                dsx1LineStatus }
            STATUS current
            DESCRIPTION
                "Description."
            ::= { lntWanPrefix 32 }

        lntWanLocalAlarmOff NOTIFICATION-TYPE
            OBJECTS { ifIndex, ifAdminStatus, ifOperStatus, ifName, ifAlias,
                dsx1LineStatus }
            STATUS current
            DESCRIPTION
                "Description."
            ::= { lntWanPrefix 33 }

        lntWanRemoteAlarmOn NOTIFICATION-TYPE
            OBJECTS { ifIndex, ifAdminStatus, ifOperStatus, ifName, ifAlias,
                dsx1LineStatus }
            STATUS current
            DESCRIPTION
                "Description."
            ::= { lntWanPrefix 34 }

        lntWanRemoteAlarmOff NOTIFICATION-TYPE
            OBJECTS { ifIndex, ifAdminStatus, ifOperStatus, ifName, ifAlias,
                dsx1LineStatus }
            STATUS current
            DESCRIPTION
                "Description."
            ::= { lntWanPrefix 35 }

        lntWanMinorAlarmOn NOTIFICATION-TYPE
            OBJECTS { ifIndex, ifAdminStatus, ifOperStatus, ifName, ifAlias,
                dsx1LineStatus }
            STATUS current
            DESCRIPTION
                "Description."
            ::= { lntWanPrefix 36 }

        lntWanMinorAlarmOff NOTIFICATION-TYPE
            OBJECTS { ifIndex, ifAdminStatus, ifOperStatus, ifName, ifAlias,
                dsx1LineStatus }
            STATUS current
            DESCRIPTION
                "Description."
            ::= { lntWanPrefix 37 }

--      ===================================================================================================
-- This section classify notifications into groups used for
-- definition of capabilties and trap filtering
-- ===================================================================================================
-- 1.3.6.1.4.1.81.38.10007
        lntNotificationGroups OBJECT IDENTIFIER ::= { lntTraps 10007 }

--      1.3.6.1.4.1.81.38.10007.1
        lntConfigChangeVarbinds OBJECT-GROUP
            OBJECTS { lntConfigChangeValue, lntConfigChangeOID, lntUnauthIpAddress, lntUnauthUserName, lntLicenseErrorCodes,
                lntSCPStrictCheckingMode, lntUnauthProtocol }
            STATUS current
            DESCRIPTION
                "varbinds related with config change trap"
            ::= { lntNotificationGroups 1 }

--      1.3.6.1.4.1.81.38.10007.5
        lntLagNotificationGroup NOTIFICATION-GROUP
            NOTIFICATIONS { lntLAGConnLostFlt, lntLAGConnLostOk, lntLAGPartialConnLostFlt, lntLAGPartialConnLostOk, lntLAGAutoNegFlt,
                lntLAGAutoNegOk, lntLAGDeleteEvent, lntLAGCreateEvent }
            STATUS current
            DESCRIPTION
                "Group of Link aggregation traps"
            ::= { lntNotificationGroups 5 }

--      1.3.6.1.4.1.81.38.10007.6
        lntSWRedundancyNotificationGroup NOTIFICATION-GROUP
            NOTIFICATIONS { lntSoftRedDelEvent, lntSoftRedNewEvent }
            STATUS current
            DESCRIPTION
                "Group of Software  Redundancy traps"
            ::= { lntNotificationGroups 6 }

--      1.3.6.1.4.1.81.38.10007.7
        lntPSUFaultNotificationGroup NOTIFICATION-GROUP
            NOTIFICATIONS { lntMainPSUFlt, lntMainPSUOk, lntBackupPSUFlt, lntBackupPSUOk }
            STATUS current
            DESCRIPTION
                "PSU related fault traps (main and backup)"
            ::= { lntNotificationGroups 7 }

--      1.3.6.1.4.1.81.38.10007.8
        lntTempratureNotificationGroup NOTIFICATION-GROUP
            NOTIFICATIONS { lntTempratureOk, lntTempratureWarning }
            STATUS current
            DESCRIPTION
                "Temperature warning related traps"
            ::= { lntNotificationGroups 8 }

--      1.3.6.1.4.1.81.38.10007.9
        lntL3FaultNotificationGroup NOTIFICATION-GROUP
            NOTIFICATIONS { lntDuplicateIPFlt, lntVLANViolationEvent, lntARPViolationEvent }
            STATUS current
            DESCRIPTION
                "Group of L3 fault traps"
            ::= { lntNotificationGroups 9 }

--      1.3.6.1.4.1.81.38.10007.10
        lntLinkDownNotificationGroup NOTIFICATION-GROUP
            NOTIFICATIONS { lntPortLinkDownEvent, lntPortLinkUpEvent, lntVPortLinkDownEvent, lntVPortLinkUpEvent }
            STATUS current
            DESCRIPTION
                "Link Down/Up traps"
            ::= { lntNotificationGroups 10 }

--      1.3.6.1.4.1.81.38.10007.11
        lntCascadeNotificationGroup NOTIFICATION-GROUP
            NOTIFICATIONS { lntCascadUpConnFlt, lntCascadUpConnOk, lntCascadDownConnOk, lntCascadDownConnFlt }
            STATUS current
            DESCRIPTION
                "Cascade fault traps"
            ::= { lntNotificationGroups 11 }

--      1.3.6.1.4.1.81.38.10007.12
        lntEthPortNotificationGroup NOTIFICATION-GROUP
            NOTIFICATIONS { lntPortFEFlt, lntPortFEOk, lntVPortFEFlt, lntVPortFEOk, lntPortAutoPartFlt,
                lntPortAutoPartOk, lntVPortAutoPartFlt, lntVPortAutoPartOK, lntEthVPortAutoNegotiationOK, lntEthPortAutoNegotiationOK,
                lntEthPortAutoNegotiationFlt, lntEthVPortAutoNegotiationFlt, lntPortInlinePowerFlt, lntPortInlinePowerOK }
            STATUS current
            DESCRIPTION
                "Eth port fault traps"
            ::= { lntNotificationGroups 12 }

--      1.3.6.1.4.1.81.38.10007.13
        lntCAMNotificationGroup NOTIFICATION-GROUP
            NOTIFICATIONS { lntPortCAMLastChange }
            STATUS obsolete
            DESCRIPTION
                "CAM change related traps"
            ::= { lntNotificationGroups 13 }

--      1.3.6.1.4.1.81.38.10007.14
        lntConfigChangeNotificationGroup NOTIFICATION-GROUP
            NOTIFICATIONS { lntConfigChangeEvent, lntStackMasterReelection }
            STATUS current
            DESCRIPTION
                "Configuration change related traps"
            ::= { lntNotificationGroups 14 }

--      1.3.6.1.4.1.81.38.10007.15
        lntPolicyNotificationGroup NOTIFICATION-GROUP
            NOTIFICATIONS { lntPolicyAccessControlListLvlRuleTrap, lntPolicyAccessControlViolationFlt, lntPolicyChangeEvent }
            STATUS current
            DESCRIPTION
                "policy related traps"
            ::= { lntNotificationGroups 15 }

--      1.3.6.1.4.1.81.38.10007.16
        lntFansNotificationGroup NOTIFICATION-GROUP
            NOTIFICATIONS { lntBackupFansFlt, lntBackupFansOK, lntMainFansFlt, lntMainFansOK }
            STATUS current
            DESCRIPTION
                "Notifications related with FAN problems"
            ::= { lntNotificationGroups 16 }

--      1.3.6.1.4.1.81.38.10007.17
        lntSecurityNotificationGroup NOTIFICATION-GROUP
            NOTIFICATIONS { lntAccountLockoutEvent, lntMACSecurityEvent, lntUnAuthAccessEvent, lntUnknownHostCopyEvent, lntLicenseStartupValidationFlt,
                lntLicenseDownloadValidationFlt }
            STATUS current
            DESCRIPTION
                "Description."
            ::= { lntNotificationGroups 17 }

        lntWanNotificationGroup NOTIFICATION-GROUP
            NOTIFICATIONS { lntWanPhysicalAlarmOn, lntWanPhysicalAlarmOff, lntWanLocalAlarmOn, lntWanLocalAlarmOff, lntWanRemoteAlarmOn,
                lntWanRemoteAlarmOff, lntWanMinorAlarmOn, lntWanMinorAlarmOff }
            STATUS current
            DESCRIPTION
                "Description."
            ::= { lntNotificationGroups 18 }

--      ===================================================================================================
-- This section defines trap generation device capabilities.
-- ===================================================================================================
-- 1.3.6.1.4.1.81.38.10008
        lntNotificationAgentCapabilities OBJECT IDENTIFIER ::= { lntTraps 10008 }

--      1.3.6.1.4.1.81.38.10008.1
        lntP330L3NotificationAgentCapabilities AGENT-CAPABILITIES
PRODUCT-RELEASE
            ""
            STATUS current
            DESCRIPTION
                "Trap Capabilities of P330 L3 Device."
            SUPPORTS Lannet-Trapsv2-MIB
                INCLUDES { lntSecurityNotificationGroup, lntConfigChangeVarbinds, lntLagNotificationGroup, lntSWRedundancyNotificationGroup, lntPSUFaultNotificationGroup,
                    lntL3FaultNotificationGroup, lntLinkDownNotificationGroup, lntCascadeNotificationGroup, lntEthPortNotificationGroup, lntCAMNotificationGroup,
                    lntConfigChangeNotificationGroup, lntPolicyNotificationGroup, lntFansNotificationGroup }
            ::= { lntNotificationAgentCapabilities 1 }

--      1.3.6.1.4.1.81.38.10008.2
        lntP330L2NotificationAgentCapabilities AGENT-CAPABILITIES
PRODUCT-RELEASE
            ""
            STATUS current
            DESCRIPTION
                "Trap capabilities of P330 L2 device."
            SUPPORTS Lannet-Trapsv2-MIB
                INCLUDES { lntLagNotificationGroup, lntSWRedundancyNotificationGroup, lntPSUFaultNotificationGroup, lntLinkDownNotificationGroup, lntCascadeNotificationGroup,
                    lntEthPortNotificationGroup, lntConfigChangeNotificationGroup, lntSecurityNotificationGroup, lntFansNotificationGroup, lntConfigChangeVarbinds
                     }
            ::= { lntNotificationAgentCapabilities 2 }

--      1.3.6.1.4.1.81.38.10008.3
        lntP130TrapAgentCapabilities AGENT-CAPABILITIES
PRODUCT-RELEASE
            ""
            STATUS current
            DESCRIPTION
                "Trap capabilities of P130 device."
            SUPPORTS Lannet-Trapsv2-MIB
                INCLUDES { lntConfigChangeVarbinds, lntLagNotificationGroup, lntSWRedundancyNotificationGroup, lntPSUFaultNotificationGroup, lntLinkDownNotificationGroup,
                    lntCascadeNotificationGroup, lntEthPortNotificationGroup, lntConfigChangeNotificationGroup, lntFansNotificationGroup, rmonNotificationGroup
                     }
            ::= { lntNotificationAgentCapabilities 3 }

--      1.3.6.1.4.1.81.38.10008.4
        lntP330MLNotificationAgentCapabilities AGENT-CAPABILITIES
PRODUCT-RELEASE
            ""
            STATUS current
            DESCRIPTION
                "Traps supported by P330ML device."
            SUPPORTS Lannet-Trapsv2-MIB
                INCLUDES { lntConfigChangeVarbinds, rmonNotificationGroup, lntLagNotificationGroup, lntSWRedundancyNotificationGroup, lntPSUFaultNotificationGroup,
                    lntTempratureNotificationGroup, lntL3FaultNotificationGroup, lntLinkDownNotificationGroup, lntCascadeNotificationGroup, lntEthPortNotificationGroup,
                    lntConfigChangeNotificationGroup, lntPolicyNotificationGroup, lntFansNotificationGroup }
            ::= { lntNotificationAgentCapabilities 4 }

        lntG350NotificationAgentCapability AGENT-CAPABILITIES
PRODUCT-RELEASE
            ""
            STATUS current
            DESCRIPTION
                "Description."
            SUPPORTS Lannet-Trapsv2-MIB
                INCLUDES { rmonNotificationGroup, lntLagNotificationGroup, lntL3FaultNotificationGroup, lntLinkDownNotificationGroup, lntEthPortNotificationGroup,
                    lntConfigChangeNotificationGroup, lntPolicyNotificationGroup, lntSecurityNotificationGroup, lntWanNotificationGroup }
            ::= { lntNotificationAgentCapabilities 5 }


    END

--
-- Lannet-Trapsv2-MIB.my
--
