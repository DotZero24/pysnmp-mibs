AVAYA-ENTITY-MIB DEFINITIONS ::= BEGIN

IMPORTS
        MODULE-IDENTITY, OBJECT-TYPE,NOTIFICATION-TYPE,Integer32, Unsigned32
                FROM SNMPv2-SMI
	mib-2
		FROM RFC1213-MIB
        MODULE-COMPLIANCE, OBJECT-GROUP, NOTIFICATION-GROUP
                FROM SNMPv2-CONF
        TEXTUAL-CONVENTION, TimeStamp
                FROM SNMPv2-TC
        entPhysicalIndex, PhysicalIndex
                FROM ENTITY-MIB
        TEXTUAL-CONVENTION, TimeStamp, DisplayString
                FROM SNMPv2-TC
	entPhysicalDescr, entPhysicalParentRelPos
		FROM ENTITY-MIB
        EntitySensorValue, entPhySensorValue
		FROM ENTITY-SENSOR-MIB
        lsg
	        FROM AVAYAGEN-MIB;

avayaEntity MODULE-IDENTITY
    LAST-UPDATED    "200612251800Z"
    ORGANIZATION    "Avaya Inc."
    CONTACT-INFO
            "        Dan Gluskin
                     Avaya Inc.
                Tel: +972-3-645-7561
              Email: dgluskin@avaya.com
             Postal: Atidim technology Park, Bldg. #3
                     Tel Aviv, Israel, 61131

                     Dan Romascanu
                     Avaya Inc.
                Tel: +972-3-645-8414
              Email: dromasca@avaya.com
             Postal: Atidim technology Park, Bldg. #3
                     Tel Aviv, Israel, 61131
		"
    DESCRIPTION
            "This module defines private extensions for Entity MIB"
--
-- REVISION    "200805051814Z"
--  Updated by: Shlomi Biton
--    DESCRIPTION Add new enumeration badExpansionCable(7) to avEntPhyChFruFault.
--				  Add new traps avEntPhyChFruExpansionTestFailure and avEntPhyChFruExpansionTestClear.
--
-- REVISION    "200612251800Z"
--  Updated by: M. Deutsch
--    DESCRIPTION "fix warning in avEntPhyChFruInsertion group definition
--
-- REVISION    "200606111218Z"
--  Updated by: Dan Gluskin
--    DESCRIPTION "I've added IMPORT statements to allow compliation with with NetSNMP"
--
-- REVISION    "200603121200Z"
--    Updated By: Meir Deutsch
--    DESCRIPTION
--    "Add the avEntPhyChFru objects to support G450 Fan and PSU status and fault reporting and notifications"
--
-- REVISION    "200606111218Z"
--    Updated By: Shlomi Biton
--    DESCRIPTION
--    "1. Remove the Varbinds: avEntPhysicalIndex, entPhysicalDescr, avEntPhyUSBDeviceUSBSupportVersion,
-- 	      avEntPhyUSBDeviceSpeed, avEntPhyUSBDevicePower from  of the
--        avEntPhyUSBDeviceRemovalOnBackupRestoreOperation trap.
--
--    REVISION    "200605301159Z"
--    Updated By: Shlomi Biton
--    DESCRIPTION
--    "1. Add avEntPhysicalIndex (accessible-for-notify) for all the traps instead of
--     entPhysicalIndex, since the entPhysicalIndex from the standard ENTITY-MIB is not-accessible
--     and for traps the varbind shall be at least accessible-for-notify.
--
--    REVISION    "200605231728Z"
--    Updated By: Shlomi Biton
--    DESCRIPTION
--    "1. Add USB trap avEntPhyUSBFileSystemNotSupported for connecting USB mass
--     storage device with file system that is not supported."
--
--    REVISION    "200601241503Z"
--    Updated By: Shlomi Biton
--    DESCRIPTION
--    "1. Add USB mib tables."
--
--    REVISION    "200412010000Z"
--    DESCRIPTION
--    "Fiv avEntAmbient Traps"
--
--    REVISION    "200311051639Z"
--    DESCRIPTION
--    "Traps OIDs moved under avEntTrapsV3separator added to support SNMPv3 traps"
--
--    REVISION    "200003240000Z"
--    DESCRIPTION
--            "Initial version"
--
--    REVISION    "200004090000Z"
--    DESCRIPTION
--       "Changes for SNMPv1 compatibility
--        Add avEntTraps group and trap items"

    ::= { lsg 99 }


AvEntPhyItuPerceivedSeverity ::= TEXTUAL-CONVENTION
       		STATUS current
       		DESCRIPTION
            		"ITU perceived severity values"
       		REFERENCE
            "ITU Recommendation M.3100, 'Generic Network Information
               Model', 1995
               ITU Recommendation X.733, 'Information Technology - Open
               Systems Interconnection - System Management: Alarm
               Reporting Function', 1992"
       		SYNTAX         INTEGER
              	{
              	cleared (1),
              	indeterminate (2),
              	critical (3),
              	major (4),
              	minor (5),
              	warning (6)
              	}
--
-- Textual Conventions
--


--
-- Entity Sensor Table
--

avEntPhySensorTable OBJECT-TYPE
    SYNTAX        SEQUENCE OF AvEntPhySensorEntry
    MAX-ACCESS    not-accessible
    STATUS        current
    DESCRIPTION
            "This table extends entPhySensorTable with thresholds on the sensors."
    ::= { avayaEntity 1 }


avEntPhySensorEntry OBJECT-TYPE
    SYNTAX        AvEntPhySensorEntry
    MAX-ACCESS    not-accessible
    STATUS        current
    DESCRIPTION
            "Thresholds for sensors described in entPhySensorTable.
             The Threshold values correspond to entPhySensorValue.

            Entries are created in this table by the agent.  An entry
            for each physical sensor SHOULD be created at the same time
            as the associated entPhysicalEntry.  An entry SHOULD be
            destroyed if the associated entPhysicalEntry is destroyed.
            No entry means that no thresholds are defined for the corresponding
            sensor"
    INDEX  { entPhysicalIndex }    -- SPARSE-AUGMENTS
    ::= { avEntPhySensorTable 1 }

AvEntPhySensorEntry ::= SEQUENCE {
        avEntPhySensorHiShutdown      EntitySensorValue,
        avEntPhySensorHiWarning       EntitySensorValue,
        avEntPhySensorHiWarningClear  EntitySensorValue,
        avEntPhySensorLoWarningClear  EntitySensorValue,
        avEntPhySensorLoWarning        EntitySensorValue,
        avEntPhySensorLoShutdown      EntitySensorValue,
	avEntPhySensorEventSupportMask OCTET STRING
}

avEntPhySensorHiShutdown OBJECT-TYPE
    SYNTAX        EntitySensorValue
    MAX-ACCESS    read-only
    STATUS        current
    DESCRIPTION
            "The system shuts down when the sensor reading reaches this value"
    ::= { avEntPhySensorEntry 1 }


avEntPhySensorHiWarning OBJECT-TYPE
    SYNTAX        EntitySensorValue
    MAX-ACCESS    read-only
    STATUS        current
    DESCRIPTION
            "The system generates a warning event when the sensor reading
	       rises and crosses this value"
    ::= { avEntPhySensorEntry 2 }

avEntPhySensorHiWarningClear OBJECT-TYPE
    SYNTAX        EntitySensorValue
    MAX-ACCESS    read-only
    STATUS        current
    DESCRIPTION
            "The system generates a warning-clear event when the sensor reading  	       falls and crosses below this value"
    ::= { avEntPhySensorEntry 3 }

avEntPhySensorLoWarningClear OBJECT-TYPE
    SYNTAX        EntitySensorValue
    MAX-ACCESS    read-only
    STATUS        current
    DESCRIPTION
            "The system generates a warning-clear event when the sensor reading
             rises and crosses this value "
    ::= { avEntPhySensorEntry 4 }

avEntPhySensorLoWarning OBJECT-TYPE
    SYNTAX        EntitySensorValue
    MAX-ACCESS    read-only
    STATUS        current
    DESCRIPTION
            "The system generates a warning event when the sensor reading
	       falls and crosses this value"
    ::= { avEntPhySensorEntry 5 }

avEntPhySensorLoShutdown OBJECT-TYPE
    SYNTAX        EntitySensorValue
    MAX-ACCESS    read-only
    STATUS        current
    DESCRIPTION
            "The system shuts down if the sensor reaches this value"
    ::= { avEntPhySensorEntry 6 }

avEntPhySensorEventSupportMask OBJECT-TYPE
    SYNTAX	OCTET STRING
    MAX-ACCESS    read-only
    STATUS        current
    DESCRIPTION
            " A trap and an event is generated upon threshold crossing if the
              correspond bit is set. Note that there may be other trap
              filtering mechanisms.
	          0/0:  hiShutdown(0)
	          0/1:  hiWarning(1)
	          0/2:  hiWarningClear(2)
	          0/3:  loWarningClear(3)
	          0/4:  loWarning(4)
	          0/5:  loShowdown(5)"
    ::= { avEntPhySensorEntry 7 }


avEntTraps	OBJECT IDENTIFIER ::= { avayaEntity 2 } -- Traps group
avEntTrapsV3separator		OBJECT IDENTIFIER ::= { avEntTraps 0 }

-- "RFC 2576 says: 'If the SNMPv1 generic-trap parameter is 'enterpriseSpecific(6)',
--       the SNMPv2 snmpTrapOID parameter SHALL be the concatentation of  the SNMPv1
--       enterprise parameter and two additional sub- identifiers, '0',
--       and the SNMPv1 specific-trap parameter.'
--
--   in SNMPv1 G350 is sending for cmg traps:
--   generic trap: 		enterpriseSpecific(6)
--   enterprise: 		avEntTraps
--   specific trap:		x (cmg trap number)
--


avEntFanFlt	NOTIFICATION-TYPE
	OBJECTS   { avEntPhysicalIndex, entPhysicalDescr, entPhySensorValue, avEntPhySensorLoWarning}
	STATUS      current
	DESCRIPTION
	"Fan Fault"
	::= { avEntTrapsV3separator 1 }

avEntFanOk	NOTIFICATION-TYPE
	OBJECTS   { avEntPhysicalIndex, entPhysicalDescr, entPhySensorValue, avEntPhySensorLoWarningClear}
	STATUS      current
	DESCRIPTION
	"Fan Fault"
	::= { avEntTrapsV3separator 2 }

avEnt48vPwrFlt NOTIFICATION-TYPE
	OBJECTS   { avEntPhysicalIndex, entPhysicalDescr, entPhySensorValue, avEntPhySensorHiWarning, avEntPhySensorLoWarning, entPhysicalParentRelPos}
	STATUS      current
	DESCRIPTION
	"48V power supply fault"
	::= { avEntTrapsV3separator 4 }

avEnt48vPwrFltOk NOTIFICATION-TYPE
	OBJECTS   { avEntPhysicalIndex, entPhysicalDescr, entPhySensorValue, avEntPhySensorHiWarningClear, avEntPhySensorLoWarningClear, entPhysicalParentRelPos}
	STATUS      current
	DESCRIPTION
	"48V power supply fault clear"
	::= { avEntTrapsV3separator 5 }

avEnt5vPwrFlt NOTIFICATION-TYPE
	OBJECTS   { avEntPhysicalIndex, entPhysicalDescr, entPhySensorValue, avEntPhySensorHiWarning, avEntPhySensorLoWarning, entPhysicalParentRelPos}
	STATUS      current
	DESCRIPTION
	"5V power supply fault"
	::= { avEntTrapsV3separator 7 }

avEnt5vPwrFltOk NOTIFICATION-TYPE
	OBJECTS   { avEntPhysicalIndex, entPhysicalDescr, entPhySensorValue, avEntPhySensorHiWarningClear, avEntPhySensorLoWarningClear, entPhysicalParentRelPos}
	STATUS      current
	DESCRIPTION
	"5V power supply fault clear"
	::= { avEntTrapsV3separator 8 }

avEnt3300mvPwrFlt NOTIFICATION-TYPE
	OBJECTS   { avEntPhysicalIndex, entPhysicalDescr, entPhySensorValue, avEntPhySensorHiWarning, avEntPhySensorLoWarning, entPhysicalParentRelPos}
	STATUS      current
	DESCRIPTION
	"3.3V (3300mv) power supply fault"
	::= { avEntTrapsV3separator 10 }

avEnt3300mvPwrFltOk NOTIFICATION-TYPE
	OBJECTS   { avEntPhysicalIndex, entPhysicalDescr, entPhySensorValue, avEntPhySensorHiWarningClear, avEntPhySensorLoWarningClear, entPhysicalParentRelPos}
	STATUS      current
	DESCRIPTION
	"3.3V (3300mv) power supply fault clear"
	::= { avEntTrapsV3separator 11 }

avEnt2500mvPwrFlt NOTIFICATION-TYPE
	OBJECTS   { avEntPhysicalIndex, entPhysicalDescr, entPhySensorValue, avEntPhySensorHiWarning, avEntPhySensorLoWarning, entPhysicalParentRelPos}
	STATUS      current
	DESCRIPTION
	"2.5V (2500mv) power supply fault"
	::= { avEntTrapsV3separator 13 }

avEnt2500mvPwrFltOk NOTIFICATION-TYPE
	OBJECTS   { avEntPhysicalIndex, entPhysicalDescr, entPhySensorValue, avEntPhySensorHiWarningClear, avEntPhySensorLoWarningClear, entPhysicalParentRelPos}
	STATUS      current
	DESCRIPTION
	"2.5V (2500mv) power supply fault clear"
	::= { avEntTrapsV3separator 14 }

avEnt1800mvPwrFlt NOTIFICATION-TYPE
	OBJECTS   { avEntPhysicalIndex, entPhysicalDescr, entPhySensorValue, avEntPhySensorHiWarning, avEntPhySensorLoWarning, entPhysicalParentRelPos}
	STATUS      current
	DESCRIPTION
	"1.8V (1800mv) power supply fault"
	::= { avEntTrapsV3separator 16 }

avEnt1800mvPwrFltOk NOTIFICATION-TYPE
	OBJECTS   { avEntPhysicalIndex, entPhysicalDescr, entPhySensorValue, avEntPhySensorHiWarningClear, avEntPhySensorLoWarningClear, entPhysicalParentRelPos}
	STATUS      current
	DESCRIPTION
	"1.8V (1800mv) power supply fault clear"
	::= { avEntTrapsV3separator 17 }

avEnt1600mvPwrFlt NOTIFICATION-TYPE
	OBJECTS   { avEntPhysicalIndex, entPhysicalDescr, entPhySensorValue, avEntPhySensorHiWarning, avEntPhySensorLoWarning, entPhysicalParentRelPos}
	STATUS      current
	DESCRIPTION
	"1.6V (1600mv) power supply fault"
	::= { avEntTrapsV3separator 19 }

avEnt1600mvPwrFltOk NOTIFICATION-TYPE
	OBJECTS   { avEntPhysicalIndex, entPhysicalDescr, entPhySensorValue, avEntPhySensorHiWarningClear, avEntPhySensorLoWarningClear, entPhysicalParentRelPos}
	STATUS      current
	DESCRIPTION
	"1.6V (1600mv) power supply fault clear"
	::= { avEntTrapsV3separator 20 }

avEntAmbientHiTempFlt NOTIFICATION-TYPE
	OBJECTS   { avEntPhysicalIndex, entPhysicalDescr, entPhySensorValue, avEntPhySensorHiWarning, entPhysicalParentRelPos}
	STATUS      current
	DESCRIPTION
	"Ambient High Temprature fault"
	::= { avEntTrapsV3separator 22 }

avEntAmbientHiTempFltOk NOTIFICATION-TYPE
	OBJECTS   { avEntPhysicalIndex, entPhysicalDescr, entPhySensorValue, avEntPhySensorHiWarningClear, entPhysicalParentRelPos}
	STATUS      current
	DESCRIPTION
	"Ambient High Temprature clear"
	::= { avEntTrapsV3separator 23 }

avEntAmbientLoTempFlt NOTIFICATION-TYPE
	OBJECTS   { avEntPhysicalIndex, entPhysicalDescr, entPhySensorValue, avEntPhySensorLoWarning, entPhysicalParentRelPos}
	STATUS      current
	DESCRIPTION
	"Ambient Low Temprature fault"
	::= { avEntTrapsV3separator 24 }

avEntAmbientLoTempFltOk NOTIFICATION-TYPE
	OBJECTS   { avEntPhysicalIndex, entPhysicalDescr, entPhySensorValue, avEntPhySensorLoWarningClear, entPhysicalParentRelPos}
	STATUS      current
	DESCRIPTION
	"Ambient High Temprature clear"
	::= { avEntTrapsV3separator 25 }


avEntPhyUSBDevices OBJECT IDENTIFIER ::=  { avayaEntity 3 }
avEntPhyUSBDevicesTraps OBJECT IDENTIFIER ::= { avEntPhyUSBDevices 0 }

avEntPhyUSBDeviceRemovalOnBackupRestoreOperation 	NOTIFICATION-TYPE
	OBJECTS   {  avEntPhyProductId, avEntPhySeverity}
	STATUS      current
	DESCRIPTION
	"The notification is based on usb mass storage device removal during
	backup/restore operation to it. If other usb devices are removed during
	this operation then no harm/syslog.
	"
	::= { avEntPhyUSBDevicesTraps 1 }


avEntPhyUSBDeviceInsecureRemoval  	NOTIFICATION-TYPE
	OBJECTS   { avEntPhysicalIndex, entPhysicalDescr, avEntPhyUSBDeviceUSBSupportVersion,
	avEntPhyUSBDeviceSpeed, avEntPhyUSBDevicePower, avEntPhyProductId, avEntPhySeverity}
	STATUS      current
	DESCRIPTION
	"The notification is based on usb device insecurely removal.
	"
	::= { avEntPhyUSBDevicesTraps 2 }

avEntPhyUSBDevicePowerFailure   	NOTIFICATION-TYPE
	OBJECTS   { avEntPhysicalIndex, entPhysicalDescr, avEntPhyUSBDeviceUSBSupportVersion,
	avEntPhyUSBDeviceSpeed, avEntPhyUSBDevicePower, avEntPhyProductId, avEntPhySeverity}
	STATUS      current
	DESCRIPTION
	"The notification is based on usb device lack of power.
	For cases as:
	a. Connecting device which requires more power then gateway can supply.
	b. Connecting USB device to non power hub which has not enough power.
	C. Disconnecting power from the USB HUB and there is not enough power to drive
	   the usb devices.
	D. Disconnecting power from a usb device which requires external power.
	E. Disconnecting power from USB device and the gateway/USB Hub can not supply
	   power to it.
	"
	::= { avEntPhyUSBDevicesTraps 3 }

avEntPhyUSBDeviceNotSupported    	NOTIFICATION-TYPE
	OBJECTS   { avEntPhysicalIndex, entPhysicalDescr, avEntPhyUSBDeviceUSBSupportVersion,
	avEntPhyUSBDeviceSpeed, avEntPhyUSBDevicePower, avEntPhyProductId, avEntPhySeverity}
	STATUS      current
	DESCRIPTION
	"The notification is based on attaching non supported usb device to the gateway.
	The Gateways supports usb mass storage devices based on flash drives that their sub
	class is SCSI and their protocol is Bulk Only Transport.
	The Gateways supports usb modems that complies to sub class SFF-8020i, MMC-2 (ATAPI)
	and protocol Control/Bulk/Interrupt protocol (with no command completion Interrupt).
	"
	::= { avEntPhyUSBDevicesTraps 4 }

avEntPhyUSBDeviceExceedMaxNumber     	NOTIFICATION-TYPE
	OBJECTS   { avEntPhysicalIndex, entPhysicalDescr, avEntPhyUSBDeviceUSBSupportVersion,
	avEntPhyUSBDeviceSpeed, avEntPhyUSBDevicePower, avEntPhyProductId, avEntPhySeverity}
	STATUS      current
	DESCRIPTION
	"The notification is based on reaching the max number of usb devices
	connected to the gateway.

	G250/G350 allows only USB Modem with only one usb mass storage device at the same time.
	"
	::= { avEntPhyUSBDevicesTraps 5 }

avEntPhyUSBFileSystemNotSupported     	NOTIFICATION-TYPE
	OBJECTS   { avEntPhysicalIndex, entPhysicalDescr, avEntPhyUSBDeviceUSBSupportVersion,
	avEntPhyUSBDeviceSpeed, avEntPhyUSBDevicePower, avEntPhyProductId, avEntPhySeverity}
	STATUS      current
	DESCRIPTION
	"The notification is based on reaching connecting USB mass storage device with file
	system that is not supported.

	"
	::= { avEntPhyUSBDevicesTraps 6 }


avEntPhyUSBDevicesTable OBJECT-TYPE
    SYNTAX        SEQUENCE OF AvEntPhyUSBDevicesEntry
    MAX-ACCESS    not-accessible
    STATUS        current
    DESCRIPTION
            "This table extends entPhysicalTable with USB devices parameters."
    ::= { avEntPhyUSBDevices 1 }


avEntPhyUSBDevicesEntry OBJECT-TYPE
    SYNTAX        AvEntPhyUSBDevicesEntry
    MAX-ACCESS    not-accessible
    STATUS        current
    DESCRIPTION
            "This table includes extension to entPhysicalTable with usb devices
            parameters."
    INDEX  { entPhysicalIndex }
    ::= { avEntPhyUSBDevicesTable 1 }

AvEntPhyUSBDevicesEntry ::= SEQUENCE {
        avEntPhyUSBDeviceUSBSupportVersion
        DisplayString,
        avEntPhyUSBDeviceClassCode
        Integer32,
        avEntPhyUSBDeviceSubClassCode
        Integer32,
        avEntPhyUSBDeviceProtocol
        Integer32,
        avEntPhyUSBDeviceVendorId
        OCTET STRING,
        avEntPhyUSBDeviceSpeed
        DisplayString,
        avEntPhyUSBDevicePower
        DisplayString,
        avEntPhyUSBDeviceCurrent
        Integer32
        }

avEntPhyUSBDeviceUSBSupportVersion OBJECT-TYPE
            SYNTAX DisplayString (SIZE (0..64))
            MAX-ACCESS read-only
            STATUS current
            DESCRIPTION
                "The USB standard version. Possible values are:
                1.1 and 2.0."
            ::= { avEntPhyUSBDevicesEntry 1 }

avEntPhyUSBDeviceClassCode OBJECT-TYPE
            SYNTAX Integer32
            MAX-ACCESS read-only
            STATUS current
            DESCRIPTION
                "The usb device class code.

                Value   Hex Value   Descriptor
				1 		1 			Audio
				2 		2 			CDC-Control
				3 		3 			HID
				5 		5 			Physical
				6 		6 			Image (subclass & protocol must be 1)
				7 		7 			Printer
				8 		8 			Mass-Storage
				9 		9 			HUB
				10 		A 			CDC-Data
				11 		B 			Chip/Smart Card
				13 		D 			Content-Security
 				14 		E 			Video
				220 	DC 			Diagnostic Device (see below for details)
				224 	E0 			Wireless Controller (see below for details)
				254 	FE 			Application-Specific (see below for details)
 				255 	FF 			Vendor-Specific

 				The G250/G350 supports usb mass storage devices of class code of 0x8
 				and usb modem with class 0x2.
 				"
            ::= { avEntPhyUSBDevicesEntry 2 }

avEntPhyUSBDeviceSubClassCode OBJECT-TYPE
            SYNTAX Integer32
            MAX-ACCESS read-only
            STATUS current
            DESCRIPTION
                "The usb device subclass code.
                USB standard describe the following class codes:
                0x01 - RBC (Reduced Block Commands)
                0x02 - SFF-8020i, MMC-2 (ATAPI)
                0x03 - QIC-157
                0x04 - UFI
                0x05 - SFF-8070i
                0x06 - SCSI

                The G250/G350 supports 0x06 - SCSI for USB mass storage devices and
                0x2 - SFF-8020i, MMC-2 (ATAPI)  for USB modem.
				"
            ::= { avEntPhyUSBDevicesEntry 3 }

avEntPhyUSBDeviceProtocol OBJECT-TYPE
            SYNTAX Integer32
            MAX-ACCESS read-only
            STATUS current
            DESCRIPTION
                "The usb device protocol code.
                0x0 - Control/Bulk/Interrupt protocol (with command completion
                      Interrupt).
                0x1 - Control/Bulk/Interrupt protocol (with no command completion
                      Interrupt).
                0x50 - Bulk Only Transport.

                The G250/G350 supports 0x50 protocol for usb mass storage devices and
                0x1 for USB modem.
                "
            ::= { avEntPhyUSBDevicesEntry 4 }


avEntPhyUSBDeviceVendorId OBJECT-TYPE
            SYNTAX OCTET STRING
            MAX-ACCESS read-only
            STATUS current
            DESCRIPTION
                "The USB device vendor HEX-formatted string as it is provided to
                the USB host by the USB device"
            ::= { avEntPhyUSBDevicesEntry 5 }

avEntPhyUSBDeviceSpeed OBJECT-TYPE
            SYNTAX DisplayString (SIZE (0..64))
            MAX-ACCESS read-only
            STATUS current
            DESCRIPTION
                "The USB device speed.
                Possible values: 'Low', 'Full' and 'High'.
                G250/G350 supports 'Full' and 'High'"
            ::= { avEntPhyUSBDevicesEntry 6 }

avEntPhyUSBDevicePower OBJECT-TYPE
            SYNTAX DisplayString (SIZE (0..64))
            MAX-ACCESS read-only
            STATUS current
            DESCRIPTION
                "The USB device power.
                Possible values: 'Unknown', 'Self Powered' and 'Bus Powered'.
                "
            ::= { avEntPhyUSBDevicesEntry 7 }

avEntPhyUSBDeviceCurrent OBJECT-TYPE
            SYNTAX Integer32
            MAX-ACCESS read-only
            STATUS current
            DESCRIPTION
                "The USB current consumption in mA."
            ::= { avEntPhyUSBDevicesEntry 8 }



avEntPhyUSBMassStorageDevicesTable OBJECT-TYPE
    SYNTAX        SEQUENCE OF AvEntPhyUSBMassStorageDevicesEntry
    MAX-ACCESS    not-accessible
    STATUS        current
    DESCRIPTION
            "This table extends entPhysicalTable with USB mass storage devices parameters."
    ::= { avEntPhyUSBDevices 2 }


avEntPhyUSBMassStorageDevicesEntry OBJECT-TYPE
    SYNTAX        AvEntPhyUSBMassStorageDevicesEntry
    MAX-ACCESS    not-accessible
    STATUS        current
    DESCRIPTION
            "This table includes extension to entPhysicalTable with usb mass storage
            devices parameters."
    INDEX  { entPhysicalIndex }
    ::= { avEntPhyUSBMassStorageDevicesTable 1 }

AvEntPhyUSBMassStorageDevicesEntry ::= SEQUENCE {
        avEntPhyUSBMassStorageDeviceFileSystemName
        DisplayString,
        avEntPhyUSBMassStorageDeviceCapacity
        Integer32,
        avEntPhyUSBMassStorageDeviceFreeMemory
        Integer32,
        avEntPhyUSBMassStorageDeviceFs
        DisplayString
        }

avEntPhyUSBMassStorageDeviceFileSystemName OBJECT-TYPE
            SYNTAX DisplayString (SIZE (0..64))
            MAX-ACCESS read-only
            STATUS current
            DESCRIPTION
                "The usb mass storage device File system name.
                An exmaple for one usb mass storage device on the gateway is
                mapped to /usbdevice0/.
                "
            ::= { avEntPhyUSBMassStorageDevicesEntry 1 }


avEntPhyUSBMassStorageDeviceCapacity OBJECT-TYPE
            SYNTAX Integer32
            MAX-ACCESS read-only
            STATUS current
            DESCRIPTION
                "Capacity of USB Mass storage device in KBytes."
            ::= { avEntPhyUSBMassStorageDevicesEntry 2 }

avEntPhyUSBMassStorageDeviceFreeMemory OBJECT-TYPE
            SYNTAX Integer32
            MAX-ACCESS read-only
            STATUS current
            DESCRIPTION
                "Free memory of USB Mass storage device in KB.
				For R/O USB mass storage devices (as CDROM) this value returns 0.
				Note that this MIB item shall be updated according backup
				operations that may consume memory space.
				"
            ::= { avEntPhyUSBMassStorageDevicesEntry 3 }

avEntPhyUSBMassStorageDeviceFs OBJECT-TYPE
            SYNTAX DisplayString (SIZE (0..64))
            MAX-ACCESS read-only
            STATUS current
            DESCRIPTION
                "The file system supported by the USB device.
                Possible values: 'FAT16' and 'FAT32'."
            ::= { avEntPhyUSBMassStorageDevicesEntry 4 }


avEntPhyNotificationDefinitions OBJECT IDENTIFIER ::= { avayaEntity 4 }

avEntPhySeverity OBJECT-TYPE
        	SYNTAX   AvEntPhyItuPerceivedSeverity
        	MAX-ACCESS accessible-for-notify
        	STATUS current
        	DESCRIPTION
         	"The severity of the notification."
        	::= { avEntPhyNotificationDefinitions 1}

avEntPhyProductId OBJECT-TYPE
        	SYNTAX   DisplayString (SIZE (0..10))
        	MAX-ACCESS accessible-for-notify
        	STATUS current
        	DESCRIPTION
         	"The Product Id of Avaya Device - 10 characters."
        	::= { avEntPhyNotificationDefinitions 2}

avEntPhysicalIndex OBJECT-TYPE
        	SYNTAX   PhysicalIndex
        	MAX-ACCESS accessible-for-notify
        	STATUS current
        	DESCRIPTION
         	"The index for this entry."
        	::= { avEntPhyNotificationDefinitions 3}

avEntPhyChFru OBJECT IDENTIFIER ::= { avayaEntity 5 }
		avEntPhyChFruNotifications OBJECT IDENTIFIER ::= { avEntPhyChFru 0 }

		avEntPhyChFruRemoval NOTIFICATION-TYPE
			OBJECTS { avEntPhysicalIndex, entPhysicalDescr, avEntPhyProductId, avEntPhySeverity }
			STATUS current
			DESCRIPTION
				"FRU unit was removed from chassis"
			::= { avEntPhyChFruNotifications 1 }


		avEntPhyChFruInsertion NOTIFICATION-TYPE
			OBJECTS { avEntPhysicalIndex, entPhysicalDescr, avEntPhyProductId, avEntPhySeverity }
			STATUS current
			DESCRIPTION
				"FRU unit was inserted into chassis"
			::= { avEntPhyChFruNotifications 2 }


		avEntPhyChFruPsuFlt NOTIFICATION-TYPE
			OBJECTS { avEntPhysicalIndex, entPhysicalDescr, avEntPhyChFruOperStat, avEntPhyChFruFault, avEntPhyProductId, avEntPhySeverity }
			STATUS current
			DESCRIPTION
				"Power Supply unit failed"
			::= { avEntPhyChFruNotifications 3 }


		avEntPhyChFruPsuFltOk NOTIFICATION-TYPE
			OBJECTS { avEntPhysicalIndex, entPhysicalDescr, avEntPhyChFruOperStat, avEntPhyChFruFault, avEntPhyProductId, avEntPhySeverity }			STATUS current
			DESCRIPTION
				"Power Supply unit resumed operation "
			::= { avEntPhyChFruNotifications 4 }

		avEntPhyChFruExpansionTestFailure NOTIFICATION-TYPE
			OBJECTS { avEntPhysicalIndex, entPhysicalDescr, avEntPhyChFruOperStat, avEntPhyChFruFault, avEntPhyProductId, avEntPhySeverity }
			STATUS current
			DESCRIPTION
				"Cable Test Failure on Expansion module"
			::= { avEntPhyChFruNotifications 5 }


		avEntPhyChFruExpansionTestClear NOTIFICATION-TYPE
			OBJECTS { avEntPhysicalIndex, entPhysicalDescr, avEntPhyChFruOperStat, avEntPhyChFruFault, avEntPhyProductId, avEntPhySeverity }			STATUS current
			DESCRIPTION
				"Cable Test Passed OK on Expansion module"
			::= { avEntPhyChFruNotifications 6 }

		avEntPhyChFruTable OBJECT-TYPE
			SYNTAX SEQUENCE OF AvEntPhyChFruEntry
			MAX-ACCESS not-accessible
			STATUS current
			DESCRIPTION
				"Table depicting the status of chassis FRU units such as Power-Supplies and Fan-Tray"
			::= { avEntPhyChFru 1 }

		avEntPhyChFruEntry OBJECT-TYPE
			SYNTAX AvEntPhyChFruEntry
			MAX-ACCESS not-accessible
			STATUS current
			DESCRIPTION
				"Table entry depicting the status of chassis FRU units such as Power-Supplies and Fan-Tray"
			INDEX { entPhysicalIndex }
			::= { avEntPhyChFruTable 1 }

		AvEntPhyChFruEntry ::=
			SEQUENCE {
				avEntPhyChFruOperStat
					INTEGER,
				avEntPhyChFruFault
					INTEGER
			 }


		avEntPhyChFruOperStat OBJECT-TYPE
			SYNTAX INTEGER
				{
				ok(1),
				fault(2),
				notPresent(3),
				unknown(255)
				}
			MAX-ACCESS read-only
			STATUS current
			DESCRIPTION
				"Operational status of the chassis FRU unit."
			::= { avEntPhyChFruEntry 1 }


		avEntPhyChFruFault OBJECT-TYPE
			SYNTAX INTEGER
				{
				none(1),
				mulfunction(2),
				acFault(3),
				malfunctionAndAcFault(4),
				singleFanFault(5),
				multipleFanFault(6),
				badExpansionCable(7),
				unknown(255)
				}
			MAX-ACCESS read-only
			STATUS current
			DESCRIPTION
				"Description of fault, in case an FRU has failed"
			::= { avEntPhyChFruEntry 2 }


		avEntPhyChFruGroup OBJECT-GROUP
			OBJECTS { avEntPhyChFruOperStat, avEntPhyChFruFault}
			STATUS current
			DESCRIPTION
				"avEntPhyChFruGroup"
			::= { avEntPhyChFru 2 }

		avEntPhyChFruNotificationGroup NOTIFICATION-GROUP
			NOTIFICATIONS { avEntPhyChFruRemoval, avEntPhyChFruInsertion, avEntPhyChFruPsuFlt, avEntPhyChFruPsuFltOk }
			STATUS current
			DESCRIPTION
				"avEntPhyChFruNotificationGroup"
			::= { avEntPhyChFru 3 }

END
