--
-- XSWITCH-MIB.my
-- MIB generated by MG-SOFT Visual MIB Builder Version 3.0 Build 253
-- Monday, November 10, 2003 at 09:05:20
--

--  XSWITCH-MIB.my
-- MIB generated by MG-SOFT Visual MIB Builder Version 3.0 Build 253
-- Thursday, May 22, 2003 at 18:18:59
--
-- =========================================================
--
-- MIB: Xswitch                               AVAYA Inc.
--
-- Version: 10.10.19                         28 Jun 2005
--
-- SourceSafe Version Information:
-- $Revision: 1.4 $
-- Check in $Date: 2005/07/06 11:29:44 $
--
-- =========================================================
--
-- Copyright 1999, 2000, 2001, 2002, 2003 AVAYA inc.
-- All Rights Reserved.
--
-- Reproduction of this document is authorized on condition
-- that the foregoing copyright notice is included.
--
-- This AVAYA SNMP Management Information Base Specification
-- (Specification) embodies AVAYA confidential and
-- Proprietary intellectual property.  AVAYA retains all
-- Title and ownership in the Specification, including any revisions
--
-- It is AVAYA's intent to encourage the widespread use of this
-- Specification in connection with the management of AVAYA products.
-- AVAYA grants vendors, end-users, and other interested parties
-- a non-exclusive license to use this Specification in connection
-- with the management of AVAYA products.
--
-- This Specification is supplied "as is," and AVAYA makes
-- no warranty, either express or implied, as to the use,
-- operation, condition, or performance of the Specification.
--
-- =========================================================
--
-- RCS
-- Version 10.10.19
-- 28 June 2005
-- Updating scGenSwitchDot1xPortMaxSuppNum range to 1..8 instead of 1..256.
--
-- Version 10.10.18
-- 16 June 2005
-- 1. scGenGroupDot1xPortMaxSuppNum will be INTEGER without limitiation for specific
-- range. The infinite value (0) is cancelled.
-- 2. Updating LLDP and 802.1x table (scGenGroupDot1xLldpTable) description.
-- 3. Moving scGenGroupDot1xPortMaxSuppNum to scGenSwitchDot1xPortMaxSuppNum. I.e. this parameter
--    can be configured on system level and not per module.
-- 4. Exchanging scGenGroupDot1xLldpTable to scGenSwitchDot1xLldpTxVlanName. The LLDP will be
--    configured on system level and not per module. The new MIB item is OCTET STRING instead of
--    table.
-- 5. Replacing scGenSwitchDot1xLldpTxVlanName to be INTEGER (Enable/Disable) instead
--    of OCTET STRING (One bit per Vlan).
-- 6. Updating scPowerEthPortConsumptionPower to be in mW units.
--
-- Version 10.10.17
-- 10 May 2005
-- 1. Renaming scGenPortDot1xPortSuppNum to scGenPortDot1xPortMaxSuppNum.
-- 2. Renaming 802.1x statistics MIBs names to Num instead of TotalNum.
-- 3. Renaming scGenGroupDot1xSystemNumSupplicant to scGenGroupDot1xSystemMaxNumSupplicant.
-- 4. Replacing PhysAddress used by scGenPortSecureMAC and scGenPortDot1xMAC to MacAddress.
-- 5. scGenPortDot1xPortMaxSuppNum supports value 0..256, where 0 is infinite.
-- 6. Fixing scGenGroupPlugInType to have values with "-" and not "_".
-- 7. scGenPortDot1xPortMaxSuppNum was moved to scGenGroupDot1xPortMaxSuppNum. I.e. user will
--    be able to configure this parameter as system level and not per port.
-- 8. Add Sourcesafe information to the header.
-- 9. Add scPowerEthPortTable - This MIB table is extension for the Standard PoE MIB.
--    This MIB table will show additional information per Group/Port.
-- 10. Using scGenPortDot1xMACGroupID, scGenPortDot1xMACPortId and scGenPortDot1xMAC as R/O instead
--     of not-accessible.
-- 11. Fixing scGenGroupBUPSAllocatedPower to be R/W with range of (100..900) and default 800.
-- 12. Changing x330w-2ds1_isdn(36) and x330w-2usp_isdn(37) to be x330w-2ds1-isdn(36) and
--  	x330w-2usp-isdn(37) respectively.
-- 13. Moving scGenPortDot1xLldpTxVlanName (Previously scGenPortDot1xPortTxVlanName) to
--   	scGenGroupDot1xLldpTable. Thus allowing configuration per system/vlan whether to send the
--		vlan-name by LLDP application after authentication of supplicants on the port.

-- Shlomi Biton
--
-- Version 10.10.16
-- 23 March 2005
-- Adding 802.1x multi-supplicant MIB extension.
-- a. scGenGroupDot1xTable - This table include additional information for the
--    extension of 802.1x multi-supplicant mode.
-- b. scGenPortDot1xMACTable - Table of 802.1x multi-supplicant MACs connected
--    to a single SC based port.
-- c. scGenPortdot1xPortTable - Table of 802.1x multi-supplicant configuration
--    and status of a single SC based port.
-- Shlomi Biton
--
-- Version 10.10.15
-- 19 June 2003
-- Added scPowerEthGroupInlineSWversion and scGenGroupBUPSAllocatedPower
-- Meir Deutsch
--
-- Version 10.10.14
-- 22 May 2003
-- Added value avayaX360STK(3) to attribute scGenGroupCascadingType.
-- Igor Umansky
--
-- Version 10.10.13
-- 5 March 2003
-- The scPriorityQueuing MIBs sub-group that controls the
-- queueng mode of operation of the which ports was added
-- Pesah Spector
--
-- Version 10.10.12
-- 3 Oct 2002
-- scGenSwitchMacAging item added
-- Dan Gluskin
--
-- Version 10.10.11
-- 19 June 2002
-- 1. Add bits to scGenPortCapability bits mask for CopyPort destination port (16), CopyPort Destination drop events (21),
--   CopyPort Errored frames (22), CopyPort unaltered frames (23) and CopyPort all good frames (24).
-- 		 Ehud Hamami
--
-- Version 10.10.10
-- 2 June 2002
-- 1. Changed scGenGroupPlugInType range 34 till 46 for current, planned and future wan expansions,
-- and to avoid conflict with hw registers inside P330.
-- 		 Michael W.
--
-- Version 10.10.9
-- 30 April 2002
-- 1. Changed scGenGroupPlugInType range 34 till 50 for current, planned and future wan expansions
-- 		 Igor Umansky.
--
-- Version 10.10.8
-- 31 March 2002
-- 1. add scGenGroupPlugInType range 36 till 50 for current, planned and future wan expansions
-- 		 Michael W.
--
-- Version 10.10.7
-- 26 December 2001
-- 1. add scGenPluginType for X330W-2DS1 - Michael W.
--
-- Version 10.10.6
-- 06 August 2001
-- 1. Add scGenSwitchWelcomeMessage & scGenSwitchPromptMessage
--    MIBs to scGenSwitch table  - Moshe A.
--
-- Version 10.10.5
-- 17 July 2001
-- 1. Remove scPowerEthPort table - Moshe A.
-- 2. Remove scPowerEthGroupPseBackupPSPower item from scPowerEthGroup- Moshe A.
--
--
-- Version 10.10.4
-- 15 July 2001                - Moshe A.
-- 1. Changed the scGenPortCopyClass to scGenPortCopyClassModuleLevel
-- 2. Add scGenPortCopyClassStackLevel  	- Moshe A.
-- 3. Change the Power over Ethernet mib items to be in different tables.
-- 4. Add Cajun as prefix to PlugInType and CascadingType
--
--
-- Version 10.10.3			- Moshe A., Michael W.
-- 09 July 2001
-- 1. Removed 'cajun' prefix from product names
-- 2. Changed the SSM plugin type to be X330W-4E1
-- 3. Added P333T-PWR private mibs: scGenGroupPsePSPowerFaultErrMsg, scGenGroupPseBackupPSPower,
-- scGenGroupPseDetectionProcess, scGenPortPowerDenyErrMsg, scGenPortPowerFaultErrMsg
--
-- Version 10.10.2
-- 03 July 2001
-- 1. Add scGenPortCopyClass		- Moshe A.
--
-- Version 10.10.1
-- 06 Jun. 2001
-- 1. Add scGenGroupDynamicVlans     -  Moshe A. & Michael W.
--
-- Version 10.10.0
-- 19 Feb. 2001
-- 1. Add new mib item scGenSwitchCAMClear to scGenSwitch table - Moshe A.
--
-- Version 10.9.0
-- 25 Oct. 2000
-- 1. Add for MultiVLAN, new mib item scGenGroupVlanCurrentEgressPorts,
--     scGenGroupVlanCurrentUntaggedPorts, scGenGroupVlanStaticEgressPorts
--     and scGenGroupVlanStaticUntaggedPorts to scGenGroupVLAN table - Ygdal N.
--
-- Version 10.8.0
-- 27 June 2000
-- 1. Change name of cajunX330ASTK(2) in scGenGroupCascadingType - Ran I.
-- 2. Add new mib items scGenPortSLDAdminStatus & scGenPortSLDStatus to scGenPort table - Moshe I.
-- 3. Add new mib item scGenGroupSLDAdminStatus to scGenGroup table - Moshe I.
--
-- Version 10.7.3
-- 18 June 2000
-- 1. Add new enum to scGenGroupInternalBuffering - Moshe I.
-- 2. Add new mib items scGenPortLagCapability & scGenPortCapability to scGenPort table - Ran I.
--
-- Version 10.7.2
-- 31 May 2000
-- 1. Add new mib scGenPortLastIntruderSourceAddr  to scGenPort table - Ygdal N.
-- 2. Add new mib scGenSwitchGigaMode to scGenSwitch table for the P130 - Ygdal N.
--
-- Version 10.7.1
-- 16 May 2000
-- 1. Add new type cajunX330ASTK to scGenGroupCascadingType - Ran I.
--
-- Version 10.7.0
-- 14 Apr. 2000
-- 1. Add new mib scGenPortSecurityMode and scGenPortSTA to scGenPort table - Ygdal N.
-- 2. Add new mib scGenGroupSecurityMode to scGenGroup table - Ygdal N.
-- 3. Change description of scGenSwitchSecurityMode - Ygdal N.
-- 4. Add new mib scGenSwitchFastAgingOnRemoteTopChg to scGenSwitch table - Ygdal N.
-- 5. Add new values cajunX130F2(31), cajunX130G2(32), cajunX130GT2(33) to genPortType - Yaron N.
-- 6. Add new values userPriority1(3), userPriority2(4), userPriority3(5), userPriority4(6),
--     userPriority5(7), userPriority6(8), userPriority7(9), userPriority8(10) to genPortPriority - Yaron N.
-- 7. Add new item to scGenGroupTable - Yaron N.
--     scGenGroupBroadcastStormControl, scGenGroupBroadcastThreshold
--     scGenGroupPriorityQueuesScheduling, scGenGroupBoundedDelay
--
-- Version 10.6.2
-- 28 March 2000
-- 1. Add new value cajunX330SSM(27), to scGenGroupPlugInType - Gidi N.
--
-- Version 10.6.1
-- 23 Mar. 2000
-- 1. Add new enum a155 and a622 to scEthPortSpeed - Yaron N.
--
-- Version 10.6.0
-- 1 Mar. 2000
-- 1. New table was added for RSP application scGenPortIPAddressRsp - Lior S.
-- 2. Add new item scGenGroupRspMode to scGenGroupRsp table - Lior S.
-- 3. Add new enumeration rspError to scEthPortFunctionalStatus - Lior S.
--
-- Version 10.5.0
-- 25 Feb. 2000
-- 1. Two tables were added for RSP application scGenGroupRsp and scGenPortRsp - Lior S.
--
-- Version 10.4.1
-- 20 Feb. 2000
-- 1. Change the name of scGenSwitchSecurityModeVal to scGenSwitchSecurityModePermit - Rafi H.
--
-- Version 10.4.0
-- 14 Feb. 2000
-- 1. Add new mib scGenSwitchLACPMode to switch table for LACP - Ygdal N.
-- 2. Add new mib scGenPortLACPMode to port table for LACP - Ygdal N.
-- 3. Add new mib scGenGroupLACPMode to group table for LACP - Ygdal N.
-- 4. Add new mib scGenSwitchSecurityModeVal to switch table, for security - Rafi H.
--
-- Version 10.3.0
-- 1 Feb. 2000
-- 1. Add new mibs to support multicast filtering in scGenSwitch table - Lior S/Ygdal N.
-- 2. Add new mibs to support multicast filtering in scGenGroup table - Lior S/Ygdal N.
--
-- Version 10.2.0
-- 20 Jan. 2000
-- 1. Add new mib scGenGroupInternalBuffering  - Moshe I.
--
-- Version 10.1.1
-- 29 Nov. 1999
-- 1. Add new value cajunX330G2(26), to scGenGroupPlugInType - Ygdal N.
--
-- Version 10.1.0
-- 29 Nov. 1999
-- 1. Add new mib items for lags and general trap enable/disable - Yigdal N.
-- scGenPortSecId, scGenPortMaxLagsOnSec and scGenPortGenericTrap
-- 2. Add new value layer2Only(3) to scGenGroupSetDefaults item - Yigal N.
--
-- Version 10.0.3
-- 29 Sep. 1999
-- 1. Add new plug in type scGenGroupPlugInType - Ygdal N.
--     cajunX330GT4(24) and cajunX330GT2(25).
--
-- Version 10.0.2
-- 9 Sep. 1999
-- 1. Add new plug in type scGenGroupPlugInType - Ran I.
--     cajunX120G2 (9), cajunX120GT2(10)
-- 2. Add 2 mib items to scGenPort table - Yaron N.
--    scGenPortVLANEgressStaticConfiguration & scGenPortStaticVLANBinding
--
-- Version 10.0.1
-- 26 July 1999
-- 1. Change of the enumeration of scGenGroupBUPSType - Ygdal N.
-- 2. Add new plug in types to scGenGroupPlugInType - Ygdal N.
--
-- Version 10.0.0
-- 10 June 1999
-- 1. Add scGenPortSendBridgedPackets new item to scGenPort table - Ygdal N.
-- 2. Add notSupported enum to scEthPortFlowControl item - Yaron N.
--
-- Version 9.9.0
-- 13 May 1999
-- 1. Add the following items to scGenGroup table - Yigdal N.
--     scGenGroupBUPSType, scGenGroupBUPSCS,
--     scGenGroupBUPSFansStatus and scGenGroupFansStatus
--
-- Version 9.8.0
-- 12 Apr. 1999
-- 1. Add scGenGroupSupportDstCopyPortList mib item to scGenGroup table - Rafi H.
--
-- Version 9.7.0
-- 22 Mar. 1999
-- 1. Add new type (11-23 and 254) to scGenGroupPlugInType - Ygdal N.
-- 2. Add new items scGenGroupCascadingType, scGenGroupCascadingDescr
--     and scGenGroupCascadingCS to scGenGroup - Ygdal N.
-- 3. Add new items scEthPortFlowControl to scEthPort table - Ygdal N.
--
-- Version 9.6.0
-- 3 Feb. 1999
-- 1. Change the ACCESS of scGenSwitchDefaultVLAN mib back to read-only - Rafi H.
-- 2. Change the enumeration of scGenGroupPlugInType - Ygdal N.
-- 3. Add to scGenSwitch table scGenSwitchVIDPNonSupportedModules,
--     scGenSwitchSTANonSupportedModules, scGenSwitchIDSNonSupportedModules -Yaron N.
--
-- Version 9.5.1
-- 2 Feb. 1999
-- 1. Change the ACCESS of scGenSwitchDefaultVLAN mib to read-write - Rafi H.
-- 2. Change the ACCESS of scGenGroupDefaultVLAN mib to read-only - Rafi H.
-- 3. Change the range of scGenPortVLAN and scGenSwitchAgVLAN to (0..4095) - Yaron N.
--
-- Version 9.5
-- 7 Jan. 1999
-- 1. Add new table scGenLinkAggregation - Yaron N.
-- 2. Add new item scGenPortLinkAggregationNumber to port table - Yaron N.
--
-- Version 9.4.1
-- 13 Dec. 1998
-- 1. Change the range of scGenSwitchAgVLAN from 1...255 to 1...3583 - Ygdal N.
-- 2. Add two new mibs scEthPortMulticastPktsSent & scEthPortUndersizePktsRec
--     to scEthPort table. - Ygdal N.
-- 3. Change the name of scGenSwitchLeakyVLAN to scGenSwitchVLANBridging - Yaron N.
-- 4. Remove scGenSwitchSWRedundnacy (new define in config.mib file) - Yaron N.
-- 5. Add mib scGenSwitchOldVersionModules to scGenSwitch - Yaron N.
--
-- Version 9.4.0
-- 24 Nov. 1998
-- 1. Add new mib item scGenGroupPlugInType, scGenGroupPlugInDescr and
--    scGenGroupPlugInCS to scGenGroup table  - Ygdal N.
-- 2. Add new enumeration for scEthPortMode and change its description - Ygdal N.
-- 3. Add new mib scEthPortPauseCapabilities to scEthPort table. - Ygdal N.
-- 4. Add four counters to scEthPort table - Ygdal N.
-- 5. Add new mib scGenGroupDefaultVLAN to scGenGroup - Yaron N.
-- 6. Add new mibs to scGenSwitch to support default VLAN, leaky VLAN & Redu -Yaron N.
--
-- Version 9.3.0
-- 23 Sep. 1998
-- 1. Add new mib item scGenSwitchSWRdChange to scGenSwitchTable - Zion S.
-- 2. Change description of scGenSwitchFindResult - Rafi H.
--
-- Version 9.2.0
-- 20 July 1998
-- 1. Add new items to scGenSwitch table scGenSwitchFindQuery  and scGenSwitchFindResult - Rafi
--
-- Version 9.1.0
-- 03 July 1998
-- 1. Add new mib item for security scGenSwitchSecurityMode - Zion S.
--
-- Version 9.0.1
-- 21 June 1998
-- 1. Remove scEthPortStandardFlowControl  from scEthPort table.
--     All followed OID's in the table are shifted down by one  - Yaron N.
--
-- Version 9.0.0
-- 04 June 1998
-- 1. Add new enumaration, gigabitEthernet to scEthPortSpeed - Yaron N.
-- 2. Add new mibs item of giga module to scEthPort table. The mibs are:
--     scEthPortStandardFlowControl, scEthPortGigaPauseStatus
--     scEthPortLower32OctetsRec, scEthPortUpper32OctetsRec
--     scEthPortLower32OctetsSent, scEthPortUpper32OctetsSent - Yaron N.
-- 3. Add new mib scGenSwitchSTA to scGenSwitch table for speningTree - Benny R.
--
-- Version 8.9.0
-- 19 May 1998
-- 1. Add new mib scGenSwitchVLANList - Rafi H.
--
-- Version 8.8.0
-- 13 Apr. 1998
-- 1. Add new mib scGenMonSwitches - Rafi H.
-- 2. Update description of scGenMonSmonCapability - Shira Z.
--
-- Version 8.7.0
-- 16 Feb. 1998
-- 1. Add two tables under scGenGroup sub-tree for SMON application the tables are:
--     scGenGroupSmonTable and scGenGroupVLANTable - Rafi H.
-- 2. Add four mib item to scGenMon table, the items are:
--     scGenMonSwitchVLANList, scGenMonMIBCtrList
--     scGenMonTimeStamp and scGenMonVlanTimeStamp - Rafi H.
-- 3. Add mib scEthPortDropEvents to scEthPort table for SMON application - Rafi H.
--
-- Version 8.6.1
-- 13 Jan. 1998
-- 1. Change description of scGenSwitchCopyDestination and scGenSwitchCopySource
--
-- Version 8.6.0
-- 28 Dec. 1997
-- 1. Add new item scGenGroupUpLinkType for scGenGroup table - Gidi N.
--
-- Version 8.5.8
-- 9 Oct. 1997
-- 1. Delete scGenMonAuthorization sub-tree. It includes scGenMonAuthKey and
--     scGenMonSmonSupport mib items. - Rafi H.
-- 2. Update scGenMonMIBCtrMode values and scGenMonSmonCapability values - Rafi H.
--
-- Version 8.5.7
-- 30 Sep. 1997
-- 1. Add new mibs scEthPortTotalOctets,
--    scEthPortTotalPkts,
--    scGenMonVLANStatsUcastPkts,
--    scGenMonVLANStatsMcastPkts,
--    scGenMonVLANStatsBcastPkts
--   for SMON application - Rafi H.
--
-- Version 8.5.6
-- 23 Sep. 1997
-- 1. Add new mib scGenGroupSupportSegCountersList for SMON application (segment
--    statistics)- Rafi H.
--
-- Version 8.5.5
-- 22 Sep. 1997
-- 1. Add new mib scGenMonMIBCtrMode for SMON application (segment statistics)- Rafi H.
--
-- Version 8.5.4
-- 17 Sep. 1997
-- 1. Change description and size of scGenMonSmonCapability to include more application.
--
-- Version 8.5.3
-- 4 Sep. 1997
-- 1. Add new mib item scGenMonSmonCapability to scGenMonTable, for SMON application.
--
-- Version 8.5.2
-- 1 Sep. 1997
-- 1. Add mib items scGenGroupSupportPortCountersList and
--    scGenGroupSupportCopyPortList to scGenGroup table for smon application - Ronen B.
--
-- Version 8.5.1
-- 24 August 1997
-- 1. Delete mib item scEthPortAutoPolarityEnable from scEthPortTable - Zion S.
--
-- Version 8.5
-- Revision A. -  1. Add 5 items to scGen table. The items are:
-- 10-Apr-1997      scGenGroupXswitchConnection
-- 	   scGenGroupStatus
-- 	   scGenGroupSwitchType
-- 	   scGenGroupNumberOfLoads
-- 	   scGenGroupSetDefaults
--                       2. Add 4 items to scSwitch table. The items are:
-- 	   scGenSwitchType
-- 	   scGenSwitchMasterId
-- 	   scGenSwitchReset
-- 	   scGenSwitchNumberOfLoads
--
-- Revision B. -	1. See Revision B. of 8.1 (8.1 is updated when 8.5 already exist).
-- 4-May-1997
--
-- Revision C. -	1. Add new items to scGenSwitch table. The items is: scGenSwitchAgVLAN
-- 15-June-1997	2. Update description of mib item scGenGroupXswitchConnection.
--
-- Revision D. -	1. Add new table scEthGroup table.
-- 21-July-1997	   move the scGenGroupAutoPartitionEnable from scGenGroup table to
-- 	   scEthGroup table.
-- 	   The name of the item changed to scEthGroupAutoPartitionSupport.
-- 	   The order of the items in scGenGroup table was changed. - Yigal N.
-- 	NOTE: See 8.1 revision C
-- 	2. Add new mib item scEthGroupFefiEnable to scEthGroup table. - Zion S.
--
--
-- Version 8.1
-- Revision A. -  1. Add new mib item scGenPorSetDefaults and scGenPortBackbone(VIDP) to
-- 10-Apr.-1997     scGenPortTable - Zion S/Yaron N.
--                       2. The status of scGenMonAuthorization table changed to deprecated -
-- 	   Yaron D.
--                       3. Add new mib item scGenSwitchVIDP to scGenSwitch table.
--
-- Revision B. -   1. Add new mib item scGenGroupAutoPartitionEnable and
-- 4-May-1997        scGenGroupCopyPortSupport to scGenGroupTable - Zion S/Yaron N.
--                        2. Add new item scEthPortAutoPolarityEnable to scEthPort Table - Zion S.
--                        3. Add new items scGenPortCopyMode and scGenPortCopyDestination to
--                            scGenPort Table.
--
-- Version 8.0.1
-- Revision A. -   1. Add new value inProgress(4) to the enumaration of
-- 13-Feb.-1997      scEthPortAutoNegotiationStatus parameter.
--
-- Version 8.0
-- Revision A. -   1. Change file name and file header.
-- 15-Nov-1996   2. Change description of scGenSwitchSetDefaults item.
--
-- =========================================================

	XSWITCH-MIB DEFINITIONS ::= BEGIN

		IMPORTS
			lannet
				FROM GEN-MIB
			OBJECT-TYPE
				FROM RFC-1212
			TimeTicks, IpAddress, Counter, NetworkAddress
				FROM RFC1155-SMI
			DisplayString
				FROM RFC1213-MIB
			PaeControlledPortStatus
				FROM  IEEE8021-PAE-MIB
			MacAddress,  TruthValue
				FROM SNMPv2-TC   ;




--
-- Type definitions
--

--  Type definitions
--
-- Type definitions
--
-- Type definitions
--
-- Type definitions
--
		RowStatus ::= INTEGER
			{
			active(1),
			notInService(2),
			notReady(3),
			createAndGo(4),
			createAndWait(5),
			destroy(6)
			}


--
-- Node definitions
--

--  Node definitions
--
-- Node definitions
--
-- Node definitions
--
-- Node definitions
--
		switchChip OBJECT IDENTIFIER ::= { lannet 28 }

--      Switch Chip group
-- Implementation of this group is mandatory for all devices
-- based on the switchChips.
-- mandatory for all sc devices.
		scGen OBJECT IDENTIFIER ::= { switchChip 1 }

		scGenChassis OBJECT IDENTIFIER ::= { scGen 1 }

--      information about the Chassis of SC based devices."
		scGenChMainAgPosition OBJECT-TYPE
			SYNTAX INTEGER (0..4)
			ACCESS read-only
			STATUS mandatory
			DESCRIPTION
				"This attribute defines the position in the chassis where the Main Agent resides."
			::= { scGenChassis 1 }

		scGenChRedunAgPosition OBJECT-TYPE
			SYNTAX INTEGER (0..4)
			ACCESS read-only
			STATUS mandatory
			DESCRIPTION
				"This attribute defines the position in the chassis where the Redundant Agent resides.
				0 means Redundant Agent not present."
			::= { scGenChassis 2 }

		scGenChRedunAgActivityStatus OBJECT-TYPE
			SYNTAX INTEGER
				{
				notPresent(1),
				dormant(2),
				active(3),
				notSupported(255)
				}
			ACCESS read-only
			STATUS mandatory
			DESCRIPTION
				"This attribute defines the status of the Redundant Agent.
				notPresent(1) - indicates that no redundant Agent exists.
				dormant(2) - indicates that the redundant Agent is ok and
				may at any moment become the Agent of the system.
				active(3) - indicates that the redundant Agent is acting as the Agent."
			::= { scGenChassis 3 }

		scGenChAgVLAN OBJECT-TYPE
			SYNTAX INTEGER (0..255)
			ACCESS read-write
			STATUS mandatory
			DESCRIPTION
				" The Virtual LAN number of the Agent's internal interface.
				The value 0 means Generic ( But can communicate with Global !).
				The values '255' mean Global."
			DEFVAL { 255 }
			::= { scGenChassis 4 }

		scGenMon OBJECT IDENTIFIER ::= { scGen 2 }

		scGenMonTable OBJECT-TYPE
			SYNTAX SEQUENCE OF ScGenMonEntry
			ACCESS not-accessible
			STATUS mandatory
			DESCRIPTION
				" Table of attributes which define Monitoring information about
				a single XSwitch in SC based devices."
			::= { scGenMon 1 }

		scGenMonEntry OBJECT-TYPE
			SYNTAX ScGenMonEntry
			ACCESS not-accessible
			STATUS mandatory
			DESCRIPTION
				"An entry in the table, containing data about a single XSwitch."
			INDEX { scGenMonSwitchId }
			::= { scGenMonTable 1 }

		ScGenMonEntry ::=
			SEQUENCE {
				scGenMonSwitchId
					INTEGER,
				scGenMonDropEvents
					Counter,
				scGenMonOctets
					Counter,
				scGenMonPkts
					Counter,
				scGenMonGoodBroadcastPkts
					Counter,
				scGenMonGoodMulticastPkts
					Counter,
				scGenMonGoodPkts
					Counter,
				scGenMonBadPkts
					Counter,
				scGenMonGoodOctets
					Counter,
				scGenMonBadOctets
					Counter,
				scGenMonSmonCapability
					OCTET STRING,
				scGenMonMIBCtrMode
					INTEGER,
				scGenMonSwitchVLANList
					OCTET STRING,
				scGenMonMIBCtrList
					OCTET STRING,
				scGenMonTimeStamp
					TimeTicks,
				scGenMonVlanTimeStamp
					TimeTicks
			 }

		scGenMonSwitchId OBJECT-TYPE
			SYNTAX INTEGER (1..255)
			ACCESS read-only
			STATUS mandatory
			DESCRIPTION
				" Index which identifies the XSwitch for which this entry contains information.
				This value is never greater than chNumberOfXSwitches. "
			::= { scGenMonEntry 1 }

		scGenMonDropEvents OBJECT-TYPE
			SYNTAX Counter
			ACCESS read-only
			STATUS mandatory
			DESCRIPTION
				"The total number of events in which the probe could not
				count packets due to lack of resources. This number is not
				necessarily the number of packets dropped; it is just the number
				of times this condition has been detected."
			::= { scGenMonEntry 2 }

		scGenMonOctets OBJECT-TYPE
			SYNTAX Counter
			ACCESS read-only
			STATUS mandatory
			DESCRIPTION
				"The total number of good octets switched and error octets filtered by this XSwitch."
			::= { scGenMonEntry 3 }

		scGenMonPkts OBJECT-TYPE
			SYNTAX Counter
			ACCESS read-only
			STATUS mandatory
			DESCRIPTION
				"The total number of good packets switched and error
				packets filtered by this XSwitch."
			::= { scGenMonEntry 4 }

		scGenMonGoodBroadcastPkts OBJECT-TYPE
			SYNTAX Counter
			ACCESS read-only
			STATUS mandatory
			DESCRIPTION
				"The total number of good packets switched by this
				XSwitch that were directed to the broadcast address."
			::= { scGenMonEntry 5 }

		scGenMonGoodMulticastPkts OBJECT-TYPE
			SYNTAX Counter
			ACCESS read-only
			STATUS mandatory
			DESCRIPTION
				"The total number of good packets switched by this XSwitch that were
				directed to the multicast address.
				Note that this number does not include packets directed to the broadcast address."
			::= { scGenMonEntry 6 }

		scGenMonGoodPkts OBJECT-TYPE
			SYNTAX Counter
			ACCESS read-only
			STATUS mandatory
			DESCRIPTION
				"The total number of good packets switched by this XSwitch."
			::= { scGenMonEntry 7 }

		scGenMonBadPkts OBJECT-TYPE
			SYNTAX Counter
			ACCESS read-only
			STATUS mandatory
			DESCRIPTION
				"The total number of bad packets filtered by this XSwitch."
			::= { scGenMonEntry 8 }

		scGenMonGoodOctets OBJECT-TYPE
			SYNTAX Counter
			ACCESS read-only
			STATUS mandatory
			DESCRIPTION
				"The total number of good octets switched by this XSwitch."
			::= { scGenMonEntry 9 }

		scGenMonBadOctets OBJECT-TYPE
			SYNTAX Counter
			ACCESS read-only
			STATUS mandatory
			DESCRIPTION
				"The total number of bad octets filtered by this XSwitch."
			::= { scGenMonEntry 10 }

		scGenMonSmonCapability OBJECT-TYPE
			SYNTAX OCTET STRING (SIZE (4))
			ACCESS read-only
			STATUS mandatory
			DESCRIPTION
				"This item is used to define which smon's application are implemented in the agent.
				When the console first performs smon application it should read this item in order
				to know which of the smon's applications are available in this agent's version.
				When there is a value of 0 (zero) in the relevant bit it means that the assosiated
				application is not supported, When there is a value of 1 (one) in the relevant bit it
				means that the assosiated application is supported.
				D0   - Statistics.
				D1   - History.
				D2   - Alarms.
				D3   - Host.
				D4   - HostTopN.
				D5   - Metrix.
				D6   - Filter.
				D7   - Capture.
				D8   - Event.
				D9   - TokenRing.
				D10  - ProtocolDir.
				D11 - ProtocolDist.
				D12 - AddressMap.
				D13 - NlHost.
				D14 - NlMatrix.
				D15 - AlHost.
				D16 - AlMatrix.
				D17 - UsrHistory.
				D18 - ProbConfig.
				D19 - Port.
				D20 - PortTopN.
				D21 - Subnet.
				D22 - SubnetMatrix.
				D23 - Vlan.
				D24 - VlanMatrix.
				D25 - nlHostTopN
				D26 - portHistory
				"
			::= { scGenMonEntry 11 }

		scGenMonMIBCtrMode OBJECT-TYPE
			SYNTAX INTEGER
				{
				enable(1),
				disable(2),
				notSupported(255)
				}
			ACCESS read-write
			STATUS mandatory
			DESCRIPTION
				" This object defines for switch ports to include/exclude local segment traffic
				in their port counters"
			DEFVAL { disable }
			::= { scGenMonEntry 12 }

		scGenMonSwitchVLANList OBJECT-TYPE
			SYNTAX OCTET STRING (SIZE (32))
			ACCESS read-only
			STATUS mandatory
			DESCRIPTION
				"A bitmap defining the status of the virtual LANs in the
				Virtual LAN Table. The first bit is for Virtual LAN 0, the
				second for Virtual LAN 1, and so on. If the Virtual LAN
				exists in the hub the value of the associated bit is 1,
				otherwise 0."
			::= { scGenMonEntry 13 }

		scGenMonMIBCtrList OBJECT-TYPE
			SYNTAX OCTET STRING (SIZE (2))
			ACCESS read-only
			STATUS mandatory
			DESCRIPTION
				"A bitmap defining the status of the MIBCtrMode for
				every group in the switch. The MSB (Most significant bit)
				representing the status of group #1. If MIBCtrMode on a
				group is enable(1) the bit is set to 1, otherwise 0."
			::= { scGenMonEntry 14 }

		scGenMonTimeStamp OBJECT-TYPE
			SYNTAX TimeTicks
			ACCESS read-only
			STATUS mandatory
			DESCRIPTION
				"This attribute contains the value of sysUpTime
				at the time switch counters were calculated."
			::= { scGenMonEntry 15 }

		scGenMonVlanTimeStamp OBJECT-TYPE
			SYNTAX TimeTicks
			ACCESS read-only
			STATUS mandatory
			DESCRIPTION
				"This attribute contains the value of sysUpTime
				at the time VLAN counters were calculated."
			::= { scGenMonEntry 16 }

		scGenMonPriorityTable OBJECT-TYPE
			SYNTAX SEQUENCE OF ScGenMonPriorityEntry
			ACCESS not-accessible
			STATUS mandatory
			DESCRIPTION
				"A list of priority count entries."
			::= { scGenMon 2 }

		scGenMonPriorityEntry OBJECT-TYPE
			SYNTAX ScGenMonPriorityEntry
			ACCESS not-accessible
			STATUS mandatory
			DESCRIPTION
				"A list of statistics related to a specific priority level on
				a single XSwitch in SC based devices."
			INDEX { scGenMonPrioritySwitchId, scGenMonPriorityId }
			::= { scGenMonPriorityTable 1 }

		ScGenMonPriorityEntry ::=
			SEQUENCE {
				scGenMonPrioritySwitchId
					INTEGER,
				scGenMonPriorityId
					INTEGER,
				scGenMonPriorityGoodPkts
					Counter,
				scGenMonPriorityGoodOctets
					Counter
			 }

		scGenMonPrioritySwitchId OBJECT-TYPE
			SYNTAX INTEGER (1..255)
			ACCESS read-only
			STATUS mandatory
			DESCRIPTION
				" Index which identifies the XSwitch for which this entry contains information.
				This value is never greater than chNumberOfXSwitches."
			::= { scGenMonPriorityEntry 1 }

		scGenMonPriorityId OBJECT-TYPE
			SYNTAX INTEGER (1..2)
			ACCESS read-only
			STATUS mandatory
			DESCRIPTION
				"The priority for which this entry reports statistics.
				1=regular.
				2=high. "
			::= { scGenMonPriorityEntry 2 }

		scGenMonPriorityGoodPkts OBJECT-TYPE
			SYNTAX Counter
			ACCESS read-only
			STATUS mandatory
			DESCRIPTION
				" The total number of good packets switched by this XSwitch
				using this packet priority level."
			::= { scGenMonPriorityEntry 3 }

		scGenMonPriorityGoodOctets OBJECT-TYPE
			SYNTAX Counter
			ACCESS read-only
			STATUS mandatory
			DESCRIPTION
				"The total number of good octets switched by this XSwitch
				using this packet priority level."
			::= { scGenMonPriorityEntry 4 }

		scGenMonVLANList OBJECT-TYPE
			SYNTAX OCTET STRING (SIZE (32))
			ACCESS read-only
			STATUS mandatory
			DESCRIPTION
				"A bitmap defining the status of the virtual LANs in the
				Virtual LAN Table. The first bit is for Virtual LAN 0, the
				second for Virtual LAN 1, and so on. If the Virtual LAN
				exists in the hub the value of the associated bit is 1, otherwise 0."
			::= { scGenMon 3 }

		scGenMonVLANTable OBJECT-TYPE
			SYNTAX SEQUENCE OF ScGenMonVLANEntry
			ACCESS not-accessible
			STATUS mandatory
			DESCRIPTION
				"A list of virtual LAN statistics."
			::= { scGenMon 4 }

		scGenMonVLANEntry OBJECT-TYPE
			SYNTAX ScGenMonVLANEntry
			ACCESS not-accessible
			STATUS mandatory
			DESCRIPTION
				"A list of statistics related to a specific Virtual LAN."
			INDEX { scGenMonVLANSwitchId, scGenMonVLANId }
			::= { scGenMonVLANTable 1 }

		ScGenMonVLANEntry ::=
			SEQUENCE {
				scGenMonVLANSwitchId
					INTEGER,
				scGenMonVLANId
					INTEGER,
				scGenMonVLANGoodPkts
					Counter,
				scGenMonVLANGoodOctets
					Counter,
				scGenMonVLANStatsUcastPkts
					Counter,
				scGenMonVLANStatsMcastPkts
					Counter,
				scGenMonVLANStatsBcastPkts
					Counter
			 }

		scGenMonVLANSwitchId OBJECT-TYPE
			SYNTAX INTEGER (1..255)
			ACCESS read-only
			STATUS mandatory
			DESCRIPTION
				" Index which identifies the XSwitch for which this entry contains information.
				This value is never greater than chNumberOfXSwitches. "
			::= { scGenMonVLANEntry 1 }

		scGenMonVLANId OBJECT-TYPE
			SYNTAX INTEGER
			ACCESS read-only
			STATUS mandatory
			DESCRIPTION
				"The Virtual LAN for which this entry contains information."
			::= { scGenMonVLANEntry 2 }

		scGenMonVLANGoodPkts OBJECT-TYPE
			SYNTAX Counter
			ACCESS read-only
			STATUS mandatory
			DESCRIPTION
				"The total number of good packets switched by the XSwitch
				on this Virtual LAN."
			::= { scGenMonVLANEntry 3 }

		scGenMonVLANGoodOctets OBJECT-TYPE
			SYNTAX Counter
			ACCESS read-only
			STATUS mandatory
			DESCRIPTION
				"The total number of good octets switched by the XSwitch
				on this Virtual LAN."
			::= { scGenMonVLANEntry 4 }

		scGenMonVLANStatsUcastPkts OBJECT-TYPE
			SYNTAX Counter
			ACCESS read-only
			STATUS mandatory
			DESCRIPTION
				"The total number of good unicast packets switched by the XSwitch
				on this Virtual LAN."
			::= { scGenMonVLANEntry 5 }

		scGenMonVLANStatsMcastPkts OBJECT-TYPE
			SYNTAX Counter
			ACCESS read-only
			STATUS mandatory
			DESCRIPTION
				"The total number of good multicast packets switched by the XSwitch
				on this Virtual LAN."
			::= { scGenMonVLANEntry 6 }

		scGenMonVLANStatsBcastPkts OBJECT-TYPE
			SYNTAX Counter
			ACCESS read-only
			STATUS mandatory
			DESCRIPTION
				"The total number of good broadcast packets switched by the XSwitch
				on this Virtual LAN."
			::= { scGenMonVLANEntry 7 }

		scGenMonSwitches OBJECT-TYPE
			SYNTAX OCTET STRING (SIZE (2))
			ACCESS read-only
			STATUS mandatory
			DESCRIPTION
				"A bitmap defining the switch status, whether it is functional or not.
				The list should start with the MSB.
				Value of each bit:
						0  -  the switch is not functional
					1  -  the switch is functional
					The mapping is:
					Bit 0 : Left DomainX
					Bit 1 : Right DomainX"
			::= { scGenMon 5 }

		scHostTimePortCorrTable OBJECT-TYPE
			SYNTAX SEQUENCE OF ScHostTimePortCorrEntry
			ACCESS not-accessible
			STATUS mandatory
			DESCRIPTION
				"An addition to the RMON MIB's hostTimeTable. This table contains
				a list of MAC addresses that were monitored on the switch
				and the ports to which they are connected.
				The index of this table is the same as for the standard RMON
				hostTimeTable. Indexes are scHostTimeCreationOrder and scHostTimeIndex.
				The MAC address is stored in scHostTimeAddress.
				The port to which the MAC address is connected is defined in
				scHostTimePortConnection."
			::= { scGenMon 6 }

		scHostTimePortCorrEntry OBJECT-TYPE
			SYNTAX ScHostTimePortCorrEntry
			ACCESS not-accessible
			STATUS mandatory
			DESCRIPTION
				"An entry in the MAC to port correlation table."
			INDEX { scHostTimeIndex, scHostTimeCreationOrder }
			::= { scHostTimePortCorrTable 1 }

		ScHostTimePortCorrEntry ::=
			SEQUENCE {
				scHostTimeAddress
					OCTET STRING,
				scHostTimeCreationOrder
					INTEGER,
				scHostTimeIndex
					INTEGER,
				scHostTimePortConnection
					INTEGER
			 }

		scHostTimeAddress OBJECT-TYPE
			SYNTAX OCTET STRING
			ACCESS read-only
			STATUS mandatory
			DESCRIPTION
				"The physical address of this host."
			::= { scHostTimePortCorrEntry 1 }

		scHostTimeCreationOrder OBJECT-TYPE
			SYNTAX INTEGER (1..65535)
			ACCESS read-only
			STATUS mandatory
			DESCRIPTION
				"An index that uniquely identifies an entry in
				the hostTime table among those entries associated
				with the same hostControlEntry.  This index shall
				be between 1 and N, where N is the value of
				the associated hostControlTableSize.  The ordering
				of the indexes is based on the order of each entry's
				insertion into the table, in which entries added
				earlier have a lower index value than entries added
				later. Thus the management station has the ability to
				learn of new entries added to this table without
				downloading the entire table.

				It is important to note that the index for a
				particular entry may change as an (earlier) entry
				is deleted from the table.  Because this order may
				change, management stations should make use of the
				hostControlLastDeleteTime variable in the
				hostControlEntry associated with the relevant
				portion of the hostTimeTable.  By observing
				this variable, the management station may detect
				the circumstances where a download of the table
				may have missed entries, and where a previous
				association between a value of hostTimeCreationOrder
				and a hostTimeEntry may no longer hold."
			::= { scHostTimePortCorrEntry 2 }

--       When the agent creates the control word for this purpose, the value of
-- hostTimeIndex is constant '999'.
		scHostTimeIndex OBJECT-TYPE
			SYNTAX INTEGER (1..65535)
			ACCESS read-only
			STATUS mandatory
			DESCRIPTION
				"The set of collected RMON host statistics of
				which this entry is a part.  The set of hosts
				identified by a particular value of this
				index is associated with the hostControlEntry
				as identified by the same value of hostControlIndex."
			::= { scHostTimePortCorrEntry 3 }

		scHostTimePortConnection OBJECT-TYPE
			SYNTAX INTEGER
			ACCESS read-only
			STATUS mandatory
			DESCRIPTION
				"The switch port to which this scHostTimeAddress is connected.
				The coding of the port number for Visage switches is:
				32*(H-1)+P, where H is the number of the hub in the stack
				and P the port in the hub (1.. 32).
				For hosts whose port connection is not identified by the agent, the
				value of this item will be 65,535 "
			::= { scHostTimePortCorrEntry 4 }

		scGenGroup OBJECT IDENTIFIER ::= { scGen 3 }

		scGenGroupTable OBJECT-TYPE
			SYNTAX SEQUENCE OF ScGenGroupEntry
			ACCESS not-accessible
			STATUS mandatory
			DESCRIPTION
				"Table of attributes which define general configuration
				information about a single SC based group."
			::= { scGenGroup 1 }

		scGenGroupEntry OBJECT-TYPE
			SYNTAX ScGenGroupEntry
			ACCESS not-accessible
			STATUS mandatory
			DESCRIPTION
				"An entry in the table, containing data about a single Group."
			INDEX { scGenGroupId }
			::= { scGenGroupTable 1 }

		ScGenGroupEntry ::=
			SEQUENCE {
				scGenGroupId
					INTEGER,
				scGenGroupUseSwitches
					INTEGER,
				scGenGroupCopyPortSupport
					INTEGER,
				scGenGroupXswitchConnection
					INTEGER,
				scGenGroupStatus
					INTEGER,
				scGenGroupSwitchType
					INTEGER,
				scGenGroupNumberOfLoads
					INTEGER,
				scGenGroupSetDefaults
					INTEGER,
				scGenGroupSupportCopyPortList
					OCTET STRING,
				scGenGroupSupportPortCountersList
					OCTET STRING,
				scGenGroupSupportSegCountersList
					OCTET STRING,
				scGenGroupUpLinkType
					INTEGER,
				scGenGroupPlugInType
					INTEGER,
				scGenGroupPlugInDescr
					DisplayString,
				scGenGroupPlugInCS
					DisplayString,
				scGenGroupDefaultVLAN
					INTEGER,
				scGenGroupCascadingType
					INTEGER,
				scGenGroupCascadingDescr
					DisplayString,
				scGenGroupCascadingCS
					DisplayString,
				scGenGroupSupportDstCopyPortList
					OCTET STRING,
				scGenGroupBUPSType
					INTEGER,
				scGenGroupBUPSCS
					DisplayString,
				scGenGroupBUPSFansStatus
					INTEGER,
				scGenGroupFansStatus
					INTEGER,
				scGenGroupInternalBuffering
					INTEGER,
				scGenGroupMcFilterBoxSupport
					INTEGER,
				scGenGroupMcFilterPersonalitySupport
					INTEGER,
				scGenGroupMcFilterStackingSupport
					INTEGER,
				scGenGroupLACPMode
					INTEGER,
				scGenGroupSecurityMode
					INTEGER,
				scGenGroupBroadcastStormControl
					INTEGER,
				scGenGroupBroadcastThreshold
					INTEGER,
				scGenGroupPriorityQueuesScheduling
					INTEGER,
				scGenGroupBoundedDelay
					INTEGER,
				scGenGroupSLDAdminStatus
					INTEGER,
				scGenGroupDynamicVlans
					INTEGER,
				scGenGroupSecurityMacCount
					INTEGER,
				scGenGroupBUPSAllocatedPower
					INTEGER
			 }

		scGenGroupId OBJECT-TYPE
			SYNTAX INTEGER
			ACCESS read-only
			STATUS mandatory
			DESCRIPTION
				"Unique Id of the group in the scGenGroupTable.
				Equals the number of the slot by which the group is accessed."
			::= { scGenGroupEntry 1 }

		scGenGroupUseSwitches OBJECT-TYPE
			SYNTAX INTEGER
				{
				on(1),
				off(2),
				notSupported(255)
				}
			ACCESS read-only
			STATUS mandatory
			DESCRIPTION
				"This attribute reflects the status of the `Use Switches' switch which
				defines the working mode of the module.
				on - The module works according to the switches. No Set commands
				may be performed on attributes related to the switches.
				off - Ignore Dip Switches, use stored parameters and accept all Set commands."
			::= { scGenGroupEntry 2 }

		scGenGroupCopyPortSupport OBJECT-TYPE
			SYNTAX INTEGER
				{
				on(1),
				off(2),
				notSupported(255)
				}
			ACCESS read-only
			STATUS mandatory
			DESCRIPTION
				" Indication whether a module supports Copy-Port [on(1)],
				or does not support Copy-Port [off(2)]."
			::= { scGenGroupEntry 3 }

		scGenGroupXswitchConnection OBJECT-TYPE
			SYNTAX INTEGER (1..255)
			ACCESS read-only
			STATUS mandatory
			DESCRIPTION
				"This attribute identifies the Xswitch number (1..4) to which the module
				is connected to.
				In non-bridged configuration, there are potentialy up to 4 Xswitches -
				1&2 for left&right Ethernet Xswitches and 3&4 for left&right TR Xswitches.
				In bridged configuration, there are potentialy 2 Xswitches -
				1 for Ethernet Xswitch and 2 for TR Xswitch."
			::= { scGenGroupEntry 4 }

		scGenGroupStatus OBJECT-TYPE
			SYNTAX INTEGER
				{
				ok(1),
				loadsBudgetProblem(2),
				notSupported(255)
				}
			ACCESS read-only
			STATUS mandatory
			DESCRIPTION
				"This attributes defines the status of the Xswitch module.
				The value 'loadsBudgetProblem' indicates that the module cannot be connected to the
				Xswitch because it exceeds the maximum number of loads allowed in the Xswitch."
			::= { scGenGroupEntry 5 }

		scGenGroupSwitchType OBJECT-TYPE
			SYNTAX INTEGER
				{
				ethernet(1),
				token-ring(2),
				notSupported(255)
				}
			ACCESS read-only
			STATUS mandatory
			DESCRIPTION
				"This attribute defines the Xswitch type of the module."
			::= { scGenGroupEntry 6 }

		scGenGroupNumberOfLoads OBJECT-TYPE
			SYNTAX INTEGER (1..255)
			ACCESS read-only
			STATUS mandatory
			DESCRIPTION
				"This attribute identifies the number of loads which that Xswitch module represents."
			::= { scGenGroupEntry 7 }

		scGenGroupSetDefaults OBJECT-TYPE
			SYNTAX INTEGER
				{
				on(1),
				off(2),
				layer2Only(3),
				notSupported(255)
				}
			ACCESS read-write
			STATUS mandatory
			DESCRIPTION
				"Set all module and ports parameters in the XSwitch module, to their default values.
				This item will always return a value of off(2), since it acts like a toggle switch.
				Set of layer2Only(3) value, will cause partial setting, to layer2 parameters only"
			DEFVAL { off }
			::= { scGenGroupEntry 8 }

		scGenGroupSupportCopyPortList OBJECT-TYPE
			SYNTAX OCTET STRING
			ACCESS read-only
			STATUS mandatory
			DESCRIPTION
				"A bitmap defining the status of each port of the hub\module whether it support copy
				port or not,
				0  -  the port does not support copy port
				1  -  the port support the copy port
				the list should start with the MSB indicates port number  1 (one)  and the LSB
				indicates the  highest number of the ports in the hub\module.
				For Example: if  a module\hub  has 8 ports and ports  number 1,3,4 support copy
				port while the other don't, the bitmap will be:   10110000."
			::= { scGenGroupEntry 9 }

		scGenGroupSupportPortCountersList OBJECT-TYPE
			SYNTAX OCTET STRING
			ACCESS read-only
			STATUS mandatory
			DESCRIPTION
				"A bitmap defining the status of each port of the hub\module whether it supports
				the port's counters,
				0  -  the port does not support  port's counters
				1  -  the port support the port's counters
				the list should start with the MSB indicates port number  1 (one)  and the LSB
				indicates the  highest number of the ports in the hub\module.
				For Example: if  a module\hub  has 8 ports and ports  number 1,3,4 support
				port's  counters while the other don't, the bitmap will be:   10110000."
			::= { scGenGroupEntry 10 }

		scGenGroupSupportSegCountersList OBJECT-TYPE
			SYNTAX OCTET STRING
			ACCESS read-only
			STATUS mandatory
			DESCRIPTION
				"A bitmap defining the status of each port of the hub\module whether it supports
				the segment counters on port,
				0  -  the port does not support segment's counters
				1  -  the port support the segment's counters
				the list should start with the MSB indicates port number  1 (one)  and the LSB
				indicates the highest number of the ports in the hub\module.
				For Example: if  a module\hub  has 8 ports and ports number 1,3,4 support
				segment's counters while the other don't, the bitmap will be: 10110000."
			::= { scGenGroupEntry 11 }

		scGenGroupUpLinkType OBJECT-TYPE
			SYNTAX INTEGER
				{
				fiber(1),
				copper(2),
				notSupported(255)
				}
			ACCESS read-write
			STATUS mandatory
			DESCRIPTION
				"The type of the Up Link port
				Relevant only for the 25th port of Visage 2500:
				Fiber (1) - 100BaseFX,
				Copper (2) -100BaseTX."
			::= { scGenGroupEntry 12 }

--      Not used
-- Not used, see below
--
--    Wan expansion modules
		scGenGroupPlugInType OBJECT-TYPE
			SYNTAX INTEGER
				{
				cajunX120T8(1),
				cajunX120F2(2),
				cajunX120S1(3),
				cajunX120S2(4),
				cajunX120L1(5),
				cajunX120L2(6),
				cajunX120T16(7),
				cajunX120F4(8),
				cajunX120G2(9),
				cajunX120GT2(10),
				cajunX330T16(11),
				cajunX330F4(12),
				cajunX330F2(13),
				cajunX330L2(14),
				cajunX330S2(15),
				cajunX330L1(16),
				cajunX330S1(17),
				cajunX330-OC12F1(18),
				cajunX330-OC12F2(19),
				cajunX330-OC3F1(20),
				cajunX330-OC3F2(21),
				cajunX330-OC12S1(22),
				cajunX330-OC12S2(23),
				cajunX330GT4(24),
				cajunX330GT2(25),
				cajunX330G2(26),
				cajunX330W-4DS1(27),
				cajunX330W-2DS1(28),
				cajunX130F2(31),
				cajunX130G2(32),
				cajunX130GT2(33),
				x330w-2ds1(34),
				x330w-2usp(35),
				x330w-2ds1-isdn(36),
				x330w-2usp-isdn(37),
				x330w-future1(38),
				x330w-future2(39),
				x330w-future3(40),
				x330w-future4(41),
				x330w-future5(42),
				x330w-future6(43),
				x330w-future7(44),
				x330w-future8(45),
				x330w-future9(46),
				unknown(254),
				none(255)
				}
			ACCESS read-only
			STATUS mandatory
			DESCRIPTION
				"Attribute describing the type of the plug-in module"
			::= { scGenGroupEntry 13 }

		scGenGroupPlugInDescr OBJECT-TYPE
			SYNTAX DisplayString (SIZE (0..32))
			ACCESS read-only
			STATUS mandatory
			DESCRIPTION
				"Descriptor of the plug-in in ASCII (readable) format,
				mainly for use with Generic management applications."
			::= { scGenGroupEntry 14 }

		scGenGroupPlugInCS OBJECT-TYPE
			SYNTAX DisplayString
			ACCESS read-only
			STATUS mandatory
			DESCRIPTION
				"ASCII string for description and display of the plug-in
				module configuration symbol. The format of the number is XXXX.YY"
			::= { scGenGroupEntry 15 }

		scGenGroupDefaultVLAN OBJECT-TYPE
			SYNTAX INTEGER
				{
				vlan0(1),
				vlan1(2),
				notSupported(255)
				}
			ACCESS read-only
			STATUS mandatory
			DESCRIPTION
				"Attribute describing the Default VLAN configuration on the switch ports of the module.
				It is determined according to scGenSwitchDefaultVLAN parameter of the agent."
			::= { scGenGroupEntry 16 }

		scGenGroupCascadingType OBJECT-TYPE
			SYNTAX INTEGER
				{
				cajunX330STK(1),
				cajunX330MLSTK(2),
				avayaX360STK(3),
				unknown(254),
				none(255)
				}
			ACCESS read-only
			STATUS mandatory
			DESCRIPTION
				"Attribute describing the type of the cascding module"
			::= { scGenGroupEntry 17 }

		scGenGroupCascadingDescr OBJECT-TYPE
			SYNTAX DisplayString (SIZE (0..32))
			ACCESS read-only
			STATUS mandatory
			DESCRIPTION
				"Descriptor of the cascading module in ASCII (readable) format,
				mainly for use with Generic management applications."
			::= { scGenGroupEntry 18 }

		scGenGroupCascadingCS OBJECT-TYPE
			SYNTAX DisplayString
			ACCESS read-only
			STATUS mandatory
			DESCRIPTION
				"ASCII string for description and display of the cascading module
				configuration symbol. The format of the number is XXX.YYY"
			::= { scGenGroupEntry 19 }

		scGenGroupSupportDstCopyPortList OBJECT-TYPE
			SYNTAX OCTET STRING
			ACCESS read-only
			STATUS mandatory
			DESCRIPTION
				"A bitmap defining the status of each port of the hub\module
				whether it supports the capability of being a destination copy-port .
				1   -  the port has the capability of being a destination copy-port
				0   -  the port does not have the capability of being a destination copy-port
				The list should start with the MSB indicating port number 1 (one)
				and the LSB indicating the highest number of the ports in the hub\module.
				For Example: if  a module\hub has 8 ports and ports number 1,3,4 can be
				destination copy ports, while the others cannot, then the bitmap will be: 10110000."
			::= { scGenGroupEntry 20 }

		scGenGroupBUPSType OBJECT-TYPE
			SYNTAX INTEGER
				{
				ac(1),
				dc(2),
				none(255)
				}
			ACCESS read-only
			STATUS mandatory
			DESCRIPTION
				"Attribute describing the type of the BUPS module"
			::= { scGenGroupEntry 21 }

		scGenGroupBUPSCS OBJECT-TYPE
			SYNTAX DisplayString
			ACCESS read-only
			STATUS mandatory
			DESCRIPTION
				"ASCII string for description and display of the BUPS
				module configuration symbol. The format of the number is X.Y"
			::= { scGenGroupEntry 22 }

		scGenGroupBUPSFansStatus OBJECT-TYPE
			SYNTAX INTEGER
				{
				allFansOK(1),
				oneFanFailed(2),
				notSupported(255)
				}
			ACCESS read-only
			STATUS mandatory
			DESCRIPTION
				"The operational status of the fans included in the BUPS module:
				allFansOK(1) - all BUPS module's fans are operational.
				oneFanFailed(2) - at least one of the BUPS module's fan is failed."
			::= { scGenGroupEntry 23 }

		scGenGroupFansStatus OBJECT-TYPE
			SYNTAX INTEGER
				{
				allFansOK(1),
				oneFanFailed(2),
				notSupported(255)
				}
			ACCESS read-only
			STATUS mandatory
			DESCRIPTION
				"The operational status of the fans included in the module:
				allFansOK(1) - all module's fans are operational.
				oneFanFailed(2) - at least one of the module's fan is failed."
			::= { scGenGroupEntry 24 }

		scGenGroupInternalBuffering OBJECT-TYPE
			SYNTAX INTEGER
				{
				min(1),
				max(2),
				med(3),
				notSupported(255)
				}
			ACCESS read-write
			STATUS mandatory
			DESCRIPTION
				"Control the internal buffering capacity."
			::= { scGenGroupEntry 25 }

		scGenGroupMcFilterBoxSupport OBJECT-TYPE
			SYNTAX INTEGER
				{
				filteringSupported(1),
				filterNotSupport(2),
				notSupported(255)
				}
			ACCESS read-only
			STATUS mandatory
			DESCRIPTION
				"Tells whether the box hardware supports filtering or not."
			::= { scGenGroupEntry 26 }

		scGenGroupMcFilterPersonalitySupport OBJECT-TYPE
			SYNTAX INTEGER
				{
				filteringSupported(1),
				filterNotSupport(2),
				personalityNotInstalled(3),
				notSupported(255)
				}
			ACCESS read-only
			STATUS mandatory
			DESCRIPTION
				"Tells whether the personality hardware supports filtering or not.
				The value PersonalityNotInstalld means that the a personality
				Extention was not installed in the specific box"
			::= { scGenGroupEntry 27 }

		scGenGroupMcFilterStackingSupport OBJECT-TYPE
			SYNTAX INTEGER
				{
				filteringSupported(1),
				filterNotSupport(2),
				stackingNotInstalled(3),
				notSupported(255)
				}
			ACCESS read-only
			STATUS mandatory
			DESCRIPTION
				"Tells whether the stacking hardware supports filtering or not
				The value StackingNotInstalld means that the a stacking daughter board
				was not installed in the specific box"
			::= { scGenGroupEntry 28 }

		scGenGroupLACPMode OBJECT-TYPE
			SYNTAX INTEGER
				{
				enable(1),
				disable(2)
				}
			ACCESS read-write
			STATUS mandatory
			DESCRIPTION
				" The value of this attribute determines whether LACPDU messages can be exchanged by the module's ports.
				If enabled, the ports will exchange LACPDU messages according to their scGenPortLACPMode MIB.
				If disabled, every port of the module will not exchange LACPDU messages - regardless of there
				scGenPortLACPMode MIB.
				This MIB is required for internal communication between the agent and its sub-agents, in order to distribute
				throughout the switch's modules the setting made on the scGenSwitchLACPMode MIB."
			::= { scGenGroupEntry 29 }

		scGenGroupSecurityMode OBJECT-TYPE
			SYNTAX INTEGER
				{
				nonSecurityMode(1),
				securityMode(2),
				notSupported(255)
				}
			ACCESS read-write
			STATUS mandatory
			DESCRIPTION
				"Group intrusion security mode assigned to this module.
				securityMode - all ports in this module are secure according to their scGenPortSecurityMode MIB's value.
				nonSecurityMode - all ports in this module are not secure."
			::= { scGenGroupEntry 30 }

		scGenGroupBroadcastStormControl OBJECT-TYPE
			SYNTAX INTEGER
				{
				on(1),
				off(2),
				notSupported(255)
				}
			ACCESS read-write
			STATUS mandatory
			DESCRIPTION
				" Set the Broadcast Storm Control function on all switch ports.
				On means that Broadcast, Multicast or Unknown packets are discarded on an ingress port,
				when the rate of those packets, received on the port,
				is above the scGenGroupBroadcastThreshold, as set by the user."
			DEFVAL { off }
			::= { scGenGroupEntry 31 }

		scGenGroupBroadcastThreshold OBJECT-TYPE
			SYNTAX INTEGER (10..144000)
			ACCESS read-write
			STATUS mandatory
			DESCRIPTION
				" Set the Rate Threshold, in packets per second, above which Broadcast,
				Multicast or Unknown packets are discarded on ingress port."
			DEFVAL { 500 }
			::= { scGenGroupEntry 32 }

		scGenGroupPriorityQueuesScheduling OBJECT-TYPE
			SYNTAX INTEGER
				{
				strict(1),
				weighted(2),
				notSupported(255)
				}
			ACCESS read-write
			STATUS mandatory
			DESCRIPTION
				" Set the Priority Queues Scheduling scheme for packets transmission from egress ports.
				Strict - will serve higher priority queue before lower priority queue, as long as the higher queue has packets.
				Weighted - will serve higher priority queue before lower priority queue,
				but will save specific bandwidth for each queue in order to avoid starvation of lower priority queues."
			DEFVAL { weighted }
			::= { scGenGroupEntry 33 }

		scGenGroupBoundedDelay OBJECT-TYPE
			SYNTAX INTEGER
				{
				on(1),
				off(2),
				notSupported(255)
				}
			ACCESS read-write
			STATUS mandatory
			DESCRIPTION
				" Set the Bounded Delay function in the switch.
				On will ensure that time-sensitive packets will be forwarded
				through the switch in no more than a maximum delay."
			DEFVAL { on }
			::= { scGenGroupEntry 34 }

		scGenGroupSLDAdminStatus OBJECT-TYPE
			SYNTAX INTEGER
				{
				enable(1),
				disable(2),
				notSupported(255)
				}
			ACCESS read-write
			STATUS mandatory
			DESCRIPTION
				" set the Self Loop Discovery application to enable/disable.
				This works with the scGenPortSLDAdminStatus"
			DEFVAL { disable }
			::= { scGenGroupEntry 35 }

		scGenGroupDynamicVlans OBJECT-TYPE
			SYNTAX INTEGER
			ACCESS read-write
			STATUS mandatory
			DESCRIPTION
				" Indicates the number of dynamic vlans detected in the module so far.
				If this value is set to zero, all dynamic vlans detected up to this time will be deleted."
			::= { scGenGroupEntry 36 }

		scGenGroupSecurityMacCount OBJECT-TYPE
			SYNTAX INTEGER (1..1024)
			ACCESS read-only
			STATUS mandatory
			DESCRIPTION
				"Indicates the number of secure MAC assigned to this module so far. The value should be
				0 if the secure MAC table is empty for this module.
				"
			::= { scGenGroupEntry 37 }

		scGenGroupBUPSAllocatedPower OBJECT-TYPE
			SYNTAX INTEGER (100..900)
			ACCESS read-write
			STATUS mandatory
			DESCRIPTION
				"Indicates the total 48V BUPS power that is allocated to this module in Watts."
			DEFVAL { 800 }
			::= { scGenGroupEntry 38 }

--      For SMON applications - group monitoring.
--
		scGenGroupSmonTable OBJECT-TYPE
			SYNTAX SEQUENCE OF ScGenGroupSmonEntry
			ACCESS not-accessible
			STATUS mandatory
			DESCRIPTION
				"Table of smon capabilities in a single group."
			::= { scGenGroup 2 }

		scGenGroupSmonEntry OBJECT-TYPE
			SYNTAX ScGenGroupSmonEntry
			ACCESS not-accessible
			STATUS mandatory
			DESCRIPTION
				"An entry in the table, containing data about
				a single Group."
			INDEX { scGenGroupSmonGroupId }
			::= { scGenGroupSmonTable 1 }

		ScGenGroupSmonEntry ::=
			SEQUENCE {
				scGenGroupSmonGroupId
					INTEGER,
				scGenGroupSmonCapability
					OCTET STRING,
				scGenGroupSmonVlanList
					OCTET STRING,
				scGenGroupSmonDropEvents
					Counter,
				scGenGroupSmonGoodBroadcastPkts
					Counter,
				scGenGroupSmonGoodMulticastPkts
					Counter,
				scGenGroupSmonGoodPkts
					Counter,
				scGenGroupSmonBadPkts
					Counter,
				scGenGroupSmonGoodOctets
					Counter,
				scGenGroupSmonBadOctets
					Counter,
				scGenGroupSmonPkts
					Counter,
				scGenGroupSmonOctets
					Counter,
				scGenGroupSmonMIBCtrMode
					INTEGER
			 }

		scGenGroupSmonGroupId OBJECT-TYPE
			SYNTAX INTEGER
			ACCESS read-only
			STATUS mandatory
			DESCRIPTION
				"Unique Id of the group in the scGenGroupSmonTable.
				Equals the number of the slot by which the group
				is accessed."
			::= { scGenGroupSmonEntry 1 }

		scGenGroupSmonCapability OBJECT-TYPE
			SYNTAX OCTET STRING (SIZE (4))
			ACCESS read-only
			STATUS mandatory
			DESCRIPTION
				"This item is used to define which smon's application are
				implemented in the group.
				When there is a value of 0 (zero) in the relevant bit
				it means that the assosiated 	application is not supported.
				When there is a value of 1 (one) in the relevant bit it
				means that the assosiated application is supported.
				D0   - Statistics.
				D1   - History.
				D2   - Alarms.
				D3   - Host.
				D4   - HostTopN.
				D5   - Metrix.
				D6   - Filter.
				D7   - Capture.
				D8   - Event.
				D9   - TokenRing.
				D10  - ProtocolDir.
				D11 - ProtocolDist.
				D12 - AddressMap.
				D13 - NlHost.
				D14 - NlMatrix.
				D15 - AlHost.
				D16 - AlMatrix.
				D17 - UsrHistory.
				D18 - ProbConfig.
				D19 - Port.
				D20 - PortTopN.
				D21 - Subnet.
				D22 - SubnetMatrix.
				D23 - Vlan.
				D24 - VlanMatrix. "
			::= { scGenGroupSmonEntry 2 }

		scGenGroupSmonVlanList OBJECT-TYPE
			SYNTAX OCTET STRING (SIZE (32))
			ACCESS read-only
			STATUS mandatory
			DESCRIPTION
				"A bitmap defining the status of the virtual LANs in the
				Virtual LAN Table. The first bit is for Virtual LAN 0, the
				second for Virtual LAN 1, and so on. If the Virtual LAN
				exists in the hub the value of the associated bit is 1, otherwise 0."
			::= { scGenGroupSmonEntry 3 }

		scGenGroupSmonDropEvents OBJECT-TYPE
			SYNTAX Counter
			ACCESS read-only
			STATUS mandatory
			DESCRIPTION
				"The total number of events ,in this group, in which the
				probe could not count packets due to lack of resources.
				This number is not necessarily the number of packets
				dropped; it is just the number of times this condition
				has been detected."
			::= { scGenGroupSmonEntry 4 }

		scGenGroupSmonGoodBroadcastPkts OBJECT-TYPE
			SYNTAX Counter
			ACCESS read-only
			STATUS mandatory
			DESCRIPTION
				"The total number of good broadcast packets in this group,
				switched by the Xswitch."
			::= { scGenGroupSmonEntry 5 }

		scGenGroupSmonGoodMulticastPkts OBJECT-TYPE
			SYNTAX Counter
			ACCESS read-only
			STATUS mandatory
			DESCRIPTION
				"The total number of good multicast packets, in this group,
				switched by the Xswitch."
			::= { scGenGroupSmonEntry 6 }

		scGenGroupSmonGoodPkts OBJECT-TYPE
			SYNTAX Counter
			ACCESS read-only
			STATUS mandatory
			DESCRIPTION
				"The total number of good packets, in this group, switched by the Xswitch."
			::= { scGenGroupSmonEntry 7 }

		scGenGroupSmonBadPkts OBJECT-TYPE
			SYNTAX Counter
			ACCESS read-only
			STATUS mandatory
			DESCRIPTION
				"The total number of bad packets , in this group, filtered by the Xswitch."
			::= { scGenGroupSmonEntry 8 }

		scGenGroupSmonGoodOctets OBJECT-TYPE
			SYNTAX Counter
			ACCESS read-only
			STATUS mandatory
			DESCRIPTION
				"The total number of good octets, in this group, switched by the Xswitch."
			::= { scGenGroupSmonEntry 9 }

		scGenGroupSmonBadOctets OBJECT-TYPE
			SYNTAX Counter
			ACCESS read-only
			STATUS mandatory
			DESCRIPTION
				"The total number of bad octets, in this group, filtered by the Xswitch."
			::= { scGenGroupSmonEntry 10 }

		scGenGroupSmonPkts OBJECT-TYPE
			SYNTAX Counter
			ACCESS read-only
			STATUS mandatory
			DESCRIPTION
				"The total number of packets, good and bad, in this group,
				switched by the Xswitch."
			::= { scGenGroupSmonEntry 11 }

		scGenGroupSmonOctets OBJECT-TYPE
			SYNTAX Counter
			ACCESS read-only
			STATUS mandatory
			DESCRIPTION
				"The total number of octets, good and bad, in this group,
				switched by the Xswitch."
			::= { scGenGroupSmonEntry 12 }

		scGenGroupSmonMIBCtrMode OBJECT-TYPE
			SYNTAX INTEGER
				{
				enable(1),
				disable(2),
				notSupported(255)
				}
			ACCESS read-write
			STATUS mandatory
			DESCRIPTION
				" This object defines for group ports to include/exclude
				local segment traffic in their port counters"
			DEFVAL { disable }
			::= { scGenGroupSmonEntry 13 }

		scGenGroupVlanTable OBJECT-TYPE
			SYNTAX SEQUENCE OF ScGenGroupVlanEntry
			ACCESS not-accessible
			STATUS mandatory
			DESCRIPTION
				"Table of attributes which define general VLAN
				counters of a single SC based group."
			::= { scGenGroup 3 }

		scGenGroupVlanEntry OBJECT-TYPE
			SYNTAX ScGenGroupVlanEntry
			ACCESS not-accessible
			STATUS mandatory
			DESCRIPTION
				"An entry in the table, containing VLAN counters in a single Group."
			INDEX { scGenGroupVlanGroupId, scGenGroupVlanId }
			::= { scGenGroupVlanTable 1 }

		ScGenGroupVlanEntry ::=
			SEQUENCE {
				scGenGroupVlanGroupId
					INTEGER,
				scGenGroupVlanId
					INTEGER,
				scGenGroupVlanUcastPkts
					Counter,
				scGenGroupVlanMcastPkts
					Counter,
				scGenGroupVlanBcastPkts
					Counter,
				scGenGroupVlanGoodPkts
					Counter,
				scGenGroupVlanGoodOctets
					Counter,
				scGenGroupVlanUcastOctets
					Counter,
				scGenGroupVlanMcastOctets
					Counter,
				scGenGroupVlanBcastOctets
					Counter,
				scGenGroupVlanCurrentEgressPorts
					OCTET STRING,
				scGenGroupVlanCurrentUntaggedPorts
					OCTET STRING,
				scGenGroupVlanStaticEgressPorts
					OCTET STRING,
				scGenGroupVlanStaticUntaggedPorts
					OCTET STRING
			 }

		scGenGroupVlanGroupId OBJECT-TYPE
			SYNTAX INTEGER
			ACCESS read-only
			STATUS mandatory
			DESCRIPTION
				"Unique Id of the group in the scGenGroupVlanTable.
				Equals the number of the slot by which the group is accessed."
			::= { scGenGroupVlanEntry 1 }

		scGenGroupVlanId OBJECT-TYPE
			SYNTAX INTEGER
			ACCESS read-only
			STATUS mandatory
			DESCRIPTION
				"The Virtual LAN for which this entry contains information."
			::= { scGenGroupVlanEntry 2 }

		scGenGroupVlanUcastPkts OBJECT-TYPE
			SYNTAX Counter
			ACCESS read-only
			STATUS mandatory
			DESCRIPTION
				"The total number of good unicast packets ,in this group,
				switched by the Xswitch on this Virtual LAN."
			::= { scGenGroupVlanEntry 3 }

		scGenGroupVlanMcastPkts OBJECT-TYPE
			SYNTAX Counter
			ACCESS read-only
			STATUS mandatory
			DESCRIPTION
				"The total number of good multicast packets ,in this group,
				switched by the Xswitch on this Virtual LAN."
			::= { scGenGroupVlanEntry 4 }

		scGenGroupVlanBcastPkts OBJECT-TYPE
			SYNTAX Counter
			ACCESS read-only
			STATUS mandatory
			DESCRIPTION
				"The total number of good broadcast packets in this group,
				switched by the Xswitch on this Virtual LAN."
			::= { scGenGroupVlanEntry 5 }

		scGenGroupVlanGoodPkts OBJECT-TYPE
			SYNTAX Counter
			ACCESS read-only
			STATUS mandatory
			DESCRIPTION
				"The total number of good packets ,in this group,
				switched by the Xswitch on this Virtual LAN."
			::= { scGenGroupVlanEntry 6 }

		scGenGroupVlanGoodOctets OBJECT-TYPE
			SYNTAX Counter
			ACCESS read-only
			STATUS mandatory
			DESCRIPTION
				"The total number of good octets ,in this group,
				switched by the Xswitch on this Virtual LAN."
			::= { scGenGroupVlanEntry 7 }

		scGenGroupVlanUcastOctets OBJECT-TYPE
			SYNTAX Counter
			ACCESS read-only
			STATUS mandatory
			DESCRIPTION
				"The total number of good unicast octets ,in this group,
				switched by the Xswitch on this Virtual LAN."
			::= { scGenGroupVlanEntry 8 }

		scGenGroupVlanMcastOctets OBJECT-TYPE
			SYNTAX Counter
			ACCESS read-only
			STATUS mandatory
			DESCRIPTION
				"The total number of good multicast octets ,in this group,
				switched by the Xswitch on this Virtual LAN."
			::= { scGenGroupVlanEntry 9 }

		scGenGroupVlanBcastOctets OBJECT-TYPE
			SYNTAX Counter
			ACCESS read-only
			STATUS mandatory
			DESCRIPTION
				"The total number of good broadcast octets ,in this group,
				switched by the Xswitch on this Virtual LAN."
			::= { scGenGroupVlanEntry 10 }

		scGenGroupVlanCurrentEgressPorts OBJECT-TYPE
			SYNTAX OCTET STRING
			ACCESS read-only
			STATUS mandatory
			DESCRIPTION
				"The set of ports in this module which are transmitting traffic for this
				vlan as either tagged or untagged frames. Each module's port is
				represented by a single bit in this 128-bits bitmap according to the
				PortList convention of RFC2674.
				This MIB is for internal agent sub-agent communication, it is aimed to
				distribute the standard dot1qVlanCurrentEgressPorts among the modules."
			REFERENCE
				"IEEE 802.1Q/D11 Section 12.10.2.1"
			::= { scGenGroupVlanEntry 11 }

		scGenGroupVlanCurrentUntaggedPorts OBJECT-TYPE
			SYNTAX OCTET STRING
			ACCESS read-only
			STATUS mandatory
			DESCRIPTION
				"The set of ports which are transmitting traffic for this VLAN as
				untagged frames. Each module's port is
				represented by a single bit in this 128-bits bitmap according to the
				PortList convention of RFC2674.
				This MIB is for internal agent sub-agent communication, it is aimed to
				distribute the standard dot1qVlanCurrentUntaggedPorts among the modules.
				It is updated together with genPortVLANMode MIB."
			REFERENCE
				"IEEE 802.1Q/D11 Section 12.10.2.1"
			::= { scGenGroupVlanEntry 12 }

		scGenGroupVlanStaticEgressPorts OBJECT-TYPE
			SYNTAX OCTET STRING
			ACCESS read-write
			STATUS mandatory
			DESCRIPTION
				"The set of ports in this module which are permanently assigned to the
				egress list for this VLAN by management.  Each module's port is
				represented by a single bit in this 128-bits bitmap according to the
				PortList convention of RFC2674. Changes to a bit in this object affect
				the per-port per-VLAN Registrar control for Registration Fixed for the
				relevant GVRP state machine on each port.  The default value of this
				object is a string of zeros long by 128 bits, indicating not fixed.
				This MIB is for internal agent sub-agent communication, it is aimed to
				distribute the standard dot1qVlanStaticEgressPorts among the modules."
			REFERENCE
				"IEEE 802.1Q/D11 Section 12.7.7.3, 11.2.3.2.3"
			::= { scGenGroupVlanEntry 13 }

		scGenGroupVlanStaticUntaggedPorts OBJECT-TYPE
			SYNTAX OCTET STRING
			ACCESS read-write
			STATUS mandatory
			DESCRIPTION
				"The set of ports which should transmit egress packets for this VLAN as
				untagged. Each module's port is represented by a single bit in this
				128-bits bitmap according to the PortList convention of RFC2674.
				The default value of this object for the default VLAN (dot1qVlanIndex =
				1) is a string of appropriate length including all ports.  There is no
				specified default for other VLANs.  If a device agent cannot
				support the set of ports being set then it will reject the
				set operation with an error. An example might be if a
				manager attempts to set more than one VLAN to be untagged
				on egress where the device does not support this IEEE 802.1Q
				option. It is updated together with genPortVLANMode MIB."
			REFERENCE
				"IEEE 802.1Q/D11 Section 12.10.2.1"
			::= { scGenGroupVlanEntry 14 }

		scGenGroupRspTable OBJECT-TYPE
			SYNTAX SEQUENCE OF ScGenGroupRspEntry
			ACCESS not-accessible
			STATUS mandatory
			DESCRIPTION
				"."
			::= { scGenGroup 4 }

		scGenGroupRspEntry OBJECT-TYPE
			SYNTAX ScGenGroupRspEntry
			ACCESS not-accessible
			STATUS mandatory
			DESCRIPTION
				"."
			INDEX { scGenGroupRspGroupId }
			::= { scGenGroupRspTable 1 }

		ScGenGroupRspEntry ::=
			SEQUENCE {
				scGenGroupRspGroupId
					INTEGER,
				scGenGroupRspHelloInterval
					INTEGER,
				scGenGroupRspDevicePollingInterval
					INTEGER,
				scGenGroupRspDeviceNotRespondingTimeout
					INTEGER,
				scGenGroupRspSwitchNotRespondingTimeout
					INTEGER,
				scGenGroupRspMoveToForwardingInterval
					INTEGER,
				scGenGroupRspBroadcastArpShortInterval
					INTEGER,
				scGenGroupRspBroadcastArpShortIntervalNumber
					INTEGER,
				scGenGroupRspBroadcastArpLongInterval
					INTEGER,
				scGenGroupRspPeriodicPingsBoxIpAddress
					IpAddress,
				scGenGroupRspPeriodicPingsDestinationIpAddress
					IpAddress,
				scGenGroupRspMode
					INTEGER
			 }

		scGenGroupRspGroupId OBJECT-TYPE
			SYNTAX INTEGER
			ACCESS read-only
			STATUS mandatory
			DESCRIPTION
				"Unique Id of the group in the scGenGroupRspTable.
				Equals the number of the slot by which the group is accessed."
			::= { scGenGroupRspEntry 1 }

		scGenGroupRspHelloInterval OBJECT-TYPE
			SYNTAX INTEGER
			ACCESS read-write
			STATUS mandatory
			DESCRIPTION
				"The interval between transmissions of hello-messages, in 100mSec units."
			DEFVAL { 1 }
			::= { scGenGroupRspEntry 2 }

		scGenGroupRspDevicePollingInterval OBJECT-TYPE
			SYNTAX INTEGER
			ACCESS read-write
			STATUS mandatory
			DESCRIPTION
				"The interval between transmissions of ARP queries for polling
				connectivity to the device, in 100mSec units."
			DEFVAL { 1 }
			::= { scGenGroupRspEntry 3 }

		scGenGroupRspDeviceNotRespondingTimeout OBJECT-TYPE
			SYNTAX INTEGER
			ACCESS read-write
			STATUS mandatory
			DESCRIPTION
				"Amount of time in which no ARP-replies are received from the device,
				which cause the RSP to assume no connection to that device, in 100mSec units."
			DEFVAL { 5 }
			::= { scGenGroupRspEntry 4 }

		scGenGroupRspSwitchNotRespondingTimeout OBJECT-TYPE
			SYNTAX INTEGER
			ACCESS read-write
			STATUS mandatory
			DESCRIPTION
				"Amount of time in which no hello-messages with acknowledge are received from the other switch,
				which cause the RSP to assume no connection to that switch, in 100mSec units."
			DEFVAL { 5 }
			::= { scGenGroupRspEntry 5 }

		scGenGroupRspMoveToForwardingInterval OBJECT-TYPE
			SYNTAX INTEGER
			ACCESS read-write
			STATUS mandatory
			DESCRIPTION
				"Amount of time the port waits upon deciding to move to forwarding mode,
				until it moves to that mode, in 100mSec units."
			DEFVAL { 5 }
			::= { scGenGroupRspEntry 6 }

		scGenGroupRspBroadcastArpShortInterval OBJECT-TYPE
			SYNTAX INTEGER
			ACCESS read-write
			STATUS mandatory
			DESCRIPTION
				"The interval in which the switch should send broadcast ARPs to the device
				when not knowing the MAC-address of the device, in 100mSec units."
			DEFVAL { 5 }
			::= { scGenGroupRspEntry 7 }

		scGenGroupRspBroadcastArpShortIntervalNumber OBJECT-TYPE
			SYNTAX INTEGER
			ACCESS read-write
			STATUS mandatory
			DESCRIPTION
				"The number of broadcast ARPs the switch should send in short interval time,
				when not knowing the MAC address of the device"
			DEFVAL { 5 }
			::= { scGenGroupRspEntry 8 }

		scGenGroupRspBroadcastArpLongInterval OBJECT-TYPE
			SYNTAX INTEGER
			ACCESS read-write
			STATUS mandatory
			DESCRIPTION
				"The interval in which the switch should send broadcast ARPs to the device
				when the device does not respond to unicast ARPs, in 100mSec units."
			DEFVAL { 150 }
			::= { scGenGroupRspEntry 9 }

		scGenGroupRspPeriodicPingsBoxIpAddress OBJECT-TYPE
			SYNTAX IpAddress
			ACCESS read-write
			STATUS mandatory
			DESCRIPTION
				"This MIB-item is the IP-address that the P330 box uses in order to periodically ping to devices
				Default value for IP Address is 0.0.0.0 "
			::= { scGenGroupRspEntry 10 }

		scGenGroupRspPeriodicPingsDestinationIpAddress OBJECT-TYPE
			SYNTAX IpAddress
			ACCESS read-write
			STATUS mandatory
			DESCRIPTION
				"This MIB-item sets an IpAddress that the devices will be configured to periodically ping to.
				The switch will be responsible to reply to ARP-queries concerning this IP-address,
				and which were issued by devices directly attached to it.
				A value of 0.0.0.0 in this Mib Item means that it does not describe an existing IpAddress.
				Default value for IP Address is 0.0.0.0 "
			::= { scGenGroupRspEntry 11 }

		scGenGroupRspMode OBJECT-TYPE
			SYNTAX INTEGER
				{
				rsp-module-mode-role-A(1),
				rsp-modue-mode-role-B(2),
				notSupported(255)
				}
			ACCESS read-write
			STATUS mandatory
			DESCRIPTION
				"Sets the mode of the module from the RSP-application prespective. Possible modes are:
				RSP-module-mode-role-A - means that the ports of this module perform the
				RSP scheme for a device connected through a repeater, in role A (primary role).
				RSP-module-mode-role-B - means that the ports of this module perform the
				RSP scheme for a device connected through a repeater, in role B (secondary role)."
			DEFVAL { rsp-module-mode-role-A }
			::= { scGenGroupRspEntry 12 }

-- Adding extension to 802.1x multi-supplicant mode.
		scGenGroupDot1xTable OBJECT-TYPE
			SYNTAX SEQUENCE OF ScGenGroupDot1xEntry
			ACCESS not-accessible
			STATUS mandatory
			DESCRIPTION
				"This table includes additional information for the extension of 802.1x multi-supplicant
				mode."
			::= { scGenGroup 5 }

		scGenGroupDot1xEntry OBJECT-TYPE
			SYNTAX ScGenGroupDot1xEntry
			ACCESS not-accessible
			STATUS mandatory
			DESCRIPTION
				"This entry includes information about 802.1x supplicants connected to
				a device/module."
			INDEX { scGenGroupDot1xGroupId }
			::= { scGenGroupDot1xTable 1 }

		ScGenGroupDot1xEntry ::=
			SEQUENCE {
				scGenGroupDot1xGroupId
					INTEGER,
				scGenGroupDot1xSystemMaxNumSupplicant
					INTEGER,
				scGenGroupDot1xCurrentNumSupplicant
					INTEGER,
				scGenGroupDot1xCurrentNumAuthenticatedSupplicant
					INTEGER,
				scGenGroupDot1xCurrentNumAuthenticatingSupplicant
					INTEGER
				}

		scGenGroupDot1xGroupId OBJECT-TYPE
			SYNTAX INTEGER
			ACCESS read-only
			STATUS mandatory
			DESCRIPTION
				"Unique Id of the group in the scGenGroupRspTable.
				Equals the number of the slot by which the group is accessed."
			::= { scGenGroupDot1xEntry 1 }

     	scGenGroupDot1xSystemMaxNumSupplicant OBJECT-TYPE
    		SYNTAX      INTEGER
    		ACCESS  read-only
    		STATUS      mandatory
    		DESCRIPTION
        		"The total number of supplicants allowed in the specific group. "
        	::= { scGenGroupDot1xEntry 2 }

        scGenGroupDot1xCurrentNumSupplicant OBJECT-TYPE
    		SYNTAX      INTEGER
    		ACCESS  read-only
    		STATUS      mandatory
    		DESCRIPTION
        		"The total number of supplicants connected in the specific group. "
        	::= { scGenGroupDot1xEntry 3 }


        scGenGroupDot1xCurrentNumAuthenticatedSupplicant OBJECT-TYPE
    		SYNTAX      INTEGER
    		ACCESS  read-only
    		STATUS      mandatory
    		DESCRIPTION
        		"The total number of authenticated supplicants connected in the specific group. "
        	::= { scGenGroupDot1xEntry 4 }

        scGenGroupDot1xCurrentNumAuthenticatingSupplicant OBJECT-TYPE
    		SYNTAX      INTEGER
    		ACCESS  read-only
    		STATUS      mandatory
    		DESCRIPTION
        		"The total number of authenticating supplicants connected in the specific group. "
        	::= { scGenGroupDot1xEntry 5 }

--      scGenPort table
--
--
		scGenPort OBJECT IDENTIFIER ::= { scGen 4 }

		scGenPortTable OBJECT-TYPE
			SYNTAX SEQUENCE OF ScGenPortEntry
			ACCESS not-accessible
			STATUS mandatory
			DESCRIPTION
				"Table of attributes which define general configuration
				information about a single SC based port."
			::= { scGenPort 1 }

		scGenPortEntry OBJECT-TYPE
			SYNTAX ScGenPortEntry
			ACCESS not-accessible
			STATUS mandatory
			DESCRIPTION
				"An entry in the table, containing data about a single Port."
			INDEX { scGenPortGroupId, scGenPortId }
			::= { scGenPortTable 1 }

		ScGenPortEntry ::=
			SEQUENCE {
				scGenPortGroupId
					INTEGER,
				scGenPortId
					INTEGER,
				scGenPortVLAN
					INTEGER,
				scGenPortPriority
					INTEGER,
				scGenPortSetDefaults
					INTEGER,
				scGenPortBackbone
					INTEGER,
				scGenPortCopyMode
					INTEGER,
				scGenPortCopyDestination
					INTEGER,
				scGenPortLinkAggregationNumber
					INTEGER,
				scGenPortSendBridgedPackets
					INTEGER,
				scGenPortVLANEgressStaticConfiguration
					OCTET STRING,
				scGenPortStaticVLANBinding
					INTEGER,
				scGenPortSecId
					INTEGER,
				scGenPortMaxLagsOnSec
					INTEGER,
				scGenPortGenericTrap
					INTEGER,
				scGenPortLACPMode
					INTEGER,
				scGenPortLastIntruderSourceAddr
					OCTET STRING,
				scGenPortSecurityMode
					INTEGER,
				scGenPortSTA
					INTEGER,
				scGenPortLagCapability
					OCTET STRING,
				scGenPortCapability
					OCTET STRING,
				scGenPortSLDAdminStatus
					INTEGER,
				scGenPortSLDStatus
					INTEGER,
				scGenPortCopyClassModuleLevel
					OCTET STRING,
				scGenPortCopyClassStackLevel
					OCTET STRING
			 }

		scGenPortGroupId OBJECT-TYPE
			SYNTAX INTEGER
			ACCESS read-only
			STATUS mandatory
			DESCRIPTION
				"Id of the group to which the port belongs."
			::= { scGenPortEntry 1 }

		scGenPortId OBJECT-TYPE
			SYNTAX INTEGER
			ACCESS read-only
			STATUS mandatory
			DESCRIPTION
				"Unique Id of the port in the scEthPortTable."
			::= { scGenPortEntry 2 }

		scGenPortVLAN OBJECT-TYPE
			SYNTAX INTEGER (0..4095)
			ACCESS read-write
			STATUS mandatory
			DESCRIPTION
				" The Virtual LAN number of the Port.
				The value 0 means Generic ( But can communicate with Global !).
				The value '255' means Global."
			DEFVAL { 0 }
			::= { scGenPortEntry 3 }

		scGenPortPriority OBJECT-TYPE
			SYNTAX INTEGER
				{
				regular(1),
				high(2),
				userPriority1(3),
				userPriority2(4),
				userPriority3(5),
				userPriority4(6),
				userPriority5(7),
				userPriority6(8),
				userPriority7(9),
				userPriority8(10),
				notSupported(255)
				}
			ACCESS read-write
			STATUS mandatory
			DESCRIPTION
				" The priority level of the packets send by the Port."
			DEFVAL { regular }
			::= { scGenPortEntry 4 }

		scGenPortSetDefaults OBJECT-TYPE
			SYNTAX INTEGER
				{
				on(1),
				off(2),
				notSupported(255)
				}
			ACCESS read-write
			STATUS mandatory
			DESCRIPTION
				"Set all port parameters in the XSwitch module, to their default values.
				This item is used for ports that are managed by Sub-agents.
				This item will always return a value of off(2), since it acts
				like a toggle switch."
			DEFVAL { off }
			::= { scGenPortEntry 5 }

		scGenPortBackbone OBJECT-TYPE
			SYNTAX INTEGER
				{
				on(1),
				off(2),
				notSupported(255)
				}
			ACCESS read-only
			STATUS mandatory
			DESCRIPTION
				" The type of the Xswitch port. 'on' indicates that the port was discovered
				by VIDP as backbone port."
			DEFVAL { off }
			::= { scGenPortEntry 6 }

		scGenPortCopyMode OBJECT-TYPE
			SYNTAX INTEGER
				{
				enable(1),
				disable(2),
				notSupported(255)
				}
			ACCESS read-write
			STATUS mandatory
			DESCRIPTION
				" Enable /Disable the Copy Port mode in the Sub-Agent."
			DEFVAL { disable }
			::= { scGenPortEntry 7 }

		scGenPortCopyDestination OBJECT-TYPE
			SYNTAX INTEGER (0..8092)
			ACCESS read-write
			STATUS mandatory
			DESCRIPTION
				" The destination of the copied information.
				The destination can be another port or the Agent acting as an RMON probe.
				The value of this item is: LSB Byte= sniffer channel number,
							Next Byte= sniffer device number.
				When sniffer device number=31, the destination is the Agent."
			::= { scGenPortEntry 8 }

		scGenPortLinkAggregationNumber OBJECT-TYPE
			SYNTAX INTEGER (0..255)
			ACCESS read-write
			STATUS mandatory
			DESCRIPTION
				"The Link Aggregation Group (LAG) number, to which the Port belongs.
				The value 0 means that this port is not part of a LAG. This is also the default."
			::= { scGenPortEntry 9 }

		scGenPortSendBridgedPackets OBJECT-TYPE
			SYNTAX INTEGER
				{
				on(1),
				off(2),
				notSupported(255)
				}
			ACCESS read-write
			STATUS mandatory
			DESCRIPTION
				"When set to on(1), the port will transmit to the line bridged frames
				(for which their secondary	VLAN was 0xFFE internally).
				This is the case for ports connected to a station or to another switch
				that has no bridging capabilities. When set to off(2), the port will reject
				the bridged frames, by not sending them to the line.
				This is the case for ports connected to another switch that has its own bridging capabilities.
				Default value is on(1)."
			::= { scGenPortEntry 10 }

		scGenPortVLANEgressStaticConfiguration OBJECT-TYPE
			SYNTAX OCTET STRING (SIZE (32))
			ACCESS read-write
			STATUS mandatory
			DESCRIPTION
				"A bitmap defining the VLANs, for which the port is member in their Egress Tables.
				The first bit is for VLAN 0, the second bit for VLAN 1, and so on.
				If the port is member in the Egress Table of a specified VLAN,
				then the value of the associated bit is 1, otherwise 0.
				The actual VLAN Table configuration, according to this item,
				is done only when  scGenPortStaticVLANBinding is enabled."
			::= { scGenPortEntry 11 }

		scGenPortStaticVLANBinding OBJECT-TYPE
			SYNTAX INTEGER
				{
				enable(1),
				disable(2),
				notSupported(255)
				}
			ACCESS read-write
			STATUS mandatory
			DESCRIPTION
				" This object defines whether Static VLAN Binding is enabled or disabled on the port.
				If enabled, the port is member in the Egress List of the VLANs, as specified in
				scGenPortVLANEgressStaticConfiguration, in addition to its Port VLAN.
				If disabled, the port is member in the Egress List of the VLANs,
				according to the VLAN Tagging mode of the port - i.e. if VLAN Tagging mode is Clear,
				then the Port is member in the Egress List of only the Port VLAN.
				If VLAN Tagging mode is 802.1Qtagging, then the Port is member in the Egress List of all VLANs."
			DEFVAL { disable }
			::= { scGenPortEntry 12 }

		scGenPortSecId OBJECT-TYPE
			SYNTAX INTEGER (1..255)
			ACCESS read-only
			STATUS mandatory
			DESCRIPTION
				"The identification number (per module) of the switching chip to which the port belongs."
			::= { scGenPortEntry 13 }

		scGenPortMaxLagsOnSec OBJECT-TYPE
			SYNTAX INTEGER (0..255)
			ACCESS read-only
			STATUS mandatory
			DESCRIPTION
				"The theoretic maximum number of LAGs that can be defined over the switching chip to which the port
				belongs. The value is fixed according to the switching chip type:
				For the Timpani chip, the value is 1.
				For the Guitar chip, the value is 2."
			::= { scGenPortEntry 14 }

		scGenPortGenericTrap OBJECT-TYPE
			SYNTAX INTEGER
				{
				enable(1),
				disable(2)
				}
			ACCESS read-write
			STATUS mandatory
			DESCRIPTION
				"The value of this attribute determines whether or not the agent sends the snmp generic traps 2 and 3,
				for link down/up events on this port."
			::= { scGenPortEntry 15 }

		scGenPortLACPMode OBJECT-TYPE
			SYNTAX INTEGER
				{
				enable(1),
				disable(2)
				}
			ACCESS read-write
			STATUS mandatory
			DESCRIPTION
				"The value of this attribute determines whether the port exchanges LACPDU messages,
				in agreement with the scGenGroupLACPMode MIB."
			::= { scGenPortEntry 16 }

		scGenPortLastIntruderSourceAddr OBJECT-TYPE
			SYNTAX OCTET STRING (SIZE (0..1))
			ACCESS read-only
			STATUS mandatory
			DESCRIPTION
				"Ethernet source address of the last intrusion attempt at this port.
				The value of this item will be 000000 (a string of 6 zeros) if security mode is
				disable or no security violation at this port. "
			::= { scGenPortEntry 17 }

		scGenPortSecurityMode OBJECT-TYPE
			SYNTAX INTEGER
				{
				nonSecurityMode(1),
				securityMode(2),
				notSupported(255)
				}
			ACCESS read-write
			STATUS mandatory
			DESCRIPTION
				"Security mode assigned to this port.
				nonSecurityMode - do not perform intrusion control security mechanism on this port.
				securityMode - perform intrusion control security mechanism and trap the console
				in case of  security violation,
				if both scGenGroupSecurityMode and scGenSwitchSecurityMode are in this mode too."
			::= { scGenPortEntry 18 }

		scGenPortSTA OBJECT-TYPE
			SYNTAX INTEGER
				{
				enable(1),
				disable(2),
				notSupported(255)
				}
			ACCESS read-write
			STATUS mandatory
			DESCRIPTION
				" Enable /Disable the Spanning Tree protocol for this port,
				meaningless when disabled at the switch level via the scGenSwitchSTA MIB."
			DEFVAL { enable }
			::= { scGenPortEntry 19 }

		scGenPortLagCapability OBJECT-TYPE
			SYNTAX OCTET STRING
			ACCESS read-only
			STATUS mandatory
			DESCRIPTION
				"An octet string with the size of the maximum number of LAGs on the device.
				Each bit represents a LAG which the port may be associated with (a member of)."
			::= { scGenPortEntry 20 }

		scGenPortCapability OBJECT-TYPE
			SYNTAX OCTET STRING
			ACCESS read-only
			STATUS mandatory
			DESCRIPTION
				"Port capability bit mask, where each bit represent the capability of the port:
				Bit #1 - 10Mbps speed support
				Bit #2 - 100Mbps speed support
				Bit #3 - 1000Mbps speed support
				Bit #4 - 10000Mbps speed support

				Bit #9 - 2 queues support
				Bit #10 - 4 queues support
				Bit #11 - 8 queue support

				Bit #16 - CopyPort destination port
				Bit #17 - CopyPort Tx support
				Bit #18 - CopyPort Rx support
				Bit #19 - CopyPort Tx&Rx support
				Bit #20 - CopyPort filtering support

				Bit #21 - CopyPort Destination drop events
				Bit #22 - CopyPort Errored frames
				Bit #23 - CopyPort unaltered frames
				Bit #24 - CopyPort all good frames

				Bit #25 - Symmetric FC support
				Bit #26 - AsymmetricTx FC support
				Bit #27 - AsymmetricRx FC support"
			::= { scGenPortEntry 21 }

		scGenPortSLDAdminStatus OBJECT-TYPE
			SYNTAX INTEGER
				{
				enabled(1),
				disabled(2)
				}
			ACCESS read-write
			STATUS mandatory
			DESCRIPTION
				"Sets the admin status of each port in the Self Loop Discovery application
				A port which is disbaled does not send LDDU .  A port which is enabled sends
				 LDDU and migth turn to blocking if a SLD is discovered."
			DEFVAL { enabled }
			::= { scGenPortEntry 22 }

		scGenPortSLDStatus OBJECT-TYPE
			SYNTAX INTEGER
				{
				selfLoop(1),
				noSelfLoop(2),
				notSupported(255)
				}
			ACCESS read-only
			STATUS mandatory
			DESCRIPTION
				"A port which is SLDEnabled can be in SelfLoop or NoSelfLoop mode .
				if the port is SLD disabled it will return notSupported."
			::= { scGenPortEntry 23 }

		scGenPortCopyClassModuleLevel OBJECT-TYPE
			SYNTAX OCTET STRING
			ACCESS read-only
			STATUS mandatory
			DESCRIPTION
				"This variable indicates the class of each kind of port on any kind
				of module for COPY PORT command at the module level. This MIB is defined
				for module level copy ports.
				This string is made of 16 bits. Each bit indicates a different class of ports.

				For example: P330 uses class A (1000...000) for all its ports.
				A P334T-ML will use class A (1000...000) for ports 1-24,
				class B (0100...000) for ports 25-48, and class C (0010...000) for ports 51-52."
			::= { scGenPortEntry 24 }

		scGenPortCopyClassStackLevel OBJECT-TYPE
			SYNTAX OCTET STRING
			ACCESS read-only
			STATUS mandatory
			DESCRIPTION
				"The first bit of this string indicates whether the requested port may
				be copied to another port in the stack or not.
				When a module is requested to copy a port to another module's port,
				it answers whether the port is capable of (100...000)
				or incapable of (000...000) doing so. The remaining bits are reserved."
			::= { scGenPortEntry 25 }

--       genPortRspTable
		scGenPortRspTable OBJECT-TYPE
			SYNTAX SEQUENCE OF ScGenPortRspEntry
			ACCESS not-accessible
			STATUS mandatory
			DESCRIPTION
				"Table of attributes which define general configuration
				information about a single SC based port."
			::= { scGenPort 2 }

		scGenPortRspEntry OBJECT-TYPE
			SYNTAX ScGenPortRspEntry
			ACCESS not-accessible
			STATUS mandatory
			DESCRIPTION
				"An entry in the table, containing data about a single Port."
			INDEX { scGenPortRspGroupId, scGenPortRspId }
			::= { scGenPortRspTable 1 }

		ScGenPortRspEntry ::=
			SEQUENCE {
				scGenPortRspGroupId
					INTEGER,
				scGenPortRspId
					INTEGER,
				scGenPortRspMode
					INTEGER
			 }

		scGenPortRspGroupId OBJECT-TYPE
			SYNTAX INTEGER
			ACCESS read-only
			STATUS mandatory
			DESCRIPTION
				"Id of the group to which the port belongs."
			::= { scGenPortRspEntry 1 }

		scGenPortRspId OBJECT-TYPE
			SYNTAX INTEGER
			ACCESS read-only
			STATUS mandatory
			DESCRIPTION
				"Unique Id of the port in the scGenPortRspTable."
			::= { scGenPortRspEntry 2 }

		scGenPortRspMode OBJECT-TYPE
			SYNTAX INTEGER
				{
				regular(1),
				rsp-mode-role-A(2),
				rsp-mode-role-B(3),
				device-mode(4),
				notSupported(255)
				}
			ACCESS read-write
			STATUS mandatory
			DESCRIPTION
				"Sets the mode of the port from the RSP-application perspective. Possible modes are:
				Regular - means that this is a regular port that does not participate in the RSP scheme,
				RSP-mode-role-A - means that this port performs the RSP
				scheme for a device connected through a repeater, in role A (primary role).
				RSP-mode-role-B - means that this port performs the RSP
				scheme for a device connected through a repeater, in role B (secondary role).
				device-mode - means that this port performs the RSP scheme for a device with two interfaces."
			DEFVAL { regular }
			::= { scGenPortRspEntry 3 }

		scGenPortSecureMACTable OBJECT-TYPE
			SYNTAX SEQUENCE OF ScGenPortSecureMACEntry
			ACCESS not-accessible
			STATUS mandatory
			DESCRIPTION
				"Table of Secure MAC list for a single SC based port."
			::= { scGenPort 3 }

		scGenPortSecureMACEntry OBJECT-TYPE
			SYNTAX ScGenPortSecureMACEntry
			ACCESS not-accessible
			STATUS mandatory
			INDEX { scGenPortSecureGroupID, scGenPortSecurePortId, scGenPortSecureMAC }
			::= { scGenPortSecureMACTable 1 }

		ScGenPortSecureMACEntry ::=
			SEQUENCE {
				scGenPortSecureGroupID
					INTEGER,
				scGenPortSecurePortId
					INTEGER,
				scGenPortSecureMAC
					MacAddress,
				scGenPortSecureMACStatus
					RowStatus
			 }

		scGenPortSecureGroupID OBJECT-TYPE
			SYNTAX INTEGER (1..10)
			ACCESS read-only
			STATUS mandatory
			DESCRIPTION
				"Unique Id of the group in the scGenGroupSecureMACTable.
				Equals the number of the slot by which the group is accessed."
			::= { scGenPortSecureMACEntry 1 }

		scGenPortSecurePortId OBJECT-TYPE
			SYNTAX INTEGER (1..1024)
			ACCESS read-only
			STATUS mandatory
			::= { scGenPortSecureMACEntry 2 }

		scGenPortSecureMAC OBJECT-TYPE
			SYNTAX MacAddress
			ACCESS read-only
			STATUS mandatory
			::= { scGenPortSecureMACEntry 3 }

		scGenPortSecureMACStatus OBJECT-TYPE
			SYNTAX RowStatus
			ACCESS read-write
			STATUS mandatory
			DESCRIPTION
				"This variable defines the status of the row.
				The values of this variables are defined and handled,
				according to the definitions in the  IETF draft:
				Row creation with SNMPv1, from 19 October 1993.
				The createAndGo value is not supported.
				"
			::= { scGenPortSecureMACEntry 4 }


-- Adding extension to 802.1x multi/single supplicant application.
		scGenPortDot1xMACTable OBJECT-TYPE
			SYNTAX SEQUENCE OF ScGenPortDot1xMACEntry
			ACCESS not-accessible
			STATUS mandatory
			DESCRIPTION
				"Table of 802.1x multi/single supplicant MACs connected to a single SC based port."
			::= { scGenPort 4 }

		scGenPortDot1xMACEntry OBJECT-TYPE
			SYNTAX ScGenPortDot1xMACEntry
			ACCESS not-accessible
			STATUS mandatory
			INDEX { scGenPortDot1xMACGroupID, scGenPortDot1xMACPortId, scGenPortDot1xMAC }
			::= { scGenPortDot1xMACTable 1 }

		ScGenPortDot1xMACEntry ::=
			SEQUENCE {
				scGenPortDot1xMACGroupID
					INTEGER,
				scGenPortDot1xMACPortId
					INTEGER,
				scGenPortDot1xMAC
					MacAddress,
				scGenPortDot1xMACAuthPaeState
					INTEGER,
				scGenPortDot1xMACAuthBackendAuthState
					INTEGER,
				scGenPortDot1xAuthAuthControlledPortStatus
					PaeControlledPortStatus
					 }

		scGenPortDot1xMACGroupID OBJECT-TYPE
			SYNTAX INTEGER (1..10)
			ACCESS read-only
			STATUS mandatory
			DESCRIPTION
				"Unique Id of the group in the scGenGroupDot1xMACTable.
				Equals the number of the slot by which the group is accessed."
			::= { scGenPortDot1xMACEntry 1 }

		scGenPortDot1xMACPortId OBJECT-TYPE
			SYNTAX INTEGER (1..1024)
			ACCESS read-only
			STATUS mandatory
			::= { scGenPortDot1xMACEntry 2 }

		scGenPortDot1xMAC OBJECT-TYPE
			SYNTAX MacAddress
			ACCESS read-only
			STATUS mandatory
			::= { scGenPortDot1xMACEntry 3 }

		scGenPortDot1xMACAuthPaeState OBJECT-TYPE
    		SYNTAX      INTEGER {
                    initialize(1),
                    disconnected(2),
                    connecting(3),
                    authenticating(4),
                    authenticated(5),
                    aborting(6),
                    held(7),
                    forceAuth(8),
                    forceUnauth(9)
                }
    		ACCESS  read-only
    		STATUS      mandatory
    		DESCRIPTION
        	"The current value of the 802.1x multi/single supplicant MAC/port state
        	machine. The MIB is identical to the dot1xAuthPaeState from IEEE8021-PAE-MIB."
    		REFERENCE
        	"9.4.1, Authenticator PAE state"
    		::= { scGenPortDot1xMACEntry 4 }

		scGenPortDot1xMACAuthBackendAuthState OBJECT-TYPE
    		SYNTAX      INTEGER {
                    request(1),
                    response(2),
                    success(3),
                    fail(4),
                    timeout(5),
                    idle(6),
                    initialize(7)
                }
    		ACCESS  read-only
    		STATUS      mandatory
    		DESCRIPTION
        		"The current state of the Backend Authentication
        		state machine for the relevant 802.1x multi/single supplicant MAC/port.
        		The MIB is identical to the dot1xAuthBackendAuthState from IEEE8021-PAE-MIB."
    		REFERENCE
        		"9.4.1, Backend Authentication state"
    		::= { scGenPortDot1xMACEntry 5 }

    	scGenPortDot1xAuthAuthControlledPortStatus OBJECT-TYPE
    		SYNTAX      PaeControlledPortStatus
    		ACCESS  read-only
    		STATUS      mandatory
    		DESCRIPTION
        		"The current value of the controlled 802.1x single-supplicant MAC
        		status parameter for the MAC.
        		The MIB is identical to the dot1xAuthAuthControlledPortStatus
        		from IEEE8021-PAE-MIB.
        		Note in multi supplicant this MIB returns no-such-instance."
    		REFERENCE
        		"9.4.1, AuthControlledPortStatus"
    		::= { scGenPortDot1xMACEntry 6 }


		scGenPortDot1xPortTable OBJECT-TYPE
			SYNTAX SEQUENCE OF ScGenPortDot1xPortEntry
			ACCESS not-accessible
			STATUS mandatory
			DESCRIPTION
				"Table of 802.1x multi-supplicant configuration and status of
				a single SC based port."
			::= { scGenPort 5 }

		scGenPortDot1xPortEntry OBJECT-TYPE
			SYNTAX ScGenPortDot1xPortEntry
			ACCESS not-accessible
			STATUS mandatory
			INDEX { scGenPortDot1xPortGroupID, scGenPortDot1xPortPortId }
			::= { scGenPortDot1xPortTable 1 }

		ScGenPortDot1xPortEntry ::=
			SEQUENCE {
				scGenPortDot1xPortGroupID
					INTEGER,
				scGenPortDot1xPortPortId
					INTEGER,
				scGenPortDot1xPortMode
					INTEGER,
				scGenPortDot1xPortNumSupplicants
					INTEGER,
				scGenPortDot1xPortNumAuthenticatedSupplicants
					INTEGER,
				scGenPortDot1xPortNumAuthenticatingSupplicants
					INTEGER
					 }

		scGenPortDot1xPortGroupID OBJECT-TYPE
			SYNTAX INTEGER (1..10)
			ACCESS not-accessible
			STATUS mandatory
			DESCRIPTION
				"Unique Id of the group in the scGenGroupDot1xPortTable.
				Equals the number of the slot by which the group is accessed."
			::= { scGenPortDot1xPortEntry 1 }

		scGenPortDot1xPortPortId OBJECT-TYPE
			SYNTAX INTEGER (1..1024)
			ACCESS not-accessible
			STATUS mandatory
			::= { scGenPortDot1xPortEntry 2 }

        scGenPortDot1xPortMode OBJECT-TYPE
    		SYNTAX      INTEGER {
                    port(1),
                    mac(2)
                }
    		ACCESS  read-write
    		STATUS      mandatory
    		DESCRIPTION
        		"The authentication method used for the port.
        		Port-Based-Authentication is used for the standard single supplicant mode.
        		MAC-Based-Authentication is used for the multi supplicant mode to support
        		a few supplicants connected to the port.
        		DEFAULT is port(1)"
        	DEFVAL { port }
    		::= { scGenPortDot1xPortEntry 3 }

		scGenPortDot1xPortNumSupplicants OBJECT-TYPE
    		SYNTAX      INTEGER
    		ACCESS  read-only
    		STATUS      mandatory
    		DESCRIPTION
        		"Total number of supplicants connected to the port."
        	::= { scGenPortDot1xPortEntry 4 }

        scGenPortDot1xPortNumAuthenticatedSupplicants OBJECT-TYPE
    		SYNTAX      INTEGER
    		ACCESS  read-only
    		STATUS      mandatory
    		DESCRIPTION
        		"Total number of authenticated supplicants connected to the port."
        	::= { scGenPortDot1xPortEntry 5 }

		scGenPortDot1xPortNumAuthenticatingSupplicants OBJECT-TYPE
    		SYNTAX      INTEGER
    		ACCESS  read-only
    		STATUS      mandatory
    		DESCRIPTION
        		"Total number of authenticating supplicants connected to the port. I.e. clients
        		which are not authenticated yet."
        	::= { scGenPortDot1xPortEntry 6 }


		scGenSwitch OBJECT IDENTIFIER ::= { scGen 5 }

		scGenSwitchTable OBJECT-TYPE
			SYNTAX SEQUENCE OF ScGenSwitchEntry
			ACCESS not-accessible
			STATUS mandatory
			DESCRIPTION
				"Table of attributes which define information about
				a single XSwitch in SC based devices."
			::= { scGenSwitch 1 }

		scGenSwitchEntry OBJECT-TYPE
			SYNTAX ScGenSwitchEntry
			ACCESS not-accessible
			STATUS mandatory
			DESCRIPTION
				"An entry in the table, containing data about a single XSwitch."
			INDEX { scGenSwitchId }
			::= { scGenSwitchTable 1 }

		ScGenSwitchEntry ::=
			SEQUENCE {
				scGenSwitchId
					INTEGER,
				scGenSwitchCopyMode
					INTEGER,
				scGenSwitchCopySource
					INTEGER,
				scGenSwitchCopyDestination
					INTEGER,
				scGenSwitchSetDefaults
					INTEGER,
				scGenSwitchVIDP
					INTEGER,
				scGenSwitchType
					INTEGER,
				scGenSwitchMasterId
					INTEGER,
				scGenSwitchReset
					INTEGER,
				scGenSwitchNumberOfLoads
					INTEGER,
				scGenSwitchAgVLAN
					INTEGER,
				scGenSwitchVLANList
					OCTET STRING,
				scGenSwitchSTA
					INTEGER,
				scGenSwitchSecurityMode
					INTEGER,
				scGenSwitchFindQuery
					OCTET STRING,
				scGenSwitchFindResult
					OCTET STRING,
				scGenSwitchSWRdChange
					OCTET STRING,
				scGenSwitchDefaultVLAN
					INTEGER,
				scGenSwitchVLANBridging
					INTEGER,
				scGenSwitchOldVersionModules
					DisplayString,
				scGenSwitchVIDPNonSupportedModules
					DisplayString,
				scGenSwitchSTANonSupportedModules
					DisplayString,
				scGenSwitchIDSNonSupportedModules
					DisplayString,
				scGenSwitchMcFilter
					INTEGER,
				scGenSwitchMcFilterHostAgingTime
					INTEGER,
				scGenSwitchMcFilterRouterAgingTime
					INTEGER,
				scGenSwitchMcFilterDelayTime
					INTEGER,
				scGenSwitchLACPMode
					INTEGER,
				scGenSwitchSecurityModePermit
					INTEGER,
				scGenSwitchFastAgingOnRemoteTopChg
					INTEGER,
				scGenSwitchGigaMode
					INTEGER,
				scGenSwitchCAMClear
					INTEGER,
				scGenSwitchWelcomeMessage
					DisplayString,
				scGenSwitchPromptMessage
					DisplayString,
				scGenSwitchMacAging
					INTEGER,
				scGenSwitchSecurityAction
					INTEGER,
				scGenSwitchDot1xPortMaxSuppNum
					INTEGER,
    			scGenSwitchDot1xLldpTxVlanName
    				INTEGER
			 }

		scGenSwitchId OBJECT-TYPE
			SYNTAX INTEGER (1..255)
			ACCESS read-only
			STATUS mandatory
			DESCRIPTION
				"Index which identifies the XSwitch for which this entry contains information.
				This value is never greater than chNumberOfXSwitches."
			::= { scGenSwitchEntry 1 }

		scGenSwitchCopyMode OBJECT-TYPE
			SYNTAX INTEGER
				{
				enable(1),
				disable(2),
				notSupported(255)
				}
			ACCESS read-write
			STATUS mandatory
			DESCRIPTION
				" Enable /Disable the Copy Port mode in the XSwitch."
			DEFVAL { disable }
			::= { scGenSwitchEntry 2 }

		scGenSwitchCopySource OBJECT-TYPE
			SYNTAX INTEGER
			ACCESS read-write
			STATUS mandatory
			DESCRIPTION
				" The port in the switch that is being copied.
				All received and transmit packets on the port( including local traffic ) are copied to
				the defined destination, besides their normal destination.
				The value of this item is: 1024*S+P,
				where S is the slot number in the hub and P the port within the slot."
			::= { scGenSwitchEntry 3 }

		scGenSwitchCopyDestination OBJECT-TYPE
			SYNTAX INTEGER
			ACCESS read-write
			STATUS mandatory
			DESCRIPTION
				" The destination of the copied information.
				The destination can be another port or the Agent acting as an RMON probe.
				The value of this item is: 1024*S+P,
				where S is the slot number in the hub and P is the port within the slot.
				Value 1023 means that the destination is the Agent."
			::= { scGenSwitchEntry 4 }

		scGenSwitchSetDefaults OBJECT-TYPE
			SYNTAX INTEGER
				{
				on(1),
				off(2),
				notSupported(255)
				}
			ACCESS read-write
			STATUS mandatory
			DESCRIPTION
				"Set all port parameters in the XSwitch, to their default values.
				This item will always return a value of off(2), since it acts like a toggle switch."
			DEFVAL { off }
			::= { scGenSwitchEntry 5 }

		scGenSwitchVIDP OBJECT-TYPE
			SYNTAX INTEGER
				{
				enable(1),
				disable(2),
				notSupported(255)
				}
			ACCESS read-write
			STATUS mandatory
			DESCRIPTION
				" Enable /Disable the VIDP protocol supported in the XSwitch."
			DEFVAL { enable }
			::= { scGenSwitchEntry 6 }

		scGenSwitchType OBJECT-TYPE
			SYNTAX INTEGER
				{
				ethernet(1),
				token-ring(2),
				notSupported(255)
				}
			ACCESS read-only
			STATUS mandatory
			DESCRIPTION
				"This attribute defines the type of the Xswitch."
			::= { scGenSwitchEntry 7 }

		scGenSwitchMasterId OBJECT-TYPE
			SYNTAX INTEGER (1..255)
			ACCESS read-only
			STATUS mandatory
			DESCRIPTION
				"This attribute defines which module in the Xswitch take the role of the Master.
				It is equal  to the slot number of the Xswitch Master."
			::= { scGenSwitchEntry 8 }

		scGenSwitchReset OBJECT-TYPE
			SYNTAX INTEGER
				{
				on(1),
				off(2),
				notSupported(255)
				}
			ACCESS read-write
			STATUS mandatory
			DESCRIPTION
				"Setting this attribute to `on' will cause a reset to the Xswitch. Default value is 'off'."
			::= { scGenSwitchEntry 9 }

		scGenSwitchNumberOfLoads OBJECT-TYPE
			SYNTAX INTEGER (1..255)
			ACCESS read-only
			STATUS mandatory
			DESCRIPTION
				"This attribute identifies the total number of loads of that Xswitch.
				There is a maximum budget of 30 loads on an single Xswitch."
			::= { scGenSwitchEntry 10 }

		scGenSwitchAgVLAN OBJECT-TYPE
			SYNTAX INTEGER (0..4095)
			ACCESS read-write
			STATUS mandatory
			DESCRIPTION
				" The Virtual LAN number of the Agent's internal interface in the switch.
				The value 0 means Generic (But can communicate with Global !).
				The value '255' means Global."
			DEFVAL { 255 }
			::= { scGenSwitchEntry 11 }

		scGenSwitchVLANList OBJECT-TYPE
			SYNTAX OCTET STRING (SIZE (32))
			ACCESS read-only
			STATUS mandatory
			DESCRIPTION
				"A bitmap defining the status of the virtual LANs in the
				Virtual LAN Table. The first bit is for Virtual LAN 0, the
				second for Virtual LAN 1, and so on. If the Virtual LAN
				exists in the hub the value of the associated bit is 1, otherwise 0."
			::= { scGenSwitchEntry 12 }

		scGenSwitchSTA OBJECT-TYPE
			SYNTAX INTEGER
				{
				enable(1),
				disable(2),
				notSupported(255)
				}
			ACCESS read-write
			STATUS mandatory
			DESCRIPTION
				" Enable /Disable the Spanning Tree protocol support in the switch."
			DEFVAL { disable }
			::= { scGenSwitchEntry 13 }

		scGenSwitchSecurityMode OBJECT-TYPE
			SYNTAX INTEGER
				{
				nonSecurityMode(1),
				securityMode(2),
				notSupported(255)
				}
			ACCESS read-write
			STATUS mandatory
			DESCRIPTION
				" This item defines the Security mode per stack.
				nonSecurityMode - all ports in the stack are not secure.
				securityMode - all ports in the stack are secure according to their scGenPortSecurityMode MIB's value."
			::= { scGenSwitchEntry 14 }

		scGenSwitchFindQuery OBJECT-TYPE
			SYNTAX OCTET STRING
			ACCESS read-write
			STATUS mandatory
			DESCRIPTION
				"An address to be searched for by the Agent.
				The Agent will start look for the address when the value is
				different than Null.
				The string format is:
				1st byte: address type - 0=MAC, 1=IP
				Next bytes: the address. (for MAC: next 6 bytes,
				for IP: next 4 bytes)."
			::= { scGenSwitchEntry 15 }

		scGenSwitchFindResult OBJECT-TYPE
			SYNTAX OCTET STRING
			ACCESS read-only
			STATUS mandatory
			DESCRIPTION
				"The search result. The result string format is:
				1st byte: address type - 0=MAC, 1=IP.
				Next bytes: the address. (for MAC: next 6 bytes,
				for IP: next 4 bytes)
				7-th byte (for MAC) or 5-th byte (for IP): number of ports with
				the specified address.
				Every next two bytes will indicate the slot and port number.
				8-th byte (for MAC) or 6-th byte (for IP): slot number.
				9-th byte (for MAC) or 7-th byte (for IP): port number. Etc.
				If the specified address was NOT found, the result will be
				with the 7-th byte (for MAC) or 5-th byte (for IP):  byte equal to _0_."
			::= { scGenSwitchEntry 16 }

		scGenSwitchSWRdChange OBJECT-TYPE
			SYNTAX OCTET STRING
			ACCESS read-write
			STATUS mandatory
			DESCRIPTION
				"A 4-byte octet-string indicating a change performed by the SW Redundancy task.
				The string will include:
				Byte 1: Group1 (module number).
				Byte 2 : Port1
				Byte 3 : Group2
				Byte 4 : port2
				Where group2 port2 are the new enabled port. "
			::= { scGenSwitchEntry 17 }

		scGenSwitchDefaultVLAN OBJECT-TYPE
			SYNTAX INTEGER
				{
				vlan0(1),
				vlan1(2),
				notSupported(255)
				}
			ACCESS read-only
			STATUS mandatory
			DESCRIPTION
				"Attribute describing the Default VLAN configuration on the switch ports.
				The user may change the value of this parameter through the setup terminal.
				Vlan1 is the standard default VLAN for port configuration."
			::= { scGenSwitchEntry 18 }

		scGenSwitchVLANBridging OBJECT-TYPE
			SYNTAX INTEGER
				{
				enable(1),
				disable(2),
				notSupported(255)
				}
			ACCESS read-write
			STATUS mandatory
			DESCRIPTION
				"VLAN Bridging mode should be enabled in all Xswitches in the network, when the user
				wants to support network-wide VLAN Bridging. VLAN Bridging should also be enabled
				in one M-MLS, and PLS-Tagging mode should be set on the backbone ports."
			DEFVAL { disable }
			::= { scGenSwitchEntry 19 }

		scGenSwitchOldVersionModules OBJECT-TYPE
			SYNTAX DisplayString (SIZE (0..32))
			ACCESS read-only
			STATUS mandatory
			DESCRIPTION
				"A list of modules, in ASCII format, that have older software versions than
				necessary in the switch. Module numbers are separated by a comma and a space.
				It is used to inform the user on version inconsistency."
			::= { scGenSwitchEntry 20 }

		scGenSwitchVIDPNonSupportedModules OBJECT-TYPE
			SYNTAX DisplayString (SIZE (0..32))
			ACCESS read-only
			STATUS mandatory
			DESCRIPTION
				"A list of modules, in ASCII format, that do not support the VIDP function.
				Module numbers are separated by a comma and a space.
				It is used to inform the user on possible problems in VIDP function,
				as not all modules in the switch support VIDP."
			::= { scGenSwitchEntry 21 }

		scGenSwitchSTANonSupportedModules OBJECT-TYPE
			SYNTAX DisplayString (SIZE (0..32))
			ACCESS read-only
			STATUS mandatory
			DESCRIPTION
				"A list of modules, in ASCII format, that do not support the STA function.
				Module numbers are separated by a comma and a space.
				It is used to inform the user on possible problems in STA function,
				as not all modules in the switch support STA."
			::= { scGenSwitchEntry 22 }

		scGenSwitchIDSNonSupportedModules OBJECT-TYPE
			SYNTAX DisplayString (SIZE (0..32))
			ACCESS read-only
			STATUS mandatory
			DESCRIPTION
				"A list of modules, in ASCII format, that do not support the IDS function.
				Module numbers are separated by a comma and a space.
				It is used to inform the user on possible problems in IDS function,
				as not all modules in the switch support IDS."
			::= { scGenSwitchEntry 23 }

		scGenSwitchMcFilter OBJECT-TYPE
			SYNTAX INTEGER
				{
				enable(1),
				disable(2),
				notSupported(255)
				}
			ACCESS read-write
			STATUS mandatory
			DESCRIPTION
				"Enable/disable the multicast  filtering mechanism supported in the switch"
			DEFVAL { disable }
			::= { scGenSwitchEntry 24 }

		scGenSwitchMcFilterHostAgingTime OBJECT-TYPE
			SYNTAX INTEGER
			ACCESS read-write
			STATUS mandatory
			DESCRIPTION
				"The Value of the Host-Aging-Time parameter used by the multicast filtering
				mechanism for aging learned multicast filtering information"
			DEFVAL { 600 }
			::= { scGenSwitchEntry 25 }

		scGenSwitchMcFilterRouterAgingTime OBJECT-TYPE
			SYNTAX INTEGER
			ACCESS read-write
			STATUS mandatory
			DESCRIPTION
				"The Value of the Router-Aging-Time parameter used by the multicast filtering
				mechanism for aging learned router-ports information"
			DEFVAL { 1800 }
			::= { scGenSwitchEntry 26 }

		scGenSwitchMcFilterDelayTime OBJECT-TYPE
			SYNTAX INTEGER
			ACCESS read-write
			STATUS mandatory
			DESCRIPTION
				"The Value of the Delay-Time parameter used by the multicast filtering
				mechanism for waiting to all registration requests before applying a filter
				on a specific group"
			DEFVAL { 10 }
			::= { scGenSwitchEntry 27 }

		scGenSwitchLACPMode OBJECT-TYPE
			SYNTAX INTEGER
				{
				enable(1),
				disable(2)
				}
			ACCESS read-write
			STATUS mandatory
			DESCRIPTION
				"The value of this attribute determines whether LACPDU messages can be exchanged by the switch's ports.
				If enabled, the ports will exchange LACPDU messages according to their scGenPortLACPMode MIB.
				If disabled, every port of the switch will not exchange LACPDU messages -
				regardless of their scGenPortLACPMode MIB."
			::= { scGenSwitchEntry 28 }

		scGenSwitchSecurityModePermit OBJECT-TYPE
			SYNTAX INTEGER
			ACCESS read-write
			STATUS mandatory
			DESCRIPTION
				" This item defines the Security mode per switch.
				This MIB is encoded in AVAYA specific security mechanism."
			::= { scGenSwitchEntry 29 }

		scGenSwitchFastAgingOnRemoteTopChg OBJECT-TYPE
			SYNTAX INTEGER
				{
				enabled(1),
				disabled(2),
				notSupported(255)
				}
			ACCESS read-write
			STATUS mandatory
			DESCRIPTION
				" This item defines if the switch performs fast aging on the MAC address
				forwarding database (or reset the cam contents) upon reception of
				Topology Change BPDU from the STA root, indicating that a remote
				topology change has occurred. Local topology changes that occur on
				valuable ports always generate a fast aging anyway."
			::= { scGenSwitchEntry 30 }

		scGenSwitchGigaMode OBJECT-TYPE
			SYNTAX INTEGER
				{
				regular(1),
				link-load-sharing(2),
				primary-bottom(3),
				primary-top(4)
				}
			ACCESS read-write
			STATUS mandatory
			DESCRIPTION
				"The value of this attribute determines the setting for the two Giga links of a P130 stack."
			DEFVAL { regular }
			::= { scGenSwitchEntry 31 }

		scGenSwitchCAMClear OBJECT-TYPE
			SYNTAX INTEGER
				{
				on(1),
				off(2),
				notSupported(255)
				}
			ACCESS read-write
			STATUS mandatory
			DESCRIPTION
				"When value sets to on(1), the switch clears its CAM table.
				This item will always return a value of off(2), since it acts like a toggle switch."
			DEFVAL { off }
			::= { scGenSwitchEntry 32 }

		scGenSwitchWelcomeMessage OBJECT-TYPE
			SYNTAX DisplayString (SIZE (0..255))
			ACCESS read-write
			STATUS mandatory
			DESCRIPTION
				"The textual message of the welcome message that should be displayed upon
				power on or  telneting to the system."
			::= { scGenSwitchEntry 33 }

		scGenSwitchPromptMessage OBJECT-TYPE
			SYNTAX DisplayString (SIZE (0..32))
			ACCESS read-write
			STATUS mandatory
			DESCRIPTION
				"The textual message of the Prompt message that should be displayed."
			::= { scGenSwitchEntry 34 }

		scGenSwitchMacAging OBJECT-TYPE
			SYNTAX INTEGER
				{
				enable(1),
				disable(2)
				}
			ACCESS read-write
			STATUS mandatory
			DESCRIPTION
				"Enable/Disable filtering database entries (MAC) aging"
			::= { scGenSwitchEntry 35 }

		scGenSwitchSecurityAction OBJECT-TYPE
			SYNTAX INTEGER
				{
				drop(1),
				dropAndNotify(2),
				shutdownAndNotify(3)
				}
			ACCESS read-write
			STATUS mandatory
			DESCRIPTION
				"Specifies global security violation action.
				Drop - drop intruder packets for 5 seconds.
				dropAndNotify - Drop and notify.
				       shutdownAndNotify - Administratively Disable port (forever) and notify.
				"
			::= { scGenSwitchEntry 36 }


		scGenSwitchDot1xPortMaxSuppNum OBJECT-TYPE
    		SYNTAX      INTEGER
    		ACCESS  read-write
    		STATUS      mandatory
    		DESCRIPTION
        		"Maximum number of supplicant allowed per port.
        		Possible values 1-8.
        		DEFAULT is 2."
        	DEFVAL { 2 }
    		::= { scGenSwitchEntry 37 }

-- Adding extension to 802.1x multi-supplicant mode and LLDP Application.

		scGenSwitchDot1xLldpTxVlanName OBJECT-TYPE
			SYNTAX INTEGER
				{
				enable(1),
				disable(2)
				}
			ACCESS read-write
			STATUS mandatory
			DESCRIPTION
				"This MIB item includes additional information for the extension of 802.1x
				multi-supplicant mode and LLDP application.
				If this MIB is Enable and if there was authentication on one
				of the ports on the device and:
				1. If the port is bind-to-static and Vlan information is sent from the radius
				server then the relevant vlan will be also send by the LLDP application.
				2. If the port is bind-to-static and NO Vlan information is send from the radius
				server then the relevant vlans on the port will be also sent by the LLDP application.
				3. If the port is bind-to-configured/bind-to-all NO matter what is the Vlan
				information send from the radius server then the all the vlans on that port
				will be also sent by the LLDP application.
				DEFAULT is 2 (disable)"
			::= { scGenSwitchEntry 38 }


		scGenLinkAggregation OBJECT IDENTIFIER ::= { scGen 6 }

		scGenLinkAggregationTable OBJECT-TYPE
			SYNTAX SEQUENCE OF ScGenLinkAggregationEntry
			ACCESS not-accessible
			STATUS mandatory
			DESCRIPTION
				"Table of attributes which define Link Aggregation Group in a single switch."
			::= { scGenLinkAggregation 1 }

		scGenLinkAggregationEntry OBJECT-TYPE
			SYNTAX ScGenLinkAggregationEntry
			ACCESS not-accessible
			STATUS mandatory
			DESCRIPTION
				"An entry in the table, containing LAG information in a single switch."
			INDEX { scGenLinkAggregationId }
			::= { scGenLinkAggregationTable 1 }

		ScGenLinkAggregationEntry ::=
			SEQUENCE {
				scGenLinkAggregationId
					INTEGER,
				scGenLinkAggregationName
					DisplayString,
				scGenLinkAggregationBasePortGroupId
					INTEGER,
				scGenLinkAggregationBasePortId
					INTEGER,
				scGenLinkAggregationNumberOfPorts
					INTEGER,
				scGenLinkAggregationLogicalPortGroupId
					INTEGER,
				scGenLinkAggregationLogicalPortId
					INTEGER,
				scGenLinkAggregationFunctionalStatus
					INTEGER,
				scGenLinkAggregationAutoNegResults
					INTEGER,
				scGenLinkAggregationFaultMask
					OCTET STRING,
				scGenLinkAggregationStatus
					RowStatus
			 }

		scGenLinkAggregationId OBJECT-TYPE
			SYNTAX INTEGER (1..100)
			ACCESS read-only
			STATUS mandatory
			DESCRIPTION
				"The Link Aggregation number for which this entry contains information."
			::= { scGenLinkAggregationEntry 1 }

		scGenLinkAggregationName OBJECT-TYPE
			SYNTAX DisplayString (SIZE (0..32))
			ACCESS read-write
			STATUS mandatory
			DESCRIPTION
				"The Link Aggregation name, given by the user."
			::= { scGenLinkAggregationEntry 2 }

		scGenLinkAggregationBasePortGroupId OBJECT-TYPE
			SYNTAX INTEGER
			ACCESS read-write
			STATUS mandatory
			DESCRIPTION
				"The slot/unit number of the Base Port for this Link Aggregation."
			::= { scGenLinkAggregationEntry 3 }

		scGenLinkAggregationBasePortId OBJECT-TYPE
			SYNTAX INTEGER
			ACCESS read-write
			STATUS mandatory
			DESCRIPTION
				"The port number in the slot/unit of the Base Port for this Link Aggregation."
			::= { scGenLinkAggregationEntry 4 }

		scGenLinkAggregationNumberOfPorts OBJECT-TYPE
			SYNTAX INTEGER
			ACCESS read-only
			STATUS mandatory
			DESCRIPTION
				"The current number of ports that belong to this Link Aggregation."
			::= { scGenLinkAggregationEntry 5 }

		scGenLinkAggregationLogicalPortGroupId OBJECT-TYPE
			SYNTAX INTEGER
			ACCESS read-only
			STATUS mandatory
			DESCRIPTION
				"The slot number of the logical port, representing this Link Aggregation.
				All parameters for the LAG are managed through that logical port."
			::= { scGenLinkAggregationEntry 6 }

		scGenLinkAggregationLogicalPortId OBJECT-TYPE
			SYNTAX INTEGER
			ACCESS read-only
			STATUS mandatory
			DESCRIPTION
				"The logical port number in the slot, representing this Link Aggregation.
				All parameters for the LAG are managed through that logical port."
			::= { scGenLinkAggregationEntry 7 }

		scGenLinkAggregationFunctionalStatus OBJECT-TYPE
			SYNTAX INTEGER
				{
				ok(1),
				fail(2),
				partialFail(3),
				notSupported(255)
				}
			ACCESS read-only
			STATUS mandatory
			DESCRIPTION
				"The functional status of the LAG:
				ok(1) - fully functional LAG, transmitting and receiving packets on all its ports.
				fail(2) - all ports in the LAG are not in ok status.
					partialFail(3) - some of the ports in the LAG are not in ok status."
			::= { scGenLinkAggregationEntry 8 }

		scGenLinkAggregationAutoNegResults OBJECT-TYPE
			SYNTAX INTEGER
				{
				ok(1),
				autoNegInconsistantResults(2),
				notSupported(255)
				}
			ACCESS read-only
			STATUS mandatory
			DESCRIPTION
				"The auto-negotiation results for speed and duplex for the LAG ports:
				ok(1) - all ports resolved the same speed and duplex mode after auto-negotiation process.
				autoNegInconsistantResults(2) - not all ports resolved the same speed and duplex mode after 	auto-negotiation process."
			::= { scGenLinkAggregationEntry 9 }

		scGenLinkAggregationFaultMask OBJECT-TYPE
			SYNTAX OCTET STRING
			ACCESS read-only
			STATUS mandatory
			DESCRIPTION
				"Each bit of this item describes the situation of the LAG
				regarding specific fault:
				bit 1: on indicates 'LAG connection lost' when
				         scGenLinkAggregationFunctionalStatus=fail(2)
				bit 2: on indicates 'LAG partial connection' when
				         scGenLinkAggregationFunctionalStatus=partailFail(3)
				bit 3: on indicates 'LAG auto-neg inconsistant results' when
				         scGenLinkAggregationAutoNegResults= autoNegInconsistantResults(2)"
			::= { scGenLinkAggregationEntry 10 }

		scGenLinkAggregationStatus OBJECT-TYPE
			SYNTAX RowStatus
			ACCESS read-write
			STATUS mandatory
			DESCRIPTION
				"The status of this scGenLinkAggregation entry. According to RMON-2 standard (RFC 2021)."
			::= { scGenLinkAggregationEntry 11 }

		scGenPortIPAddressRsp OBJECT IDENTIFIER ::= { scGen 7 }

		scGenPortIPAddressRspTable OBJECT-TYPE
			SYNTAX SEQUENCE OF ScGenPortIPAddressRspEntry
			ACCESS not-accessible
			STATUS mandatory
			DESCRIPTION
				"Table of attributes which define general configuration
				information about a single SC based port."
			::= { scGenPortIPAddressRsp 1 }

		scGenPortIPAddressRspEntry OBJECT-TYPE
			SYNTAX ScGenPortIPAddressRspEntry
			ACCESS not-accessible
			STATUS mandatory
			DESCRIPTION
				"An entry in the table, containing data about a single Port."
			INDEX { scGenPortIPAddressRspGroupId, scGenPortIPAddressRspPortId, scGenPortIPAddressRspIpAddressIndex }
			::= { scGenPortIPAddressRspTable 1 }

		ScGenPortIPAddressRspEntry ::=
			SEQUENCE {
				scGenPortIPAddressRspGroupId
					INTEGER,
				scGenPortIPAddressRspPortId
					INTEGER,
				scGenPortIPAddressRspIpAddressIndex
					INTEGER,
				scGenPortIPAddressRspIpAddress
					IpAddress
			 }

		scGenPortIPAddressRspGroupId OBJECT-TYPE
			SYNTAX INTEGER
			ACCESS read-only
			STATUS mandatory
			DESCRIPTION
				"Id of the group to which the port belongs."
			::= { scGenPortIPAddressRspEntry 1 }

		scGenPortIPAddressRspPortId OBJECT-TYPE
			SYNTAX INTEGER
			ACCESS read-only
			STATUS mandatory
			DESCRIPTION
				"Unique Id of the port in the scGenPortRspTable."
			::= { scGenPortIPAddressRspEntry 2 }

		scGenPortIPAddressRspIpAddressIndex OBJECT-TYPE
			SYNTAX INTEGER
			ACCESS read-only
			STATUS mandatory
			DESCRIPTION
				"Unique Id of the port in the scGenPortRspTable."
			::= { scGenPortIPAddressRspEntry 3 }

		scGenPortIPAddressRspIpAddress OBJECT-TYPE
			SYNTAX IpAddress
			ACCESS read-write
			STATUS mandatory
			DESCRIPTION
				"This MIB-item sets an IpAddress of a station that is connected to a port that performs RSP.
				A value of 0.0.0.0 in this Mib Item means that it does not describe an existing IpAddress.
					Default value is 0.0.0.0"
			::= { scGenPortIPAddressRspEntry 4 }

--      Mandatory for all Visage Ethernet devices.
--
		scEth OBJECT IDENTIFIER ::= { switchChip 2 }

		scEthPort OBJECT IDENTIFIER ::= { scEth 1 }

		scEthPortTable OBJECT-TYPE
			SYNTAX SEQUENCE OF ScEthPortEntry
			ACCESS not-accessible
			STATUS mandatory
			DESCRIPTION
				"Table of attributes which define configuration,
				performance and error information about ethernet
				ports based on the switchChip."
			::= { scEthPort 1 }

		scEthPortEntry OBJECT-TYPE
			SYNTAX ScEthPortEntry
			ACCESS not-accessible
			STATUS mandatory
			DESCRIPTION
				"An entry in the table, containing data about a single port."
			INDEX { scEthPortGroupId, scEthPortId }
			::= { scEthPortTable 1 }

		ScEthPortEntry ::=
			SEQUENCE {
				scEthPortGroupId
					INTEGER,
				scEthPortId
					INTEGER,
				scEthPortOctetsRec
					Counter,
				scEthPortPktsRec
					Counter,
				scEthPortGoodBroadcastPktsRec
					Counter,
				scEthPortGoodMulticastPktsRec
					Counter,
				scEthPortCRCAlignErrors
					Counter,
				scEthPortOversizePkts
					Counter,
				scEthPortFragments
					Counter,
				scEthPortJabber
					Counter,
				scEthPortCollisions
					Counter,
				scEthPortPkts64Octets
					Counter,
				scEthPortPkts65to127Octets
					Counter,
				scEthPortPkts128to255Octets
					Counter,
				scEthPortPkts256to511Octets
					Counter,
				scEthPortPkts512to1023Octets
					Counter,
				scEthPortPkts1024to1518Octets
					Counter,
				scEthPortGoodPktsRec
					Counter,
				scEthPortBadPkts
					Counter,
				scEthPortGoodOctetsRec
					Counter,
				scEthPortBadOctets
					Counter,
				scEthPortGoodBroadcastOctetsRec
					Counter,
				scEthPortGoodMulticastOctetsRec
					Counter,
				scEthPortGoodOctetsSent
					Counter,
				scEthPortGoodPktsSent
					Counter,
				scEthPortLateCollisions
					Counter,
				scEthPortFunctionalStatus
					INTEGER,
				scEthPortMode
					INTEGER,
				scEthPortSpeed
					INTEGER,
				scEthPortAutoNegotiation
					INTEGER,
				scEthPortAutoNegotiationStatus
					INTEGER,
				scEthPortTotalOctets
					Counter,
				scEthPortTotalPkts
					Counter,
				scEthPortDropEvents
					Counter,
				scEthPortGigaPauseStatus
					INTEGER,
				scEthPortLower32OctetsRec
					Counter,
				scEthPortUpper32OctetsRec
					Counter,
				scEthPortLower32OctetsSent
					Counter,
				scEthPortUpper32OctetsSent
					Counter,
				scEthPortGoodUnicastPktsRec
					Counter,
				scEthPortDiscardPktsRec
					Counter,
				scEthPortUnicastPktsSent
					Counter,
				scEthPortDiscardPktsSent
					Counter,
				scEthPortPauseCapabilities
					INTEGER,
				scEthPortMulticastPktsSent
					Counter,
				scEthPortUndersizePktsRec
					Counter,
				scEthPortFlowControl
					INTEGER
			 }

		scEthPortGroupId OBJECT-TYPE
			SYNTAX INTEGER
			ACCESS read-only
			STATUS mandatory
			DESCRIPTION
				"Id of the group to which the port belongs."
			::= { scEthPortEntry 1 }

		scEthPortId OBJECT-TYPE
			SYNTAX INTEGER
			ACCESS read-only
			STATUS mandatory
			DESCRIPTION
				"Unique Id of the port in the scEthPortTable."
			::= { scEthPortEntry 2 }

		scEthPortOctetsRec OBJECT-TYPE
			SYNTAX Counter
			ACCESS read-only
			STATUS mandatory
			DESCRIPTION
				"The total number of good octets received and bad octets
				filtered by the port (excluding framing bits but including
				FCS octets).
				This item is the summation of scEthPortGoodOctetsRec
				and scEthPortBadOctets."
			::= { scEthPortEntry 3 }

		scEthPortPktsRec OBJECT-TYPE
			SYNTAX Counter
			ACCESS read-only
			STATUS mandatory
			DESCRIPTION
				"The total number of good packets received and bad
				packets filtered by the port.
				This item is the summation of scEthPortGoodPktsRec
				and scEthPortBadPkts."
			::= { scEthPortEntry 4 }

		scEthPortGoodBroadcastPktsRec OBJECT-TYPE
			SYNTAX Counter
			ACCESS read-only
			STATUS mandatory
			DESCRIPTION
				"The total number of good packets received that were
				directed to the broadcast address."
			::= { scEthPortEntry 5 }

		scEthPortGoodMulticastPktsRec OBJECT-TYPE
			SYNTAX Counter
			ACCESS read-only
			STATUS mandatory
			DESCRIPTION
				"The total number of good packets received that were
				directed to a multicast address.
				Note that this number does not include packets directed to
				the broadcast address."
			::= { scEthPortEntry 6 }

		scEthPortCRCAlignErrors OBJECT-TYPE
			SYNTAX Counter
			ACCESS read-only
			STATUS mandatory
			DESCRIPTION
				"The total number of packets received that had a length
				(excluding framing bits, but including FCS octets) of
				between 64 and 1518 octets, inclusive, but were not an
				integral number of octets in length or had a bad Frame
				Check Sequence (FCS)."
			::= { scEthPortEntry 7 }

		scEthPortOversizePkts OBJECT-TYPE
			SYNTAX Counter
			ACCESS read-only
			STATUS mandatory
			DESCRIPTION
				"The total number of packets received that were longer
				than 1518 octets (excluding framing bits, but including
				FCS octets) and were otherwise well formed."
			::= { scEthPortEntry 8 }

		scEthPortFragments OBJECT-TYPE
			SYNTAX Counter
			ACCESS read-only
			STATUS mandatory
			DESCRIPTION
				"The total number of packets received that were  less than 64 octets in
				length (excluding framing bits but including FCS octets)."
			::= { scEthPortEntry 9 }

		scEthPortJabber OBJECT-TYPE
			SYNTAX Counter
			ACCESS read-only
			STATUS mandatory
			DESCRIPTION
				"The total number of packets received that were longer
				than 1518 octets (excluding framing bits, but including
				FCS octets), and were not an integral number of octets in
				length or had a bad Frame Check Sequence (FCS)."
			::= { scEthPortEntry 10 }

		scEthPortCollisions OBJECT-TYPE
			SYNTAX Counter
			ACCESS read-only
			STATUS mandatory
			DESCRIPTION
				"The best estimate of the total number of collisions on this
				Ethernet segment."
			::= { scEthPortEntry 11 }

		scEthPortPkts64Octets OBJECT-TYPE
			SYNTAX Counter
			ACCESS read-only
			STATUS mandatory
			DESCRIPTION
				"The total number of packets (including error packets)
				that were 64 octets in length (excluding framing
				bits but including FCS octets)."
			::= { scEthPortEntry 12 }

		scEthPortPkts65to127Octets OBJECT-TYPE
			SYNTAX Counter
			ACCESS read-only
			STATUS mandatory
			DESCRIPTION
				"The total number of packets (including error packets)
				that were between 65 and 127 octets in length
				inclusive (excluding framing bits but including FCS
				octets)."
			::= { scEthPortEntry 13 }

		scEthPortPkts128to255Octets OBJECT-TYPE
			SYNTAX Counter
			ACCESS read-only
			STATUS mandatory
			DESCRIPTION
				"The total number of packets (including error packets)
				that were between 128 and 255 octets in length
				inclusive (excluding framing bits but including FCS
				octets)."
			::= { scEthPortEntry 14 }

		scEthPortPkts256to511Octets OBJECT-TYPE
			SYNTAX Counter
			ACCESS read-only
			STATUS mandatory
			DESCRIPTION
				"The total number of packets (including error packets)
				that were between 256 and 511 octets in length
				inclusive (excluding framing bits but including FCS
				octets)."
			::= { scEthPortEntry 15 }

		scEthPortPkts512to1023Octets OBJECT-TYPE
			SYNTAX Counter
			ACCESS read-only
			STATUS mandatory
			DESCRIPTION
				"The total number of packets (including error packets)
				that were between 512 and 1023 octets in length
				inclusive (excluding framing bits but including FCS
				octets)."
			::= { scEthPortEntry 16 }

		scEthPortPkts1024to1518Octets OBJECT-TYPE
			SYNTAX Counter
			ACCESS read-only
			STATUS mandatory
			DESCRIPTION
				"The total number of packets (including error packets)
				that were between 1024 and 1518 octets in length
				inclusive (excluding framing bits but including FCS
				octets)."
			::= { scEthPortEntry 17 }

		scEthPortGoodPktsRec OBJECT-TYPE
			SYNTAX Counter
			ACCESS read-only
			STATUS mandatory
			DESCRIPTION
				"The total number of good packets received by the port."
			::= { scEthPortEntry 18 }

		scEthPortBadPkts OBJECT-TYPE
			SYNTAX Counter
			ACCESS read-only
			STATUS mandatory
			DESCRIPTION
				"The total number of bad packets filtered by the port.
				This item is the summation of:
				scEthPortCRCAlignErrors, scEthPortOversizePkts,

				scEthPortFragments	and scEthPortJabber. "
			::= { scEthPortEntry 19 }

		scEthPortGoodOctetsRec OBJECT-TYPE
			SYNTAX Counter
			ACCESS read-only
			STATUS mandatory
			DESCRIPTION
				"The total number of good octets of data received by the port."
			::= { scEthPortEntry 20 }

		scEthPortBadOctets OBJECT-TYPE
			SYNTAX Counter
			ACCESS read-only
			STATUS mandatory
			DESCRIPTION
				"The total number of bad octets of data filtered by the port."
			::= { scEthPortEntry 21 }

		scEthPortGoodBroadcastOctetsRec OBJECT-TYPE
			SYNTAX Counter
			ACCESS read-only
			STATUS mandatory
			DESCRIPTION
				"The total number of good octets received that were
				directed to the broadcast address."
			::= { scEthPortEntry 22 }

		scEthPortGoodMulticastOctetsRec OBJECT-TYPE
			SYNTAX Counter
			ACCESS read-only
			STATUS mandatory
			DESCRIPTION
				"The total number of good octets received that were
				directed to a multicast address.  Note that this number does
				not include octets directed to the broadcast address."
			::= { scEthPortEntry 23 }

		scEthPortGoodOctetsSent OBJECT-TYPE
			SYNTAX Counter
			ACCESS read-only
			STATUS mandatory
			DESCRIPTION
				"The total number of good octets of data sent by the port."
			::= { scEthPortEntry 24 }

		scEthPortGoodPktsSent OBJECT-TYPE
			SYNTAX Counter
			ACCESS read-only
			STATUS mandatory
			DESCRIPTION
				"The total number of good packets sent by the port."
			::= { scEthPortEntry 25 }

		scEthPortLateCollisions OBJECT-TYPE
			SYNTAX Counter
			ACCESS read-only
			STATUS mandatory
			DESCRIPTION
				"The best estimate of the total number of late collisions on
				this Ethernet segment."
			::= { scEthPortEntry 26 }

--      RxLinkDown (Link Test Fail)
		scEthPortFunctionalStatus OBJECT-TYPE
			SYNTAX INTEGER
				{
				ok(1),
				rld(2),
				rxJabber(3),
				partition(8),
				remoteFault(10),
				rspError(11),
				notSupported(255)
				}
			ACCESS read-only
			STATUS mandatory
			DESCRIPTION
				"The functional status of the port:
				ok(1) - fully functional port, transmitting and receiving
				packets.
				rld(2) - receive link down condition on the port - Indicates
				a cable  or connector failure detected by the port H/W.
				partition(8) - the port is in partition state."
			::= { scEthPortEntry 27 }

		scEthPortMode OBJECT-TYPE
			SYNTAX INTEGER
				{
				halfDuplex(1),
				fullDuplexNoPause(2),
				fullDuplexProprietaryFC(3),
				fullDuplexISL(4),
				fullDuplexFlowControlISL(5),
				fullDuplexAsymTxPause(6),
				fullDuplexSymPause(7),
				fullDuplexAsymRxPause(8),
				notSupported(255)
				}
			ACCESS read-write
			STATUS mandatory
			DESCRIPTION
				"The flow control mode of the port when operated in full duplex:
				halfDuplex(1) - Half duplex connection, standard mode for segment
				fullDuplexNoPause(2) - Full duplex connection without exchanging flow control packets
				fullDuplexProprietaryFC(3) -
				         Full duplex connection with AVAYA's proprietary flow control frames exchanged
				fullDuplexISL(4) -
				         Full duplex connection with ISL proprietary protocol control words for
				         VLAN & priority exchanged, 	ISL = Inter-Switch-Link
				fullDuplexFlowControlISL(5) -
				        Full duplex connection with both ISL proprietary protocol control words
				        and flow control frames exchanged
				fullDuplexAsymTxPause(6) -
				       Full duplex connection with STD 802.3x flow control frames sent from this port,
				       but flow control packets received on it are not processed
				fullDuplexSymPause(7) -
				       Full duplex connection with STD 802.3x flow control frames exchanged
				fullDuplexAsymRxPause(8) -
				       Full duplex connection with no flow control frames sent from this port,
				       but STD 802.3x flow control 0frames received on it are processed.
				For Giga ports, when auto-negotiation is enabled, the flow control mode is set
				internally according to auto-negotiation resolution; and access to this item is read-only."
			::= { scEthPortEntry 28 }

		scEthPortSpeed OBJECT-TYPE
			SYNTAX INTEGER
				{
				ethernet(1),
				fastEthernet(2),
				gigabitEthernet(3),
				a155Mbps(4),
				a622Mbps(5),
				notSupported(255)
				}
			ACCESS read-write
			STATUS mandatory
			DESCRIPTION
				"This parameter defines the port speed:
				ethernet(1) and fastEthernet(2)."
			DEFVAL { fastEthernet }
			::= { scEthPortEntry 29 }

		scEthPortAutoNegotiation OBJECT-TYPE
			SYNTAX INTEGER
				{
				enable(1),
				disable(2),
				notSupported(255)
				}
			ACCESS read-write
			STATUS mandatory
			DESCRIPTION
				" This object define if the Auto Sense /Auto Negotiation
				process is enable(1) or disable (2)
				for modules that don't support the Auto Snese mode
				please define the notSupported option.."
			DEFVAL { disable }
			::= { scEthPortEntry 30 }

		scEthPortAutoNegotiationStatus OBJECT-TYPE
			SYNTAX INTEGER
				{
				pass(1),
				fail(2),
				disable(3),
				inProgress(4),
				notSupported(255)
				}
			ACCESS read-only
			STATUS mandatory
			DESCRIPTION
				" This object define the status of the Auto Negotiation process:
				pass: The Auto negotiation process was completed and succeeded .
				fail: The Auto Negotiation process failed .
				disable: The Auto Negotiation process is not enabled .
				notSupported: The Auto Negotiation feature is not available in this module  .
				"
			DEFVAL { disable }
			::= { scEthPortEntry 31 }

		scEthPortTotalOctets OBJECT-TYPE
			SYNTAX Counter
			ACCESS read-only
			STATUS mandatory
			DESCRIPTION
				"The total number of octets received and transmitted on
				the port (including all good and bad).
				This item is the summation of scEthPortOctetsRec
				and scEthPortGoodOctetsSent."
			::= { scEthPortEntry 32 }

		scEthPortTotalPkts OBJECT-TYPE
			SYNTAX Counter
			ACCESS read-only
			STATUS mandatory
			DESCRIPTION
				"The total number of packets received and transmitted on
				the port (including all good and bad).
				This item is the summation of scEthPortPktsRec
				and scEthPortGoodPktsSent."
			::= { scEthPortEntry 33 }

		scEthPortDropEvents OBJECT-TYPE
			SYNTAX Counter
			ACCESS read-only
			STATUS mandatory
			DESCRIPTION
				"The total number of events in which the probe could not
				count packets due to lack of resources. This number is not
				necessarily the number of packets dropped; it is just the
				number  of times this condition has been detected."
			::= { scEthPortEntry 34 }

		scEthPortGigaPauseStatus OBJECT-TYPE
			SYNTAX INTEGER
				{
				noPause(1),
				symmetricPause(2),
				asymmetricPauseRx(3),
				notSupported(255)
				}
			ACCESS read-only
			STATUS mandatory
			DESCRIPTION
				"Indicates the status of the Flow Control as determined in the Auto Negotiation process on the
				Gigabit 	ports:
				noPause(1) indicates that there is no Flow Control.
				symmetricPause(2) indicates that both sides are working in Tx&Rx Flow Control.
				asymmetricPauseRx(3) indicates that both sides agreed on working in asynnetric Flow Control
				- TxOnly against RxOnly.
				If Giga Auto Neg is disabled, then noPause(1) is indicated when Flow Control is disabled,
				while symmetricPause(2) is indicated when Flow Control is enabled."
			::= { scEthPortEntry 35 }

		scEthPortLower32OctetsRec OBJECT-TYPE
			SYNTAX Counter
			ACCESS read-only
			STATUS mandatory
			DESCRIPTION
				"Lower 32 bit conter of the total number of octets of data received by the port."
			::= { scEthPortEntry 36 }

		scEthPortUpper32OctetsRec OBJECT-TYPE
			SYNTAX Counter
			ACCESS read-only
			STATUS mandatory
			DESCRIPTION
				"Upper 32 bit conter of the total number of octets of data received by the port."
			::= { scEthPortEntry 37 }

		scEthPortLower32OctetsSent OBJECT-TYPE
			SYNTAX Counter
			ACCESS read-only
			STATUS mandatory
			DESCRIPTION
				"Lower 32 bit conter of the total number of octets of data sent by the port."
			::= { scEthPortEntry 38 }

		scEthPortUpper32OctetsSent OBJECT-TYPE
			SYNTAX Counter
			ACCESS read-only
			STATUS mandatory
			DESCRIPTION
				"Upper 32 bit conter of the total number of octets of data sent by the port."
			::= { scEthPortEntry 39 }

		scEthPortGoodUnicastPktsRec OBJECT-TYPE
			SYNTAX Counter
			ACCESS read-only
			STATUS mandatory
			DESCRIPTION
				"The total number of good packets received that were directed to a unicast address."
			::= { scEthPortEntry 40 }

		scEthPortDiscardPktsRec OBJECT-TYPE
			SYNTAX Counter
			ACCESS read-only
			STATUS mandatory
			DESCRIPTION
				"The total number of packets which were chosen to be discarded even
				though no errors had been detected to prevent their being deliverable
				to a higher-layer protocol. One possible reason for discarding such
				a packet could be to free up buffer space."
			::= { scEthPortEntry 41 }

		scEthPortUnicastPktsSent OBJECT-TYPE
			SYNTAX Counter
			ACCESS read-only
			STATUS mandatory
			DESCRIPTION
				"The total number of good packets sent by the port
				that were directed to a unicast address."
			::= { scEthPortEntry 42 }

		scEthPortDiscardPktsSent OBJECT-TYPE
			SYNTAX Counter
			ACCESS read-only
			STATUS mandatory
			DESCRIPTION
				"The total number of packets which were chosen to be discarded even though no errors
				had been detected to prevent their being transmitted.
				One possible reason for discarding such a packet could be to free up buffer space."
			::= { scEthPortEntry 43 }

		scEthPortPauseCapabilities OBJECT-TYPE
			SYNTAX INTEGER
				{
				noFlowControl(1),
				asymTxFlowControlOnly(2),
				symFlowControlOnly(3),
				symAndAsymRxFlowControl(4),
				notSupported(255)
				}
			ACCESS read-write
			STATUS mandatory
			DESCRIPTION
				"The Pause capabilities of a Giga port that should be advertised to the link
				partner when performing auto-negotiation:
				noFlowControl (1) - no flow control support in any direction
				asymTxFlowControlOnly (2) - STD 802.3x flow control frames can be sent from this port,
				                                       but flow control packets received on it can not be processed.
				symFlowControlOnly (3) - STD 802.3x flow control frames must be supported in both directions
				symAndAsymRxFlowControl (4) -
				              STD 802.3x flow control frames must be supported in both directions or
				              at least received flowcontrol frames on this port can be processed."
			DEFVAL { symAndAsymRxFlowControl }
			::= { scEthPortEntry 44 }

		scEthPortMulticastPktsSent OBJECT-TYPE
			SYNTAX Counter
			ACCESS read-only
			STATUS mandatory
			DESCRIPTION
				"The total number of good packets sent by the port that were directed to a multicast address."
			::= { scEthPortEntry 45 }

		scEthPortUndersizePktsRec OBJECT-TYPE
			SYNTAX Counter
			ACCESS read-only
			STATUS mandatory
			DESCRIPTION
				"The total number of packets received that were less than 64 octets long (excluding framing
				bits, but including FCS octets) and were otherwise well formed."
			::= { scEthPortEntry 46 }

		scEthPortFlowControl OBJECT-TYPE
			SYNTAX INTEGER
				{
				noFlowControl(1),
				asymTxFlowControl(2),
				symFlowControl(3),
				asymRxFlowControl(4),
				proprietaryFlowControl(5),
				notSupported(255)
				}
			ACCESS read-write
			STATUS mandatory
			DESCRIPTION
				"The flow control mode of the port"
			::= { scEthPortEntry 47 }

		scEthGroup OBJECT IDENTIFIER ::= { scEth 2 }

		scEthGroupTable OBJECT-TYPE
			SYNTAX SEQUENCE OF ScEthGroupEntry
			ACCESS not-accessible
			STATUS mandatory
			DESCRIPTION
				"Table of attributes which define ethernet configuration
				information about a single SC based group."
			::= { scEthGroup 1 }

		scEthGroupEntry OBJECT-TYPE
			SYNTAX ScEthGroupEntry
			ACCESS not-accessible
			STATUS mandatory
			DESCRIPTION
				"An entry in the table, containing data about a single Group."
			INDEX { scEthGroupId }
			::= { scEthGroupTable 1 }

		ScEthGroupEntry ::=
			SEQUENCE {
				scEthGroupId
					INTEGER,
				scEthGroupAutoPartitionEnable
					INTEGER,
				scEthGroupFefiEnable
					INTEGER,
				scPowerEthGroupInlineSWversion
					OCTET STRING
			 }

		scEthGroupId OBJECT-TYPE
			SYNTAX INTEGER
			ACCESS read-only
			STATUS mandatory
			DESCRIPTION
				"Unique Id of the group in the scEthGroupTable.
				Equals the number of the slot by which the group is accessed."
			::= { scEthGroupEntry 1 }

		scEthGroupAutoPartitionEnable OBJECT-TYPE
			SYNTAX INTEGER
				{
				enable(1),
				disable(2),
				notSupported(255)
				}
			ACCESS read-write
			STATUS mandatory
			DESCRIPTION
				" Enables/Disables the Auto-Partition mechanism in all ports of this module."
			DEFVAL { disable }
			::= { scEthGroupEntry 2 }

		scEthGroupFefiEnable OBJECT-TYPE
			SYNTAX INTEGER
				{
				enable(1),
				disable(2),
				notSupported(255)
				}
			ACCESS read-write
			STATUS mandatory
			DESCRIPTION
				"This item enables\disables the FEFI mechanism of all Fast-Ethernet
				PHY's in the module. It enables\disables both the transmission and
				the recognition of FEFI signals."
			DEFVAL { enable }
			::= { scEthGroupEntry 3 }

		scPowerEthGroupInlineSWversion OBJECT-TYPE
			SYNTAX OCTET STRING (SIZE (0..10))
			ACCESS read-only
			STATUS mandatory
			DESCRIPTION
				"Indicates the Powerinline image version of the groupID module."
			::= { scEthGroupEntry 4 }

--      Mandatory for all Power Ethernet devices.
--
		scPowerEth OBJECT IDENTIFIER ::= { switchChip 3 }

		scPowerEthGroupTable OBJECT-TYPE
			SYNTAX SEQUENCE OF ScPowerEthGroupEntry
			ACCESS not-accessible
			STATUS mandatory
			DESCRIPTION
				"Table of attributes which define general configuration
				information about a single SC based port."
			::= { scPowerEth 1 }

		scPowerEthGroupEntry OBJECT-TYPE
			SYNTAX ScPowerEthGroupEntry
			ACCESS not-accessible
			STATUS mandatory
			DESCRIPTION
				"An entry in the table, containing data about a single Port."
			INDEX { scPowerEthGroupId }
			::= { scPowerEthGroupTable 1 }

		ScPowerEthGroupEntry ::=
			SEQUENCE {
				scPowerEthGroupId
					INTEGER,
				scPowerEthGroupPsePSPowerFaultErrMsg
					DisplayString,
				scPowerEthGroupPseDetectionProcess
					INTEGER
			 }

		scPowerEthGroupId OBJECT-TYPE
			SYNTAX INTEGER
			ACCESS read-only
			STATUS mandatory
			DESCRIPTION
				"Id of the group to which the port belongs."
			::= { scPowerEthGroupEntry 1 }

		scPowerEthGroupPsePSPowerFaultErrMsg OBJECT-TYPE
			SYNTAX DisplayString
			ACCESS read-only
			STATUS mandatory
			DESCRIPTION
				"Free text informing a main power failure."
			::= { scPowerEthGroupEntry 2 }

		scPowerEthGroupPseDetectionProcess OBJECT-TYPE
			SYNTAX INTEGER
				{
				resistive(1),
				capacitive(2),
				both(3)
				}
			ACCESS read-write
			STATUS mandatory
			DESCRIPTION
				"This object specifies the detection process used by PD.
				Resistive investigates the line for resistive type load,
				Capacitive investigates the line for a capacitive load,
				and both detects for a resistive type first, then for a capacitive"
			::= { scPowerEthGroupEntry 3 }

-- This MIB table is extension for the Standard PoE MIB. This MIB table
-- will show additional information per Group/Port.
	 	scPowerEthPortTable OBJECT-TYPE
			SYNTAX SEQUENCE OF ScPowerEthPortEntry
			ACCESS not-accessible
			STATUS mandatory
			DESCRIPTION
				"Table of additional information about PoE ports."
			::= { scPowerEth 2 }

		scPowerEthPortEntry OBJECT-TYPE
			SYNTAX ScPowerEthPortEntry
			ACCESS not-accessible
			STATUS mandatory
			DESCRIPTION
				"An entry in the table, containing data about a single Port."
			INDEX { scPowerEthPortGroupId, scPowerEthPortPortId }
			::= { scPowerEthPortTable 1 }

		ScPowerEthPortEntry ::=
			SEQUENCE {
				scPowerEthPortGroupId
					INTEGER,
				scPowerEthPortPortId
					INTEGER,
				scPowerEthPortConsumptionPower
					INTEGER
			 }

		scPowerEthPortGroupId OBJECT-TYPE
			SYNTAX INTEGER
			ACCESS not-accessible
			STATUS mandatory
			DESCRIPTION
				"Id of the group to which the port belongs."
			::= { scPowerEthPortEntry 1 }

		scPowerEthPortPortId OBJECT-TYPE
			SYNTAX INTEGER
			ACCESS not-accessible
			STATUS mandatory
			DESCRIPTION
				"Id of the port in the relevant group."
			::= { scPowerEthPortEntry 2 }

		scPowerEthPortConsumptionPower OBJECT-TYPE
			SYNTAX INTEGER
			ACCESS read-only
			STATUS mandatory
			DESCRIPTION
				"Indicates the amount of power consumption in mWatts for the specific port."
			::= { scPowerEthPortEntry 3 }



--      Node definitions
-- The scPriorityQueuing MIBs control the queueng mode
-- of operation of the switch ports.
--
		scPriorityQueuing OBJECT IDENTIFIER ::= { switchChip 4 }

		scPriorityQueuingTable OBJECT-TYPE
			SYNTAX SEQUENCE OF ScPriorityQueuingEntry
			ACCESS not-accessible
			STATUS mandatory
			DESCRIPTION
				"The Priority Queuing table controls the queuing mode
				of the switch ports. This table is arranged by module
				so that the queuing parameters are set on per module id."
			::= { scPriorityQueuing 1 }

		scPriorityQueuingEntry OBJECT-TYPE
			SYNTAX ScPriorityQueuingEntry
			ACCESS not-accessible
			STATUS mandatory
			DESCRIPTION
				"An entry in the table, containing data about a single module."
			INDEX { scPriorityQueuingModuleID }
			::= { scPriorityQueuingTable 1 }

		ScPriorityQueuingEntry ::=
			SEQUENCE {
				scPriorityQueuingModuleID
					INTEGER,
				scPriorityQueuingNumberOfQueues
					INTEGER,
				scPriorityQueuingExpediteWRRFlg
					INTEGER,
				scPriorityQueuingModeControl
					INTEGER,
				scPriorityQueuingDefaultControl
					INTEGER,
				scPriorityQueuingWRRWeights
					OCTET STRING
			 }

		scPriorityQueuingModuleID OBJECT-TYPE
			SYNTAX INTEGER (1..21)
			ACCESS read-only
			STATUS mandatory
			DESCRIPTION
				"Module number - position of a module in the stack
				or a slot within a modular chassis."
			::= { scPriorityQueuingEntry 1 }

		scPriorityQueuingNumberOfQueues OBJECT-TYPE
			SYNTAX INTEGER (1..8)
			ACCESS read-only
			STATUS mandatory
			DESCRIPTION
				"Number of Priority queues supported by corrsponding module."
			::= { scPriorityQueuingEntry 2 }

		scPriorityQueuingExpediteWRRFlg OBJECT-TYPE
			SYNTAX INTEGER
				{
				no(1),
				yes(2)
				}
			ACCESS read-only
			STATUS mandatory
			DESCRIPTION
				"When yes - supports an expedite queuing mode.
				In expedite mode the highest priority queue is serviced
				until it is empty and only then WRR queues are served."
			::= { scPriorityQueuingEntry 3 }

		scPriorityQueuingModeControl OBJECT-TYPE
			SYNTAX INTEGER
				{
				strictMode(1),
				wrrMode(2),
				expediteMode(3)
				}
			ACCESS read-write
			STATUS mandatory
			DESCRIPTION
				"Queuing operational mode.

				Strict - in strict mode the low priority egress queues
				are serviced only after the higher priority queue is emptied.

				WRR mode - the egress queues serviced according to specified
				ratio in weighted round robin manner.

				Expedite - in expedite mode the highest priority queue
				is serviced until it is empty and only then WRR queues
				are served.

				If Set-Request is executed when a device is in default mode
				the corresponding module(s) immediately exits the default
				state and the scPriorityQueuingDefaultControl table entry
				respectively returns off value."
			::= { scPriorityQueuingEntry 4 }

		scPriorityQueuingDefaultControl OBJECT-TYPE
			SYNTAX INTEGER
				{
				on(1),
				off(2)
				}
			ACCESS read-write
			STATUS mandatory
			DESCRIPTION
				"Setting this value to on(1) returns queuing mode
				to default values.

				Should return off(2)if the default values are overwritten.

				Activating Default control affects the values read from the
				scPriorityQueuingWRRWeights and scPriorityQueuingModeControl
				table entries. The value of these MIB objects return to a
				factory defaults for the corresponding module(s). "
			::= { scPriorityQueuingEntry 5 }

		scPriorityQueuingWRRWeights OBJECT-TYPE
			SYNTAX OCTET STRING (SIZE (1..8))
			ACCESS read-write
			STATUS mandatory
			DESCRIPTION
				"The array of weights ordered by weight for priority 0 in
				position 1 and weight for priority 7 is in position 8.

				The number of elements in the array should match the number
				of queues defined  by scPriorityQueuingNumberOfQueues
				MIB object.

				For example for two queues with WRR ration 0f 8:1 the first
				octet=1 and the second octet=8.

				When 0 value set then the corresponding queue is served
				only when higher priority queues are empty.

				If Set-Request is executed when device is in Default Mode
				the corresponding module(s) immediately exits the default
				state and the scPriorityQueuingDefaultControl table entry
				respectively returns off value.

				The values assigned to this MIB have effect on queuing only
				when corresponding module(s)runs in a non-strict queuing,
				i.e., the scPriorityQueuingModeControl is assigned value
				other than strictMode."
			::= { scPriorityQueuingEntry 6 }


	END

--
-- XSWITCH-MIB.my
--
