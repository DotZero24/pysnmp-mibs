AVAYA-SURV-MIB DEFINITIONS ::= BEGIN
	IMPORTS
		OBJECT-GROUP, NOTIFICATION-GROUP, MODULE-COMPLIANCE
			FROM SNMPv2-CONF
		Integer32, Unsigned32, enterprises, Gauge32, Counter32, OBJECT-TYPE, MODULE-IDENTITY, NOTIFICATION-TYPE
			FROM SNMPv2-SMI
		RowStatus, TEXTUAL-CONVENTION, TruthValue, DateAndTime, TimeInterval, DisplayString
			FROM SNMPv2-TC
		InetAddressType, InetAddress, InetPortNumber, InetAddressIPv6
			FROM INET-ADDRESS-MIB
		IpAddress
			FROM RFC1155-SMI
		avGatewayMibs
			FROM AVAYAGEN-MIB;

	avSurvMib MODULE-IDENTITY
		LAST-UPDATED "200810221615Z"
		ORGANIZATION
                       "Avaya"
		CONTACT-INFO
		"
			Avaya Customer Services
			Postal: Avaya, Inc.
			211 Mt Airy Rd.
			Basking Ridge, NJ 07920
			USA
			Tel:	+1 908 953 6000
			E-mail: executiveoffic@avaya.com
			WWW: 	http://www.avaya.com
		"
		DESCRIPTION
		"
		R4.1 Standard Local Survivability (SLS) MIB

            This module defines an interface to Survivability mode
            of operation.This allows a gateway to have a basic set
            of call features if it loses communication with a main
            call controller (CC).
		When the gateway is in survivabilty mode of operation,
            it will continue to register to H.248 controller IP
            addresses in the MGC list. If a re-registration to the
            H.248 controller can be made, the survivability mode will
            be disabled and any new calls will be managed by the MGC.
		Active calls between two local IP phones will be maintained
		because they are established as shuffled calls.


		Copyright notice:

		This AVAYA SNMP Management Information Base Specification
            (Specification)embodies AVAYA confidential and Proprietary
            intellectual property. AVAYA retains all Title and ownership
            in the Specification, including any revisions.
            It is AVAYA's intent to encourage the widespread use of this
            Specification in connection with the management of AVAYA
            products. AVAYA grants vendors, end-users, and other
            interested parties non-exclusive license to use this
            Specification in connection with the management of AVAYA
            products.
            This Specification is supplied 'as is', and AVAYA makes no
            warranty, either express or implied, as to the use,
            operation, condition, or performance of the Specification.


		avSurvMib
		|
		+	.0 avSurvNotification
		|
		+	.1 avSurvConfig
		|
		+	.2 avSurvStationTable
		|		(index: avSurvStationIndex)
		|
		+	.3 avSurvTrunkGroupTable
		|		(index: avSurvTrunkGroupNum)
		|
		+	.4 avSurvTrunkTable
		|		(indexes: avSurvTrunkRefNumber,
		|					avSurvTrunkIndex)
		|
		+	.5 avSurvArsTable
		|		(index: avSurvDialIndex)
		|
		+	.6 avSurvFacTable
		|		(index: avSurvFacIndex)
		|
		+	.7 avSurvIpVoiceCodecSetTable
		|		(indexes: avSurvIpVoiceCodecSetNum,)
		|				avSurvIpVoiceCodecSetIndex)
		|
		+	.8 avSurvIpCodecSetConfig
		|
		|
		+	.9 avSurvSlotConfigTable
		|		(index: avSurvSlotConfigIndex)
		|
		+	.10 avSurvDs1Table
		|		(index: avSurvDs1Index)
		|
		+	.11 avSurvSigGroupTable
		|		(index: avSurvSigGroupIndex)
		|
		+	.12 avSurvBriTable
		|		(index: avSurvBriIndex)
		|
		+	.13 avSurvIncomingRoutingTable
		|		(indexes: avSurvIncomingRoutingGroupRefNumber,
            |                             avSurvIncomingRoutingIndex)
		|
		+	.14 avSurvNfasTable
		|		(indexes: avSurvNfasSigGroupRefNumber,
            |                                   avSurvNfasIndex)
		|
		+	.15 Add G430 values for avSurvMaxIPReg and avSurvBriIndex.
		|       Change avSurvBriIndex to be 1..64 instead of 1..24.
		"
		::= { avGatewayMibs 4 }


-- 1.3.6.1.4.1.6889.2.6.4.0
avSurvNotification OBJECT IDENTIFIER ::= { avSurvMib 0 }

	-- 1.3.6.1.4.1.6889.2.6.4.0.1
	avSurvEnabled				NOTIFICATION-TYPE
		OBJECTS   { avSurvNotificationSeverity }
		STATUS      current
		DESCRIPTION
			"This trap indicates that survivability.o has been administratively enabled."
		::= { avSurvNotification 1 }

	-- 1.3.6.1.4.1.6889.2.6.4.0.2
	avSurvDisabled			NOTIFICATION-TYPE
		OBJECTS   { avSurvNotificationSeverity }
		STATUS      current
		DESCRIPTION
			"This trap indicates that survivability.o has been administratively disabled."
		::= { avSurvNotification 2 }

	-- 1.3.6.1.4.1.6889.2.6.4.0.3
	avSurvActive			NOTIFICATION-TYPE
		OBJECTS   { avSurvNotificationSeverity }
		STATUS      current
		DESCRIPTION
			"This trap indicates that survivability.o is now the call controller of record
			 and is processing calls."
		::= { avSurvNotification 3 }

	-- 1.3.6.1.4.1.6889.2.6.4.0.4
	avSurvInactive			NOTIFICATION-TYPE
		OBJECTS   { avSurvNotificationSeverity }
		STATUS      current
		DESCRIPTION
			"This trap indicates that survivability.o has stopped processing calls.
			 A more powerful controller may have taken over, either an LSP or a primary call controller."
		::= { avSurvNotification 4 }

-- 1.3.6.1.4.1.6889.2.6.4.1
avSurvConfig OBJECT IDENTIFIER ::= { avSurvMib 1 }

	-- 1.3.6.1.4.1.6889.2.6.4.1.1
	avSurvAdminState OBJECT-TYPE
		SYNTAX INTEGER
			{
				enabled		(1),
				disabled		(2)
			}
		MAX-ACCESS read-write
		STATUS current
		DESCRIPTION
			"Allows craft or PIM to enable the SLS call engine or read its current state"
		::= { avSurvConfig 1 }

	-- 1.3.6.1.4.1.6889.2.6.4.1.2
	avSurvStatus OBJECT-TYPE
		SYNTAX INTEGER
			{
				active		(1),
				inactive		(2)
			}
		MAX-ACCESS read-only
		STATUS current
		DESCRIPTION
			"Current operational status of SLS call engine"
		::= { avSurvConfig 2 }

	-- 1.3.6.1.4.1.6889.2.6.4.1.3
	avSurvMaxIPReg OBJECT-TYPE
		SYNTAX Integer32 (1..240)
		MAX-ACCESS read-write
		STATUS current
		DESCRIPTION
			"Maximum IP phone registrations allowed.
                  Gateway SLS firmware will restrict per model.
                  G250 R3.0 = 10;
			G250 R3.1 and R4.0 = 12; G350 R4.0 = 72;
                  IG550 [Juniper gateways(4350, 6350) R4.0 = 100;
                  IG550 [Juniper gateways(2320, 2350) R4.1 = 100;
                  G450 R4.1 =240
            G430 = 150"
		::= { avSurvConfig 3 }

	-- 1.3.6.1.4.1.6889.2.6.4.1.4
	avSurvDateFormat OBJECT-TYPE
		SYNTAX INTEGER
			{
				mmDdYy			(1),
				ddMmYy			(2),
				yyMmDd			(3)
			}
		MAX-ACCESS read-write
		STATUS current
		DESCRIPTION
			"Date Format. This is used for calendar/clock display on DCP & IP phones"
		::= { avSurvConfig 4 }

	-- 1.3.6.1.4.1.6889.2.6.4.1.5
	avSurvEndDLTimeStamp OBJECT-TYPE
		SYNTAX DateAndTime
		MAX-ACCESS read-write
		STATUS current
		DESCRIPTION
			"Date/Timestamp of last download from PIM. This is written by PIM after it
			 completes initialization of all configuration parameters"
		::= { avSurvConfig 5 }

	-- 1.3.6.1.4.1.6889.2.6.4.1.6
	avSurvNotificationSeverity OBJECT-TYPE
		SYNTAX INTEGER
			{
				cleared			(1),
				indeterminate		(2),
				critical			(3),
				major				(4),
				minor				(5),
				warning			(6)
			}
		MAX-ACCESS read-only
		STATUS current
		DESCRIPTION
			"Severity of last sent trap"
		::= { avSurvConfig 6 }

	-- 1.3.6.1.4.1.6889.2.6.4.1.7
	avSurvConfigCommand OBJECT-TYPE
		SYNTAX INTEGER
			{
				clear			(1)
			}
		MAX-ACCESS read-write
		STATUS current
		DESCRIPTION
			"Clear Running Configuration Command, write only"
		::= { avSurvConfig 7 }

	-- 1.3.6.1.4.1.6889.2.6.4.1.8
	avSurvGatewayNumber OBJECT-TYPE
		SYNTAX Integer32 (1..250)
	 	MAX-ACCESS read-only
		STATUS current
		DESCRIPTION
			"Gateway Identification Number (see CM Media Gateway form)"
		::= { avSurvConfig 8 }

	-- 1.3.6.1.4.1.6889.2.6.4.1.9
	avSurvPimLockout OBJECT-TYPE
		SYNTAX INTEGER
			{
				enabled	(1),
				disabled	(2)
			}
	 	MAX-ACCESS read-write
		STATUS current
		DESCRIPTION
			"Allows Craft to prevent PIM updates from being downloaded during local diagnostic session"
		::= { avSurvConfig 9 }

	-- 1.3.6.1.4.1.6889.2.6.4.1.10
	avSurvAttendantAccessCode OBJECT-TYPE
		SYNTAX DisplayString (SIZE (1..3))
		MAX-ACCESS read-create
		STATUS current
		DESCRIPTION
			"Allows a station in the branch office to be able
                    to directly dial an attendant position"
		::= { avSurvConfig 10 }

	-- 1.3.6.1.4.1.6889.2.6.4.1.11
	avSurvAttendantExtension OBJECT-TYPE
		SYNTAX DisplayString (SIZE (1..13))
		MAX-ACCESS read-create
		STATUS current
		DESCRIPTION
			"Specifies the station which shall serve as the branch office attendant position.
                   Used as destination to direct un-routable incoming trunk calls."
		::= { avSurvConfig 11 }

-- 1.3.6.1.4.1.6889.2.6.4.2
avSurvStationTable OBJECT-TYPE
	SYNTAX SEQUENCE OF AvSurvStationEntry
	MAX-ACCESS not-accessible
	STATUS current
	DESCRIPTION
		"Station Table"
	::= { avSurvMib 2 }

	-- 1.3.6.1.4.1.6889.2.6.4.2.1
	avSurvStationEntry OBJECT-TYPE
		SYNTAX AvSurvStationEntry
		MAX-ACCESS not-accessible
		STATUS current
		DESCRIPTION
			"Each entry contains index, extension number, type, interface bit map, COR, trunk-destination status, expansion-module, slot/port, switchhook-flash, IP address of registered station, and station name"
		INDEX {
			avSurvStationIndex
		}
		::= { avSurvStationTable 1 }

		AvSurvStationEntry ::= SEQUENCE {
			avSurvStationIndex			Integer32,
			avSurvStationExt				DisplayString,
			avSurvStationType				INTEGER,
			avSurvStationInterfaceIndex		Integer32,
			avSurvStationCOR				INTEGER,
			avSurvStationTrunkDest			TruthValue,
			avSurvStationRowStatus			RowStatus,
			avSurvStationExpansionModule		TruthValue,
			avSurvStationSlotPort			DisplayString,
			avSurvStationSwitchHookFlash		TruthValue,
			avSurvStationIpAddressRegistered	OCTET STRING,
			avSurvStationName				DisplayString
			}

		-- 1.3.6.1.4.1.6889.2.6.4.2.1.1
		avSurvStationIndex OBJECT-TYPE
			SYNTAX Integer32 (1..340)
			MAX-ACCESS read-create
			STATUS current
			DESCRIPTION
				"Station Table Index"
			::= { avSurvStationEntry 1 }

		-- 1.3.6.1.4.1.6889.2.6.4.2.1.2
		avSurvStationExt OBJECT-TYPE
			SYNTAX DisplayString (SIZE (1..13))
			MAX-ACCESS read-create
			STATUS current
			DESCRIPTION
				"Station Extension number"
			::= { avSurvStationEntry 2 }


		-- 1.3.6.1.4.1.6889.2.6.4.2.1.3
		avSurvStationType OBJECT-TYPE
			SYNTAX INTEGER
				{
					ip4601		(1),
					ip4602		(2),
					ip4602Sw		(3),
					ip4606		(4),
					ip4610Sw		(5),
					ip4612		(6),
					ip4620		(7),
					ip4620Sw		(8),
					ip4624		(9),
					analog2500		(10),
					ip4621		(11),
					ip4622		(12),
					ip4625		(13),
					dcp2402		(20),
					dcp2410		(21),
					dcp2420		(22),
					dcp6402		(30),
					dcp6402D		(31),
					dcp6408		(32),
					dcp6408plus		(33),
					dcp6408D		(34),
					dcp6408Dplus	(35),
					dcp6416Dplus	(36),
					dcp6424Dplus	(37),
					dcp8403B		(40),
					dcp8405B		(41),
					dcp8405Bplus	(42),
					dcp8405D		(43),
					dcp8405Dplus	(44),
					dcp8410B		(45),
					dcp8410D		(46),
					dcp8411B		(47),
					dcp8411D		(48),
					dcp8434D		(49)
				}
			MAX-ACCESS read-create
			STATUS current
			DESCRIPTION
				"Station model type"
			::= { avSurvStationEntry 3 }

		-- 1.3.6.1.4.1.6889.2.6.4.2.1.4
		avSurvStationInterfaceIndex OBJECT-TYPE
			SYNTAX Integer32 (1..2147483647)
			MAX-ACCESS read-create
			STATUS current
			DESCRIPTION
				"Interface Index bit map. Bit assignment as follows: bits 0-7 = port,
				  bits 8-11 = slot, bits 12-23 = unused, bits 24-31 = module type.
                          Note: This element has been deprecated in SLS R4.1. For legacy stations,
                                 use avSurvStationSlotPort to communicate slot-port info."
			::= { avSurvStationEntry 4 }

		-- 1.3.6.1.4.1.6889.2.6.4.2.1.5
		avSurvStationCOR OBJECT-TYPE
			SYNTAX INTEGER
				{
					emergency			(1),
					internal			(2),
					local				(3),
					toll				(4),
					unrestricted		(5)
				}
			MAX-ACCESS read-create
			STATUS current
			DESCRIPTION
				"Station Class of Outgoing Restriction (COR) level"
			::= { avSurvStationEntry 5 }

		-- 1.3.6.1.4.1.6889.2.6.4.2.1.6
		avSurvStationTrunkDest OBJECT-TYPE
			SYNTAX TruthValue
			MAX-ACCESS read-create
			STATUS current
			DESCRIPTION
				"Station trunk destination. Can be used to answer incomming trunk calls"
			::= { avSurvStationEntry 6 }

		-- 1.3.6.1.4.1.6889.2.6.4.2.1.7
		avSurvStationRowStatus OBJECT-TYPE
			SYNTAX RowStatus
			MAX-ACCESS read-create
			STATUS current
			DESCRIPTION
				"Create/Delete a row entry"
			::= {avSurvStationEntry 7 }

		-- 1.3.6.1.4.1.6889.2.6.4.2.1.8
		avSurvStationExpansionModule OBJECT-TYPE
			SYNTAX TruthValue
			MAX-ACCESS read-create
			STATUS current
			DESCRIPTION
				"Station set has an expansion module in place. This is only
                          allowed for the digital phones (IP and DCP.
                          IP phone models 4620, 4621, 4625 may use EU24 and EU24BL.
				  DCP phone models 2420 may use EU24 and EU24BL.
				  DCP phone models 6416 and 6424 may use modesl 801A and XM24."
			::= {avSurvStationEntry 8 }

		-- 1.3.6.1.4.1.6889.2.6.4.2.1.9
		avSurvStationSlotPort OBJECT-TYPE
			SYNTAX DisplayString (SIZE (4..4))
			MAX-ACCESS read-create
			STATUS current
			DESCRIPTION
				"CM slot/port in the Vyxx format"
			::= {avSurvStationEntry 9 }

		-- 1.3.6.1.4.1.6889.2.6.4.2.1.10
		avSurvStationSwitchHookFlash OBJECT-TYPE
			SYNTAX TruthValue
			MAX-ACCESS read-create
			STATUS current
			DESCRIPTION
				"Switchhook flash is allowed only for analog phones"
			::= {avSurvStationEntry 10 }


		-- 1.3.6.1.4.1.6889.2.6.4.2.1.11
		avSurvStationIpAddressRegistered OBJECT-TYPE
			SYNTAX OCTET STRING (SIZE(1..4))
			MAX-ACCESS read-only
			STATUS current
			DESCRIPTION
				"IP address of registered IP station. Note only for IP stations"
			::= {avSurvStationEntry 11 }

		-- 1.3.6.1.4.1.6889.2.6.4.2.1.12
		avSurvStationName OBJECT-TYPE
			SYNTAX DisplayString (SIZE (0..27))
			MAX-ACCESS read-create
			STATUS current
			DESCRIPTION
				"Station or user's Name"
			::= { avSurvStationEntry 12 }

-- 1.3.6.1.4.1.6889.2.6.4.3
avSurvTrunkGroupTable OBJECT-TYPE
	SYNTAX SEQUENCE OF AvSurvTrunkGroupEntry
	MAX-ACCESS not-accessible
	STATUS current
	DESCRIPTION
		"Trunk Group Table"
	::= { avSurvMib 3 }

	-- 1.3.6.1.4.1.6889.2.6.4.3.1
	avSurvTrunkGroupEntry OBJECT-TYPE
		SYNTAX AvSurvTrunkGroupEntry
		MAX-ACCESS not-accessible
		STATUS current
		DESCRIPTION
			"Each entry contains index(ACM Trunk Group Number),  trunk-type, Trunk Access Code, and dial-mode"
		INDEX {
			avSurvTrunkGroupNum
		}
		::= { avSurvTrunkGroupTable 1 }

		AvSurvTrunkGroupEntry ::= SEQUENCE {
			avSurvTrunkGroupNum			INTEGER,
			avSurvTrunkGroupType			INTEGER,
			avSurvTrunkGroupTAC			DisplayString,
			avSurvTrunkGroupDial			INTEGER,
			avSurvTrunkGroupRowStatus		RowStatus,
			avSurvTrunkGroupDidDigitTreatment	INTEGER,
			avSurvTrunkGroupDidDigitsInsert	DisplayString,
			avSurvTrunkGroupDidSupervision	INTEGER,
			avSurvTrunkGroupName			DisplayString,
			avSurvTrunkGroupCodesetDisplay	INTEGER,
			avSurvTrunkGroupCodesetNational	INTEGER,
			avSurvTrunkGroupChannelPreference	INTEGER,
			avSurvTrunkGroupDigitHandling		INTEGER,
			avSurvTrunkGroupJapanDisconnect	INTEGER,
			avSurvTrunkGroupSendName		INTEGER,
			avSurvTrunkGroupSendCallingNumber	INTEGER,
			avSurvTrunkGroupNumberingFormat	INTEGER,
			avSurvTrunkGroupIncomingDestination	DisplayString,
			avSurvTrunkGroupIncomingDialTone	INTEGER,
			avSurvTrunkGroupR2MFCSignaling	INTEGER,
			avSurvTrunkGroupTrunkHunt		INTEGER,
			avSurvTrunkGroupDs1Supervision	INTEGER,
			avSurvTrunkGroupCbc                 INTEGER,
			avSurvTrunkGroupCbcServiceFeature   INTEGER,
			avSurvTrunkGroupCbcParameter        INTEGER,
			avSurvTrunkGroupBusyDisconnect	INTEGER
		}

		-- 1.3.6.1.4.1.6889.2.6.4.3.1.1
		avSurvTrunkGroupNum OBJECT-TYPE
			SYNTAX INTEGER (1..2000)
			MAX-ACCESS read-create
			STATUS current
			DESCRIPTION
				"Trunk Group Number"
			::= { avSurvTrunkGroupEntry 1 }

		-- 1.3.6.1.4.1.6889.2.6.4.3.1.2
		avSurvTrunkGroupType OBJECT-TYPE
			SYNTAX INTEGER
				{
					analogLoopStart 		(1),
					analogDid			(2),
					analogGroundStart		(3),
					bri				(4),
					t1InBandSignaling		(5),
					t1IsdnSignaling		(6),
					e1InBandSignaling		(7),
					e1IsdnSignaling		(8)
				}
			MAX-ACCESS read-create
			STATUS current
			DESCRIPTION
				"Trunk Group Type"
			::= { avSurvTrunkGroupEntry 2 }

		-- 1.3.6.1.4.1.6889.2.6.4.3.1.3
		avSurvTrunkGroupTAC OBJECT-TYPE
			SYNTAX DisplayString (SIZE (1..4))
			MAX-ACCESS read-create
			STATUS current
			DESCRIPTION
				"Trunk Group Trunk Access Code (TAC)"
			::= { avSurvTrunkGroupEntry 3 }

		-- 1.3.6.1.4.1.6889.2.6.4.3.1.4
			avSurvTrunkGroupDial OBJECT-TYPE
			SYNTAX INTEGER
				{
					rotary	(1),
					dtmf		(2),
					mf		(3)
				}
			MAX-ACCESS read-create
			STATUS current
			DESCRIPTION
				"Trunk Group Outward Dial. Note MF not supported in SLS"
			::= { avSurvTrunkGroupEntry 4 }

		-- 1.3.6.1.4.1.6889.2.6.4.3.1.5
		avSurvTrunkGroupRowStatus OBJECT-TYPE
			SYNTAX RowStatus
			MAX-ACCESS read-create
			STATUS current
			DESCRIPTION
				"Create/Delete a row entry"
			::= {avSurvTrunkGroupEntry 5 }

		-- 1.3.6.1.4.1.6889.2.6.4.3.1.6
		avSurvTrunkGroupDidDigitTreatment OBJECT-TYPE
			SYNTAX INTEGER
				{
					absorb1	(1),
					absorb2	(2),
					absorb3	(3),
					absorb4	(4),
					absorb5	(5),
					insert1	(11),
					insert2	(12),
					insert3	(13),
					insert4	(14),
					blank		(99)
				}
			MAX-ACCESS read-create
			STATUS current
			DESCRIPTION
				"Trunk Group DID digit treatment option.
                         This applies for analog DID trunks and non-ISDN digital tie trunks.
				  Note: blank means take no action."
			::= { avSurvTrunkGroupEntry 6 }

		-- 1.3.6.1.4.1.6889.2.6.4.3.1.7
		avSurvTrunkGroupDidDigitsInsert OBJECT-TYPE
			SYNTAX DisplayString (SIZE (0..4))
			MAX-ACCESS read-create
			STATUS current
			DESCRIPTION
				"Digit string to be inserted for DID treatment
                         This applies for analog DID trunks and non-ISDN digital tie trunks."
			::= { avSurvTrunkGroupEntry 7 }

		-- 1.3.6.1.4.1.6889.2.6.4.3.1.8
		avSurvTrunkGroupDidSupervision OBJECT-TYPE
			SYNTAX INTEGER
				{
					immediate	(1),
					wink		(2)
				}
			MAX-ACCESS read-create
			STATUS current
			DESCRIPTION
				"Type of incoming supervision used on DID trunk.
                          This applies only for analog DID trunks."
			::= { avSurvTrunkGroupEntry 8 }

		-- 1.3.6.1.4.1.6889.2.6.4.3.1.9
		avSurvTrunkGroupName OBJECT-TYPE
			SYNTAX DisplayString (SIZE (0..27))
			MAX-ACCESS read-create
			STATUS current
			DESCRIPTION
				"Customer's name for trunk group"
			::= { avSurvTrunkGroupEntry 9 }

		-- 1.3.6.1.4.1.6889.2.6.4.3.1.10
		avSurvTrunkGroupCodesetDisplay OBJECT-TYPE
			SYNTAX INTEGER
				{
					codeset0	(0),
					codeset6	(6),
					codeset7	(7)
				}
			MAX-ACCESS read-create
			STATUS current
			DESCRIPTION
				"Which Q.931 codesets are allowed to send Display IE's to the user phones
                         This applies only to ISDN BRI/PRI trunks."
			::= { avSurvTrunkGroupEntry 10 }

		-- 1.3.6.1.4.1.6889.2.6.4.3.1.11
		avSurvTrunkGroupCodesetNational OBJECT-TYPE
			SYNTAX INTEGER
				{
					codeset6	(6),
					codeset7	(7)
				}
			MAX-ACCESS read-create
			STATUS current
			DESCRIPTION
				"Which codesets are allowed to send National supported IE's.
                          This applies only to ISDN BRI/PRI trunks."
			::= { avSurvTrunkGroupEntry 11 }

		-- 1.3.6.1.4.1.6889.2.6.4.3.1.12
		avSurvTrunkGroupChannelPreference OBJECT-TYPE
			SYNTAX INTEGER
				{
					exclusive	(1),
					preferred	(2)
				}
			MAX-ACCESS read-create
			STATUS current
			DESCRIPTION
				"Used for encoding Channel-ID IE.
                          This applies only to ISDN BRI/PRI trunks."
			::= { avSurvTrunkGroupEntry 12 }

		-- 1.3.6.1.4.1.6889.2.6.4.3.1.13
		avSurvTrunkGroupDigitHandling OBJECT-TYPE
			SYNTAX INTEGER
				{
					enblocEnbloc	(0),
					enblocOverlap	(1),
					overlapEnbloc	(2),
					overlapOverlap	(3)
				}
			MAX-ACCESS read-create
			STATUS current
			DESCRIPTION
				"Defines overlap receiving and transmitting rules.
                         This applies only to ISDN BRI/PRI trunks."
			::= { avSurvTrunkGroupEntry 13 }

		-- 1.3.6.1.4.1.6889.2.6.4.3.1.14
		avSurvTrunkGroupJapanDisconnect OBJECT-TYPE
			SYNTAX INTEGER
				{
					yes		(1),
					no		(2)
				}
			MAX-ACCESS read-create
			STATUS current
			DESCRIPTION
				"Send a Q.931 CONNECT msg right before sending DISCONNECT msg.
                         This applies only to ISDN BRI/PRI trunks in Japan."
			::= { avSurvTrunkGroupEntry 14 }

		-- 1.3.6.1.4.1.6889.2.6.4.3.1.15
		avSurvTrunkGroupSendName OBJECT-TYPE
			SYNTAX INTEGER
				{
					yes			(1),
					no			(2),
					restricted		(3)
				}
			MAX-ACCESS read-create
			STATUS current
			DESCRIPTION
				"Specifies whether Calling, Connected, Called party's name
                          is to be shared with network.
                          This applies only to ISDN BRI/PRI trunks.
                          Default is no."
			::= { avSurvTrunkGroupEntry 15 }

		-- 1.3.6.1.4.1.6889.2.6.4.3.1.16
		avSurvTrunkGroupSendCallingNumber OBJECT-TYPE
			SYNTAX INTEGER
				{
					yes			(1),
					no			(2),
					restricted		(3)
				}
			MAX-ACCESS read-create
			STATUS current
			DESCRIPTION
				"Specifies how to fill the Calling-Party and Called-Party IE fields.
                          This applies only to ISDN BRI/PRI trunks.
                          Default is no."
			::= { avSurvTrunkGroupEntry 16 }

		-- 1.3.6.1.4.1.6889.2.6.4.3.1.17
		avSurvTrunkGroupNumberingFormat OBJECT-TYPE
			SYNTAX INTEGER
				{
					unknown		(1),
					public		(2),
					private		(3),
					unknownPrivate	(4)
				}
			MAX-ACCESS read-create
			STATUS current
			DESCRIPTION
				"Specifies how to fill the Calling-Party and Called-Party IE fields.
                         This applies only to ISDN BRI/PRI trunks.
                         SLS only supports unknown(1) and public(2). Default is unknown."
			::= { avSurvTrunkGroupEntry 17 }

		-- 1.3.6.1.4.1.6889.2.6.4.3.1.18
		avSurvTrunkGroupIncomingDestination OBJECT-TYPE
			SYNTAX DisplayString (SIZE (0..13))
			MAX-ACCESS read-create
			STATUS current
			DESCRIPTION
				" Analog DID and non-ISDN Digital:Sets a destination station for routing incoming trunk group calls"
			::= { avSurvTrunkGroupEntry 18 }

		-- 1.3.6.1.4.1.6889.2.6.4.3.1.19
		avSurvTrunkGroupIncomingDialTone OBJECT-TYPE
			SYNTAX INTEGER
				{
					yes	(1),
					no	(2)
				}
			MAX-ACCESS read-create
			STATUS current
			DESCRIPTION
				"Analog DID and non-ISDN Digital:Determines whether SLS is to supply dial tone in response to far-end seizure"
			::= { avSurvTrunkGroupEntry 19 }

		-- 1.3.6.1.4.1.6889.2.6.4.3.1.20
		avSurvTrunkGroupR2MFCSignaling OBJECT-TYPE
			SYNTAX INTEGER
				{
					set1	(1),
					set2	(2),
					set3	(3),
					set4	(4),
					set5	(5),
					set6	(6),
					set7	(7),
					set8	(8)
				}
			MAX-ACCESS read-create
			STATUS current
			DESCRIPTION
				"Determines MFC signaling set to be used.
                          This only applies to R2MFC trunks.
                          This feature not supported in SLS for R4.0"
			::= { avSurvTrunkGroupEntry 20 }

		-- 1.3.6.1.4.1.6889.2.6.4.3.1.21
		avSurvTrunkGroupTrunkHunt OBJECT-TYPE
			SYNTAX INTEGER
				{
					ascend	(1),
					cyclical	(2),
					descend	(3)
				}
			MAX-ACCESS read-create
			STATUS current
			DESCRIPTION
				"Determines the method in which the SLS call engine selects from
                         the trunk group pool of available trunks.
			       This only applies to digital trunks."
			::= { avSurvTrunkGroupEntry 21 }

		-- 1.3.6.1.4.1.6889.2.6.4.3.1.22
		avSurvTrunkGroupDs1Supervision OBJECT-TYPE
			SYNTAX INTEGER
				{
					loopStart			(3),
					groundStart			(4),
					winkWink			(5),
					winkImmediate		(6),
					winkAuto			(7),
					immediateImmediate	(8),
					autoAuto			(9),
					autoWink			(10)
				}
			MAX-ACCESS read-create
			STATUS current
			DESCRIPTION
				"Applies to non-ISDN DS1 trunks: Specifies the type
				of incomming/outgoing supervision that is used on these trunks."
			::= { avSurvTrunkGroupEntry 22 }


		-- 1.3.6.1.4.1.6889.2.6.4.3.1.23
		avSurvTrunkGroupCbc OBJECT-TYPE
			SYNTAX INTEGER
				{
					yes		(1),
					no		(2)
				}
			MAX-ACCESS read-create
			STATUS current
			DESCRIPTION
				"Applies to ISDN DS1 trunks: Specifies whether the trunk is to
                         operate in call-by-call basis. If yes, then send the NSF IE."
			::= { avSurvTrunkGroupEntry 23 }


		-- 1.3.6.1.4.1.6889.2.6.4.3.1.24
		avSurvTrunkGroupCbcServiceFeature OBJECT-TYPE
			SYNTAX INTEGER
				{
					sdn					(225),
					megacom				(227),
					operator			(197),
					suboperator			(198),
					lds   				(231),
					scocs				(246)
				}
			MAX-ACCESS read-create
			STATUS current
			DESCRIPTION
				"Applies to ISDN DS1 trunks: Specifies the type of service
                         or feature specifed in the NSF IE for outbound trunk calls.
                         Only valid if CBC=yes."
			::= { avSurvTrunkGroupEntry 24 }

		-- 1.3.6.1.4.1.6889.2.6.4.3.1.25
		avSurvTrunkGroupCbcParameter OBJECT-TYPE
			SYNTAX INTEGER (0..99999)
			MAX-ACCESS read-create
			STATUS current
			DESCRIPTION
				"Applies to ISDN DS1 trunks: Specifies the class of
                         service being offered as part of Selective Class of
                         Call Selection (scocs)service mode.
                         Only valid if service mode is scocs."
			::= { avSurvTrunkGroupEntry 25 }


		-- 1.3.6.1.4.1.6889.2.6.4.3.1.26
		avSurvTrunkGroupBusyDisconnect OBJECT-TYPE
			SYNTAX INTEGER
				{
					yes		(1),
					no		(2)
				}
			MAX-ACCESS read-create
			STATUS current
			DESCRIPTION
				"Applies to Analog Loop Start Trunks: Specifies whether
						the presence of busy tone signal will cause the
						trunk call to be disconnected. Default = no."
			::= { avSurvTrunkGroupEntry 26 }

-- 1.3.6.1.4.1.6889.2.6.4.4
avSurvTrunkTable OBJECT-TYPE
	SYNTAX SEQUENCE OF AvSurvTrunkEntry
	MAX-ACCESS not-accessible
	STATUS current
	DESCRIPTION
		"Trunk table"
	::= { avSurvMib 4 }

	-- 1.3.6.1.4.1.6889.2.6.4.4.1
	avSurvTrunkEntry OBJECT-TYPE
		SYNTAX AvSurvTrunkEntry
		MAX-ACCESS not-accessible
		STATUS current
		DESCRIPTION
			"Each entry contains dual index(group-reference-number and table index), interface bit map, slot-port, and sig-group reference-number"
		INDEX {
			avSurvTrunkGroupRefNumber, avSurvTrunkIndex
		}
		::= { avSurvTrunkTable 1 }

		AvSurvTrunkEntry ::= SEQUENCE {
			avSurvTrunkGroupRefNumber	INTEGER,
			avSurvTrunkIndex			Integer32,
			avSurvTrunkInterfaceIndex	Integer32,
			avSurvTrunkRowStatus		RowStatus,
			avSurvTrunkSlotPort		DisplayString,
			avSurvTrunkSigGroupRefNumber INTEGER
		}

		-- 1.3.6.1.4.1.6889.2.6.4.4.1.1
		avSurvTrunkGroupRefNumber OBJECT-TYPE
			SYNTAX INTEGER (1..2000)
			MAX-ACCESS read-create
			STATUS current
			DESCRIPTION
				"Trunk Pool Group Reference Number - Association of trunk pool
				with trunk group"
			::= { avSurvTrunkEntry 1 }

		-- 1.3.6.1.4.1.6889.2.6.4.4.1.2
		avSurvTrunkIndex OBJECT-TYPE
			SYNTAX Integer32	(1..255)
			MAX-ACCESS read-create
			STATUS current
			DESCRIPTION
				"trunk table index"
			::= { avSurvTrunkEntry 2 }

		-- 1.3.6.1.4.1.6889.2.6.4.4.1.3
		avSurvTrunkInterfaceIndex OBJECT-TYPE
			SYNTAX Integer32 (1..2147483647)
			MAX-ACCESS read-create
			STATUS current
			DESCRIPTION
				"Interface Index bit map. Bit assignment as follows: bits 0-7 = port,
				  bits 8-11 = slot, bits 12-23 = unused, bits 24-31 = module type
                          Note: This element has been deprecated in SLS R4.1. For legacy trunks,
                                 use avSurvTrunkSlotPort to communicate slot-port info."
			::= { avSurvTrunkEntry 3 }

		-- 1.3.6.1.4.1.6889.2.6.4.4.1.4
		avSurvTrunkRowStatus OBJECT-TYPE
			SYNTAX RowStatus
			MAX-ACCESS read-create
			STATUS current
			DESCRIPTION
				"Create/Delete a row entry"
			::= {avSurvTrunkEntry 4 }

		-- 1.3.6.1.4.1.6889.2.6.4.4.1.5
		avSurvTrunkSlotPort OBJECT-TYPE
			SYNTAX DisplayString (SIZE(4..4))
			MAX-ACCESS read-create
			STATUS current
			DESCRIPTION
				"ACM slot/port in the Vyxx format"
			::= {avSurvTrunkEntry 5 }

		-- 1.3.6.1.4.1.6889.2.6.4.4.1.6
		avSurvTrunkSigGroupRefNumber OBJECT-TYPE
			SYNTAX INTEGER (1..650)
			MAX-ACCESS read-create
			STATUS current
			DESCRIPTION
				"Signaling Group Number that is the manager of this ISDN trunk member"
			::= { avSurvTrunkEntry 6 }


-- 1.3.6.1.4.1.6889.2.6.4.5
avSurvArsTable OBJECT-TYPE
	SYNTAX SEQUENCE OF AvSurvArsEntry
	MAX-ACCESS not-accessible
	STATUS current
	DESCRIPTION
		"Automatic Route Selection (ARS) Table"
	::= { avSurvMib 5 }

	-- 1.3.6.1.4.1.6889.2.6.4.5.1
	avSurvArsEntry OBJECT-TYPE
		SYNTAX AvSurvArsEntry
		MAX-ACCESS not-accessible
		STATUS current
		DESCRIPTION
			"Each entry contains index, dial-string-pattern, dial-plan-type, max-length, group-reference-number, dial-action, delete-digits, insert-digits, and min-length"
		INDEX {
			avSurvDialIndex
		}
		::= { avSurvArsTable 1 }

		AvSurvArsEntry ::= SEQUENCE {
			avSurvDialIndex			Integer32,
			avSurvDialString			DisplayString,
			avSurvDialType			INTEGER,
			avSurvDialMaximumLength		INTEGER,
			avSurvDialGroupRefNumber	INTEGER,
			avSurvDialAction			INTEGER,
			avSurvDialRowStatus		RowStatus,
			avSurvDialDeleteDigits		INTEGER,
			avSurvDialInsertDigits		DisplayString,
			avSurvDialMinimumLength		INTEGER
		}

		-- 1.3.6.1.4.1.6889.2.6.4.5.1.1
		avSurvDialIndex OBJECT-TYPE
			SYNTAX Integer32	(1..100)
			MAX-ACCESS read-create
			STATUS current
			DESCRIPTION
				"Call Pattern index"
			::= { avSurvArsEntry 1 }

		-- 1.3.6.1.4.1.6889.2.6.4.5.1.2
		avSurvDialString OBJECT-TYPE
			SYNTAX DisplayString (SIZE (1..18))
			MAX-ACCESS read-create
			STATUS current
			DESCRIPTION
				"Dialed string entry that is used to match a pattern
						within the user-dialed number"
			::= { avSurvArsEntry 2 }

		-- 1.3.6.1.4.1.6889.2.6.4.5.1.3
		avSurvDialType OBJECT-TYPE
			SYNTAX INTEGER
				{
					emergency				(1),
					foreignNumberingPlanArea	(2),
					homeNumberingPlanArea		(3),
					international			(4),
					internationalOperator		(5),
					local					(6),
					national				(7),
					operator				(8),
					service				(9)
				}
			MAX-ACCESS read-create
			STATUS current
			DESCRIPTION
				"Call Type"
			::= { avSurvArsEntry 3 }

		-- 1.3.6.1.4.1.6889.2.6.4.5.1.4
		avSurvDialMaximumLength OBJECT-TYPE
			SYNTAX INTEGER (1..28)
			MAX-ACCESS read-create
			STATUS current
			DESCRIPTION
				"Maximum length of the user-dialed number that the survivability
					call-engine collects to match to the dialed-string.
					By default, the minimum length is defined to be equal to
					the length of the dialed string"
			::= { avSurvArsEntry 4 }

		-- 1.3.6.1.4.1.6889.2.6.4.5.1.5
		avSurvDialGroupRefNumber OBJECT-TYPE
			SYNTAX INTEGER (1..2000)
			MAX-ACCESS read-create
			STATUS current
			DESCRIPTION
				"Call group reference number"
			::= { avSurvArsEntry 5 }

		-- 1.3.6.1.4.1.6889.2.6.4.5.1.6
		avSurvDialAction OBJECT-TYPE
			SYNTAX INTEGER
				{
					denyCall		(1),
					allowCall		(2)
				}
			MAX-ACCESS read-create
			STATUS current
			DESCRIPTION
				"Call dial action"
			::= { avSurvArsEntry 6 }

		-- 1.3.6.1.4.1.6889.2.6.4.5.1.7
		avSurvDialRowStatus OBJECT-TYPE
			SYNTAX RowStatus
			MAX-ACCESS read-create
			STATUS current
			DESCRIPTION
				"Create/Delete a row entry"
			::= {avSurvArsEntry 7 }

		-- 1.3.6.1.4.1.6889.2.6.4.5.1.8
		avSurvDialDeleteDigits OBJECT-TYPE
			SYNTAX INTEGER (0..28)
			MAX-ACCESS read-create
			STATUS current
			DESCRIPTION
				"Specifies the number of dialed digits to be deleted from
				 the beginning of the string"
			::= { avSurvArsEntry 8 }

		-- 1.3.6.1.4.1.6889.2.6.4.5.1.9
		avSurvDialInsertDigits OBJECT-TYPE
			SYNTAX DisplayString (SIZE (0..36))
			MAX-ACCESS read-create
			STATUS current
			DESCRIPTION
				"Specifies the digit string to be inserted. Includes ',' for pause."
			::= { avSurvArsEntry 9 }

		-- 1.3.6.1.4.1.6889.2.6.4.5.1.10
		avSurvDialMinimumLength OBJECT-TYPE
			SYNTAX INTEGER (1..28)
			MAX-ACCESS read-create
			STATUS current
			DESCRIPTION
				"Minimum length of the user-dialed number that the survivability
					call-engine collects to match to the dialed-string.
					By default, the minimum length is defined to be equal to
					the length of the avSurvDialString element"
			::= { avSurvArsEntry 10 }



-- 1.3.6.1.4.1.6889.2.6.4.6
avSurvFacTable OBJECT-TYPE
	SYNTAX SEQUENCE OF AvSurvFacEntry
	MAX-ACCESS not-accessible
	STATUS current
	DESCRIPTION
		"Automatic Route Selection Facility Table"
	::= { avSurvMib 6 }

	-- 1.3.6.1.4.1.6889.2.6.4.6.1
	avSurvFacEntry OBJECT-TYPE
		SYNTAX AvSurvFacEntry
		MAX-ACCESS not-accessible
		STATUS current
		DESCRIPTION
			"Each entry contains index, an ARS Facility dialing code and the Type of FAC feature"
		INDEX {
			avSurvFacIndex
		}
		::= { avSurvFacTable 1 }

		AvSurvFacEntry ::= SEQUENCE {
			avSurvFacIndex		Integer32,
			avSurvFacId			DisplayString,
			avSurvFacRowStatus	RowStatus,
			avSurvFacType		INTEGER
		}

		-- 1.3.6.1.4.1.6889.2.6.4.6.1.1
		avSurvFacIndex OBJECT-TYPE
			SYNTAX Integer32	(1..20)
			MAX-ACCESS read-create
			STATUS current
			DESCRIPTION
				"Fac Index"
			::= { avSurvFacEntry 1 }

		-- 1.3.6.1.4.1.6889.2.6.4.6.1.2
		avSurvFacId OBJECT-TYPE
			SYNTAX DisplayString (SIZE (1..4))
			MAX-ACCESS read-create
			STATUS current
			DESCRIPTION
				"ARS Facility dialing code"
			::= { avSurvFacEntry 2 }

		-- 1.3.6.1.4.1.6889.2.6.4.6.1.3
		avSurvFacRowStatus OBJECT-TYPE
			SYNTAX RowStatus
			MAX-ACCESS read-create
			STATUS current
			DESCRIPTION
				"Create/Delete a row entry"
			::= { avSurvFacEntry 3 }


		-- 1.3.6.1.4.1.6889.2.6.4.6.1.4
		avSurvFacType OBJECT-TYPE
			SYNTAX INTEGER
				{
					ars1			(1),
					ars2			(2),
					hold			(3),
					contactOpen		(4),
					contactClose	(5),
					contactPulse	(6)
				}
			MAX-ACCESS read-create
			STATUS current
			DESCRIPTION
				"Feature Access Code(FAC) dial codes Supported"
			::= { avSurvFacEntry 4 }



-- 1.3.6.1.4.1.6889.2.6.4.1.7
avSurvIpVoiceCodecSetTable OBJECT-TYPE
	SYNTAX SEQUENCE OF AvSurvIpVoiceCodecSetEntry
	MAX-ACCESS not-accessible
	STATUS current
	DESCRIPTION
		"Ip Voice Codec Set Table"
	::= { avSurvMib 7 }

	-- 1.3.6.1.4.1.6889.2.6.4.7.1
	avSurvIpVoiceCodecSetEntry OBJECT-TYPE
		SYNTAX AvSurvIpVoiceCodecSetEntry
		MAX-ACCESS not-accessible
		STATUS current
		DESCRIPTION
			"Each entry contains dual index(cm-codec-set-num and table index), priority, codec-type, silence sup, number-of-frames"
		INDEX {
			avSurvIpVoiceCodecSetNum, avSurvIpVoiceCodecSetIndex
		}
		::= { avSurvIpVoiceCodecSetTable 1 }

		AvSurvIpVoiceCodecSetEntry ::= SEQUENCE {
			avSurvIpVoiceCodecSetNum			Integer32,
			avSurvIpVoiceCodecSetIndex			Integer32,
			avSurvIpVoiceCodecSetPriority			INTEGER,
			avSurvIpVoiceCodecSetType			INTEGER,
			avSurvIpVoiceCodecSetSilence			TruthValue,
			avSurvIpVoiceCodecSetFrames			INTEGER,
			avSurvIpVoiceCodecSetRowStatus		RowStatus
		}

		-- 1.3.6.1.4.1.6889.2.6.4.7.1.1
		avSurvIpVoiceCodecSetNum OBJECT-TYPE
			SYNTAX Integer32	(1..7)
			MAX-ACCESS read-create
			STATUS current
			DESCRIPTION
				"Ip Codec Set Identification"
			::= { avSurvIpVoiceCodecSetEntry 1 }

		-- 1.3.6.1.4.1.6889.2.6.4.7.1.2
		avSurvIpVoiceCodecSetIndex OBJECT-TYPE
			SYNTAX Integer32	(1..7)
			MAX-ACCESS read-create
			STATUS current
			DESCRIPTION
				"Ip Codec Index"
			::= { avSurvIpVoiceCodecSetEntry 2 }

		-- 1.3.6.1.4.1.6889.2.6.4.7.1.3
		avSurvIpVoiceCodecSetPriority OBJECT-TYPE
			SYNTAX INTEGER (1 .. 7)
			MAX-ACCESS read-create
			STATUS current
			DESCRIPTION
				"Priority of codec set type (determines preferential use)"
			::= { avSurvIpVoiceCodecSetEntry 3 }

		-- 1.3.6.1.4.1.6889.2.6.4.7.1.4
		avSurvIpVoiceCodecSetType OBJECT-TYPE
			SYNTAX INTEGER
				{
					g711u			(1),
					g711a			(2),
					g723			(3),
					g729			(4),
					g729a			(5),
					g729b			(6),
					g729ab		(7)
				}
			MAX-ACCESS read-create
			STATUS current
			DESCRIPTION
				"Ip Codec Type"
			::= { avSurvIpVoiceCodecSetEntry 4 }

		-- 1.3.6.1.4.1.6889.2.6.4.7.1.5
		avSurvIpVoiceCodecSetSilence OBJECT-TYPE
			SYNTAX TruthValue
			MAX-ACCESS read-create
			STATUS current
			DESCRIPTION
				"IP Codec Silence Suppression"
			::= { avSurvIpVoiceCodecSetEntry 5 }

		-- 1.3.6.1.4.1.6889.2.6.4.7.1.6
		avSurvIpVoiceCodecSetFrames OBJECT-TYPE
			SYNTAX INTEGER (1..6)
			MAX-ACCESS read-create
			STATUS current
			DESCRIPTION
				"IP Codec number of frames"
			::= { avSurvIpVoiceCodecSetEntry 6 }

		-- 1.3.6.1.4.1.6889.2.6.4.1.7.1.7
		avSurvIpVoiceCodecSetRowStatus OBJECT-TYPE
			SYNTAX RowStatus
			MAX-ACCESS read-create
			STATUS current
			DESCRIPTION
				"Create/Delete a row entry"
			::= { avSurvIpVoiceCodecSetEntry 7 }

-- 1.3.6.1.4.1.6889.2.6.4.8
avSurvIpCodecSetConfig OBJECT IDENTIFIER ::= { avSurvMib 8 }

	-- 1.3.6.1.4.1.6889.2.6.4.8.1
	avSurvIpCodecSetFaxMode OBJECT-TYPE
		SYNTAX INTEGER
			{
				off		(1),
				relay		(2),
				passthru	(3),
				t38		(4)
			}
		MAX-ACCESS read-create
		STATUS current
		DESCRIPTION
			"Fax operational protocol mode"
		::= { avSurvIpCodecSetConfig 1 }

	-- 1.3.6.1.4.1.6889.2.6.4.8.2
	avSurvIpCodecSetFaxRedundancy OBJECT-TYPE
		SYNTAX INTEGER (0 .. 3)
		MAX-ACCESS read-create
		STATUS current
		DESCRIPTION
			" Redundant packets encoded during fax mode"
		::= { avSurvIpCodecSetConfig 2 }

	-- 1.3.6.1.4.1.6889.2.6.4.8.3
	avSurvIpCodecSetModemMode OBJECT-TYPE
		SYNTAX INTEGER
			{
				off		(1),
				relay		(2),
				passthru	(3)
			}
		MAX-ACCESS read-create
		STATUS current
		DESCRIPTION
			"Data modem protocol mode"
		::= { avSurvIpCodecSetConfig 3 }

	-- 1.3.6.1.4.1.6889.2.6.4.8.4
	avSurvIpCodecSetModemRedundancy OBJECT-TYPE
		SYNTAX INTEGER (0 .. 3)
		MAX-ACCESS read-create
		STATUS current
		DESCRIPTION
			" Redundant packets encoded for Modem mode"
		::= { avSurvIpCodecSetConfig 4 }

	-- 1.3.6.1.4.1.6889.2.6.4.8.5
	avSurvIpCodecSetTtyMode OBJECT-TYPE
		SYNTAX INTEGER
			{
				off			(1),
				us			(2),
				uk			(3),
				passthru		(4)
			}
		MAX-ACCESS read-create
		STATUS current
		DESCRIPTION
			"TTY protocol mode"
		::= { avSurvIpCodecSetConfig 5 }

	-- 1.3.6.1.4.1.6889.2.6.4.8.6
	avSurvIpCodecSetTtyRedundancy OBJECT-TYPE
		SYNTAX INTEGER (0 .. 3)
		MAX-ACCESS read-create
		STATUS current
		DESCRIPTION
			"Redundant packets encoded for TTY mode"
		::= { avSurvIpCodecSetConfig 6 }

	-- 1.3.6.1.4.1.6889.2.6.4.8.7
	avSurvIpCodecSetClearChanMode OBJECT-TYPE
		SYNTAX INTEGER
			{
				disabled	(1),
				enabled	(2)
			}
		MAX-ACCESS read-create
		STATUS current
		DESCRIPTION
			"Clear channel protocol mode. Preference for G711 wrapping"
		::= { avSurvIpCodecSetConfig 7 }

	-- 1.3.6.1.4.1.6889.2.6.4.8.8
	avSurvIpCodecSetClearChanRedundancy OBJECT-TYPE
		SYNTAX INTEGER (0 .. 1)
		MAX-ACCESS read-create
		STATUS current
		DESCRIPTION
			"Redundant packets encoded for clear channel mode"
		::= { avSurvIpCodecSetConfig 8 }

	-- 1.3.6.1.4.1.6889.2.6.4.8.9
		avSurvIpCodecSetEncryptPriority1 OBJECT-TYPE
		SYNTAX INTEGER
			{
				aes	(1),
				aea	(2),
				none	(3)
			}
		MAX-ACCESS read-create
		STATUS current
		DESCRIPTION
			"Media Encryption type - 1st priority"
		::= { avSurvIpCodecSetConfig 9 }

	-- 1.3.6.1.4.1.6889.2.6.4.8.10
		avSurvIpCodecSetEncryptPriority2 OBJECT-TYPE
		SYNTAX INTEGER
			{
				aes		(1),
				aea		(2),
				none		(3),
				unused	(4)
			}
		MAX-ACCESS read-create
		STATUS current
		DESCRIPTION
			"Media Encryption type - 2nd priority "
		::= { avSurvIpCodecSetConfig 10 }

	-- 1.3.6.1.4.1.6889.2.6.4.8.11
		avSurvIpCodecSetEncryptPriority3 OBJECT-TYPE
		SYNTAX INTEGER
			{
				aes		(1),
				aea		(2),
				none		(3),
				unused	(4)
			}
		MAX-ACCESS read-create
		STATUS current
		DESCRIPTION
			"Media Encryption type - 3rd priority"
		::= { avSurvIpCodecSetConfig 11 }

-- 1.3.6.1.4.1.6889.2.6.4.9
avSurvSlotConfigTable OBJECT-TYPE
	SYNTAX SEQUENCE OF AvSurvSlotConfigEntry
	MAX-ACCESS not-accessible
	STATUS current
	DESCRIPTION
		"Slot Configuration Table"
	::= { avSurvMib 9 }

	-- 1.3.6.1.4.1.6889.2.6.4.9.1
	avSurvSlotConfigEntry OBJECT-TYPE
		SYNTAX AvSurvSlotConfigEntry
		MAX-ACCESS not-accessible
		STATUS current
		DESCRIPTION
			"Each entry contains an index, number id, board type, and row status"
		INDEX {
			avSurvSlotConfigIndex
		}
		::= { avSurvSlotConfigTable 1 }

		AvSurvSlotConfigEntry ::= SEQUENCE {
			avSurvSlotConfigIndex			Integer32,
			avSurvSlotConfigNumberId		DisplayString,
			avSurvSlotConfigBoardType		INTEGER,
			avSurvSlotConfigRowStatus		RowStatus
		}

		-- 1.3.6.1.4.1.6889.2.6.4.9.1.1
		avSurvSlotConfigIndex OBJECT-TYPE
			SYNTAX Integer32	(1..10)
			MAX-ACCESS read-create
			STATUS current
			DESCRIPTION
				"Slot Config Table Index"
			::= { avSurvSlotConfigEntry 1 }

		-- 1.3.6.1.4.1.6889.2.6.4.9.1.2
		avSurvSlotConfigNumberId OBJECT-TYPE
			SYNTAX DisplayString (SIZE (2))
			MAX-ACCESS read-create
			STATUS current
			DESCRIPTION
				"This is the string identifier that CM uses to identify the slot
                          of the media gateway. The first character is defined as a v
                          followed by one decimal number, e.g. v1"
			::= { avSurvSlotConfigEntry 2 }

		-- 1.3.6.1.4.1.6889.2.6.4.9.1.3
		avSurvSlotConfigBoardType OBJECT-TYPE
			SYNTAX INTEGER
					{
						mm312		(32),
						mm710		(5),
						mm711		(4),
						mm712		(3),
						mm714		(7),
						mm716		(22),
						mm717		(14),
						mm720		(2),
						mm722		(8),
						anaImm1t2l	(9),
						anaImm4t2l	(16),
						briImm	(17),
						dcpImm	(18),
						ds1Imm	(19),
						tgm550	(23),
						tim508      (29),
                                    tim510	(25),
						tim514	(24),
						tim516	(30),
                                    tim518      (31),
						tim521	(26)
					}
			MAX-ACCESS read-create
			STATUS current
			DESCRIPTION
				"Type of media module in the associated slot
				  mm312 has 24 low-density DCP station ports
				  mm710 has one DS1 interface
				  mm711 has 8 port universal analog
				  mm712 has 8 DCP station ports
				  mm714 has 4 analog trunk ports and 4 analog station ports
				  mm716 has 24 high-density analog station ports
				  mm717 has 24 high-density DCP station ports
				  mm720 has 8 bri trunk ports (16 channels)
				  mm722 has 2 bri trunk ports (4 channels)
				  anaImm1t2l is G250 Internal media module 1 Analog Trunk  + 2 Analog Lines
				  anaImm4t2l is G250 Internal media module 4 Analog Trunks + 2 Analog Lines
				  briImm is G250 Internal media module 2 port BRI
				  dcpImm is G250 Internal media module 12 port DCP
				  ds1Imm is G250 Internal media module DS1
				  tgm550 is IG550 telephony gateway module with 2 Analog Trunks + 2 Analog Lines
                          tim508 is IG550 telephony interface module 8 analog station ports
                          tim510 is IG550 telephony interface module DS1
				  tim514 is IG550 telephony interface module 4 Analog Trunks + 2 Analog stations
				  tim516 is IG550 telephony interface module 16 analog station ports
                          tim518 is IG550 telephony interface module 8 analog stations and 8 analog trunks
				  tim521 is IG550 telephony interface module 4 port BRI"
			::= { avSurvSlotConfigEntry 3 }

		-- 1.3.6.1.4.1.6889.2.6.4.9.1.4
		avSurvSlotConfigRowStatus OBJECT-TYPE
			SYNTAX RowStatus
			MAX-ACCESS read-create
			STATUS current
			DESCRIPTION
				"Create/Delete a row entry in this table"
			::= { avSurvSlotConfigEntry 4 }


-- 1.3.6.1.4.1.6889.2.6.4.1.10
avSurvDs1Table OBJECT-TYPE
	SYNTAX SEQUENCE OF AvSurvDs1Entry
	MAX-ACCESS not-accessible
	STATUS current
	DESCRIPTION
		"DS1 trunk instantiation Table"
	::= { avSurvMib 10 }

	-- 1.3.6.1.4.1.6889.2.6.4.10.1
	avSurvDs1Entry OBJECT-TYPE
		SYNTAX AvSurvDs1Entry
		MAX-ACCESS not-accessible
		STATUS current
		DESCRIPTION
			"Each entry contains an index, name, bit-rate, signaling-mode, channel numbering, connect, interface, side, country-protocol, protocol-version, bearer-capability, interface-companding, long-timer, and slot-number-id. "
		INDEX {
			avSurvDs1Index
		}
		::= { avSurvDs1Table 1 }

		AvSurvDs1Entry ::= SEQUENCE {
			avSurvDs1Index				Integer32,
			avSurvDs1Name				DisplayString,
			avSurvDs1BitRate				INTEGER,
			avSurvDs1SignalingMode			INTEGER,
			avSurvDs1ChannelNumbering		INTEGER,
			avSurvDs1Connect				INTEGER,
			avSurvDs1Interface			INTEGER,
			avSurvDs1Side				INTEGER,
			avSurvDs1CountryProtocol		INTEGER,
			avSurvDs1ProtocolVersion		INTEGER,
			avSurvDs1BearerCapability		INTEGER,
			avSurvDs1InterfaceCompanding		INTEGER,
			avSurvDs1LongTimer			INTEGER,
			avSurvDs1RowStatus			RowStatus,
			avSurvDs1SlotNumberId			DisplayString
		}

		-- 1.3.6.1.4.1.6889.2.6.4.10.1.1
		avSurvDs1Index OBJECT-TYPE
			SYNTAX Integer32	(1..4)
			MAX-ACCESS read-create
			STATUS current
			DESCRIPTION
				"DS1 Table Index"
			::= { avSurvDs1Entry 1 }

		-- 1.3.6.1.4.1.6889.2.6.4.10.1.2
		avSurvDs1Name OBJECT-TYPE
			SYNTAX DisplayString (SIZE (0..15))
			MAX-ACCESS read-create
			STATUS current
			DESCRIPTION
				"Name of the service provider and/or site destination of DS1 facility"
			::= { avSurvDs1Entry 2 }

		-- 1.3.6.1.4.1.6889.2.6.4.10.1.3
		avSurvDs1BitRate OBJECT-TYPE
			SYNTAX INTEGER
					{
						rate1544		(1),
						rate2048		(2)
					}
			MAX-ACCESS read-create
			STATUS current
			DESCRIPTION
				"Maximum transmission rate for DS1 interface"
			::= { avSurvDs1Entry 3 }

		-- 1.3.6.1.4.1.6889.2.6.4.10.1.4
		avSurvDs1SignalingMode OBJECT-TYPE
			SYNTAX INTEGER
					{
						cas		(1),
						robbedBit	(2),
						isdnPri	(3),
						isdnExt	(4)
					}
			MAX-ACCESS read-create
			STATUS current
			DESCRIPTION
				"Selects the signaling method deployed on the given DS1 facility"
			::= { avSurvDs1Entry 4 }

		-- 1.3.6.1.4.1.6889.2.6.4.10.1.5
		avSurvDs1ChannelNumbering OBJECT-TYPE
			SYNTAX INTEGER
					{
						sequential	(1),
						timeSlot	(2)
					}
			MAX-ACCESS read-create
			STATUS current
			DESCRIPTION
				"Channel numbering scheme;
				E1 interface for ETSI and QSIG requires sequential encoding from
				1 to 30"
			::= { avSurvDs1Entry 5 }

		-- 1.3.6.1.4.1.6889.2.6.4.10.1.6
		avSurvDs1Connect OBJECT-TYPE
			SYNTAX INTEGER
					{
						host		(1),
						network	(2),
						pbx		(3),
						lineSide	(4)
					}
			MAX-ACCESS read-create
			STATUS current
			DESCRIPTION
				"Specifies what type of equipment is at the far end of the DS1 link"
			::= { avSurvDs1Entry 6 }

		-- 1.3.6.1.4.1.6889.2.6.4.10.1.7
		avSurvDs1Interface OBJECT-TYPE
			SYNTAX INTEGER
					{
						user		(0),
						network	(1),
						peerMaster	(3),
						peerSlave	(4)
					}
			MAX-ACCESS read-create
			STATUS current
			DESCRIPTION
				"Determines glare handling"
			::= { avSurvDs1Entry 7 }

		-- 1.3.6.1.4.1.6889.2.6.4.10.1.8
		avSurvDs1Side OBJECT-TYPE
			SYNTAX INTEGER
					{
						a		(0),
						b		(1)
					}
			MAX-ACCESS read-create
			STATUS current
			DESCRIPTION
				"QSIG glare handling when interface field is peerSlave"
			::= { avSurvDs1Entry 8 }

		-- 1.3.6.1.4.1.6889.2.6.4.10.1.9
		avSurvDs1CountryProtocol OBJECT-TYPE
			SYNTAX INTEGER
					{
						country1		(1),
						country2		(2),
						country3		(3),
						country4		(4),
						country5		(5),
						country6		(6),
						country7		(7),
						country8		(8),
						country9		(9),
						country10		(10),
						country11		(11),
						country12		(12),
						country13		(13),
						country14		(14),
						country15		(15),
						country16		(16),
						country17		(17),
						country18		(18),
						country19		(19),
						country20		(20),
						country21		(21),
						country22		(22),
						country23		(23),
						country24		(24),
						country25		(25),
						etsi			(62),
						qsig			(63)
					}
			MAX-ACCESS read-create
			STATUS current
			DESCRIPTION
				"Specifies the Layer 3 signaling protocol used by the
				  country-specific service provider.
				  This applies to ISDN trunk."
			::= { avSurvDs1Entry 9 }

		-- 1.3.6.1.4.1.6889.2.6.4.10.1.10
		avSurvDs1ProtocolVersion OBJECT-TYPE
			SYNTAX INTEGER
					{
						a		(0),
						b		(1),
						c		(2),
						d		(3)
					}
			MAX-ACCESS read-create
			STATUS current
			DESCRIPTION
				"Used in countries whose public networks allow multiple Layer-3
                          signaling protocols for ISDN PRI service."
			::= { avSurvDs1Entry 10 }

		-- 1.3.6.1.4.1.6889.2.6.4.10.1.11
		avSurvDs1BearerCapability OBJECT-TYPE
			SYNTAX INTEGER
					{
						threeKhz	(0),
						speech	(1)
					}
			MAX-ACCESS read-create
			STATUS current
			DESCRIPTION
				"Sets the information transfer capability in the Bearer Capability
                            IE of SETUP message for ISDN PRI service."
			::= { avSurvDs1Entry 11 }

		-- 1.3.6.1.4.1.6889.2.6.4.10.1.12
		avSurvDs1InterfaceCompanding OBJECT-TYPE
			SYNTAX INTEGER
					{
						alaw	(1),
						ulaw	(2)
					}
			MAX-ACCESS read-create
			STATUS current
			DESCRIPTION
				"Specifies the companding method used by the far-end switch"
			::= { avSurvDs1Entry 12 }

		-- 1.3.6.1.4.1.6889.2.6.4.10.1.13
		avSurvDs1LongTimer OBJECT-TYPE
			SYNTAX INTEGER
					{
						no	(1),
						yes	(2)
					}
			MAX-ACCESS read-create
			STATUS current
			DESCRIPTION
				"Specifies whether the duration of the T302 and T303 Q.931 timers
				  should be extended to a longer duration. Used for Russia country
                          code"
			::= { avSurvDs1Entry 13 }

		-- 1.3.6.1.4.1.6889.2.6.4.10.1.14
		avSurvDs1RowStatus OBJECT-TYPE
			SYNTAX RowStatus
			MAX-ACCESS read-create
			STATUS current
			DESCRIPTION
				"Create/Delete a row entry in this table"
			::= { avSurvDs1Entry 14 }

		-- 1.3.6.1.4.1.6889.2.6.4.10.1.15
		avSurvDs1SlotNumberId OBJECT-TYPE
			SYNTAX DisplayString (SIZE (2))
			MAX-ACCESS read-create
			STATUS current
			DESCRIPTION
				"This is the string identifier that CM uses to identify the slot
                          of the media gateway. The first character is defined as a v
                          followed by one decimal number, e.g. v1"
			::= { avSurvDs1Entry 15 }


-- 1.3.6.1.4.1.6889.2.6.4.1.11
avSurvSigGroupTable OBJECT-TYPE
	SYNTAX SEQUENCE OF AvSurvSigGroupEntry
	MAX-ACCESS not-accessible
	STATUS current
	DESCRIPTION
		"Signaling Group, associated with an ISDN trunk group, Table"
	::= { avSurvMib 11 }

	-- 1.3.6.1.4.1.6889.2.6.4.11.1
	avSurvSigGroupEntry OBJECT-TYPE
		SYNTAX AvSurvSigGroupEntry
		MAX-ACCESS not-accessible
		STATUS current
		DESCRIPTION
			"Each entry contains an index, channel selection, associated signaling, primary D channel, and row status"
		INDEX {
			avSurvSigGroupIndex
		}
		::= { avSurvSigGroupTable 1 }

		AvSurvSigGroupEntry ::= SEQUENCE {
			avSurvSigGroupIndex			Integer32,
			avSurvSigGroupChannelSelection	INTEGER,
			avSurvSigGroupAssociatedSignaling	INTEGER,
			avSurvSigGroupPrimaryDChannel		DisplayString,
			avSurvSigGroupRowStatus			RowStatus
		}

		-- 1.3.6.1.4.1.6889.2.6.4.11.1.1
		avSurvSigGroupIndex OBJECT-TYPE
			SYNTAX Integer32	(1..650)
			MAX-ACCESS read-create
			STATUS current
			DESCRIPTION
				"SigGroup Table Index"
			::= { avSurvSigGroupEntry 1 }

		-- 1.3.6.1.4.1.6889.2.6.4.11.1.2
		avSurvSigGroupChannelSelection OBJECT-TYPE
			SYNTAX INTEGER (1..2000)
			MAX-ACCESS read-create
			STATUS current
			DESCRIPTION
				"If there is more than one trunk group assigned to this signaling
                          group, the channel selection number is the trunk group that can
                          accept incoming calls"
			::= { avSurvSigGroupEntry 2 }

		-- 1.3.6.1.4.1.6889.2.6.4.11.1.3
		avSurvSigGroupAssociatedSignaling OBJECT-TYPE
			SYNTAX INTEGER
					{
						yes			(1),
						no			(2)
					}
			MAX-ACCESS read-create
			STATUS current
			DESCRIPTION
				"Specifies whether the D-channel is physically associated in the
                         DS1 facility, yes = D-channel present"
			::= { avSurvSigGroupEntry 3 }

		-- 1.3.6.1.4.1.6889.2.6.4.11.1.4
		avSurvSigGroupPrimaryDChannel OBJECT-TYPE
			SYNTAX DisplayString (SIZE (7))
			MAX-ACCESS read-create
			STATUS current
			DESCRIPTION
				"The identity for the D-channel 3 digit gw number + 2 character
                         slot number + 2 digit port circuit number"
			::= { avSurvSigGroupEntry 4 }

		-- 1.3.6.1.4.1.6889.2.6.4.11.1.5
		avSurvSigGroupRowStatus OBJECT-TYPE
			SYNTAX RowStatus
			MAX-ACCESS read-create
			STATUS current
			DESCRIPTION
				"Create/Delete a row entry in this table"
			::= { avSurvSigGroupEntry 5 }

-- 1.3.6.1.4.1.6889.2.6.4.1.12
avSurvBriTable OBJECT-TYPE
	SYNTAX SEQUENCE OF AvSurvBriEntry
	MAX-ACCESS not-accessible
	STATUS current
	DESCRIPTION
		"BRI trunk instantiation Table"
	::= { avSurvMib 12 }

	-- 1.3.6.1.4.1.6889.2.6.4.12.1
	avSurvBriEntry OBJECT-TYPE
		SYNTAX AvSurvBriEntry
		MAX-ACCESS not-accessible
		STATUS current
		DESCRIPTION
			"Each entry contains an index, name, interface, side, country-protocol,
                   bearer-capability, interface-companding, tei-assignment, directory-numberA,
                   directory-numberB, spidA, spidB, endpoint-initialization,
                   layer1-stable, and slot-number-id.
			 This table instantiation completely specifies a BRI circuit, consisting
	             of channel B1 and channel B2"
		INDEX {
			avSurvBriIndex
		}
		::= { avSurvBriTable 1 }

		AvSurvBriEntry ::= SEQUENCE {
			avSurvBriIndex				Integer32,
			avSurvBriName				DisplayString,
			avSurvBriInterface			INTEGER,
			avSurvBriSide				INTEGER,
			avSurvBriCountryProtocol		INTEGER,
			avSurvBriBearerCapability		INTEGER,
			avSurvBriInterfaceCompanding		INTEGER,
			avSurvBriTeiAssignment			INTEGER,
			avSurvBriDirectoryNumberA		DisplayString,
			avSurvBriDirectoryNumberB		DisplayString,
			avSurvBriSpidA				DisplayString,
			avSurvBriSpidB				DisplayString,
			avSurvBriEndpointInit			INTEGER,
			avSurvBriLayer1Stable			INTEGER,
			avSurvBriRowStatus			RowStatus,
			avSurvBriSlotPortNumberId			DisplayString
		}

		-- 1.3.6.1.4.1.6889.2.6.4.12.1.1
		avSurvBriIndex OBJECT-TYPE
			SYNTAX Integer32	(1..64)
			MAX-ACCESS read-create
			STATUS current
			DESCRIPTION
				"BRI Table Index
				 Note: G250-BRI supports 2 ports (4-channels)
					 G350/IG550 is allocated a max of 24 ports (48-channels)
					 G430/G450 is allocated a max of 64 ports (128 channels).
					 "
			::= { avSurvBriEntry 1 }

		-- 1.3.6.1.4.1.6889.2.6.4.12.1.2
		avSurvBriName OBJECT-TYPE
			SYNTAX DisplayString (SIZE (0..15))
			MAX-ACCESS read-create
			STATUS current
			DESCRIPTION
				"Name of the service provider and/or site destination of BRI facility"
			::= { avSurvBriEntry 2 }

		-- 1.3.6.1.4.1.6889.2.6.4.12.1.3
		avSurvBriInterface OBJECT-TYPE
			SYNTAX INTEGER
					{
						user		(0),
						network	(1),
						peerMaster	(3),
						peerSlave	(4)
					}
			MAX-ACCESS read-create
			STATUS current
			DESCRIPTION
				"Determines glare handling. Non-QSIG calls: a-network, b-user;
                             QSIG calls: a-peerMaster, b-peerSlave"
			::= { avSurvBriEntry 3 }

		-- 1.3.6.1.4.1.6889.2.6.4.12.1.4
		avSurvBriSide OBJECT-TYPE
			SYNTAX INTEGER
					{
						a		(0),
						b		(1)
					}
			MAX-ACCESS read-create
			STATUS current
			DESCRIPTION
				"QSIG glare handling when interface field is peerSlave"
			::= { avSurvBriEntry 4 }

		-- 1.3.6.1.4.1.6889.2.6.4.12.1.5
		avSurvBriCountryProtocol OBJECT-TYPE
			SYNTAX INTEGER
					{
						country1		(1),
						country2		(2),
						country3		(3),
						country4		(4),
						country5		(5),
						country6		(6),
						country7		(7),
						country8		(8),
						country9		(9),
						country10		(10),
						country11		(11),
						country12		(12),
						country13		(13),
						country14		(14),
						country15		(15),
						country16		(16),
						country17		(17),
						country18		(18),
						country19		(19),
						country20		(20),
						country21		(21),
						country22		(22),
						country23		(23),
						country24		(24),
						country25		(25),
						etsi			(62),
						qsig			(63)
					}
			MAX-ACCESS read-create
			STATUS current
			DESCRIPTION
				"Specifies the Layer 3 signaling protocol used by the
                          country-specific service provider"
			::= { avSurvBriEntry 5 }


		-- 1.3.6.1.4.1.6889.2.6.4.12.1.6
		avSurvBriBearerCapability OBJECT-TYPE
			SYNTAX INTEGER
					{
						threeKhz	(0),
						speech	(1)
					}
			MAX-ACCESS read-create
			STATUS current
			DESCRIPTION
				"Sets the information transfer capability in the Bearer Capability
                          IE of SETUP message"
			::= { avSurvBriEntry 6 }

		-- 1.3.6.1.4.1.6889.2.6.4.12.1.7
		avSurvBriInterfaceCompanding OBJECT-TYPE
			SYNTAX INTEGER
					{
						alaw	(1),
						ulaw	(2)
					}
			MAX-ACCESS read-create
			STATUS current
			DESCRIPTION
				"Specifies the companding method used )for all circuits on this
                          media module) by the far-end switch"
			::= { avSurvBriEntry 7 }

		-- 1.3.6.1.4.1.6889.2.6.4.12.1.8
		avSurvBriTeiAssignment OBJECT-TYPE
			SYNTAX INTEGER
					{
						auto		(1),
						zero		(2)
					}
			MAX-ACCESS read-create
			STATUS current
			DESCRIPTION
				"LAPD address assignment for TEI field, auto is assigned by
                            network provider"
			::= { avSurvBriEntry 8 }

		-- 1.3.6.1.4.1.6889.2.6.4.12.1.9
		avSurvBriDirectoryNumberA OBJECT-TYPE
			SYNTAX DisplayString (SIZE (1..10))
			MAX-ACCESS read-create
			STATUS current
			DESCRIPTION
				"Channel B1's directory number"
			::= { avSurvBriEntry 9 }

		-- 1.3.6.1.4.1.6889.2.6.4.12.1.10
		avSurvBriDirectoryNumberB OBJECT-TYPE
			SYNTAX DisplayString (SIZE (1..10))
			MAX-ACCESS read-create
			STATUS current
			DESCRIPTION
				"Channel B2's directory number"
			::= { avSurvBriEntry 10 }

		-- 1.3.6.1.4.1.6889.2.6.4.12.1.11
		avSurvBriSpidA OBJECT-TYPE
			SYNTAX DisplayString (SIZE (0..14))
			MAX-ACCESS read-create
			STATUS current
			DESCRIPTION
				"Service Provider Identifier required for Country Code 1 (USA)
          				to be associated with channel B1"
			::= { avSurvBriEntry 11 }

			-- 1.3.6.1.4.1.6889.2.6.4.12.1.12
		avSurvBriSpidB OBJECT-TYPE
			SYNTAX DisplayString (SIZE (0..14))
			MAX-ACCESS read-create
			STATUS current
			DESCRIPTION
				"Service Provider Identifier required for Country Code 1 (USA)
					to be associated with channel B2"
			::= { avSurvBriEntry 12 }

		-- 1.3.6.1.4.1.6889.2.6.4.12.1.13
		avSurvBriEndpointInit OBJECT-TYPE
			SYNTAX INTEGER
					{
						yes		(1),
						no		(2)
					}
			MAX-ACCESS read-create
			STATUS current
			DESCRIPTION
				"Determines whether the far end supports endpoint initialization"
			::= { avSurvBriEntry 13 }

		-- 1.3.6.1.4.1.6889.2.6.4.12.1.14
		avSurvBriLayer1Stable OBJECT-TYPE
			SYNTAX INTEGER
					{
						yes		(1),
						no		(2)
					}
			MAX-ACCESS read-create
			STATUS current
			DESCRIPTION
				"Determines whether to expect the network to drop BRI layer 1
                           when no calls are active.
                           yes = keep layer 1 stable"
			::= { avSurvBriEntry 14 }

		-- 1.3.6.1.4.1.6889.2.6.4.12.1.15
		avSurvBriRowStatus OBJECT-TYPE
			SYNTAX RowStatus
			MAX-ACCESS read-create
			STATUS current
			DESCRIPTION
				"Create/Delete a row entry in this table"
			::= { avSurvBriEntry 15 }

		-- 1.3.6.1.4.1.6889.2.6.4.12.1.16
		avSurvBriSlotPortNumberId OBJECT-TYPE
			SYNTAX DisplayString (SIZE (4..4))
			MAX-ACCESS read-create
			STATUS current
			DESCRIPTION
				"This is the string identifier formed by the combination of the slot identifier that CM uses
                     to identify the slot of the media gateway(first character is a v followed by one numeric
                     character). The port consists of two numeric characters that identify the first B-channel
                     of the physical BRI port circuit(for example the 1st port is always 01)."
			::= { avSurvBriEntry 16 }


-- 1.3.6.1.4.1.6889.2.6.4.1.13
avSurvIncomingRoutingTable OBJECT-TYPE
	SYNTAX SEQUENCE OF AvSurvIncomingRoutingEntry
	MAX-ACCESS not-accessible
	STATUS current
	DESCRIPTION
		"Incoming Routing Table"
	::= { avSurvMib 13 }

	-- 1.3.6.1.4.1.6889.2.6.4.13.1
	avSurvIncomingRoutingEntry OBJECT-TYPE
		SYNTAX AvSurvIncomingRoutingEntry
		MAX-ACCESS not-accessible
		STATUS current
		DESCRIPTION
			"Each entry contains a dual index(trunk-group-reference-number and
                   table index), match-pattern, delete-digits, insert-digits specification
                   and routing-mode.
			 This table instantiation completely specifies an the digit handling for
                   an incoming dial-string pattern.
                   Note 1: If the trunk-group employs Overlap Receiving, there will only be one
                   entry (this may only have a delete or an insert operand).
                   Note 2: If the trunk-group employs Enbloc Receiving, there may be a maximum
                   of 50 entries. Each entry will have a Match-pattern, Length, Delete, and
			 Insert element."
		INDEX {
			avSurvIncomingRoutingGroupRefNumber,avSurvIncomingRoutingIndex
		}
		::= { avSurvIncomingRoutingTable 1 }

		AvSurvIncomingRoutingEntry ::= SEQUENCE {
			avSurvIncomingRoutingGroupRefNumber	INTEGER,
			avSurvIncomingRoutingIndex		Integer32,
			avSurvIncomingRoutingMatchPattern	DisplayString,
			avSurvIncomingRoutingLength		INTEGER,
			avSurvIncomingRoutingDeleteDigits	INTEGER,
			avSurvIncomingRoutingInsertDigits	DisplayString,
			avSurvIncomingRoutingMode	INTEGER,
			avSurvIncomingRoutingRowStatus	RowStatus
		}

		-- 1.3.6.1.4.1.6889.2.6.4.13.1.1
		avSurvIncomingRoutingGroupRefNumber OBJECT-TYPE
			SYNTAX INTEGER (1..2000)
			MAX-ACCESS read-create
			STATUS current
			DESCRIPTION
				"Incoming trunk-group reference number"
			::= { avSurvIncomingRoutingEntry 1 }

		-- 1.3.6.1.4.1.6889.2.6.4.13.1.2
		avSurvIncomingRoutingIndex OBJECT-TYPE
			SYNTAX Integer32	(1..50)
			MAX-ACCESS read-create
			STATUS current
			DESCRIPTION
				"Incoming Routing Table Index"
			::= { avSurvIncomingRoutingEntry 2 }

		-- 1.3.6.1.4.1.6889.2.6.4.13.1.3
		avSurvIncomingRoutingMatchPattern OBJECT-TYPE
			SYNTAX DisplayString (SIZE (0..16))
			MAX-ACCESS read-create
			STATUS current
			DESCRIPTION
				"Dial-string entry that is used to match a pattern on inbound
				   trunk calls. Note that '0' is used to designate the blank
                           or empty string value as a wild card match."
			::= { avSurvIncomingRoutingEntry 3 }

		-- 1.3.6.1.4.1.6889.2.6.4.13.1.4
		avSurvIncomingRoutingLength OBJECT-TYPE
			SYNTAX INTEGER
				{
					len0	(0),
                              len1	(1),
                              len2	(2),
                              len3	(3),
                              len4	(4),
                              len5	(5),
                              len6	(6),
                              len7	(7),
                              len8	(8),
                              len9	(9),
                              len10	(10),
                              len11	(11),
                              len12	(12),
                              len13	(13),
                              len14	(14),
                              len15	(15),
                              len16	(16),
                              len17	(17),
                              len18	(18),
                              len19	(19),
                              len20	(20),
                              len21	(21),
                              blank	(99)
				}
			MAX-ACCESS read-create
			STATUS current
			DESCRIPTION
				"Maximum length of the user-dialed number that the SLS call-engine
                         collects before beginning the pattern matching. Note that CM uses
                         the blank as a wild card, subject to rule of the MatchPattern
                         field being set to a wild card value as well."
			::= { avSurvIncomingRoutingEntry 4 }

		-- 1.3.6.1.4.1.6889.2.6.4.13.1.5
		avSurvIncomingRoutingDeleteDigits OBJECT-TYPE
			SYNTAX INTEGER (0..21)
			MAX-ACCESS read-create
			STATUS current
			DESCRIPTION
				"Specifies the number of dialed digits to be deleted from
                         the beginning of the incoming trunk's received digit string"
			::= { avSurvIncomingRoutingEntry 5 }

		-- 1.3.6.1.4.1.6889.2.6.4.13.1.6
		avSurvIncomingRoutingInsertDigits OBJECT-TYPE
			SYNTAX DisplayString (SIZE (0..16))
			MAX-ACCESS read-create
			STATUS current
			DESCRIPTION
				"Specifies the digit string to be inserted (after the deletion
                          process has been completed) to the incoming trunk digit string"
			::= { avSurvIncomingRoutingEntry 6 }

		-- 1.3.6.1.4.1.6889.2.6.4.13.1.7
		avSurvIncomingRoutingMode OBJECT-TYPE
			SYNTAX INTEGER
				{
					enbloc	(0),
					overlap	(1)
				}
			MAX-ACCESS read-create
			STATUS current
			DESCRIPTION
				"Defines overlap receiving and transmitting rules.
                         This applies only to ISDN BRI/PRI trunks."
			::= { avSurvIncomingRoutingEntry 7 }

		-- 1.3.6.1.4.1.6889.2.6.4.13.1.8
		avSurvIncomingRoutingRowStatus OBJECT-TYPE
			SYNTAX RowStatus
			MAX-ACCESS read-create
			STATUS current
			DESCRIPTION
				"Create/Delete a row entry in this table"
			::= { avSurvIncomingRoutingEntry 8 }


-- 1.3.6.1.4.1.6889.2.6.4.1.14
avSurvNfasTable OBJECT-TYPE
	SYNTAX SEQUENCE OF AvSurvNfasEntry
	MAX-ACCESS not-accessible
	STATUS current
	DESCRIPTION
		"Signaling Group Nfas , associated with an ISDN trunk group, Table"
	::= { avSurvMib 14 }

	-- 1.3.6.1.4.1.6889.2.6.4.14.1
	avSurvNfasEntry OBJECT-TYPE
		SYNTAX AvSurvNfasEntry
		MAX-ACCESS not-accessible
		STATUS current
		DESCRIPTION
			"Each entry contains a dual index(sig-group-reference-number and table index), interface string, interface id,  and row status"
		INDEX {
			avSurvNfasSigGroupRefNumber, avSurvNfasIndex
		}
		::= { avSurvNfasTable 1 }

		AvSurvNfasEntry ::= SEQUENCE {
			avSurvNfasSigGroupRefNumber		INTEGER,
                  avSurvNfasIndex				Integer32,
			avSurvNfasInterface			DisplayString,
			avSurvNfasInterfaceId			INTEGER,
			avSurvNfasRowStatus			RowStatus
		}

		-- 1.3.6.1.4.1.6889.2.6.4.14.1.1
		avSurvNfasSigGroupRefNumber OBJECT-TYPE
			SYNTAX INTEGER (1..650)
			MAX-ACCESS read-create
			STATUS current
			DESCRIPTION
				"Entry pointing to the associated signaling group number in the signaling group table"
			::= { avSurvNfasEntry 1 }

		-- 1.3.6.1.4.1.6889.2.6.4.14.1.2
		avSurvNfasIndex OBJECT-TYPE
			SYNTAX Integer32	(1..10)
			MAX-ACCESS read-create
			STATUS current
			DESCRIPTION
				"Nfas Table Index"
			::= { avSurvNfasEntry 2 }

		-- 1.3.6.1.4.1.6889.2.6.4.14.1.3
		avSurvNfasInterface OBJECT-TYPE
			SYNTAX DisplayString (SIZE (5))
			MAX-ACCESS read-create
			STATUS current
			DESCRIPTION
				"The identity for the NFAS DS1 facility group: 3 digit gateway
                          number + 2 character slot number"
			::= { avSurvNfasEntry 3 }

		-- 1.3.6.1.4.1.6889.2.6.4.14.1.4
		avSurvNfasInterfaceId OBJECT-TYPE
			SYNTAX INTEGER (0..31)
			MAX-ACCESS read-create
			STATUS current
			DESCRIPTION
				"For an NFAS circuit, this specifies the identification number of
                          the DS1 circuit that is associated with this NFAS group. Note
                          that this ID number must be coordinated with the PSTN provider
                          so that the signaling protocol will operate correctly with respect
                          to physical facility circuit selection."
			::= { avSurvNfasEntry 4 }


		-- 1.3.6.1.4.1.6889.2.6.4.14.1.5
		avSurvNfasRowStatus OBJECT-TYPE
			SYNTAX RowStatus
			MAX-ACCESS read-create
			STATUS current
			DESCRIPTION
				"Create/Delete a row entry in this table"
			::= { avSurvNfasEntry 5 }

END
