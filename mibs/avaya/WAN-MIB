--
-- WAN-MIB.my
-- MIB generated by MG-SOFT Visual MIB Builder Version 3.0 Build 253
-- Thursday, June 09, 2005 at 17:41:48
--

--  WAN-MIB.mib
--
-- ========================================================
-- SourceSafe Version Information:
-- $Revision: 29 $
-- Check in $Date: 21/06/05 11:24a $
-- $Author: Dgluskin $
-- $Archive: /MIBs/Version 1.0/Source/Avaya/WAN-MIB.MY $
-- ========================================================
-- Copyright 2002 AVAYA,  inc.
-- All Rights Reserved.
--
-- Reproduction of this document is authorized on condition
-- that the foregoing copyright notice is included.
--
-- This AVAYA SNMP Management Information Base Specification
-- (Specification) embodies AVAYA confidential and
-- Proprietary intellectual property.  AVAYA retains all
-- Title and ownership in the Specification, including any revisions
-- It is AVAYA's intent to encourage the widespread use of this
-- Specification in connection with the management of AVAYA products.
-- AVAYA grants vendors, end-users, and other interested parties
-- a non-exclusive license to use this Specification in connection
-- with the management of AVAYA products.
--
-- This Specification is supplied "as is," and AVAYA makes
-- no warranty, either express or implied, as to the use,
-- operation, condition, or performance of the Specification.
-- ========================================================

	WAN-MIB DEFINITIONS ::= BEGIN

		IMPORTS
			lsg
				FROM AVAYAGEN-MIB
			dsx0BundleIndex, dsx0BundleIfIndex, dsx0BundleCircuitIdentifier, dsx0BundleRowStatus
				FROM DS0BUNDLE-MIB
			DLCI
				FROM FRAME-RELAY-DTE-MIB
			ifIndex, ifAdminStatus, ifOperStatus, ifName, ifAlias,
			InterfaceIndex
				FROM IF-MIB
			PhysAddress
				FROM RFC1213-MIB
			OBJECT-GROUP, MODULE-COMPLIANCE
				FROM SNMPv2-CONF
			IpAddress, Integer32, Unsigned32, Gauge32, OBJECT-TYPE,
			MODULE-IDENTITY
				FROM SNMPv2-SMI
			DisplayString, RowStatus, TEXTUAL-CONVENTION
				FROM SNMPv2-TC;

-- REVISION "0506210920Z" 	@@ June 21, 2005 at 09:20 GMT
--  "Version 2.1.12 - Dan Gluskin
--	  Add    ifTableXtndType for modem type setting
--  November 03, 2004 at 08:00
-- REVISION "0504141644Z" 	@@ April 14, 2005 at 16:44 GMT
--   "Version 2.1.11 - Shlomi Biton
-- Adding explanation to frameRelayNonIetf enumeration in the ifTableXtndEncapsulation."
-- REVISION "0503201531Z" 	@@ Mar 21, 2005 at 15:31 GMT
--   "Version 2.1.10 - Shlomi Biton
--    Adding loopback to the ifTableXtndOperStatus description.
-- Adding frameRelayNonIetf enumeration to the ifTableXtndEncapsulation."
-- REVISION "0412221908Z" 	@@ December 22, 2004 at 19:08 GMT
--   "Version 2.1.9 - Shlomi Biton
--      Updating ifTableXtndKeepaliveTrackId default value to 'ffffffff'h"
-- REVISION "0412121802Z" 	@@ December 12, 2004 at 18:02 GMT
--   "Version 2.1.8 - Shlomi Biton
--      Adding notSupported value to ifTableXtndKeepaliveTrackId for interface that track can not
-- activated on."
-- REVISION "0410121326Z" 	@@ November 03, 2004 at 08:00 GMT
--   "Version 2.1.7 - Shlomi Biton
--      Add ifTableXtndKeepaliveTrackId for activating track on specific interfaces."
-- REVISION "0410121326Z" 	@@ October 12th, 2004 at 13:27 GMT
--   "Version 2.1.6 - Shlomi Biton
--      fix the ifTableXtndPppIpcpDnsOptionRequest definition."
-- REVISION "0410101200Z" 	@@ October 10th, 2004 at 12:00 GMT
--   "Version 2.1.5 - Dan Gluskin
--      add 'wanDialerPersistentInitial' for dialer persistent initial delay"
-- REVISION "0410040830Z" 	@@ October 04, 2004 at 08:30 GMT
--  "Version 2.1.4 - Shlomi Biton
-- 1. Adding to ifTableXtndTable the ifTableXtndPppIpcpDnsOptionRequest -
--        PPP-IPCP DNS option request "
-- REVISION "0409270715Z" 	@@ September 27st, 2004 at 07:15 GMT
--  "Version 2.1.3 - Dan Gluskin
-- 1. modem enums added to ifTableXtndOperStatus
--     2. ifTableXtndConfString added "
-- REVISION "0409011245Z" 	@@ September 1st, 2004 at 12:45 GMT
--  "Version 2.1.2 - Dan Gluskin
--      Remove the wanDialerPreemptive item "
-- REVISION "0408261433Z" 	@@ August 26, 2004 at 14:33 GMT
--  "Version 2.1.1 - Dan Gluskin
--       Move 'wanDialer under ifs'
-- REVISION "0407050540Z" @@ August 22, 2004 at 15:10 GMT
--   "Version 2.1.0 - Dan Gluskin
--     Add wanDialer group"
-- REVISION "0407050540Z" 	@@ July 5, 2004 at 05:40 GMT
--   "Version 2.0.18 - Dan Gluskin
--    add an ifTableXtndMinPmtu item"
-- REVISION "0406210910Z" 	@@ June 21, 2004 at 09:10 GMT
--   "Version 2.0.17 - Dan Gluskin
--   ifTableXtndIpSecDfBit should be read only"
-- REVISION "0405231700Z"	@@ May 23, 2004 at 17:00 GMT
--   "Ver 2.0.16 - Dan Gluskin
--     add ifTableXtndIpSecDfBit"
-- REVISION "0404151700Z"	@@ Mer 15, 2004 at 17:00 GMT
-- "Ver 2.0.15 - Dan Gluskin'
--  add 'pppoe' and 'arpa' enums to  IfTableXtndEncapsulation"
--
-- REVISION "0402091001Z"	@@ Feb 09, 2004 at 10:01 GMT
--     DESCRIPTION
--     "Ver 2.0.14 - Shlomi Biton
--     Changing keepalive element names to xtndKeepAlive.
-- Changing keepAliveDown status to xtndKeepAliveDown"
-- REVISION "0311171004Z"	@@ November 17, 2003 at 10:04 GMT
--     DESCRIPTION
--     "Ver 2.0.13 - Shlomi Biton
--     Add Health Check Table
-- Add new value for ifTableXtndOperStatus of keepAlive Down
-- Add new Item to ifTableXtndEntry of ifTableXtndCommonApplifStatus for PBR
-- Supporting next hop Interface
-- REVISION "0311091431Z"	@@ November 9, 2003 at 14:31 GMT
--     DESCRIPTION
--     "Ver 2.0.12 - Dan Gluskin
--     change ifTableXtndVoIPQueue syntax to integer and add fairQ enumeration"
-- REVISION "1210031441Z"	@@ October 22, 2003 at 14:41 GMT
--     DESCRIPTION
--     "Ver 2.0.11 - Dan Gluskin
-- 	   Add dynamic CAC entries:
-- 	        ifTableXtndCacBBL
-- ifTableXtndCacPriority
-- ifTableXtndCacifStatus"
-- REVISION "1007031541Z"	@@ July 10, 2003 at 15:41 GMT
--     DESCRIPTION
--     "Ver 2.0.10 - Dan Gluskin
-- 	   Add ds1CurrentDeviceMode"
-- REVISION "0211021041Z"	@@ November 02, 2002 at 10:41 GMT
--     DESCRIPTION
--     "Ver 2.0.9 - Dan Gluskin
--     ========================
--     Add Interface Traffic-Shaper items to ifTableXtnd"
-- REVISION "0208011941Z"		@@ August 01, 2002 at 19:41 GMT
-- DESCRIPTION
--     "Ver 2.0.8 - ItaiZ
--     =================
--     backup Delays  ranges
--     modified to be in -1..3600 range.
--     "
-- REVISION "0207231140Z"		@@ July 23, 2002 at 11:40 GMT
-- DESCRIPTION
--     "Ver 2.0.7 - Itai Z.
--     ===================
--     1. Removed ifTableXtndBackupTrigger.
--        Note that the next item OID was chaned as well.
--     2. Range restriction removed from backupEnable, disable delays.
--        'Never' can be modeled as MAXINT.
--     3. Added new serial Line items:
--        ifTableXtndCarrierDelay
--        ifTableXtndDtrRestartDelay
--        ifTableXtndDtrPulseTime
--     4. Added average load and bit rate
--        counters & config parameter:
--        ifTableXtndLoadInterval
--        ifTableXtndInputRate
--        ifTableXtndOutputRate
--        ifTableXtndInputLoad
--        ifTableXtndOutputLoad
--        ifTableXtndReliability
--
--
--
--
--     "
-- REVISION "0206271532Z"		@@ June 27, 2002 at 15:32 GMT
-- DESCRIPTION
--     "Version 2.0.6 - Itai Z.
--     =======================
--     1. Fix ifTableXtndOperStatus - added back the adminDown value."
-- REVISION "0206261405Z"		@@ June 26, 2002 at 14:05 GMT
-- DESCRIPTION
--     "Version 2.0.5 - ItaiZ
--     =====================
--     1. frStaticCircuitDLCIrole - description & enaums have changed.
--     2. frStaticCircuitPriorityClass removed."
-- REVISION "0206251441Z"		@@ June 25, 2002 at 14:41 GMT
-- DESCRIPTION
--     "Version 2.0.4 - ItaiZ
--     =====================
--     1. Added Avaya Boiler plate
--     2. frStaticCircuitTable modified
--        to include frStaticDLCIrole
--        as index. This provides
--        the ability to map DLCIs to
--        priority-sets. The index
--        enforce DLCI creation/deletion
--        restrictions.
--     3. Added ifTableXtndBackupCapabilities,
--        ifTableXtndBackupIf,
--        ifTableXtndBackupEnableDelay,
--        ifTableXtndBackupDisableDelay,
--        ifTableXtndBackupTrigger and
--        ifTableXtndPrimaryIf to support backup
--        interfaces.
--     4. ifTablXtndOperStatus has another value -
--        dormantDown to reflect backup Interface in dormant
--        state.
--
--     "
-- REVISION "0206121108Z"		@@ June 12, 2002 at 11:08 GMT
-- DESCRIPTION
--     "Version 2.0.3 - ItaiZ
--     =====================
--     1. frStatiCircuitLFI removed.
--        LFI will be controlled via
--        a frame relay map-class MIB,
--        when defined.
--     2. Description of ifTableXtndBandwidth
--        explicitly says that the units are Kbps
--     "
-- REVISION "0206061550Z"		@@ June 06, 2002 at 15:50 GMT
-- DESCRIPTION
--     "Version 2.0.2 - Itai Z.
--
--     1. frStaticCircuitPriorityClasss
--        is now read only, and has
--        two more values to represent possible
--        values assigned through CLI
--     2. ifTableXtendOperStatus explained in
--        pseudo code"
-- REVISION "0205291903Z"		@@ May 29, 2002 at 19:03 GMT
-- DESCRIPTION
--     "Version 2.0.1 - Itai Z.
--     1. Changed name & definition of frCircuitXtendTable
--        to frStaticCircuitTable.This table is now used to create and delete
--        Static DLCIs.
--     2. ifTableXtndOperStatus defined
--     "
-- REVISION "0205281910Z"		@@ May 28, 2002 at 19:10 GMT
-- DESCRIPTION
--     "Version 2.0.0 - Itai Zilbershtein
--     Added support for Frame Relay and Universal Serial Ports
--     For X330WAN V1.5"
-- REVISION "0203051047Z"		@@ March 05, 2002 at 10:47 GMT
-- DESCRIPTION
--     "Version 1.0 - Michael W.
--     Keepalive added."
-- REVISION "0203041042Z"		@@ March 04, 2002 at 10:42 GMT
-- DESCRIPTION
--     "Version 0.4 - Michael W.
--     Added description, cablelength and gain
--     extensions to ifTable."
-- REVISION "0202241242Z"		@@ February 24, 2002 at 12:42 GMT
-- DESCRIPTION
--     "Version 0.3 - Michael W.
--     Added the ifTableXtndTable
--     Added speed factor per ds0bundle"
-- REVISION "0112191015Z"		@@ December 19, 2001 at 10:15 GMT
-- DESCRIPTION
--     "Version 0.2 - Michael W.
--     Added the ds0BundleMembers table
--     to override the ifStack.
--     ifStack usage will be deferred to
--     a later version, at which time the
--     ds0BundleMembers mib will become
--     obsolete.
--     "
-- REVISION "0112061045Z"		@@ December 06, 2001 at 10:45 GMT
-- DESCRIPTION
--     "Version 0.1 - Michael Weksler:
--     First SMIv2 version
--
--     "
		avayaEISWan MODULE-IDENTITY
			LAST-UPDATED "0506210920Z" 	-- June 21, 2005 at 09:20 GMT
			ORGANIZATION
				"Avaya Inc."
			CONTACT-INFO
				"Dan Gluskin, Avaya Inc.
				+972-3-6457561
				mailto:dgluskin@avaya.com

				Itai Zilbershtein, Avaya Inc.
				+972 3 6457667
				mailto:izilbers@avaya.com"
			DESCRIPTION
				"The mib for controlling WAN-related
				features of WAN access devices."
			::= { lsg 6 }



--
-- Textual conventions
--

--  Textual conventions
--
		OnOff ::= TEXTUAL-CONVENTION
			STATUS current
			DESCRIPTION
				"This textual convention describes a feature
				that can be either turned on, off or is not
				relevant for an object."
			SYNTAX INTEGER
				{
				on(1),
				off(2),
				notRelevant(255)
				}


--
-- Node definitions
--

--  Node definitions
--
-- 1.3.6.1.4.1.6889.2.1.6.1
		-- 1.3.6.1.4.1.6889.2.1.6.1
		deviceSpecific OBJECT IDENTIFIER ::= { avayaEISWan 1 }

--  1.3.6.1.4.1.6889.2.1.6.1.1
		-- 1.3.6.1.4.1.6889.2.1.6.1.1
		x330wanSpecific OBJECT IDENTIFIER ::= { deviceSpecific 1 }

--  1.3.6.1.4.1.6889.2.1.6.1.1.1
		-- 1.3.6.1.4.1.6889.2.1.6.1.1.1
		intWanPortTable OBJECT-TYPE
			SYNTAX SEQUENCE OF IntWanPortEntry
			MAX-ACCESS not-accessible
			STATUS current
			DESCRIPTION
				"Internal Wan Port configuration table.
				Each entry in the table specifies the configuration of
				an internal port, connecting the WAN blade to the host
				switch."
			::= { x330wanSpecific 1 }

--  1.3.6.1.4.1.6889.2.1.6.1.1.1.1
		-- 1.3.6.1.4.1.6889.2.1.6.1.1.1.1
		intWanPortEntry OBJECT-TYPE
			SYNTAX IntWanPortEntry
			MAX-ACCESS not-accessible
			STATUS current
			DESCRIPTION
				"Table of port configuration entries."
			INDEX { intWanGroupID, intWanPortID }
			::= { intWanPortTable 1 }

		IntWanPortEntry ::=
			SEQUENCE {
				intWanGroupID
					INTEGER,
				intWanPortID
					INTEGER,
				intWanPortSpeed
					INTEGER,
				intWanPortMode
					INTEGER,
				intWanPortAutoNegotiation
					INTEGER,
				intWanPortVLANMode
					INTEGER,
				intWanPortVLANBindingMode
					INTEGER,
				intWanPortVlanList
					OCTET STRING
			 }

--  1.3.6.1.4.1.6889.2.1.6.1.1.1.1.1
		-- 1.3.6.1.4.1.6889.2.1.6.1.1.1.1.1
		intWanGroupID OBJECT-TYPE
			SYNTAX INTEGER (1..65535)
			MAX-ACCESS read-only
			STATUS current
			DESCRIPTION
				"The Id of the group in which the port to be configured resides."
			::= { intWanPortEntry 1 }

--  1.3.6.1.4.1.6889.2.1.6.1.1.1.1.2
		-- 1.3.6.1.4.1.6889.2.1.6.1.1.1.1.2
		intWanPortID OBJECT-TYPE
			SYNTAX INTEGER (1..65535)
			MAX-ACCESS read-only
			STATUS current
			DESCRIPTION
				"The Id of the port to be configured."
			::= { intWanPortEntry 2 }

--  1.3.6.1.4.1.6889.2.1.6.1.1.1.1.3
		-- 1.3.6.1.4.1.6889.2.1.6.1.1.1.1.3
		intWanPortSpeed OBJECT-TYPE
			SYNTAX INTEGER
				{
				ethernet(1),
				fastEthernet(2),
				notSupported(255)
				}
			MAX-ACCESS read-write
			STATUS current
			DESCRIPTION
				"This parameter defines the port speed:
				ethernet(1) and fastEthernet(2)."
			DEFVAL { fastEthernet }
			::= { intWanPortEntry 3 }

--  1.3.6.1.4.1.6889.2.1.6.1.1.1.1.4
		-- 1.3.6.1.4.1.6889.2.1.6.1.1.1.1.4
		intWanPortMode OBJECT-TYPE
			SYNTAX INTEGER
				{
				halfDuplex(1),
				fullDuplexSymPause(7),
				notSupported(255)
				}
			MAX-ACCESS read-write
			STATUS current
			DESCRIPTION
				"The flow control mode of the port when operated in full duplex:
				halfDuplex(1) - Half duplex connection, standard mode for segment
				fullDuplexNoPause(2) - Full duplex connection without exchanging flow control packets
				fullDuplexProprietaryFC(3) -
				         Full duplex connection with AVAYA's proprietary flow control frames exchanged
				fullDuplexISL(4) -
				         Full duplex connection with ISL proprietary protocol control words for
				         VLAN & priority exchanged, 	ISL = Inter-Switch-Link
				fullDuplexFlowControlISL(5) -
				        Full duplex connection with both ISL proprietary protocol control words
				        and flow control frames exchanged
				fullDuplexAsymTxPause(6) -
				       Full duplex connection with STD 802.3x flow control frames sent from this port,
				       but flow control packets received on it are not processed
				fullDuplexSymPause(7) -
				       Full duplex connection with STD 802.3x flow control frames exchanged
				fullDuplexAsymRxPause(8) -
				       Full duplex connection with no flow control frames sent from this port,
				       but STD 802.3x flow control 0frames received on it are processed.
				For Giga ports, when auto-negotiation is enabled, the flow control mode is set
				internally according to auto-negotiation resolution; and access to this item is read-only."
			DEFVAL { fullDuplexSymPause }
			::= { intWanPortEntry 4 }

--  1.3.6.1.4.1.6889.2.1.6.1.1.1.1.5
		-- 1.3.6.1.4.1.6889.2.1.6.1.1.1.1.5
		intWanPortAutoNegotiation OBJECT-TYPE
			SYNTAX INTEGER
				{
				enable(1),
				disable(2),
				notSupported(255)
				}
			MAX-ACCESS read-write
			STATUS current
			DESCRIPTION
				" This object define if the Auto Sense /Auto Negotiation
				process is enable(1) or disable (2)
				for modules that don't support the Auto Snese mode
				please define the notSupported option.."
			DEFVAL { disable }
			::= { intWanPortEntry 5 }

--  1.3.6.1.4.1.6889.2.1.6.1.1.1.1.6
		-- 1.3.6.1.4.1.6889.2.1.6.1.1.1.1.6
		intWanPortVLANMode OBJECT-TYPE
			SYNTAX INTEGER
				{
				perPortOnly(1),
				dot1QTagging(2),
				notSupported(255)
				}
			MAX-ACCESS read-write
			STATUS current
			DESCRIPTION
				"This item defines the VLAN operation mode of the port:

				perPortOnly(1)	- indicates that all received packets are mapped to the VLAN, defined on the
				port, and packets are transmitted in untagged format;

				dot1QTagging(2)	- indicates that all received packets are mapped to VLANs according to
				802.1Q standard. All transmitted packets are tagged according to the standard 802.1Q tagging;

				plusTagging(3)	- indicates that all packets recieved and transmitted on that port are tagged
					according to Lannet_s PlusTagging	scheme. This mode is used when inter-VLAN bridging
					should be supported;

				islTagging(4)	- indicates that all packets recieved and transmitted on that port are tagged
					according to the proprietary ISL mode of Lannet;

				dot1QTaggingButPVID(5) - indicates that all received packets are mapped to VLANs
					according to 802.1Q standard. All transmitted packets are tagged according to the standard
					802.1Q tagging, exluding packets that belong to the port_s VLAN,which are transmitted untagged."
			DEFVAL { dot1QTagging }
			::= { intWanPortEntry 6 }

--  1.3.6.1.4.1.6889.2.1.6.1.1.1.1.7
		-- 1.3.6.1.4.1.6889.2.1.6.1.1.1.1.7
		intWanPortVLANBindingMode OBJECT-TYPE
			SYNTAX INTEGER
				{
				static(1),
				bindToReceive(2),
				bindToAll(3),
				notSupported(255)
				}
			MAX-ACCESS read-write
			STATUS current
			DESCRIPTION
				"VLAN binding mode assigned to this port.
				static - this port supports only the egress VLAN list as configured manually in its corresponding
				dot1qVlanStaticEgressPort. This is the default VLAN Binding mode.
				bindToReceive - this port supports the whole range of 3K VLANs from VLAN ID 1 to 3071.
				bindToAll - this port supports the egress VLAN IDs for which dot1qVlanStaticTable rows exist.
				GVRP - this port supports the egress VLAN IDs configured manually in its corresponding
				dot1qVlanStaticEgressPort as well as VLAN IDs requested by the GVRP link partner."
			DEFVAL { static }
			::= { intWanPortEntry 7 }

--  1.3.6.1.4.1.6889.2.1.6.1.1.1.1.8
		-- 1.3.6.1.4.1.6889.2.1.6.1.1.1.1.8
		intWanPortVlanList OBJECT-TYPE
			SYNTAX OCTET STRING
			MAX-ACCESS read-write
			STATUS current
			DESCRIPTION
				"An 4096-bit-long bitmask of all vlans supported on a port. For example:
				A 1 bit in the 10th place means that vlan 10 is supported."
			::= { intWanPortEntry 8 }

--  1.3.6.1.4.1.6889.2.1.6.1.1.2
		-- 1.3.6.1.4.1.6889.2.1.6.1.1.2
		ds0BundleMemmbersTable OBJECT-TYPE
			SYNTAX SEQUENCE OF Ds0BundleMemmbersEntry
			MAX-ACCESS not-accessible
			STATUS current
			DESCRIPTION
				"This table is used to quickly assign members to a ds0Bunbdle
				Its effect is similar as using the ifStack table,
				only it does it in one go.
				"
			::= { x330wanSpecific 2 }

--  1.3.6.1.4.1.6889.2.1.6.1.1.2.1
		-- 1.3.6.1.4.1.6889.2.1.6.1.1.2.1
		ds0BundleMemmbersEntry OBJECT-TYPE
			SYNTAX Ds0BundleMemmbersEntry
			MAX-ACCESS not-accessible
			STATUS current
			DESCRIPTION
				"An entry in yhr ds0BundleMembers table"
			INDEX { dsx0BundleIndex }
			::= { ds0BundleMemmbersTable 1 }

		Ds0BundleMemmbersEntry ::=
			SEQUENCE {
				ds0BundleMemmbersList
					OCTET STRING,
				ds0BundleSpeedFactor
					INTEGER
			 }

--  1.3.6.1.4.1.6889.2.1.6.1.1.2.1.1
		-- 1.3.6.1.4.1.6889.2.1.6.1.1.2.1.1
		ds0BundleMemmbersList OBJECT-TYPE
			SYNTAX OCTET STRING
			MAX-ACCESS read-write
			STATUS current
			DESCRIPTION
				"A bit mask of timeslots that are part of the channel group
				identified by ds0BundleIndex.
				First (leftmost) bit stands for timeslot 0."
			DEFVAL { '00'h }
			::= { ds0BundleMemmbersEntry 1 }

--  1.3.6.1.4.1.6889.2.1.6.1.1.2.1.2
		-- 1.3.6.1.4.1.6889.2.1.6.1.1.2.1.2
		ds0BundleSpeedFactor OBJECT-TYPE
			SYNTAX INTEGER
				{
				a64kbps(1),
				a56kbps(2)
				}
			MAX-ACCESS read-write
			STATUS current
			DESCRIPTION
				"The speed factor for this ds0bundle.
				This can either be 56k or 64k."
			::= { ds0BundleMemmbersEntry 2 }

--  Interfaces specific objects
--
-- 1.3.6.1.4.1.6889.2.1.6.2
		-- 1.3.6.1.4.1.6889.2.1.6.2
		ifs OBJECT IDENTIFIER ::= { avayaEISWan 2 }

--  1.3.6.1.4.1.6889.2.1.6.2.1
		-- 1.3.6.1.4.1.6889.2.1.6.2.1
		ds1objs OBJECT IDENTIFIER ::= { ifs 1 }

--  1.3.6.1.4.1.6889.2.1.6.2.1.1
		-- 1.3.6.1.4.1.6889.2.1.6.2.1.1
		ds1DeviceMode OBJECT-TYPE
			SYNTAX INTEGER
				{
				e1(1),
				t1(2),
				j1(3)
				}
			MAX-ACCESS read-write
			STATUS current
			DESCRIPTION
				"The configured device mode. Either all DS1s on the device are e1, t1 or j1.
				To activate a new selection, perform 'copy running-config startup-config'
				 and reset the device."
			::= { ds1objs 1 }

--  1.3.6.1.4.1.6889.2.1.6.2.1.1
		-- 1.3.6.1.4.1.6889.2.1.6.2.1.2
		ds1CurrentDeviceMode OBJECT-TYPE
			SYNTAX INTEGER
				{
				e1(1),
				t1(2),
				j1(3)
				}
			MAX-ACCESS read-only
			STATUS current
			DESCRIPTION
				"The current device mode"
			::= { ds1objs 2 }

--  1.3.6.1.4.1.6889.2.1.6.2.2
		-- 1.3.6.1.4.1.6889.2.1.6.2.2
		ifTablePrivateExtensions OBJECT IDENTIFIER ::= { ifs 2 }

--  This table provides additional
-- information for interfaces that appear
-- in the ifTable.
-- 1.3.6.1.4.1.6889.2.1.6.2.2.1
		-- 1.3.6.1.4.1.6889.2.1.6.2.2.1
		ifTableXtndTable OBJECT-TYPE
			SYNTAX SEQUENCE OF IfTableXtndEntry
			MAX-ACCESS not-accessible
			STATUS current
			DESCRIPTION
				"The ifTableXtndTable table."
			::= { ifTablePrivateExtensions 1 }

--  An entry in the ifTableXtndTable.
-- 1.3.6.1.4.1.6889.2.1.6.2.2.1.1
		-- 1.3.6.1.4.1.6889.2.1.6.2.2.1.1
		ifTableXtndEntry OBJECT-TYPE
			SYNTAX IfTableXtndEntry
			MAX-ACCESS not-accessible
			STATUS current
			DESCRIPTION
				"This table is an extension of the itTable.
				It contains a row per every row of the ifTable.

				It is used to perform additional configuration,
				not available through standard mibs.
				A row will exist in this table for each row
				in the ifTable, even if specific
				configuration object has no meaning for
				the type of interface for which this row is used."
			INDEX { ifTableXtndIndex }
			::= { ifTableXtndTable 1 }

		IfTableXtndEntry ::=
			SEQUENCE {
				ifTableXtndIndex
					InterfaceIndex,
				ifTableXtndPeerAddress
					IpAddress,
				ifTableXtndVoIPQueue
					INTEGER,
				ifTableXtndCableLength
					INTEGER,
				ifTableXtndGain
					INTEGER,
				ifTableXtndDescription
					DisplayString,
				ifTableXtndKeepAlive
					Integer32,
				ifTableXtndMtu
					Integer32,
				ifTableXtndInvertTxClock
					OnOff,
				ifTableXtndDTELoopback
					OnOff,
				ifTableXtndIgnoreDCD
					OnOff,
				ifTableXtndIdleChars
					INTEGER,
				ifTableXtndBandwidth
					Integer32,
				ifTableXtndEncapsulation
					INTEGER,
				ifTableXtndOperStatus
					INTEGER,
				ifTableXtndBackupCapabilities
					INTEGER,
				ifTableXtndBackupIf
					InterfaceIndex,
				ifTableXtndBackupEnableDelay
					INTEGER,
				ifTableXtndBackupDisableDelay
					INTEGER,
				ifTableXtndPrimaryIf
					InterfaceIndex,
				ifTableXtndCarrierDelay
					Integer32,
				ifTableXtndDtrRestartDelay
					Integer32,
				ifTableXtndDtrPulseTime
					Integer32,
				ifTableXtndLoadInterval
					Integer32,
				ifTableXtndInputRate
					Gauge32,
				ifTableXtndOutputRate
					Gauge32,
				ifTableXtndInputLoad
					Gauge32,
				ifTableXtndOutputLoad
					Gauge32,
				ifTableXtndReliability
					Gauge32,
				ifTableXtndTrafficShaperRate
					Integer32,
				ifTableXtndCacBBL
					Integer32,
				ifTableXtndCacPriority
					Integer32,
				ifTableXtndCacifStatus
					INTEGER,
				ifTableXtndCommonApplifStatus
					OCTET STRING,
				ifTableXtndIpSecDfBit
					INTEGER,
				ifTableXtndMinPmtu
					Integer32,
				ifTableXtndConfString
					DisplayString,
				ifTableXtndPppIpcpDnsOptionRequest
					INTEGER,
				ifTableXtndKeepaliveTrackId
					Unsigned32,
				ifTableXtndFrTrafficShaping
					OnOff,
			    ifTableXtndType
			        INTEGER
			 }

--  1.3.6.1.4.1.6889.2.1.6.2.2.1.1.1
		-- 1.3.6.1.4.1.6889.2.1.6.2.2.1.1.1
		ifTableXtndIndex OBJECT-TYPE
			SYNTAX InterfaceIndex
			MAX-ACCESS read-only
			STATUS current
			DESCRIPTION
				"The index in the ifTable for which this row
				is providing information."
			::= { ifTableXtndEntry 1 }

--  1.3.6.1.4.1.6889.2.1.6.2.2.1.1.2
		-- 1.3.6.1.4.1.6889.2.1.6.2.2.1.1.2
		ifTableXtndPeerAddress OBJECT-TYPE
			SYNTAX IpAddress
			MAX-ACCESS read-only
			STATUS current
			DESCRIPTION
				"The IP Address of the peer device on
				the link identified by this ifIndex.
				This value is only meaningful for
				point to point links."
			::= { ifTableXtndEntry 2 }

--  1.3.6.1.4.1.6889.2.1.6.2.2.1.1.3
		-- 1.3.6.1.4.1.6889.2.1.6.2.2.1.1.3
		ifTableXtndVoIPQueue OBJECT-TYPE
			SYNTAX INTEGER
				{
				on(1),
				off(2),
				fairQ(3),
				notRelevant(255)
				}
			MAX-ACCESS read-write
			STATUS current
			DESCRIPTION
				"Turns voip-queueing on or off or turn fair-queuing on."
			DEFVAL { notRelevant }
			::= { ifTableXtndEntry 3 }

--  1.3.6.1.4.1.6889.2.1.6.2.2.1.1.4
		-- 1.3.6.1.4.1.6889.2.1.6.2.2.1.1.4
		ifTableXtndCableLength OBJECT-TYPE
			SYNTAX INTEGER
				{
				long15db(1),
				long22dot5db(2),
				long7dot5db(3),
				long0db(4),
				short133ft(5),
				short266ft(6),
				short399ft(7),
				short533ft(8),
				short655ft(9),
				notSupported(255)
				}
			MAX-ACCESS read-write
			STATUS current
			DESCRIPTION
				"Cable length attenuation on this interface."
			::= { ifTableXtndEntry 4 }

--  1.3.6.1.4.1.6889.2.1.6.2.2.1.1.5
		-- 1.3.6.1.4.1.6889.2.1.6.2.2.1.1.5
		ifTableXtndGain OBJECT-TYPE
			SYNTAX INTEGER
				{
				a26(1),
				a36(2),
				notSupported(255)
				}
			MAX-ACCESS read-write
			STATUS current
			DESCRIPTION
				"The gain on this interface."
			::= { ifTableXtndEntry 5 }

--  1.3.6.1.4.1.6889.2.1.6.2.2.1.1.6
		-- 1.3.6.1.4.1.6889.2.1.6.2.2.1.1.6
		ifTableXtndDescription OBJECT-TYPE
			SYNTAX DisplayString
			MAX-ACCESS read-write
			STATUS current
			DESCRIPTION
				"This object is a Read-Write equivalent
				of ifDescr. It is used to enable users
				to change the value of ifDescr."
			DEFVAL { ''b }
			::= { ifTableXtndEntry 6 }

--  1.3.6.1.4.1.6889.2.1.6.2.2.1.1.7
		-- 1.3.6.1.4.1.6889.2.1.6.2.2.1.1.7
		ifTableXtndKeepAlive OBJECT-TYPE
			SYNTAX Integer32
			MAX-ACCESS read-write
			STATUS current
			DESCRIPTION
				"Time, in seconds, between keepalive messages.
				0 means keepalive should not be used, or is not
				supported."
			DEFVAL { 0 }
			::= { ifTableXtndEntry 7 }

--  1.3.6.1.4.1.6889.2.1.6.2.2.1.1.8
		-- 1.3.6.1.4.1.6889.2.1.6.2.2.1.1.8
		ifTableXtndMtu OBJECT-TYPE
			SYNTAX Integer32
			MAX-ACCESS read-write
			STATUS current
			DESCRIPTION
				"This object is a R/W copy of the ifMtu
				object from the ifTable.
				It enables changing of the MTU for
				interfaces that allow this."
			DEFVAL { 0 }
			::= { ifTableXtndEntry 8 }

--  1.3.6.1.4.1.6889.2.1.6.2.2.1.1.9
		-- 1.3.6.1.4.1.6889.2.1.6.2.2.1.1.9
		ifTableXtndInvertTxClock OBJECT-TYPE
			SYNTAX OnOff
			MAX-ACCESS read-write
			STATUS current
			DESCRIPTION
				"This object is only applicable for rs232-like
				synchronuos DTE interefaces.
				It determines whether the transmit clock
				is inverted.
				"
			DEFVAL { notRelevant }
			::= { ifTableXtndEntry 9 }

--  1.3.6.1.4.1.6889.2.1.6.2.2.1.1.10
		-- 1.3.6.1.4.1.6889.2.1.6.2.2.1.1.10
		ifTableXtndDTELoopback OBJECT-TYPE
			SYNTAX OnOff
			MAX-ACCESS read-write
			STATUS current
			DESCRIPTION
				"This object is only applicable for rs232-like
				synchronuos DTE interefaces.
				It determines the status of the DTE loopback."
			DEFVAL { notRelevant }
			::= { ifTableXtndEntry 10 }

--  1.3.6.1.4.1.6889.2.1.6.2.2.1.1.11
		-- 1.3.6.1.4.1.6889.2.1.6.2.2.1.1.11
		ifTableXtndIgnoreDCD OBJECT-TYPE
			SYNTAX OnOff
			MAX-ACCESS read-write
			STATUS current
			DESCRIPTION
				"This object is only applicable for rs232-like
				synchronuos DTE interefaces.
				This command configures the serial interface
				to monitor the DSR/CTS signals, instead of
				DCD signal, as the line up/down indicator."
			DEFVAL { notRelevant }
			::= { ifTableXtndEntry 11 }

--  1.3.6.1.4.1.6889.2.1.6.2.2.1.1.12
		-- 1.3.6.1.4.1.6889.2.1.6.2.2.1.1.12
		ifTableXtndIdleChars OBJECT-TYPE
			SYNTAX INTEGER
				{
				flag(1),
				mark(2),
				space(3),
				notRelevant(255)
				}
			MAX-ACCESS read-write
			STATUS current
			DESCRIPTION
				"This object is only applicable for rs232-like
				synchronuos DTE interefaces.
				This command sets the bit pattern used to
				indicate an idle line."
			DEFVAL { notRelevant }
			::= { ifTableXtndEntry 12 }

--  1.3.6.1.4.1.6889.2.1.6.2.2.1.1.13
		-- 1.3.6.1.4.1.6889.2.1.6.2.2.1.1.13
		ifTableXtndBandwidth OBJECT-TYPE
			SYNTAX Integer32
			MAX-ACCESS read-write
			STATUS current
			DESCRIPTION
				"This object is used to determine the bandwidth
				of the interface, in Kbps, for interfaces that
				support it.

				This information is informational, and does not
				affect the actual transmission rate."
			DEFVAL { 0 }
			::= { ifTableXtndEntry 13 }

--  1.3.6.1.4.1.6889.2.1.6.2.2.1.1.14
		-- 1.3.6.1.4.1.6889.2.1.6.2.2.1.1.14
		ifTableXtndEncapsulation OBJECT-TYPE
			SYNTAX INTEGER
				{
				ppp(1),
				frameRelay(2),
				pppoe(3),
				arpa(4),
				frameRelayNonIetf(5),
				notSupported(255)
				}
			MAX-ACCESS read-write
			STATUS current
			DESCRIPTION
				"Applicable only to layer 1 interfaces.
				The type of the layer 2 interface on top of this
				Interface.

				ppp - The Layer 2 interface is PPP
				frameRelay - The Layer 2 interface is IETF Frame Relay.
				pppoe - PPPoE-client mode for Ethernet interfaces
				arpa - non-PPPoE client mode for Ethernet interfaces
				frameRelayNonIetf - The Layer 2 interface is Frame Relay compliant with Cisco
				frame relay but not compliant to IETF.
				interactive - External Modem enabled (for Console & USB-modem interfaces).
				terminal - External modem disabled   (for Console  interface)
				"
			DEFVAL { ppp }
			::= { ifTableXtndEntry 14 }

--  1.3.6.1.4.1.6889.2.1.6.2.2.1.1.15
		-- 1.3.6.1.4.1.6889.2.1.6.2.2.1.1.15
		ifTableXtndOperStatus OBJECT-TYPE
			SYNTAX INTEGER
				{
				up(1),
				faultDown(2),
				testing(3),
				partiallyDownFault(4),
				adminDown(5),
				dormantDown(6),
				xtndKeepAliveDown(7),
				modemUndetected(8),
				modemReady(9),
				modemDialing(10),
				modemConnectedDialin(11),
				modemConnectedDialout(12),
				notSupported(255)
				}
			MAX-ACCESS read-only
			STATUS current
			DESCRIPTION
				"An extension to ifOperStatus, for showing faults
				and partial faliures, including aggregation of upper
				layer faults (up to but not including L3).
				The following Pseudo code describes how the MIB
				value is calculated for different interfaces:
				if (AdminStatus is down) {
				   XtndOperStatus= adminDown
				} else
				if (OperStatus is testing) {
				   XtndOperStatus = testing
				} else
				if (This is a backup interface and its currently in
				    dormant state)
				{
				  XtndOperStatus= dormantDown
				} else
				if (OperStatus = down) {
				   XtndOperStatus = faultDown
				} else
				switch interface type {
				  case E1/T1:
				      if (XtndOperStatus of any Channel
				          Group over this I/F is (faultDown
				          or partialDownFault)){
				            XtndOperStatus = partialDownFault
				      } else
				           XtndOperStatus = up
				      break;
				   case USP or Channel Group:
				      if (XtndOperStatus of FR or PPP I/F over
				          this I/F is (faultDown or
				          partialDownFault)){
				        XtndOperStatus = partialDownFault
				      } else
				      XtndOperStatus = up
				      break;
				case FastEthernet or loopback:
				if (XtndKeepAliveStatus is Down)  {
				XtndOperStatus = keepAliveDown
				} else   XtndOperStatus = up
				break;
				case PPP or FabricFastEthernet:
				XtndOperStatus = up
				break;
				case Frame Relay:
				      if (XtndOperStatus of any Sub FR over this
				          I/F is (faultDown or
				          partialDownFault)) {
				         XtndOperStatus = partialDownFault
				      } else
				      XtndOperStatus = up
				      break;
				   case Frame Relay Sub I/F:
				      if (at least one DLCI is up, and at least
				         one is down){
				        XtndOperStatus = partialDownFault
				      } else
				        XtndOperStatus = up
				      break;
				   case Modem:
				       If (modem is undetected) {XtndOperStatus = modemUndetected}
				       elseif (modem is ready to accept calls){XtndOperStatus = modemReady)
				       elseif (a dialer is dialing the modem) {XtndOperStatus = modemDialing}
				       elseif (modem is connected - incoming call)
				        {XtndOperStatus = modemConnectedDialin}
				       elseif (modem is connected - outgoing call)
				       {XtndOperStatus = modemConnectedDialout}
				}    "
			::= { ifTableXtndEntry 15 }

--  1.3.6.1.4.1.6889.2.1.6.2.2.1.1.16
		-- 1.3.6.1.4.1.6889.2.1.6.2.2.1.1.16
		ifTableXtndBackupCapabilities OBJECT-TYPE
			SYNTAX INTEGER
				{
				primaryAndBackUp(1),
				primaryOnly(2),
				backupOnly(3),
				notSupported(255)
				}
			MAX-ACCESS read-only
			STATUS current
			DESCRIPTION
				"Determines what roles an interface can play in a backup
				relation. This should be filled per interface,
				according to its capabilities.

				primaryAndBackup - the interface can be play  both the
				                 primary and the backup roles.

				primaryOnly - the interface can only play the primary
				              role.

				backupOnly - the interface can only play the backup
				             role.

				notSupported - the interface can play no role in a
				              backup relation."
			::= { ifTableXtndEntry 16 }

--  1.3.6.1.4.1.6889.2.1.6.2.2.1.1.17
		-- 1.3.6.1.4.1.6889.2.1.6.2.2.1.1.17
		ifTableXtndBackupIf OBJECT-TYPE
			SYNTAX InterfaceIndex
			MAX-ACCESS read-write
			STATUS current
			DESCRIPTION
				"The ifIndex of the backup interface for this primary
				interface.

				0 if no backup is defined.

				The agent will not permit setting this value, if:
				The intreface is not capable of the primary role,
				OR
				The supplied backup index does not point to an
				interface capable of the backup role, which is not
				currently in a backup role."
			DEFVAL { 0 }
			::= { ifTableXtndEntry 17 }

--  1.3.6.1.4.1.6889.2.1.6.2.2.1.1.18
		-- 1.3.6.1.4.1.6889.2.1.6.2.2.1.1.18
		ifTableXtndBackupEnableDelay OBJECT-TYPE
			SYNTAX INTEGER (0..3600)
			MAX-ACCESS read-write
			STATUS current
			DESCRIPTION
				"The delay (in Secs) that a primary interface must be
				inactive before its backup interface is activated.

				Configurable on the primary interface only."
			::= { ifTableXtndEntry 18 }

--  1.3.6.1.4.1.6889.2.1.6.2.2.1.1.19
		-- 1.3.6.1.4.1.6889.2.1.6.2.2.1.1.19
		ifTableXtndBackupDisableDelay OBJECT-TYPE
			SYNTAX INTEGER (-1..3600)
			MAX-ACCESS read-write
			STATUS current
			DESCRIPTION
				"The delay (in Secs) between the primary coming back to
				life and its activation and de-activation of its
				backup interface.
				The value '-1' means that the primary is never
				re-activated and the backup is never de-activated.
				Configurable on the primary interface only."
			::= { ifTableXtndEntry 19 }

--  1.3.6.1.4.1.6889.2.1.6.2.2.1.1.20
		-- 1.3.6.1.4.1.6889.2.1.6.2.2.1.1.20
		ifTableXtndPrimaryIf OBJECT-TYPE
			SYNTAX InterfaceIndex
			MAX-ACCESS read-only
			STATUS current
			DESCRIPTION
				"On a backup interface, this will point to the primary
				interface. '0' means no primary interface."
			::= { ifTableXtndEntry 20 }

--  1.3.6.1.4.1.6889.2.1.6.2.2.1.1.21
		-- 1.3.6.1.4.1.6889.2.1.6.2.2.1.1.21
		ifTableXtndCarrierDelay OBJECT-TYPE
			SYNTAX Integer32 (0..60)
			MAX-ACCESS read-write
			STATUS current
			DESCRIPTION
				"This command sets the carrier delay on a serial
				interface in seconds. If a link goes down and comes
				back up before the carrier delay timer expires, the
				down state is effectively filtered, and the switch is
				not aware that a link-down event occurred."
			DEFVAL { 2 }
			::= { ifTableXtndEntry 21 }

--  1.3.6.1.4.1.6889.2.1.6.2.2.1.1.22
		-- 1.3.6.1.4.1.6889.2.1.6.2.2.1.1.22
		ifTableXtndDtrRestartDelay OBJECT-TYPE
			SYNTAX Integer32 (0..900)
			MAX-ACCESS read-write
			STATUS current
			DESCRIPTION
				"Determines the period in seconds for deactivating
				DTR signal when the serial line is inactive."
			DEFVAL { 30 }
			::= { ifTableXtndEntry 22 }

--  1.3.6.1.4.1.6889.2.1.6.2.2.1.1.23
		-- 1.3.6.1.4.1.6889.2.1.6.2.2.1.1.23
		ifTableXtndDtrPulseTime OBJECT-TYPE
			SYNTAX Integer32 (0..60)
			MAX-ACCESS read-write
			STATUS current
			DESCRIPTION
				"Determines the interval in milliseconds DTR signal is
				held inactive when the serial line is inactive."
			DEFVAL { 1 }
			::= { ifTableXtndEntry 23 }

--  1.3.6.1.4.1.6889.2.1.6.2.2.1.1.24
		-- 1.3.6.1.4.1.6889.2.1.6.2.2.1.1.24
		ifTableXtndLoadInterval OBJECT-TYPE
			SYNTAX Integer32 (30..600)
			MAX-ACCESS read-write
			STATUS current
			DESCRIPTION
				"Determines interval (in secs) for exponential averages
				calculations for an interface.
				Must be a multiple of 30."
			DEFVAL { 300 }
			::= { ifTableXtndEntry 24 }

--  1.3.6.1.4.1.6889.2.1.6.2.2.1.1.25
		-- 1.3.6.1.4.1.6889.2.1.6.2.2.1.1.25
		ifTableXtndInputRate OBJECT-TYPE
			SYNTAX Gauge32
			MAX-ACCESS read-only
			STATUS current
			DESCRIPTION
				"Expoential Average of the Number of bits
				received per second calculated for the interval
				specified in ifTableXtndLoadInterval.
				The exponentail average smooths peaks while correctly
				showing current trends.

				Calculated as follows:
				RateSample= (bitsLast - bitCurrent)/5
				where bitCurrent = number of bits received, sampled
				every 5 seconds.

				new_ifTableXtndInputRate =
				(old_ifTableXtndInputRate - RateSample)
				*exp( -5/LoadInterval) + RateSample

				"
			::= { ifTableXtndEntry 25 }

--  1.3.6.1.4.1.6889.2.1.6.2.2.1.1.26
		-- 1.3.6.1.4.1.6889.2.1.6.2.2.1.1.26
		ifTableXtndOutputRate OBJECT-TYPE
			SYNTAX Gauge32
			MAX-ACCESS read-only
			STATUS current
			DESCRIPTION
				"Expoential Average of the Number of bits
				sent per second calculated for the interval
				specified in ifTableXtndLoadInterval.
				The exponentail average smooths peaks while correctly
				showing current trends.

				Calculated as follows:
				RateSample= (bitsLast - bitCurrent)/5
				where bitCurrent = number of bits sent, sampled
				every 5 seconds.

				new_ifTableXtndOutputRate =
				(old_ifTableXtndOutputRate - RateSample)
				*exp( -5/LoadInterval) + RateSample

				"
			::= { ifTableXtndEntry 26 }

--  1.3.6.1.4.1.6889.2.1.6.2.2.1.1.27
		-- 1.3.6.1.4.1.6889.2.1.6.2.2.1.1.27
		ifTableXtndInputLoad OBJECT-TYPE
			SYNTAX Gauge32
			MAX-ACCESS read-only
			STATUS current
			DESCRIPTION
				"Expoential Average of the Input Load calculated for the interval
				specified in ifTableXtndLoadInterval.
				Load is expressed a a number in the range 1 to 255.
				255 = 100% utilization (input bits per second equal
				the interface speed).
				1 = 0% utilization.

				The exponentail average smooths peaks while correctly
				showing current trends.

				Calculated as follows:
				RateSample= int((bitsLast - bitCurrent)/(5*ifSpeed))*254
				+1
				where bitCurrent = number of bits received, sampled
				every 5 seconds.

				new_ifTableXtndInputLoad =
				(old_ifTableXtndInputLoad - RateSample)
				*exp( -5/LoadInterval) + RateSample

				"
			::= { ifTableXtndEntry 27 }

--  1.3.6.1.4.1.6889.2.1.6.2.2.1.1.28
		-- 1.3.6.1.4.1.6889.2.1.6.2.2.1.1.28
		ifTableXtndOutputLoad OBJECT-TYPE
			SYNTAX Gauge32
			MAX-ACCESS read-only
			STATUS current
			DESCRIPTION
				"Expoential Average of the Output Load calculated for the interval
				specified in ifTableXtndLoadInterval.
				Load is expressed a a number in the range 1 to 255.
				255 = 100% utilization (input bits per second equal
				the interface speed).
				1 = 0% utilization.

				The exponentail average smooths peaks while correctly
				showing current trends.

				Calculated as follows:
				RateSample= int((bitsLast - bitCurrent)/(5*ifSpeed))*254
				+1
				where bitCurrent = number of bits sent, sampled
				every 5 seconds.

				new_ifTableXtndOutputLoad =
				(old_ifTableXtndOutputLoad - RateSample)
				*exp( -5/LoadInterval) + RateSample

				"
			::= { ifTableXtndEntry 28 }

--  1.3.6.1.4.1.6889.2.1.6.2.2.1.1.29
		-- 1.3.6.1.4.1.6889.2.1.6.2.2.1.1.29
		ifTableXtndReliability OBJECT-TYPE
			SYNTAX Gauge32
			MAX-ACCESS read-only
			STATUS current
			DESCRIPTION
				"Expoential Average of the Reliability of an interface
				calculated for the interval specified in
				ifTableXtndLoadInterval.

				Reliability is expressed a a number in the range 1 to
				255.
				255 = Fully Reliable interface.
				1 = Interface is extremly un reliable.


				The exponentail average smooths peaks while correctly
				showing current trends.

				RateSample is calculated every 5 seconds as follows:
				If (OperStatus is down and Admin status is Up)
				   RateSample =1
				else
				   RateSample = 255

				new_ifTableXtndReliability =
				(old_ifTableXtndReliability - RateSample)
				*exp( -5/LoadInterval) + RateSample

				"
			::= { ifTableXtndEntry 29 }

--  1.3.6.1.4.1.6889.2.1.6.2.2.1.1.30
		-- 1.3.6.1.4.1.6889.2.1.6.2.2.1.1.30
		ifTableXtndTrafficShaperRate OBJECT-TYPE
			SYNTAX Integer32
			MAX-ACCESS read-write
			STATUS current
			DESCRIPTION
				"This item controls a traffic shaper on the interface.
				Its value is the shaping rate in bits per seconds.
				When zero, the shaper is disabled"
			DEFVAL { 0 }
			::= { ifTableXtndEntry 30 }

--  1.3.6.1.4.1.6889.2.1.6.2.2.1.1.31
		-- 1.3.6.1.4.1.6889.2.1.6.2.2.1.1.31
		ifTableXtndCacBBL OBJECT-TYPE
			SYNTAX Integer32
			MAX-ACCESS read-write
			STATUS current
			DESCRIPTION
				"Dynamic CAC Bearer Bandwidth Limit in
				kilo-bits-per-seconds. This item equals -1 when dynamic CAC
				is not configured."
			DEFVAL { -1 }
			::= { ifTableXtndEntry 31 }

--  1.3.6.1.4.1.6889.2.1.6.2.2.1.1.32
		-- 1.3.6.1.4.1.6889.2.1.6.2.2.1.1.32
		ifTableXtndCacPriority OBJECT-TYPE
			SYNTAX Integer32
			MAX-ACCESS read-write
			STATUS current
			DESCRIPTION
				"If more than one interface with configured BBL is up,
				the gateway reports the BBL of the interface with the highest
				 activation priority value. If N active interfaces shares the
				 same highest CAC activation priority. The gateway's RBBL is
				 equals N multiple by the lowest BBL value in this interface group.
				 If the activation priority is unspecified, it receives the default
				 value (5). ."
			DEFVAL { 5 }
			::= { ifTableXtndEntry 32 }

--  1.3.6.1.4.1.6889.2.1.6.2.2.1.1.33
		-- 1.3.6.1.4.1.6889.2.1.6.2.2.1.1.33
		ifTableXtndCacifStatus OBJECT-TYPE
			SYNTAX INTEGER
				{
				notConfigured(1),
				active(2),
				notActive(3),
				activeECMP(4),
				notSupported(255)
				}
			MAX-ACCESS read-only
			STATUS current
			DESCRIPTION
				"Dynamic CAC status of the interface."
			DEFVAL { notSupported }
			::= { ifTableXtndEntry 33 }

--  1.3.6.1.4.1.6889.2.1.6.2.2.1.1.34
		-- 1.3.6.1.4.1.6889.2.1.6.2.2.1.1.34
		ifTableXtndCommonApplifStatus OBJECT-TYPE
			SYNTAX OCTET STRING
			MAX-ACCESS read-only
			STATUS current
			DESCRIPTION
				"Supported Application on this Interface.
				If 0 value - Not supported else supported.
				Bit 0 - Unknown Application.
				Bit 1 - Support of Next Hop Interface in Policy Based Routing Application."
			::= { ifTableXtndEntry 34 }

--  1.3.6.1.4.1.6889.2.1.6.2.2.1.1.35
		-- 1.3.6.1.4.1.6889.2.1.6.2.2.1.1.35
		ifTableXtndIpSecDfBit OBJECT-TYPE
			SYNTAX INTEGER
				{
				clear(1),
				copy(2),
				notSupported(255)
				}
			MAX-ACCESS read-write
			STATUS current
			DESCRIPTION
				"This item controls whether the DF (don't fragment) bit of incoming packets
				is copied to the external IPSec header"
			DEFVAL { notSupported }
			::= { ifTableXtndEntry 35 }

--  1.3.6.1.4.1.6889.2.1.6.2.2.1.1.36
		-- 1.3.6.1.4.1.6889.2.1.6.2.2.1.1.36
		ifTableXtndMinPmtu OBJECT-TYPE
			SYNTAX Integer32
			MAX-ACCESS read-write
			STATUS current
			DESCRIPTION
				"Set the minimal PMTU for IPSec tunnels."
			::= { ifTableXtndEntry 36 }

--  1.3.6.1.4.1.6889.2.1.6.2.2.1.1.37
		-- 1.3.6.1.4.1.6889.2.1.6.2.2.1.1.37
		ifTableXtndConfString OBJECT-TYPE
			SYNTAX DisplayString
			MAX-ACCESS read-write
			STATUS current
			DESCRIPTION
				"An additional configuration string for the interface.
				init-string - for modem interfaces "
			::= { ifTableXtndEntry 37 }

		-- 1.3.6.1.4.1.6889.2.1.6.2.2.1.1.38
		ifTableXtndPppIpcpDnsOptionRequest OBJECT-TYPE
			SYNTAX INTEGER
				{
				enable(1),
				disable(2),
				notSupported(255)
				}
			MAX-ACCESS read-write
			STATUS current
			DESCRIPTION
				"PPP-IPCP DNS option request. Configuration whether during the PPP-IPCP
				negotiation the DNS option will be requested. Default: Disable.
				The DNS information gathered will be used by the DNS resolver to resolve hostnames.
				1 - enable
				2 - disable
				255 - notSupported, this Mib item related only to PPP-IPCP interfaces. Other interfaces
				which are not PPP-IPCP, will return this value."
			::= { ifTableXtndEntry 38 }

		-- 1.3.6.1.4.1.6889.2.1.6.2.2.1.1.39
		ifTableXtndKeepaliveTrackId OBJECT-TYPE
			SYNTAX Unsigned32
			MAX-ACCESS read-write
			STATUS current
			DESCRIPTION
				"Bind the status of this interface to an object-tracker by specifying
				the ID of the object-tracker (avstrTrackerId in
				AVAYA-SAA-TRACK-MIB).
				A value of 0 means that interface is not bound to any
				object-tracker.
				A value of 0xffffffff is notSupported feature for the relevant interface.
				"
			DEFVAL { 'ffffffff'h }
			::= { ifTableXtndEntry 39 }

		-- 1.3.6.1.4.1.6889.2.1.6.2.2.1.1.40
		ifTableXtndFrTrafficShaping OBJECT-TYPE
			SYNTAX OnOff
			MAX-ACCESS read-write
			STATUS current
			DESCRIPTION
				"This object determines / indicates whether Frame-Relay
				Traffic-Shaping is enabled (on) or disabled (off) for this
				interface.
				This object can be set only for interfaces, but not for
				sub-interfaces.
				This object is applicable only for interfaces which
				ifTableXtndEncapsulation is Frame-Relay (i.e. frameRelay,
				frameRelayNonIetf)."
			DEFVAL { off }
			::= { ifTableXtndEntry 40 }

		ifTableXtndType 	OBJECT-TYPE
		SYNTAX INTEGER
				{
				nullModem(1),
				usrSporsterModem(2),
				multitechZbaModem(3),
				multitechIsdnModem(4),
				notSupported(255)
				}
			MAX-ACCESS read-write
			STATUS current
			DESCRIPTION    "
			  Extended type is, currently, required for modem interfaces
			"
		   ::= { ifTableXtndEntry 41 }

--  1.3.6.1.4.1.6889.2.1.6.2.2.2
		-- 1.3.6.1.4.1.6889.2.1.6.2.2.2
		xtndKeepAliveTable OBJECT-TYPE
			SYNTAX SEQUENCE OF XtndKeepAliveEntry
			MAX-ACCESS not-accessible
			STATUS current
			DESCRIPTION
				"The Extended Keepalive Parameters Table."
			::= { ifTablePrivateExtensions 2 }

--  1.3.6.1.4.1.6889.2.1.6.2.2.2.1
		-- 1.3.6.1.4.1.6889.2.1.6.2.2.2.1
		xtndKeepAliveEntry OBJECT-TYPE
			SYNTAX XtndKeepAliveEntry
			MAX-ACCESS not-accessible
			STATUS current
			DESCRIPTION
				"This table contains the extended keepalive parameters.
				The Table is per interface. Although for the first phase
				it will be relevant for WAN Fast Ethernet Port. But may be
				available in the future for interface.

				The keepalive on specific interface may bring it to
				line protocol down according the results.

				The main idea is to check certain IP that if not
				responding then the link/route may be down and therefore
				the interface is bring to line protocol down.

				In this case there still be sent extended keepalive packets
				in order to check whether the line protocol is up.
				 "
			INDEX { xtndKeepAliveifIndex }
			::= { xtndKeepAliveTable 1 }

		XtndKeepAliveEntry ::=
			SEQUENCE {
				xtndKeepAliveifIndex
					InterfaceIndex,
				xtndKeepAliveMethod
					INTEGER,
				xtndKeepAliveTimeout
					Integer32,
				xtndKeepAliveUpRetries
					Integer32,
				xtndKeepAliveDownRetries
					Integer32,
				xtndKeepAliveInterval
					Integer32,
				xtndKeepAliveSrcIPAddr
					IpAddress,
				xtndKeepAliveIPAddr
					IpAddress,
				xtndKeepAliveNextHopMAC
					PhysAddress,
				xtndKeepAliveStatus
					INTEGER,
				xtndKeepAliveMode
					INTEGER
			 }

--  1.3.6.1.4.1.6889.2.1.6.2.2.2.1.1
		-- 1.3.6.1.4.1.6889.2.1.6.2.2.2.1.1
		xtndKeepAliveifIndex OBJECT-TYPE
			SYNTAX InterfaceIndex
			MAX-ACCESS read-only
			STATUS current
			DESCRIPTION
				"The index in the ifTable for which this row
				is providing information."
			::= { xtndKeepAliveEntry 1 }

--  1.3.6.1.4.1.6889.2.1.6.2.2.2.1.2
		-- 1.3.6.1.4.1.6889.2.1.6.2.2.2.1.2
		xtndKeepAliveMethod OBJECT-TYPE
			SYNTAX INTEGER
				{
				icmpPing(1),
				tcpConnect(2),
				httpGet(3)
				}
			MAX-ACCESS read-write
			STATUS current
			DESCRIPTION
				"The type of the extended keepalive.
				icmpPing(1),tcpConnect(2),httpGet(3)
				Default is IcmpPing."
			DEFVAL { icmpPing }
			::= { xtndKeepAliveEntry 2 }

--  1.3.6.1.4.1.6889.2.1.6.2.2.2.1.3
		-- 1.3.6.1.4.1.6889.2.1.6.2.2.2.1.3
		xtndKeepAliveTimeout OBJECT-TYPE
			SYNTAX Integer32
			MAX-ACCESS read-write
			STATUS current
			DESCRIPTION
				"Timeout in seconds to wait for a reply.
				Applicable to non-TCP tests such as ICMP Echo, UDP.
				Default 1second."
			::= { xtndKeepAliveEntry 3 }

--  1.3.6.1.4.1.6889.2.1.6.2.2.2.1.4
		-- 1.3.6.1.4.1.6889.2.1.6.2.2.2.1.4
		xtndKeepAliveUpRetries OBJECT-TYPE
			SYNTAX Integer32
			MAX-ACCESS read-write
			STATUS current
			DESCRIPTION
				"The number of successful extended keepalive necessary to
				determine that the next hop router is operational."
			::= { xtndKeepAliveEntry 4 }

--  1.3.6.1.4.1.6889.2.1.6.2.2.2.1.5
		-- 1.3.6.1.4.1.6889.2.1.6.2.2.2.1.5
		xtndKeepAliveDownRetries OBJECT-TYPE
			SYNTAX Integer32
			MAX-ACCESS read-write
			STATUS current
			DESCRIPTION
				"The number of unsuccessful extedned keepalive necessary
				to determine that the next hop router is not operational."
			::= { xtndKeepAliveEntry 5 }

--  1.3.6.1.4.1.6889.2.1.6.2.2.2.1.6
		-- 1.3.6.1.4.1.6889.2.1.6.2.2.2.1.6
		xtndKeepAliveInterval OBJECT-TYPE
			SYNTAX Integer32
			MAX-ACCESS read-write
			STATUS current
			DESCRIPTION
				"The extended keepliave interval in seconds"
			::= { xtndKeepAliveEntry 6 }

--  1.3.6.1.4.1.6889.2.1.6.2.2.2.1.7
		-- 1.3.6.1.4.1.6889.2.1.6.2.2.2.1.7
		xtndKeepAliveSrcIPAddr OBJECT-TYPE
			SYNTAX IpAddress
			MAX-ACCESS read-write
			STATUS current
			DESCRIPTION
				"The Source IP address to use.
				Default is the primary IP address of the interface.
				Setting the address 0.0.0.0 will reset the xtndKeepAliveSrcIPAddr to
				the primary IP interface address"
			DEFVAL { '7f000001'h }
			::= { xtndKeepAliveEntry 7 }

--  1.3.6.1.4.1.6889.2.1.6.2.2.2.1.8
		-- 1.3.6.1.4.1.6889.2.1.6.2.2.2.1.8
		xtndKeepAliveIPAddr OBJECT-TYPE
			SYNTAX IpAddress
			MAX-ACCESS read-write
			STATUS current
			DESCRIPTION
				"The IP address that it status shall be checked. "
			DEFVAL { '00000000'h }
			::= { xtndKeepAliveEntry 8 }

--  1.3.6.1.4.1.6889.2.1.6.2.2.2.1.9
		-- 1.3.6.1.4.1.6889.2.1.6.2.2.2.1.9
		xtndKeepAliveNextHopMAC OBJECT-TYPE
			SYNTAX PhysAddress
			MAX-ACCESS read-write
			STATUS current
			DESCRIPTION
				"The next Hop MAC, Valid for Ethernet Interfaces."
			DEFVAL { '000000000000'h }
			::= { xtndKeepAliveEntry 9 }

		-- 1.3.6.1.4.1.6889.2.1.6.2.2.2.1.10
		xtndKeepAliveStatus OBJECT-TYPE
			SYNTAX INTEGER
				{
				up(1),
				down(2),
				disable(3)
				}
			MAX-ACCESS read-only
			STATUS current
			DESCRIPTION
				"The Status of the extended KeepAlive. I.e. whether the current
				extended KeepAlive succeeded.
				1 - up
				2 - down
				3 - disable
				"
			::= { xtndKeepAliveEntry 10 }

		-- 1.3.6.1.4.1.6889.2.1.6.2.2.2.1.11
		xtndKeepAliveMode OBJECT-TYPE
			SYNTAX INTEGER
				{
				enable(1),
				disable(2)
				}
			MAX-ACCESS read-write
			STATUS current
			DESCRIPTION
				"Extended KeepAlive Mode.
				1 - enable
				2 - disable"
			::= { xtndKeepAliveEntry 11 }

--  Frame Relay Specific Interface extensions.
-- The extemsions extend the MIB defined in RFC2115.
-- 1.3.6.1.4.1.6889.2.1.6.2.4
		-- 1.3.6.1.4.1.6889.2.1.6.2.4
		frameRelay OBJECT IDENTIFIER ::= { ifs 4 }

--  1.3.6.1.4.1.6889.2.1.6.2.4.1
		-- 1.3.6.1.4.1.6889.2.1.6.2.4.1
		frDlcmiXtndTable OBJECT-TYPE
			SYNTAX SEQUENCE OF FrDlcmiXtndEntry
			MAX-ACCESS not-accessible
			STATUS current
			DESCRIPTION
				"This table extends the standard frDlcmiTable,
				which models RFR I/Fs. Entries are created by
				the agent for Frame Relay I/Fs, and are
				deleted when those entries are deleted."
			REFERENCE
				"RFC2115:frDlcmiTable"
			::= { frameRelay 1 }

--  1.3.6.1.4.1.6889.2.1.6.2.4.1.1
		-- 1.3.6.1.4.1.6889.2.1.6.2.4.1.1
		frDlcmiXtndEntry OBJECT-TYPE
			SYNTAX FrDlcmiXtndEntry
			MAX-ACCESS not-accessible
			STATUS current
			DESCRIPTION
				"Each Entry corresponds to a Frame Relay Interface.
				Entries are created & deleted automatically by the
				agent, when ifTableXtndEncapsulation of the underlying
				Layer 1 Interface is changed.
				"
			INDEX { frDlcmiXtndIndex }
			::= { frDlcmiXtndTable 1 }

		FrDlcmiXtndEntry ::=
			SEQUENCE {
				frDlcmiXtndIndex
					InterfaceIndex,
				frDlcmiXtndLMIAutoSense
					OnOff
			 }

--  1.3.6.1.4.1.6889.2.1.6.2.4.1.1.1
		-- 1.3.6.1.4.1.6889.2.1.6.2.4.1.1.1
		frDlcmiXtndIndex OBJECT-TYPE
			SYNTAX InterfaceIndex
			MAX-ACCESS read-only
			STATUS current
			DESCRIPTION
				"The ifIndex assigned to
				The Frame Relay interface is calculated by a known
				formula, which is agent-type specific."
			::= { frDlcmiXtndEntry 1 }

--  1.3.6.1.4.1.6889.2.1.6.2.4.1.1.2
		-- 1.3.6.1.4.1.6889.2.1.6.2.4.1.1.2
		frDlcmiXtndLMIAutoSense OBJECT-TYPE
			SYNTAX OnOff
			MAX-ACCESS read-write
			STATUS current
			DESCRIPTION
				"Enable/disable automatic detection
				(By sending all supported keepalives) of the
				Local Management Interface (LMI) on the Frame Relay
				Interface."
			DEFVAL { on }
			::= { frDlcmiXtndEntry 2 }

--  1.3.6.1.4.1.6889.2.1.6.2.4.2
		-- 1.3.6.1.4.1.6889.2.1.6.2.4.2
		frStaticCircuitTable OBJECT-TYPE
			SYNTAX SEQUENCE OF FrStaticCircuitEntry
			MAX-ACCESS not-accessible
			STATUS current
			DESCRIPTION
				"This table is used to create/associate/delete
				A Virtual Channel (DLCI) with a specific Frame Relay
				Sub Interface. When an entry is created in this table:

				If the DLCI is the same as that of a dynamic frCircuit
				leraned on the Frame Relay Interface layered bellow
				the Sub Interface specified by the entry then:
				- The DLCI's status is changed to Static
				Else - A new static DLCI is created.

				In both cases, the static DLCI is assigned to the
				specified Frame Relay Sub Interface.
				"
			::= { frameRelay 2 }

--  1.3.6.1.4.1.6889.2.1.6.2.4.2.1
		-- 1.3.6.1.4.1.6889.2.1.6.2.4.2.1
		frStaticCircuitEntry OBJECT-TYPE
			SYNTAX FrStaticCircuitEntry
			MAX-ACCESS not-accessible
			STATUS current
			DESCRIPTION
				"An Entry represent a Virtual Channel available on a
				specific Frame Relay Interface.
				"
			INDEX { frStaticCircuitSubIfIndex, frStaticCircuitDLCI, frStaticCircuitDLCIrole }
			::= { frStaticCircuitTable 1 }

		FrStaticCircuitEntry ::=
			SEQUENCE {
				frStaticCircuitSubIfIndex
					InterfaceIndex,
				frStaticCircuitDLCI
					DLCI,
				frStaticCircuitDLCIrole
					INTEGER,
				frStaticCircuitStatus
					RowStatus,
				frStaticCircuitMapClass
					DisplayString
			 }

--  IfIndex of the Frame Relay Sub Interface
-- this VC is associated with.
-- 1.3.6.1.4.1.6889.2.1.6.2.4.2.1.1
		-- 1.3.6.1.4.1.6889.2.1.6.2.4.2.1.1
		frStaticCircuitSubIfIndex OBJECT-TYPE
			SYNTAX InterfaceIndex
			MAX-ACCESS read-only
			STATUS current
			DESCRIPTION
				"Description."
			::= { frStaticCircuitEntry 1 }

--  1.3.6.1.4.1.6889.2.1.6.2.4.2.1.2
		-- 1.3.6.1.4.1.6889.2.1.6.2.4.2.1.2
		frStaticCircuitDLCI OBJECT-TYPE
			SYNTAX DLCI
			MAX-ACCESS read-only
			STATUS current
			DESCRIPTION
				"The virtual channel identifier.
				"
			::= { frStaticCircuitEntry 2 }

--  1.3.6.1.4.1.6889.2.1.6.2.4.2.1.3
		-- 1.3.6.1.4.1.6889.2.1.6.2.4.2.1.3
		frStaticCircuitDLCIrole OBJECT-TYPE
			SYNTAX INTEGER
				{
				priority6to7(1),
				priority4to5(2),
				priority2to3(3),
				priority0to1(4),
				primary(100)
				}
			MAX-ACCESS read-only
			STATUS current
			DESCRIPTION
				"The role of the VC in this interface.
				primary - the state of this VC determines the
				          operStatus of the interface.
				          For point to point interfaces, the agent will not
				          permit more than one primary to exist.
				          A sub interface for which no primary is defined
				          will be down.

				priority6to7 -
				          This VC handles high priority (forwarding class
				          6 to 7)traffic. If this VC does not exists,
				          the sub interface will send all traffic
				          through the primary VC (no priority-dlci-group)
				          In point to point interfaces, only one such VC
				          can be configured.

				priority4to5 -
				          This VC handles Medium priority (forwarding class
				          4 to 5)traffic. If this VC does not exists,
				          the sub interface will send all traffic
				          through the primary VC (no priority-dlci-group)
				          In point to point interfaces, only one such VC
				          can be configured.

				priority2to3 -
				          This VC handles Normal priority (forwarding class
				          2 to 3)traffic. If this VC does not exists,
				          the sub interface will send all traffic
				          through the primary VC (no priority-dlci-group)
				          In point to point interfaces, only one such VC
				          can be configured.

				priority0to1 -
				          This VC handles Low priority (forwarding class
				          0 to 1)traffic. If this VC does not exists,
				          the sub interface will send all traffic
				          through the primary VC (no priority-dlci-group)
				          In point to point interfaces, only one such VC
				          can be configured.
				"
			::= { frStaticCircuitEntry 3 }

--  1.3.6.1.4.1.6889.2.1.6.2.4.2.1.4
		-- 1.3.6.1.4.1.6889.2.1.6.2.4.2.1.4
		frStaticCircuitStatus OBJECT-TYPE
			SYNTAX RowStatus
			MAX-ACCESS read-write
			STATUS current
			DESCRIPTION
				"Used to create/associate/delete a DLCI to a
				Sub FrameRelay Interface.
				Note that the frStaticCircuitDLCIrole defines
				limitations on creation and deletion of DLCIs.
				The notInService state will not be implemented."
			::= { frStaticCircuitEntry 4 }

		-- 1.3.6.1.4.1.6889.2.1.6.2.4.2.1.5
		frStaticCircuitMapClass OBJECT-TYPE
			SYNTAX DisplayString (SIZE (1..64))
			MAX-ACCESS read-write
			STATUS current
			DESCRIPTION
				"A pointer to a 'map-class frame-relay' entry applicable
				for this row.
				A 'map-class frame-relay' is an entry in the frMapClassTable.
				The value of this object must be identical to the value
				of the desired entry's frMapClassName in the frMapClassTable.

				NOTES:
				1. This object can only a point to an existing entry.
				   Trying to set this object to a value that does not pertain
				   to an existing entry in frMapClassTable shall fail.
				2. An entry in the frMapClassTable can be deleted only when
				   it is not pointed to by any entry in this table
				   (frStaticCircuitTable).
				3. The map-class is activated only when the containing interface
				   has Frame-Relay Traffic-Shaping enables.
				   See description of ifTableXtndFrTrafficShaping for details
				   about FRTS.
				4. The frMapClassTable contains a persistent, non-deletable
				   default entry, by the name 'default'."
			DEFVAL { "default" }
			::= { frStaticCircuitEntry 5 }

--  1.3.6.1.4.1.6889.2.1.6.2.4.3
		-- 1.3.6.1.4.1.6889.2.1.6.2.4.3
		frSubIfTable OBJECT-TYPE
			SYNTAX SEQUENCE OF FrSubIfEntry
			MAX-ACCESS not-accessible
			STATUS current
			DESCRIPTION
				"A Frame Relay Sub Interface is the Layer 2 interface
				to which Layer 3 (IP) Interfaces are assigned.
				This Logical Interface is hinted at but not modeled by
				the RFC2115 Frame-Relay DTE MIB.

				This table manages the creation/deletion of Frame
				Relay Sub I/Fs. Entries are created by the Creator
				of a sub-I/F."
			::= { frameRelay 3 }

--  1.3.6.1.4.1.6889.2.1.6.2.4.3.1
		-- 1.3.6.1.4.1.6889.2.1.6.2.4.3.1
		frSubIfEntry OBJECT-TYPE
			SYNTAX FrSubIfEntry
			MAX-ACCESS not-accessible
			STATUS current
			DESCRIPTION
				"An Entry in this table defines a Frame Relay Sub
				Interface of a specific type, defined over a
				specific Frame Relay Interface.

				Note that although the MIB model allow for two
				SubFR I/Fs to have the same ifIndex and have
				different Frame Relay I/Fs or FR types, the agent
				will allow only a single suc interface - the first
				one defined.
				"
			INDEX { frSubIfDlcmiIndex, frSubIfSubIndex, frSubIfType }
			::= { frSubIfTable 1 }

		FrSubIfEntry ::=
			SEQUENCE {
				frSubIfDlcmiIndex
					InterfaceIndex,
				frSubIfSubIndex
					InterfaceIndex,
				frSubIfType
					INTEGER,
				frSubIfStatus
					RowStatus
			 }

--  1.3.6.1.4.1.6889.2.1.6.2.4.3.1.1
		-- 1.3.6.1.4.1.6889.2.1.6.2.4.3.1.1
		frSubIfDlcmiIndex OBJECT-TYPE
			SYNTAX InterfaceIndex
			MAX-ACCESS read-only
			STATUS current
			DESCRIPTION
				"The ifIndex of the Frame Relay Interface this Sub
				Interface is created over."
			::= { frSubIfEntry 1 }

--  1.3.6.1.4.1.6889.2.1.6.2.4.3.1.2
		-- 1.3.6.1.4.1.6889.2.1.6.2.4.3.1.2
		frSubIfSubIndex OBJECT-TYPE
			SYNTAX InterfaceIndex
			MAX-ACCESS read-only
			STATUS current
			DESCRIPTION
				"The ifIndex of the Sub Interface. Note that the
				Mnagement station must select a sub interface number
				in the permissible range (which is agent-type
				dependent.)
				Agent Type     ifIndex Range
				==========     =============
				X330WAN        8000-8999
				"
			::= { frSubIfEntry 2 }

--  The X330WAN V1.5 will support ONLY the point2point type
-- 1.3.6.1.4.1.6889.2.1.6.2.4.3.1.3
		-- 1.3.6.1.4.1.6889.2.1.6.2.4.3.1.3
		frSubIfType OBJECT-TYPE
			SYNTAX INTEGER
				{
				point2point(1),
				point2multiPoint(2)
				}
			MAX-ACCESS read-only
			STATUS current
			DESCRIPTION
				"The Type of the Sub Interface.
				point2point - A Point to Point Interface.
				Point2multiPoint - Point to multi-point interface."
			::= { frSubIfEntry 3 }

--  1.3.6.1.4.1.6889.2.1.6.2.4.3.1.4
		-- 1.3.6.1.4.1.6889.2.1.6.2.4.3.1.4
		frSubIfStatus OBJECT-TYPE
			SYNTAX RowStatus
			MAX-ACCESS read-create
			STATUS current
			DESCRIPTION
				"Creation/Deletion of a Frame Relay Sub Interface over
				a Frame Relay Interface.

				The Agent will refuse to delete a Sub Interface
				if there are IP Interfaces associated with it.
				"
			::= { frSubIfEntry 4 }

		-- 1.3.6.1.4.1.6889.2.1.6.2.4.4
		frMapClassTable OBJECT-TYPE
			SYNTAX SEQUENCE OF FrMapClassEntry
			MAX-ACCESS not-accessible
			STATUS current
			DESCRIPTION
				"This table contains the 'map-class frame-relay' entries
				in the system. A 'map-class frame-relay' entry is a
				collection of QoS-related parameters that can be attached to
				a Frame-Relay DLCI.

				An entry in this table can be attached to a DLCI by
				setting the value of frStaticCircuitMapClass in
				frStaticCircuitTable to the value of the frMapClassName
				of an entry in this table.

				An entry in this table can be deleted only when
				it is not pointed to by any entry in frStaticCircuitTable.
				Trying to delete an entry that does not correspond to that
				shall fail.

				This table contains a default entry that can be modified, but
				cannot be deleted. The value of frMapClassName for that entry
				is 'default'."
			::= { frameRelay 4 }

		-- 1.3.6.1.4.1.6889.2.1.6.2.4.4.1
		frMapClassEntry OBJECT-TYPE
			SYNTAX FrMapClassEntry
			MAX-ACCESS not-accessible
			STATUS current
			DESCRIPTION
				"An entry in the table, which represents a 'frame-relay
				map-class' object."
			INDEX { IMPLIED frMapClassName }
			::= { frMapClassTable 1 }

		FrMapClassEntry ::=
			SEQUENCE {
				frMapClassName
					DisplayString,
				frMapClassBcOut
					Unsigned32,
				frMapClassBeOut
					Unsigned32,
				frMapClassCirOut
					Unsigned32,
				frMapClassFrf12Frag
					Integer32,
				frMapClassRowStatus
					RowStatus
			 }

		-- 1.3.6.1.4.1.6889.2.1.6.2.4.4.1.1
		frMapClassName OBJECT-TYPE
			SYNTAX DisplayString (SIZE (1..64))
			MAX-ACCESS not-accessible
			STATUS current
			DESCRIPTION
				"The name of the map-class, which is also the only index
				component of this table.
				NOTE: This object can only contain a lower-case string!
				Trying to use upper-case characters on creation shall
				result in a failure."
			::= { frMapClassEntry 1 }

		-- 1.3.6.1.4.1.6889.2.1.6.2.4.4.1.2
		frMapClassBcOut OBJECT-TYPE
			SYNTAX Unsigned32
			UNITS "Bits"
			MAX-ACCESS read-write
			STATUS current
			DESCRIPTION
				"The output Commited Burst size, in bits.
				Valid range is 300-39999999."
			DEFVAL { 7000 }
			::= { frMapClassEntry 2 }

		-- 1.3.6.1.4.1.6889.2.1.6.2.4.4.1.3
		frMapClassBeOut OBJECT-TYPE
			SYNTAX Unsigned32
			UNITS "Bits"
			MAX-ACCESS read-write
			STATUS current
			DESCRIPTION
				"The output Excess Burst size, in bits.
				Valid range is 0-39999999."
			DEFVAL { 0 }
			::= { frMapClassEntry 3 }

		-- 1.3.6.1.4.1.6889.2.1.6.2.4.4.1.4
		frMapClassCirOut OBJECT-TYPE
			SYNTAX Unsigned32
			UNITS "Bits per second"
			MAX-ACCESS read-write
			STATUS current
			DESCRIPTION
				"The Committed Information Rate, in bits per second.
				Valid range is 1000-39999999."
			DEFVAL { 56000 }
			::= { frMapClassEntry 4 }

		-- 1.3.6.1.4.1.6889.2.1.6.2.4.4.1.5
		frMapClassFrf12Frag OBJECT-TYPE
			SYNTAX Integer32 (0 | 16..1600)
			UNITS "Bytes"
			MAX-ACCESS read-write
			STATUS current
			DESCRIPTION
				"Disable or enable FRF.12 fragmentation, and determine fragment
				size:
				The reserved value zero means FRF.12 fragmentation is
				disabled.
				A value larger then zero means FRF.12 fragmentation is
				enabled, and the fragment size in bytes is equal to the
				value of this object.
				"
			DEFVAL { 0 }
			::= { frMapClassEntry 5 }

		-- 1.3.6.1.4.1.6889.2.1.6.2.4.4.1.6
		frMapClassRowStatus OBJECT-TYPE
			SYNTAX RowStatus
			MAX-ACCESS read-write
			STATUS current
			DESCRIPTION
				"This object is used to create a new row or
				destroy an existing row in the manner described in the
				definition of the RowStatus textual convention.

				The value of this object has no effect on whether other
				objects in this conceptual row can be modified.

				Use createAndGo (not createAndWait) to create this row."
			::= { frMapClassEntry 6 }

--  1.3.6.1.4.1.6889.2.1.6.6
		-- 1.3.6.1.4.1.6889.2.1.6.2.5
		wanDialer OBJECT IDENTIFIER ::= { ifs 5 }

-- --------------------------------------------------------------------------------------------
-- 1.3.6.1.4.1.6889.2.1.6.6.1
		-- 1.3.6.1.4.1.6889.2.1.6.2.5.1
		wanDialerTable OBJECT-TYPE
			SYNTAX SEQUENCE OF WanDialerEntry
			MAX-ACCESS not-accessible
			STATUS current
			DESCRIPTION
				"This table is used for configuring Dialer interfaces. "
			::= { wanDialer 1 }

--  1.3.6.1.4.1.6889.2.1.6.6.1.1
		-- 1.3.6.1.4.1.6889.2.1.6.2.5.1.1
		wanDialerEntry OBJECT-TYPE
			SYNTAX WanDialerEntry
			MAX-ACCESS not-accessible
			STATUS current
			DESCRIPTION			 " "
			INDEX { ifIndex }
			::= { wanDialerTable 1 }

		WanDialerEntry ::=
			SEQUENCE {
				wanDialerModemIf
					Integer32,
				wanDialerState
					INTEGER,
				wanDialerPersistentDelay
					Integer32,
				wanDialerPersistentMaxAttempts
					Integer32,
				wanDialerPersistentReenable
					Integer32,
				wanDialerOrder
					INTEGER,
				wanDialerString1
					DisplayString,
				wanDialerString2
					DisplayString,
				wanDialerString3
					DisplayString,
				wanDialerString4
					DisplayString,
				wanDialerString5
					DisplayString,
				wanDialerLastDialed
					DisplayString,
				wanDialerWaitForIpcp
					Integer32,
				wanDialerPersistentInitial
					Integer32
			 }

--  1.3.6.1.4.1.6889.2.1.6.6.1.1.1
		-- 1.3.6.1.4.1.6889.2.1.6.2.5.1.1.1
		wanDialerModemIf OBJECT-TYPE
			SYNTAX Integer32
			MAX-ACCESS read-write
			STATUS current
			DESCRIPTION
				"The ifIndex of the modem interface"
			::= { wanDialerEntry 1 }

--  1.3.6.1.4.1.6889.2.1.6.6.1.1.2
		-- 1.3.6.1.4.1.6889.2.1.6.2.5.1.1.2
		wanDialerState OBJECT-TYPE
			SYNTAX INTEGER
				{
				initModem(1),
				idle(2),
				waiting4Modem(3),
				maxAttemptsDisabled(4),
				preDialReset(5),
				waitForConnect(6),
				waitForDCD(7),
				hangUp(8),
				persistentDelay(9),
				waitForIPCP(10),
				connected(11)
				}
			MAX-ACCESS read-only
			STATUS current
			DESCRIPTION
				"The current state of the dialer finit-state-machine"
			::= { wanDialerEntry 2 }

--  1.3.6.1.4.1.6889.2.1.6.6.1.1.3
		-- 1.3.6.1.4.1.6889.2.1.6.2.5.1.1.3
		wanDialerPersistentDelay OBJECT-TYPE
			SYNTAX Integer32
			MAX-ACCESS read-write
			STATUS current
			DESCRIPTION
				"The number of seconds between persistent dial attempts
				(zero= no persistent dialing)"
			::= { wanDialerEntry 3 }

--  1.3.6.1.4.1.6889.2.1.6.6.1.1.4
		-- 1.3.6.1.4.1.6889.2.1.6.2.5.1.1.4
		wanDialerPersistentMaxAttempts OBJECT-TYPE
			SYNTAX Integer32
			MAX-ACCESS read-write
			STATUS current
			DESCRIPTION
				"The interval between persistent (non-DDR) dial attempts.
				Zero means no persistent dialing"
			::= { wanDialerEntry 4 }

--  1.3.6.1.4.1.6889.2.1.6.6.1.1.5
		-- 1.3.6.1.4.1.6889.2.1.6.2.5.1.1.5
		wanDialerPersistentReenable OBJECT-TYPE
			SYNTAX Integer32
			MAX-ACCESS read-write
			STATUS current
			DESCRIPTION
				"The time (in seconds) the dialer is disabled after it exhausts
				its consecutive dial attempts quota (wanDialerPersistentMaxAttempts).
				Zero means that the dialer is disabled until the dialing the current
				 dial trigger disappears."
			::= { wanDialerEntry 5 }

--  1.3.6.1.4.1.6889.2.1.6.6.1.1.6
		-- 1.3.6.1.4.1.6889.2.1.6.2.5.1.1.6
		wanDialerOrder OBJECT-TYPE
			SYNTAX INTEGER
				{
				sequential(1),
				roundRobin(2),
				lastSuccessful(3)
				}
			MAX-ACCESS read-write
			STATUS current
			DESCRIPTION
				"The dial strings list usage order where:
				sequential(1) : The dialer starts from the beginning of the list when there is
				 a new reason to dial (dial trigger.

				roundRobin(2): The dialer use the dialing string that is right after the
				 last one dialed.

				lastSuccessful(3) : If the previous dial attempt was successful, the dialer
				 starts with its dial strings."
			::= { wanDialerEntry 6 }

--  1.3.6.1.4.1.6889.2.1.6.6.1.1.7
		-- 1.3.6.1.4.1.6889.2.1.6.2.5.1.1.7
		wanDialerString1 OBJECT-TYPE
			SYNTAX DisplayString
			MAX-ACCESS read-write
			STATUS current
			DESCRIPTION
				"The 1st dial string in the list(NULL=unconfigured)"
			::= { wanDialerEntry 7 }

--  1.3.6.1.4.1.6889.2.1.6.6.1.1.8
		-- 1.3.6.1.4.1.6889.2.1.6.2.5.1.1.8
		wanDialerString2 OBJECT-TYPE
			SYNTAX DisplayString
			MAX-ACCESS read-write
			STATUS current
			DESCRIPTION
				"The 2nd dial string in the list(NULL=unconfigured)"
			::= { wanDialerEntry 8 }

--  1.3.6.1.4.1.6889.2.1.6.6.1.1.9
		-- 1.3.6.1.4.1.6889.2.1.6.2.5.1.1.9
		wanDialerString3 OBJECT-TYPE
			SYNTAX DisplayString
			MAX-ACCESS read-write
			STATUS current
			DESCRIPTION
				"The 3rd dial string in the list(NULL=unconfigured)"
			::= { wanDialerEntry 9 }

--  1.3.6.1.4.1.6889.2.1.6.6.1.1.10
		-- 1.3.6.1.4.1.6889.2.1.6.2.5.1.1.10
		wanDialerString4 OBJECT-TYPE
			SYNTAX DisplayString
			MAX-ACCESS read-write
			STATUS current
			DESCRIPTION
				"The 4th dial string in the list(NULL=unconfigured)"
			::= { wanDialerEntry 10 }

--  1.3.6.1.4.1.6889.2.1.6.6.1.1.11
		-- 1.3.6.1.4.1.6889.2.1.6.2.5.1.1.11
		wanDialerString5 OBJECT-TYPE
			SYNTAX DisplayString
			MAX-ACCESS read-write
			STATUS current
			DESCRIPTION
				"The 5th dial string in the list(NULL=unconfigured)"
			::= { wanDialerEntry 11 }

--  1.3.6.1.4.1.6889.2.1.6.6.1.1.12
		-- 1.3.6.1.4.1.6889.2.1.6.2.5.1.1.12
		wanDialerLastDialed OBJECT-TYPE
			SYNTAX DisplayString
			MAX-ACCESS read-only
			STATUS current
			DESCRIPTION
				"The last used display string"
			::= { wanDialerEntry 12 }

--  1.3.6.1.4.1.6889.2.1.6.6.1.1.13
		-- 1.3.6.1.4.1.6889.2.1.6.2.5.1.1.13
		wanDialerWaitForIpcp OBJECT-TYPE
			SYNTAX Integer32
			MAX-ACCESS read-write
			STATUS current
			DESCRIPTION
				"The maximum time (in seconds) the dialer waits from dialing until PPP/IPCP is up. "
			DEFVAL { 45 }
			::= { wanDialerEntry 13 }

--  1.3.6.1.4.1.6889.2.1.6.6.1.1.14
		-- 1.3.6.1.4.1.6889.2.1.6.2.5.1.1.14
		wanDialerPersistentInitial OBJECT-TYPE
			SYNTAX Integer32
			MAX-ACCESS read-write
			STATUS current
			DESCRIPTION
				"The minimum delay (in seconds) from boot to persitent dialing."
			DEFVAL { 10 }
			::= { wanDialerEntry 14 }

--  1.3.6.1.4.1.6889.2.1.6.4
		-- 1.3.6.1.4.1.6889.2.1.6.4
		avayaEISWanTraps OBJECT IDENTIFIER ::= { avayaEISWan 4 }

--  1.3.6.1.4.1.6889.2.1.6.5
		-- 1.3.6.1.4.1.6889.2.1.6.5
		avayaEISWanGroups OBJECT IDENTIFIER ::= { avayaEISWan 5 }

--  1.3.6.1.4.1.6889.2.1.6.5.1
		-- 1.3.6.1.4.1.6889.2.1.6.5.1
		hostModuleGroup OBJECT-GROUP
			OBJECTS { intWanGroupID, intWanPortID, intWanPortSpeed, intWanPortMode, intWanPortAutoNegotiation,
				intWanPortVLANMode, intWanPortVLANBindingMode, intWanPortVlanList }
			STATUS current
			DESCRIPTION
				"Mib objects for controlling the fabric port,
				connecting a LAN switch to its WAN router."
			::= { avayaEISWanGroups 1 }

--  1.3.6.1.4.1.6889.2.1.6.5.2
		-- 1.3.6.1.4.1.6889.2.1.6.5.2
		wanRouterBladeGroup OBJECT-GROUP
			OBJECTS { ds0BundleSpeedFactor, ifTableXtndIndex, ifTableXtndPeerAddress, ifTableXtndVoIPQueue, ifTableXtndCableLength,
				ifTableXtndGain, ifTableXtndDescription, ifTableXtndKeepAlive, ifTableXtndMtu, ifTableXtndInvertTxClock,
				ifTableXtndDTELoopback, ifTableXtndIgnoreDCD, ifTableXtndIdleChars, ifTableXtndBandwidth, ifTableXtndEncapsulation,
				frDlcmiXtndLMIAutoSense, frDlcmiXtndIndex, frSubIfDlcmiIndex, frSubIfSubIndex, frSubIfType,
				frSubIfStatus, frStaticCircuitDLCIrole, ifTableXtndPrimaryIf, ifTableXtndBackupDisableDelay, ifTableXtndBackupEnableDelay,
				ifTableXtndBackupIf, ifTableXtndBackupCapabilities, ds1DeviceMode, ds0BundleMemmbersList, ifTableXtndOperStatus,
				frStaticCircuitSubIfIndex, frStaticCircuitDLCI, frStaticCircuitStatus, ifTableXtndReliability, ifTableXtndOutputLoad,
				ifTableXtndInputLoad, ifTableXtndOutputRate, ifTableXtndInputRate, ifTableXtndLoadInterval, ifTableXtndDtrPulseTime,
				frMapClassRowStatus, frMapClassFrf12Frag, frMapClassCirOut, frMapClassBeOut, frMapClassBcOut,
				ifTableXtndFrTrafficShaping, frStaticCircuitMapClass, ifTableXtndDtrRestartDelay, ifTableXtndCarrierDelay }
			STATUS current
			DESCRIPTION
				"Mib object that belong to the WAN router."
			::= { avayaEISWanGroups 2 }

-- --------------------------------------------------------------------------------------------
-- 1.3.6.1.4.1.6889.2.1.6.7
		-- 1.3.6.1.4.1.6889.2.1.6.7
		avayaEISWanCompliances OBJECT IDENTIFIER ::= { avayaEISWan 7 }

--  1.3.6.1.4.1.6889.2.1.6.7.1
-- this module
		-- 1.3.6.1.4.1.6889.2.1.6.7.1
		hostModuleCompliance MODULE-COMPLIANCE
			STATUS current
			DESCRIPTION
				"The host module should only support the
				host module group."
			MODULE -- this module
				MANDATORY-GROUPS { hostModuleGroup }
			::= { avayaEISWanCompliances 1 }

--  1.3.6.1.4.1.6889.2.1.6.7.2
-- this module
		-- 1.3.6.1.4.1.6889.2.1.6.7.2
		wanRouterBladeCompliance MODULE-COMPLIANCE
			STATUS current
			DESCRIPTION
				"The wan router blade should support the wan
				router blade group."
			MODULE -- this module
				MANDATORY-GROUPS { wanRouterBladeGroup }
			::= { avayaEISWanCompliances 2 }


	END

--
-- WAN-MIB.my
--
