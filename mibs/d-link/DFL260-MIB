--
-- DFL-260 SMIv2 module
--

DFL260-MIB DEFINITIONS ::= BEGIN

IMPORTS
    MODULE-COMPLIANCE, OBJECT-GROUP
        FROM SNMPv2-CONF
    Counter32, Counter64, Gauge32, Integer32, MODULE-IDENTITY,
    OBJECT-TYPE, enterprises
        FROM SNMPv2-SMI
    DisplayString
        FROM SNMPv2-TC;

dfl260-MIB MODULE-IDENTITY
    LAST-UPDATED "201009021139Z"
    ORGANIZATION
        "D-Link Corporation"
    CONTACT-INFO
        "Postal: D-Link Corporation
         No. 289, Sinhu 3rd Road,
         Neihu District, Taipei City 114,
         Taiwan, R.O.C.
         Tel: +886-2-66000123
         Fax: +886-2-55509988"
    DESCRIPTION
        "The MIB module for D-Link DFL-260 series product."

    REVISION  "201009021139Z"
    DESCRIPTION
        "Added 64-bit counters"
    REVISION  "201003300900Z"
    DESCRIPTION
        "Added values for SMTP ALG objects."
    REVISION  "200911100916Z"
    DESCRIPTION
        "Added values for opened and closed connections per second"
    REVISION  "200811181605Z"
    DESCRIPTION
        "Added value for timer usage"
    REVISION  "200810141227Z"
    DESCRIPTION
        "Added values for memory usage and TCP buffer usage"
    REVISION  "200710310000Z"
    DESCRIPTION
        "Initial version."
    ::= { dfl260MibModules 2 }


dlink OBJECT IDENTIFIER
    ::= { enterprises 171 }

netdefendMgmt OBJECT IDENTIFIER
    ::= { dlink 20 }

utmFirewall OBJECT IDENTIFIER
    ::= { netdefendMgmt 2 }

dfl260 OBJECT IDENTIFIER
    ::= { utmFirewall 1 }

dfl260OS OBJECT IDENTIFIER
    ::= { dfl260 1 }

dfl260OSStats OBJECT IDENTIFIER
    ::= { dfl260OS 2 }

dfl260reg OBJECT IDENTIFIER
    ::= { dfl260 2 }

dfl260MibModules OBJECT IDENTIFIER
    ::= { dfl260reg 1 }

dfl260MibConfs OBJECT IDENTIFIER
    ::= { dfl260reg 2 }

dfl260MibObjectGroups OBJECT IDENTIFIER
    ::= { dfl260reg 3 }


dfl260System OBJECT IDENTIFIER
    ::= { dfl260OSStats 1 }

dfl260SysCpuLoad OBJECT-TYPE
    SYNTAX      Gauge32
    MAX-ACCESS  read-only
    STATUS      current
    DESCRIPTION
        "The system cpu load."
    ::= { dfl260System 1 }

dfl260SysForwardedBits OBJECT-TYPE
    SYNTAX      Counter32
    MAX-ACCESS  read-only
    STATUS      current
    DESCRIPTION
        "The number of bits forwarded through the gateway."
    ::= { dfl260System 2 }

dfl260SysForwardedPackets OBJECT-TYPE
    SYNTAX      Counter32
    MAX-ACCESS  read-only
    STATUS      current
    DESCRIPTION
        "Total number of forwarded packets."
    ::= { dfl260System 3 }

dfl260SysBuffUse OBJECT-TYPE
    SYNTAX      Gauge32
    MAX-ACCESS  read-only
    STATUS      current
    DESCRIPTION
        "The current number of buffers in use."
    ::= { dfl260System 4 }

dfl260SysConns OBJECT-TYPE
    SYNTAX      Gauge32
    MAX-ACCESS  read-only
    STATUS      current
    DESCRIPTION
        "The numer of connections."
    ::= { dfl260System 5 }

dfl260SysPerStateCounters OBJECT IDENTIFIER
    ::= { dfl260System 6 }

dfl260SysPscTcpSyn OBJECT-TYPE
    SYNTAX      Gauge32
    MAX-ACCESS  read-only
    STATUS      current
    DESCRIPTION
        "Number of TCP connections in the SYN state."
    ::= { dfl260SysPerStateCounters 1 }

dfl260SysPscTcpOpen OBJECT-TYPE
    SYNTAX      Gauge32
    MAX-ACCESS  read-only
    STATUS      current
    DESCRIPTION
        "Number of TCP connections in the OPEN state."
    ::= { dfl260SysPerStateCounters 2 }

dfl260SysPscTcpFin OBJECT-TYPE
    SYNTAX      Gauge32
    MAX-ACCESS  read-only
    STATUS      current
    DESCRIPTION
        "Number of TCP connections in the FIN state."
    ::= { dfl260SysPerStateCounters 3 }

dfl260SysPscUdp OBJECT-TYPE
    SYNTAX      Gauge32
    MAX-ACCESS  read-only
    STATUS      current
    DESCRIPTION
        "Number of UDP connections."
    ::= { dfl260SysPerStateCounters 4 }

dfl260SysPscIcmp OBJECT-TYPE
    SYNTAX      Gauge32
    MAX-ACCESS  read-only
    STATUS      current
    DESCRIPTION
        "Number of ICMP connections."
    ::= { dfl260SysPerStateCounters 5 }

dfl260SysPscOther OBJECT-TYPE
    SYNTAX      Gauge32
    MAX-ACCESS  read-only
    STATUS      current
    DESCRIPTION
        "Number of other connections."
    ::= { dfl260SysPerStateCounters 6 }

dfl260IfStatsTable OBJECT-TYPE
    SYNTAX      SEQUENCE OF Dfl260IfStatsEntry
    MAX-ACCESS  not-accessible
    STATUS      current
    DESCRIPTION
        "A table of DFL-260 specific interfaces statistics"
    ::= { dfl260System 7 }

dfl260IfStatsEntry OBJECT-TYPE
    SYNTAX      Dfl260IfStatsEntry
    MAX-ACCESS  not-accessible
    STATUS      current
    DESCRIPTION
        "The row in a table of DFL-260 specific interface statistics"
    INDEX       { dfl260IfStatsIndex }
    ::= { dfl260IfStatsTable 1 }

Dfl260IfStatsEntry ::= SEQUENCE {
    dfl260IfStatsIndex     Integer32,
    dfl260IfName           DisplayString,
    dfl260IfFragsIn        Counter32,
    dfl260IfFragReassOk    Counter32,
    dfl260IfFragReassFail  Counter32,
    dfl260IfPktsInCnt      Counter32,
    dfl260IfPktsOutCnt     Counter32,
    dfl260IfBitsInCnt      Counter32,
    dfl260IfBitsOutCnt     Counter32,
    dfl260IfPktsTotCnt     Counter32,
    dfl260IfBitsTotCnt     Counter32,
    dfl260IfHCPktsInCnt    Counter64,
    dfl260IfHCPktsOutCnt   Counter64,
    dfl260IfHCBitsInCnt    Counter64,
    dfl260IfHCBitsOutCnt   Counter64,
    dfl260IfHCPktsTotCnt   Counter64,
    dfl260IfHCBitsTotCnt   Counter64
}

dfl260IfStatsIndex OBJECT-TYPE
    SYNTAX      Integer32 (1..2147483647)
    MAX-ACCESS  not-accessible
    STATUS      current
    DESCRIPTION
        "Index of a row in dfl260SysIfStatsTable"
    ::= { dfl260IfStatsEntry 1 }

dfl260IfName OBJECT-TYPE
    SYNTAX      DisplayString
    MAX-ACCESS  read-only
    STATUS      current
    DESCRIPTION
        "The name of the interface."
    ::= { dfl260IfStatsEntry 2 }

dfl260IfFragsIn OBJECT-TYPE
    SYNTAX      Counter32
    MAX-ACCESS  read-only
    STATUS      current
    DESCRIPTION
        "Number of IP packet fragments received
         in the interface."
    ::= { dfl260IfStatsEntry 3 }

dfl260IfFragReassOk OBJECT-TYPE
    SYNTAX      Counter32
    MAX-ACCESS  read-only
    STATUS      current
    DESCRIPTION
        "Number of complete IP packets successfully
         reassembled from the fragments received in
         the interface."
    ::= { dfl260IfStatsEntry 4 }

dfl260IfFragReassFail OBJECT-TYPE
    SYNTAX      Counter32
    MAX-ACCESS  read-only
    STATUS      current
    DESCRIPTION
        "Number of packets that could not be reassembled,
         either due to resource starvation, illegal fragmentation,
         or just packet loss."
    ::= { dfl260IfStatsEntry 5 }

dfl260IfPktsInCnt OBJECT-TYPE
    SYNTAX      Counter32
    MAX-ACCESS  read-only
    STATUS      current
    DESCRIPTION
        "Number of packets received by the interface."
    ::= { dfl260IfStatsEntry 6 }

dfl260IfPktsOutCnt OBJECT-TYPE
    SYNTAX      Counter32
    MAX-ACCESS  read-only
    STATUS      current
    DESCRIPTION
        "Number of packets sent by the interface"
    ::= { dfl260IfStatsEntry 7 }

dfl260IfBitsInCnt OBJECT-TYPE
    SYNTAX      Counter32
    MAX-ACCESS  read-only
    STATUS      current
    DESCRIPTION
        "Number of bits received by the interface"
    ::= { dfl260IfStatsEntry 8 }

dfl260IfBitsOutCnt OBJECT-TYPE
    SYNTAX      Counter32
    MAX-ACCESS  read-only
    STATUS      current
    DESCRIPTION
        "Number of bits sent by the interface"
    ::= { dfl260IfStatsEntry 9 }

dfl260IfPktsTotCnt OBJECT-TYPE
    SYNTAX      Counter32
    MAX-ACCESS  read-only
    STATUS      current
    DESCRIPTION
        "Totat number of packets transmited by the interface"
    ::= { dfl260IfStatsEntry 10 }

dfl260IfBitsTotCnt OBJECT-TYPE
    SYNTAX      Counter32
    MAX-ACCESS  read-only
    STATUS      current
    DESCRIPTION
        "Totat number of bits transmited by the interface"
    ::= { dfl260IfStatsEntry 11 }

dfl260IfHCPktsInCnt OBJECT-TYPE
    SYNTAX      Counter64
    MAX-ACCESS  read-only
    STATUS      current
    DESCRIPTION
        "Number of packets received by the interface.
        This object is a 64-bit version of dfl260IfPktsInCnt."
    ::= { dfl260IfStatsEntry 12 }

dfl260IfHCPktsOutCnt OBJECT-TYPE
    SYNTAX      Counter64
    MAX-ACCESS  read-only
    STATUS      current
    DESCRIPTION
        "Number of packets sent by the interface.
        This object is a 64-bit version of dfl260IfPktsOutCnt."
    ::= { dfl260IfStatsEntry 13 }

dfl260IfHCBitsInCnt OBJECT-TYPE
    SYNTAX      Counter64
    MAX-ACCESS  read-only
    STATUS      current
    DESCRIPTION
        "Number of bits received by the interface.
        This object is a 64-bit version of dfl260IfBitsInCnt."
    ::= { dfl260IfStatsEntry 14 }

dfl260IfHCBitsOutCnt OBJECT-TYPE
    SYNTAX      Counter64
    MAX-ACCESS  read-only
    STATUS      current
    DESCRIPTION
        "Number of bits sent by the interface.
        This object is a 64-bit version of dfl260IfBitsOutCnt."
    ::= { dfl260IfStatsEntry 15 }

dfl260IfHCPktsTotCnt OBJECT-TYPE
    SYNTAX      Counter64
    MAX-ACCESS  read-only
    STATUS      current
    DESCRIPTION
        "Totat number of packets transmited by the interface.
        This object is a 64-bit version of dfl260IfPktsTotCnt."
    ::= { dfl260IfStatsEntry 16 }

dfl260IfHCBitsTotCnt OBJECT-TYPE
    SYNTAX      Counter64
    MAX-ACCESS  read-only
    STATUS      current
    DESCRIPTION
        "Totat number of bits transmited by the interface.
        This object is a 64-bit version of dfl260IfBitsTotCnt."
    ::= { dfl260IfStatsEntry 17 }

dfl260IfRxRingTable OBJECT-TYPE
    SYNTAX      SEQUENCE OF Dfl260IfRxRingEntry
    MAX-ACCESS  not-accessible
    STATUS      current
    DESCRIPTION
        "A table of DFL-260 specific interface Rx ring statistics"
    ::= { dfl260System 8 }

dfl260IfRxRingEntry OBJECT-TYPE
    SYNTAX      Dfl260IfRxRingEntry
    MAX-ACCESS  not-accessible
    STATUS      current
    DESCRIPTION
        "The row in a table of DFL-260 specific interface Rx ring
         statistics."
    INDEX       { dfl260IfRxRingIndex }
    ::= { dfl260IfRxRingTable 1 }

Dfl260IfRxRingEntry ::= SEQUENCE {
    dfl260IfRxRingIndex        Integer32,
    dfl260IfRxRingFifoErrors   Counter32,
    dfl260IfRxDespools         Gauge32,
    dfl260IfRxAvgUse           Gauge32,
    dfl260IfRxRingSaturation   Gauge32,
    dfl260RxRingFlooded        Gauge32
}

dfl260IfRxRingIndex OBJECT-TYPE
    SYNTAX      Integer32 (1..2147483647)
    MAX-ACCESS  not-accessible
    STATUS      current
    DESCRIPTION
        "Index of a row in dfl260IfRxRingTable."
    ::= { dfl260IfRxRingEntry 1 }

dfl260IfRxRingFifoErrors OBJECT-TYPE
    SYNTAX      Counter32
    MAX-ACCESS  read-only
    STATUS      current
    DESCRIPTION
        "Rx Ring number of FIFO errors."
    ::= { dfl260IfRxRingEntry 2 }

dfl260IfRxDespools OBJECT-TYPE
    SYNTAX      Gauge32
    MAX-ACCESS  read-only
    STATUS      current
    DESCRIPTION
        "Number of despool events per second."
    ::= { dfl260IfRxRingEntry 3 }

dfl260IfRxAvgUse OBJECT-TYPE
    SYNTAX      Gauge32
    MAX-ACCESS  read-only
    STATUS      current
    DESCRIPTION
        "Rx Ring average usage."
    ::= { dfl260IfRxRingEntry 4 }

dfl260IfRxRingSaturation OBJECT-TYPE
    SYNTAX      Gauge32
    MAX-ACCESS  read-only
    STATUS      current
    DESCRIPTION
        "Rx Ring sturation. Percentage of ring use per despool
         event when the ring has been more than half full."
    ::= { dfl260IfRxRingEntry 5 }

dfl260RxRingFlooded OBJECT-TYPE
    SYNTAX      Gauge32
    MAX-ACCESS  read-only
    STATUS      current
    DESCRIPTION
        "Rx Ring number of despool events for which
         the ring has been completely flooded"
    ::= { dfl260IfRxRingEntry 6 }

dfl260IfTxRingTable OBJECT-TYPE
    SYNTAX      SEQUENCE OF Dfl260IfTxRingEntry
    MAX-ACCESS  not-accessible
    STATUS      current
    DESCRIPTION
        "A table of DFL-260 specific interface Tx ring statistics"
    ::= { dfl260System 9 }

dfl260IfTxRingEntry OBJECT-TYPE
    SYNTAX      Dfl260IfTxRingEntry
    MAX-ACCESS  not-accessible
    STATUS      current
    DESCRIPTION
        "The row in a table of DFL-260 specific interface Tx ring
         statistics."
    INDEX       { dfl260IfTxRingIndex }
    ::= { dfl260IfTxRingTable 1 }

Dfl260IfTxRingEntry ::= SEQUENCE {
    dfl260IfTxRingIndex        Integer32,
    dfl260IfTxDespools         Gauge32,
    dfl260IfTxAvgUse           Gauge32,
    dfl260IfTxRingSaturation   Gauge32,
    dfl260RxTingFlooded        Gauge32
}

dfl260IfTxRingIndex OBJECT-TYPE
    SYNTAX      Integer32 (1..2147483647)
    MAX-ACCESS  not-accessible
    STATUS      current
    DESCRIPTION
        "Index of a row in dfl260IfRxRingTable."
    ::= { dfl260IfTxRingEntry 1 }

dfl260IfTxDespools OBJECT-TYPE
    SYNTAX      Gauge32
    MAX-ACCESS  read-only
    STATUS      current
    DESCRIPTION
        "Tx Ring number of despool event per second (polls when
         there is at least one buffer in the ring)"
    ::= { dfl260IfTxRingEntry 2 }

dfl260IfTxAvgUse OBJECT-TYPE
    SYNTAX      Gauge32
    MAX-ACCESS  read-only
    STATUS      current
    DESCRIPTION
        "Tx Ring number of despool events when the ring has
         been completely flooded"
    ::= { dfl260IfTxRingEntry 3 }

dfl260IfTxRingSaturation OBJECT-TYPE
    SYNTAX      Gauge32
    MAX-ACCESS  read-only
    STATUS      current
    DESCRIPTION
        "Tx Ring percentage of use per despool event when the
         ring has been more than half full."
    ::= { dfl260IfTxRingEntry 4 }

dfl260RxTingFlooded OBJECT-TYPE
    SYNTAX      Gauge32
    MAX-ACCESS  read-only
    STATUS      current
    DESCRIPTION
        "Tx Ring number of despool events for in which the ring has
         been completely flooded"
    ::= { dfl260IfTxRingEntry 5 }

dfl260IfVlanStatsTable OBJECT-TYPE
    SYNTAX      SEQUENCE OF Dfl260IfVlanStatsEntry
    MAX-ACCESS  not-accessible
    STATUS      current
    DESCRIPTION
        "A table of DFL-260 VLAN statistics"
    ::= { dfl260System 10 }

dfl260IfVlanStatsEntry OBJECT-TYPE
    SYNTAX      Dfl260IfVlanStatsEntry
    MAX-ACCESS  not-accessible
    STATUS      current
    DESCRIPTION
        "The row in a table of dfl260IfVlanStatsTable. Each has an index
         equal to the ifIndex of the corresponding physical interface"
    INDEX       { dfl260IfVlanIndex }
    ::= { dfl260IfVlanStatsTable 1 }

Dfl260IfVlanStatsEntry ::= SEQUENCE {
    dfl260IfVlanIndex              Integer32,
    dfl260IfVlanUntaggedInPkts     Counter32,
    dfl260IfVlanUntaggedOutPkts    Counter32,
    dfl260IfVlanUntaggedTotPkts    Counter32,
    dfl260IfVlanUntaggedInOctets   Counter32,
    dfl260IfVlanUntaggedOutOctets  Counter32,
    dfl260IfVlanUntaggedTotOctets  Counter32
}

dfl260IfVlanIndex OBJECT-TYPE
    SYNTAX      Integer32 (1..2147483647)
    MAX-ACCESS  not-accessible
    STATUS      current
    DESCRIPTION
        "Extended index of a row in dfl260IfVlanStatsTable."
    ::= { dfl260IfVlanStatsEntry 1 }

dfl260IfVlanUntaggedInPkts OBJECT-TYPE
    SYNTAX      Counter32
    MAX-ACCESS  read-only
    STATUS      current
    DESCRIPTION
        "Number of untaged packets untagged packets received by the interface."
    ::= { dfl260IfVlanStatsEntry 2 }

dfl260IfVlanUntaggedOutPkts OBJECT-TYPE
    SYNTAX      Counter32
    MAX-ACCESS  read-only
    STATUS      current
    DESCRIPTION
        "Number of untagged packets sent by the interface."
    ::= { dfl260IfVlanStatsEntry 3 }

dfl260IfVlanUntaggedTotPkts OBJECT-TYPE
    SYNTAX      Counter32
    MAX-ACCESS  read-only
    STATUS      current
    DESCRIPTION
        "Total number of untagged packets processed by the interface."
    ::= { dfl260IfVlanStatsEntry 4 }

dfl260IfVlanUntaggedInOctets OBJECT-TYPE
    SYNTAX      Counter32
    MAX-ACCESS  read-only
    STATUS      current
    DESCRIPTION
        "Total number of octects in untagged packets received by the interface."
    ::= { dfl260IfVlanStatsEntry 5 }

dfl260IfVlanUntaggedOutOctets OBJECT-TYPE
    SYNTAX      Counter32
    MAX-ACCESS  read-only
    STATUS      current
    DESCRIPTION
        "Total number of octects in untagged packets sent by the interface."
    ::= { dfl260IfVlanStatsEntry 6 }

dfl260IfVlanUntaggedTotOctets OBJECT-TYPE
    SYNTAX      Counter32
    MAX-ACCESS  read-only
    STATUS      current
    DESCRIPTION
        "Total number of octects in untagged packets processed by the
         interface."
    ::= { dfl260IfVlanStatsEntry 7 }

dfl260HWSensorTable OBJECT-TYPE
    SYNTAX      SEQUENCE OF Dfl260HWSensorEntry
    MAX-ACCESS  not-accessible
    STATUS      current
    DESCRIPTION
        "Table of hardware sensors."
    ::= { dfl260System 11 }

dfl260HWSensorEntry OBJECT-TYPE
    SYNTAX      Dfl260HWSensorEntry
    MAX-ACCESS  not-accessible
    STATUS      current
    DESCRIPTION
        "Entry  of table of hardware sensors."
    INDEX       { dfl260HWSensorIndex }
    ::= { dfl260HWSensorTable 1 }

Dfl260HWSensorEntry ::= SEQUENCE {
    dfl260HWSensorIndex    Integer32,
    dfl260HWSensorName     DisplayString,
    dfl260HWSensorValue    Gauge32,
    dfl260HWSensorUnit     DisplayString
}

dfl260HWSensorIndex OBJECT-TYPE
    SYNTAX      Integer32 (1..2147483647)
    MAX-ACCESS  not-accessible
    STATUS      current
    DESCRIPTION
        "Index of the entries of the sensor table."
    ::= { dfl260HWSensorEntry 1 }

dfl260HWSensorName OBJECT-TYPE
    SYNTAX      DisplayString
    MAX-ACCESS  read-only
    STATUS      current
    DESCRIPTION
        "The description of the sensor."
    ::= { dfl260HWSensorEntry 2 }

dfl260HWSensorValue OBJECT-TYPE
    SYNTAX      Gauge32
    MAX-ACCESS  read-only
    STATUS      current
    DESCRIPTION
        "The value of the sensor."
    ::= { dfl260HWSensorEntry 3 }

dfl260HWSensorUnit OBJECT-TYPE
    SYNTAX      DisplayString
    MAX-ACCESS  read-only
    STATUS      current
    DESCRIPTION
        "The description of the unit of the value mesured by sensor."
    ::= { dfl260HWSensorEntry 4 }

dfl260SysMemUsage OBJECT-TYPE
    SYNTAX      Gauge32
    MAX-ACCESS  read-only
    STATUS      current
    DESCRIPTION
        "The current memory usage."
    ::= { dfl260System 12 }

dfl260SysTCPUsage OBJECT IDENTIFIER
    ::= { dfl260System 13 }

dfl260SysTCPRecvSmall OBJECT-TYPE
    SYNTAX      Gauge32
    MAX-ACCESS  read-only
    STATUS      current
    DESCRIPTION
        "Small TCP receive windows usage."
    ::= { dfl260SysTCPUsage 1 }

dfl260SysTCPRecvLarge OBJECT-TYPE
    SYNTAX      Gauge32
    MAX-ACCESS  read-only
    STATUS      current
    DESCRIPTION
        "Large TCP receive windows usage."
    ::= { dfl260SysTCPUsage 2 }

dfl260SysTCPSendSmall OBJECT-TYPE
    SYNTAX      Gauge32
    MAX-ACCESS  read-only
    STATUS      current
    DESCRIPTION
        "Small TCP send windows usage."
    ::= { dfl260SysTCPUsage 3 }

dfl260SysTCPSendLarge OBJECT-TYPE
    SYNTAX      Gauge32
    MAX-ACCESS  read-only
    STATUS      current
    DESCRIPTION
        "Large TCP send windows usage."
    ::= { dfl260SysTCPUsage 4 }

dfl260SysTimerUsage OBJECT-TYPE
    SYNTAX      Gauge32
    MAX-ACCESS  read-only
    STATUS      current
    DESCRIPTION
        "The current number of timers in use."
    ::= { dfl260System 14 }

dfl260SysConnOPS OBJECT-TYPE
    SYNTAX      Gauge32
    MAX-ACCESS  read-only
    STATUS      current
    DESCRIPTION
        "The number of connections opened per second."
    ::= { dfl260System 15 }

dfl260SysConnCPS OBJECT-TYPE
    SYNTAX      Gauge32
    MAX-ACCESS  read-only
    STATUS      current
    DESCRIPTION
        "The number of connections closed per second."
    ::= { dfl260System 16 }

dfl260SysHCForwardedBits OBJECT-TYPE
    SYNTAX      Counter64
    MAX-ACCESS  read-only
    STATUS      current
    DESCRIPTION
        "The number of bits forwarded through the gateway."
    ::= { dfl260System 17 }

dfl260VPN OBJECT IDENTIFIER
    ::= { dfl260OSStats 2 }

dfl260IPsec OBJECT IDENTIFIER
    ::= { dfl260VPN 1 }

dfl260IPsecGlobal OBJECT IDENTIFIER
    ::= { dfl260IPsec 1 }

dfl260IPsecPhaseOneActive OBJECT-TYPE
    SYNTAX      Gauge32
    MAX-ACCESS  read-only
    STATUS      current
    DESCRIPTION
        "Number of Phase-1 active negotiations"
    ::= { dfl260IPsecGlobal 1 }

dfl260IPsecPhaseOneAggrModeDone OBJECT-TYPE
    SYNTAX      Gauge32
    MAX-ACCESS  read-only
    STATUS      current
    DESCRIPTION
        "Number of Phase-1 aggressive mode negotiations."
    ::= { dfl260IPsecGlobal 2 }

dfl260IPsecQuickModeActive OBJECT-TYPE
    SYNTAX      Gauge32
    MAX-ACCESS  read-only
    STATUS      current
    DESCRIPTION
        "Number of quick mode active negotiations."
    ::= { dfl260IPsecGlobal 3 }

dfl260IPsecPhaseOneDone OBJECT-TYPE
    SYNTAX      Counter32
    MAX-ACCESS  read-only
    STATUS      current
    DESCRIPTION
        "Number of Phase-1 negotiations done."
    ::= { dfl260IPsecGlobal 4 }

dfl260IPsecPhaseOneFailed OBJECT-TYPE
    SYNTAX      Counter32
    MAX-ACCESS  read-only
    STATUS      current
    DESCRIPTION
        "Number of Phase-1 negotiations failed."
    ::= { dfl260IPsecGlobal 5 }

dfl260IPsecPhaseOneRekeyed OBJECT-TYPE
    SYNTAX      Counter32
    MAX-ACCESS  read-only
    STATUS      current
    DESCRIPTION
        "Number of Phase-1 negotiations rekeyed."
    ::= { dfl260IPsecGlobal 6 }

dfl260IPsecQuickModeDone OBJECT-TYPE
    SYNTAX      Counter32
    MAX-ACCESS  read-only
    STATUS      current
    DESCRIPTION
        "Number of quick mode  negotiations done."
    ::= { dfl260IPsecGlobal 7 }

dfl260IPsecQuickModeFailed OBJECT-TYPE
    SYNTAX      Counter32
    MAX-ACCESS  read-only
    STATUS      current
    DESCRIPTION
        "Number of quick mode negotiations failed."
    ::= { dfl260IPsecGlobal 8 }

dfl260IPsecInfoDone OBJECT-TYPE
    SYNTAX      Counter32
    MAX-ACCESS  read-only
    STATUS      current
    DESCRIPTION
        "Number of informational exchanges done.
         (Not available in IKEv1 implementations)"
    ::= { dfl260IPsecGlobal 9 }

dfl260IPsecInfoFailed OBJECT-TYPE
    SYNTAX      Counter32
    MAX-ACCESS  read-only
    STATUS      current
    DESCRIPTION
        "Number of informational exchanges failed.
         (Not available in IKEv1 implementations)"
    ::= { dfl260IPsecGlobal 10 }

dfl260IPsecInOctetsComp OBJECT-TYPE
    SYNTAX      Counter64
    MAX-ACCESS  read-only
    STATUS      current
    DESCRIPTION
        "Total octets in before decompression."
    ::= { dfl260IPsecGlobal 11 }

dfl260IPsecInOctetsUncomp OBJECT-TYPE
    SYNTAX      Counter64
    MAX-ACCESS  read-only
    STATUS      current
    DESCRIPTION
        "Total octets in after decompression."
    ::= { dfl260IPsecGlobal 12 }

dfl260IPsecOutOctetsComp OBJECT-TYPE
    SYNTAX      Counter64
    MAX-ACCESS  read-only
    STATUS      current
    DESCRIPTION
        "Total octets out after compression."
    ::= { dfl260IPsecGlobal 13 }

dfl260IPsecOutOctetsUncomp OBJECT-TYPE
    SYNTAX      Counter64
    MAX-ACCESS  read-only
    STATUS      current
    DESCRIPTION
        "Total octets out before compression."
    ::= { dfl260IPsecGlobal 14 }

dfl260IPsecForwardedOctetsComp OBJECT-TYPE
    SYNTAX      Counter64
    MAX-ACCESS  read-only
    STATUS      current
    DESCRIPTION
        "Total octets forwarded after compression."
    ::= { dfl260IPsecGlobal 15 }

dfl260IPsecForwardedOctetsUcomp OBJECT-TYPE
    SYNTAX      Counter64
    MAX-ACCESS  read-only
    STATUS      current
    DESCRIPTION
        "Total octets forwarded before compression."
    ::= { dfl260IPsecGlobal 16 }

dfl260IPsecInPackets OBJECT-TYPE
    SYNTAX      Counter64
    MAX-ACCESS  read-only
    STATUS      current
    DESCRIPTION
        "Total packets in."
    ::= { dfl260IPsecGlobal 17 }

dfl260IPsecOutPackets OBJECT-TYPE
    SYNTAX      Counter64
    MAX-ACCESS  read-only
    STATUS      current
    DESCRIPTION
        "Total packets Out."
    ::= { dfl260IPsecGlobal 18 }

dfl260IPsecForwardedPackets OBJECT-TYPE
    SYNTAX      Counter64
    MAX-ACCESS  read-only
    STATUS      current
    DESCRIPTION
        "Total packets forwarded."
    ::= { dfl260IPsecGlobal 19 }

dfl260IPsecActiveTransforms OBJECT-TYPE
    SYNTAX      Gauge32
    MAX-ACCESS  read-only
    STATUS      current
    DESCRIPTION
        "Number of currently active transforms."
    ::= { dfl260IPsecGlobal 20 }

dfl260IPsecTotalTransforms OBJECT-TYPE
    SYNTAX      Counter32
    MAX-ACCESS  read-only
    STATUS      current
    DESCRIPTION
        "Total number of transform records created."
    ::= { dfl260IPsecGlobal 21 }

dfl260IPsecOutOfTransforms OBJECT-TYPE
    SYNTAX      Counter32
    MAX-ACCESS  read-only
    STATUS      current
    DESCRIPTION
        "Number of packets dropped due to no available transform object.
         (Not available in IKEv1 implementations)"
    ::= { dfl260IPsecGlobal 22 }

dfl260IPsecTotalRekeys OBJECT-TYPE
    SYNTAX      Counter32
    MAX-ACCESS  read-only
    STATUS      current
    DESCRIPTION
        "Total number of rekeys performed."
    ::= { dfl260IPsecGlobal 23 }

dfl260Rules OBJECT IDENTIFIER
    ::= { dfl260OSStats 3 }

dfl260RuleUseTable OBJECT-TYPE
    SYNTAX      SEQUENCE OF Dfl260RuleUseEntry
    MAX-ACCESS  not-accessible
    STATUS      current
    DESCRIPTION
        "A list of general rules usage statistics."
    ::= { dfl260Rules 2 }

dfl260RuleUseEntry OBJECT-TYPE
    SYNTAX      Dfl260RuleUseEntry
    MAX-ACCESS  not-accessible
    STATUS      current
    DESCRIPTION
        "The statistics over a rule usage."
    INDEX       { dfl260RuleIndex }
    ::= { dfl260RuleUseTable 1 }

Dfl260RuleUseEntry ::= SEQUENCE {
    dfl260RuleIndex    Integer32,
    dfl260RuleName     DisplayString,
    dfl260RuleUse      Counter32
}

dfl260RuleIndex OBJECT-TYPE
    SYNTAX      Integer32 (1..2147483647)
    MAX-ACCESS  not-accessible
    STATUS      current
    DESCRIPTION
        "The rule usage index."
    ::= { dfl260RuleUseEntry 1 }

dfl260RuleName OBJECT-TYPE
    SYNTAX      DisplayString
    MAX-ACCESS  read-only
    STATUS      current
    DESCRIPTION
        "The name of the rule."
    ::= { dfl260RuleUseEntry 2 }

dfl260RuleUse OBJECT-TYPE
    SYNTAX      Counter32
    MAX-ACCESS  read-only
    STATUS      current
    DESCRIPTION
        "The number of times o rule was used."
    ::= { dfl260RuleUseEntry 3 }

dfl260IPPools OBJECT IDENTIFIER
    ::= { dfl260OSStats 4 }

dfl260IPPoolsNumber OBJECT-TYPE
    SYNTAX      Integer32
    MAX-ACCESS  read-only
    STATUS      current
    DESCRIPTION
        "The number of ip pools"
    ::= { dfl260IPPools 1 }

dfl260IPPoolTable OBJECT-TYPE
    SYNTAX      SEQUENCE OF Dfl260IPPoolEntry
    MAX-ACCESS  not-accessible
    STATUS      current
    DESCRIPTION
        "A list of IP pools"
    ::= { dfl260IPPools 2 }

dfl260IPPoolEntry OBJECT-TYPE
    SYNTAX      Dfl260IPPoolEntry
    MAX-ACCESS  not-accessible
    STATUS      current
    DESCRIPTION
        "The attributes of an ip pool"
    INDEX       { dfl260IPPoolIndex }
    ::= { dfl260IPPoolTable 1 }

Dfl260IPPoolEntry ::= SEQUENCE {
    dfl260IPPoolIndex          Integer32,
    dfl260IPPoolName           DisplayString,
    dfl260IPPoolPrepare        Gauge32,
    dfl260IPPoolFree           Gauge32,
    dfl260IPPoolMisses         Gauge32,
    dfl260IPPoolClientFails    Gauge32,
    dfl260IPPoolUsed           Gauge32
}

dfl260IPPoolIndex OBJECT-TYPE
    SYNTAX      Integer32 (1..2147483647)
    MAX-ACCESS  not-accessible
    STATUS      current
    DESCRIPTION
        "The ip pool index"
    ::= { dfl260IPPoolEntry 1 }

dfl260IPPoolName OBJECT-TYPE
    SYNTAX      DisplayString
    MAX-ACCESS  read-only
    STATUS      current
    DESCRIPTION
        "The ip pool name"
    ::= { dfl260IPPoolEntry 2 }

dfl260IPPoolPrepare OBJECT-TYPE
    SYNTAX      Gauge32
    MAX-ACCESS  read-only
    STATUS      current
    DESCRIPTION
        "Number of IP pool objects in prepare mode."
    ::= { dfl260IPPoolEntry 3 }

dfl260IPPoolFree OBJECT-TYPE
    SYNTAX      Gauge32
    MAX-ACCESS  read-only
    STATUS      current
    DESCRIPTION
        "Number of available IPs in the pool."
    ::= { dfl260IPPoolEntry 4 }

dfl260IPPoolMisses OBJECT-TYPE
    SYNTAX      Gauge32
    MAX-ACCESS  read-only
    STATUS      current
    DESCRIPTION
        "Mumber of missed IP pool negotiations for other reasons
         than lack of available IP numbers."
    ::= { dfl260IPPoolEntry 5 }

dfl260IPPoolClientFails OBJECT-TYPE
    SYNTAX      Gauge32
    MAX-ACCESS  read-only
    STATUS      current
    DESCRIPTION
        "Number of failed IP pool transactions."
    ::= { dfl260IPPoolEntry 6 }

dfl260IPPoolUsed OBJECT-TYPE
    SYNTAX      Gauge32
    MAX-ACCESS  read-only
    STATUS      current
    DESCRIPTION
        "Number of IP numbers in use from the pool."
    ::= { dfl260IPPoolEntry 7 }

dfl260DHCPServer OBJECT IDENTIFIER
    ::= { dfl260OSStats 5 }

dfl260DHCPTotalRejected OBJECT-TYPE
    SYNTAX      Gauge32
    MAX-ACCESS  read-only
    STATUS      current
    DESCRIPTION
        "Total number of rejected packets (all rules)."
    ::= { dfl260DHCPServer 1 }

dfl260DHCPRuleTable OBJECT-TYPE
    SYNTAX      SEQUENCE OF Dfl260DHCPRuleEntry
    MAX-ACCESS  not-accessible
    STATUS      current
    DESCRIPTION
        "A list of all DHCP server rules usage statistics."
    ::= { dfl260DHCPServer 2 }

dfl260DHCPRuleEntry OBJECT-TYPE
    SYNTAX      Dfl260DHCPRuleEntry
    MAX-ACCESS  not-accessible
    STATUS      current
    DESCRIPTION
        "The attributes of a DHCP server rule statistics."
    INDEX       { dfl260DHCPRuleIndex }
    ::= { dfl260DHCPRuleTable 1 }

Dfl260DHCPRuleEntry ::= SEQUENCE {
    dfl260DHCPRuleIndex                Integer32,
    dfl260DHCPRuleName                 DisplayString,
    dfl260DHCPRuleUsage                Gauge32,
    dfl260DHCPRuleUsagePercent         Gauge32,
    dfl260DHCPActiveClients            Gauge32,
    dfl260DHCPActiveClientsPercent     Gauge32,
    dfl260DHCPRejectedRequests         Gauge32,
    dfl260DHCPTotalLeases              Gauge32
}

dfl260DHCPRuleIndex OBJECT-TYPE
    SYNTAX      Integer32 (1..2147483647)
    MAX-ACCESS  not-accessible
    STATUS      current
    DESCRIPTION
        "The DHCP server rule  index"
    ::= { dfl260DHCPRuleEntry 1 }

dfl260DHCPRuleName OBJECT-TYPE
    SYNTAX      DisplayString
    MAX-ACCESS  read-only
    STATUS      current
    DESCRIPTION
        "The DHCP server rule name."
    ::= { dfl260DHCPRuleEntry 2 }

dfl260DHCPRuleUsage OBJECT-TYPE
    SYNTAX      Gauge32
    MAX-ACCESS  read-only
    STATUS      current
    DESCRIPTION
        "Number of used IPs in the pool."
    ::= { dfl260DHCPRuleEntry 3 }

dfl260DHCPRuleUsagePercent OBJECT-TYPE
    SYNTAX      Gauge32
    MAX-ACCESS  read-only
    STATUS      current
    DESCRIPTION
        "The percentage of the used IPs in
         relation to the IP pool size."
    ::= { dfl260DHCPRuleEntry 4 }

dfl260DHCPActiveClients OBJECT-TYPE
    SYNTAX      Gauge32
    MAX-ACCESS  read-only
    STATUS      current
    DESCRIPTION
        "Number of currently active clients."
    ::= { dfl260DHCPRuleEntry 5 }

dfl260DHCPActiveClientsPercent OBJECT-TYPE
    SYNTAX      Gauge32
    MAX-ACCESS  read-only
    STATUS      current
    DESCRIPTION
        "The number of currently active clients
         as a percentage of the pool size."
    ::= { dfl260DHCPRuleEntry 6 }

dfl260DHCPRejectedRequests OBJECT-TYPE
    SYNTAX      Gauge32
    MAX-ACCESS  read-only
    STATUS      current
    DESCRIPTION
        "Number of rejected requests matching
         the current rule."
    ::= { dfl260DHCPRuleEntry 7 }

dfl260DHCPTotalLeases OBJECT-TYPE
    SYNTAX      Gauge32
    MAX-ACCESS  read-only
    STATUS      current
    DESCRIPTION
        "Total number of leases in the pool."
    ::= { dfl260DHCPRuleEntry 8 }

dfl260UserAuth OBJECT IDENTIFIER
    ::= { dfl260OSStats 6 }

dfl260UserAuthHTTPUsers OBJECT-TYPE
    SYNTAX      Gauge32
    MAX-ACCESS  read-only
    STATUS      current
    DESCRIPTION
        "Number of currently  logged in HTTP users."
    ::= { dfl260UserAuth 1 }

dfl260UserAuthXAUTHUsers OBJECT-TYPE
    SYNTAX      Gauge32
    MAX-ACCESS  read-only
    STATUS      current
    DESCRIPTION
        "Number of currently logged in XAUTH users."
    ::= { dfl260UserAuth 2 }

dfl260UserAuthHTTPSUsers OBJECT-TYPE
    SYNTAX      Gauge32
    MAX-ACCESS  read-only
    STATUS      current
    DESCRIPTION
        "Number of currently logged in HTTPS users."
    ::= { dfl260UserAuth 3 }

dfl260UserAuthPPPUsers OBJECT-TYPE
    SYNTAX      Gauge32
    MAX-ACCESS  read-only
    STATUS      current
    DESCRIPTION
        "Number of currently logged in PPP users."
    ::= { dfl260UserAuth 4 }

dfl260UserAuthEAPUsers OBJECT-TYPE
    SYNTAX      Gauge32
    MAX-ACCESS  read-only
    STATUS      current
    DESCRIPTION
        "Number of currently logged in EAP users."
    ::= { dfl260UserAuth 5 }

dfl260UserAuthRuleUseTable OBJECT-TYPE
    SYNTAX      SEQUENCE OF Dfl260UserAuthRuleUseEntry
    MAX-ACCESS  not-accessible
    STATUS      current
    DESCRIPTION
        "Table of user authentication rule usage."
    ::= { dfl260UserAuth 6 }

dfl260UserAuthRuleUseEntry OBJECT-TYPE
    SYNTAX      Dfl260UserAuthRuleUseEntry
    MAX-ACCESS  not-accessible
    STATUS      current
    DESCRIPTION
        "The attributes of an authentication rule
         usage statistics."
    INDEX       { dfl260UserAuthRuleIndex }
    ::= { dfl260UserAuthRuleUseTable 1 }

Dfl260UserAuthRuleUseEntry ::= SEQUENCE {
    dfl260UserAuthRuleIndex    Integer32,
    dfl260UserAuthRuleName     DisplayString,
    dfl260UserAuthRuleUse      Counter32
}

dfl260UserAuthRuleIndex OBJECT-TYPE
    SYNTAX      Integer32 (1..2147483647)
    MAX-ACCESS  not-accessible
    STATUS      current
    DESCRIPTION
        "The rule usage index."
    ::= { dfl260UserAuthRuleUseEntry 1 }

dfl260UserAuthRuleName OBJECT-TYPE
    SYNTAX      DisplayString
    MAX-ACCESS  read-only
    STATUS      current
    DESCRIPTION
        "The name of the rule."
    ::= { dfl260UserAuthRuleUseEntry 2 }

dfl260UserAuthRuleUse OBJECT-TYPE
    SYNTAX      Counter32
    MAX-ACCESS  read-only
    STATUS      current
    DESCRIPTION
        "The number of times o rule was used."
    ::= { dfl260UserAuthRuleUseEntry 3 }

dfl260LinkMonitor OBJECT IDENTIFIER
    ::= { dfl260OSStats 7 }

dfl260LinkMonGrp OBJECT-TYPE
    SYNTAX      Integer32
    MAX-ACCESS  read-only
    STATUS      current
    DESCRIPTION
        "The number of groups of monitored links"
    ::= { dfl260LinkMonitor 1 }

dfl260LinkMonGrpTable OBJECT-TYPE
    SYNTAX      SEQUENCE OF Dfl260LinkMonGrpEntry
    MAX-ACCESS  not-accessible
    STATUS      current
    DESCRIPTION
        "Table of link monitor groups."
    ::= { dfl260LinkMonitor 2 }

dfl260LinkMonGrpEntry OBJECT-TYPE
    SYNTAX      Dfl260LinkMonGrpEntry
    MAX-ACCESS  not-accessible
    STATUS      current
    DESCRIPTION
        "The attributes of a link monitor group"
    INDEX       { dfl260LinkMonGrpIndex }
    ::= { dfl260LinkMonGrpTable 1 }

Dfl260LinkMonGrpEntry ::= SEQUENCE {
    dfl260LinkMonGrpIndex      Integer32,
    dfl260LinkMonGrpName       DisplayString,
    dfl260LinkMonGrpHostsUp    Gauge32
}

dfl260LinkMonGrpIndex OBJECT-TYPE
    SYNTAX      Integer32 (1..2147483647)
    MAX-ACCESS  not-accessible
    STATUS      current
    DESCRIPTION
        "The index row in the table of link monitor groups."
    ::= { dfl260LinkMonGrpEntry 1 }

dfl260LinkMonGrpName OBJECT-TYPE
    SYNTAX      DisplayString
    MAX-ACCESS  read-only
    STATUS      current
    DESCRIPTION
        "The link monitor group name."
    ::= { dfl260LinkMonGrpEntry 2 }

dfl260LinkMonGrpHostsUp OBJECT-TYPE
    SYNTAX      Gauge32
    MAX-ACCESS  read-only
    STATUS      current
    DESCRIPTION
        "The percentage of monitored hosts available."
    ::= { dfl260LinkMonGrpEntry 3 }

dfl260LinkMonHostTable OBJECT-TYPE
    SYNTAX      SEQUENCE OF Dfl260LinkMonHostEntry
    MAX-ACCESS  not-accessible
    STATUS      current
    DESCRIPTION
        "Table of link monitored hosts in a link monnitor group."
    ::= { dfl260LinkMonitor 3 }

dfl260LinkMonHostEntry OBJECT-TYPE
    SYNTAX      Dfl260LinkMonHostEntry
    MAX-ACCESS  not-accessible
    STATUS      current
    DESCRIPTION
        "The attributes of a monitored host."
    INDEX       { dfl260LinkMonGrpIndex, dfl260LinkMonHostIndex }
    ::= { dfl260LinkMonHostTable 1 }

Dfl260LinkMonHostEntry ::= SEQUENCE {
    dfl260LinkMonHostIndex             Integer32,
    dfl260LinkMonHostId                DisplayString,
    dfl260LinkMonHostShortTermLoss     Gauge32,
    dfl260LinkMonHostPacketsLost       Counter32
}

dfl260LinkMonHostIndex OBJECT-TYPE
    SYNTAX      Integer32 (1..2147483647)
    MAX-ACCESS  not-accessible
    STATUS      current
    DESCRIPTION
        "The index an host in the table of link monitor hosts."
    ::= { dfl260LinkMonHostEntry 1 }

dfl260LinkMonHostId OBJECT-TYPE
    SYNTAX      DisplayString
    MAX-ACCESS  read-only
    STATUS      current
    DESCRIPTION
        "The monitored host identifier."
    ::= { dfl260LinkMonHostEntry 2 }

dfl260LinkMonHostShortTermLoss OBJECT-TYPE
    SYNTAX      Gauge32
    MAX-ACCESS  read-only
    STATUS      current
    DESCRIPTION
        "The percentage of short term losst packets."
    ::= { dfl260LinkMonHostEntry 3 }

dfl260LinkMonHostPacketsLost OBJECT-TYPE
    SYNTAX      Counter32
    MAX-ACCESS  read-only
    STATUS      current
    DESCRIPTION
        "Total number of lost monitoring packets."
    ::= { dfl260LinkMonHostEntry 4 }

dfl260Pipes OBJECT IDENTIFIER
    ::= { dfl260OSStats 8 }

dfl260PipeUsers OBJECT-TYPE
    SYNTAX      Gauge32
    MAX-ACCESS  read-only
    STATUS      current
    DESCRIPTION
        "The current number of users, as defined by the grouping
         settings of each pipe, being tracked in the pipes system.
         Note that this value corresponds to the number of users
         active in each time slice of 1/20th of a second, and not
         to the number of users having open connections."
    ::= { dfl260Pipes 1 }

dfl260PipeTable OBJECT-TYPE
    SYNTAX      SEQUENCE OF Dfl260PipeEntry
    MAX-ACCESS  not-accessible
    STATUS      current
    DESCRIPTION
        "Table of pipes"
    ::= { dfl260Pipes 2 }

dfl260PipeEntry OBJECT-TYPE
    SYNTAX      Dfl260PipeEntry
    MAX-ACCESS  not-accessible
    STATUS      current
    DESCRIPTION
        "A entry of the pipes table"
    INDEX       { dfl260PipeIndex }
    ::= { dfl260PipeTable 1 }

Dfl260PipeEntry ::= SEQUENCE {
    dfl260PipeIndex            Integer32,
    dfl260PipeName             DisplayString,
    dfl260PipeMinPrec          Integer32,
    dfl260PipeMaxPrec          Integer32,
    dfl260PipeDefPrec          Integer32,
    dfl260PipeNumPrec          Integer32,
    dfl260PipeNumUsers         Gauge32,
    dfl260PipeCurrentBps       Gauge32,
    dfl260PipeCurrentPps       Gauge32,
    dfl260PipeDelayedPackets   Counter32,
    dfl260PipeDropedPackets    Counter32
}

dfl260PipeIndex OBJECT-TYPE
    SYNTAX      Integer32 (1..2147483647)
    MAX-ACCESS  not-accessible
    STATUS      current
    DESCRIPTION
        "The pipe index"
    ::= { dfl260PipeEntry 1 }

dfl260PipeName OBJECT-TYPE
    SYNTAX      DisplayString
    MAX-ACCESS  read-only
    STATUS      current
    DESCRIPTION
        "The name of the pipe"
    ::= { dfl260PipeEntry 2 }

dfl260PipeMinPrec OBJECT-TYPE
    SYNTAX      Integer32
    MAX-ACCESS  read-only
    STATUS      current
    DESCRIPTION
        "The minimum of the range of pipe precedences."
    ::= { dfl260PipeEntry 3 }

dfl260PipeMaxPrec OBJECT-TYPE
    SYNTAX      Integer32
    MAX-ACCESS  read-only
    STATUS      current
    DESCRIPTION
        "The maximum of the range of pipe precedences."
    ::= { dfl260PipeEntry 4 }

dfl260PipeDefPrec OBJECT-TYPE
    SYNTAX      Integer32
    MAX-ACCESS  read-only
    STATUS      current
    DESCRIPTION
        "The precedence assigned to a packet for which has not one
         allready done by a Pipe Rule."
    ::= { dfl260PipeEntry 5 }

dfl260PipeNumPrec OBJECT-TYPE
    SYNTAX      Integer32
    MAX-ACCESS  read-only
    STATUS      current
    DESCRIPTION
        "The number of pipe precedences"
    ::= { dfl260PipeEntry 6 }

dfl260PipeNumUsers OBJECT-TYPE
    SYNTAX      Gauge32
    MAX-ACCESS  read-only
    STATUS      current
    DESCRIPTION
        "The current number of users, as defined by the grouping settings
         of each pipe, being tracked in the pipes system. This value
         corresponds to the number of users active in each time slice
         and not to the number of users having  open connections."
    ::= { dfl260PipeEntry 7 }

dfl260PipeCurrentBps OBJECT-TYPE
    SYNTAX      Gauge32
    MAX-ACCESS  read-only
    STATUS      current
    DESCRIPTION
        "The current throughput of a pipe, in bits per second, as a sum of
         the corresponding values for all precedences."
    ::= { dfl260PipeEntry 8 }

dfl260PipeCurrentPps OBJECT-TYPE
    SYNTAX      Gauge32
    MAX-ACCESS  read-only
    STATUS      current
    DESCRIPTION
        "The current throughput of a pipe, in packets per second, as a sum of
         the corresponding values for all precedences."
    ::= { dfl260PipeEntry 9 }

dfl260PipeDelayedPackets OBJECT-TYPE
    SYNTAX      Counter32
    MAX-ACCESS  read-only
    STATUS      current
    DESCRIPTION
        "The number of times packets have been delayed as a result of a pipe,
         or pipe user having used up its allotted bandwidth. Note that one single
         packet may be delayed several times; if a pipe is really full, this
         count may exceed the number of packets actually passing through the
         pipe."
    ::= { dfl260PipeEntry 10 }

dfl260PipeDropedPackets OBJECT-TYPE
    SYNTAX      Counter32
    MAX-ACCESS  read-only
    STATUS      current
    DESCRIPTION
        "The number of packets dropped by a pipe. Packets are dropped when
         CorePlus is running out of packet buffers. This occurs when excessive
         amounts of packets need to be queued for later delivery. The packet
         dropped is always the one that has been queued the longest time
         globally, which means that the connection suffering from packet loss
         will be the one most overloading the system."
    ::= { dfl260PipeEntry 11 }

dfl260PipePrecTable OBJECT-TYPE
    SYNTAX      SEQUENCE OF Dfl260PipePrecEntry
    MAX-ACCESS  not-accessible
    STATUS      current
    DESCRIPTION
        "There is a one to many relation between a pipe and its precedences.
         The number of precedences is a instance attribute of each pipe.
         This table extends the pipes table in order to express the relation
         between a pipe and the respective precedences."
    ::= { dfl260Pipes 3 }

dfl260PipePrecEntry OBJECT-TYPE
    SYNTAX      Dfl260PipePrecEntry
    MAX-ACCESS  not-accessible
    STATUS      current
    DESCRIPTION
        "An entry of the table of pipe pecedences. These table entries
         are chracterized by been indexed by two values. The first index
         the same as the pipe index of the corresponding row in table of
         pipes and the second index is the index of the set of precedences
         of the corresponding pipe."
    INDEX       { dfl260PipeIndex, dfl260PipePrecIndex }
    ::= { dfl260PipePrecTable 1 }

Dfl260PipePrecEntry ::= SEQUENCE {
    dfl260PipePrecIndex            Integer32,
    dfl260PipePrec                 Integer32,
    dfl260PipePrecBps              Gauge32,
    dfl260PipePrecTotalPps         Gauge32,
    dfl260PipePrecReservedBps      Gauge32,
    dfl260PipePrecDynLimBps        Gauge32,
    dfl260PipePrecDynUsrLimBps     Gauge32,
    dfl260PipePrecDelayedPackets   Counter32,
    dfl260PipePrecDropedPackets    Counter32
}

dfl260PipePrecIndex OBJECT-TYPE
    SYNTAX      Integer32 (1..2147483647)
    MAX-ACCESS  not-accessible
    STATUS      current
    DESCRIPTION
        "Index of a precedence of a specific pipe. This is the second index
         of the entries of pipe precedence table described by object
         dfl260PipePrecEntry."
    ::= { dfl260PipePrecEntry 1 }

dfl260PipePrec OBJECT-TYPE
    SYNTAX      Integer32
    MAX-ACCESS  read-only
    STATUS      current
    DESCRIPTION
        "The precedence value"
    ::= { dfl260PipePrecEntry 2 }

dfl260PipePrecBps OBJECT-TYPE
    SYNTAX      Gauge32
    MAX-ACCESS  read-only
    STATUS      current
    DESCRIPTION
        "The current throughput of the pipe, in bits per second, with
         the corresponding precedence."
    ::= { dfl260PipePrecEntry 3 }

dfl260PipePrecTotalPps OBJECT-TYPE
    SYNTAX      Gauge32
    MAX-ACCESS  read-only
    STATUS      current
    DESCRIPTION
        "The current throughput of the pipe precedence, in packets per second."
    ::= { dfl260PipePrecEntry 4 }

dfl260PipePrecReservedBps OBJECT-TYPE
    SYNTAX      Gauge32
    MAX-ACCESS  read-only
    STATUS      current
    DESCRIPTION
        "The current bandwidth allocated to the precedence."
    ::= { dfl260PipePrecEntry 5 }

dfl260PipePrecDynLimBps OBJECT-TYPE
    SYNTAX      Gauge32
    MAX-ACCESS  read-only
    STATUS      current
    DESCRIPTION
        "The current bandwidth limit limit applied the precedence."
    ::= { dfl260PipePrecEntry 6 }

dfl260PipePrecDynUsrLimBps OBJECT-TYPE
    SYNTAX      Gauge32
    MAX-ACCESS  read-only
    STATUS      current
    DESCRIPTION
        "The current precedence bandwidth limit per user of the pipe."
    ::= { dfl260PipePrecEntry 7 }

dfl260PipePrecDelayedPackets OBJECT-TYPE
    SYNTAX      Counter32
    MAX-ACCESS  read-only
    STATUS      current
    DESCRIPTION
        "The number of times packets have been delayed as a result of a
         precedence, or pipe user having used up its allotted bandwidth.
         Note that one single packet may be delayed several times; if a
         pipe is really full, this count may exceed the number of packets
         of this precedence actually passing through the pipe."
    ::= { dfl260PipePrecEntry 8 }

dfl260PipePrecDropedPackets OBJECT-TYPE
    SYNTAX      Counter32
    MAX-ACCESS  read-only
    STATUS      current
    DESCRIPTION
        "The number of pipe dropped packets with the corresponding precedence."
    ::= { dfl260PipePrecEntry 9 }

dfl260ALG OBJECT IDENTIFIER
    ::= { dfl260OSStats 9 }

dfl260AlgSessions OBJECT-TYPE
    SYNTAX      Gauge32
    MAX-ACCESS  read-only
    STATUS      current
    DESCRIPTION
        "Total ALG sessions"
    ::= { dfl260ALG 1 }

dfl260AlgConnections OBJECT-TYPE
    SYNTAX      Gauge32
    MAX-ACCESS  read-only
    STATUS      current
    DESCRIPTION
        "Total ALG connections"
    ::= { dfl260ALG 2 }

dfl260AlgTCPStreams OBJECT-TYPE
    SYNTAX      Gauge32
    MAX-ACCESS  read-only
    STATUS      current
    DESCRIPTION
        "Total ALG TCP streams"
    ::= { dfl260ALG 3 }

dfl260HttpAlg OBJECT IDENTIFIER
    ::= { dfl260ALG 4 }

dfl260HttpAlgTable OBJECT-TYPE
    SYNTAX      SEQUENCE OF Dfl260HttpAlgEntry
    MAX-ACCESS  not-accessible
    STATUS      current
    DESCRIPTION
        "Table of HTTP ALG objects."
    ::= { dfl260HttpAlg 1 }

dfl260HttpAlgEntry OBJECT-TYPE
    SYNTAX      Dfl260HttpAlgEntry
    MAX-ACCESS  not-accessible
    STATUS      current
    DESCRIPTION
        "A row of the table of HTTP ALG objects."
    INDEX       { dfl260HttpAlgIndex }
    ::= { dfl260HttpAlgTable 1 }

Dfl260HttpAlgEntry ::= SEQUENCE {
    dfl260HttpAlgIndex             Integer32,
    dfl260HttpAlgName              DisplayString,
    dfl260HttpAlgTotalRequested    Gauge32,
    dfl260HttpAlgTotalAllowed      Gauge32,
    dfl260HttpAlgTotalBlocked      Gauge32
}

dfl260HttpAlgIndex OBJECT-TYPE
    SYNTAX      Integer32 (1..2147483647)
    MAX-ACCESS  not-accessible
    STATUS      current
    DESCRIPTION
        "The index of an entry of the  Table of HTTP ALG objects."
    ::= { dfl260HttpAlgEntry 1 }

dfl260HttpAlgName OBJECT-TYPE
    SYNTAX      DisplayString
    MAX-ACCESS  read-only
    STATUS      current
    DESCRIPTION
        "The name of an HTTP ALG object."
    ::= { dfl260HttpAlgEntry 2 }

dfl260HttpAlgTotalRequested OBJECT-TYPE
    SYNTAX      Gauge32
    MAX-ACCESS  read-only
    STATUS      current
    DESCRIPTION
        "Total number of URL requests."
    ::= { dfl260HttpAlgEntry 3 }

dfl260HttpAlgTotalAllowed OBJECT-TYPE
    SYNTAX      Gauge32
    MAX-ACCESS  read-only
    STATUS      current
    DESCRIPTION
        "Total number of allowed URL requests."
    ::= { dfl260HttpAlgEntry 4 }

dfl260HttpAlgTotalBlocked OBJECT-TYPE
    SYNTAX      Gauge32
    MAX-ACCESS  read-only
    STATUS      current
    DESCRIPTION
        "Total number of blocked URL requests."
    ::= { dfl260HttpAlgEntry 5 }

dfl260HttpAlgCntFltTable OBJECT-TYPE
    SYNTAX      SEQUENCE OF Dfl260HttpAlgCntFltEntry
    MAX-ACCESS  not-accessible
    STATUS      current
    DESCRIPTION
        "Table of HTTP ALG content filtering rules."
    ::= { dfl260HttpAlg 2 }

dfl260HttpAlgCntFltEntry OBJECT-TYPE
    SYNTAX      Dfl260HttpAlgCntFltEntry
    MAX-ACCESS  not-accessible
    STATUS      current
    DESCRIPTION
        "Entry of the table of HTTP ALG content filtering rules."
    INDEX       { dfl260HttpAlgIndex, dfl260HttpAlgCntFltIndex }
    ::= { dfl260HttpAlgCntFltTable 1 }

Dfl260HttpAlgCntFltEntry ::= SEQUENCE {
    dfl260HttpAlgCntFltIndex       Integer32,
    dfl260HttpAlgCntFltName        DisplayString,
    dfl260HttpAlgCntFltRequests    Gauge32,
    dfl260HttpAlgCntFltAllowed     Gauge32,
    dfl260HttpAlgCntFltBlocked     Gauge32
}

dfl260HttpAlgCntFltIndex OBJECT-TYPE
    SYNTAX      Integer32 (1..2147483647)
    MAX-ACCESS  not-accessible
    STATUS      current
    DESCRIPTION
        "The index of an entry of the  Table of HTTP ALG
         content filtering objects."
    ::= { dfl260HttpAlgCntFltEntry 1 }

dfl260HttpAlgCntFltName OBJECT-TYPE
    SYNTAX      DisplayString
    MAX-ACCESS  read-only
    STATUS      current
    DESCRIPTION
        "The name of the a HTTP ALG content fitering."
    ::= { dfl260HttpAlgCntFltEntry 2 }

dfl260HttpAlgCntFltRequests OBJECT-TYPE
    SYNTAX      Gauge32
    MAX-ACCESS  read-only
    STATUS      current
    DESCRIPTION
        "Total number of URLs intercepted by a content
         filtering object."
    ::= { dfl260HttpAlgCntFltEntry 3 }

dfl260HttpAlgCntFltAllowed OBJECT-TYPE
    SYNTAX      Gauge32
    MAX-ACCESS  read-only
    STATUS      current
    DESCRIPTION
        "Total number of URLs intercepted and allowed
         by a content filtering object."
    ::= { dfl260HttpAlgCntFltEntry 4 }

dfl260HttpAlgCntFltBlocked OBJECT-TYPE
    SYNTAX      Gauge32
    MAX-ACCESS  read-only
    STATUS      current
    DESCRIPTION
        "Total number of URLs intercepted and blocked
         by a content filtering object."
    ::= { dfl260HttpAlgCntFltEntry 5 }

dfl260SmtpAlg OBJECT IDENTIFIER
    ::= { dfl260ALG 5 }

dfl260SmtpAlgTable OBJECT-TYPE
    SYNTAX  SEQUENCE OF Dfl260SmtpAlgEntry
    MAX-ACCESS  not-accessible
    STATUS  current
    DESCRIPTION
  "Table of SMTP ALG objects."
    ::= { dfl260SmtpAlg 1 }

dfl260SmtpAlgEntry OBJECT-TYPE
   SYNTAX  Dfl260SmtpAlgEntry
   MAX-ACCESS  not-accessible
    STATUS      current
    DESCRIPTION
        "A row of the table of SMTP ALG objects."
    INDEX       { dfl260SmtpAlgIndex }
    ::= { dfl260SmtpAlgTable 1 }

Dfl260SmtpAlgEntry ::= SEQUENCE {
    dfl260SmtpAlgIndex           Integer32,
    dfl260SmtpAlgName            DisplayString,
    dfl260SmtpAlgTotCheckedSes   Gauge32,
    dfl260SmtpAlgTotSpamSes      Gauge32,
    dfl260SmtpAlgTotDroppedSes   Gauge32
}

dfl260SmtpAlgIndex OBJECT-TYPE
    SYNTAX      Integer32 (1..2147483647)
    MAX-ACCESS  not-accessible
    STATUS      current
    DESCRIPTION
        "The index of an entry of the  Table of SMTP ALG objects."
    ::= { dfl260SmtpAlgEntry 1 }

dfl260SmtpAlgName OBJECT-TYPE
    SYNTAX      DisplayString
    MAX-ACCESS  read-only
    STATUS      current
    DESCRIPTION
        "The name of an SMTP ALG object."
    ::= { dfl260SmtpAlgEntry 2 }

dfl260SmtpAlgTotCheckedSes OBJECT-TYPE
    SYNTAX      Gauge32
    MAX-ACCESS  read-only
    STATUS      current
    DESCRIPTION
        "Total sessions checked by the SMTP ALG of corresponding index."
    ::= { dfl260SmtpAlgEntry 3 }

dfl260SmtpAlgTotSpamSes OBJECT-TYPE
    SYNTAX      Gauge32
    MAX-ACCESS  read-only
    STATUS      current
    DESCRIPTION
        "Total spam sessions detected by the SMTP ALG of corresponding index."
    ::= { dfl260SmtpAlgEntry 4 }

dfl260SmtpAlgTotDroppedSes OBJECT-TYPE
    SYNTAX      Gauge32
    MAX-ACCESS  read-only
    STATUS      current
    DESCRIPTION
        "Total deroped sessions for the SMTP ALG of corresponding index."
    ::= { dfl260SmtpAlgEntry 5 }


dfl260SmtpAlgDnsBlTable OBJECT-TYPE
    SYNTAX  SEQUENCE OF Dfl260SmtpAlgDnsBlEntry
    MAX-ACCESS  not-accessible
    STATUS  current
    DESCRIPTION
  "Table of SMTP ALG DNS balck list objects."
    ::= { dfl260SmtpAlg 2 }


dfl260SmtpAlgDnsBlEntry OBJECT-TYPE
   SYNTAX  Dfl260SmtpAlgDnsBlEntry
   MAX-ACCESS  not-accessible
    STATUS      current
    DESCRIPTION
        "A row of the table of SMTP ALG DNS black list objects."
    INDEX       { dfl260SmtpAlgIndex, dfl260SmtpAlgDnsBlIndex }
    ::= { dfl260SmtpAlgDnsBlTable 1 }


Dfl260SmtpAlgDnsBlEntry ::= SEQUENCE {
    dfl260SmtpAlgDnsBlIndex  Integer32,
    dfl260SmtpAlgDnsBlName    DisplayString,
    dfl260SmtpAlgDnsBlChecked      Gauge32,
    dfl260SmtpAlgDnsBlMatched  Gauge32,
    dfl260SmtpAlgDnsBlFailChecks  Gauge32
}

dfl260SmtpAlgDnsBlIndex OBJECT-TYPE
    SYNTAX      Integer32 (1..2147483647)
    MAX-ACCESS  not-accessible
    STATUS      current
    DESCRIPTION
        "The index of an entry of the  SMTP ALG DNS black list objects."
    ::= { dfl260SmtpAlgDnsBlEntry 1 }

dfl260SmtpAlgDnsBlName OBJECT-TYPE
    SYNTAX      DisplayString
    MAX-ACCESS  read-only
    STATUS      current
    DESCRIPTION
  "The SMTP DNS black list name."
    ::= { dfl260SmtpAlgDnsBlEntry 2 }

dfl260SmtpAlgDnsBlChecked OBJECT-TYPE
    SYNTAX      Gauge32
    MAX-ACCESS  read-only
    STATUS      current
    DESCRIPTION
  "Total sessions checked againt SMTP ALG DNS black list of corresponding index"
    ::= { dfl260SmtpAlgDnsBlEntry 3 }

dfl260SmtpAlgDnsBlMatched OBJECT-TYPE
    SYNTAX      Gauge32
    MAX-ACCESS  read-only
    STATUS      current
    DESCRIPTION
  "Total sessions that matched SMTP ALG DNS black list of corresponding index"
    ::= { dfl260SmtpAlgDnsBlEntry 4 }

dfl260SmtpAlgDnsBlFailChecks OBJECT-TYPE
    SYNTAX      Gauge32
    MAX-ACCESS  read-only
    STATUS      current
    DESCRIPTION
  "Total failed checks for the SMTP ALG DNS black list of corresponding index"
    ::= { dfl260SmtpAlgDnsBlEntry 5 }

dfl260DHCPRelay OBJECT IDENTIFIER
    ::= { dfl260OSStats 11 }

dfl260DHCPRelayCurClients OBJECT-TYPE
    SYNTAX      Gauge32
    MAX-ACCESS  read-only
    STATUS      current
    DESCRIPTION
        "Total DHCP relay active relayed clients."
    ::= { dfl260DHCPRelay 1 }

dfl260DHCPRelayCurTrans OBJECT-TYPE
    SYNTAX      Gauge32
    MAX-ACCESS  read-only
    STATUS      current
    DESCRIPTION
        "Ongoing DHCP relay transactions."
    ::= { dfl260DHCPRelay 2 }

dfl260DHCPRelayRejected OBJECT-TYPE
    SYNTAX      Gauge32
    MAX-ACCESS  read-only
    STATUS      current
    DESCRIPTION
        "Total DHCP relay packets rejected."
    ::= { dfl260DHCPRelay 3 }

dfl260DHCPRelayRuleTable OBJECT-TYPE
    SYNTAX      SEQUENCE OF Dfl260DHCPRelayRuleEntry
    MAX-ACCESS  not-accessible
    STATUS      current
    DESCRIPTION
        "Table of DHCP relay rules."
    ::= { dfl260DHCPRelay 4 }

dfl260DHCPRelayRuleEntry OBJECT-TYPE
    SYNTAX      Dfl260DHCPRelayRuleEntry
    MAX-ACCESS  not-accessible
    STATUS      current
    DESCRIPTION
        "Entry of the table of DHCP relay rules"
    INDEX       { dfl260DHCPRelayRuleIndex }
    ::= { dfl260DHCPRelayRuleTable 1 }

Dfl260DHCPRelayRuleEntry ::= SEQUENCE {
    dfl260DHCPRelayRuleIndex       Integer32,
    dfl260DHCPRelayRuleName        DisplayString,
    dfl260DHCPRelayRuleHits        Gauge32,
    dfl260DHCPRelayRuleCurClients  Gauge32,
    dfl260DHCPRelayRuleRejCliPkts  Gauge32,
    dfl260DHCPRelayRuleRejSrvPkts  Gauge32
}

dfl260DHCPRelayRuleIndex OBJECT-TYPE
    SYNTAX      Integer32 (1..2147483647)
    MAX-ACCESS  not-accessible
    STATUS      current
    DESCRIPTION
        "Index of the table of DHCP relay rules."
    ::= { dfl260DHCPRelayRuleEntry 1 }

dfl260DHCPRelayRuleName OBJECT-TYPE
    SYNTAX      DisplayString
    MAX-ACCESS  read-only
    STATUS      current
    DESCRIPTION
        "Display name of a DHCP relay rule"
    ::= { dfl260DHCPRelayRuleEntry 2 }

dfl260DHCPRelayRuleHits OBJECT-TYPE
    SYNTAX      Gauge32
    MAX-ACCESS  read-only
    STATUS      current
    DESCRIPTION
        "Number of the times the  DHCP relay rule with corresponding index was
         used."
    ::= { dfl260DHCPRelayRuleEntry 3 }

dfl260DHCPRelayRuleCurClients OBJECT-TYPE
    SYNTAX      Gauge32
    MAX-ACCESS  read-only
    STATUS      current
    DESCRIPTION
        "Number of ctive relayed clients by the DHCP relay rule with corresponding index."
    ::= { dfl260DHCPRelayRuleEntry 4 }

dfl260DHCPRelayRuleRejCliPkts OBJECT-TYPE
    SYNTAX      Gauge32
    MAX-ACCESS  read-only
    STATUS      current
    DESCRIPTION
        "Number of client packets rejected by a rule."
    ::= { dfl260DHCPRelayRuleEntry 5 }

dfl260DHCPRelayRuleRejSrvPkts OBJECT-TYPE
    SYNTAX      Gauge32
    MAX-ACCESS  read-only
    STATUS      current
    DESCRIPTION
        "Number of DHCP server packets rejected by the DHCP relay rule
         with the corresponding index."
    ::= { dfl260DHCPRelayRuleEntry 6 }

dfl260HA OBJECT IDENTIFIER
    ::= { dfl260OSStats 12 }

dfl260HASyncSendQueueLength OBJECT-TYPE
    SYNTAX      Gauge32
    MAX-ACCESS  read-only
    STATUS      current
    DESCRIPTION
        "Size of the queue used for the High Availability sync interface."
    ::= { dfl260HA 1 }

dfl260HASyncSendQueueUsagePkt OBJECT-TYPE
    SYNTAX      Gauge32
    MAX-ACCESS  read-only
    STATUS      current
    DESCRIPTION
        "High Availability Sync interface queue usage in number of packets."
    ::= { dfl260HA 2 }

dfl260HASyncSendQueueUsageOct OBJECT-TYPE
    SYNTAX      Gauge32
    MAX-ACCESS  read-only
    STATUS      current
    DESCRIPTION
        "High Availability Sync interface queue usage in number of octects."
    ::= { dfl260HA 3 }

dfl260HASyncSentPackets OBJECT-TYPE
    SYNTAX      Counter32
    MAX-ACCESS  read-only
    STATUS      current
    DESCRIPTION
        "Number High Availability packets sent on Sync."
    ::= { dfl260HA 4 }

dfl260HASyncSendResentPackets OBJECT-TYPE
    SYNTAX      Counter32
    MAX-ACCESS  read-only
    STATUS      current
    DESCRIPTION
        "Number of High Availability packets resent on Sync."
    ::= { dfl260HA 5 }

dfl260StatsConformance OBJECT IDENTIFIER
    ::= { dfl260MibConfs 1 }

dfl260StatsRegGroups OBJECT IDENTIFIER
    ::= { dfl260MibObjectGroups 1 }

dfl260SystemObjectGroup OBJECT-GROUP
    OBJECTS     { dfl260SysCpuLoad,
                  dfl260SysForwardedBits,
                  dfl260SysForwardedPackets,
                  dfl260SysBuffUse,
                  dfl260SysConns,
                  dfl260HWSensorName,
                  dfl260HWSensorValue,
                  dfl260HWSensorUnit,
                  dfl260SysMemUsage,
                  dfl260SysTimerUsage,
                  dfl260SysConnOPS,
                  dfl260SysConnCPS,
                  dfl260SysHCForwardedBits }
    STATUS      current
    DESCRIPTION
        "System statistics Group"
    ::= { dfl260StatsRegGroups 1 }

dfl260IPsecObjectGroup OBJECT-GROUP
    OBJECTS     { dfl260IPsecPhaseOneActive,
                  dfl260IPsecPhaseOneAggrModeDone,
                  dfl260IPsecQuickModeActive,
                  dfl260IPsecPhaseOneDone,
                  dfl260IPsecPhaseOneFailed,
                  dfl260IPsecPhaseOneRekeyed,
                  dfl260IPsecQuickModeDone,
                  dfl260IPsecQuickModeFailed,
                  dfl260IPsecInfoDone,
                  dfl260IPsecInfoFailed,
                  dfl260IPsecInOctetsComp,
                  dfl260IPsecInOctetsUncomp,
                  dfl260IPsecOutOctetsComp,
                  dfl260IPsecOutOctetsUncomp,
                  dfl260IPsecForwardedOctetsComp,
                  dfl260IPsecForwardedOctetsUcomp,
                  dfl260IPsecInPackets,
                  dfl260IPsecOutPackets,
                  dfl260IPsecForwardedPackets,
                  dfl260IPsecActiveTransforms,
                  dfl260IPsecTotalTransforms,
                  dfl260IPsecOutOfTransforms,
                  dfl260IPsecTotalRekeys }
    STATUS      current
    DESCRIPTION
        "IPsec Group"
    ::= { dfl260StatsRegGroups 2 }

dfl260StateCountersGroup OBJECT-GROUP
    OBJECTS     { dfl260SysPscTcpSyn,
                  dfl260SysPscTcpOpen,
                  dfl260SysPscTcpFin,
                  dfl260SysPscUdp,
                  dfl260SysPscIcmp,
                  dfl260SysPscOther }
    STATUS      current
    DESCRIPTION
        "Per state counters"
    ::= { dfl260StatsRegGroups 3 }

dfl260IPPoolGroup OBJECT-GROUP
    OBJECTS     { dfl260IPPoolsNumber,
                  dfl260IPPoolName,
                  dfl260IPPoolPrepare,
                  dfl260IPPoolFree,
                  dfl260IPPoolMisses,
                  dfl260IPPoolClientFails,
                  dfl260IPPoolUsed }
    STATUS      current
    DESCRIPTION
        "IP pool entry objects group"
    ::= { dfl260StatsRegGroups 4 }

dfl260DHCPServerGroup OBJECT-GROUP
    OBJECTS     { dfl260DHCPTotalRejected,
                  dfl260DHCPRuleName,
                  dfl260DHCPRuleUsage,
                  dfl260DHCPRuleUsagePercent,
                  dfl260DHCPActiveClients,
                  dfl260DHCPActiveClientsPercent,
                  dfl260DHCPRejectedRequests,
                  dfl260DHCPTotalLeases }
    STATUS      current
    DESCRIPTION
        "DHCP server rules objects."
    ::= { dfl260StatsRegGroups 5 }

dfl260RuleUseGroup OBJECT-GROUP
    OBJECTS     { dfl260RuleName, dfl260RuleUse }
    STATUS      current
    DESCRIPTION
        "Rule use objects."
    ::= { dfl260StatsRegGroups 6 }

dfl260UserAuthGroup OBJECT-GROUP
    OBJECTS     { dfl260UserAuthHTTPUsers, dfl260UserAuthXAUTHUsers,
                  dfl260UserAuthHTTPSUsers, dfl260UserAuthPPPUsers,
                  dfl260UserAuthEAPUsers, dfl260UserAuthRuleName,
                  dfl260UserAuthRuleUse }
    STATUS      current
    DESCRIPTION
        "User auth objects."
    ::= { dfl260StatsRegGroups 7 }

dfl260IfStatsGroup OBJECT-GROUP
    OBJECTS     { dfl260IfName,
                  dfl260IfFragsIn,
                  dfl260IfFragReassOk,
                  dfl260IfFragReassFail,
                  dfl260IfPktsInCnt,
                  dfl260IfPktsOutCnt,
                  dfl260IfBitsInCnt,
                  dfl260IfBitsOutCnt,
                  dfl260IfPktsTotCnt,
                  dfl260IfBitsTotCnt,
                  dfl260IfHCPktsInCnt,
                  dfl260IfHCPktsOutCnt,
                  dfl260IfHCBitsInCnt,
                  dfl260IfHCBitsOutCnt,
                  dfl260IfHCPktsTotCnt,
                  dfl260IfHCBitsTotCnt,
                  dfl260IfRxRingFifoErrors,
                  dfl260IfRxDespools,
                  dfl260IfRxAvgUse,
                  dfl260IfRxRingSaturation,
                  dfl260RxRingFlooded,
                  dfl260IfTxDespools,
                  dfl260IfTxAvgUse,
                  dfl260IfTxRingSaturation,
                  dfl260RxTingFlooded }
    STATUS      current
    DESCRIPTION
        "DFL-260 interface statistics group."
    ::= { dfl260StatsRegGroups 8 }

dfl260LinkMonitorGroup OBJECT-GROUP
    OBJECTS     { dfl260LinkMonGrp,
                  dfl260LinkMonGrpName,
                  dfl260LinkMonGrpHostsUp,
                  dfl260LinkMonHostId,
                  dfl260LinkMonHostShortTermLoss,
                  dfl260LinkMonHostPacketsLost }
    STATUS      current
    DESCRIPTION
        "DFL-260 link monitor statistics group"
    ::= { dfl260StatsRegGroups 9 }

dfl260PipesObjectGroup OBJECT-GROUP
    OBJECTS     { dfl260PipeUsers,
                  dfl260PipeName,
                  dfl260PipeMinPrec,
                  dfl260PipeMaxPrec,
                  dfl260PipeDefPrec,
                  dfl260PipeNumPrec,
                  dfl260PipeNumUsers,
                  dfl260PipeCurrentBps,
                  dfl260PipeCurrentPps,
                  dfl260PipeDelayedPackets,
                  dfl260PipeDropedPackets,
                  dfl260PipePrec,
                  dfl260PipePrecBps,
                  dfl260PipePrecTotalPps,
                  dfl260PipePrecReservedBps,
                  dfl260PipePrecDynLimBps,
                  dfl260PipePrecDynUsrLimBps,
                  dfl260PipePrecDelayedPackets,
                  dfl260PipePrecDropedPackets }
    STATUS      current
    DESCRIPTION
        "DFL-260 pipes statistics group"
    ::= { dfl260StatsRegGroups 10 }

dfl260DHCPRelayObjectGroup OBJECT-GROUP
    OBJECTS     { dfl260DHCPRelayCurClients,
                  dfl260DHCPRelayCurTrans,
                  dfl260DHCPRelayRejected,
                  dfl260DHCPRelayRuleName,
                  dfl260DHCPRelayRuleHits,
                  dfl260DHCPRelayRuleCurClients,
                  dfl260DHCPRelayRuleRejCliPkts,
                  dfl260DHCPRelayRuleRejSrvPkts }
    STATUS      current
    DESCRIPTION
        "DFL-260 DHCP relay statistics group"
    ::= { dfl260StatsRegGroups 12 }

dfl260AlgGroup OBJECT-GROUP
    OBJECTS     { dfl260AlgSessions,
                  dfl260AlgConnections,
                  dfl260AlgTCPStreams,
                  dfl260HttpAlgName,
                  dfl260HttpAlgTotalRequested,
                  dfl260HttpAlgTotalAllowed,
                  dfl260HttpAlgTotalBlocked,
                  dfl260HttpAlgCntFltName,
                  dfl260HttpAlgCntFltRequests,
                  dfl260HttpAlgCntFltAllowed,
                  dfl260HttpAlgCntFltBlocked }
    STATUS      current
    DESCRIPTION
        "DFL-260 HTTP ALG statistics group"
    ::= { dfl260StatsRegGroups 13 }

dfl260HAGroup OBJECT-GROUP
    OBJECTS     { dfl260HASyncSendQueueLength,
                  dfl260HASyncSendQueueUsagePkt,
                  dfl260HASyncSendQueueUsageOct,
                  dfl260HASyncSentPackets,
                  dfl260HASyncSendResentPackets }
    STATUS      current
    DESCRIPTION
        "DFL-260 HA statistics group"
    ::= { dfl260StatsRegGroups 14 }

dfl260IfVlanGroup OBJECT-GROUP
    OBJECTS     { dfl260IfVlanUntaggedInPkts,
                  dfl260IfVlanUntaggedOutPkts,
                  dfl260IfVlanUntaggedTotPkts,
                  dfl260IfVlanUntaggedInOctets,
                  dfl260IfVlanUntaggedOutOctets,
                  dfl260IfVlanUntaggedTotOctets }
    STATUS      current
    DESCRIPTION
        "DFL-260 VLAN statistics group"
    ::= { dfl260StatsRegGroups 15 }


dfl260SmtpAlgGroup OBJECT-GROUP
    OBJECTS { dfl260SmtpAlgName,
              dfl260SmtpAlgTotCheckedSes,
              dfl260SmtpAlgTotSpamSes,
              dfl260SmtpAlgTotDroppedSes,
              dfl260SmtpAlgDnsBlName,
              dfl260SmtpAlgDnsBlChecked,
              dfl260SmtpAlgDnsBlMatched,
              dfl260SmtpAlgDnsBlFailChecks }
   STATUS current
   DESCRIPTION
       "Clavister SMTP ALG objects group"
   ::= { dfl260StatsRegGroups 16 }

dfl260SysTCPGroup OBJECT-GROUP
    OBJECTS { dfl260SysTCPRecvSmall,
              dfl260SysTCPRecvLarge,
              dfl260SysTCPSendSmall,
              dfl260SysTCPSendLarge }
    STATUS current
    DESCRIPTION
      "DFL-260 TCP buffer usage group"
    ::= { dfl260StatsRegGroups 17 }



dfl260StatsCompliance MODULE-COMPLIANCE
    STATUS      current
    DESCRIPTION
        "Module Compliance"

    MODULE      -- this module

        MANDATORY-GROUPS
                { dfl260SystemObjectGroup,
                  dfl260IPsecObjectGroup,
                  dfl260StateCountersGroup,
                  dfl260IPPoolGroup,
                  dfl260DHCPServerGroup,
                  dfl260RuleUseGroup,
                  dfl260UserAuthGroup,
                  dfl260IfStatsGroup,
                  dfl260LinkMonitorGroup,
                  dfl260PipesObjectGroup,
                  dfl260DHCPRelayObjectGroup,
                  dfl260AlgGroup,
                  dfl260HAGroup,
                  dfl260IfVlanGroup,
                  dfl260SmtpAlgGroup,
                  dfl260SysTCPGroup }

    ::= { dfl260StatsConformance 1 }

END -- end of module DFL260-MIB.
