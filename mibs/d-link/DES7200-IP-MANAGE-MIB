-- *****************************************************************
-- MY-IP-MANAGE-MIB.mib:  My IP MANAGE MIB file
--
-- $Copyright$
--
-- *****************************************************************
--

DES7200-IP-MANAGE-MIB DEFINITIONS ::= BEGIN

IMPORTS
        MODULE-IDENTITY,
        OBJECT-TYPE,
        NOTIFICATION-TYPE,
        Integer32,
        Counter32,
        IpAddress
                FROM SNMPv2-SMI
        VlanId
                FROM Q-BRIDGE-MIB
        TruthValue,
        DisplayString,
        RowStatus,
        MacAddress
                FROM SNMPv2-TC
        MODULE-COMPLIANCE,
        OBJECT-GROUP,
        NOTIFICATION-GROUP
                FROM SNMPv2-CONF
        ConfigStatus,
        MemberMap
                FROM DES7200-TC
        EnabledStatus
                FROM P-BRIDGE-MIB
        myMgmt
                FROM DES7200-SMI;

myIpManageMIB MODULE-IDENTITY
        LAST-UPDATED "200203200000Z"
        ORGANIZATION "$Company$"
        CONTACT-INFO
                "
                Tel: $Telephone$

                E-mail: $E-mail$"
        DESCRIPTION
                "This module defines my IP managment mibs."
        REVISION      "200203200000Z"
        DESCRIPTION
                "Initial version of this MIB module."
        ::= { myMgmt 12}

myDhcpMIBObjects OBJECT IDENTIFIER ::= { myIpManageMIB 1 }
myIpMIBObjects OBJECT IDENTIFIER ::= { myIpManageMIB 2 }
--
-- my  Dhcp Group
--

myDhcpRelayAgentGlobalStatus OBJECT-TYPE
    SYNTAX EnabledStatus
    MAX-ACCESS read-write
    STATUS current
    DESCRIPTION
            "Global Dhcp relay agent status"
    DEFVAL { disabled }
            ::={ myDhcpMIBObjects 2 }

myDhcpServerIp OBJECT-TYPE
    SYNTAX IpAddress
    MAX-ACCESS read-write
    STATUS current
    DESCRIPTION
             "Ip address of internet host which returns configuration
              parameters to DHCP clients."
        ::={ myDhcpMIBObjects 3 }


myIpDefaultGateWay OBJECT-TYPE
    SYNTAX IpAddress
    MAX-ACCESS read-write
    STATUS current
    DESCRIPTION
             "Ip default gateway of system. This value applay only in layer 2"
        ::={ myIpMIBObjects 1 }

myIpManageMIBConformance OBJECT IDENTIFIER ::= { myIpManageMIB 3 }
myIpManageMIBCompliances OBJECT IDENTIFIER ::= { myIpManageMIBConformance 1 }
myIpManageMIBGroups      OBJECT IDENTIFIER ::= { myIpManageMIBConformance 2 }


-- compliance statements

myIpManageMIBCompliance MODULE-COMPLIANCE
        STATUS  current
        DESCRIPTION
                "The compliance statement for entities which implement
                the My Snooping Dhcp MIB"
        MODULE  -- this module
                MANDATORY-GROUPS { myL2L3DhcpManageMIBGroup
                 }
        ::= { myIpManageMIBCompliances 1 }

-- units of conformance

myL2L3DhcpManageMIBGroup OBJECT-GROUP
        OBJECTS {
           myDhcpRelayAgentGlobalStatus,
           myDhcpServerIp
        }
        STATUS  current
        DESCRIPTION
                "A collection of objects providing IP managment in layer2 or layer3 mode."
        ::= { myIpManageMIBGroups 1 }

END
