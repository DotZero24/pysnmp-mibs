--
-- DFL-800 SMIv2 module
--

DFL800-MIB DEFINITIONS ::= BEGIN

IMPORTS
    MODULE-COMPLIANCE, OBJECT-GROUP
        FROM SNMPv2-CONF
    Counter32, Counter64, Gauge32, Integer32, MODULE-IDENTITY,
    OBJECT-TYPE, enterprises
        FROM SNMPv2-SMI
    DisplayString
        FROM SNMPv2-TC;

dfl800-MIB MODULE-IDENTITY
    LAST-UPDATED "201009021139Z"
    ORGANIZATION
        "D-Link Corporation"
    CONTACT-INFO
        "Postal: D-Link Corporation
         No. 289, Sinhu 3rd Road,
         Neihu District, Taipei City 114,
         Taiwan, R.O.C.
         Tel: +886-2-66000123
         Fax: +886-2-55509988"
    DESCRIPTION
        "The MIB module for D-Link DFL-800 series product."

    REVISION  "201009021139Z"
    DESCRIPTION
        "Added 64-bit counters"
    REVISION  "201003300900Z"
    DESCRIPTION
        "Added values for SMTP ALG objects."
    REVISION  "200911100916Z"
    DESCRIPTION
        "Added values for opened and closed connections per second"
    REVISION  "200811181605Z"
    DESCRIPTION
        "Added value for timer usage"
    REVISION  "200810141227Z"
    DESCRIPTION
        "Added values for memory usage and TCP buffer usage"
    REVISION  "200710310000Z"
    DESCRIPTION
        "Initial version."
    ::= { dfl800MibModules 2 }


dlink OBJECT IDENTIFIER
    ::= { enterprises 171 }

netdefendMgmt OBJECT IDENTIFIER
    ::= { dlink 20 }

ipsFirewall OBJECT IDENTIFIER
    ::= { netdefendMgmt 1 }

dfl800 OBJECT IDENTIFIER
    ::= { ipsFirewall 2 }

dfl800OS OBJECT IDENTIFIER
    ::= { dfl800 1 }

dfl800OSStats OBJECT IDENTIFIER
    ::= { dfl800OS 2 }

dfl800reg OBJECT IDENTIFIER
    ::= { dfl800 2 }

dfl800MibModules OBJECT IDENTIFIER
    ::= { dfl800reg 1 }

dfl800MibConfs OBJECT IDENTIFIER
    ::= { dfl800reg 2 }

dfl800MibObjectGroups OBJECT IDENTIFIER
    ::= { dfl800reg 3 }


dfl800System OBJECT IDENTIFIER
    ::= { dfl800OSStats 1 }

dfl800SysCpuLoad OBJECT-TYPE
    SYNTAX      Gauge32
    MAX-ACCESS  read-only
    STATUS      current
    DESCRIPTION
        "The system cpu load."
    ::= { dfl800System 1 }

dfl800SysForwardedBits OBJECT-TYPE
    SYNTAX      Counter32
    MAX-ACCESS  read-only
    STATUS      current
    DESCRIPTION
        "The number of bits forwarded through the gateway."
    ::= { dfl800System 2 }

dfl800SysForwardedPackets OBJECT-TYPE
    SYNTAX      Counter32
    MAX-ACCESS  read-only
    STATUS      current
    DESCRIPTION
        "Total number of forwarded packets."
    ::= { dfl800System 3 }

dfl800SysBuffUse OBJECT-TYPE
    SYNTAX      Gauge32
    MAX-ACCESS  read-only
    STATUS      current
    DESCRIPTION
        "The current number of buffers in use."
    ::= { dfl800System 4 }

dfl800SysConns OBJECT-TYPE
    SYNTAX      Gauge32
    MAX-ACCESS  read-only
    STATUS      current
    DESCRIPTION
        "The numer of connections."
    ::= { dfl800System 5 }

dfl800SysPerStateCounters OBJECT IDENTIFIER
    ::= { dfl800System 6 }

dfl800SysPscTcpSyn OBJECT-TYPE
    SYNTAX      Gauge32
    MAX-ACCESS  read-only
    STATUS      current
    DESCRIPTION
        "Number of TCP connections in the SYN state."
    ::= { dfl800SysPerStateCounters 1 }

dfl800SysPscTcpOpen OBJECT-TYPE
    SYNTAX      Gauge32
    MAX-ACCESS  read-only
    STATUS      current
    DESCRIPTION
        "Number of TCP connections in the OPEN state."
    ::= { dfl800SysPerStateCounters 2 }

dfl800SysPscTcpFin OBJECT-TYPE
    SYNTAX      Gauge32
    MAX-ACCESS  read-only
    STATUS      current
    DESCRIPTION
        "Number of TCP connections in the FIN state."
    ::= { dfl800SysPerStateCounters 3 }

dfl800SysPscUdp OBJECT-TYPE
    SYNTAX      Gauge32
    MAX-ACCESS  read-only
    STATUS      current
    DESCRIPTION
        "Number of UDP connections."
    ::= { dfl800SysPerStateCounters 4 }

dfl800SysPscIcmp OBJECT-TYPE
    SYNTAX      Gauge32
    MAX-ACCESS  read-only
    STATUS      current
    DESCRIPTION
        "Number of ICMP connections."
    ::= { dfl800SysPerStateCounters 5 }

dfl800SysPscOther OBJECT-TYPE
    SYNTAX      Gauge32
    MAX-ACCESS  read-only
    STATUS      current
    DESCRIPTION
        "Number of other connections."
    ::= { dfl800SysPerStateCounters 6 }

dfl800IfStatsTable OBJECT-TYPE
    SYNTAX      SEQUENCE OF Dfl800IfStatsEntry
    MAX-ACCESS  not-accessible
    STATUS      current
    DESCRIPTION
        "A table of DFL-800 specific interfaces statistics"
    ::= { dfl800System 7 }

dfl800IfStatsEntry OBJECT-TYPE
    SYNTAX      Dfl800IfStatsEntry
    MAX-ACCESS  not-accessible
    STATUS      current
    DESCRIPTION
        "The row in a table of DFL-800 specific interface statistics"
    INDEX       { dfl800IfStatsIndex }
    ::= { dfl800IfStatsTable 1 }

Dfl800IfStatsEntry ::= SEQUENCE {
    dfl800IfStatsIndex     Integer32,
    dfl800IfName           DisplayString,
    dfl800IfFragsIn        Counter32,
    dfl800IfFragReassOk    Counter32,
    dfl800IfFragReassFail  Counter32,
    dfl800IfPktsInCnt      Counter32,
    dfl800IfPktsOutCnt     Counter32,
    dfl800IfBitsInCnt      Counter32,
    dfl800IfBitsOutCnt     Counter32,
    dfl800IfPktsTotCnt     Counter32,
    dfl800IfBitsTotCnt     Counter32,
    dfl800IfHCPktsInCnt    Counter64,
    dfl800IfHCPktsOutCnt   Counter64,
    dfl800IfHCBitsInCnt    Counter64,
    dfl800IfHCBitsOutCnt   Counter64,
    dfl800IfHCPktsTotCnt   Counter64,
    dfl800IfHCBitsTotCnt   Counter64
}

dfl800IfStatsIndex OBJECT-TYPE
    SYNTAX      Integer32 (1..2147483647)
    MAX-ACCESS  not-accessible
    STATUS      current
    DESCRIPTION
        "Index of a row in dfl800SysIfStatsTable"
    ::= { dfl800IfStatsEntry 1 }

dfl800IfName OBJECT-TYPE
    SYNTAX      DisplayString
    MAX-ACCESS  read-only
    STATUS      current
    DESCRIPTION
        "The name of the interface."
    ::= { dfl800IfStatsEntry 2 }

dfl800IfFragsIn OBJECT-TYPE
    SYNTAX      Counter32
    MAX-ACCESS  read-only
    STATUS      current
    DESCRIPTION
        "Number of IP packet fragments received
         in the interface."
    ::= { dfl800IfStatsEntry 3 }

dfl800IfFragReassOk OBJECT-TYPE
    SYNTAX      Counter32
    MAX-ACCESS  read-only
    STATUS      current
    DESCRIPTION
        "Number of complete IP packets successfully
         reassembled from the fragments received in
         the interface."
    ::= { dfl800IfStatsEntry 4 }

dfl800IfFragReassFail OBJECT-TYPE
    SYNTAX      Counter32
    MAX-ACCESS  read-only
    STATUS      current
    DESCRIPTION
        "Number of packets that could not be reassembled,
         either due to resource starvation, illegal fragmentation,
         or just packet loss."
    ::= { dfl800IfStatsEntry 5 }

dfl800IfPktsInCnt OBJECT-TYPE
    SYNTAX      Counter32
    MAX-ACCESS  read-only
    STATUS      current
    DESCRIPTION
        "Number of packets received by the interface."
    ::= { dfl800IfStatsEntry 6 }

dfl800IfPktsOutCnt OBJECT-TYPE
    SYNTAX      Counter32
    MAX-ACCESS  read-only
    STATUS      current
    DESCRIPTION
        "Number of packets sent by the interface"
    ::= { dfl800IfStatsEntry 7 }

dfl800IfBitsInCnt OBJECT-TYPE
    SYNTAX      Counter32
    MAX-ACCESS  read-only
    STATUS      current
    DESCRIPTION
        "Number of bits received by the interface"
    ::= { dfl800IfStatsEntry 8 }

dfl800IfBitsOutCnt OBJECT-TYPE
    SYNTAX      Counter32
    MAX-ACCESS  read-only
    STATUS      current
    DESCRIPTION
        "Number of bits sent by the interface"
    ::= { dfl800IfStatsEntry 9 }

dfl800IfPktsTotCnt OBJECT-TYPE
    SYNTAX      Counter32
    MAX-ACCESS  read-only
    STATUS      current
    DESCRIPTION
        "Totat number of packets transmited by the interface"
    ::= { dfl800IfStatsEntry 10 }

dfl800IfBitsTotCnt OBJECT-TYPE
    SYNTAX      Counter32
    MAX-ACCESS  read-only
    STATUS      current
    DESCRIPTION
        "Totat number of bits transmited by the interface"
    ::= { dfl800IfStatsEntry 11 }

dfl800IfHCPktsInCnt OBJECT-TYPE
    SYNTAX      Counter64
    MAX-ACCESS  read-only
    STATUS      current
    DESCRIPTION
        "Number of packets received by the interface.
        This object is a 64-bit version of dfl800IfPktsInCnt."
    ::= { dfl800IfStatsEntry 12 }

dfl800IfHCPktsOutCnt OBJECT-TYPE
    SYNTAX      Counter64
    MAX-ACCESS  read-only
    STATUS      current
    DESCRIPTION
        "Number of packets sent by the interface.
        This object is a 64-bit version of dfl800IfPktsOutCnt."
    ::= { dfl800IfStatsEntry 13 }

dfl800IfHCBitsInCnt OBJECT-TYPE
    SYNTAX      Counter64
    MAX-ACCESS  read-only
    STATUS      current
    DESCRIPTION
        "Number of bits received by the interface.
        This object is a 64-bit version of dfl800IfBitsInCnt."
    ::= { dfl800IfStatsEntry 14 }

dfl800IfHCBitsOutCnt OBJECT-TYPE
    SYNTAX      Counter64
    MAX-ACCESS  read-only
    STATUS      current
    DESCRIPTION
        "Number of bits sent by the interface.
        This object is a 64-bit version of dfl800IfBitsOutCnt."
    ::= { dfl800IfStatsEntry 15 }

dfl800IfHCPktsTotCnt OBJECT-TYPE
    SYNTAX      Counter64
    MAX-ACCESS  read-only
    STATUS      current
    DESCRIPTION
        "Totat number of packets transmited by the interface.
        This object is a 64-bit version of dfl800IfPktsTotCnt."
    ::= { dfl800IfStatsEntry 16 }

dfl800IfHCBitsTotCnt OBJECT-TYPE
    SYNTAX      Counter64
    MAX-ACCESS  read-only
    STATUS      current
    DESCRIPTION
        "Totat number of bits transmited by the interface.
        This object is a 64-bit version of dfl800IfBitsTotCnt."
    ::= { dfl800IfStatsEntry 17 }

dfl800IfRxRingTable OBJECT-TYPE
    SYNTAX      SEQUENCE OF Dfl800IfRxRingEntry
    MAX-ACCESS  not-accessible
    STATUS      current
    DESCRIPTION
        "A table of DFL-800 specific interface Rx ring statistics"
    ::= { dfl800System 8 }

dfl800IfRxRingEntry OBJECT-TYPE
    SYNTAX      Dfl800IfRxRingEntry
    MAX-ACCESS  not-accessible
    STATUS      current
    DESCRIPTION
        "The row in a table of DFL-800 specific interface Rx ring
         statistics."
    INDEX       { dfl800IfRxRingIndex }
    ::= { dfl800IfRxRingTable 1 }

Dfl800IfRxRingEntry ::= SEQUENCE {
    dfl800IfRxRingIndex        Integer32,
    dfl800IfRxRingFifoErrors   Counter32,
    dfl800IfRxDespools         Gauge32,
    dfl800IfRxAvgUse           Gauge32,
    dfl800IfRxRingSaturation   Gauge32,
    dfl800RxRingFlooded        Gauge32
}

dfl800IfRxRingIndex OBJECT-TYPE
    SYNTAX      Integer32 (1..2147483647)
    MAX-ACCESS  not-accessible
    STATUS      current
    DESCRIPTION
        "Index of a row in dfl800IfRxRingTable."
    ::= { dfl800IfRxRingEntry 1 }

dfl800IfRxRingFifoErrors OBJECT-TYPE
    SYNTAX      Counter32
    MAX-ACCESS  read-only
    STATUS      current
    DESCRIPTION
        "Rx Ring number of FIFO errors."
    ::= { dfl800IfRxRingEntry 2 }

dfl800IfRxDespools OBJECT-TYPE
    SYNTAX      Gauge32
    MAX-ACCESS  read-only
    STATUS      current
    DESCRIPTION
        "Number of despool events per second."
    ::= { dfl800IfRxRingEntry 3 }

dfl800IfRxAvgUse OBJECT-TYPE
    SYNTAX      Gauge32
    MAX-ACCESS  read-only
    STATUS      current
    DESCRIPTION
        "Rx Ring average usage."
    ::= { dfl800IfRxRingEntry 4 }

dfl800IfRxRingSaturation OBJECT-TYPE
    SYNTAX      Gauge32
    MAX-ACCESS  read-only
    STATUS      current
    DESCRIPTION
        "Rx Ring sturation. Percentage of ring use per despool
         event when the ring has been more than half full."
    ::= { dfl800IfRxRingEntry 5 }

dfl800RxRingFlooded OBJECT-TYPE
    SYNTAX      Gauge32
    MAX-ACCESS  read-only
    STATUS      current
    DESCRIPTION
        "Rx Ring number of despool events for which
         the ring has been completely flooded"
    ::= { dfl800IfRxRingEntry 6 }

dfl800IfTxRingTable OBJECT-TYPE
    SYNTAX      SEQUENCE OF Dfl800IfTxRingEntry
    MAX-ACCESS  not-accessible
    STATUS      current
    DESCRIPTION
        "A table of DFL-800 specific interface Tx ring statistics"
    ::= { dfl800System 9 }

dfl800IfTxRingEntry OBJECT-TYPE
    SYNTAX      Dfl800IfTxRingEntry
    MAX-ACCESS  not-accessible
    STATUS      current
    DESCRIPTION
        "The row in a table of DFL-800 specific interface Tx ring
         statistics."
    INDEX       { dfl800IfTxRingIndex }
    ::= { dfl800IfTxRingTable 1 }

Dfl800IfTxRingEntry ::= SEQUENCE {
    dfl800IfTxRingIndex        Integer32,
    dfl800IfTxDespools         Gauge32,
    dfl800IfTxAvgUse           Gauge32,
    dfl800IfTxRingSaturation   Gauge32,
    dfl800RxTingFlooded        Gauge32
}

dfl800IfTxRingIndex OBJECT-TYPE
    SYNTAX      Integer32 (1..2147483647)
    MAX-ACCESS  not-accessible
    STATUS      current
    DESCRIPTION
        "Index of a row in dfl800IfRxRingTable."
    ::= { dfl800IfTxRingEntry 1 }

dfl800IfTxDespools OBJECT-TYPE
    SYNTAX      Gauge32
    MAX-ACCESS  read-only
    STATUS      current
    DESCRIPTION
        "Tx Ring number of despool event per second (polls when
         there is at least one buffer in the ring)"
    ::= { dfl800IfTxRingEntry 2 }

dfl800IfTxAvgUse OBJECT-TYPE
    SYNTAX      Gauge32
    MAX-ACCESS  read-only
    STATUS      current
    DESCRIPTION
        "Tx Ring number of despool events when the ring has
         been completely flooded"
    ::= { dfl800IfTxRingEntry 3 }

dfl800IfTxRingSaturation OBJECT-TYPE
    SYNTAX      Gauge32
    MAX-ACCESS  read-only
    STATUS      current
    DESCRIPTION
        "Tx Ring percentage of use per despool event when the
         ring has been more than half full."
    ::= { dfl800IfTxRingEntry 4 }

dfl800RxTingFlooded OBJECT-TYPE
    SYNTAX      Gauge32
    MAX-ACCESS  read-only
    STATUS      current
    DESCRIPTION
        "Tx Ring number of despool events for in which the ring has
         been completely flooded"
    ::= { dfl800IfTxRingEntry 5 }

dfl800IfVlanStatsTable OBJECT-TYPE
    SYNTAX      SEQUENCE OF Dfl800IfVlanStatsEntry
    MAX-ACCESS  not-accessible
    STATUS      current
    DESCRIPTION
        "A table of DFL-800 VLAN statistics"
    ::= { dfl800System 10 }

dfl800IfVlanStatsEntry OBJECT-TYPE
    SYNTAX      Dfl800IfVlanStatsEntry
    MAX-ACCESS  not-accessible
    STATUS      current
    DESCRIPTION
        "The row in a table of dfl800IfVlanStatsTable. Each has an index
         equal to the ifIndex of the corresponding physical interface"
    INDEX       { dfl800IfVlanIndex }
    ::= { dfl800IfVlanStatsTable 1 }

Dfl800IfVlanStatsEntry ::= SEQUENCE {
    dfl800IfVlanIndex              Integer32,
    dfl800IfVlanUntaggedInPkts     Counter32,
    dfl800IfVlanUntaggedOutPkts    Counter32,
    dfl800IfVlanUntaggedTotPkts    Counter32,
    dfl800IfVlanUntaggedInOctets   Counter32,
    dfl800IfVlanUntaggedOutOctets  Counter32,
    dfl800IfVlanUntaggedTotOctets  Counter32
}

dfl800IfVlanIndex OBJECT-TYPE
    SYNTAX      Integer32 (1..2147483647)
    MAX-ACCESS  not-accessible
    STATUS      current
    DESCRIPTION
        "Extended index of a row in dfl800IfVlanStatsTable."
    ::= { dfl800IfVlanStatsEntry 1 }

dfl800IfVlanUntaggedInPkts OBJECT-TYPE
    SYNTAX      Counter32
    MAX-ACCESS  read-only
    STATUS      current
    DESCRIPTION
        "Number of untaged packets untagged packets received by the interface."
    ::= { dfl800IfVlanStatsEntry 2 }

dfl800IfVlanUntaggedOutPkts OBJECT-TYPE
    SYNTAX      Counter32
    MAX-ACCESS  read-only
    STATUS      current
    DESCRIPTION
        "Number of untagged packets sent by the interface."
    ::= { dfl800IfVlanStatsEntry 3 }

dfl800IfVlanUntaggedTotPkts OBJECT-TYPE
    SYNTAX      Counter32
    MAX-ACCESS  read-only
    STATUS      current
    DESCRIPTION
        "Total number of untagged packets processed by the interface."
    ::= { dfl800IfVlanStatsEntry 4 }

dfl800IfVlanUntaggedInOctets OBJECT-TYPE
    SYNTAX      Counter32
    MAX-ACCESS  read-only
    STATUS      current
    DESCRIPTION
        "Total number of octects in untagged packets received by the interface."
    ::= { dfl800IfVlanStatsEntry 5 }

dfl800IfVlanUntaggedOutOctets OBJECT-TYPE
    SYNTAX      Counter32
    MAX-ACCESS  read-only
    STATUS      current
    DESCRIPTION
        "Total number of octects in untagged packets sent by the interface."
    ::= { dfl800IfVlanStatsEntry 6 }

dfl800IfVlanUntaggedTotOctets OBJECT-TYPE
    SYNTAX      Counter32
    MAX-ACCESS  read-only
    STATUS      current
    DESCRIPTION
        "Total number of octects in untagged packets processed by the
         interface."
    ::= { dfl800IfVlanStatsEntry 7 }

dfl800HWSensorTable OBJECT-TYPE
    SYNTAX      SEQUENCE OF Dfl800HWSensorEntry
    MAX-ACCESS  not-accessible
    STATUS      current
    DESCRIPTION
        "Table of hardware sensors."
    ::= { dfl800System 11 }

dfl800HWSensorEntry OBJECT-TYPE
    SYNTAX      Dfl800HWSensorEntry
    MAX-ACCESS  not-accessible
    STATUS      current
    DESCRIPTION
        "Entry  of table of hardware sensors."
    INDEX       { dfl800HWSensorIndex }
    ::= { dfl800HWSensorTable 1 }

Dfl800HWSensorEntry ::= SEQUENCE {
    dfl800HWSensorIndex    Integer32,
    dfl800HWSensorName     DisplayString,
    dfl800HWSensorValue    Gauge32,
    dfl800HWSensorUnit     DisplayString
}

dfl800HWSensorIndex OBJECT-TYPE
    SYNTAX      Integer32 (1..2147483647)
    MAX-ACCESS  not-accessible
    STATUS      current
    DESCRIPTION
        "Index of the entries of the sensor table."
    ::= { dfl800HWSensorEntry 1 }

dfl800HWSensorName OBJECT-TYPE
    SYNTAX      DisplayString
    MAX-ACCESS  read-only
    STATUS      current
    DESCRIPTION
        "The description of the sensor."
    ::= { dfl800HWSensorEntry 2 }

dfl800HWSensorValue OBJECT-TYPE
    SYNTAX      Gauge32
    MAX-ACCESS  read-only
    STATUS      current
    DESCRIPTION
        "The value of the sensor."
    ::= { dfl800HWSensorEntry 3 }

dfl800HWSensorUnit OBJECT-TYPE
    SYNTAX      DisplayString
    MAX-ACCESS  read-only
    STATUS      current
    DESCRIPTION
        "The description of the unit of the value mesured by sensor."
    ::= { dfl800HWSensorEntry 4 }

dfl800SysMemUsage OBJECT-TYPE
    SYNTAX      Gauge32
    MAX-ACCESS  read-only
    STATUS      current
    DESCRIPTION
        "The current memory usage."
    ::= { dfl800System 12 }

dfl800SysTCPUsage OBJECT IDENTIFIER
    ::= { dfl800System 13 }

dfl800SysTCPRecvSmall OBJECT-TYPE
    SYNTAX      Gauge32
    MAX-ACCESS  read-only
    STATUS      current
    DESCRIPTION
        "Small TCP receive windows usage."
    ::= { dfl800SysTCPUsage 1 }

dfl800SysTCPRecvLarge OBJECT-TYPE
    SYNTAX      Gauge32
    MAX-ACCESS  read-only
    STATUS      current
    DESCRIPTION
        "Large TCP receive windows usage."
    ::= { dfl800SysTCPUsage 2 }

dfl800SysTCPSendSmall OBJECT-TYPE
    SYNTAX      Gauge32
    MAX-ACCESS  read-only
    STATUS      current
    DESCRIPTION
        "Small TCP send windows usage."
    ::= { dfl800SysTCPUsage 3 }

dfl800SysTCPSendLarge OBJECT-TYPE
    SYNTAX      Gauge32
    MAX-ACCESS  read-only
    STATUS      current
    DESCRIPTION
        "Large TCP send windows usage."
    ::= { dfl800SysTCPUsage 4 }

dfl800SysTimerUsage OBJECT-TYPE
    SYNTAX      Gauge32
    MAX-ACCESS  read-only
    STATUS      current
    DESCRIPTION
        "The current number of timers in use."
    ::= { dfl800System 14 }

dfl800SysConnOPS OBJECT-TYPE
    SYNTAX      Gauge32
    MAX-ACCESS  read-only
    STATUS      current
    DESCRIPTION
        "The number of connections opened per second."
    ::= { dfl800System 15 }

dfl800SysConnCPS OBJECT-TYPE
    SYNTAX      Gauge32
    MAX-ACCESS  read-only
    STATUS      current
    DESCRIPTION
        "The number of connections closed per second."
    ::= { dfl800System 16 }

dfl800SysHCForwardedBits OBJECT-TYPE
    SYNTAX      Counter64
    MAX-ACCESS  read-only
    STATUS      current
    DESCRIPTION
        "The number of bits forwarded through the gateway."
    ::= { dfl800System 17 }

dfl800VPN OBJECT IDENTIFIER
    ::= { dfl800OSStats 2 }

dfl800IPsec OBJECT IDENTIFIER
    ::= { dfl800VPN 1 }

dfl800IPsecGlobal OBJECT IDENTIFIER
    ::= { dfl800IPsec 1 }

dfl800IPsecPhaseOneActive OBJECT-TYPE
    SYNTAX      Gauge32
    MAX-ACCESS  read-only
    STATUS      current
    DESCRIPTION
        "Number of Phase-1 active negotiations"
    ::= { dfl800IPsecGlobal 1 }

dfl800IPsecPhaseOneAggrModeDone OBJECT-TYPE
    SYNTAX      Gauge32
    MAX-ACCESS  read-only
    STATUS      current
    DESCRIPTION
        "Number of Phase-1 aggressive mode negotiations."
    ::= { dfl800IPsecGlobal 2 }

dfl800IPsecQuickModeActive OBJECT-TYPE
    SYNTAX      Gauge32
    MAX-ACCESS  read-only
    STATUS      current
    DESCRIPTION
        "Number of quick mode active negotiations."
    ::= { dfl800IPsecGlobal 3 }

dfl800IPsecPhaseOneDone OBJECT-TYPE
    SYNTAX      Counter32
    MAX-ACCESS  read-only
    STATUS      current
    DESCRIPTION
        "Number of Phase-1 negotiations done."
    ::= { dfl800IPsecGlobal 4 }

dfl800IPsecPhaseOneFailed OBJECT-TYPE
    SYNTAX      Counter32
    MAX-ACCESS  read-only
    STATUS      current
    DESCRIPTION
        "Number of Phase-1 negotiations failed."
    ::= { dfl800IPsecGlobal 5 }

dfl800IPsecPhaseOneRekeyed OBJECT-TYPE
    SYNTAX      Counter32
    MAX-ACCESS  read-only
    STATUS      current
    DESCRIPTION
        "Number of Phase-1 negotiations rekeyed."
    ::= { dfl800IPsecGlobal 6 }

dfl800IPsecQuickModeDone OBJECT-TYPE
    SYNTAX      Counter32
    MAX-ACCESS  read-only
    STATUS      current
    DESCRIPTION
        "Number of quick mode  negotiations done."
    ::= { dfl800IPsecGlobal 7 }

dfl800IPsecQuickModeFailed OBJECT-TYPE
    SYNTAX      Counter32
    MAX-ACCESS  read-only
    STATUS      current
    DESCRIPTION
        "Number of quick mode negotiations failed."
    ::= { dfl800IPsecGlobal 8 }

dfl800IPsecInfoDone OBJECT-TYPE
    SYNTAX      Counter32
    MAX-ACCESS  read-only
    STATUS      current
    DESCRIPTION
        "Number of informational exchanges done.
         (Not available in IKEv1 implementations)"
    ::= { dfl800IPsecGlobal 9 }

dfl800IPsecInfoFailed OBJECT-TYPE
    SYNTAX      Counter32
    MAX-ACCESS  read-only
    STATUS      current
    DESCRIPTION
        "Number of informational exchanges failed.
         (Not available in IKEv1 implementations)"
    ::= { dfl800IPsecGlobal 10 }

dfl800IPsecInOctetsComp OBJECT-TYPE
    SYNTAX      Counter64
    MAX-ACCESS  read-only
    STATUS      current
    DESCRIPTION
        "Total octets in before decompression."
    ::= { dfl800IPsecGlobal 11 }

dfl800IPsecInOctetsUncomp OBJECT-TYPE
    SYNTAX      Counter64
    MAX-ACCESS  read-only
    STATUS      current
    DESCRIPTION
        "Total octets in after decompression."
    ::= { dfl800IPsecGlobal 12 }

dfl800IPsecOutOctetsComp OBJECT-TYPE
    SYNTAX      Counter64
    MAX-ACCESS  read-only
    STATUS      current
    DESCRIPTION
        "Total octets out after compression."
    ::= { dfl800IPsecGlobal 13 }

dfl800IPsecOutOctetsUncomp OBJECT-TYPE
    SYNTAX      Counter64
    MAX-ACCESS  read-only
    STATUS      current
    DESCRIPTION
        "Total octets out before compression."
    ::= { dfl800IPsecGlobal 14 }

dfl800IPsecForwardedOctetsComp OBJECT-TYPE
    SYNTAX      Counter64
    MAX-ACCESS  read-only
    STATUS      current
    DESCRIPTION
        "Total octets forwarded after compression."
    ::= { dfl800IPsecGlobal 15 }

dfl800IPsecForwardedOctetsUcomp OBJECT-TYPE
    SYNTAX      Counter64
    MAX-ACCESS  read-only
    STATUS      current
    DESCRIPTION
        "Total octets forwarded before compression."
    ::= { dfl800IPsecGlobal 16 }

dfl800IPsecInPackets OBJECT-TYPE
    SYNTAX      Counter64
    MAX-ACCESS  read-only
    STATUS      current
    DESCRIPTION
        "Total packets in."
    ::= { dfl800IPsecGlobal 17 }

dfl800IPsecOutPackets OBJECT-TYPE
    SYNTAX      Counter64
    MAX-ACCESS  read-only
    STATUS      current
    DESCRIPTION
        "Total packets Out."
    ::= { dfl800IPsecGlobal 18 }

dfl800IPsecForwardedPackets OBJECT-TYPE
    SYNTAX      Counter64
    MAX-ACCESS  read-only
    STATUS      current
    DESCRIPTION
        "Total packets forwarded."
    ::= { dfl800IPsecGlobal 19 }

dfl800IPsecActiveTransforms OBJECT-TYPE
    SYNTAX      Gauge32
    MAX-ACCESS  read-only
    STATUS      current
    DESCRIPTION
        "Number of currently active transforms."
    ::= { dfl800IPsecGlobal 20 }

dfl800IPsecTotalTransforms OBJECT-TYPE
    SYNTAX      Counter32
    MAX-ACCESS  read-only
    STATUS      current
    DESCRIPTION
        "Total number of transform records created."
    ::= { dfl800IPsecGlobal 21 }

dfl800IPsecOutOfTransforms OBJECT-TYPE
    SYNTAX      Counter32
    MAX-ACCESS  read-only
    STATUS      current
    DESCRIPTION
        "Number of packets dropped due to no available transform object.
         (Not available in IKEv1 implementations)"
    ::= { dfl800IPsecGlobal 22 }

dfl800IPsecTotalRekeys OBJECT-TYPE
    SYNTAX      Counter32
    MAX-ACCESS  read-only
    STATUS      current
    DESCRIPTION
        "Total number of rekeys performed."
    ::= { dfl800IPsecGlobal 23 }

dfl800Rules OBJECT IDENTIFIER
    ::= { dfl800OSStats 3 }

dfl800RuleUseTable OBJECT-TYPE
    SYNTAX      SEQUENCE OF Dfl800RuleUseEntry
    MAX-ACCESS  not-accessible
    STATUS      current
    DESCRIPTION
        "A list of general rules usage statistics."
    ::= { dfl800Rules 2 }

dfl800RuleUseEntry OBJECT-TYPE
    SYNTAX      Dfl800RuleUseEntry
    MAX-ACCESS  not-accessible
    STATUS      current
    DESCRIPTION
        "The statistics over a rule usage."
    INDEX       { dfl800RuleIndex }
    ::= { dfl800RuleUseTable 1 }

Dfl800RuleUseEntry ::= SEQUENCE {
    dfl800RuleIndex    Integer32,
    dfl800RuleName     DisplayString,
    dfl800RuleUse      Counter32
}

dfl800RuleIndex OBJECT-TYPE
    SYNTAX      Integer32 (1..2147483647)
    MAX-ACCESS  not-accessible
    STATUS      current
    DESCRIPTION
        "The rule usage index."
    ::= { dfl800RuleUseEntry 1 }

dfl800RuleName OBJECT-TYPE
    SYNTAX      DisplayString
    MAX-ACCESS  read-only
    STATUS      current
    DESCRIPTION
        "The name of the rule."
    ::= { dfl800RuleUseEntry 2 }

dfl800RuleUse OBJECT-TYPE
    SYNTAX      Counter32
    MAX-ACCESS  read-only
    STATUS      current
    DESCRIPTION
        "The number of times o rule was used."
    ::= { dfl800RuleUseEntry 3 }

dfl800IPPools OBJECT IDENTIFIER
    ::= { dfl800OSStats 4 }

dfl800IPPoolsNumber OBJECT-TYPE
    SYNTAX      Integer32
    MAX-ACCESS  read-only
    STATUS      current
    DESCRIPTION
        "The number of ip pools"
    ::= { dfl800IPPools 1 }

dfl800IPPoolTable OBJECT-TYPE
    SYNTAX      SEQUENCE OF Dfl800IPPoolEntry
    MAX-ACCESS  not-accessible
    STATUS      current
    DESCRIPTION
        "A list of IP pools"
    ::= { dfl800IPPools 2 }

dfl800IPPoolEntry OBJECT-TYPE
    SYNTAX      Dfl800IPPoolEntry
    MAX-ACCESS  not-accessible
    STATUS      current
    DESCRIPTION
        "The attributes of an ip pool"
    INDEX       { dfl800IPPoolIndex }
    ::= { dfl800IPPoolTable 1 }

Dfl800IPPoolEntry ::= SEQUENCE {
    dfl800IPPoolIndex          Integer32,
    dfl800IPPoolName           DisplayString,
    dfl800IPPoolPrepare        Gauge32,
    dfl800IPPoolFree           Gauge32,
    dfl800IPPoolMisses         Gauge32,
    dfl800IPPoolClientFails    Gauge32,
    dfl800IPPoolUsed           Gauge32
}

dfl800IPPoolIndex OBJECT-TYPE
    SYNTAX      Integer32 (1..2147483647)
    MAX-ACCESS  not-accessible
    STATUS      current
    DESCRIPTION
        "The ip pool index"
    ::= { dfl800IPPoolEntry 1 }

dfl800IPPoolName OBJECT-TYPE
    SYNTAX      DisplayString
    MAX-ACCESS  read-only
    STATUS      current
    DESCRIPTION
        "The ip pool name"
    ::= { dfl800IPPoolEntry 2 }

dfl800IPPoolPrepare OBJECT-TYPE
    SYNTAX      Gauge32
    MAX-ACCESS  read-only
    STATUS      current
    DESCRIPTION
        "Number of IP pool objects in prepare mode."
    ::= { dfl800IPPoolEntry 3 }

dfl800IPPoolFree OBJECT-TYPE
    SYNTAX      Gauge32
    MAX-ACCESS  read-only
    STATUS      current
    DESCRIPTION
        "Number of available IPs in the pool."
    ::= { dfl800IPPoolEntry 4 }

dfl800IPPoolMisses OBJECT-TYPE
    SYNTAX      Gauge32
    MAX-ACCESS  read-only
    STATUS      current
    DESCRIPTION
        "Mumber of missed IP pool negotiations for other reasons
         than lack of available IP numbers."
    ::= { dfl800IPPoolEntry 5 }

dfl800IPPoolClientFails OBJECT-TYPE
    SYNTAX      Gauge32
    MAX-ACCESS  read-only
    STATUS      current
    DESCRIPTION
        "Number of failed IP pool transactions."
    ::= { dfl800IPPoolEntry 6 }

dfl800IPPoolUsed OBJECT-TYPE
    SYNTAX      Gauge32
    MAX-ACCESS  read-only
    STATUS      current
    DESCRIPTION
        "Number of IP numbers in use from the pool."
    ::= { dfl800IPPoolEntry 7 }

dfl800DHCPServer OBJECT IDENTIFIER
    ::= { dfl800OSStats 5 }

dfl800DHCPTotalRejected OBJECT-TYPE
    SYNTAX      Gauge32
    MAX-ACCESS  read-only
    STATUS      current
    DESCRIPTION
        "Total number of rejected packets (all rules)."
    ::= { dfl800DHCPServer 1 }

dfl800DHCPRuleTable OBJECT-TYPE
    SYNTAX      SEQUENCE OF Dfl800DHCPRuleEntry
    MAX-ACCESS  not-accessible
    STATUS      current
    DESCRIPTION
        "A list of all DHCP server rules usage statistics."
    ::= { dfl800DHCPServer 2 }

dfl800DHCPRuleEntry OBJECT-TYPE
    SYNTAX      Dfl800DHCPRuleEntry
    MAX-ACCESS  not-accessible
    STATUS      current
    DESCRIPTION
        "The attributes of a DHCP server rule statistics."
    INDEX       { dfl800DHCPRuleIndex }
    ::= { dfl800DHCPRuleTable 1 }

Dfl800DHCPRuleEntry ::= SEQUENCE {
    dfl800DHCPRuleIndex                Integer32,
    dfl800DHCPRuleName                 DisplayString,
    dfl800DHCPRuleUsage                Gauge32,
    dfl800DHCPRuleUsagePercent         Gauge32,
    dfl800DHCPActiveClients            Gauge32,
    dfl800DHCPActiveClientsPercent     Gauge32,
    dfl800DHCPRejectedRequests         Gauge32,
    dfl800DHCPTotalLeases              Gauge32
}

dfl800DHCPRuleIndex OBJECT-TYPE
    SYNTAX      Integer32 (1..2147483647)
    MAX-ACCESS  not-accessible
    STATUS      current
    DESCRIPTION
        "The DHCP server rule  index"
    ::= { dfl800DHCPRuleEntry 1 }

dfl800DHCPRuleName OBJECT-TYPE
    SYNTAX      DisplayString
    MAX-ACCESS  read-only
    STATUS      current
    DESCRIPTION
        "The DHCP server rule name."
    ::= { dfl800DHCPRuleEntry 2 }

dfl800DHCPRuleUsage OBJECT-TYPE
    SYNTAX      Gauge32
    MAX-ACCESS  read-only
    STATUS      current
    DESCRIPTION
        "Number of used IPs in the pool."
    ::= { dfl800DHCPRuleEntry 3 }

dfl800DHCPRuleUsagePercent OBJECT-TYPE
    SYNTAX      Gauge32
    MAX-ACCESS  read-only
    STATUS      current
    DESCRIPTION
        "The percentage of the used IPs in
         relation to the IP pool size."
    ::= { dfl800DHCPRuleEntry 4 }

dfl800DHCPActiveClients OBJECT-TYPE
    SYNTAX      Gauge32
    MAX-ACCESS  read-only
    STATUS      current
    DESCRIPTION
        "Number of currently active clients."
    ::= { dfl800DHCPRuleEntry 5 }

dfl800DHCPActiveClientsPercent OBJECT-TYPE
    SYNTAX      Gauge32
    MAX-ACCESS  read-only
    STATUS      current
    DESCRIPTION
        "The number of currently active clients
         as a percentage of the pool size."
    ::= { dfl800DHCPRuleEntry 6 }

dfl800DHCPRejectedRequests OBJECT-TYPE
    SYNTAX      Gauge32
    MAX-ACCESS  read-only
    STATUS      current
    DESCRIPTION
        "Number of rejected requests matching
         the current rule."
    ::= { dfl800DHCPRuleEntry 7 }

dfl800DHCPTotalLeases OBJECT-TYPE
    SYNTAX      Gauge32
    MAX-ACCESS  read-only
    STATUS      current
    DESCRIPTION
        "Total number of leases in the pool."
    ::= { dfl800DHCPRuleEntry 8 }

dfl800UserAuth OBJECT IDENTIFIER
    ::= { dfl800OSStats 6 }

dfl800UserAuthHTTPUsers OBJECT-TYPE
    SYNTAX      Gauge32
    MAX-ACCESS  read-only
    STATUS      current
    DESCRIPTION
        "Number of currently  logged in HTTP users."
    ::= { dfl800UserAuth 1 }

dfl800UserAuthXAUTHUsers OBJECT-TYPE
    SYNTAX      Gauge32
    MAX-ACCESS  read-only
    STATUS      current
    DESCRIPTION
        "Number of currently logged in XAUTH users."
    ::= { dfl800UserAuth 2 }

dfl800UserAuthHTTPSUsers OBJECT-TYPE
    SYNTAX      Gauge32
    MAX-ACCESS  read-only
    STATUS      current
    DESCRIPTION
        "Number of currently logged in HTTPS users."
    ::= { dfl800UserAuth 3 }

dfl800UserAuthPPPUsers OBJECT-TYPE
    SYNTAX      Gauge32
    MAX-ACCESS  read-only
    STATUS      current
    DESCRIPTION
        "Number of currently logged in PPP users."
    ::= { dfl800UserAuth 4 }

dfl800UserAuthEAPUsers OBJECT-TYPE
    SYNTAX      Gauge32
    MAX-ACCESS  read-only
    STATUS      current
    DESCRIPTION
        "Number of currently logged in EAP users."
    ::= { dfl800UserAuth 5 }

dfl800UserAuthRuleUseTable OBJECT-TYPE
    SYNTAX      SEQUENCE OF Dfl800UserAuthRuleUseEntry
    MAX-ACCESS  not-accessible
    STATUS      current
    DESCRIPTION
        "Table of user authentication rule usage."
    ::= { dfl800UserAuth 6 }

dfl800UserAuthRuleUseEntry OBJECT-TYPE
    SYNTAX      Dfl800UserAuthRuleUseEntry
    MAX-ACCESS  not-accessible
    STATUS      current
    DESCRIPTION
        "The attributes of an authentication rule
         usage statistics."
    INDEX       { dfl800UserAuthRuleIndex }
    ::= { dfl800UserAuthRuleUseTable 1 }

Dfl800UserAuthRuleUseEntry ::= SEQUENCE {
    dfl800UserAuthRuleIndex    Integer32,
    dfl800UserAuthRuleName     DisplayString,
    dfl800UserAuthRuleUse      Counter32
}

dfl800UserAuthRuleIndex OBJECT-TYPE
    SYNTAX      Integer32 (1..2147483647)
    MAX-ACCESS  not-accessible
    STATUS      current
    DESCRIPTION
        "The rule usage index."
    ::= { dfl800UserAuthRuleUseEntry 1 }

dfl800UserAuthRuleName OBJECT-TYPE
    SYNTAX      DisplayString
    MAX-ACCESS  read-only
    STATUS      current
    DESCRIPTION
        "The name of the rule."
    ::= { dfl800UserAuthRuleUseEntry 2 }

dfl800UserAuthRuleUse OBJECT-TYPE
    SYNTAX      Counter32
    MAX-ACCESS  read-only
    STATUS      current
    DESCRIPTION
        "The number of times o rule was used."
    ::= { dfl800UserAuthRuleUseEntry 3 }

dfl800LinkMonitor OBJECT IDENTIFIER
    ::= { dfl800OSStats 7 }

dfl800LinkMonGrp OBJECT-TYPE
    SYNTAX      Integer32
    MAX-ACCESS  read-only
    STATUS      current
    DESCRIPTION
        "The number of groups of monitored links"
    ::= { dfl800LinkMonitor 1 }

dfl800LinkMonGrpTable OBJECT-TYPE
    SYNTAX      SEQUENCE OF Dfl800LinkMonGrpEntry
    MAX-ACCESS  not-accessible
    STATUS      current
    DESCRIPTION
        "Table of link monitor groups."
    ::= { dfl800LinkMonitor 2 }

dfl800LinkMonGrpEntry OBJECT-TYPE
    SYNTAX      Dfl800LinkMonGrpEntry
    MAX-ACCESS  not-accessible
    STATUS      current
    DESCRIPTION
        "The attributes of a link monitor group"
    INDEX       { dfl800LinkMonGrpIndex }
    ::= { dfl800LinkMonGrpTable 1 }

Dfl800LinkMonGrpEntry ::= SEQUENCE {
    dfl800LinkMonGrpIndex      Integer32,
    dfl800LinkMonGrpName       DisplayString,
    dfl800LinkMonGrpHostsUp    Gauge32
}

dfl800LinkMonGrpIndex OBJECT-TYPE
    SYNTAX      Integer32 (1..2147483647)
    MAX-ACCESS  not-accessible
    STATUS      current
    DESCRIPTION
        "The index row in the table of link monitor groups."
    ::= { dfl800LinkMonGrpEntry 1 }

dfl800LinkMonGrpName OBJECT-TYPE
    SYNTAX      DisplayString
    MAX-ACCESS  read-only
    STATUS      current
    DESCRIPTION
        "The link monitor group name."
    ::= { dfl800LinkMonGrpEntry 2 }

dfl800LinkMonGrpHostsUp OBJECT-TYPE
    SYNTAX      Gauge32
    MAX-ACCESS  read-only
    STATUS      current
    DESCRIPTION
        "The percentage of monitored hosts available."
    ::= { dfl800LinkMonGrpEntry 3 }

dfl800LinkMonHostTable OBJECT-TYPE
    SYNTAX      SEQUENCE OF Dfl800LinkMonHostEntry
    MAX-ACCESS  not-accessible
    STATUS      current
    DESCRIPTION
        "Table of link monitored hosts in a link monnitor group."
    ::= { dfl800LinkMonitor 3 }

dfl800LinkMonHostEntry OBJECT-TYPE
    SYNTAX      Dfl800LinkMonHostEntry
    MAX-ACCESS  not-accessible
    STATUS      current
    DESCRIPTION
        "The attributes of a monitored host."
    INDEX       { dfl800LinkMonGrpIndex, dfl800LinkMonHostIndex }
    ::= { dfl800LinkMonHostTable 1 }

Dfl800LinkMonHostEntry ::= SEQUENCE {
    dfl800LinkMonHostIndex             Integer32,
    dfl800LinkMonHostId                DisplayString,
    dfl800LinkMonHostShortTermLoss     Gauge32,
    dfl800LinkMonHostPacketsLost       Counter32
}

dfl800LinkMonHostIndex OBJECT-TYPE
    SYNTAX      Integer32 (1..2147483647)
    MAX-ACCESS  not-accessible
    STATUS      current
    DESCRIPTION
        "The index an host in the table of link monitor hosts."
    ::= { dfl800LinkMonHostEntry 1 }

dfl800LinkMonHostId OBJECT-TYPE
    SYNTAX      DisplayString
    MAX-ACCESS  read-only
    STATUS      current
    DESCRIPTION
        "The monitored host identifier."
    ::= { dfl800LinkMonHostEntry 2 }

dfl800LinkMonHostShortTermLoss OBJECT-TYPE
    SYNTAX      Gauge32
    MAX-ACCESS  read-only
    STATUS      current
    DESCRIPTION
        "The percentage of short term losst packets."
    ::= { dfl800LinkMonHostEntry 3 }

dfl800LinkMonHostPacketsLost OBJECT-TYPE
    SYNTAX      Counter32
    MAX-ACCESS  read-only
    STATUS      current
    DESCRIPTION
        "Total number of lost monitoring packets."
    ::= { dfl800LinkMonHostEntry 4 }

dfl800Pipes OBJECT IDENTIFIER
    ::= { dfl800OSStats 8 }

dfl800PipeUsers OBJECT-TYPE
    SYNTAX      Gauge32
    MAX-ACCESS  read-only
    STATUS      current
    DESCRIPTION
        "The current number of users, as defined by the grouping
         settings of each pipe, being tracked in the pipes system.
         Note that this value corresponds to the number of users
         active in each time slice of 1/20th of a second, and not
         to the number of users having open connections."
    ::= { dfl800Pipes 1 }

dfl800PipeTable OBJECT-TYPE
    SYNTAX      SEQUENCE OF Dfl800PipeEntry
    MAX-ACCESS  not-accessible
    STATUS      current
    DESCRIPTION
        "Table of pipes"
    ::= { dfl800Pipes 2 }

dfl800PipeEntry OBJECT-TYPE
    SYNTAX      Dfl800PipeEntry
    MAX-ACCESS  not-accessible
    STATUS      current
    DESCRIPTION
        "A entry of the pipes table"
    INDEX       { dfl800PipeIndex }
    ::= { dfl800PipeTable 1 }

Dfl800PipeEntry ::= SEQUENCE {
    dfl800PipeIndex            Integer32,
    dfl800PipeName             DisplayString,
    dfl800PipeMinPrec          Integer32,
    dfl800PipeMaxPrec          Integer32,
    dfl800PipeDefPrec          Integer32,
    dfl800PipeNumPrec          Integer32,
    dfl800PipeNumUsers         Gauge32,
    dfl800PipeCurrentBps       Gauge32,
    dfl800PipeCurrentPps       Gauge32,
    dfl800PipeDelayedPackets   Counter32,
    dfl800PipeDropedPackets    Counter32
}

dfl800PipeIndex OBJECT-TYPE
    SYNTAX      Integer32 (1..2147483647)
    MAX-ACCESS  not-accessible
    STATUS      current
    DESCRIPTION
        "The pipe index"
    ::= { dfl800PipeEntry 1 }

dfl800PipeName OBJECT-TYPE
    SYNTAX      DisplayString
    MAX-ACCESS  read-only
    STATUS      current
    DESCRIPTION
        "The name of the pipe"
    ::= { dfl800PipeEntry 2 }

dfl800PipeMinPrec OBJECT-TYPE
    SYNTAX      Integer32
    MAX-ACCESS  read-only
    STATUS      current
    DESCRIPTION
        "The minimum of the range of pipe precedences."
    ::= { dfl800PipeEntry 3 }

dfl800PipeMaxPrec OBJECT-TYPE
    SYNTAX      Integer32
    MAX-ACCESS  read-only
    STATUS      current
    DESCRIPTION
        "The maximum of the range of pipe precedences."
    ::= { dfl800PipeEntry 4 }

dfl800PipeDefPrec OBJECT-TYPE
    SYNTAX      Integer32
    MAX-ACCESS  read-only
    STATUS      current
    DESCRIPTION
        "The precedence assigned to a packet for which has not one
         allready done by a Pipe Rule."
    ::= { dfl800PipeEntry 5 }

dfl800PipeNumPrec OBJECT-TYPE
    SYNTAX      Integer32
    MAX-ACCESS  read-only
    STATUS      current
    DESCRIPTION
        "The number of pipe precedences"
    ::= { dfl800PipeEntry 6 }

dfl800PipeNumUsers OBJECT-TYPE
    SYNTAX      Gauge32
    MAX-ACCESS  read-only
    STATUS      current
    DESCRIPTION
        "The current number of users, as defined by the grouping settings
         of each pipe, being tracked in the pipes system. This value
         corresponds to the number of users active in each time slice
         and not to the number of users having  open connections."
    ::= { dfl800PipeEntry 7 }

dfl800PipeCurrentBps OBJECT-TYPE
    SYNTAX      Gauge32
    MAX-ACCESS  read-only
    STATUS      current
    DESCRIPTION
        "The current throughput of a pipe, in bits per second, as a sum of
         the corresponding values for all precedences."
    ::= { dfl800PipeEntry 8 }

dfl800PipeCurrentPps OBJECT-TYPE
    SYNTAX      Gauge32
    MAX-ACCESS  read-only
    STATUS      current
    DESCRIPTION
        "The current throughput of a pipe, in packets per second, as a sum of
         the corresponding values for all precedences."
    ::= { dfl800PipeEntry 9 }

dfl800PipeDelayedPackets OBJECT-TYPE
    SYNTAX      Counter32
    MAX-ACCESS  read-only
    STATUS      current
    DESCRIPTION
        "The number of times packets have been delayed as a result of a pipe,
         or pipe user having used up its allotted bandwidth. Note that one single
         packet may be delayed several times; if a pipe is really full, this
         count may exceed the number of packets actually passing through the
         pipe."
    ::= { dfl800PipeEntry 10 }

dfl800PipeDropedPackets OBJECT-TYPE
    SYNTAX      Counter32
    MAX-ACCESS  read-only
    STATUS      current
    DESCRIPTION
        "The number of packets dropped by a pipe. Packets are dropped when
         CorePlus is running out of packet buffers. This occurs when excessive
         amounts of packets need to be queued for later delivery. The packet
         dropped is always the one that has been queued the longest time
         globally, which means that the connection suffering from packet loss
         will be the one most overloading the system."
    ::= { dfl800PipeEntry 11 }

dfl800PipePrecTable OBJECT-TYPE
    SYNTAX      SEQUENCE OF Dfl800PipePrecEntry
    MAX-ACCESS  not-accessible
    STATUS      current
    DESCRIPTION
        "There is a one to many relation between a pipe and its precedences.
         The number of precedences is a instance attribute of each pipe.
         This table extends the pipes table in order to express the relation
         between a pipe and the respective precedences."
    ::= { dfl800Pipes 3 }

dfl800PipePrecEntry OBJECT-TYPE
    SYNTAX      Dfl800PipePrecEntry
    MAX-ACCESS  not-accessible
    STATUS      current
    DESCRIPTION
        "An entry of the table of pipe pecedences. These table entries
         are chracterized by been indexed by two values. The first index
         the same as the pipe index of the corresponding row in table of
         pipes and the second index is the index of the set of precedences
         of the corresponding pipe."
    INDEX       { dfl800PipeIndex, dfl800PipePrecIndex }
    ::= { dfl800PipePrecTable 1 }

Dfl800PipePrecEntry ::= SEQUENCE {
    dfl800PipePrecIndex            Integer32,
    dfl800PipePrec                 Integer32,
    dfl800PipePrecBps              Gauge32,
    dfl800PipePrecTotalPps         Gauge32,
    dfl800PipePrecReservedBps      Gauge32,
    dfl800PipePrecDynLimBps        Gauge32,
    dfl800PipePrecDynUsrLimBps     Gauge32,
    dfl800PipePrecDelayedPackets   Counter32,
    dfl800PipePrecDropedPackets    Counter32
}

dfl800PipePrecIndex OBJECT-TYPE
    SYNTAX      Integer32 (1..2147483647)
    MAX-ACCESS  not-accessible
    STATUS      current
    DESCRIPTION
        "Index of a precedence of a specific pipe. This is the second index
         of the entries of pipe precedence table described by object
         dfl800PipePrecEntry."
    ::= { dfl800PipePrecEntry 1 }

dfl800PipePrec OBJECT-TYPE
    SYNTAX      Integer32
    MAX-ACCESS  read-only
    STATUS      current
    DESCRIPTION
        "The precedence value"
    ::= { dfl800PipePrecEntry 2 }

dfl800PipePrecBps OBJECT-TYPE
    SYNTAX      Gauge32
    MAX-ACCESS  read-only
    STATUS      current
    DESCRIPTION
        "The current throughput of the pipe, in bits per second, with
         the corresponding precedence."
    ::= { dfl800PipePrecEntry 3 }

dfl800PipePrecTotalPps OBJECT-TYPE
    SYNTAX      Gauge32
    MAX-ACCESS  read-only
    STATUS      current
    DESCRIPTION
        "The current throughput of the pipe precedence, in packets per second."
    ::= { dfl800PipePrecEntry 4 }

dfl800PipePrecReservedBps OBJECT-TYPE
    SYNTAX      Gauge32
    MAX-ACCESS  read-only
    STATUS      current
    DESCRIPTION
        "The current bandwidth allocated to the precedence."
    ::= { dfl800PipePrecEntry 5 }

dfl800PipePrecDynLimBps OBJECT-TYPE
    SYNTAX      Gauge32
    MAX-ACCESS  read-only
    STATUS      current
    DESCRIPTION
        "The current bandwidth limit limit applied the precedence."
    ::= { dfl800PipePrecEntry 6 }

dfl800PipePrecDynUsrLimBps OBJECT-TYPE
    SYNTAX      Gauge32
    MAX-ACCESS  read-only
    STATUS      current
    DESCRIPTION
        "The current precedence bandwidth limit per user of the pipe."
    ::= { dfl800PipePrecEntry 7 }

dfl800PipePrecDelayedPackets OBJECT-TYPE
    SYNTAX      Counter32
    MAX-ACCESS  read-only
    STATUS      current
    DESCRIPTION
        "The number of times packets have been delayed as a result of a
         precedence, or pipe user having used up its allotted bandwidth.
         Note that one single packet may be delayed several times; if a
         pipe is really full, this count may exceed the number of packets
         of this precedence actually passing through the pipe."
    ::= { dfl800PipePrecEntry 8 }

dfl800PipePrecDropedPackets OBJECT-TYPE
    SYNTAX      Counter32
    MAX-ACCESS  read-only
    STATUS      current
    DESCRIPTION
        "The number of pipe dropped packets with the corresponding precedence."
    ::= { dfl800PipePrecEntry 9 }

dfl800ALG OBJECT IDENTIFIER
    ::= { dfl800OSStats 9 }

dfl800AlgSessions OBJECT-TYPE
    SYNTAX      Gauge32
    MAX-ACCESS  read-only
    STATUS      current
    DESCRIPTION
        "Total ALG sessions"
    ::= { dfl800ALG 1 }

dfl800AlgConnections OBJECT-TYPE
    SYNTAX      Gauge32
    MAX-ACCESS  read-only
    STATUS      current
    DESCRIPTION
        "Total ALG connections"
    ::= { dfl800ALG 2 }

dfl800AlgTCPStreams OBJECT-TYPE
    SYNTAX      Gauge32
    MAX-ACCESS  read-only
    STATUS      current
    DESCRIPTION
        "Total ALG TCP streams"
    ::= { dfl800ALG 3 }

dfl800HttpAlg OBJECT IDENTIFIER
    ::= { dfl800ALG 4 }

dfl800HttpAlgTable OBJECT-TYPE
    SYNTAX      SEQUENCE OF Dfl800HttpAlgEntry
    MAX-ACCESS  not-accessible
    STATUS      current
    DESCRIPTION
        "Table of HTTP ALG objects."
    ::= { dfl800HttpAlg 1 }

dfl800HttpAlgEntry OBJECT-TYPE
    SYNTAX      Dfl800HttpAlgEntry
    MAX-ACCESS  not-accessible
    STATUS      current
    DESCRIPTION
        "A row of the table of HTTP ALG objects."
    INDEX       { dfl800HttpAlgIndex }
    ::= { dfl800HttpAlgTable 1 }

Dfl800HttpAlgEntry ::= SEQUENCE {
    dfl800HttpAlgIndex             Integer32,
    dfl800HttpAlgName              DisplayString,
    dfl800HttpAlgTotalRequested    Gauge32,
    dfl800HttpAlgTotalAllowed      Gauge32,
    dfl800HttpAlgTotalBlocked      Gauge32
}

dfl800HttpAlgIndex OBJECT-TYPE
    SYNTAX      Integer32 (1..2147483647)
    MAX-ACCESS  not-accessible
    STATUS      current
    DESCRIPTION
        "The index of an entry of the  Table of HTTP ALG objects."
    ::= { dfl800HttpAlgEntry 1 }

dfl800HttpAlgName OBJECT-TYPE
    SYNTAX      DisplayString
    MAX-ACCESS  read-only
    STATUS      current
    DESCRIPTION
        "The name of an HTTP ALG object."
    ::= { dfl800HttpAlgEntry 2 }

dfl800HttpAlgTotalRequested OBJECT-TYPE
    SYNTAX      Gauge32
    MAX-ACCESS  read-only
    STATUS      current
    DESCRIPTION
        "Total number of URL requests."
    ::= { dfl800HttpAlgEntry 3 }

dfl800HttpAlgTotalAllowed OBJECT-TYPE
    SYNTAX      Gauge32
    MAX-ACCESS  read-only
    STATUS      current
    DESCRIPTION
        "Total number of allowed URL requests."
    ::= { dfl800HttpAlgEntry 4 }

dfl800HttpAlgTotalBlocked OBJECT-TYPE
    SYNTAX      Gauge32
    MAX-ACCESS  read-only
    STATUS      current
    DESCRIPTION
        "Total number of blocked URL requests."
    ::= { dfl800HttpAlgEntry 5 }

dfl800HttpAlgCntFltTable OBJECT-TYPE
    SYNTAX      SEQUENCE OF Dfl800HttpAlgCntFltEntry
    MAX-ACCESS  not-accessible
    STATUS      current
    DESCRIPTION
        "Table of HTTP ALG content filtering rules."
    ::= { dfl800HttpAlg 2 }

dfl800HttpAlgCntFltEntry OBJECT-TYPE
    SYNTAX      Dfl800HttpAlgCntFltEntry
    MAX-ACCESS  not-accessible
    STATUS      current
    DESCRIPTION
        "Entry of the table of HTTP ALG content filtering rules."
    INDEX       { dfl800HttpAlgIndex, dfl800HttpAlgCntFltIndex }
    ::= { dfl800HttpAlgCntFltTable 1 }

Dfl800HttpAlgCntFltEntry ::= SEQUENCE {
    dfl800HttpAlgCntFltIndex       Integer32,
    dfl800HttpAlgCntFltName        DisplayString,
    dfl800HttpAlgCntFltRequests    Gauge32,
    dfl800HttpAlgCntFltAllowed     Gauge32,
    dfl800HttpAlgCntFltBlocked     Gauge32
}

dfl800HttpAlgCntFltIndex OBJECT-TYPE
    SYNTAX      Integer32 (1..2147483647)
    MAX-ACCESS  not-accessible
    STATUS      current
    DESCRIPTION
        "The index of an entry of the  Table of HTTP ALG
         content filtering objects."
    ::= { dfl800HttpAlgCntFltEntry 1 }

dfl800HttpAlgCntFltName OBJECT-TYPE
    SYNTAX      DisplayString
    MAX-ACCESS  read-only
    STATUS      current
    DESCRIPTION
        "The name of the a HTTP ALG content fitering."
    ::= { dfl800HttpAlgCntFltEntry 2 }

dfl800HttpAlgCntFltRequests OBJECT-TYPE
    SYNTAX      Gauge32
    MAX-ACCESS  read-only
    STATUS      current
    DESCRIPTION
        "Total number of URLs intercepted by a content
         filtering object."
    ::= { dfl800HttpAlgCntFltEntry 3 }

dfl800HttpAlgCntFltAllowed OBJECT-TYPE
    SYNTAX      Gauge32
    MAX-ACCESS  read-only
    STATUS      current
    DESCRIPTION
        "Total number of URLs intercepted and allowed
         by a content filtering object."
    ::= { dfl800HttpAlgCntFltEntry 4 }

dfl800HttpAlgCntFltBlocked OBJECT-TYPE
    SYNTAX      Gauge32
    MAX-ACCESS  read-only
    STATUS      current
    DESCRIPTION
        "Total number of URLs intercepted and blocked
         by a content filtering object."
    ::= { dfl800HttpAlgCntFltEntry 5 }

dfl800SmtpAlg OBJECT IDENTIFIER
    ::= { dfl800ALG 5 }

dfl800SmtpAlgTable OBJECT-TYPE
    SYNTAX  SEQUENCE OF Dfl800SmtpAlgEntry
    MAX-ACCESS  not-accessible
    STATUS  current
    DESCRIPTION
  "Table of SMTP ALG objects."
    ::= { dfl800SmtpAlg 1 }

dfl800SmtpAlgEntry OBJECT-TYPE
   SYNTAX  Dfl800SmtpAlgEntry
   MAX-ACCESS  not-accessible
    STATUS      current
    DESCRIPTION
        "A row of the table of SMTP ALG objects."
    INDEX       { dfl800SmtpAlgIndex }
    ::= { dfl800SmtpAlgTable 1 }

Dfl800SmtpAlgEntry ::= SEQUENCE {
    dfl800SmtpAlgIndex           Integer32,
    dfl800SmtpAlgName            DisplayString,
    dfl800SmtpAlgTotCheckedSes   Gauge32,
    dfl800SmtpAlgTotSpamSes      Gauge32,
    dfl800SmtpAlgTotDroppedSes   Gauge32
}

dfl800SmtpAlgIndex OBJECT-TYPE
    SYNTAX      Integer32 (1..2147483647)
    MAX-ACCESS  not-accessible
    STATUS      current
    DESCRIPTION
        "The index of an entry of the  Table of SMTP ALG objects."
    ::= { dfl800SmtpAlgEntry 1 }

dfl800SmtpAlgName OBJECT-TYPE
    SYNTAX      DisplayString
    MAX-ACCESS  read-only
    STATUS      current
    DESCRIPTION
        "The name of an SMTP ALG object."
    ::= { dfl800SmtpAlgEntry 2 }

dfl800SmtpAlgTotCheckedSes OBJECT-TYPE
    SYNTAX      Gauge32
    MAX-ACCESS  read-only
    STATUS      current
    DESCRIPTION
        "Total sessions checked by the SMTP ALG of corresponding index."
    ::= { dfl800SmtpAlgEntry 3 }

dfl800SmtpAlgTotSpamSes OBJECT-TYPE
    SYNTAX      Gauge32
    MAX-ACCESS  read-only
    STATUS      current
    DESCRIPTION
        "Total spam sessions detected by the SMTP ALG of corresponding index."
    ::= { dfl800SmtpAlgEntry 4 }

dfl800SmtpAlgTotDroppedSes OBJECT-TYPE
    SYNTAX      Gauge32
    MAX-ACCESS  read-only
    STATUS      current
    DESCRIPTION
        "Total deroped sessions for the SMTP ALG of corresponding index."
    ::= { dfl800SmtpAlgEntry 5 }


dfl800SmtpAlgDnsBlTable OBJECT-TYPE
    SYNTAX  SEQUENCE OF Dfl800SmtpAlgDnsBlEntry
    MAX-ACCESS  not-accessible
    STATUS  current
    DESCRIPTION
  "Table of SMTP ALG DNS balck list objects."
    ::= { dfl800SmtpAlg 2 }


dfl800SmtpAlgDnsBlEntry OBJECT-TYPE
   SYNTAX  Dfl800SmtpAlgDnsBlEntry
   MAX-ACCESS  not-accessible
    STATUS      current
    DESCRIPTION
        "A row of the table of SMTP ALG DNS black list objects."
    INDEX       { dfl800SmtpAlgIndex, dfl800SmtpAlgDnsBlIndex }
    ::= { dfl800SmtpAlgDnsBlTable 1 }


Dfl800SmtpAlgDnsBlEntry ::= SEQUENCE {
    dfl800SmtpAlgDnsBlIndex  Integer32,
    dfl800SmtpAlgDnsBlName    DisplayString,
    dfl800SmtpAlgDnsBlChecked      Gauge32,
    dfl800SmtpAlgDnsBlMatched  Gauge32,
    dfl800SmtpAlgDnsBlFailChecks  Gauge32
}

dfl800SmtpAlgDnsBlIndex OBJECT-TYPE
    SYNTAX      Integer32 (1..2147483647)
    MAX-ACCESS  not-accessible
    STATUS      current
    DESCRIPTION
        "The index of an entry of the  SMTP ALG DNS black list objects."
    ::= { dfl800SmtpAlgDnsBlEntry 1 }

dfl800SmtpAlgDnsBlName OBJECT-TYPE
    SYNTAX      DisplayString
    MAX-ACCESS  read-only
    STATUS      current
    DESCRIPTION
  "The SMTP DNS black list name."
    ::= { dfl800SmtpAlgDnsBlEntry 2 }

dfl800SmtpAlgDnsBlChecked OBJECT-TYPE
    SYNTAX      Gauge32
    MAX-ACCESS  read-only
    STATUS      current
    DESCRIPTION
  "Total sessions checked againt SMTP ALG DNS black list of corresponding index"
    ::= { dfl800SmtpAlgDnsBlEntry 3 }

dfl800SmtpAlgDnsBlMatched OBJECT-TYPE
    SYNTAX      Gauge32
    MAX-ACCESS  read-only
    STATUS      current
    DESCRIPTION
  "Total sessions that matched SMTP ALG DNS black list of corresponding index"
    ::= { dfl800SmtpAlgDnsBlEntry 4 }

dfl800SmtpAlgDnsBlFailChecks OBJECT-TYPE
    SYNTAX      Gauge32
    MAX-ACCESS  read-only
    STATUS      current
    DESCRIPTION
  "Total failed checks for the SMTP ALG DNS black list of corresponding index"
    ::= { dfl800SmtpAlgDnsBlEntry 5 }

dfl800DHCPRelay OBJECT IDENTIFIER
    ::= { dfl800OSStats 11 }

dfl800DHCPRelayCurClients OBJECT-TYPE
    SYNTAX      Gauge32
    MAX-ACCESS  read-only
    STATUS      current
    DESCRIPTION
        "Total DHCP relay active relayed clients."
    ::= { dfl800DHCPRelay 1 }

dfl800DHCPRelayCurTrans OBJECT-TYPE
    SYNTAX      Gauge32
    MAX-ACCESS  read-only
    STATUS      current
    DESCRIPTION
        "Ongoing DHCP relay transactions."
    ::= { dfl800DHCPRelay 2 }

dfl800DHCPRelayRejected OBJECT-TYPE
    SYNTAX      Gauge32
    MAX-ACCESS  read-only
    STATUS      current
    DESCRIPTION
        "Total DHCP relay packets rejected."
    ::= { dfl800DHCPRelay 3 }

dfl800DHCPRelayRuleTable OBJECT-TYPE
    SYNTAX      SEQUENCE OF Dfl800DHCPRelayRuleEntry
    MAX-ACCESS  not-accessible
    STATUS      current
    DESCRIPTION
        "Table of DHCP relay rules."
    ::= { dfl800DHCPRelay 4 }

dfl800DHCPRelayRuleEntry OBJECT-TYPE
    SYNTAX      Dfl800DHCPRelayRuleEntry
    MAX-ACCESS  not-accessible
    STATUS      current
    DESCRIPTION
        "Entry of the table of DHCP relay rules"
    INDEX       { dfl800DHCPRelayRuleIndex }
    ::= { dfl800DHCPRelayRuleTable 1 }

Dfl800DHCPRelayRuleEntry ::= SEQUENCE {
    dfl800DHCPRelayRuleIndex       Integer32,
    dfl800DHCPRelayRuleName        DisplayString,
    dfl800DHCPRelayRuleHits        Gauge32,
    dfl800DHCPRelayRuleCurClients  Gauge32,
    dfl800DHCPRelayRuleRejCliPkts  Gauge32,
    dfl800DHCPRelayRuleRejSrvPkts  Gauge32
}

dfl800DHCPRelayRuleIndex OBJECT-TYPE
    SYNTAX      Integer32 (1..2147483647)
    MAX-ACCESS  not-accessible
    STATUS      current
    DESCRIPTION
        "Index of the table of DHCP relay rules."
    ::= { dfl800DHCPRelayRuleEntry 1 }

dfl800DHCPRelayRuleName OBJECT-TYPE
    SYNTAX      DisplayString
    MAX-ACCESS  read-only
    STATUS      current
    DESCRIPTION
        "Display name of a DHCP relay rule"
    ::= { dfl800DHCPRelayRuleEntry 2 }

dfl800DHCPRelayRuleHits OBJECT-TYPE
    SYNTAX      Gauge32
    MAX-ACCESS  read-only
    STATUS      current
    DESCRIPTION
        "Number of the times the  DHCP relay rule with corresponding index was
         used."
    ::= { dfl800DHCPRelayRuleEntry 3 }

dfl800DHCPRelayRuleCurClients OBJECT-TYPE
    SYNTAX      Gauge32
    MAX-ACCESS  read-only
    STATUS      current
    DESCRIPTION
        "Number of ctive relayed clients by the DHCP relay rule with corresponding index."
    ::= { dfl800DHCPRelayRuleEntry 4 }

dfl800DHCPRelayRuleRejCliPkts OBJECT-TYPE
    SYNTAX      Gauge32
    MAX-ACCESS  read-only
    STATUS      current
    DESCRIPTION
        "Number of client packets rejected by a rule."
    ::= { dfl800DHCPRelayRuleEntry 5 }

dfl800DHCPRelayRuleRejSrvPkts OBJECT-TYPE
    SYNTAX      Gauge32
    MAX-ACCESS  read-only
    STATUS      current
    DESCRIPTION
        "Number of DHCP server packets rejected by the DHCP relay rule
         with the corresponding index."
    ::= { dfl800DHCPRelayRuleEntry 6 }

dfl800HA OBJECT IDENTIFIER
    ::= { dfl800OSStats 12 }

dfl800HASyncSendQueueLength OBJECT-TYPE
    SYNTAX      Gauge32
    MAX-ACCESS  read-only
    STATUS      current
    DESCRIPTION
        "Size of the queue used for the High Availability sync interface."
    ::= { dfl800HA 1 }

dfl800HASyncSendQueueUsagePkt OBJECT-TYPE
    SYNTAX      Gauge32
    MAX-ACCESS  read-only
    STATUS      current
    DESCRIPTION
        "High Availability Sync interface queue usage in number of packets."
    ::= { dfl800HA 2 }

dfl800HASyncSendQueueUsageOct OBJECT-TYPE
    SYNTAX      Gauge32
    MAX-ACCESS  read-only
    STATUS      current
    DESCRIPTION
        "High Availability Sync interface queue usage in number of octects."
    ::= { dfl800HA 3 }

dfl800HASyncSentPackets OBJECT-TYPE
    SYNTAX      Counter32
    MAX-ACCESS  read-only
    STATUS      current
    DESCRIPTION
        "Number High Availability packets sent on Sync."
    ::= { dfl800HA 4 }

dfl800HASyncSendResentPackets OBJECT-TYPE
    SYNTAX      Counter32
    MAX-ACCESS  read-only
    STATUS      current
    DESCRIPTION
        "Number of High Availability packets resent on Sync."
    ::= { dfl800HA 5 }

dfl800StatsConformance OBJECT IDENTIFIER
    ::= { dfl800MibConfs 1 }

dfl800StatsRegGroups OBJECT IDENTIFIER
    ::= { dfl800MibObjectGroups 1 }

dfl800SystemObjectGroup OBJECT-GROUP
    OBJECTS     { dfl800SysCpuLoad,
                  dfl800SysForwardedBits,
                  dfl800SysForwardedPackets,
                  dfl800SysBuffUse,
                  dfl800SysConns,
                  dfl800HWSensorName,
                  dfl800HWSensorValue,
                  dfl800HWSensorUnit,
                  dfl800SysMemUsage,
                  dfl800SysTimerUsage,
                  dfl800SysConnOPS,
                  dfl800SysConnCPS,
                  dfl800SysHCForwardedBits }
    STATUS      current
    DESCRIPTION
        "System statistics Group"
    ::= { dfl800StatsRegGroups 1 }

dfl800IPsecObjectGroup OBJECT-GROUP
    OBJECTS     { dfl800IPsecPhaseOneActive,
                  dfl800IPsecPhaseOneAggrModeDone,
                  dfl800IPsecQuickModeActive,
                  dfl800IPsecPhaseOneDone,
                  dfl800IPsecPhaseOneFailed,
                  dfl800IPsecPhaseOneRekeyed,
                  dfl800IPsecQuickModeDone,
                  dfl800IPsecQuickModeFailed,
                  dfl800IPsecInfoDone,
                  dfl800IPsecInfoFailed,
                  dfl800IPsecInOctetsComp,
                  dfl800IPsecInOctetsUncomp,
                  dfl800IPsecOutOctetsComp,
                  dfl800IPsecOutOctetsUncomp,
                  dfl800IPsecForwardedOctetsComp,
                  dfl800IPsecForwardedOctetsUcomp,
                  dfl800IPsecInPackets,
                  dfl800IPsecOutPackets,
                  dfl800IPsecForwardedPackets,
                  dfl800IPsecActiveTransforms,
                  dfl800IPsecTotalTransforms,
                  dfl800IPsecOutOfTransforms,
                  dfl800IPsecTotalRekeys }
    STATUS      current
    DESCRIPTION
        "IPsec Group"
    ::= { dfl800StatsRegGroups 2 }

dfl800StateCountersGroup OBJECT-GROUP
    OBJECTS     { dfl800SysPscTcpSyn,
                  dfl800SysPscTcpOpen,
                  dfl800SysPscTcpFin,
                  dfl800SysPscUdp,
                  dfl800SysPscIcmp,
                  dfl800SysPscOther }
    STATUS      current
    DESCRIPTION
        "Per state counters"
    ::= { dfl800StatsRegGroups 3 }

dfl800IPPoolGroup OBJECT-GROUP
    OBJECTS     { dfl800IPPoolsNumber,
                  dfl800IPPoolName,
                  dfl800IPPoolPrepare,
                  dfl800IPPoolFree,
                  dfl800IPPoolMisses,
                  dfl800IPPoolClientFails,
                  dfl800IPPoolUsed }
    STATUS      current
    DESCRIPTION
        "IP pool entry objects group"
    ::= { dfl800StatsRegGroups 4 }

dfl800DHCPServerGroup OBJECT-GROUP
    OBJECTS     { dfl800DHCPTotalRejected,
                  dfl800DHCPRuleName,
                  dfl800DHCPRuleUsage,
                  dfl800DHCPRuleUsagePercent,
                  dfl800DHCPActiveClients,
                  dfl800DHCPActiveClientsPercent,
                  dfl800DHCPRejectedRequests,
                  dfl800DHCPTotalLeases }
    STATUS      current
    DESCRIPTION
        "DHCP server rules objects."
    ::= { dfl800StatsRegGroups 5 }

dfl800RuleUseGroup OBJECT-GROUP
    OBJECTS     { dfl800RuleName, dfl800RuleUse }
    STATUS      current
    DESCRIPTION
        "Rule use objects."
    ::= { dfl800StatsRegGroups 6 }

dfl800UserAuthGroup OBJECT-GROUP
    OBJECTS     { dfl800UserAuthHTTPUsers, dfl800UserAuthXAUTHUsers,
                  dfl800UserAuthHTTPSUsers, dfl800UserAuthPPPUsers,
                  dfl800UserAuthEAPUsers, dfl800UserAuthRuleName,
                  dfl800UserAuthRuleUse }
    STATUS      current
    DESCRIPTION
        "User auth objects."
    ::= { dfl800StatsRegGroups 7 }

dfl800IfStatsGroup OBJECT-GROUP
    OBJECTS     { dfl800IfName,
                  dfl800IfFragsIn,
                  dfl800IfFragReassOk,
                  dfl800IfFragReassFail,
                  dfl800IfPktsInCnt,
                  dfl800IfPktsOutCnt,
                  dfl800IfBitsInCnt,
                  dfl800IfBitsOutCnt,
                  dfl800IfPktsTotCnt,
                  dfl800IfBitsTotCnt,
                  dfl800IfHCPktsInCnt,
                  dfl800IfHCPktsOutCnt,
                  dfl800IfHCBitsInCnt,
                  dfl800IfHCBitsOutCnt,
                  dfl800IfHCPktsTotCnt,
                  dfl800IfHCBitsTotCnt,
                  dfl800IfRxRingFifoErrors,
                  dfl800IfRxDespools,
                  dfl800IfRxAvgUse,
                  dfl800IfRxRingSaturation,
                  dfl800RxRingFlooded,
                  dfl800IfTxDespools,
                  dfl800IfTxAvgUse,
                  dfl800IfTxRingSaturation,
                  dfl800RxTingFlooded }
    STATUS      current
    DESCRIPTION
        "DFL-800 interface statistics group."
    ::= { dfl800StatsRegGroups 8 }

dfl800LinkMonitorGroup OBJECT-GROUP
    OBJECTS     { dfl800LinkMonGrp,
                  dfl800LinkMonGrpName,
                  dfl800LinkMonGrpHostsUp,
                  dfl800LinkMonHostId,
                  dfl800LinkMonHostShortTermLoss,
                  dfl800LinkMonHostPacketsLost }
    STATUS      current
    DESCRIPTION
        "DFL-800 link monitor statistics group"
    ::= { dfl800StatsRegGroups 9 }

dfl800PipesObjectGroup OBJECT-GROUP
    OBJECTS     { dfl800PipeUsers,
                  dfl800PipeName,
                  dfl800PipeMinPrec,
                  dfl800PipeMaxPrec,
                  dfl800PipeDefPrec,
                  dfl800PipeNumPrec,
                  dfl800PipeNumUsers,
                  dfl800PipeCurrentBps,
                  dfl800PipeCurrentPps,
                  dfl800PipeDelayedPackets,
                  dfl800PipeDropedPackets,
                  dfl800PipePrec,
                  dfl800PipePrecBps,
                  dfl800PipePrecTotalPps,
                  dfl800PipePrecReservedBps,
                  dfl800PipePrecDynLimBps,
                  dfl800PipePrecDynUsrLimBps,
                  dfl800PipePrecDelayedPackets,
                  dfl800PipePrecDropedPackets }
    STATUS      current
    DESCRIPTION
        "DFL-800 pipes statistics group"
    ::= { dfl800StatsRegGroups 10 }

dfl800DHCPRelayObjectGroup OBJECT-GROUP
    OBJECTS     { dfl800DHCPRelayCurClients,
                  dfl800DHCPRelayCurTrans,
                  dfl800DHCPRelayRejected,
                  dfl800DHCPRelayRuleName,
                  dfl800DHCPRelayRuleHits,
                  dfl800DHCPRelayRuleCurClients,
                  dfl800DHCPRelayRuleRejCliPkts,
                  dfl800DHCPRelayRuleRejSrvPkts }
    STATUS      current
    DESCRIPTION
        "DFL-800 DHCP relay statistics group"
    ::= { dfl800StatsRegGroups 12 }

dfl800AlgGroup OBJECT-GROUP
    OBJECTS     { dfl800AlgSessions,
                  dfl800AlgConnections,
                  dfl800AlgTCPStreams,
                  dfl800HttpAlgName,
                  dfl800HttpAlgTotalRequested,
                  dfl800HttpAlgTotalAllowed,
                  dfl800HttpAlgTotalBlocked,
                  dfl800HttpAlgCntFltName,
                  dfl800HttpAlgCntFltRequests,
                  dfl800HttpAlgCntFltAllowed,
                  dfl800HttpAlgCntFltBlocked }
    STATUS      current
    DESCRIPTION
        "DFL-800 HTTP ALG statistics group"
    ::= { dfl800StatsRegGroups 13 }

dfl800HAGroup OBJECT-GROUP
    OBJECTS     { dfl800HASyncSendQueueLength,
                  dfl800HASyncSendQueueUsagePkt,
                  dfl800HASyncSendQueueUsageOct,
                  dfl800HASyncSentPackets,
                  dfl800HASyncSendResentPackets }
    STATUS      current
    DESCRIPTION
        "DFL-800 HA statistics group"
    ::= { dfl800StatsRegGroups 14 }

dfl800IfVlanGroup OBJECT-GROUP
    OBJECTS     { dfl800IfVlanUntaggedInPkts,
                  dfl800IfVlanUntaggedOutPkts,
                  dfl800IfVlanUntaggedTotPkts,
                  dfl800IfVlanUntaggedInOctets,
                  dfl800IfVlanUntaggedOutOctets,
                  dfl800IfVlanUntaggedTotOctets }
    STATUS      current
    DESCRIPTION
        "DFL-800 VLAN statistics group"
    ::= { dfl800StatsRegGroups 15 }


dfl800SmtpAlgGroup OBJECT-GROUP
    OBJECTS { dfl800SmtpAlgName,
              dfl800SmtpAlgTotCheckedSes,
              dfl800SmtpAlgTotSpamSes,
              dfl800SmtpAlgTotDroppedSes,
              dfl800SmtpAlgDnsBlName,
              dfl800SmtpAlgDnsBlChecked,
              dfl800SmtpAlgDnsBlMatched,
              dfl800SmtpAlgDnsBlFailChecks }
   STATUS current
   DESCRIPTION
       "Clavister SMTP ALG objects group"
   ::= { dfl800StatsRegGroups 16 }

dfl800SysTCPGroup OBJECT-GROUP
    OBJECTS { dfl800SysTCPRecvSmall,
              dfl800SysTCPRecvLarge,
              dfl800SysTCPSendSmall,
              dfl800SysTCPSendLarge }
    STATUS current
    DESCRIPTION
      "DFL-800 TCP buffer usage group"
    ::= { dfl800StatsRegGroups 17 }



dfl800StatsCompliance MODULE-COMPLIANCE
    STATUS      current
    DESCRIPTION
        "Module Compliance"

    MODULE      -- this module

        MANDATORY-GROUPS
                { dfl800SystemObjectGroup,
                  dfl800IPsecObjectGroup,
                  dfl800StateCountersGroup,
                  dfl800IPPoolGroup,
                  dfl800DHCPServerGroup,
                  dfl800RuleUseGroup,
                  dfl800UserAuthGroup,
                  dfl800IfStatsGroup,
                  dfl800LinkMonitorGroup,
                  dfl800PipesObjectGroup,
                  dfl800DHCPRelayObjectGroup,
                  dfl800AlgGroup,
                  dfl800HAGroup,
                  dfl800IfVlanGroup,
                  dfl800SmtpAlgGroup,
                  dfl800SysTCPGroup }

    ::= { dfl800StatsConformance 1 }

END -- end of module DFL800-MIB.
