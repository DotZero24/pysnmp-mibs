--------------------------------------------------------------------------------
-- MIB NAME : System Information Mib
-- FILE NAME: DGS-6600-SYSTEM-INFO-MIB.mib
-- DATE     : 2011/09/15
-- VERSION  : 1.00
-- PURPOSE  : To construct the MIB structure of chassis system information
--            for proprietary enterprise
--------------------------------------------------------------------------------
-- MODIFICTION HISTORY:
--------------------------------------------------------------------------------
-- Version 1.00, 2011/09/15, Andy
-- This is the first formal version for universal MIB definition.
--------------------------------------------------------------------------------

DGS-6600-SYSTEM-INFO-MIB  DEFINITIONS ::= BEGIN

    IMPORTS
        IpAddress, MODULE-IDENTITY,
        OBJECT-TYPE,Integer32                      FROM SNMPv2-SMI
        TruthValue,RowStatus,MacAddress            FROM SNMPv2-TC
        DisplayString                   FROM RFC1213-MIB
        InetAddressType, InetAddress    FROM INET-ADDRESS-MIB
        dgs6600-system                  FROM DGS-6600-ID-MIB;


      dgs6600SystemInfoMIB MODULE-IDENTITY
            LAST-UPDATED "1302210000Z"
            ORGANIZATION "D-Link Crop."
            CONTACT-INFO
                "http://support.dlink.com"
            DESCRIPTION
                    "The Structure of chassis system informatiom for enterprise."
        ::= { dgs6600-system 1 }

-- -----------------------------------------------------------------------------
-- systemBasicInfo
-- -----------------------------------------------------------------------------
    systemBasicInfo          OBJECT IDENTIFIER ::= { dgs6600SystemInfoMIB 1 }

-- -----------------------------------------------------------------------------
-- systemCPUutilization
-- -----------------------------------------------------------------------------
    systemCPUutilization          OBJECT IDENTIFIER ::= { systemBasicInfo 1 }

    systemCPUutilizationIn5sec OBJECT-TYPE
        SYNTAX  Integer32
        MAX-ACCESS  read-only
        STATUS  current
        DESCRIPTION
            "The time scale is set at 5 second intervals.
             The value will be between 0%(idle) and 100%(very busy)."
        ::= { systemCPUutilization 1 }

    systemCPUutilizationIn1min OBJECT-TYPE
        SYNTAX  Integer32

        MAX-ACCESS  read-only
        STATUS  current
        DESCRIPTION
            "The time scale is set at 1 minute intervals.
             The value will be between 0%(idle) and 100%(very busy)."
        ::= { systemCPUutilization 2 }

    systemCPUutilizationIn5min OBJECT-TYPE
        SYNTAX  Integer32
        MAX-ACCESS  read-only
        STATUS  current
        DESCRIPTION
            "The time scale is set at 5 minute intervals.
             The value will be between 0%(idle) and 100%(very busy)."
        ::= { systemCPUutilization 3 }

-- -----------------------------------------------------------------------------
-- systemDRAMutilizationTable
-- -----------------------------------------------------------------------------

    systemDRAMutilizationTable OBJECT-TYPE
        SYNTAX  SEQUENCE OF SystemDRAMutilizationEntry
        MAX-ACCESS not-accessible
        STATUS  current
        DESCRIPTION
             "Information about DRAM memory."
        ::={systemBasicInfo 2}

    systemDRAMutilizationEntry OBJECT-TYPE
        SYNTAX   SystemDRAMutilizationEntry
        MAX-ACCESS not-accessible
        STATUS   current
        DESCRIPTION
            "A list of information about DRAM memory."
        INDEX {systemDRAMutilizationUnitID}
        ::={systemDRAMutilizationTable 1}

     SystemDRAMutilizationEntry ::=
        SEQUENCE {
                systemDRAMutilizationUnitID
                         INTEGER,
                systemDRAMutilizationTotalDRAM
                         INTEGER,
                systemDRAMutilizationUsedDRAM
                         INTEGER,
                systemDRAMutilization
                         INTEGER
                 }

     systemDRAMutilizationUnitID OBJECT-TYPE
        SYNTAX  INTEGER (1..8)
        MAX-ACCESS not-accessible
        STATUS  current
        DESCRIPTION
             "Specifies the unit ID.
              If the ID equals to zero, it means the current device."
        ::={ systemDRAMutilizationEntry 1 }

     systemDRAMutilizationTotalDRAM OBJECT-TYPE
        SYNTAX  INTEGER
        UNITS	"KB"
        MAX-ACCESS read-only
        STATUS current
        DESCRIPTION
            "The size of Total DRAM Memory."
        ::={systemDRAMutilizationEntry 2}

     systemDRAMutilizationUsedDRAM OBJECT-TYPE
        SYNTAX  INTEGER
        UNITS	"KB"
        MAX-ACCESS read-only
        STATUS current
        DESCRIPTION
            "The size of used DRAM memory."
        ::={systemDRAMutilizationEntry 3}

     systemDRAMutilization OBJECT-TYPE
        SYNTAX  INTEGER
        MAX-ACCESS read-only
        STATUS  current
        DESCRIPTION
             "The percentage of used DRAM memory of the total DRAM memory available.
              The value will be between 0%(idle) and 100%(very busy)."
        ::={systemDRAMutilizationEntry 4}

-- -----------------------------------------------------------------------------
-- systemDRAMUtilizationTable
-- -----------------------------------------------------------------------------

     systemFLASHutilizationTable OBJECT-TYPE
        SYNTAX  SEQUENCE OF SystemFLASHutilizationEntry
        MAX-ACCESS not-accessible
        STATUS  current
        DESCRIPTION
             "The information about FLASH memory."
        ::={systemBasicInfo 3}

     systemFLASHutilizationEntry OBJECT-TYPE
        SYNTAX   SystemFLASHutilizationEntry
        MAX-ACCESS not-accessible
        STATUS   current
        DESCRIPTION
            "A list of information about FLASH memory."
        INDEX {systemFLASHutilizationUnitID}
        ::={systemFLASHutilizationTable 1}

     SystemFLASHutilizationEntry ::=
        SEQUENCE {
                 systemFLASHutilizationUnitID
                         INTEGER,
                 systemFLASHutilizationTotalFLASH
                         INTEGER,
                 systemFLASHutilizationUsedFLASH
                         INTEGER,
                 systemFLASHutilization
                         INTEGER
                 }

     systemFLASHutilizationUnitID OBJECT-TYPE
        SYNTAX  INTEGER  (1..8)
        MAX-ACCESS read-only
        STATUS  current
        DESCRIPTION
             "Specifies the unit ID.
              If the ID equals to zero, it means the current device."
        ::={ systemFLASHutilizationEntry 1 }

     systemFLASHutilizationTotalFLASH OBJECT-TYPE
        SYNTAX  INTEGER
        UNITS	"KB"
        MAX-ACCESS read-only
        STATUS current
        DESCRIPTION
            "The size of the total FLASH memory."
        ::={systemFLASHutilizationEntry 2}

     systemFLASHutilizationUsedFLASH OBJECT-TYPE
        SYNTAX  INTEGER
        UNITS	"KB"
        MAX-ACCESS read-only
        STATUS current
        DESCRIPTION
            "The size of the used FLASH memory."
        ::={systemFLASHutilizationEntry 3}

     systemFLASHutilization OBJECT-TYPE
        SYNTAX  INTEGER
        MAX-ACCESS read-only
        STATUS  current
        DESCRIPTION
             "The percentage of used FLASH memory in total FLASH memory.
              The value will be between 0%(idle) and 100%(very busy)."
        ::={systemFLASHutilizationEntry 4}

END
