SWPRIMGMT-DES1228ME-MIB	DEFINITIONS ::= BEGIN
	IMPORTS
		MODULE-IDENTITY			FROM SNMPv2-SMI
		dlink-products,dlink-mgmt	FROM DLINK-ID-REC-MIB;

	dlink-des1228MEproductProd OBJECT IDENTIFIER ::= {dlink-products 116}

	dlink-des1228MEProd	OBJECT IDENTIFIER ::= {dlink-des1228MEproductProd 1}

	dlink-des1228MEv2Prod	OBJECT IDENTIFIER ::= {dlink-des1228MEproductProd 2}

	des1228MESeriesProd	OBJECT IDENTIFIER ::= {dlink-mgmt 116}

	des1228ME			OBJECT IDENTIFIER ::= {des1228MESeriesProd 1}
	des1228MEv2			OBJECT IDENTIFIER ::= {des1228MESeriesProd 2}

END
