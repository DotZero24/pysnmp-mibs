DLINK-SWPRIMGMT-MIB    DEFINITIONS ::= BEGIN

    IMPORTS
        MODULE-IDENTITY             FROM SNMPv2-SMI
        dlink-products,dlink-mgmt   FROM DLINK-ID-REC-MIB;


    dlink-des30xxproductProd   OBJECT IDENTIFIER ::= { dlink-products 63}

    dlink-des3010xProd       OBJECT IDENTIFIER ::= { dlink-des30xxproductProd 1 }
    dlink-des3010FProd       OBJECT IDENTIFIER ::= { dlink-des3010xProd 1 }
    dlink-des3010GProd       OBJECT IDENTIFIER ::= { dlink-des3010xProd 2 }
    dlink-des3018Prod       OBJECT IDENTIFIER ::= { dlink-des30xxproductProd 2 }
    dlink-des3026Prod       OBJECT IDENTIFIER ::= { dlink-des30xxproductProd 3 }
    dlink-des3010FLProd       OBJECT IDENTIFIER ::= { dlink-des30xxproductProd 4 }
    dlink-des3016Prod       OBJECT IDENTIFIER ::= { dlink-des30xxproductProd 10 }


    des30xxSeriesProd   OBJECT IDENTIFIER ::= { dlink-mgmt 63 }
    des3010       OBJECT IDENTIFIER ::= { des30xxSeriesProd 1 }
    des3010f      OBJECT IDENTIFIER ::= { des3010 1 }
    des3010g      OBJECT IDENTIFIER ::= { des3010 2 }
    des3018      OBJECT IDENTIFIER ::= { des30xxSeriesProd 2 }
    des3026      OBJECT IDENTIFIER ::= { des30xxSeriesProd 3 }
    des3010fl      OBJECT IDENTIFIER ::= { des30xxSeriesProd 4 }
    des3016      OBJECT IDENTIFIER ::= { des30xxSeriesProd 10 }



END
