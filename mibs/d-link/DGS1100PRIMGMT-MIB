DGS1100PRIMGMT-MIB    DEFINITIONS ::= BEGIN

    IMPORTS
        MODULE-IDENTITY             FROM SNMPv2-SMI
        dlink-products,dlink-mgmt   FROM DLINK-ID-REC-MIB;


    dgs1100SeriesProd   OBJECT IDENTIFIER ::= { dlink-products 134 }
    dgs1100-16          OBJECT IDENTIFIER ::= { dgs1100SeriesProd 3 }
    dgs1100-16ME        OBJECT IDENTIFIER ::= { dgs1100SeriesProd 4 }
    dgs1100-18          OBJECT IDENTIFIER ::= { dgs1100SeriesProd 5 }
    dgs1100-18ME        OBJECT IDENTIFIER ::= { dgs1100SeriesProd 6 }
    dgs1100-24          OBJECT IDENTIFIER ::= { dgs1100SeriesProd 7 }
    dgs1100-24ME        OBJECT IDENTIFIER ::= { dgs1100SeriesProd 8 }
    dgs1100-24P         OBJECT IDENTIFIER ::= { dgs1100SeriesProd 9 }
    dgs1100-24PME       OBJECT IDENTIFIER ::= { dgs1100SeriesProd 10 }
    dgs1100-26          OBJECT IDENTIFIER ::= { dgs1100SeriesProd 11 }
    dgs1100-26ME        OBJECT IDENTIFIER ::= { dgs1100SeriesProd 12 }

END
