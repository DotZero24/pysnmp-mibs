-- *****************************************************************
-- DLINKPRIME-LACP-EXT-MIB.mib : D-Link Link Aggregation Control Extenstions MIB
--
-- Copyright (c) 2014 D-Link Corporation, all rights reserved.
--
-- *****************************************************************

DLINKPRIME-LACP-EXT-MIB DEFINITIONS ::= BEGIN

	IMPORTS
        MODULE-IDENTITY , OBJECT-TYPE, Integer32
        	FROM SNMPv2-SMI
       	RowStatus
       		FROM SNMPv2-TC
        MODULE-COMPLIANCE, OBJECT-GROUP
		    FROM SNMPv2-CONF
       	InterfaceIndex
            FROM IF-MIB
       	PortList
            FROM Q-BRIDGE-MIB
	    dlinkPrimeCommon
        	FROM DLINK-ID-REC-MIB;

	dlinkPrimeLacpExtMIB MODULE-IDENTITY
        LAST-UPDATED "201404260000Z"
        ORGANIZATION "D-Link Corp."
        CONTACT-INFO
            "        D-Link Corporation
             Postal: No. 289, Sinhu 3rd Rd., Neihu District,
             Taipei City 114, Taiwan, R.O.C
             Tel:     +886-2-66000123
             E-mail: tsd@dlink.com.tw
            "
        DESCRIPTION
            "The MIB module for managing D-Link LACP extensions which are
            not covered by standard MIBs."
        REVISION	"201404260000Z"
        DESCRIPTION
        	"Initial revision of this MIB module."
    ::= { dlinkPrimeCommon 6 }

--
--	MIB OBJECTS
--
    dpLacpExtMIBObjects 	OBJECT IDENTIFIER ::= { dlinkPrimeLacpExtMIB 1 }
    dpLacpExtMIBConformance 	OBJECT IDENTIFIER ::= { dlinkPrimeLacpExtMIB 2 }

-----------------------------------------------
--	Lacp Objects
-----------------------------------------------
    dpLacpExtGroupTable OBJECT-TYPE
        SYNTAX          SEQUENCE OF DpLacpExtGroupEntry
        MAX-ACCESS      not-accessible
        STATUS          current
        DESCRIPTION
            "This table consists of a list of channel group information."
        ::= { dpLacpExtMIBObjects 1 }

    dpLacpExtGroupEntry OBJECT-TYPE
        SYNTAX          DpLacpExtGroupEntry
        MAX-ACCESS      not-accessible
        STATUS          current
        DESCRIPTION
            "An entry presents a channel group information, which is not
            covered by standard MIB(s)."
        INDEX  { dpLacpExtGroupChannelNo }
        ::= { dpLacpExtGroupTable 1 }

    DpLacpExtGroupEntry ::=
        SEQUENCE {
            dpLacpExtGroupChannelNo          Integer32,
            dpLacpExtGroupType               INTEGER,
            dpLacpExtGroupMemberPorts        PortList,
            dpLacpExtGroupRowStatus          RowStatus
        }

    dpLacpExtGroupChannelNo OBJECT-TYPE
        SYNTAX          Integer32 (1 .. 255)
        MAX-ACCESS      not-accessible
        STATUS          current
        DESCRIPTION
            "This object indicates the channel group ID. "
        ::= { dpLacpExtGroupEntry 1 }

    dpLacpExtGroupType OBJECT-TYPE
        SYNTAX  INTEGER {
            static_on(1),
            lacp_active(2),
            lacp_passive(3)
        }
       	MAX-ACCESS  read-create
        STATUS  current
        DESCRIPTION
            "This object indicates the type of channel group.
            "
        ::= { dpLacpExtGroupEntry 2 }

    dpLacpExtGroupMemberPorts OBJECT-TYPE
        SYNTAX          PortList
        MAX-ACCESS      read-create
        STATUS          current
        DESCRIPTION
            "This object indicates the ports which are grouped into this
            channel group.
	        "
        ::= { dpLacpExtGroupEntry 3 }

    dpLacpExtGroupRowStatus OBJECT-TYPE
        SYNTAX          RowStatus
        MAX-ACCESS      read-create
        STATUS          current
        DESCRIPTION
            "This object indicates the status of this entry."
        ::= { dpLacpExtGroupEntry 4 }

-----------------------------------------------
--	Lacp Conformance
-----------------------------------------------
    dpLacpExtCompliances   	OBJECT IDENTIFIER ::= { dpLacpExtMIBConformance 1 }


    dpLacpExtCompliance MODULE-COMPLIANCE
    	STATUS current
    	DESCRIPTION
        	"The compliance statement for entities which implement the
			DLINKPRIME-LACP-EXT-MIB."
        MODULE
	    MANDATORY-GROUPS {
		    dpLacpExtChannelGrpInfoGroup
		}
	    ::= { dpLacpExtCompliances 1 }

	dpLacpExtGroups   		OBJECT IDENTIFIER ::= { dpLacpExtMIBConformance 2 }

    dpLacpExtChannelGrpInfoGroup OBJECT-GROUP
  		OBJECTS {
          dpLacpExtGroupType,
          dpLacpExtGroupMemberPorts,
          dpLacpExtGroupRowStatus
        }
	    STATUS current
	    DESCRIPTION
	        "A collection of objects providing configuration of channel groups."
	    ::= { dpLacpExtGroups 1 }


END
