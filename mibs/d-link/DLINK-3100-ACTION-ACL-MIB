DLINK-3100-ACTION-ACL-MIB DEFINITIONS ::= BEGIN

          IMPORTS
                rnd                                         FROM DLINK-3100-MIB
                OBJECT-TYPE, MODULE-IDENTITY                FROM SNMPv2-SMI
                RowStatus                                   FROM SNMPv2-TC
                PortList                                    FROM Q-BRIDGE-MIB;





rlActionAcl MODULE-IDENTITY
    LAST-UPDATED "2007111800Z"
    ORGANIZATION "Dlink, Inc."
    CONTACT-INFO
        "www.dlink.com"
    DESCRIPTION
        "Dlink ACLs MIBs"
    REVISION "200711180000Z"
    DESCRIPTION
            "Initial revision."

    ::={ rnd 130 }

ClassMapAction ::= TEXTUAL-CONVENTION
    STATUS  current
    DESCRIPTION
        "Specifies one of 8 Class-map actios:
         1- no action.
         2- Mark IP-Precedence.
         3- Mark DSCP.
         4- Set Egress queueu
         5- Mark VPT
         6- Choose queue by the VPT.
         7- Choose queue by the DSCP.
         8- Choose queue by the TCP/UDP port."
    SYNTAX  INTEGER {
        none(1),
        setIP-Precedence(2),
        setDSCP(3),
        setQueue(4),
        setCos(5),
        trustCos(6),
        trustDSCP(7),
        trustTCP-UDPport(8),
        trustCosDscp(9)
        }

rlActionAclTable OBJECT-TYPE
    SYNTAX      SEQUENCE OF RlActionAclEntry
    MAX-ACCESS  read-write
    STATUS      current
    DESCRIPTION
        "This table holds the group membership information and the group/ports status"
    ::= { rlActionAcl 1 }

rlActionAclEntry OBJECT-TYPE
    SYNTAX      RlActionAclEntry
    MAX-ACCESS  read-write
    STATUS      current
    DESCRIPTION
        "The row definition for this table."
    INDEX { rlActionAclAclIndex  }
    ::= { rlActionAclTable 1 }

RlActionAclEntry ::= SEQUENCE {
    rlActionAclAclIndex                        INTEGER,
    rlActionAclPorts                           PortList,
    rlActionAclClassMapAction                  ClassMapAction,
    rlActionAclClassMapMarkValue               INTEGER,
    rlActionAclPolicerIndex                    INTEGER,
    rlActionAclStatus                          RowStatus
}

rlActionAclAclIndex OBJECT-TYPE
    SYNTAX      INTEGER (1..240)
    MAX-ACCESS  not-accessible
    STATUS      current
    DESCRIPTION
        "The Access Id/ ACL Index"
    ::=  { rlActionAclEntry 1 }

rlActionAclPorts OBJECT-TYPE
    SYNTAX      PortList
    MAX-ACCESS  read-write
    STATUS      current
    DESCRIPTION
        "Portlist of ports associated with the ACL Index"
    ::=  { rlActionAclEntry 2 }

rlActionAclClassMapAction OBJECT-TYPE
    SYNTAX      ClassMapAction
    MAX-ACCESS  read-write
    STATUS      current
    DESCRIPTION
        "Action to perform on data base for ACL (add/remove)"
    ::=  { rlActionAclEntry 3 }

rlActionAclClassMapMarkValue OBJECT-TYPE
    SYNTAX      INTEGER
    MAX-ACCESS  read-write
    STATUS      current
    DESCRIPTION
        "The policer index bounded to the action of that ACL"
    ::=  { rlActionAclEntry 4 }

rlActionAclPolicerIndex OBJECT-TYPE
    SYNTAX      INTEGER
    MAX-ACCESS  read-write
    STATUS      current
    DESCRIPTION
        "The policer index bounded to the action of that ACL"
    ::=  { rlActionAclEntry 5 }

rlActionAclStatus OBJECT-TYPE
    SYNTAX      RowStatus
    MAX-ACCESS  read-write
    STATUS      current
    DESCRIPTION
        "The index of profile to perform the action"
    ::=  { rlActionAclEntry 6 }

-- delete profile MIB

rlPort2AclsMappingTable OBJECT-TYPE
    SYNTAX      SEQUENCE OF RlPort2AclsMappingEntry
    MAX-ACCESS  read-write
    STATUS      current
    DESCRIPTION
        "This table holds the group membership information and the group/ports status"
    ::= { rlActionAcl 2 }

rlPort2AclsMappingEntry OBJECT-TYPE
    SYNTAX      RlPort2AclsMappingEntry
    MAX-ACCESS  read-write
    STATUS      current
    DESCRIPTION
        "The row definition for this table."
    INDEX { rlPorts2AclsMappingPortIndex  }
    ::= { rlPort2AclsMappingTable 1 }

RlPort2AclsMappingEntry ::= SEQUENCE {
    rlPorts2AclsMappingPortIndex               INTEGER,
    rlPorts2AclsMappingPortAcls                PortList
}

rlPorts2AclsMappingPortIndex OBJECT-TYPE
    SYNTAX      INTEGER
    MAX-ACCESS  not-accessible
    STATUS      current
    DESCRIPTION
        "The ifindex"
    ::=  { rlPort2AclsMappingEntry 1 }

rlPorts2AclsMappingPortAcls OBJECT-TYPE
    SYNTAX      PortList
    MAX-ACCESS  read-only
    STATUS      current
    DESCRIPTION
        "Portlist of ACLs associated with the ifIndex"
    ::=  { rlPort2AclsMappingEntry 2 }

rlActionAclDeleteProfileIndex OBJECT-TYPE
    SYNTAX  INTEGER (1..15)
    MAX-ACCESS  read-write
    STATUS  current
    DESCRIPTION
        "The scalar defines access profile index to be deleted."
--    DEFVAL { 1 }
    ::= { rlActionAcl 3 }

rlNumOfUsedTcamAces OBJECT-TYPE
    SYNTAX      INTEGER
    MAX-ACCESS  read-only
    STATUS      current
    DESCRIPTION
        "Read used Tcam Aces"
    ::=  { rlActionAcl 4 }

END
