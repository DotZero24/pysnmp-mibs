--  *****************************************************************
--  DLINKPRIME-DDP-CLIENT-MIB.mib : DLINK discovery protocol MIB
--
--  Copyright (c) 2014 D-Link Corporation, all rights reserved.
--
--  *****************************************************************
DLINKPRIME-DDP-CLIENT-MIB DEFINITIONS ::= BEGIN

    IMPORTS
        MODULE-IDENTITY,
        OBJECT-TYPE,
        NOTIFICATION-TYPE,
        Unsigned32
                FROM SNMPv2-SMI
        TruthValue
                FROM SNMPv2-TC
        dlinkPrimeCommon
            FROM DLINK-ID-REC-MIB;


    dlinkPrimeDdpClientMIB MODULE-IDENTITY
        LAST-UPDATED "201404260000Z"
        ORGANIZATION "D-Link Corp."
        CONTACT-INFO
            "        D-Link Corporation

             Postal: No. 289, Sinhu 3rd Rd., Neihu District,
                     Taipei City 114, Taiwan, R.O.C
             Tel:     +886-2-66000123
             E-mail: tsd@dlink.com.tw
            "
        DESCRIPTION
            "This MIB module defines objects for D-Link Discovery Protocol client."

        REVISION "201404260000Z"
        DESCRIPTION
            " This is the first version of the MIB file.
            "
        ::= { dlinkPrimeCommon 2 }

-- -----------------------------------------------------------------------------
    dpDdpClientNotifications    OBJECT IDENTIFIER ::= { dlinkPrimeDdpClientMIB 0 }
    dpDdpClientObjects          OBJECT IDENTIFIER ::= { dlinkPrimeDdpClientMIB 1 }
    dpDdpClientConformance      OBJECT IDENTIFIER ::= { dlinkPrimeDdpClientMIB 2 }

-- -----------------------------------------------------------------------------
-- Notifications
-- -----------------------------------------------------------------------------

-- -----------------------------------------------------------------------------
-- Objects
-- -----------------------------------------------------------------------------
    dpDdpClientCtrl            OBJECT IDENTIFIER ::= { dpDdpClientObjects 1 }

    dpDdpClientGlobalState  OBJECT-TYPE
        SYNTAX        TruthValue
        MAX-ACCESS    read-write
        STATUS        current
        DESCRIPTION
            "This object represents the DDP client's global state
		        true - Indicates the DDP client is enabled
		        false - Indicates the DDP client is disabled"
       DEFVAL { true }
        ::= { dpDdpClientCtrl 1 }

    dpDdpClientReportTimer OBJECT-TYPE
        SYNTAX       	Unsigned32 (0|30|60|90|120)
        UNITS        	"second"
        MAX-ACCESS	read-write
        STATUS		current
        DESCRIPTION
            "This object specifies the interval at which DDP report messages are sent
			by the device.
            Setting the object to 0 prohibits the device from sending DDP report message."
        DEFVAL { 0 }
        ::= { dpDdpClientCtrl 2 }

 -- -----------------------------------------------------------------------------
-- Conformance
-- -------------------------------------------------------------------------------

    dpDdpClientCompliances OBJECT IDENTIFIER ::= { dpDdpClientConformance 1 }
    dpDdpClientGroups	  OBJECT IDENTIFIER ::= { dpDdpClientConformance 2 }

--  compliance statements
dpDdpClientCompliance MODULE-COMPLIANCE
        STATUS         current
        DESCRIPTION
            "The compliance statement for entities which implement the
            DLINKPRIME-DDP-CLIENT-MIB."

        MODULE  -- this module
        MANDATORY-GROUPS
            {
            	dpDdpClientControlGroup
            }
        GROUP dpDdpClientControlGroup
            DESCRIPTION
                "This group is mandatory for those devices support DLINK discovery protocol."
        ::= { dpDdpClientCompliances 1 }

--  units of conformance

    dpDdpClientControlGroup OBJECT-GROUP
        OBJECTS             {
            dpDdpClientGlobalState
        }
        STATUS  current
        DESCRIPTION
            "A collection of objects providing accessing to global status and report time or the status of a port."
        ::= { dpDdpClientGroups 1 }

END
