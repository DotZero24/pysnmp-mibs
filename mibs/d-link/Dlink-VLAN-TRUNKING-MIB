Dlink-VLAN-TRUNKING-MIB DEFINITIONS ::= BEGIN

          IMPORTS
                rnd                                         FROM DLINK-3100-MIB
                DisplayString, TruthValue                   FROM SNMPv2-TC
                OBJECT-TYPE, MODULE-IDENTITY                FROM SNMPv2-SMI
                PortList                                    FROM Q-BRIDGE-MIB;


-- module

            rlVlanTrunking MODULE-IDENTITY
                LAST-UPDATED "2007111800Z"
                ORGANIZATION "Dlink, Inc."
                CONTACT-INFO
                    "www.dlink.com"
                DESCRIPTION
                    "Dlink Vlan Trunking MIBs"
                REVISION "200711180000Z"
                DESCRIPTION
                        "Initial revision."
                ::={ rnd 136 }

            rlVlanTrunkingEnabled OBJECT-TYPE
                SYNTAX      TruthValue
                MAX-ACCESS  read-write
                STATUS      current
                DESCRIPTION
                    "VLAN Trunking feature's status"
                DEFVAL { false }
                ::=  { rlVlanTrunking 1 }

            rlVlanTrunkingUplinkPorts OBJECT-TYPE
                SYNTAX      PortList
                MAX-ACCESS  read-write
                STATUS      current
                DESCRIPTION
                    "VLAN Trunking Uplink PortList "
                ::=  { rlVlanTrunking 2 }

          END
