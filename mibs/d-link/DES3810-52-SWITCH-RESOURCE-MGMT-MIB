-- -----------------------------------------------------------------------------
-- MIB NAME : SWITCH-RESOURCE-MGMT-MIB
-- FILE NAME: SwitchResourceMgmt.mib
-- DATE     : 2010/05/06
-- VERSION  : 1.00
-- PURPOSE  : To construct the MIB structure of switch resource management
--            function for proprietary enterprise
-- -----------------------------------------------------------------------------
-- MODIFICTION HISTORY:
-- -----------------------------------------------------------------------------
-- Version, Date, Author
-- Description:
--  [New Object]
--  [Modification]
-- Notes: (Requested by who and which project)
--
-- Version 1.00, 2010/05/06, Carl Zeng
-- This is the first formal version for universal MIB definition.
-- -----------------------------------------------------------------------------


DES3810-52-SWITCH-RESOURCE-MGMT-MIB DEFINITIONS ::= BEGIN

    IMPORTS
		MODULE-IDENTITY,OBJECT-TYPE	FROM SNMPv2-SMI
		RowStatus                       FROM SNMPv2-TC
		des3810-52	                        FROM SW3810PRIMGMT-MIB;

    swSwitchResourceMgmtMIB MODULE-IDENTITY
          LAST-UPDATED "201005060000Z"
          ORGANIZATION "D-Link Corp."
          CONTACT-INFO
                       "http://support.dlink.com"
          DESCRIPTION
		    "The Structure of switch resource management for the proprietary enterprise."
        ::= { des3810-52 4 }

	swSwitchResourceMgmtMIBObjects	OBJECT IDENTIFIER ::= { swSwitchResourceMgmtMIB 1 }
-- -----------------------------------------------------------------------------

    swSwitchResourceMgmtSRMMode  OBJECT-TYPE
        SYNTAX  INTEGER {
	               routing(1),
	               vpws(2)
                }
        MAX-ACCESS  read-write
        STATUS  current
        DESCRIPTION
            "The switch configure SRM mode, it need be saved and
            will be taken effect after reboot."
        DEFVAL{routing}
        ::= { swSwitchResourceMgmtMIBObjects 2 }

    swSwitchResourceMgmtSRMCurrentMode  OBJECT-TYPE
        SYNTAX  INTEGER {
	               routing(1),
	               vpws(2)
                }
        MAX-ACCESS  read-only
        STATUS  current
        DESCRIPTION
            "The switch current SRM mode."
        ::= { swSwitchResourceMgmtMIBObjects 3 }


END
