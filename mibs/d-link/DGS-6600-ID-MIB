-- *****************************************************************
-- For D-Link DGS-6600 series
--
-- Copyright (c) 2012 D-Link Corporation, all rights reserved.
--
-- *****************************************************************

DGS-6600-ID-MIB DEFINITIONS ::= BEGIN

    IMPORTS
        MODULE-IDENTITY
            FROM SNMPv2-SMI
        TEXTUAL-CONVENTION
            FROM SNMPv2-TC
       dlink-products
            FROM DLINK-ID-REC-MIB;

    dgs6600Series           OBJECT IDENTIFIER ::= { dlink-products 120 }
    dgs6604                 OBJECT IDENTIFIER ::= { dgs6600Series 1 }
    dgs6608                 OBJECT IDENTIFIER ::= { dgs6600Series 2 }
    dgs6600Private          OBJECT IDENTIFIER ::= { dgs6600Series 100 }
    dgs6600-system          OBJECT IDENTIFIER ::= { dgs6600Private 1 }
    dgs6600-l2              OBJECT IDENTIFIER ::= { dgs6600Private 2 }
    dgs6600-l3              OBJECT IDENTIFIER ::= { dgs6600Private 3 }
    dgs6600-mpls            OBJECT IDENTIFIER ::= { dgs6600Private 4 }
    dgs6600-qosacl          OBJECT IDENTIFIER ::= { dgs6600Private 5 }
    dgs6600-security        OBJECT IDENTIFIER ::= { dgs6600Private 6 }
    dgs6600-mgmt            OBJECT IDENTIFIER ::= { dgs6600Private 7 }
    dgs6600-others          OBJECT IDENTIFIER ::= { dgs6600Private 8 }

END
