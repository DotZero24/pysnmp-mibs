-- DLINK Private MIB
-- DLINK agents also support the following Public MIBs:
-- MIB-II  ( RFC1213 )
-- dlkEnterpriseAP-dlk80211bPlus MODULE

DLINK-WLAN-MIB DEFINITIONS ::= BEGIN

IMPORTS
	mgmt, enterprises, IpAddress			FROM RFC1155-SMI
	MODULE-IDENTITY, OBJECT-TYPE, Integer32, Counter32		FROM SNMPv2-SMI
--	OBJECT-TYPE, Integer32, Counter32		FROM RFC-1212
	DisplayString, MacAddress, RowStatus,
	TruthValue					FROM SNMPv2-TC
	ifIndex						FROM RFC1213-MIB
;


 --mgmt           OBJECT IDENTIFIER ::= { iso org(3) dod(6) internet(1)  mgmt(2) }
 --mib            OBJECT IDENTIFIER ::= { mgmt 1  }
 --directory      OBJECT IDENTIFIER ::= { internet 1  }
 --experimental   OBJECT IDENTIFIER ::= { internet 3  }
 --private        OBJECT IDENTIFIER ::= { internet 4  }
 --enterprises    OBJECT IDENTIFIER ::= { private 1  }

   dlink	OBJECT IDENTIFIER ::= { enterprises 171 }


   --should be implemented as module
   --dlkEnterpriseAP	OBJECT IDENTIFIER ::= { dlink 1 }
   --dlkWLANRouter		OBJECT IDENTIFIER ::= { dlink 2 }
   --dlkRouter			OBJECT IDENTIFIER ::= { dlink 3 }



-- **********************************************************************
-- *  MODULE IDENTITY
-- **********************************************************************
    dlkEnterpriseAP MODULE-IDENTITY
    LAST-UPDATED "200208160000Z"
    ORGANIZATION "D-Link, Inc."
    CONTACT-INFO
           "Postal: D-Link, Inc.
                    2F, No.233-2, Pao-Chiao Road,
                    Hsin-Tien, Taipei,
                    Taiwan, R.O.C.
               Tel: +886-2-29161600
               Fax: +886-2-29146299"

    DESCRIPTION
        "The MIB module for D-Link 802.11 series product.
         This module derived from IEEE ieee802dot11"
    ::= { dlink 1 }


-- **********************************************************************
-- *  end of MODULE IDENTITY
-- **********************************************************************

-- dlkEnterpriseAP OBJECT IDs Groups

	dlkEnterpriseAPsys		OBJECT IDENTIFIER ::= {	dlkEnterpriseAP 1 }
	dlkEnterpriseAPlan		OBJECT IDENTIFIER ::= {	dlkEnterpriseAP 2 }
	dlk80211bPlusDot11		OBJECT IDENTIFIER ::= {	dlkEnterpriseAP 3 }
	dlkEnterpriseAPTrap		OBJECT IDENTIFIER ::= {	dlkEnterpriseAP 4 }

-- **********************************************************************
-- *  Major sections
-- **********************************************************************
-- **********************************************************************
-- *  dlkEnterpriseAPsys sections
-- **********************************************************************
enterpriseAPSysConfigSave OBJECT-TYPE
        SYNTAX INTEGER { write(1) }
        MAX-ACCESS read-write
        STATUS current
        DESCRIPTION

            "User must manually SET this OID in order to save the change(s) made through SNMP to
            main configuration."

    ::= { dlkEnterpriseAPsys 1 }

enterpriseAPSysReboot OBJECT-TYPE
        SYNTAX INTEGER { reboot(1) }
        MAX-ACCESS read-write
        STATUS current
        DESCRIPTION

            "This attribute is to reboot the enterprise AP system.
            Doesn't save the changes that had been made."

    ::= { dlkEnterpriseAPsys 2 }

enterpriseAPSysConfigApply OBJECT-TYPE
        SYNTAX INTEGER { saveAndReboot(1) }
        MAX-ACCESS read-write
        STATUS current
        DESCRIPTION

            "This attribute is equivalent of setting enterpriseAPSysConfigSave then
            enterpriseAPSysConfigApply."

    ::= { dlkEnterpriseAPsys 3 }

-- **********************************************************************
-- *  end of dlkEnterpriseAPsys sections
-- **********************************************************************

--  Station ManagemenT (SMT) Attributes
    --  DEFINED AS "The SMT object class provides the necessary support at the
    --  station to manage the processes in the station such that the
    --  station may work cooperatively as a part of an IEEE 802.11 network.";

    dot11smt   		   OBJECT IDENTIFIER ::= { dlk80211bPlusDot11 1 }

      dot11StationConfigEntry		OBJECT IDENTIFIER ::= { dot11smt 1 }
      dot11APModeConfigEntry		OBJECT IDENTIFIER ::= { dot11smt 2 }
      dot11PrivacyEntry			OBJECT IDENTIFIER ::= { dot11smt 3 }

--  MAC Attributes
    --  DEFINED AS "The MAC object class provides the necessary support
    --  for the access control, generation, and verification of frame check
    --  sequences, and proper delivery of valid data to upper layers.";

    dot11mac 			OBJECT IDENTIFIER ::=   {dlk80211bPlusDot11 2}

         dot11OperationEntry   	OBJECT IDENTIFIER ::=   {dot11mac 1}
         dot11CountersEntry    	OBJECT IDENTIFIER ::=    {dot11mac 2}
         --  dot11GroupAddressesTable 	::=    {dot11mac 3}

--  Resource Type ID
      dot11res 		OBJECT IDENTIFIER 	::=   {dlk80211bPlusDot11 3}
      dot11resAttribute OBJECT IDENTIFIER 	::=   {dot11res 1 }

--  PHY Attributes
    --  DEFINED AS "The PHY object class provides the necessary support
    --  for required PHY operational information that may vary from PHY
    --  to PHY and from STA to STA to be communicated to upper layers."

   dot11phy OBJECT IDENTIFIER ::=   {dlk80211bPlusDot11 4}

        dot11PhyOperationEntry	OBJECT IDENTIFIER   	::=  {dot11phy 1}
        dot11PhyAntennaEntry    OBJECT IDENTIFIER  	::=  {dot11phy 2}
        dot11PhyTxPowerEntry    OBJECT IDENTIFIER  	::=  {dot11phy 3}
        dot11PhyDSSSEntry       OBJECT IDENTIFIER  	::=  {dot11phy 4}


-- ****************************************************************************************
--	dlkEnterpriseAPsys - system/platform MIB elements
-- ****************************************************************************************


-- ****************************************************************************************
--	dlkEnterpriseAPlan - Ethernet Standard MIB elements
-- ****************************************************************************************


-- **********************************************************************
-- * Textual conventions from 802 definitions
-- **********************************************************************


-- **********************************************************************
-- *  SMT Station Config  Table
-- **********************************************************************


dot11StationID OBJECT-TYPE
        SYNTAX MacAddress
        MAX-ACCESS read-only
        STATUS deprecated
        DESCRIPTION

            "The purpose of dot11StationID is to allow a manager to identify
            a station for its own purposes.  This attribute provides
            for that eventuality while keeping the true MAC address
            independent.  Its syntax is MAC address and default value
            is the station's assigned, unique MAC address."

    ::= { dot11StationConfigEntry 1 }

dot11PrivacyOptionImplemented OBJECT-TYPE
        SYNTAX TruthValue
        MAX-ACCESS read-only
        STATUS current
        DESCRIPTION

            "This attribute, when true, shall indicate that the IEEE
             802.11 WEP option is implemented.  The default value of
             this attribute shall be false."

    ::= {  dot11StationConfigEntry 2 }

dot11PowerManagementMode OBJECT-TYPE
		SYNTAX INTEGER { active(1), powersave(2) }
		MAX-ACCESS read-only
		STATUS current
		DESCRIPTION
			"This attribute shall specify the power management
			 mode of the STA. When set to active, it shall indicate
			 that the station is not in power-save mode. When set
			 to powersave, it shall indicate that the station is
			 in power-save mode. The power management mode is
			 transmitted in all frames according to the rules
			 in  7.1.3.1.7."
	::= { dot11StationConfigEntry 3 }

dot11DesiredSSID OBJECT-TYPE
		SYNTAX OCTET STRING (SIZE(0..32))
		MAX-ACCESS read-write
		STATUS current
		DESCRIPTION
			"This attribute reflects the Service Set ID used
			in the DesiredSSID parameter of the most recent
			MLME_Scan.request.  This value may be modified
			by an external management entity and used by the
			local SME to make decisions about the Scanning process."
	::= { dot11StationConfigEntry 4 }

dot11DesiredBSSType OBJECT-TYPE
		SYNTAX INTEGER { infrastructure(1), independent(2), any(3) }
		MAX-ACCESS read-only
		STATUS current
		DESCRIPTION
			"This attribute shall specify the type of BSS the
			 station shall use when scanning for a BSS with which
			 to synchronize. This value is used to filter Probe
			 Response frames and Beacons. When set to infrastructure,
			 the station shall only synchronize with a BSS whose
			 Capability Information field has the ESS subfield set
			 to 1. When set to independent, the station shall only
			 synchronize with a BSS whose Capability Information
			 field has the IBSS subfield set to 1. When set to
			 any, the station may synchronize to either type of
			 BSS."
	::= { dot11StationConfigEntry 5 }

dot11OperationalRateSet OBJECT-TYPE
		SYNTAX OCTET STRING (SIZE(1..126))
		MAX-ACCESS read-write
		STATUS current
		DESCRIPTION
			"This attribute shall specify the set of data rates
			 at which the station may transmit data.  Each octet
 			 contains a value representing a rate.  Each rate
			 shall be within the range from 2 to 127,
			 corresponding to data rates in increments of
			 500 kb/s from 1 Mb/s to 63.5 Mb/s, and shall be
			 supported (as indicated in the supported rates
			 table) for receiving data. This value is reported in
			 transmitted Beacon, Probe Request, Probe Response,
			 Association Request, Association Response,
			 Reassociation Request, and Reassociation Response
			 frames, and is used to determine whether a BSS
			 with which the station desires to synchronize is
			 suitable. It is also used when starting a BSS,
			 as specified in  10.3.

			 This atribute also indicate the Basic Rate of the AP,
			 rate that is used as transmit rate of 802.11
			 management and control packet. If 22Mbps is as
			 basic rate, the bit 7(MSB) should be set(i.e. 0xAC,
			 instead of 0x2C).
			 Valid basic rate are (2-1)Mbps, (11-5.5-2-1)Mbps,
			 (22-11-5.5-2-1)Mbps.
			 example:
			    (2-1)Mbps		: 0x2C160B8482
			    (11-5.5-2-1)Mbps	: 0x2C968B8482
			    (22-11-5.5-2-1)Mbps	: 0xAC968B8482"
	::= { dot11StationConfigEntry 6 }

dot11BeaconPeriod OBJECT-TYPE
		SYNTAX INTEGER (1..1000)
		MAX-ACCESS read-write
		STATUS current
		DESCRIPTION
			"This attribute shall specify the number of TU that a
			 station shall use for scheduling Beacon transmissions.
			 This value is transmitted in Beacon and Probe Response
			 frames."
	::= { dot11StationConfigEntry 7 }

dot11DTIMPeriod OBJECT-TYPE
		SYNTAX INTEGER(1..255)
		MAX-ACCESS read-write
		STATUS current
		DESCRIPTION
			"This attribute shall specify the number of beacon
			 intervals that shall elapse between transmission of
			 Beacons frames containing a TIM element whose DTIM
			 Count field is 0. This value is transmitted in
			 the DTIM Period field of Beacon frames."
	::= { dot11StationConfigEntry 8 }

dot11DisassociateReason OBJECT-TYPE
		SYNTAX INTEGER(0..65535)
		MAX-ACCESS read-only
		STATUS current
		DESCRIPTION
			"This attribute holds the most recently
			transmitted Reason Code in a Disassociation
			frame.  If no Disassociation frame has been
			transmitted, the value of this attribute shall
			be 0."

REFERENCE "IEEE Std 802.11-1997, 7.3.1.7"
	::= { dot11StationConfigEntry 9 }

dot11DisassociateStation OBJECT-TYPE
		SYNTAX MacAddress
		MAX-ACCESS read-only
		STATUS current
		DESCRIPTION
			"This attribute holds the MAC address from the
			Address 1 field of the most recently transmitted
			Disassociation frame.  If no Disassociation
			frame has been transmitted, the value of this
			attribute shall be 0."
	::= { dot11StationConfigEntry 10 }

dot11DeauthenticateReason OBJECT-TYPE
		SYNTAX INTEGER(0..65535)
		MAX-ACCESS read-only
		STATUS current
		DESCRIPTION
			"This attribute holds the most recently
			transmitted Reason Code in a Deauthentication
			frame.  If no Deauthentication frame has been
			transmitted, the value of this attribute shall
			be 0."

REFERENCE "IEEE Std 802.11-1997, 7.3.1.7"
	::= { dot11StationConfigEntry 11 }

dot11DeauthenticateStation OBJECT-TYPE
		SYNTAX MacAddress
		MAX-ACCESS read-only
		STATUS current
		DESCRIPTION
			"This attribute holds the MAC address from the
			Address 1 field of the most recently transmitted
			Deauthentication frame.  If no Deauthentication
			frame has been transmitted, the value of this
			attribute shall be 0."
	::= { dot11StationConfigEntry 12 }

dot11AuthenticateFailStatus OBJECT-TYPE
		SYNTAX INTEGER(0..65535)
		MAX-ACCESS read-only
		STATUS current
		DESCRIPTION
			"This attribute holds the most recently
			transmitted Status Code in a failed
			Authentication frame.  If no failed
			Authentication frame has been transmitted, the
			value of this attribute shall be 0."

REFERENCE "IEEE Std 802.11-1997, 7.3.1.9"
	::= { dot11StationConfigEntry 13 }

-- **********************************************************************
-- *    End of dot11StationConfig  TABLE
-- **********************************************************************

-- **********************************************************************
-- *    dot11EnterpriseConfigEntry  TABLE
-- **********************************************************************

dot11AccessPointMode OBJECT-TYPE
        SYNTAX INTEGER {  accessPoint (1),
        		  wirelessBridge (2),
        		  wirelessAPClient (3),
        		  wirelessMultiBridge (4),
        		  backupAccessPoint (5),
        		  repeater (6),
        		  groupAccessPoint (7) }
        MAX-ACCESS read-write
        STATUS current
        DESCRIPTION

        "This attribute shall be a set of all the access point mode
        supported by the AP. The following are the
        default values and the associated mode.
        Value = 1: Normal AP
        Value = 2: Wireless Bridge
        Value = 3: Wireless AP Client
        Value = 4: Wireless Multi Bridge
        Value = 5: Backup AP
        Value = 6: Repeater
        Value = 7: Group AP"

    ::= {  dot11APModeConfigEntry 1 }

dot11RemoteMACAddress OBJECT-TYPE
        SYNTAX MacAddress
        MAX-ACCESS read-write
        STATUS current
        DESCRIPTION

        "This Remote MAC Address used by these following AP mode:
        Wireless Bridge, Wireless AP Client, Backup AP, Repeater.
        Consequently, this attribute must be set if any above mentioned
        mode is desired."

    ::= {  dot11APModeConfigEntry 2 }

dot11BackupAPRemoteServerIPAddress OBJECT-TYPE
        SYNTAX IpAddress
        MAX-ACCESS read-write
        STATUS current
        DESCRIPTION

        "This attribute used to check the wired LAN connection
         (A.K.A. Link Integrity) when AP in Backup AP mode."

    ::= {  dot11APModeConfigEntry 3 }

dot11GroupAPID OBJECT-TYPE
        SYNTAX OCTET STRING (SIZE(0..32))
        MAX-ACCESS read-write
        STATUS current
        DESCRIPTION

        "This attribute is to identify current Group ID of the AP."

    ::= {  dot11APModeConfigEntry 4 }


-- **********************************************************************
-- *    End of dot11EnterpriseConfigEntry  TABLE
-- **********************************************************************

-- **********************************************************************
-- *    dot11PrivacyTable  TABLE
-- **********************************************************************


dot11AuthenticationAlgorithm OBJECT-TYPE
        SYNTAX INTEGER {  openSystem (1), sharedKey (2), both (3) }
        MAX-ACCESS read-only
        STATUS current
        DESCRIPTION

        "This attribute shall be the authentication algorithms currently used
        by the AP. The following are the default values and the associated algorithm.
        Value = 1: Open System
        Value = 2: Shared Key
        Value = 3: Both Open System and Shared Key"

    ::= {  dot11PrivacyEntry 1 }

dot11PrivacyInvoked OBJECT-TYPE
        SYNTAX TruthValue
        MAX-ACCESS read-write
        STATUS current
        DESCRIPTION

        "When this attribute is true, it shall indicate that the IEEE
        802.11 WEP mechanism is used for transmitting frames of type
        Data. The default value of this attribute shall be false."
    ::= {  dot11PrivacyEntry 2 }

dot11WEPDefaultKeyID  OBJECT-TYPE
        SYNTAX INTEGER (0..3)
        MAX-ACCESS read-write
        STATUS current
        DESCRIPTION

            "This attribute shall indicate the use of the first,
            second, third, or fourth element of the WEPDefaultKeys
            array when set to values of zero, one, two, or three.  The
            default value of this attribute shall be 0."
        REFERENCE "IEEE Std 802.11-1997, 8.3.2"
    ::= {  dot11PrivacyEntry 3 }

dot11WEPKeyLength  OBJECT-TYPE
        SYNTAX INTEGER {  w-64Bit (1), w-128Bit (2), w-256Bit (3) }
        MAX-ACCESS read-write
        STATUS current
        DESCRIPTION

            "This attribute shall indicate the length of WEP encryption length used.
             Value 1: 64 bit that need 5 characters of WEP Default Key
             Value 2: 128 bit that need 13 characters of WEP Default Key
             Value 3: 256 bit that need 29 characters of WEP Default Key"
    ::= {  dot11PrivacyEntry 4 }

dot11WEPKeyMappingLength  OBJECT-TYPE
        SYNTAX INTEGER (10..64)
        MAX-ACCESS read-only
        STATUS current
        DESCRIPTION
            "The maximum number of tuples that dot11WEPKeyMappings can hold."
        REFERENCE "IEEE Std 802.11-1997, 8.3.2"
    ::= {  dot11PrivacyEntry 5 }

dot11ExcludeUnencrypted  OBJECT-TYPE
        SYNTAX TruthValue
        MAX-ACCESS read-only
        STATUS current
        DESCRIPTION

        "When this attribute is true, the STA shall not indicate at
        the MAC service interface received MSDUs that have the WEP
        subfield of the Frame Control field equal to zero. When this
        attribute is false, the STA may accept MSDUs that have the WEP
        subfield of the Frame Control field equal to zero. The default
        value of this attribute shall be false."

    ::= {  dot11PrivacyEntry 6 }

dot11WEPICVErrorCount  OBJECT-TYPE
        SYNTAX Counter32
        MAX-ACCESS read-only
        STATUS current
        DESCRIPTION
            "This counter shall increment when a frame is received with the
            WEP subfield of the Frame Control field set to one and the value
            of the ICV as received in the frame does not match the ICV value
            that is calculated for the contents of the received frame."
    ::= {  dot11PrivacyEntry 7 }

dot11WEPExcludedCount  OBJECT-TYPE
        SYNTAX Counter32
        MAX-ACCESS read-only
        STATUS current
        DESCRIPTION
            "This counter shall increment when a frame is received with the
            WEP subfield of the Frame Control field set to zero and the value
            of dot11ExcludeUnencrypted causes that frame to be discarded."
    ::= {  dot11PrivacyEntry 8 }

-- **********************************************************************
-- *    End of dot11Privacy  TABLE
-- **********************************************************************

-- **********************************************************************
-- *    MAC Attribute Templates
-- **********************************************************************

-- **********************************************************************
-- *    dot11OperationTable  TABLE
-- **********************************************************************


dot11MACAddress OBJECT-TYPE
        SYNTAX MacAddress
        MAX-ACCESS read-only
        STATUS current
        DESCRIPTION
                "Unique MAC Address assigned to the STA."
    ::= {  dot11OperationEntry 1 }

dot11RTSThreshold OBJECT-TYPE
        SYNTAX INTEGER (256..2432)
        MAX-ACCESS read-write
        STATUS current
        DESCRIPTION

        "This attribute shall indicate the number of octets in an MPDU,
        below which an RTS/CTS handshake shall not be performed. An
        RTS/CTS handshake shall be performed at the beginning of any
        frame exchange sequence where the MPDU is of type Data or
        Management, the MPDU has an individual address in the Address1
        field, and the length of the MPDU is greater than
        this threshold. (For additional details, refer to Table 21 in
        9.7.) Setting this attribute to be larger than the maximum
        MSDU size shall have the effect of turning off the RTS/CTS
        handshake for frames of Data or Management type transmitted by
        this STA. Setting this attribute to zero shall have the effect
        of turning on the RTS/CTS handshake for all frames of Data or
        Management type transmitted by this STA. The default value of
        this attribute shall be 2347."

    ::= {  dot11OperationEntry 2 }

dot11ShortRetryLimit OBJECT-TYPE
        SYNTAX INTEGER (1..255)
        MAX-ACCESS read-write
        STATUS current
        DESCRIPTION

        "This attribute shall indicate the maximum number of
        transmission attempts of a frame, the length of which is less
        than or equal to dot11RTSThreshold, that shall be made before a
        failure condition is indicated. The default value of this
        attribute shall be 7."

    ::= {  dot11OperationEntry 3 }

dot11LongRetryLimit OBJECT-TYPE
        SYNTAX INTEGER (1..255)
        MAX-ACCESS read-write
        STATUS current
        DESCRIPTION

        "This attribute shall indicate the maximum number of
        transmission attempts of a frame, the length of which is
        greater than dot11RTSThreshold, that shall be made before a
        failure condition is indicated. The default value of this
        attribute shall be 4."

    ::= {  dot11OperationEntry 4 }

dot11FragmentationThreshold OBJECT-TYPE
        SYNTAX INTEGER (256..2346)
        MAX-ACCESS read-write
        STATUS current
        DESCRIPTION

        "This attribute shall specify the current maximum size, in
        octets, of the MPDU that may be delivered to the PHY. An MSDU
        shall be broken into fragments if its size exceeds the value
of this attribute after adding MAC headers and trailers. An MSDU or MMPDU shall be fragmented when the resulting frame has an individual address in the Address1 field, and the length of the frame is larger than this threshold. The default value for this attribute shall be the lesser of 2346 or the aMPDUMaxLength of the attached PHY and shall never exceed the lesser of 2346 or the  aMPDUMaxLength of the attached PHY. The value of this attribute shall never be less than 256. "

    ::= {  dot11OperationEntry 5 }

dot11SSIDBroadcast OBJECT-TYPE
        SYNTAX TruthValue
        MAX-ACCESS read-write
        STATUS current
        DESCRIPTION

            "This attribute indicate whether SSID broadcast is enabled."

    ::= {  dot11OperationEntry 6 }

dot11PreambleType OBJECT-TYPE
        SYNTAX INTEGER {  longPreamble (1), shortPreamble (2) }
        MAX-ACCESS read-write
        STATUS current
        DESCRIPTION

            "This attribute indicate what preamble type is used.
            The default value should be Long Preamble."

    ::= {  dot11OperationEntry 7 }

dot11MaxTransmitMSDULifetime OBJECT-TYPE
        SYNTAX INTEGER (1..65535)
        MAX-ACCESS read-write
        STATUS current
        DESCRIPTION

        "The MaxTransmitMSDULifetime shall be the elapsed time in TU,
        after the initial transmission of an MSDU, after which further
        attempts to transmit the MSDU shall be terminated. The default
        value of this attribute shall be 512."

    ::= {  dot11OperationEntry 8 }

dot11MaxReceiveLifetime OBJECT-TYPE
        SYNTAX INTEGER (1..65535)
        MAX-ACCESS read-write
        STATUS current
        DESCRIPTION

            "The MaxReceiveLifetime shall be the elapsed time in TU,
            after the initial reception of a fragmented MMPDU or MSDU,
            after which further attempts to reassemble the MMPDU or
            MSDU shall be terminated. The default value shall be
            512."
    ::= {  dot11OperationEntry 9 }

dot11ManufacturerID OBJECT-TYPE
        SYNTAX DisplayString (SIZE(0..128))
        MAX-ACCESS read-only
        STATUS current
        DESCRIPTION

            "The ManufacturerID shall include, at a minimum, the name
            of the manufacturer.  It may include additional
            information at the manufacturer's discretion.  The default
            value of this attribute shall be null."

    ::= {  dot11OperationEntry 10 }

dot11ProductID OBJECT-TYPE
        SYNTAX DisplayString (SIZE(0..128))
        MAX-ACCESS read-only
        STATUS current
        DESCRIPTION

            "The ProductID shall include, at a minimum, an identifier
            that is unique to the manufacturer.  It may include
            additional information at the manufacturer's discretion.
            The default value of this attribute shall be null."

    ::= {  dot11OperationEntry 11 }

-- **********************************************************************
-- *    End of dot11OperationEntry  TABLE
-- **********************************************************************

-- **********************************************************************
-- *    dot11Counters TABLE
-- **********************************************************************


dot11TransmittedFragmentCount OBJECT-TYPE
        SYNTAX Counter32
        MAX-ACCESS read-only
        STATUS current
        DESCRIPTION

            "This counter shall be incremented for an acknowledged MPDU
            with an individual address in the address 1 field or an MPDU
            with a multicast address in the address 1 field of type Data
            or Management."

    ::= {  dot11CountersEntry 1 }

dot11MulticastTransmittedFrameCount OBJECT-TYPE
        SYNTAX Counter32
        MAX-ACCESS read-only
        STATUS current
        DESCRIPTION

            " This counter shall increment only when the multicast bit
            is set in the destination MAC address of a successfully
            transmitted MSDU.  When operating as a STA in an ESS, where
            these frames are directed to the AP, this implies having
            received an acknowledgment to all associated MPDUs. "

    ::= {  dot11CountersEntry 2 }

dot11FailedCount OBJECT-TYPE
        SYNTAX Counter32
        MAX-ACCESS read-only
        STATUS current
        DESCRIPTION

        "This counter shall increment when an MSDU is not transmitted
        successfully due to the number of transmit attempts exceeding
        either the  dot11ShortRetryLimit or dot11LongRetryLimit. "

    ::= {  dot11CountersEntry 3 }

dot11RetryCount OBJECT-TYPE
        SYNTAX Counter32
        MAX-ACCESS read-only
        STATUS current
        DESCRIPTION

            "This counter shall increment when an MSDU is successfully
            transmitted after one or more retransmissions."
    ::= {  dot11CountersEntry 4 }

dot11MultipleRetryCount OBJECT-TYPE
        SYNTAX Counter32
        MAX-ACCESS read-only
        STATUS current
        DESCRIPTION

            "This counter shall increment when an MSDU is successfully
            transmitted after more than one retransmission."

    ::= {  dot11CountersEntry 5 }

dot11FrameDuplicateCount  OBJECT-TYPE
        SYNTAX Counter32
        MAX-ACCESS read-only
        STATUS current
        DESCRIPTION

            "This counter shall increment when a frame is received
            that the Sequence Control field indicates is a
            duplicate."

    ::= {  dot11CountersEntry 6 }

dot11RTSSuccessCount OBJECT-TYPE
        SYNTAX Counter32
        MAX-ACCESS read-only
        STATUS current
        DESCRIPTION

            "This counter shall increment when a CTS is received in
            response to an RTS."
        ::= {  dot11CountersEntry 7 }

dot11RTSFailureCount OBJECT-TYPE
        SYNTAX Counter32
        MAX-ACCESS read-only
        STATUS current
        DESCRIPTION


        "This counter shall increment when a CTS is not received in
        response to an RTS."

    ::= { dot11CountersEntry 8 }

dot11ACKFailureCount OBJECT-TYPE
        SYNTAX Counter32
        MAX-ACCESS read-only
        STATUS current
        DESCRIPTION

            "This counter shall increment when an ACK is not received
            when expected."

    ::= {  dot11CountersEntry 9 }

dot11ReceivedFragmentCount OBJECT-TYPE
        SYNTAX Counter32
        MAX-ACCESS read-only
        STATUS current
        DESCRIPTION

            "This counter shall be incremented for each successfully
            received MPDU of type Data or Management."

    ::= {  dot11CountersEntry 10 }

dot11MulticastReceivedFrameCount OBJECT-TYPE
        SYNTAX Counter32
        MAX-ACCESS read-only
        STATUS current
        DESCRIPTION

            "This counter shall increment when a MSDU is received
            with the multicast bit set in the destination
            MAC address."
    ::= {  dot11CountersEntry 11 }

dot11FCSErrorCount OBJECT-TYPE
        SYNTAX Counter32
        MAX-ACCESS read-only
        STATUS current
        DESCRIPTION

            "This counter shall increment when an FCS error is
            detected in a received MPDU."

    ::= {  dot11CountersEntry 12 }

dot11TransmittedFrameCount OBJECT-TYPE
        SYNTAX Counter32
        MAX-ACCESS read-only
        STATUS current
        DESCRIPTION

"This counter shall increment for each successfully transmitted MSDU."

    ::= {  dot11CountersEntry 13 }

dot11WEPUndecryptableCount OBJECT-TYPE
        SYNTAX Counter32
        MAX-ACCESS read-only
        STATUS current
        DESCRIPTION

        "This counter shall increment when a frame is received with
        the WEP subfield of the Frame Control field set to one and the
        WEPOn value for the key mapped to the TA's MAC address
        indicates that the frame should not have been encrypted or
        that frame is discarded due to the receiving STA not
        implementing the privacy option."

    ::= { dot11CountersEntry 14 }

-- **********************************************************************
-- *    End of dot11CountersEntry  TABLE
-- **********************************************************************

-- **********************************************************************
-- *    Resource Type Attribute Templates
-- **********************************************************************
dot11ResourceTypeIDName OBJECT-TYPE
        SYNTAX DisplayString (SIZE(4))
        MAX-ACCESS read-only
        STATUS current
        DESCRIPTION

            "Contains the name of the Resource Type ID managed object.
            The attribute is read-write and always contains the value
            RTID.  This attribute value shall not be used as a naming
            attribute for any other managed object class."

        REFERENCE "IEEE Std 802.1F-1993,  A.7"
        DEFVAL {"RTID"}
    ::= {  dot11resAttribute 1 }

-- **********************************************************************
-- *    dot11ResourceInfo  TABLE
-- **********************************************************************


     --   REFERENCE "IEEE Std 802.1F-1993,  A.7"

dot11ResourceInfoEntry 		OBJECT IDENTIFIER ::= {  dot11resAttribute 2 }

dot11manufacturerOUI OBJECT-TYPE
        SYNTAX OCTET STRING (SIZE(3))
        MAX-ACCESS read-only
        STATUS current
        DESCRIPTION
            "Takes the value of an organizationally unique identifier.
            0x00032F for D-Link, Inc."
    ::= {  dot11ResourceInfoEntry 1 }

dot11manufacturerName OBJECT-TYPE
        SYNTAX DisplayString (SIZE(0..128))
        MAX-ACCESS read-only
        STATUS current
        DESCRIPTION
            "A printable string used to identify the manufacturer of the
            resource.  Maximum string length is 128 octets.
            D-Link, Inc."
    ::= {  dot11ResourceInfoEntry 2 }

dot11manufacturerProductName OBJECT-TYPE
        SYNTAX DisplayString (SIZE(0..128))
        MAX-ACCESS read-only
        STATUS current
        DESCRIPTION
            "A printable string used to identify the manufacturer's product
            name of the resource.  Maximum string length is 128 octets."
    ::= {  dot11ResourceInfoEntry 3 }

dot11manufacturerProductVersion OBJECT-TYPE
        SYNTAX DisplayString (SIZE(0..128))
        MAX-ACCESS read-only
        STATUS current
        DESCRIPTION
            "Printable string used to identify the manufacturer's product
            version of the resource.  Maximum string length is 128 octets."
    ::= {  dot11ResourceInfoEntry 4 }

-- **********************************************************************
-- *    End of dot11ResourceInfo  TABLE
-- **********************************************************************

-- **********************************************************************
-- *   PHY Attribute Templates
-- **********************************************************************

-- **********************************************************************
-- *    dot11PhyOperation  TABLE
-- **********************************************************************

dot11PHYType OBJECT-TYPE
        SYNTAX INTEGER {fhss(1), dsss(2), irbaseband(3)}
        MAX-ACCESS read-only
        STATUS current
        DESCRIPTION

        "This is an 8-bit integer value that identifies the PHY type
        supported by the attached PLCP and PMD. Currently defined
        values and their corresponding PHY types are:

        FHSS 2.4 GHz = 01 , DSSS 2.4 GHz = 02, IR Baseband = 03"

    ::= {  dot11PhyOperationEntry 1 }

dot11CurrentRegDomain OBJECT-TYPE
        SYNTAX Integer32
        MAX-ACCESS read-only
        STATUS current
        DESCRIPTION

            "The current regulatory domain this instance of the PMD is
            supporting.  This object corresponds to one of the
            RegDomains listed in dot11RegDomainsSupported."

    ::= {   dot11PhyOperationEntry 2 }

dot11TempType OBJECT-TYPE
        SYNTAX INTEGER {tempType1(1), tempType2(2) }
        MAX-ACCESS read-only
        STATUS current
        DESCRIPTION

        "There are different operating temperature requirements
        dependent on the anticipated environmental conditions. This
        attribute describes the current PHY's operating temperature
        range capability. Currently defined values and their
        corresponding temperature ranges are:

        Type 1 = X'01'-Commercial range of 0 to 40 degrees C,

        Type 2 = X'02'-Industrial range of -30 to 70 degrees C."

    ::= {   dot11PhyOperationEntry 3 }


dot11RegDomainsSupportValue OBJECT-TYPE

        SYNTAX INTEGER {fcc(16), doc(32), etsi(48), spain (49), france
        (50), mkk (64) }
        MAX-ACCESS read-only
        STATUS current
        DESCRIPTION
            "There are different operational requirements dependent on
            the regulatory domain.  This attribute list describes the
            regulatory domains the PLCP and PMD support in this
            implementation.  Currently de- fined values and their
            corresponding Regulatory Domains are:

            FCC (USA) = X'10', DOC (Canada) = X'20', ETSI (most of
            Europe) = X'30', Spain = X'31', France = X'32', MKK
            (Japan) = X'40' "
    ::= {  dot11PhyOperationEntry 4 }

dot11SupportedDataRatesTxValue OBJECT-TYPE
        SYNTAX Integer32 (2..127)
        MAX-ACCESS read-only
        STATUS current
        DESCRIPTION

            "The Transmit bit rates supported by the PLCP and PMD,
            represented by a count from X?2-X?f, corresponding to data
            rates in increments of 500Kb/s from 1 Mb/s to 63.5 Mb/s subject
            to limitations of each individual PHY."

    ::= {  dot11PhyOperationEntry 5 }

dot11SupportedDataRatesRxValue OBJECT-TYPE
        SYNTAX Integer32 (2..127)
        MAX-ACCESS read-only
        STATUS current
        DESCRIPTION
            "The receive bit rates supported by the PLCP and PMD,
            represented by a count from X?2-X?f, corresponding to data
            rates in increments of 500Kb/s from 1 Mb/s to 63.5 Mb/s."
    ::= {  dot11PhyOperationEntry 6 }

dot11CurrentTxRate OBJECT-TYPE
		SYNTAX INTEGER (2..127)
		MAX-ACCESS read-write
		STATUS current
		DESCRIPTION
			"The current tx operating rate. corresponding to data
            rates in increments of 500Kb/s from 1 Mb/s to 63.5 Mb/s."

	::= { dot11PhyOperationEntry 7 }

dot11ChannelAgilityPresent OBJECT-TYPE
		SYNTAX TruthValue
		MAX-ACCESS read-only
		STATUS current
		DESCRIPTION
		   "This attribute indicates that the PHY is capable of channel agility."

	::= { dot11PhyOperationEntry 8 }

dot11ChannelAgilityEnabled OBJECT-TYPE
		SYNTAX TruthValue
		MAX-ACCESS read-only
		STATUS current
		DESCRIPTION
			"This attribute indicates that the PHY channel agility
			functionality is enabled."

	::= { dot11PhyOperationEntry 9 }


-- **********************************************************************
-- *    End of dot11PhyOperation  TABLE
-- **********************************************************************

-- **********************************************************************
-- *    dot11PhyAntenna  TABLE
-- **********************************************************************

dot11CurrentTxAntenna OBJECT-TYPE
        SYNTAX Integer32 (1..255)
        MAX-ACCESS read-only
        STATUS current
        DESCRIPTION

            "The current antenna being used to transmit.  This value
        is one of the values appearing in
        dot11SupportedTxAntenna. This may be used by a management agent to control which antenna is used for transmission. "

    ::= {  dot11PhyAntennaEntry 1 }

dot11DiversitySupport OBJECT-TYPE
        SYNTAX INTEGER {fixedlist(1), notsupported(2), dynamic(3)}
        MAX-ACCESS read-only
        STATUS current
        DESCRIPTION

        "This implementation's support for diversity, encoded as:

        X'01'-diversity is available and is performed over the fixed
            list of antennas defined in dot11DiversitySelectionRx.

        X'02'-diversity is not supported.

        X'03'-diversity is supported and control of diversity is also
            available, in which case the attribute
            dot11DiversitySelectionRx can be dynamically modified by the
            LME."
    ::= {  dot11PhyAntennaEntry 2 }

dot11CurrentRxAntenna OBJECT-TYPE
        SYNTAX Integer32 (1..255)
        MAX-ACCESS read-only
        STATUS current
        DESCRIPTION

"The current antenna being used to receive, if the dot11 DiversitySupport indicates that diversity is not supported.  The selected antenna shall be one of the antennae marked for receive in the dot11AntennasListTable. "

    ::= {  dot11PhyAntennaEntry 3 }

-- **********************************************************************
-- *    End of dot11PhyAntenna  TABLE
-- **********************************************************************

-- **********************************************************************
-- *    dot11PhyTxPower  TABLE
-- **********************************************************************


dot11NumberSupportedPowerLevels OBJECT-TYPE
        SYNTAX INTEGER (1..8)
        MAX-ACCESS read-only
        STATUS current
        DESCRIPTION
            "The number of power levels supported by the PMD.
            This attribute can have a value of 1 to 8."
    ::= {  dot11PhyTxPowerEntry 1 }

dot11TxPowerLevel1 OBJECT-TYPE
        SYNTAX INTEGER (0..10000)
        MAX-ACCESS read-only
        STATUS current
        DESCRIPTION
            "The transmit output power for LEVEL1 in mW.
            This is also the default power level."
    ::= {   dot11PhyTxPowerEntry 2 }

dot11TxPowerLevel2 OBJECT-TYPE
        SYNTAX INTEGER (0..10000)
        MAX-ACCESS read-only
        STATUS current
        DESCRIPTION
            "The transmit output power for LEVEL2 in mW."
    ::= {   dot11PhyTxPowerEntry 3 }

dot11TxPowerLevel3 OBJECT-TYPE
        SYNTAX INTEGER (0..10000)
        MAX-ACCESS read-only
        STATUS current
        DESCRIPTION
            "The transmit output power for LEVEL3 in mW."
    ::= {   dot11PhyTxPowerEntry 4 }

dot11TxPowerLevel4 OBJECT-TYPE
        SYNTAX INTEGER (0..10000)
        MAX-ACCESS read-only
        STATUS current
        DESCRIPTION
            "The transmit output power for LEVEL4 in mW."
    ::= {   dot11PhyTxPowerEntry 5 }

dot11TxPowerLevel5 OBJECT-TYPE
        SYNTAX INTEGER (0..10000)
        MAX-ACCESS read-only
        STATUS current
        DESCRIPTION
            "The transmit output power for LEVEL5 in mW."
    ::= {   dot11PhyTxPowerEntry 6 }

dot11TxPowerLevel6 OBJECT-TYPE
        SYNTAX INTEGER (0..10000)
        MAX-ACCESS read-only
        STATUS current
        DESCRIPTION
            "The transmit output power for LEVEL6 in mW."
    ::= {   dot11PhyTxPowerEntry 7 }

dot11TxPowerLevel7 OBJECT-TYPE
        SYNTAX INTEGER (0..10000)
        MAX-ACCESS read-only
        STATUS current
        DESCRIPTION
            "The transmit output power for LEVEL7 in mW."
    ::= {   dot11PhyTxPowerEntry 8 }

dot11TxPowerLevel8 OBJECT-TYPE
        SYNTAX INTEGER (0..10000)
        MAX-ACCESS read-only
        STATUS current
        DESCRIPTION
            "The transmit output power for LEVEL8 in mW."
    ::= {   dot11PhyTxPowerEntry 9 }

dot11CurrentTxPowerLevel OBJECT-TYPE
        SYNTAX INTEGER (1..8)
        MAX-ACCESS read-only
        STATUS current
        DESCRIPTION

            "The TxPowerLevel N currently being used to transmit data.
            Some PHYs also use this value to determine the receiver
            sensitivity requirements for CCA."

    ::= {   dot11PhyTxPowerEntry 10 }

-- **********************************************************************
-- *    End of dot11PhyTxPower  TABLE
-- **********************************************************************

-- **********************************************************************
-- *    dot11PhyDSSSEntry  TABLE
-- **********************************************************************

dot11CurrentChannel OBJECT-TYPE
        SYNTAX INTEGER (1..14)
        MAX-ACCESS read-write
        STATUS current
        DESCRIPTION
            "The current operating frequency channel of the DSSS
            PHY. Valid channel numbers are as defined in 15.4.6.2"
    ::= {   dot11PhyDSSSEntry 1 }

dot11DynamicChannelEnabled OBJECT-TYPE
        SYNTAX TruthValue
        MAX-ACCESS read-write
        STATUS current
        DESCRIPTION
            "This attribute indicate dynamic channel is enabled."
    ::= {   dot11PhyDSSSEntry 2 }

dot11CCAModeSupported OBJECT-TYPE
        SYNTAX INTEGER (1..7)
        MAX-ACCESS read-only
        STATUS current
        DESCRIPTION
            "dot11CCAModeSupported is a bit-significant value, representing all of the CCA modes supported by the PHY.  Valid values are:

            energy detect only (ED_ONLY) = 01,
		carrier sense only (CS_ONLY) = 02,
		carrier sense and energy detect (ED_and_CS)= 04

or the logical sum of any of these values."
    ::= {   dot11PhyDSSSEntry 3 }

dot11CurrentCCAMode OBJECT-TYPE
        SYNTAX INTEGER {edonly(1), csonly(2), edandcs(4)}
        MAX-ACCESS read-only
        STATUS current
        DESCRIPTION
            "The current CCA method in operation.   Valid values are:
                energy detect only (edonly) = 01,
                carrier sense only (csonly) = 02,
                carrier sense and energy detect (edandcs)= 04."
::= {   dot11PhyDSSSEntry 4 }

dot11EDThreshold OBJECT-TYPE
        SYNTAX Integer32
        MAX-ACCESS read-write
        STATUS current
        DESCRIPTION
            "The current Energy Detect Threshold being used by the DSSS PHY."
    ::= {   dot11PhyDSSSEntry 5 }

dot11ShortPreambleOptionImplemented OBJECT-TYPE
		SYNTAX INTEGER {true(1), false(2)}
		MAX-ACCESS read-only
		STATUS current
		DESCRIPTION
			"This attribute, when true, shall indicate that the short
			preamble option as deTned in subclause 18.2.2.2 is implemented.
			The default value of this attribute shall be false."

	::= { dot11PhyDSSSEntry 6 }

dot11PBCCOptionImplemented OBJECT-TYPE
		SYNTAX INTEGER {true(1), false(2)}
		MAX-ACCESS read-only
		STATUS current
		DESCRIPTION
		    "This attribute, when true, shall indicate that the PBCC modulation
		    option as defined in subclause 18.4.6.6 is implemented. The default
		    value of this attribute shall be false."

	::= { dot11PhyDSSSEntry 7 }

-- **********************************************************************
-- *    End of dot11PhyDSSSEntry  TABLE
-- **********************************************************************

-- **********************************************************************
-- *   End of 80211 MIB
-- **********************************************************************
END
