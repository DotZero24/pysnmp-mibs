DLINK-3100-SAFE-GUARD-MIB DEFINITIONS ::= BEGIN

          IMPORTS
                rnd                                         FROM DLINK-3100-MIB
                DisplayString, TruthValue                   FROM SNMPv2-TC
                Counter32, OBJECT-TYPE, MODULE-IDENTITY     FROM SNMPv2-SMI
                TruthValue                                  FROM SNMPv2-TC;


-- module

        rlSafeGuard MODULE-IDENTITY
            LAST-UPDATED "2007111800Z"
            ORGANIZATION "Dlink, Inc."
            CONTACT-INFO
                "www.dlink.com"
            DESCRIPTION
                "Safe Guard MIBs"
            REVISION "200711180000Z"
            DESCRIPTION
                    "Initial revision."

            ::={ rnd 131 }

        rlSafeGuardEnabled OBJECT-TYPE
            SYNTAX TruthValue
            MAX-ACCESS  read-write
            STATUS  current
            DESCRIPTION
                "The scalar enables/disables Safeguard engine."
            DEFVAL { false }
            ::= { rlSafeGuard 1 }

        rlSafeGuardStatus OBJECT-TYPE
            SYNTAX INTEGER  {
                idle(0),
                attack(1)
            }
            MAX-ACCESS  read-only
            STATUS  current
            DESCRIPTION
              "Returns the SafeGuard status."
            ::= { rlSafeGuard 2  }

        rlSafeGuardCpuUtilizationUpper OBJECT-TYPE
            SYNTAX  INTEGER (1..100)
            -- UNITS "percentage"
            MAX-ACCESS  read-write
            STATUS  current
            DESCRIPTION
                "The scalar defines CPU utilization percentage threshold for detection of the start of an attack."
            DEFVAL { 70 }
            ::= { rlSafeGuard 3 }

        rlSafeGuardCpuUtilizationLower OBJECT-TYPE
            SYNTAX  INTEGER (1..100)
            -- UNITS "percentage"
            MAX-ACCESS  read-write
            STATUS  current
            DESCRIPTION
                "The scalar defines CPU utilization percentage threshold for detection of the end of an attack."
            DEFVAL { 20 }
            ::= { rlSafeGuard 4 }

        rlSafeGuardBroadcastRateUpper OBJECT-TYPE
            SYNTAX  INTEGER (90..1000)
            -- UNITS "packets per second"
            MAX-ACCESS  read-write
            STATUS  current
            DESCRIPTION
                "The scalar defines Broadcast rate threshold for detection of the start of an attack."
            DEFVAL { 350 }
            ::= { rlSafeGuard 5 }

        rlSafeGuardBroadcastRateLower OBJECT-TYPE
            SYNTAX  INTEGER (90..1000)
            -- UNITS "packets per second"
            MAX-ACCESS  read-write
            STATUS  current
            DESCRIPTION
                "The scalar defines Broadcast rate threshold for detection of the end of an attack."
            DEFVAL { 100 }
            ::= { rlSafeGuard 6 }

          END
