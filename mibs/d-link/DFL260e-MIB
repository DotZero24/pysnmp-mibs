--
-- DFL-260e SMIv2 module
--

DFL260e-MIB DEFINITIONS ::= BEGIN

IMPORTS
    MODULE-COMPLIANCE, OBJECT-GROUP
        FROM SNMPv2-CONF
    Counter32, Counter64, Gauge32, Integer32, MODULE-IDENTITY,
    OBJECT-TYPE, enterprises
        FROM SNMPv2-SMI
    DisplayString
        FROM SNMPv2-TC;

dfl260e-MIB MODULE-IDENTITY
    LAST-UPDATED "201009021139Z"
    ORGANIZATION
        "D-Link Corporation"
    CONTACT-INFO
        "Postal: D-Link Corporation
         No. 289, Sinhu 3rd Road,
         Neihu District, Taipei City 114,
         Taiwan, R.O.C.
         Tel: +886-2-66000123
         Fax: +886-2-55509988"
    DESCRIPTION
        "The MIB module for D-Link DFL-260e series product."

    REVISION  "201009021139Z"
    DESCRIPTION
        "Added 64-bit counters"
    REVISION  "201003300900Z"
    DESCRIPTION
        "Added values for SMTP ALG objects."
    REVISION  "200911100916Z"
    DESCRIPTION
        "Added values for opened and closed connections per second"
    REVISION  "200811181605Z"
    DESCRIPTION
        "Added value for timer usage"
    REVISION  "200810141227Z"
    DESCRIPTION
        "Added values for memory usage and TCP buffer usage"
    REVISION  "200710310000Z"
    DESCRIPTION
        "Initial version."
    ::= { dfl260eMibModules 2 }


dlink OBJECT IDENTIFIER
    ::= { enterprises 171 }

netdefendMgmt OBJECT IDENTIFIER
    ::= { dlink 20 }

utmFirewall OBJECT IDENTIFIER
    ::= { netdefendMgmt 2 }

dfl260e OBJECT IDENTIFIER
    ::= { utmFirewall 6 }

dfl260eOS OBJECT IDENTIFIER
    ::= { dfl260e 1 }

dfl260eOSStats OBJECT IDENTIFIER
    ::= { dfl260eOS 2 }

dfl260ereg OBJECT IDENTIFIER
    ::= { dfl260e 2 }

dfl260eMibModules OBJECT IDENTIFIER
    ::= { dfl260ereg 1 }

dfl260eMibConfs OBJECT IDENTIFIER
    ::= { dfl260ereg 2 }

dfl260eMibObjectGroups OBJECT IDENTIFIER
    ::= { dfl260ereg 3 }


dfl260eSystem OBJECT IDENTIFIER
    ::= { dfl260eOSStats 1 }

dfl260eSysCpuLoad OBJECT-TYPE
    SYNTAX      Gauge32
    MAX-ACCESS  read-only
    STATUS      current
    DESCRIPTION
        "The system cpu load."
    ::= { dfl260eSystem 1 }

dfl260eSysForwardedBits OBJECT-TYPE
    SYNTAX      Counter32
    MAX-ACCESS  read-only
    STATUS      current
    DESCRIPTION
        "The number of bits forwarded through the gateway."
    ::= { dfl260eSystem 2 }

dfl260eSysForwardedPackets OBJECT-TYPE
    SYNTAX      Counter32
    MAX-ACCESS  read-only
    STATUS      current
    DESCRIPTION
        "Total number of forwarded packets."
    ::= { dfl260eSystem 3 }

dfl260eSysBuffUse OBJECT-TYPE
    SYNTAX      Gauge32
    MAX-ACCESS  read-only
    STATUS      current
    DESCRIPTION
        "The current number of buffers in use."
    ::= { dfl260eSystem 4 }

dfl260eSysConns OBJECT-TYPE
    SYNTAX      Gauge32
    MAX-ACCESS  read-only
    STATUS      current
    DESCRIPTION
        "The numer of connections."
    ::= { dfl260eSystem 5 }

dfl260eSysPerStateCounters OBJECT IDENTIFIER
    ::= { dfl260eSystem 6 }

dfl260eSysPscTcpSyn OBJECT-TYPE
    SYNTAX      Gauge32
    MAX-ACCESS  read-only
    STATUS      current
    DESCRIPTION
        "Number of TCP connections in the SYN state."
    ::= { dfl260eSysPerStateCounters 1 }

dfl260eSysPscTcpOpen OBJECT-TYPE
    SYNTAX      Gauge32
    MAX-ACCESS  read-only
    STATUS      current
    DESCRIPTION
        "Number of TCP connections in the OPEN state."
    ::= { dfl260eSysPerStateCounters 2 }

dfl260eSysPscTcpFin OBJECT-TYPE
    SYNTAX      Gauge32
    MAX-ACCESS  read-only
    STATUS      current
    DESCRIPTION
        "Number of TCP connections in the FIN state."
    ::= { dfl260eSysPerStateCounters 3 }

dfl260eSysPscUdp OBJECT-TYPE
    SYNTAX      Gauge32
    MAX-ACCESS  read-only
    STATUS      current
    DESCRIPTION
        "Number of UDP connections."
    ::= { dfl260eSysPerStateCounters 4 }

dfl260eSysPscIcmp OBJECT-TYPE
    SYNTAX      Gauge32
    MAX-ACCESS  read-only
    STATUS      current
    DESCRIPTION
        "Number of ICMP connections."
    ::= { dfl260eSysPerStateCounters 5 }

dfl260eSysPscOther OBJECT-TYPE
    SYNTAX      Gauge32
    MAX-ACCESS  read-only
    STATUS      current
    DESCRIPTION
        "Number of other connections."
    ::= { dfl260eSysPerStateCounters 6 }

dfl260eIfStatsTable OBJECT-TYPE
    SYNTAX      SEQUENCE OF Dfl260eIfStatsEntry
    MAX-ACCESS  not-accessible
    STATUS      current
    DESCRIPTION
        "A table of DFL-260e specific interfaces statistics"
    ::= { dfl260eSystem 7 }

dfl260eIfStatsEntry OBJECT-TYPE
    SYNTAX      Dfl260eIfStatsEntry
    MAX-ACCESS  not-accessible
    STATUS      current
    DESCRIPTION
        "The row in a table of DFL-260e specific interface statistics"
    INDEX       { dfl260eIfStatsIndex }
    ::= { dfl260eIfStatsTable 1 }

Dfl260eIfStatsEntry ::= SEQUENCE {
    dfl260eIfStatsIndex     Integer32,
    dfl260eIfName           DisplayString,
    dfl260eIfFragsIn        Counter32,
    dfl260eIfFragReassOk    Counter32,
    dfl260eIfFragReassFail  Counter32,
    dfl260eIfPktsInCnt      Counter32,
    dfl260eIfPktsOutCnt     Counter32,
    dfl260eIfBitsInCnt      Counter32,
    dfl260eIfBitsOutCnt     Counter32,
    dfl260eIfPktsTotCnt     Counter32,
    dfl260eIfBitsTotCnt     Counter32,
    dfl260eIfHCPktsInCnt    Counter64,
    dfl260eIfHCPktsOutCnt   Counter64,
    dfl260eIfHCBitsInCnt    Counter64,
    dfl260eIfHCBitsOutCnt   Counter64,
    dfl260eIfHCPktsTotCnt   Counter64,
    dfl260eIfHCBitsTotCnt   Counter64
}

dfl260eIfStatsIndex OBJECT-TYPE
    SYNTAX      Integer32 (1..2147483647)
    MAX-ACCESS  not-accessible
    STATUS      current
    DESCRIPTION
        "Index of a row in dfl260eSysIfStatsTable"
    ::= { dfl260eIfStatsEntry 1 }

dfl260eIfName OBJECT-TYPE
    SYNTAX      DisplayString
    MAX-ACCESS  read-only
    STATUS      current
    DESCRIPTION
        "The name of the interface."
    ::= { dfl260eIfStatsEntry 2 }

dfl260eIfFragsIn OBJECT-TYPE
    SYNTAX      Counter32
    MAX-ACCESS  read-only
    STATUS      current
    DESCRIPTION
        "Number of IP packet fragments received
         in the interface."
    ::= { dfl260eIfStatsEntry 3 }

dfl260eIfFragReassOk OBJECT-TYPE
    SYNTAX      Counter32
    MAX-ACCESS  read-only
    STATUS      current
    DESCRIPTION
        "Number of complete IP packets successfully
         reassembled from the fragments received in
         the interface."
    ::= { dfl260eIfStatsEntry 4 }

dfl260eIfFragReassFail OBJECT-TYPE
    SYNTAX      Counter32
    MAX-ACCESS  read-only
    STATUS      current
    DESCRIPTION
        "Number of packets that could not be reassembled,
         either due to resource starvation, illegal fragmentation,
         or just packet loss."
    ::= { dfl260eIfStatsEntry 5 }

dfl260eIfPktsInCnt OBJECT-TYPE
    SYNTAX      Counter32
    MAX-ACCESS  read-only
    STATUS      current
    DESCRIPTION
        "Number of packets received by the interface."
    ::= { dfl260eIfStatsEntry 6 }

dfl260eIfPktsOutCnt OBJECT-TYPE
    SYNTAX      Counter32
    MAX-ACCESS  read-only
    STATUS      current
    DESCRIPTION
        "Number of packets sent by the interface"
    ::= { dfl260eIfStatsEntry 7 }

dfl260eIfBitsInCnt OBJECT-TYPE
    SYNTAX      Counter32
    MAX-ACCESS  read-only
    STATUS      current
    DESCRIPTION
        "Number of bits received by the interface"
    ::= { dfl260eIfStatsEntry 8 }

dfl260eIfBitsOutCnt OBJECT-TYPE
    SYNTAX      Counter32
    MAX-ACCESS  read-only
    STATUS      current
    DESCRIPTION
        "Number of bits sent by the interface"
    ::= { dfl260eIfStatsEntry 9 }

dfl260eIfPktsTotCnt OBJECT-TYPE
    SYNTAX      Counter32
    MAX-ACCESS  read-only
    STATUS      current
    DESCRIPTION
        "Totat number of packets transmited by the interface"
    ::= { dfl260eIfStatsEntry 10 }

dfl260eIfBitsTotCnt OBJECT-TYPE
    SYNTAX      Counter32
    MAX-ACCESS  read-only
    STATUS      current
    DESCRIPTION
        "Totat number of bits transmited by the interface"
    ::= { dfl260eIfStatsEntry 11 }

dfl260eIfHCPktsInCnt OBJECT-TYPE
    SYNTAX      Counter64
    MAX-ACCESS  read-only
    STATUS      current
    DESCRIPTION
        "Number of packets received by the interface.
        This object is a 64-bit version of dfl260eIfPktsInCnt."
    ::= { dfl260eIfStatsEntry 12 }

dfl260eIfHCPktsOutCnt OBJECT-TYPE
    SYNTAX      Counter64
    MAX-ACCESS  read-only
    STATUS      current
    DESCRIPTION
        "Number of packets sent by the interface.
        This object is a 64-bit version of dfl260eIfPktsOutCnt."
    ::= { dfl260eIfStatsEntry 13 }

dfl260eIfHCBitsInCnt OBJECT-TYPE
    SYNTAX      Counter64
    MAX-ACCESS  read-only
    STATUS      current
    DESCRIPTION
        "Number of bits received by the interface.
        This object is a 64-bit version of dfl260eIfBitsInCnt."
    ::= { dfl260eIfStatsEntry 14 }

dfl260eIfHCBitsOutCnt OBJECT-TYPE
    SYNTAX      Counter64
    MAX-ACCESS  read-only
    STATUS      current
    DESCRIPTION
        "Number of bits sent by the interface.
        This object is a 64-bit version of dfl260eIfBitsOutCnt."
    ::= { dfl260eIfStatsEntry 15 }

dfl260eIfHCPktsTotCnt OBJECT-TYPE
    SYNTAX      Counter64
    MAX-ACCESS  read-only
    STATUS      current
    DESCRIPTION
        "Totat number of packets transmited by the interface.
        This object is a 64-bit version of dfl260eIfPktsTotCnt."
    ::= { dfl260eIfStatsEntry 16 }

dfl260eIfHCBitsTotCnt OBJECT-TYPE
    SYNTAX      Counter64
    MAX-ACCESS  read-only
    STATUS      current
    DESCRIPTION
        "Totat number of bits transmited by the interface.
        This object is a 64-bit version of dfl260eIfBitsTotCnt."
    ::= { dfl260eIfStatsEntry 17 }

dfl260eIfRxRingTable OBJECT-TYPE
    SYNTAX      SEQUENCE OF Dfl260eIfRxRingEntry
    MAX-ACCESS  not-accessible
    STATUS      current
    DESCRIPTION
        "A table of DFL-260e specific interface Rx ring statistics"
    ::= { dfl260eSystem 8 }

dfl260eIfRxRingEntry OBJECT-TYPE
    SYNTAX      Dfl260eIfRxRingEntry
    MAX-ACCESS  not-accessible
    STATUS      current
    DESCRIPTION
        "The row in a table of DFL-260e specific interface Rx ring
         statistics."
    INDEX       { dfl260eIfRxRingIndex }
    ::= { dfl260eIfRxRingTable 1 }

Dfl260eIfRxRingEntry ::= SEQUENCE {
    dfl260eIfRxRingIndex        Integer32,
    dfl260eIfRxRingFifoErrors   Counter32,
    dfl260eIfRxDespools         Gauge32,
    dfl260eIfRxAvgUse           Gauge32,
    dfl260eIfRxRingSaturation   Gauge32,
    dfl260eRxRingFlooded        Gauge32
}

dfl260eIfRxRingIndex OBJECT-TYPE
    SYNTAX      Integer32 (1..2147483647)
    MAX-ACCESS  not-accessible
    STATUS      current
    DESCRIPTION
        "Index of a row in dfl260eIfRxRingTable."
    ::= { dfl260eIfRxRingEntry 1 }

dfl260eIfRxRingFifoErrors OBJECT-TYPE
    SYNTAX      Counter32
    MAX-ACCESS  read-only
    STATUS      current
    DESCRIPTION
        "Rx Ring number of FIFO errors."
    ::= { dfl260eIfRxRingEntry 2 }

dfl260eIfRxDespools OBJECT-TYPE
    SYNTAX      Gauge32
    MAX-ACCESS  read-only
    STATUS      current
    DESCRIPTION
        "Number of despool events per second."
    ::= { dfl260eIfRxRingEntry 3 }

dfl260eIfRxAvgUse OBJECT-TYPE
    SYNTAX      Gauge32
    MAX-ACCESS  read-only
    STATUS      current
    DESCRIPTION
        "Rx Ring average usage."
    ::= { dfl260eIfRxRingEntry 4 }

dfl260eIfRxRingSaturation OBJECT-TYPE
    SYNTAX      Gauge32
    MAX-ACCESS  read-only
    STATUS      current
    DESCRIPTION
        "Rx Ring sturation. Percentage of ring use per despool
         event when the ring has been more than half full."
    ::= { dfl260eIfRxRingEntry 5 }

dfl260eRxRingFlooded OBJECT-TYPE
    SYNTAX      Gauge32
    MAX-ACCESS  read-only
    STATUS      current
    DESCRIPTION
        "Rx Ring number of despool events for which
         the ring has been completely flooded"
    ::= { dfl260eIfRxRingEntry 6 }

dfl260eIfTxRingTable OBJECT-TYPE
    SYNTAX      SEQUENCE OF Dfl260eIfTxRingEntry
    MAX-ACCESS  not-accessible
    STATUS      current
    DESCRIPTION
        "A table of DFL-260e specific interface Tx ring statistics"
    ::= { dfl260eSystem 9 }

dfl260eIfTxRingEntry OBJECT-TYPE
    SYNTAX      Dfl260eIfTxRingEntry
    MAX-ACCESS  not-accessible
    STATUS      current
    DESCRIPTION
        "The row in a table of DFL-260e specific interface Tx ring
         statistics."
    INDEX       { dfl260eIfTxRingIndex }
    ::= { dfl260eIfTxRingTable 1 }

Dfl260eIfTxRingEntry ::= SEQUENCE {
    dfl260eIfTxRingIndex        Integer32,
    dfl260eIfTxDespools         Gauge32,
    dfl260eIfTxAvgUse           Gauge32,
    dfl260eIfTxRingSaturation   Gauge32,
    dfl260eRxTingFlooded        Gauge32
}

dfl260eIfTxRingIndex OBJECT-TYPE
    SYNTAX      Integer32 (1..2147483647)
    MAX-ACCESS  not-accessible
    STATUS      current
    DESCRIPTION
        "Index of a row in dfl260eIfRxRingTable."
    ::= { dfl260eIfTxRingEntry 1 }

dfl260eIfTxDespools OBJECT-TYPE
    SYNTAX      Gauge32
    MAX-ACCESS  read-only
    STATUS      current
    DESCRIPTION
        "Tx Ring number of despool event per second (polls when
         there is at least one buffer in the ring)"
    ::= { dfl260eIfTxRingEntry 2 }

dfl260eIfTxAvgUse OBJECT-TYPE
    SYNTAX      Gauge32
    MAX-ACCESS  read-only
    STATUS      current
    DESCRIPTION
        "Tx Ring number of despool events when the ring has
         been completely flooded"
    ::= { dfl260eIfTxRingEntry 3 }

dfl260eIfTxRingSaturation OBJECT-TYPE
    SYNTAX      Gauge32
    MAX-ACCESS  read-only
    STATUS      current
    DESCRIPTION
        "Tx Ring percentage of use per despool event when the
         ring has been more than half full."
    ::= { dfl260eIfTxRingEntry 4 }

dfl260eRxTingFlooded OBJECT-TYPE
    SYNTAX      Gauge32
    MAX-ACCESS  read-only
    STATUS      current
    DESCRIPTION
        "Tx Ring number of despool events for in which the ring has
         been completely flooded"
    ::= { dfl260eIfTxRingEntry 5 }

dfl260eIfVlanStatsTable OBJECT-TYPE
    SYNTAX      SEQUENCE OF Dfl260eIfVlanStatsEntry
    MAX-ACCESS  not-accessible
    STATUS      current
    DESCRIPTION
        "A table of DFL-260e VLAN statistics"
    ::= { dfl260eSystem 10 }

dfl260eIfVlanStatsEntry OBJECT-TYPE
    SYNTAX      Dfl260eIfVlanStatsEntry
    MAX-ACCESS  not-accessible
    STATUS      current
    DESCRIPTION
        "The row in a table of dfl260eIfVlanStatsTable. Each has an index
         equal to the ifIndex of the corresponding physical interface"
    INDEX       { dfl260eIfVlanIndex }
    ::= { dfl260eIfVlanStatsTable 1 }

Dfl260eIfVlanStatsEntry ::= SEQUENCE {
    dfl260eIfVlanIndex              Integer32,
    dfl260eIfVlanUntaggedInPkts     Counter32,
    dfl260eIfVlanUntaggedOutPkts    Counter32,
    dfl260eIfVlanUntaggedTotPkts    Counter32,
    dfl260eIfVlanUntaggedInOctets   Counter32,
    dfl260eIfVlanUntaggedOutOctets  Counter32,
    dfl260eIfVlanUntaggedTotOctets  Counter32
}

dfl260eIfVlanIndex OBJECT-TYPE
    SYNTAX      Integer32 (1..2147483647)
    MAX-ACCESS  not-accessible
    STATUS      current
    DESCRIPTION
        "Extended index of a row in dfl260eIfVlanStatsTable."
    ::= { dfl260eIfVlanStatsEntry 1 }

dfl260eIfVlanUntaggedInPkts OBJECT-TYPE
    SYNTAX      Counter32
    MAX-ACCESS  read-only
    STATUS      current
    DESCRIPTION
        "Number of untaged packets untagged packets received by the interface."
    ::= { dfl260eIfVlanStatsEntry 2 }

dfl260eIfVlanUntaggedOutPkts OBJECT-TYPE
    SYNTAX      Counter32
    MAX-ACCESS  read-only
    STATUS      current
    DESCRIPTION
        "Number of untagged packets sent by the interface."
    ::= { dfl260eIfVlanStatsEntry 3 }

dfl260eIfVlanUntaggedTotPkts OBJECT-TYPE
    SYNTAX      Counter32
    MAX-ACCESS  read-only
    STATUS      current
    DESCRIPTION
        "Total number of untagged packets processed by the interface."
    ::= { dfl260eIfVlanStatsEntry 4 }

dfl260eIfVlanUntaggedInOctets OBJECT-TYPE
    SYNTAX      Counter32
    MAX-ACCESS  read-only
    STATUS      current
    DESCRIPTION
        "Total number of octects in untagged packets received by the interface."
    ::= { dfl260eIfVlanStatsEntry 5 }

dfl260eIfVlanUntaggedOutOctets OBJECT-TYPE
    SYNTAX      Counter32
    MAX-ACCESS  read-only
    STATUS      current
    DESCRIPTION
        "Total number of octects in untagged packets sent by the interface."
    ::= { dfl260eIfVlanStatsEntry 6 }

dfl260eIfVlanUntaggedTotOctets OBJECT-TYPE
    SYNTAX      Counter32
    MAX-ACCESS  read-only
    STATUS      current
    DESCRIPTION
        "Total number of octects in untagged packets processed by the
         interface."
    ::= { dfl260eIfVlanStatsEntry 7 }

dfl260eHWSensorTable OBJECT-TYPE
    SYNTAX      SEQUENCE OF Dfl260eHWSensorEntry
    MAX-ACCESS  not-accessible
    STATUS      current
    DESCRIPTION
        "Table of hardware sensors."
    ::= { dfl260eSystem 11 }

dfl260eHWSensorEntry OBJECT-TYPE
    SYNTAX      Dfl260eHWSensorEntry
    MAX-ACCESS  not-accessible
    STATUS      current
    DESCRIPTION
        "Entry  of table of hardware sensors."
    INDEX       { dfl260eHWSensorIndex }
    ::= { dfl260eHWSensorTable 1 }

Dfl260eHWSensorEntry ::= SEQUENCE {
    dfl260eHWSensorIndex    Integer32,
    dfl260eHWSensorName     DisplayString,
    dfl260eHWSensorValue    Gauge32,
    dfl260eHWSensorUnit     DisplayString
}

dfl260eHWSensorIndex OBJECT-TYPE
    SYNTAX      Integer32 (1..2147483647)
    MAX-ACCESS  not-accessible
    STATUS      current
    DESCRIPTION
        "Index of the entries of the sensor table."
    ::= { dfl260eHWSensorEntry 1 }

dfl260eHWSensorName OBJECT-TYPE
    SYNTAX      DisplayString
    MAX-ACCESS  read-only
    STATUS      current
    DESCRIPTION
        "The description of the sensor."
    ::= { dfl260eHWSensorEntry 2 }

dfl260eHWSensorValue OBJECT-TYPE
    SYNTAX      Gauge32
    MAX-ACCESS  read-only
    STATUS      current
    DESCRIPTION
        "The value of the sensor."
    ::= { dfl260eHWSensorEntry 3 }

dfl260eHWSensorUnit OBJECT-TYPE
    SYNTAX      DisplayString
    MAX-ACCESS  read-only
    STATUS      current
    DESCRIPTION
        "The description of the unit of the value mesured by sensor."
    ::= { dfl260eHWSensorEntry 4 }

dfl260eSysMemUsage OBJECT-TYPE
    SYNTAX      Gauge32
    MAX-ACCESS  read-only
    STATUS      current
    DESCRIPTION
        "The current memory usage."
    ::= { dfl260eSystem 12 }

dfl260eSysTCPUsage OBJECT IDENTIFIER
    ::= { dfl260eSystem 13 }

dfl260eSysTCPRecvSmall OBJECT-TYPE
    SYNTAX      Gauge32
    MAX-ACCESS  read-only
    STATUS      current
    DESCRIPTION
        "Small TCP receive windows usage."
    ::= { dfl260eSysTCPUsage 1 }

dfl260eSysTCPRecvLarge OBJECT-TYPE
    SYNTAX      Gauge32
    MAX-ACCESS  read-only
    STATUS      current
    DESCRIPTION
        "Large TCP receive windows usage."
    ::= { dfl260eSysTCPUsage 2 }

dfl260eSysTCPSendSmall OBJECT-TYPE
    SYNTAX      Gauge32
    MAX-ACCESS  read-only
    STATUS      current
    DESCRIPTION
        "Small TCP send windows usage."
    ::= { dfl260eSysTCPUsage 3 }

dfl260eSysTCPSendLarge OBJECT-TYPE
    SYNTAX      Gauge32
    MAX-ACCESS  read-only
    STATUS      current
    DESCRIPTION
        "Large TCP send windows usage."
    ::= { dfl260eSysTCPUsage 4 }

dfl260eSysTimerUsage OBJECT-TYPE
    SYNTAX      Gauge32
    MAX-ACCESS  read-only
    STATUS      current
    DESCRIPTION
        "The current number of timers in use."
    ::= { dfl260eSystem 14 }

dfl260eSysConnOPS OBJECT-TYPE
    SYNTAX      Gauge32
    MAX-ACCESS  read-only
    STATUS      current
    DESCRIPTION
        "The number of connections opened per second."
    ::= { dfl260eSystem 15 }

dfl260eSysConnCPS OBJECT-TYPE
    SYNTAX      Gauge32
    MAX-ACCESS  read-only
    STATUS      current
    DESCRIPTION
        "The number of connections closed per second."
    ::= { dfl260eSystem 16 }

dfl260eSysHCForwardedBits OBJECT-TYPE
    SYNTAX      Counter64
    MAX-ACCESS  read-only
    STATUS      current
    DESCRIPTION
        "The number of bits forwarded through the gateway."
    ::= { dfl260eSystem 17 }

dfl260eVPN OBJECT IDENTIFIER
    ::= { dfl260eOSStats 2 }

dfl260eIPsec OBJECT IDENTIFIER
    ::= { dfl260eVPN 1 }

dfl260eIPsecGlobal OBJECT IDENTIFIER
    ::= { dfl260eIPsec 1 }

dfl260eIPsecPhaseOneActive OBJECT-TYPE
    SYNTAX      Gauge32
    MAX-ACCESS  read-only
    STATUS      current
    DESCRIPTION
        "Number of Phase-1 active negotiations"
    ::= { dfl260eIPsecGlobal 1 }

dfl260eIPsecPhaseOneAggrModeDone OBJECT-TYPE
    SYNTAX      Gauge32
    MAX-ACCESS  read-only
    STATUS      current
    DESCRIPTION
        "Number of Phase-1 aggressive mode negotiations."
    ::= { dfl260eIPsecGlobal 2 }

dfl260eIPsecQuickModeActive OBJECT-TYPE
    SYNTAX      Gauge32
    MAX-ACCESS  read-only
    STATUS      current
    DESCRIPTION
        "Number of quick mode active negotiations."
    ::= { dfl260eIPsecGlobal 3 }

dfl260eIPsecPhaseOneDone OBJECT-TYPE
    SYNTAX      Counter32
    MAX-ACCESS  read-only
    STATUS      current
    DESCRIPTION
        "Number of Phase-1 negotiations done."
    ::= { dfl260eIPsecGlobal 4 }

dfl260eIPsecPhaseOneFailed OBJECT-TYPE
    SYNTAX      Counter32
    MAX-ACCESS  read-only
    STATUS      current
    DESCRIPTION
        "Number of Phase-1 negotiations failed."
    ::= { dfl260eIPsecGlobal 5 }

dfl260eIPsecPhaseOneRekeyed OBJECT-TYPE
    SYNTAX      Counter32
    MAX-ACCESS  read-only
    STATUS      current
    DESCRIPTION
        "Number of Phase-1 negotiations rekeyed."
    ::= { dfl260eIPsecGlobal 6 }

dfl260eIPsecQuickModeDone OBJECT-TYPE
    SYNTAX      Counter32
    MAX-ACCESS  read-only
    STATUS      current
    DESCRIPTION
        "Number of quick mode  negotiations done."
    ::= { dfl260eIPsecGlobal 7 }

dfl260eIPsecQuickModeFailed OBJECT-TYPE
    SYNTAX      Counter32
    MAX-ACCESS  read-only
    STATUS      current
    DESCRIPTION
        "Number of quick mode negotiations failed."
    ::= { dfl260eIPsecGlobal 8 }

dfl260eIPsecInfoDone OBJECT-TYPE
    SYNTAX      Counter32
    MAX-ACCESS  read-only
    STATUS      current
    DESCRIPTION
        "Number of informational exchanges done.
         (Not available in IKEv1 implementations)"
    ::= { dfl260eIPsecGlobal 9 }

dfl260eIPsecInfoFailed OBJECT-TYPE
    SYNTAX      Counter32
    MAX-ACCESS  read-only
    STATUS      current
    DESCRIPTION
        "Number of informational exchanges failed.
         (Not available in IKEv1 implementations)"
    ::= { dfl260eIPsecGlobal 10 }

dfl260eIPsecInOctetsComp OBJECT-TYPE
    SYNTAX      Counter64
    MAX-ACCESS  read-only
    STATUS      current
    DESCRIPTION
        "Total octets in before decompression."
    ::= { dfl260eIPsecGlobal 11 }

dfl260eIPsecInOctetsUncomp OBJECT-TYPE
    SYNTAX      Counter64
    MAX-ACCESS  read-only
    STATUS      current
    DESCRIPTION
        "Total octets in after decompression."
    ::= { dfl260eIPsecGlobal 12 }

dfl260eIPsecOutOctetsComp OBJECT-TYPE
    SYNTAX      Counter64
    MAX-ACCESS  read-only
    STATUS      current
    DESCRIPTION
        "Total octets out after compression."
    ::= { dfl260eIPsecGlobal 13 }

dfl260eIPsecOutOctetsUncomp OBJECT-TYPE
    SYNTAX      Counter64
    MAX-ACCESS  read-only
    STATUS      current
    DESCRIPTION
        "Total octets out before compression."
    ::= { dfl260eIPsecGlobal 14 }

dfl260eIPsecForwardedOctetsComp OBJECT-TYPE
    SYNTAX      Counter64
    MAX-ACCESS  read-only
    STATUS      current
    DESCRIPTION
        "Total octets forwarded after compression."
    ::= { dfl260eIPsecGlobal 15 }

dfl260eIPsecForwardedOctetsUcomp OBJECT-TYPE
    SYNTAX      Counter64
    MAX-ACCESS  read-only
    STATUS      current
    DESCRIPTION
        "Total octets forwarded before compression."
    ::= { dfl260eIPsecGlobal 16 }

dfl260eIPsecInPackets OBJECT-TYPE
    SYNTAX      Counter64
    MAX-ACCESS  read-only
    STATUS      current
    DESCRIPTION
        "Total packets in."
    ::= { dfl260eIPsecGlobal 17 }

dfl260eIPsecOutPackets OBJECT-TYPE
    SYNTAX      Counter64
    MAX-ACCESS  read-only
    STATUS      current
    DESCRIPTION
        "Total packets Out."
    ::= { dfl260eIPsecGlobal 18 }

dfl260eIPsecForwardedPackets OBJECT-TYPE
    SYNTAX      Counter64
    MAX-ACCESS  read-only
    STATUS      current
    DESCRIPTION
        "Total packets forwarded."
    ::= { dfl260eIPsecGlobal 19 }

dfl260eIPsecActiveTransforms OBJECT-TYPE
    SYNTAX      Gauge32
    MAX-ACCESS  read-only
    STATUS      current
    DESCRIPTION
        "Number of currently active transforms."
    ::= { dfl260eIPsecGlobal 20 }

dfl260eIPsecTotalTransforms OBJECT-TYPE
    SYNTAX      Counter32
    MAX-ACCESS  read-only
    STATUS      current
    DESCRIPTION
        "Total number of transform records created."
    ::= { dfl260eIPsecGlobal 21 }

dfl260eIPsecOutOfTransforms OBJECT-TYPE
    SYNTAX      Counter32
    MAX-ACCESS  read-only
    STATUS      current
    DESCRIPTION
        "Number of packets dropped due to no available transform object.
         (Not available in IKEv1 implementations)"
    ::= { dfl260eIPsecGlobal 22 }

dfl260eIPsecTotalRekeys OBJECT-TYPE
    SYNTAX      Counter32
    MAX-ACCESS  read-only
    STATUS      current
    DESCRIPTION
        "Total number of rekeys performed."
    ::= { dfl260eIPsecGlobal 23 }

dfl260eRules OBJECT IDENTIFIER
    ::= { dfl260eOSStats 3 }

dfl260eRuleUseTable OBJECT-TYPE
    SYNTAX      SEQUENCE OF Dfl260eRuleUseEntry
    MAX-ACCESS  not-accessible
    STATUS      current
    DESCRIPTION
        "A list of general rules usage statistics."
    ::= { dfl260eRules 2 }

dfl260eRuleUseEntry OBJECT-TYPE
    SYNTAX      Dfl260eRuleUseEntry
    MAX-ACCESS  not-accessible
    STATUS      current
    DESCRIPTION
        "The statistics over a rule usage."
    INDEX       { dfl260eRuleIndex }
    ::= { dfl260eRuleUseTable 1 }

Dfl260eRuleUseEntry ::= SEQUENCE {
    dfl260eRuleIndex    Integer32,
    dfl260eRuleName     DisplayString,
    dfl260eRuleUse      Counter32
}

dfl260eRuleIndex OBJECT-TYPE
    SYNTAX      Integer32 (1..2147483647)
    MAX-ACCESS  not-accessible
    STATUS      current
    DESCRIPTION
        "The rule usage index."
    ::= { dfl260eRuleUseEntry 1 }

dfl260eRuleName OBJECT-TYPE
    SYNTAX      DisplayString
    MAX-ACCESS  read-only
    STATUS      current
    DESCRIPTION
        "The name of the rule."
    ::= { dfl260eRuleUseEntry 2 }

dfl260eRuleUse OBJECT-TYPE
    SYNTAX      Counter32
    MAX-ACCESS  read-only
    STATUS      current
    DESCRIPTION
        "The number of times o rule was used."
    ::= { dfl260eRuleUseEntry 3 }

dfl260eIPPools OBJECT IDENTIFIER
    ::= { dfl260eOSStats 4 }

dfl260eIPPoolsNumber OBJECT-TYPE
    SYNTAX      Integer32
    MAX-ACCESS  read-only
    STATUS      current
    DESCRIPTION
        "The number of ip pools"
    ::= { dfl260eIPPools 1 }

dfl260eIPPoolTable OBJECT-TYPE
    SYNTAX      SEQUENCE OF Dfl260eIPPoolEntry
    MAX-ACCESS  not-accessible
    STATUS      current
    DESCRIPTION
        "A list of IP pools"
    ::= { dfl260eIPPools 2 }

dfl260eIPPoolEntry OBJECT-TYPE
    SYNTAX      Dfl260eIPPoolEntry
    MAX-ACCESS  not-accessible
    STATUS      current
    DESCRIPTION
        "The attributes of an ip pool"
    INDEX       { dfl260eIPPoolIndex }
    ::= { dfl260eIPPoolTable 1 }

Dfl260eIPPoolEntry ::= SEQUENCE {
    dfl260eIPPoolIndex          Integer32,
    dfl260eIPPoolName           DisplayString,
    dfl260eIPPoolPrepare        Gauge32,
    dfl260eIPPoolFree           Gauge32,
    dfl260eIPPoolMisses         Gauge32,
    dfl260eIPPoolClientFails    Gauge32,
    dfl260eIPPoolUsed           Gauge32
}

dfl260eIPPoolIndex OBJECT-TYPE
    SYNTAX      Integer32 (1..2147483647)
    MAX-ACCESS  not-accessible
    STATUS      current
    DESCRIPTION
        "The ip pool index"
    ::= { dfl260eIPPoolEntry 1 }

dfl260eIPPoolName OBJECT-TYPE
    SYNTAX      DisplayString
    MAX-ACCESS  read-only
    STATUS      current
    DESCRIPTION
        "The ip pool name"
    ::= { dfl260eIPPoolEntry 2 }

dfl260eIPPoolPrepare OBJECT-TYPE
    SYNTAX      Gauge32
    MAX-ACCESS  read-only
    STATUS      current
    DESCRIPTION
        "Number of IP pool objects in prepare mode."
    ::= { dfl260eIPPoolEntry 3 }

dfl260eIPPoolFree OBJECT-TYPE
    SYNTAX      Gauge32
    MAX-ACCESS  read-only
    STATUS      current
    DESCRIPTION
        "Number of available IPs in the pool."
    ::= { dfl260eIPPoolEntry 4 }

dfl260eIPPoolMisses OBJECT-TYPE
    SYNTAX      Gauge32
    MAX-ACCESS  read-only
    STATUS      current
    DESCRIPTION
        "Mumber of missed IP pool negotiations for other reasons
         than lack of available IP numbers."
    ::= { dfl260eIPPoolEntry 5 }

dfl260eIPPoolClientFails OBJECT-TYPE
    SYNTAX      Gauge32
    MAX-ACCESS  read-only
    STATUS      current
    DESCRIPTION
        "Number of failed IP pool transactions."
    ::= { dfl260eIPPoolEntry 6 }

dfl260eIPPoolUsed OBJECT-TYPE
    SYNTAX      Gauge32
    MAX-ACCESS  read-only
    STATUS      current
    DESCRIPTION
        "Number of IP numbers in use from the pool."
    ::= { dfl260eIPPoolEntry 7 }

dfl260eDHCPServer OBJECT IDENTIFIER
    ::= { dfl260eOSStats 5 }

dfl260eDHCPTotalRejected OBJECT-TYPE
    SYNTAX      Gauge32
    MAX-ACCESS  read-only
    STATUS      current
    DESCRIPTION
        "Total number of rejected packets (all rules)."
    ::= { dfl260eDHCPServer 1 }

dfl260eDHCPRuleTable OBJECT-TYPE
    SYNTAX      SEQUENCE OF Dfl260eDHCPRuleEntry
    MAX-ACCESS  not-accessible
    STATUS      current
    DESCRIPTION
        "A list of all DHCP server rules usage statistics."
    ::= { dfl260eDHCPServer 2 }

dfl260eDHCPRuleEntry OBJECT-TYPE
    SYNTAX      Dfl260eDHCPRuleEntry
    MAX-ACCESS  not-accessible
    STATUS      current
    DESCRIPTION
        "The attributes of a DHCP server rule statistics."
    INDEX       { dfl260eDHCPRuleIndex }
    ::= { dfl260eDHCPRuleTable 1 }

Dfl260eDHCPRuleEntry ::= SEQUENCE {
    dfl260eDHCPRuleIndex                Integer32,
    dfl260eDHCPRuleName                 DisplayString,
    dfl260eDHCPRuleUsage                Gauge32,
    dfl260eDHCPRuleUsagePercent         Gauge32,
    dfl260eDHCPActiveClients            Gauge32,
    dfl260eDHCPActiveClientsPercent     Gauge32,
    dfl260eDHCPRejectedRequests         Gauge32,
    dfl260eDHCPTotalLeases              Gauge32
}

dfl260eDHCPRuleIndex OBJECT-TYPE
    SYNTAX      Integer32 (1..2147483647)
    MAX-ACCESS  not-accessible
    STATUS      current
    DESCRIPTION
        "The DHCP server rule  index"
    ::= { dfl260eDHCPRuleEntry 1 }

dfl260eDHCPRuleName OBJECT-TYPE
    SYNTAX      DisplayString
    MAX-ACCESS  read-only
    STATUS      current
    DESCRIPTION
        "The DHCP server rule name."
    ::= { dfl260eDHCPRuleEntry 2 }

dfl260eDHCPRuleUsage OBJECT-TYPE
    SYNTAX      Gauge32
    MAX-ACCESS  read-only
    STATUS      current
    DESCRIPTION
        "Number of used IPs in the pool."
    ::= { dfl260eDHCPRuleEntry 3 }

dfl260eDHCPRuleUsagePercent OBJECT-TYPE
    SYNTAX      Gauge32
    MAX-ACCESS  read-only
    STATUS      current
    DESCRIPTION
        "The percentage of the used IPs in
         relation to the IP pool size."
    ::= { dfl260eDHCPRuleEntry 4 }

dfl260eDHCPActiveClients OBJECT-TYPE
    SYNTAX      Gauge32
    MAX-ACCESS  read-only
    STATUS      current
    DESCRIPTION
        "Number of currently active clients."
    ::= { dfl260eDHCPRuleEntry 5 }

dfl260eDHCPActiveClientsPercent OBJECT-TYPE
    SYNTAX      Gauge32
    MAX-ACCESS  read-only
    STATUS      current
    DESCRIPTION
        "The number of currently active clients
         as a percentage of the pool size."
    ::= { dfl260eDHCPRuleEntry 6 }

dfl260eDHCPRejectedRequests OBJECT-TYPE
    SYNTAX      Gauge32
    MAX-ACCESS  read-only
    STATUS      current
    DESCRIPTION
        "Number of rejected requests matching
         the current rule."
    ::= { dfl260eDHCPRuleEntry 7 }

dfl260eDHCPTotalLeases OBJECT-TYPE
    SYNTAX      Gauge32
    MAX-ACCESS  read-only
    STATUS      current
    DESCRIPTION
        "Total number of leases in the pool."
    ::= { dfl260eDHCPRuleEntry 8 }

dfl260eUserAuth OBJECT IDENTIFIER
    ::= { dfl260eOSStats 6 }

dfl260eUserAuthHTTPUsers OBJECT-TYPE
    SYNTAX      Gauge32
    MAX-ACCESS  read-only
    STATUS      current
    DESCRIPTION
        "Number of currently  logged in HTTP users."
    ::= { dfl260eUserAuth 1 }

dfl260eUserAuthXAUTHUsers OBJECT-TYPE
    SYNTAX      Gauge32
    MAX-ACCESS  read-only
    STATUS      current
    DESCRIPTION
        "Number of currently logged in XAUTH users."
    ::= { dfl260eUserAuth 2 }

dfl260eUserAuthHTTPSUsers OBJECT-TYPE
    SYNTAX      Gauge32
    MAX-ACCESS  read-only
    STATUS      current
    DESCRIPTION
        "Number of currently logged in HTTPS users."
    ::= { dfl260eUserAuth 3 }

dfl260eUserAuthPPPUsers OBJECT-TYPE
    SYNTAX      Gauge32
    MAX-ACCESS  read-only
    STATUS      current
    DESCRIPTION
        "Number of currently logged in PPP users."
    ::= { dfl260eUserAuth 4 }

dfl260eUserAuthEAPUsers OBJECT-TYPE
    SYNTAX      Gauge32
    MAX-ACCESS  read-only
    STATUS      current
    DESCRIPTION
        "Number of currently logged in EAP users."
    ::= { dfl260eUserAuth 5 }

dfl260eUserAuthRuleUseTable OBJECT-TYPE
    SYNTAX      SEQUENCE OF Dfl260eUserAuthRuleUseEntry
    MAX-ACCESS  not-accessible
    STATUS      current
    DESCRIPTION
        "Table of user authentication rule usage."
    ::= { dfl260eUserAuth 6 }

dfl260eUserAuthRuleUseEntry OBJECT-TYPE
    SYNTAX      Dfl260eUserAuthRuleUseEntry
    MAX-ACCESS  not-accessible
    STATUS      current
    DESCRIPTION
        "The attributes of an authentication rule
         usage statistics."
    INDEX       { dfl260eUserAuthRuleIndex }
    ::= { dfl260eUserAuthRuleUseTable 1 }

Dfl260eUserAuthRuleUseEntry ::= SEQUENCE {
    dfl260eUserAuthRuleIndex    Integer32,
    dfl260eUserAuthRuleName     DisplayString,
    dfl260eUserAuthRuleUse      Counter32
}

dfl260eUserAuthRuleIndex OBJECT-TYPE
    SYNTAX      Integer32 (1..2147483647)
    MAX-ACCESS  not-accessible
    STATUS      current
    DESCRIPTION
        "The rule usage index."
    ::= { dfl260eUserAuthRuleUseEntry 1 }

dfl260eUserAuthRuleName OBJECT-TYPE
    SYNTAX      DisplayString
    MAX-ACCESS  read-only
    STATUS      current
    DESCRIPTION
        "The name of the rule."
    ::= { dfl260eUserAuthRuleUseEntry 2 }

dfl260eUserAuthRuleUse OBJECT-TYPE
    SYNTAX      Counter32
    MAX-ACCESS  read-only
    STATUS      current
    DESCRIPTION
        "The number of times o rule was used."
    ::= { dfl260eUserAuthRuleUseEntry 3 }

dfl260eLinkMonitor OBJECT IDENTIFIER
    ::= { dfl260eOSStats 7 }

dfl260eLinkMonGrp OBJECT-TYPE
    SYNTAX      Integer32
    MAX-ACCESS  read-only
    STATUS      current
    DESCRIPTION
        "The number of groups of monitored links"
    ::= { dfl260eLinkMonitor 1 }

dfl260eLinkMonGrpTable OBJECT-TYPE
    SYNTAX      SEQUENCE OF Dfl260eLinkMonGrpEntry
    MAX-ACCESS  not-accessible
    STATUS      current
    DESCRIPTION
        "Table of link monitor groups."
    ::= { dfl260eLinkMonitor 2 }

dfl260eLinkMonGrpEntry OBJECT-TYPE
    SYNTAX      Dfl260eLinkMonGrpEntry
    MAX-ACCESS  not-accessible
    STATUS      current
    DESCRIPTION
        "The attributes of a link monitor group"
    INDEX       { dfl260eLinkMonGrpIndex }
    ::= { dfl260eLinkMonGrpTable 1 }

Dfl260eLinkMonGrpEntry ::= SEQUENCE {
    dfl260eLinkMonGrpIndex      Integer32,
    dfl260eLinkMonGrpName       DisplayString,
    dfl260eLinkMonGrpHostsUp    Gauge32
}

dfl260eLinkMonGrpIndex OBJECT-TYPE
    SYNTAX      Integer32 (1..2147483647)
    MAX-ACCESS  not-accessible
    STATUS      current
    DESCRIPTION
        "The index row in the table of link monitor groups."
    ::= { dfl260eLinkMonGrpEntry 1 }

dfl260eLinkMonGrpName OBJECT-TYPE
    SYNTAX      DisplayString
    MAX-ACCESS  read-only
    STATUS      current
    DESCRIPTION
        "The link monitor group name."
    ::= { dfl260eLinkMonGrpEntry 2 }

dfl260eLinkMonGrpHostsUp OBJECT-TYPE
    SYNTAX      Gauge32
    MAX-ACCESS  read-only
    STATUS      current
    DESCRIPTION
        "The percentage of monitored hosts available."
    ::= { dfl260eLinkMonGrpEntry 3 }

dfl260eLinkMonHostTable OBJECT-TYPE
    SYNTAX      SEQUENCE OF Dfl260eLinkMonHostEntry
    MAX-ACCESS  not-accessible
    STATUS      current
    DESCRIPTION
        "Table of link monitored hosts in a link monnitor group."
    ::= { dfl260eLinkMonitor 3 }

dfl260eLinkMonHostEntry OBJECT-TYPE
    SYNTAX      Dfl260eLinkMonHostEntry
    MAX-ACCESS  not-accessible
    STATUS      current
    DESCRIPTION
        "The attributes of a monitored host."
    INDEX       { dfl260eLinkMonGrpIndex, dfl260eLinkMonHostIndex }
    ::= { dfl260eLinkMonHostTable 1 }

Dfl260eLinkMonHostEntry ::= SEQUENCE {
    dfl260eLinkMonHostIndex             Integer32,
    dfl260eLinkMonHostId                DisplayString,
    dfl260eLinkMonHostShortTermLoss     Gauge32,
    dfl260eLinkMonHostPacketsLost       Counter32
}

dfl260eLinkMonHostIndex OBJECT-TYPE
    SYNTAX      Integer32 (1..2147483647)
    MAX-ACCESS  not-accessible
    STATUS      current
    DESCRIPTION
        "The index an host in the table of link monitor hosts."
    ::= { dfl260eLinkMonHostEntry 1 }

dfl260eLinkMonHostId OBJECT-TYPE
    SYNTAX      DisplayString
    MAX-ACCESS  read-only
    STATUS      current
    DESCRIPTION
        "The monitored host identifier."
    ::= { dfl260eLinkMonHostEntry 2 }

dfl260eLinkMonHostShortTermLoss OBJECT-TYPE
    SYNTAX      Gauge32
    MAX-ACCESS  read-only
    STATUS      current
    DESCRIPTION
        "The percentage of short term losst packets."
    ::= { dfl260eLinkMonHostEntry 3 }

dfl260eLinkMonHostPacketsLost OBJECT-TYPE
    SYNTAX      Counter32
    MAX-ACCESS  read-only
    STATUS      current
    DESCRIPTION
        "Total number of lost monitoring packets."
    ::= { dfl260eLinkMonHostEntry 4 }

dfl260ePipes OBJECT IDENTIFIER
    ::= { dfl260eOSStats 8 }

dfl260ePipeUsers OBJECT-TYPE
    SYNTAX      Gauge32
    MAX-ACCESS  read-only
    STATUS      current
    DESCRIPTION
        "The current number of users, as defined by the grouping
         settings of each pipe, being tracked in the pipes system.
         Note that this value corresponds to the number of users
         active in each time slice of 1/20th of a second, and not
         to the number of users having open connections."
    ::= { dfl260ePipes 1 }

dfl260ePipeTable OBJECT-TYPE
    SYNTAX      SEQUENCE OF Dfl260ePipeEntry
    MAX-ACCESS  not-accessible
    STATUS      current
    DESCRIPTION
        "Table of pipes"
    ::= { dfl260ePipes 2 }

dfl260ePipeEntry OBJECT-TYPE
    SYNTAX      Dfl260ePipeEntry
    MAX-ACCESS  not-accessible
    STATUS      current
    DESCRIPTION
        "A entry of the pipes table"
    INDEX       { dfl260ePipeIndex }
    ::= { dfl260ePipeTable 1 }

Dfl260ePipeEntry ::= SEQUENCE {
    dfl260ePipeIndex            Integer32,
    dfl260ePipeName             DisplayString,
    dfl260ePipeMinPrec          Integer32,
    dfl260ePipeMaxPrec          Integer32,
    dfl260ePipeDefPrec          Integer32,
    dfl260ePipeNumPrec          Integer32,
    dfl260ePipeNumUsers         Gauge32,
    dfl260ePipeCurrentBps       Gauge32,
    dfl260ePipeCurrentPps       Gauge32,
    dfl260ePipeDelayedPackets   Counter32,
    dfl260ePipeDropedPackets    Counter32
}

dfl260ePipeIndex OBJECT-TYPE
    SYNTAX      Integer32 (1..2147483647)
    MAX-ACCESS  not-accessible
    STATUS      current
    DESCRIPTION
        "The pipe index"
    ::= { dfl260ePipeEntry 1 }

dfl260ePipeName OBJECT-TYPE
    SYNTAX      DisplayString
    MAX-ACCESS  read-only
    STATUS      current
    DESCRIPTION
        "The name of the pipe"
    ::= { dfl260ePipeEntry 2 }

dfl260ePipeMinPrec OBJECT-TYPE
    SYNTAX      Integer32
    MAX-ACCESS  read-only
    STATUS      current
    DESCRIPTION
        "The minimum of the range of pipe precedences."
    ::= { dfl260ePipeEntry 3 }

dfl260ePipeMaxPrec OBJECT-TYPE
    SYNTAX      Integer32
    MAX-ACCESS  read-only
    STATUS      current
    DESCRIPTION
        "The maximum of the range of pipe precedences."
    ::= { dfl260ePipeEntry 4 }

dfl260ePipeDefPrec OBJECT-TYPE
    SYNTAX      Integer32
    MAX-ACCESS  read-only
    STATUS      current
    DESCRIPTION
        "The precedence assigned to a packet for which has not one
         allready done by a Pipe Rule."
    ::= { dfl260ePipeEntry 5 }

dfl260ePipeNumPrec OBJECT-TYPE
    SYNTAX      Integer32
    MAX-ACCESS  read-only
    STATUS      current
    DESCRIPTION
        "The number of pipe precedences"
    ::= { dfl260ePipeEntry 6 }

dfl260ePipeNumUsers OBJECT-TYPE
    SYNTAX      Gauge32
    MAX-ACCESS  read-only
    STATUS      current
    DESCRIPTION
        "The current number of users, as defined by the grouping settings
         of each pipe, being tracked in the pipes system. This value
         corresponds to the number of users active in each time slice
         and not to the number of users having  open connections."
    ::= { dfl260ePipeEntry 7 }

dfl260ePipeCurrentBps OBJECT-TYPE
    SYNTAX      Gauge32
    MAX-ACCESS  read-only
    STATUS      current
    DESCRIPTION
        "The current throughput of a pipe, in bits per second, as a sum of
         the corresponding values for all precedences."
    ::= { dfl260ePipeEntry 8 }

dfl260ePipeCurrentPps OBJECT-TYPE
    SYNTAX      Gauge32
    MAX-ACCESS  read-only
    STATUS      current
    DESCRIPTION
        "The current throughput of a pipe, in packets per second, as a sum of
         the corresponding values for all precedences."
    ::= { dfl260ePipeEntry 9 }

dfl260ePipeDelayedPackets OBJECT-TYPE
    SYNTAX      Counter32
    MAX-ACCESS  read-only
    STATUS      current
    DESCRIPTION
        "The number of times packets have been delayed as a result of a pipe,
         or pipe user having used up its allotted bandwidth. Note that one single
         packet may be delayed several times; if a pipe is really full, this
         count may exceed the number of packets actually passing through the
         pipe."
    ::= { dfl260ePipeEntry 10 }

dfl260ePipeDropedPackets OBJECT-TYPE
    SYNTAX      Counter32
    MAX-ACCESS  read-only
    STATUS      current
    DESCRIPTION
        "The number of packets dropped by a pipe. Packets are dropped when
         CorePlus is running out of packet buffers. This occurs when excessive
         amounts of packets need to be queued for later delivery. The packet
         dropped is always the one that has been queued the longest time
         globally, which means that the connection suffering from packet loss
         will be the one most overloading the system."
    ::= { dfl260ePipeEntry 11 }

dfl260ePipePrecTable OBJECT-TYPE
    SYNTAX      SEQUENCE OF Dfl260ePipePrecEntry
    MAX-ACCESS  not-accessible
    STATUS      current
    DESCRIPTION
        "There is a one to many relation between a pipe and its precedences.
         The number of precedences is a instance attribute of each pipe.
         This table extends the pipes table in order to express the relation
         between a pipe and the respective precedences."
    ::= { dfl260ePipes 3 }

dfl260ePipePrecEntry OBJECT-TYPE
    SYNTAX      Dfl260ePipePrecEntry
    MAX-ACCESS  not-accessible
    STATUS      current
    DESCRIPTION
        "An entry of the table of pipe pecedences. These table entries
         are chracterized by been indexed by two values. The first index
         the same as the pipe index of the corresponding row in table of
         pipes and the second index is the index of the set of precedences
         of the corresponding pipe."
    INDEX       { dfl260ePipeIndex, dfl260ePipePrecIndex }
    ::= { dfl260ePipePrecTable 1 }

Dfl260ePipePrecEntry ::= SEQUENCE {
    dfl260ePipePrecIndex            Integer32,
    dfl260ePipePrec                 Integer32,
    dfl260ePipePrecBps              Gauge32,
    dfl260ePipePrecTotalPps         Gauge32,
    dfl260ePipePrecReservedBps      Gauge32,
    dfl260ePipePrecDynLimBps        Gauge32,
    dfl260ePipePrecDynUsrLimBps     Gauge32,
    dfl260ePipePrecDelayedPackets   Counter32,
    dfl260ePipePrecDropedPackets    Counter32
}

dfl260ePipePrecIndex OBJECT-TYPE
    SYNTAX      Integer32 (1..2147483647)
    MAX-ACCESS  not-accessible
    STATUS      current
    DESCRIPTION
        "Index of a precedence of a specific pipe. This is the second index
         of the entries of pipe precedence table described by object
         dfl260ePipePrecEntry."
    ::= { dfl260ePipePrecEntry 1 }

dfl260ePipePrec OBJECT-TYPE
    SYNTAX      Integer32
    MAX-ACCESS  read-only
    STATUS      current
    DESCRIPTION
        "The precedence value"
    ::= { dfl260ePipePrecEntry 2 }

dfl260ePipePrecBps OBJECT-TYPE
    SYNTAX      Gauge32
    MAX-ACCESS  read-only
    STATUS      current
    DESCRIPTION
        "The current throughput of the pipe, in bits per second, with
         the corresponding precedence."
    ::= { dfl260ePipePrecEntry 3 }

dfl260ePipePrecTotalPps OBJECT-TYPE
    SYNTAX      Gauge32
    MAX-ACCESS  read-only
    STATUS      current
    DESCRIPTION
        "The current throughput of the pipe precedence, in packets per second."
    ::= { dfl260ePipePrecEntry 4 }

dfl260ePipePrecReservedBps OBJECT-TYPE
    SYNTAX      Gauge32
    MAX-ACCESS  read-only
    STATUS      current
    DESCRIPTION
        "The current bandwidth allocated to the precedence."
    ::= { dfl260ePipePrecEntry 5 }

dfl260ePipePrecDynLimBps OBJECT-TYPE
    SYNTAX      Gauge32
    MAX-ACCESS  read-only
    STATUS      current
    DESCRIPTION
        "The current bandwidth limit limit applied the precedence."
    ::= { dfl260ePipePrecEntry 6 }

dfl260ePipePrecDynUsrLimBps OBJECT-TYPE
    SYNTAX      Gauge32
    MAX-ACCESS  read-only
    STATUS      current
    DESCRIPTION
        "The current precedence bandwidth limit per user of the pipe."
    ::= { dfl260ePipePrecEntry 7 }

dfl260ePipePrecDelayedPackets OBJECT-TYPE
    SYNTAX      Counter32
    MAX-ACCESS  read-only
    STATUS      current
    DESCRIPTION
        "The number of times packets have been delayed as a result of a
         precedence, or pipe user having used up its allotted bandwidth.
         Note that one single packet may be delayed several times; if a
         pipe is really full, this count may exceed the number of packets
         of this precedence actually passing through the pipe."
    ::= { dfl260ePipePrecEntry 8 }

dfl260ePipePrecDropedPackets OBJECT-TYPE
    SYNTAX      Counter32
    MAX-ACCESS  read-only
    STATUS      current
    DESCRIPTION
        "The number of pipe dropped packets with the corresponding precedence."
    ::= { dfl260ePipePrecEntry 9 }

dfl260eALG OBJECT IDENTIFIER
    ::= { dfl260eOSStats 9 }

dfl260eAlgSessions OBJECT-TYPE
    SYNTAX      Gauge32
    MAX-ACCESS  read-only
    STATUS      current
    DESCRIPTION
        "Total ALG sessions"
    ::= { dfl260eALG 1 }

dfl260eAlgConnections OBJECT-TYPE
    SYNTAX      Gauge32
    MAX-ACCESS  read-only
    STATUS      current
    DESCRIPTION
        "Total ALG connections"
    ::= { dfl260eALG 2 }

dfl260eAlgTCPStreams OBJECT-TYPE
    SYNTAX      Gauge32
    MAX-ACCESS  read-only
    STATUS      current
    DESCRIPTION
        "Total ALG TCP streams"
    ::= { dfl260eALG 3 }

dfl260eHttpAlg OBJECT IDENTIFIER
    ::= { dfl260eALG 4 }

dfl260eHttpAlgTable OBJECT-TYPE
    SYNTAX      SEQUENCE OF Dfl260eHttpAlgEntry
    MAX-ACCESS  not-accessible
    STATUS      current
    DESCRIPTION
        "Table of HTTP ALG objects."
    ::= { dfl260eHttpAlg 1 }

dfl260eHttpAlgEntry OBJECT-TYPE
    SYNTAX      Dfl260eHttpAlgEntry
    MAX-ACCESS  not-accessible
    STATUS      current
    DESCRIPTION
        "A row of the table of HTTP ALG objects."
    INDEX       { dfl260eHttpAlgIndex }
    ::= { dfl260eHttpAlgTable 1 }

Dfl260eHttpAlgEntry ::= SEQUENCE {
    dfl260eHttpAlgIndex             Integer32,
    dfl260eHttpAlgName              DisplayString,
    dfl260eHttpAlgTotalRequested    Gauge32,
    dfl260eHttpAlgTotalAllowed      Gauge32,
    dfl260eHttpAlgTotalBlocked      Gauge32
}

dfl260eHttpAlgIndex OBJECT-TYPE
    SYNTAX      Integer32 (1..2147483647)
    MAX-ACCESS  not-accessible
    STATUS      current
    DESCRIPTION
        "The index of an entry of the  Table of HTTP ALG objects."
    ::= { dfl260eHttpAlgEntry 1 }

dfl260eHttpAlgName OBJECT-TYPE
    SYNTAX      DisplayString
    MAX-ACCESS  read-only
    STATUS      current
    DESCRIPTION
        "The name of an HTTP ALG object."
    ::= { dfl260eHttpAlgEntry 2 }

dfl260eHttpAlgTotalRequested OBJECT-TYPE
    SYNTAX      Gauge32
    MAX-ACCESS  read-only
    STATUS      current
    DESCRIPTION
        "Total number of URL requests."
    ::= { dfl260eHttpAlgEntry 3 }

dfl260eHttpAlgTotalAllowed OBJECT-TYPE
    SYNTAX      Gauge32
    MAX-ACCESS  read-only
    STATUS      current
    DESCRIPTION
        "Total number of allowed URL requests."
    ::= { dfl260eHttpAlgEntry 4 }

dfl260eHttpAlgTotalBlocked OBJECT-TYPE
    SYNTAX      Gauge32
    MAX-ACCESS  read-only
    STATUS      current
    DESCRIPTION
        "Total number of blocked URL requests."
    ::= { dfl260eHttpAlgEntry 5 }

dfl260eHttpAlgCntFltTable OBJECT-TYPE
    SYNTAX      SEQUENCE OF Dfl260eHttpAlgCntFltEntry
    MAX-ACCESS  not-accessible
    STATUS      current
    DESCRIPTION
        "Table of HTTP ALG content filtering rules."
    ::= { dfl260eHttpAlg 2 }

dfl260eHttpAlgCntFltEntry OBJECT-TYPE
    SYNTAX      Dfl260eHttpAlgCntFltEntry
    MAX-ACCESS  not-accessible
    STATUS      current
    DESCRIPTION
        "Entry of the table of HTTP ALG content filtering rules."
    INDEX       { dfl260eHttpAlgIndex, dfl260eHttpAlgCntFltIndex }
    ::= { dfl260eHttpAlgCntFltTable 1 }

Dfl260eHttpAlgCntFltEntry ::= SEQUENCE {
    dfl260eHttpAlgCntFltIndex       Integer32,
    dfl260eHttpAlgCntFltName        DisplayString,
    dfl260eHttpAlgCntFltRequests    Gauge32,
    dfl260eHttpAlgCntFltAllowed     Gauge32,
    dfl260eHttpAlgCntFltBlocked     Gauge32
}

dfl260eHttpAlgCntFltIndex OBJECT-TYPE
    SYNTAX      Integer32 (1..2147483647)
    MAX-ACCESS  not-accessible
    STATUS      current
    DESCRIPTION
        "The index of an entry of the  Table of HTTP ALG
         content filtering objects."
    ::= { dfl260eHttpAlgCntFltEntry 1 }

dfl260eHttpAlgCntFltName OBJECT-TYPE
    SYNTAX      DisplayString
    MAX-ACCESS  read-only
    STATUS      current
    DESCRIPTION
        "The name of the a HTTP ALG content fitering."
    ::= { dfl260eHttpAlgCntFltEntry 2 }

dfl260eHttpAlgCntFltRequests OBJECT-TYPE
    SYNTAX      Gauge32
    MAX-ACCESS  read-only
    STATUS      current
    DESCRIPTION
        "Total number of URLs intercepted by a content
         filtering object."
    ::= { dfl260eHttpAlgCntFltEntry 3 }

dfl260eHttpAlgCntFltAllowed OBJECT-TYPE
    SYNTAX      Gauge32
    MAX-ACCESS  read-only
    STATUS      current
    DESCRIPTION
        "Total number of URLs intercepted and allowed
         by a content filtering object."
    ::= { dfl260eHttpAlgCntFltEntry 4 }

dfl260eHttpAlgCntFltBlocked OBJECT-TYPE
    SYNTAX      Gauge32
    MAX-ACCESS  read-only
    STATUS      current
    DESCRIPTION
        "Total number of URLs intercepted and blocked
         by a content filtering object."
    ::= { dfl260eHttpAlgCntFltEntry 5 }

dfl260eSmtpAlg OBJECT IDENTIFIER
    ::= { dfl260eALG 5 }

dfl260eSmtpAlgTable OBJECT-TYPE
    SYNTAX  SEQUENCE OF Dfl260eSmtpAlgEntry
    MAX-ACCESS  not-accessible
    STATUS  current
    DESCRIPTION
  "Table of SMTP ALG objects."
    ::= { dfl260eSmtpAlg 1 }

dfl260eSmtpAlgEntry OBJECT-TYPE
   SYNTAX  Dfl260eSmtpAlgEntry
   MAX-ACCESS  not-accessible
    STATUS      current
    DESCRIPTION
        "A row of the table of SMTP ALG objects."
    INDEX       { dfl260eSmtpAlgIndex }
    ::= { dfl260eSmtpAlgTable 1 }

Dfl260eSmtpAlgEntry ::= SEQUENCE {
    dfl260eSmtpAlgIndex           Integer32,
    dfl260eSmtpAlgName            DisplayString,
    dfl260eSmtpAlgTotCheckedSes   Gauge32,
    dfl260eSmtpAlgTotSpamSes      Gauge32,
    dfl260eSmtpAlgTotDroppedSes   Gauge32
}

dfl260eSmtpAlgIndex OBJECT-TYPE
    SYNTAX      Integer32 (1..2147483647)
    MAX-ACCESS  not-accessible
    STATUS      current
    DESCRIPTION
        "The index of an entry of the  Table of SMTP ALG objects."
    ::= { dfl260eSmtpAlgEntry 1 }

dfl260eSmtpAlgName OBJECT-TYPE
    SYNTAX      DisplayString
    MAX-ACCESS  read-only
    STATUS      current
    DESCRIPTION
        "The name of an SMTP ALG object."
    ::= { dfl260eSmtpAlgEntry 2 }

dfl260eSmtpAlgTotCheckedSes OBJECT-TYPE
    SYNTAX      Gauge32
    MAX-ACCESS  read-only
    STATUS      current
    DESCRIPTION
        "Total sessions checked by the SMTP ALG of corresponding index."
    ::= { dfl260eSmtpAlgEntry 3 }

dfl260eSmtpAlgTotSpamSes OBJECT-TYPE
    SYNTAX      Gauge32
    MAX-ACCESS  read-only
    STATUS      current
    DESCRIPTION
        "Total spam sessions detected by the SMTP ALG of corresponding index."
    ::= { dfl260eSmtpAlgEntry 4 }

dfl260eSmtpAlgTotDroppedSes OBJECT-TYPE
    SYNTAX      Gauge32
    MAX-ACCESS  read-only
    STATUS      current
    DESCRIPTION
        "Total deroped sessions for the SMTP ALG of corresponding index."
    ::= { dfl260eSmtpAlgEntry 5 }


dfl260eSmtpAlgDnsBlTable OBJECT-TYPE
    SYNTAX  SEQUENCE OF Dfl260eSmtpAlgDnsBlEntry
    MAX-ACCESS  not-accessible
    STATUS  current
    DESCRIPTION
  "Table of SMTP ALG DNS balck list objects."
    ::= { dfl260eSmtpAlg 2 }


dfl260eSmtpAlgDnsBlEntry OBJECT-TYPE
   SYNTAX  Dfl260eSmtpAlgDnsBlEntry
   MAX-ACCESS  not-accessible
    STATUS      current
    DESCRIPTION
        "A row of the table of SMTP ALG DNS black list objects."
    INDEX       { dfl260eSmtpAlgIndex, dfl260eSmtpAlgDnsBlIndex }
    ::= { dfl260eSmtpAlgDnsBlTable 1 }


Dfl260eSmtpAlgDnsBlEntry ::= SEQUENCE {
    dfl260eSmtpAlgDnsBlIndex  Integer32,
    dfl260eSmtpAlgDnsBlName    DisplayString,
    dfl260eSmtpAlgDnsBlChecked      Gauge32,
    dfl260eSmtpAlgDnsBlMatched  Gauge32,
    dfl260eSmtpAlgDnsBlFailChecks  Gauge32
}

dfl260eSmtpAlgDnsBlIndex OBJECT-TYPE
    SYNTAX      Integer32 (1..2147483647)
    MAX-ACCESS  not-accessible
    STATUS      current
    DESCRIPTION
        "The index of an entry of the  SMTP ALG DNS black list objects."
    ::= { dfl260eSmtpAlgDnsBlEntry 1 }

dfl260eSmtpAlgDnsBlName OBJECT-TYPE
    SYNTAX      DisplayString
    MAX-ACCESS  read-only
    STATUS      current
    DESCRIPTION
  "The SMTP DNS black list name."
    ::= { dfl260eSmtpAlgDnsBlEntry 2 }

dfl260eSmtpAlgDnsBlChecked OBJECT-TYPE
    SYNTAX      Gauge32
    MAX-ACCESS  read-only
    STATUS      current
    DESCRIPTION
  "Total sessions checked againt SMTP ALG DNS black list of corresponding index"
    ::= { dfl260eSmtpAlgDnsBlEntry 3 }

dfl260eSmtpAlgDnsBlMatched OBJECT-TYPE
    SYNTAX      Gauge32
    MAX-ACCESS  read-only
    STATUS      current
    DESCRIPTION
  "Total sessions that matched SMTP ALG DNS black list of corresponding index"
    ::= { dfl260eSmtpAlgDnsBlEntry 4 }

dfl260eSmtpAlgDnsBlFailChecks OBJECT-TYPE
    SYNTAX      Gauge32
    MAX-ACCESS  read-only
    STATUS      current
    DESCRIPTION
  "Total failed checks for the SMTP ALG DNS black list of corresponding index"
    ::= { dfl260eSmtpAlgDnsBlEntry 5 }

dfl260eDHCPRelay OBJECT IDENTIFIER
    ::= { dfl260eOSStats 11 }

dfl260eDHCPRelayCurClients OBJECT-TYPE
    SYNTAX      Gauge32
    MAX-ACCESS  read-only
    STATUS      current
    DESCRIPTION
        "Total DHCP relay active relayed clients."
    ::= { dfl260eDHCPRelay 1 }

dfl260eDHCPRelayCurTrans OBJECT-TYPE
    SYNTAX      Gauge32
    MAX-ACCESS  read-only
    STATUS      current
    DESCRIPTION
        "Ongoing DHCP relay transactions."
    ::= { dfl260eDHCPRelay 2 }

dfl260eDHCPRelayRejected OBJECT-TYPE
    SYNTAX      Gauge32
    MAX-ACCESS  read-only
    STATUS      current
    DESCRIPTION
        "Total DHCP relay packets rejected."
    ::= { dfl260eDHCPRelay 3 }

dfl260eDHCPRelayRuleTable OBJECT-TYPE
    SYNTAX      SEQUENCE OF Dfl260eDHCPRelayRuleEntry
    MAX-ACCESS  not-accessible
    STATUS      current
    DESCRIPTION
        "Table of DHCP relay rules."
    ::= { dfl260eDHCPRelay 4 }

dfl260eDHCPRelayRuleEntry OBJECT-TYPE
    SYNTAX      Dfl260eDHCPRelayRuleEntry
    MAX-ACCESS  not-accessible
    STATUS      current
    DESCRIPTION
        "Entry of the table of DHCP relay rules"
    INDEX       { dfl260eDHCPRelayRuleIndex }
    ::= { dfl260eDHCPRelayRuleTable 1 }

Dfl260eDHCPRelayRuleEntry ::= SEQUENCE {
    dfl260eDHCPRelayRuleIndex       Integer32,
    dfl260eDHCPRelayRuleName        DisplayString,
    dfl260eDHCPRelayRuleHits        Gauge32,
    dfl260eDHCPRelayRuleCurClients  Gauge32,
    dfl260eDHCPRelayRuleRejCliPkts  Gauge32,
    dfl260eDHCPRelayRuleRejSrvPkts  Gauge32
}

dfl260eDHCPRelayRuleIndex OBJECT-TYPE
    SYNTAX      Integer32 (1..2147483647)
    MAX-ACCESS  not-accessible
    STATUS      current
    DESCRIPTION
        "Index of the table of DHCP relay rules."
    ::= { dfl260eDHCPRelayRuleEntry 1 }

dfl260eDHCPRelayRuleName OBJECT-TYPE
    SYNTAX      DisplayString
    MAX-ACCESS  read-only
    STATUS      current
    DESCRIPTION
        "Display name of a DHCP relay rule"
    ::= { dfl260eDHCPRelayRuleEntry 2 }

dfl260eDHCPRelayRuleHits OBJECT-TYPE
    SYNTAX      Gauge32
    MAX-ACCESS  read-only
    STATUS      current
    DESCRIPTION
        "Number of the times the  DHCP relay rule with corresponding index was
         used."
    ::= { dfl260eDHCPRelayRuleEntry 3 }

dfl260eDHCPRelayRuleCurClients OBJECT-TYPE
    SYNTAX      Gauge32
    MAX-ACCESS  read-only
    STATUS      current
    DESCRIPTION
        "Number of ctive relayed clients by the DHCP relay rule with corresponding index."
    ::= { dfl260eDHCPRelayRuleEntry 4 }

dfl260eDHCPRelayRuleRejCliPkts OBJECT-TYPE
    SYNTAX      Gauge32
    MAX-ACCESS  read-only
    STATUS      current
    DESCRIPTION
        "Number of client packets rejected by a rule."
    ::= { dfl260eDHCPRelayRuleEntry 5 }

dfl260eDHCPRelayRuleRejSrvPkts OBJECT-TYPE
    SYNTAX      Gauge32
    MAX-ACCESS  read-only
    STATUS      current
    DESCRIPTION
        "Number of DHCP server packets rejected by the DHCP relay rule
         with the corresponding index."
    ::= { dfl260eDHCPRelayRuleEntry 6 }

dfl260eHA OBJECT IDENTIFIER
    ::= { dfl260eOSStats 12 }

dfl260eHASyncSendQueueLength OBJECT-TYPE
    SYNTAX      Gauge32
    MAX-ACCESS  read-only
    STATUS      current
    DESCRIPTION
        "Size of the queue used for the High Availability sync interface."
    ::= { dfl260eHA 1 }

dfl260eHASyncSendQueueUsagePkt OBJECT-TYPE
    SYNTAX      Gauge32
    MAX-ACCESS  read-only
    STATUS      current
    DESCRIPTION
        "High Availability Sync interface queue usage in number of packets."
    ::= { dfl260eHA 2 }

dfl260eHASyncSendQueueUsageOct OBJECT-TYPE
    SYNTAX      Gauge32
    MAX-ACCESS  read-only
    STATUS      current
    DESCRIPTION
        "High Availability Sync interface queue usage in number of octects."
    ::= { dfl260eHA 3 }

dfl260eHASyncSentPackets OBJECT-TYPE
    SYNTAX      Counter32
    MAX-ACCESS  read-only
    STATUS      current
    DESCRIPTION
        "Number High Availability packets sent on Sync."
    ::= { dfl260eHA 4 }

dfl260eHASyncSendResentPackets OBJECT-TYPE
    SYNTAX      Counter32
    MAX-ACCESS  read-only
    STATUS      current
    DESCRIPTION
        "Number of High Availability packets resent on Sync."
    ::= { dfl260eHA 5 }

dfl260eStatsConformance OBJECT IDENTIFIER
    ::= { dfl260eMibConfs 1 }

dfl260eStatsRegGroups OBJECT IDENTIFIER
    ::= { dfl260eMibObjectGroups 1 }

dfl260eSystemObjectGroup OBJECT-GROUP
    OBJECTS     { dfl260eSysCpuLoad,
                  dfl260eSysForwardedBits,
                  dfl260eSysForwardedPackets,
                  dfl260eSysBuffUse,
                  dfl260eSysConns,
                  dfl260eHWSensorName,
                  dfl260eHWSensorValue,
                  dfl260eHWSensorUnit,
                  dfl260eSysMemUsage,
                  dfl260eSysTimerUsage,
                  dfl260eSysConnOPS,
                  dfl260eSysConnCPS,
                  dfl260eSysHCForwardedBits }
    STATUS      current
    DESCRIPTION
        "System statistics Group"
    ::= { dfl260eStatsRegGroups 1 }

dfl260eIPsecObjectGroup OBJECT-GROUP
    OBJECTS     { dfl260eIPsecPhaseOneActive,
                  dfl260eIPsecPhaseOneAggrModeDone,
                  dfl260eIPsecQuickModeActive,
                  dfl260eIPsecPhaseOneDone,
                  dfl260eIPsecPhaseOneFailed,
                  dfl260eIPsecPhaseOneRekeyed,
                  dfl260eIPsecQuickModeDone,
                  dfl260eIPsecQuickModeFailed,
                  dfl260eIPsecInfoDone,
                  dfl260eIPsecInfoFailed,
                  dfl260eIPsecInOctetsComp,
                  dfl260eIPsecInOctetsUncomp,
                  dfl260eIPsecOutOctetsComp,
                  dfl260eIPsecOutOctetsUncomp,
                  dfl260eIPsecForwardedOctetsComp,
                  dfl260eIPsecForwardedOctetsUcomp,
                  dfl260eIPsecInPackets,
                  dfl260eIPsecOutPackets,
                  dfl260eIPsecForwardedPackets,
                  dfl260eIPsecActiveTransforms,
                  dfl260eIPsecTotalTransforms,
                  dfl260eIPsecOutOfTransforms,
                  dfl260eIPsecTotalRekeys }
    STATUS      current
    DESCRIPTION
        "IPsec Group"
    ::= { dfl260eStatsRegGroups 2 }

dfl260eStateCountersGroup OBJECT-GROUP
    OBJECTS     { dfl260eSysPscTcpSyn,
                  dfl260eSysPscTcpOpen,
                  dfl260eSysPscTcpFin,
                  dfl260eSysPscUdp,
                  dfl260eSysPscIcmp,
                  dfl260eSysPscOther }
    STATUS      current
    DESCRIPTION
        "Per state counters"
    ::= { dfl260eStatsRegGroups 3 }

dfl260eIPPoolGroup OBJECT-GROUP
    OBJECTS     { dfl260eIPPoolsNumber,
                  dfl260eIPPoolName,
                  dfl260eIPPoolPrepare,
                  dfl260eIPPoolFree,
                  dfl260eIPPoolMisses,
                  dfl260eIPPoolClientFails,
                  dfl260eIPPoolUsed }
    STATUS      current
    DESCRIPTION
        "IP pool entry objects group"
    ::= { dfl260eStatsRegGroups 4 }

dfl260eDHCPServerGroup OBJECT-GROUP
    OBJECTS     { dfl260eDHCPTotalRejected,
                  dfl260eDHCPRuleName,
                  dfl260eDHCPRuleUsage,
                  dfl260eDHCPRuleUsagePercent,
                  dfl260eDHCPActiveClients,
                  dfl260eDHCPActiveClientsPercent,
                  dfl260eDHCPRejectedRequests,
                  dfl260eDHCPTotalLeases }
    STATUS      current
    DESCRIPTION
        "DHCP server rules objects."
    ::= { dfl260eStatsRegGroups 5 }

dfl260eRuleUseGroup OBJECT-GROUP
    OBJECTS     { dfl260eRuleName, dfl260eRuleUse }
    STATUS      current
    DESCRIPTION
        "Rule use objects."
    ::= { dfl260eStatsRegGroups 6 }

dfl260eUserAuthGroup OBJECT-GROUP
    OBJECTS     { dfl260eUserAuthHTTPUsers, dfl260eUserAuthXAUTHUsers,
                  dfl260eUserAuthHTTPSUsers, dfl260eUserAuthPPPUsers,
                  dfl260eUserAuthEAPUsers, dfl260eUserAuthRuleName,
                  dfl260eUserAuthRuleUse }
    STATUS      current
    DESCRIPTION
        "User auth objects."
    ::= { dfl260eStatsRegGroups 7 }

dfl260eIfStatsGroup OBJECT-GROUP
    OBJECTS     { dfl260eIfName,
                  dfl260eIfFragsIn,
                  dfl260eIfFragReassOk,
                  dfl260eIfFragReassFail,
                  dfl260eIfPktsInCnt,
                  dfl260eIfPktsOutCnt,
                  dfl260eIfBitsInCnt,
                  dfl260eIfBitsOutCnt,
                  dfl260eIfPktsTotCnt,
                  dfl260eIfBitsTotCnt,
                  dfl260eIfHCPktsInCnt,
                  dfl260eIfHCPktsOutCnt,
                  dfl260eIfHCBitsInCnt,
                  dfl260eIfHCBitsOutCnt,
                  dfl260eIfHCPktsTotCnt,
                  dfl260eIfHCBitsTotCnt,
                  dfl260eIfRxRingFifoErrors,
                  dfl260eIfRxDespools,
                  dfl260eIfRxAvgUse,
                  dfl260eIfRxRingSaturation,
                  dfl260eRxRingFlooded,
                  dfl260eIfTxDespools,
                  dfl260eIfTxAvgUse,
                  dfl260eIfTxRingSaturation,
                  dfl260eRxTingFlooded }
    STATUS      current
    DESCRIPTION
        "DFL-260e interface statistics group."
    ::= { dfl260eStatsRegGroups 8 }

dfl260eLinkMonitorGroup OBJECT-GROUP
    OBJECTS     { dfl260eLinkMonGrp,
                  dfl260eLinkMonGrpName,
                  dfl260eLinkMonGrpHostsUp,
                  dfl260eLinkMonHostId,
                  dfl260eLinkMonHostShortTermLoss,
                  dfl260eLinkMonHostPacketsLost }
    STATUS      current
    DESCRIPTION
        "DFL-260e link monitor statistics group"
    ::= { dfl260eStatsRegGroups 9 }

dfl260ePipesObjectGroup OBJECT-GROUP
    OBJECTS     { dfl260ePipeUsers,
                  dfl260ePipeName,
                  dfl260ePipeMinPrec,
                  dfl260ePipeMaxPrec,
                  dfl260ePipeDefPrec,
                  dfl260ePipeNumPrec,
                  dfl260ePipeNumUsers,
                  dfl260ePipeCurrentBps,
                  dfl260ePipeCurrentPps,
                  dfl260ePipeDelayedPackets,
                  dfl260ePipeDropedPackets,
                  dfl260ePipePrec,
                  dfl260ePipePrecBps,
                  dfl260ePipePrecTotalPps,
                  dfl260ePipePrecReservedBps,
                  dfl260ePipePrecDynLimBps,
                  dfl260ePipePrecDynUsrLimBps,
                  dfl260ePipePrecDelayedPackets,
                  dfl260ePipePrecDropedPackets }
    STATUS      current
    DESCRIPTION
        "DFL-260e pipes statistics group"
    ::= { dfl260eStatsRegGroups 10 }

dfl260eDHCPRelayObjectGroup OBJECT-GROUP
    OBJECTS     { dfl260eDHCPRelayCurClients,
                  dfl260eDHCPRelayCurTrans,
                  dfl260eDHCPRelayRejected,
                  dfl260eDHCPRelayRuleName,
                  dfl260eDHCPRelayRuleHits,
                  dfl260eDHCPRelayRuleCurClients,
                  dfl260eDHCPRelayRuleRejCliPkts,
                  dfl260eDHCPRelayRuleRejSrvPkts }
    STATUS      current
    DESCRIPTION
        "DFL-260e DHCP relay statistics group"
    ::= { dfl260eStatsRegGroups 12 }

dfl260eAlgGroup OBJECT-GROUP
    OBJECTS     { dfl260eAlgSessions,
                  dfl260eAlgConnections,
                  dfl260eAlgTCPStreams,
                  dfl260eHttpAlgName,
                  dfl260eHttpAlgTotalRequested,
                  dfl260eHttpAlgTotalAllowed,
                  dfl260eHttpAlgTotalBlocked,
                  dfl260eHttpAlgCntFltName,
                  dfl260eHttpAlgCntFltRequests,
                  dfl260eHttpAlgCntFltAllowed,
                  dfl260eHttpAlgCntFltBlocked }
    STATUS      current
    DESCRIPTION
        "DFL-260e HTTP ALG statistics group"
    ::= { dfl260eStatsRegGroups 13 }

dfl260eHAGroup OBJECT-GROUP
    OBJECTS     { dfl260eHASyncSendQueueLength,
                  dfl260eHASyncSendQueueUsagePkt,
                  dfl260eHASyncSendQueueUsageOct,
                  dfl260eHASyncSentPackets,
                  dfl260eHASyncSendResentPackets }
    STATUS      current
    DESCRIPTION
        "DFL-260e HA statistics group"
    ::= { dfl260eStatsRegGroups 14 }

dfl260eIfVlanGroup OBJECT-GROUP
    OBJECTS     { dfl260eIfVlanUntaggedInPkts,
                  dfl260eIfVlanUntaggedOutPkts,
                  dfl260eIfVlanUntaggedTotPkts,
                  dfl260eIfVlanUntaggedInOctets,
                  dfl260eIfVlanUntaggedOutOctets,
                  dfl260eIfVlanUntaggedTotOctets }
    STATUS      current
    DESCRIPTION
        "DFL-260e VLAN statistics group"
    ::= { dfl260eStatsRegGroups 15 }


dfl260eSmtpAlgGroup OBJECT-GROUP
    OBJECTS { dfl260eSmtpAlgName,
              dfl260eSmtpAlgTotCheckedSes,
              dfl260eSmtpAlgTotSpamSes,
              dfl260eSmtpAlgTotDroppedSes,
              dfl260eSmtpAlgDnsBlName,
              dfl260eSmtpAlgDnsBlChecked,
              dfl260eSmtpAlgDnsBlMatched,
              dfl260eSmtpAlgDnsBlFailChecks }
   STATUS current
   DESCRIPTION
       "Clavister SMTP ALG objects group"
   ::= { dfl260eStatsRegGroups 16 }

dfl260eSysTCPGroup OBJECT-GROUP
    OBJECTS { dfl260eSysTCPRecvSmall,
              dfl260eSysTCPRecvLarge,
              dfl260eSysTCPSendSmall,
              dfl260eSysTCPSendLarge }
    STATUS current
    DESCRIPTION
      "DFL-260e TCP buffer usage group"
    ::= { dfl260eStatsRegGroups 17 }



dfl260eStatsCompliance MODULE-COMPLIANCE
    STATUS      current
    DESCRIPTION
        "Module Compliance"

    MODULE      -- this module

        MANDATORY-GROUPS
                { dfl260eSystemObjectGroup,
                  dfl260eIPsecObjectGroup,
                  dfl260eStateCountersGroup,
                  dfl260eIPPoolGroup,
                  dfl260eDHCPServerGroup,
                  dfl260eRuleUseGroup,
                  dfl260eUserAuthGroup,
                  dfl260eIfStatsGroup,
                  dfl260eLinkMonitorGroup,
                  dfl260ePipesObjectGroup,
                  dfl260eDHCPRelayObjectGroup,
                  dfl260eAlgGroup,
                  dfl260eHAGroup,
                  dfl260eIfVlanGroup,
                  dfl260eSmtpAlgGroup,
                  dfl260eSysTCPGroup }

    ::= { dfl260eStatsConformance 1 }

END -- end of module DFL260e-MIB.
