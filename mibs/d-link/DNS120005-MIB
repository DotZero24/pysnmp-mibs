--
-- DNS120005.mib
--

-- Copyright (c) 2001-2011 alphanetworks Inc.,
-- Module Name: DNS120005.mib
-- Abstract:
-- 	Defines the DNS120005 NAS MIBs .
-- Authors: Casper Huang/Hikaru Tsai
--

	DNS120005-MIB DEFINITIONS ::= BEGIN


	IMPORTS
		OBJECT-TYPE, Integer32, enterprises,
		NOTIFICATION-TYPE
			FROM SNMPv2-SMI
		DisplayString
			FROM SNMPv2-TC;

--
--  OID definitions
--

	d-link		OBJECT IDENTIFIER ::= { enterprises 171 }
	productID	OBJECT IDENTIFIER ::= { d-link 50}
	projectID	OBJECT IDENTIFIER ::= { productID 1}
	modelID 	OBJECT IDENTIFIER ::= { projectID 1}
	submodelID OBJECT IDENTIFIER ::= { modelID 1}
	nasAgent1200	OBJECT IDENTIFIER ::= { submodelID 1}


--
-- Node definitions
--
			nasAgentVer OBJECT-TYPE
				SYNTAX DisplayString
				MAX-ACCESS read-only
				STATUS current
				DESCRIPTION
					"version information for the agent of SNMP of DNS120005."
				::= { nasAgent1200 1 }

-- ============================================================================

			sysTable OBJECT-TYPE
				SYNTAX SEQUENCE OF SysEntry
				MAX-ACCESS not-accessible
				STATUS current
				DESCRIPTION
					"A table of system info of the NAS device."
				::= { nasAgent1200 2 }

			sysEntry OBJECT-TYPE
				SYNTAX SysEntry
				MAX-ACCESS not-accessible
				STATUS current
				DESCRIPTION
					"An entry in the system info table."
				INDEX { sysNum }
				::= { sysTable 1 }

			SysEntry ::=
				SEQUENCE {
					sysNum
						Integer32,
					sysName
						DisplayString,
					sysFWVer
						DisplayString,
					sysNetType
						DisplayString,
					sysFanSpeed
						DisplayString,
					sysTemperature
						DisplayString,
					sysPrinterName
						DisplayString,
					sysCIFS
						DisplayString,
					sysFtpServer
						DisplayString,
					sysNFSServer
						DisplayString,
					sysDFSServer
						DisplayString,
					sysQuota
						DisplayString,
					sysAFP
						DisplayString,
					sysWebDAV
						DisplayString,
					sysWebFileServer
						DisplayString,
					sysiSCSITarget
						DisplayString,
					sysiSNS
						DisplayString
				 }

			sysNum OBJECT-TYPE
				SYNTAX Integer32
				MAX-ACCESS read-only
				STATUS current
				DESCRIPTION
					"Instance number of the system info entry."
				::= { sysEntry 1 }

			sysName OBJECT-TYPE
				SYNTAX DisplayString
				MAX-ACCESS read-only
				STATUS current
				DESCRIPTION
					"The device name"
				::= { sysEntry 2 }

			sysFWVer OBJECT-TYPE
				SYNTAX DisplayString
				MAX-ACCESS read-only
				STATUS current
				DESCRIPTION
					"The device firmware version"
				::= { sysEntry 3 }

			sysNetType OBJECT-TYPE
				SYNTAX DisplayString
				MAX-ACCESS read-only
				STATUS current
				DESCRIPTION
					"The Network type.
					(	0 : Workgroup
						1 : Active Directory)"
				::= { sysEntry 4 }

			sysFanSpeed OBJECT-TYPE
				SYNTAX DisplayString
				MAX-ACCESS read-only
				STATUS current
				DESCRIPTION
					"The current speed of the fan.
						(high, low, stop.)"
				::= { sysEntry 5 }

			sysTemperature OBJECT-TYPE
				SYNTAX DisplayString
				MAX-ACCESS read-only
				STATUS current
				DESCRIPTION
					"The centigrade temperature of the system."
				::= { sysEntry 6 }

			sysPrinterName OBJECT-TYPE
				SYNTAX DisplayString
				MAX-ACCESS read-only
				STATUS current
				DESCRIPTION
					"The mode name of printer"
				::= { sysEntry 7 }

			sysCIFS OBJECT-TYPE
				SYNTAX DisplayString
				MAX-ACCESS read-only
				STATUS current
				DESCRIPTION
					"Samba status.
					1 : enable
					0 : disable
					"
				::= { sysEntry 8 }

			sysFtpServer OBJECT-TYPE
				SYNTAX DisplayString
				MAX-ACCESS read-only
				STATUS current
				DESCRIPTION
					"Ftp Server status.
					1 : enable
					0 : disable
					"
				::= { sysEntry 9 }

			sysNFSServer OBJECT-TYPE
				SYNTAX DisplayString
				MAX-ACCESS read-only
				STATUS current
				DESCRIPTION
					"NFS Server status.
					1 : enable
					0 : disable
					"
				::= { sysEntry 10 }

			sysDFSServer OBJECT-TYPE
				SYNTAX DisplayString
				MAX-ACCESS read-only
				STATUS current
				DESCRIPTION
					"DFS Server status.
					1 : enable
					0 : disable
					"
				::= { sysEntry 11 }

			sysQuota OBJECT-TYPE
				SYNTAX DisplayString
				MAX-ACCESS read-only
				STATUS current
				DESCRIPTION
					"Quota status.
					1 : enable
					0 : disable
					"
				::= { sysEntry 12 }

			sysAFP OBJECT-TYPE
				SYNTAX DisplayString
				MAX-ACCESS read-only
				STATUS current
				DESCRIPTION
					"AFP status.
					1 : enable
					0 : disable
					"
				::= { sysEntry 13 }

			sysWebDAV OBJECT-TYPE
				SYNTAX DisplayString
				MAX-ACCESS read-only
				STATUS current
				DESCRIPTION
					"WebDAV status.
					1 : enable
					0 : disable
					"
				::= { sysEntry 14 }

			sysWebFileServer OBJECT-TYPE
				SYNTAX DisplayString
				MAX-ACCESS read-only
				STATUS current
				DESCRIPTION
					"WebFile Server status.
					1 : enable
					0 : disable
					"
				::= { sysEntry 15 }

			sysiSCSITarget OBJECT-TYPE
				SYNTAX DisplayString
				MAX-ACCESS read-only
				STATUS current
				DESCRIPTION
					"iSCSI target status.
					1 : enable
					0 : disable
					"
				::= { sysEntry 16 }

			sysiSNS OBJECT-TYPE
				SYNTAX DisplayString
				MAX-ACCESS read-only
				STATUS current
				DESCRIPTION
					"iSNS Server status.
					1 : enable
					0 : disable
					"
				::= { sysEntry 17 }

-- ============================================================================

		diskTable OBJECT-TYPE
			SYNTAX SEQUENCE OF DiskEntry
			MAX-ACCESS not-accessible
			STATUS current
			DESCRIPTION
				"A table of physical disks attached to the NAS device."
			::= { nasAgent1200 3 }

		diskEntry OBJECT-TYPE
			SYNTAX DiskEntry
			MAX-ACCESS not-accessible
			STATUS current
			DESCRIPTION
				"An entry in the physical disk table."
			INDEX { diskNum }
			::= { diskTable 1 }

		DiskEntry ::=
			SEQUENCE {
				diskNum
					Integer32,
				diskName
					DisplayString,
				diskModel
					DisplayString,
        diskTemperature
					DisplayString,
				diskCapacity
					DisplayString,
				diskStatus
					DisplayString
			 }

		diskNum OBJECT-TYPE
			SYNTAX Integer32
			MAX-ACCESS read-only
			STATUS current
			DESCRIPTION
				"Instance number of the disk entry."
			::= { diskEntry 1 }

		diskName OBJECT-TYPE
			SYNTAX DisplayString
			MAX-ACCESS read-only
			STATUS current
			DESCRIPTION
				"The device name that the disk is connected to. Example : sda, sdb, sdc sdd"
			::= { diskEntry 2 }

		diskModel OBJECT-TYPE
			SYNTAX DisplayString
			MAX-ACCESS read-only
			STATUS current
			DESCRIPTION
				"The disk drive's model name."
			::= { diskEntry 3 }

		diskTemperature OBJECT-TYPE
			SYNTAX DisplayString
			MAX-ACCESS read-only
			STATUS current
			DESCRIPTION
				"The centigrade temperature of this disk."
			::= { diskEntry 4 }

		diskCapacity OBJECT-TYPE
			SYNTAX DisplayString
			MAX-ACCESS read-only
			STATUS current
			DESCRIPTION
				"The capacity of the disk in bytes."
			::= { diskEntry 5 }

		diskStatus OBJECT-TYPE
			SYNTAX DisplayString
			MAX-ACCESS read-only
			STATUS current
			DESCRIPTION
				"The status of the disk.
				has disk : Online
				no disk : Offline
				"
			::= { diskEntry 6 }

-- ============================================================================

		volumeTable OBJECT-TYPE
			SYNTAX SEQUENCE OF VolumeEntry
			MAX-ACCESS not-accessible
			STATUS current
			DESCRIPTION
				"A table of active volumes on the NAS device."
			::= { nasAgent1200 4 }

		volumeEntry OBJECT-TYPE
			SYNTAX VolumeEntry
			MAX-ACCESS not-accessible
			STATUS current
			DESCRIPTION
				"An entry in the volume table."
			INDEX { volumeNum }
			::= { volumeTable 1 }

		VolumeEntry ::=
			SEQUENCE {
				volumeNum
					Integer32,
				volumeName
					DisplayString,
				volumeEncryption
					DisplayString,
				volumeFsType
					DisplayString,
				volumeRaidLevel
					DisplayString,
				volumeSize
					DisplayString,
				volumeFreeSpace
					DisplayString,
				volumeState
				DisplayString
			 }

		volumeNum OBJECT-TYPE
			SYNTAX Integer32
			MAX-ACCESS read-only
			STATUS current
			DESCRIPTION
				"Instance number of the volume entry."
			::= { volumeEntry 1 }

		volumeName OBJECT-TYPE
			SYNTAX DisplayString
			MAX-ACCESS read-only
			STATUS current
			DESCRIPTION
				"The name of the volume."
			::= { volumeEntry 2 }

		volumeEncryption OBJECT-TYPE
			SYNTAX DisplayString
			MAX-ACCESS read-only
			STATUS current
			DESCRIPTION
				"The encryption of the volume."
			::= { volumeEntry 3 }

		volumeFsType OBJECT-TYPE
			SYNTAX DisplayString
			MAX-ACCESS read-only
			STATUS current
			DESCRIPTION
				"The type of file systme of the volume.
				Example : ext2 or ext3"
			::= { volumeEntry 4 }

		volumeRaidLevel OBJECT-TYPE
			SYNTAX DisplayString
			MAX-ACCESS read-only
			STATUS current
			DESCRIPTION
				"The RAID level of the volume."
			::= { volumeEntry 5 }

		volumeSize OBJECT-TYPE
			SYNTAX DisplayString
			MAX-ACCESS read-only
			STATUS current
			DESCRIPTION
				"The size of the volume in bytes."
			::= { volumeEntry 6 }

		volumeFreeSpace OBJECT-TYPE
			SYNTAX DisplayString
			MAX-ACCESS read-only
			STATUS current
			DESCRIPTION
				"Free space on the volume in bytes."
			::= { volumeEntry 7 }

		volumeState OBJECT-TYPE
			SYNTAX DisplayString
			MAX-ACCESS read-only
			STATUS current
			DESCRIPTION
				"The state of the volume."
			::= { volumeEntry 8 }

-- ============================================================================

		snapShotTable OBJECT-TYPE
			SYNTAX SEQUENCE OF SnapShotEntry
			MAX-ACCESS not-accessible
			STATUS current
			DESCRIPTION
				"A table of Volume SnapShot on the NAS device."
			::= { nasAgent1200 5 }

		snapShotEntry OBJECT-TYPE
			SYNTAX SnapShotEntry
			MAX-ACCESS not-accessible
			STATUS current
			DESCRIPTION
				"An entry in the SnapShot table."
			INDEX { snapShotNum }
			::= { snapShotTable 1 }

		SnapShotEntry ::=
			SEQUENCE {
				snapShotNum
					Integer32,
				snapShotVolume
					DisplayString,
				snapShotName
					DisplayString,
				snapShotSchedule
					DisplayString,
				snapShotCount
					DisplayString,
				snapShotState
					DisplayString,
				snapShotPath
					DisplayString
			 }

		snapShotNum OBJECT-TYPE
			SYNTAX Integer32
			MAX-ACCESS read-only
			STATUS current
			DESCRIPTION
				"Instance number of the SnapShot entry."
			::= { snapShotEntry 1 }

		snapShotVolume OBJECT-TYPE
			SYNTAX DisplayString
			MAX-ACCESS read-only
			STATUS current
			DESCRIPTION
				"The volume of the SnapShot."
			::= { snapShotEntry 2 }

		snapShotName OBJECT-TYPE
			SYNTAX DisplayString
			MAX-ACCESS read-only
			STATUS current
			DESCRIPTION
				"The name of the SnapShot."
			::= { snapShotEntry 3 }

		snapShotSchedule OBJECT-TYPE
			SYNTAX DisplayString
			MAX-ACCESS read-only
			STATUS current
			DESCRIPTION
				"The schedule of SnapShot."
			::= { snapShotEntry 4 }

		snapShotCount OBJECT-TYPE
			SYNTAX DisplayString
			MAX-ACCESS read-only
			STATUS current
			DESCRIPTION
				"The count squash of SnapShot."
			::= { snapShotEntry 5 }

		snapShotState OBJECT-TYPE
			SYNTAX DisplayString
			MAX-ACCESS read-only
			STATUS current
			DESCRIPTION
				"The state of SnapShot."
			::= { snapShotEntry 6 }

		snapShotPath OBJECT-TYPE
			SYNTAX DisplayString
			MAX-ACCESS read-only
			STATUS current
			DESCRIPTION
				"The path of SnapShot."
			::= { snapShotEntry 7 }

-- ============================================================================

		dFSTable OBJECT-TYPE
			SYNTAX SEQUENCE OF DFSEntry
			MAX-ACCESS not-accessible
			STATUS current
			DESCRIPTION
				"A table of Distributed File System on the NAS device."
			::= { nasAgent1200 6 }

		dFSEntry OBJECT-TYPE
			SYNTAX DFSEntry
			MAX-ACCESS not-accessible
			STATUS current
			DESCRIPTION
				"An entry in the DFS table."
			INDEX { dFSNum }
			::= { dFSTable 1 }

		DFSEntry ::=
			SEQUENCE {
				dFSNum
					Integer32,
				dFSLShareName
					DisplayString,
				dFSHost
					DisplayString,
				dFSRSharefolder
					DisplayString
			 }

		dFSNum OBJECT-TYPE
			SYNTAX Integer32
			MAX-ACCESS read-only
			STATUS current
			DESCRIPTION
				"Instance number of the DFS entry."
			::= { dFSEntry 1 }

		dFSLShareName OBJECT-TYPE
			SYNTAX DisplayString
			MAX-ACCESS read-only
			STATUS current
			DESCRIPTION
				"The local share name of the DFS."
			::= { dFSEntry 2 }

		dFSHost OBJECT-TYPE
			SYNTAX DisplayString
			MAX-ACCESS read-only
			STATUS current
			DESCRIPTION
				"The Host of DFS."
			::= { dFSEntry 3 }

		dFSRSharefolder OBJECT-TYPE
			SYNTAX DisplayString
			MAX-ACCESS read-only
			STATUS current
			DESCRIPTION
				"The remote share folder of DFS."
			::= { dFSEntry 4 }

-- ============================================================================

		nFSTable OBJECT-TYPE
			SYNTAX SEQUENCE OF NFSEntry
			MAX-ACCESS not-accessible
			STATUS current
			DESCRIPTION
				"A table of Network File System on the NAS device."
			::= { nasAgent1200 7}

		nFSEntry OBJECT-TYPE
			SYNTAX NFSEntry
			MAX-ACCESS not-accessible
			STATUS current
			DESCRIPTION
				"An entry in the NFS table."
			INDEX { nFSNum }
			::= { nFSTable 1 }

		NFSEntry ::=
			SEQUENCE {
				nFSNum
					Integer32,
				nFSMountPath
					DisplayString,
				nFSHost
					DisplayString,
				nFSPermission
					DisplayString,
				nFSRootSquash
					DisplayString,
				nFSStatus
					DisplayString
			 }

		nFSNum OBJECT-TYPE
			SYNTAX Integer32
			MAX-ACCESS read-only
			STATUS current
			DESCRIPTION
				"Instance number of the NFS entry."
			::= { nFSEntry 1 }

		nFSMountPath OBJECT-TYPE
			SYNTAX DisplayString
			MAX-ACCESS read-only
			STATUS current
			DESCRIPTION
				"The mount path of the NFS."
			::= { nFSEntry 2 }

		nFSHost OBJECT-TYPE
			SYNTAX DisplayString
			MAX-ACCESS read-only
			STATUS current
			DESCRIPTION
				"The host of the NFS."
			::= { nFSEntry 3 }

		nFSPermission OBJECT-TYPE
			SYNTAX DisplayString
			MAX-ACCESS read-only
			STATUS current
			DESCRIPTION
				"The permission of NFS."
			::= { nFSEntry 4 }

		nFSRootSquash OBJECT-TYPE
			SYNTAX DisplayString
			MAX-ACCESS read-only
			STATUS current
			DESCRIPTION
				"The root squash of NFS."
			::= { nFSEntry 5 }

		nFSStatus OBJECT-TYPE
			SYNTAX DisplayString
			MAX-ACCESS read-only
			STATUS current
			DESCRIPTION
				"The status of NFS."
			::= { nFSEntry 6 }

-- ============================================================================

		iSOTable OBJECT-TYPE
			SYNTAX SEQUENCE OF ISOEntry
			MAX-ACCESS not-accessible
			STATUS current
			DESCRIPTION
				"A table of ISO fileon the NAS device."
			::= { nasAgent1200 8 }

		iSOEntry OBJECT-TYPE
			SYNTAX ISOEntry
			MAX-ACCESS not-accessible
			STATUS current
			DESCRIPTION
				"An entry in the ISO table."
			INDEX { iSONum }
			::= { iSOTable 1 }

		ISOEntry ::=
			SEQUENCE {
				iSONum
					Integer32,
				iSOShareName
					DisplayString,
				iSOPath
					DisplayString,
				iSOStatus
					DisplayString
			 }

		iSONum OBJECT-TYPE
			SYNTAX Integer32
			MAX-ACCESS read-only
			STATUS current
			DESCRIPTION
				"Instance number of the ISO entry."
			::= { iSOEntry 1 }

		iSOShareName OBJECT-TYPE
			SYNTAX DisplayString
			MAX-ACCESS read-only
			STATUS current
			DESCRIPTION
				"The share name of the ISO."
			::= { iSOEntry 2 }

		iSOPath OBJECT-TYPE
			SYNTAX DisplayString
			MAX-ACCESS read-only
			STATUS current
			DESCRIPTION
				"The path of the ISO."
			::= { iSOEntry 3 }

		iSOStatus OBJECT-TYPE
			SYNTAX DisplayString
			MAX-ACCESS read-only
			STATUS current
			DESCRIPTION
				"The status of ISO."
			::= { iSOEntry 4 }

-- ============================================================================

		logServerTable OBJECT-TYPE
			SYNTAX SEQUENCE OF LogServerEntry
			MAX-ACCESS not-accessible
			STATUS current
			DESCRIPTION
				"A table of syslog server on the NAS device."
			::= { nasAgent1200 9 }

		logServerEntry OBJECT-TYPE
			SYNTAX LogServerEntry
			MAX-ACCESS not-accessible
			STATUS current
			DESCRIPTION
				"An entry in the logServer table."
			INDEX { logServerNum }
			::= { logServerTable 1 }

		LogServerEntry ::=
			SEQUENCE {
				logServerNum
					Integer32,
				logServerRuleName
					DisplayString,
				logServerLogfiles
					DisplayString,
				logServerStatus
					DisplayString
			 }

		logServerNum OBJECT-TYPE
			SYNTAX Integer32
			MAX-ACCESS read-only
			STATUS current
			DESCRIPTION
				"Instance number of the logServer entry."
			::= { logServerEntry 1 }

		logServerRuleName OBJECT-TYPE
			SYNTAX DisplayString
			MAX-ACCESS read-only
			STATUS current
			DESCRIPTION
				"The rule name of the syslog server."
			::= { logServerEntry 2 }

		logServerLogfiles OBJECT-TYPE
			SYNTAX DisplayString
			MAX-ACCESS read-only
			STATUS current
			DESCRIPTION
				"The log files of syslog server."
			::= { logServerEntry 3 }

		logServerStatus OBJECT-TYPE
			SYNTAX DisplayString
			MAX-ACCESS read-only
			STATUS current
			DESCRIPTION
				"The staus of syslog server."
			::= { logServerEntry 4 }

-- ============================================================================

		uPSTable OBJECT-TYPE
			SYNTAX SEQUENCE OF UPSEntry
			MAX-ACCESS not-accessible
			STATUS current
			DESCRIPTION
				"A table of UPS on the NAS device."
			::= { nasAgent1200 10 }

		uPSEntry OBJECT-TYPE
			SYNTAX UPSEntry
			MAX-ACCESS not-accessible
			STATUS current
			DESCRIPTION
				"An entry in the UPS table."
			INDEX { uPSNum }
			::= { uPSTable 1 }

		UPSEntry ::=
			SEQUENCE {
				uPSNum
					Integer32,
				uPSDeviceInfo
					DisplayString,
				uPSProduct
					DisplayString,
				uPSManufacturer
					DisplayString,
				uPSBattery
					DisplayString,
				uPSState
					DisplayString,
				uPSServerIP
					DisplayString,
				uPSAllowedIP
					DisplayString
			 }

		uPSNum OBJECT-TYPE
			SYNTAX Integer32
			MAX-ACCESS read-only
			STATUS current
			DESCRIPTION
				"Instance number of the uPS entry."
			::= { uPSEntry 1 }

		uPSDeviceInfo OBJECT-TYPE
			SYNTAX DisplayString
			MAX-ACCESS read-only
			STATUS current
			DESCRIPTION
				"The deviceinfo of the UPS."
			::= { uPSEntry 2 }

		uPSProduct OBJECT-TYPE
			SYNTAX DisplayString
			MAX-ACCESS read-only
			STATUS current
			DESCRIPTION
				"The product of UPS."
			::= { uPSEntry 3 }

		uPSManufacturer OBJECT-TYPE
			SYNTAX DisplayString
			MAX-ACCESS read-only
			STATUS current
			DESCRIPTION
				"The manufacturer of UPS."
			::= { uPSEntry 4 }

		uPSBattery OBJECT-TYPE
			SYNTAX DisplayString
			MAX-ACCESS read-only
			STATUS current
			DESCRIPTION
				"The battery of UPS."
			::= { uPSEntry 5 }

		uPSState OBJECT-TYPE
			SYNTAX DisplayString
			MAX-ACCESS read-only
			STATUS current
			DESCRIPTION
				"The state of SnapShot."
			::= { uPSEntry 6 }

		uPSServerIP OBJECT-TYPE
			SYNTAX DisplayString
			MAX-ACCESS read-only
			STATUS current
			DESCRIPTION
				"The server IP of UPS."
			::= { uPSEntry 7 }

		uPSAllowedIP OBJECT-TYPE
			SYNTAX DisplayString
			MAX-ACCESS read-only
			STATUS current
			DESCRIPTION
				"The allowed IP of UPS."
			::= { uPSEntry 8 }

-- ============================================================================

		vVTable OBJECT-TYPE
			SYNTAX SEQUENCE OF VVEntry
			MAX-ACCESS not-accessible
			STATUS current
			DESCRIPTION
				"A table of Virtual Volume on the NAS device."
			::= { nasAgent1200 11 }

		vVEntry OBJECT-TYPE
			SYNTAX VVEntry
			MAX-ACCESS not-accessible
			STATUS current
			DESCRIPTION
				"An entry in the Virtual Volume table."
			INDEX { vVNum }
			::= { vVTable 1 }

		VVEntry ::=
			SEQUENCE {
				vVNum
					Integer32,
				vVTargetName
					DisplayString,
				vVSharefolder
					DisplayString,
				vVStatus
					DisplayString,
				vVSize
					DisplayString
			 }

		vVNum OBJECT-TYPE
			SYNTAX Integer32
			MAX-ACCESS read-only
			STATUS current
			DESCRIPTION
				"Instance number of the Virtual Volume entry."
			::= { vVEntry 1 }

		vVTargetName OBJECT-TYPE
			SYNTAX DisplayString
			MAX-ACCESS read-only
			STATUS current
			DESCRIPTION
				"The target name of the Virtual Volume."
			::= { vVEntry 2 }

		vVSharefolder OBJECT-TYPE
			SYNTAX DisplayString
			MAX-ACCESS read-only
			STATUS current
			DESCRIPTION
				"The share folder of Virtual Volume."
			::= { vVEntry 3 }

		vVStatus OBJECT-TYPE
			SYNTAX DisplayString
			MAX-ACCESS read-only
			STATUS current
			DESCRIPTION
				"The status of Virtual Volume."
			::= { vVEntry 4 }

		vVSize OBJECT-TYPE
			SYNTAX DisplayString
			MAX-ACCESS read-only
			STATUS current
			DESCRIPTION
				"The size of Virtual Volume."
			::= { vVEntry 5 }

-- ============================================================================

		iSCSITargetTable OBJECT-TYPE
			SYNTAX SEQUENCE OF ISCSITargetEntry
			MAX-ACCESS not-accessible
			STATUS current
			DESCRIPTION
				"A table of iSCSI targets on the NAS device."
			::= { nasAgent1200 12 }

		iSCSITargetEntry OBJECT-TYPE
			SYNTAX ISCSITargetEntry
			MAX-ACCESS not-accessible
			STATUS current
			DESCRIPTION
				"An entry in the iSCSITarget table."
			INDEX { iSCSITargetNum }
			::= { iSCSITargetTable 1 }

		ISCSITargetEntry ::=
			SEQUENCE {
				iSCSITargetNum
					Integer32,
				iSCSITargetIQN
					DisplayString,
				iSCSITargetStatus
					DisplayString
			 }

		iSCSITargetNum OBJECT-TYPE
			SYNTAX Integer32
			MAX-ACCESS read-only
			STATUS current
			DESCRIPTION
				"Instance number of the iSCSI Target entry."
			::= { iSCSITargetEntry 1 }

		iSCSITargetIQN OBJECT-TYPE
			SYNTAX DisplayString
			MAX-ACCESS read-only
			STATUS current
			DESCRIPTION
				"The IQN of the iSCSI Target."
			::= { iSCSITargetEntry 2 }

		iSCSITargetStatus OBJECT-TYPE
			SYNTAX DisplayString
			MAX-ACCESS read-only
			STATUS current
			DESCRIPTION
				"The status of iSCSI Target."
			::= { iSCSITargetEntry 3 }

-- ============================================================================

		iSCSILUNTable OBJECT-TYPE
			SYNTAX SEQUENCE OF ISCSILUNEntry
			MAX-ACCESS not-accessible
			STATUS current
			DESCRIPTION
				"A table of iSCSI LUN on the NAS device."
			::= { nasAgent1200 13 }

		iSCSILUNEntry OBJECT-TYPE
			SYNTAX ISCSILUNEntry
			MAX-ACCESS not-accessible
			STATUS current
			DESCRIPTION
				"An entry in the iSCSI LUN table."
			INDEX { iSCSILUNNum }
			::= { iSCSILUNTable 1 }

		ISCSILUNEntry ::=
			SEQUENCE {
				iSCSILUNNum
					Integer32,
				iSCSILUNName
					DisplayString,
				iSCSILUNVolume
					DisplayString,
				iSCSILUNSize
					DisplayString,
				iSCSILUNStatus
					DisplayString,
				iSCSILUNMapping
					DisplayString
			 }

		iSCSILUNNum OBJECT-TYPE
			SYNTAX Integer32
			MAX-ACCESS read-only
			STATUS current
			DESCRIPTION
				"Instance number of the iSCSI Target entry."
			::= { iSCSILUNEntry 1 }

		iSCSILUNName OBJECT-TYPE
			SYNTAX DisplayString
			MAX-ACCESS read-only
			STATUS current
			DESCRIPTION
				"The name of the iSCSI LUN."
			::= { iSCSILUNEntry 2 }

		iSCSILUNVolume OBJECT-TYPE
			SYNTAX DisplayString
			MAX-ACCESS read-only
			STATUS current
			DESCRIPTION
				"The volume of iSCSI LUN."
			::= { iSCSILUNEntry 3 }

		iSCSILUNSize OBJECT-TYPE
			SYNTAX DisplayString
			MAX-ACCESS read-only
			STATUS current
			DESCRIPTION
				"The size of iSCSI LUN."
			::= { iSCSILUNEntry 4 }

		iSCSILUNStatus OBJECT-TYPE
			SYNTAX DisplayString
			MAX-ACCESS read-only
			STATUS current
			DESCRIPTION
				"The status of iSCSI LUN."
			::= { iSCSILUNEntry 5 }

		iSCSILUNMapping OBJECT-TYPE
			SYNTAX DisplayString
			MAX-ACCESS read-only
			STATUS current
			DESCRIPTION
				"The mapping of iSCSI LUN."
			::= { iSCSILUNEntry 6 }

-- ============================================================================

		iSCSIACLTable OBJECT-TYPE
			SYNTAX SEQUENCE OF ISCSIACLEntry
			MAX-ACCESS not-accessible
			STATUS current
			DESCRIPTION
				"A table of iSCSI ACL on the NAS device."
			::= { nasAgent1200 14 }

		iSCSIACLEntry OBJECT-TYPE
			SYNTAX ISCSIACLEntry
			MAX-ACCESS not-accessible
			STATUS current
			DESCRIPTION
				"An entry in the iSCSI ACL table."
			INDEX { iSCSIACLNum }
			::= { iSCSIACLTable 1 }

		ISCSIACLEntry ::=
			SEQUENCE {
				iSCSIACLNum
					Integer32,
				iSCSIACLName
					DisplayString,
				iSCSIACLInitiator
					DisplayString
			 }

		iSCSIACLNum OBJECT-TYPE
			SYNTAX Integer32
			MAX-ACCESS read-only
			STATUS current
			DESCRIPTION
				"Instance number of the iSCSIACL entry."
			::= { iSCSIACLEntry 1 }

		iSCSIACLName OBJECT-TYPE
			SYNTAX DisplayString
			MAX-ACCESS read-only
			STATUS current
			DESCRIPTION
				"The name of the iSCSI ACL."
			::= { iSCSIACLEntry 2 }

		iSCSIACLInitiator OBJECT-TYPE
			SYNTAX DisplayString
			MAX-ACCESS read-only
			STATUS current
			DESCRIPTION
				"The iniator name of iSCSI ACL."
			::= { iSCSIACLEntry 3 }

-- ============================================================================

		aMAZONS3Table OBJECT-TYPE
			SYNTAX SEQUENCE OF AMAZONS3Entry
			MAX-ACCESS not-accessible
			STATUS current
			DESCRIPTION
				"A table of AMAZON S3 on the NAS device."
			::= { nasAgent1200 15 }

		aMAZONS3Entry OBJECT-TYPE
			SYNTAX AMAZONS3Entry
			MAX-ACCESS not-accessible
			STATUS current
			DESCRIPTION
				"An entry in the AMAZON S3 table."
			INDEX { aMAZONS3Num }
			::= { aMAZONS3Table 1 }

		AMAZONS3Entry ::=
			SEQUENCE {
				aMAZONS3Num
					Integer32,
				aMAZONS3Task
					DisplayString,
				aMAZONS3Schedule
					DisplayString,
				aMAZONS3Status
					DisplayString,
				aMAZONS3Enable
					DisplayString,
				aMAZONS3BackupNow
					DisplayString,
				aMAZONS3Restore
					DisplayString
			 }

		aMAZONS3Num OBJECT-TYPE
			SYNTAX Integer32
			MAX-ACCESS read-only
			STATUS current
			DESCRIPTION
				"Instance number of the AMAZON S3 entry."
			::= { aMAZONS3Entry 1 }

		aMAZONS3Task OBJECT-TYPE
			SYNTAX DisplayString
			MAX-ACCESS read-only
			STATUS current
			DESCRIPTION
				"The task of the AMAZON S3."
			::= { aMAZONS3Entry 2 }

		aMAZONS3Schedule OBJECT-TYPE
			SYNTAX DisplayString
			MAX-ACCESS read-only
			STATUS current
			DESCRIPTION
				"The schedule of AMAZON S3."
			::= { aMAZONS3Entry 3 }

		aMAZONS3Status OBJECT-TYPE
			SYNTAX DisplayString
			MAX-ACCESS read-only
			STATUS current
			DESCRIPTION
				"The status of AMAZON S3."
			::= { aMAZONS3Entry 4 }

		aMAZONS3Enable OBJECT-TYPE
			SYNTAX DisplayString
			MAX-ACCESS read-only
			STATUS current
			DESCRIPTION
				"The enable status of AMAZON S3."
			::= { aMAZONS3Entry 5 }

		aMAZONS3BackupNow OBJECT-TYPE
			SYNTAX DisplayString
			MAX-ACCESS read-only
			STATUS current
			DESCRIPTION
				"The backup now status of AMAZON S3."
			::= { aMAZONS3Entry 6 }

		aMAZONS3Restore OBJECT-TYPE
			SYNTAX DisplayString
			MAX-ACCESS read-only
			STATUS current
			DESCRIPTION
				"The restore status of AMAZON S3."
			::= { aMAZONS3Entry 7 }
-- ============================================================================

		connectionTable OBJECT-TYPE
			SYNTAX SEQUENCE OF 	CONNECTIONEntry
			MAX-ACCESS not-accessible
			STATUS current
			DESCRIPTION
				"A table of connection on the NAS device."
			::= { nasAgent1200 16 }

		connectionEntry OBJECT-TYPE
			SYNTAX CONNECTIONEntry
			MAX-ACCESS not-accessible
			STATUS current
			DESCRIPTION
				"An entry in the connection table."
			INDEX { connectionNum }
			::= { connectionTable 1 }

		CONNECTIONEntry ::=
			SEQUENCE {
				connectionNum
					Integer32,
				connectionDateTime
					DisplayString,
				connectionServiceType
					DisplayString,
				connectionIPAddress
					DisplayString,
				connectionUser
					DisplayString,
				connectionComputerName
					DisplayString,
				connectionUsedResources
					DisplayString
			 }

		connectionNum OBJECT-TYPE
			SYNTAX Integer32
			MAX-ACCESS read-only
			STATUS current
			DESCRIPTION
				"Instance number of the connection entry."
			::= { connectionEntry 1 }

		connectionDateTime OBJECT-TYPE
			SYNTAX DisplayString
			MAX-ACCESS read-only
			STATUS current
			DESCRIPTION
				"The datetime of the connection."
			::= { connectionEntry 2 }

		connectionServiceType OBJECT-TYPE
			SYNTAX DisplayString
			MAX-ACCESS read-only
			STATUS current
			DESCRIPTION
				"The service type of connection."
			::= { connectionEntry 3 }

		connectionIPAddress OBJECT-TYPE
			SYNTAX DisplayString
			MAX-ACCESS read-only
			STATUS current
			DESCRIPTION
				"The ip address of connection."
			::= { connectionEntry 4 }

		connectionUser OBJECT-TYPE
			SYNTAX DisplayString
			MAX-ACCESS read-only
			STATUS current
			DESCRIPTION
				"The user of connection."
			::= { connectionEntry 5 }

		connectionComputerName OBJECT-TYPE
			SYNTAX DisplayString
			MAX-ACCESS read-only
			STATUS current
			DESCRIPTION
				"The computer name of connection."
			::= { connectionEntry 6 }

		connectionUsedResources OBJECT-TYPE
			SYNTAX DisplayString
			MAX-ACCESS read-only
			STATUS current
			DESCRIPTION
				"The used resources of connection."
			::= { connectionEntry 7 }
-- ============================================================================

		portForwardingTable OBJECT-TYPE
			SYNTAX SEQUENCE OF 	PORTFORWARDINGEntry
			MAX-ACCESS not-accessible
			STATUS current
			DESCRIPTION
				"A table of port forwarding on the NAS device."
			::= { nasAgent1200 17 }

		portForwardingEntry OBJECT-TYPE
			SYNTAX PORTFORWARDINGEntry
			MAX-ACCESS not-accessible
			STATUS current
			DESCRIPTION
				"An entry in the port forwarding table."
			INDEX { portForwardingNum }
			::= { portForwardingTable 1 }

		PORTFORWARDINGEntry ::=
			SEQUENCE {
				portForwardingNum
					Integer32,
				portForwardingEnable
					DisplayString,
				portForwardingStatus
					DisplayString,
				portForwardingService
					DisplayString,
				portForwardingProtocol
					DisplayString,
				portForwardingExternalPort
					DisplayString,
				portForwardingInternalPort
					DisplayString
			 }

		portForwardingNum OBJECT-TYPE
			SYNTAX Integer32
			MAX-ACCESS read-only
			STATUS current
			DESCRIPTION
				"Instance number of the port forwarding entry."
			::= { portForwardingEntry 1 }

		portForwardingEnable OBJECT-TYPE
			SYNTAX DisplayString
			MAX-ACCESS read-only
			STATUS current
			DESCRIPTION
				"The enable status of the port forwarding."
			::= { portForwardingEntry 2 }

		portForwardingStatus OBJECT-TYPE
			SYNTAX DisplayString
			MAX-ACCESS read-only
			STATUS current
			DESCRIPTION
				"The status of port forwarding."
			::= { portForwardingEntry 3 }

		portForwardingService OBJECT-TYPE
			SYNTAX DisplayString
			MAX-ACCESS read-only
			STATUS current
			DESCRIPTION
				"The service of port forwarding."
			::= { portForwardingEntry 4 }

		portForwardingProtocol OBJECT-TYPE
			SYNTAX DisplayString
			MAX-ACCESS read-only
			STATUS current
			DESCRIPTION
				"The protocol of port forwarding."
			::= { portForwardingEntry 5 }

		portForwardingExternalPort OBJECT-TYPE
			SYNTAX DisplayString
			MAX-ACCESS read-only
			STATUS current
			DESCRIPTION
				"The external port of port forwarding."
			::= { portForwardingEntry 6 }

		portForwardingInternalPort OBJECT-TYPE
			SYNTAX DisplayString
			MAX-ACCESS read-only
			STATUS current
			DESCRIPTION
				"The internal port of port forwarding."
			::= { portForwardingEntry 7 }
-- ============================================================================
--
--  Notifications
--

	notifyEvts OBJECT IDENTIFIER ::= { nasAgent1200 200 }

	notifyPasswdChanged        NOTIFICATION-TYPE
    STATUS      current
    DESCRIPTION
        "An indication that the Administrator's password has been changed."
    ::= { notifyEvts 1 }

    notifyNetworketh0Changed        NOTIFICATION-TYPE
    STATUS      current
    DESCRIPTION
        "An indication that the network eth0 settings has been changed."
    ::= { notifyEvts 2 }

    notifyNetworketh1Changed        NOTIFICATION-TYPE
    STATUS      current
    DESCRIPTION
        "An indication that the network eth1 settings has been changed."
    ::= { notifyEvts 3 }

    notifyTemperatureExceeded        NOTIFICATION-TYPE
    STATUS      current
    DESCRIPTION
        "An indication that system temperature has exceeded ."
    ::= { notifyEvts 4 }

    notifyPowerFailure     NOTIFICATION-TYPE
    STATUS      current
    DESCRIPTION
        "An indication that System has rebooted from power failure."
    ::= { notifyEvts 5 }

    notifyFirmwareUpgraded     NOTIFICATION-TYPE
    STATUS      current
    DESCRIPTION
        "An indication that firmware has been upgraded."
    ::= { notifyEvts 6 }

    notifyDiskLost        NOTIFICATION-TYPE
    STATUS      current
    DESCRIPTION
        "An indication that disk lost ."
    ::= { notifyEvts 7 }

    notifyDiskInsertion        NOTIFICATION-TYPE
    STATUS      current
    DESCRIPTION
        "An indication that disk insertion ."
    ::= { notifyEvts 8 }

    notifyRaidFailed        NOTIFICATION-TYPE
    STATUS      current
    DESCRIPTION
        "An indication that disk fail ."
    ::= { notifyEvts 9 }

    notifyVolumeCreateSuccess        NOTIFICATION-TYPE
    STATUS      current
    DESCRIPTION
        "An indication that volume create successfully ."
    ::= { notifyEvts 10 }

    notifyVolumeCreateFailed        NOTIFICATION-TYPE
    STATUS      current
    DESCRIPTION
        "An indication that volume create failed ."
    ::= { notifyEvts 11 }

    notifyVolumeRemoveSuccess        NOTIFICATION-TYPE
    STATUS      current
    DESCRIPTION
        "An indication that volume remove successfully ."
    ::= { notifyEvts 12 }

    notifyVolumeRemoveFailed        NOTIFICATION-TYPE
    STATUS      current
    DESCRIPTION
        "An indication that volume remove failed ."
    ::= { notifyEvts 13 }

    notifyVolumeStatusCrashed        NOTIFICATION-TYPE
    STATUS      current
    DESCRIPTION
        "An indication that volume status crashed ."
    ::= { notifyEvts 14 }

    notifyVolumeStatusDegraded        NOTIFICATION-TYPE
    STATUS      current
    DESCRIPTION
        "An indication that volume status degraded ."
    ::= { notifyEvts 15 }

    notifyVolumeStatusREBUILD        NOTIFICATION-TYPE
    STATUS      current
    DESCRIPTION
        "An indication that volume status REBUILD ."
    ::= { notifyEvts 16 }

    notifyVolumeStatusREBUILT        NOTIFICATION-TYPE
    STATUS      current
    DESCRIPTION
        "An indication that volume status REBUILT ."
    ::= { notifyEvts 17 }

    notifyHDFull        NOTIFICATION-TYPE
    STATUS      current
    DESCRIPTION
        "An indication that HD Full ."
    ::= { notifyEvts 18 }

    notifyVolumeSpace        NOTIFICATION-TYPE
    STATUS      current
    DESCRIPTION
        "An indication that Volume space ."
    ::= { notifyEvts 19 }

    notifySeleftest        NOTIFICATION-TYPE
    STATUS      current
    DESCRIPTION
        "An indication that Self test results ."
    ::= { notifyEvts 20 }

--              ******************************************************

--              ******************************************************

	END

--
-- DNS120005.mib
--
