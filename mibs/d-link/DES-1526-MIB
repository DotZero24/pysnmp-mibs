------------------------------------------------------------------------------
------------------------------------------------------------------------------
--
--
------------------------------------------------------------------------------
-- Groups in the company MIB
--
-- The following groups are supported for company
--
-- Active....
--    companyCommGroup     Permits the user to configure the communities
--    companyHostGroup     Permits the user to configure the hosts
--    companyMiscGroup     Permits the user to configure miscellaneous items
--    companySpanGroup     Permits the user to configure Spanning Tree
--
--
------------------------------------------------------------------------------
------------------------------------------------------------------------------
        DES-1526-MIB DEFINITIONS ::= BEGIN

        IMPORTS
            OBJECT-TYPE                          FROM RFC-1212
            enterprises,
            Counter, TimeTicks, IpAddress        FROM RFC1155-SMI
                mib-2,
            DisplayString, PhysAddress           FROM RFC1213-MIB;


        d-link						OBJECT IDENTIFIER ::= { enterprises 171 }
        dlink-products				OBJECT IDENTIFIER ::= { d-link 10 }
        dlink-DES1526SeriesProd		OBJECT IDENTIFIER ::= { dlink-products 60}
        DES-1526					OBJECT IDENTIFIER ::= { dlink-DES1526SeriesProd 1 }

        -- textual conventions

        OwnerString ::= DisplayString
        MacAddress ::= OCTET STRING (SIZE (6))
        PortList ::= TEXTUAL-CONVENTION
            STATUS      current
            DESCRIPTION
                "Each octet within this value specifies a set of eight
                ports, with the first octet specifying ports 1 through
                8, the second octet specifying ports 9 through 16, etc.
                Within each octet, the most significant bit represents
                the lowest numbered port, and the least significant bit
                represents the highest numbered port.  Thus, each port
                of the bridge is represented by a single bit within the
                value of this object.  If that bit has a value of '1'
                then that port is included in the set of ports; the port
                is not included if its bit has a value of '0'."
            SYNTAX      OCTET STRING (SIZE (6))
		RowStatus ::= TEXTUAL-CONVENTION
    	    STATUS       current
    	    DESCRIPTION  ""

    	    SYNTAX       INTEGER {
                         active(1),
                         notInService(2),
                         notReady(3),
                         createAndGo(4),
                         createAndWait(5),
                         destroy(6)
                         }


        -- This data type is used to model an administratively
        -- assigned name of the owner of a resource. This
        -- information is taken from the NVT ASCII character set.
        -- It is suggested that this name contain one or more
        -- of the following:
        -- IP address, management station name, network manager's
        -- name, location, or phone number.
        -- In some cases the agent itself will be the owner of
        -- an entry.  In these cases, this string shall be set
        -- to a string starting with 'monitor'.
        --
        -- SNMP access control is articulated entirely in terms of
        -- the contents of MIB views; access to a particular SNMP
        -- object instance depends only upon its presence or
        -- absence in a particular MIB view and never upon its
        -- value or the value of related object instances. Thus,
        -- objects of this type afford resolution of resource
        -- contention only among cooperating managers; they
        -- realize no access control function with respect
        -- to uncooperative parties.
        --
        -- By convention, objects with this syntax are declared
        -- as having
        --
        --      SIZE (0..127)


        --
        -- company Enterprise MIB Extensions
        --
        companyCommGroup        OBJECT IDENTIFIER ::= { DES-1526 1 }
--        companyHostGroup        OBJECT IDENTIFIER ::= { DES-1526 2 }
        companyMiscGroup        OBJECT IDENTIFIER ::= { DES-1526 3 }
--        companySpanGroup        OBJECT IDENTIFIER ::= { DES-1526 4 }
        --
        companyConfigGroup      OBJECT IDENTIFIER ::= { DES-1526 11 }
--        companyPVlanGroup       OBJECT IDENTIFIER ::= { DES-1526 12 }
        companyTVlanGroup       OBJECT IDENTIFIER ::= { DES-1526 13 }
        companyPortTrunkGroup   OBJECT IDENTIFIER ::= { DES-1526 14 }


        --
        -- company Extension MIB, Set Community Information
        --
        commSetTable OBJECT-TYPE
            SYNTAX SEQUENCE OF CommSetEntry
            ACCESS not-accessible
            STATUS mandatory
            DESCRIPTION
                "A list of SNMP Set Community Entries "
            ::= { companyCommGroup 1 }

        commSetEntry OBJECT-TYPE
            SYNTAX CommSetEntry
            ACCESS not-accessible
            STATUS mandatory
            DESCRIPTION
                "A list of SNMP Set Community properties"
            INDEX { commSetIndex }
            ::= { commSetTable 1 }

        CommSetEntry ::= SEQUENCE {
            commSetIndex                 INTEGER,
            commSetName                  DisplayString,
            commSetStatus                RowStatus
        }

        commSetIndex OBJECT-TYPE
            SYNTAX INTEGER (1..2)
            ACCESS read-only
            STATUS mandatory
            DESCRIPTION
                "An index that uniquely identifies an entry in the
                 Community Table. Eight entries are currently supported."
            ::= { commSetEntry 1 }

        commSetName OBJECT-TYPE
            SYNTAX DisplayString (SIZE (0..20))
            ACCESS read-write
            STATUS mandatory
            DESCRIPTION
                "The name of this SNMP Set Community Entry."
            ::= { commSetEntry 2 }

        commSetStatus OBJECT-TYPE
            SYNTAX RowStatus
            ACCESS read-write
            STATUS mandatory
            DESCRIPTION
                "The RowStatus for the Set Community entry."
            ::= { commSetEntry 3 }

        --
        -- company Extension MIB, Get Community Information
        --
        commGetTable OBJECT-TYPE
            SYNTAX SEQUENCE OF CommGetEntry
            ACCESS not-accessible
            STATUS mandatory
            DESCRIPTION
                "A list of SNMP Get Community Entries "
            ::= { companyCommGroup 2 }

        commGetEntry OBJECT-TYPE
            SYNTAX CommGetEntry
            ACCESS not-accessible
            STATUS mandatory
            DESCRIPTION
                "A list of SNMP Get Community properties"
            INDEX { commGetIndex }
            ::= { commGetTable 1 }

        CommGetEntry ::= SEQUENCE {
            commGetIndex                 INTEGER,
            commGetName                  DisplayString,
            commGetStatus                RowStatus
        }

        commGetIndex OBJECT-TYPE
            SYNTAX INTEGER (1..2)
            ACCESS read-only
            STATUS mandatory
            DESCRIPTION
                "An index that uniquely identifies an entry in the
                 Community Table. Eight entries are currently supported."
            ::= { commGetEntry 1 }

        commGetName OBJECT-TYPE
            SYNTAX DisplayString (SIZE (0..20))
            ACCESS read-write
            STATUS mandatory
            DESCRIPTION
                "The name of this SNMP Get Community Entry."
            ::= { commGetEntry 2 }

        commGetStatus OBJECT-TYPE
            SYNTAX RowStatus
            ACCESS read-write
            STATUS mandatory
            DESCRIPTION
                "The RowStatus for the Get Community entry."
            ::= { commGetEntry 3 }

        --
        -- company Extension MIB, Trap Community Information
        --
        commTrapTable OBJECT-TYPE
            SYNTAX SEQUENCE OF CommTrapEntry
            ACCESS not-accessible
            STATUS mandatory
            DESCRIPTION
                "A list of SNMP Trap Community Entries "
            ::= { companyCommGroup 3 }

        commTrapEntry OBJECT-TYPE
            SYNTAX CommTrapEntry
            ACCESS not-accessible
            STATUS mandatory
            DESCRIPTION
                "A list of SNMP Trap Community properties"
            INDEX { commTrapIndex }
            ::= { commTrapTable 1 }

        CommTrapEntry ::= SEQUENCE {
            commTrapIndex                    INTEGER,
            commTrapName                     DisplayString,
            commTrapIpAddress                IpAddress,
            commTrapVlanId                   INTEGER,
            commTrapSNMPBootup               INTEGER,
            commTrapSNMPTPLinkUpDown         INTEGER,
            commTrapSNMPFiberLinkUpDown      INTEGER,
--            commTrapTrapInsertRemove         INTEGER,
            commTrapTrapAbnormalTPRXError    INTEGER,
            commTrapTrapAbnormalTPTXError    INTEGER,
            commTrapTrapAbnormalFiberRXError INTEGER,
            commTrapTrapAbnormalFiberTXError INTEGER,
            commTrapTrapPOEPowerFail		 INTEGER,
            commTrapTrapPOEPortOvercurrent	 INTEGER,
            commTrapTrapPOEPortShort		 INTEGER,
            commTrapStatus                   RowStatus
        }

        commTrapIndex OBJECT-TYPE
            SYNTAX INTEGER (1..2)
            ACCESS read-only
            STATUS mandatory
            DESCRIPTION
                "An index that uniquely identifies an entry in the
                 Community Table. Eight entries are currently supported."
            ::= { commTrapEntry 1 }

        commTrapName OBJECT-TYPE
            SYNTAX DisplayString (SIZE (0..20))
            ACCESS read-write
            STATUS mandatory
            DESCRIPTION
                "The name of this SNMP Trap Community Entry."
            ::= { commTrapEntry 2 }

        commTrapIpAddress OBJECT-TYPE
            SYNTAX IpAddress
            ACCESS read-write
            STATUS mandatory
            DESCRIPTION
                "The IP Address of this SNMP Trap Community Entry."
            ::= { commTrapEntry 3 }

        commTrapVlanId OBJECT-TYPE
            SYNTAX INTEGER
            ACCESS read-write
            STATUS mandatory
            DESCRIPTION
                "The Trap VLAN identifier of this SNMP Trap Community Entry.
                 The value must be from 1 to 4094."
            ::= { commTrapEntry 4 }

        commTrapSNMPBootup  OBJECT-TYPE
            SYNTAX INTEGER  {
        		 enabled(1),
        		 disabled(2)
            }
            ACCESS read-write
            STATUS mandatory
            DESCRIPTION
                "Bootup trap"
            ::= { commTrapEntry 5 }

        commTrapSNMPTPLinkUpDown  OBJECT-TYPE
            SYNTAX INTEGER  {
        		 enabled(1),
        		 disabled(2)
            }
            ACCESS read-write
            STATUS mandatory
            DESCRIPTION
                "Twisted Pair link up / link down trap"
            ::= { commTrapEntry 6 }

        commTrapSNMPFiberLinkUpDown  OBJECT-TYPE
            SYNTAX INTEGER  {
        		 enabled(1),
        		 disabled(2)
            }
            ACCESS read-write
            STATUS mandatory
            DESCRIPTION
                "Fiber link up / link down trap"
            ::= { commTrapEntry 7 }

--        commTrapTrapInsertRemove  OBJECT-TYPE
--            SYNTAX INTEGER  {
--        		 enabled(1),
--        		 disabled(2)
--            }
--            ACCESS read-write
--            STATUS mandatory
--            DESCRIPTION
--                "Fiber Inserted / removed trap"
--            ::= { commTrapEntry 8 }

        commTrapTrapAbnormalTPRXError  OBJECT-TYPE
            SYNTAX INTEGER  {
        		 enabled(1),
        		 disabled(2)
            }
            ACCESS read-write
            STATUS mandatory
            DESCRIPTION
                "Twisted Pair abnormal receive error trap"
            ::= { commTrapEntry 9 }

        commTrapTrapAbnormalTPTXError  OBJECT-TYPE
            SYNTAX INTEGER  {
        		 enabled(1),
        		 disabled(2)
            }
            ACCESS read-write
            STATUS mandatory
            DESCRIPTION
                "Twisted Pair abnormal transmit error trap"
            ::= { commTrapEntry 10 }

        commTrapTrapAbnormalFiberRXError  OBJECT-TYPE
            SYNTAX INTEGER  {
        		 enabled(1),
        		 disabled(2)
            }
            ACCESS read-write
            STATUS mandatory
            DESCRIPTION
                "Fiber abnormal receive error trap"
            ::= { commTrapEntry 11 }

        commTrapTrapAbnormalFiberTXError  OBJECT-TYPE
            SYNTAX INTEGER  {
        		 enabled(1),
        		 disabled(2)
            }
            ACCESS read-write
            STATUS mandatory
            DESCRIPTION
                "Fiber abnormal transmit error trap"
            ::= { commTrapEntry 12 }
--poe private trap
        commTrapTrapPOEPowerFail  OBJECT-TYPE
            SYNTAX INTEGER  {
        		 enabled(1),
        		 disabled(2)
            }
            ACCESS read-write
            STATUS mandatory
            DESCRIPTION
                "PoE POWER Fail"
            ::= { commTrapEntry 13 }

        commTrapTrapPOEPortOvercurrent  OBJECT-TYPE
            SYNTAX INTEGER  {
        		 enabled(1),
        		 disabled(2)
            }
            ACCESS read-write
            STATUS mandatory
            DESCRIPTION
                "PoE port Overcurrent"
            ::= { commTrapEntry 14 }

        commTrapTrapPOEPortShort  OBJECT-TYPE
            SYNTAX INTEGER  {
        		 enabled(1),
        		 disabled(2)
            }
            ACCESS read-write
            STATUS mandatory
            DESCRIPTION
                "PoE port Shortcircuit"
            ::= { commTrapEntry 15 }

        commTrapStatus OBJECT-TYPE
            SYNTAX RowStatus
            ACCESS read-write
            STATUS mandatory
            DESCRIPTION
                "The RowStatus for the Trap Community entry."
            ::= { commTrapEntry 16 }

--        commTable OBJECT-TYPE
--            SYNTAX SEQUENCE OF CommEntry
--            ACCESS not-accessible
--            STATUS mandatory
--            DESCRIPTION
--                "A list of SNMP Community Entries "
--            ::= { companyCommGroup 1 }
--
--        commEntry OBJECT-TYPE
--            SYNTAX CommEntry
--            ACCESS not-accessible
--            STATUS mandatory
--            DESCRIPTION
--                "A list of SNMP Community properties"
--            INDEX { commIndex }
--            ::= { commTable 1 }
--
--        CommEntry ::= SEQUENCE {
--            commIndex                 INTEGER,
--            commName                  DisplayString,
--            commGet                   INTEGER,
--            commSet                   INTEGER,
--            commTrap                  INTEGER,
--            commStatus                INTEGER
--        }
--
--        commIndex OBJECT-TYPE
--            SYNTAX INTEGER (1..2)
--            ACCESS read-only
--            STATUS mandatory
--            DESCRIPTION
--                "An index that uniquely identifies an entry in the
--                 Community Table. Eight entries are currently supported."
--            ::= { commEntry 1 }
--
--        commName OBJECT-TYPE
--            SYNTAX DisplayString (SIZE (0..20))
--            ACCESS read-write
--            STATUS mandatory
--            DESCRIPTION
--                "The name of this SNMP Community Entry."
--            ::= { commEntry 2 }
--
--        commGet OBJECT-TYPE
--            SYNTAX INTEGER {
--                   enabled(1),
--                   disabled(2)
--            }
--            ACCESS read-write
--            STATUS mandatory
--            DESCRIPTION
--                "The GET permission for the community. A (1) indicates a
--                 GET enable.  A (2) indicates a GET disable."
--            ::= { commEntry 3 }
--
--        commSet OBJECT-TYPE
--            SYNTAX INTEGER {
--                   enabled(1),
--                   disabled(2)
--            }
--            ACCESS read-write
--            STATUS mandatory
--            DESCRIPTION
--                "The SET permission for the community. A (1) indicates a
--                 SET enable. A (2) indicates a SET disable."
--            ::= { commEntry 4 }
--
--        commTrap OBJECT-TYPE
--            SYNTAX INTEGER {
--                   enabled(1),
--                   disabled(2)
--            }
--            ACCESS read-write
--            STATUS mandatory
--            DESCRIPTION
--                "The TRAP permission for the community. A (1) indicates a
--                 TRAP enable.  A (2) indicates a TRAP disable."
--            ::= { commEntry 5 }
--
--        commStatus OBJECT-TYPE
--            SYNTAX INTEGER (1..6)
--            ACCESS read-write
--            STATUS mandatory
--            DESCRIPTION
--                "The RowStatus for the community entry."
--            ::= { commEntry 6 }


--        --
--        -- company Extension MIB, Host Information
--        --
--        hostTable OBJECT-TYPE
--            SYNTAX SEQUENCE OF HostEntry
--            ACCESS not-accessible
--            STATUS mandatory
--            DESCRIPTION
--                "A list of SNMP Trusted Host Entries "
--            ::= { companyHostGroup 1 }
--
--        hostEntry OBJECT-TYPE
--            SYNTAX HostEntry
--            ACCESS not-accessible
--            STATUS mandatory
--            DESCRIPTION
--                "A list of SNMP Host properties"
--            INDEX { hostIndex }
--            ::= { hostTable 1 }
--
--        HostEntry ::= SEQUENCE {
--            hostIndex                 INTEGER,
--            hostName                  DisplayString,
--            hostIP                    IpAddress,
--            hostComm                  DisplayString,
--            hostStatus                INTEGER
--        }
--
--        hostIndex OBJECT-TYPE
--            SYNTAX INTEGER (1..16)
--            ACCESS read-only
--            STATUS mandatory
--            DESCRIPTION
--                "An index that uniquely identifies an entry in the
--                 Host Table. Sixteen entries are currently supported."
--            ::= { hostEntry 1 }
--
--        hostName OBJECT-TYPE
--            SYNTAX DisplayString (SIZE (0..31))
--            ACCESS read-write
--            STATUS mandatory
--            DESCRIPTION
--                "The name of this Host Entry."
--            ::= { hostEntry 2 }
--
--        hostIP OBJECT-TYPE
--            SYNTAX IpAddress
--            ACCESS read-write
--            STATUS mandatory
--            DESCRIPTION
--                "The IP Address for the host."
--            ::= { hostEntry 3 }
--
--        hostComm OBJECT-TYPE
--            SYNTAX DisplayString (SIZE (0..31))
--            ACCESS read-write
--            STATUS mandatory
--            DESCRIPTION
--                "The name of the community this host belongs to."
--            ::= { hostEntry 4 }
--
--        hostStatus OBJECT-TYPE
--            SYNTAX INTEGER (1..6)
--            ACCESS read-write
--            STATUS mandatory
--            DESCRIPTION
--                "The RowStatus for the community entry."
--            ::= { hostEntry 5 }

        --
        -- company Extension MIB, Miscellaneous Information
        --

--        miscReset OBJECT-TYPE
--            SYNTAX INTEGER {
--                   reset(1),
--                   noop(2)
--            }
--            ACCESS read-write
--            STATUS mandatory
--            DESCRIPTION
--                "Physically resets the unit - use with care. A (1) resets
--                 the unit, a (2) does nothing."
--            ::= { companyMiscGroup 2 }

        miscStatisticsReset OBJECT-TYPE
            SYNTAX INTEGER {
                   reset(1),
                   noop(2)
            }
            ACCESS read-write
            STATUS mandatory
            DESCRIPTION
                "Resets the units statistics. A (1) resets
                 the unit, a (2) does nothing."
            ::= { companyMiscGroup 3 }

        --
        -- company Extension MIB, Spanning Tree Configuration
        --
--       spanOnOff OBJECT-TYPE
--            SYNTAX INTEGER {
--                   enabled(1),
--                   disabled(2)
--            }
--            ACCESS read-write
--            STATUS mandatory
--            DESCRIPTION
--                "Enable/Disable Spanning Tree. A (1) enables, a (2) disables."
--            ::= { companySpanGroup 1 }


        -- ---------------------------------------------------------------------
        -- Products Extension
        -- ---------------------------------------------------------------------
        configVerSwPrimary OBJECT-TYPE
            SYNTAX DisplayString (SIZE(0..31))
            ACCESS read-only
            STATUS mandatory
            DESCRIPTION
                "The software image version string"
            ::= { companyConfigGroup 1 }

        configVerHwChipSet OBJECT-TYPE
            SYNTAX DisplayString (SIZE(0..31))
            ACCESS read-only
            STATUS mandatory
            DESCRIPTION
                "The hardware chipset version string"
            ::= { companyConfigGroup 2 }

--        configBootMode OBJECT-TYPE
--            SYNTAX INTEGER {
--                   lastSaved(1),
--                   net(2),
--		   netAndSave(3)
--            }
--            ACCESS read-write
--            STATUS mandatory
--            DESCRIPTION
--                "Defines the method used for downloading the image when reset."
--            ::= { companyConfigGroup 3 }
--
--        configBootFtpServerIp OBJECT-TYPE
--            SYNTAX IpAddress
--            ACCESS read-write
--            STATUS mandatory
--            DESCRIPTION
--                "The FTP server's IP address used for downloading the
--		 boot image"
--            ::= { companyConfigGroup 4 }
--
--        configBootImageFileName OBJECT-TYPE
--            SYNTAX DisplayString (SIZE(0..63))
--            ACCESS read-write
--            STATUS mandatory
--            DESCRIPTION
--                "The path and filename of the boot image to download"
--            ::= { companyConfigGroup 5 }

        configPortTable OBJECT-TYPE
            SYNTAX SEQUENCE OF ConfigPortEntry
            ACCESS not-accessible
            STATUS mandatory
            DESCRIPTION
                "A list of interface entries used for enterprise specific
                 configuration.  The number of entries is given by the value
                 of ifNumber.  All interface entries are assumed to be
                 Ethernet interafaces."
            ::= { companyConfigGroup 6 }

        configPortEntry OBJECT-TYPE
            SYNTAX ConfigPortEntry
            ACCESS not-accessible
            STATUS mandatory
            DESCRIPTION
                "An enterprise specific interface entry."
            INDEX { configPort }
            ::= { configPortTable 1 }

--           ConfigPortEntry ::= SEQUENCE {
--               configPort                 INTEGER,
--               configPortDuplex           INTEGER,
--               configPortDataRate         INTEGER,
--               configPortDuplexOper       INTEGER,
--               configPortDataRateOper     INTEGER,
--               configPortStateOper        INTEGER,
--               configPortFlowControl      INTEGER,
--               configPortDefaultVlanId    INTEGER,
--               configPortComments         DisplayString,
--               configPortAutoNegotiation  INTEGER,
--               configPortFlowControlOper  INTEGER,
--	        configPortGBIC	           INTEGER,
--	        configPortFastLink	       INTEGER,
--	        configPortPriority         INTEGER,
--	        configPortBroadcastControl INTEGER
--           }

        ConfigPortEntry ::= SEQUENCE {
            configPort                 INTEGER,
            configPortSpeed            INTEGER,
            configPortOperStatus       INTEGER,
            configPortFlowControl      INTEGER,
            configPortFlowControlOper  INTEGER,
	        configPortPriority         INTEGER
        }

        configPort OBJECT-TYPE
            SYNTAX INTEGER
            ACCESS read-only
            STATUS mandatory
            DESCRIPTION
                "A unique value for each interface that correlates to ifIndex.
                 Its value ranges between 1 and the value of ifNumber."
            ::= { configPortEntry 1 }

        configPortSpeed OBJECT-TYPE
            SYNTAX INTEGER {
                   disable(1),
                   auto(2),
                   rate10M-Half(3),
                   rate10M-Full(4),
                   rate100M-Half(5),
                   rate100M-Full(6)
            }
            ACCESS read-write
            STATUS mandatory
            DESCRIPTION
                "The port's speed desired state."
            ::= { configPortEntry 2 }

        configPortOperStatus OBJECT-TYPE
            SYNTAX INTEGER {
                   down(1),
                   rate10M-Half(2),
                   rate10M-Full(3),
                   rate100M-Half(4),
                   rate100M-Full(5),
                   rate1G-Half(6),
                   rate1G-Full(7)
            }
            ACCESS read-only
            STATUS mandatory
            DESCRIPTION
                "The port's operating speed state."
            ::= { configPortEntry 3 }

        configPortFlowControl OBJECT-TYPE
            SYNTAX INTEGER {
                   enabled(1),
                   disabled(2)
            }
            ACCESS read-write
            STATUS mandatory
            DESCRIPTION
                "The port will avoid transmitting a new packet
                 for the period of time specified in a received
                 PAUSE packet when enabled."
            ::= { configPortEntry 4 }

        configPortFlowControlOper OBJECT-TYPE
            SYNTAX INTEGER {
                   enabled(1),
                   disabled(2)
            }
            ACCESS read-only
            STATUS mandatory
            DESCRIPTION
                "The port's operating flow control state."
            ::= { configPortEntry 5 }

        configPortPriority OBJECT-TYPE
            SYNTAX INTEGER {
                   normal(1),
                   high(2)
            }
            ACCESS read-write
            STATUS mandatory
            DESCRIPTION
                "The port's current priority."
            ::= { configPortEntry 6 }

        --
        -- VLAN Mode
        --
--        configVLANMode OBJECT-TYPE
--            SYNTAX INTEGER {
--                   modePortBased(1),
--                   modeTagBased(2)
--            }
--            ACCESS read-write
--            STATUS mandatory
--            DESCRIPTION
--                "Determines the VLAN mode."
--           ::= { companyConfigGroup 7 }

	    --
        -- Additional Configuration objects
        --

        -- ---------------------------------------------------------------------
        -- Mirror
        -- ---------------------------------------------------------------------
        configMirrorTable OBJECT-TYPE
            SYNTAX SEQUENCE OF ConfigMirrorEntry
            ACCESS not-accessible
            STATUS mandatory
            DESCRIPTION
                "A list of the Mirror"
            ::= { companyConfigGroup 8 }

        configMirrorEntry OBJECT-TYPE
            SYNTAX ConfigMirrorEntry
            ACCESS not-accessible
            STATUS mandatory
            DESCRIPTION
                "A Mirror entry containing the Mirror id and mode"
            INDEX { configMirrorId }
            ::= { configMirrorTable 1 }

        ConfigMirrorEntry ::= SEQUENCE {
            configMirrorId             INTEGER,
            configMirrorMode           INTEGER,
            configMirrorMon            INTEGER,
            configMirrorSrc            PortList,
            configMirrorStatus         RowStatus
        }

        configMirrorId OBJECT-TYPE
            SYNTAX INTEGER (1)
            ACCESS read-only
            STATUS mandatory
            DESCRIPTION
                "An index that uniquely identifies an entry in the
                 Mirror Table. One entries are currently supported."
            ::= { configMirrorEntry 1 }

        configMirrorMode OBJECT-TYPE
            SYNTAX INTEGER {
                   disabled(0),
                   Rx(1),
                   Tx(2),
                   both(3)
            }
            ACCESS read-write
            STATUS mandatory
            DESCRIPTION
                "When deciding the mirroring source port, then Mirror mode will
                 be available."
            ::= { configMirrorEntry 2 }

        configMirrorMon OBJECT-TYPE
            SYNTAX INTEGER
            ACCESS read-write
            STATUS mandatory
            DESCRIPTION
                "When mirroring is enabled (configMirroringMode =
                 ingress, egress, both), this identifies the mirroring monitoring
                 port.  This value has a valid range of 1 to ifNumber when
                 enabled."
            ::= { configMirrorEntry 3 }

        configMirrorSrc OBJECT-TYPE
            SYNTAX PortList
            ACCESS read-write
            STATUS mandatory
            DESCRIPTION
                "When mirroring is enabled (configMirroringMode =
                 ingress, egress, both), this identifies the mirroring source port.
                 This value has a valid range of 1 to ifNumber when enbaled.
                 Each octet within this value specifies a set of eight
                 ports, with the first octet specifying ports 1 through
                 8, the second octet specifying ports 9 through 16, etc.
                 Within each octet, the most significant bit represents
                 the lowest numbered port, and the least significant bit
                 represents the highest numbered port.  Thus, each port
                 of the bridge is represented by a single bit within the
                 value of this object.  If that bit has a value of '1'
                 then that port is included in the set of ports; the port
                 is not included if its bit has a value of '0'."
            ::= { configMirrorEntry 4 }

        configMirrorStatus OBJECT-TYPE
            SYNTAX RowStatus
            ACCESS read-write
            STATUS mandatory
            DESCRIPTION
                "The RowStatus for the Mirror entry."
            ::= { configMirrorEntry 5 }

        -- ---------------------------------------------------------------------
        -- SNMP Function
        -- ---------------------------------------------------------------------
        configSNMPEnable OBJECT-TYPE
            SYNTAX INTEGER {
                   enabled(1),
                   disabled(2)
            }
            ACCESS read-write
            STATUS mandatory
            DESCRIPTION
                "Enable/Disable SNMP function. A (1) enables, a (2) disables."
            ::= { companyConfigGroup 9 }

        -- ---------------------------------------------------------------------
        --
        -- ---------------------------------------------------------------------
        configIpAssignmentMode OBJECT-TYPE
            SYNTAX INTEGER {
                   manual(1),
                   dhcp(2),
                   other(3)
            }
            ACCESS read-write
            STATUS mandatory
            DESCRIPTION
                "Indicates whether the device address is assigned by
		         the user (manual), or DHCP, or Others(BootP)."
            ::= { companyConfigGroup 12 }

        configPhysAddress OBJECT-TYPE
            SYNTAX MacAddress
            ACCESS read-only
            STATUS mandatory
            DESCRIPTION
                "The interface's address at the protocol layer
                 immediately 'below' the network layer in the
                 protocol stack.  This is the physical address
                 for the end-station."
            ::= { companyConfigGroup 13 }

        configPasswordAdmin OBJECT-TYPE
            SYNTAX DisplayString (SIZE(0..20))
            ACCESS write-only
            STATUS mandatory
            DESCRIPTION
                "The adminstrator password"
            ::= { companyConfigGroup 15 }

        configIpAddress OBJECT-TYPE
            SYNTAX IpAddress
            ACCESS read-write
            STATUS mandatory
            DESCRIPTION
                "The IP Address for the RDU box."
            ::= { companyConfigGroup 16 }

        configNetMask OBJECT-TYPE
            SYNTAX IpAddress
            ACCESS read-write
            STATUS mandatory
            DESCRIPTION
                "The network mask for the RDU box."
            ::= { companyConfigGroup 17 }

        configGateway OBJECT-TYPE
            SYNTAX IpAddress
            ACCESS read-write
            STATUS mandatory
            DESCRIPTION
                "The Gatway Address for the unit."
            ::= { companyConfigGroup 18 }

        configSave OBJECT-TYPE
            SYNTAX INTEGER {
                   save(1),
                   noop(2)
            }
            ACCESS read-write
            STATUS mandatory
            DESCRIPTION
                "Physically saves the current configuration to nvram.
                 - use with care.
                    (1) saves the configuration
                    (2) does nothing."
            ::= { companyConfigGroup 19 }

--        configVerBootRomImage OBJECT-TYPE
--            SYNTAX DisplayString (SIZE(0..31))
--            ACCESS read-only
--            STATUS mandatory
--            DESCRIPTION
--                "The Boot ROM version string"
--            ::= { companyConfigGroup 21 }

        configRestoreDefaults OBJECT-TYPE
            SYNTAX INTEGER {
                   restore(1),
                   noop(2)
            }
            ACCESS read-write
            STATUS mandatory
            DESCRIPTION
                "Restores the configuration of the unit to the
                 original settings."
            ::= { companyConfigGroup 22 }

--        configIGMPOnOff OBJECT-TYPE
--            SYNTAX INTEGER {
--                   enabled(1),
--                   disabled(2)
--            }
--            ACCESS read-write
--            STATUS mandatory
--            DESCRIPTION
--                "Enable or disable the IGMP protocol within the switch."
--            ::= { companyConfigGroup 23 }
--
--	    configWebOnOff OBJECT-TYPE
--                SYNTAX INTEGER {
--                       enabled(1),
--                       disabled(2)
--                }
--                ACCESS read-write
--                STATUS mandatory
--                DESCRIPTION
--                    "Enable or disable the Web Interface."
--                ::= { companyConfigGroup 24 }
--
--	    configHighPriorityOptimization OBJECT-TYPE
--                SYNTAX INTEGER {
--                       enabled(1),
--                       disabled(2)
--                }
--                ACCESS read-write
--                STATUS mandatory
--                DESCRIPTION
--                    "Enable or disable high priority optimization."
--                ::= { companyConfigGroup 25 }
--
--        configUserAuthenticationMode OBJECT-TYPE
--            SYNTAX INTEGER {
--                   basicPasswordOnly(1),
--                   basicPasswordThenRemoteRADIUS(2),
--                   remoteRADIUSOnly(4)
--            }
--            ACCESS read-write
--            STATUS mandatory
--            DESCRIPTION
--                "Determines whether the user password will be authenticated
--		           by the switch, a remote RADIUS server, or some combination
--		           of the two."
--            ::= { companyConfigGroup 27 }
--
--        configRadiusServerIpAddress OBJECT-TYPE
--            SYNTAX IpAddress
--            ACCESS read-write
--            STATUS mandatory
--            DESCRIPTION
--                "The IP Address of the RADIUS server used for remote
--		 user authentication."
--            ::= { companyConfigGroup 28 }
--
--        configRadiusSharedSecret OBJECT-TYPE
--            SYNTAX DisplayString (SIZE(0..32))
--            ACCESS read-write
--            STATUS mandatory
--            DESCRIPTION
--                "A string of characters used in the RADIUS password
--		 encryption process."
--            ::= { companyConfigGroup 29 }
--
--        configTelnetConsole OBJECT-TYPE
--            SYNTAX INTEGER {
--                   enabled(1),
--                   disabled(2)
--            }
--            ACCESS read-write
--            STATUS mandatory
--            DESCRIPTION
--                "Enable or disable the telnet console."
--            ::= { companyConfigGroup 30 }

        -- ---------------------------------------------------------------------
        -- DiffServ
        -- ---------------------------------------------------------------------
--        configDiffServTable OBJECT-TYPE
--            SYNTAX SEQUENCE OF ConfigDiffServEntry
--            ACCESS not-accessible
--            STATUS mandatory
--            DESCRIPTION
--                "A list of DSCP Priorities."
--            ::= { companyConfigGroup 31 }
--
--        configDiffServEntry OBJECT-TYPE
--            SYNTAX ConfigDiffServEntry
--            ACCESS not-accessible
--            STATUS mandatory
--            DESCRIPTION
--                "An enterprise specific DSCP entry."
--            INDEX { configDiffServDSCP }
--            ::= { configDiffServTable 1 }
--
--        ConfigDiffServEntry ::= SEQUENCE {
--            configDiffServDSCP             INTEGER,
--	          configDiffServPriority         INTEGER
--        }
--
--        configDiffServDSCP OBJECT-TYPE
--            SYNTAX INTEGER
--            ACCESS read-only
--            STATUS mandatory
--            DESCRIPTION
--                "A DSCP value (0 - 63)."
--            ::= { configDiffServEntry 1 }
--
--        configDiffServPriority OBJECT-TYPE
--            SYNTAX INTEGER {
--                   normal(1),
--                   high(2)
--            }
--            ACCESS read-write
--            STATUS mandatory
--            DESCRIPTION
--                "The DSCP's current priority setting."
--            ::= { configDiffServEntry 2 }

--        configTftpServerIpAddress OBJECT-TYPE
--            SYNTAX IpAddress
--            ACCESS read-write
--            STATUS mandatory
--            DESCRIPTION
--                "The IP Address of the tftp server used to upload and
--		 download configuration files. This object is to be used
--		 in conjunction with configTftpServerFileName and
--		 configTftpOperation."
--            ::= { companyConfigGroup 32 }
--
--        configTftpServerFileName OBJECT-TYPE
--            SYNTAX DisplayString (SIZE(0..64))
--            ACCESS read-write
--            STATUS mandatory
--            DESCRIPTION
--                "The filename, including the path, used to store or
--		 retrieve a configuration file from the tftp server.
--		 This object is to be used in conjunction with
--		 configTftpServerIpAddress and configTftpOperation."
--            ::= { companyConfigGroup 33 }
--
--        configTftpOperation OBJECT-TYPE
--            SYNTAX INTEGER {
--                   download(1),
--                   upload(2)
--            }
--            ACCESS read-write
--            STATUS mandatory
--            DESCRIPTION
--                "The tftp operation to perform. Either download a
--		 configuration to the unit or upload the current
--		 configuration to the tftp server. This object is
--		 to be used in conjunction with
--		 configTftpServerIpAddress and configTftpServerFileName."
--            ::= { companyConfigGroup 34 }

        -- ---------------------------------------------------------------------
        --
        -- ---------------------------------------------------------------------
--        configIpFilter OBJECT-TYPE
--            SYNTAX INTEGER {
--                   enabled(1),
--                   disabled(2)
--            }
--            ACCESS read-write
--            STATUS mandatory
--            DESCRIPTION
--                "Determines if access to the device is limited to only
--		         those IP addresses specified in the configIpFilterTable."
--            ::= { companyConfigGroup 35 }
--
--        configIpFilterTable OBJECT-TYPE
--            SYNTAX SEQUENCE OF ConfigIpFilterEntry
--            ACCESS not-accessible
--            STATUS mandatory
--            DESCRIPTION
--                "A list of IP addresses allowed access to this device."
--            ::= { companyConfigGroup 36 }
--
--        configIpFilterEntry OBJECT-TYPE
--            SYNTAX ConfigIpFilterEntry
--            ACCESS not-accessible
--            STATUS mandatory
--            DESCRIPTION
--                "An enterprise specific IP filter entry."
--            INDEX { configIpFilterIpAddress }
--            ::= { configIpFilterTable 1 }
--
--        ConfigIpFilterEntry ::= SEQUENCE {
--            configIpFilterIpAddress       IpAddress,
--	        configIpFilterStatus          INTEGER
--        }
--
--        configIpFilterIpAddress OBJECT-TYPE
--            SYNTAX IpAddress
--            ACCESS read-only
--            STATUS mandatory
--            DESCRIPTION
--                "An IP address which is allowed access to this device."
--            ::= { configIpFilterEntry 1 }
--
--        configIpFilterStatus OBJECT-TYPE
--            SYNTAX INTEGER {
--                    active (1),
--                    destroy (6)
--            }
--            ACCESS read-write
--            STATUS mandatory
--            DESCRIPTION
--                "The status of an entry in the IP filter Table.  Only
--		 a subset of the rowstatus variables (active, destroy)
--                 are available."
--            ::= { configIpFilterEntry 2 }
--
--         configUserName OBJECT-TYPE
--             SYNTAX DisplayString (SIZE(0..20))
--             ACCESS read-write
--             STATUS mandatory
--             DESCRIPTION
--                 "The users login Id."
--             ::= { companyConfigGroup 37 }
--
--        configPasswordProtection OBJECT-TYPE
--            SYNTAX INTEGER {
--                   enabled(1),
--                   disabled(2)
--            }
--            ACCESS read-write
--            STATUS mandatory
--            DESCRIPTION
--                "Determines if a user must login before gaining access
--		 to the device."
--            ::= { companyConfigGroup 38 }
--
--        configPasswordEncryption OBJECT-TYPE
--            SYNTAX INTEGER {
--                   clearText(1),
--                   encrypted(2)
--            }
--            ACCESS read-write
--            STATUS mandatory
--            DESCRIPTION
--                "Determines when the password is written to the
--		           configuration file whether it is written as clear
--		           text or encrypted format."
--            ::= { companyConfigGroup 39 }
--
--        configAuthServerIpAddress OBJECT-TYPE
--            SYNTAX IpAddress
--            ACCESS read-write
--            STATUS mandatory
--            DESCRIPTION
--                "The IP Address of the server used for 802.1x
--		           authentication."
--            ::= { companyConfigGroup 40 }
--
--        configAuthServerSharedSecret OBJECT-TYPE
--            SYNTAX DisplayString (SIZE(0..32))
--            ACCESS read-write
--            STATUS mandatory
--            DESCRIPTION
--                "A string of characters used in the RADIUS password
--		           encryption process by 802.1x authentication."
--            ::= { companyConfigGroup 41 }

        --
        -- The PVLAN group
        --

--        pvlanTable OBJECT-TYPE
--            SYNTAX SEQUENCE OF PvlanEntry
--            ACCESS not-accessible
--            STATUS mandatory
--            DESCRIPTION
--                "A list of the Port-based VLANs"
--            ::= { companyPVlanGroup 1 }
--
--        pvlanEntry OBJECT-TYPE
--            SYNTAX PvlanEntry
--            ACCESS not-accessible
--            STATUS mandatory
--            DESCRIPTION
--                "A Port-based VLAN entry containing the id and name."
--            INDEX { pvlanId }
--            ::= { pvlanTable 1 }
--
--        PvlanEntry ::= SEQUENCE {
--            pvlanId              INTEGER,
--            pvlanName            DisplayString,
--            pvlanMember          PortList,
--            pvlanStatus          INTEGER
--        }
--
--        pvlanId OBJECT-TYPE
--            SYNTAX INTEGER
--            ACCESS read-only
--            STATUS mandatory
--            DESCRIPTION
--                "The VLAN identifier.  A maximum of 28 VLANs is supported.
--                 The value must be from 1 to 28"
--            ::= { pvlanEntry 1 }
--
--        pvlanName OBJECT-TYPE
--           SYNTAX DisplayString (SIZE(0..8))
--           ACCESS read-write
--           STATUS mandatory
--           DESCRIPTION
--               "The VLAN name associated with the Id."
--           ::= { pvlanEntry 2 }
--
--        pvlanMember OBJECT-TYPE
--            SYNTAX PortList
--            ACCESS read-write
--            STATUS mandatory
--            DESCRIPTION
--                "The set of the device's member ports that belong
-- 	            to the VLAN.
-- 	            Each octet within the value of this object specifies a
-- 	            set of eight ports, with the first octet specifying ports
-- 	            1 through 8, the second octet specifying ports 9
-- 	            through 16, etc.   Within each octet, the most
-- 	            significant bit represents the lowest numbered
-- 	            port, and the least significant bit represents the
-- 	            highest numbered port.  Thus, each port of the
-- 	            VLAN is represented by a single bit within the
-- 	            value of this object.  If that bit has a value of
-- 	            '1' then that port is included in the set of
-- 	            ports; the port is not included if its bit has a
-- 	            value of '0'."
--
--            ::= { pvlanEntry 3 }
--
--        pvlanStatus OBJECT-TYPE
--            SYNTAX INTEGER {
--                    active (1),
--                    createAndGo (4),
--                    destroy (6)
--            }
--            ACCESS read-write
--            STATUS mandatory
--            DESCRIPTION
--                "The status of an entry in the VLAN Table.  Only a subset
--                 of the rowstatus variables (active, createAndGo, destroy)
--                 are available."
--            ::= { pvlanEntry 5 }

        --
        -- The TVLAN group
        --

        tvlanTable OBJECT-TYPE
            SYNTAX SEQUENCE OF TvlanEntry
            ACCESS not-accessible
            STATUS mandatory
            DESCRIPTION
                "A list of the VLANs"
            ::= { companyTVlanGroup 1 }

        tvlanEntry OBJECT-TYPE
            SYNTAX TvlanEntry
            ACCESS not-accessible
            STATUS mandatory
            DESCRIPTION
                "A VLAN entry containing the VLAN id and name."
            INDEX { tvlanId }
            ::= { tvlanTable 1 }

        TvlanEntry ::= SEQUENCE {
            tvlanId              INTEGER,
            -- tvlanName            DisplayString,
            tvlanMember          PortList,
            tvlanUntaggedPorts   PortList,
            tvlanStatus          INTEGER
        }

        tvlanId OBJECT-TYPE
            SYNTAX INTEGER
            ACCESS read-only
            STATUS mandatory
            DESCRIPTION
                "The VLAN identifier.  A maximum of 64 VLANs is supported.
                 The value must be from 1 to 4094."
            ::= { tvlanEntry 1 }

--        tvlanName OBJECT-TYPE
--            SYNTAX DisplayString (SIZE(0..8))
--            ACCESS read-write
--            STATUS mandatory
--            DESCRIPTION
--                "The VLAN name associated with the VLAN Id."
--            ::= { tvlanEntry 2 }

        tvlanMember OBJECT-TYPE
            SYNTAX PortList
            ACCESS read-write
            STATUS mandatory
            DESCRIPTION
                "The set of the device's member ports that belong
 	            to the VLAN.

 	            Each octet within the value of this object specifies a
 	            set of eight ports, with the first octet specifying ports
 	            1 through 8, the second octet specifying ports 9
 	            through 16, etc.   Within each octet, the most
 	            significant bit represents the lowest numbered
 	            port, and the least significant bit represents the
 	            highest numbered port.  Thus, each port of the
 	            VLAN is represented by a single bit within the
 	            value of this object.  If that bit has a value of
 	            '1' then that port is included in the set of
 	            ports; the port is not included if its bit has a
 	            value of '0'."

            ::= { tvlanEntry 3 }

        tvlanUntaggedPorts OBJECT-TYPE
            SYNTAX PortList
            ACCESS read-write
            STATUS mandatory
            DESCRIPTION
                "If that bit has a value of '1' the outgoing frame on the egress
                 port is untagged. If that bit has a value of '0' the outgoing
                 frame on the egress port is tagged."
            ::= { tvlanEntry 4 }

        tvlanStatus OBJECT-TYPE
            SYNTAX INTEGER {
                    active (1),
                    createAndGo (4),
                    destroy (6)
            }
            ACCESS read-write
            STATUS mandatory
            DESCRIPTION
                "The status of an entry in the VLAN Table.  Only a subset
                 of the rowstatus variables (active, createAndGo, destroy)
                 are available."
            ::= { tvlanEntry 5 }


        tvlanPortTable OBJECT-TYPE
            SYNTAX SEQUENCE OF TvlanPortEntry
            ACCESS not-accessible
            STATUS mandatory
            DESCRIPTION
                "A list of ports and their associated VLAN."
            ::= { companyTVlanGroup 2 }

        tvlanPortEntry OBJECT-TYPE
            SYNTAX TvlanPortEntry
            ACCESS not-accessible
            STATUS mandatory
            DESCRIPTION
                "Information pertaining to an individual port regarding
                 to which VLAN it belongs."
--            INDEX { tvlanPortPortId, tvlanPortVlanId }
            INDEX { tvlanPortPortId }
            ::= { tvlanPortTable 1 }

        TvlanPortEntry ::= SEQUENCE {
            tvlanPortPortId       INTEGER,
            tvlanPortVlanId       INTEGER,
--            tvlanPortPriority     INTEGER
--            tvlanPortStatus       INTEGER
        }

        tvlanPortPortId OBJECT-TYPE
            SYNTAX INTEGER
            ACCESS read-only
            STATUS mandatory
            DESCRIPTION
                "A port identifier that is in the range of 1 to ifNumber."
            ::= { tvlanPortEntry 1 }

        tvlanPortVlanId OBJECT-TYPE
            SYNTAX INTEGER
            ACCESS read-write
            STATUS mandatory
            DESCRIPTION
                "The default VLAN identifier."
            ::= { tvlanPortEntry 2 }

--        tvlanPortPriority OBJECT-TYPE
--            SYNTAX INTEGER
--            ACCESS read-write
--           STATUS mandatory
--            DESCRIPTION
--                "The default priority."
--            ::= { tvlanPortEntry 3 }

--        tvlanPortTaggedMode OBJECT-TYPE
--            SYNTAX INTEGER {
--                    untagged(1),
--                    tagged(2)
--            }
--            ACCESS read-write
--            STATUS mandatory
--            DESCRIPTION
--                "The tagged mode of a VLAN port."
--            ::= { tvlanPortEntry 4 }

--        tvlanPortStatus OBJECT-TYPE
--            SYNTAX INTEGER {
--                    active (1),
--                    createAndGo (4),
--                    destroy (6)
--            }
--            ACCESS read-write
--            STATUS mandatory
--            DESCRIPTION
--                "The status of this port's association within this VLAN.  Only
--                 a subset of the rowstatus variables (active, createAndGo,
--                 destroy) are available."
--            ::= { tvlanPortEntry 5 }

        --
        -- The Port Trunking Group
        --
        portTrunkTable OBJECT-TYPE
            SYNTAX SEQUENCE OF PortTrunkEntry
            ACCESS not-accessible
            STATUS mandatory
            DESCRIPTION
                "A list of port trunks and their associated members."
            ::= { companyPortTrunkGroup 1 }

        portTrunkEntry OBJECT-TYPE
            SYNTAX PortTrunkEntry
            ACCESS not-accessible
            STATUS mandatory
            DESCRIPTION
                "A port trunk entry containing the trunk id and trunk members."
            INDEX { portTrunkId, portTrunkMember }
            ::= { portTrunkTable 1 }

        PortTrunkEntry ::= SEQUENCE {
            portTrunkId           INTEGER,
            portTrunkMember       PortList,
            portTrunkMemberValue  PortList,
            portTrunkEnable       INTEGER
        }

        portTrunkId OBJECT-TYPE
            SYNTAX INTEGER
            ACCESS read-only
            STATUS mandatory
           DESCRIPTION
                "The port trunk identifier.  The current range is from 1 to 4."
            ::= { portTrunkEntry 1 }

        portTrunkMember OBJECT-TYPE
            SYNTAX PortList
            ACCESS read-only
            STATUS mandatory
            DESCRIPTION
                "Trunk group 1 - 3 has eight members (Port 01/09/17 - 08/16/24).
                 Trunk group 4 has two members (Port 25-26).
                 Each octet within this value specifies a set of eight
                 ports, with the first octet specifying ports 1 through
                 8, the second octet specifying ports 9 through 16, etc.
                 Within each octet, the most significant bit represents
                 the lowest numbered port, and the least significant bit
                 represents the highest numbered port.  Thus, each port
                 of the bridge is represented by a single bit within the
                 value of this object.  If that bit has a value of '1'
                 then that port is included in the set of ports; the port
                 is not included if its bit has a value of '0'."
            ::= { portTrunkEntry 2 }

        portTrunkMemberValue OBJECT-TYPE
            SYNTAX PortList
            ACCESS read-write
            STATUS mandatory
            DESCRIPTION
                "A port trunk member value indicates which port is a
                 member of the specified trunk.  Valid values are in the
                 range from 0 to ifNumber.  A zero indicates that no port
                 is contained in the specifed member.
                 Each octet within this value specifies a set of eight
                 ports, with the first octet specifying ports 1 through
                 8, the second octet specifying ports 9 through 16, etc.
                 Within each octet, the most significant bit represents
                 the lowest numbered port, and the least significant bit
                 represents the highest numbered port.  Thus, each port
                 of the bridge is represented by a single bit within the
                 value of this object.  If that bit has a value of '1'
                 then that port is included in the set of ports; the port
                 is not included if its bit has a value of '0'."
            ::= { portTrunkEntry 3 }

       portTrunkEnable OBJECT-TYPE
           SYNTAX INTEGER {
                   enabled(1),
                   disabled(2)
            }
            ACCESS read-write
            STATUS mandatory
            DESCRIPTION
                "Enable/Disable Trunk group. A (1) enables, a (2) disables."
            ::= { portTrunkEntry 4 }


-- *****************************************************************
--
--  Enterprise Trap group
--
-- *****************************************************************

swFiberInsert TRAP-TYPE
	ENTERPRISE DES-1526
        DESCRIPTION
           "Fiber insert trap"
        ::= 1

swFiberRemove TRAP-TYPE
	ENTERPRISE DES-1526
        DESCRIPTION
           "Fiber remove trap"
        ::= 2

swFiberAbnormalRXError TRAP-TYPE
	ENTERPRISE DES-1526
        DESCRIPTION
           "Fiber abnormal rx error trap"
        ::= 3

swFiberAbnormalTXError TRAP-TYPE
	ENTERPRISE DES-1526
        DESCRIPTION
           "Fiber abnormal tx error trap"
        ::= 4

swTPAbnormalRXError TRAP-TYPE
	ENTERPRISE DES-1526
        DESCRIPTION
           "Twisted Pair abnormal rx error trap"
        ::= 5

swTPAbnormalTXError TRAP-TYPE
	ENTERPRISE DES-1526
        DESCRIPTION
           "Twisted Pair abnormal tx error trap"
        ::= 6

       END
