--
-- DFL-1660 SMIv2 module
--

DFL1660-MIB DEFINITIONS ::= BEGIN

IMPORTS
    MODULE-COMPLIANCE, OBJECT-GROUP
        FROM SNMPv2-CONF
    Counter32, Counter64, Gauge32, Integer32, MODULE-IDENTITY,
    OBJECT-TYPE, enterprises
        FROM SNMPv2-SMI
    DisplayString
        FROM SNMPv2-TC;

dfl1660-MIB MODULE-IDENTITY
    LAST-UPDATED "201009021139Z"
    ORGANIZATION
        "D-Link Corporation"
    CONTACT-INFO
        "Postal: D-Link Corporation
         No. 289, Sinhu 3rd Road,
         Neihu District, Taipei City 114,
         Taiwan, R.O.C.
         Tel: +886-2-66000123
         Fax: +886-2-55509988"
    DESCRIPTION
        "The MIB module for D-Link DFL-1660 series product."

    REVISION  "201009021139Z"
    DESCRIPTION
        "Added 64-bit counters"
    REVISION  "201003300900Z"
    DESCRIPTION
        "Added values for SMTP ALG objects."
    REVISION  "200911100916Z"
    DESCRIPTION
        "Added values for opened and closed connections per second"
    REVISION  "200811181605Z"
    DESCRIPTION
        "Added value for timer usage"
    REVISION  "200810141227Z"
    DESCRIPTION
        "Added values for memory usage and TCP buffer usage"
    REVISION  "200710310000Z"
    DESCRIPTION
        "Initial version."
    ::= { dfl1660MibModules 2 }


dlink OBJECT IDENTIFIER
    ::= { enterprises 171 }

netdefendMgmt OBJECT IDENTIFIER
    ::= { dlink 20 }

utmFirewall OBJECT IDENTIFIER
    ::= { netdefendMgmt 2 }

dfl1660 OBJECT IDENTIFIER
    ::= { utmFirewall 3 }

dfl1660OS OBJECT IDENTIFIER
    ::= { dfl1660 1 }

dfl1660OSStats OBJECT IDENTIFIER
    ::= { dfl1660OS 2 }

dfl1660reg OBJECT IDENTIFIER
    ::= { dfl1660 2 }

dfl1660MibModules OBJECT IDENTIFIER
    ::= { dfl1660reg 1 }

dfl1660MibConfs OBJECT IDENTIFIER
    ::= { dfl1660reg 2 }

dfl1660MibObjectGroups OBJECT IDENTIFIER
    ::= { dfl1660reg 3 }


dfl1660System OBJECT IDENTIFIER
    ::= { dfl1660OSStats 1 }

dfl1660SysCpuLoad OBJECT-TYPE
    SYNTAX      Gauge32
    MAX-ACCESS  read-only
    STATUS      current
    DESCRIPTION
        "The system cpu load."
    ::= { dfl1660System 1 }

dfl1660SysForwardedBits OBJECT-TYPE
    SYNTAX      Counter32
    MAX-ACCESS  read-only
    STATUS      current
    DESCRIPTION
        "The number of bits forwarded through the gateway."
    ::= { dfl1660System 2 }

dfl1660SysForwardedPackets OBJECT-TYPE
    SYNTAX      Counter32
    MAX-ACCESS  read-only
    STATUS      current
    DESCRIPTION
        "Total number of forwarded packets."
    ::= { dfl1660System 3 }

dfl1660SysBuffUse OBJECT-TYPE
    SYNTAX      Gauge32
    MAX-ACCESS  read-only
    STATUS      current
    DESCRIPTION
        "The current number of buffers in use."
    ::= { dfl1660System 4 }

dfl1660SysConns OBJECT-TYPE
    SYNTAX      Gauge32
    MAX-ACCESS  read-only
    STATUS      current
    DESCRIPTION
        "The numer of connections."
    ::= { dfl1660System 5 }

dfl1660SysPerStateCounters OBJECT IDENTIFIER
    ::= { dfl1660System 6 }

dfl1660SysPscTcpSyn OBJECT-TYPE
    SYNTAX      Gauge32
    MAX-ACCESS  read-only
    STATUS      current
    DESCRIPTION
        "Number of TCP connections in the SYN state."
    ::= { dfl1660SysPerStateCounters 1 }

dfl1660SysPscTcpOpen OBJECT-TYPE
    SYNTAX      Gauge32
    MAX-ACCESS  read-only
    STATUS      current
    DESCRIPTION
        "Number of TCP connections in the OPEN state."
    ::= { dfl1660SysPerStateCounters 2 }

dfl1660SysPscTcpFin OBJECT-TYPE
    SYNTAX      Gauge32
    MAX-ACCESS  read-only
    STATUS      current
    DESCRIPTION
        "Number of TCP connections in the FIN state."
    ::= { dfl1660SysPerStateCounters 3 }

dfl1660SysPscUdp OBJECT-TYPE
    SYNTAX      Gauge32
    MAX-ACCESS  read-only
    STATUS      current
    DESCRIPTION
        "Number of UDP connections."
    ::= { dfl1660SysPerStateCounters 4 }

dfl1660SysPscIcmp OBJECT-TYPE
    SYNTAX      Gauge32
    MAX-ACCESS  read-only
    STATUS      current
    DESCRIPTION
        "Number of ICMP connections."
    ::= { dfl1660SysPerStateCounters 5 }

dfl1660SysPscOther OBJECT-TYPE
    SYNTAX      Gauge32
    MAX-ACCESS  read-only
    STATUS      current
    DESCRIPTION
        "Number of other connections."
    ::= { dfl1660SysPerStateCounters 6 }

dfl1660IfStatsTable OBJECT-TYPE
    SYNTAX      SEQUENCE OF Dfl1660IfStatsEntry
    MAX-ACCESS  not-accessible
    STATUS      current
    DESCRIPTION
        "A table of DFL-1660 specific interfaces statistics"
    ::= { dfl1660System 7 }

dfl1660IfStatsEntry OBJECT-TYPE
    SYNTAX      Dfl1660IfStatsEntry
    MAX-ACCESS  not-accessible
    STATUS      current
    DESCRIPTION
        "The row in a table of DFL-1660 specific interface statistics"
    INDEX       { dfl1660IfStatsIndex }
    ::= { dfl1660IfStatsTable 1 }

Dfl1660IfStatsEntry ::= SEQUENCE {
    dfl1660IfStatsIndex     Integer32,
    dfl1660IfName           DisplayString,
    dfl1660IfFragsIn        Counter32,
    dfl1660IfFragReassOk    Counter32,
    dfl1660IfFragReassFail  Counter32,
    dfl1660IfPktsInCnt      Counter32,
    dfl1660IfPktsOutCnt     Counter32,
    dfl1660IfBitsInCnt      Counter32,
    dfl1660IfBitsOutCnt     Counter32,
    dfl1660IfPktsTotCnt     Counter32,
    dfl1660IfBitsTotCnt     Counter32,
    dfl1660IfHCPktsInCnt    Counter64,
    dfl1660IfHCPktsOutCnt   Counter64,
    dfl1660IfHCBitsInCnt    Counter64,
    dfl1660IfHCBitsOutCnt   Counter64,
    dfl1660IfHCPktsTotCnt   Counter64,
    dfl1660IfHCBitsTotCnt   Counter64
}

dfl1660IfStatsIndex OBJECT-TYPE
    SYNTAX      Integer32 (1..2147483647)
    MAX-ACCESS  not-accessible
    STATUS      current
    DESCRIPTION
        "Index of a row in dfl1660SysIfStatsTable"
    ::= { dfl1660IfStatsEntry 1 }

dfl1660IfName OBJECT-TYPE
    SYNTAX      DisplayString
    MAX-ACCESS  read-only
    STATUS      current
    DESCRIPTION
        "The name of the interface."
    ::= { dfl1660IfStatsEntry 2 }

dfl1660IfFragsIn OBJECT-TYPE
    SYNTAX      Counter32
    MAX-ACCESS  read-only
    STATUS      current
    DESCRIPTION
        "Number of IP packet fragments received
         in the interface."
    ::= { dfl1660IfStatsEntry 3 }

dfl1660IfFragReassOk OBJECT-TYPE
    SYNTAX      Counter32
    MAX-ACCESS  read-only
    STATUS      current
    DESCRIPTION
        "Number of complete IP packets successfully
         reassembled from the fragments received in
         the interface."
    ::= { dfl1660IfStatsEntry 4 }

dfl1660IfFragReassFail OBJECT-TYPE
    SYNTAX      Counter32
    MAX-ACCESS  read-only
    STATUS      current
    DESCRIPTION
        "Number of packets that could not be reassembled,
         either due to resource starvation, illegal fragmentation,
         or just packet loss."
    ::= { dfl1660IfStatsEntry 5 }

dfl1660IfPktsInCnt OBJECT-TYPE
    SYNTAX      Counter32
    MAX-ACCESS  read-only
    STATUS      current
    DESCRIPTION
        "Number of packets received by the interface."
    ::= { dfl1660IfStatsEntry 6 }

dfl1660IfPktsOutCnt OBJECT-TYPE
    SYNTAX      Counter32
    MAX-ACCESS  read-only
    STATUS      current
    DESCRIPTION
        "Number of packets sent by the interface"
    ::= { dfl1660IfStatsEntry 7 }

dfl1660IfBitsInCnt OBJECT-TYPE
    SYNTAX      Counter32
    MAX-ACCESS  read-only
    STATUS      current
    DESCRIPTION
        "Number of bits received by the interface"
    ::= { dfl1660IfStatsEntry 8 }

dfl1660IfBitsOutCnt OBJECT-TYPE
    SYNTAX      Counter32
    MAX-ACCESS  read-only
    STATUS      current
    DESCRIPTION
        "Number of bits sent by the interface"
    ::= { dfl1660IfStatsEntry 9 }

dfl1660IfPktsTotCnt OBJECT-TYPE
    SYNTAX      Counter32
    MAX-ACCESS  read-only
    STATUS      current
    DESCRIPTION
        "Totat number of packets transmited by the interface"
    ::= { dfl1660IfStatsEntry 10 }

dfl1660IfBitsTotCnt OBJECT-TYPE
    SYNTAX      Counter32
    MAX-ACCESS  read-only
    STATUS      current
    DESCRIPTION
        "Totat number of bits transmited by the interface"
    ::= { dfl1660IfStatsEntry 11 }

dfl1660IfHCPktsInCnt OBJECT-TYPE
    SYNTAX      Counter64
    MAX-ACCESS  read-only
    STATUS      current
    DESCRIPTION
        "Number of packets received by the interface.
        This object is a 64-bit version of dfl1660IfPktsInCnt."
    ::= { dfl1660IfStatsEntry 12 }

dfl1660IfHCPktsOutCnt OBJECT-TYPE
    SYNTAX      Counter64
    MAX-ACCESS  read-only
    STATUS      current
    DESCRIPTION
        "Number of packets sent by the interface.
        This object is a 64-bit version of dfl1660IfPktsOutCnt."
    ::= { dfl1660IfStatsEntry 13 }

dfl1660IfHCBitsInCnt OBJECT-TYPE
    SYNTAX      Counter64
    MAX-ACCESS  read-only
    STATUS      current
    DESCRIPTION
        "Number of bits received by the interface.
        This object is a 64-bit version of dfl1660IfBitsInCnt."
    ::= { dfl1660IfStatsEntry 14 }

dfl1660IfHCBitsOutCnt OBJECT-TYPE
    SYNTAX      Counter64
    MAX-ACCESS  read-only
    STATUS      current
    DESCRIPTION
        "Number of bits sent by the interface.
        This object is a 64-bit version of dfl1660IfBitsOutCnt."
    ::= { dfl1660IfStatsEntry 15 }

dfl1660IfHCPktsTotCnt OBJECT-TYPE
    SYNTAX      Counter64
    MAX-ACCESS  read-only
    STATUS      current
    DESCRIPTION
        "Totat number of packets transmited by the interface.
        This object is a 64-bit version of dfl1660IfPktsTotCnt."
    ::= { dfl1660IfStatsEntry 16 }

dfl1660IfHCBitsTotCnt OBJECT-TYPE
    SYNTAX      Counter64
    MAX-ACCESS  read-only
    STATUS      current
    DESCRIPTION
        "Totat number of bits transmited by the interface.
        This object is a 64-bit version of dfl1660IfBitsTotCnt."
    ::= { dfl1660IfStatsEntry 17 }

dfl1660IfRxRingTable OBJECT-TYPE
    SYNTAX      SEQUENCE OF Dfl1660IfRxRingEntry
    MAX-ACCESS  not-accessible
    STATUS      current
    DESCRIPTION
        "A table of DFL-1660 specific interface Rx ring statistics"
    ::= { dfl1660System 8 }

dfl1660IfRxRingEntry OBJECT-TYPE
    SYNTAX      Dfl1660IfRxRingEntry
    MAX-ACCESS  not-accessible
    STATUS      current
    DESCRIPTION
        "The row in a table of DFL-1660 specific interface Rx ring
         statistics."
    INDEX       { dfl1660IfRxRingIndex }
    ::= { dfl1660IfRxRingTable 1 }

Dfl1660IfRxRingEntry ::= SEQUENCE {
    dfl1660IfRxRingIndex        Integer32,
    dfl1660IfRxRingFifoErrors   Counter32,
    dfl1660IfRxDespools         Gauge32,
    dfl1660IfRxAvgUse           Gauge32,
    dfl1660IfRxRingSaturation   Gauge32,
    dfl1660RxRingFlooded        Gauge32
}

dfl1660IfRxRingIndex OBJECT-TYPE
    SYNTAX      Integer32 (1..2147483647)
    MAX-ACCESS  not-accessible
    STATUS      current
    DESCRIPTION
        "Index of a row in dfl1660IfRxRingTable."
    ::= { dfl1660IfRxRingEntry 1 }

dfl1660IfRxRingFifoErrors OBJECT-TYPE
    SYNTAX      Counter32
    MAX-ACCESS  read-only
    STATUS      current
    DESCRIPTION
        "Rx Ring number of FIFO errors."
    ::= { dfl1660IfRxRingEntry 2 }

dfl1660IfRxDespools OBJECT-TYPE
    SYNTAX      Gauge32
    MAX-ACCESS  read-only
    STATUS      current
    DESCRIPTION
        "Number of despool events per second."
    ::= { dfl1660IfRxRingEntry 3 }

dfl1660IfRxAvgUse OBJECT-TYPE
    SYNTAX      Gauge32
    MAX-ACCESS  read-only
    STATUS      current
    DESCRIPTION
        "Rx Ring average usage."
    ::= { dfl1660IfRxRingEntry 4 }

dfl1660IfRxRingSaturation OBJECT-TYPE
    SYNTAX      Gauge32
    MAX-ACCESS  read-only
    STATUS      current
    DESCRIPTION
        "Rx Ring sturation. Percentage of ring use per despool
         event when the ring has been more than half full."
    ::= { dfl1660IfRxRingEntry 5 }

dfl1660RxRingFlooded OBJECT-TYPE
    SYNTAX      Gauge32
    MAX-ACCESS  read-only
    STATUS      current
    DESCRIPTION
        "Rx Ring number of despool events for which
         the ring has been completely flooded"
    ::= { dfl1660IfRxRingEntry 6 }

dfl1660IfTxRingTable OBJECT-TYPE
    SYNTAX      SEQUENCE OF Dfl1660IfTxRingEntry
    MAX-ACCESS  not-accessible
    STATUS      current
    DESCRIPTION
        "A table of DFL-1660 specific interface Tx ring statistics"
    ::= { dfl1660System 9 }

dfl1660IfTxRingEntry OBJECT-TYPE
    SYNTAX      Dfl1660IfTxRingEntry
    MAX-ACCESS  not-accessible
    STATUS      current
    DESCRIPTION
        "The row in a table of DFL-1660 specific interface Tx ring
         statistics."
    INDEX       { dfl1660IfTxRingIndex }
    ::= { dfl1660IfTxRingTable 1 }

Dfl1660IfTxRingEntry ::= SEQUENCE {
    dfl1660IfTxRingIndex        Integer32,
    dfl1660IfTxDespools         Gauge32,
    dfl1660IfTxAvgUse           Gauge32,
    dfl1660IfTxRingSaturation   Gauge32,
    dfl1660RxTingFlooded        Gauge32
}

dfl1660IfTxRingIndex OBJECT-TYPE
    SYNTAX      Integer32 (1..2147483647)
    MAX-ACCESS  not-accessible
    STATUS      current
    DESCRIPTION
        "Index of a row in dfl1660IfRxRingTable."
    ::= { dfl1660IfTxRingEntry 1 }

dfl1660IfTxDespools OBJECT-TYPE
    SYNTAX      Gauge32
    MAX-ACCESS  read-only
    STATUS      current
    DESCRIPTION
        "Tx Ring number of despool event per second (polls when
         there is at least one buffer in the ring)"
    ::= { dfl1660IfTxRingEntry 2 }

dfl1660IfTxAvgUse OBJECT-TYPE
    SYNTAX      Gauge32
    MAX-ACCESS  read-only
    STATUS      current
    DESCRIPTION
        "Tx Ring number of despool events when the ring has
         been completely flooded"
    ::= { dfl1660IfTxRingEntry 3 }

dfl1660IfTxRingSaturation OBJECT-TYPE
    SYNTAX      Gauge32
    MAX-ACCESS  read-only
    STATUS      current
    DESCRIPTION
        "Tx Ring percentage of use per despool event when the
         ring has been more than half full."
    ::= { dfl1660IfTxRingEntry 4 }

dfl1660RxTingFlooded OBJECT-TYPE
    SYNTAX      Gauge32
    MAX-ACCESS  read-only
    STATUS      current
    DESCRIPTION
        "Tx Ring number of despool events for in which the ring has
         been completely flooded"
    ::= { dfl1660IfTxRingEntry 5 }

dfl1660IfVlanStatsTable OBJECT-TYPE
    SYNTAX      SEQUENCE OF Dfl1660IfVlanStatsEntry
    MAX-ACCESS  not-accessible
    STATUS      current
    DESCRIPTION
        "A table of DFL-1660 VLAN statistics"
    ::= { dfl1660System 10 }

dfl1660IfVlanStatsEntry OBJECT-TYPE
    SYNTAX      Dfl1660IfVlanStatsEntry
    MAX-ACCESS  not-accessible
    STATUS      current
    DESCRIPTION
        "The row in a table of dfl1660IfVlanStatsTable. Each has an index
         equal to the ifIndex of the corresponding physical interface"
    INDEX       { dfl1660IfVlanIndex }
    ::= { dfl1660IfVlanStatsTable 1 }

Dfl1660IfVlanStatsEntry ::= SEQUENCE {
    dfl1660IfVlanIndex              Integer32,
    dfl1660IfVlanUntaggedInPkts     Counter32,
    dfl1660IfVlanUntaggedOutPkts    Counter32,
    dfl1660IfVlanUntaggedTotPkts    Counter32,
    dfl1660IfVlanUntaggedInOctets   Counter32,
    dfl1660IfVlanUntaggedOutOctets  Counter32,
    dfl1660IfVlanUntaggedTotOctets  Counter32
}

dfl1660IfVlanIndex OBJECT-TYPE
    SYNTAX      Integer32 (1..2147483647)
    MAX-ACCESS  not-accessible
    STATUS      current
    DESCRIPTION
        "Extended index of a row in dfl1660IfVlanStatsTable."
    ::= { dfl1660IfVlanStatsEntry 1 }

dfl1660IfVlanUntaggedInPkts OBJECT-TYPE
    SYNTAX      Counter32
    MAX-ACCESS  read-only
    STATUS      current
    DESCRIPTION
        "Number of untaged packets untagged packets received by the interface."
    ::= { dfl1660IfVlanStatsEntry 2 }

dfl1660IfVlanUntaggedOutPkts OBJECT-TYPE
    SYNTAX      Counter32
    MAX-ACCESS  read-only
    STATUS      current
    DESCRIPTION
        "Number of untagged packets sent by the interface."
    ::= { dfl1660IfVlanStatsEntry 3 }

dfl1660IfVlanUntaggedTotPkts OBJECT-TYPE
    SYNTAX      Counter32
    MAX-ACCESS  read-only
    STATUS      current
    DESCRIPTION
        "Total number of untagged packets processed by the interface."
    ::= { dfl1660IfVlanStatsEntry 4 }

dfl1660IfVlanUntaggedInOctets OBJECT-TYPE
    SYNTAX      Counter32
    MAX-ACCESS  read-only
    STATUS      current
    DESCRIPTION
        "Total number of octects in untagged packets received by the interface."
    ::= { dfl1660IfVlanStatsEntry 5 }

dfl1660IfVlanUntaggedOutOctets OBJECT-TYPE
    SYNTAX      Counter32
    MAX-ACCESS  read-only
    STATUS      current
    DESCRIPTION
        "Total number of octects in untagged packets sent by the interface."
    ::= { dfl1660IfVlanStatsEntry 6 }

dfl1660IfVlanUntaggedTotOctets OBJECT-TYPE
    SYNTAX      Counter32
    MAX-ACCESS  read-only
    STATUS      current
    DESCRIPTION
        "Total number of octects in untagged packets processed by the
         interface."
    ::= { dfl1660IfVlanStatsEntry 7 }

dfl1660HWSensorTable OBJECT-TYPE
    SYNTAX      SEQUENCE OF Dfl1660HWSensorEntry
    MAX-ACCESS  not-accessible
    STATUS      current
    DESCRIPTION
        "Table of hardware sensors."
    ::= { dfl1660System 11 }

dfl1660HWSensorEntry OBJECT-TYPE
    SYNTAX      Dfl1660HWSensorEntry
    MAX-ACCESS  not-accessible
    STATUS      current
    DESCRIPTION
        "Entry  of table of hardware sensors."
    INDEX       { dfl1660HWSensorIndex }
    ::= { dfl1660HWSensorTable 1 }

Dfl1660HWSensorEntry ::= SEQUENCE {
    dfl1660HWSensorIndex    Integer32,
    dfl1660HWSensorName     DisplayString,
    dfl1660HWSensorValue    Gauge32,
    dfl1660HWSensorUnit     DisplayString
}

dfl1660HWSensorIndex OBJECT-TYPE
    SYNTAX      Integer32 (1..2147483647)
    MAX-ACCESS  not-accessible
    STATUS      current
    DESCRIPTION
        "Index of the entries of the sensor table."
    ::= { dfl1660HWSensorEntry 1 }

dfl1660HWSensorName OBJECT-TYPE
    SYNTAX      DisplayString
    MAX-ACCESS  read-only
    STATUS      current
    DESCRIPTION
        "The description of the sensor."
    ::= { dfl1660HWSensorEntry 2 }

dfl1660HWSensorValue OBJECT-TYPE
    SYNTAX      Gauge32
    MAX-ACCESS  read-only
    STATUS      current
    DESCRIPTION
        "The value of the sensor."
    ::= { dfl1660HWSensorEntry 3 }

dfl1660HWSensorUnit OBJECT-TYPE
    SYNTAX      DisplayString
    MAX-ACCESS  read-only
    STATUS      current
    DESCRIPTION
        "The description of the unit of the value mesured by sensor."
    ::= { dfl1660HWSensorEntry 4 }

dfl1660SysMemUsage OBJECT-TYPE
    SYNTAX      Gauge32
    MAX-ACCESS  read-only
    STATUS      current
    DESCRIPTION
        "The current memory usage."
    ::= { dfl1660System 12 }

dfl1660SysTCPUsage OBJECT IDENTIFIER
    ::= { dfl1660System 13 }

dfl1660SysTCPRecvSmall OBJECT-TYPE
    SYNTAX      Gauge32
    MAX-ACCESS  read-only
    STATUS      current
    DESCRIPTION
        "Small TCP receive windows usage."
    ::= { dfl1660SysTCPUsage 1 }

dfl1660SysTCPRecvLarge OBJECT-TYPE
    SYNTAX      Gauge32
    MAX-ACCESS  read-only
    STATUS      current
    DESCRIPTION
        "Large TCP receive windows usage."
    ::= { dfl1660SysTCPUsage 2 }

dfl1660SysTCPSendSmall OBJECT-TYPE
    SYNTAX      Gauge32
    MAX-ACCESS  read-only
    STATUS      current
    DESCRIPTION
        "Small TCP send windows usage."
    ::= { dfl1660SysTCPUsage 3 }

dfl1660SysTCPSendLarge OBJECT-TYPE
    SYNTAX      Gauge32
    MAX-ACCESS  read-only
    STATUS      current
    DESCRIPTION
        "Large TCP send windows usage."
    ::= { dfl1660SysTCPUsage 4 }

dfl1660SysTimerUsage OBJECT-TYPE
    SYNTAX      Gauge32
    MAX-ACCESS  read-only
    STATUS      current
    DESCRIPTION
        "The current number of timers in use."
    ::= { dfl1660System 14 }

dfl1660SysConnOPS OBJECT-TYPE
    SYNTAX      Gauge32
    MAX-ACCESS  read-only
    STATUS      current
    DESCRIPTION
        "The number of connections opened per second."
    ::= { dfl1660System 15 }

dfl1660SysConnCPS OBJECT-TYPE
    SYNTAX      Gauge32
    MAX-ACCESS  read-only
    STATUS      current
    DESCRIPTION
        "The number of connections closed per second."
    ::= { dfl1660System 16 }

dfl1660SysHCForwardedBits OBJECT-TYPE
    SYNTAX      Counter64
    MAX-ACCESS  read-only
    STATUS      current
    DESCRIPTION
        "The number of bits forwarded through the gateway."
    ::= { dfl1660System 17 }

dfl1660VPN OBJECT IDENTIFIER
    ::= { dfl1660OSStats 2 }

dfl1660IPsec OBJECT IDENTIFIER
    ::= { dfl1660VPN 1 }

dfl1660IPsecGlobal OBJECT IDENTIFIER
    ::= { dfl1660IPsec 1 }

dfl1660IPsecPhaseOneActive OBJECT-TYPE
    SYNTAX      Gauge32
    MAX-ACCESS  read-only
    STATUS      current
    DESCRIPTION
        "Number of Phase-1 active negotiations"
    ::= { dfl1660IPsecGlobal 1 }

dfl1660IPsecPhaseOneAggrModeDone OBJECT-TYPE
    SYNTAX      Gauge32
    MAX-ACCESS  read-only
    STATUS      current
    DESCRIPTION
        "Number of Phase-1 aggressive mode negotiations."
    ::= { dfl1660IPsecGlobal 2 }

dfl1660IPsecQuickModeActive OBJECT-TYPE
    SYNTAX      Gauge32
    MAX-ACCESS  read-only
    STATUS      current
    DESCRIPTION
        "Number of quick mode active negotiations."
    ::= { dfl1660IPsecGlobal 3 }

dfl1660IPsecPhaseOneDone OBJECT-TYPE
    SYNTAX      Counter32
    MAX-ACCESS  read-only
    STATUS      current
    DESCRIPTION
        "Number of Phase-1 negotiations done."
    ::= { dfl1660IPsecGlobal 4 }

dfl1660IPsecPhaseOneFailed OBJECT-TYPE
    SYNTAX      Counter32
    MAX-ACCESS  read-only
    STATUS      current
    DESCRIPTION
        "Number of Phase-1 negotiations failed."
    ::= { dfl1660IPsecGlobal 5 }

dfl1660IPsecPhaseOneRekeyed OBJECT-TYPE
    SYNTAX      Counter32
    MAX-ACCESS  read-only
    STATUS      current
    DESCRIPTION
        "Number of Phase-1 negotiations rekeyed."
    ::= { dfl1660IPsecGlobal 6 }

dfl1660IPsecQuickModeDone OBJECT-TYPE
    SYNTAX      Counter32
    MAX-ACCESS  read-only
    STATUS      current
    DESCRIPTION
        "Number of quick mode  negotiations done."
    ::= { dfl1660IPsecGlobal 7 }

dfl1660IPsecQuickModeFailed OBJECT-TYPE
    SYNTAX      Counter32
    MAX-ACCESS  read-only
    STATUS      current
    DESCRIPTION
        "Number of quick mode negotiations failed."
    ::= { dfl1660IPsecGlobal 8 }

dfl1660IPsecInfoDone OBJECT-TYPE
    SYNTAX      Counter32
    MAX-ACCESS  read-only
    STATUS      current
    DESCRIPTION
        "Number of informational exchanges done.
         (Not available in IKEv1 implementations)"
    ::= { dfl1660IPsecGlobal 9 }

dfl1660IPsecInfoFailed OBJECT-TYPE
    SYNTAX      Counter32
    MAX-ACCESS  read-only
    STATUS      current
    DESCRIPTION
        "Number of informational exchanges failed.
         (Not available in IKEv1 implementations)"
    ::= { dfl1660IPsecGlobal 10 }

dfl1660IPsecInOctetsComp OBJECT-TYPE
    SYNTAX      Counter64
    MAX-ACCESS  read-only
    STATUS      current
    DESCRIPTION
        "Total octets in before decompression."
    ::= { dfl1660IPsecGlobal 11 }

dfl1660IPsecInOctetsUncomp OBJECT-TYPE
    SYNTAX      Counter64
    MAX-ACCESS  read-only
    STATUS      current
    DESCRIPTION
        "Total octets in after decompression."
    ::= { dfl1660IPsecGlobal 12 }

dfl1660IPsecOutOctetsComp OBJECT-TYPE
    SYNTAX      Counter64
    MAX-ACCESS  read-only
    STATUS      current
    DESCRIPTION
        "Total octets out after compression."
    ::= { dfl1660IPsecGlobal 13 }

dfl1660IPsecOutOctetsUncomp OBJECT-TYPE
    SYNTAX      Counter64
    MAX-ACCESS  read-only
    STATUS      current
    DESCRIPTION
        "Total octets out before compression."
    ::= { dfl1660IPsecGlobal 14 }

dfl1660IPsecForwardedOctetsComp OBJECT-TYPE
    SYNTAX      Counter64
    MAX-ACCESS  read-only
    STATUS      current
    DESCRIPTION
        "Total octets forwarded after compression."
    ::= { dfl1660IPsecGlobal 15 }

dfl1660IPsecForwardedOctetsUcomp OBJECT-TYPE
    SYNTAX      Counter64
    MAX-ACCESS  read-only
    STATUS      current
    DESCRIPTION
        "Total octets forwarded before compression."
    ::= { dfl1660IPsecGlobal 16 }

dfl1660IPsecInPackets OBJECT-TYPE
    SYNTAX      Counter64
    MAX-ACCESS  read-only
    STATUS      current
    DESCRIPTION
        "Total packets in."
    ::= { dfl1660IPsecGlobal 17 }

dfl1660IPsecOutPackets OBJECT-TYPE
    SYNTAX      Counter64
    MAX-ACCESS  read-only
    STATUS      current
    DESCRIPTION
        "Total packets Out."
    ::= { dfl1660IPsecGlobal 18 }

dfl1660IPsecForwardedPackets OBJECT-TYPE
    SYNTAX      Counter64
    MAX-ACCESS  read-only
    STATUS      current
    DESCRIPTION
        "Total packets forwarded."
    ::= { dfl1660IPsecGlobal 19 }

dfl1660IPsecActiveTransforms OBJECT-TYPE
    SYNTAX      Gauge32
    MAX-ACCESS  read-only
    STATUS      current
    DESCRIPTION
        "Number of currently active transforms."
    ::= { dfl1660IPsecGlobal 20 }

dfl1660IPsecTotalTransforms OBJECT-TYPE
    SYNTAX      Counter32
    MAX-ACCESS  read-only
    STATUS      current
    DESCRIPTION
        "Total number of transform records created."
    ::= { dfl1660IPsecGlobal 21 }

dfl1660IPsecOutOfTransforms OBJECT-TYPE
    SYNTAX      Counter32
    MAX-ACCESS  read-only
    STATUS      current
    DESCRIPTION
        "Number of packets dropped due to no available transform object.
         (Not available in IKEv1 implementations)"
    ::= { dfl1660IPsecGlobal 22 }

dfl1660IPsecTotalRekeys OBJECT-TYPE
    SYNTAX      Counter32
    MAX-ACCESS  read-only
    STATUS      current
    DESCRIPTION
        "Total number of rekeys performed."
    ::= { dfl1660IPsecGlobal 23 }

dfl1660Rules OBJECT IDENTIFIER
    ::= { dfl1660OSStats 3 }

dfl1660RuleUseTable OBJECT-TYPE
    SYNTAX      SEQUENCE OF Dfl1660RuleUseEntry
    MAX-ACCESS  not-accessible
    STATUS      current
    DESCRIPTION
        "A list of general rules usage statistics."
    ::= { dfl1660Rules 2 }

dfl1660RuleUseEntry OBJECT-TYPE
    SYNTAX      Dfl1660RuleUseEntry
    MAX-ACCESS  not-accessible
    STATUS      current
    DESCRIPTION
        "The statistics over a rule usage."
    INDEX       { dfl1660RuleIndex }
    ::= { dfl1660RuleUseTable 1 }

Dfl1660RuleUseEntry ::= SEQUENCE {
    dfl1660RuleIndex    Integer32,
    dfl1660RuleName     DisplayString,
    dfl1660RuleUse      Counter32
}

dfl1660RuleIndex OBJECT-TYPE
    SYNTAX      Integer32 (1..2147483647)
    MAX-ACCESS  not-accessible
    STATUS      current
    DESCRIPTION
        "The rule usage index."
    ::= { dfl1660RuleUseEntry 1 }

dfl1660RuleName OBJECT-TYPE
    SYNTAX      DisplayString
    MAX-ACCESS  read-only
    STATUS      current
    DESCRIPTION
        "The name of the rule."
    ::= { dfl1660RuleUseEntry 2 }

dfl1660RuleUse OBJECT-TYPE
    SYNTAX      Counter32
    MAX-ACCESS  read-only
    STATUS      current
    DESCRIPTION
        "The number of times o rule was used."
    ::= { dfl1660RuleUseEntry 3 }

dfl1660IPPools OBJECT IDENTIFIER
    ::= { dfl1660OSStats 4 }

dfl1660IPPoolsNumber OBJECT-TYPE
    SYNTAX      Integer32
    MAX-ACCESS  read-only
    STATUS      current
    DESCRIPTION
        "The number of ip pools"
    ::= { dfl1660IPPools 1 }

dfl1660IPPoolTable OBJECT-TYPE
    SYNTAX      SEQUENCE OF Dfl1660IPPoolEntry
    MAX-ACCESS  not-accessible
    STATUS      current
    DESCRIPTION
        "A list of IP pools"
    ::= { dfl1660IPPools 2 }

dfl1660IPPoolEntry OBJECT-TYPE
    SYNTAX      Dfl1660IPPoolEntry
    MAX-ACCESS  not-accessible
    STATUS      current
    DESCRIPTION
        "The attributes of an ip pool"
    INDEX       { dfl1660IPPoolIndex }
    ::= { dfl1660IPPoolTable 1 }

Dfl1660IPPoolEntry ::= SEQUENCE {
    dfl1660IPPoolIndex          Integer32,
    dfl1660IPPoolName           DisplayString,
    dfl1660IPPoolPrepare        Gauge32,
    dfl1660IPPoolFree           Gauge32,
    dfl1660IPPoolMisses         Gauge32,
    dfl1660IPPoolClientFails    Gauge32,
    dfl1660IPPoolUsed           Gauge32
}

dfl1660IPPoolIndex OBJECT-TYPE
    SYNTAX      Integer32 (1..2147483647)
    MAX-ACCESS  not-accessible
    STATUS      current
    DESCRIPTION
        "The ip pool index"
    ::= { dfl1660IPPoolEntry 1 }

dfl1660IPPoolName OBJECT-TYPE
    SYNTAX      DisplayString
    MAX-ACCESS  read-only
    STATUS      current
    DESCRIPTION
        "The ip pool name"
    ::= { dfl1660IPPoolEntry 2 }

dfl1660IPPoolPrepare OBJECT-TYPE
    SYNTAX      Gauge32
    MAX-ACCESS  read-only
    STATUS      current
    DESCRIPTION
        "Number of IP pool objects in prepare mode."
    ::= { dfl1660IPPoolEntry 3 }

dfl1660IPPoolFree OBJECT-TYPE
    SYNTAX      Gauge32
    MAX-ACCESS  read-only
    STATUS      current
    DESCRIPTION
        "Number of available IPs in the pool."
    ::= { dfl1660IPPoolEntry 4 }

dfl1660IPPoolMisses OBJECT-TYPE
    SYNTAX      Gauge32
    MAX-ACCESS  read-only
    STATUS      current
    DESCRIPTION
        "Mumber of missed IP pool negotiations for other reasons
         than lack of available IP numbers."
    ::= { dfl1660IPPoolEntry 5 }

dfl1660IPPoolClientFails OBJECT-TYPE
    SYNTAX      Gauge32
    MAX-ACCESS  read-only
    STATUS      current
    DESCRIPTION
        "Number of failed IP pool transactions."
    ::= { dfl1660IPPoolEntry 6 }

dfl1660IPPoolUsed OBJECT-TYPE
    SYNTAX      Gauge32
    MAX-ACCESS  read-only
    STATUS      current
    DESCRIPTION
        "Number of IP numbers in use from the pool."
    ::= { dfl1660IPPoolEntry 7 }

dfl1660DHCPServer OBJECT IDENTIFIER
    ::= { dfl1660OSStats 5 }

dfl1660DHCPTotalRejected OBJECT-TYPE
    SYNTAX      Gauge32
    MAX-ACCESS  read-only
    STATUS      current
    DESCRIPTION
        "Total number of rejected packets (all rules)."
    ::= { dfl1660DHCPServer 1 }

dfl1660DHCPRuleTable OBJECT-TYPE
    SYNTAX      SEQUENCE OF Dfl1660DHCPRuleEntry
    MAX-ACCESS  not-accessible
    STATUS      current
    DESCRIPTION
        "A list of all DHCP server rules usage statistics."
    ::= { dfl1660DHCPServer 2 }

dfl1660DHCPRuleEntry OBJECT-TYPE
    SYNTAX      Dfl1660DHCPRuleEntry
    MAX-ACCESS  not-accessible
    STATUS      current
    DESCRIPTION
        "The attributes of a DHCP server rule statistics."
    INDEX       { dfl1660DHCPRuleIndex }
    ::= { dfl1660DHCPRuleTable 1 }

Dfl1660DHCPRuleEntry ::= SEQUENCE {
    dfl1660DHCPRuleIndex                Integer32,
    dfl1660DHCPRuleName                 DisplayString,
    dfl1660DHCPRuleUsage                Gauge32,
    dfl1660DHCPRuleUsagePercent         Gauge32,
    dfl1660DHCPActiveClients            Gauge32,
    dfl1660DHCPActiveClientsPercent     Gauge32,
    dfl1660DHCPRejectedRequests         Gauge32,
    dfl1660DHCPTotalLeases              Gauge32
}

dfl1660DHCPRuleIndex OBJECT-TYPE
    SYNTAX      Integer32 (1..2147483647)
    MAX-ACCESS  not-accessible
    STATUS      current
    DESCRIPTION
        "The DHCP server rule  index"
    ::= { dfl1660DHCPRuleEntry 1 }

dfl1660DHCPRuleName OBJECT-TYPE
    SYNTAX      DisplayString
    MAX-ACCESS  read-only
    STATUS      current
    DESCRIPTION
        "The DHCP server rule name."
    ::= { dfl1660DHCPRuleEntry 2 }

dfl1660DHCPRuleUsage OBJECT-TYPE
    SYNTAX      Gauge32
    MAX-ACCESS  read-only
    STATUS      current
    DESCRIPTION
        "Number of used IPs in the pool."
    ::= { dfl1660DHCPRuleEntry 3 }

dfl1660DHCPRuleUsagePercent OBJECT-TYPE
    SYNTAX      Gauge32
    MAX-ACCESS  read-only
    STATUS      current
    DESCRIPTION
        "The percentage of the used IPs in
         relation to the IP pool size."
    ::= { dfl1660DHCPRuleEntry 4 }

dfl1660DHCPActiveClients OBJECT-TYPE
    SYNTAX      Gauge32
    MAX-ACCESS  read-only
    STATUS      current
    DESCRIPTION
        "Number of currently active clients."
    ::= { dfl1660DHCPRuleEntry 5 }

dfl1660DHCPActiveClientsPercent OBJECT-TYPE
    SYNTAX      Gauge32
    MAX-ACCESS  read-only
    STATUS      current
    DESCRIPTION
        "The number of currently active clients
         as a percentage of the pool size."
    ::= { dfl1660DHCPRuleEntry 6 }

dfl1660DHCPRejectedRequests OBJECT-TYPE
    SYNTAX      Gauge32
    MAX-ACCESS  read-only
    STATUS      current
    DESCRIPTION
        "Number of rejected requests matching
         the current rule."
    ::= { dfl1660DHCPRuleEntry 7 }

dfl1660DHCPTotalLeases OBJECT-TYPE
    SYNTAX      Gauge32
    MAX-ACCESS  read-only
    STATUS      current
    DESCRIPTION
        "Total number of leases in the pool."
    ::= { dfl1660DHCPRuleEntry 8 }

dfl1660UserAuth OBJECT IDENTIFIER
    ::= { dfl1660OSStats 6 }

dfl1660UserAuthHTTPUsers OBJECT-TYPE
    SYNTAX      Gauge32
    MAX-ACCESS  read-only
    STATUS      current
    DESCRIPTION
        "Number of currently  logged in HTTP users."
    ::= { dfl1660UserAuth 1 }

dfl1660UserAuthXAUTHUsers OBJECT-TYPE
    SYNTAX      Gauge32
    MAX-ACCESS  read-only
    STATUS      current
    DESCRIPTION
        "Number of currently logged in XAUTH users."
    ::= { dfl1660UserAuth 2 }

dfl1660UserAuthHTTPSUsers OBJECT-TYPE
    SYNTAX      Gauge32
    MAX-ACCESS  read-only
    STATUS      current
    DESCRIPTION
        "Number of currently logged in HTTPS users."
    ::= { dfl1660UserAuth 3 }

dfl1660UserAuthPPPUsers OBJECT-TYPE
    SYNTAX      Gauge32
    MAX-ACCESS  read-only
    STATUS      current
    DESCRIPTION
        "Number of currently logged in PPP users."
    ::= { dfl1660UserAuth 4 }

dfl1660UserAuthEAPUsers OBJECT-TYPE
    SYNTAX      Gauge32
    MAX-ACCESS  read-only
    STATUS      current
    DESCRIPTION
        "Number of currently logged in EAP users."
    ::= { dfl1660UserAuth 5 }

dfl1660UserAuthRuleUseTable OBJECT-TYPE
    SYNTAX      SEQUENCE OF Dfl1660UserAuthRuleUseEntry
    MAX-ACCESS  not-accessible
    STATUS      current
    DESCRIPTION
        "Table of user authentication rule usage."
    ::= { dfl1660UserAuth 6 }

dfl1660UserAuthRuleUseEntry OBJECT-TYPE
    SYNTAX      Dfl1660UserAuthRuleUseEntry
    MAX-ACCESS  not-accessible
    STATUS      current
    DESCRIPTION
        "The attributes of an authentication rule
         usage statistics."
    INDEX       { dfl1660UserAuthRuleIndex }
    ::= { dfl1660UserAuthRuleUseTable 1 }

Dfl1660UserAuthRuleUseEntry ::= SEQUENCE {
    dfl1660UserAuthRuleIndex    Integer32,
    dfl1660UserAuthRuleName     DisplayString,
    dfl1660UserAuthRuleUse      Counter32
}

dfl1660UserAuthRuleIndex OBJECT-TYPE
    SYNTAX      Integer32 (1..2147483647)
    MAX-ACCESS  not-accessible
    STATUS      current
    DESCRIPTION
        "The rule usage index."
    ::= { dfl1660UserAuthRuleUseEntry 1 }

dfl1660UserAuthRuleName OBJECT-TYPE
    SYNTAX      DisplayString
    MAX-ACCESS  read-only
    STATUS      current
    DESCRIPTION
        "The name of the rule."
    ::= { dfl1660UserAuthRuleUseEntry 2 }

dfl1660UserAuthRuleUse OBJECT-TYPE
    SYNTAX      Counter32
    MAX-ACCESS  read-only
    STATUS      current
    DESCRIPTION
        "The number of times o rule was used."
    ::= { dfl1660UserAuthRuleUseEntry 3 }

dfl1660LinkMonitor OBJECT IDENTIFIER
    ::= { dfl1660OSStats 7 }

dfl1660LinkMonGrp OBJECT-TYPE
    SYNTAX      Integer32
    MAX-ACCESS  read-only
    STATUS      current
    DESCRIPTION
        "The number of groups of monitored links"
    ::= { dfl1660LinkMonitor 1 }

dfl1660LinkMonGrpTable OBJECT-TYPE
    SYNTAX      SEQUENCE OF Dfl1660LinkMonGrpEntry
    MAX-ACCESS  not-accessible
    STATUS      current
    DESCRIPTION
        "Table of link monitor groups."
    ::= { dfl1660LinkMonitor 2 }

dfl1660LinkMonGrpEntry OBJECT-TYPE
    SYNTAX      Dfl1660LinkMonGrpEntry
    MAX-ACCESS  not-accessible
    STATUS      current
    DESCRIPTION
        "The attributes of a link monitor group"
    INDEX       { dfl1660LinkMonGrpIndex }
    ::= { dfl1660LinkMonGrpTable 1 }

Dfl1660LinkMonGrpEntry ::= SEQUENCE {
    dfl1660LinkMonGrpIndex      Integer32,
    dfl1660LinkMonGrpName       DisplayString,
    dfl1660LinkMonGrpHostsUp    Gauge32
}

dfl1660LinkMonGrpIndex OBJECT-TYPE
    SYNTAX      Integer32 (1..2147483647)
    MAX-ACCESS  not-accessible
    STATUS      current
    DESCRIPTION
        "The index row in the table of link monitor groups."
    ::= { dfl1660LinkMonGrpEntry 1 }

dfl1660LinkMonGrpName OBJECT-TYPE
    SYNTAX      DisplayString
    MAX-ACCESS  read-only
    STATUS      current
    DESCRIPTION
        "The link monitor group name."
    ::= { dfl1660LinkMonGrpEntry 2 }

dfl1660LinkMonGrpHostsUp OBJECT-TYPE
    SYNTAX      Gauge32
    MAX-ACCESS  read-only
    STATUS      current
    DESCRIPTION
        "The percentage of monitored hosts available."
    ::= { dfl1660LinkMonGrpEntry 3 }

dfl1660LinkMonHostTable OBJECT-TYPE
    SYNTAX      SEQUENCE OF Dfl1660LinkMonHostEntry
    MAX-ACCESS  not-accessible
    STATUS      current
    DESCRIPTION
        "Table of link monitored hosts in a link monnitor group."
    ::= { dfl1660LinkMonitor 3 }

dfl1660LinkMonHostEntry OBJECT-TYPE
    SYNTAX      Dfl1660LinkMonHostEntry
    MAX-ACCESS  not-accessible
    STATUS      current
    DESCRIPTION
        "The attributes of a monitored host."
    INDEX       { dfl1660LinkMonGrpIndex, dfl1660LinkMonHostIndex }
    ::= { dfl1660LinkMonHostTable 1 }

Dfl1660LinkMonHostEntry ::= SEQUENCE {
    dfl1660LinkMonHostIndex             Integer32,
    dfl1660LinkMonHostId                DisplayString,
    dfl1660LinkMonHostShortTermLoss     Gauge32,
    dfl1660LinkMonHostPacketsLost       Counter32
}

dfl1660LinkMonHostIndex OBJECT-TYPE
    SYNTAX      Integer32 (1..2147483647)
    MAX-ACCESS  not-accessible
    STATUS      current
    DESCRIPTION
        "The index an host in the table of link monitor hosts."
    ::= { dfl1660LinkMonHostEntry 1 }

dfl1660LinkMonHostId OBJECT-TYPE
    SYNTAX      DisplayString
    MAX-ACCESS  read-only
    STATUS      current
    DESCRIPTION
        "The monitored host identifier."
    ::= { dfl1660LinkMonHostEntry 2 }

dfl1660LinkMonHostShortTermLoss OBJECT-TYPE
    SYNTAX      Gauge32
    MAX-ACCESS  read-only
    STATUS      current
    DESCRIPTION
        "The percentage of short term losst packets."
    ::= { dfl1660LinkMonHostEntry 3 }

dfl1660LinkMonHostPacketsLost OBJECT-TYPE
    SYNTAX      Counter32
    MAX-ACCESS  read-only
    STATUS      current
    DESCRIPTION
        "Total number of lost monitoring packets."
    ::= { dfl1660LinkMonHostEntry 4 }

dfl1660Pipes OBJECT IDENTIFIER
    ::= { dfl1660OSStats 8 }

dfl1660PipeUsers OBJECT-TYPE
    SYNTAX      Gauge32
    MAX-ACCESS  read-only
    STATUS      current
    DESCRIPTION
        "The current number of users, as defined by the grouping
         settings of each pipe, being tracked in the pipes system.
         Note that this value corresponds to the number of users
         active in each time slice of 1/20th of a second, and not
         to the number of users having open connections."
    ::= { dfl1660Pipes 1 }

dfl1660PipeTable OBJECT-TYPE
    SYNTAX      SEQUENCE OF Dfl1660PipeEntry
    MAX-ACCESS  not-accessible
    STATUS      current
    DESCRIPTION
        "Table of pipes"
    ::= { dfl1660Pipes 2 }

dfl1660PipeEntry OBJECT-TYPE
    SYNTAX      Dfl1660PipeEntry
    MAX-ACCESS  not-accessible
    STATUS      current
    DESCRIPTION
        "A entry of the pipes table"
    INDEX       { dfl1660PipeIndex }
    ::= { dfl1660PipeTable 1 }

Dfl1660PipeEntry ::= SEQUENCE {
    dfl1660PipeIndex            Integer32,
    dfl1660PipeName             DisplayString,
    dfl1660PipeMinPrec          Integer32,
    dfl1660PipeMaxPrec          Integer32,
    dfl1660PipeDefPrec          Integer32,
    dfl1660PipeNumPrec          Integer32,
    dfl1660PipeNumUsers         Gauge32,
    dfl1660PipeCurrentBps       Gauge32,
    dfl1660PipeCurrentPps       Gauge32,
    dfl1660PipeDelayedPackets   Counter32,
    dfl1660PipeDropedPackets    Counter32
}

dfl1660PipeIndex OBJECT-TYPE
    SYNTAX      Integer32 (1..2147483647)
    MAX-ACCESS  not-accessible
    STATUS      current
    DESCRIPTION
        "The pipe index"
    ::= { dfl1660PipeEntry 1 }

dfl1660PipeName OBJECT-TYPE
    SYNTAX      DisplayString
    MAX-ACCESS  read-only
    STATUS      current
    DESCRIPTION
        "The name of the pipe"
    ::= { dfl1660PipeEntry 2 }

dfl1660PipeMinPrec OBJECT-TYPE
    SYNTAX      Integer32
    MAX-ACCESS  read-only
    STATUS      current
    DESCRIPTION
        "The minimum of the range of pipe precedences."
    ::= { dfl1660PipeEntry 3 }

dfl1660PipeMaxPrec OBJECT-TYPE
    SYNTAX      Integer32
    MAX-ACCESS  read-only
    STATUS      current
    DESCRIPTION
        "The maximum of the range of pipe precedences."
    ::= { dfl1660PipeEntry 4 }

dfl1660PipeDefPrec OBJECT-TYPE
    SYNTAX      Integer32
    MAX-ACCESS  read-only
    STATUS      current
    DESCRIPTION
        "The precedence assigned to a packet for which has not one
         allready done by a Pipe Rule."
    ::= { dfl1660PipeEntry 5 }

dfl1660PipeNumPrec OBJECT-TYPE
    SYNTAX      Integer32
    MAX-ACCESS  read-only
    STATUS      current
    DESCRIPTION
        "The number of pipe precedences"
    ::= { dfl1660PipeEntry 6 }

dfl1660PipeNumUsers OBJECT-TYPE
    SYNTAX      Gauge32
    MAX-ACCESS  read-only
    STATUS      current
    DESCRIPTION
        "The current number of users, as defined by the grouping settings
         of each pipe, being tracked in the pipes system. This value
         corresponds to the number of users active in each time slice
         and not to the number of users having  open connections."
    ::= { dfl1660PipeEntry 7 }

dfl1660PipeCurrentBps OBJECT-TYPE
    SYNTAX      Gauge32
    MAX-ACCESS  read-only
    STATUS      current
    DESCRIPTION
        "The current throughput of a pipe, in bits per second, as a sum of
         the corresponding values for all precedences."
    ::= { dfl1660PipeEntry 8 }

dfl1660PipeCurrentPps OBJECT-TYPE
    SYNTAX      Gauge32
    MAX-ACCESS  read-only
    STATUS      current
    DESCRIPTION
        "The current throughput of a pipe, in packets per second, as a sum of
         the corresponding values for all precedences."
    ::= { dfl1660PipeEntry 9 }

dfl1660PipeDelayedPackets OBJECT-TYPE
    SYNTAX      Counter32
    MAX-ACCESS  read-only
    STATUS      current
    DESCRIPTION
        "The number of times packets have been delayed as a result of a pipe,
         or pipe user having used up its allotted bandwidth. Note that one single
         packet may be delayed several times; if a pipe is really full, this
         count may exceed the number of packets actually passing through the
         pipe."
    ::= { dfl1660PipeEntry 10 }

dfl1660PipeDropedPackets OBJECT-TYPE
    SYNTAX      Counter32
    MAX-ACCESS  read-only
    STATUS      current
    DESCRIPTION
        "The number of packets dropped by a pipe. Packets are dropped when
         CorePlus is running out of packet buffers. This occurs when excessive
         amounts of packets need to be queued for later delivery. The packet
         dropped is always the one that has been queued the longest time
         globally, which means that the connection suffering from packet loss
         will be the one most overloading the system."
    ::= { dfl1660PipeEntry 11 }

dfl1660PipePrecTable OBJECT-TYPE
    SYNTAX      SEQUENCE OF Dfl1660PipePrecEntry
    MAX-ACCESS  not-accessible
    STATUS      current
    DESCRIPTION
        "There is a one to many relation between a pipe and its precedences.
         The number of precedences is a instance attribute of each pipe.
         This table extends the pipes table in order to express the relation
         between a pipe and the respective precedences."
    ::= { dfl1660Pipes 3 }

dfl1660PipePrecEntry OBJECT-TYPE
    SYNTAX      Dfl1660PipePrecEntry
    MAX-ACCESS  not-accessible
    STATUS      current
    DESCRIPTION
        "An entry of the table of pipe pecedences. These table entries
         are chracterized by been indexed by two values. The first index
         the same as the pipe index of the corresponding row in table of
         pipes and the second index is the index of the set of precedences
         of the corresponding pipe."
    INDEX       { dfl1660PipeIndex, dfl1660PipePrecIndex }
    ::= { dfl1660PipePrecTable 1 }

Dfl1660PipePrecEntry ::= SEQUENCE {
    dfl1660PipePrecIndex            Integer32,
    dfl1660PipePrec                 Integer32,
    dfl1660PipePrecBps              Gauge32,
    dfl1660PipePrecTotalPps         Gauge32,
    dfl1660PipePrecReservedBps      Gauge32,
    dfl1660PipePrecDynLimBps        Gauge32,
    dfl1660PipePrecDynUsrLimBps     Gauge32,
    dfl1660PipePrecDelayedPackets   Counter32,
    dfl1660PipePrecDropedPackets    Counter32
}

dfl1660PipePrecIndex OBJECT-TYPE
    SYNTAX      Integer32 (1..2147483647)
    MAX-ACCESS  not-accessible
    STATUS      current
    DESCRIPTION
        "Index of a precedence of a specific pipe. This is the second index
         of the entries of pipe precedence table described by object
         dfl1660PipePrecEntry."
    ::= { dfl1660PipePrecEntry 1 }

dfl1660PipePrec OBJECT-TYPE
    SYNTAX      Integer32
    MAX-ACCESS  read-only
    STATUS      current
    DESCRIPTION
        "The precedence value"
    ::= { dfl1660PipePrecEntry 2 }

dfl1660PipePrecBps OBJECT-TYPE
    SYNTAX      Gauge32
    MAX-ACCESS  read-only
    STATUS      current
    DESCRIPTION
        "The current throughput of the pipe, in bits per second, with
         the corresponding precedence."
    ::= { dfl1660PipePrecEntry 3 }

dfl1660PipePrecTotalPps OBJECT-TYPE
    SYNTAX      Gauge32
    MAX-ACCESS  read-only
    STATUS      current
    DESCRIPTION
        "The current throughput of the pipe precedence, in packets per second."
    ::= { dfl1660PipePrecEntry 4 }

dfl1660PipePrecReservedBps OBJECT-TYPE
    SYNTAX      Gauge32
    MAX-ACCESS  read-only
    STATUS      current
    DESCRIPTION
        "The current bandwidth allocated to the precedence."
    ::= { dfl1660PipePrecEntry 5 }

dfl1660PipePrecDynLimBps OBJECT-TYPE
    SYNTAX      Gauge32
    MAX-ACCESS  read-only
    STATUS      current
    DESCRIPTION
        "The current bandwidth limit limit applied the precedence."
    ::= { dfl1660PipePrecEntry 6 }

dfl1660PipePrecDynUsrLimBps OBJECT-TYPE
    SYNTAX      Gauge32
    MAX-ACCESS  read-only
    STATUS      current
    DESCRIPTION
        "The current precedence bandwidth limit per user of the pipe."
    ::= { dfl1660PipePrecEntry 7 }

dfl1660PipePrecDelayedPackets OBJECT-TYPE
    SYNTAX      Counter32
    MAX-ACCESS  read-only
    STATUS      current
    DESCRIPTION
        "The number of times packets have been delayed as a result of a
         precedence, or pipe user having used up its allotted bandwidth.
         Note that one single packet may be delayed several times; if a
         pipe is really full, this count may exceed the number of packets
         of this precedence actually passing through the pipe."
    ::= { dfl1660PipePrecEntry 8 }

dfl1660PipePrecDropedPackets OBJECT-TYPE
    SYNTAX      Counter32
    MAX-ACCESS  read-only
    STATUS      current
    DESCRIPTION
        "The number of pipe dropped packets with the corresponding precedence."
    ::= { dfl1660PipePrecEntry 9 }

dfl1660ALG OBJECT IDENTIFIER
    ::= { dfl1660OSStats 9 }

dfl1660AlgSessions OBJECT-TYPE
    SYNTAX      Gauge32
    MAX-ACCESS  read-only
    STATUS      current
    DESCRIPTION
        "Total ALG sessions"
    ::= { dfl1660ALG 1 }

dfl1660AlgConnections OBJECT-TYPE
    SYNTAX      Gauge32
    MAX-ACCESS  read-only
    STATUS      current
    DESCRIPTION
        "Total ALG connections"
    ::= { dfl1660ALG 2 }

dfl1660AlgTCPStreams OBJECT-TYPE
    SYNTAX      Gauge32
    MAX-ACCESS  read-only
    STATUS      current
    DESCRIPTION
        "Total ALG TCP streams"
    ::= { dfl1660ALG 3 }

dfl1660HttpAlg OBJECT IDENTIFIER
    ::= { dfl1660ALG 4 }

dfl1660HttpAlgTable OBJECT-TYPE
    SYNTAX      SEQUENCE OF Dfl1660HttpAlgEntry
    MAX-ACCESS  not-accessible
    STATUS      current
    DESCRIPTION
        "Table of HTTP ALG objects."
    ::= { dfl1660HttpAlg 1 }

dfl1660HttpAlgEntry OBJECT-TYPE
    SYNTAX      Dfl1660HttpAlgEntry
    MAX-ACCESS  not-accessible
    STATUS      current
    DESCRIPTION
        "A row of the table of HTTP ALG objects."
    INDEX       { dfl1660HttpAlgIndex }
    ::= { dfl1660HttpAlgTable 1 }

Dfl1660HttpAlgEntry ::= SEQUENCE {
    dfl1660HttpAlgIndex             Integer32,
    dfl1660HttpAlgName              DisplayString,
    dfl1660HttpAlgTotalRequested    Gauge32,
    dfl1660HttpAlgTotalAllowed      Gauge32,
    dfl1660HttpAlgTotalBlocked      Gauge32
}

dfl1660HttpAlgIndex OBJECT-TYPE
    SYNTAX      Integer32 (1..2147483647)
    MAX-ACCESS  not-accessible
    STATUS      current
    DESCRIPTION
        "The index of an entry of the  Table of HTTP ALG objects."
    ::= { dfl1660HttpAlgEntry 1 }

dfl1660HttpAlgName OBJECT-TYPE
    SYNTAX      DisplayString
    MAX-ACCESS  read-only
    STATUS      current
    DESCRIPTION
        "The name of an HTTP ALG object."
    ::= { dfl1660HttpAlgEntry 2 }

dfl1660HttpAlgTotalRequested OBJECT-TYPE
    SYNTAX      Gauge32
    MAX-ACCESS  read-only
    STATUS      current
    DESCRIPTION
        "Total number of URL requests."
    ::= { dfl1660HttpAlgEntry 3 }

dfl1660HttpAlgTotalAllowed OBJECT-TYPE
    SYNTAX      Gauge32
    MAX-ACCESS  read-only
    STATUS      current
    DESCRIPTION
        "Total number of allowed URL requests."
    ::= { dfl1660HttpAlgEntry 4 }

dfl1660HttpAlgTotalBlocked OBJECT-TYPE
    SYNTAX      Gauge32
    MAX-ACCESS  read-only
    STATUS      current
    DESCRIPTION
        "Total number of blocked URL requests."
    ::= { dfl1660HttpAlgEntry 5 }

dfl1660HttpAlgCntFltTable OBJECT-TYPE
    SYNTAX      SEQUENCE OF Dfl1660HttpAlgCntFltEntry
    MAX-ACCESS  not-accessible
    STATUS      current
    DESCRIPTION
        "Table of HTTP ALG content filtering rules."
    ::= { dfl1660HttpAlg 2 }

dfl1660HttpAlgCntFltEntry OBJECT-TYPE
    SYNTAX      Dfl1660HttpAlgCntFltEntry
    MAX-ACCESS  not-accessible
    STATUS      current
    DESCRIPTION
        "Entry of the table of HTTP ALG content filtering rules."
    INDEX       { dfl1660HttpAlgIndex, dfl1660HttpAlgCntFltIndex }
    ::= { dfl1660HttpAlgCntFltTable 1 }

Dfl1660HttpAlgCntFltEntry ::= SEQUENCE {
    dfl1660HttpAlgCntFltIndex       Integer32,
    dfl1660HttpAlgCntFltName        DisplayString,
    dfl1660HttpAlgCntFltRequests    Gauge32,
    dfl1660HttpAlgCntFltAllowed     Gauge32,
    dfl1660HttpAlgCntFltBlocked     Gauge32
}

dfl1660HttpAlgCntFltIndex OBJECT-TYPE
    SYNTAX      Integer32 (1..2147483647)
    MAX-ACCESS  not-accessible
    STATUS      current
    DESCRIPTION
        "The index of an entry of the  Table of HTTP ALG
         content filtering objects."
    ::= { dfl1660HttpAlgCntFltEntry 1 }

dfl1660HttpAlgCntFltName OBJECT-TYPE
    SYNTAX      DisplayString
    MAX-ACCESS  read-only
    STATUS      current
    DESCRIPTION
        "The name of the a HTTP ALG content fitering."
    ::= { dfl1660HttpAlgCntFltEntry 2 }

dfl1660HttpAlgCntFltRequests OBJECT-TYPE
    SYNTAX      Gauge32
    MAX-ACCESS  read-only
    STATUS      current
    DESCRIPTION
        "Total number of URLs intercepted by a content
         filtering object."
    ::= { dfl1660HttpAlgCntFltEntry 3 }

dfl1660HttpAlgCntFltAllowed OBJECT-TYPE
    SYNTAX      Gauge32
    MAX-ACCESS  read-only
    STATUS      current
    DESCRIPTION
        "Total number of URLs intercepted and allowed
         by a content filtering object."
    ::= { dfl1660HttpAlgCntFltEntry 4 }

dfl1660HttpAlgCntFltBlocked OBJECT-TYPE
    SYNTAX      Gauge32
    MAX-ACCESS  read-only
    STATUS      current
    DESCRIPTION
        "Total number of URLs intercepted and blocked
         by a content filtering object."
    ::= { dfl1660HttpAlgCntFltEntry 5 }

dfl1660SmtpAlg OBJECT IDENTIFIER
    ::= { dfl1660ALG 5 }

dfl1660SmtpAlgTable OBJECT-TYPE
    SYNTAX  SEQUENCE OF Dfl1660SmtpAlgEntry
    MAX-ACCESS  not-accessible
    STATUS  current
    DESCRIPTION
  "Table of SMTP ALG objects."
    ::= { dfl1660SmtpAlg 1 }

dfl1660SmtpAlgEntry OBJECT-TYPE
   SYNTAX  Dfl1660SmtpAlgEntry
   MAX-ACCESS  not-accessible
    STATUS      current
    DESCRIPTION
        "A row of the table of SMTP ALG objects."
    INDEX       { dfl1660SmtpAlgIndex }
    ::= { dfl1660SmtpAlgTable 1 }

Dfl1660SmtpAlgEntry ::= SEQUENCE {
    dfl1660SmtpAlgIndex           Integer32,
    dfl1660SmtpAlgName            DisplayString,
    dfl1660SmtpAlgTotCheckedSes   Gauge32,
    dfl1660SmtpAlgTotSpamSes      Gauge32,
    dfl1660SmtpAlgTotDroppedSes   Gauge32
}

dfl1660SmtpAlgIndex OBJECT-TYPE
    SYNTAX      Integer32 (1..2147483647)
    MAX-ACCESS  not-accessible
    STATUS      current
    DESCRIPTION
        "The index of an entry of the  Table of SMTP ALG objects."
    ::= { dfl1660SmtpAlgEntry 1 }

dfl1660SmtpAlgName OBJECT-TYPE
    SYNTAX      DisplayString
    MAX-ACCESS  read-only
    STATUS      current
    DESCRIPTION
        "The name of an SMTP ALG object."
    ::= { dfl1660SmtpAlgEntry 2 }

dfl1660SmtpAlgTotCheckedSes OBJECT-TYPE
    SYNTAX      Gauge32
    MAX-ACCESS  read-only
    STATUS      current
    DESCRIPTION
        "Total sessions checked by the SMTP ALG of corresponding index."
    ::= { dfl1660SmtpAlgEntry 3 }

dfl1660SmtpAlgTotSpamSes OBJECT-TYPE
    SYNTAX      Gauge32
    MAX-ACCESS  read-only
    STATUS      current
    DESCRIPTION
        "Total spam sessions detected by the SMTP ALG of corresponding index."
    ::= { dfl1660SmtpAlgEntry 4 }

dfl1660SmtpAlgTotDroppedSes OBJECT-TYPE
    SYNTAX      Gauge32
    MAX-ACCESS  read-only
    STATUS      current
    DESCRIPTION
        "Total deroped sessions for the SMTP ALG of corresponding index."
    ::= { dfl1660SmtpAlgEntry 5 }


dfl1660SmtpAlgDnsBlTable OBJECT-TYPE
    SYNTAX  SEQUENCE OF Dfl1660SmtpAlgDnsBlEntry
    MAX-ACCESS  not-accessible
    STATUS  current
    DESCRIPTION
  "Table of SMTP ALG DNS balck list objects."
    ::= { dfl1660SmtpAlg 2 }


dfl1660SmtpAlgDnsBlEntry OBJECT-TYPE
   SYNTAX  Dfl1660SmtpAlgDnsBlEntry
   MAX-ACCESS  not-accessible
    STATUS      current
    DESCRIPTION
        "A row of the table of SMTP ALG DNS black list objects."
    INDEX       { dfl1660SmtpAlgIndex, dfl1660SmtpAlgDnsBlIndex }
    ::= { dfl1660SmtpAlgDnsBlTable 1 }


Dfl1660SmtpAlgDnsBlEntry ::= SEQUENCE {
    dfl1660SmtpAlgDnsBlIndex  Integer32,
    dfl1660SmtpAlgDnsBlName    DisplayString,
    dfl1660SmtpAlgDnsBlChecked      Gauge32,
    dfl1660SmtpAlgDnsBlMatched  Gauge32,
    dfl1660SmtpAlgDnsBlFailChecks  Gauge32
}

dfl1660SmtpAlgDnsBlIndex OBJECT-TYPE
    SYNTAX      Integer32 (1..2147483647)
    MAX-ACCESS  not-accessible
    STATUS      current
    DESCRIPTION
        "The index of an entry of the  SMTP ALG DNS black list objects."
    ::= { dfl1660SmtpAlgDnsBlEntry 1 }

dfl1660SmtpAlgDnsBlName OBJECT-TYPE
    SYNTAX      DisplayString
    MAX-ACCESS  read-only
    STATUS      current
    DESCRIPTION
  "The SMTP DNS black list name."
    ::= { dfl1660SmtpAlgDnsBlEntry 2 }

dfl1660SmtpAlgDnsBlChecked OBJECT-TYPE
    SYNTAX      Gauge32
    MAX-ACCESS  read-only
    STATUS      current
    DESCRIPTION
  "Total sessions checked againt SMTP ALG DNS black list of corresponding index"
    ::= { dfl1660SmtpAlgDnsBlEntry 3 }

dfl1660SmtpAlgDnsBlMatched OBJECT-TYPE
    SYNTAX      Gauge32
    MAX-ACCESS  read-only
    STATUS      current
    DESCRIPTION
  "Total sessions that matched SMTP ALG DNS black list of corresponding index"
    ::= { dfl1660SmtpAlgDnsBlEntry 4 }

dfl1660SmtpAlgDnsBlFailChecks OBJECT-TYPE
    SYNTAX      Gauge32
    MAX-ACCESS  read-only
    STATUS      current
    DESCRIPTION
  "Total failed checks for the SMTP ALG DNS black list of corresponding index"
    ::= { dfl1660SmtpAlgDnsBlEntry 5 }

dfl1660DHCPRelay OBJECT IDENTIFIER
    ::= { dfl1660OSStats 11 }

dfl1660DHCPRelayCurClients OBJECT-TYPE
    SYNTAX      Gauge32
    MAX-ACCESS  read-only
    STATUS      current
    DESCRIPTION
        "Total DHCP relay active relayed clients."
    ::= { dfl1660DHCPRelay 1 }

dfl1660DHCPRelayCurTrans OBJECT-TYPE
    SYNTAX      Gauge32
    MAX-ACCESS  read-only
    STATUS      current
    DESCRIPTION
        "Ongoing DHCP relay transactions."
    ::= { dfl1660DHCPRelay 2 }

dfl1660DHCPRelayRejected OBJECT-TYPE
    SYNTAX      Gauge32
    MAX-ACCESS  read-only
    STATUS      current
    DESCRIPTION
        "Total DHCP relay packets rejected."
    ::= { dfl1660DHCPRelay 3 }

dfl1660DHCPRelayRuleTable OBJECT-TYPE
    SYNTAX      SEQUENCE OF Dfl1660DHCPRelayRuleEntry
    MAX-ACCESS  not-accessible
    STATUS      current
    DESCRIPTION
        "Table of DHCP relay rules."
    ::= { dfl1660DHCPRelay 4 }

dfl1660DHCPRelayRuleEntry OBJECT-TYPE
    SYNTAX      Dfl1660DHCPRelayRuleEntry
    MAX-ACCESS  not-accessible
    STATUS      current
    DESCRIPTION
        "Entry of the table of DHCP relay rules"
    INDEX       { dfl1660DHCPRelayRuleIndex }
    ::= { dfl1660DHCPRelayRuleTable 1 }

Dfl1660DHCPRelayRuleEntry ::= SEQUENCE {
    dfl1660DHCPRelayRuleIndex       Integer32,
    dfl1660DHCPRelayRuleName        DisplayString,
    dfl1660DHCPRelayRuleHits        Gauge32,
    dfl1660DHCPRelayRuleCurClients  Gauge32,
    dfl1660DHCPRelayRuleRejCliPkts  Gauge32,
    dfl1660DHCPRelayRuleRejSrvPkts  Gauge32
}

dfl1660DHCPRelayRuleIndex OBJECT-TYPE
    SYNTAX      Integer32 (1..2147483647)
    MAX-ACCESS  not-accessible
    STATUS      current
    DESCRIPTION
        "Index of the table of DHCP relay rules."
    ::= { dfl1660DHCPRelayRuleEntry 1 }

dfl1660DHCPRelayRuleName OBJECT-TYPE
    SYNTAX      DisplayString
    MAX-ACCESS  read-only
    STATUS      current
    DESCRIPTION
        "Display name of a DHCP relay rule"
    ::= { dfl1660DHCPRelayRuleEntry 2 }

dfl1660DHCPRelayRuleHits OBJECT-TYPE
    SYNTAX      Gauge32
    MAX-ACCESS  read-only
    STATUS      current
    DESCRIPTION
        "Number of the times the  DHCP relay rule with corresponding index was
         used."
    ::= { dfl1660DHCPRelayRuleEntry 3 }

dfl1660DHCPRelayRuleCurClients OBJECT-TYPE
    SYNTAX      Gauge32
    MAX-ACCESS  read-only
    STATUS      current
    DESCRIPTION
        "Number of ctive relayed clients by the DHCP relay rule with corresponding index."
    ::= { dfl1660DHCPRelayRuleEntry 4 }

dfl1660DHCPRelayRuleRejCliPkts OBJECT-TYPE
    SYNTAX      Gauge32
    MAX-ACCESS  read-only
    STATUS      current
    DESCRIPTION
        "Number of client packets rejected by a rule."
    ::= { dfl1660DHCPRelayRuleEntry 5 }

dfl1660DHCPRelayRuleRejSrvPkts OBJECT-TYPE
    SYNTAX      Gauge32
    MAX-ACCESS  read-only
    STATUS      current
    DESCRIPTION
        "Number of DHCP server packets rejected by the DHCP relay rule
         with the corresponding index."
    ::= { dfl1660DHCPRelayRuleEntry 6 }

dfl1660HA OBJECT IDENTIFIER
    ::= { dfl1660OSStats 12 }

dfl1660HASyncSendQueueLength OBJECT-TYPE
    SYNTAX      Gauge32
    MAX-ACCESS  read-only
    STATUS      current
    DESCRIPTION
        "Size of the queue used for the High Availability sync interface."
    ::= { dfl1660HA 1 }

dfl1660HASyncSendQueueUsagePkt OBJECT-TYPE
    SYNTAX      Gauge32
    MAX-ACCESS  read-only
    STATUS      current
    DESCRIPTION
        "High Availability Sync interface queue usage in number of packets."
    ::= { dfl1660HA 2 }

dfl1660HASyncSendQueueUsageOct OBJECT-TYPE
    SYNTAX      Gauge32
    MAX-ACCESS  read-only
    STATUS      current
    DESCRIPTION
        "High Availability Sync interface queue usage in number of octects."
    ::= { dfl1660HA 3 }

dfl1660HASyncSentPackets OBJECT-TYPE
    SYNTAX      Counter32
    MAX-ACCESS  read-only
    STATUS      current
    DESCRIPTION
        "Number High Availability packets sent on Sync."
    ::= { dfl1660HA 4 }

dfl1660HASyncSendResentPackets OBJECT-TYPE
    SYNTAX      Counter32
    MAX-ACCESS  read-only
    STATUS      current
    DESCRIPTION
        "Number of High Availability packets resent on Sync."
    ::= { dfl1660HA 5 }

dfl1660StatsConformance OBJECT IDENTIFIER
    ::= { dfl1660MibConfs 1 }

dfl1660StatsRegGroups OBJECT IDENTIFIER
    ::= { dfl1660MibObjectGroups 1 }

dfl1660SystemObjectGroup OBJECT-GROUP
    OBJECTS     { dfl1660SysCpuLoad,
                  dfl1660SysForwardedBits,
                  dfl1660SysForwardedPackets,
                  dfl1660SysBuffUse,
                  dfl1660SysConns,
                  dfl1660HWSensorName,
                  dfl1660HWSensorValue,
                  dfl1660HWSensorUnit,
                  dfl1660SysMemUsage,
                  dfl1660SysTimerUsage,
                  dfl1660SysConnOPS,
                  dfl1660SysConnCPS,
                  dfl1660SysHCForwardedBits }
    STATUS      current
    DESCRIPTION
        "System statistics Group"
    ::= { dfl1660StatsRegGroups 1 }

dfl1660IPsecObjectGroup OBJECT-GROUP
    OBJECTS     { dfl1660IPsecPhaseOneActive,
                  dfl1660IPsecPhaseOneAggrModeDone,
                  dfl1660IPsecQuickModeActive,
                  dfl1660IPsecPhaseOneDone,
                  dfl1660IPsecPhaseOneFailed,
                  dfl1660IPsecPhaseOneRekeyed,
                  dfl1660IPsecQuickModeDone,
                  dfl1660IPsecQuickModeFailed,
                  dfl1660IPsecInfoDone,
                  dfl1660IPsecInfoFailed,
                  dfl1660IPsecInOctetsComp,
                  dfl1660IPsecInOctetsUncomp,
                  dfl1660IPsecOutOctetsComp,
                  dfl1660IPsecOutOctetsUncomp,
                  dfl1660IPsecForwardedOctetsComp,
                  dfl1660IPsecForwardedOctetsUcomp,
                  dfl1660IPsecInPackets,
                  dfl1660IPsecOutPackets,
                  dfl1660IPsecForwardedPackets,
                  dfl1660IPsecActiveTransforms,
                  dfl1660IPsecTotalTransforms,
                  dfl1660IPsecOutOfTransforms,
                  dfl1660IPsecTotalRekeys }
    STATUS      current
    DESCRIPTION
        "IPsec Group"
    ::= { dfl1660StatsRegGroups 2 }

dfl1660StateCountersGroup OBJECT-GROUP
    OBJECTS     { dfl1660SysPscTcpSyn,
                  dfl1660SysPscTcpOpen,
                  dfl1660SysPscTcpFin,
                  dfl1660SysPscUdp,
                  dfl1660SysPscIcmp,
                  dfl1660SysPscOther }
    STATUS      current
    DESCRIPTION
        "Per state counters"
    ::= { dfl1660StatsRegGroups 3 }

dfl1660IPPoolGroup OBJECT-GROUP
    OBJECTS     { dfl1660IPPoolsNumber,
                  dfl1660IPPoolName,
                  dfl1660IPPoolPrepare,
                  dfl1660IPPoolFree,
                  dfl1660IPPoolMisses,
                  dfl1660IPPoolClientFails,
                  dfl1660IPPoolUsed }
    STATUS      current
    DESCRIPTION
        "IP pool entry objects group"
    ::= { dfl1660StatsRegGroups 4 }

dfl1660DHCPServerGroup OBJECT-GROUP
    OBJECTS     { dfl1660DHCPTotalRejected,
                  dfl1660DHCPRuleName,
                  dfl1660DHCPRuleUsage,
                  dfl1660DHCPRuleUsagePercent,
                  dfl1660DHCPActiveClients,
                  dfl1660DHCPActiveClientsPercent,
                  dfl1660DHCPRejectedRequests,
                  dfl1660DHCPTotalLeases }
    STATUS      current
    DESCRIPTION
        "DHCP server rules objects."
    ::= { dfl1660StatsRegGroups 5 }

dfl1660RuleUseGroup OBJECT-GROUP
    OBJECTS     { dfl1660RuleName, dfl1660RuleUse }
    STATUS      current
    DESCRIPTION
        "Rule use objects."
    ::= { dfl1660StatsRegGroups 6 }

dfl1660UserAuthGroup OBJECT-GROUP
    OBJECTS     { dfl1660UserAuthHTTPUsers, dfl1660UserAuthXAUTHUsers,
                  dfl1660UserAuthHTTPSUsers, dfl1660UserAuthPPPUsers,
                  dfl1660UserAuthEAPUsers, dfl1660UserAuthRuleName,
                  dfl1660UserAuthRuleUse }
    STATUS      current
    DESCRIPTION
        "User auth objects."
    ::= { dfl1660StatsRegGroups 7 }

dfl1660IfStatsGroup OBJECT-GROUP
    OBJECTS     { dfl1660IfName,
                  dfl1660IfFragsIn,
                  dfl1660IfFragReassOk,
                  dfl1660IfFragReassFail,
                  dfl1660IfPktsInCnt,
                  dfl1660IfPktsOutCnt,
                  dfl1660IfBitsInCnt,
                  dfl1660IfBitsOutCnt,
                  dfl1660IfPktsTotCnt,
                  dfl1660IfBitsTotCnt,
                  dfl1660IfHCPktsInCnt,
                  dfl1660IfHCPktsOutCnt,
                  dfl1660IfHCBitsInCnt,
                  dfl1660IfHCBitsOutCnt,
                  dfl1660IfHCPktsTotCnt,
                  dfl1660IfHCBitsTotCnt,
                  dfl1660IfRxRingFifoErrors,
                  dfl1660IfRxDespools,
                  dfl1660IfRxAvgUse,
                  dfl1660IfRxRingSaturation,
                  dfl1660RxRingFlooded,
                  dfl1660IfTxDespools,
                  dfl1660IfTxAvgUse,
                  dfl1660IfTxRingSaturation,
                  dfl1660RxTingFlooded }
    STATUS      current
    DESCRIPTION
        "DFL-1660 interface statistics group."
    ::= { dfl1660StatsRegGroups 8 }

dfl1660LinkMonitorGroup OBJECT-GROUP
    OBJECTS     { dfl1660LinkMonGrp,
                  dfl1660LinkMonGrpName,
                  dfl1660LinkMonGrpHostsUp,
                  dfl1660LinkMonHostId,
                  dfl1660LinkMonHostShortTermLoss,
                  dfl1660LinkMonHostPacketsLost }
    STATUS      current
    DESCRIPTION
        "DFL-1660 link monitor statistics group"
    ::= { dfl1660StatsRegGroups 9 }

dfl1660PipesObjectGroup OBJECT-GROUP
    OBJECTS     { dfl1660PipeUsers,
                  dfl1660PipeName,
                  dfl1660PipeMinPrec,
                  dfl1660PipeMaxPrec,
                  dfl1660PipeDefPrec,
                  dfl1660PipeNumPrec,
                  dfl1660PipeNumUsers,
                  dfl1660PipeCurrentBps,
                  dfl1660PipeCurrentPps,
                  dfl1660PipeDelayedPackets,
                  dfl1660PipeDropedPackets,
                  dfl1660PipePrec,
                  dfl1660PipePrecBps,
                  dfl1660PipePrecTotalPps,
                  dfl1660PipePrecReservedBps,
                  dfl1660PipePrecDynLimBps,
                  dfl1660PipePrecDynUsrLimBps,
                  dfl1660PipePrecDelayedPackets,
                  dfl1660PipePrecDropedPackets }
    STATUS      current
    DESCRIPTION
        "DFL-1660 pipes statistics group"
    ::= { dfl1660StatsRegGroups 10 }

dfl1660DHCPRelayObjectGroup OBJECT-GROUP
    OBJECTS     { dfl1660DHCPRelayCurClients,
                  dfl1660DHCPRelayCurTrans,
                  dfl1660DHCPRelayRejected,
                  dfl1660DHCPRelayRuleName,
                  dfl1660DHCPRelayRuleHits,
                  dfl1660DHCPRelayRuleCurClients,
                  dfl1660DHCPRelayRuleRejCliPkts,
                  dfl1660DHCPRelayRuleRejSrvPkts }
    STATUS      current
    DESCRIPTION
        "DFL-1660 DHCP relay statistics group"
    ::= { dfl1660StatsRegGroups 12 }

dfl1660AlgGroup OBJECT-GROUP
    OBJECTS     { dfl1660AlgSessions,
                  dfl1660AlgConnections,
                  dfl1660AlgTCPStreams,
                  dfl1660HttpAlgName,
                  dfl1660HttpAlgTotalRequested,
                  dfl1660HttpAlgTotalAllowed,
                  dfl1660HttpAlgTotalBlocked,
                  dfl1660HttpAlgCntFltName,
                  dfl1660HttpAlgCntFltRequests,
                  dfl1660HttpAlgCntFltAllowed,
                  dfl1660HttpAlgCntFltBlocked }
    STATUS      current
    DESCRIPTION
        "DFL-1660 HTTP ALG statistics group"
    ::= { dfl1660StatsRegGroups 13 }

dfl1660HAGroup OBJECT-GROUP
    OBJECTS     { dfl1660HASyncSendQueueLength,
                  dfl1660HASyncSendQueueUsagePkt,
                  dfl1660HASyncSendQueueUsageOct,
                  dfl1660HASyncSentPackets,
                  dfl1660HASyncSendResentPackets }
    STATUS      current
    DESCRIPTION
        "DFL-1660 HA statistics group"
    ::= { dfl1660StatsRegGroups 14 }

dfl1660IfVlanGroup OBJECT-GROUP
    OBJECTS     { dfl1660IfVlanUntaggedInPkts,
                  dfl1660IfVlanUntaggedOutPkts,
                  dfl1660IfVlanUntaggedTotPkts,
                  dfl1660IfVlanUntaggedInOctets,
                  dfl1660IfVlanUntaggedOutOctets,
                  dfl1660IfVlanUntaggedTotOctets }
    STATUS      current
    DESCRIPTION
        "DFL-1660 VLAN statistics group"
    ::= { dfl1660StatsRegGroups 15 }


dfl1660SmtpAlgGroup OBJECT-GROUP
    OBJECTS { dfl1660SmtpAlgName,
              dfl1660SmtpAlgTotCheckedSes,
              dfl1660SmtpAlgTotSpamSes,
              dfl1660SmtpAlgTotDroppedSes,
              dfl1660SmtpAlgDnsBlName,
              dfl1660SmtpAlgDnsBlChecked,
              dfl1660SmtpAlgDnsBlMatched,
              dfl1660SmtpAlgDnsBlFailChecks }
   STATUS current
   DESCRIPTION
       "Clavister SMTP ALG objects group"
   ::= { dfl1660StatsRegGroups 16 }

dfl1660SysTCPGroup OBJECT-GROUP
    OBJECTS { dfl1660SysTCPRecvSmall,
              dfl1660SysTCPRecvLarge,
              dfl1660SysTCPSendSmall,
              dfl1660SysTCPSendLarge }
    STATUS current
    DESCRIPTION
      "DFL-1660 TCP buffer usage group"
    ::= { dfl1660StatsRegGroups 17 }



dfl1660StatsCompliance MODULE-COMPLIANCE
    STATUS      current
    DESCRIPTION
        "Module Compliance"

    MODULE      -- this module

        MANDATORY-GROUPS
                { dfl1660SystemObjectGroup,
                  dfl1660IPsecObjectGroup,
                  dfl1660StateCountersGroup,
                  dfl1660IPPoolGroup,
                  dfl1660DHCPServerGroup,
                  dfl1660RuleUseGroup,
                  dfl1660UserAuthGroup,
                  dfl1660IfStatsGroup,
                  dfl1660LinkMonitorGroup,
                  dfl1660PipesObjectGroup,
                  dfl1660DHCPRelayObjectGroup,
                  dfl1660AlgGroup,
                  dfl1660HAGroup,
                  dfl1660IfVlanGroup,
                  dfl1660SmtpAlgGroup,
                  dfl1660SysTCPGroup }

    ::= { dfl1660StatsConformance 1 }

END -- end of module DFL1660-MIB.
