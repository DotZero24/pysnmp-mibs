SW3x50PRIMGMT-MIB    DEFINITIONS ::= BEGIN

    IMPORTS
        MODULE-IDENTITY             FROM SNMPv2-SMI
        dlink-mgmt,dlink-products   FROM DLINK-ID-REC-MIB;

--
--  DES-3x50 Series
--
    dlink-Des3x50SeriesProd OBJECT IDENTIFIER ::= { dlink-products 52 }
    dlink-Des3x50Prod	OBJECT IDENTIFIER ::= { dlink-Des3x50SeriesProd 1 }

    dlink-Des3x50Prod-Des3250		OBJECT IDENTIFIER ::= { dlink-Des3x50Prod 1 }
    dlink-Des3x50Prod-Des3350		OBJECT IDENTIFIER ::= { dlink-Des3x50Prod 2 }
    dlink-Des3x50Prod-Des3550	    OBJECT IDENTIFIER ::= { dlink-Des3x50Prod 3 }

    des3x50DevRegistration  OBJECT IDENTIFIER ::= { dlink-Des3x50SeriesProd 2 }
        des3x50Device    	OBJECT IDENTIFIER ::= { des3x50DevRegistration 1 }

    des3x50UnitRegistration    	OBJECT IDENTIFIER ::= { dlink-Des3x50SeriesProd 3 }
        des3x50Unit	    		OBJECT IDENTIFIER ::= { des3x50UnitRegistration 1 }

    des3x50ModuleRegistration    	OBJECT IDENTIFIER ::= { dlink-Des3x50SeriesProd 4 }
		des3x50-Module-Mainboard-48Port			OBJECT IDENTIFIER ::= { des3x50ModuleRegistration 1 }
		des3x50-Module-1-Port-GBIC     			OBJECT IDENTIFIER ::= { des3x50ModuleRegistration 2 }

    des3x50PortRegistration 		OBJECT IDENTIFIER ::= { dlink-Des3x50SeriesProd 5 }
        des3x50-Port-10-100-TX		        OBJECT IDENTIFIER ::= { des3x50PortRegistration 1 }
		des3x50-Port-1000-SX-GBIC			OBJECT IDENTIFIER ::= { des3x50PortRegistration 2 }
		des3x50-Port-1000-LX-GBIC			OBJECT IDENTIFIER ::= { des3x50PortRegistration 3 }
		des3x50-Port-1000-TX				OBJECT IDENTIFIER ::= { des3x50PortRegistration 4 }

    des3x50SlotRegistration    	OBJECT IDENTIFIER ::= { dlink-Des3x50SeriesProd 6 }
        des3x50Slot1			OBJECT IDENTIFIER ::= { des3x50SlotRegistration 1 }


END
