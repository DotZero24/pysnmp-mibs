-- ----------------------------------------------------------------------------
-- proprietary management MIB
-- ----------------------------------------------------------------------------

SW3600PRIMGMT-MIB    DEFINITIONS ::= BEGIN

    IMPORTS
        MODULE-IDENTITY             FROM SNMPv2-SMI
        dlink-products   FROM DLINK-ID-REC-MIB;

    	dXS-3600Series   	OBJECT IDENTIFIER ::= { dlink-products 127 }
			dXS-3600-32S			OBJECT IDENTIFIER ::= { dXS-3600Series 1 }
            dXS-3600-16S			OBJECT IDENTIFIER ::= { dXS-3600Series 2 }






END
