--  *****************************************************************
--  DLINKPRIME-SAFEGUARD-ENGINE-MIB.mib : Safeguard Engine Configuration MIB
--
--  Copyright (c) 2014 D-Link Corporation, all rights reserved.
--
--  *****************************************************************

	DLINKPRIME-SAFEGUARD-ENGINE-MIB DEFINITIONS ::= BEGIN

		IMPORTS
			OBJECT-GROUP, MODULE-COMPLIANCE
				FROM SNMPv2-CONF
			Integer32, Counter32, OBJECT-TYPE, MODULE-IDENTITY
				FROM SNMPv2-SMI
			TruthValue,
			RowStatus,
			TEXTUAL-CONVENTION
				FROM SNMPv2-TC
			dlinkPrimeCommon
				FROM DLINK-ID-REC-MIB;

		dlinkPrimeSafeguardEngineMIB MODULE-IDENTITY
			LAST-UPDATED "201404260000Z"
            ORGANIZATION "D-Link Corp."
            CONTACT-INFO
                "        D-Link Corporation

                 Postal: No. 289, Sinhu 3rd Rd., Neihu District,
                         Taipei City 114, Taiwan, R.O.C
                 Tel:     +886-2-66000123
                 E-mail: tsd@dlink.com.tw
                "
			DESCRIPTION
				"The MIB module for managing Safeguard engine."
			REVISION        "201404260000Z"
            DESCRIPTION
                "Initial version of this MIB module."
			::= { dlinkPrimeCommon 14 }

--
-- Node definitions
--

		dpSafeguardEngineMIBNotif        OBJECT IDENTIFIER ::= { dlinkPrimeSafeguardEngineMIB 0 }
		dpSafeguardEngineMIBObjects      OBJECT IDENTIFIER ::= { dlinkPrimeSafeguardEngineMIB 1 }
		dpSafeguardEngineMIBConformance  OBJECT IDENTIFIER ::= { dlinkPrimeSafeguardEngineMIB 2 }

--  ***************************************************************************
--  Safeguard-Engine
--  ***************************************************************************

		dpSafeguardEngineState OBJECT-TYPE
			SYNTAX      INTEGER
				{ 	enable(1),
				    disable(2)
				}
			MAX-ACCESS read-write
			STATUS current
			DESCRIPTION
				"This object is used to configure and show the state of Safeguard Engine."
			DEFVAL      { disable }
			::= { dpSafeguardEngineMIBObjects 1 }

	END
