-- D-Link Common MIBs
-- DLINK-ID-REC
-- -----------------------------------------------------------------------------
-- Version X.X, 2016/2/11
-- This is compilation of multiple different DLINK-ID-REC-MIB files
-- by Mike Stupalov
-- -----------------------------------------------------------------------------
-- Version 1.4, 2014/4/24
-- Add dlinkPrimeCommon for DGS1100 serial product.
-- by Al Fu
-- -----------------------------------------------------------------------------
-- Version 1.3, 2009/1/15
-- Modify syntax of AgentNotifyLevel
-- for support 8 notification levels.
-- by Green Zhu
-- -----------------------------------------------------------------------------
-- Version 1.2, 2008/8/11
-- Add dlink-broadband-products and dlink-broadband-mgmt.
-- by Green Zhu
-- -----------------------------------------------------------------------------
-- Version 1.1, 2004/7/6
-- Modify syntax of AgentNotifyLevel
-- by Karen
-- -----------------------------------------------------------------------------
-- Version 1.0.12  01-29-2002
-- -----------------------------------------------------------------------------
DLINK-ID-REC-MIB    DEFINITIONS ::= BEGIN
    IMPORTS
        enterprises    FROM RFC1155-SMI;

    AgentNotifyLevel ::= TEXTUAL-CONVENTION
        STATUS  current
        DESCRIPTION
        	"Notification  leveling."
        SYNTAX  INTEGER {
        	critical(0),
        	warning(1),
        	information(2),
        	emergency(3),
        	alert(4),
        	error(5),
        	notice(6),
            debug(7)
     }

    dlink    				OBJECT IDENTIFIER ::= { enterprises 171 }
    dlink-products    		OBJECT IDENTIFIER ::= { dlink 10 }
    dlink-mgmt    			OBJECT IDENTIFIER ::= { dlink 11 }
    dlink-common-mgmt    	OBJECT IDENTIFIER ::= { dlink 12 }
    dlinkIndustrialCommon   OBJECT IDENTIFIER ::= { dlink 14 }
    dlinkPrimeCommon        OBJECT IDENTIFIER ::= { dlink 15 }
    dlink-broadband-products  OBJECT IDENTIFIER ::= { dlink 30 }
    dlink-broadband-mgmt 	  OBJECT IDENTIFIER ::= { dlink 31 }


    dlink-Des3624Prod    	OBJECT IDENTIFIER ::= { dlink-products 25 }
    -- swProperty    			OBJECT IDENTIFIER ::= { dlink-Des3624Prod 1 }
    -- swModule    			OBJECT IDENTIFIER ::= { swProperty 1 }


--
--  3624 registration
--

    des3624DevRegistration  OBJECT IDENTIFIER ::= { dlink-Des3624Prod 2 }
        des3624Device    	OBJECT IDENTIFIER ::= { des3624DevRegistration 1 }

    des3624UnitRegistration OBJECT IDENTIFIER ::= { dlink-Des3624Prod 3 }
        des3624Master    	OBJECT IDENTIFIER ::= { des3624UnitRegistration 1 }
        des3624Slave1    	OBJECT IDENTIFIER ::= { des3624UnitRegistration 2 }
        des3624Slave2    	OBJECT IDENTIFIER ::= { des3624UnitRegistration 3 }
        des3624Slave3    	OBJECT IDENTIFIER ::= { des3624UnitRegistration 4 }

    des3624ModuleRegistration    	OBJECT IDENTIFIER ::= { dlink-Des3624Prod 4 }
        des3624ModuleMainboardTx 	OBJECT IDENTIFIER ::= { des3624ModuleRegistration 1 }
        des3624ModuleTxTwoPort		OBJECT IDENTIFIER ::= { des3624ModuleRegistration 2 }
        des3624ModuleFxSC    		OBJECT IDENTIFIER ::= { des3624ModuleRegistration 3 }
        des3624ModuleFxMTRJ    		OBJECT IDENTIFIER ::= { des3624ModuleRegistration 4 }
        des3624ModuleSIO    		OBJECT IDENTIFIER ::= { des3624ModuleRegistration 5 }
        des3624ModuleSXGIGAOnePort  OBJECT IDENTIFIER ::= { des3624ModuleRegistration 6 }
        des3624ModuleSXGIGATwoPort  OBJECT IDENTIFIER ::= { des3624ModuleRegistration 7 }
        des3624ModuleLXGIGAOnePort  OBJECT IDENTIFIER ::= { des3624ModuleRegistration 8 }
        des3624ModuleLXGIGATwoPort  OBJECT IDENTIFIER ::= { des3624ModuleRegistration 9 }
        des3624ModuleNone    		OBJECT IDENTIFIER ::= { des3624ModuleRegistration 10 }

--
--   3225G registration
--

    dlink-Des3225gProd      		OBJECT IDENTIFIER ::= { dlink-products 24 }

    des3225gDevRegistration			OBJECT IDENTIFIER ::= { dlink-Des3225gProd 2 }
        des3225gDevice    			OBJECT IDENTIFIER ::= { des3225gDevRegistration 1 }

    des3225gUnitRegistration    	OBJECT IDENTIFIER ::= { dlink-Des3225gProd 3 }
        des3225gUnit	    		OBJECT IDENTIFIER ::= { des3225gUnitRegistration 1 }

    des3225gModuleRegistration    	OBJECT IDENTIFIER ::= { dlink-Des3225gProd 4 }
        des3225gModule-Mainboard-22Port	OBJECT IDENTIFIER ::= { des3225gModuleRegistration 1 }
		des3225gModule-362TX-2Ports		OBJECT IDENTIFIER ::= { des3225gModuleRegistration 2 }
		des3225gModule-361FX-1Port		OBJECT IDENTIFIER ::= { des3225gModuleRegistration 3 }
		des3225gModule-362FM-2Ports		OBJECT IDENTIFIER ::= { des3225gModuleRegistration 4 }
		des3225gModule-3251G-1Port		OBJECT IDENTIFIER ::= { des3225gModuleRegistration 5 }
		des3225gModule-3251GL-1Port		OBJECT IDENTIFIER ::= { des3225gModuleRegistration 6 }
		des3225gModule-321GT-1Port		OBJECT IDENTIFIER ::= { des3225gModuleRegistration 7 }

    des3225gPortRegistration 		OBJECT IDENTIFIER ::= { dlink-Des3225gProd 5 }
        des3225gPort-10-100TX	    OBJECT IDENTIFIER ::= { des3225gPortRegistration 1 }
        des3225gPort-100-SC			OBJECT IDENTIFIER ::= { des3225gPortRegistration 2 }
        des3225gPort-100-MTRJ	    OBJECT IDENTIFIER ::= { des3225gPortRegistration 3 }
        des3225gPort-1000-SX	    OBJECT IDENTIFIER ::= { des3225gPortRegistration 4 }
        des3225gPort-1000-LX	    OBJECT IDENTIFIER ::= { des3225gPortRegistration 5 }
        des3225gPort-1000-TX	    OBJECT IDENTIFIER ::= { des3225gPortRegistration 6 }

    des3225gPowerSupplyRegistration OBJECT IDENTIFIER ::= { dlink-Des3225gProd 6 }
        des3225gPowerSupply    		OBJECT IDENTIFIER ::= { des3225gPowerSupplyRegistration 1 }

    des3225gFanRegistration    		OBJECT IDENTIFIER ::= { dlink-Des3225gProd 7 }
        des3225gFan   				OBJECT IDENTIFIER ::= { des3225gFanRegistration 1 }

    des3225gSlotRegistration    	OBJECT IDENTIFIER ::= { dlink-Des3225gProd 8 }
        des3225gSlot1			OBJECT IDENTIFIER ::= { des3225gSlotRegistration 1 }
        des3225gSlot2    		OBJECT IDENTIFIER ::= { des3225gSlotRegistration 2 }

    des3225gSensorRegistration		OBJECT IDENTIFIER ::= { dlink-Des3225gProd 9 }

    des3225gBackplaneRegistration	OBJECT IDENTIFIER ::= { dlink-Des3225gProd 10 }

--
--  3124 registration
--

    dlink-Des3124Prod       			OBJECT IDENTIFIER ::= { dlink-products 19 }

    des3124DevRegistration    			OBJECT IDENTIFIER ::= { dlink-Des3124Prod 2 }
        des3124Device    				OBJECT IDENTIFIER ::= { des3124DevRegistration 1 }

    des3124UnitRegistration    			OBJECT IDENTIFIER ::= { dlink-Des3124Prod 3 }
        des3124Unit	    				OBJECT IDENTIFIER ::= { des3124UnitRegistration 1 }

    des3124ModuleRegistration    		OBJECT IDENTIFIER ::= { dlink-Des3124Prod 4 }
        des3124Module-Mainboard-24Ports	OBJECT IDENTIFIER ::= { des3124ModuleRegistration 1 }
		des3124Module-NMM				OBJECT IDENTIFIER ::= { des3124ModuleRegistration 2 }

    des3124PortRegistration 			OBJECT IDENTIFIER ::= { dlink-Des3124Prod 5 }
        des3124Port-10-100TX	    	OBJECT IDENTIFIER ::= { des3124PortRegistration 1 }

    des3124PowerSupplyRegistration 		OBJECT IDENTIFIER ::= { dlink-Des3124Prod 6 }
        des3124PowerSupply    			OBJECT IDENTIFIER ::= { des3124PowerSupplyRegistration 1 }

    des3124FanRegistration    			OBJECT IDENTIFIER ::= { dlink-Des3124Prod 7 }
        des3124Fan   					OBJECT IDENTIFIER ::= { des3124FanRegistration 1 }

--
--  3126 registration
--

    dlink-Des3126Prod      		OBJECT IDENTIFIER ::= { dlink-products 29 }

    des3126DevRegistration			OBJECT IDENTIFIER ::= { dlink-Des3126Prod 2 }
        des3126Device    			OBJECT IDENTIFIER ::= { des3126DevRegistration 1 }

    des3126UnitRegistration    	OBJECT IDENTIFIER ::= { dlink-Des3126Prod 3 }
        des3126Unit	    		OBJECT IDENTIFIER ::= { des3126UnitRegistration 1 }

    des3126ModuleRegistration    	OBJECT IDENTIFIER ::= { dlink-Des3126Prod 4 }
        des3126Module-Mainboard-22Port	OBJECT IDENTIFIER ::= { des3126ModuleRegistration 1 }
		des3126Module-362TX-2Ports		OBJECT IDENTIFIER ::= { des3126ModuleRegistration 2 }
		des3126Module-361FX-1Port		OBJECT IDENTIFIER ::= { des3126ModuleRegistration 3 }
		des3126Module-362FM-2Ports		OBJECT IDENTIFIER ::= { des3126ModuleRegistration 4 }
		des3126Module-361G-1Port		OBJECT IDENTIFIER ::= { des3126ModuleRegistration 5 }
		des3126Module-361GL-1Port		OBJECT IDENTIFIER ::= { des3126ModuleRegistration 6 }
		des3126Module-361GT-1Port		OBJECT IDENTIFIER ::= { des3126ModuleRegistration 7 }
		des3126Module-362G-2Port		OBJECT IDENTIFIER ::= { des3126ModuleRegistration 8 }
		des3126Module-362GL-2Port		OBJECT IDENTIFIER ::= { des3126ModuleRegistration 9 }
		des3126Module-362GT-2Port		OBJECT IDENTIFIER ::= { des3126ModuleRegistration 10 }

    des3126PortRegistration 		OBJECT IDENTIFIER ::= { dlink-Des3126Prod 5 }
        des3126Port-10-100TX	    OBJECT IDENTIFIER ::= { des3126PortRegistration 1 }
        des3126Port-100-SC			OBJECT IDENTIFIER ::= { des3126PortRegistration 2 }
        des3126Port-100-MTRJ	    OBJECT IDENTIFIER ::= { des3126PortRegistration 3 }
        des3126Port-1000-SX	    OBJECT IDENTIFIER ::= { des3126PortRegistration 4 }
        des3126Port-1000-LX	    OBJECT IDENTIFIER ::= { des3126PortRegistration 5 }
        des3126Port-1000-TX	    OBJECT IDENTIFIER ::= { des3126PortRegistration 6 }

    des3126PowerSupplyRegistration OBJECT IDENTIFIER ::= { dlink-Des3126Prod 6 }
        des3126PowerSupply    		OBJECT IDENTIFIER ::= { des3126PowerSupplyRegistration 1 }

    des3126FanRegistration    		OBJECT IDENTIFIER ::= { dlink-Des3126Prod 7 }
        des3126Fan   				OBJECT IDENTIFIER ::= { des3126FanRegistration 1 }

    des3126SlotRegistration    	OBJECT IDENTIFIER ::= { dlink-Des3126Prod 8 }
        des3126Slot1			OBJECT IDENTIFIER ::= { des3126SlotRegistration 1 }
        des3126Slot2    		OBJECT IDENTIFIER ::= { des3126SlotRegistration 2 }

    des3126SensorRegistration		OBJECT IDENTIFIER ::= { dlink-Des3126Prod 9 }

    des3126BackplaneRegistration	OBJECT IDENTIFIER ::= { dlink-Des3126Prod 10 }

--
--  3208 registration
--
    dlink-DGS3208Prod       OBJECT IDENTIFIER ::= { dlink-products 23 }

    dgs3208DevRegistration           OBJECT IDENTIFIER ::= { dlink-DGS3208Prod 2 }
        dgs3208Device                    OBJECT IDENTIFIER ::= { dgs3208DevRegistration 1 }

    dgs3208UnitRegistration          OBJECT IDENTIFIER ::= { dlink-DGS3208Prod 3 }
        dgs3208Unit                      OBJECT IDENTIFIER ::= { dgs3208UnitRegistration 1 }

    dgs3208ModuleRegistration       OBJECT IDENTIFIER ::= { dlink-DGS3208Prod 4 }
        dgs3208Module-Mainboard-8Port  OBJECT IDENTIFIER ::= { dgs3208ModuleRegistration 1 }
        dgs3208Module-Mainboard-6Port  OBJECT IDENTIFIER ::= { dgs3208ModuleRegistration 2 }
        dgs3208Module-GBIC-SX          OBJECT IDENTIFIER ::= { dgs3208ModuleRegistration 3 }
        dgs3208Module-GBIC-LX          OBJECT IDENTIFIER ::= { dgs3208ModuleRegistration 4 }
        dgs3208Module-GBIC-LH          OBJECT IDENTIFIER ::= { dgs3208ModuleRegistration 5 }

    dgs3208PortRegistration       OBJECT IDENTIFIER ::= { dlink-DGS3208Prod 5 }
        dgs3208Port-1000-SX             OBJECT IDENTIFIER ::= { dgs3208PortRegistration 1 }
        dgs3208Port-1000-LX             OBJECT IDENTIFIER ::= { dgs3208PortRegistration 2 }
        dgs3208Port-100-1000-TX         OBJECT IDENTIFIER ::= { dgs3208PortRegistration 3 }

    dgs3208PowerSupplyRegistration  OBJECT IDENTIFIER ::= { dlink-DGS3208Prod 6 }
        dgs3208PowerSupply              OBJECT IDENTIFIER ::= { dgs3208PowerSupplyRegistration 1 }

    dgs3208FanRegistration          OBJECT IDENTIFIER ::= { dlink-DGS3208Prod 7 }
        dgs3208Fan                      OBJECT IDENTIFIER ::= { dgs3208FanRegistration 1 }

    dgs3208SlotRegistration         OBJECT IDENTIFIER ::= { dlink-DGS3208Prod 8 }
        dgs3208Slot1                    OBJECT IDENTIFIER ::= { dgs3208SlotRegistration 1 }
        dgs3208Slot2                    OBJECT IDENTIFIER ::= { dgs3208SlotRegistration 2 }
--
--    The Des6000 ID Record
--

    dlink-Des6000Prod   OBJECT IDENTIFIER ::= { dlink-products 28 }

    	-- swProperty          OBJECT IDENTIFIER ::= { dlink-Des6000Prod 1 }
        -- swModule        OBJECT IDENTIFIER ::= { swProperty 1 }

    des6000DevRegistration  OBJECT IDENTIFIER ::= { dlink-Des6000Prod 2 }
        des6000Device       OBJECT IDENTIFIER ::= { des6000DevRegistration 1 }

    des6000UnitRegistration OBJECT IDENTIFIER ::= { dlink-Des6000Prod 3 }
        des6000Main         OBJECT IDENTIFIER ::= { des6000UnitRegistration 1 }

-- Modify by Jim Liu 2000-8-15 04:53PM
    des6000ModuleRegistration   OBJECT IDENTIFIER ::= { dlink-Des6000Prod 4 }
        des6000ModuleTx          OBJECT IDENTIFIER ::= { des6000ModuleRegistration 1 }
        des6000ModuleFx          OBJECT IDENTIFIER ::= { des6000ModuleRegistration 2 }
        des6000ModuleGIGAMTRJSX  OBJECT IDENTIFIER ::= { des6000ModuleRegistration 3 }
        des6000ModuleGIGAMTRJLX  OBJECT IDENTIFIER ::= { des6000ModuleRegistration 4 }
        des6000ModuleGIGASCSX    OBJECT IDENTIFIER ::= { des6000ModuleRegistration 5 }
        des6000ModuleGIGASCLX    OBJECT IDENTIFIER ::= { des6000ModuleRegistration 6 }
        des6000ModuleGIGATX      OBJECT IDENTIFIER ::= { des6000ModuleRegistration 7 }
        des6000ModuleCPUMaster   OBJECT IDENTIFIER ::= { des6000ModuleRegistration 8 }
        des6000ModuleCPUBackup   OBJECT IDENTIFIER ::= { des6000ModuleRegistration 9 }
        des6000ModuleNone        OBJECT IDENTIFIER ::= { des6000ModuleRegistration 10 }

    des6000PortRegistration    OBJECT IDENTIFIER ::= { dlink-Des6000Prod 5 }
        des6000Port-10-100TX    OBJECT IDENTIFIER ::= { des6000PortRegistration 1 }
        des6000Port-100-MTRJ    OBJECT IDENTIFIER ::= { des6000PortRegistration 2 }
        des6000Port-1000-SX-MTRJ    OBJECT IDENTIFIER ::= { des6000PortRegistration 3 }
        des6000Port-1000-LX-MTRJ    OBJECT IDENTIFIER ::= { des6000PortRegistration 4 }
        des6000Port-1000-SX-SC    OBJECT IDENTIFIER ::= { des6000PortRegistration 5 }
        des6000Port-1000-LX-SC    OBJECT IDENTIFIER ::= { des6000PortRegistration 6 }
        des6000Port-1000-TX    OBJECT IDENTIFIER ::= { des6000PortRegistration 7 }

    des6000PowerSupplyRegistration    OBJECT IDENTIFIER ::= { dlink-Des6000Prod 6 }
        des6000PowerSupply1    	OBJECT IDENTIFIER ::= { des6000PowerSupplyRegistration 1 }
        des6000PowerSupply2    	OBJECT IDENTIFIER ::= { des6000PowerSupplyRegistration 2 }

    des6000FanRegistration    OBJECT IDENTIFIER ::= { dlink-Des6000Prod 7 }
        des6000Fan1    OBJECT IDENTIFIER ::= { des6000FanRegistration 1 }
        des6000Fan2    OBJECT IDENTIFIER ::= { des6000FanRegistration 2 }
        des6000Fan3    OBJECT IDENTIFIER ::= { des6000FanRegistration 3 }
        des6000Fan4    OBJECT IDENTIFIER ::= { des6000FanRegistration 4 }

    des6000SlotRegistration    OBJECT IDENTIFIER ::= { dlink-Des6000Prod 8 }
        des6000Slot1    OBJECT IDENTIFIER ::= { des6000SlotRegistration 1 }
        des6000Slot2    OBJECT IDENTIFIER ::= { des6000SlotRegistration 2 }
        des6000Slot3    OBJECT IDENTIFIER ::= { des6000SlotRegistration 3 }
        des6000Slot4    OBJECT IDENTIFIER ::= { des6000SlotRegistration 4 }
        des6000Slot5    OBJECT IDENTIFIER ::= { des6000SlotRegistration 5 }
        des6000Slot6    OBJECT IDENTIFIER ::= { des6000SlotRegistration 6 }
        des6000Slot7    OBJECT IDENTIFIER ::= { des6000SlotRegistration 7 }
        des6000Slot8    OBJECT IDENTIFIER ::= { des6000SlotRegistration 8 }
        des6000CPUSlot    OBJECT IDENTIFIER ::= { des6000SlotRegistration 9 }
        des6000SysFan1Socket    OBJECT IDENTIFIER ::= { des6000SlotRegistration 10 }
        des6000SysFan2Socket    OBJECT IDENTIFIER ::= { des6000SlotRegistration 11 }
        des6000SysFan3Socket    OBJECT IDENTIFIER ::= { des6000SlotRegistration 12 }
        des6000SysFan4Socket    OBJECT IDENTIFIER ::= { des6000SlotRegistration 13 }
        des6000Power1Socket    OBJECT IDENTIFIER ::= { des6000SlotRegistration 14 }
        des6000Power2Socket    OBJECT IDENTIFIER ::= { des6000SlotRegistration 15 }

    des6000BackplaneRegistration    OBJECT IDENTIFIER ::= { dlink-Des6000Prod 9 }
        des6000Backplane    	OBJECT IDENTIFIER ::= { des6000BackplaneRegistration 1 }

    des6000SensorRegistration    OBJECT IDENTIFIER ::= { dlink-Des6000Prod 10 }

--  End of DES6000 Registration

--
--   DES3326 series Product , Add by WindChen, 1-4-2001
--

    dlink-Des3326SeriesProd   OBJECT IDENTIFIER ::= { dlink-products 32 }
    dlink-Des3326sProd		OBJECT IDENTIFIER ::= { dlink-Des3326SeriesProd 2 }

    --swProperty          OBJECT IDENTIFIER ::= { dlink-Des3326sProd 1 }
    --    swModule        OBJECT IDENTIFIER ::= { swProperty 1 }

    des3326sDevRegistration  OBJECT IDENTIFIER ::= { dlink-Des3326sProd 2 }
        des3326sDevice       OBJECT IDENTIFIER ::= { des3326sDevRegistration 1 }

    des3326sUnitRegistration OBJECT IDENTIFIER ::= { dlink-Des3326sProd 3 }
        des3326sMain         OBJECT IDENTIFIER ::= { des3326sUnitRegistration 1 }

-- Modify by Jim Liu 2000-8-15 04:53PM
    des3326sModuleRegistration   OBJECT IDENTIFIER ::= { dlink-Des3326sProd 4 }

        des3326sModuleGIGASCSX    OBJECT IDENTIFIER ::= { des3326sModuleRegistration 1 }
        des3326sModuleGIGASCLX    OBJECT IDENTIFIER ::= { des3326sModuleRegistration 2 }
        des3326sModuleGIGATX      OBJECT IDENTIFIER ::= { des3326sModuleRegistration 3 }
        des3326sModuleGBIC        OBJECT IDENTIFIER ::= { des3326sModuleRegistration 4 }


    des3326sPortRegistration    OBJECT IDENTIFIER ::= { dlink-Des3326sProd 5 }
        des3326sPort-10-100TX    OBJECT IDENTIFIER ::= { des3326sPortRegistration 1 }
        des3326sPort-1000-SX    OBJECT IDENTIFIER ::= { des3326sPortRegistration 2 }
        des3326sPort-1000-TX    OBJECT IDENTIFIER ::= { des3326sPortRegistration 3 }

--
--   DHS3226 series Product
--

    dlink-Dhs3226SeriesProd		OBJECT IDENTIFIER ::= { dlink-products 36 }
    dlink-Dhs3226Prod			OBJECT IDENTIFIER ::= { dlink-Dhs3226SeriesProd 1 }
    dlink-Dhs3226Prod-Dhs3226			OBJECT IDENTIFIER ::= { dlink-Dhs3226SeriesProd 1 1 }
    dlink-Dhs3226Prod-Dhs3218			OBJECT IDENTIFIER ::= { dlink-Dhs3226SeriesProd 1 2 }
    dlink-Dhs3226Prod-Dhs3210			OBJECT IDENTIFIER ::= { dlink-Dhs3226SeriesProd 1 3 }
    dlink-Dhs3226Prod-Des3226			OBJECT IDENTIFIER ::= { dlink-Dhs3226SeriesProd 1 11 }
    dlink-Dhs3226Prod-Des3218			OBJECT IDENTIFIER ::= { dlink-Dhs3226SeriesProd 1 12 }
    dlink-Dhs3226Prod-Des3210			OBJECT IDENTIFIER ::= { dlink-Dhs3226SeriesProd 1 13 }

    dhs3226DevRegistration		OBJECT IDENTIFIER ::= { dlink-Dhs3226Prod 2 }
        dhs3226Device			OBJECT IDENTIFIER ::= { dhs3226DevRegistration 1 }

    dhs3226UnitRegistration		OBJECT IDENTIFIER ::= { dlink-Dhs3226Prod 3 }
        dhs3226Unit				OBJECT IDENTIFIER ::= { dhs3226UnitRegistration 1 }

    dhs3226ModuleRegistration   OBJECT IDENTIFIER ::= { dlink-Dhs3226Prod 4 }
		dhs3226-Module-Mainboard-24Port			OBJECT IDENTIFIER ::= { dhs3226ModuleRegistration 1 }
		dhs3226-Module-1-Port-100-FX			OBJECT IDENTIFIER ::= { dhs3226ModuleRegistration 2 }
		dhs3226-Module-2-Port-100-FX			OBJECT IDENTIFIER ::= { dhs3226ModuleRegistration 3 }
		dhs3226-Module-1-Port-100-FL			OBJECT IDENTIFIER ::= { dhs3226ModuleRegistration 4 }
		dhs3226-Module-2-Port-100-FL			OBJECT IDENTIFIER ::= { dhs3226ModuleRegistration 5 }
		dhs3226-Module-2-Port-1000-SX			OBJECT IDENTIFIER ::= { dhs3226ModuleRegistration 6 }
		dhs3226-Module-2-Port-1000-LX			OBJECT IDENTIFIER ::= { dhs3226ModuleRegistration 7 }
		dhs3226-Module-2-Port-1000-TX			OBJECT IDENTIFIER ::= { dhs3226ModuleRegistration 8 }
		dhs3226-Module-2-Port-GBIC				OBJECT IDENTIFIER ::= { dhs3226ModuleRegistration 9 }
		dhs3226-Module-Mainboard-8Port			OBJECT IDENTIFIER ::= { dhs3226ModuleRegistration 10 }
		dhs3226-Module-Mainboard-16Port			OBJECT IDENTIFIER ::= { dhs3226ModuleRegistration 11 }
		dhs3226-Module-2-Port-100-TX			OBJECT IDENTIFIER ::= { dhs3226ModuleRegistration 12 }

    dhs3226PortRegistration    OBJECT IDENTIFIER ::= { dlink-Dhs3226Prod 5 }
        dhs3226-Port-10-100-TX				OBJECT IDENTIFIER ::= { dhs3226PortRegistration 1 }
		dhs3226-Port-100-FX					OBJECT IDENTIFIER ::= { dhs3226PortRegistration 2 }
		dhs3226-Port-100-FL					OBJECT IDENTIFIER ::= { dhs3226PortRegistration 3 }
		dhs3226-Port-1000-SX				OBJECT IDENTIFIER ::= { dhs3226PortRegistration 4 }
		dhs3226-Port-1000-LX				OBJECT IDENTIFIER ::= { dhs3226PortRegistration 5 }
		dhs3226-Port-1000-TX				OBJECT IDENTIFIER ::= { dhs3226PortRegistration 6 }
		dhs3226-Port-GBIC					OBJECT IDENTIFIER ::= { dhs3226PortRegistration 7 }
		dhs3226-Port-100-TX					OBJECT IDENTIFIER ::= { dhs3226PortRegistration 8 }

    dhs3226SlotRegistration    	OBJECT IDENTIFIER ::= { dlink-Dhs3226Prod 6 }
        dhs3226Slot1			OBJECT IDENTIFIER ::= { dhs3226SlotRegistration 1 }

END
