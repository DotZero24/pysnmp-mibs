--
-- DNS345.mib
--

-- Copyright (c) 2001-2011 alphanetworks Inc.,
-- Module Name: DNS345.mib
-- Abstract:
-- Defines the DNS345 NAS MIBs .
--
-- Renamed from NAS-MIB to DNS345-MIB by Observium developers.
--

	DNS345-MIB DEFINITIONS ::= BEGIN


	IMPORTS
		OBJECT-TYPE, Integer32, enterprises,
		NOTIFICATION-TYPE
			FROM SNMPv2-SMI
		DisplayString
			FROM SNMPv2-TC;

--
--  OID definitions
--

	d-link		OBJECT IDENTIFIER ::= { enterprises 171}
	productID	OBJECT IDENTIFIER ::= { d-link 50}
	projectID	OBJECT IDENTIFIER ::= { productID 1}
	modelID 	OBJECT IDENTIFIER ::= { projectID 5}
	submodelID	OBJECT IDENTIFIER ::= { modelID 1}
	nasAgent	OBJECT IDENTIFIER ::= { submodelID 1}


--
-- Node definitions
--
			dns345AgentVer OBJECT-TYPE
				SYNTAX DisplayString
				MAX-ACCESS read-only
				STATUS current
				DESCRIPTION
					"Version information for the agent of SNMP of DNS345."
				::= { nasAgent 1 }

-- ============================================================================

--
-- system information definitions
--
			dns345SoftwareVersion OBJECT-TYPE
				SYNTAX DisplayString
				MAX-ACCESS read-only
				STATUS current
				DESCRIPTION
					"The device software version."
				::= { nasAgent 2 }

			dns345HostName OBJECT-TYPE
				SYNTAX DisplayString
				MAX-ACCESS read-only
				STATUS current
				DESCRIPTION
					"The device host name."
				::= { nasAgent 3 }


			dns345FTPServer OBJECT-TYPE
				SYNTAX DisplayString
				MAX-ACCESS read-only
				STATUS current
				DESCRIPTION
					"Ftp Server status.
					1 : enable
					0 : disable
					"
				::= { nasAgent 5 }

			dns345NetType OBJECT-TYPE
				SYNTAX DisplayString
				MAX-ACCESS read-only
				STATUS current
				DESCRIPTION
					"The Network type.
					(	0 : Workgroup
						1 : Active Directory)"
				::= { nasAgent 6 }

			dns345Temperature OBJECT-TYPE
				SYNTAX DisplayString
				MAX-ACCESS read-only
				STATUS current
				DESCRIPTION
					"The temperature of the system."
				::= { nasAgent 7 }

			dns345FanStatus OBJECT-TYPE
				SYNTAX DisplayString
				MAX-ACCESS read-only
				STATUS current
				DESCRIPTION
					"The status of the fan0 & fan1."
				::= { nasAgent 8 }

-- ============================================================================

			dns345VolumeTable OBJECT-TYPE
			SYNTAX SEQUENCE OF Dns345VolumeEntry
			MAX-ACCESS not-accessible
			STATUS current
			DESCRIPTION
				"A table of active volumes on the NAS device."
			::= { nasAgent 9 }

			dns345VolumeEntry OBJECT-TYPE
			SYNTAX Dns345VolumeEntry
			MAX-ACCESS not-accessible
			STATUS current
			DESCRIPTION
				"An entry in the volume table."
			INDEX { dns345VolumeNum }
			::= { dns345VolumeTable 1 }

			Dns345VolumeEntry ::=
			SEQUENCE {
				dns345VolumeNum
					Integer32,
				dns345VolumeName
					DisplayString,
				dns345VolumeFsType
					DisplayString,
				dns345VolumeRaidLevel
					DisplayString,
				dns345VolumeSize
					DisplayString,
				dns345VolumeFreeSpace
					DisplayString
			 }

			dns345VolumeNum OBJECT-TYPE
			SYNTAX Integer32
			MAX-ACCESS read-only
			STATUS current
			DESCRIPTION
				"Instance number of the volume entry."
			::= { dns345VolumeEntry 1 }

			dns345VolumeName OBJECT-TYPE
			SYNTAX DisplayString
			MAX-ACCESS read-only
			STATUS current
			DESCRIPTION
				"The name of the volume."
			::= { dns345VolumeEntry 2 }

			dns345VolumeFsType OBJECT-TYPE
			SYNTAX DisplayString
			MAX-ACCESS read-only
			STATUS current
			DESCRIPTION
				"The type of file system of the volume.
				Example : ext3 or ext4"
			::= { dns345VolumeEntry 3 }

			dns345VolumeRaidLevel OBJECT-TYPE
			SYNTAX DisplayString
			MAX-ACCESS read-only
			STATUS current
			DESCRIPTION
				"The RAID level of the volume. (STANDARD LINEAR RAID0 RAID1 RAID5 RAID10 RAID5+SPARE)"
			::= { dns345VolumeEntry 4 }

			dns345VolumeSize OBJECT-TYPE
			SYNTAX DisplayString
			MAX-ACCESS read-only
			STATUS current
			DESCRIPTION
				"The size of the volume in bytes."
			::= { dns345VolumeEntry 5 }

			dns345VolumeFreeSpace OBJECT-TYPE
			SYNTAX DisplayString
			MAX-ACCESS read-only
			STATUS current
			DESCRIPTION
				"Free space on the volume in bytes."
			::= { dns345VolumeEntry 6 }

-- ============================================================================

		dns345DiskTable OBJECT-TYPE
			SYNTAX SEQUENCE OF Dns345DiskEntry
			MAX-ACCESS not-accessible
			STATUS current
			DESCRIPTION
				"A table of physical disks attached to the NAS device."
			::= { nasAgent 10 }

		dns345DiskEntry OBJECT-TYPE
			SYNTAX Dns345DiskEntry
			MAX-ACCESS not-accessible
			STATUS current
			DESCRIPTION
				"An entry in the physical disk table."
			INDEX { dns345DiskNum }
			::= { dns345DiskTable 1 }

		Dns345DiskEntry ::=
			SEQUENCE {
				dns345DiskNum
					Integer32,
				dns345DiskVendor
					DisplayString,
				dns345DiskModel
					DisplayString,
				dns345DiskSerialNumber
					DisplayString,
        		dns345DiskTemperature
					DisplayString,
				dns345DiskCapacity
					DisplayString
			 }

		dns345DiskNum OBJECT-TYPE
			SYNTAX Integer32
			MAX-ACCESS read-only
			STATUS current
			DESCRIPTION
				"Instance number of the disk entry."
			::= { dns345DiskEntry 1 }

		dns345DiskVendor OBJECT-TYPE
			SYNTAX DisplayString
			MAX-ACCESS read-only
			STATUS current
			DESCRIPTION
				"The vendor of the disk drive."
			::= { dns345DiskEntry 2 }

		dns345DiskModel OBJECT-TYPE
			SYNTAX DisplayString
			MAX-ACCESS read-only
			STATUS current
			DESCRIPTION
				"The disk drive's model name."
			::= { dns345DiskEntry 3 }

		dns345DiskSerialNumber OBJECT-TYPE
			SYNTAX DisplayString
			MAX-ACCESS read-only
			STATUS current
			DESCRIPTION
				"The disk drive's serial number."
			::= { dns345DiskEntry 4 }

		dns345DiskTemperature OBJECT-TYPE
			SYNTAX DisplayString
			MAX-ACCESS read-only
			STATUS current
			DESCRIPTION
				"The centigrade temperature of this disk."
			::= { dns345DiskEntry 5 }

		dns345DiskCapacity OBJECT-TYPE
			SYNTAX DisplayString
			MAX-ACCESS read-only
			STATUS current
			DESCRIPTION
				"The capacity of the disk in GB."
			::= { dns345DiskEntry 6 }

-- ============================================================================
--
--  Notifications
--

	notifyEvts OBJECT IDENTIFIER ::= { nasAgent 200 }

	notifyPasswdChanged        NOTIFICATION-TYPE
    STATUS      current
    DESCRIPTION
        "An indication that the Administrator's password has been changed."
    ::= { notifyEvts 1 }

    notifyFirmwareUpgraded     NOTIFICATION-TYPE
    STATUS      current
    DESCRIPTION
        "An indication that firmware has been upgraded."
    ::= { notifyEvts 2 }

    notifyNetworkChanged        NOTIFICATION-TYPE
    STATUS      current
    DESCRIPTION
        "An indication that the network settings has been changed."
    ::= { notifyEvts 3 }

    notifyTemperatureExceeded        NOTIFICATION-TYPE
    STATUS      current
    DESCRIPTION
        "An indication that system temperature has exceeded."
    ::= { notifyEvts 4 }







--              ******************************************************

--              ******************************************************


	END

--
-- DNS345.mib
--
