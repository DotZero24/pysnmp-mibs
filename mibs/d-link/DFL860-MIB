--
-- DFL-860 SMIv2 module
--

DFL860-MIB DEFINITIONS ::= BEGIN

IMPORTS
    MODULE-COMPLIANCE, OBJECT-GROUP
        FROM SNMPv2-CONF
    Counter32, Counter64, Gauge32, Integer32, MODULE-IDENTITY,
    OBJECT-TYPE, enterprises
        FROM SNMPv2-SMI
    DisplayString
        FROM SNMPv2-TC;

dfl860-MIB MODULE-IDENTITY
    LAST-UPDATED "201009021139Z"
    ORGANIZATION
        "D-Link Corporation"
    CONTACT-INFO
        "Postal: D-Link Corporation
         No. 289, Sinhu 3rd Road,
         Neihu District, Taipei City 114,
         Taiwan, R.O.C.
         Tel: +886-2-66000123
         Fax: +886-2-55509988"
    DESCRIPTION
        "The MIB module for D-Link DFL-860 series product."

    REVISION  "201009021139Z"
    DESCRIPTION
        "Added 64-bit counters"
    REVISION  "201003300900Z"
    DESCRIPTION
        "Added values for SMTP ALG objects."
    REVISION  "200911100916Z"
    DESCRIPTION
        "Added values for opened and closed connections per second"
    REVISION  "200811181605Z"
    DESCRIPTION
        "Added value for timer usage"
    REVISION  "200810141227Z"
    DESCRIPTION
        "Added values for memory usage and TCP buffer usage"
    REVISION  "200710310000Z"
    DESCRIPTION
        "Initial version."
    ::= { dfl860MibModules 2 }


dlink OBJECT IDENTIFIER
    ::= { enterprises 171 }

netdefendMgmt OBJECT IDENTIFIER
    ::= { dlink 20 }

utmFirewall OBJECT IDENTIFIER
    ::= { netdefendMgmt 2 }

dfl860 OBJECT IDENTIFIER
    ::= { utmFirewall 2 }

dfl860OS OBJECT IDENTIFIER
    ::= { dfl860 1 }

dfl860OSStats OBJECT IDENTIFIER
    ::= { dfl860OS 2 }

dfl860reg OBJECT IDENTIFIER
    ::= { dfl860 2 }

dfl860MibModules OBJECT IDENTIFIER
    ::= { dfl860reg 1 }

dfl860MibConfs OBJECT IDENTIFIER
    ::= { dfl860reg 2 }

dfl860MibObjectGroups OBJECT IDENTIFIER
    ::= { dfl860reg 3 }


dfl860System OBJECT IDENTIFIER
    ::= { dfl860OSStats 1 }

dfl860SysCpuLoad OBJECT-TYPE
    SYNTAX      Gauge32
    MAX-ACCESS  read-only
    STATUS      current
    DESCRIPTION
        "The system cpu load."
    ::= { dfl860System 1 }

dfl860SysForwardedBits OBJECT-TYPE
    SYNTAX      Counter32
    MAX-ACCESS  read-only
    STATUS      current
    DESCRIPTION
        "The number of bits forwarded through the gateway."
    ::= { dfl860System 2 }

dfl860SysForwardedPackets OBJECT-TYPE
    SYNTAX      Counter32
    MAX-ACCESS  read-only
    STATUS      current
    DESCRIPTION
        "Total number of forwarded packets."
    ::= { dfl860System 3 }

dfl860SysBuffUse OBJECT-TYPE
    SYNTAX      Gauge32
    MAX-ACCESS  read-only
    STATUS      current
    DESCRIPTION
        "The current number of buffers in use."
    ::= { dfl860System 4 }

dfl860SysConns OBJECT-TYPE
    SYNTAX      Gauge32
    MAX-ACCESS  read-only
    STATUS      current
    DESCRIPTION
        "The numer of connections."
    ::= { dfl860System 5 }

dfl860SysPerStateCounters OBJECT IDENTIFIER
    ::= { dfl860System 6 }

dfl860SysPscTcpSyn OBJECT-TYPE
    SYNTAX      Gauge32
    MAX-ACCESS  read-only
    STATUS      current
    DESCRIPTION
        "Number of TCP connections in the SYN state."
    ::= { dfl860SysPerStateCounters 1 }

dfl860SysPscTcpOpen OBJECT-TYPE
    SYNTAX      Gauge32
    MAX-ACCESS  read-only
    STATUS      current
    DESCRIPTION
        "Number of TCP connections in the OPEN state."
    ::= { dfl860SysPerStateCounters 2 }

dfl860SysPscTcpFin OBJECT-TYPE
    SYNTAX      Gauge32
    MAX-ACCESS  read-only
    STATUS      current
    DESCRIPTION
        "Number of TCP connections in the FIN state."
    ::= { dfl860SysPerStateCounters 3 }

dfl860SysPscUdp OBJECT-TYPE
    SYNTAX      Gauge32
    MAX-ACCESS  read-only
    STATUS      current
    DESCRIPTION
        "Number of UDP connections."
    ::= { dfl860SysPerStateCounters 4 }

dfl860SysPscIcmp OBJECT-TYPE
    SYNTAX      Gauge32
    MAX-ACCESS  read-only
    STATUS      current
    DESCRIPTION
        "Number of ICMP connections."
    ::= { dfl860SysPerStateCounters 5 }

dfl860SysPscOther OBJECT-TYPE
    SYNTAX      Gauge32
    MAX-ACCESS  read-only
    STATUS      current
    DESCRIPTION
        "Number of other connections."
    ::= { dfl860SysPerStateCounters 6 }

dfl860IfStatsTable OBJECT-TYPE
    SYNTAX      SEQUENCE OF Dfl860IfStatsEntry
    MAX-ACCESS  not-accessible
    STATUS      current
    DESCRIPTION
        "A table of DFL-860 specific interfaces statistics"
    ::= { dfl860System 7 }

dfl860IfStatsEntry OBJECT-TYPE
    SYNTAX      Dfl860IfStatsEntry
    MAX-ACCESS  not-accessible
    STATUS      current
    DESCRIPTION
        "The row in a table of DFL-860 specific interface statistics"
    INDEX       { dfl860IfStatsIndex }
    ::= { dfl860IfStatsTable 1 }

Dfl860IfStatsEntry ::= SEQUENCE {
    dfl860IfStatsIndex     Integer32,
    dfl860IfName           DisplayString,
    dfl860IfFragsIn        Counter32,
    dfl860IfFragReassOk    Counter32,
    dfl860IfFragReassFail  Counter32,
    dfl860IfPktsInCnt      Counter32,
    dfl860IfPktsOutCnt     Counter32,
    dfl860IfBitsInCnt      Counter32,
    dfl860IfBitsOutCnt     Counter32,
    dfl860IfPktsTotCnt     Counter32,
    dfl860IfBitsTotCnt     Counter32,
    dfl860IfHCPktsInCnt    Counter64,
    dfl860IfHCPktsOutCnt   Counter64,
    dfl860IfHCBitsInCnt    Counter64,
    dfl860IfHCBitsOutCnt   Counter64,
    dfl860IfHCPktsTotCnt   Counter64,
    dfl860IfHCBitsTotCnt   Counter64
}

dfl860IfStatsIndex OBJECT-TYPE
    SYNTAX      Integer32 (1..2147483647)
    MAX-ACCESS  not-accessible
    STATUS      current
    DESCRIPTION
        "Index of a row in dfl860SysIfStatsTable"
    ::= { dfl860IfStatsEntry 1 }

dfl860IfName OBJECT-TYPE
    SYNTAX      DisplayString
    MAX-ACCESS  read-only
    STATUS      current
    DESCRIPTION
        "The name of the interface."
    ::= { dfl860IfStatsEntry 2 }

dfl860IfFragsIn OBJECT-TYPE
    SYNTAX      Counter32
    MAX-ACCESS  read-only
    STATUS      current
    DESCRIPTION
        "Number of IP packet fragments received
         in the interface."
    ::= { dfl860IfStatsEntry 3 }

dfl860IfFragReassOk OBJECT-TYPE
    SYNTAX      Counter32
    MAX-ACCESS  read-only
    STATUS      current
    DESCRIPTION
        "Number of complete IP packets successfully
         reassembled from the fragments received in
         the interface."
    ::= { dfl860IfStatsEntry 4 }

dfl860IfFragReassFail OBJECT-TYPE
    SYNTAX      Counter32
    MAX-ACCESS  read-only
    STATUS      current
    DESCRIPTION
        "Number of packets that could not be reassembled,
         either due to resource starvation, illegal fragmentation,
         or just packet loss."
    ::= { dfl860IfStatsEntry 5 }

dfl860IfPktsInCnt OBJECT-TYPE
    SYNTAX      Counter32
    MAX-ACCESS  read-only
    STATUS      current
    DESCRIPTION
        "Number of packets received by the interface."
    ::= { dfl860IfStatsEntry 6 }

dfl860IfPktsOutCnt OBJECT-TYPE
    SYNTAX      Counter32
    MAX-ACCESS  read-only
    STATUS      current
    DESCRIPTION
        "Number of packets sent by the interface"
    ::= { dfl860IfStatsEntry 7 }

dfl860IfBitsInCnt OBJECT-TYPE
    SYNTAX      Counter32
    MAX-ACCESS  read-only
    STATUS      current
    DESCRIPTION
        "Number of bits received by the interface"
    ::= { dfl860IfStatsEntry 8 }

dfl860IfBitsOutCnt OBJECT-TYPE
    SYNTAX      Counter32
    MAX-ACCESS  read-only
    STATUS      current
    DESCRIPTION
        "Number of bits sent by the interface"
    ::= { dfl860IfStatsEntry 9 }

dfl860IfPktsTotCnt OBJECT-TYPE
    SYNTAX      Counter32
    MAX-ACCESS  read-only
    STATUS      current
    DESCRIPTION
        "Totat number of packets transmited by the interface"
    ::= { dfl860IfStatsEntry 10 }

dfl860IfBitsTotCnt OBJECT-TYPE
    SYNTAX      Counter32
    MAX-ACCESS  read-only
    STATUS      current
    DESCRIPTION
        "Totat number of bits transmited by the interface"
    ::= { dfl860IfStatsEntry 11 }

dfl860IfHCPktsInCnt OBJECT-TYPE
    SYNTAX      Counter64
    MAX-ACCESS  read-only
    STATUS      current
    DESCRIPTION
        "Number of packets received by the interface.
        This object is a 64-bit version of dfl860IfPktsInCnt."
    ::= { dfl860IfStatsEntry 12 }

dfl860IfHCPktsOutCnt OBJECT-TYPE
    SYNTAX      Counter64
    MAX-ACCESS  read-only
    STATUS      current
    DESCRIPTION
        "Number of packets sent by the interface.
        This object is a 64-bit version of dfl860IfPktsOutCnt."
    ::= { dfl860IfStatsEntry 13 }

dfl860IfHCBitsInCnt OBJECT-TYPE
    SYNTAX      Counter64
    MAX-ACCESS  read-only
    STATUS      current
    DESCRIPTION
        "Number of bits received by the interface.
        This object is a 64-bit version of dfl860IfBitsInCnt."
    ::= { dfl860IfStatsEntry 14 }

dfl860IfHCBitsOutCnt OBJECT-TYPE
    SYNTAX      Counter64
    MAX-ACCESS  read-only
    STATUS      current
    DESCRIPTION
        "Number of bits sent by the interface.
        This object is a 64-bit version of dfl860IfBitsOutCnt."
    ::= { dfl860IfStatsEntry 15 }

dfl860IfHCPktsTotCnt OBJECT-TYPE
    SYNTAX      Counter64
    MAX-ACCESS  read-only
    STATUS      current
    DESCRIPTION
        "Totat number of packets transmited by the interface.
        This object is a 64-bit version of dfl860IfPktsTotCnt."
    ::= { dfl860IfStatsEntry 16 }

dfl860IfHCBitsTotCnt OBJECT-TYPE
    SYNTAX      Counter64
    MAX-ACCESS  read-only
    STATUS      current
    DESCRIPTION
        "Totat number of bits transmited by the interface.
        This object is a 64-bit version of dfl860IfBitsTotCnt."
    ::= { dfl860IfStatsEntry 17 }

dfl860IfRxRingTable OBJECT-TYPE
    SYNTAX      SEQUENCE OF Dfl860IfRxRingEntry
    MAX-ACCESS  not-accessible
    STATUS      current
    DESCRIPTION
        "A table of DFL-860 specific interface Rx ring statistics"
    ::= { dfl860System 8 }

dfl860IfRxRingEntry OBJECT-TYPE
    SYNTAX      Dfl860IfRxRingEntry
    MAX-ACCESS  not-accessible
    STATUS      current
    DESCRIPTION
        "The row in a table of DFL-860 specific interface Rx ring
         statistics."
    INDEX       { dfl860IfRxRingIndex }
    ::= { dfl860IfRxRingTable 1 }

Dfl860IfRxRingEntry ::= SEQUENCE {
    dfl860IfRxRingIndex        Integer32,
    dfl860IfRxRingFifoErrors   Counter32,
    dfl860IfRxDespools         Gauge32,
    dfl860IfRxAvgUse           Gauge32,
    dfl860IfRxRingSaturation   Gauge32,
    dfl860RxRingFlooded        Gauge32
}

dfl860IfRxRingIndex OBJECT-TYPE
    SYNTAX      Integer32 (1..2147483647)
    MAX-ACCESS  not-accessible
    STATUS      current
    DESCRIPTION
        "Index of a row in dfl860IfRxRingTable."
    ::= { dfl860IfRxRingEntry 1 }

dfl860IfRxRingFifoErrors OBJECT-TYPE
    SYNTAX      Counter32
    MAX-ACCESS  read-only
    STATUS      current
    DESCRIPTION
        "Rx Ring number of FIFO errors."
    ::= { dfl860IfRxRingEntry 2 }

dfl860IfRxDespools OBJECT-TYPE
    SYNTAX      Gauge32
    MAX-ACCESS  read-only
    STATUS      current
    DESCRIPTION
        "Number of despool events per second."
    ::= { dfl860IfRxRingEntry 3 }

dfl860IfRxAvgUse OBJECT-TYPE
    SYNTAX      Gauge32
    MAX-ACCESS  read-only
    STATUS      current
    DESCRIPTION
        "Rx Ring average usage."
    ::= { dfl860IfRxRingEntry 4 }

dfl860IfRxRingSaturation OBJECT-TYPE
    SYNTAX      Gauge32
    MAX-ACCESS  read-only
    STATUS      current
    DESCRIPTION
        "Rx Ring sturation. Percentage of ring use per despool
         event when the ring has been more than half full."
    ::= { dfl860IfRxRingEntry 5 }

dfl860RxRingFlooded OBJECT-TYPE
    SYNTAX      Gauge32
    MAX-ACCESS  read-only
    STATUS      current
    DESCRIPTION
        "Rx Ring number of despool events for which
         the ring has been completely flooded"
    ::= { dfl860IfRxRingEntry 6 }

dfl860IfTxRingTable OBJECT-TYPE
    SYNTAX      SEQUENCE OF Dfl860IfTxRingEntry
    MAX-ACCESS  not-accessible
    STATUS      current
    DESCRIPTION
        "A table of DFL-860 specific interface Tx ring statistics"
    ::= { dfl860System 9 }

dfl860IfTxRingEntry OBJECT-TYPE
    SYNTAX      Dfl860IfTxRingEntry
    MAX-ACCESS  not-accessible
    STATUS      current
    DESCRIPTION
        "The row in a table of DFL-860 specific interface Tx ring
         statistics."
    INDEX       { dfl860IfTxRingIndex }
    ::= { dfl860IfTxRingTable 1 }

Dfl860IfTxRingEntry ::= SEQUENCE {
    dfl860IfTxRingIndex        Integer32,
    dfl860IfTxDespools         Gauge32,
    dfl860IfTxAvgUse           Gauge32,
    dfl860IfTxRingSaturation   Gauge32,
    dfl860RxTingFlooded        Gauge32
}

dfl860IfTxRingIndex OBJECT-TYPE
    SYNTAX      Integer32 (1..2147483647)
    MAX-ACCESS  not-accessible
    STATUS      current
    DESCRIPTION
        "Index of a row in dfl860IfRxRingTable."
    ::= { dfl860IfTxRingEntry 1 }

dfl860IfTxDespools OBJECT-TYPE
    SYNTAX      Gauge32
    MAX-ACCESS  read-only
    STATUS      current
    DESCRIPTION
        "Tx Ring number of despool event per second (polls when
         there is at least one buffer in the ring)"
    ::= { dfl860IfTxRingEntry 2 }

dfl860IfTxAvgUse OBJECT-TYPE
    SYNTAX      Gauge32
    MAX-ACCESS  read-only
    STATUS      current
    DESCRIPTION
        "Tx Ring number of despool events when the ring has
         been completely flooded"
    ::= { dfl860IfTxRingEntry 3 }

dfl860IfTxRingSaturation OBJECT-TYPE
    SYNTAX      Gauge32
    MAX-ACCESS  read-only
    STATUS      current
    DESCRIPTION
        "Tx Ring percentage of use per despool event when the
         ring has been more than half full."
    ::= { dfl860IfTxRingEntry 4 }

dfl860RxTingFlooded OBJECT-TYPE
    SYNTAX      Gauge32
    MAX-ACCESS  read-only
    STATUS      current
    DESCRIPTION
        "Tx Ring number of despool events for in which the ring has
         been completely flooded"
    ::= { dfl860IfTxRingEntry 5 }

dfl860IfVlanStatsTable OBJECT-TYPE
    SYNTAX      SEQUENCE OF Dfl860IfVlanStatsEntry
    MAX-ACCESS  not-accessible
    STATUS      current
    DESCRIPTION
        "A table of DFL-860 VLAN statistics"
    ::= { dfl860System 10 }

dfl860IfVlanStatsEntry OBJECT-TYPE
    SYNTAX      Dfl860IfVlanStatsEntry
    MAX-ACCESS  not-accessible
    STATUS      current
    DESCRIPTION
        "The row in a table of dfl860IfVlanStatsTable. Each has an index
         equal to the ifIndex of the corresponding physical interface"
    INDEX       { dfl860IfVlanIndex }
    ::= { dfl860IfVlanStatsTable 1 }

Dfl860IfVlanStatsEntry ::= SEQUENCE {
    dfl860IfVlanIndex              Integer32,
    dfl860IfVlanUntaggedInPkts     Counter32,
    dfl860IfVlanUntaggedOutPkts    Counter32,
    dfl860IfVlanUntaggedTotPkts    Counter32,
    dfl860IfVlanUntaggedInOctets   Counter32,
    dfl860IfVlanUntaggedOutOctets  Counter32,
    dfl860IfVlanUntaggedTotOctets  Counter32
}

dfl860IfVlanIndex OBJECT-TYPE
    SYNTAX      Integer32 (1..2147483647)
    MAX-ACCESS  not-accessible
    STATUS      current
    DESCRIPTION
        "Extended index of a row in dfl860IfVlanStatsTable."
    ::= { dfl860IfVlanStatsEntry 1 }

dfl860IfVlanUntaggedInPkts OBJECT-TYPE
    SYNTAX      Counter32
    MAX-ACCESS  read-only
    STATUS      current
    DESCRIPTION
        "Number of untaged packets untagged packets received by the interface."
    ::= { dfl860IfVlanStatsEntry 2 }

dfl860IfVlanUntaggedOutPkts OBJECT-TYPE
    SYNTAX      Counter32
    MAX-ACCESS  read-only
    STATUS      current
    DESCRIPTION
        "Number of untagged packets sent by the interface."
    ::= { dfl860IfVlanStatsEntry 3 }

dfl860IfVlanUntaggedTotPkts OBJECT-TYPE
    SYNTAX      Counter32
    MAX-ACCESS  read-only
    STATUS      current
    DESCRIPTION
        "Total number of untagged packets processed by the interface."
    ::= { dfl860IfVlanStatsEntry 4 }

dfl860IfVlanUntaggedInOctets OBJECT-TYPE
    SYNTAX      Counter32
    MAX-ACCESS  read-only
    STATUS      current
    DESCRIPTION
        "Total number of octects in untagged packets received by the interface."
    ::= { dfl860IfVlanStatsEntry 5 }

dfl860IfVlanUntaggedOutOctets OBJECT-TYPE
    SYNTAX      Counter32
    MAX-ACCESS  read-only
    STATUS      current
    DESCRIPTION
        "Total number of octects in untagged packets sent by the interface."
    ::= { dfl860IfVlanStatsEntry 6 }

dfl860IfVlanUntaggedTotOctets OBJECT-TYPE
    SYNTAX      Counter32
    MAX-ACCESS  read-only
    STATUS      current
    DESCRIPTION
        "Total number of octects in untagged packets processed by the
         interface."
    ::= { dfl860IfVlanStatsEntry 7 }

dfl860HWSensorTable OBJECT-TYPE
    SYNTAX      SEQUENCE OF Dfl860HWSensorEntry
    MAX-ACCESS  not-accessible
    STATUS      current
    DESCRIPTION
        "Table of hardware sensors."
    ::= { dfl860System 11 }

dfl860HWSensorEntry OBJECT-TYPE
    SYNTAX      Dfl860HWSensorEntry
    MAX-ACCESS  not-accessible
    STATUS      current
    DESCRIPTION
        "Entry  of table of hardware sensors."
    INDEX       { dfl860HWSensorIndex }
    ::= { dfl860HWSensorTable 1 }

Dfl860HWSensorEntry ::= SEQUENCE {
    dfl860HWSensorIndex    Integer32,
    dfl860HWSensorName     DisplayString,
    dfl860HWSensorValue    Gauge32,
    dfl860HWSensorUnit     DisplayString
}

dfl860HWSensorIndex OBJECT-TYPE
    SYNTAX      Integer32 (1..2147483647)
    MAX-ACCESS  not-accessible
    STATUS      current
    DESCRIPTION
        "Index of the entries of the sensor table."
    ::= { dfl860HWSensorEntry 1 }

dfl860HWSensorName OBJECT-TYPE
    SYNTAX      DisplayString
    MAX-ACCESS  read-only
    STATUS      current
    DESCRIPTION
        "The description of the sensor."
    ::= { dfl860HWSensorEntry 2 }

dfl860HWSensorValue OBJECT-TYPE
    SYNTAX      Gauge32
    MAX-ACCESS  read-only
    STATUS      current
    DESCRIPTION
        "The value of the sensor."
    ::= { dfl860HWSensorEntry 3 }

dfl860HWSensorUnit OBJECT-TYPE
    SYNTAX      DisplayString
    MAX-ACCESS  read-only
    STATUS      current
    DESCRIPTION
        "The description of the unit of the value mesured by sensor."
    ::= { dfl860HWSensorEntry 4 }

dfl860SysMemUsage OBJECT-TYPE
    SYNTAX      Gauge32
    MAX-ACCESS  read-only
    STATUS      current
    DESCRIPTION
        "The current memory usage."
    ::= { dfl860System 12 }

dfl860SysTCPUsage OBJECT IDENTIFIER
    ::= { dfl860System 13 }

dfl860SysTCPRecvSmall OBJECT-TYPE
    SYNTAX      Gauge32
    MAX-ACCESS  read-only
    STATUS      current
    DESCRIPTION
        "Small TCP receive windows usage."
    ::= { dfl860SysTCPUsage 1 }

dfl860SysTCPRecvLarge OBJECT-TYPE
    SYNTAX      Gauge32
    MAX-ACCESS  read-only
    STATUS      current
    DESCRIPTION
        "Large TCP receive windows usage."
    ::= { dfl860SysTCPUsage 2 }

dfl860SysTCPSendSmall OBJECT-TYPE
    SYNTAX      Gauge32
    MAX-ACCESS  read-only
    STATUS      current
    DESCRIPTION
        "Small TCP send windows usage."
    ::= { dfl860SysTCPUsage 3 }

dfl860SysTCPSendLarge OBJECT-TYPE
    SYNTAX      Gauge32
    MAX-ACCESS  read-only
    STATUS      current
    DESCRIPTION
        "Large TCP send windows usage."
    ::= { dfl860SysTCPUsage 4 }

dfl860SysTimerUsage OBJECT-TYPE
    SYNTAX      Gauge32
    MAX-ACCESS  read-only
    STATUS      current
    DESCRIPTION
        "The current number of timers in use."
    ::= { dfl860System 14 }

dfl860SysConnOPS OBJECT-TYPE
    SYNTAX      Gauge32
    MAX-ACCESS  read-only
    STATUS      current
    DESCRIPTION
        "The number of connections opened per second."
    ::= { dfl860System 15 }

dfl860SysConnCPS OBJECT-TYPE
    SYNTAX      Gauge32
    MAX-ACCESS  read-only
    STATUS      current
    DESCRIPTION
        "The number of connections closed per second."
    ::= { dfl860System 16 }

dfl860SysHCForwardedBits OBJECT-TYPE
    SYNTAX      Counter64
    MAX-ACCESS  read-only
    STATUS      current
    DESCRIPTION
        "The number of bits forwarded through the gateway."
    ::= { dfl860System 17 }

dfl860VPN OBJECT IDENTIFIER
    ::= { dfl860OSStats 2 }

dfl860IPsec OBJECT IDENTIFIER
    ::= { dfl860VPN 1 }

dfl860IPsecGlobal OBJECT IDENTIFIER
    ::= { dfl860IPsec 1 }

dfl860IPsecPhaseOneActive OBJECT-TYPE
    SYNTAX      Gauge32
    MAX-ACCESS  read-only
    STATUS      current
    DESCRIPTION
        "Number of Phase-1 active negotiations"
    ::= { dfl860IPsecGlobal 1 }

dfl860IPsecPhaseOneAggrModeDone OBJECT-TYPE
    SYNTAX      Gauge32
    MAX-ACCESS  read-only
    STATUS      current
    DESCRIPTION
        "Number of Phase-1 aggressive mode negotiations."
    ::= { dfl860IPsecGlobal 2 }

dfl860IPsecQuickModeActive OBJECT-TYPE
    SYNTAX      Gauge32
    MAX-ACCESS  read-only
    STATUS      current
    DESCRIPTION
        "Number of quick mode active negotiations."
    ::= { dfl860IPsecGlobal 3 }

dfl860IPsecPhaseOneDone OBJECT-TYPE
    SYNTAX      Counter32
    MAX-ACCESS  read-only
    STATUS      current
    DESCRIPTION
        "Number of Phase-1 negotiations done."
    ::= { dfl860IPsecGlobal 4 }

dfl860IPsecPhaseOneFailed OBJECT-TYPE
    SYNTAX      Counter32
    MAX-ACCESS  read-only
    STATUS      current
    DESCRIPTION
        "Number of Phase-1 negotiations failed."
    ::= { dfl860IPsecGlobal 5 }

dfl860IPsecPhaseOneRekeyed OBJECT-TYPE
    SYNTAX      Counter32
    MAX-ACCESS  read-only
    STATUS      current
    DESCRIPTION
        "Number of Phase-1 negotiations rekeyed."
    ::= { dfl860IPsecGlobal 6 }

dfl860IPsecQuickModeDone OBJECT-TYPE
    SYNTAX      Counter32
    MAX-ACCESS  read-only
    STATUS      current
    DESCRIPTION
        "Number of quick mode  negotiations done."
    ::= { dfl860IPsecGlobal 7 }

dfl860IPsecQuickModeFailed OBJECT-TYPE
    SYNTAX      Counter32
    MAX-ACCESS  read-only
    STATUS      current
    DESCRIPTION
        "Number of quick mode negotiations failed."
    ::= { dfl860IPsecGlobal 8 }

dfl860IPsecInfoDone OBJECT-TYPE
    SYNTAX      Counter32
    MAX-ACCESS  read-only
    STATUS      current
    DESCRIPTION
        "Number of informational exchanges done.
         (Not available in IKEv1 implementations)"
    ::= { dfl860IPsecGlobal 9 }

dfl860IPsecInfoFailed OBJECT-TYPE
    SYNTAX      Counter32
    MAX-ACCESS  read-only
    STATUS      current
    DESCRIPTION
        "Number of informational exchanges failed.
         (Not available in IKEv1 implementations)"
    ::= { dfl860IPsecGlobal 10 }

dfl860IPsecInOctetsComp OBJECT-TYPE
    SYNTAX      Counter64
    MAX-ACCESS  read-only
    STATUS      current
    DESCRIPTION
        "Total octets in before decompression."
    ::= { dfl860IPsecGlobal 11 }

dfl860IPsecInOctetsUncomp OBJECT-TYPE
    SYNTAX      Counter64
    MAX-ACCESS  read-only
    STATUS      current
    DESCRIPTION
        "Total octets in after decompression."
    ::= { dfl860IPsecGlobal 12 }

dfl860IPsecOutOctetsComp OBJECT-TYPE
    SYNTAX      Counter64
    MAX-ACCESS  read-only
    STATUS      current
    DESCRIPTION
        "Total octets out after compression."
    ::= { dfl860IPsecGlobal 13 }

dfl860IPsecOutOctetsUncomp OBJECT-TYPE
    SYNTAX      Counter64
    MAX-ACCESS  read-only
    STATUS      current
    DESCRIPTION
        "Total octets out before compression."
    ::= { dfl860IPsecGlobal 14 }

dfl860IPsecForwardedOctetsComp OBJECT-TYPE
    SYNTAX      Counter64
    MAX-ACCESS  read-only
    STATUS      current
    DESCRIPTION
        "Total octets forwarded after compression."
    ::= { dfl860IPsecGlobal 15 }

dfl860IPsecForwardedOctetsUcomp OBJECT-TYPE
    SYNTAX      Counter64
    MAX-ACCESS  read-only
    STATUS      current
    DESCRIPTION
        "Total octets forwarded before compression."
    ::= { dfl860IPsecGlobal 16 }

dfl860IPsecInPackets OBJECT-TYPE
    SYNTAX      Counter64
    MAX-ACCESS  read-only
    STATUS      current
    DESCRIPTION
        "Total packets in."
    ::= { dfl860IPsecGlobal 17 }

dfl860IPsecOutPackets OBJECT-TYPE
    SYNTAX      Counter64
    MAX-ACCESS  read-only
    STATUS      current
    DESCRIPTION
        "Total packets Out."
    ::= { dfl860IPsecGlobal 18 }

dfl860IPsecForwardedPackets OBJECT-TYPE
    SYNTAX      Counter64
    MAX-ACCESS  read-only
    STATUS      current
    DESCRIPTION
        "Total packets forwarded."
    ::= { dfl860IPsecGlobal 19 }

dfl860IPsecActiveTransforms OBJECT-TYPE
    SYNTAX      Gauge32
    MAX-ACCESS  read-only
    STATUS      current
    DESCRIPTION
        "Number of currently active transforms."
    ::= { dfl860IPsecGlobal 20 }

dfl860IPsecTotalTransforms OBJECT-TYPE
    SYNTAX      Counter32
    MAX-ACCESS  read-only
    STATUS      current
    DESCRIPTION
        "Total number of transform records created."
    ::= { dfl860IPsecGlobal 21 }

dfl860IPsecOutOfTransforms OBJECT-TYPE
    SYNTAX      Counter32
    MAX-ACCESS  read-only
    STATUS      current
    DESCRIPTION
        "Number of packets dropped due to no available transform object.
         (Not available in IKEv1 implementations)"
    ::= { dfl860IPsecGlobal 22 }

dfl860IPsecTotalRekeys OBJECT-TYPE
    SYNTAX      Counter32
    MAX-ACCESS  read-only
    STATUS      current
    DESCRIPTION
        "Total number of rekeys performed."
    ::= { dfl860IPsecGlobal 23 }

dfl860Rules OBJECT IDENTIFIER
    ::= { dfl860OSStats 3 }

dfl860RuleUseTable OBJECT-TYPE
    SYNTAX      SEQUENCE OF Dfl860RuleUseEntry
    MAX-ACCESS  not-accessible
    STATUS      current
    DESCRIPTION
        "A list of general rules usage statistics."
    ::= { dfl860Rules 2 }

dfl860RuleUseEntry OBJECT-TYPE
    SYNTAX      Dfl860RuleUseEntry
    MAX-ACCESS  not-accessible
    STATUS      current
    DESCRIPTION
        "The statistics over a rule usage."
    INDEX       { dfl860RuleIndex }
    ::= { dfl860RuleUseTable 1 }

Dfl860RuleUseEntry ::= SEQUENCE {
    dfl860RuleIndex    Integer32,
    dfl860RuleName     DisplayString,
    dfl860RuleUse      Counter32
}

dfl860RuleIndex OBJECT-TYPE
    SYNTAX      Integer32 (1..2147483647)
    MAX-ACCESS  not-accessible
    STATUS      current
    DESCRIPTION
        "The rule usage index."
    ::= { dfl860RuleUseEntry 1 }

dfl860RuleName OBJECT-TYPE
    SYNTAX      DisplayString
    MAX-ACCESS  read-only
    STATUS      current
    DESCRIPTION
        "The name of the rule."
    ::= { dfl860RuleUseEntry 2 }

dfl860RuleUse OBJECT-TYPE
    SYNTAX      Counter32
    MAX-ACCESS  read-only
    STATUS      current
    DESCRIPTION
        "The number of times o rule was used."
    ::= { dfl860RuleUseEntry 3 }

dfl860IPPools OBJECT IDENTIFIER
    ::= { dfl860OSStats 4 }

dfl860IPPoolsNumber OBJECT-TYPE
    SYNTAX      Integer32
    MAX-ACCESS  read-only
    STATUS      current
    DESCRIPTION
        "The number of ip pools"
    ::= { dfl860IPPools 1 }

dfl860IPPoolTable OBJECT-TYPE
    SYNTAX      SEQUENCE OF Dfl860IPPoolEntry
    MAX-ACCESS  not-accessible
    STATUS      current
    DESCRIPTION
        "A list of IP pools"
    ::= { dfl860IPPools 2 }

dfl860IPPoolEntry OBJECT-TYPE
    SYNTAX      Dfl860IPPoolEntry
    MAX-ACCESS  not-accessible
    STATUS      current
    DESCRIPTION
        "The attributes of an ip pool"
    INDEX       { dfl860IPPoolIndex }
    ::= { dfl860IPPoolTable 1 }

Dfl860IPPoolEntry ::= SEQUENCE {
    dfl860IPPoolIndex          Integer32,
    dfl860IPPoolName           DisplayString,
    dfl860IPPoolPrepare        Gauge32,
    dfl860IPPoolFree           Gauge32,
    dfl860IPPoolMisses         Gauge32,
    dfl860IPPoolClientFails    Gauge32,
    dfl860IPPoolUsed           Gauge32
}

dfl860IPPoolIndex OBJECT-TYPE
    SYNTAX      Integer32 (1..2147483647)
    MAX-ACCESS  not-accessible
    STATUS      current
    DESCRIPTION
        "The ip pool index"
    ::= { dfl860IPPoolEntry 1 }

dfl860IPPoolName OBJECT-TYPE
    SYNTAX      DisplayString
    MAX-ACCESS  read-only
    STATUS      current
    DESCRIPTION
        "The ip pool name"
    ::= { dfl860IPPoolEntry 2 }

dfl860IPPoolPrepare OBJECT-TYPE
    SYNTAX      Gauge32
    MAX-ACCESS  read-only
    STATUS      current
    DESCRIPTION
        "Number of IP pool objects in prepare mode."
    ::= { dfl860IPPoolEntry 3 }

dfl860IPPoolFree OBJECT-TYPE
    SYNTAX      Gauge32
    MAX-ACCESS  read-only
    STATUS      current
    DESCRIPTION
        "Number of available IPs in the pool."
    ::= { dfl860IPPoolEntry 4 }

dfl860IPPoolMisses OBJECT-TYPE
    SYNTAX      Gauge32
    MAX-ACCESS  read-only
    STATUS      current
    DESCRIPTION
        "Mumber of missed IP pool negotiations for other reasons
         than lack of available IP numbers."
    ::= { dfl860IPPoolEntry 5 }

dfl860IPPoolClientFails OBJECT-TYPE
    SYNTAX      Gauge32
    MAX-ACCESS  read-only
    STATUS      current
    DESCRIPTION
        "Number of failed IP pool transactions."
    ::= { dfl860IPPoolEntry 6 }

dfl860IPPoolUsed OBJECT-TYPE
    SYNTAX      Gauge32
    MAX-ACCESS  read-only
    STATUS      current
    DESCRIPTION
        "Number of IP numbers in use from the pool."
    ::= { dfl860IPPoolEntry 7 }

dfl860DHCPServer OBJECT IDENTIFIER
    ::= { dfl860OSStats 5 }

dfl860DHCPTotalRejected OBJECT-TYPE
    SYNTAX      Gauge32
    MAX-ACCESS  read-only
    STATUS      current
    DESCRIPTION
        "Total number of rejected packets (all rules)."
    ::= { dfl860DHCPServer 1 }

dfl860DHCPRuleTable OBJECT-TYPE
    SYNTAX      SEQUENCE OF Dfl860DHCPRuleEntry
    MAX-ACCESS  not-accessible
    STATUS      current
    DESCRIPTION
        "A list of all DHCP server rules usage statistics."
    ::= { dfl860DHCPServer 2 }

dfl860DHCPRuleEntry OBJECT-TYPE
    SYNTAX      Dfl860DHCPRuleEntry
    MAX-ACCESS  not-accessible
    STATUS      current
    DESCRIPTION
        "The attributes of a DHCP server rule statistics."
    INDEX       { dfl860DHCPRuleIndex }
    ::= { dfl860DHCPRuleTable 1 }

Dfl860DHCPRuleEntry ::= SEQUENCE {
    dfl860DHCPRuleIndex                Integer32,
    dfl860DHCPRuleName                 DisplayString,
    dfl860DHCPRuleUsage                Gauge32,
    dfl860DHCPRuleUsagePercent         Gauge32,
    dfl860DHCPActiveClients            Gauge32,
    dfl860DHCPActiveClientsPercent     Gauge32,
    dfl860DHCPRejectedRequests         Gauge32,
    dfl860DHCPTotalLeases              Gauge32
}

dfl860DHCPRuleIndex OBJECT-TYPE
    SYNTAX      Integer32 (1..2147483647)
    MAX-ACCESS  not-accessible
    STATUS      current
    DESCRIPTION
        "The DHCP server rule  index"
    ::= { dfl860DHCPRuleEntry 1 }

dfl860DHCPRuleName OBJECT-TYPE
    SYNTAX      DisplayString
    MAX-ACCESS  read-only
    STATUS      current
    DESCRIPTION
        "The DHCP server rule name."
    ::= { dfl860DHCPRuleEntry 2 }

dfl860DHCPRuleUsage OBJECT-TYPE
    SYNTAX      Gauge32
    MAX-ACCESS  read-only
    STATUS      current
    DESCRIPTION
        "Number of used IPs in the pool."
    ::= { dfl860DHCPRuleEntry 3 }

dfl860DHCPRuleUsagePercent OBJECT-TYPE
    SYNTAX      Gauge32
    MAX-ACCESS  read-only
    STATUS      current
    DESCRIPTION
        "The percentage of the used IPs in
         relation to the IP pool size."
    ::= { dfl860DHCPRuleEntry 4 }

dfl860DHCPActiveClients OBJECT-TYPE
    SYNTAX      Gauge32
    MAX-ACCESS  read-only
    STATUS      current
    DESCRIPTION
        "Number of currently active clients."
    ::= { dfl860DHCPRuleEntry 5 }

dfl860DHCPActiveClientsPercent OBJECT-TYPE
    SYNTAX      Gauge32
    MAX-ACCESS  read-only
    STATUS      current
    DESCRIPTION
        "The number of currently active clients
         as a percentage of the pool size."
    ::= { dfl860DHCPRuleEntry 6 }

dfl860DHCPRejectedRequests OBJECT-TYPE
    SYNTAX      Gauge32
    MAX-ACCESS  read-only
    STATUS      current
    DESCRIPTION
        "Number of rejected requests matching
         the current rule."
    ::= { dfl860DHCPRuleEntry 7 }

dfl860DHCPTotalLeases OBJECT-TYPE
    SYNTAX      Gauge32
    MAX-ACCESS  read-only
    STATUS      current
    DESCRIPTION
        "Total number of leases in the pool."
    ::= { dfl860DHCPRuleEntry 8 }

dfl860UserAuth OBJECT IDENTIFIER
    ::= { dfl860OSStats 6 }

dfl860UserAuthHTTPUsers OBJECT-TYPE
    SYNTAX      Gauge32
    MAX-ACCESS  read-only
    STATUS      current
    DESCRIPTION
        "Number of currently  logged in HTTP users."
    ::= { dfl860UserAuth 1 }

dfl860UserAuthXAUTHUsers OBJECT-TYPE
    SYNTAX      Gauge32
    MAX-ACCESS  read-only
    STATUS      current
    DESCRIPTION
        "Number of currently logged in XAUTH users."
    ::= { dfl860UserAuth 2 }

dfl860UserAuthHTTPSUsers OBJECT-TYPE
    SYNTAX      Gauge32
    MAX-ACCESS  read-only
    STATUS      current
    DESCRIPTION
        "Number of currently logged in HTTPS users."
    ::= { dfl860UserAuth 3 }

dfl860UserAuthPPPUsers OBJECT-TYPE
    SYNTAX      Gauge32
    MAX-ACCESS  read-only
    STATUS      current
    DESCRIPTION
        "Number of currently logged in PPP users."
    ::= { dfl860UserAuth 4 }

dfl860UserAuthEAPUsers OBJECT-TYPE
    SYNTAX      Gauge32
    MAX-ACCESS  read-only
    STATUS      current
    DESCRIPTION
        "Number of currently logged in EAP users."
    ::= { dfl860UserAuth 5 }

dfl860UserAuthRuleUseTable OBJECT-TYPE
    SYNTAX      SEQUENCE OF Dfl860UserAuthRuleUseEntry
    MAX-ACCESS  not-accessible
    STATUS      current
    DESCRIPTION
        "Table of user authentication rule usage."
    ::= { dfl860UserAuth 6 }

dfl860UserAuthRuleUseEntry OBJECT-TYPE
    SYNTAX      Dfl860UserAuthRuleUseEntry
    MAX-ACCESS  not-accessible
    STATUS      current
    DESCRIPTION
        "The attributes of an authentication rule
         usage statistics."
    INDEX       { dfl860UserAuthRuleIndex }
    ::= { dfl860UserAuthRuleUseTable 1 }

Dfl860UserAuthRuleUseEntry ::= SEQUENCE {
    dfl860UserAuthRuleIndex    Integer32,
    dfl860UserAuthRuleName     DisplayString,
    dfl860UserAuthRuleUse      Counter32
}

dfl860UserAuthRuleIndex OBJECT-TYPE
    SYNTAX      Integer32 (1..2147483647)
    MAX-ACCESS  not-accessible
    STATUS      current
    DESCRIPTION
        "The rule usage index."
    ::= { dfl860UserAuthRuleUseEntry 1 }

dfl860UserAuthRuleName OBJECT-TYPE
    SYNTAX      DisplayString
    MAX-ACCESS  read-only
    STATUS      current
    DESCRIPTION
        "The name of the rule."
    ::= { dfl860UserAuthRuleUseEntry 2 }

dfl860UserAuthRuleUse OBJECT-TYPE
    SYNTAX      Counter32
    MAX-ACCESS  read-only
    STATUS      current
    DESCRIPTION
        "The number of times o rule was used."
    ::= { dfl860UserAuthRuleUseEntry 3 }

dfl860LinkMonitor OBJECT IDENTIFIER
    ::= { dfl860OSStats 7 }

dfl860LinkMonGrp OBJECT-TYPE
    SYNTAX      Integer32
    MAX-ACCESS  read-only
    STATUS      current
    DESCRIPTION
        "The number of groups of monitored links"
    ::= { dfl860LinkMonitor 1 }

dfl860LinkMonGrpTable OBJECT-TYPE
    SYNTAX      SEQUENCE OF Dfl860LinkMonGrpEntry
    MAX-ACCESS  not-accessible
    STATUS      current
    DESCRIPTION
        "Table of link monitor groups."
    ::= { dfl860LinkMonitor 2 }

dfl860LinkMonGrpEntry OBJECT-TYPE
    SYNTAX      Dfl860LinkMonGrpEntry
    MAX-ACCESS  not-accessible
    STATUS      current
    DESCRIPTION
        "The attributes of a link monitor group"
    INDEX       { dfl860LinkMonGrpIndex }
    ::= { dfl860LinkMonGrpTable 1 }

Dfl860LinkMonGrpEntry ::= SEQUENCE {
    dfl860LinkMonGrpIndex      Integer32,
    dfl860LinkMonGrpName       DisplayString,
    dfl860LinkMonGrpHostsUp    Gauge32
}

dfl860LinkMonGrpIndex OBJECT-TYPE
    SYNTAX      Integer32 (1..2147483647)
    MAX-ACCESS  not-accessible
    STATUS      current
    DESCRIPTION
        "The index row in the table of link monitor groups."
    ::= { dfl860LinkMonGrpEntry 1 }

dfl860LinkMonGrpName OBJECT-TYPE
    SYNTAX      DisplayString
    MAX-ACCESS  read-only
    STATUS      current
    DESCRIPTION
        "The link monitor group name."
    ::= { dfl860LinkMonGrpEntry 2 }

dfl860LinkMonGrpHostsUp OBJECT-TYPE
    SYNTAX      Gauge32
    MAX-ACCESS  read-only
    STATUS      current
    DESCRIPTION
        "The percentage of monitored hosts available."
    ::= { dfl860LinkMonGrpEntry 3 }

dfl860LinkMonHostTable OBJECT-TYPE
    SYNTAX      SEQUENCE OF Dfl860LinkMonHostEntry
    MAX-ACCESS  not-accessible
    STATUS      current
    DESCRIPTION
        "Table of link monitored hosts in a link monnitor group."
    ::= { dfl860LinkMonitor 3 }

dfl860LinkMonHostEntry OBJECT-TYPE
    SYNTAX      Dfl860LinkMonHostEntry
    MAX-ACCESS  not-accessible
    STATUS      current
    DESCRIPTION
        "The attributes of a monitored host."
    INDEX       { dfl860LinkMonGrpIndex, dfl860LinkMonHostIndex }
    ::= { dfl860LinkMonHostTable 1 }

Dfl860LinkMonHostEntry ::= SEQUENCE {
    dfl860LinkMonHostIndex             Integer32,
    dfl860LinkMonHostId                DisplayString,
    dfl860LinkMonHostShortTermLoss     Gauge32,
    dfl860LinkMonHostPacketsLost       Counter32
}

dfl860LinkMonHostIndex OBJECT-TYPE
    SYNTAX      Integer32 (1..2147483647)
    MAX-ACCESS  not-accessible
    STATUS      current
    DESCRIPTION
        "The index an host in the table of link monitor hosts."
    ::= { dfl860LinkMonHostEntry 1 }

dfl860LinkMonHostId OBJECT-TYPE
    SYNTAX      DisplayString
    MAX-ACCESS  read-only
    STATUS      current
    DESCRIPTION
        "The monitored host identifier."
    ::= { dfl860LinkMonHostEntry 2 }

dfl860LinkMonHostShortTermLoss OBJECT-TYPE
    SYNTAX      Gauge32
    MAX-ACCESS  read-only
    STATUS      current
    DESCRIPTION
        "The percentage of short term losst packets."
    ::= { dfl860LinkMonHostEntry 3 }

dfl860LinkMonHostPacketsLost OBJECT-TYPE
    SYNTAX      Counter32
    MAX-ACCESS  read-only
    STATUS      current
    DESCRIPTION
        "Total number of lost monitoring packets."
    ::= { dfl860LinkMonHostEntry 4 }

dfl860Pipes OBJECT IDENTIFIER
    ::= { dfl860OSStats 8 }

dfl860PipeUsers OBJECT-TYPE
    SYNTAX      Gauge32
    MAX-ACCESS  read-only
    STATUS      current
    DESCRIPTION
        "The current number of users, as defined by the grouping
         settings of each pipe, being tracked in the pipes system.
         Note that this value corresponds to the number of users
         active in each time slice of 1/20th of a second, and not
         to the number of users having open connections."
    ::= { dfl860Pipes 1 }

dfl860PipeTable OBJECT-TYPE
    SYNTAX      SEQUENCE OF Dfl860PipeEntry
    MAX-ACCESS  not-accessible
    STATUS      current
    DESCRIPTION
        "Table of pipes"
    ::= { dfl860Pipes 2 }

dfl860PipeEntry OBJECT-TYPE
    SYNTAX      Dfl860PipeEntry
    MAX-ACCESS  not-accessible
    STATUS      current
    DESCRIPTION
        "A entry of the pipes table"
    INDEX       { dfl860PipeIndex }
    ::= { dfl860PipeTable 1 }

Dfl860PipeEntry ::= SEQUENCE {
    dfl860PipeIndex            Integer32,
    dfl860PipeName             DisplayString,
    dfl860PipeMinPrec          Integer32,
    dfl860PipeMaxPrec          Integer32,
    dfl860PipeDefPrec          Integer32,
    dfl860PipeNumPrec          Integer32,
    dfl860PipeNumUsers         Gauge32,
    dfl860PipeCurrentBps       Gauge32,
    dfl860PipeCurrentPps       Gauge32,
    dfl860PipeDelayedPackets   Counter32,
    dfl860PipeDropedPackets    Counter32
}

dfl860PipeIndex OBJECT-TYPE
    SYNTAX      Integer32 (1..2147483647)
    MAX-ACCESS  not-accessible
    STATUS      current
    DESCRIPTION
        "The pipe index"
    ::= { dfl860PipeEntry 1 }

dfl860PipeName OBJECT-TYPE
    SYNTAX      DisplayString
    MAX-ACCESS  read-only
    STATUS      current
    DESCRIPTION
        "The name of the pipe"
    ::= { dfl860PipeEntry 2 }

dfl860PipeMinPrec OBJECT-TYPE
    SYNTAX      Integer32
    MAX-ACCESS  read-only
    STATUS      current
    DESCRIPTION
        "The minimum of the range of pipe precedences."
    ::= { dfl860PipeEntry 3 }

dfl860PipeMaxPrec OBJECT-TYPE
    SYNTAX      Integer32
    MAX-ACCESS  read-only
    STATUS      current
    DESCRIPTION
        "The maximum of the range of pipe precedences."
    ::= { dfl860PipeEntry 4 }

dfl860PipeDefPrec OBJECT-TYPE
    SYNTAX      Integer32
    MAX-ACCESS  read-only
    STATUS      current
    DESCRIPTION
        "The precedence assigned to a packet for which has not one
         allready done by a Pipe Rule."
    ::= { dfl860PipeEntry 5 }

dfl860PipeNumPrec OBJECT-TYPE
    SYNTAX      Integer32
    MAX-ACCESS  read-only
    STATUS      current
    DESCRIPTION
        "The number of pipe precedences"
    ::= { dfl860PipeEntry 6 }

dfl860PipeNumUsers OBJECT-TYPE
    SYNTAX      Gauge32
    MAX-ACCESS  read-only
    STATUS      current
    DESCRIPTION
        "The current number of users, as defined by the grouping settings
         of each pipe, being tracked in the pipes system. This value
         corresponds to the number of users active in each time slice
         and not to the number of users having  open connections."
    ::= { dfl860PipeEntry 7 }

dfl860PipeCurrentBps OBJECT-TYPE
    SYNTAX      Gauge32
    MAX-ACCESS  read-only
    STATUS      current
    DESCRIPTION
        "The current throughput of a pipe, in bits per second, as a sum of
         the corresponding values for all precedences."
    ::= { dfl860PipeEntry 8 }

dfl860PipeCurrentPps OBJECT-TYPE
    SYNTAX      Gauge32
    MAX-ACCESS  read-only
    STATUS      current
    DESCRIPTION
        "The current throughput of a pipe, in packets per second, as a sum of
         the corresponding values for all precedences."
    ::= { dfl860PipeEntry 9 }

dfl860PipeDelayedPackets OBJECT-TYPE
    SYNTAX      Counter32
    MAX-ACCESS  read-only
    STATUS      current
    DESCRIPTION
        "The number of times packets have been delayed as a result of a pipe,
         or pipe user having used up its allotted bandwidth. Note that one single
         packet may be delayed several times; if a pipe is really full, this
         count may exceed the number of packets actually passing through the
         pipe."
    ::= { dfl860PipeEntry 10 }

dfl860PipeDropedPackets OBJECT-TYPE
    SYNTAX      Counter32
    MAX-ACCESS  read-only
    STATUS      current
    DESCRIPTION
        "The number of packets dropped by a pipe. Packets are dropped when
         CorePlus is running out of packet buffers. This occurs when excessive
         amounts of packets need to be queued for later delivery. The packet
         dropped is always the one that has been queued the longest time
         globally, which means that the connection suffering from packet loss
         will be the one most overloading the system."
    ::= { dfl860PipeEntry 11 }

dfl860PipePrecTable OBJECT-TYPE
    SYNTAX      SEQUENCE OF Dfl860PipePrecEntry
    MAX-ACCESS  not-accessible
    STATUS      current
    DESCRIPTION
        "There is a one to many relation between a pipe and its precedences.
         The number of precedences is a instance attribute of each pipe.
         This table extends the pipes table in order to express the relation
         between a pipe and the respective precedences."
    ::= { dfl860Pipes 3 }

dfl860PipePrecEntry OBJECT-TYPE
    SYNTAX      Dfl860PipePrecEntry
    MAX-ACCESS  not-accessible
    STATUS      current
    DESCRIPTION
        "An entry of the table of pipe pecedences. These table entries
         are chracterized by been indexed by two values. The first index
         the same as the pipe index of the corresponding row in table of
         pipes and the second index is the index of the set of precedences
         of the corresponding pipe."
    INDEX       { dfl860PipeIndex, dfl860PipePrecIndex }
    ::= { dfl860PipePrecTable 1 }

Dfl860PipePrecEntry ::= SEQUENCE {
    dfl860PipePrecIndex            Integer32,
    dfl860PipePrec                 Integer32,
    dfl860PipePrecBps              Gauge32,
    dfl860PipePrecTotalPps         Gauge32,
    dfl860PipePrecReservedBps      Gauge32,
    dfl860PipePrecDynLimBps        Gauge32,
    dfl860PipePrecDynUsrLimBps     Gauge32,
    dfl860PipePrecDelayedPackets   Counter32,
    dfl860PipePrecDropedPackets    Counter32
}

dfl860PipePrecIndex OBJECT-TYPE
    SYNTAX      Integer32 (1..2147483647)
    MAX-ACCESS  not-accessible
    STATUS      current
    DESCRIPTION
        "Index of a precedence of a specific pipe. This is the second index
         of the entries of pipe precedence table described by object
         dfl860PipePrecEntry."
    ::= { dfl860PipePrecEntry 1 }

dfl860PipePrec OBJECT-TYPE
    SYNTAX      Integer32
    MAX-ACCESS  read-only
    STATUS      current
    DESCRIPTION
        "The precedence value"
    ::= { dfl860PipePrecEntry 2 }

dfl860PipePrecBps OBJECT-TYPE
    SYNTAX      Gauge32
    MAX-ACCESS  read-only
    STATUS      current
    DESCRIPTION
        "The current throughput of the pipe, in bits per second, with
         the corresponding precedence."
    ::= { dfl860PipePrecEntry 3 }

dfl860PipePrecTotalPps OBJECT-TYPE
    SYNTAX      Gauge32
    MAX-ACCESS  read-only
    STATUS      current
    DESCRIPTION
        "The current throughput of the pipe precedence, in packets per second."
    ::= { dfl860PipePrecEntry 4 }

dfl860PipePrecReservedBps OBJECT-TYPE
    SYNTAX      Gauge32
    MAX-ACCESS  read-only
    STATUS      current
    DESCRIPTION
        "The current bandwidth allocated to the precedence."
    ::= { dfl860PipePrecEntry 5 }

dfl860PipePrecDynLimBps OBJECT-TYPE
    SYNTAX      Gauge32
    MAX-ACCESS  read-only
    STATUS      current
    DESCRIPTION
        "The current bandwidth limit limit applied the precedence."
    ::= { dfl860PipePrecEntry 6 }

dfl860PipePrecDynUsrLimBps OBJECT-TYPE
    SYNTAX      Gauge32
    MAX-ACCESS  read-only
    STATUS      current
    DESCRIPTION
        "The current precedence bandwidth limit per user of the pipe."
    ::= { dfl860PipePrecEntry 7 }

dfl860PipePrecDelayedPackets OBJECT-TYPE
    SYNTAX      Counter32
    MAX-ACCESS  read-only
    STATUS      current
    DESCRIPTION
        "The number of times packets have been delayed as a result of a
         precedence, or pipe user having used up its allotted bandwidth.
         Note that one single packet may be delayed several times; if a
         pipe is really full, this count may exceed the number of packets
         of this precedence actually passing through the pipe."
    ::= { dfl860PipePrecEntry 8 }

dfl860PipePrecDropedPackets OBJECT-TYPE
    SYNTAX      Counter32
    MAX-ACCESS  read-only
    STATUS      current
    DESCRIPTION
        "The number of pipe dropped packets with the corresponding precedence."
    ::= { dfl860PipePrecEntry 9 }

dfl860ALG OBJECT IDENTIFIER
    ::= { dfl860OSStats 9 }

dfl860AlgSessions OBJECT-TYPE
    SYNTAX      Gauge32
    MAX-ACCESS  read-only
    STATUS      current
    DESCRIPTION
        "Total ALG sessions"
    ::= { dfl860ALG 1 }

dfl860AlgConnections OBJECT-TYPE
    SYNTAX      Gauge32
    MAX-ACCESS  read-only
    STATUS      current
    DESCRIPTION
        "Total ALG connections"
    ::= { dfl860ALG 2 }

dfl860AlgTCPStreams OBJECT-TYPE
    SYNTAX      Gauge32
    MAX-ACCESS  read-only
    STATUS      current
    DESCRIPTION
        "Total ALG TCP streams"
    ::= { dfl860ALG 3 }

dfl860HttpAlg OBJECT IDENTIFIER
    ::= { dfl860ALG 4 }

dfl860HttpAlgTable OBJECT-TYPE
    SYNTAX      SEQUENCE OF Dfl860HttpAlgEntry
    MAX-ACCESS  not-accessible
    STATUS      current
    DESCRIPTION
        "Table of HTTP ALG objects."
    ::= { dfl860HttpAlg 1 }

dfl860HttpAlgEntry OBJECT-TYPE
    SYNTAX      Dfl860HttpAlgEntry
    MAX-ACCESS  not-accessible
    STATUS      current
    DESCRIPTION
        "A row of the table of HTTP ALG objects."
    INDEX       { dfl860HttpAlgIndex }
    ::= { dfl860HttpAlgTable 1 }

Dfl860HttpAlgEntry ::= SEQUENCE {
    dfl860HttpAlgIndex             Integer32,
    dfl860HttpAlgName              DisplayString,
    dfl860HttpAlgTotalRequested    Gauge32,
    dfl860HttpAlgTotalAllowed      Gauge32,
    dfl860HttpAlgTotalBlocked      Gauge32
}

dfl860HttpAlgIndex OBJECT-TYPE
    SYNTAX      Integer32 (1..2147483647)
    MAX-ACCESS  not-accessible
    STATUS      current
    DESCRIPTION
        "The index of an entry of the  Table of HTTP ALG objects."
    ::= { dfl860HttpAlgEntry 1 }

dfl860HttpAlgName OBJECT-TYPE
    SYNTAX      DisplayString
    MAX-ACCESS  read-only
    STATUS      current
    DESCRIPTION
        "The name of an HTTP ALG object."
    ::= { dfl860HttpAlgEntry 2 }

dfl860HttpAlgTotalRequested OBJECT-TYPE
    SYNTAX      Gauge32
    MAX-ACCESS  read-only
    STATUS      current
    DESCRIPTION
        "Total number of URL requests."
    ::= { dfl860HttpAlgEntry 3 }

dfl860HttpAlgTotalAllowed OBJECT-TYPE
    SYNTAX      Gauge32
    MAX-ACCESS  read-only
    STATUS      current
    DESCRIPTION
        "Total number of allowed URL requests."
    ::= { dfl860HttpAlgEntry 4 }

dfl860HttpAlgTotalBlocked OBJECT-TYPE
    SYNTAX      Gauge32
    MAX-ACCESS  read-only
    STATUS      current
    DESCRIPTION
        "Total number of blocked URL requests."
    ::= { dfl860HttpAlgEntry 5 }

dfl860HttpAlgCntFltTable OBJECT-TYPE
    SYNTAX      SEQUENCE OF Dfl860HttpAlgCntFltEntry
    MAX-ACCESS  not-accessible
    STATUS      current
    DESCRIPTION
        "Table of HTTP ALG content filtering rules."
    ::= { dfl860HttpAlg 2 }

dfl860HttpAlgCntFltEntry OBJECT-TYPE
    SYNTAX      Dfl860HttpAlgCntFltEntry
    MAX-ACCESS  not-accessible
    STATUS      current
    DESCRIPTION
        "Entry of the table of HTTP ALG content filtering rules."
    INDEX       { dfl860HttpAlgIndex, dfl860HttpAlgCntFltIndex }
    ::= { dfl860HttpAlgCntFltTable 1 }

Dfl860HttpAlgCntFltEntry ::= SEQUENCE {
    dfl860HttpAlgCntFltIndex       Integer32,
    dfl860HttpAlgCntFltName        DisplayString,
    dfl860HttpAlgCntFltRequests    Gauge32,
    dfl860HttpAlgCntFltAllowed     Gauge32,
    dfl860HttpAlgCntFltBlocked     Gauge32
}

dfl860HttpAlgCntFltIndex OBJECT-TYPE
    SYNTAX      Integer32 (1..2147483647)
    MAX-ACCESS  not-accessible
    STATUS      current
    DESCRIPTION
        "The index of an entry of the  Table of HTTP ALG
         content filtering objects."
    ::= { dfl860HttpAlgCntFltEntry 1 }

dfl860HttpAlgCntFltName OBJECT-TYPE
    SYNTAX      DisplayString
    MAX-ACCESS  read-only
    STATUS      current
    DESCRIPTION
        "The name of the a HTTP ALG content fitering."
    ::= { dfl860HttpAlgCntFltEntry 2 }

dfl860HttpAlgCntFltRequests OBJECT-TYPE
    SYNTAX      Gauge32
    MAX-ACCESS  read-only
    STATUS      current
    DESCRIPTION
        "Total number of URLs intercepted by a content
         filtering object."
    ::= { dfl860HttpAlgCntFltEntry 3 }

dfl860HttpAlgCntFltAllowed OBJECT-TYPE
    SYNTAX      Gauge32
    MAX-ACCESS  read-only
    STATUS      current
    DESCRIPTION
        "Total number of URLs intercepted and allowed
         by a content filtering object."
    ::= { dfl860HttpAlgCntFltEntry 4 }

dfl860HttpAlgCntFltBlocked OBJECT-TYPE
    SYNTAX      Gauge32
    MAX-ACCESS  read-only
    STATUS      current
    DESCRIPTION
        "Total number of URLs intercepted and blocked
         by a content filtering object."
    ::= { dfl860HttpAlgCntFltEntry 5 }

dfl860SmtpAlg OBJECT IDENTIFIER
    ::= { dfl860ALG 5 }

dfl860SmtpAlgTable OBJECT-TYPE
    SYNTAX  SEQUENCE OF Dfl860SmtpAlgEntry
    MAX-ACCESS  not-accessible
    STATUS  current
    DESCRIPTION
  "Table of SMTP ALG objects."
    ::= { dfl860SmtpAlg 1 }

dfl860SmtpAlgEntry OBJECT-TYPE
   SYNTAX  Dfl860SmtpAlgEntry
   MAX-ACCESS  not-accessible
    STATUS      current
    DESCRIPTION
        "A row of the table of SMTP ALG objects."
    INDEX       { dfl860SmtpAlgIndex }
    ::= { dfl860SmtpAlgTable 1 }

Dfl860SmtpAlgEntry ::= SEQUENCE {
    dfl860SmtpAlgIndex           Integer32,
    dfl860SmtpAlgName            DisplayString,
    dfl860SmtpAlgTotCheckedSes   Gauge32,
    dfl860SmtpAlgTotSpamSes      Gauge32,
    dfl860SmtpAlgTotDroppedSes   Gauge32
}

dfl860SmtpAlgIndex OBJECT-TYPE
    SYNTAX      Integer32 (1..2147483647)
    MAX-ACCESS  not-accessible
    STATUS      current
    DESCRIPTION
        "The index of an entry of the  Table of SMTP ALG objects."
    ::= { dfl860SmtpAlgEntry 1 }

dfl860SmtpAlgName OBJECT-TYPE
    SYNTAX      DisplayString
    MAX-ACCESS  read-only
    STATUS      current
    DESCRIPTION
        "The name of an SMTP ALG object."
    ::= { dfl860SmtpAlgEntry 2 }

dfl860SmtpAlgTotCheckedSes OBJECT-TYPE
    SYNTAX      Gauge32
    MAX-ACCESS  read-only
    STATUS      current
    DESCRIPTION
        "Total sessions checked by the SMTP ALG of corresponding index."
    ::= { dfl860SmtpAlgEntry 3 }

dfl860SmtpAlgTotSpamSes OBJECT-TYPE
    SYNTAX      Gauge32
    MAX-ACCESS  read-only
    STATUS      current
    DESCRIPTION
        "Total spam sessions detected by the SMTP ALG of corresponding index."
    ::= { dfl860SmtpAlgEntry 4 }

dfl860SmtpAlgTotDroppedSes OBJECT-TYPE
    SYNTAX      Gauge32
    MAX-ACCESS  read-only
    STATUS      current
    DESCRIPTION
        "Total deroped sessions for the SMTP ALG of corresponding index."
    ::= { dfl860SmtpAlgEntry 5 }


dfl860SmtpAlgDnsBlTable OBJECT-TYPE
    SYNTAX  SEQUENCE OF Dfl860SmtpAlgDnsBlEntry
    MAX-ACCESS  not-accessible
    STATUS  current
    DESCRIPTION
  "Table of SMTP ALG DNS balck list objects."
    ::= { dfl860SmtpAlg 2 }


dfl860SmtpAlgDnsBlEntry OBJECT-TYPE
   SYNTAX  Dfl860SmtpAlgDnsBlEntry
   MAX-ACCESS  not-accessible
    STATUS      current
    DESCRIPTION
        "A row of the table of SMTP ALG DNS black list objects."
    INDEX       { dfl860SmtpAlgIndex, dfl860SmtpAlgDnsBlIndex }
    ::= { dfl860SmtpAlgDnsBlTable 1 }


Dfl860SmtpAlgDnsBlEntry ::= SEQUENCE {
    dfl860SmtpAlgDnsBlIndex  Integer32,
    dfl860SmtpAlgDnsBlName    DisplayString,
    dfl860SmtpAlgDnsBlChecked      Gauge32,
    dfl860SmtpAlgDnsBlMatched  Gauge32,
    dfl860SmtpAlgDnsBlFailChecks  Gauge32
}

dfl860SmtpAlgDnsBlIndex OBJECT-TYPE
    SYNTAX      Integer32 (1..2147483647)
    MAX-ACCESS  not-accessible
    STATUS      current
    DESCRIPTION
        "The index of an entry of the  SMTP ALG DNS black list objects."
    ::= { dfl860SmtpAlgDnsBlEntry 1 }

dfl860SmtpAlgDnsBlName OBJECT-TYPE
    SYNTAX      DisplayString
    MAX-ACCESS  read-only
    STATUS      current
    DESCRIPTION
  "The SMTP DNS black list name."
    ::= { dfl860SmtpAlgDnsBlEntry 2 }

dfl860SmtpAlgDnsBlChecked OBJECT-TYPE
    SYNTAX      Gauge32
    MAX-ACCESS  read-only
    STATUS      current
    DESCRIPTION
  "Total sessions checked againt SMTP ALG DNS black list of corresponding index"
    ::= { dfl860SmtpAlgDnsBlEntry 3 }

dfl860SmtpAlgDnsBlMatched OBJECT-TYPE
    SYNTAX      Gauge32
    MAX-ACCESS  read-only
    STATUS      current
    DESCRIPTION
  "Total sessions that matched SMTP ALG DNS black list of corresponding index"
    ::= { dfl860SmtpAlgDnsBlEntry 4 }

dfl860SmtpAlgDnsBlFailChecks OBJECT-TYPE
    SYNTAX      Gauge32
    MAX-ACCESS  read-only
    STATUS      current
    DESCRIPTION
  "Total failed checks for the SMTP ALG DNS black list of corresponding index"
    ::= { dfl860SmtpAlgDnsBlEntry 5 }

dfl860DHCPRelay OBJECT IDENTIFIER
    ::= { dfl860OSStats 11 }

dfl860DHCPRelayCurClients OBJECT-TYPE
    SYNTAX      Gauge32
    MAX-ACCESS  read-only
    STATUS      current
    DESCRIPTION
        "Total DHCP relay active relayed clients."
    ::= { dfl860DHCPRelay 1 }

dfl860DHCPRelayCurTrans OBJECT-TYPE
    SYNTAX      Gauge32
    MAX-ACCESS  read-only
    STATUS      current
    DESCRIPTION
        "Ongoing DHCP relay transactions."
    ::= { dfl860DHCPRelay 2 }

dfl860DHCPRelayRejected OBJECT-TYPE
    SYNTAX      Gauge32
    MAX-ACCESS  read-only
    STATUS      current
    DESCRIPTION
        "Total DHCP relay packets rejected."
    ::= { dfl860DHCPRelay 3 }

dfl860DHCPRelayRuleTable OBJECT-TYPE
    SYNTAX      SEQUENCE OF Dfl860DHCPRelayRuleEntry
    MAX-ACCESS  not-accessible
    STATUS      current
    DESCRIPTION
        "Table of DHCP relay rules."
    ::= { dfl860DHCPRelay 4 }

dfl860DHCPRelayRuleEntry OBJECT-TYPE
    SYNTAX      Dfl860DHCPRelayRuleEntry
    MAX-ACCESS  not-accessible
    STATUS      current
    DESCRIPTION
        "Entry of the table of DHCP relay rules"
    INDEX       { dfl860DHCPRelayRuleIndex }
    ::= { dfl860DHCPRelayRuleTable 1 }

Dfl860DHCPRelayRuleEntry ::= SEQUENCE {
    dfl860DHCPRelayRuleIndex       Integer32,
    dfl860DHCPRelayRuleName        DisplayString,
    dfl860DHCPRelayRuleHits        Gauge32,
    dfl860DHCPRelayRuleCurClients  Gauge32,
    dfl860DHCPRelayRuleRejCliPkts  Gauge32,
    dfl860DHCPRelayRuleRejSrvPkts  Gauge32
}

dfl860DHCPRelayRuleIndex OBJECT-TYPE
    SYNTAX      Integer32 (1..2147483647)
    MAX-ACCESS  not-accessible
    STATUS      current
    DESCRIPTION
        "Index of the table of DHCP relay rules."
    ::= { dfl860DHCPRelayRuleEntry 1 }

dfl860DHCPRelayRuleName OBJECT-TYPE
    SYNTAX      DisplayString
    MAX-ACCESS  read-only
    STATUS      current
    DESCRIPTION
        "Display name of a DHCP relay rule"
    ::= { dfl860DHCPRelayRuleEntry 2 }

dfl860DHCPRelayRuleHits OBJECT-TYPE
    SYNTAX      Gauge32
    MAX-ACCESS  read-only
    STATUS      current
    DESCRIPTION
        "Number of the times the  DHCP relay rule with corresponding index was
         used."
    ::= { dfl860DHCPRelayRuleEntry 3 }

dfl860DHCPRelayRuleCurClients OBJECT-TYPE
    SYNTAX      Gauge32
    MAX-ACCESS  read-only
    STATUS      current
    DESCRIPTION
        "Number of ctive relayed clients by the DHCP relay rule with corresponding index."
    ::= { dfl860DHCPRelayRuleEntry 4 }

dfl860DHCPRelayRuleRejCliPkts OBJECT-TYPE
    SYNTAX      Gauge32
    MAX-ACCESS  read-only
    STATUS      current
    DESCRIPTION
        "Number of client packets rejected by a rule."
    ::= { dfl860DHCPRelayRuleEntry 5 }

dfl860DHCPRelayRuleRejSrvPkts OBJECT-TYPE
    SYNTAX      Gauge32
    MAX-ACCESS  read-only
    STATUS      current
    DESCRIPTION
        "Number of DHCP server packets rejected by the DHCP relay rule
         with the corresponding index."
    ::= { dfl860DHCPRelayRuleEntry 6 }

dfl860HA OBJECT IDENTIFIER
    ::= { dfl860OSStats 12 }

dfl860HASyncSendQueueLength OBJECT-TYPE
    SYNTAX      Gauge32
    MAX-ACCESS  read-only
    STATUS      current
    DESCRIPTION
        "Size of the queue used for the High Availability sync interface."
    ::= { dfl860HA 1 }

dfl860HASyncSendQueueUsagePkt OBJECT-TYPE
    SYNTAX      Gauge32
    MAX-ACCESS  read-only
    STATUS      current
    DESCRIPTION
        "High Availability Sync interface queue usage in number of packets."
    ::= { dfl860HA 2 }

dfl860HASyncSendQueueUsageOct OBJECT-TYPE
    SYNTAX      Gauge32
    MAX-ACCESS  read-only
    STATUS      current
    DESCRIPTION
        "High Availability Sync interface queue usage in number of octects."
    ::= { dfl860HA 3 }

dfl860HASyncSentPackets OBJECT-TYPE
    SYNTAX      Counter32
    MAX-ACCESS  read-only
    STATUS      current
    DESCRIPTION
        "Number High Availability packets sent on Sync."
    ::= { dfl860HA 4 }

dfl860HASyncSendResentPackets OBJECT-TYPE
    SYNTAX      Counter32
    MAX-ACCESS  read-only
    STATUS      current
    DESCRIPTION
        "Number of High Availability packets resent on Sync."
    ::= { dfl860HA 5 }

dfl860StatsConformance OBJECT IDENTIFIER
    ::= { dfl860MibConfs 1 }

dfl860StatsRegGroups OBJECT IDENTIFIER
    ::= { dfl860MibObjectGroups 1 }

dfl860SystemObjectGroup OBJECT-GROUP
    OBJECTS     { dfl860SysCpuLoad,
                  dfl860SysForwardedBits,
                  dfl860SysForwardedPackets,
                  dfl860SysBuffUse,
                  dfl860SysConns,
                  dfl860HWSensorName,
                  dfl860HWSensorValue,
                  dfl860HWSensorUnit,
                  dfl860SysMemUsage,
                  dfl860SysTimerUsage,
                  dfl860SysConnOPS,
                  dfl860SysConnCPS,
                  dfl860SysHCForwardedBits }
    STATUS      current
    DESCRIPTION
        "System statistics Group"
    ::= { dfl860StatsRegGroups 1 }

dfl860IPsecObjectGroup OBJECT-GROUP
    OBJECTS     { dfl860IPsecPhaseOneActive,
                  dfl860IPsecPhaseOneAggrModeDone,
                  dfl860IPsecQuickModeActive,
                  dfl860IPsecPhaseOneDone,
                  dfl860IPsecPhaseOneFailed,
                  dfl860IPsecPhaseOneRekeyed,
                  dfl860IPsecQuickModeDone,
                  dfl860IPsecQuickModeFailed,
                  dfl860IPsecInfoDone,
                  dfl860IPsecInfoFailed,
                  dfl860IPsecInOctetsComp,
                  dfl860IPsecInOctetsUncomp,
                  dfl860IPsecOutOctetsComp,
                  dfl860IPsecOutOctetsUncomp,
                  dfl860IPsecForwardedOctetsComp,
                  dfl860IPsecForwardedOctetsUcomp,
                  dfl860IPsecInPackets,
                  dfl860IPsecOutPackets,
                  dfl860IPsecForwardedPackets,
                  dfl860IPsecActiveTransforms,
                  dfl860IPsecTotalTransforms,
                  dfl860IPsecOutOfTransforms,
                  dfl860IPsecTotalRekeys }
    STATUS      current
    DESCRIPTION
        "IPsec Group"
    ::= { dfl860StatsRegGroups 2 }

dfl860StateCountersGroup OBJECT-GROUP
    OBJECTS     { dfl860SysPscTcpSyn,
                  dfl860SysPscTcpOpen,
                  dfl860SysPscTcpFin,
                  dfl860SysPscUdp,
                  dfl860SysPscIcmp,
                  dfl860SysPscOther }
    STATUS      current
    DESCRIPTION
        "Per state counters"
    ::= { dfl860StatsRegGroups 3 }

dfl860IPPoolGroup OBJECT-GROUP
    OBJECTS     { dfl860IPPoolsNumber,
                  dfl860IPPoolName,
                  dfl860IPPoolPrepare,
                  dfl860IPPoolFree,
                  dfl860IPPoolMisses,
                  dfl860IPPoolClientFails,
                  dfl860IPPoolUsed }
    STATUS      current
    DESCRIPTION
        "IP pool entry objects group"
    ::= { dfl860StatsRegGroups 4 }

dfl860DHCPServerGroup OBJECT-GROUP
    OBJECTS     { dfl860DHCPTotalRejected,
                  dfl860DHCPRuleName,
                  dfl860DHCPRuleUsage,
                  dfl860DHCPRuleUsagePercent,
                  dfl860DHCPActiveClients,
                  dfl860DHCPActiveClientsPercent,
                  dfl860DHCPRejectedRequests,
                  dfl860DHCPTotalLeases }
    STATUS      current
    DESCRIPTION
        "DHCP server rules objects."
    ::= { dfl860StatsRegGroups 5 }

dfl860RuleUseGroup OBJECT-GROUP
    OBJECTS     { dfl860RuleName, dfl860RuleUse }
    STATUS      current
    DESCRIPTION
        "Rule use objects."
    ::= { dfl860StatsRegGroups 6 }

dfl860UserAuthGroup OBJECT-GROUP
    OBJECTS     { dfl860UserAuthHTTPUsers, dfl860UserAuthXAUTHUsers,
                  dfl860UserAuthHTTPSUsers, dfl860UserAuthPPPUsers,
                  dfl860UserAuthEAPUsers, dfl860UserAuthRuleName,
                  dfl860UserAuthRuleUse }
    STATUS      current
    DESCRIPTION
        "User auth objects."
    ::= { dfl860StatsRegGroups 7 }

dfl860IfStatsGroup OBJECT-GROUP
    OBJECTS     { dfl860IfName,
                  dfl860IfFragsIn,
                  dfl860IfFragReassOk,
                  dfl860IfFragReassFail,
                  dfl860IfPktsInCnt,
                  dfl860IfPktsOutCnt,
                  dfl860IfBitsInCnt,
                  dfl860IfBitsOutCnt,
                  dfl860IfPktsTotCnt,
                  dfl860IfBitsTotCnt,
                  dfl860IfHCPktsInCnt,
                  dfl860IfHCPktsOutCnt,
                  dfl860IfHCBitsInCnt,
                  dfl860IfHCBitsOutCnt,
                  dfl860IfHCPktsTotCnt,
                  dfl860IfHCBitsTotCnt,
                  dfl860IfRxRingFifoErrors,
                  dfl860IfRxDespools,
                  dfl860IfRxAvgUse,
                  dfl860IfRxRingSaturation,
                  dfl860RxRingFlooded,
                  dfl860IfTxDespools,
                  dfl860IfTxAvgUse,
                  dfl860IfTxRingSaturation,
                  dfl860RxTingFlooded }
    STATUS      current
    DESCRIPTION
        "DFL-860 interface statistics group."
    ::= { dfl860StatsRegGroups 8 }

dfl860LinkMonitorGroup OBJECT-GROUP
    OBJECTS     { dfl860LinkMonGrp,
                  dfl860LinkMonGrpName,
                  dfl860LinkMonGrpHostsUp,
                  dfl860LinkMonHostId,
                  dfl860LinkMonHostShortTermLoss,
                  dfl860LinkMonHostPacketsLost }
    STATUS      current
    DESCRIPTION
        "DFL-860 link monitor statistics group"
    ::= { dfl860StatsRegGroups 9 }

dfl860PipesObjectGroup OBJECT-GROUP
    OBJECTS     { dfl860PipeUsers,
                  dfl860PipeName,
                  dfl860PipeMinPrec,
                  dfl860PipeMaxPrec,
                  dfl860PipeDefPrec,
                  dfl860PipeNumPrec,
                  dfl860PipeNumUsers,
                  dfl860PipeCurrentBps,
                  dfl860PipeCurrentPps,
                  dfl860PipeDelayedPackets,
                  dfl860PipeDropedPackets,
                  dfl860PipePrec,
                  dfl860PipePrecBps,
                  dfl860PipePrecTotalPps,
                  dfl860PipePrecReservedBps,
                  dfl860PipePrecDynLimBps,
                  dfl860PipePrecDynUsrLimBps,
                  dfl860PipePrecDelayedPackets,
                  dfl860PipePrecDropedPackets }
    STATUS      current
    DESCRIPTION
        "DFL-860 pipes statistics group"
    ::= { dfl860StatsRegGroups 10 }

dfl860DHCPRelayObjectGroup OBJECT-GROUP
    OBJECTS     { dfl860DHCPRelayCurClients,
                  dfl860DHCPRelayCurTrans,
                  dfl860DHCPRelayRejected,
                  dfl860DHCPRelayRuleName,
                  dfl860DHCPRelayRuleHits,
                  dfl860DHCPRelayRuleCurClients,
                  dfl860DHCPRelayRuleRejCliPkts,
                  dfl860DHCPRelayRuleRejSrvPkts }
    STATUS      current
    DESCRIPTION
        "DFL-860 DHCP relay statistics group"
    ::= { dfl860StatsRegGroups 12 }

dfl860AlgGroup OBJECT-GROUP
    OBJECTS     { dfl860AlgSessions,
                  dfl860AlgConnections,
                  dfl860AlgTCPStreams,
                  dfl860HttpAlgName,
                  dfl860HttpAlgTotalRequested,
                  dfl860HttpAlgTotalAllowed,
                  dfl860HttpAlgTotalBlocked,
                  dfl860HttpAlgCntFltName,
                  dfl860HttpAlgCntFltRequests,
                  dfl860HttpAlgCntFltAllowed,
                  dfl860HttpAlgCntFltBlocked }
    STATUS      current
    DESCRIPTION
        "DFL-860 HTTP ALG statistics group"
    ::= { dfl860StatsRegGroups 13 }

dfl860HAGroup OBJECT-GROUP
    OBJECTS     { dfl860HASyncSendQueueLength,
                  dfl860HASyncSendQueueUsagePkt,
                  dfl860HASyncSendQueueUsageOct,
                  dfl860HASyncSentPackets,
                  dfl860HASyncSendResentPackets }
    STATUS      current
    DESCRIPTION
        "DFL-860 HA statistics group"
    ::= { dfl860StatsRegGroups 14 }

dfl860IfVlanGroup OBJECT-GROUP
    OBJECTS     { dfl860IfVlanUntaggedInPkts,
                  dfl860IfVlanUntaggedOutPkts,
                  dfl860IfVlanUntaggedTotPkts,
                  dfl860IfVlanUntaggedInOctets,
                  dfl860IfVlanUntaggedOutOctets,
                  dfl860IfVlanUntaggedTotOctets }
    STATUS      current
    DESCRIPTION
        "DFL-860 VLAN statistics group"
    ::= { dfl860StatsRegGroups 15 }


dfl860SmtpAlgGroup OBJECT-GROUP
    OBJECTS { dfl860SmtpAlgName,
              dfl860SmtpAlgTotCheckedSes,
              dfl860SmtpAlgTotSpamSes,
              dfl860SmtpAlgTotDroppedSes,
              dfl860SmtpAlgDnsBlName,
              dfl860SmtpAlgDnsBlChecked,
              dfl860SmtpAlgDnsBlMatched,
              dfl860SmtpAlgDnsBlFailChecks }
   STATUS current
   DESCRIPTION
       "Clavister SMTP ALG objects group"
   ::= { dfl860StatsRegGroups 16 }

dfl860SysTCPGroup OBJECT-GROUP
    OBJECTS { dfl860SysTCPRecvSmall,
              dfl860SysTCPRecvLarge,
              dfl860SysTCPSendSmall,
              dfl860SysTCPSendLarge }
    STATUS current
    DESCRIPTION
      "DFL-860 TCP buffer usage group"
    ::= { dfl860StatsRegGroups 17 }



dfl860StatsCompliance MODULE-COMPLIANCE
    STATUS      current
    DESCRIPTION
        "Module Compliance"

    MODULE      -- this module

        MANDATORY-GROUPS
                { dfl860SystemObjectGroup,
                  dfl860IPsecObjectGroup,
                  dfl860StateCountersGroup,
                  dfl860IPPoolGroup,
                  dfl860DHCPServerGroup,
                  dfl860RuleUseGroup,
                  dfl860UserAuthGroup,
                  dfl860IfStatsGroup,
                  dfl860LinkMonitorGroup,
                  dfl860PipesObjectGroup,
                  dfl860DHCPRelayObjectGroup,
                  dfl860AlgGroup,
                  dfl860HAGroup,
                  dfl860IfVlanGroup,
                  dfl860SmtpAlgGroup,
                  dfl860SysTCPGroup }

    ::= { dfl860StatsConformance 1 }

END -- end of module DFL860-MIB.
