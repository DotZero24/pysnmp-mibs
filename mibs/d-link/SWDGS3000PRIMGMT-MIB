-- *****************************************************************************
-- proprietary management MIB
-- *****************************************************************************



SWDGS3000PRIMGMT-MIB    DEFINITIONS ::= BEGIN

    IMPORTS
        MODULE-IDENTITY             FROM SNMPv2-SMI
        dlink-mgmt,dlink-products   FROM DLINK-ID-REC-MIB;

--
--   DGS3000 series Product
--

    dlink-Dgs3000Prod					OBJECT IDENTIFIER ::= { dlink-products 133 }
    dlink-Dgs3000Prod-DGS3000-28SC  	OBJECT IDENTIFIER ::= { dlink-Dgs3000Prod 5 }
    dlink-Dgs3000Prod-DGS3000-28SCax	OBJECT IDENTIFIER ::= { dlink-Dgs3000Prod-DGS3000-28SC 1 }


    dlink-Dgs3000Proj					OBJECT IDENTIFIER ::= { dlink-mgmt 133 }
    dlink-Dgs3000Proj-DGS3000-28SC		OBJECT IDENTIFIER ::= { dlink-Dgs3000Proj 5 }
    dlink-Dgs3000Proj-DGS3000-28SCax	OBJECT IDENTIFIER ::= { dlink-Dgs3000Proj-DGS3000-28SC 1 }


END
