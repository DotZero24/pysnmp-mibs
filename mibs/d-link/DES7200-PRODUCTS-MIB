-- *****************************************************************
-- MY-PRODUCTS-MIB.mib:  My Product Object Identifier Assignments
--
-- March 2002, Wuzg
--
-- Copyright (c) 2002 by My Networks Co.,Ltd.
-- All rights reserved.
--
-- *****************************************************************
--

DES7200-PRODUCTS-MIB DEFINITIONS ::= BEGIN

IMPORTS
        MODULE-IDENTITY,
        OBJECT-TYPE
                FROM SNMPv2-SMI
        MODULE-COMPLIANCE,
        OBJECT-GROUP,
        NOTIFICATION-GROUP
                FROM SNMPv2-CONF
        myModules,
        mySwitchProducts
                FROM DES7200-SMI;

myProductsMIB MODULE-IDENTITY
        LAST-UPDATED "200203200000Z"
        ORGANIZATION "My Networks Co.,Ltd."
        CONTACT-INFO
                "
                Tel: 0591-83057888

                E-mail: service@star-net.cn"
        DESCRIPTION
                "This module defines the object identifiers that are
            		assigned to various hardware platforms, and hence are
            		returned as values for sysObjectID"
        REVISION      "200203200000Z"
        DESCRIPTION
                "Initial version of this MIB module."
        ::= { myModules 1}

-- devices return a sysObjectID value that corresponds to the
-- device model number

-- ****************************** switch ***********************************

des-7206  OBJECT IDENTIFIER ::= { mySwitchProducts 1 }

des-7210  OBJECT IDENTIFIER ::= { mySwitchProducts 2 }

des-7206E OBJECT IDENTIFIER ::= { mySwitchProducts 3 }

des-7210E OBJECT IDENTIFIER ::= { mySwitchProducts 4 }


END
