SW-PROJECTX-SRPRIMGMT-MIB    DEFINITIONS ::= BEGIN

    IMPORTS
        MODULE-IDENTITY					FROM SNMPv2-SMI
        dlink-products,dlink-mgmt		FROM DLINK-ID-REC-MIB;


	dlink-ProjectXSeriesProd	OBJECT IDENTIFIER ::= { dlink-products 59 }
	dlink-Dgs3224SRi			OBJECT IDENTIFIER ::= { dlink-ProjectXSeriesProd 1 }
	dlink-Dgs3224SR				OBJECT IDENTIFIER ::= { dlink-ProjectXSeriesProd 2 }
	dlink-Des3252SR				OBJECT IDENTIFIER ::= { dlink-ProjectXSeriesProd 3 }
	dlink-Dgs3324SRi			OBJECT IDENTIFIER ::= { dlink-ProjectXSeriesProd 4 }
	dlink-Dgs3324SR				OBJECT IDENTIFIER ::= { dlink-ProjectXSeriesProd 5 }
	dlink-Des3352SR				OBJECT IDENTIFIER ::= { dlink-ProjectXSeriesProd 6 }
	dlink-Dxs3326GSR			OBJECT IDENTIFIER ::= { dlink-ProjectXSeriesProd 7 }
	dlink-Dxs3350SR				OBJECT IDENTIFIER ::= { dlink-ProjectXSeriesProd 8 }


    dgsProjectXSeriesProd		OBJECT IDENTIFIER ::= { dlink-mgmt 59 }
    dgs3224SRi       			OBJECT IDENTIFIER ::= { dgsProjectXSeriesProd 1 }
	dgs3224SR       			OBJECT IDENTIFIER ::= { dgsProjectXSeriesProd 2 }
    des3252SR	       			OBJECT IDENTIFIER ::= { dgsProjectXSeriesProd 3 }
    dgs3324SRi       			OBJECT IDENTIFIER ::= { dgsProjectXSeriesProd 4 }
    dgs3324SR       			OBJECT IDENTIFIER ::= { dgsProjectXSeriesProd 5 }
    des3352SR       			OBJECT IDENTIFIER ::= { dgsProjectXSeriesProd 6 }
    dxs3326GSR       			OBJECT IDENTIFIER ::= { dgsProjectXSeriesProd 7 }
    dxs3350SR       			OBJECT IDENTIFIER ::= { dgsProjectXSeriesProd 8 }

--  --------------------------------------------------------------------------------

	dlink-Des6500SeriesProd		OBJECT IDENTIFIER ::= { dlink-products 61 }
    dlink-Des6500				OBJECT IDENTIFIER ::= { dlink-Des6500SeriesProd 1 }

    des6500SeriesProd			OBJECT IDENTIFIER ::= { dlink-mgmt 61 }
    des6500						OBJECT IDENTIFIER ::= { des6500SeriesProd 1 }


END
