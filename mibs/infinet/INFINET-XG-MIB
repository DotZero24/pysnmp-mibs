INFINET-XG-MIB DEFINITIONS ::= BEGIN

IMPORTS
	infinet
		FROM INFINET-MIB
	MODULE-IDENTITY
		FROM SNMPv2-SMI;


iwbridge MODULE-IDENTITY
	LAST-UPDATED "201408290240Z"
	ORGANIZATION "Infinet Wireless Ltd."
	CONTACT-INFO
		"Anthony Berzin

		Postal: Infinet Wireless Ltd.,
		        Russia, Ekaterinburg,
		        Serafimi Deryabinoi st, 24

		Phone:  +7 343 253 1533
		Email:  aberzin@infinetwireless.com"
	DESCRIPTION
		"The mib module, containing XG bridge options."
	::= { infinet 4 }


xg OBJECT IDENTIFIER 	::= { iwbridge 1 }


END
