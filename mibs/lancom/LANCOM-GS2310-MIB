LANCOM-GS2310-MIB DEFINITIONS ::= BEGIN

IMPORTS
    DisplayString,MacAddress FROM SNMPv2-TC
    MODULE-COMPLIANCE,OBJECT-GROUP, NOTIFICATION-GROUP       FROM SNMPv2-CONF
    ifIndex    FROM RFC1213-MIB
    enterprises,MODULE-IDENTITY,OBJECT-TYPE,NOTIFICATION-TYPE,Counter32,Counter64,IpAddress        FROM SNMPv2-SMI
    InetAddress                   FROM INET-ADDRESS-MIB
    MacAddress FROM BRIDGE-MIB;

lancom-systems MODULE-IDENTITY
        LAST-UPDATED "202002190000Z"
        ORGANIZATION "LANCOM Systems GmbH."
        CONTACT-INFO
            "Adenauerstrasse 20 / B2, 52146 Wuerselen, Germany
            Email: info@lancom.de
            TEL: +49 (0)2405 49936 0
            FAX: +49 (0)2405 49936 99"
        DESCRIPTION
            "The MIB module is for LANCOM Systems"
        ::= { enterprises 2356 }

switchingSystems                                                          OBJECT IDENTIFIER ::= { lancom-systems 800 }

gigabitEthernetSwitches                                             OBJECT IDENTIFIER ::= { switchingSystems 3 }

lancomGS2310                                                   OBJECT IDENTIFIER ::= { gigabitEthernetSwitches 2313 }

gs2310System                                                   OBJECT IDENTIFIER ::= { lancomGS2310 1 }

gs2310SystemInformation                                        OBJECT IDENTIFIER ::= { gs2310System 1 }

gs2310ModelName OBJECT-TYPE
   SYNTAX       DisplayString
   MAX-ACCESS   read-only
   STATUS       current
   DESCRIPTION
       ""
 ::= { gs2310SystemInformation 1 }

gs2310BIOSVersion OBJECT-TYPE
   SYNTAX       DisplayString
   MAX-ACCESS   read-only
   STATUS       current
   DESCRIPTION
       ""
   ::= { gs2310SystemInformation 2 }

gs2310FirmwareVersion OBJECT-TYPE
   SYNTAX       DisplayString
   MAX-ACCESS   read-only
   STATUS       current
   DESCRIPTION
       ""
   ::= { gs2310SystemInformation 3 }

gs2310HardwareMechanicalVersion OBJECT-TYPE
   SYNTAX       DisplayString
   MAX-ACCESS   read-only
   STATUS       current
   DESCRIPTION
       ""
   ::= { gs2310SystemInformation 4 }

gs2310SerialNumber OBJECT-TYPE
   SYNTAX       DisplayString
   MAX-ACCESS   read-only
   STATUS       current
   DESCRIPTION
       ""
   ::= { gs2310SystemInformation 5 }

gs2310HostMACAddress OBJECT-TYPE
   SYNTAX       MacAddress
   MAX-ACCESS   read-only
   STATUS       current
   DESCRIPTION
       ""
   ::= { gs2310SystemInformation 6 }

gs2310ConsoleBaudrate OBJECT-TYPE
   SYNTAX       DisplayString
   MAX-ACCESS   read-only
   STATUS       current
   DESCRIPTION
       ""
   ::= { gs2310SystemInformation 7 }

gs2310RAMSize OBJECT-TYPE
   SYNTAX       DisplayString
   MAX-ACCESS   read-only
   STATUS       current
   DESCRIPTION
       ""
   ::= { gs2310SystemInformation 8 }

gs2310FlashSize OBJECT-TYPE
   SYNTAX       DisplayString
   MAX-ACCESS   read-only
   STATUS       current
   DESCRIPTION
       ""
   ::= { gs2310SystemInformation 9 }

gs2310BridgeFDBSize OBJECT-TYPE
   SYNTAX       DisplayString
   MAX-ACCESS   read-only
   STATUS       current
   DESCRIPTION
       ""
   ::= { gs2310SystemInformation 10 }

gs2310TransmitQueue OBJECT-TYPE
   SYNTAX       DisplayString
   MAX-ACCESS   read-only
   STATUS       current
   DESCRIPTION
       ""
   ::= { gs2310SystemInformation 11 }

gs2310MaximumFrameSize OBJECT-TYPE
   SYNTAX       DisplayString
   MAX-ACCESS   read-only
   STATUS       current
   DESCRIPTION
       ""
   ::= { gs2310SystemInformation 12 }

gs2310CPULoad OBJECT-TYPE
   SYNTAX       DisplayString
   MAX-ACCESS   read-only
   STATUS       current
   DESCRIPTION
       ""
   ::= { gs2310SystemInformation 13 }

gs2310SystemDescription OBJECT-TYPE
   SYNTAX       DisplayString
   MAX-ACCESS   read-only
   STATUS       current
   DESCRIPTION
       ""
   ::= { gs2310SystemInformation 21 }

gs2310Location OBJECT-TYPE
   SYNTAX       DisplayString
   MAX-ACCESS   read-only
   STATUS       current
   DESCRIPTION
       ""
   ::= { gs2310SystemInformation 22 }

gs2310Contact OBJECT-TYPE
   SYNTAX       DisplayString
   MAX-ACCESS   read-only
   STATUS       current
   DESCRIPTION
       ""
   ::= { gs2310SystemInformation 23 }

gs2310DeviceName OBJECT-TYPE
   SYNTAX       DisplayString
   MAX-ACCESS   read-only
   STATUS       current
   DESCRIPTION
       ""
   ::= { gs2310SystemInformation 24 }

gs2310SystemDate OBJECT-TYPE
   SYNTAX       DisplayString
   MAX-ACCESS   read-only
   STATUS       current
   DESCRIPTION
       ""
   ::= { gs2310SystemInformation 25 }

gs2310SystemUptime OBJECT-TYPE
   SYNTAX       DisplayString
   MAX-ACCESS   read-only
   STATUS       current
   DESCRIPTION
       ""
   ::= { gs2310SystemInformation 26 }

gs2310SystemIPv4Address OBJECT-TYPE
   SYNTAX       DisplayString
   MAX-ACCESS   read-only
   STATUS       current
   DESCRIPTION
       ""
   ::= { gs2310SystemInformation 27 }

gs2310SystemIPv4SubnetMask OBJECT-TYPE
   SYNTAX       DisplayString
   MAX-ACCESS   read-only
   STATUS       current
   DESCRIPTION
       ""
   ::= { gs2310SystemInformation 28 }

gs2310SystemIPv4Gateway OBJECT-TYPE
   SYNTAX       DisplayString
   MAX-ACCESS   read-only
   STATUS       current
   DESCRIPTION
       ""
   ::= { gs2310SystemInformation 29 }

gs2310IPv6LinkLocalAddress OBJECT-TYPE
   SYNTAX       DisplayString
   MAX-ACCESS   read-only
   STATUS       current
   DESCRIPTION
       ""
   ::= { gs2310SystemInformation 30 }

gs2310IPv6Address OBJECT-TYPE
   SYNTAX       DisplayString
   MAX-ACCESS   read-only
   STATUS       current
   DESCRIPTION
       ""
   ::= { gs2310SystemInformation 31 }

gs2310IPv6Prefix OBJECT-TYPE
   SYNTAX       DisplayString
   MAX-ACCESS   read-only
   STATUS       current
   DESCRIPTION
       ""
   ::= { gs2310SystemInformation 32 }

gs2310IPv6Gateway OBJECT-TYPE
   SYNTAX       DisplayString
   MAX-ACCESS   read-only
   STATUS       current
   DESCRIPTION
       ""
   ::= { gs2310SystemInformation 33 }

gs2310LargestFreeMemBlock OBJECT-TYPE
   SYNTAX       Integer32
   MAX-ACCESS   read-only
   STATUS       current
   DESCRIPTION
       "Largest free memory block in Kb"
   ::= { gs2310SystemInformation 1500 }

gs2310MemFree  OBJECT-TYPE
   SYNTAX       Integer32
   MAX-ACCESS   read-only
   STATUS       current
   DESCRIPTION
       "Free memory in Kb"
   ::= { gs2310SystemInformation 1501 }



gs2310SystemTime                                            OBJECT IDENTIFIER ::= { gs2310System 2 }

gs2310SystemTimeManual                                      OBJECT IDENTIFIER ::= { gs2310SystemTime 1 }

gs2310SystemTimeManualClockSource OBJECT-TYPE
   SYNTAX	INTEGER {useLocal(0),useNTP(1)}
   MAX-ACCESS   read-write
   STATUS       current
   DESCRIPTION
       "default: 0,
        0 : Use Local Settings,
        1 : Use NTP Server."
   ::= { gs2310SystemTimeManual 1 }

gs2310SystemTimeManualLocaltime OBJECT-TYPE
   SYNTAX       DisplayString
   MAX-ACCESS   read-write
   STATUS       current
   DESCRIPTION
       "Get/Set the system time of the device.
        The input format is 'Year-Month-Day Hour:Minute:Second'.
        ex: 2011-01-01 05:43:05  means 2011/1/1 - 05:43:05 .
        The value range:
        Year    : 2010 - 2090,
        Mouth   : 1 - 12,
        Day     : 1 - 31,
        Hour    : 0 - 23,
        Minute  : 0 - 59,
        Sec     : 0 - 59."
   ::= { gs2310SystemTimeManual 2 }

gs2310SystemTimeManualTimeZoneOffset OBJECT-TYPE
   SYNTAX       INTEGER(-720..780)
   MAX-ACCESS   read-write
   STATUS       current
   DESCRIPTION
       "Get/Set the NTP Time Zone.
        The value range is between -720 and 780 (minutes)."
   ::= { gs2310SystemTimeManual 3 }

gs2310SystemTimeManualDaylightSavings OBJECT-TYPE
   SYNTAX       INTEGER { disable(0), enable(1) }
   MAX-ACCESS   read-write
   STATUS       current
   DESCRIPTION
       "default: 0,
        0 : Disable,
        1 : Enable."
   ::= { gs2310SystemTimeManual 4 }

gs2310SystemTimeManualTimeSetOffset OBJECT-TYPE
   SYNTAX       Integer32(1..1440)
   MAX-ACCESS   read-write
   STATUS       current
   DESCRIPTION
       "Get/Set the Daylight Saving Time.
        The value range is between 1 and 1440 (minutes),
        Default : 60 (minutes)."
   ::= { gs2310SystemTimeManual 5 }

gs2310SystemTimeManualDaylightSavingsType OBJECT-TYPE
   SYNTAX       INTEGER { byDates(0), recurring(1) }
   MAX-ACCESS   read-write
   STATUS       current
   DESCRIPTION
       "default: 0,
        0 : By dates,
        1 : Recurring."
   ::= { gs2310SystemTimeManual 6 }

gs2310SystemTimeManualDaylightSavingsBydatesFrom OBJECT-TYPE
   SYNTAX       DisplayString
   MAX-ACCESS   read-write
   STATUS       current
   DESCRIPTION
       "Get/Set the Start time of By dates Daylight Savings.
        The input format is 'Year-Month-Day Hour:Minute'.
        ex: 2011-01-01 05:43  means 2011/1/1 - 05:43 .
        The value range:
        Year    : 2010 - 2090,
        Mouth   : 1 - 12,
        Day     : 1 - 31,
        Hour    : 0 - 23,
        Minute  : 0 - 59."
   ::= { gs2310SystemTimeManual 7 }

gs2310SystemTimeManualDaylightSavingsBydatesTo OBJECT-TYPE
   SYNTAX       DisplayString
   MAX-ACCESS   read-write
   STATUS       current
   DESCRIPTION
       "Get/Set the End time of By dates Daylight Savings.
        The input format is 'Year-Month-Day Hour:Minute'.
        ex: 2011-01-01 05:43  means 2011/1/1 - 05:43 .
        The value range:
        Year    : 2010 - 2090,
        Mouth   : 1 - 12,
        Day     : 1 - 31,
        Hour    : 0 - 23,
        Minute  : 0 - 59."
   ::= { gs2310SystemTimeManual 8 }

gs2310SystemTimeManualDaylightSavingsRecurringDayFrom OBJECT-TYPE
   SYNTAX      INTEGER {
                        sunday(0),
                        monday(1),
                        tuseday(2),
                        wednesday(3),
                        thursday(4),
                        friday(5),
                        saturday(6)
                        }
   MAX-ACCESS   read-write
   STATUS       current
   DESCRIPTION
       "Get/Set the Daylight Saving Time Day From.
        0 : Sun, 1 : Mon, 2 : Tue, 3 : Wed, 4 : Thu, 5 : Fri, 6 : Sat."
   ::= { gs2310SystemTimeManual 9 }

gs2310SystemTimeManualDaylightSavingsRecurringWeekFrom OBJECT-TYPE
   SYNTAX       INTEGER{
                        firstWeek(1),
                        secondWeek(2),
                        thirdWeek(3),
                        fourthWeek(4),
                        listWeek(5)
                        }
   MAX-ACCESS   read-write
   STATUS       current
   DESCRIPTION
       "Get/Set the Daylight Saving Time Week From.
        1 : first week, 2, 3, 4, 5 : last week"
   ::= { gs2310SystemTimeManual 10 }

gs2310SystemTimeManualDaylightSavingsRecurringMonthFrom OBJECT-TYPE
   SYNTAX      INTEGER {
                        jan(1),
                        feb(2),
                        mar(3),
                        apr(4),
                        may(5),
                        jun(6),
                        jul(7),
                        aug(8),
                        sep(9),
                        oct(10),
                        nov(11),
                        dec(12)
                        }
   MAX-ACCESS   read-write
   STATUS       current
   DESCRIPTION
       "Get/Set the Daylight Saving Time Month From.
        1 : Jan, 2 : Feb, 3 : Mar, 4 : Apr, 5 : May, 6 : Jun,
        7 : Jul, 8 : Aug, 9 : Sep, 10 : Oct, 11 : Nov, 12 : Dec."
   ::= { gs2310SystemTimeManual 11 }

gs2310SystemTimeManualDaylightSavingsRecurringTimeFrom OBJECT-TYPE
   SYNTAX       DisplayString
   MAX-ACCESS   read-write
   STATUS       current
   DESCRIPTION
       "Get/Set the Start time of By dates Daylight Savings.
        The input format is 'Hour:Minute'.
        ex: 05:43.
        The value range:
        Hour    : 0 - 23,
        Minute  : 0 - 59."
   ::= { gs2310SystemTimeManual 12 }

gs2310SystemTimeManualDaylightSavingsRecurringDayTo OBJECT-TYPE
   SYNTAX      INTEGER {
                        sunday(0),
                        monday(1),
                        tuseday(2),
                        wednesday(3),
                        thursday(4),
                        friday(5),
                        saturday(6)
                        }
   MAX-ACCESS   read-write
   STATUS       current
   DESCRIPTION
       "Get/Set the Daylight Saving Time Day To.
        0 : Sun, 1 : Mon, 2 : Tue, 3 : Wed, 4 : Thu, 5 : Fri, 6 : Sat."
   ::= { gs2310SystemTimeManual 13 }

gs2310SystemTimeManualDaylightSavingsRecurringWeekTo OBJECT-TYPE
   SYNTAX       INTEGER{
                        firstWeek(1),
                        secondWeek(2),
                        thirdWeek(3),
                        fourthWeek(4),
                        listWeek(5)
                        }
   MAX-ACCESS   read-write
   STATUS       current
   DESCRIPTION
       "Get/Set the Daylight Saving Time Week To.
        1 : first week, 2, 3, 4, 5 : last week"
   ::= { gs2310SystemTimeManual 14 }

gs2310SystemTimeManualDaylightSavingsRecurringMonthTo OBJECT-TYPE
   SYNTAX      INTEGER {
                        jan(1),
                        feb(2),
                        mar(3),
                        apr(4),
                        may(5),
                        jun(6),
                        jul(7),
                        aug(8),
                        sep(9),
                        oct(10),
                        nov(11),
                        dec(12)
                        }
   MAX-ACCESS   read-write
   STATUS       current
   DESCRIPTION
       "Get/Set the Daylight Saving Time Month To.
        1 : Jan, 2 : Feb, 3 : Mar, 4 : Apr, 5 : May, 6 : Jun,
        7 : Jul, 8 : Aug, 9 : Sep, 10 : Oct, 11 : Nov, 12 : Dec."
   ::= { gs2310SystemTimeManual 15 }

gs2310SystemTimeManualDaylightSavingsRecurringTimeTo OBJECT-TYPE
   SYNTAX       DisplayString
   MAX-ACCESS   read-write
   STATUS       current
   DESCRIPTION
       "Get/Set the Start time of By dates Daylight Savings.
        The input format is 'Hour:Minute'.
        ex: 05:43.
        The value range:
        Hour    : 0 - 23,
        Minute  : 0 - 59."
   ::= { gs2310SystemTimeManual 16 }

gs2310SystemTimeNTP                                     OBJECT IDENTIFIER ::= { gs2310SystemTime 2 }

gs2310SystemTimeNTPTable OBJECT-TYPE
   SYNTAX      SEQUENCE OF GS2310SystemTimeNTPEntry
   MAX-ACCESS  not-accessible
   STATUS      current
   DESCRIPTION
       " "
   ::= { gs2310SystemTimeNTP 1 }

gs2310SystemTimeNTPEntry OBJECT-TYPE
   SYNTAX      GS2310SystemTimeNTPEntry
   MAX-ACCESS  not-accessible
   STATUS      current
   DESCRIPTION
       ""
   INDEX    { gs2310SystemTimeNTPIndex  }
   ::= { gs2310SystemTimeNTPTable 1 }

GS2310SystemTimeNTPEntry ::= SEQUENCE {
   gs2310SystemTimeNTPIndex             Integer32,
   gs2310SystemTimeNTPServerIPType      INTEGER,
   gs2310SystemTimeNTPServer            DisplayString,
   gs2310SystemTimeNTPCurrentMode       INTEGER
}

gs2310SystemTimeNTPIndex OBJECT-TYPE
   SYNTAX      Integer32(1..5)
   MAX-ACCESS  not-accessible
   STATUS      current
   DESCRIPTION
       " The index of the ntp entry. "
   ::= { gs2310SystemTimeNTPEntry 1 }

gs2310SystemTimeNTPServerIPType OBJECT-TYPE
   SYNTAX       INTEGER { ipv4(0), ipv6(1) }
   MAX-ACCESS   read-write
   STATUS       current
   DESCRIPTION
       "Default: 0,
        0 : IPv4,
        1 : IPv6."
   ::= { gs2310SystemTimeNTPEntry 2 }

gs2310SystemTimeNTPServer OBJECT-TYPE
   SYNTAX       DisplayString
   MAX-ACCESS   read-write
   STATUS       current
   DESCRIPTION
       "Get/Set the NTP Time Server1. You can use the IP address or domain name."
   ::= { gs2310SystemTimeNTPEntry 3 }

gs2310SystemTimeNTPCurrentMode OBJECT-TYPE
   SYNTAX      INTEGER { empty(0), active(1), edit(2), delete(3) }
   MAX-ACCESS  read-write
   STATUS      current
   DESCRIPTION
       " 0: Empty
        1: Active
        2: Edit
        3: Delete"
   ::= { gs2310SystemTimeNTPEntry 4 }

gs2310SystemTimeNTPRequestInterval OBJECT-TYPE
   SYNTAX       INTEGER(60..999999999)
   MAX-ACCESS   read-write
   STATUS       current
   DESCRIPTION
       "Get/Set the NTP Request Interval.
        Default : 86400.
        The value range is between 60 and 999999999 (seconds)."
   ::= { gs2310SystemTimeNTP 2 }

gs2310SystemTimeNTPTriesNumber OBJECT-TYPE
   SYNTAX       INTEGER(0..999999999)
   MAX-ACCESS   read-write
   STATUS       current
   DESCRIPTION
       "Get/Set the NTP Number of tries.
        Default : 4.
        The value range is between 0 and 999999999."
   ::= { gs2310SystemTimeNTP 3 }


gs2310SystemAccount                                         OBJECT IDENTIFIER ::= { gs2310System 3 }

gs2310SystemAccountUsers                                    OBJECT IDENTIFIER ::= { gs2310SystemAccount 1 }

gs2310SystemAccountUserCreate OBJECT-TYPE
   SYNTAX       INTEGER { none(0), create(1) }
   MAX-ACCESS   read-write
   STATUS       current
   DESCRIPTION
       "default: 0
        0 : None  (read only)
        1 : Create a user account"
   ::= { gs2310SystemAccountUsers 1 }

gs2310SystemAccountUsersTable OBJECT-TYPE
   SYNTAX      SEQUENCE OF GS2310SystemAccountUsersEntry
   MAX-ACCESS  not-accessible
   STATUS      current
   DESCRIPTION
       " "
   ::= { gs2310SystemAccountUsers 2 }

gs2310SystemAccountUsersEntry OBJECT-TYPE
   SYNTAX      GS2310SystemAccountUsersEntry
   MAX-ACCESS  not-accessible
   STATUS      current
   DESCRIPTION
       ""
   INDEX    { gs2310UserIndex  }
   ::= { gs2310SystemAccountUsersTable 1 }


GS2310SystemAccountUsersEntry ::= SEQUENCE {
   gs2310UserIndex              Integer32 ,
   gs2310UserName               DisplayString,
   gs2310Password               DisplayString,
   gs2310UserPrivilegeLevel     Integer32 ,
   gs2310AccountUserRowStatus   INTEGER
}


gs2310UserIndex OBJECT-TYPE
   SYNTAX      Integer32 (1..20)
   MAX-ACCESS  not-accessible
   STATUS      current
   DESCRIPTION
       " "
   ::= { gs2310SystemAccountUsersEntry 1 }

gs2310UserName OBJECT-TYPE
   SYNTAX      DisplayString (SIZE (1..32))
   MAX-ACCESS  read-write
   STATUS      current
   DESCRIPTION
       "Please use a combination of letters, numbers and underscores"
   ::= { gs2310SystemAccountUsersEntry 2 }

gs2310Password OBJECT-TYPE
   SYNTAX      DisplayString (SIZE (1..32))
   MAX-ACCESS  read-write
   STATUS      current
   DESCRIPTION
       "Please use ASCII printable code except Quotation mark, Colon (punctuation), Less-than sign, Greater-than sign, At sign, Question mark and Space (punctuation)"
   ::= { gs2310SystemAccountUsersEntry 3 }

gs2310UserPrivilegeLevel OBJECT-TYPE
   SYNTAX      Integer32 (1..15)
   MAX-ACCESS  read-write
   STATUS      current
   DESCRIPTION
       "default:1
        User privilege level range : 1 - 15"
   ::= { gs2310SystemAccountUsersEntry 4 }

gs2310AccountUserRowStatus OBJECT-TYPE
   SYNTAX      INTEGER { active(1), notInservice(2), edit(3), destroy(4), undo(5) }
   MAX-ACCESS  read-write
   STATUS      current
   DESCRIPTION
       " 1: active
        2: notInservice
        3: edit
        4: destroy
        5: undo"
   ::= { gs2310SystemAccountUsersEntry 5 }

gs2310SystemAccountUsersSuperUserPassword OBJECT-TYPE
   SYNTAX      OCTET STRING (SIZE (0..32))
   MAX-ACCESS read-write
   STATUS      current
   DESCRIPTION
        "Super-User Password"
   ::= { gs2310SystemAccountUsers 1500 }

gs2310SystemAccountEnforcePasswordRules OBJECT-TYPE
   SYNTAX       INTEGER { yes(0), no(1) }
   MAX-ACCESS   read-write
   STATUS       current
   DESCRIPTION
       "default: 0
        0 : Do not enforce rules
        1 : enforce rules"
   ::= { gs2310SystemAccountUsers 1501 }

gs2310SystemAccountPrivilegeLevel                           OBJECT IDENTIFIER ::= { gs2310SystemAccount 2 }

gs2310AccountPrivilegeLevel OBJECT-TYPE
   SYNTAX      Integer32 (1..15)
   MAX-ACCESS  read-write
   STATUS      current
   DESCRIPTION
       "Default:15, Range : 1-15. "
   ::= { gs2310SystemAccountPrivilegeLevel 1 }

gs2310AggregationPrivilegeLevel OBJECT-TYPE
   SYNTAX      Integer32 (1..15)
   MAX-ACCESS  read-write
   STATUS      current
   DESCRIPTION
       "Default:15, Range : 1-15. "
   ::= { gs2310SystemAccountPrivilegeLevel 2 }

gs2310DiagnosticsPrivilegeLevel OBJECT-TYPE
   SYNTAX      Integer32 (1..15)
   MAX-ACCESS  read-write
   STATUS      current
   DESCRIPTION
       "Default:15, Range : 1-15. "
   ::= { gs2310SystemAccountPrivilegeLevel 3 }

gs2310EEEPrivilegeLevel OBJECT-TYPE
   SYNTAX      Integer32 (1..15)
   MAX-ACCESS  read-write
   STATUS      current
   DESCRIPTION
       "Default:15, Range : 1-15. "
   ::= { gs2310SystemAccountPrivilegeLevel 4 }

gs2310EasyportPrivilegeLevel OBJECT-TYPE
   SYNTAX      Integer32 (1..15)
   MAX-ACCESS  read-write
   STATUS      current
   DESCRIPTION
       "Default:15, Range : 1-15. "
   ::= { gs2310SystemAccountPrivilegeLevel 9 }

gs2310GARPPrivilegeLevel OBJECT-TYPE
   SYNTAX      Integer32 (1..15)
   MAX-ACCESS  read-write
   STATUS      current
   DESCRIPTION
       "Default:15, Range : 1-15. "
   ::= { gs2310SystemAccountPrivilegeLevel 10 }

gs2310GVRPPrivilegeLevel OBJECT-TYPE
   SYNTAX      Integer32 (1..15)
   MAX-ACCESS  read-write
   STATUS      current
   DESCRIPTION
       "Default:15, Range : 1-15. "
   ::= { gs2310SystemAccountPrivilegeLevel 11 }

gs2310IPPrivilegeLevel OBJECT-TYPE
   SYNTAX      Integer32 (1..15)
   MAX-ACCESS  read-write
   STATUS      current
   DESCRIPTION
       "Default:15, Range : 1-15. "
   ::= { gs2310SystemAccountPrivilegeLevel 12 }

gs2310IPMCSnoopingPrivilegeLevel OBJECT-TYPE
   SYNTAX      Integer32 (1..15)
   MAX-ACCESS  read-write
   STATUS      current
   DESCRIPTION
       "Default:15, Range : 1-15. "
   ::= { gs2310SystemAccountPrivilegeLevel 13 }

gs2310LACPPrivilegeLevel OBJECT-TYPE
   SYNTAX      Integer32 (1..15)
   MAX-ACCESS  read-write
   STATUS      current
   DESCRIPTION
       "Default:15, Range : 1-15. "
   ::= { gs2310SystemAccountPrivilegeLevel 14 }

gs2310LLDPPrivilegeLevel OBJECT-TYPE
   SYNTAX      Integer32 (1..15)
   MAX-ACCESS  read-write
   STATUS      current
   DESCRIPTION
       "Default:15, Range : 1-15. "
   ::= { gs2310SystemAccountPrivilegeLevel 15 }

gs2310LLDPMEDPrivilegeLevel OBJECT-TYPE
   SYNTAX      Integer32 (1..15)
   MAX-ACCESS  read-write
   STATUS      current
   DESCRIPTION
       "Default:15, Range : 1-15. "
   ::= { gs2310SystemAccountPrivilegeLevel 16 }

gs2310LoopProtectPrivilegeLevel OBJECT-TYPE
   SYNTAX      Integer32 (1..15)
   MAX-ACCESS  read-write
   STATUS      current
   DESCRIPTION
       "Default:15, Range : 1-15. "
   ::= { gs2310SystemAccountPrivilegeLevel 17 }

gs2310MACTablePrivilegeLevel OBJECT-TYPE
   SYNTAX      Integer32 (1..15)
   MAX-ACCESS  read-write
   STATUS      current
   DESCRIPTION
       "Default:15, Range : 1-15. "
   ::= { gs2310SystemAccountPrivilegeLevel 18 }

gs2310MVRPrivilegeLevel OBJECT-TYPE
   SYNTAX      Integer32 (1..15)
   MAX-ACCESS  read-write
   STATUS      current
   DESCRIPTION
       "Default:15, Range : 1-15. "
   ::= { gs2310SystemAccountPrivilegeLevel 22 }

gs2310MaintenancePrivilegeLevel OBJECT-TYPE
   SYNTAX      Integer32 (1..15)
   MAX-ACCESS  read-write
   STATUS      current
   DESCRIPTION
       "Default:15, Range : 1-15. "
   ::= { gs2310SystemAccountPrivilegeLevel 24 }

gs2310MirroringPrivilegeLevel OBJECT-TYPE
   SYNTAX      Integer32 (1..15)
   MAX-ACCESS  read-write
   STATUS      current
   DESCRIPTION
       "Default:15, Range : 1-15. "
   ::= { gs2310SystemAccountPrivilegeLevel 25 }

gs2310PortsPrivilegeLevel OBJECT-TYPE
   SYNTAX      Integer32 (1..15)
   MAX-ACCESS  read-write
   STATUS      current
   DESCRIPTION
       "Default:15, Range : 1-15. "
   ::= { gs2310SystemAccountPrivilegeLevel 27 }

gs2310PrivateVLANsPrivilegeLevel OBJECT-TYPE
   SYNTAX      Integer32 (1..15)
   MAX-ACCESS  read-write
   STATUS      current
   DESCRIPTION
       "Default:15, Range : 1-15. "
   ::= { gs2310SystemAccountPrivilegeLevel 28 }

gs2310QoSPrivilegeLevel OBJECT-TYPE
   SYNTAX      Integer32 (1..15)
   MAX-ACCESS  read-write
   STATUS      current
   DESCRIPTION
       "Default:15, Range : 1-15. "
   ::= { gs2310SystemAccountPrivilegeLevel 29 }

gs2310SFlowPrivilegeLevel OBJECT-TYPE
   SYNTAX      Integer32 (1..15)
   MAX-ACCESS  read-write
   STATUS      current
   DESCRIPTION
       "Default:15, Range : 1-15. "
   ::= { gs2310SystemAccountPrivilegeLevel 30 }

gs2310SMTPPrivilegeLevel OBJECT-TYPE
   SYNTAX      Integer32 (1..15)
   MAX-ACCESS  read-write
   STATUS      current
   DESCRIPTION
       "Default:15, Range : 1-15. "
   ::= { gs2310SystemAccountPrivilegeLevel 31 }

gs2310SNMPPrivilegeLevel OBJECT-TYPE
   SYNTAX      Integer32 (1..15)
   MAX-ACCESS  read-write
   STATUS      current
   DESCRIPTION
       "Default:15, Range : 1-15. "
   ::= { gs2310SystemAccountPrivilegeLevel 32 }

gs2310SecurityPrivilegeLevel OBJECT-TYPE
   SYNTAX      Integer32 (1..15)
   MAX-ACCESS  read-write
   STATUS      current
   DESCRIPTION
       "Default:15, Range : 1-15. "
   ::= { gs2310SystemAccountPrivilegeLevel 33 }

gs2310SingleIPPrivilegeLevel OBJECT-TYPE
   SYNTAX      Integer32 (1..15)
   MAX-ACCESS  read-write
   STATUS      current
   DESCRIPTION
       "Default:15, Range : 1-15. "
   ::= { gs2310SystemAccountPrivilegeLevel 34 }

gs2310SpanningTreePrivilegeLevel OBJECT-TYPE
   SYNTAX      Integer32 (1..15)
   MAX-ACCESS  read-write
   STATUS      current
   DESCRIPTION
       "Default:15, Range : 1-15. "
   ::= { gs2310SystemAccountPrivilegeLevel 35 }

gs2310SystemPrivilegeLevel OBJECT-TYPE
   SYNTAX      Integer32 (1..15)
   MAX-ACCESS  read-write
   STATUS      current
   DESCRIPTION
       "Default:15, Range : 1-15. "
   ::= { gs2310SystemAccountPrivilegeLevel 36 }

gs2310TrapEventPrivilegeLevel OBJECT-TYPE
   SYNTAX      Integer32 (1..15)
   MAX-ACCESS  read-write
   STATUS      current
   DESCRIPTION
       "Default:15, Range : 1-15. "
   ::= { gs2310SystemAccountPrivilegeLevel 37 }

gs2310UPnPPrivilegeLevel OBJECT-TYPE
   SYNTAX      Integer32 (1..15)
   MAX-ACCESS  read-write
   STATUS      current
   DESCRIPTION
       "Default:15, Range : 1-15. "
   ::= { gs2310SystemAccountPrivilegeLevel 38 }

gs2310VCLPrivilegeLevel OBJECT-TYPE
   SYNTAX      Integer32 (1..15)
   MAX-ACCESS  read-write
   STATUS      current
   DESCRIPTION
       "Default:15, Range : 1-15. "
   ::= { gs2310SystemAccountPrivilegeLevel 39 }

gs2310VLANsPrivilegeLevel OBJECT-TYPE
   SYNTAX      Integer32 (1..15)
   MAX-ACCESS  read-write
   STATUS      current
   DESCRIPTION
       "Default:15, Range : 1-15. "
   ::= { gs2310SystemAccountPrivilegeLevel 41 }

gs2310VoiceVLANPrivilegeLevel OBJECT-TYPE
   SYNTAX      Integer32 (1..15)
   MAX-ACCESS  read-write
   STATUS      current
   DESCRIPTION
       "Default:15, Range : 1-15. "
   ::= { gs2310SystemAccountPrivilegeLevel 42 }

gs2310IP                                                    OBJECT IDENTIFIER ::= { gs2310System 4 }

gs2310IPv4                                                  OBJECT IDENTIFIER ::= { gs2310IP 1 }

gs2310IPv4Configured                                                  OBJECT IDENTIFIER ::= { gs2310IPv4 1 }

gs2310Ipv4DHCPClient OBJECT-TYPE
   SYNTAX      INTEGER { disable(0), enable(1) }
   MAX-ACCESS  read-write
   STATUS      current
   DESCRIPTION
       "default:0
       0: disable
       1: enable"
   ::= { gs2310IPv4Configured 1 }

gs2310IPv4Address OBJECT-TYPE
   SYNTAX      IpAddress
   MAX-ACCESS  read-write
   STATUS      current
   DESCRIPTION
       ""
   ::= { gs2310IPv4Configured 2 }

gs2310IPv4Mask OBJECT-TYPE
   SYNTAX      IpAddress
   MAX-ACCESS  read-write
   STATUS      current
   DESCRIPTION
       ""
   ::= { gs2310IPv4Configured 3 }

gs2310IPv4Gateway OBJECT-TYPE
   SYNTAX      IpAddress
   MAX-ACCESS  read-write
   STATUS      current
   DESCRIPTION
       ""
   ::= { gs2310IPv4Configured 4 }

gs2310IPv4VLANId OBJECT-TYPE
   SYNTAX      Integer32(1..4094)
   MAX-ACCESS  read-write
   STATUS      current
   DESCRIPTION
       "default:1"
   ::= { gs2310IPv4Configured 5 }

gs2310IPv4DNSServer OBJECT-TYPE
   SYNTAX      IpAddress
   MAX-ACCESS  read-write
   STATUS      current
   DESCRIPTION
       ""
   ::= { gs2310IPv4Configured 6 }

gs2310IPv4DNSProxy OBJECT-TYPE
   SYNTAX      INTEGER { disable(0), enable(1) }
   MAX-ACCESS  read-write
   STATUS      current
   DESCRIPTION
       "0:disable, 1:enable "
   ::= { gs2310IPv4Configured 7 }

gs2310IPv4Current                                                  OBJECT IDENTIFIER ::= { gs2310IPv4 2 }

gs2310Ipv4CurrentDHCPClient OBJECT-TYPE
   SYNTAX      INTEGER { none(0), renew(1) }
   MAX-ACCESS  read-write
   STATUS      current
   DESCRIPTION
       "default:0
       0: none (for read)
       1: renew"
   ::= { gs2310IPv4Current 1 }

gs2310IPv4CurrentAddress OBJECT-TYPE
   SYNTAX      IpAddress
   MAX-ACCESS  read-only
   STATUS      current
   DESCRIPTION
       ""
   ::= { gs2310IPv4Current 2 }

gs2310IPv4CurrentMask OBJECT-TYPE
   SYNTAX      IpAddress
   MAX-ACCESS  read-only
   STATUS      current
   DESCRIPTION
       ""
   ::= { gs2310IPv4Current 3 }

gs2310IPv4CurrentGateway OBJECT-TYPE
   SYNTAX      IpAddress
   MAX-ACCESS  read-only
   STATUS      current
   DESCRIPTION
       ""
   ::= { gs2310IPv4Current 4 }

gs2310IPv4CurrentVLANId OBJECT-TYPE
   SYNTAX      Integer32(1..4094)
   MAX-ACCESS  read-only
   STATUS      current
   DESCRIPTION
       "default:1"
   ::= { gs2310IPv4Current 5 }

gs2310IPv4CurrentDNSServer OBJECT-TYPE
   SYNTAX      IpAddress
   MAX-ACCESS  read-only
   STATUS      current
   DESCRIPTION
       ""
   ::= { gs2310IPv4Current 6 }


gs2310IPv6                                                  OBJECT IDENTIFIER ::= { gs2310IP 2 }

gs2310IPv6Configured                                                  OBJECT IDENTIFIER ::= { gs2310IPv6 1 }

gs2310Ipv6AutoConfiguration OBJECT-TYPE
   SYNTAX      INTEGER { disable(0), enable(1) }
   MAX-ACCESS  read-write
   STATUS      current
   DESCRIPTION
       "default:0
       0: disable
       1: enable"
   ::= { gs2310IPv6Configured 1 }

gs2310Ipv6Address OBJECT-TYPE
   SYNTAX      DisplayString (SIZE (0..30))
   MAX-ACCESS  read-write
   STATUS      current
   DESCRIPTION
       ""
   ::= { gs2310IPv6Configured 2 }

gs2310Ipv6Prefix OBJECT-TYPE
   SYNTAX      Integer32 (1..128)
   MAX-ACCESS  read-write
   STATUS      current
   DESCRIPTION
       "default: 96"
   ::= { gs2310IPv6Configured 3 }

gs2310Ipv6Gateway OBJECT-TYPE
   SYNTAX      DisplayString (SIZE (0..30))
   MAX-ACCESS  read-write
   STATUS      current
   DESCRIPTION
       " "
   ::= { gs2310IPv6Configured 4 }

gs2310IPv6Current                                                  OBJECT IDENTIFIER ::= { gs2310IPv6 2 }

gs2310Ipv6CurrentAutoConfiguration OBJECT-TYPE
   SYNTAX      INTEGER { disable(0), enable(1) }
   MAX-ACCESS  read-only
   STATUS      current
   DESCRIPTION
       "default:0
       0: disable
       1: enable"
   ::= { gs2310IPv6Current 1 }

gs2310Ipv6CurrentAddress OBJECT-TYPE
   SYNTAX      DisplayString (SIZE (0..30))
   MAX-ACCESS  read-only
   STATUS      current
   DESCRIPTION
       ""
   ::= { gs2310IPv6Current 2 }


gs2310Ipv6CurrentLinkLocalAddress OBJECT-TYPE
   SYNTAX      DisplayString(SIZE (0..30))
   MAX-ACCESS  read-only
   STATUS      current
   DESCRIPTION
       ""
   ::= { gs2310IPv6Current 3 }


gs2310Ipv6CurrentPrefix OBJECT-TYPE
   SYNTAX      DisplayString(SIZE (0..64))
   MAX-ACCESS  read-only
   STATUS      current
   DESCRIPTION
       ""
   ::= { gs2310IPv6Current 4 }

gs2310Ipv6CurrentGateway OBJECT-TYPE
   SYNTAX      DisplayString (SIZE (0..30))
   MAX-ACCESS  read-only
   STATUS      current
   DESCRIPTION
       " "
   ::= { gs2310IPv6Current 5 }

gs2310Syslog                                                OBJECT IDENTIFIER ::= { gs2310System 5 }

gs2310SyslogConf                                            OBJECT IDENTIFIER ::= { gs2310Syslog 1 }

gs2310ServerMode OBJECT-TYPE
   SYNTAX      INTEGER { disable(0), enable(1) }
   MAX-ACCESS  read-write
   STATUS      current
   DESCRIPTION
       "default: 0
       0: disable
       1: enable "
   ::= { gs2310SyslogConf 1 }

gs2310ServerAddress1 OBJECT-TYPE
   SYNTAX      IpAddress
   MAX-ACCESS  read-write
   STATUS      current
   DESCRIPTION
       " "
   ::= { gs2310SyslogConf 2 }

gs2310ServerAddress2 OBJECT-TYPE
   SYNTAX      IpAddress
   MAX-ACCESS  read-write
   STATUS      current
   DESCRIPTION
       " "
   ::= { gs2310SyslogConf 3 }

gs2310SyslogLevel OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       "default: 6 (Info)
       0: Emergency
       1: Alert
       2: Critical
       3: Error
       4: Warning
       5: Notice
       6: Info
       7: Debug"
   ::= { gs2310SyslogConf 4 }

gs2310SyslogDetailedInfo                                    OBJECT IDENTIFIER ::= { gs2310Syslog 2 }

gs2310SyslogDetailedInfoClear OBJECT-TYPE
   SYNTAX      INTEGER { none(0), clear(1) }
   MAX-ACCESS  read-write
   STATUS      current
   DESCRIPTION
      "default: 0
       0 : None  (read only)
       1 : Clear Syslog"
   ::= { gs2310SyslogDetailedInfo 1 }

gs2310SyslogDetailedInfoTable OBJECT-TYPE
  SYNTAX      SEQUENCE OF GS2310SyslogDetailedInfoEntry
  MAX-ACCESS  not-accessible
  STATUS      current
  DESCRIPTION
           " "
       ::= { gs2310SyslogDetailedInfo 2 }

gs2310SyslogDetailedInfoEntry OBJECT-TYPE
   SYNTAX      GS2310SyslogDetailedInfoEntry
   MAX-ACCESS  not-accessible
   STATUS      current
   DESCRIPTION
           ""
   INDEX    { gs2310SyslogDetailedInfoIndex  }
   ::= { gs2310SyslogDetailedInfoTable 1 }

GS2310SyslogDetailedInfoEntry ::= SEQUENCE {
   gs2310SyslogDetailedInfoIndex       Integer32,
   gs2310SyslogDetailedInfoLevel       DisplayString,
   gs2310SyslogDetailedInfoTime        DisplayString,
   gs2310SyslogDetailedInfoMessage     DisplayString
}

gs2310SyslogDetailedInfoIndex OBJECT-TYPE
   SYNTAX      Integer32(1..1024)
   MAX-ACCESS  not-accessible
   STATUS      current
   DESCRIPTION
       " "
   ::= { gs2310SyslogDetailedInfoEntry 1 }

gs2310SyslogDetailedInfoLevel OBJECT-TYPE
   SYNTAX      DisplayString
   MAX-ACCESS  read-only
   STATUS      current
   DESCRIPTION
       " "
   ::= { gs2310SyslogDetailedInfoEntry 2 }

gs2310SyslogDetailedInfoTime OBJECT-TYPE
   SYNTAX      DisplayString(SIZE (0..20))
   MAX-ACCESS  read-only
   STATUS      current
   DESCRIPTION
       " "
   ::= { gs2310SyslogDetailedInfoEntry 3 }

gs2310SyslogDetailedInfoMessage OBJECT-TYPE
   SYNTAX      DisplayString
   MAX-ACCESS  read-only
   STATUS      current
   DESCRIPTION
       " "
   ::= { gs2310SyslogDetailedInfoEntry 4 }


gs2310Snmp                                                OBJECT IDENTIFIER ::= { gs2310System 6 }

gs2310SnmpConf                                            OBJECT IDENTIFIER ::= { gs2310Snmp 1 }

gs2310GetCommunityMode OBJECT-TYPE
   SYNTAX       INTEGER { disable(0), enable(1) }
   MAX-ACCESS   read-write
   STATUS       current
   DESCRIPTION
       "Get/Set the get-community mode of the SNMP.
        default : 1, 0: disable, 1: enable. "
   ::= { gs2310SnmpConf 1 }

gs2310GetCommunity OBJECT-TYPE
   SYNTAX       DisplayString
   MAX-ACCESS   read-write
   STATUS       current
   DESCRIPTION
       "Get/Set the get-community of the SNMP."
   ::= { gs2310SnmpConf 2 }

gs2310SetCommunityMode OBJECT-TYPE
   SYNTAX       INTEGER { disable(0), enable(1) }
   MAX-ACCESS   read-write
   STATUS       current
   DESCRIPTION
       "Get/Set the set-community mode of the SNMP.
        default : 1, 0: disable, 1: enable. "
   ::= { gs2310SnmpConf 3 }

gs2310SetCommunity OBJECT-TYPE
   SYNTAX       DisplayString
   MAX-ACCESS   read-write
   STATUS       current
   DESCRIPTION
       "Get/Set the set-community of the SNMP."
   ::= { gs2310SnmpConf 4 }

gs2310GetCommunityConfTable OBJECT-TYPE
   SYNTAX      SEQUENCE OF GS2310GetCommunityConfEntry
   MAX-ACCESS  not-accessible
   STATUS      current
   DESCRIPTION
       " Show get-community of the SNMP. "
   ::= { gs2310SnmpConf 5 }

gs2310GetCommunityConfEntry OBJECT-TYPE
   SYNTAX      GS2310GetCommunityConfEntry
   MAX-ACCESS  not-accessible
   STATUS      current
   DESCRIPTION
       ""
   INDEX    { gs2310CommunityConfIndex  }
   ::= { gs2310GetCommunityConfTable 1 }

GS2310GetCommunityConfEntry ::= SEQUENCE {
   gs2310CommunityConfIndex				Integer32,
   gs2310CommunityConfGetCommunity			DisplayString
}

gs2310CommunityConfIndex OBJECT-TYPE
   SYNTAX      Integer32(1..4095)
   MAX-ACCESS  not-accessible
   STATUS      current
   DESCRIPTION
       " index, range : 1 - 5. "
   ::= { gs2310GetCommunityConfEntry 1 }

gs2310CommunityConfGetCommunity OBJECT-TYPE
   SYNTAX      DisplayString
   MAX-ACCESS  read-write
   STATUS      current
   DESCRIPTION
       " Get/Set the get-community of the SNMP."
   ::= { gs2310GetCommunityConfEntry 2 }

gs2310TrapHostConfTable OBJECT-TYPE
   SYNTAX      SEQUENCE OF GS2310TrapHostConfEntry
   MAX-ACCESS  not-accessible
   STATUS      current
   DESCRIPTION
       "A list of trap host entry. The numbers of entries are given by the value of gs2310TrapHostConfNumber."
   ::= { gs2310SnmpConf 6 }

gs2310TrapHostConfEntry OBJECT-TYPE
   SYNTAX      GS2310TrapHostConfEntry
   MAX-ACCESS  not-accessible
   STATUS      current
   DESCRIPTION
       "This is the entry information for trap host."
   INDEX    { gs2310TrapHostConfIndex  }
   ::= { gs2310TrapHostConfTable 1 }

GS2310TrapHostConfEntry ::= SEQUENCE {
    gs2310TrapHostConfIndex             Integer32,
    gs2310TrapHostConfVersion           INTEGER,
    gs2310TrapHostConfIPType            INTEGER,
    gs2310TrapHostConfIP                DisplayString,
    gs2310TrapHostConfPort              Integer32,
    gs2310TrapHostConfCommunity         DisplayString,
    gs2310TrapHostConfSeverityLevel     INTEGER,
    gs2310TrapHostConfSecurityLevel     INTEGER,
    gs2310TrapHostConfAuthPtc           INTEGER,
    gs2310TrapHostConfAuthPassword      DisplayString,
    gs2310TrapHostConfPrivPtc           INTEGER,
    gs2310TrapHostConfPrivPassword      DisplayString,
    gs2310TrapHostConfCurrentMode       INTEGER
}

gs2310TrapHostConfIndex OBJECT-TYPE
   SYNTAX      Integer32(1..6)
   MAX-ACCESS  not-accessible
   STATUS      current
   DESCRIPTION
       " The index of the trap host entry. "
   ::= { gs2310TrapHostConfEntry 1 }

gs2310TrapHostConfVersion OBJECT-TYPE
   SYNTAX       INTEGER { snmpv2c(2), snmpv3(3) }
   MAX-ACCESS   read-write
   STATUS       current
   DESCRIPTION
       "The version of the Trap PDU. Version : 2(SNMPv2c), 3(SNMPv3)"
   ::= { gs2310TrapHostConfEntry 2 }

gs2310TrapHostConfIPType OBJECT-TYPE
   SYNTAX       INTEGER { ipv4(4), ipv6(6) }
   MAX-ACCESS   read-write
   STATUS       current
   DESCRIPTION
       "Server IP Type. Default: 4,
        4 : IPv4,
        6 : IPv6."
   ::= { gs2310TrapHostConfEntry 3 }

gs2310TrapHostConfIP OBJECT-TYPE
   SYNTAX       DisplayString
   MAX-ACCESS   read-write
   STATUS       current
   DESCRIPTION
       "This is the IP of the trap host."
   ::= { gs2310TrapHostConfEntry 4 }

gs2310TrapHostConfPort OBJECT-TYPE
   SYNTAX       Integer32(1..65535)
   MAX-ACCESS   read-write
   STATUS       current
   DESCRIPTION
       "This is the receiving-port number of the trap host.
        range : 1 - 65535."
   ::= { gs2310TrapHostConfEntry 5 }

gs2310TrapHostConfCommunity OBJECT-TYPE
   SYNTAX       DisplayString (SIZE (1..32))
   MAX-ACCESS   read-write
   STATUS       current
   DESCRIPTION
       "The community/security name for the trap PDU."
   ::= { gs2310TrapHostConfEntry 6 }

gs2310TrapHostConfSeverityLevel	OBJECT-TYPE
   SYNTAX      INTEGER {
                    emergency(0),
                    alert(1),
                    critical(2),
                    error(3),
                    warning(4),
                    notice(5),
                    info(6),
                    debug(7)
                }
   MAX-ACCESS   read-write
   STATUS       current
   DESCRIPTION
       "The Severity Level.
        0 : Emerg, 1 : Alert, 2 : Critical, 3 : Error, 4 : Warning, 5 : Notice, 6 : Info, 7 : Debug."
	::= { gs2310TrapHostConfEntry 7 }

gs2310TrapHostConfSecurityLevel	OBJECT-TYPE
   SYNTAX       INTEGER { noAuthNoPriv(1), authNoPriv(2), authPriv(3) }
   MAX-ACCESS   read-write
   STATUS       current
   DESCRIPTION
       "The Security Level, NoAuthNoPriv, AuthNoPriv, and AuthPriv.
        1 : NoAuthNoPriv, 2 : AuthNoPriv, 3 : AuthPriv.
        Privacy protocol will be configured as 'DES' automatically if security level is 3(AuthPriv)."
	::= { gs2310TrapHostConfEntry 8 }

gs2310TrapHostConfAuthPtc	OBJECT-TYPE
   SYNTAX       INTEGER { md5(1), sha(2) }
   MAX-ACCESS   read-write
   STATUS       current
   DESCRIPTION
       "Authentication Protocol, there are SHA and MD5 supported presently.
        1 : MD5, 2 : SHA."
	::= { gs2310TrapHostConfEntry 9 }

gs2310TrapHostConfAuthPassword	OBJECT-TYPE
   SYNTAX      DisplayString
   MAX-ACCESS  read-write
   STATUS		current
   DESCRIPTION
       "Authentication Password, is used for authenticating. The return value is always '********'.
        If the authentication protocol is MD5, the length of password should be 8 ~ 32 characters.
        If the authentication protocol is SHA, the length of password should be 8 ~ 40 characters."
   ::= { gs2310TrapHostConfEntry 10 }

gs2310TrapHostConfPrivPtc	OBJECT-TYPE
   SYNTAX       INTEGER { des(1) }
   MAX-ACCESS   read-write
   STATUS       current
   DESCRIPTION
       "This is the Privacy Protocol, which is used in AuthPriv. Only supports DES.
        An empty string will be returned if the security level is not 3(AuthPriv).
        1 : DES."
	::= { gs2310TrapHostConfEntry 11 }

gs2310TrapHostConfPrivPassword	OBJECT-TYPE
   SYNTAX       DisplayString
   MAX-ACCESS   read-write
   STATUS       current
   DESCRIPTION
       "The password is Privacy Key.  The return value is always '********'.  This Key
        must be more than 8 characters, and less than 32 characters."
   ::= { gs2310TrapHostConfEntry 12 }

gs2310TrapHostConfCurrentMode OBJECT-TYPE
   SYNTAX       INTEGER { empty(0), active(1), edit(2), delete(3) }
   MAX-ACCESS   read-write
   STATUS       current
   DESCRIPTION
       "0:Empty, 1:Active mode, 2:Edit mode, 3:Delete."
   ::= { gs2310TrapHostConfEntry 13 }


gs2310SnmpSystem                                          OBJECT IDENTIFIER ::= { gs2310Snmp 2 }

gs2310SnmpState OBJECT-TYPE
   SYNTAX       INTEGER { disable(0), enable(1) }
   MAX-ACCESS   read-write
   STATUS       current
   DESCRIPTION
       "Get/Set the state of the SNMP.
        default : 1, 0: disable, 1: enable. "
   ::= { gs2310SnmpSystem 1 }

gs2310SnmpEngineID OBJECT-TYPE
   SYNTAX       OCTET STRING (SIZE(5..32))
   MAX-ACCESS   read-write
   STATUS       current
   DESCRIPTION
       "Get/Set the Engine ID of the SNMP.
        An SNMP engine's administratively-unique identifier."
   ::= { gs2310SnmpSystem 2 }

gs2310SnmpCommunities                                          OBJECT IDENTIFIER ::= { gs2310Snmp 3 }

gs2310SnmpCommunitiesCreate OBJECT-TYPE
   SYNTAX       INTEGER { none(0), create(1) }
   MAX-ACCESS   read-write
   STATUS       current
   DESCRIPTION
       "default: 0
        0 : None  (read only)
        1 : Create entry"
   ::= { gs2310SnmpCommunities 1 }

gs2310SnmpCommunitiesTable OBJECT-TYPE
   SYNTAX      SEQUENCE OF GS2310SnmpCommunitiesEntry
   MAX-ACCESS  not-accessible
   STATUS      current
   DESCRIPTION
       " Create SNMPv1/v2 Communities entry."
   ::= { gs2310SnmpCommunities 2 }

gs2310SnmpCommunitiesEntry OBJECT-TYPE
   SYNTAX      GS2310SnmpCommunitiesEntry
   MAX-ACCESS  not-accessible
   STATUS      current
   DESCRIPTION
       ""
   INDEX    { gs2310SnmpCommunitiesIndex  }
   ::= { gs2310SnmpCommunitiesTable 1 }

GS2310SnmpCommunitiesEntry ::= SEQUENCE {
   gs2310SnmpCommunitiesIndex          Integer32,
   gs2310SnmpCommunitiesCommunity      DisplayString,
   gs2310SnmpCommunitiesUserName       DisplayString,
   gs2310SnmpCommunitiesSourceIP       IpAddress,
   gs2310SnmpCommunitiesSourceMask     IpAddress,
   gs2310SnmpCommunitiesRowStatus      INTEGER
}

gs2310SnmpCommunitiesIndex OBJECT-TYPE
   SYNTAX      Integer32(1..4)
   MAX-ACCESS  not-accessible
   STATUS      current
   DESCRIPTION
       " "
   ::= { gs2310SnmpCommunitiesEntry 1 }

gs2310SnmpCommunitiesCommunity OBJECT-TYPE
   SYNTAX      DisplayString (SIZE (1..32))
   MAX-ACCESS  read-write
   STATUS      current
   DESCRIPTION
       "Up to 32 characters describing Community."
   ::= { gs2310SnmpCommunitiesEntry 2 }

gs2310SnmpCommunitiesUserName OBJECT-TYPE
   SYNTAX      DisplayString (SIZE (1..32))
   MAX-ACCESS  read-write
   STATUS      current
   DESCRIPTION
       " Up to 32 characters describing User Name. "
   ::= { gs2310SnmpCommunitiesEntry 3 }

gs2310SnmpCommunitiesSourceIP OBJECT-TYPE
   SYNTAX      IpAddress
   MAX-ACCESS  read-write
   STATUS      current
   DESCRIPTION
       " SNMP access source ip. "
   ::= { gs2310SnmpCommunitiesEntry 4 }

gs2310SnmpCommunitiesSourceMask OBJECT-TYPE
   SYNTAX      IpAddress
   MAX-ACCESS  read-write
   STATUS      current
   DESCRIPTION
       " SNMP access source address mask. "
   ::= { gs2310SnmpCommunitiesEntry 5 }

gs2310SnmpCommunitiesRowStatus OBJECT-TYPE
   SYNTAX      INTEGER { active(1), notInservice(2), destroy(4), undo(5) }
   MAX-ACCESS  read-write
   STATUS      current
   DESCRIPTION
       "1: active
        2: notInservice
        4: destroy
        5: undo"
   ::= { gs2310SnmpCommunitiesEntry 6 }


gs2310SnmpUsers                                          OBJECT IDENTIFIER ::= { gs2310Snmp 4 }

gs2310SnmpUsersCreate OBJECT-TYPE
   SYNTAX       INTEGER { none(0), create(1) }
   MAX-ACCESS   read-write
   STATUS       current
   DESCRIPTION
       "default: 0
        0 : None  (read only)
        1 : Create entry"
   ::= { gs2310SnmpUsers 1 }

gs2310SnmpUsersTable OBJECT-TYPE
   SYNTAX      SEQUENCE OF GS2310SnmpUsersEntry
   MAX-ACCESS  not-accessible
   STATUS      current
   DESCRIPTION
       " Create SNMPv3 users entry."
   ::= { gs2310SnmpUsers 2 }

gs2310SnmpUsersEntry OBJECT-TYPE
   SYNTAX      GS2310SnmpUsersEntry
   MAX-ACCESS  not-accessible
   STATUS      current
   DESCRIPTION
       ""
   INDEX    { gs2310SnmpUsersIndex  }
   ::= { gs2310SnmpUsersTable 1 }

GS2310SnmpUsersEntry ::= SEQUENCE {
   gs2310SnmpUsersIndex                    Integer32,
   gs2310SnmpUsersUserName                 DisplayString,
   gs2310SnmpUsersSecurityLevel            INTEGER,
   gs2310SnmpUsersAuthenticationProtocol   INTEGER,
   gs2310SnmpUsersAuthenticationPassword   DisplayString,
   gs2310SnmpUsersPrivacyProtocol          INTEGER,
   gs2310SnmpUsersPrivacyPassword          DisplayString,
   gs2310SnmpUsersRowStatus                INTEGER
}

gs2310SnmpUsersIndex OBJECT-TYPE
   SYNTAX      Integer32(1..10)
   MAX-ACCESS  not-accessible
   STATUS      current
   DESCRIPTION
       " "
   ::= { gs2310SnmpUsersEntry 1 }

gs2310SnmpUsersUserName OBJECT-TYPE
   SYNTAX      DisplayString (SIZE (1..32))
   MAX-ACCESS  read-write
   STATUS      current
   DESCRIPTION
       "Up to 32 characters describing User Name."
   ::= { gs2310SnmpUsersEntry 2 }

gs2310SnmpUsersSecurityLevel OBJECT-TYPE
   SYNTAX      INTEGER { noauthnopriv(1), authnopriv(2), authpriv(3) }
   MAX-ACCESS  read-write
   STATUS      current
   DESCRIPTION
       " 1: No authentication and no privacy.
         2: Authentication and no privacy.
         3: Authentication and privacy. "
   ::= { gs2310SnmpUsersEntry 3 }

gs2310SnmpUsersAuthenticationProtocol OBJECT-TYPE
   SYNTAX      INTEGER { none(0), md5(1), sha(2) }
   MAX-ACCESS  read-write
   STATUS      current
   DESCRIPTION
       " 0: None.
         1: MD5.
         2: SHA "
   ::= { gs2310SnmpUsersEntry 4 }

gs2310SnmpUsersAuthenticationPassword OBJECT-TYPE
   SYNTAX      DisplayString
   MAX-ACCESS  read-write
   STATUS      current
   DESCRIPTION
       " Authentication Password, is used for authenticating. The return value is always '********'.
         If the authentication protocol is MD5, the length of password should be 8 ~ 32 characters.
         If the authentication protocol is SHA, the length of password should be 8 ~ 40 characters. "
   ::= { gs2310SnmpUsersEntry 5 }

gs2310SnmpUsersPrivacyProtocol OBJECT-TYPE
   SYNTAX      INTEGER { none(0), des(1), aes(2) }
   MAX-ACCESS  read-write
   STATUS      current
   DESCRIPTION
       " 0: None.
         1: DES.
         2: AES
         This is the Privacy Protocol, which is used in AuthPriv.
         An empty string will be returned if the security level is not 3(AuthPriv) "
   ::= { gs2310SnmpUsersEntry 6 }

gs2310SnmpUsersPrivacyPassword OBJECT-TYPE
   SYNTAX      DisplayString
   MAX-ACCESS  read-write
   STATUS      current
   DESCRIPTION
       " The password is Privacy Key.  The return value is always '********'.  This Key
        must be more than 8 characters, and less than 32 characters. "
   ::= { gs2310SnmpUsersEntry 7 }

gs2310SnmpUsersRowStatus OBJECT-TYPE
   SYNTAX      INTEGER { active(1), notInservice(2), destroy(4), undo(5) }
   MAX-ACCESS  read-write
   STATUS      current
   DESCRIPTION
       "1: active
        2: notInservice
        4: destroy
        5: undo"
   ::= { gs2310SnmpUsersEntry 8 }


gs2310SnmpGroups                                          OBJECT IDENTIFIER ::= { gs2310Snmp 5 }

gs2310SnmpGroupsCreate OBJECT-TYPE
   SYNTAX       INTEGER { none(0), create(1) }
   MAX-ACCESS   read-write
   STATUS       current
   DESCRIPTION
       "default: 0
        0 : None  (read only)
        1 : Create entry"
   ::= { gs2310SnmpGroups 1 }

gs2310SnmpGroupsTable OBJECT-TYPE
   SYNTAX      SEQUENCE OF GS2310SnmpGroupsEntry
   MAX-ACCESS  not-accessible
   STATUS      current
   DESCRIPTION
       " Create SNMPv3 groups entry."
   ::= { gs2310SnmpGroups 2 }

gs2310SnmpGroupsEntry OBJECT-TYPE
   SYNTAX      GS2310SnmpGroupsEntry
   MAX-ACCESS  not-accessible
   STATUS      current
   DESCRIPTION
       ""
   INDEX    { gs2310SnmpGroupsIndex  }
   ::= { gs2310SnmpGroupsTable 1 }

GS2310SnmpGroupsEntry ::= SEQUENCE {
   gs2310SnmpGroupsIndex           Integer32,
   gs2310SnmpGroupsSecurityModel   INTEGER,
   gs2310SnmpGroupsSecurityName    DisplayString,
   gs2310SnmpGroupsGroupName       DisplayString,
   gs2310SnmpGroupsRowStatus       INTEGER
}

gs2310SnmpGroupsIndex OBJECT-TYPE
   SYNTAX      Integer32(1..14)
   MAX-ACCESS  not-accessible
   STATUS      current
   DESCRIPTION
       " "
   ::= { gs2310SnmpGroupsEntry 1 }

gs2310SnmpGroupsSecurityModel OBJECT-TYPE
   SYNTAX      INTEGER { v1(1), v2c(2), usm(3) }
   MAX-ACCESS  read-write
   STATUS      current
   DESCRIPTION
       " 1: v1.
         2: v2c.
         3: usm."
   ::= { gs2310SnmpGroupsEntry 2 }

gs2310SnmpGroupsSecurityName OBJECT-TYPE
   SYNTAX      DisplayString (SIZE (1..32))
   MAX-ACCESS  read-write
   STATUS      current
   DESCRIPTION
       "Up to 32 characters describing User Name."
   ::= { gs2310SnmpGroupsEntry 3 }

gs2310SnmpGroupsGroupName OBJECT-TYPE
   SYNTAX      DisplayString (SIZE (1..32))
   MAX-ACCESS  read-write
   STATUS      current
   DESCRIPTION
       "Up to 32 characters describing Group Name."
   ::= { gs2310SnmpGroupsEntry 4 }

gs2310SnmpGroupsRowStatus OBJECT-TYPE
   SYNTAX      INTEGER { active(1), notInservice(2), destroy(4), undo(5) }
   MAX-ACCESS  read-write
   STATUS      current
   DESCRIPTION
       "1: active
        2: notInservice
        4: destroy
        5: undo"
   ::= { gs2310SnmpGroupsEntry 5 }

gs2310SnmpViews                                              OBJECT IDENTIFIER ::= { gs2310Snmp 6 }

gs2310SnmpViewsCreate OBJECT-TYPE
   SYNTAX       INTEGER { none(0), create(1) }
   MAX-ACCESS   read-write
   STATUS       current
   DESCRIPTION
       "default: 0
        0 : None  (read only)
        1 : Create entry"
   ::= { gs2310SnmpViews 1 }

gs2310SnmpViewsTable OBJECT-TYPE
   SYNTAX      SEQUENCE OF GS2310SnmpViewsEntry
   MAX-ACCESS  not-accessible
   STATUS      current
   DESCRIPTION
       " Create SNMPv1/v2 Views entry."
   ::= { gs2310SnmpViews 2 }

gs2310SnmpViewsEntry OBJECT-TYPE
   SYNTAX      GS2310SnmpViewsEntry
   MAX-ACCESS  not-accessible
   STATUS      current
   DESCRIPTION
       ""
   INDEX    { gs2310SnmpViewsIndex  }
   ::= { gs2310SnmpViewsTable 1 }

GS2310SnmpViewsEntry ::= SEQUENCE {
   gs2310SnmpViewsIndex        Integer32,
   gs2310SnmpViewsName         DisplayString,
   gs2310SnmpViewsType         INTEGER,
   gs2310SnmpViewsOIDSubtree   DisplayString,
   gs2310SnmpViewsRowStatus    INTEGER
}

gs2310SnmpViewsIndex OBJECT-TYPE
   SYNTAX      Integer32(1..4)
   MAX-ACCESS  not-accessible
   STATUS      current
   DESCRIPTION
       " "
   ::= { gs2310SnmpViewsEntry 1 }

gs2310SnmpViewsName OBJECT-TYPE
   SYNTAX      DisplayString (SIZE (1..32))
   MAX-ACCESS  read-write
   STATUS      current
   DESCRIPTION
       "Up to 32 characters describing view Name."
   ::= { gs2310SnmpViewsEntry 2 }

gs2310SnmpViewsType OBJECT-TYPE
   SYNTAX      INTEGER { included(1), excluded(2) }
   MAX-ACCESS  read-write
   STATUS      current
   DESCRIPTION
       "1: included, An optional flag to indicate that this view subtree should be included.
	   2: excluded, An optional flag to indicate that this view subtree should be excluded."
   ::= { gs2310SnmpViewsEntry 3 }

gs2310SnmpViewsOIDSubtree OBJECT-TYPE
   SYNTAX      DisplayString (SIZE (1..128))
   MAX-ACCESS  read-write
   STATUS      current
   DESCRIPTION
       "The OID defining the root of the subtree to add to the named view."
   ::= { gs2310SnmpViewsEntry 4 }

gs2310SnmpViewsRowStatus OBJECT-TYPE
   SYNTAX      INTEGER { active(1), notInservice(2), destroy(4), undo(5) }
   MAX-ACCESS  read-write
   STATUS      current
   DESCRIPTION
       "1: active
        2: notInservice
        4: destroy
        5: undo"
   ::= { gs2310SnmpViewsEntry 5 }


gs2310SnmpAccess                                          OBJECT IDENTIFIER ::= { gs2310Snmp 7 }

gs2310SnmpAccessCreate OBJECT-TYPE
   SYNTAX       INTEGER { none(0), create(1) }
   MAX-ACCESS   read-write
   STATUS       current
   DESCRIPTION
       "default: 0
        0 : None  (read only)
        1 : Create entry"
   ::= { gs2310SnmpAccess 1 }

gs2310SnmpAccessTable OBJECT-TYPE
   SYNTAX      SEQUENCE OF GS2310SnmpAccessEntry
   MAX-ACCESS  not-accessible
   STATUS      current
   DESCRIPTION
       " Create SNMPv3 Access entry."
   ::= { gs2310SnmpAccess 2 }

gs2310SnmpAccessEntry OBJECT-TYPE
   SYNTAX      GS2310SnmpAccessEntry
   MAX-ACCESS  not-accessible
   STATUS      current
   DESCRIPTION
       ""
   INDEX    { gs2310SnmpAccessIndex  }
   ::= { gs2310SnmpAccessTable 1 }

GS2310SnmpAccessEntry ::= SEQUENCE {
   gs2310SnmpAccessIndex             Integer32,
   gs2310SnmpAccessGroupName         DisplayString,
   gs2310SnmpAccessSecurityModel     INTEGER,
   gs2310SnmpAccessSecurityLevel     INTEGER,
   gs2310SnmpAccessReadViewName      DisplayString,
   gs2310SnmpAccessWriteViewName     DisplayString,
   gs2310SnmpAccessRowStatus         INTEGER
}

gs2310SnmpAccessIndex OBJECT-TYPE
   SYNTAX      Integer32(1..14)
   MAX-ACCESS  not-accessible
   STATUS      current
   DESCRIPTION
       " "
   ::= { gs2310SnmpAccessEntry 1 }

gs2310SnmpAccessGroupName OBJECT-TYPE
   SYNTAX      DisplayString (SIZE (1..32))
   MAX-ACCESS  read-write
   STATUS      current
   DESCRIPTION
       "Up to 32 characters describing Group Name."
   ::= { gs2310SnmpAccessEntry 2 }

gs2310SnmpAccessSecurityModel OBJECT-TYPE
   SYNTAX      INTEGER { any(0), v1(1), v2c(2), usm(3) }
   MAX-ACCESS  read-write
   STATUS      current
   DESCRIPTION
       " 0: any.
         1: v1.
         2: v2c.
         3: usm."
   ::= { gs2310SnmpAccessEntry 3 }

gs2310SnmpAccessSecurityLevel OBJECT-TYPE
   SYNTAX      INTEGER { noauthnopriv(1), authnopriv(2), authpriv(3) }
   MAX-ACCESS  read-write
   STATUS      current
   DESCRIPTION
       " 1: No authentication and no privacy.
         2: Authentication and no privacy.
         3: Authentication and privacy. "
   ::= { gs2310SnmpAccessEntry 4 }

gs2310SnmpAccessReadViewName OBJECT-TYPE
   SYNTAX      DisplayString (SIZE (1..32))
   MAX-ACCESS  read-write
   STATUS      current
   DESCRIPTION
       "Up to 32 characters describing Read View Name.
        None is reserved for Empty."
   ::= { gs2310SnmpAccessEntry 5 }

gs2310SnmpAccessWriteViewName OBJECT-TYPE
   SYNTAX      DisplayString (SIZE (1..32))
   MAX-ACCESS  read-write
   STATUS      current
   DESCRIPTION
       "Up to 32 characters describing Write View Name.
        None is reserved for Empty."
   ::= { gs2310SnmpAccessEntry 6 }

gs2310SnmpAccessRowStatus OBJECT-TYPE
   SYNTAX      INTEGER { active(1), notInservice(2), destroy(4), undo(5) }
   MAX-ACCESS  read-write
   STATUS      current
   DESCRIPTION
       "1: active
        2: notInservice
        4: destroy
        5: undo"
   ::= { gs2310SnmpAccessEntry 7 }

----------------------------------------------------------------------------------------------------

gs2310Configuration                                         OBJECT IDENTIFIER ::= { lancomGS2310 2 }

gs2310Port                                                  OBJECT IDENTIFIER ::= { gs2310Configuration 1 }

gs2310PortConfigurationTable OBJECT-TYPE
   SYNTAX      SEQUENCE OF GS2310PortConfigurationEntry
   MAX-ACCESS  not-accessible
   STATUS      current
   DESCRIPTION
       " Show port configurations. "
   ::= { gs2310Port 1 }

gs2310PortConfigurationEntry OBJECT-TYPE
   SYNTAX      GS2310PortConfigurationEntry
   MAX-ACCESS  not-accessible
   STATUS      current
   DESCRIPTION
       ""
   INDEX    { gs2310PortConfPort  }
   ::= { gs2310PortConfigurationTable 1 }

GS2310PortConfigurationEntry ::= SEQUENCE {
   gs2310PortConfPort                     Integer32,
   gs2310PortConfPortMedia                DisplayString,
   gs2310PortConfLink                     DisplayString,
   gs2310PortConfCurrentSpeed             DisplayString,
   gs2310PortConfSpeed                    INTEGER,
   gs2310PortConfCurrentFlowControlRx     INTEGER,
   gs2310PortConfCurrentFlowControlTx     INTEGER,
   gs2310PortConfFlowControl              INTEGER,
   gs2310PortConfMaxFrameSize             Integer32,
   gs2310PortConfExcessiveCollisionMode   INTEGER,
   gs2310PortConfPowerControl             INTEGER,
   gs2310PortConfDescription              DisplayString
}

gs2310PortConfPort OBJECT-TYPE
   SYNTAX      Integer32(1..4095)
   MAX-ACCESS  not-accessible
   STATUS      current
   DESCRIPTION
       " port, range : 1 - port number. "
   ::= { gs2310PortConfigurationEntry 1 }

gs2310PortConfPortMedia OBJECT-TYPE
   SYNTAX      DisplayString(SIZE (1..4))
   MAX-ACCESS  read-only
   STATUS      current
   DESCRIPTION
       " Show port media. "
   ::= { gs2310PortConfigurationEntry 2 }

gs2310PortConfLink OBJECT-TYPE
   SYNTAX      DisplayString(SIZE (2..4))
   MAX-ACCESS  read-only
   STATUS      current
   DESCRIPTION
       " The current link state. "
   ::= { gs2310PortConfigurationEntry 3 }

gs2310PortConfCurrentSpeed OBJECT-TYPE
   SYNTAX      DisplayString(SIZE (6..12))
   MAX-ACCESS  read-only
   STATUS      current
   DESCRIPTION
       " The current link speed of the port. "
   ::= { gs2310PortConfigurationEntry 4 }

gs2310PortConfSpeed OBJECT-TYPE
   SYNTAX      INTEGER {
                    disable(0),
                    auto(1),
                    speed10Half(2),
                    speed10Full(3),
                    speed100Half(4),
                    speed100Full(5),
                    speed1Gfull(6),
                    sfpAutoAMS(7),
                    speed100FXAMS(8),
                    speed1000XAMS(9),
                    speed100FX(10),
                    speed1000X(11)
                }
   MAX-ACCESS  read-write
   STATUS      current
   DESCRIPTION
       "default: 1,
        0: disable state,
        1: auto,
        2: 10 Half,
        3: 10 Full,
        4: 100 Half,
        5: 100 Full,
        6: 1G full,
        only 'Dual Media' port have 7-11 option.
        Dual Media port default: 7,
        7: SFP_Auto_AMS,
        8: 100FX_AMS,
        9: 1000X_AMS,
        10: 100FX,
        11: 1000X "
   ::= { gs2310PortConfigurationEntry 5 }

gs2310PortConfCurrentFlowControlRx OBJECT-TYPE
   SYNTAX      INTEGER { disable(0), enable(1), noSupport(2) }
   MAX-ACCESS  read-only
   STATUS      current
   DESCRIPTION
       "0: disable
        1: enable
        2: no support.  "
   ::= { gs2310PortConfigurationEntry 6 }

gs2310PortConfCurrentFlowControlTx OBJECT-TYPE
   SYNTAX      INTEGER { disable(0), enable(1), noSupport(2) }
   MAX-ACCESS  read-only
   STATUS      current
   DESCRIPTION
       "0: disable
        1: enable
        2: no support.  "
   ::= { gs2310PortConfigurationEntry 7 }

gs2310PortConfFlowControl OBJECT-TYPE
   SYNTAX      INTEGER { disable(0), enable(1), noSupport(2) }
   MAX-ACCESS  read-write
   STATUS      current
   DESCRIPTION
       "default: 0,
        0: disable
        1: enable
        2: no support. "
   ::= { gs2310PortConfigurationEntry 8 }

gs2310PortConfMaxFrameSize OBJECT-TYPE
   SYNTAX      Integer32 (1518..9600)
   MAX-ACCESS  read-write
   STATUS      current
   DESCRIPTION
       "default: 9600 , range : 1518 - 9600 "
   ::= { gs2310PortConfigurationEntry 9 }

gs2310PortConfExcessiveCollisionMode OBJECT-TYPE
   SYNTAX      INTEGER { discard(0), restart(1), noSupport(2) }
   MAX-ACCESS  read-write
   STATUS      current
   DESCRIPTION
       "default: 0,
        Excessive Collision Mode :
        0: Discard,
        1: Restart,
        2: no support.
       "
   ::= { gs2310PortConfigurationEntry 10 }

gs2310PortConfPowerControl OBJECT-TYPE
   SYNTAX      INTEGER { disable(0), actiphy(1), dynamic(2), enable(3), noSupport(4) }
   MAX-ACCESS  read-write
   STATUS      current
   DESCRIPTION
       "default: 0,
        PowerControl :
        0: disable,
        1: Actiphy,
        2: Dynamic (perfectReach),
        3: Enable,
        4: no support.
       "
   ::= { gs2310PortConfigurationEntry 11 }

gs2310PortConfDescription OBJECT-TYPE
   SYNTAX      DisplayString
   MAX-ACCESS  read-write
   STATUS      current
   DESCRIPTION
       " Interface specific description.
         Up to 47 characters describing this interface. "
   ::= { gs2310PortConfigurationEntry 12 }


gs2310PortTrafficStatisticsTable OBJECT-TYPE
   SYNTAX      SEQUENCE OF GS2310PortTrafficStatisticsEntry
   MAX-ACCESS  not-accessible
   STATUS      current
   DESCRIPTION
       " "
   ::= { gs2310Port 2 }

gs2310PortTrafficStatisticsEntry OBJECT-TYPE
   SYNTAX      GS2310PortTrafficStatisticsEntry
   MAX-ACCESS  not-accessible
   STATUS      current
   DESCRIPTION
       ""
   INDEX    { gs2310PortTrafficStatisticsPort  }
   ::= { gs2310PortTrafficStatisticsTable 1 }

GS2310PortTrafficStatisticsEntry ::= SEQUENCE {
   gs2310PortTrafficStatisticsPort          Integer32,
   gs2310PortTrafficStatisticsClear         INTEGER,
   gs2310PortTrafficRxPackets               Counter64,
   gs2310PortTrafficRxOctets                Counter64,
   gs2310PortTrafficRxUnicast               Counter64,
   gs2310PortTrafficRxMulticast             Counter64,
   gs2310PortTrafficRxBroadcast             Counter64,
   gs2310PortTrafficRxPause                 Counter64,
   gs2310PortTrafficRx64Bytes               Counter64,
   gs2310PortTrafficRx65to127Bytes          Counter64,
   gs2310PortTrafficRx128to255Bytes         Counter64,
   gs2310PortTrafficRx256to511Bytes         Counter64,
   gs2310PortTrafficRx512to1023Bytes        Counter64,
   gs2310PortTrafficRx1024to1526Bytes       Counter64,
   gs2310PortTrafficRxExceecd1527Bytes      Counter64,
   gs2310PortTrafficRxQ0                    Counter64,
   gs2310PortTrafficRxQ1                    Counter64,
   gs2310PortTrafficRxQ2                    Counter64,
   gs2310PortTrafficRxQ3                    Counter64,
   gs2310PortTrafficRxQ4                    Counter64,
   gs2310PortTrafficRxQ5                    Counter64,
   gs2310PortTrafficRxQ6                    Counter64,
   gs2310PortTrafficRxQ7                    Counter64,
   gs2310PortTrafficRxDrops                 Counter64,
   gs2310PortTrafficRxCRCorAlignment        Counter64,
   gs2310PortTrafficRxUndersize             Counter64,
   gs2310PortTrafficRxOversize              Counter64,
   gs2310PortTrafficRxFragments             Counter64,
   gs2310PortTrafficRxJabber                Counter64,
   gs2310PortTrafficRxFiltered              Counter64,
   gs2310PortTrafficTxPackets               Counter64,
   gs2310PortTrafficTxOctets                Counter64,
   gs2310PortTrafficTxUnicast               Counter64,
   gs2310PortTrafficTxMulticast             Counter64,
   gs2310PortTrafficTxBroadcast             Counter64,
   gs2310PortTrafficTxPause                 Counter64,
   gs2310PortTrafficTx64Bytes               Counter64,
   gs2310PortTrafficTx65to127Bytes          Counter64,
   gs2310PortTrafficTx128to255Bytes         Counter64,
   gs2310PortTrafficTx256to511Bytes         Counter64,
   gs2310PortTrafficTx512to1023Bytes        Counter64,
   gs2310PortTrafficTx1024to1526Bytes       Counter64,
   gs2310PortTrafficTxExceecd1527Bytes      Counter64,
   gs2310PortTrafficTxQ0                    Counter64,
   gs2310PortTrafficTxQ1                    Counter64,
   gs2310PortTrafficTxQ2                    Counter64,
   gs2310PortTrafficTxQ3                    Counter64,
   gs2310PortTrafficTxQ4                    Counter64,
   gs2310PortTrafficTxQ5                    Counter64,
   gs2310PortTrafficTxQ6                    Counter64,
   gs2310PortTrafficTxQ7                    Counter64,
   gs2310PortTrafficTxDrops                 Counter64,
   gs2310PortTrafficTxLateOrExcColl         Counter64
}

gs2310PortTrafficStatisticsPort OBJECT-TYPE
   SYNTAX      Integer32 (1..4095)
   MAX-ACCESS  not-accessible
   STATUS      current
   DESCRIPTION
       " "
   ::= { gs2310PortTrafficStatisticsEntry 1 }

gs2310PortTrafficStatisticsClear OBJECT-TYPE
   SYNTAX      INTEGER { disable(0), enable(1) }
   MAX-ACCESS  read-write
   STATUS      current
   DESCRIPTION
       " "
   ::= { gs2310PortTrafficStatisticsEntry 2 }

gs2310PortTrafficRxPackets OBJECT-TYPE
   SYNTAX      Counter64
   MAX-ACCESS  read-only
   STATUS      current
   DESCRIPTION
       " "
   ::= { gs2310PortTrafficStatisticsEntry 3 }

gs2310PortTrafficRxOctets OBJECT-TYPE
   SYNTAX      Counter64
   MAX-ACCESS  read-only
   STATUS      current
   DESCRIPTION
       " "
   ::= { gs2310PortTrafficStatisticsEntry 4 }

gs2310PortTrafficRxUnicast OBJECT-TYPE
   SYNTAX      Counter64
   MAX-ACCESS  read-only
   STATUS      current
   DESCRIPTION
       " "
   ::= { gs2310PortTrafficStatisticsEntry 5 }

gs2310PortTrafficRxMulticast OBJECT-TYPE
   SYNTAX      Counter64
   MAX-ACCESS  read-only
   STATUS      current
   DESCRIPTION
       " "
   ::= { gs2310PortTrafficStatisticsEntry 6 }

gs2310PortTrafficRxBroadcast OBJECT-TYPE
   SYNTAX      Counter64
   MAX-ACCESS  read-only
   STATUS      current
   DESCRIPTION
       " "
   ::= { gs2310PortTrafficStatisticsEntry 7 }

gs2310PortTrafficRxPause OBJECT-TYPE
   SYNTAX      Counter64
   MAX-ACCESS  read-only
   STATUS      current
   DESCRIPTION
       " "
   ::= { gs2310PortTrafficStatisticsEntry 8 }

gs2310PortTrafficRx64Bytes OBJECT-TYPE
   SYNTAX      Counter64
   MAX-ACCESS  read-only
   STATUS      current
   DESCRIPTION
       " "
   ::= { gs2310PortTrafficStatisticsEntry 9 }

gs2310PortTrafficRx65to127Bytes OBJECT-TYPE
   SYNTAX      Counter64
   MAX-ACCESS  read-only
   STATUS      current
   DESCRIPTION
       " "
   ::= { gs2310PortTrafficStatisticsEntry 10 }

gs2310PortTrafficRx128to255Bytes OBJECT-TYPE
   SYNTAX      Counter64
   MAX-ACCESS  read-only
   STATUS      current
   DESCRIPTION
       " "
   ::= { gs2310PortTrafficStatisticsEntry 11 }

gs2310PortTrafficRx256to511Bytes OBJECT-TYPE
   SYNTAX      Counter64
   MAX-ACCESS  read-only
   STATUS      current
   DESCRIPTION
       " "
   ::= { gs2310PortTrafficStatisticsEntry 12 }

gs2310PortTrafficRx512to1023Bytes OBJECT-TYPE
   SYNTAX      Counter64
   MAX-ACCESS  read-only
   STATUS      current
   DESCRIPTION
       " "
   ::= { gs2310PortTrafficStatisticsEntry 13 }

gs2310PortTrafficRx1024to1526Bytes OBJECT-TYPE
   SYNTAX      Counter64
   MAX-ACCESS  read-only
   STATUS      current
   DESCRIPTION
       " "
   ::= { gs2310PortTrafficStatisticsEntry 14 }

gs2310PortTrafficRxExceecd1527Bytes OBJECT-TYPE
   SYNTAX      Counter64
   MAX-ACCESS  read-only
   STATUS      current
   DESCRIPTION
       " "
   ::= { gs2310PortTrafficStatisticsEntry 15 }

gs2310PortTrafficRxQ0 OBJECT-TYPE
   SYNTAX      Counter64
   MAX-ACCESS  read-only
   STATUS      current
   DESCRIPTION
       " "
   ::= { gs2310PortTrafficStatisticsEntry 16 }

gs2310PortTrafficRxQ1 OBJECT-TYPE
   SYNTAX      Counter64
   MAX-ACCESS  read-only
   STATUS      current
   DESCRIPTION
       " "
   ::= { gs2310PortTrafficStatisticsEntry 17 }

gs2310PortTrafficRxQ2 OBJECT-TYPE
   SYNTAX      Counter64
   MAX-ACCESS  read-only
   STATUS      current
   DESCRIPTION
       " "
   ::= { gs2310PortTrafficStatisticsEntry 18 }

gs2310PortTrafficRxQ3 OBJECT-TYPE
   SYNTAX      Counter64
   MAX-ACCESS  read-only
   STATUS      current
   DESCRIPTION
       " "
   ::= { gs2310PortTrafficStatisticsEntry 19 }

gs2310PortTrafficRxQ4 OBJECT-TYPE
   SYNTAX      Counter64
   MAX-ACCESS  read-only
   STATUS      current
   DESCRIPTION
       " "
   ::= { gs2310PortTrafficStatisticsEntry 20 }

gs2310PortTrafficRxQ5 OBJECT-TYPE
   SYNTAX      Counter64
   MAX-ACCESS  read-only
   STATUS      current
   DESCRIPTION
       " "
   ::= { gs2310PortTrafficStatisticsEntry 21 }

gs2310PortTrafficRxQ6 OBJECT-TYPE
   SYNTAX      Counter64
   MAX-ACCESS  read-only
   STATUS      current
   DESCRIPTION
       " "
   ::= { gs2310PortTrafficStatisticsEntry 22 }

gs2310PortTrafficRxQ7 OBJECT-TYPE
   SYNTAX      Counter64
   MAX-ACCESS  read-only
   STATUS      current
   DESCRIPTION
       " "
   ::= { gs2310PortTrafficStatisticsEntry 23 }

gs2310PortTrafficRxDrops OBJECT-TYPE
   SYNTAX      Counter64
   MAX-ACCESS  read-only
   STATUS      current
   DESCRIPTION
       " "
   ::= { gs2310PortTrafficStatisticsEntry 24 }

gs2310PortTrafficRxCRCorAlignment OBJECT-TYPE
   SYNTAX      Counter64
   MAX-ACCESS  read-only
   STATUS      current
   DESCRIPTION
       " "
   ::= { gs2310PortTrafficStatisticsEntry 25 }

gs2310PortTrafficRxUndersize OBJECT-TYPE
   SYNTAX      Counter64
   MAX-ACCESS  read-only
   STATUS      current
   DESCRIPTION
       " "
   ::= { gs2310PortTrafficStatisticsEntry 26 }

gs2310PortTrafficRxOversize OBJECT-TYPE
   SYNTAX      Counter64
   MAX-ACCESS  read-only
   STATUS      current
   DESCRIPTION
       " "
   ::= { gs2310PortTrafficStatisticsEntry 27 }

gs2310PortTrafficRxFragments OBJECT-TYPE
   SYNTAX      Counter64
   MAX-ACCESS  read-only
   STATUS      current
   DESCRIPTION
       " "
   ::= { gs2310PortTrafficStatisticsEntry 28 }

gs2310PortTrafficRxJabber OBJECT-TYPE
   SYNTAX      Counter64
   MAX-ACCESS  read-only
   STATUS      current
   DESCRIPTION
       " "
   ::= { gs2310PortTrafficStatisticsEntry 29 }

gs2310PortTrafficRxFiltered OBJECT-TYPE
   SYNTAX      Counter64
   MAX-ACCESS  read-only
   STATUS      current
   DESCRIPTION
       " "
   ::= { gs2310PortTrafficStatisticsEntry 30 }

gs2310PortTrafficTxPackets OBJECT-TYPE
   SYNTAX      Counter64
   MAX-ACCESS  read-only
   STATUS      current
   DESCRIPTION
       " "
   ::= { gs2310PortTrafficStatisticsEntry 31 }

gs2310PortTrafficTxOctets OBJECT-TYPE
   SYNTAX      Counter64
   MAX-ACCESS  read-only
   STATUS      current
   DESCRIPTION
       " "
   ::= { gs2310PortTrafficStatisticsEntry 32 }

gs2310PortTrafficTxUnicast OBJECT-TYPE
   SYNTAX      Counter64
   MAX-ACCESS  read-only
   STATUS      current
   DESCRIPTION
       " "
   ::= { gs2310PortTrafficStatisticsEntry 33 }

gs2310PortTrafficTxMulticast OBJECT-TYPE
   SYNTAX      Counter64
   MAX-ACCESS  read-only
   STATUS      current
   DESCRIPTION
       " "
   ::= { gs2310PortTrafficStatisticsEntry 34 }

gs2310PortTrafficTxBroadcast OBJECT-TYPE
   SYNTAX      Counter64
   MAX-ACCESS  read-only
   STATUS      current
   DESCRIPTION
       " "
   ::= { gs2310PortTrafficStatisticsEntry 35 }

gs2310PortTrafficTxPause OBJECT-TYPE
   SYNTAX      Counter64
   MAX-ACCESS  read-only
   STATUS      current
   DESCRIPTION
       " "
   ::= { gs2310PortTrafficStatisticsEntry 36 }

gs2310PortTrafficTx64Bytes OBJECT-TYPE
   SYNTAX      Counter64
   MAX-ACCESS  read-only
   STATUS      current
   DESCRIPTION
       " "
   ::= { gs2310PortTrafficStatisticsEntry 37 }

gs2310PortTrafficTx65to127Bytes OBJECT-TYPE
   SYNTAX      Counter64
   MAX-ACCESS  read-only
   STATUS      current
   DESCRIPTION
       " "
   ::= { gs2310PortTrafficStatisticsEntry 38 }

gs2310PortTrafficTx128to255Bytes OBJECT-TYPE
   SYNTAX      Counter64
   MAX-ACCESS  read-only
   STATUS      current
   DESCRIPTION
       " "
   ::= { gs2310PortTrafficStatisticsEntry 39 }

gs2310PortTrafficTx256to511Bytes OBJECT-TYPE
   SYNTAX      Counter64
   MAX-ACCESS  read-only
   STATUS      current
   DESCRIPTION
       " "
   ::= { gs2310PortTrafficStatisticsEntry 40 }

gs2310PortTrafficTx512to1023Bytes OBJECT-TYPE
   SYNTAX      Counter64
   MAX-ACCESS  read-only
   STATUS      current
   DESCRIPTION
       " "
   ::= { gs2310PortTrafficStatisticsEntry 41 }

gs2310PortTrafficTx1024to1526Bytes OBJECT-TYPE
   SYNTAX      Counter64
   MAX-ACCESS  read-only
   STATUS      current
   DESCRIPTION
       " "
   ::= { gs2310PortTrafficStatisticsEntry 42 }

gs2310PortTrafficTxExceecd1527Bytes OBJECT-TYPE
   SYNTAX      Counter64
   MAX-ACCESS  read-only
   STATUS      current
   DESCRIPTION
       " "
   ::= { gs2310PortTrafficStatisticsEntry 43 }

gs2310PortTrafficTxQ0 OBJECT-TYPE
   SYNTAX      Counter64
   MAX-ACCESS  read-only
   STATUS      current
   DESCRIPTION
       " "
   ::= { gs2310PortTrafficStatisticsEntry 44 }

gs2310PortTrafficTxQ1 OBJECT-TYPE
   SYNTAX      Counter64
   MAX-ACCESS  read-only
   STATUS      current
   DESCRIPTION
       " "
   ::= { gs2310PortTrafficStatisticsEntry 45 }

gs2310PortTrafficTxQ2 OBJECT-TYPE
   SYNTAX      Counter64
   MAX-ACCESS  read-only
   STATUS      current
   DESCRIPTION
       " "
   ::= { gs2310PortTrafficStatisticsEntry 46 }

gs2310PortTrafficTxQ3 OBJECT-TYPE
   SYNTAX      Counter64
   MAX-ACCESS  read-only
   STATUS      current
   DESCRIPTION
       " "
   ::= { gs2310PortTrafficStatisticsEntry 47 }

gs2310PortTrafficTxQ4 OBJECT-TYPE
   SYNTAX      Counter64
   MAX-ACCESS  read-only
   STATUS      current
   DESCRIPTION
       " "
   ::= { gs2310PortTrafficStatisticsEntry 48 }

gs2310PortTrafficTxQ5 OBJECT-TYPE
   SYNTAX      Counter64
   MAX-ACCESS  read-only
   STATUS      current
   DESCRIPTION
       " "
   ::= { gs2310PortTrafficStatisticsEntry 49 }

gs2310PortTrafficTxQ6 OBJECT-TYPE
   SYNTAX      Counter64
   MAX-ACCESS  read-only
   STATUS      current
   DESCRIPTION
       " "
   ::= { gs2310PortTrafficStatisticsEntry 50 }


gs2310PortTrafficTxQ7 OBJECT-TYPE
   SYNTAX      Counter64
   MAX-ACCESS  read-only
   STATUS      current
   DESCRIPTION
       " "
   ::= { gs2310PortTrafficStatisticsEntry 51 }

gs2310PortTrafficTxDrops OBJECT-TYPE
   SYNTAX      Counter64
   MAX-ACCESS  read-only
   STATUS      current
   DESCRIPTION
       " "
   ::= { gs2310PortTrafficStatisticsEntry 52 }

gs2310PortTrafficTxLateOrExcColl OBJECT-TYPE
   SYNTAX      Counter64
   MAX-ACCESS  read-only
   STATUS      current
   DESCRIPTION
       " "
   ::= { gs2310PortTrafficStatisticsEntry 53 }


gs2310PortQoSStatistics                                     OBJECT IDENTIFIER ::= { gs2310Port 3 }

gs2310PortQoSStatisticsClear OBJECT-TYPE
   SYNTAX      INTEGER { none(0), clear(1) }
   MAX-ACCESS  read-only
   STATUS      current
   DESCRIPTION
       "default: 0
       0: none
       1: clear "
   ::= { gs2310PortQoSStatistics 1 }

gs2310PortQoSStatisticsTable OBJECT-TYPE
   SYNTAX      SEQUENCE OF GS2310PortQoSStatisticsEntry
   MAX-ACCESS  not-accessible
   STATUS      current
   DESCRIPTION
       " "
   ::= { gs2310PortQoSStatistics 2 }

gs2310PortQoSStatisticsEntry OBJECT-TYPE
   SYNTAX      GS2310PortQoSStatisticsEntry
   MAX-ACCESS  not-accessible
   STATUS      current
   DESCRIPTION
       ""
   INDEX    { gs2310PortQoSStatisticsPort  }
   ::= { gs2310PortQoSStatisticsTable 1 }

GS2310PortQoSStatisticsEntry ::= SEQUENCE {
   gs2310PortQoSStatisticsPort      Integer32,
   gs2310PortQoSQ0Rx                Counter64,
   gs2310PortQoSQ0Tx                Counter64,
   gs2310PortQoSQ1Rx                Counter64,
   gs2310PortQoSQ1Tx                Counter64,
   gs2310PortQoSQ2Rx                Counter64,
   gs2310PortQoSQ2Tx                Counter64,
   gs2310PortQoSQ3Rx                Counter64,
   gs2310PortQoSQ3Tx                Counter64,
   gs2310PortQoSQ4Rx                Counter64,
   gs2310PortQoSQ4Tx                Counter64,
   gs2310PortQoSQ5Rx                Counter64,
   gs2310PortQoSQ5Tx                Counter64,
   gs2310PortQoSQ6Rx                Counter64,
   gs2310PortQoSQ6Tx                Counter64,
   gs2310PortQoSQ7Rx                Counter64,
   gs2310PortQoSQ7Tx                Counter64
}

gs2310PortQoSStatisticsPort OBJECT-TYPE
   SYNTAX      Integer32(1..4095)
   MAX-ACCESS  not-accessible
   STATUS      current
   DESCRIPTION
       " "
   ::= { gs2310PortQoSStatisticsEntry 1 }

gs2310PortQoSQ0Rx OBJECT-TYPE
   SYNTAX      Counter64
   MAX-ACCESS  read-only
   STATUS      current
   DESCRIPTION
       " "
   ::= { gs2310PortQoSStatisticsEntry 2 }

gs2310PortQoSQ0Tx OBJECT-TYPE
   SYNTAX      Counter64
   MAX-ACCESS  read-only
   STATUS      current
   DESCRIPTION
       " "
   ::= { gs2310PortQoSStatisticsEntry 3 }

gs2310PortQoSQ1Rx OBJECT-TYPE
   SYNTAX      Counter64
   MAX-ACCESS  read-only
   STATUS      current
   DESCRIPTION
       " "
   ::= { gs2310PortQoSStatisticsEntry 4 }

gs2310PortQoSQ1Tx OBJECT-TYPE
   SYNTAX      Counter64
   MAX-ACCESS  read-only
   STATUS      current
   DESCRIPTION
       " "
   ::= { gs2310PortQoSStatisticsEntry 5 }

gs2310PortQoSQ2Rx OBJECT-TYPE
   SYNTAX      Counter64
   MAX-ACCESS  read-only
   STATUS      current
   DESCRIPTION
       " "
   ::= { gs2310PortQoSStatisticsEntry 6 }

gs2310PortQoSQ2Tx OBJECT-TYPE
   SYNTAX      Counter64
   MAX-ACCESS  read-only
   STATUS      current
   DESCRIPTION
       " "
   ::= { gs2310PortQoSStatisticsEntry 7 }

gs2310PortQoSQ3Rx OBJECT-TYPE
   SYNTAX      Counter64
   MAX-ACCESS  read-only
   STATUS      current
   DESCRIPTION
       " "
   ::= { gs2310PortQoSStatisticsEntry 8 }

gs2310PortQoSQ3Tx OBJECT-TYPE
   SYNTAX      Counter64
   MAX-ACCESS  read-only
   STATUS      current
   DESCRIPTION
       " "
   ::= { gs2310PortQoSStatisticsEntry 9 }

gs2310PortQoSQ4Rx OBJECT-TYPE
   SYNTAX      Counter64
   MAX-ACCESS  read-only
   STATUS      current
   DESCRIPTION
       " "
   ::= { gs2310PortQoSStatisticsEntry 10 }

gs2310PortQoSQ4Tx OBJECT-TYPE
   SYNTAX      Counter64
   MAX-ACCESS  read-only
   STATUS      current
   DESCRIPTION
       " "
   ::= { gs2310PortQoSStatisticsEntry 11 }

gs2310PortQoSQ5Rx OBJECT-TYPE
   SYNTAX      Counter64
   MAX-ACCESS  read-only
   STATUS      current
   DESCRIPTION
       " "
   ::= { gs2310PortQoSStatisticsEntry 12 }

gs2310PortQoSQ5Tx OBJECT-TYPE
   SYNTAX      Counter64
   MAX-ACCESS  read-only
   STATUS      current
   DESCRIPTION
       " "
   ::= { gs2310PortQoSStatisticsEntry 13 }

gs2310PortQoSQ6Rx OBJECT-TYPE
   SYNTAX      Counter64
   MAX-ACCESS  read-only
   STATUS      current
   DESCRIPTION
       " "
   ::= { gs2310PortQoSStatisticsEntry 14 }

gs2310PortQoSQ6Tx OBJECT-TYPE
   SYNTAX      Counter64
   MAX-ACCESS  read-only
   STATUS      current
   DESCRIPTION
       " "
   ::= { gs2310PortQoSStatisticsEntry 15 }

gs2310PortQoSQ7Rx OBJECT-TYPE
   SYNTAX      Counter64
   MAX-ACCESS  read-only
   STATUS      current
   DESCRIPTION
       " "
   ::= { gs2310PortQoSStatisticsEntry 16 }

gs2310PortQoSQ7Tx OBJECT-TYPE
   SYNTAX      Counter64
   MAX-ACCESS  read-only
   STATUS      current
   DESCRIPTION
       " "
   ::= { gs2310PortQoSStatisticsEntry 17 }

gs2310SFPInfoTable OBJECT-TYPE
   SYNTAX      SEQUENCE OF GS2310SFPInfoEntry
   MAX-ACCESS  not-accessible
   STATUS      current
   DESCRIPTION
       " "
   ::= { gs2310Port 4 }

gs2310SFPInfoEntry OBJECT-TYPE
   SYNTAX      GS2310SFPInfoEntry
   MAX-ACCESS  not-accessible
   STATUS      current
   DESCRIPTION
       ""
   INDEX    { gs2310SFPInfoIndex }
   ::= { gs2310SFPInfoTable 1 }

GS2310SFPInfoEntry ::= SEQUENCE {
   gs2310SFPInfoIndex               Integer32,
   gs2310SFPInfoPort                DisplayString,
   gs2310SFPConnectorType           DisplayString,
   gs2310SFPFiberType               DisplayString,
   gs2310SFPTxCentralWavelength     DisplayString,
   gs2310SFPBaudRate                DisplayString,
   gs2310SFPVendorOUI               DisplayString,
   gs2310SFPVendorName              DisplayString,
   gs2310SFPVendorPN                DisplayString,
   gs2310SFPVendorRev               DisplayString,
   gs2310SFPVendorSN                DisplayString,
   gs2310SFPDateCode                DisplayString,
   gs2310SFPTemperature             DisplayString,
   gs2310SFPVcc                     DisplayString,
   gs2310SFPMon1Bias                DisplayString,
   gs2310SFPMon2TxPWR               DisplayString,
   gs2310SFPMon3RxPWR               DisplayString
}

gs2310SFPInfoIndex OBJECT-TYPE
   SYNTAX      Integer32(1..4095)
   MAX-ACCESS  not-accessible
   STATUS      current
   DESCRIPTION
       " "
   ::= { gs2310SFPInfoEntry 1 }

gs2310SFPInfoPort OBJECT-TYPE
   SYNTAX      DisplayString
   MAX-ACCESS  read-only
   STATUS      current
   DESCRIPTION
       " "
   ::= { gs2310SFPInfoEntry 2 }

gs2310SFPConnectorType OBJECT-TYPE
   SYNTAX      DisplayString
   MAX-ACCESS  read-only
   STATUS      current
   DESCRIPTION
       " "
   ::= { gs2310SFPInfoEntry 3 }

gs2310SFPFiberType OBJECT-TYPE
   SYNTAX      DisplayString
   MAX-ACCESS  read-only
   STATUS      current
   DESCRIPTION
       " "
   ::= { gs2310SFPInfoEntry 4 }

gs2310SFPTxCentralWavelength OBJECT-TYPE
   SYNTAX      DisplayString
   MAX-ACCESS  read-only
   STATUS      current
   DESCRIPTION
       " "
   ::= { gs2310SFPInfoEntry 5 }

gs2310SFPBaudRate OBJECT-TYPE
   SYNTAX      DisplayString
   MAX-ACCESS  read-only
   STATUS      current
   DESCRIPTION
       " "
   ::= { gs2310SFPInfoEntry 6 }

gs2310SFPVendorOUI OBJECT-TYPE
   SYNTAX      DisplayString
   MAX-ACCESS  read-only
   STATUS      current
   DESCRIPTION
       " "
   ::= { gs2310SFPInfoEntry 7 }

gs2310SFPVendorName OBJECT-TYPE
   SYNTAX      DisplayString
   MAX-ACCESS  read-only
   STATUS      current
   DESCRIPTION
       " "
   ::= { gs2310SFPInfoEntry 8 }

gs2310SFPVendorPN OBJECT-TYPE
   SYNTAX      DisplayString
   MAX-ACCESS  read-only
   STATUS      current
   DESCRIPTION
       " "
   ::= { gs2310SFPInfoEntry 9 }

gs2310SFPVendorRev OBJECT-TYPE
   SYNTAX      DisplayString
   MAX-ACCESS  read-only
   STATUS      current
   DESCRIPTION
       " "
   ::= { gs2310SFPInfoEntry 10 }

gs2310SFPVendorSN OBJECT-TYPE
   SYNTAX      DisplayString
   MAX-ACCESS  read-only
   STATUS      current
   DESCRIPTION
       " "
   ::= { gs2310SFPInfoEntry 11 }

gs2310SFPDateCode OBJECT-TYPE
   SYNTAX      DisplayString
   MAX-ACCESS  read-only
   STATUS      current
   DESCRIPTION
       " "
   ::= { gs2310SFPInfoEntry 12 }

gs2310SFPTemperature OBJECT-TYPE
   SYNTAX      DisplayString
   MAX-ACCESS  read-only
   STATUS      current
   DESCRIPTION
       " "
   ::= { gs2310SFPInfoEntry 13 }

gs2310SFPVcc OBJECT-TYPE
   SYNTAX      DisplayString
   MAX-ACCESS  read-only
   STATUS      current
   DESCRIPTION
       " "
   ::= { gs2310SFPInfoEntry 14 }

gs2310SFPMon1Bias OBJECT-TYPE
   SYNTAX      DisplayString
   MAX-ACCESS  read-only
   STATUS      current
   DESCRIPTION
       " "
   ::= { gs2310SFPInfoEntry 15 }

gs2310SFPMon2TxPWR OBJECT-TYPE
   SYNTAX      DisplayString
   MAX-ACCESS  read-only
   STATUS      current
   DESCRIPTION
       " "
   ::= { gs2310SFPInfoEntry 16 }

gs2310SFPMon3RxPWR OBJECT-TYPE
   SYNTAX      DisplayString
   MAX-ACCESS  read-only
   STATUS      current
   DESCRIPTION
       " "
   ::= { gs2310SFPInfoEntry 17 }


gs2310PortEEETable OBJECT-TYPE
   SYNTAX      SEQUENCE OF GS2310PortEEEEntry
   MAX-ACCESS  not-accessible
   STATUS      current
   DESCRIPTION
      " "
   ::= { gs2310Port 5 }

gs2310PortEEEEntry OBJECT-TYPE
   SYNTAX      GS2310PortEEEEntry
   MAX-ACCESS  not-accessible
   STATUS      current
   DESCRIPTION
       ""
   INDEX    { gs2310PortEEEPort }
   ::= { gs2310PortEEETable 1 }

GS2310PortEEEEntry ::= SEQUENCE {
   gs2310PortEEEPort		        Integer32,
   gs2310PortEEEMode		        INTEGER,
   gs2310PortEEEUrgentQueue1		INTEGER,
   gs2310PortEEEUrgentQueue2		INTEGER,
   gs2310PortEEEUrgentQueue3		INTEGER,
   gs2310PortEEEUrgentQueue4		INTEGER,
   gs2310PortEEEUrgentQueue5		INTEGER,
   gs2310PortEEEUrgentQueue6		INTEGER,
   gs2310PortEEEUrgentQueue7		INTEGER,
   gs2310PortEEEUrgentQueue8		INTEGER
}

gs2310PortEEEPort OBJECT-TYPE
   SYNTAX      Integer32(1..4095)
   MAX-ACCESS  not-accessible
   STATUS      current
   DESCRIPTION
       " "
   ::= { gs2310PortEEEEntry 1 }

gs2310PortEEEMode OBJECT-TYPE
   SYNTAX      INTEGER { disable(0), enable(1) }
   MAX-ACCESS  read-write
   STATUS      current
   DESCRIPTION
       "default: 0
       0:disable
       1:enable "
   ::= { gs2310PortEEEEntry 2 }

gs2310PortEEEUrgentQueue1 OBJECT-TYPE
   SYNTAX      INTEGER { disable(0), enable(1) }
   MAX-ACCESS  read-write
   STATUS      current
   DESCRIPTION
       "default: 0
       0:disable
       1:enable "
   ::= { gs2310PortEEEEntry 3 }

gs2310PortEEEUrgentQueue2 OBJECT-TYPE
   SYNTAX      INTEGER { disable(0), enable(1) }
   MAX-ACCESS  read-write
   STATUS      current
   DESCRIPTION
       "default: 0
       0:disable
       1:enable "
   ::= { gs2310PortEEEEntry 4 }

gs2310PortEEEUrgentQueue3 OBJECT-TYPE
   SYNTAX      INTEGER { disable(0), enable(1) }
   MAX-ACCESS  read-write
   STATUS      current
   DESCRIPTION
       "default: 0
       0:disable
       1:enable "
   ::= { gs2310PortEEEEntry 5 }

gs2310PortEEEUrgentQueue4 OBJECT-TYPE
   SYNTAX      INTEGER { disable(0), enable(1) }
   MAX-ACCESS  read-write
   STATUS      current
   DESCRIPTION
       "default: 0
       0:disable
       1:enable "
   ::= { gs2310PortEEEEntry 6 }

gs2310PortEEEUrgentQueue5 OBJECT-TYPE
   SYNTAX      INTEGER { disable(0), enable(1) }
   MAX-ACCESS  read-write
   STATUS      current
   DESCRIPTION
       "default: 0
       0:disable
       1:enable "
   ::= { gs2310PortEEEEntry 7 }

gs2310PortEEEUrgentQueue6 OBJECT-TYPE
   SYNTAX      INTEGER { disable(0), enable(1) }
   MAX-ACCESS  read-write
   STATUS      current
   DESCRIPTION
       "default: 0
       0:disable
       1:enable "
   ::= { gs2310PortEEEEntry 8 }

gs2310PortEEEUrgentQueue7 OBJECT-TYPE
   SYNTAX      INTEGER { disable(0), enable(1) }
   MAX-ACCESS  read-write
   STATUS      current
   DESCRIPTION
       "default: 0
       0:disable
       1:enable "
   ::= { gs2310PortEEEEntry 9 }

gs2310PortEEEUrgentQueue8 OBJECT-TYPE
   SYNTAX      INTEGER { disable(0), enable(1) }
   MAX-ACCESS  read-write
   STATUS      current
   DESCRIPTION
       "default: 0
       0:disable
       1:enable "
   ::= { gs2310PortEEEEntry 10 }


gs2310VoiceVLAN                                             OBJECT IDENTIFIER ::= { gs2310Configuration 2 }

gs2310VoiceVLANConf                                         OBJECT IDENTIFIER ::= { gs2310VoiceVLAN 1 }

gs2310VoiceVLANMode OBJECT-TYPE
   SYNTAX      INTEGER { disable(0), enable(1) }
   MAX-ACCESS  read-write
   STATUS      current
   DESCRIPTION
       " Voice VLAN mode operation.
       default: 0,
       0: disable
       1: enable"
   ::= { gs2310VoiceVLANConf 1 }

gs2310VoiceVLANVLANId OBJECT-TYPE
   SYNTAX      Integer32(1..4094)
   MAX-ACCESS  read-write
   STATUS      current
   DESCRIPTION
       "Voice VLAN ID.
        default: 1000,
        range : 1-4094. "
   ::= { gs2310VoiceVLANConf 2 }

gs2310VoiceVLANAgingTime OBJECT-TYPE
   SYNTAX      Integer32(10..1000000)
   MAX-ACCESS  read-write
   STATUS      current
   DESCRIPTION
       " Voice VLAN secure learning aging time.
         default: 86400,
         range : 10 - 10000000. "
   ::= { gs2310VoiceVLANConf 3 }

gs2310VoiceVLANTrafficClass OBJECT-TYPE
   SYNTAX      Integer32(0..7)
   MAX-ACCESS  read-write
   STATUS      current
   DESCRIPTION
       " Voice VLAN traffic class, all traffic on the Voice VLAN
         will apply this class, available value is from 0(Low)
         to 7(High).
         default: 7. "
   ::= { gs2310VoiceVLANConf 4 }


gs2310VoiceVLANPortTable OBJECT-TYPE
   SYNTAX      SEQUENCE OF GS2310VoiceVLANPortEntry
   MAX-ACCESS  not-accessible
   STATUS      current
   DESCRIPTION
       " Show Voice Vlan configuration. "
   ::= { gs2310VoiceVLANConf 5 }

gs2310VoiceVLANPortEntry OBJECT-TYPE
   SYNTAX      GS2310VoiceVLANPortEntry
   MAX-ACCESS  not-accessible
   STATUS      current
   DESCRIPTION
       ""
   INDEX    { gs2310VoiceVLANPort  }
   ::= { gs2310VoiceVLANPortTable 1 }

GS2310VoiceVLANPortEntry ::= SEQUENCE {
   gs2310VoiceVLANPort                    Integer32,
   gs2310VoiceVLANPortMode                INTEGER,
   gs2310VoiceVLANPortSecurity            INTEGER,
   gs2310VoiceVLANPortDiscoveryProtocol   INTEGER
}

gs2310VoiceVLANPort OBJECT-TYPE
   SYNTAX      Integer32(1..4095)
   MAX-ACCESS  not-accessible
   STATUS      current
   DESCRIPTION
       " port, range : 1 - port number. "
   ::= { gs2310VoiceVLANPortEntry 1 }

gs2310VoiceVLANPortMode OBJECT-TYPE
   SYNTAX      INTEGER { disable(0), auto(1), forced(2) }
   MAX-ACCESS  read-write
   STATUS      current
   DESCRIPTION
       " Voice VLAN port mode.
         default: 0,
         0: Disable (Disjoin from Voice VLAN.)
         1: Auto (Enable auto detect mode. It detects whether there is VoIP phone attached to the specific port and configures the Voice VLAN members automatically.)
         2: Forced (Force join to Voice VLAN.)"
   ::= { gs2310VoiceVLANPortEntry 2 }

gs2310VoiceVLANPortSecurity OBJECT-TYPE
   SYNTAX      INTEGER { disable(0), enable(1) }
   MAX-ACCESS  read-write
   STATUS      current
   DESCRIPTION
       " Voice VLAN port security mode.
         default: 0,
         0: Disable (Disjoin from Voice VLAN.)
         1: enable ( Enable Voice VLAN security mode. When the function is
                     enabled, all non-telephone MAC address in Voice VLAN
                     will be blocked 10 seconds.)"
   ::= { gs2310VoiceVLANPortEntry 3 }

gs2310VoiceVLANPortDiscoveryProtocol OBJECT-TYPE
   SYNTAX      INTEGER { oui(0), lldp(1), both(2) }
   MAX-ACCESS  read-write
   STATUS      current
   DESCRIPTION
       " Voice VLAN port discovery protocol.
         default: 0
         0: OUI (Detect telephony device by OUI address.)
         1: LLDP (Detect telephony device by LLDP.)
         2: Both (Both OUI and LLDP.) "
   ::= { gs2310VoiceVLANPortEntry 4 }

gs2310VoiceVLANSkipNAS OBJECT-TYPE
   SYNTAX      INTEGER { disable(0), enable(1) }
   MAX-ACCESS  read-write
   STATUS      current
   DESCRIPTION
       " Voice VLAN skip NAS mode.
         default: 0,
         0: Disable (Do not skip NAS on Voice VLAN.)
         1: enable (Enable skipping of NAS on Voice VLAN. When the function is
                    enabled, authentication through the NAS module is not
                    applied to the Voice VLAN, but clients are allowed without
                    authentication.)"
   ::= { gs2310VoiceVLANPortEntry 5 }


gs2310VoiceVLANOUI                                          OBJECT IDENTIFIER ::= { gs2310VoiceVLAN 2 }

gs2310VoiceVLANOUICreate OBJECT-TYPE
   SYNTAX       INTEGER { none(0), create(1) }
   MAX-ACCESS   read-write
   STATUS       current
   DESCRIPTION
       "default: 0
        0 : None  (read only)
        1 : Create an OUI entry"
   ::= { gs2310VoiceVLANOUI 1 }

gs2310VoiceVLANOUITable OBJECT-TYPE
   SYNTAX      SEQUENCE OF GS2310VoiceVLANOUIEntry
   MAX-ACCESS  not-accessible
   STATUS      current
   DESCRIPTION
       " Create Voice VLAN OUI entry. Modify OUI table will
         restart auto detect OUI process. "
   ::= { gs2310VoiceVLANOUI 2 }

gs2310VoiceVLANOUIEntry OBJECT-TYPE
   SYNTAX      GS2310VoiceVLANOUIEntry
   MAX-ACCESS  not-accessible
   STATUS      current
   DESCRIPTION
       ""
   INDEX    { gs2310VoiceVLANOUIIndex  }
   ::= { gs2310VoiceVLANOUITable 1 }

GS2310VoiceVLANOUIEntry ::= SEQUENCE {
   gs2310VoiceVLANOUIIndex         Integer32,
   gs2310VoiceVLANTelephonyOUI     OCTET STRING,
   gs2310VoiceVLANDescription      DisplayString,
   gs2310VoiceVLANOUIRowStatus     INTEGER
}

gs2310VoiceVLANOUIIndex OBJECT-TYPE
   SYNTAX      Integer32(1..16)
   MAX-ACCESS  not-accessible
   STATUS      current
   DESCRIPTION
       " "
   ::= { gs2310VoiceVLANOUIEntry 1 }

gs2310VoiceVLANTelephonyOUI OBJECT-TYPE
   SYNTAX      OCTET STRING (SIZE (1..32))
   MAX-ACCESS  read-write
   STATUS      current
   DESCRIPTION
       "OUI address, format : 0a 1b 2c "
   ::= { gs2310VoiceVLANOUIEntry 2 }

gs2310VoiceVLANDescription OBJECT-TYPE
   SYNTAX      DisplayString (SIZE (1..32))
   MAX-ACCESS  read-write
   STATUS      current
   DESCRIPTION
       " Up to 32 characters describing OUI address. "
   ::= { gs2310VoiceVLANOUIEntry 3 }

gs2310VoiceVLANOUIRowStatus OBJECT-TYPE
   SYNTAX      INTEGER { active(1), notInservice(2), destroy(4), undo(5) }
   MAX-ACCESS  read-write
   STATUS      current
   DESCRIPTION
       "1: active
        2: notInservice
        4: destroy
        5: undo"
   ::= { gs2310VoiceVLANOUIEntry 4 }

gs2310GARP                                                   OBJECT IDENTIFIER ::= { gs2310Configuration 3 }

gs2310GARPConfTable OBJECT-TYPE
   SYNTAX      SEQUENCE OF GS2310GARPConfEntry
   MAX-ACCESS  not-accessible
   STATUS      current
   DESCRIPTION
       " "
   ::= { gs2310GARP 1 }

gs2310GARPConfEntry OBJECT-TYPE
   SYNTAX      GS2310GARPConfEntry
   MAX-ACCESS  not-accessible
   STATUS      current
   DESCRIPTION
       ""
   INDEX    { gs2310GARPConfPort  }
   ::= { gs2310GARPConfTable 1 }

GS2310GARPConfEntry ::= SEQUENCE {
   gs2310GARPConfPort           Integer32,
   gs2310GARPJoinTimer          Integer32,
   gs2310GARPLeaveTimer         Integer32,
   gs2310GARPLeaveAllTimer      Integer32,
   gs2310GARPApplicantion       INTEGER,
   gs2310GARPAttributeType      INTEGER,
   gs2310GARPApplicant          INTEGER
}

gs2310GARPConfPort OBJECT-TYPE
   SYNTAX      Integer32(1..4095)
   MAX-ACCESS  not-accessible
   STATUS      current
   DESCRIPTION
       " "
   ::= { gs2310GARPConfEntry 1 }

gs2310GARPJoinTimer OBJECT-TYPE
   SYNTAX      Integer32(200..1000)
   MAX-ACCESS  read-write
   STATUS      current
   DESCRIPTION
       "default: 200, range : 200 - 1000 "
   ::= { gs2310GARPConfEntry 2 }

gs2310GARPLeaveTimer OBJECT-TYPE
   SYNTAX      Integer32(600..3000)
   MAX-ACCESS  read-write
   STATUS      current
   DESCRIPTION
       "default: 600 , range : 600 - 3000"
   ::= { gs2310GARPConfEntry 3 }

gs2310GARPLeaveAllTimer OBJECT-TYPE
   SYNTAX      Integer32(10000..50000)
   MAX-ACCESS  read-write
   STATUS      current
   DESCRIPTION
       "default: 10000, range : 10000 - 50000 "
   ::= { gs2310GARPConfEntry 4 }

gs2310GARPApplicantion OBJECT-TYPE
   SYNTAX      INTEGER { gvrp(1)}
   MAX-ACCESS  read-write
   STATUS      current
   DESCRIPTION
       "default: 1
       1: GVRP"
   ::= { gs2310GARPConfEntry 5 }

gs2310GARPAttributeType OBJECT-TYPE
   SYNTAX      INTEGER { vlan(1)}
   MAX-ACCESS  read-write
   STATUS      current
   DESCRIPTION
       "default: 1
       1: VLAN"
   ::= { gs2310GARPConfEntry 6 }

gs2310GARPApplicant OBJECT-TYPE
   SYNTAX      INTEGER { participant(0), nonParticipant(1) }
   MAX-ACCESS  read-write
   STATUS      current
   DESCRIPTION
       "default: 0
       0: normal-participant
       1: non-participant"
   ::= { gs2310GARPConfEntry 7 }

gs2310GARPStatisticsTable OBJECT-TYPE
   SYNTAX      SEQUENCE OF GS2310GARPStatisticsEntry
   MAX-ACCESS  not-accessible
   STATUS      current
   DESCRIPTION
       " Show the basic GARP port statistics. "
   ::= { gs2310GARP 2 }

gs2310GARPStatisticsEntry OBJECT-TYPE
   SYNTAX      GS2310GARPStatisticsEntry
   MAX-ACCESS  not-accessible
   STATUS      current
   DESCRIPTION
       ""
   INDEX    { gs2310GARPStatisticsPort  }
   ::= { gs2310GARPStatisticsTable 1 }

GS2310GARPStatisticsEntry ::= SEQUENCE {
   gs2310GARPStatisticsPort             Integer32,
   gs2310GARPStatisticsPeerMAC          DisplayString,
   gs2310GARPStatisticsFailedCount      Counter32
}

gs2310GARPStatisticsPort OBJECT-TYPE
   SYNTAX      Integer32(1..4095)
   MAX-ACCESS  not-accessible
   STATUS      current
   DESCRIPTION
       " port, range : 1 - port number. "
   ::= { gs2310GARPStatisticsEntry 1 }

gs2310GARPStatisticsPeerMAC OBJECT-TYPE
   SYNTAX      DisplayString
   MAX-ACCESS  read-only
   STATUS      current
   DESCRIPTION
       " Peer MAC is MAC address of the neighbour Switch from with GARP frame is received.  "
   ::= { gs2310GARPStatisticsEntry 2 }

gs2310GARPStatisticsFailedCount OBJECT-TYPE
   SYNTAX      Counter32
   MAX-ACCESS  read-only
   STATUS      current
   DESCRIPTION
       " explain Failed count here. "
   ::= { gs2310GARPStatisticsEntry 3 }

gs2310GVRP                                                   OBJECT IDENTIFIER ::= { gs2310Configuration 4 }

gs2310GVRPConf                                                   OBJECT IDENTIFIER ::= { gs2310GVRP 1 }

gs2310GVRPMode OBJECT-TYPE
   SYNTAX      INTEGER { disable(0), enable(1) }
   MAX-ACCESS  read-write
   STATUS      current
   DESCRIPTION
       "default: 0,
        0: disable,
        1: enable. "
   ::= { gs2310GVRPConf 1 }

gs2310GVRPConfTable OBJECT-TYPE
   SYNTAX      SEQUENCE OF GS2310GVRPConfEntry
   MAX-ACCESS  not-accessible
   STATUS      current
   DESCRIPTION
       " "
   ::= { gs2310GVRPConf 2 }

gs2310GVRPConfEntry OBJECT-TYPE
   SYNTAX      GS2310GVRPConfEntry
   MAX-ACCESS  not-accessible
   STATUS      current
   DESCRIPTION
       ""
   INDEX    { gs2310GVRPConfPort  }
   ::= { gs2310GVRPConfTable 1 }

GS2310GVRPConfEntry ::= SEQUENCE {
   gs2310GVRPConfPort           Integer32,
   gs2310GVRPConfPortMode       INTEGER,
   gs2310GVRPConfPortRRole      INTEGER
}

gs2310GVRPConfPort OBJECT-TYPE
   SYNTAX      Integer32(1..4095)
   MAX-ACCESS  not-accessible
   STATUS      current
   DESCRIPTION
       " "
   ::= { gs2310GVRPConfEntry 1 }

gs2310GVRPConfPortMode OBJECT-TYPE
   SYNTAX      INTEGER { disable(0), enable(1) }
   MAX-ACCESS  read-write
   STATUS      current
   DESCRIPTION
       "default: 0
       1: enable
       0: disable"
   ::= { gs2310GVRPConfEntry 2 }

gs2310GVRPConfPortRRole OBJECT-TYPE
   SYNTAX      INTEGER { disable(0), enable(1) }
   MAX-ACCESS  read-write
   STATUS      current
   DESCRIPTION
       "default: 0
       1: enable
       0: disable"
   ::= { gs2310GVRPConfEntry 3 }

gs2310GVRPStatisticsTable OBJECT-TYPE
   SYNTAX      SEQUENCE OF GS2310GVRPStatisticsEntry
   MAX-ACCESS  not-accessible
   STATUS      current
   DESCRIPTION
       " "
   ::= { gs2310GVRP 2 }

gs2310GVRPStatisticsEntry OBJECT-TYPE
   SYNTAX      GS2310GVRPStatisticsEntry
   MAX-ACCESS  not-accessible
   STATUS      current
   DESCRIPTION
       ""
   INDEX    { gs2310GVRPStatisticsPort  }
   ::= { gs2310GVRPStatisticsTable 1 }

GS2310GVRPStatisticsEntry ::= SEQUENCE {
   gs2310GVRPStatisticsPort         Integer32,
   gs2310GVRPStatisticsJoinTxCnt    Counter32,
   gs2310GVRPStatisticsLeaveTxCnt   Counter32
}

gs2310GVRPStatisticsPort OBJECT-TYPE
   SYNTAX      Integer32(1..4095)
   MAX-ACCESS  not-accessible
   STATUS      current
   DESCRIPTION
       " "
   ::= { gs2310GVRPStatisticsEntry 1 }

gs2310GVRPStatisticsJoinTxCnt OBJECT-TYPE
   SYNTAX      Counter32
   MAX-ACCESS  read-only
   STATUS      current
   DESCRIPTION
       ""
   ::= { gs2310GVRPStatisticsEntry 2 }

gs2310GVRPStatisticsLeaveTxCnt OBJECT-TYPE
   SYNTAX      Counter32
   MAX-ACCESS  read-only
   STATUS      current
   DESCRIPTION
       ""
   ::= { gs2310GVRPStatisticsEntry 3 }


gs2310Mirroring                                             OBJECT IDENTIFIER ::= { gs2310Configuration 6 }

gs2310PortToMirrorOn OBJECT-TYPE
   SYNTAX      Integer32(0..10)
   MAX-ACCESS  read-write
   STATUS      current
   DESCRIPTION
       "default: 0
        0: disable,
        range : 1 - port number. "
   ::= { gs2310Mirroring 1 }

gs2310MirrorTable OBJECT-TYPE
   SYNTAX      SEQUENCE OF GS2310MirrorEntry
   MAX-ACCESS  not-accessible
   STATUS      current
   DESCRIPTION
       " "
   ::= { gs2310Mirroring 2 }

gs2310MirrorEntry OBJECT-TYPE
   SYNTAX      GS2310MirrorEntry
   MAX-ACCESS  not-accessible
   STATUS      current
   DESCRIPTION
       ""
   INDEX    { gs2310MirrorPort  }
   ::= { gs2310MirrorTable 1 }

GS2310MirrorEntry ::= SEQUENCE {
   gs2310MirrorPort		Integer32,
   gs2310MirrorMode		INTEGER
}

gs2310MirrorPort OBJECT-TYPE
   SYNTAX      Integer32(1..4095)
   MAX-ACCESS  not-accessible
   STATUS      current
   DESCRIPTION
       " "
   ::= { gs2310MirrorEntry 1 }

gs2310MirrorMode OBJECT-TYPE
   SYNTAX      INTEGER { disable(0), enable(1), rxOnly(2), txOnly(3) }
   MAX-ACCESS  read-write
   STATUS      current
   DESCRIPTION
       "default: 0
       0: disable
       1: enable
       2: rx only
       3: tx only
       Setting Tx mirroring for analyzer port has no effect. Tx mirroring ignored"
   ::= { gs2310MirrorEntry 2 }

gs2310TrapEventSeverity                                             OBJECT IDENTIFIER ::= { gs2310Configuration 7 }

gs2310TrapEventSeverityACL OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  6(Info)
        0: Emergency
        1: Alert
        2: Critical
        3: Error
        4: Warning
        5: Notice
        6: Info
        7: Debug"
   ::= { gs2310TrapEventSeverity 1 }

gs2310TrapEventSeverityACLLog OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  7(Debug)
        0: Emergency
        1: Alert
        2: Critical
        3: Error
        4: Warning
        5: Notice
        6: Info
        7: Debug"
   ::= { gs2310TrapEventSeverity 2 }

gs2310TrapEventSeverityAccessMgmt OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  6(Info)
        0: Emergency
        1: Alert
        2: Critical
        3: Error
        4: Warning
        5: Notice
        6: Info
        7: Debug"
   ::= { gs2310TrapEventSeverity 3 }

gs2310TrapEventSeverityAuthFailed OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  4(Warning)
        0: Emergency
        1: Alert
        2: Critical
        3: Error
        4: Warning
        5: Notice
        6: Info
        7: Debug"
   ::= { gs2310TrapEventSeverity 4 }

gs2310TrapEventSeverityColdStart OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  4(Warning)
        0: Emergency
        1: Alert
        2: Critical
        3: Error
        4: Warning
        5: Notice
        6: Info
        7: Debug"
   ::= { gs2310TrapEventSeverity 5 }

gs2310TrapEventSeverityConfigInfo OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  6(Info)
        0: Emergency
        1: Alert
        2: Critical
        3: Error
        4: Warning
        5: Notice
        6: Info
        7: Debug"
   ::= { gs2310TrapEventSeverity 6 }

gs2310TrapEventSeverityFirmwareUpgrade OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  6(Info)
        0: Emergency
        1: Alert
        2: Critical
        3: Error
        4: Warning
        5: Notice
        6: Info
        7: Debug"
   ::= { gs2310TrapEventSeverity 7 }

gs2310TrapEventSeverityImportExport OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  6(Info)
        0: Emergency
        1: Alert
        2: Critical
        3: Error
        4: Warning
        5: Notice
        6: Info
        7: Debug"
   ::= { gs2310TrapEventSeverity 8 }

gs2310TrapEventSeverityLACP OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  6(Info)
        0: Emergency
        1: Alert
        2: Critical
        3: Error
        4: Warning
        5: Notice
        6: Info
        7: Debug"
   ::= { gs2310TrapEventSeverity 9 }

gs2310TrapEventSeverityLinkStatus OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  4(Warning)
        0: Emergency
        1: Alert
        2: Critical
        3: Error
        4: Warning
        5: Notice
        6: Info
        7: Debug"
   ::= { gs2310TrapEventSeverity 10 }

gs2310TrapEventSeverityLogin OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  6(Info)
        0: Emergency
        1: Alert
        2: Critical
        3: Error
        4: Warning
        5: Notice
        6: Info
        7: Debug"
   ::= { gs2310TrapEventSeverity 11 }

gs2310TrapEventSeverityLogout OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  6(Info)
        0: Emergency
        1: Alert
        2: Critical
        3: Error
        4: Warning
        5: Notice
        6: Info
        7: Debug"
   ::= { gs2310TrapEventSeverity 12 }

gs2310TrapEventSeverityLoopProtect OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  6(Info)
        0: Emergency
        1: Alert
        2: Critical
        3: Error
        4: Warning
        5: Notice
        6: Info
        7: Debug"
   ::= { gs2310TrapEventSeverity 13 }

gs2310TrapEventSeverityMgmtIPChange OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  6(Info)
        0: Emergency
        1: Alert
        2: Critical
        3: Error
        4: Warning
        5: Notice
        6: Info
        7: Debug"
   ::= { gs2310TrapEventSeverity 14 }

gs2310TrapEventSeverityModuleChange OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  5(Notice)
        0: Emergency
        1: Alert
        2: Critical
        3: Error
        4: Warning
        5: Notice
        6: Info
        7: Debug"
   ::= { gs2310TrapEventSeverity 15 }

gs2310TrapEventSeverityNAS OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  6(Info)
        0: Emergency
        1: Alert
        2: Critical
        3: Error
        4: Warning
        5: Notice
        6: Info
        7: Debug"
   ::= { gs2310TrapEventSeverity 16 }

gs2310TrapEventSeverityPasswordChange OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  6(Info)
        0: Emergency
        1: Alert
        2: Critical
        3: Error
        4: Warning
        5: Notice
        6: Info
        7: Debug"
   ::= { gs2310TrapEventSeverity 17 }

gs2310TrapEventSeverityPortSecurity OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  6(Info)
        0: Emergency
        1: Alert
        2: Critical
        3: Error
        4: Warning
        5: Notice
        6: Info
        7: Debug"
   ::= { gs2310TrapEventSeverity 18 }

gs2310TrapEventSeverityVLAN OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  6(Info)
        0: Emergency
        1: Alert
        2: Critical
        3: Error
        4: Warning
        5: Notice
        6: Info
        7: Debug"
   ::= { gs2310TrapEventSeverity 20 }

gs2310TrapEventSeverityWarmStart OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  4(Warning)
        0: Emergency
        1: Alert
        2: Critical
        3: Error
        4: Warning
        5: Notice
        6: Info
        7: Debug"
   ::= { gs2310TrapEventSeverity 21 }



gs2310TrapEventSeverityARPConflict OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  4(Warning)
        0: Emergency
        1: Alert
        2: Critical
        3: Error
        4: Warning
        5: Notice
        6: Info
        7: Debug"
   ::= { gs2310TrapEventSeverity 25 }

gs2310TrapEventSeveritySpoofingLimit OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  4(Warning)
        0: Emergency
        1: Alert
        2: Critical
        3: Error
        4: Warning
        5: Notice
        6: Info
        7: Debug"
   ::= { gs2310TrapEventSeverity 27 }

gs2310TrapEventSeverityStaticARPConflict	 OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  4(Warning)
        0: Emergency
        1: Alert
        2: Critical
        3: Error
        4: Warning
        5: Notice
        6: Info
        7: Debug"
   ::= { gs2310TrapEventSeverity 28 }

gs2310SMTP                                             OBJECT IDENTIFIER ::= { gs2310Configuration 8 }

gs2310SMTPMailServer OBJECT-TYPE
   SYNTAX      DisplayString
   MAX-ACCESS  read-write
   STATUS      current
   DESCRIPTION
       " Up to 47 characters describing email server. "
   ::= { gs2310SMTP 1 }

gs2310SMTPUserName OBJECT-TYPE
   SYNTAX      DisplayString
   MAX-ACCESS  read-write
   STATUS      current
   DESCRIPTION
       " Up to 47 characters describing user name. "
   ::= { gs2310SMTP 2 }

gs2310SMTPPassword OBJECT-TYPE
   SYNTAX      DisplayString
   MAX-ACCESS  read-write
   STATUS      current
   DESCRIPTION
       " Up to 47 characters describing password. "
   ::= { gs2310SMTP 3 }

gs2310SMTPServeriryLevel OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       "default: 6
       0: Emergency
       1: Alert
       2: Critical
       3: Error
       4: Warning
       5: Notice
       6: Info
       7: Debug"
   ::= { gs2310SMTP 4 }

gs2310SMTPSender OBJECT-TYPE
   SYNTAX      DisplayString
   MAX-ACCESS  read-write
   STATUS      current
   DESCRIPTION
       " Up to 47 characters describing sender. "
   ::= { gs2310SMTP 5 }

gs2310SMTPReturnPath OBJECT-TYPE
   SYNTAX      DisplayString
   MAX-ACCESS  read-write
   STATUS      current
   DESCRIPTION
       " Up to 47 characters describing return path. "
   ::= { gs2310SMTP 6 }

gs2310SMTPEmailAddress1 OBJECT-TYPE
   SYNTAX      DisplayString
   MAX-ACCESS  read-write
   STATUS      current
   DESCRIPTION
       " Up to 47 characters describing mail address. "
   ::= { gs2310SMTP 7 }

gs2310SMTPEmailAddress2 OBJECT-TYPE
   SYNTAX      DisplayString
   MAX-ACCESS  read-write
   STATUS      current
   DESCRIPTION
       " Up to 47 characters describing mail address. "
   ::= { gs2310SMTP 8 }

gs2310SMTPEmailAddress3 OBJECT-TYPE
   SYNTAX      DisplayString
   MAX-ACCESS  read-write
   STATUS      current
   DESCRIPTION
       " Up to 47 characters describing mail address. "
   ::= { gs2310SMTP 9 }

gs2310SMTPEmailAddress4 OBJECT-TYPE
   SYNTAX      DisplayString
   MAX-ACCESS  read-write
   STATUS      current
   DESCRIPTION
       " Up to 47 characters describing mail address. "
   ::= { gs2310SMTP 10 }

gs2310SMTPEmailAddress5 OBJECT-TYPE
   SYNTAX      DisplayString
   MAX-ACCESS  read-write
   STATUS      current
   DESCRIPTION
       " Up to 47 characters describing mail address. "
   ::= { gs2310SMTP 11 }

gs2310SMTPEmailAddress6 OBJECT-TYPE
   SYNTAX      DisplayString
   MAX-ACCESS  read-write
   STATUS      current
   DESCRIPTION
       " Up to 47 characters describing mail address. "
   ::= { gs2310SMTP 12 }


gs2310ACL                                                   OBJECT IDENTIFIER ::= { gs2310Configuration 9 }

gs2310ACLPortsConfTable OBJECT-TYPE
   SYNTAX      SEQUENCE OF GS2310ACLPortsConfEntry
   MAX-ACCESS  not-accessible
   STATUS      current
   DESCRIPTION
       " "
   ::= { gs2310ACL 1 }

gs2310ACLPortsConfEntry OBJECT-TYPE
   SYNTAX      GS2310ACLPortsConfEntry
   MAX-ACCESS  not-accessible
   STATUS      current
   DESCRIPTION
       ""
   INDEX    { gs2310ACLPortsConfPort  }
   ::= { gs2310ACLPortsConfTable 1 }

GS2310ACLPortsConfEntry ::= SEQUENCE {
   gs2310ACLPortsConfPort               Integer32,
   gs2310ACLPortsConfPolicyID           Integer32,
   gs2310ACLPortsConfAction             INTEGER,
   gs2310ACLPortsConfRateLimiterID      Integer32,
   gs2310ACLPortsConfPortRedirect       Integer32,
   gs2310ACLPortsConfMirror             INTEGER,
   gs2310ACLPortsConfLogging            INTEGER,
   gs2310ACLPortsConfShutdown           INTEGER,
   gs2310ACLPortsConfState              INTEGER,
   gs2310ACLPortsConfCounter            Counter32
}

gs2310ACLPortsConfPort OBJECT-TYPE
   SYNTAX      Integer32 (1..4095)
   MAX-ACCESS  not-accessible
   STATUS      current
   DESCRIPTION
       " "
   ::= { gs2310ACLPortsConfEntry 1 }

gs2310ACLPortsConfPolicyID OBJECT-TYPE
   SYNTAX      Integer32 (0..255)
   MAX-ACCESS  read-write
   STATUS      current
   DESCRIPTION
       "default: 0, range : 0 - 255 "
   ::= { gs2310ACLPortsConfEntry 2 }

gs2310ACLPortsConfAction OBJECT-TYPE
   SYNTAX      INTEGER { deny(0), permit(1) }
   MAX-ACCESS  read-write
   STATUS      current
   DESCRIPTION
       "default: 1,
        0: Deny
        1: Permit"
   ::= { gs2310ACLPortsConfEntry 3 }

gs2310ACLPortsConfRateLimiterID OBJECT-TYPE
   SYNTAX      Integer32 (0..12)
   MAX-ACCESS  read-write
   STATUS      current
   DESCRIPTION
       "default: 0,
        0: Disable
        range : 0 - 12 "
   ::= { gs2310ACLPortsConfEntry 4 }

gs2310ACLPortsConfPortRedirect OBJECT-TYPE
   SYNTAX      Integer32 (0..4095)
   MAX-ACCESS  read-write
   STATUS      current
   DESCRIPTION
       "default: 0
        0: Disable
        range : 0 - end port number "
   ::= { gs2310ACLPortsConfEntry 5 }

gs2310ACLPortsConfMirror OBJECT-TYPE
   SYNTAX      INTEGER { disable(0), enable(1) }
   MAX-ACCESS  read-write
   STATUS      current
   DESCRIPTION
       "default: 0
        0: Disable
        1: Enable "
   ::= { gs2310ACLPortsConfEntry 6 }

gs2310ACLPortsConfLogging OBJECT-TYPE
   SYNTAX      INTEGER { disable(0), enable(1) }
   MAX-ACCESS  read-write
   STATUS      current
   DESCRIPTION
       "default: 0
        0: Disable
        1: Enable "
   ::= { gs2310ACLPortsConfEntry 7 }

gs2310ACLPortsConfShutdown OBJECT-TYPE
   SYNTAX      INTEGER { disable(0), enable(1) }
   MAX-ACCESS  read-write
   STATUS      current
   DESCRIPTION
       "default: 0
        0: Disable
        1: Enable "
   ::= { gs2310ACLPortsConfEntry 8 }

gs2310ACLPortsConfState OBJECT-TYPE
   SYNTAX      INTEGER { disable(0), enable(1) }
   MAX-ACCESS  read-write
   STATUS      current
   DESCRIPTION
       "default: 1
        0: Disable
        1: Enable "
   ::= { gs2310ACLPortsConfEntry 9 }

gs2310ACLPortsConfCounter OBJECT-TYPE
   SYNTAX      Counter32
   MAX-ACCESS  read-only
   STATUS      current
   DESCRIPTION
       "Counts the number of frames that match this ACE. "
   ::= { gs2310ACLPortsConfEntry 10 }


gs2310ACLRateLimiterTable OBJECT-TYPE
   SYNTAX      SEQUENCE OF GS2310ACLRateLimiterEntry
   MAX-ACCESS  not-accessible
   STATUS      current
   DESCRIPTION
       " "
   ::= { gs2310ACL 2 }

gs2310ACLRateLimiterEntry OBJECT-TYPE
   SYNTAX      GS2310ACLRateLimiterEntry
   MAX-ACCESS  not-accessible
   STATUS      current
   DESCRIPTION
       ""
   INDEX    { gs2310ACLRateLimiterID  }
   ::= { gs2310ACLRateLimiterTable 1 }

GS2310ACLRateLimiterEntry ::= SEQUENCE {
   gs2310ACLRateLimiterID       Integer32,
   gs2310ACLRateLimiterUnit     INTEGER,
   gs2310ACLRateLimiterRate     Integer32
}

gs2310ACLRateLimiterID OBJECT-TYPE
   SYNTAX      Integer32 (1..12)
   MAX-ACCESS  not-accessible
   STATUS      current
   DESCRIPTION
       " Rate Limiter ID.
         range : 1-12 "
   ::= { gs2310ACLRateLimiterEntry 1 }

gs2310ACLRateLimiterUnit OBJECT-TYPE
   SYNTAX      INTEGER { pps(0), kbps(1) }
   MAX-ACCESS  read-write
   STATUS      current
   DESCRIPTION
       "default: 0,
        0: pps
        1: kbps"
   ::= { gs2310ACLRateLimiterEntry 2 }

gs2310ACLRateLimiterRate OBJECT-TYPE
   SYNTAX      Integer32(0..3276700)
   MAX-ACCESS  read-write
   STATUS      current
   DESCRIPTION
       "default: 1,
        range : <0-3276700> pps
                <0-10000> kbps"
   ::= { gs2310ACLRateLimiterEntry 3 }


gs2310ACLACE                                          OBJECT IDENTIFIER ::= { gs2310ACL 3 }

gs2310ACLACECreate OBJECT-TYPE
   SYNTAX       INTEGER { none(0), create(1) }
   MAX-ACCESS   read-write
   STATUS       current
   DESCRIPTION
       "default: 0
        0 : None  (read only)
        1 : Create an ACE entry"
   ::= { gs2310ACLACE 1 }

gs2310ACLACETable OBJECT-TYPE
   SYNTAX      SEQUENCE OF GS2310ACLACEEntry
   MAX-ACCESS  not-accessible
   STATUS      current
   DESCRIPTION
       " Create ACL ACE entry. "
   ::= { gs2310ACLACE 2 }

gs2310ACLACEEntry OBJECT-TYPE
   SYNTAX      GS2310ACLACEEntry
   MAX-ACCESS  not-accessible
   STATUS      current
   DESCRIPTION
       ""
   INDEX    { gs2310ACLACEIndex  }
   ::= { gs2310ACLACETable 1 }

GS2310ACLACEEntry ::= SEQUENCE {
   gs2310ACLACEIndex                Integer32,
   gs2310ACLACEID                   Integer32,
   gs2310ACLACENextID               Integer32,
   gs2310ACLACEIngressPort          DisplayString,
   gs2310ACLACEPortPolicyNumber     Integer32,

   gs2310ACLACEPortPolicyBitmask    Integer32,
   gs2310ACLACEFrameType            INTEGER,
   gs2310ACLACEAction               INTEGER,
   gs2310ACLACEDenyPortRedirect     DisplayString,
   gs2310ACLACELogging              INTEGER,

   gs2310ACLACEMirror               INTEGER,
   gs2310ACLACERateLimiter          Integer32,
   gs2310ACLACEShutdown             INTEGER,
   gs2310ACLACEVLAN8021QTagged      INTEGER,
   gs2310ACLACEVLANTagPriority      Integer32,

   gs2310ACLACEVLANVID              Integer32,
   gs2310ACLACEEtherType            Integer32,
   gs2310ACLACESMAC                 DisplayString,
   gs2310ACLACEDMACType             INTEGER,
   gs2310ACLACEDMAC                 DisplayString,

   gs2310ACLACEArpOpcode            INTEGER,
   gs2310ACLACEArpFlagsRequestReply INTEGER,
   gs2310ACLACEArpFlagsArpSmac      INTEGER,
   gs2310ACLACEArpFlagsRarpDmac     INTEGER,
   gs2310ACLACEArpFlagsLength       INTEGER,

   gs2310ACLACEArpFlagsIp           INTEGER,
   gs2310ACLACEArpFlagsEthernet     INTEGER,
   gs2310ACLACESIPType              INTEGER,
   gs2310ACLACESIPIPAddress         IpAddress,
   gs2310ACLACESIPNetworkPrefix     Integer32,

   gs2310ACLACEDIPType              INTEGER,
   gs2310ACLACEDIPIPAddress         IpAddress,
   gs2310ACLACEDIPNetworkPrefix     Integer32,

   gs2310ACLACEIPProtocol           Integer32,
   gs2310ACLACEIPFlagsTTL           INTEGER,
   gs2310ACLACEIPFlagsOptions       INTEGER,
   gs2310ACLACEIPFlagsFragment      INTEGER,
   gs2310ACLACEICMPType             Integer32,

   gs2310ACLACEICMPCode             Integer32,
   gs2310ACLACESourcePortMin        Integer32,
   gs2310ACLACESourcePortMax        Integer32,
   gs2310ACLACEDestPortMin          Integer32,
   gs2310ACLACEDestPortMax          Integer32,

   gs2310ACLACETCPFlagsFin          INTEGER,
   gs2310ACLACETCPFlagsSyn          INTEGER,
   gs2310ACLACETCPFlagsRst          INTEGER,
   gs2310ACLACETCPFlagsPsh          INTEGER,
   gs2310ACLACETCPFlagsAck          INTEGER,

   gs2310ACLACETCPFlagsUrg          INTEGER,

   gs2310ACLACERowStatus            INTEGER
}

gs2310ACLACEIndex OBJECT-TYPE
   SYNTAX      Integer32(1..256)
   MAX-ACCESS  not-accessible
   STATUS      current
   DESCRIPTION
       " "
   ::= { gs2310ACLACEEntry 1 }

gs2310ACLACEID OBJECT-TYPE
   SYNTAX      Integer32(1..256)
   MAX-ACCESS  read-write
   STATUS      current
   DESCRIPTION
       " If the ACE ID is specified and an entry with this ACE ID
         already exists, the ACE will be modified. Otherwise, a
         new ACE will be added.
         range : 1 - 256. "
   ::= { gs2310ACLACEEntry 2 }

gs2310ACLACENextID OBJECT-TYPE
   SYNTAX      Integer32 (0..256)
   MAX-ACCESS  read-write
   STATUS      current
   DESCRIPTION
       " If the next ACE ID is non zero, the ACE will be placed
         before this ACE in the list. If the next ACE ID is zero,
         the ACE will be placed last in the list.
         range : 0 - 256. "
   ::= { gs2310ACLACEEntry 3 }

gs2310ACLACEIngressPort OBJECT-TYPE
   SYNTAX      DisplayString
   MAX-ACCESS  read-write
   STATUS      current
   DESCRIPTION
       " Indicates the ingress port of the ACE. Possible values are:
         All: The ACE will match all ingress port.
         Port: The ACE will match a specific ingress port.Format: 1,3,6."
   ::= { gs2310ACLACEEntry 4 }

gs2310ACLACEPortPolicyNumber OBJECT-TYPE
   SYNTAX      Integer32(0..255)
   MAX-ACCESS  read-write
   STATUS      current
   DESCRIPTION
       " policy value.
         range : 0 - 255. "
   ::= { gs2310ACLACEEntry 5 }

gs2310ACLACEPortPolicyBitmask OBJECT-TYPE
   SYNTAX      Integer32(0..255)
   MAX-ACCESS  read-write
   STATUS      current
   DESCRIPTION
       " policy bitmask.
         range : 0 - 255(0xff). "
   ::= { gs2310ACLACEEntry 6 }

gs2310ACLACEFrameType OBJECT-TYPE
   SYNTAX      INTEGER {
                        any(0),
                        arp(1),
                        etype(2),
                        icmp(3),
                        ipv4(4),
                        tcp(5),
                        udp(6)
                        }
   MAX-ACCESS  read-write
   STATUS      current
   DESCRIPTION
       " 0: any,
         1: arp,
         2: etype,
         3: icmp,
         4: ipv4,
         5: tcp,
         6: udp."
   ::= { gs2310ACLACEEntry 7 }

gs2310ACLACEAction OBJECT-TYPE
   SYNTAX      INTEGER { deny(0), permit(1) }
   MAX-ACCESS  read-write
   STATUS      current
   DESCRIPTION
       "default: 1,
        0: Deny
        1: Permit"
   ::= { gs2310ACLACEEntry 8 }

gs2310ACLACEDenyPortRedirect OBJECT-TYPE
   SYNTAX      DisplayString
   MAX-ACCESS  read-write
   STATUS      current
   DESCRIPTION
       " Frames that hit the ACE are redirected to the port number specified here.
         Disabled: indicates that the port redirect operation is disabled.
         Port Format: 1,3,6."
   ::= { gs2310ACLACEEntry 9 }

gs2310ACLACELogging OBJECT-TYPE
   SYNTAX      INTEGER { disable(0), enable(1) }
   MAX-ACCESS  read-write
   STATUS      current
   DESCRIPTION
       "default: 0,
        0: disable - Frames matching the ACE are not logged.
        1: enable - Frames matching the ACE are stored in the system log."
   ::= { gs2310ACLACEEntry 10 }

gs2310ACLACEMirror OBJECT-TYPE
   SYNTAX      INTEGER { disable(0), enable(1) }
   MAX-ACCESS  read-write
   STATUS      current
   DESCRIPTION
       "default: 0,
        0: disable - Frames matching the ACE are not mirrored.
        1: enable - Frames matching the ACE are mirrored."
   ::= { gs2310ACLACEEntry 11 }

gs2310ACLACERateLimiter OBJECT-TYPE
   SYNTAX      Integer32(0..12)
   MAX-ACCESS  read-write
   STATUS      current
   DESCRIPTION
       "default: 0,
        0: Disable
        range : 0 - 12 "
   ::= { gs2310ACLACEEntry 12 }

gs2310ACLACEShutdown OBJECT-TYPE
   SYNTAX      INTEGER { disable(0), enable(1) }
   MAX-ACCESS  read-write
   STATUS      current
   DESCRIPTION
       "default: 0,
        0: disable - Port shut down is disabled for the AC.
        1: enable - If a frame matches the ACE, the ingress port will be disabled."
   ::= { gs2310ACLACEEntry 13 }

gs2310ACLACEVLAN8021QTagged OBJECT-TYPE
   SYNTAX      INTEGER { disable(0), enable(1), any(2) }
   MAX-ACCESS  read-write
   STATUS      current
   DESCRIPTION
       "Specify whether frames can hit the action according to the 802.1Q tagged.
        default: 2,
        0: disable - Untagged frame only.
        1: enable - Tagged frame only.
        2: Any - Any value is allowed. "
   ::= { gs2310ACLACEEntry 14 }

gs2310ACLACEVLANTagPriority OBJECT-TYPE
   SYNTAX      Integer32(0..8)
   MAX-ACCESS  read-write
   STATUS      current
   DESCRIPTION
       "Specify the tag priority for this ACE.
        The tag priority can't be set when 802.1Q Tagged is disabled
        default: 8,
        8: Any,
        range : 0 - 8 "
   ::= { gs2310ACLACEEntry 15 }

gs2310ACLACEVLANVID OBJECT-TYPE
   SYNTAX      Integer32(0..4094)
   MAX-ACCESS  read-write
   STATUS      current
   DESCRIPTION
       "Specify the VLAN ID filter for this ACE.
        The vid can't be set when 802.1Q Tagged is disabled.
        default: 0,
        0: Any - No VLAN ID filter is specified.
        range : 0 - 4094 "
   ::= { gs2310ACLACEEntry 16 }

gs2310ACLACEEtherType OBJECT-TYPE
   SYNTAX      Integer32(0..65535)
   MAX-ACCESS  read-write
   STATUS      current
   DESCRIPTION
       " 0: Any - Any but excluding 0x0800(IPv4) 0x0806(ARP) and 0x86DD(IPv6).
         range : 0 or 1536(0x0600)- 65535(0xffff). "
   ::= { gs2310ACLACEEntry 17 }

gs2310ACLACESMAC OBJECT-TYPE
   SYNTAX      DisplayString
   MAX-ACCESS  read-write
   STATUS      current
   DESCRIPTION
       " Configure source MAC address for this ACE.
         <mac-address>: A frame that hits this ACE matches this source MAC address value.
         Any: Don't care."
   ::= { gs2310ACLACEEntry 18 }

gs2310ACLACEDMACType OBJECT-TYPE
   SYNTAX      INTEGER { any(0), broadcast(1), unicast(2), multicast(3) , macAddress(4) }
   MAX-ACCESS  read-write
   STATUS      current
   DESCRIPTION
       "DMAC Type.
        default: 0,
        0: Any - Don't care.
        1: Broadcast - Frame must be broadcast.
        2: Unicast - Frame must be unicast.
        3: Multicast - Frame must be multicast.
        4: mac address.
        range : 0 - 4 "
   ::= { gs2310ACLACEEntry 19 }

gs2310ACLACEDMAC OBJECT-TYPE
   SYNTAX      DisplayString
   MAX-ACCESS  read-write
   STATUS      current
   DESCRIPTION
       " Configure destination MAC address for this ACE.
         <mac-address>: A frame that hits this ACE matches this destination MAC address value.
         Any: Don't care.
         Broadcast: Frame must be broadcast.
         Unicast: Frame must be unicast.
         Multicast: Frame must be multicast. "
   ::= { gs2310ACLACEEntry 20 }

gs2310ACLACEArpOpcode OBJECT-TYPE
   SYNTAX      INTEGER { any(0), arp(1), rarp(2), other(3), noData(4) }
   MAX-ACCESS  read-write
   STATUS      current
   DESCRIPTION
       "Configure ARP opcode for this ACE.
        default: 0,
        0: Any - Don't care.
        1: arp.
        2: rarp.
        3: other.
        4: No data.
        range : 0 - 4 "
   ::= { gs2310ACLACEEntry 21 }

gs2310ACLACEArpFlagsRequestReply OBJECT-TYPE
   SYNTAX      INTEGER { reply(0), request(1), any(2), noData(3)}
   MAX-ACCESS  read-write
   STATUS      current
   DESCRIPTION
       "Specify the available ARP/RARP opcode (OP) flag for this ACE.
        default: 2,
        0: Frame must have ARP Reply or RARP Reply OP flag.
        1: Frame must have ARP Request or RARP Request OP flag set.
        2: Any - Don't care.
        3: No data.
        range : 0 - 3 "
   ::= { gs2310ACLACEEntry 22 }

gs2310ACLACEArpFlagsArpSmac OBJECT-TYPE
   SYNTAX      INTEGER { notEqualSMAC(0), equalSMAC(1), any(2), noData(3)}
   MAX-ACCESS  read-write
   STATUS      current
   DESCRIPTION
       "Specify whether frames can hit the action according to their sender hardware address field (SHA) settings.
        default: 2,
        0: ARP frames where SHA is not equal to the SMAC address.
        1: ARP frames where SHA is equal to the SMAC address.
        2: Any - Don't care.
        3: No data.
        range : 0 - 3 "
   ::= { gs2310ACLACEEntry 23 }

gs2310ACLACEArpFlagsRarpDmac OBJECT-TYPE
   SYNTAX      INTEGER { notEqualDMAC(0), equalDMAC(1), any(2), noData(3)}
   MAX-ACCESS  read-write
   STATUS      current
   DESCRIPTION
       "Specify whether frames can hit the action according to their target hardware address field (THA) settings.
        default: 2,
        0: RARP frames where THA is not equal to the DMAC address.
        1: RARP frames where THA is equal to the DMAC address.
        2: Any - Don't care.
        3: No data.
        range : 0 - 3 "
   ::= { gs2310ACLACEEntry 24 }

gs2310ACLACEArpFlagsLength OBJECT-TYPE
   SYNTAX      INTEGER(0..3)
   MAX-ACCESS  read-write
   STATUS      current
   DESCRIPTION
       "Specify whether frames can hit the action according to their ARP/RARP hardware address length (HLN) and
        protocol address length (PLN) settings.
        default: 2,
        0: ARP/RARP frames where the HLN is not equal to Ethernet(0x06) or the (PLN) is not equal to IPv4(0x04).
        1: ARP/RARP frames where the HLN is equal to Ethernet (0x06) and the (PLN) is equal to IPv4(0x04).
        2: Any - Don't care.
        3: No data.
        range : 0 - 3 "
   ::= { gs2310ACLACEEntry 25 }

gs2310ACLACEArpFlagsIp OBJECT-TYPE
   SYNTAX      INTEGER(0..3)
   MAX-ACCESS  read-write
   STATUS      current
   DESCRIPTION
       "Specify whether frames can hit the action according to their ARP/RARP hardware address space (HRD) settings.
        default: 2,
        0: ARP/RARP frames where the HLD is not equal to Ethernet(1).
        1: ARP/RARP frames where the HLD is equal to Ethernet(1).
        2: Any - Don't care.
        3: No data.
        range : 0 - 3 "
   ::= { gs2310ACLACEEntry 26 }

gs2310ACLACEArpFlagsEthernet OBJECT-TYPE
   SYNTAX      INTEGER(0..3)
   MAX-ACCESS  read-write
   STATUS      current
   DESCRIPTION
       "Specify whether frames can hit the action according to their ARP/RARP protocol address space (PRO) settings.
        default: 2,
        0: ARP/RARP frames where the PRO is not equal to IP\n(0x800).
        1: ARP/RARP frames where the PRO is equal to IP(0x800).
        2: Any - Don't care.
        3: No data.
        range : 0 - 3 "
   ::= { gs2310ACLACEEntry 27 }

gs2310ACLACESIPType OBJECT-TYPE
   SYNTAX      INTEGER { any(0), ip(1), noData(2) }
   MAX-ACCESS  read-write
   STATUS      current
   DESCRIPTION
       "Configure source IP address for this ACE.
        default: 0,
        0: Any - Don't care.
        1: IP Address.
        2: No data.
        range : 0 - 1"
   ::= { gs2310ACLACEEntry 28 }

gs2310ACLACESIPIPAddress OBJECT-TYPE
   SYNTAX      IpAddress
   MAX-ACCESS  read-write
   STATUS      current
   DESCRIPTION
       "A frame that hits this ACE matches this source IP address value."
   ::= { gs2310ACLACEEntry 29 }

gs2310ACLACESIPNetworkPrefix OBJECT-TYPE
   SYNTAX      Integer32(0..32)
   MAX-ACCESS  read-write
   STATUS      current
   DESCRIPTION
       "Network prefix.
        default: 32,
        0: No data.
        range : 1 - 32"
   ::= { gs2310ACLACEEntry 30 }


gs2310ACLACEDIPType OBJECT-TYPE
   SYNTAX      INTEGER { any(0), ip(1),noData(2) }
   MAX-ACCESS  read-write
   STATUS      current
   DESCRIPTION
       "Configure destination IP address for this ACE.
        default: 0,
        0: Any - Don't care.
        1: IP Address.
        2: No data.
        range : 0 - 1"
   ::= { gs2310ACLACEEntry 32 }

gs2310ACLACEDIPIPAddress OBJECT-TYPE
   SYNTAX      IpAddress
   MAX-ACCESS  read-write
   STATUS      current
   DESCRIPTION
       "A frame that hits this ACE matches this destination IP address value."
   ::= { gs2310ACLACEEntry 33 }

gs2310ACLACEDIPNetworkPrefix OBJECT-TYPE
   SYNTAX      Integer32(0..32)
   MAX-ACCESS  read-write
   STATUS      current
   DESCRIPTION
       "Network prefix.
        default: 32,
        0: No data.
        range : 1 - 32"
   ::= { gs2310ACLACEEntry 34 }


gs2310ACLACEIPProtocol OBJECT-TYPE
   SYNTAX      Integer32(0..257)
   MAX-ACCESS  read-write
   STATUS      current
   DESCRIPTION
       "Configure IP protocol for this ACE.
        default: 256,
        256: Any - Don't care.
        257: No data.
        range : 0 - 256"
   ::= { gs2310ACLACEEntry 36 }

gs2310ACLACEIPFlagsTTL OBJECT-TYPE
   SYNTAX      INTEGER (0..3)
   MAX-ACCESS  read-write
   STATUS      current
   DESCRIPTION
       "Configure IP Time-to-Live flags for this ACE.
        default: 2,
        0: IPv4 frames with a Time-to-Live field is equal to zero.
        1: IPv4 frames with a Time-to-Live field greater than zero.
        2: Any - Don't care.
        3: No data.
        range : 0 - 3 "
   ::= { gs2310ACLACEEntry 37 }

gs2310ACLACEIPFlagsOptions OBJECT-TYPE
   SYNTAX      INTEGER { unset(0), set(1), any(2), noData(3) }
   MAX-ACCESS  read-write
   STATUS      current
   DESCRIPTION
       "Configure IP options flag for this ACE.
        default: 2,
        0: IPv4 frames where the options flag is unset.
        1: IPv4 frames where the options flag is set.
        2: Any - Don't care.
        3: No data.
        range : 0 - 3 "
   ::= { gs2310ACLACEEntry 38 }

gs2310ACLACEIPFlagsFragment OBJECT-TYPE
   SYNTAX      INTEGER(0..3)
   MAX-ACCESS  read-write
   STATUS      current
   DESCRIPTION
       "Configure IP fragment offset flags for this ACE.
        default: 2,
        0: IPv4 frames where the MF bit is unset and the FRAG OFFSET field is equal zero.
        1: IPv4 frames where the MF bit is set or the FRAG OFFSET field is greater than zero.
        2: Any - Don't care.
        3: No data.
        range : 0 - 3 "
   ::= { gs2310ACLACEEntry 39 }

gs2310ACLACEICMPType OBJECT-TYPE
   SYNTAX      Integer32(0..257)
   MAX-ACCESS  read-write
   STATUS      current
   DESCRIPTION
       "Configure ICMP type for this ACE.
        default: 256,
        256: Any - Don't care.
        257: No data.
        range : 0 - 256"
   ::= { gs2310ACLACEEntry 40 }

gs2310ACLACEICMPCode OBJECT-TYPE
   SYNTAX      Integer32(0..257)
   MAX-ACCESS  read-write
   STATUS      current
   DESCRIPTION
       "Configure ICMP code for this ACE.
        default: 256,
        256: Any - Don't care.
        257: No data.
        range : 0 - 257"
   ::= { gs2310ACLACEEntry 41 }

gs2310ACLACESourcePortMin OBJECT-TYPE
   SYNTAX      Integer32(0..65536)
   MAX-ACCESS  read-write
   STATUS      current
   DESCRIPTION
       "Configure Source UDP/TCP port range for this ACE.
        default: 0,
        65536: No data.
        range : 0 - 65536"
   ::= { gs2310ACLACEEntry 42 }

gs2310ACLACESourcePortMax OBJECT-TYPE
   SYNTAX      Integer32(0..65536)
   MAX-ACCESS  read-write
   STATUS      current
   DESCRIPTION
       "Configure Source UDP/TCP port range for this ACE.
        default: 0,
        65536: No data.
        range : 0 - 65536"
   ::= { gs2310ACLACEEntry 43 }

gs2310ACLACEDestPortMin OBJECT-TYPE
   SYNTAX      Integer32(0..65536)
   MAX-ACCESS  read-write
   STATUS      current
   DESCRIPTION
       "Configure Destination UDP/TCP port range for this ACE.
        default: 0,
        65536: No data.
        range : 0 - 65535"
   ::= { gs2310ACLACEEntry 44 }

gs2310ACLACEDestPortMax OBJECT-TYPE
   SYNTAX      Integer32(0..65536)
   MAX-ACCESS  read-write
   STATUS      current
   DESCRIPTION
       "Configure Destination UDP/TCP port range for this ACE.
        default: 0,
        65536: No data.
        range : 0 - 65535"
   ::= { gs2310ACLACEEntry 45 }

gs2310ACLACETCPFlagsFin OBJECT-TYPE
   SYNTAX      INTEGER { unset(0), set(1), any(2), noData(3) }
   MAX-ACCESS  read-write
   STATUS      current
   DESCRIPTION
       "Configure TCP (FIN) flags for this ACE.
        default: 2,
        0: TCP frames where the FIN field is unset.
        1: TCP frames where the FIN field is set.
        2: Any - Don't care.
        3: No data.
        range : 0 - 3 "
   ::= { gs2310ACLACEEntry 46 }

gs2310ACLACETCPFlagsSyn OBJECT-TYPE
   SYNTAX      INTEGER { unset(0), set(1), any(2), noData(3) }
   MAX-ACCESS  read-write
   STATUS      current
   DESCRIPTION
       "Configure TCP (SYN) flags for this ACE.
        default: 2,
        0: TCP frames where the SYN field is unset.
        1: TCP frames where the SYN field is set.
        2: Any - Don't care.
        3: No data.
        range : 0 - 3 "
   ::= { gs2310ACLACEEntry 47 }

gs2310ACLACETCPFlagsRst OBJECT-TYPE
   SYNTAX      INTEGER { unset(0), set(1), any(2), noData(3) }
   MAX-ACCESS  read-write
   STATUS      current
   DESCRIPTION
       "Configure TCP (RST) flags for this ACE.
        default: 2,
        0: TCP frames where the RST field is unset.
        1: TCP frames where the RST field is set.
        2: Any - Don't care.
        3: No data.
        range : 0 - 3 "
   ::= { gs2310ACLACEEntry 48 }

gs2310ACLACETCPFlagsPsh OBJECT-TYPE
   SYNTAX      INTEGER { unset(0), set(1), any(2), noData(3) }
   MAX-ACCESS  read-write
   STATUS      current
   DESCRIPTION
       "Configure TCP (PSH) flags for this ACE.
        default: 2,
        0: TCP frames where the PSH field is unset.
        1: TCP frames where the PSH field is set.
        2: Any - Don't care.
        3: No data.
        range : 0 - 3 "
   ::= { gs2310ACLACEEntry 49 }

gs2310ACLACETCPFlagsAck OBJECT-TYPE
   SYNTAX      INTEGER { unset(0), set(1), any(2), noData(3) }
   MAX-ACCESS  read-write
   STATUS      current
   DESCRIPTION
       "Configure TCP (ACK) flags for this ACE.
        default: 2,
        0: TCP frames where the ACK field is unset.
        1: TCP frames where the ACK field is set.
        2: Any - Don't care.
        3: No data.
        range : 0 - 3 "
   ::= { gs2310ACLACEEntry 50 }

gs2310ACLACETCPFlagsUrg OBJECT-TYPE
   SYNTAX      INTEGER { unset(0), set(1), any(2), noData(3) }
   MAX-ACCESS  read-write
   STATUS      current
   DESCRIPTION
       "Configure TCP (URG) flags for this ACE.
        default: 2,
        0: TCP frames where the URG field is unset.
        1: TCP frames where the URG field is set.
        2: Any - Don't care.
        3: No data.
        range : 0 - 3 "
   ::= { gs2310ACLACEEntry 51 }

gs2310ACLACERowStatus OBJECT-TYPE
   SYNTAX      INTEGER { active(1), notInservice(2), destroy(4), undo(5) }
   MAX-ACCESS  read-write
   STATUS      current
   DESCRIPTION
       " 1: active
         2: notInservice
         4: destroy
         5: undo"
   ::= { gs2310ACLACEEntry 66 }


gs2310ACLACEClear OBJECT-TYPE
   SYNTAX       INTEGER { noAction(0), clear(1) }
   MAX-ACCESS   read-write
   STATUS       current
   DESCRIPTION
       "default: 0
        0 : No action
        1 : Clear all ACL counters."
   ::= { gs2310ACLACE 3 }

gs2310ACLACEMoveACEID OBJECT-TYPE
   SYNTAX       Integer32(0..256)
   MAX-ACCESS   read-write
   STATUS       current
   DESCRIPTION
       "Move ACE,
        default: 0
        ACE ID must be exist.
        range : 1 - 256."
   ::= { gs2310ACLACE 4 }

gs2310ACLACEMoveNextACEID OBJECT-TYPE
   SYNTAX       Integer32(0..256)
   MAX-ACCESS   read-write
   STATUS       current
   DESCRIPTION
       "Move ACE,
        default: 0
        If the next ACE ID is non zero, the ACE will be placed before this ACE in the list. If the next ACE ID is zero,
        the ACE will be placed last in the list.
        range : 0 - 256."
   ::= { gs2310ACLACE 5 }

gs2310ACLACEStatusTable OBJECT-TYPE
   SYNTAX      SEQUENCE OF GS2310ACLACEStatusEntry
   MAX-ACCESS  not-accessible
   STATUS      current
   DESCRIPTION
       " ACL ACE Status entry. "
   ::= { gs2310ACLACE 6 }

gs2310ACLACEStatusEntry OBJECT-TYPE
   SYNTAX      GS2310ACLACEStatusEntry
   MAX-ACCESS  not-accessible
   STATUS      current
   DESCRIPTION
       ""
   INDEX    { gs2310ACLACEStatusIndex  }
   ::= { gs2310ACLACEStatusTable 1 }

GS2310ACLACEStatusEntry ::= SEQUENCE {
   gs2310ACLACEStatusIndex          Integer32,
   gs2310ACLACEStatusUser           DisplayString,
   gs2310ACLACEStatusID             Integer32,
   gs2310ACLACEStatusIngressPort    DisplayString,
   gs2310ACLACEStatusFrameType      DisplayString,
   gs2310ACLACEStatusAction         DisplayString,
   gs2310ACLACEStatusRateLimiter    DisplayString,
   gs2310ACLACEStatusPortCopy       DisplayString,
   gs2310ACLACEStatusMirror         DisplayString,
   gs2310ACLACEStatusCPU            DisplayString,
   gs2310ACLACEStatusCounter        Counter32,
   gs2310ACLACEStatusConflict       DisplayString
}

gs2310ACLACEStatusIndex OBJECT-TYPE
   SYNTAX      Integer32(1..256)
   MAX-ACCESS  not-accessible
   STATUS      current
   DESCRIPTION
       " "
   ::= { gs2310ACLACEStatusEntry 1 }

gs2310ACLACEStatusUser OBJECT-TYPE
   SYNTAX      DisplayString
   MAX-ACCESS  read-only
   STATUS      current
   DESCRIPTION
       " Indicates the ACL user.
         S : Static.
         IPMG : IP Management.
         IPSG : IP Source Guard.
         IPMC : IPMC.
         ARPI : Arp Inspection.
         UPnP : UPnP.
         DHCP : DHCP. "
   ::= { gs2310ACLACEStatusEntry 2 }

gs2310ACLACEStatusID OBJECT-TYPE
   SYNTAX      Integer32(1..256)
   MAX-ACCESS  read-only
   STATUS      current
   DESCRIPTION
       " ACE ID.
         range : 1 - 256. "
   ::= { gs2310ACLACEStatusEntry 3 }

gs2310ACLACEStatusIngressPort OBJECT-TYPE
   SYNTAX      DisplayString
   MAX-ACCESS  read-only
   STATUS      current
   DESCRIPTION
       " Indicates the ingress port of the ACE. Possible values are:
         All: The ACE will match all ingress port.
         Port: The ACE will match a specific ingress port. "
   ::= { gs2310ACLACEStatusEntry 4 }

gs2310ACLACEStatusFrameType OBJECT-TYPE
   SYNTAX      DisplayString
   MAX-ACCESS  read-only
   STATUS      current
   DESCRIPTION
       " Indicates the frame type of the ACE. "
   ::= { gs2310ACLACEStatusEntry 5 }

gs2310ACLACEStatusAction OBJECT-TYPE
   SYNTAX      DisplayString
   MAX-ACCESS  read-only
   STATUS      current
   DESCRIPTION
       " Indicates the forwarding action of the ACE. "
   ::= { gs2310ACLACEStatusEntry 6 }

gs2310ACLACEStatusRateLimiter OBJECT-TYPE
   SYNTAX      DisplayString
   MAX-ACCESS  read-only
   STATUS      current
   DESCRIPTION
       " Indicates the rate limiter number of the ACE. "
   ::= { gs2310ACLACEStatusEntry 7 }

gs2310ACLACEStatusPortCopy OBJECT-TYPE
   SYNTAX      DisplayString
   MAX-ACCESS  read-only
   STATUS      current
   DESCRIPTION
       " Indicates the port redirect operation of the ACE. Frames matching the ACE are redirected to the port number. "
   ::= { gs2310ACLACEStatusEntry 8 }

gs2310ACLACEStatusMirror OBJECT-TYPE
   SYNTAX      DisplayString
   MAX-ACCESS  read-only
   STATUS      current
   DESCRIPTION
       " Specify the mirror operation of this port. "
   ::= { gs2310ACLACEStatusEntry 9 }

gs2310ACLACEStatusCPU OBJECT-TYPE
   SYNTAX      DisplayString
   MAX-ACCESS  read-only
   STATUS      current
   DESCRIPTION
       " Forward packet that matched the specific ACE to CPU. "
   ::= { gs2310ACLACEStatusEntry 10 }

gs2310ACLACEStatusCounter OBJECT-TYPE
   SYNTAX      Counter32
   MAX-ACCESS  read-only
   STATUS      current
   DESCRIPTION
       " The counter indicates the number of times the ACE was hit by a frame. "
   ::= { gs2310ACLACEStatusEntry 11 }

gs2310ACLACEStatusConflict OBJECT-TYPE
   SYNTAX      DisplayString
   MAX-ACCESS  read-only
   STATUS      current
   DESCRIPTION
       " Indicates the hardware status of the specific ACE. The specific ACE is not applied to the hardware due to hardware limitations. "
   ::= { gs2310ACLACEStatusEntry 12 }

gs2310LoopProtection                                                  OBJECT IDENTIFIER ::= { gs2310Configuration 12 }

gs2310LoopProtectionConfig                                            OBJECT IDENTIFIER ::= { gs2310LoopProtection 1 }

gs2310LoopProtectionGlobalEnable OBJECT-TYPE
   SYNTAX      INTEGER { disable(0), enable(1) }
   MAX-ACCESS  read-write
   STATUS      current
   DESCRIPTION
       "Configure loop protection mode.
        0: disable,
        1: enable,
        default: disable. "
   ::= { gs2310LoopProtectionConfig 1 }

gs2310LoopProtectionTranmisstionTime OBJECT-TYPE
   SYNTAX      Integer32(1..10)
   MAX-ACCESS  read-write
   STATUS      current
   DESCRIPTION
       "Configure loop protection transmit interval.
        default: 5,
        range: 1-10. "
   ::= { gs2310LoopProtectionConfig 2 }

gs2310LoopProtectionShutdownTime OBJECT-TYPE
   SYNTAX      Integer32(0..604800)
   MAX-ACCESS  read-write
   STATUS      current
   DESCRIPTION
       "Configure loop protection shutdown time.
        default: 180,
        range: 0-604800. "
   ::= { gs2310LoopProtectionConfig 3 }

gs2310LoopProtectionConfigurationTable OBJECT-TYPE
   SYNTAX      SEQUENCE OF GS2310LoopProtectionConfigurationEntry
   MAX-ACCESS  not-accessible
   STATUS      current
   DESCRIPTION
       " Show Loop Protection configurations. "
   ::= { gs2310LoopProtectionConfig 4 }

gs2310LoopProtectionConfigurationEntry OBJECT-TYPE
   SYNTAX      GS2310LoopProtectionConfigurationEntry
   MAX-ACCESS  not-accessible
   STATUS      current
   DESCRIPTION
       ""
   INDEX    { gs2310LoopProtectionConfPort  }
   ::= { gs2310LoopProtectionConfigurationTable 1 }

GS2310LoopProtectionConfigurationEntry ::= SEQUENCE {
   gs2310LoopProtectionConfPort	    Integer32,
   gs2310LoopProtectionConfEnable	INTEGER,
   gs2310LoopProtectionConfAction	INTEGER,
   gs2310LoopProtectionConfTxmode	INTEGER
}

gs2310LoopProtectionConfPort OBJECT-TYPE
   SYNTAX      Integer32(1..4095)
   MAX-ACCESS  not-accessible
   STATUS      current
   DESCRIPTION
       " port, range : 1 - port number. "
   ::= { gs2310LoopProtectionConfigurationEntry 1 }

gs2310LoopProtectionConfEnable OBJECT-TYPE
   SYNTAX      INTEGER { disable(0), enable(1) }
   MAX-ACCESS  read-write
   STATUS      current
   DESCRIPTION
       "Configure loop protection port mode.
        0: disable,
        1: enable,
        default: enable. "
   ::= { gs2310LoopProtectionConfigurationEntry 2 }

gs2310LoopProtectionConfAction OBJECT-TYPE
   SYNTAX      INTEGER { shutdown(0), shutdownLog(1), log(2) }
   MAX-ACCESS  read-write
   STATUS      current
   DESCRIPTION
       " Configure loop protection port action.
         0: Shutdown port,
         1: Shutdown port and Log,
         2: Log Only,
         default: Shutdown port. "
   ::= { gs2310LoopProtectionConfigurationEntry 3 }

gs2310LoopProtectionConfTxmode OBJECT-TYPE
   SYNTAX      INTEGER { disable(0), enable(1) }
   MAX-ACCESS  read-write
   STATUS      current
   DESCRIPTION
       "Configure loop protection port transmit mode.
        0: disable,
        1: enable,
        default: enable. "
   ::= { gs2310LoopProtectionConfigurationEntry 4 }

gs2310LoopProtectionStatusTable OBJECT-TYPE
   SYNTAX      SEQUENCE OF GS2310LoopProtectionStatusEntry
   MAX-ACCESS  not-accessible
   STATUS      current
   DESCRIPTION
       " Show Loop Protection Status. "
   ::= { gs2310LoopProtection 2 }

gs2310LoopProtectionStatusEntry OBJECT-TYPE
   SYNTAX      GS2310LoopProtectionStatusEntry
   MAX-ACCESS  not-accessible
   STATUS      current
   DESCRIPTION
       ""
   INDEX    { gs2310LoopProtectionStatusPort  }
   ::= { gs2310LoopProtectionStatusTable 1 }

GS2310LoopProtectionStatusEntry ::= SEQUENCE {
   gs2310LoopProtectionStatusPort	       Integer32,
   gs2310LoopProtectionStatusAction	       DisplayString,
   gs2310LoopProtectionStatusTransmit	   DisplayString,
   gs2310LoopProtectionStatusLoops	       Integer32,
   gs2310LoopProtectionStatusStatus	       DisplayString,
   gs2310LoopProtectionStatusLoop	       DisplayString,
   gs2310LoopProtectionStatusTimeLastLoop  DisplayString
}

gs2310LoopProtectionStatusPort OBJECT-TYPE
   SYNTAX      Integer32(1..4095)
   MAX-ACCESS  not-accessible
   STATUS      current
   DESCRIPTION
       " port, range : 1 - port number. "
   ::= { gs2310LoopProtectionStatusEntry 1 }

gs2310LoopProtectionStatusAction OBJECT-TYPE
   SYNTAX      DisplayString
   MAX-ACCESS  read-only
   STATUS      current
   DESCRIPTION
       " The currently configured port action. "
   ::= { gs2310LoopProtectionStatusEntry 2 }

gs2310LoopProtectionStatusTransmit OBJECT-TYPE
   SYNTAX      DisplayString
   MAX-ACCESS  read-only
   STATUS      current
   DESCRIPTION
       " The currently configured port transmit mode. "
   ::= { gs2310LoopProtectionStatusEntry 3 }

gs2310LoopProtectionStatusLoops OBJECT-TYPE
   SYNTAX      Integer32(0..1000000)
   MAX-ACCESS  read-only
   STATUS      current
   DESCRIPTION
       " The number of loops detected on this port. "
   ::= { gs2310LoopProtectionStatusEntry 4 }

gs2310LoopProtectionStatusStatus OBJECT-TYPE
   SYNTAX      DisplayString
   MAX-ACCESS  read-only
   STATUS      current
   DESCRIPTION
       " The current loop protection status of the port. "
   ::= { gs2310LoopProtectionStatusEntry 5 }

gs2310LoopProtectionStatusLoop OBJECT-TYPE
   SYNTAX      DisplayString
   MAX-ACCESS  read-only
   STATUS      current
   DESCRIPTION
       " Whether a loop is currently detected on the port. "
   ::= { gs2310LoopProtectionStatusEntry 6 }

gs2310LoopProtectionStatusTimeLastLoop OBJECT-TYPE
   SYNTAX      DisplayString
   MAX-ACCESS  read-only
   STATUS      current
   DESCRIPTION
       " The time of the last loop event detected. "
   ::= { gs2310LoopProtectionStatusEntry 7 }

gs2310Qos                                                             OBJECT IDENTIFIER ::= { gs2310Configuration 14 }

gs2310QosPortClassification                                           OBJECT IDENTIFIER ::= { gs2310Qos 1 }

gs2310QosPortClassificationTable OBJECT-TYPE
   SYNTAX      SEQUENCE OF GS2310QosPortClassificationEntry
   MAX-ACCESS  not-accessible
   STATUS      current
   DESCRIPTION
       " QoS Ingress Port Classification . "
   ::= { gs2310QosPortClassification  1 }

gs2310QosPortClassificationEntry OBJECT-TYPE
   SYNTAX      GS2310QosPortClassificationEntry
   MAX-ACCESS  not-accessible
   STATUS      current
   DESCRIPTION
       ""
   INDEX    { gs2310QosPortClassificationPort  }
   ::= { gs2310QosPortClassificationTable 1 }

GS2310QosPortClassificationEntry ::= SEQUENCE {
   gs2310QosPortClassificationPort	        Integer32,
   gs2310QosPortClassificationQoSclass       Integer32,
   gs2310QosPortClassificationDPlevel	    Integer32,
   gs2310QosPortClassificationPCP	        Integer32,
   gs2310QosPortClassificationDEI	        INTEGER,
   gs2310QosPortClassificationTagClass	    INTEGER,
   gs2310QosPortClassificationDSCPBased    INTEGER,
   gs2310QosPortClassificationAddressMode  INTEGER
}

gs2310QosPortClassificationPort OBJECT-TYPE
   SYNTAX      Integer32(1..4095)
   MAX-ACCESS  not-accessible
   STATUS      current
   DESCRIPTION
       " port, range : 1 - port number. "
   ::= { gs2310QosPortClassificationEntry 1 }

gs2310QosPortClassificationQoSclass OBJECT-TYPE
   SYNTAX      Integer32(0..7)
   MAX-ACCESS  read-write
   STATUS      current
   DESCRIPTION
      "Controls the default QoS class, i.e., the QoS class
      for frames not classified in any other way. There is
      a one to one mapping between QoS class, queue and priority.
      A QoS class of 0 (zero) has the lowest priority.
      Note: If the QoS class has been dynamically changed, then
      the actual QoS class is shown in parentheses after the
      configured QoS class.

      Configure the default QoS class.
        range: 0-7,
        default: 0. "
   ::= { gs2310QosPortClassificationEntry 2 }

gs2310QosPortClassificationDPlevel OBJECT-TYPE
   SYNTAX      Integer32(0|1)
   MAX-ACCESS  read-write
   STATUS      current
   DESCRIPTION
       " DP level for frames not classified in any other way.
         range: 0-1,
         default: 0. "
   ::= { gs2310QosPortClassificationEntry 3 }

gs2310QosPortClassificationPCP OBJECT-TYPE
   SYNTAX      Integer32(0..7)
   MAX-ACCESS  read-write
   STATUS      current
   DESCRIPTION
      " Priority Code Point. It is a 3-bit field storing the priority level for the 802.1Q frame.
        range: 0-7,
        default: 0. "
   ::= { gs2310QosPortClassificationEntry 4 }

gs2310QosPortClassificationDEI OBJECT-TYPE
   SYNTAX      INTEGER { disable(0), enable(1) }
   MAX-ACCESS  read-write
   STATUS      current
   DESCRIPTION
      " Drop Eligible Indicator. It is a 1-bit field in the VLAN.
        range 0-1,
        default: 0. "
   ::= { gs2310QosPortClassificationEntry 5 }

gs2310QosPortClassificationTagClass OBJECT-TYPE
   SYNTAX      INTEGER { disable(0), enable(1) }
   MAX-ACCESS  read-write
   STATUS      current
   DESCRIPTION
      " Configure the classification mode for tagged frames.
        0: Disable,
        1: Enable,
        default: Disable. "
   ::= { gs2310QosPortClassificationEntry 6 }

gs2310QosPortClassificationDSCPBased OBJECT-TYPE
   SYNTAX      INTEGER { disable(0), enable(1) }
   MAX-ACCESS  read-write
   STATUS      current
   DESCRIPTION
      " Click to Enable DSCP Based QoS Ingress Port Classification.
        0: disable,
        1: enable,
        default: disable. "
   ::= { gs2310QosPortClassificationEntry 7 }

gs2310QosPortClassificationAddressMode OBJECT-TYPE
   SYNTAX      INTEGER { source(0), destination(1) }
   MAX-ACCESS  read-write
   STATUS      current
   DESCRIPTION
      "The IP/MAC address mode specifying whether the QCL classification
       must be based on source (SMAC/SIP) or destination (DMAC/DIP)
       addresses on this port.
        0: source,
        1: destination,
        default: source. "
   ::= { gs2310QosPortClassificationEntry 8 }

gs2310QoSIngressPortTagClassificationTable OBJECT-TYPE
   SYNTAX      SEQUENCE OF GS2310QoSIngressPortTagClassificationEntry
   MAX-ACCESS  not-accessible
   STATUS      current
   DESCRIPTION
       " Show QoS Ingress Port Tag Classification. "
   ::= { gs2310QosPortClassification 2 }

gs2310QoSIngressPortTagClassificationEntry OBJECT-TYPE
   SYNTAX      GS2310QoSIngressPortTagClassificationEntry
   MAX-ACCESS  not-accessible
   STATUS      current
   DESCRIPTION
       ""
   INDEX    { gs2310QoSIngressPortTagClassificationPort, gs2310QoSIngressPortTagPCP, gs2310QoSIngressPortTagDEI  }
   ::= { gs2310QoSIngressPortTagClassificationTable 1 }

GS2310QoSIngressPortTagClassificationEntry ::= SEQUENCE {
   gs2310QoSIngressPortTagClassificationPort	Integer32,
   gs2310QoSIngressPortTagPCP					INTEGER,
   gs2310QoSIngressPortTagDEI					INTEGER,
   gs2310QoSIngressPortTagQosClass				Integer32,
   gs2310QoSIngressPortTagDPLevel				Integer32
}

gs2310QoSIngressPortTagClassificationPort OBJECT-TYPE
   SYNTAX      Integer32(1..4095)
   MAX-ACCESS  not-accessible
   STATUS      current
   DESCRIPTION
       " port, range : 1 - port number. "
   ::= { gs2310QoSIngressPortTagClassificationEntry 1 }

gs2310QoSIngressPortTagPCP OBJECT-TYPE
   SYNTAX      INTEGER { pcp0(1), pcp1(2), pcp2(3), pcp3(4), pcp4(5), pcp5(6), pcp6(7), pcp7(8) }
   MAX-ACCESS  not-accessible
   STATUS      current
   DESCRIPTION
       " range: 1-8,
         PCP0:1, PCP1:2...  "
   ::= { gs2310QoSIngressPortTagClassificationEntry 2 }

gs2310QoSIngressPortTagDEI OBJECT-TYPE
   SYNTAX      INTEGER { dei0(1), dei1(2) }
   MAX-ACCESS  not-accessible
   STATUS      current
   DESCRIPTION
       " range: 1-2,
         DEI0:1, DEI1:2. "
   ::= { gs2310QoSIngressPortTagClassificationEntry 3 }

gs2310QoSIngressPortTagQosClass OBJECT-TYPE
   SYNTAX      Integer32 (0..7)
   MAX-ACCESS  read-write
   STATUS      current
   DESCRIPTION
       " range: 0-7.  "
   ::= { gs2310QoSIngressPortTagClassificationEntry 4 }

gs2310QoSIngressPortTagDPLevel OBJECT-TYPE
   SYNTAX      Integer32 (0|1)
   MAX-ACCESS  read-write
   STATUS      current
   DESCRIPTION
       " range: 0-1.  "
   ::= { gs2310QoSIngressPortTagClassificationEntry 5 }


gs2310QosPortPolicingTable OBJECT-TYPE
   SYNTAX      SEQUENCE OF GS2310QosPortPolicingEntry
   MAX-ACCESS  not-accessible
   STATUS      current
   DESCRIPTION
       "  configure the Policer settings for all switch ports. "
   ::= { gs2310Qos  2 }

gs2310QosPortPolicingEntry OBJECT-TYPE
   SYNTAX      GS2310QosPortPolicingEntry
   MAX-ACCESS  not-accessible
   STATUS      current
   DESCRIPTION
       ""
   INDEX    { gs2310QosPortPolicingPort  }
   ::= { gs2310QosPortPolicingTable 1 }

GS2310QosPortPolicingEntry ::= SEQUENCE {
   gs2310QosPortPolicingPort	        Integer32,
   gs2310QosPortPolicingMode           INTEGER,
   gs2310QosPortPolicingRate	        Integer32,
   gs2310QosPortPolicingUnit	        INTEGER,
   gs2310QosPortPolicingFlowControl	INTEGER
}

gs2310QosPortPolicingPort OBJECT-TYPE
   SYNTAX      Integer32 (1..4095)
   MAX-ACCESS  not-accessible
   STATUS      current
   DESCRIPTION
       " port, range : 1 - port number. "
   ::= { gs2310QosPortPolicingEntry 1 }

gs2310QosPortPolicingMode OBJECT-TYPE
   SYNTAX      INTEGER { disable(0), enable(1) }
   MAX-ACCESS  read-write
   STATUS      current
   DESCRIPTION
      " Controls whether the policer is enabled on this switch port.
        0: disable,
        1: enable,
        default: disable. "
   ::= { gs2310QosPortPolicingEntry 2 }

gs2310QosPortPolicingRate OBJECT-TYPE
   SYNTAX      Integer32(100..10000000)
   MAX-ACCESS  read-write
   STATUS      current
   DESCRIPTION
       " Controls the rate for the policer.
         range: 100-10000000(kbps/fps),
         default: 500(kbps). "
   ::= { gs2310QosPortPolicingEntry 3 }

gs2310QosPortPolicingUnit OBJECT-TYPE
   SYNTAX      INTEGER { kbps(0), fps(1) }
   MAX-ACCESS  read-write
   STATUS      current
   DESCRIPTION
       " Controls the unit of measure for the policer rate.
         0: kbps,
         1: fps,
         default: kbps. "
   ::= { gs2310QosPortPolicingEntry 4 }

gs2310QosPortPolicingFlowControl OBJECT-TYPE
   SYNTAX      INTEGER { disable(0), enable(1) }
   MAX-ACCESS  read-write
   STATUS      current
   DESCRIPTION
       " If flow control is enabled and the port is in flow control mode,
        then pause frames are sent instead of discarding frames.
         0: disable,
         1: enable,
         default: disable. "
   ::= { gs2310QosPortPolicingEntry 5 }

gs2310QosPortScheduler                                           OBJECT IDENTIFIER ::= { gs2310Qos 3 }

gs2310QosPortSchedulerModeTable OBJECT-TYPE
   SYNTAX      SEQUENCE OF GS2310QosPortSchedulerModeEntry
   MAX-ACCESS  not-accessible
   STATUS      current
   DESCRIPTION
       " configure the basic QoS Port Scheduler Mode settings for all switch ports. "
   ::= { gs2310QosPortScheduler  1 }

gs2310QosPortSchedulerModeEntry OBJECT-TYPE
   SYNTAX      GS2310QosPortSchedulerModeEntry
   MAX-ACCESS  not-accessible
   STATUS      current
   DESCRIPTION
       ""
   INDEX    { gs2310QosSchedulerModePort  }
   ::= { gs2310QosPortSchedulerModeTable 1 }

GS2310QosPortSchedulerModeEntry ::= SEQUENCE {
   gs2310QosSchedulerModePort	                Integer32,
   gs2310QosSchedulerMode                        INTEGER,
   gs2310QosSchedulerShaper	                    INTEGER,
   gs2310QosSchedulerShaperRate	                Integer32
}

gs2310QosSchedulerModePort OBJECT-TYPE
   SYNTAX      Integer32 (1..4095)
   MAX-ACCESS  not-accessible
   STATUS      current
   DESCRIPTION
       " port, range : 1 - port number. "
   ::= { gs2310QosPortSchedulerModeEntry 1 }

gs2310QosSchedulerMode OBJECT-TYPE
   SYNTAX      INTEGER { strictPriority(0), weighted(1) }
   MAX-ACCESS  read-write
   STATUS      current
   DESCRIPTION
       " Controls whether the scheduler mode is Strict Priority or Weighted
       on this switch port.
       0:Strict Priority
       1:Weighted
         default: Strict Priority. "
   ::= { gs2310QosPortSchedulerModeEntry 2 }

gs2310QosSchedulerShaper OBJECT-TYPE
   SYNTAX      INTEGER { disable(0), enable(1) }
   MAX-ACCESS  read-write
   STATUS      current
   DESCRIPTION
       " Controls whether the port shaper is enabled
         0: Disable
         1: Enable.
         default: disable. "
   ::= { gs2310QosPortSchedulerModeEntry 3 }

gs2310QosSchedulerShaperRate OBJECT-TYPE
   SYNTAX      Integer32(100..1000000)
   MAX-ACCESS  read-write
   STATUS      current
   DESCRIPTION
       " Controls the rate for the port shaper.
         range: 100-1000000
         default: 500 kbps. "
   ::= { gs2310QosPortSchedulerModeEntry 4 }

gs2310QosPortSchedulerTable OBJECT-TYPE
   SYNTAX      SEQUENCE OF GS2310QosPortSchedulerEntry
   MAX-ACCESS  not-accessible
   STATUS      current
   DESCRIPTION
       " Show Qos Port Scheduler. "
   ::= { gs2310QosPortScheduler 2 }

gs2310QosPortSchedulerEntry OBJECT-TYPE
   SYNTAX      GS2310QosPortSchedulerEntry
   MAX-ACCESS  not-accessible
   STATUS      current
   DESCRIPTION
       ""
   INDEX    { gs2310QosSchedulerPort, gs2310QosSchedulerPortQueue}
   ::= { gs2310QosPortSchedulerTable 1 }

GS2310QosPortSchedulerEntry ::= SEQUENCE {
   gs2310QosSchedulerPort						Integer32,
   gs2310QosSchedulerPortQueue					INTEGER,
   gs2310QosSchedulerPortQueueShaper				INTEGER,
   gs2310QosSchedulerPortQueueShaperRate			Integer32,
   gs2310QosSchedulerPortQueueShaperExcess		INTEGER,
   gs2310QosSchedulerPortQueueSchedulerWeight	Integer32,
   gs2310QosSchedulerPortQueueSchedulerPercent	DisplayString
}

gs2310QosSchedulerPort OBJECT-TYPE
   SYNTAX      Integer32 (1..4095)
   MAX-ACCESS  not-accessible
   STATUS      current
   DESCRIPTION
       " port, range : 1 - port number. "
   ::= { gs2310QosPortSchedulerEntry 1 }

gs2310QosSchedulerPortQueue OBJECT-TYPE
   SYNTAX      INTEGER { q0(1), q1(2), q2(3), q3(4), q4(5), q5(6), q6(7), q7(8) }
   MAX-ACCESS  not-accessible
   STATUS      current
   DESCRIPTION
       " range: 1-8.
         Q0: 1, Q1: 2, ... "
   ::= { gs2310QosPortSchedulerEntry 2 }

gs2310QosSchedulerPortQueueShaper OBJECT-TYPE
   SYNTAX      INTEGER { disable(0), enable(1) }
   MAX-ACCESS  read-write
   STATUS      current
   DESCRIPTION
       " 0: disable  1:enable,
         default: 0.  "
   ::= { gs2310QosPortSchedulerEntry 3 }

gs2310QosSchedulerPortQueueShaperRate OBJECT-TYPE
   SYNTAX      Integer32(100..1000000)
   MAX-ACCESS  read-write
   STATUS      current
   DESCRIPTION
       " range: 100..1000000 kbps.  "
   ::= { gs2310QosPortSchedulerEntry 4 }

gs2310QosSchedulerPortQueueShaperExcess OBJECT-TYPE
   SYNTAX      INTEGER { disable(0), enable(1) }
   MAX-ACCESS  read-write
   STATUS      current
   DESCRIPTION
       " 0: disable  1:enable,
         default: 0.  "
   ::= { gs2310QosPortSchedulerEntry 5 }

gs2310QosSchedulerPortQueueSchedulerWeight OBJECT-TYPE
   SYNTAX      Integer32(0..100)
   MAX-ACCESS  read-write
   STATUS      current
   DESCRIPTION
       " range: 1-100,
         default: 17.
         Only use in Q0 - Q5.  Q6 & Q7 show 0 "
   ::= { gs2310QosPortSchedulerEntry 6 }

gs2310QosSchedulerPortQueueSchedulerPercent OBJECT-TYPE
   SYNTAX      DisplayString
   MAX-ACCESS  read-only
   STATUS      current
   DESCRIPTION
       " Only use in Q0 - Q5. Q6 & Q7 show empty "
   ::= { gs2310QosPortSchedulerEntry 7 }

gs2310QosPortEgressTagRemarking                                           OBJECT IDENTIFIER ::= { gs2310Qos 4 }

gs2310QosPortEgressTagRemarkingTable OBJECT-TYPE
   SYNTAX      SEQUENCE OF GS2310QosPortEgressTagRemarkingEntry
   MAX-ACCESS  not-accessible
   STATUS      current
   DESCRIPTION
       " configure the basic QoS Port Egress Tag Remark Configuration settings for all switch ports. "
   ::= { gs2310QosPortEgressTagRemarking  1 }

gs2310QosPortEgressTagRemarkingEntry OBJECT-TYPE
   SYNTAX      GS2310QosPortEgressTagRemarkingEntry
   MAX-ACCESS  not-accessible
   STATUS      current
   DESCRIPTION
       ""
   INDEX    { gs2310QosEgressTagRemarkingPort  }
   ::= { gs2310QosPortEgressTagRemarkingTable 1 }

GS2310QosPortEgressTagRemarkingEntry ::= SEQUENCE {
   gs2310QosEgressTagRemarkingPort	                Integer32,
   gs2310QosEgressTagRemarkingMode	                INTEGER
}

gs2310QosEgressTagRemarkingPort OBJECT-TYPE
   SYNTAX      Integer32 (1..4095)
   MAX-ACCESS  not-accessible
   STATUS      current
   DESCRIPTION
       " port, range : 1 - port number. "
   ::= { gs2310QosPortEgressTagRemarkingEntry 1 }

gs2310QosEgressTagRemarkingMode OBJECT-TYPE
   SYNTAX      INTEGER { classified(0), default(1), mapped(2) }
   MAX-ACCESS  read-write
   STATUS      current
   DESCRIPTION
       " the tag remarking mode for this port.
       0:Classified, Use classified PCP/DEI values.
       1:Default, Use default PCP/DEI values.
       2:Mapped, Use mapped versions of QoS class and DP level."
   ::= { gs2310QosPortEgressTagRemarkingEntry 2 }


gs2310QosPortEgressTagRemarkingDefTable OBJECT-TYPE
   SYNTAX      SEQUENCE OF GS2310QosPortEgressTagRemarkingDefEntry
   MAX-ACCESS  not-accessible
   STATUS      current
   DESCRIPTION
       " configure the basic QoS Port Egress Tag Remark Configuration settings for all switch ports. "
   ::= { gs2310QosPortEgressTagRemarking  2 }

gs2310QosPortEgressTagRemarkingDefEntry OBJECT-TYPE
   SYNTAX      GS2310QosPortEgressTagRemarkingDefEntry
   MAX-ACCESS  not-accessible
   STATUS      current
   DESCRIPTION
       ""
   INDEX    { gs2310QosEgressTagRemarkingDefPort  }
   ::= { gs2310QosPortEgressTagRemarkingDefTable 1 }

GS2310QosPortEgressTagRemarkingDefEntry ::= SEQUENCE {
   gs2310QosEgressTagRemarkingDefPort	            Integer32,
   gs2310QosEgressTagRemarkingDefPCP	                Integer32,
   gs2310QosEgressTagRemarkingDefDEI	                INTEGER
}

gs2310QosEgressTagRemarkingDefPort OBJECT-TYPE
   SYNTAX      Integer32(1..4095)
   MAX-ACCESS  not-accessible
   STATUS      current
   DESCRIPTION
       " port, range : 1 - port number. "
   ::= { gs2310QosPortEgressTagRemarkingDefEntry 1 }

gs2310QosEgressTagRemarkingDefPCP OBJECT-TYPE
   SYNTAX      Integer32(0..7)
   MAX-ACCESS  read-write
   STATUS      current
   DESCRIPTION
       " Controls the default PCP
       Range : 0-7"
   ::= { gs2310QosPortEgressTagRemarkingDefEntry 2 }

gs2310QosEgressTagRemarkingDefDEI OBJECT-TYPE
   SYNTAX      INTEGER { disable(0), enable(1) }
   MAX-ACCESS  read-write
   STATUS      current
   DESCRIPTION
       " controls the DEI
       Range 0-1"
   ::= { gs2310QosPortEgressTagRemarkingDefEntry 3 }

gs2310QosPortEgressTagRemarkingMapTable OBJECT-TYPE
   SYNTAX      SEQUENCE OF GS2310QosPortEgressTagRemarkingMapEntry
   MAX-ACCESS  not-accessible
   STATUS      current
   DESCRIPTION
       " Show Qos Port Egress Tag Remarking Map. "
   ::= { gs2310QosPortEgressTagRemarking 4 }

gs2310QosPortEgressTagRemarkingMapEntry OBJECT-TYPE
   SYNTAX      GS2310QosPortEgressTagRemarkingMapEntry
   MAX-ACCESS  not-accessible
   STATUS      current
   DESCRIPTION
       ""
   INDEX    { gs2310QosPortEgressTagRemarkingMapPort, gs2310QosTagRemarkingQoSClass, gs2310QosTagRemarkingDPLevel  }
   ::= { gs2310QosPortEgressTagRemarkingMapTable 1 }

GS2310QosPortEgressTagRemarkingMapEntry ::= SEQUENCE {
   gs2310QosPortEgressTagRemarkingMapPort	Integer32,
   gs2310QosTagRemarkingQoSClass			INTEGER,
   gs2310QosTagRemarkingDPLevel				INTEGER,
   gs2310QosTagRemarkingPCP					Integer32,
   gs2310QosTagRemarkingDEI					INTEGER
}

gs2310QosPortEgressTagRemarkingMapPort OBJECT-TYPE
   SYNTAX      Integer32 (1..4095)
   MAX-ACCESS  not-accessible
   STATUS      current
   DESCRIPTION
       " port, range : 1 - port number. "
   ::= { gs2310QosPortEgressTagRemarkingMapEntry 1 }

gs2310QosTagRemarkingQoSClass OBJECT-TYPE
   SYNTAX      INTEGER {
                        class0(1),
                        class1(2),
                        class2(3),
                        class3(4),
                        class4(5),
                        class5(6),
                        class6(7),
                        class7(8)
                        }
   MAX-ACCESS  not-accessible
   STATUS      current
   DESCRIPTION
       " range: 1-8,
         QoS Class0: 1, QoS Class1: 2...  "
   ::= { gs2310QosPortEgressTagRemarkingMapEntry 2 }

gs2310QosTagRemarkingDPLevel OBJECT-TYPE
   SYNTAX      INTEGER { level0(1), level1(2) }
   MAX-ACCESS  not-accessible
   STATUS      current
   DESCRIPTION
       " range: 1-2,
         DP Level0: 1, DP Level1: 2. "
   ::= { gs2310QosPortEgressTagRemarkingMapEntry 3 }

gs2310QosTagRemarkingPCP OBJECT-TYPE
   SYNTAX      Integer32 (0..7)
   MAX-ACCESS  read-write
   STATUS      current
   DESCRIPTION
       " range: 0-7.  "
   ::= { gs2310QosPortEgressTagRemarkingMapEntry 4 }

gs2310QosTagRemarkingDEI OBJECT-TYPE
   SYNTAX      INTEGER (0|1)
   MAX-ACCESS  read-write
   STATUS      current
   DESCRIPTION
       " range: 0-1.  "
   ::= { gs2310QosPortEgressTagRemarkingMapEntry 5 }


gs2310QosPortDSCPTable OBJECT-TYPE
   SYNTAX      SEQUENCE OF GS2310QosPortDSCPEntry
   MAX-ACCESS  not-accessible
   STATUS      current
   DESCRIPTION
       " configure the basic QoS Port DSCP Configuration settings for all switch ports. "
   ::= { gs2310Qos  5 }

gs2310QosPortDSCPEntry OBJECT-TYPE
   SYNTAX      GS2310QosPortDSCPEntry
   MAX-ACCESS  not-accessible
   STATUS      current
   DESCRIPTION
       ""
   INDEX    { gs2310QosPortDSCPPort  }
   ::= { gs2310QosPortDSCPTable 1 }

GS2310QosPortDSCPEntry ::= SEQUENCE {
   gs2310QosPortDSCPPort	                Integer32,
   gs2310QosPortDSCPIngressTranslate       INTEGER,
   gs2310QosPortDSCPIngressClassify	    INTEGER,
   gs2310QosPortDSCPEgressRewrite	        INTEGER
}

gs2310QosPortDSCPPort OBJECT-TYPE
   SYNTAX      Integer32 (1..4095)
   MAX-ACCESS  not-accessible
   STATUS      current
   DESCRIPTION
       " port, range : 1 - port number. "
   ::= { gs2310QosPortDSCPEntry 1 }

gs2310QosPortDSCPIngressTranslate OBJECT-TYPE
   SYNTAX      INTEGER { disable(0), enable(1) }
   MAX-ACCESS  read-write
   STATUS      current
   DESCRIPTION
      " Configure DSCP ingress translation mode.
        0: disable,
        1: enable,
        default: disable. "
   ::= { gs2310QosPortDSCPEntry 2 }

gs2310QosPortDSCPIngressClassify OBJECT-TYPE
   SYNTAX      INTEGER(0..3)
   MAX-ACCESS  read-write
   STATUS      current
   DESCRIPTION
       " Classification for a port have 4 different values.
         range: 0-3,
         0: disable,No Ingress DSCP Classification.
         1: DSCP=0,Classify if incoming (or translated if enabled) DSCP is 0.
         2: Selected,Classify only selected DSCP for which classification is
         enabled as specified in DSCP Translation window for the specific DSCP.
         3: All,Classify all DSCP.
         default: disable. "
   ::= { gs2310QosPortDSCPEntry 3 }

gs2310QosPortDSCPEgressRewrite OBJECT-TYPE
   SYNTAX      INTEGER(0..3)
   MAX-ACCESS  read-write
   STATUS      current
   DESCRIPTION
       " Configure the port egress rewriting mode.
         range: 0-2
         0: Disable,No Egress rewrite.
         1: Enable, Rewrite enabled without remapping.
         2: Remap DP Unaware , DSCP from analyzer is remapped and frame is
         remarked with remapped DSCP value. The remapped DSCP value is always
         taken from the DSCP Translation->Egress Remap DP0 table.
         3: Remap DP Aware: DSCP from analyzer is remapped and frame is remarked
          with remapped DSCP value. Depending on the DP level of the frame, the
          remapped DSCP value is either taken from the DSCP Translation->Egress
          Remap DP0 table or from the DSCP Translation->Egress Remap DP1 table.
         default: disable. "
   ::= { gs2310QosPortDSCPEntry 4 }


gs2310QosDSCPTable OBJECT-TYPE
   SYNTAX      SEQUENCE OF GS2310QosDSCPEntry
   MAX-ACCESS  not-accessible
   STATUS      current
   DESCRIPTION
       " configure the basic QoS DSCP based QoS Ingress Classification settings for all switches. "
   ::= { gs2310Qos  6 }

gs2310QosDSCPEntry OBJECT-TYPE
   SYNTAX      GS2310QosDSCPEntry
   MAX-ACCESS  not-accessible
   STATUS      current
   DESCRIPTION
       ""
   INDEX    { gs2310QosDSCPList  }
   ::= { gs2310QosDSCPTable 1 }

GS2310QosDSCPEntry ::= SEQUENCE {
   gs2310QosDSCPList       Integer32,
   gs2310QosDSCP           DisplayString,
   gs2310QosDSCPTrust      INTEGER,
   gs2310QosDSCPQosClass	  Integer32,
   gs2310QosDSCPDPL	      INTEGER
}

gs2310QosDSCPList OBJECT-TYPE
   SYNTAX      Integer32(1..64)
   MAX-ACCESS  not-accessible
   STATUS      current
   DESCRIPTION
      " DSCP mapping table index(1-64). "
   ::= { gs2310QosDSCPEntry 1 }

gs2310QosDSCP OBJECT-TYPE
   SYNTAX      DisplayString
   MAX-ACCESS  read-only
   STATUS      current
   DESCRIPTION
      "Maximum number of supported DSCP values are 64."
   ::= { gs2310QosDSCPEntry 2 }

gs2310QosDSCPTrust OBJECT-TYPE
   SYNTAX      INTEGER { disable(0), enable(1) }
   MAX-ACCESS  read-write
   STATUS      current
   DESCRIPTION
      " Controls whether a specific DSCP value is trusted. Only frames with
      trusted DSCP values are mapped to a specific QoS class and Drop Precedence
       Level. Frames with untrusted DSCP values are treated as a non-IP frame.
        0: disable,
        1: enable,
        default: disable. "
   ::= { gs2310QosDSCPEntry 3 }

gs2310QosDSCPQosClass OBJECT-TYPE
   SYNTAX      Integer32(0..7)
   MAX-ACCESS  read-write
   STATUS      current
   DESCRIPTION
      " QoS class.
        range: 0-7,
        default: 0. "
   ::= { gs2310QosDSCPEntry 4 }

gs2310QosDSCPDPL OBJECT-TYPE
   SYNTAX      INTEGER(0|1)
   MAX-ACCESS  read-write
   STATUS      current
   DESCRIPTION
      " Drop Precedence Level.
        range: 0-1,
        default: disable. "
   ::= { gs2310QosDSCPEntry 5 }

gs2310QosDSCPTranslationTable OBJECT-TYPE
   SYNTAX      SEQUENCE OF GS2310QosDSCPTranslationEntry
   MAX-ACCESS  not-accessible
   STATUS      current
   DESCRIPTION
       "  configure the basic QoS DSCP Translation settings for all switches. "
   ::= { gs2310Qos  7 }

gs2310QosDSCPTranslationEntry OBJECT-TYPE
   SYNTAX      GS2310QosDSCPTranslationEntry
   MAX-ACCESS  not-accessible
   STATUS      current
   DESCRIPTION
       ""
   INDEX    { gs2310QosDSCPTranslationList  }
   ::= { gs2310QosDSCPTranslationTable 1 }

GS2310QosDSCPTranslationEntry ::= SEQUENCE {
   gs2310QosDSCPTranslationList                 Integer32,
   gs2310QosDSCPTranslationDSCPBasedId          DisplayString,
   gs2310QosDSCPTranslationIngressTranslate     Integer32,
   gs2310QosDSCPTranslationIngressClassify      INTEGER,
   gs2310QosDSCPTranslationEgressRemapDP0       Integer32,
   gs2310QosDSCPTranslationEgressRemapDP1       Integer32
}

gs2310QosDSCPTranslationList OBJECT-TYPE
   SYNTAX      Integer32(1..64)
   MAX-ACCESS  not-accessible
   STATUS      current
   DESCRIPTION
      " DSCP translation table index(1-64). "
   ::= { gs2310QosDSCPTranslationEntry 1 }

gs2310QosDSCPTranslationDSCPBasedId OBJECT-TYPE
   SYNTAX      DisplayString
   MAX-ACCESS  read-write
   STATUS      current
   DESCRIPTION
      " Configure global ingress DSCP translation table. "
   ::= { gs2310QosDSCPTranslationEntry 2 }

gs2310QosDSCPTranslationIngressTranslate OBJECT-TYPE
   SYNTAX      Integer32(0..63)
   MAX-ACCESS  read-write
   STATUS      current
   DESCRIPTION
      " DSCP at Ingress side can be translated to any of DSCP values.
        range: 0-63,
        default: 0. "
   ::= { gs2310QosDSCPTranslationEntry 3 }

gs2310QosDSCPTranslationIngressClassify OBJECT-TYPE
   SYNTAX      INTEGER { disable(0), enable(1) }
   MAX-ACCESS  read-write
   STATUS      current
   DESCRIPTION
      " Configure DSCP ingress classification.
        0: disable,
        1: enable,
        default: disable. "
   ::= { gs2310QosDSCPTranslationEntry 4 }

gs2310QosDSCPTranslationEgressRemapDP0 OBJECT-TYPE
   SYNTAX      Integer32(0..63)
   MAX-ACCESS  read-write
   STATUS      current
   DESCRIPTION
      "Controls the remapping for frames with DP level 0.
      Select the DSCP value from select menu to which you want to remap.
        range: 0-63,
        default: 0. "
   ::= { gs2310QosDSCPTranslationEntry 5 }

gs2310QosDSCPTranslationEgressRemapDP1 OBJECT-TYPE
   SYNTAX      Integer32(0..63)
   MAX-ACCESS  read-write
   STATUS      current
   DESCRIPTION
      "Controls the remapping for frames with DP level 1.
      Select the DSCP value from select menu to which you want to remap.
        range: 0-63,
        default: 0. "
   ::= { gs2310QosDSCPTranslationEntry 6 }


gs2310QosDSCPClassificationTable OBJECT-TYPE
   SYNTAX      SEQUENCE OF GS2310QosDSCPClassificationEntry
   MAX-ACCESS  not-accessible
   STATUS      current
   DESCRIPTION
       "   configure the mapping of QoS class  to DSCP value. "
   ::= { gs2310Qos  8 }

gs2310QosDSCPClassificationEntry OBJECT-TYPE
   SYNTAX      GS2310QosDSCPClassificationEntry
   MAX-ACCESS  not-accessible
   STATUS      current
   DESCRIPTION
       ""
   INDEX    { gs2310QosDSCPClassificationQoSClass, gs2310QosDSCPClassificationDPL }
   ::= { gs2310QosDSCPClassificationTable 1 }

GS2310QosDSCPClassificationEntry ::= SEQUENCE {
   gs2310QosDSCPClassificationQoSClass		INTEGER,
   gs2310QosDSCPClassificationDPL			INTEGER,
   gs2310QosDSCPClassificationDSCP			Integer32
}

gs2310QosDSCPClassificationQoSClass OBJECT-TYPE
   SYNTAX      INTEGER {
                        class0(1),
                        class1(2),
                        class2(3),
                        class3(4),
                        class4(5),
                        class5(6),
                        class6(7),
                        class7(8)
                        }
   MAX-ACCESS  not-accessible
   STATUS      current
   DESCRIPTION
      " Actual QoS class. Index 1~8 mean Qos Class 0~7."
   ::= { gs2310QosDSCPClassificationEntry 1 }

gs2310QosDSCPClassificationDPL OBJECT-TYPE
   SYNTAX      INTEGER(1|2)
   MAX-ACCESS  not-accessible
   STATUS      current
   DESCRIPTION
      " DPL. Index 1~2 mean DPL 0~1."
   ::= { gs2310QosDSCPClassificationEntry 2 }

gs2310QosDSCPClassificationDSCP OBJECT-TYPE
   SYNTAX      Integer32(0..63)
   MAX-ACCESS  read-write
   STATUS      current
   DESCRIPTION
      " Select the classified DSCP value.
        range: 0-63,
        default: 0. "
   ::= { gs2310QosDSCPClassificationEntry 3 }

gs2310QosControlList                                         OBJECT IDENTIFIER ::= { gs2310Qos 9 }

gs2310QosQceCreate OBJECT-TYPE
   SYNTAX       INTEGER { none(0), create(1) }
   MAX-ACCESS   read-write
   STATUS       current
   DESCRIPTION
       "default: 0
        0 : None  (read only)
        1 : Create an Qos entry"
   ::= { gs2310QosControlList 1 }

gs2310QosQceTable OBJECT-TYPE
   SYNTAX      SEQUENCE OF GS2310QosQceEntry
   MAX-ACCESS  not-accessible
   STATUS      current
   DESCRIPTION
       " Create Qos QCE entry. "
   ::= { gs2310QosControlList 2 }

gs2310QosQceEntry OBJECT-TYPE
   SYNTAX      GS2310QosQceEntry
   MAX-ACCESS  not-accessible
   STATUS      current
   DESCRIPTION
       ""
   INDEX    { gs2310QosQceIndex  }
   ::= { gs2310QosQceTable 1 }

GS2310QosQceEntry ::= SEQUENCE {
   gs2310QosQceIndex                Integer32,
   gs2310QosQceID                   Integer32,
   gs2310QosQceNextID               Integer32,
   gs2310QosQcePortMembers          DisplayString,

   gs2310QosQceTag                  DisplayString,
   gs2310QosQceVID                  DisplayString,
   gs2310QosPCP                     DisplayString,
   gs2310QosDEI                     DisplayString,
   gs2310QosSMAC                    DisplayString,
   gs2310QosDMACType                DisplayString,
   gs2310QosFrameType               INTEGER,

   gs2310QosMacEtherType            DisplayString,

   gs2310QosLLCSSAPAddr             DisplayString,
   gs2310QosLLCDSAPAddr             DisplayString,
   gs2310QosLLCControl              DisplayString,

   gs2310QosSNAPPID                 DisplayString,

   gs2310QosIpv4Protocol            DisplayString,
   gs2310QosIpv4ProtocolValue       Integer32,
   gs2310QosIpv4ProtocolUDPSport    DisplayString,
   gs2310QosIpv4ProtocolUDPDport    DisplayString,
   gs2310QosIpv4ProtocolTCPSport    DisplayString,
   gs2310QosIpv4ProtocolTCPDport    DisplayString,
   gs2310QosIpv4Ip                  DisplayString,
   gs2310QosIpv4Mask                DisplayString,
   gs2310QosIpv4IPFragment          INTEGER,
   gs2310QosIpv4DSCP                DisplayString,


   gs2310QosIpv6Protocol            DisplayString,
   gs2310QosIpv6ProtocolValue       Integer32,
   gs2310QosIpv6ProtocolUDPSport    DisplayString,
   gs2310QosIpv6ProtocolUDPDport    DisplayString,
   gs2310QosIpv6ProtocolTCPSport    DisplayString,
   gs2310QosIpv6ProtocolTCPDport    DisplayString,
   gs2310QosIpv6Ip                  DisplayString,
   gs2310QosIpv6Mask                DisplayString,
   gs2310QosIpv6DSCP                DisplayString,

   gs2310QosActionClass             Integer32,
   gs2310QosActionDPL               INTEGER,
   gs2310QosActionDSCP              Integer32,
   gs2310QosQceRowStatus            INTEGER
}

gs2310QosQceIndex OBJECT-TYPE
   SYNTAX      Integer32(1..256)
   MAX-ACCESS  not-accessible
   STATUS      current
   DESCRIPTION
       " "
   ::= { gs2310QosQceEntry 1 }

gs2310QosQceID OBJECT-TYPE
   SYNTAX      Integer32(1..256)
   MAX-ACCESS  read-write
   STATUS      current
   DESCRIPTION
       " If the QCE ID is specified and an entry with this QCE ID
         already exists, the QCE will be modified. Otherwise, a
         new QCE will be added.
         range : 1 - 256. "
   ::= { gs2310QosQceEntry 2 }

gs2310QosQceNextID OBJECT-TYPE
   SYNTAX      Integer32(1..256)
   MAX-ACCESS  read-write
   STATUS      current
   DESCRIPTION
       " If the next QCE ID is non zero, the QCE will be placed
         before this QCE in the list. If the next QCE ID is zero,
         the QCE will be placed last in the list.
         range : 1 - 256. "
   ::= { gs2310QosQceEntry 3 }

gs2310QosQcePortMembers OBJECT-TYPE
   SYNTAX      DisplayString
   MAX-ACCESS  read-write
   STATUS      current
   DESCRIPTION
       " Indicates the ingress port of the QCE. Possible values are:
         All: The QCE will match all ingress port.
         Port: The QCE will match a specific ingress port.Format: 1,3-6."
   ::= { gs2310QosQceEntry 4 }

gs2310QosQceTag OBJECT-TYPE
   SYNTAX      DisplayString
   MAX-ACCESS  read-write
   STATUS      current
   DESCRIPTION
       " Value of Tag field can be 'Any', 'Untag' or 'Tag'. "
   ::= { gs2310QosQceEntry 5 }

gs2310QosQceVID OBJECT-TYPE
   SYNTAX      DisplayString
   MAX-ACCESS  read-write
   STATUS      current
   DESCRIPTION
       " Valid value of VLAN ID can be any value in 'Specific 1~4094' or 'range 1-4094' or 'Any'. "
   ::= { gs2310QosQceEntry 6 }

gs2310QosPCP OBJECT-TYPE
   SYNTAX      DisplayString
   MAX-ACCESS  read-write
   STATUS      current
   DESCRIPTION
       " Priority Code Point: Valid value PCP are specific(0, 1, 2, 3, 4, 5, 6, 7)
         or range(0-1, 2-3, 4-5, 6-7, 0-3, 4-7) or 'Any'. "
   ::= { gs2310QosQceEntry 7 }

gs2310QosDEI OBJECT-TYPE
   SYNTAX      DisplayString
   MAX-ACCESS  read-write
   STATUS      current
   DESCRIPTION
       " Drop Eligible Indicator: Valid value of DEI can be any of values between 0, 1 or 'Any'. "
   ::= { gs2310QosQceEntry 8 }

gs2310QosSMAC  OBJECT-TYPE
   SYNTAX      DisplayString
   MAX-ACCESS  read-write
   STATUS      current
   DESCRIPTION
       "  Source MAC address: 24 MS bits OUI(00-00-00 ~ FF-FF-FF) or 'Any'. "
   ::= { gs2310QosQceEntry 9 }

gs2310QosDMACType OBJECT-TYPE
   SYNTAX      DisplayString
   MAX-ACCESS  read-write
   STATUS      current
   DESCRIPTION
       " Destination MAC type: possible values are 'UC'(unicast), 'MC'(multicast), 'BC'(broadcast) or 'Any'. "
   ::= { gs2310QosQceEntry 10 }

gs2310QosFrameType OBJECT-TYPE
   SYNTAX      INTEGER {
                        any(1),
                        ethernet(2),
                        llc(3),
                        snap(4),
                        ipv4(5),
                        ipv6(6)
                        }
   MAX-ACCESS  read-write
   STATUS      current
   DESCRIPTION
       " Frame Type can have any of the following values:
         1: Any,
         2: Ethernet,
         3: LLC,
         4: SNAP,
         5: IPv4,
         6: IPv6. "
   ::= { gs2310QosQceEntry 11 }

gs2310QosMacEtherType OBJECT-TYPE
   SYNTAX      DisplayString
   MAX-ACCESS  read-write
   STATUS      current
   DESCRIPTION
       " Valid ethernet type can have a value within 0x600-0xFFFF or 'Any' ,
         but excluding 0x800(IPv4) and 0x86DD(IPv6),
         range: 0000-FFFF,
         default: Any."
   ::= { gs2310QosQceEntry 12 }

gs2310QosLLCSSAPAddr OBJECT-TYPE
   SYNTAX      DisplayString
   MAX-ACCESS  read-write
   STATUS      current
   DESCRIPTION
       " Valid SSAP(Source Service Access Point) can vary from 0x00 to 0xFF or 'Any',
         range: 00-FF,
         default: Any. "
   ::= { gs2310QosQceEntry 13 }

gs2310QosLLCDSAPAddr OBJECT-TYPE
   SYNTAX      DisplayString
   MAX-ACCESS  read-write
   STATUS      current
   DESCRIPTION
       " Valid DSAP(Destination Service Access Point) can vary from 0x00 to 0xFF or 'Any',
         range: 00-FF,
         default: Any. "
   ::= { gs2310QosQceEntry 14 }

gs2310QosLLCControl OBJECT-TYPE
   SYNTAX      DisplayString
   MAX-ACCESS  read-write
   STATUS      current
   DESCRIPTION
       " Valid Control field can vary from 0x00 to 0xFF or 'Any',
         range: 00-FF,
         default: Any. "
   ::= { gs2310QosQceEntry 15 }

gs2310QosSNAPPID OBJECT-TYPE
   SYNTAX      DisplayString
   MAX-ACCESS  read-write
   STATUS      current
   DESCRIPTION
       " Valid PID(a.k.a ethernet type) can have value within 0x00-0xFFFF or 'Any',
         range: 0000-FFFF,
         default: Any. "
   ::= { gs2310QosQceEntry 16 }

gs2310QosIpv4Protocol OBJECT-TYPE
   SYNTAX      DisplayString
   MAX-ACCESS  read-write
   STATUS      current
   DESCRIPTION
       " IP protocol number: (Other, TCP or UDP) or 'Any'. "
   ::= { gs2310QosQceEntry 17 }

gs2310QosIpv4ProtocolValue  OBJECT-TYPE
   SYNTAX      Integer32(0..255)
   MAX-ACCESS  read-write
   STATUS      current
   DESCRIPTION
       " Ipv4 Protocol is Other.
         range: 0-255
         default: 0. "
   ::= { gs2310QosQceEntry 18 }

gs2310QosIpv4ProtocolUDPSport OBJECT-TYPE
   SYNTAX      DisplayString
   MAX-ACCESS  read-write
   STATUS      current
   DESCRIPTION
       " Source  TCP/UDP port:(0-65535) or 'Any',
         specific or port range applicable for IP protocol UDP/TCP. "
   ::= { gs2310QosQceEntry 19 }

gs2310QosIpv4ProtocolUDPDport OBJECT-TYPE
   SYNTAX      DisplayString
   MAX-ACCESS  read-write
   STATUS      current
   DESCRIPTION
       " Destination TCP/UDP port:(0-65535) or 'Any',
         specific or port range applicable for IP protocol UDP/TCP. "
   ::= { gs2310QosQceEntry 20 }

gs2310QosIpv4ProtocolTCPSport OBJECT-TYPE
   SYNTAX      DisplayString
   MAX-ACCESS  read-write
   STATUS      current
   DESCRIPTION
       " Source TCP/UDP port:(0-65535) or 'Any',
         specific or port range applicable for IP protocol UDP/TCP. "
   ::= { gs2310QosQceEntry 21 }

gs2310QosIpv4ProtocolTCPDport OBJECT-TYPE
   SYNTAX      DisplayString
   MAX-ACCESS  read-write
   STATUS      current
   DESCRIPTION
       " Destination TCP/UDP port:(0-65535) or 'Any',
         specific or port range applicable for IP protocol UDP/TCP. "
   ::= { gs2310QosQceEntry 22 }

gs2310QosIpv4Ip OBJECT-TYPE
   SYNTAX      DisplayString
   MAX-ACCESS  read-write
   STATUS      current
   DESCRIPTION
       "  Specific Source IP address in value format or value 0.0.0.0 is 'Any'.
          if Ipv4 Mask value 0.0.0.0 is 'Any' ,IP address value also is 'Any'.
          (x.y.z.w),x=0 unless y.z.w also 0,x not is 127 or greater than 223.
          If a port is configured to match on DMAC/DIP, this field is the
          Destination IP address."
   ::= { gs2310QosQceEntry 23 }

gs2310QosIpv4Mask OBJECT-TYPE
   SYNTAX      DisplayString
   MAX-ACCESS  read-write
   STATUS      current
   DESCRIPTION
       " Specific IP address in mask format or value 0.0.0.0 is 'Any'. "
   ::= { gs2310QosQceEntry 24 }

gs2310QosIpv4IPFragment OBJECT-TYPE
   SYNTAX      INTEGER { any(0), no(1), yes(2) }
   MAX-ACCESS  read-write
   STATUS      current
   DESCRIPTION
       " IPv4 frame fragmented option:
         2: yes,
         1: no,
         0: any. "
   ::= { gs2310QosQceEntry 25 }

gs2310QosIpv4DSCP OBJECT-TYPE
   SYNTAX      DisplayString
   MAX-ACCESS  read-write
   STATUS      current
   DESCRIPTION
       " Diffserv Code Point value (DSCP): It can be a specific value,
         range of values or 'Any'. DSCP values are in the range 0-63. "
   ::= { gs2310QosQceEntry 26 }

gs2310QosIpv6Protocol OBJECT-TYPE
   SYNTAX      DisplayString
   MAX-ACCESS  read-write
   STATUS      current
   DESCRIPTION
       " IP protocol number: (Other, TCP or UDP) or 'Any'. "
   ::= { gs2310QosQceEntry 27 }

gs2310QosIpv6ProtocolValue OBJECT-TYPE
   SYNTAX      Integer32(0..255)
   MAX-ACCESS  read-write
   STATUS      current
   DESCRIPTION
       " when IPv6 protocol is Other ,
         range: 0-255. "
   ::= { gs2310QosQceEntry 28 }

gs2310QosIpv6ProtocolUDPSport OBJECT-TYPE
   SYNTAX      DisplayString
   MAX-ACCESS  read-write
   STATUS      current
   DESCRIPTION
       " Source TCP/UDP port:(0-65535) or 'Any',
         specific or port range applicable for IP protocol UDP/TCP. "
   ::= { gs2310QosQceEntry 29 }

gs2310QosIpv6ProtocolUDPDport OBJECT-TYPE
   SYNTAX      DisplayString
   MAX-ACCESS  read-write
   STATUS      current
   DESCRIPTION
       " Destination TCP/UDP port:(0-65535) or 'Any',
         specific or port range applicable for IP protocol UDP/TCP. "
   ::= { gs2310QosQceEntry 30 }

gs2310QosIpv6ProtocolTCPSport OBJECT-TYPE
   SYNTAX      DisplayString
   MAX-ACCESS  read-write
   STATUS      current
   DESCRIPTION
       " Source TCP/UDP port:(0-65535) or 'Any',
         specific or port range applicable for IP protocol UDP/TCP. "
   ::= { gs2310QosQceEntry 31 }


gs2310QosIpv6ProtocolTCPDport OBJECT-TYPE
   SYNTAX      DisplayString
   MAX-ACCESS  read-write
   STATUS      current
   DESCRIPTION
       " Destination TCP/UDP port:(0-65535) or 'Any',
         specific or port range applicable for IP protocol UDP/TCP. "
   ::= { gs2310QosQceEntry 32 }

gs2310QosIpv6Ip OBJECT-TYPE
   SYNTAX      DisplayString
   MAX-ACCESS  read-write
   STATUS      current
   DESCRIPTION
       " IPv6 source address: (a.b.c.d) or value 0.0.0.0 is 'Any', 32 LS bits.
         If a port is configured to match on DMAC/DIP, this field is the
         Destination IP address."
   ::= { gs2310QosQceEntry 33 }

gs2310QosIpv6Mask OBJECT-TYPE
   SYNTAX      DisplayString
   MAX-ACCESS  read-write
   STATUS      current
   DESCRIPTION
       " IPv6 mask address: (a.b.c.d) or value 0.0.0.0 is 'Any', 32 LS bits. "
   ::= { gs2310QosQceEntry 34 }

gs2310QosIpv6DSCP OBJECT-TYPE
   SYNTAX      DisplayString
   MAX-ACCESS  read-write
   STATUS      current
   DESCRIPTION
       " Diffserv Code Point value (DSCP): It can be a specific value,
         range of values or 'Any'. DSCP values are in the range 0-63 including BE,
         CS1-CS7, EF or AF11-AF43. "
   ::= { gs2310QosQceEntry 35 }

gs2310QosActionClass  OBJECT-TYPE
   SYNTAX      Integer32(0..8)
   MAX-ACCESS  read-write
   STATUS      current
   DESCRIPTION
       " QoS class: (0-7) or 8: Default."
   ::= { gs2310QosQceEntry 36 }

gs2310QosActionDPL OBJECT-TYPE
   SYNTAX      INTEGER (0..4)
   MAX-ACCESS  read-write
   STATUS      current
   DESCRIPTION
       " DP Valid Drop Precedence Level can be (0-3) or 4: Default. "
   ::= { gs2310QosQceEntry 37 }

gs2310QosActionDSCP OBJECT-TYPE
   SYNTAX      Integer32(0..64)
   MAX-ACCESS  read-write
   STATUS      current
   DESCRIPTION
       " Valid DSCP value can be (0-63, BE, CS1-CS7, EF or AF11-AF43) or 64: Default. "
   ::= { gs2310QosQceEntry 38 }

gs2310QosQceRowStatus OBJECT-TYPE
   SYNTAX      INTEGER { active(1), notInservice(2), destroy(4) }
   MAX-ACCESS  read-write
   STATUS      current
   DESCRIPTION
       "  1: active2: notInservice 4: destroy"
   ::= { gs2310QosQceEntry 39 }

gs2310QosQceMoveID OBJECT-TYPE
   SYNTAX       Integer32(0..256)
   MAX-ACCESS   read-write
   STATUS       current
   DESCRIPTION
       " Move Qos,
         default: 0
         Qos ID must be exist.
         range : 0 - 256."
   ::= { gs2310QosControlList 3 }

gs2310QosQceMoveNextID OBJECT-TYPE
   SYNTAX       Integer32(0..256)
   MAX-ACCESS   read-write
   STATUS       current
   DESCRIPTION
       " Move Qos,
         default: 0
         If the next Qos ID is non zero, the Qos will be placed before this Qos in the list.
         If the next Qos ID is zero,the Qos will be placed last in the list.
         range : 0 - 256. "
   ::= { gs2310QosControlList 4 }


gs2310QosQCLStatusTable OBJECT-TYPE
   SYNTAX      SEQUENCE OF GS2310QosQCLStatusEntry
   MAX-ACCESS  not-accessible
   STATUS      current
   DESCRIPTION
       "  configure the basic QoS DSCP Translation settings for all switches. "
   ::= { gs2310Qos  10 }

gs2310QosQCLStatusEntry OBJECT-TYPE
   SYNTAX      GS2310QosQCLStatusEntry
   MAX-ACCESS  not-accessible
   STATUS      current
   DESCRIPTION
       ""
   INDEX    { gs2310QosQCLStatusList  }
   ::= { gs2310QosQCLStatusTable 1 }

GS2310QosQCLStatusEntry ::= SEQUENCE {
   gs2310QosQCLStatusList               Integer32,
   gs2310QosQCLStatusUser               DisplayString,
   gs2310QosQCLStatusQCEId              DisplayString,
   gs2310QosQCLStatusFrameType          DisplayString,
   gs2310QosQCLStatusPortlist           DisplayString,
   gs2310QosQCLStatusActionClass	       DisplayString,
   gs2310QosQCLStatusActionDPL	       DisplayString,
   gs2310QosQCLStatusActionDSCP	       DisplayString,
   gs2310QosQCLStatusActionConflict     DisplayString
}

gs2310QosQCLStatusList OBJECT-TYPE
   SYNTAX      Integer32(1..4095)
   MAX-ACCESS  not-accessible
   STATUS      current
   DESCRIPTION
       " QCL table index. "
   ::= { gs2310QosQCLStatusEntry 1}

gs2310QosQCLStatusUser OBJECT-TYPE
   SYNTAX      DisplayString
   MAX-ACCESS  read-only
   STATUS      current
   DESCRIPTION
       " Indicates the QCL user. "
   ::= { gs2310QosQCLStatusEntry 2 }

gs2310QosQCLStatusQCEId OBJECT-TYPE
   SYNTAX      DisplayString
   MAX-ACCESS  read-only
   STATUS      current
   DESCRIPTION
      " Indicates the index of QCE. "
   ::= { gs2310QosQCLStatusEntry 3}

gs2310QosQCLStatusFrameType OBJECT-TYPE
   SYNTAX      DisplayString
   MAX-ACCESS  read-only
   STATUS      current
   DESCRIPTION
       " Indicates the type of frame to look for incomming frames.
       Any: The QCE will match all frame type.
       Ethernet: Only Ethernet frames (with Ether Type 0x600-0xFFFF) are allowed.
       LLC: Only (LLC) frames are allowed.
       SNAP: Only (SNAP) frames are allowed.
       IPv4: The QCE will match only IPV4 frames.
       IPv6: The QCE will match only IPV6 frames."
   ::= { gs2310QosQCLStatusEntry 4}

gs2310QosQCLStatusPortlist OBJECT-TYPE
   SYNTAX      DisplayString
   MAX-ACCESS  read-only
   STATUS      current
   DESCRIPTION
       " Indicates the list of ports configured with the QCE. "
   ::= { gs2310QosQCLStatusEntry 5}

gs2310QosQCLStatusActionClass OBJECT-TYPE
   SYNTAX      DisplayString
   MAX-ACCESS  read-only
   STATUS      current
   DESCRIPTION
       " Classified QoS class; if a frame matches the QCE it will be put in the
       queue. "
   ::= { gs2310QosQCLStatusEntry 6}

gs2310QosQCLStatusActionDPL OBJECT-TYPE
   SYNTAX      DisplayString
   MAX-ACCESS  read-only
   STATUS      current
   DESCRIPTION
       " Drop Precedence Level; if a frame matches the QCE then DP level will
       set to value displayed under DPL column."
   ::= { gs2310QosQCLStatusEntry 7}

gs2310QosQCLStatusActionDSCP OBJECT-TYPE
   SYNTAX      DisplayString
   MAX-ACCESS  read-only
   STATUS      current
   DESCRIPTION
       " If a frame matches the QCE then DSCP will be classified with the value
       displayed under DSCP column."
   ::= { gs2310QosQCLStatusEntry 8}

gs2310QosQCLStatusActionConflict OBJECT-TYPE
   SYNTAX      DisplayString
   MAX-ACCESS  read-only
   STATUS      current
   DESCRIPTION
       " If a frame matches the QCE then DSCP will be classified with the value
        displayed under DSCP column. "
   ::= { gs2310QosQCLStatusEntry 9}


gs2310QosStormControl                                           OBJECT IDENTIFIER ::= { gs2310Qos 11 }

gs2310QoSStormControlUC OBJECT-TYPE
   SYNTAX      INTEGER { disable(0), enable(1) }
   MAX-ACCESS  read-write
   STATUS      current
   DESCRIPTION
       "Enable or disable the storm control status for the Unicast frame type.
       default:  0
        0: disable
        1: enable"
   ::= { gs2310QosStormControl 2 }

gs2310QoSStormControlUCRate OBJECT-TYPE
   SYNTAX      DisplayString
   MAX-ACCESS  read-write
   STATUS      current
   DESCRIPTION
       "The rate unit is packets per second (pps). Valid values are: 1, 2, 4, 8,
        16, 32, 64, 128, 256, 512, 1K, 2K, 4K, 8K, 16K, 32K, 64K, 128K, 256K,
        512K or 1024K."
   ::= { gs2310QosStormControl 3 }

gs2310QoSStormControlMC OBJECT-TYPE
   SYNTAX      INTEGER { disable(0), enable(1) }
   MAX-ACCESS  read-write
   STATUS      current
   DESCRIPTION
       "Enable or disable the storm control status for the Multicast frame type.
       default:  0
        0: disable
        1: enable"
   ::= { gs2310QosStormControl 4 }

gs2310QoSStormControlMCRate OBJECT-TYPE
   SYNTAX      DisplayString
   MAX-ACCESS  read-write
   STATUS      current
   DESCRIPTION
       "The rate unit is packets per second (pps). Valid values are: 1, 2, 4, 8,
        16, 32, 64, 128, 256, 512, 1K, 2K, 4K, 8K, 16K, 32K, 64K, 128K, 256K,
        512K or 1024K."
   ::= { gs2310QosStormControl 5 }

gs2310QoSStormControlBC OBJECT-TYPE
   SYNTAX      INTEGER { disable(0), enable(1) }
   MAX-ACCESS  read-write
   STATUS      current
   DESCRIPTION
       "Enable or disable the storm control status for the Broadcast frame type.
       default:  0
        0: disable
        1: enable"
   ::= { gs2310QosStormControl 6 }

gs2310QoSStormControlBCRate OBJECT-TYPE
   SYNTAX      DisplayString
   MAX-ACCESS  read-write
   STATUS      current
   DESCRIPTION
       "The rate unit is packets per second (pps). Valid values are: 1, 2, 4, 8,
        16, 32, 64, 128, 256, 512, 1K, 2K, 4K, 8K, 16K, 32K, 64K, 128K, 256K,
        512K or 1024K."
   ::= { gs2310QosStormControl 7 }


gs2310Vlan                                                           OBJECT IDENTIFIER ::= { gs2310Configuration 15 }

gs2310VlanPorts                                                      OBJECT IDENTIFIER ::= { gs2310Vlan 1 }

gs2310VlanPortsTPIDforCustomSport  OBJECT-TYPE
   SYNTAX      OCTET STRING(SIZE(2))
   MAX-ACCESS  read-write
   STATUS      current
   DESCRIPTION
       "Configure the TPID used for Custom S-ports. This is a global setting for
       all the Custom S-ports.
       range: 0x0600-0xffff,
       default: 0x88a8. "
   ::= { gs2310VlanPorts 1 }

gs2310VlanPortsTable OBJECT-TYPE
   SYNTAX      SEQUENCE OF GS2310VlanPortsEntry
   MAX-ACCESS  not-accessible
   STATUS      current
   DESCRIPTION
       " Configure Vlan ports Configuration mode. "
   ::= { gs2310VlanPorts 2 }

gs2310VlanPortsEntry OBJECT-TYPE
   SYNTAX      GS2310VlanPortsEntry
   MAX-ACCESS  not-accessible
   STATUS      current
   DESCRIPTION
       ""
   INDEX    { gs2310VlanPortsPort  }
   ::= { gs2310VlanPortsTable 1 }

GS2310VlanPortsEntry ::= SEQUENCE {
   gs2310VlanPortsPort	         Integer32,
   gs2310VlanPortsPVID     Integer32,
   gs2310VlanPortsFrameType      INTEGER,
   gs2310VlanPortsIngressFilter  INTEGER,
   gs2310VlanPortsEgressRule     INTEGER,
   gs2310VlanPortsPortType       INTEGER
}

gs2310VlanPortsPort OBJECT-TYPE
   SYNTAX      Integer32(1..4094)
   MAX-ACCESS  not-accessible
   STATUS      current
   DESCRIPTION
       " port, range : 1 - port number. "
   ::= { gs2310VlanPortsEntry 1 }

gs2310VlanPortsPVID OBJECT-TYPE
   SYNTAX      Integer32(1..4094)
   MAX-ACCESS  read-write
   STATUS      current
   DESCRIPTION
       "Configure PVID.
        range: 1-4094,
        default: 1. "
   ::= { gs2310VlanPortsEntry 2 }

gs2310VlanPortsFrameType OBJECT-TYPE
   SYNTAX      INTEGER { all(0), tagged(1), untagged(2) }
   MAX-ACCESS  read-write
   STATUS      current
   DESCRIPTION
       "Configure frame type of switch ports.
        0: all,
        1: tagged,
        2: untagged,
        default: all.  "
   ::= { gs2310VlanPortsEntry 3 }

gs2310VlanPortsIngressFilter OBJECT-TYPE
   SYNTAX      INTEGER { disable(0), enable(1) }
   MAX-ACCESS  read-write
   STATUS      current
   DESCRIPTION
       "Configure ingress filtering of switch ports.
        0: disable,
        1: enable,
        default:disable . "
   ::= { gs2310VlanPortsEntry 4 }

gs2310VlanPortsEgressRule OBJECT-TYPE
   SYNTAX      INTEGER { access(0), hybrid(1), trunk(2) }
   MAX-ACCESS  read-write
   STATUS      current
   DESCRIPTION
       "Configure egress-rule of switch ports.
        0: access,
        1: hybrid,
        2: trunk"
   ::= { gs2310VlanPortsEntry 5 }

gs2310VlanPortsPortType OBJECT-TYPE
   SYNTAX      INTEGER { cPort(0), sCustomPort(1), sPort(2), unaware(3) }
   MAX-ACCESS  read-write
   STATUS      current
   DESCRIPTION
       "Configure port type of switch ports.
        0: c-port,
        1: s-custom-port,
        2: s-port,
        3: unaware.
        default: c-port. "
   ::= { gs2310VlanPortsEntry 6 }

gs2310VlanPrivateVLAN                                                              OBJECT IDENTIFIER ::= { gs2310Vlan 2 }

gs2310VlanPrivateVLANMembership                                                    OBJECT IDENTIFIER ::= { gs2310VlanPrivateVLAN 1 }

gs2310VlanPrivateVLANMembershipCreate OBJECT-TYPE
   SYNTAX       Integer32(1..4094)
   MAX-ACCESS   read-write
   STATUS       current
   DESCRIPTION
       "default: 0
        0 : None  (read only)
        1 : Create a pvlan"
   ::= { gs2310VlanPrivateVLANMembership 1 }

gs2310VlanPrivateVLANMembershipTable OBJECT-TYPE
   SYNTAX      SEQUENCE OF GS2310VlanPrivateVLANMembershipEntry
   MAX-ACCESS  not-accessible
   STATUS      current
   DESCRIPTION
       " Configure Private Vlan Configuration. "
   ::= { gs2310VlanPrivateVLANMembership 2 }

gs2310VlanPrivateVLANMembershipEntry OBJECT-TYPE
   SYNTAX      GS2310VlanPrivateVLANMembershipEntry
   MAX-ACCESS  not-accessible
   STATUS      current
   DESCRIPTION
       ""
   INDEX    { gs2310VlanPrivateVLANIndex  }
   ::= { gs2310VlanPrivateVLANMembershipTable 1 }

GS2310VlanPrivateVLANMembershipEntry ::= SEQUENCE {
   gs2310VlanPrivateVLANIndex          Integer32,
   gs2310VlanPrivateVLANID             Integer32,
   gs2310VlanPrivateVLANMemberships    DisplayString,
   gs2310VlanPrivateVLANRowStatus      INTEGER
}

gs2310VlanPrivateVLANIndex OBJECT-TYPE
   SYNTAX      Integer32(1..52)
   MAX-ACCESS  not-accessible
   STATUS      current
   DESCRIPTION
       "private VLAN Index. "
   ::= { gs2310VlanPrivateVLANMembershipEntry 1 }

gs2310VlanPrivateVLANID OBJECT-TYPE
   SYNTAX      Integer32(1..52)
   MAX-ACCESS  read-write
   STATUS      current
   DESCRIPTION
       "Indicates the ID of this particular private VLAN.
       The CreateEntry can be modify, the other entry can't be modify."
   ::= { gs2310VlanPrivateVLANMembershipEntry 2 }

gs2310VlanPrivateVLANMemberships OBJECT-TYPE
   SYNTAX      DisplayString
   MAX-ACCESS  read-write
   STATUS      current
   DESCRIPTION
       "To include the ports in a Private VLAN"
   ::= { gs2310VlanPrivateVLANMembershipEntry 3 }

gs2310VlanPrivateVLANRowStatus OBJECT-TYPE
   SYNTAX      INTEGER { active(1), notInservice(2), destroy(4) }
   MAX-ACCESS  read-write
   STATUS      current
   DESCRIPTION
       "1: active
        2: notInservice
        4: destroy"
   ::= { gs2310VlanPrivateVLANMembershipEntry 4 }

gs2310VlanPortIsolationTable OBJECT-TYPE
   SYNTAX      SEQUENCE OF GS2310VlanPortIsolationEntry
   MAX-ACCESS  not-accessible
   STATUS      current
   DESCRIPTION
       " Configure Vlan Port Isolation Configuration. "
   ::= { gs2310VlanPrivateVLAN 2 }

gs2310VlanPortIsolationEntry OBJECT-TYPE
   SYNTAX      GS2310VlanPortIsolationEntry
   MAX-ACCESS  not-accessible
   STATUS      current
   DESCRIPTION
       ""
   INDEX    { gs2310VlanPortIsolationPort  }
   ::= { gs2310VlanPortIsolationTable 1 }

GS2310VlanPortIsolationEntry ::= SEQUENCE {
   gs2310VlanPortIsolationPort Integer32,
   gs2310VlanPortIsolation     INTEGER
}

gs2310VlanPortIsolationPort OBJECT-TYPE
   SYNTAX      Integer32(1..4094)
   MAX-ACCESS  not-accessible
   STATUS      current
   DESCRIPTION
       " port, range : 1 - port number. "
   ::= { gs2310VlanPortIsolationEntry 1 }

gs2310VlanPortIsolation OBJECT-TYPE
   SYNTAX      INTEGER{ disable(0), enable(1) }
   MAX-ACCESS  read-write
   STATUS      current
   DESCRIPTION
       "default: 0
        0:disable
        1:enable"
   ::= { gs2310VlanPortIsolationEntry 2 }


gs2310MACbasedVLAN                                                      OBJECT IDENTIFIER ::= { gs2310Vlan 3 }

gs2310MACbasedVLANConf                                                      OBJECT IDENTIFIER ::= { gs2310MACbasedVLAN 1 }

gs2310MACbasedVLANConfCreate OBJECT-TYPE
   SYNTAX       Integer32
   MAX-ACCESS   read-write
   STATUS       current
   DESCRIPTION
       "default: 0
       0 : None  (read only) 1 : Create MAC base vlan"
   ::= { gs2310MACbasedVLANConf 1 }

gs2310MACbasedVLANConfTable OBJECT-TYPE
   SYNTAX      SEQUENCE OF GS2310MACbasedVLANConfEntry
   MAX-ACCESS  not-accessible
   STATUS      current
   DESCRIPTION
       " Configure Vlan Port Isolation Configuration. "
   ::= { gs2310MACbasedVLANConf 2 }

gs2310MACbasedVLANConfEntry OBJECT-TYPE
   SYNTAX      GS2310MACbasedVLANConfEntry
   MAX-ACCESS  not-accessible
   STATUS      current
   DESCRIPTION
       ""
   INDEX    { gs2310MACbasedVLANIndex  }
   ::= { gs2310MACbasedVLANConfTable 1 }

GS2310MACbasedVLANConfEntry ::= SEQUENCE {
   gs2310MACbasedVLANIndex         Integer32,
   gs2310MACbasedVLANMACAddress    MacAddress,
   gs2310MACbasedVLANID            Integer32,
   gs2310MACbasedMemberships       DisplayString,
   gs2310MACbaseRowStatus          INTEGER
}

gs2310MACbasedVLANIndex OBJECT-TYPE
   SYNTAX      Integer32(1..256)
   MAX-ACCESS  read-write
   STATUS      current
   DESCRIPTION
       "Indicates the VLAN ID. "
   ::= { gs2310MACbasedVLANConfEntry 1 }

gs2310MACbasedVLANMACAddress OBJECT-TYPE
   SYNTAX      MacAddress
   MAX-ACCESS  read-write
   STATUS      current
   DESCRIPTION
       "Indicates the MAC address.
       The CreateEntry can be modify, the other entry can't be modify."
   ::= { gs2310MACbasedVLANConfEntry 2 }

gs2310MACbasedVLANID OBJECT-TYPE
   SYNTAX      Integer32(1..4094)
   MAX-ACCESS  read-write
   STATUS      current
   DESCRIPTION
       "Indicates the VLAN ID. "
   ::= { gs2310MACbasedVLANConfEntry 3 }

gs2310MACbasedMemberships OBJECT-TYPE
   SYNTAX      DisplayString
   MAX-ACCESS  read-write
   STATUS      current
   DESCRIPTION
       "The ports are displayed for each MAC-based VLAN entry.
        To include the port in a MAC-based VLAN"
   ::= { gs2310MACbasedVLANConfEntry 4 }


gs2310MACbaseRowStatus OBJECT-TYPE
   SYNTAX      INTEGER { active(1), notInservice(2), destroy(4)}
   MAX-ACCESS  read-write
   STATUS      current
   DESCRIPTION
       "1: active
        2: notInservice
        4: destroy"
   ::= { gs2310MACbasedVLANConfEntry 5 }


gs2310IGMPSnooping                                                           OBJECT IDENTIFIER ::= { gs2310Configuration 16 }

gs2310IGMPSnoopingBasic                                                      OBJECT IDENTIFIER ::= { gs2310IGMPSnooping 1 }

gs2310IGMPSnoopingEnable  OBJECT-TYPE
   SYNTAX      INTEGER { disable(0), enable(1) }
   MAX-ACCESS  read-write
   STATUS      current
   DESCRIPTION
       "Enable/Disable the Global IGMP Snooping"
   ::= { gs2310IGMPSnoopingBasic 1 }

gs2310IGMPSnoopingUnregisteredIPMCv4Flooding  OBJECT-TYPE
   SYNTAX      INTEGER { disable(0), enable(1) }
   MAX-ACCESS  read-write
   STATUS      current
   DESCRIPTION
       "Enable/Disable unregistered IPMCv4 traffic flooding. "
   ::= { gs2310IGMPSnoopingBasic 2 }

gs2310IGMPSnoopingSSMIPRangeAddr  OBJECT-TYPE
   SYNTAX      DisplayString
   MAX-ACCESS  read-write
   STATUS      current
   DESCRIPTION
       "SSM (Source-Specific Multicast) Range allows the SSM-aware hosts and
       routers run the SSM service model for the groups in the address range. "
   ::= { gs2310IGMPSnoopingBasic 3 }

gs2310IGMPSnoopingSSMIPRangeValue  OBJECT-TYPE
   SYNTAX      Integer32(4..32)
   MAX-ACCESS  read-write
   STATUS      current
   DESCRIPTION
       "SSM (Source-Specific Multicast) Range allows the SSM-aware hosts and
       routers run the SSM service model for the groups in the address range value. "
   ::= { gs2310IGMPSnoopingBasic 4 }

gs2310IGMPSnoopingProxyEnabled  OBJECT-TYPE
   SYNTAX      INTEGER { disable(0), enable(1) }
   MAX-ACCESS  read-write
   STATUS      current
   DESCRIPTION
       "Enable/Disable IGMP Proxy. This feature can be used to avoid forwarding
       unnecessary join and leave messages to the router side. "
   ::= { gs2310IGMPSnoopingBasic 5 }

gs2310IGMPSnoopingPortRelatedTable OBJECT-TYPE
   SYNTAX      SEQUENCE OF Gs2310IGMPSnoopingPortRelatedEntry
   MAX-ACCESS  not-accessible
   STATUS      current
   DESCRIPTION
       " Configure IGMP Snooping Port Related Configuration. "
   ::= { gs2310IGMPSnoopingBasic 6 }

gs2310IGMPSnoopingPortRelatedEntry OBJECT-TYPE
   SYNTAX      Gs2310IGMPSnoopingPortRelatedEntry
   MAX-ACCESS  not-accessible
   STATUS      current
   DESCRIPTION
       ""
   INDEX    { ifIndex  }
   ::= { gs2310IGMPSnoopingPortRelatedTable 1 }

Gs2310IGMPSnoopingPortRelatedEntry ::= SEQUENCE {
   gs2310IGMPSnoopingRouterPort	INTEGER,
   gs2310IGMPSnoopingFastLeave  	INTEGER,
   gs2310IGMPSnoopingThrottling    Integer32
}

gs2310IGMPSnoopingRouterPort OBJECT-TYPE
   SYNTAX      INTEGER { disable(0), enable(1) }
   MAX-ACCESS  read-write
   STATUS      current
   DESCRIPTION
       "Specify which ports act as router ports. A router port is a port on the
       Ethernet switch that leads towards the Layer 3 multicast device or IGMP
       querier. If an aggregation member port is selected as a router port, the
       whole aggregation will act as a router port. "
   ::= { gs2310IGMPSnoopingPortRelatedEntry 1 }

gs2310IGMPSnoopingFastLeave OBJECT-TYPE
   SYNTAX      INTEGER { disable(0), enable(1) }
   MAX-ACCESS  read-write
   STATUS      current
   DESCRIPTION
       "Enable/Disable the fast leave on the port. "
   ::= { gs2310IGMPSnoopingPortRelatedEntry 2 }

gs2310IGMPSnoopingThrottling OBJECT-TYPE
   SYNTAX      Integer32(0..10)
   MAX-ACCESS  read-write
   STATUS      current
   DESCRIPTION
       "Enable to limit the number of multicast groups to which a switch port can belong.
       0: unlimited"
   ::= { gs2310IGMPSnoopingPortRelatedEntry 3 }

gs2310IGMPSnoopingVLANTable OBJECT-TYPE
   SYNTAX      SEQUENCE OF GS2310IGMPSnoopingVLANEntry
   MAX-ACCESS  not-accessible
   STATUS      current
   DESCRIPTION
       " Configure IGMP Snooping Vlan Configuration. "
   ::= { gs2310IGMPSnooping 2 }

gs2310IGMPSnoopingVLANEntry OBJECT-TYPE
   SYNTAX      GS2310IGMPSnoopingVLANEntry
   MAX-ACCESS  not-accessible
   STATUS      current
   DESCRIPTION
       ""
   INDEX    { gs2310IGMPSnoopingVLANID  }
   ::= { gs2310IGMPSnoopingVLANTable 1 }

GS2310IGMPSnoopingVLANEntry ::= SEQUENCE {
   gs2310IGMPSnoopingVLANID        	Integer32,
   gs2310IGMPSnoopingVLANEnable    	INTEGER,
   gs2310IGMPSnoopingVLANIGMPQuerier   INTEGER,
   gs2310IGMPSnoopingVLANCompatibility INTEGER,
   gs2310IGMPSnoopingVLANRV        	Integer32,
   gs2310IGMPSnoopingVLANQI      	    Integer32,
   gs2310IGMPSnoopingVLANQRI   	    Integer32,
   gs2310IGMPSnoopingVLANLLQI   	    Integer32,
   gs2310IGMPSnoopingVLANURI    	    Integer32
}

gs2310IGMPSnoopingVLANID OBJECT-TYPE
   SYNTAX      Integer32(1..4095)
   MAX-ACCESS  read-write
   STATUS      current
   DESCRIPTION
       "The VLAN ID of the entry"
   ::= { gs2310IGMPSnoopingVLANEntry 1 }

gs2310IGMPSnoopingVLANEnable OBJECT-TYPE
   SYNTAX      INTEGER { disable(0), enable(1) }
   MAX-ACCESS  read-write
   STATUS      current
   DESCRIPTION
       "Enable/Disable the per-VLAN IGMP Snooping. Up to 32 VLANs can be
       selected for IGMP Snooping. "
   ::= { gs2310IGMPSnoopingVLANEntry 2 }

gs2310IGMPSnoopingVLANIGMPQuerier OBJECT-TYPE
   SYNTAX      INTEGER { disable(0), enable(1) }
   MAX-ACCESS  read-write
   STATUS      current
   DESCRIPTION
       "Enable/Disable the IGMP Querier in the VLAN. "
   ::= { gs2310IGMPSnoopingVLANEntry 3 }

gs2310IGMPSnoopingVLANCompatibility OBJECT-TYPE
   SYNTAX      INTEGER { igmpAuto(0), forcedIGMPv1(1), forcedIGMPv2(2), forcedIGMPv3(3), none(4) }
   MAX-ACCESS  read-write
   STATUS      current
   DESCRIPTION
       "Compatibility is maintained by hosts and routers taking appropriate
       actions depending on the versions of IGMP operating on hosts and routers
       within a network. The allowed selection is IGMP-Auto, Forced IGMPv1,
       Forced IGMPv2, Forced IGMPv3, default compatibility value is IGMP-Auto. "
   ::= { gs2310IGMPSnoopingVLANEntry 4 }

gs2310IGMPSnoopingVLANRV OBJECT-TYPE
   SYNTAX      Integer32(-1|1..255)
   MAX-ACCESS  read-write
   STATUS      current
   DESCRIPTION
       "Robustness Variable. The Robustness Variable allows tuning for the
       expected packet loss on a network. The allowed range is 1 to 255, default
        robustness variable value is 2. (-1: none)"
   ::= { gs2310IGMPSnoopingVLANEntry 5 }

gs2310IGMPSnoopingVLANQI OBJECT-TYPE
   SYNTAX      Integer32(-1|1..31744)
   MAX-ACCESS  read-write
   STATUS      current
   DESCRIPTION
       "Query Interval. The Query Interval is the interval between General
       Queries sent by the Querier. The allowed range is 1 to 31744 seconds,
       default query interval is 125 seconds.  (-1: none)"
   ::= { gs2310IGMPSnoopingVLANEntry 6 }

gs2310IGMPSnoopingVLANQRI OBJECT-TYPE
   SYNTAX      Integer32(-1|0..31744)
   MAX-ACCESS  read-write
   STATUS      current
   DESCRIPTION
       "Query Response Interval. The Maximum Response Delay used to calculate
       the Maximum Response Code inserted into the periodic General Queries. The
        allowed range is 0 to 31744 in tenths of seconds, default query response
         interval is 100 in tenths of seconds (10 seconds).   (-1: none)"
   ::= { gs2310IGMPSnoopingVLANEntry 7 }

gs2310IGMPSnoopingVLANLLQI OBJECT-TYPE
   SYNTAX      Integer32(-1|0..31744)
   MAX-ACCESS  read-write
   STATUS      current
   DESCRIPTION
       "LLQI (LMQI for IGMP).  Last Member Query Interval. The Last Member Query
       Time is the time value represented by the Last Member Query Interval,
       multiplied by the Last Member Query Count. The allowed range is 0 to
       31744 in tenths of seconds, default last member query interval is 10 in
       tenths of seconds (1 second).    (-1: none)"
   ::= { gs2310IGMPSnoopingVLANEntry 8 }

gs2310IGMPSnoopingVLANURI OBJECT-TYPE
   SYNTAX      Integer32(-1|0..31744)
   MAX-ACCESS  read-write
   STATUS      current
   DESCRIPTION
       "Unsolicited Report Interval. The Unsolicited Report Interval is the time
        between repetitions of a host's initial report of membership in a group.
         The allowed range is 0 to 31744 seconds, default unsolicited report
         interval is 1 second.    (-1: none)"
   ::= { gs2310IGMPSnoopingVLANEntry 9 }

gs2310IGMPSnoopingPortGroupFiltering                                                      OBJECT IDENTIFIER ::= { gs2310IGMPSnooping 3 }

gs2310IGMPSnoopingPortGroupFilteringCreate OBJECT-TYPE
   SYNTAX       Integer32
   MAX-ACCESS   read-write
   STATUS       current
   DESCRIPTION
       "default: 0
       0 : None  (read only) 1 : Create IGMP Snooping Port Group Filtering "
   ::= { gs2310IGMPSnoopingPortGroupFiltering 1 }

gs2310IGMPSnoopingPortGroupFilteringTable OBJECT-TYPE
   SYNTAX      SEQUENCE OF GS2310IGMPSnoopingPortGroupFilteringEntry
   MAX-ACCESS  not-accessible
   STATUS      current
   DESCRIPTION
       " Configure IGMP Snooping port group filtering. "
   ::= { gs2310IGMPSnoopingPortGroupFiltering 2 }

gs2310IGMPSnoopingPortGroupFilteringEntry OBJECT-TYPE
   SYNTAX      GS2310IGMPSnoopingPortGroupFilteringEntry
   MAX-ACCESS  not-accessible
   STATUS      current
   DESCRIPTION
       ""
   INDEX    { gs2310IGMPSnoopingPortGroupFilteringIndex  }
   ::= { gs2310IGMPSnoopingPortGroupFilteringTable 1 }

GS2310IGMPSnoopingPortGroupFilteringEntry ::= SEQUENCE {
   gs2310IGMPSnoopingPortGroupFilteringIndex         Integer32,
   gs2310IGMPSnoopingPortGroupFilteringPort          Integer32,
   gs2310IGMPSnoopingPortGroupFilteringGroups        DisplayString,
   gs2310IGMPSnoopingPortGroupFilteringRowStatus     INTEGER
}

gs2310IGMPSnoopingPortGroupFilteringIndex OBJECT-TYPE
   SYNTAX      Integer32(1..65535)
   MAX-ACCESS  not-accessible
   STATUS      current
   DESCRIPTION
       "IGMP Snooping Port Group Filtering Configuration Index. "
   ::= { gs2310IGMPSnoopingPortGroupFilteringEntry 1 }

gs2310IGMPSnoopingPortGroupFilteringPort OBJECT-TYPE
   SYNTAX      Integer32(1..65535)
   MAX-ACCESS  read-write
   STATUS      current
   DESCRIPTION
       "The logical port for the settings. "
   ::= { gs2310IGMPSnoopingPortGroupFilteringEntry 2 }

gs2310IGMPSnoopingPortGroupFilteringGroups OBJECT-TYPE
   SYNTAX      DisplayString
   MAX-ACCESS  read-write
   STATUS      current
   DESCRIPTION
       "The IP Multicast Group that will be filtered. "
   ::= { gs2310IGMPSnoopingPortGroupFilteringEntry 3 }

gs2310IGMPSnoopingPortGroupFilteringRowStatus OBJECT-TYPE
   SYNTAX      INTEGER { active(1), notInservice(2), destroy(4)}
   MAX-ACCESS  read-write
   STATUS      current
   DESCRIPTION
       "1: active
        2: notInservice
        4: destroy"
   ::= { gs2310IGMPSnoopingPortGroupFilteringEntry 4 }

gs2310IGMPSnoopingStatus                                                      OBJECT IDENTIFIER ::= { gs2310IGMPSnooping 4 }

gs2310IGMPSnoopingstatisticClear OBJECT-TYPE
   SYNTAX      INTEGER { none(0), clear(1)}
   MAX-ACCESS  read-write
   STATUS      current
   DESCRIPTION
       "Clears all Statistics counters."
   ::= { gs2310IGMPSnoopingStatus 1 }


gs2310IGMPSnoopingstatisticTable OBJECT-TYPE
   SYNTAX      SEQUENCE OF GS2310IGMPSnoopingstatisticEntry
   MAX-ACCESS  not-accessible
   STATUS      current
   DESCRIPTION
       " Configure Vlan Port Isolation Configuration. "
   ::= { gs2310IGMPSnoopingStatus 2 }

gs2310IGMPSnoopingstatisticEntry OBJECT-TYPE
   SYNTAX      GS2310IGMPSnoopingstatisticEntry
   MAX-ACCESS  not-accessible
   STATUS      current
   DESCRIPTION
       ""
   INDEX    { gs2310IGMPSnoopingstatisticVLANID  }
   ::= { gs2310IGMPSnoopingstatisticTable 1 }

GS2310IGMPSnoopingstatisticEntry ::= SEQUENCE {
   gs2310IGMPSnoopingstatisticVLANID              Integer32,
   gs2310IGMPSnoopingstatisticQuerierVersion      DisplayString,
   gs2310IGMPSnoopingstatisticHostVersion         DisplayString,
   gs2310IGMPSnoopingstatisticQuerierStatus       DisplayString,
   gs2310IGMPSnoopingstatisticQueriesTransmitted  Counter32,
   gs2310IGMPSnoopingstatisticQueriesReceived     Counter32,
   gs2310IGMPSnoopingstatisticV1ReportsReceived   Counter32,
   gs2310IGMPSnoopingstatisticV2ReportsReceived   Counter32,
   gs2310IGMPSnoopingstatisticV3ReportsReceived   Counter32,
   gs2310IGMPSnoopingstatisticV2LeavesReceived    Counter32
}


gs2310IGMPSnoopingstatisticVLANID OBJECT-TYPE
   SYNTAX      Integer32(1..4095)
   MAX-ACCESS  read-only
   STATUS      current
   DESCRIPTION
       "The VLAN ID of the entry. "
   ::= { gs2310IGMPSnoopingstatisticEntry 1 }

gs2310IGMPSnoopingstatisticQuerierVersion OBJECT-TYPE
   SYNTAX      DisplayString
   MAX-ACCESS  read-only
   STATUS      current
   DESCRIPTION
       "Working Querier Version currently. "
   ::= { gs2310IGMPSnoopingstatisticEntry 2 }

gs2310IGMPSnoopingstatisticHostVersion OBJECT-TYPE
   SYNTAX      DisplayString
   MAX-ACCESS  read-only
   STATUS      current
   DESCRIPTION
       "Working Host Version currently. "
   ::= { gs2310IGMPSnoopingstatisticEntry 3 }

gs2310IGMPSnoopingstatisticQuerierStatus OBJECT-TYPE
   SYNTAX      DisplayString
   MAX-ACCESS  read-only
   STATUS      current
   DESCRIPTION
       "Shows the Querier status is ACTIVE or IDLE. DISABLE denotes the specific
        interface is administratively disabled. "
   ::= { gs2310IGMPSnoopingstatisticEntry 4 }

gs2310IGMPSnoopingstatisticQueriesTransmitted OBJECT-TYPE
   SYNTAX      Counter32
   MAX-ACCESS  read-only
   STATUS      current
   DESCRIPTION
       "The number of Transmitted Queries. "
   ::= { gs2310IGMPSnoopingstatisticEntry 5 }

gs2310IGMPSnoopingstatisticQueriesReceived OBJECT-TYPE
   SYNTAX      Counter32
   MAX-ACCESS  read-only
   STATUS      current
   DESCRIPTION
       "The number of Received Queries. "
   ::= { gs2310IGMPSnoopingstatisticEntry 6 }

gs2310IGMPSnoopingstatisticV1ReportsReceived OBJECT-TYPE
   SYNTAX      Counter32
   MAX-ACCESS  read-only
   STATUS      current
   DESCRIPTION
       "The number of Received V1 Reports. "
   ::= { gs2310IGMPSnoopingstatisticEntry 7 }

gs2310IGMPSnoopingstatisticV2ReportsReceived OBJECT-TYPE
   SYNTAX      Counter32
   MAX-ACCESS  read-only
   STATUS      current
   DESCRIPTION
       "The number of Received V2 Reports. "
   ::= { gs2310IGMPSnoopingstatisticEntry 8 }

gs2310IGMPSnoopingstatisticV3ReportsReceived OBJECT-TYPE
   SYNTAX      Counter32
   MAX-ACCESS  read-only
   STATUS      current
   DESCRIPTION
       "The number of Received V3 Reports. "
   ::= { gs2310IGMPSnoopingstatisticEntry 9 }

gs2310IGMPSnoopingstatisticV2LeavesReceived OBJECT-TYPE
   SYNTAX      Counter32
   MAX-ACCESS  read-only
   STATUS      current
   DESCRIPTION
       "The number of Received V2 Leaves. "
   ::= { gs2310IGMPSnoopingstatisticEntry 10 }

gs2310IGMPSnoopingRouterPortTable OBJECT-TYPE
   SYNTAX      SEQUENCE OF GS2310IGMPSnoopingRouterPortEntry
   MAX-ACCESS  not-accessible
   STATUS      current
   DESCRIPTION
       " Configure Vlan Port Isolation Configuration. "
   ::= { gs2310IGMPSnoopingStatus 3 }

gs2310IGMPSnoopingRouterPortEntry OBJECT-TYPE
   SYNTAX      GS2310IGMPSnoopingRouterPortEntry
   MAX-ACCESS  not-accessible
   STATUS      current
   DESCRIPTION
       ""
   INDEX    { ifIndex  }
   ::= { gs2310IGMPSnoopingRouterPortTable 1 }

GS2310IGMPSnoopingRouterPortEntry ::= SEQUENCE {
   gs2310IGMPSnoopingRouterPortStatus            DisplayString
}

gs2310IGMPSnoopingRouterPortStatus OBJECT-TYPE
   SYNTAX      DisplayString
   MAX-ACCESS  read-only
   STATUS      current
   DESCRIPTION
       "Display which ports act as router ports. A router port is a port on the
       Ethernet switch that leads towards the Layer 3 multicast device or IGMP
       querier.
       Static denotes the specific port is configured to be a router port.
       Dynamic denotes the specific port is learnt to be a router port.
       Both denote the specific port is configured or learnt to be a router port. "
   ::= { gs2310IGMPSnoopingRouterPortEntry 1 }

gs2310IGMPSnoopingGroupsTable OBJECT-TYPE
   SYNTAX      SEQUENCE OF GS2310IGMPSnoopingGroupsEntry
   MAX-ACCESS  not-accessible
   STATUS      current
   DESCRIPTION
       "IGMP Snooping Groups Information . "
   ::= { gs2310IGMPSnooping 5 }

gs2310IGMPSnoopingGroupsEntry OBJECT-TYPE
   SYNTAX      GS2310IGMPSnoopingGroupsEntry
   MAX-ACCESS  not-accessible
   STATUS      current
   DESCRIPTION
       ""
   INDEX    { gs2310IGMPSnoopingGroupsIndex  }
   ::= { gs2310IGMPSnoopingGroupsTable 1 }

GS2310IGMPSnoopingGroupsEntry ::= SEQUENCE {
   gs2310IGMPSnoopingGroupsIndex          Integer32,
   gs2310IGMPSnoopingGroupsVLANID         Integer32,
   gs2310IGMPSnoopingGroups               InetAddress,
   gs2310IGMPSnoopingGroupsMemberships    DisplayString
}

gs2310IGMPSnoopingGroupsIndex OBJECT-TYPE
   SYNTAX      Integer32(1..65535)
   MAX-ACCESS  not-accessible
   STATUS      current
   DESCRIPTION
       "IGMP Snooping Groups Index"
   ::= { gs2310IGMPSnoopingGroupsEntry 1 }

gs2310IGMPSnoopingGroupsVLANID OBJECT-TYPE
   SYNTAX      Integer32(1..4095)
   MAX-ACCESS  read-only
   STATUS      current
   DESCRIPTION
       "VLAN ID of the group. "
   ::= { gs2310IGMPSnoopingGroupsEntry 2 }

gs2310IGMPSnoopingGroups OBJECT-TYPE
   SYNTAX      DisplayString
   MAX-ACCESS  read-only
   STATUS      current
   DESCRIPTION
       "Group address of the group displayed."
   ::= { gs2310IGMPSnoopingGroupsEntry 3 }

gs2310IGMPSnoopingGroupsMemberships OBJECT-TYPE
   SYNTAX      DisplayString
   MAX-ACCESS  read-only
   STATUS      current
   DESCRIPTION
       "Ports under this group."
   ::= { gs2310IGMPSnoopingGroupsEntry 4 }

gs2310IGMPSnoopingSSMTable OBJECT-TYPE
   SYNTAX      SEQUENCE OF GS2310IGMPSnoopingSSMEntry
   MAX-ACCESS  not-accessible
   STATUS      current
   DESCRIPTION
       "The IGMP SFM (Source-Filtered Multicast) Information Table also contains
        the SSM (Source-Specific Multicast) information. This table is sorted
         first by VLAN ID, then by group, and then by Port. Different source
         addresses belong to the same group are treated as single entry."
   ::= { gs2310IGMPSnooping 6 }

gs2310IGMPSnoopingSSMEntry OBJECT-TYPE
   SYNTAX      GS2310IGMPSnoopingSSMEntry
   MAX-ACCESS  not-accessible
   STATUS      current
   DESCRIPTION
       ""
   INDEX    { gs2310IGMPSnoopingSSMIndex  }
   ::= { gs2310IGMPSnoopingSSMTable 1 }

GS2310IGMPSnoopingSSMEntry ::= SEQUENCE {
   gs2310IGMPSnoopingSSMIndex          Integer32,
   gs2310IGMPSnoopingSSMVLANID         Integer32,
   gs2310IGMPSnoopingSSMGroup          DisplayString,
   gs2310IGMPSnoopingSSMPort           Integer32,
   gs2310IGMPSnoopingSSMMode           DisplayString,
   gs2310IGMPSnoopingSSMSourceAddress  DisplayString,
   gs2310IGMPSnoopingSSMType           DisplayString
}

gs2310IGMPSnoopingSSMIndex OBJECT-TYPE
   SYNTAX      Integer32(1..65535)
   MAX-ACCESS  not-accessible
   STATUS      current
   DESCRIPTION
       "IGMP Snooping SSM Index"
   ::= { gs2310IGMPSnoopingSSMEntry 1 }

gs2310IGMPSnoopingSSMVLANID OBJECT-TYPE
   SYNTAX      Integer32(1..4095)
   MAX-ACCESS  read-only
   STATUS      current
   DESCRIPTION
       "VLAN ID of the group. "
   ::= { gs2310IGMPSnoopingSSMEntry 2 }

gs2310IGMPSnoopingSSMGroup OBJECT-TYPE
   SYNTAX      DisplayString
   MAX-ACCESS  read-only
   STATUS      current
   DESCRIPTION
       "Group address of the group displayed."
   ::= { gs2310IGMPSnoopingSSMEntry 3 }

gs2310IGMPSnoopingSSMPort OBJECT-TYPE
   SYNTAX      Integer32(1..65535)
   MAX-ACCESS  read-only
   STATUS      current
   DESCRIPTION
       "Ports under this group."
   ::= { gs2310IGMPSnoopingSSMEntry 4 }

gs2310IGMPSnoopingSSMMode OBJECT-TYPE
   SYNTAX      DisplayString
   MAX-ACCESS  read-only
   STATUS      current
   DESCRIPTION
       "Indicates the filtering mode maintained per (VLAN ID, port number,
       Group Address) basis. It can be either Include or Exclude."
   ::= { gs2310IGMPSnoopingSSMEntry 5 }

gs2310IGMPSnoopingSSMSourceAddress OBJECT-TYPE
   SYNTAX      DisplayString
   MAX-ACCESS  read-only
   STATUS      current
   DESCRIPTION
       "IP Address of the source. Currently, system limits the total number of
       IP source addresses for filtering to be 128."
   ::= { gs2310IGMPSnoopingSSMEntry 6 }

gs2310IGMPSnoopingSSMType OBJECT-TYPE
   SYNTAX      DisplayString
   MAX-ACCESS  read-only
   STATUS      current
   DESCRIPTION
       "Indicates the Type. It can be either Allow or Deny."
   ::= { gs2310IGMPSnoopingSSMEntry 7 }

gs2310MLDSnooping                                                           OBJECT IDENTIFIER ::= { gs2310Configuration 17 }

gs2310MLDSnoopingBasic                                                      OBJECT IDENTIFIER ::= { gs2310MLDSnooping 1 }

gs2310MLDSnoopingEnable  OBJECT-TYPE
   SYNTAX      INTEGER { disable(0), enable(1) }
   MAX-ACCESS  read-write
   STATUS      current
   DESCRIPTION
       "Enable/Disable the Global MLD Snooping"
   ::= { gs2310MLDSnoopingBasic 1 }

gs2310MLDSnoopingUnregisteredIPMCv6Flooding  OBJECT-TYPE
   SYNTAX      INTEGER { disable(0), enable(1) }
   MAX-ACCESS  read-write
   STATUS      current
   DESCRIPTION
       "Enable/Disable unregistered IPMCv6 traffic flooding. "
   ::= { gs2310MLDSnoopingBasic 2 }

gs2310MLDSnoopingSSMIPRangeAddr  OBJECT-TYPE
   SYNTAX      DisplayString
   MAX-ACCESS  read-write
   STATUS      current
   DESCRIPTION
       "SSM (Source-Specific Multicast) Range allows the SSM-aware hosts and
       routers run the SSM service model for the groups in the address range. "
   ::= { gs2310MLDSnoopingBasic 3 }

gs2310MLDSnoopingSSMIPRangeValue  OBJECT-TYPE
   SYNTAX      Integer32(8..128)
   MAX-ACCESS  read-write
   STATUS      current
   DESCRIPTION
       "SSM (Source-Specific Multicast) Range allows the SSM-aware hosts and
       routers run the SSM service model for the groups in the address range value. "
   ::= { gs2310MLDSnoopingBasic 4 }

gs2310MLDSnoopingProxyEnabled  OBJECT-TYPE
   SYNTAX      INTEGER { disable(0), enable(1) }
   MAX-ACCESS  read-write
   STATUS      current
   DESCRIPTION
       "Enable/Disable MLD Proxy. This feature can be used to avoid forwarding
       unnecessary join and leave messages to the router side. "
   ::= { gs2310MLDSnoopingBasic 5 }

gs2310MLDSnoopingPortRelatedTable OBJECT-TYPE
   SYNTAX      SEQUENCE OF Gs2310MLDSnoopingPortRelatedEntry
   MAX-ACCESS  not-accessible
   STATUS      current
   DESCRIPTION
       " Configure MLD Snooping Port Related Configuration. "
   ::= { gs2310MLDSnoopingBasic 6 }

gs2310MLDSnoopingPortRelatedEntry OBJECT-TYPE
   SYNTAX      Gs2310MLDSnoopingPortRelatedEntry
   MAX-ACCESS  not-accessible
   STATUS      current
   DESCRIPTION
       ""
   INDEX    { ifIndex  }
   ::= { gs2310MLDSnoopingPortRelatedTable 1 }

Gs2310MLDSnoopingPortRelatedEntry ::= SEQUENCE {
   gs2310MLDSnoopingRouterPort	INTEGER,
   gs2310MLDSnoopingFastLeave  	INTEGER,
   gs2310MLDSnoopingThrottling    Integer32
}

gs2310MLDSnoopingRouterPort OBJECT-TYPE
   SYNTAX      INTEGER { disable(0), enable(1) }
   MAX-ACCESS  read-write
   STATUS      current
   DESCRIPTION
       "Specify which ports act as router ports. A router port is a port on the
       Ethernet switch that leads towards the Layer 3 multicast device or IGMP
       querier. If an aggregation member port is selected as a router port, the
       whole aggregation will act as a router port. "
   ::= { gs2310MLDSnoopingPortRelatedEntry 1 }

gs2310MLDSnoopingFastLeave OBJECT-TYPE
   SYNTAX      INTEGER { disable(0), enable(1) }
   MAX-ACCESS  read-write
   STATUS      current
   DESCRIPTION
       "Enable/Disable the fast leave on the port. "
   ::= { gs2310MLDSnoopingPortRelatedEntry 2 }

gs2310MLDSnoopingThrottling OBJECT-TYPE
   SYNTAX      Integer32(0..10)
   MAX-ACCESS  read-write
   STATUS      current
   DESCRIPTION
       "Enable to limit the number of multicast groups to which a switch port can belong.
       0: unlimited"
   ::= { gs2310MLDSnoopingPortRelatedEntry 3 }

gs2310MLDSnoopingVLANTable OBJECT-TYPE
   SYNTAX      SEQUENCE OF Gs2310MLDSnoopingVLANEntry
   MAX-ACCESS  not-accessible
   STATUS      current
   DESCRIPTION
       " Configure MLD Snooping Vlan Configuration. "
   ::= { gs2310MLDSnooping 2 }

gs2310MLDSnoopingVLANEntry OBJECT-TYPE
   SYNTAX      Gs2310MLDSnoopingVLANEntry
   MAX-ACCESS  not-accessible
   STATUS      current
   DESCRIPTION
       ""
   INDEX    { gs2310MLDSnoopingVLANID  }
   ::= { gs2310MLDSnoopingVLANTable 1 }

Gs2310MLDSnoopingVLANEntry ::= SEQUENCE {
   gs2310MLDSnoopingVLANID        	Integer32,
   gs2310MLDSnoopingVLANEnable    	INTEGER,
   gs2310MLDSnoopingVLANIGMPQuerier   INTEGER,
   gs2310MLDSnoopingVLANCompatibility INTEGER,
   gs2310MLDSnoopingVLANRV        	Integer32,
   gs2310MLDSnoopingVLANQI      	    Integer32,
   gs2310MLDSnoopingVLANQRI   	    Integer32,
   gs2310MLDSnoopingVLANLLQI   	    Integer32,
   gs2310MLDSnoopingVLANURI    	    Integer32
}

gs2310MLDSnoopingVLANID OBJECT-TYPE
   SYNTAX      Integer32(1..4095)
   MAX-ACCESS  read-write
   STATUS      current
   DESCRIPTION
       "The VLAN ID of the entry"
   ::= { gs2310MLDSnoopingVLANEntry 1 }

gs2310MLDSnoopingVLANEnable OBJECT-TYPE
   SYNTAX      INTEGER { disable(0), enable(1) }
   MAX-ACCESS  read-write
   STATUS      current
   DESCRIPTION
       "Enable/Disable the per-VLAN MLD Snooping. Up to 32 VLANs can be
       selected for MLD Snooping. "
   ::= { gs2310MLDSnoopingVLANEntry 2 }

gs2310MLDSnoopingVLANIGMPQuerier OBJECT-TYPE
   SYNTAX      INTEGER { disable(0), enable(1) }
   MAX-ACCESS  read-write
   STATUS      current
   DESCRIPTION
       "Enable/Disable the MLD Querier in the VLAN. "
   ::= { gs2310MLDSnoopingVLANEntry 3 }

gs2310MLDSnoopingVLANCompatibility OBJECT-TYPE
   SYNTAX      INTEGER { mldAuto(0), forcedMLDv1(1), forcedMLDv2(2), none(3) }
   MAX-ACCESS  read-write
   STATUS      current
   DESCRIPTION
       "Compatibility is maintained by hosts and routers taking appropriate
       actions depending on the versions of IGMP operating on hosts and routers
       within a network. The allowed selection is MLD-Auto, Forced MLDv1,
       Forced MLDv2, default compatibility value is IGMP-Auto. "
   ::= { gs2310MLDSnoopingVLANEntry 4 }

gs2310MLDSnoopingVLANRV OBJECT-TYPE
   SYNTAX      Integer32(-1|1..255)
   MAX-ACCESS  read-write
   STATUS      current
   DESCRIPTION
       "Robustness Variable. The Robustness Variable allows tuning for the
       expected packet loss on a network. The allowed range is 1 to 255, default
        robustness variable value is 2. (-1: none)"
   ::= { gs2310MLDSnoopingVLANEntry 5 }

gs2310MLDSnoopingVLANQI OBJECT-TYPE
   SYNTAX      Integer32(-1|1..31744)
   MAX-ACCESS  read-write
   STATUS      current
   DESCRIPTION
       "Query Interval. The Query Interval is the interval between General
       Queries sent by the Querier. The allowed range is 1 to 31744 seconds,
       default query interval is 125 seconds.  (-1: none)"
   ::= { gs2310MLDSnoopingVLANEntry 6 }

gs2310MLDSnoopingVLANQRI OBJECT-TYPE
   SYNTAX      Integer32(-1|0..31744)
   MAX-ACCESS  read-write
   STATUS      current
   DESCRIPTION
       "Query Response Interval. The Maximum Response Delay used to calculate
       the Maximum Response Code inserted into the periodic General Queries. The
        allowed range is 0 to 31744 in tenths of seconds, default query response
         interval is 100 in tenths of seconds (10 seconds).   (-1: none)"
   ::= { gs2310MLDSnoopingVLANEntry 7 }

gs2310MLDSnoopingVLANLLQI OBJECT-TYPE
   SYNTAX      Integer32(-1|0..31744)
   MAX-ACCESS  read-write
   STATUS      current
   DESCRIPTION
       "LLQI (LMQI for MLD).  Last Member Query Interval. The Last Member Query
       Time is the time value represented by the Last Member Query Interval,
       multiplied by the Last Member Query Count. The allowed range is 0 to
       31744 in tenths of seconds, default last member query interval is 10 in
       tenths of seconds (1 second).    (-1: none)"
   ::= { gs2310MLDSnoopingVLANEntry 8 }

gs2310MLDSnoopingVLANURI OBJECT-TYPE
   SYNTAX      Integer32(-1|0..31744)
   MAX-ACCESS  read-write
   STATUS      current
   DESCRIPTION
       "Unsolicited Report Interval. The Unsolicited Report Interval is the time
        between repetitions of a host's initial report of membership in a group.
         The allowed range is 0 to 31744 seconds, default unsolicited report
         interval is 1 second.    (-1: none)"
   ::= { gs2310MLDSnoopingVLANEntry 9 }

gs2310MLDSnoopingPortGroupFiltering                                                      OBJECT IDENTIFIER ::= { gs2310MLDSnooping 3 }

gs2310MLDSnoopingPortGroupFilteringCreate OBJECT-TYPE
   SYNTAX       Integer32
   MAX-ACCESS   read-write
   STATUS       current
   DESCRIPTION
       "default: 0
       0 : None  (read only) 1 : Create MLD Snooping Port Group Filtering "
   ::= { gs2310MLDSnoopingPortGroupFiltering 1 }

gs2310MLDSnoopingPortGroupFilteringTable OBJECT-TYPE
   SYNTAX      SEQUENCE OF Gs2310MLDSnoopingPortGroupFilteringEntry
   MAX-ACCESS  not-accessible
   STATUS      current
   DESCRIPTION
       " Configure MLD Snooping port group filtering. "
   ::= { gs2310MLDSnoopingPortGroupFiltering 2 }

gs2310MLDSnoopingPortGroupFilteringEntry OBJECT-TYPE
   SYNTAX      Gs2310MLDSnoopingPortGroupFilteringEntry
   MAX-ACCESS  not-accessible
   STATUS      current
   DESCRIPTION
       ""
   INDEX    { gs2310MLDSnoopingPortGroupFilteringIndex  }
   ::= { gs2310MLDSnoopingPortGroupFilteringTable 1 }

Gs2310MLDSnoopingPortGroupFilteringEntry ::= SEQUENCE {
   gs2310MLDSnoopingPortGroupFilteringIndex         Integer32,
   gs2310MLDSnoopingPortGroupFilteringPort          Integer32,
   gs2310MLDSnoopingPortGroupFilteringGroups        DisplayString,
   gs2310MLDSnoopingPortGroupFilteringRowStatus     INTEGER
}

gs2310MLDSnoopingPortGroupFilteringIndex OBJECT-TYPE
   SYNTAX      Integer32(1..65535)
   MAX-ACCESS  not-accessible
   STATUS      current
   DESCRIPTION
       "MLD Snooping Port Group Filtering Configuration Index. "
   ::= { gs2310MLDSnoopingPortGroupFilteringEntry 1 }

gs2310MLDSnoopingPortGroupFilteringPort OBJECT-TYPE
   SYNTAX      Integer32(1..65535)
   MAX-ACCESS  read-write
   STATUS      current
   DESCRIPTION
       "The logical port for the settings. "
   ::= { gs2310MLDSnoopingPortGroupFilteringEntry 2 }

gs2310MLDSnoopingPortGroupFilteringGroups OBJECT-TYPE
   SYNTAX      DisplayString
   MAX-ACCESS  read-write
   STATUS      current
   DESCRIPTION
       "The IP Multicast Group that will be filtered. "
   ::= { gs2310MLDSnoopingPortGroupFilteringEntry 3 }

gs2310MLDSnoopingPortGroupFilteringRowStatus OBJECT-TYPE
   SYNTAX      INTEGER { active(1), notInservice(2), destroy(4)}
   MAX-ACCESS  read-write
   STATUS      current
   DESCRIPTION
       "1: active
        2: notInservice
        4: destroy"
   ::= { gs2310MLDSnoopingPortGroupFilteringEntry 4 }

gs2310MLDSnoopingStatus                                                      OBJECT IDENTIFIER ::= { gs2310MLDSnooping 4 }

gs2310MLDSnoopingstatisticClear OBJECT-TYPE
   SYNTAX      INTEGER { none(0), clear(1)}
   MAX-ACCESS  read-write
   STATUS      current
   DESCRIPTION
       "Clears all Statistics counters."
   ::= { gs2310MLDSnoopingStatus 1 }


gs2310MLDSnoopingstatisticTable OBJECT-TYPE
   SYNTAX      SEQUENCE OF Gs2310MLDSnoopingstatisticEntry
   MAX-ACCESS  not-accessible
   STATUS      current
   DESCRIPTION
       " Configure Vlan Port Isolation Configuration. "
   ::= { gs2310MLDSnoopingStatus 2 }

gs2310MLDSnoopingstatisticEntry OBJECT-TYPE
   SYNTAX      Gs2310MLDSnoopingstatisticEntry
   MAX-ACCESS  not-accessible
   STATUS      current
   DESCRIPTION
       ""
   INDEX    { gs2310MLDSnoopingstatisticVLANID  }
   ::= { gs2310MLDSnoopingstatisticTable 1 }

Gs2310MLDSnoopingstatisticEntry ::= SEQUENCE {
   gs2310MLDSnoopingstatisticVLANID              Integer32,
   gs2310MLDSnoopingstatisticQuerierVersion      DisplayString,
   gs2310MLDSnoopingstatisticHostVersion         DisplayString,
   gs2310MLDSnoopingstatisticQuerierStatus       DisplayString,
   gs2310MLDSnoopingstatisticQueriesTransmitted  Counter32,
   gs2310MLDSnoopingstatisticQueriesReceived     Counter32,
   gs2310MLDSnoopingstatisticV1ReportsReceived   Counter32,
   gs2310MLDSnoopingstatisticV2ReportsReceived   Counter32,
   gs2310MLDSnoopingstatisticV1LeavesReceived    Counter32
}


gs2310MLDSnoopingstatisticVLANID OBJECT-TYPE
   SYNTAX      Integer32(1..4095)
   MAX-ACCESS  read-only
   STATUS      current
   DESCRIPTION
       "The VLAN ID of the entry. "
   ::= { gs2310MLDSnoopingstatisticEntry 1 }

gs2310MLDSnoopingstatisticQuerierVersion OBJECT-TYPE
   SYNTAX      DisplayString
   MAX-ACCESS  read-only
   STATUS      current
   DESCRIPTION
       "Working Querier Version currently. "
   ::= { gs2310MLDSnoopingstatisticEntry 2 }

gs2310MLDSnoopingstatisticHostVersion OBJECT-TYPE
   SYNTAX      DisplayString
   MAX-ACCESS  read-only
   STATUS      current
   DESCRIPTION
       "Working Host Version currently. "
   ::= { gs2310MLDSnoopingstatisticEntry 3 }

gs2310MLDSnoopingstatisticQuerierStatus OBJECT-TYPE
   SYNTAX      DisplayString
   MAX-ACCESS  read-only
   STATUS      current
   DESCRIPTION
       "Shows the Querier status is ACTIVE or IDLE. DISABLE denotes the specific
        interface is administratively disabled. "
   ::= { gs2310MLDSnoopingstatisticEntry 4 }

gs2310MLDSnoopingstatisticQueriesTransmitted OBJECT-TYPE
   SYNTAX      Counter32
   MAX-ACCESS  read-only
   STATUS      current
   DESCRIPTION
       "The number of Transmitted Queries. "
   ::= { gs2310MLDSnoopingstatisticEntry 5 }

gs2310MLDSnoopingstatisticQueriesReceived OBJECT-TYPE
   SYNTAX      Counter32
   MAX-ACCESS  read-only
   STATUS      current
   DESCRIPTION
       "The number of Received Queries. "
   ::= { gs2310MLDSnoopingstatisticEntry 6 }

gs2310MLDSnoopingstatisticV1ReportsReceived OBJECT-TYPE
   SYNTAX      Counter32
   MAX-ACCESS  read-only
   STATUS      current
   DESCRIPTION
       "The number of Received V1 Reports. "
   ::= { gs2310MLDSnoopingstatisticEntry 7 }

gs2310MLDSnoopingstatisticV2ReportsReceived OBJECT-TYPE
   SYNTAX      Counter32
   MAX-ACCESS  read-only
   STATUS      current
   DESCRIPTION
       "The number of Received V2 Reports. "
   ::= { gs2310MLDSnoopingstatisticEntry 8 }

gs2310MLDSnoopingstatisticV1LeavesReceived OBJECT-TYPE
   SYNTAX      Counter32
   MAX-ACCESS  read-only
   STATUS      current
   DESCRIPTION
       "The number of Received V1 Leaves. "
   ::= { gs2310MLDSnoopingstatisticEntry 9 }

gs2310MLDSnoopingRouterPortTable OBJECT-TYPE
   SYNTAX      SEQUENCE OF Gs2310MLDSnoopingRouterPortEntry
   MAX-ACCESS  not-accessible
   STATUS      current
   DESCRIPTION
       " Configure Vlan Port Isolation Configuration. "
   ::= { gs2310MLDSnoopingStatus 3 }

gs2310MLDSnoopingRouterPortEntry OBJECT-TYPE
   SYNTAX      Gs2310MLDSnoopingRouterPortEntry
   MAX-ACCESS  not-accessible
   STATUS      current
   DESCRIPTION
       ""
   INDEX    { ifIndex  }
   ::= { gs2310MLDSnoopingRouterPortTable 1 }

Gs2310MLDSnoopingRouterPortEntry ::= SEQUENCE {
   gs2310MLDSnoopingRouterPortStatus            DisplayString
}

gs2310MLDSnoopingRouterPortStatus OBJECT-TYPE
   SYNTAX      DisplayString
   MAX-ACCESS  read-only
   STATUS      current
   DESCRIPTION
       "Display which ports act as router ports. A router port is a port on the
       Ethernet switch that leads towards the Layer 3 multicast device or IGMP
       querier.
       Static denotes the specific port is configured to be a router port.
       Dynamic denotes the specific port is learnt to be a router port.
       Both denote the specific port is configured or learnt to be a router port. "
   ::= { gs2310MLDSnoopingRouterPortEntry 1 }

gs2310MLDSnoopingGroupsTable OBJECT-TYPE
   SYNTAX      SEQUENCE OF Gs2310MLDSnoopingGroupsEntry
   MAX-ACCESS  not-accessible
   STATUS      current
   DESCRIPTION
       "MLD Snooping Groups Information . "
   ::= { gs2310MLDSnooping 5 }

gs2310MLDSnoopingGroupsEntry OBJECT-TYPE
   SYNTAX      Gs2310MLDSnoopingGroupsEntry
   MAX-ACCESS  not-accessible
   STATUS      current
   DESCRIPTION
       ""
   INDEX    { gs2310MLDSnoopingGroupsIndex  }
   ::= { gs2310MLDSnoopingGroupsTable 1 }

Gs2310MLDSnoopingGroupsEntry ::= SEQUENCE {
   gs2310MLDSnoopingGroupsIndex          Integer32,
   gs2310MLDSnoopingGroupsVLANID         Integer32,
   gs2310MLDSnoopingGroups               InetAddress,
   gs2310MLDSnoopingGroupsMemberships    DisplayString
}

gs2310MLDSnoopingGroupsIndex OBJECT-TYPE
   SYNTAX      Integer32(1..65535)
   MAX-ACCESS  not-accessible
   STATUS      current
   DESCRIPTION
       "MLD Snooping Groups Index"
   ::= { gs2310MLDSnoopingGroupsEntry 1 }

gs2310MLDSnoopingGroupsVLANID OBJECT-TYPE
   SYNTAX      Integer32(1..4095)
   MAX-ACCESS  read-only
   STATUS      current
   DESCRIPTION
       "VLAN ID of the group. "
   ::= { gs2310MLDSnoopingGroupsEntry 2 }

gs2310MLDSnoopingGroups OBJECT-TYPE
   SYNTAX      DisplayString
   MAX-ACCESS  read-only
   STATUS      current
   DESCRIPTION
       "Group address of the group displayed."
   ::= { gs2310MLDSnoopingGroupsEntry 3 }

gs2310MLDSnoopingGroupsMemberships OBJECT-TYPE
   SYNTAX      DisplayString
   MAX-ACCESS  read-only
   STATUS      current
   DESCRIPTION
       "Ports under this group."
   ::= { gs2310MLDSnoopingGroupsEntry 4 }

gs2310MLDSnoopingSSMTable OBJECT-TYPE
   SYNTAX      SEQUENCE OF Gs2310MLDSnoopingSSMEntry
   MAX-ACCESS  not-accessible
   STATUS      current
   DESCRIPTION
       "The MLD SFM (Source-Filtered Multicast) Information Table also contains
        the SSM (Source-Specific Multicast) information. This table is sorted
         first by VLAN ID, then by group, and then by Port. Different source
         addresses belong to the same group are treated as single entry."
   ::= { gs2310MLDSnooping 6 }

gs2310MLDSnoopingSSMEntry OBJECT-TYPE
   SYNTAX      Gs2310MLDSnoopingSSMEntry
   MAX-ACCESS  not-accessible
   STATUS      current
   DESCRIPTION
       ""
   INDEX    { gs2310MLDSnoopingSSMIndex  }
   ::= { gs2310MLDSnoopingSSMTable 1 }

Gs2310MLDSnoopingSSMEntry ::= SEQUENCE {
   gs2310MLDSnoopingSSMIndex          Integer32,
   gs2310MLDSnoopingSSMVLANID         Integer32,
   gs2310MLDSnoopingSSMGroup          DisplayString,
   gs2310MLDSnoopingSSMPort           Integer32,
   gs2310MLDSnoopingSSMMode           DisplayString,
   gs2310MLDSnoopingSSMSourceAddress  DisplayString,
   gs2310MLDSnoopingSSMType           DisplayString
}

gs2310MLDSnoopingSSMIndex OBJECT-TYPE
   SYNTAX      Integer32(1..65535)
   MAX-ACCESS  not-accessible
   STATUS      current
   DESCRIPTION
       "MLD Snooping SSM Index"
   ::= { gs2310MLDSnoopingSSMEntry 1 }

gs2310MLDSnoopingSSMVLANID OBJECT-TYPE
   SYNTAX      Integer32(1..4095)
   MAX-ACCESS  read-only
   STATUS      current
   DESCRIPTION
       "VLAN ID of the group. "
   ::= { gs2310MLDSnoopingSSMEntry 2 }

gs2310MLDSnoopingSSMGroup OBJECT-TYPE
   SYNTAX      DisplayString
   MAX-ACCESS  read-only
   STATUS      current
   DESCRIPTION
       "Group address of the group displayed."
   ::= { gs2310MLDSnoopingSSMEntry 3 }

gs2310MLDSnoopingSSMPort OBJECT-TYPE
   SYNTAX      Integer32(1..65535)
   MAX-ACCESS  read-only
   STATUS      current
   DESCRIPTION
       "Ports under this group."
   ::= { gs2310MLDSnoopingSSMEntry 4 }

gs2310MLDSnoopingSSMMode OBJECT-TYPE
   SYNTAX      DisplayString
   MAX-ACCESS  read-only
   STATUS      current
   DESCRIPTION
       "Indicates the filtering mode maintained per (VLAN ID, port number,
       Group Address) basis. It can be either Include or Exclude."
   ::= { gs2310MLDSnoopingSSMEntry 5 }

gs2310MLDSnoopingSSMSourceAddress OBJECT-TYPE
   SYNTAX      DisplayString
   MAX-ACCESS  read-only
   STATUS      current
   DESCRIPTION
       "IP Address of the source. Currently, system limits the total number of
       IP source addresses for filtering to be 128."
   ::= { gs2310MLDSnoopingSSMEntry 6 }

gs2310MLDSnoopingSSMType OBJECT-TYPE
   SYNTAX      DisplayString
   MAX-ACCESS  read-only
   STATUS      current
   DESCRIPTION
       "Indicates the Type. It can be either Allow or Deny."
   ::= { gs2310MLDSnoopingSSMEntry 7 }


gs2310MVR                                                                   OBJECT IDENTIFIER ::= { gs2310Configuration 18 }

gs2310MVRConfiguration                                                      OBJECT IDENTIFIER ::= { gs2310MVR 1 }

gs2310MVRMode  OBJECT-TYPE
   SYNTAX      INTEGER { disable(0), enable(1) }
   MAX-ACCESS  read-write
   STATUS      current
   DESCRIPTION
       "Enable/Disable the Global MVR. "
   ::= { gs2310MVRConfiguration 1 }

gs2310MVRVLANId  OBJECT-TYPE
   SYNTAX      Integer32(1..4094)
   MAX-ACCESS  read-write
   STATUS      current
   DESCRIPTION
       "Specify the Multicast VLAN ID. "
   ::= { gs2310MVRConfiguration 2 }

gs2310MVRPortConfigurationTable OBJECT-TYPE
   SYNTAX      SEQUENCE OF Gs2310MVRPortConfigurationEntry
   MAX-ACCESS  not-accessible
   STATUS      current
   DESCRIPTION
       " Configure MVR Port Configuration. "
   ::= { gs2310MVRConfiguration 3 }

gs2310MVRPortConfigurationEntry OBJECT-TYPE
   SYNTAX      Gs2310MVRPortConfigurationEntry
   MAX-ACCESS  not-accessible
   STATUS      current
   DESCRIPTION
       ""
   INDEX    { ifIndex  }
   ::= { gs2310MVRPortConfigurationTable 1 }

Gs2310MVRPortConfigurationEntry ::= SEQUENCE {
   gs2310MVRPortConfigurationMode	INTEGER,
   gs2310MVRPortConfigurationType  	INTEGER,
   gs2310MVRPortConfigurationImmediateLeave    INTEGER
}

gs2310MVRPortConfigurationMode OBJECT-TYPE
   SYNTAX      INTEGER { disable(0), enable(1) }
   MAX-ACCESS  read-write
   STATUS      current
   DESCRIPTION
       "Enable MVR on the port. "
   ::= { gs2310MVRPortConfigurationEntry 1 }

gs2310MVRPortConfigurationType OBJECT-TYPE
   SYNTAX      INTEGER { receiver(0), source(1) }
   MAX-ACCESS  read-write
   STATUS      current
   DESCRIPTION
       "Specify the MVR port type on the port. "
   ::= { gs2310MVRPortConfigurationEntry 2 }

gs2310MVRPortConfigurationImmediateLeave OBJECT-TYPE
   SYNTAX      INTEGER { disable(0), enable(1) }
   MAX-ACCESS  read-write
   STATUS      current
   DESCRIPTION
       "Enable the fast leave on the port. "
   ::= { gs2310MVRPortConfigurationEntry 3 }


gs2310MVRPortGroupFiltering                                                      OBJECT IDENTIFIER ::= { gs2310MVR 2 }

gs2310MVRPortGroupFilteringCreate OBJECT-TYPE
   SYNTAX       Integer32
   MAX-ACCESS   read-write
   STATUS       current
   DESCRIPTION
       "default: 0
       0 : None  (read only) 1 : Create MLD Snooping Port Group Filtering "
   ::= { gs2310MVRPortGroupFiltering 1 }

gs2310MVRPortGroupFilteringTable OBJECT-TYPE
   SYNTAX      SEQUENCE OF Gs2310MVRPortGroupFilteringEntry
   MAX-ACCESS  not-accessible
   STATUS      current
   DESCRIPTION
       " Configure MVR port group filtering. "
   ::= { gs2310MVRPortGroupFiltering 2 }

gs2310MVRPortGroupFilteringEntry OBJECT-TYPE
   SYNTAX      Gs2310MVRPortGroupFilteringEntry
   MAX-ACCESS  not-accessible
   STATUS      current
   DESCRIPTION
       ""
   INDEX    { gs2310MVRPortGroupFilteringIndex  }
   ::= { gs2310MVRPortGroupFilteringTable 1 }

Gs2310MVRPortGroupFilteringEntry ::= SEQUENCE {
   gs2310MVRPortGroupFilteringIndex         Integer32,
   gs2310MVRPortGroupFilteringPort          Integer32,
   gs2310MVRPortGroupFilteringStartGroups   DisplayString,
   gs2310MVRPortGroupFilteringEndGroups     DisplayString,
   gs2310MVRPortGroupFilteringRowStatus     INTEGER
}

gs2310MVRPortGroupFilteringIndex OBJECT-TYPE
   SYNTAX      Integer32(1..65535)
   MAX-ACCESS  not-accessible
   STATUS      current
   DESCRIPTION
       "MVR Port Group Filtering Configuration Index. "
   ::= { gs2310MVRPortGroupFilteringEntry 1 }

gs2310MVRPortGroupFilteringPort OBJECT-TYPE
   SYNTAX      Integer32(1..65535)
   MAX-ACCESS  read-write
   STATUS      current
   DESCRIPTION
       "The logical port for the settings. "
   ::= { gs2310MVRPortGroupFilteringEntry 2 }

gs2310MVRPortGroupFilteringStartGroups OBJECT-TYPE
   SYNTAX      DisplayString
   MAX-ACCESS  read-write
   STATUS      current
   DESCRIPTION
       "The IP Multicast Group that will be allowed. "
   ::= { gs2310MVRPortGroupFilteringEntry 3 }

gs2310MVRPortGroupFilteringEndGroups OBJECT-TYPE
   SYNTAX      DisplayString
   MAX-ACCESS  read-write
   STATUS      current
   DESCRIPTION
       "The IP Multicast Group that will be allowed. "
   ::= { gs2310MVRPortGroupFilteringEntry 4 }

gs2310MVRPortGroupFilteringRowStatus OBJECT-TYPE
   SYNTAX      INTEGER { active(1), notInservice(2), destroy(4)}
   MAX-ACCESS  read-write
   STATUS      current
   DESCRIPTION
       "1: active
        2: notInservice
        4: destroy"
   ::= { gs2310MVRPortGroupFilteringEntry 5 }

gs2310MVRGroupsTable OBJECT-TYPE
   SYNTAX      SEQUENCE OF Gs2310MVRGroupsEntry
   MAX-ACCESS  not-accessible
   STATUS      current
   DESCRIPTION
       "MVR Groups Information . "
   ::= { gs2310MVR 3 }

gs2310MVRGroupsEntry OBJECT-TYPE
   SYNTAX      Gs2310MVRGroupsEntry
   MAX-ACCESS  not-accessible
   STATUS      current
   DESCRIPTION
       ""
   INDEX    { gs2310MVRGroupsIndex  }
   ::= { gs2310MVRGroupsTable 1 }

Gs2310MVRGroupsEntry ::= SEQUENCE {
   gs2310MVRGroupsIndex          Integer32,
   gs2310MVRGroupsVLANID         Integer32,
   gs2310MVRGroups               InetAddress,
   gs2310MVRGroupsMemberships    DisplayString
}

gs2310MVRGroupsIndex OBJECT-TYPE
   SYNTAX      Integer32(1..65535)
   MAX-ACCESS  not-accessible
   STATUS      current
   DESCRIPTION
       "MVR Groups Index"
   ::= { gs2310MVRGroupsEntry 1 }

gs2310MVRGroupsVLANID OBJECT-TYPE
   SYNTAX      Integer32(1..4095)
   MAX-ACCESS  read-only
   STATUS      current
   DESCRIPTION
       "VLAN ID of the group. "
   ::= { gs2310MVRGroupsEntry 2 }

gs2310MVRGroups OBJECT-TYPE
   SYNTAX      DisplayString
   MAX-ACCESS  read-only
   STATUS      current
   DESCRIPTION
       "Group address of the group displayed."
   ::= { gs2310MVRGroupsEntry 3 }

gs2310MVRGroupsMemberships OBJECT-TYPE
   SYNTAX      DisplayString
   MAX-ACCESS  read-only
   STATUS      current
   DESCRIPTION
       "Ports under this group."
   ::= { gs2310MVRGroupsEntry 4 }


gs2310MVRStatus                                                      OBJECT IDENTIFIER ::= { gs2310MVR 4 }

gs2310MVRstatisticClear OBJECT-TYPE
   SYNTAX      INTEGER { none(0), clear(1)}
   MAX-ACCESS  read-write
   STATUS      current
   DESCRIPTION
       "Clears all Statistics counters."
   ::= { gs2310MVRStatus 1 }

gs2310MVRstatisticVLANID OBJECT-TYPE
   SYNTAX      Integer32(1..4095)
   MAX-ACCESS  read-only
   STATUS      current
   DESCRIPTION
       "The VLAN ID of the entry. "
   ::= { gs2310MVRStatus 2 }

gs2310MVRstatisticV1ReportsReceived OBJECT-TYPE
   SYNTAX      Counter32
   MAX-ACCESS  read-only
   STATUS      current
   DESCRIPTION
       "The number of Received V1 Reports. "
   ::= { gs2310MVRStatus 3 }

gs2310MVRstatisticV2ReportsReceived OBJECT-TYPE
   SYNTAX      Counter32
   MAX-ACCESS  read-only
   STATUS      current
   DESCRIPTION
       "The number of Received V2 Reports. "
   ::= { gs2310MVRStatus 4 }

gs2310MVRstatisticV3ReportsReceived OBJECT-TYPE
   SYNTAX      Counter32
   MAX-ACCESS  read-only
   STATUS      current
   DESCRIPTION
       "The number of Received V3 Reports. "
   ::= { gs2310MVRStatus 5 }

gs2310MVRstatisticV2LeavesReceived OBJECT-TYPE
   SYNTAX      Counter32
   MAX-ACCESS  read-only
   STATUS      current
   DESCRIPTION
       "The number of Received V2 Leaves. "
   ::= { gs2310MVRStatus 6 }

gs2310LACP                                                     OBJECT IDENTIFIER ::= { gs2310Configuration 19 }

gs2310LACPConf                                                 OBJECT IDENTIFIER ::= { gs2310LACP 1 }

gs2310LACPPortConfigurationTable OBJECT-TYPE
   SYNTAX      SEQUENCE OF Gs2310LACPPortConfigurationEntry
   MAX-ACCESS  not-accessible
   STATUS      current
   DESCRIPTION
       " "
   ::= { gs2310LACPConf 1 }

gs2310LACPPortConfigurationEntry OBJECT-TYPE
   SYNTAX      Gs2310LACPPortConfigurationEntry
   MAX-ACCESS  not-accessible
   STATUS      current
   DESCRIPTION
       ""
   INDEX    { gs2310LACPPortConfigurationPort  }
   ::= { gs2310LACPPortConfigurationTable 1 }

Gs2310LACPPortConfigurationEntry ::= SEQUENCE {
    gs2310LACPPortConfigurationPort         Integer32,
    gs2310LACPPortConfigurationMode         INTEGER,
    gs2310LACPPortConfigurationKey          Integer32,
    gs2310LACPPortConfigurationRole         INTEGER
}

gs2310LACPPortConfigurationPort OBJECT-TYPE
   SYNTAX      Integer32(1..4095)
   MAX-ACCESS  not-accessible
   STATUS      current
   DESCRIPTION
       " "
   ::= { gs2310LACPPortConfigurationEntry 1 }

gs2310LACPPortConfigurationMode OBJECT-TYPE
   SYNTAX      INTEGER { disable(0), enable(1) }
   MAX-ACCESS  read-write
   STATUS      current
   DESCRIPTION
       "Enable/Disable LACP Mode."
   ::= { gs2310LACPPortConfigurationEntry 2 }

gs2310LACPPortConfigurationKey OBJECT-TYPE
   SYNTAX      Integer32(0..65535)
   MAX-ACCESS  read-write
   STATUS      current
   DESCRIPTION
       "LACP key : 1-65535. 0 : Auto"
   ::= { gs2310LACPPortConfigurationEntry 3 }

gs2310LACPPortConfigurationRole OBJECT-TYPE
   SYNTAX      INTEGER { passive(0), active(1) }
   MAX-ACCESS  read-write
   STATUS      current
   DESCRIPTION
       "0 : passive, Listen for LACP packets.
        1 : active, Initiate LACP negotiation, and transmit LACP packets each second"
   ::= { gs2310LACPPortConfigurationEntry 4 }

gs2310LACPSystemStatusTable OBJECT-TYPE
   SYNTAX      SEQUENCE OF Gs2310LACPSystemStatusEntry
   MAX-ACCESS  not-accessible
   STATUS      current
   DESCRIPTION
       " "
   ::= { gs2310LACP 2 }

gs2310LACPSystemStatusEntry OBJECT-TYPE
   SYNTAX      Gs2310LACPSystemStatusEntry
   MAX-ACCESS  not-accessible
   STATUS      current
   DESCRIPTION
       ""
   INDEX    { gs2310LACPSystemStatusIndex  }
   ::= { gs2310LACPSystemStatusTable 1 }

Gs2310LACPSystemStatusEntry ::= SEQUENCE {
   gs2310LACPSystemStatusIndex             Integer32,
   gs2310LACPSystemStatusAggrID            DisplayString,
   gs2310LACPSystemStatusPartnerSystemID   MacAddress,
   gs2310LACPSystemStatusPartnerKey        DisplayString,
   gs2310LACPSystemStatusLastchanged       DisplayString,
   gs2310LACPSystemStatusLocalPorts        DisplayString
}

gs2310LACPSystemStatusIndex OBJECT-TYPE
   SYNTAX      Integer32(1..12)
   MAX-ACCESS  not-accessible
   STATUS      current
   DESCRIPTION
       " "
   ::= { gs2310LACPSystemStatusEntry 1 }

gs2310LACPSystemStatusAggrID OBJECT-TYPE
   SYNTAX      DisplayString
   MAX-ACCESS  read-only
   STATUS      current
   DESCRIPTION
       "The Aggregation ID associated with this aggregation instance."
   ::= { gs2310LACPSystemStatusEntry 2 }

gs2310LACPSystemStatusPartnerSystemID OBJECT-TYPE
   SYNTAX      MacAddress
   MAX-ACCESS  read-only
   STATUS      current
   DESCRIPTION
       "The system ID (MAC address) of the aggregation partner."
   ::= { gs2310LACPSystemStatusEntry 3 }

gs2310LACPSystemStatusPartnerKey OBJECT-TYPE
   SYNTAX      DisplayString
   MAX-ACCESS  read-only
   STATUS      current
   DESCRIPTION
       " The Key that the partner has assigned to this aggregation ID. "
   ::= { gs2310LACPSystemStatusEntry 4 }

gs2310LACPSystemStatusLastchanged OBJECT-TYPE
   SYNTAX      DisplayString
   MAX-ACCESS  read-only
   STATUS      current
   DESCRIPTION
       " The time since this aggregation changed. "
   ::= { gs2310LACPSystemStatusEntry 5 }

gs2310LACPSystemStatusLocalPorts OBJECT-TYPE
   SYNTAX      DisplayString
   MAX-ACCESS  read-only
   STATUS      current
   DESCRIPTION
       " Shows which ports are a part of this aggregation for this switch. "
   ::= { gs2310LACPSystemStatusEntry 6 }

gs2310LACPStatusTable OBJECT-TYPE
   SYNTAX      SEQUENCE OF Gs2310LACPStatusEntry
   MAX-ACCESS  not-accessible
   STATUS      current
   DESCRIPTION
       " "
   ::= { gs2310LACP 3 }

gs2310LACPStatusEntry OBJECT-TYPE
   SYNTAX      Gs2310LACPStatusEntry
   MAX-ACCESS  not-accessible
   STATUS      current
   DESCRIPTION
       ""
   INDEX    { gs2310LACPStatusPort  }
   ::= { gs2310LACPStatusTable 1 }

Gs2310LACPStatusEntry ::= SEQUENCE {
   gs2310LACPStatusPort                Integer32,
   gs2310LACPStatusLACP                DisplayString,
   gs2310LACPStatusKey                 DisplayString,
   gs2310LACPStatusAggrID              DisplayString,
   gs2310LACPStatusPartnerSystemID     DisplayString,
   gs2310LACPStatusPartnerPort         DisplayString
}

gs2310LACPStatusPort OBJECT-TYPE
   SYNTAX      Integer32(1..4095)
   MAX-ACCESS  not-accessible
   STATUS      current
   DESCRIPTION
       " "
   ::= { gs2310LACPStatusEntry 1 }

gs2310LACPStatusLACP OBJECT-TYPE
   SYNTAX      DisplayString
   MAX-ACCESS  read-only
   STATUS      current
   DESCRIPTION
       "Enabled means that LACP is enabled and the port link is up.
        Disabled means that LACP is not enabled or that the port link is down.
        Backup means that the port could not join the aggregation group but will join if other port leaves.
        Meanwhile it's LACP status is disabled."
   ::= { gs2310LACPStatusEntry 2 }

gs2310LACPStatusKey OBJECT-TYPE
   SYNTAX      DisplayString
   MAX-ACCESS  read-only
   STATUS      current
   DESCRIPTION
       "The key assigned to this port. Only ports with the same key can aggregate together."
   ::= { gs2310LACPStatusEntry 3 }

gs2310LACPStatusAggrID	 OBJECT-TYPE
   SYNTAX      DisplayString
   MAX-ACCESS  read-only
   STATUS      current
   DESCRIPTION
       " The Aggregation ID assigned to this aggregation group. "
   ::= { gs2310LACPStatusEntry 4 }

gs2310LACPStatusPartnerSystemID OBJECT-TYPE
   SYNTAX      DisplayString
   MAX-ACCESS  read-only
   STATUS      current
   DESCRIPTION
       " The partner's System ID. "
   ::= { gs2310LACPStatusEntry 5 }

gs2310LACPStatusPartnerPort OBJECT-TYPE
   SYNTAX      DisplayString
   MAX-ACCESS  read-only
   STATUS      current
   DESCRIPTION
       " The partner's port number connected to this port. "
   ::= { gs2310LACPStatusEntry 6 }


gs2310LACPStatisticsTable OBJECT-TYPE
   SYNTAX      SEQUENCE OF Gs2310LACPStatisticsEntry
   MAX-ACCESS  not-accessible
   STATUS      current
   DESCRIPTION
       " "
   ::= { gs2310LACP 4 }

gs2310LACPStatisticsEntry OBJECT-TYPE
   SYNTAX      Gs2310LACPStatisticsEntry
   MAX-ACCESS  not-accessible
   STATUS      current
   DESCRIPTION
       ""
   INDEX    { gs2310LACPStatisticsPort  }
   ::= { gs2310LACPStatisticsTable 1 }

Gs2310LACPStatisticsEntry ::= SEQUENCE {
   gs2310LACPStatisticsPort        Integer32,
   gs2310LACPReceived              Counter32,
   gs2310LACPTransmitted           Counter32,
   gs2310LACPDiscardedUnknown      Counter32,
   gs2310LACPDiscardedIllegal      Counter32
}

gs2310LACPStatisticsPort OBJECT-TYPE
   SYNTAX      Integer32(1..4095)
   MAX-ACCESS  not-accessible
   STATUS      current
   DESCRIPTION
       " "
   ::= { gs2310LACPStatisticsEntry 1 }

gs2310LACPReceived OBJECT-TYPE
   SYNTAX      Counter32
   MAX-ACCESS  read-only
   STATUS      current
   DESCRIPTION
       "Shows how many LACP frames have been received at each port. "
   ::= { gs2310LACPStatisticsEntry 2 }

gs2310LACPTransmitted OBJECT-TYPE
   SYNTAX      Counter32
   MAX-ACCESS  read-only
   STATUS      current
   DESCRIPTION
       " Shows how many LACP frames have been sent from each port. "
   ::= { gs2310LACPStatisticsEntry 3 }

gs2310LACPDiscardedUnknown OBJECT-TYPE
   SYNTAX      Counter32
   MAX-ACCESS  read-only
   STATUS      current
   DESCRIPTION
       " Shows how many unknown LACP frames have been discarded at each port. "
   ::= { gs2310LACPStatisticsEntry 4 }

gs2310LACPDiscardedIllegal OBJECT-TYPE
   SYNTAX      Counter32
   MAX-ACCESS  read-only
   STATUS      current
   DESCRIPTION
       " Shows how many illegal LACP frames have been discarded at each port. "
   ::= { gs2310LACPStatisticsEntry 5 }

gs2310LACPStatisticsClear OBJECT-TYPE
   SYNTAX      INTEGER { none(0), clear(1) }
   MAX-ACCESS  read-write
   STATUS      current
   DESCRIPTION
       "default: 0
       0: none
       1: clear"
   ::= { gs2310LACP 5 }

gs2310STP                                                     OBJECT IDENTIFIER ::= { gs2310Configuration 20 }

gs2310STPBridgeBasicConf                                                 OBJECT IDENTIFIER ::= { gs2310STP 1 }

gs2310STPBridgeProtocolVersion OBJECT-TYPE
   SYNTAX      INTEGER { stp(0), rstp(2), mstp(3) }
   MAX-ACCESS  read-write
   STATUS      current
   DESCRIPTION
       "default: 3,
       0: stp
       2: rstp
       3: mstp"
   ::= { gs2310STPBridgeBasicConf 1 }

gs2310STPBridgePriority OBJECT-TYPE
   SYNTAX      Integer32(0..61440)
   MAX-ACCESS  read-write
   STATUS      current
   DESCRIPTION
       " default: 32768,
       STP bridge priority (0/4096/8192/12288/16384/20480/24576/28672/32768/36864/40960/45056/49152/53248/57344/61440)"
   ::= { gs2310STPBridgeBasicConf 2 }

gs2310STPBridgeForwardDelay OBJECT-TYPE
   SYNTAX      Integer32(4..30)
   MAX-ACCESS  read-write
   STATUS      current
   DESCRIPTION
       " Forward Delay default: 15, range: 4 - 30.
         MaxAge must be <= (FwdDelay-1)*2."
   ::= { gs2310STPBridgeBasicConf 3 }

gs2310STPBridgeMaxAge OBJECT-TYPE
   SYNTAX      Integer32(6..40)
   MAX-ACCESS  read-write
   STATUS      current
   DESCRIPTION
       " Max Age default: 20, range: 6 - 40.
         MaxAge must be <= (FwdDelay-1)*2"
   ::= { gs2310STPBridgeBasicConf 4 }

gs2310STPBridgeMaximumHopCount OBJECT-TYPE
   SYNTAX      Integer32(6..40)
   MAX-ACCESS  read-write
   STATUS      current
   DESCRIPTION
       " Maximum Hop Count default: 20, range: 6 - 40."
   ::= { gs2310STPBridgeBasicConf 5 }

gs2310STPBridgeTransmitHoldCount OBJECT-TYPE
   SYNTAX      Integer32(1..10)
   MAX-ACCESS  read-write
   STATUS      current
   DESCRIPTION
       " Transmit Hold Count default: 6, range: 1 - 10."
   ::= { gs2310STPBridgeBasicConf 6 }

gs2310STPBridgeAdvancedConf                                                 OBJECT IDENTIFIER ::= { gs2310STP 2 }

gs2310STPBridgeEdgePortBPDUFiltering OBJECT-TYPE
   SYNTAX      INTEGER { disable(0), enable(1) }
   MAX-ACCESS  read-write
   STATUS      current
   DESCRIPTION
       " default: 0,
        0: disable
        1: enable"
   ::= { gs2310STPBridgeAdvancedConf 1 }

gs2310STPBridgeEdgePortBPDUGuard OBJECT-TYPE
   SYNTAX      INTEGER { disable(0), enable(1) }
   MAX-ACCESS  read-write
   STATUS      current
   DESCRIPTION
       " default: 0,
        0: disable
        1: enable"
   ::= { gs2310STPBridgeAdvancedConf 2 }

gs2310STPBridgePortErrorRecoveryTimeout OBJECT-TYPE
   SYNTAX      Integer32(0..86400)
   MAX-ACCESS  read-write
   STATUS      current
   DESCRIPTION
       " Port Error Recovery Timeout disable: 0, range: 30 - 86400."
   ::= { gs2310STPBridgeAdvancedConf 3 }

gs2310STPMSTIConf                                                 OBJECT IDENTIFIER ::= { gs2310STP 3 }

gs2310STPMSTIConfigurationName OBJECT-TYPE
   SYNTAX      DisplayString (SIZE (1..32))
   MAX-ACCESS  read-write
   STATUS      current
   DESCRIPTION
       "A text string up to 32 characters long."
   ::= { gs2310STPMSTIConf 1 }

gs2310STPMSTIConfigurationRevision   OBJECT-TYPE
   SYNTAX      Integer32(0..65535)
   MAX-ACCESS  read-write
   STATUS      current
   DESCRIPTION
       " Configuration Revision default: 0, range: 0 - 65535."
   ::= { gs2310STPMSTIConf 2 }

gs2310STPMSTIMappingConf                                                 OBJECT IDENTIFIER ::= { gs2310STP 4 }

gs2310STPMSTI1VLANsMapped OBJECT-TYPE
   SYNTAX      DisplayString (SIZE (1..4096))
   MAX-ACCESS  read-write
   STATUS      current
   DESCRIPTION
       "The list of VLANs mapped to the MSTI1.
       The VLANs must be separated with comma or space.
       An unused MSTI should just be left empty. "
   ::= { gs2310STPMSTIMappingConf 1 }

gs2310STPMSTI2VLANsMapped OBJECT-TYPE
   SYNTAX      DisplayString (SIZE (1..4096))
   MAX-ACCESS  read-write
   STATUS      current
   DESCRIPTION
       "The list of VLANs mapped to the MSTI2.
       The VLANs must be separated with comma or space.
       An unused MSTI should just be left empty. "
   ::= { gs2310STPMSTIMappingConf 2 }

gs2310STPMSTI3VLANsMapped OBJECT-TYPE
   SYNTAX      DisplayString (SIZE (1..4096))
   MAX-ACCESS  read-write
   STATUS      current
   DESCRIPTION
       "The list of VLANs mapped to the MSTI3.
       The VLANs must be separated with comma or space.
       An unused MSTI should just be left empty. "
   ::= { gs2310STPMSTIMappingConf 3 }

gs2310STPMSTI4VLANsMapped OBJECT-TYPE
   SYNTAX      DisplayString (SIZE (1..4096))
   MAX-ACCESS  read-write
   STATUS      current
   DESCRIPTION
       "The list of VLANs mapped to the MSTI4.
       The VLANs must be separated with comma or space.
       An unused MSTI should just be left empty. "
   ::= { gs2310STPMSTIMappingConf 4 }

gs2310STPMSTI5VLANsMapped OBJECT-TYPE
   SYNTAX      DisplayString (SIZE (1..4096))
   MAX-ACCESS  read-write
   STATUS      current
   DESCRIPTION
       "The list of VLANs mapped to the MSTI5.
       The VLANs must be separated with comma or space.
       An unused MSTI should just be left empty. "
   ::= { gs2310STPMSTIMappingConf 5 }

gs2310STPMSTI6VLANsMapped OBJECT-TYPE
   SYNTAX      DisplayString (SIZE (1..4096))
   MAX-ACCESS  read-write
   STATUS      current
   DESCRIPTION
       "The list of VLANs mapped to the MSTI6.
       The VLANs must be separated with comma or space.
       An unused MSTI should just be left empty. "
   ::= { gs2310STPMSTIMappingConf 6 }

gs2310STPMSTI7VLANsMapped OBJECT-TYPE
   SYNTAX      DisplayString (SIZE (1..4096))
   MAX-ACCESS  read-write
   STATUS      current
   DESCRIPTION
       "The list of VLANs mapped to the MSTI7.
       The VLANs must be separated with comma or space.
       An unused MSTI should just be left empty. "
   ::= { gs2310STPMSTIMappingConf 7 }

gs2310STPMSTIPriority                                                 OBJECT IDENTIFIER ::= { gs2310STP 5 }

gs2310STPCISTPriority OBJECT-TYPE
   SYNTAX      Integer32(0..61440)
   MAX-ACCESS  read-write
   STATUS      current
   DESCRIPTION
       " default: 32768,
       STP CIST priority (0/4096/8192/12288/16384/20480/24576/28672/32768/36864/40960/45056/49152/53248/57344/61440)"
   ::= { gs2310STPMSTIPriority 1 }

gs2310STPMSTI1Priority OBJECT-TYPE
   SYNTAX      Integer32(0..61440)
   MAX-ACCESS  read-write
   STATUS      current
   DESCRIPTION
       " default: 32768,
       STP CIST priority (0/4096/8192/12288/16384/20480/24576/28672/32768/36864/40960/45056/49152/53248/57344/61440)"
   ::= { gs2310STPMSTIPriority 2 }

gs2310STPMSTI2Priority OBJECT-TYPE
   SYNTAX      Integer32(0..61440)
   MAX-ACCESS  read-write
   STATUS      current
   DESCRIPTION
       " default: 32768,
       STP CIST priority (0/4096/8192/12288/16384/20480/24576/28672/32768/36864/40960/45056/49152/53248/57344/61440)"
   ::= { gs2310STPMSTIPriority 3 }

gs2310STPMSTI3Priority OBJECT-TYPE
   SYNTAX      Integer32(0..61440)
   MAX-ACCESS  read-write
   STATUS      current
   DESCRIPTION
       " default: 32768,
       STP CIST priority (0/4096/8192/12288/16384/20480/24576/28672/32768/36864/40960/45056/49152/53248/57344/61440)"
   ::= { gs2310STPMSTIPriority 4 }

gs2310STPMSTI4Priority OBJECT-TYPE
   SYNTAX      Integer32(0..61440)
   MAX-ACCESS  read-write
   STATUS      current
   DESCRIPTION
       " default: 32768,
       STP CIST priority (0/4096/8192/12288/16384/20480/24576/28672/32768/36864/40960/45056/49152/53248/57344/61440)"
   ::= { gs2310STPMSTIPriority 5 }

gs2310STPMSTI5Priority OBJECT-TYPE
   SYNTAX      Integer32(0..61440)
   MAX-ACCESS  read-write
   STATUS      current
   DESCRIPTION
       " default: 32768,
       STP CIST priority (0/4096/8192/12288/16384/20480/24576/28672/32768/36864/40960/45056/49152/53248/57344/61440)"
   ::= { gs2310STPMSTIPriority 6 }

gs2310STPMSTI6Priority OBJECT-TYPE
   SYNTAX      Integer32(0..61440)
   MAX-ACCESS  read-write
   STATUS      current
   DESCRIPTION
       " default: 32768,
       STP CIST priority (0/4096/8192/12288/16384/20480/24576/28672/32768/36864/40960/45056/49152/53248/57344/61440)"
   ::= { gs2310STPMSTIPriority 7 }

gs2310STPMSTI7Priority OBJECT-TYPE
   SYNTAX      Integer32(0..61440)
   MAX-ACCESS  read-write
   STATUS      current
   DESCRIPTION
       " default: 32768,
       STP CIST priority (0/4096/8192/12288/16384/20480/24576/28672/32768/36864/40960/45056/49152/53248/57344/61440)"
   ::= { gs2310STPMSTIPriority 8 }

gs2310STPCISTPort                                                          OBJECT IDENTIFIER ::= { gs2310STP 6 }

gs2310STPCISTAggregatedPort                                                OBJECT IDENTIFIER ::= { gs2310STPCISTPort 1 }

gs2310STPCISTAggregatedPortSTPEnabled OBJECT-TYPE
   SYNTAX      INTEGER { disable(0), enable(1) }
   MAX-ACCESS  read-write
   STATUS      current
   DESCRIPTION
       " default: 0,
        0: disable
        1: enable"
   ::= { gs2310STPCISTAggregatedPort 1 }

gs2310STPCISTAggregatedPortPathCost OBJECT-TYPE
   SYNTAX      Integer32(0..200000000)
   MAX-ACCESS  read-write
   STATUS      current
   DESCRIPTION
       " Auto: 0,
        Specific Path Cost range: 1 - 200000000."
   ::= { gs2310STPCISTAggregatedPort 2 }

gs2310STPCISTAggregatedPortPriority OBJECT-TYPE
   SYNTAX      Integer32(0..240)
   MAX-ACCESS  read-write
   STATUS      current
   DESCRIPTION
       " default: 128,
       CIST Aggregated Port Priority (0/16/32/48/64/80/96/112/128/144/160/176/192/208/224/240)"
   ::= { gs2310STPCISTAggregatedPort 3 }

gs2310STPCISTAggregatedPortAdminEdge OBJECT-TYPE
   SYNTAX      INTEGER { non-edge(0), edge(1) }
   MAX-ACCESS  read-write
   STATUS      current
   DESCRIPTION
       " default: 0,
        0: non-edge
        1: edge"
   ::= { gs2310STPCISTAggregatedPort 4 }

gs2310STPCISTAggregatedPortAutoEdge OBJECT-TYPE
   SYNTAX      INTEGER { disable(0), enable(1) }
   MAX-ACCESS  read-write
   STATUS      current
   DESCRIPTION
       " default: 1,
        0: disable
        1: enable"
   ::= { gs2310STPCISTAggregatedPort 5 }

gs2310STPCISTAggregatedPortRestrictedRole OBJECT-TYPE
   SYNTAX      INTEGER { disable(0), enable(1) }
   MAX-ACCESS  read-write
   STATUS      current
   DESCRIPTION
       " default: 0,
        0: disable
        1: enable"
   ::= { gs2310STPCISTAggregatedPort 6 }

gs2310STPCISTAggregatedPortRestrictedTCN OBJECT-TYPE
   SYNTAX      INTEGER { disable(0), enable(1) }
   MAX-ACCESS  read-write
   STATUS      current
   DESCRIPTION
       " default: 0,
        0: disable
        1: enable"
   ::= { gs2310STPCISTAggregatedPort 7 }

gs2310STPCISTAggregatedPortBPDUGuard OBJECT-TYPE
   SYNTAX      INTEGER { disable(0), enable(1) }
   MAX-ACCESS  read-write
   STATUS      current
   DESCRIPTION
       " default: 0,
        0: disable
        1: enable"
   ::= { gs2310STPCISTAggregatedPort 8 }

gs2310STPCISTAggregatedPortPointtoPoint OBJECT-TYPE
   SYNTAX      INTEGER { forcetrue(0), forcefalse(1), auto(2) }
   MAX-ACCESS  read-write
   STATUS      current
   DESCRIPTION
       " default: 0,
        0: Forced True
        1: Forced False
        2: Auto"
   ::= { gs2310STPCISTAggregatedPort 9 }

gs2310STPCISTNormalPortTable OBJECT-TYPE
   SYNTAX      SEQUENCE OF Gs2310STPCISTNormalPortEntry
   MAX-ACCESS  not-accessible
   STATUS      current
   DESCRIPTION
       " Show CIST Normal Port Configurations. "
   ::= { gs2310STPCISTPort 2 }

gs2310STPCISTNormalPortEntry OBJECT-TYPE
   SYNTAX      Gs2310STPCISTNormalPortEntry
   MAX-ACCESS  not-accessible
   STATUS      current
   DESCRIPTION
       ""
   INDEX    { gs2310STPCISTNormalPortConfPort  }
   ::= { gs2310STPCISTNormalPortTable 1 }

Gs2310STPCISTNormalPortEntry ::= SEQUENCE {
   gs2310STPCISTNormalPortConfPort         Integer32,
   gs2310STPCISTNormalPortSTPEnabled       INTEGER,
   gs2310STPCISTNormalPortPathCost         Integer32,
   gs2310STPCISTNormalPortPriority         Integer32,
   gs2310STPCISTNormalPortAdminEdge        INTEGER,
   gs2310STPCISTNormalPortAutoEdge         INTEGER,
   gs2310STPCISTNormalPortRestrictedRole   INTEGER,
   gs2310STPCISTNormalPortRestrictedTCN    INTEGER,
   gs2310STPCISTNormalPortBPDUGuard        INTEGER,
   gs2310STPCISTNormalPortPointtoPoint     INTEGER
}

gs2310STPCISTNormalPortConfPort OBJECT-TYPE
   SYNTAX      Integer32(1..4095)
   MAX-ACCESS  not-accessible
   STATUS      current
   DESCRIPTION
       " port, range : 1 - port number. "
   ::= { gs2310STPCISTNormalPortEntry 1 }

gs2310STPCISTNormalPortSTPEnabled OBJECT-TYPE
   SYNTAX      INTEGER { disable(0), enable(1) }
   MAX-ACCESS  read-write
   STATUS      current
   DESCRIPTION
       " default: 0,
        0: disable
        1: enable"
   ::= { gs2310STPCISTNormalPortEntry 2 }

gs2310STPCISTNormalPortPathCost OBJECT-TYPE
   SYNTAX      Integer32(0..200000000)
   MAX-ACCESS  read-write
   STATUS      current
   DESCRIPTION
       " Auto: 0,
        Specific Path Cost range: 1 - 200000000."
   ::= { gs2310STPCISTNormalPortEntry 3 }

gs2310STPCISTNormalPortPriority OBJECT-TYPE
   SYNTAX      Integer32(0..240)
   MAX-ACCESS  read-write
   STATUS      current
   DESCRIPTION
       " default: 128,
       CIST Aggregated Port Priority (0/16/32/48/64/80/96/112/128/144/160/176/192/208/224/240)"
   ::= { gs2310STPCISTNormalPortEntry 4 }

gs2310STPCISTNormalPortAdminEdge OBJECT-TYPE
   SYNTAX      INTEGER { non-edge(0), edge(1) }
   MAX-ACCESS  read-write
   STATUS      current
   DESCRIPTION
       " default: 0,
        0: non-edge
        1: edge"
   ::= { gs2310STPCISTNormalPortEntry 5 }

gs2310STPCISTNormalPortAutoEdge OBJECT-TYPE
   SYNTAX      INTEGER { disable(0), enable(1) }
   MAX-ACCESS  read-write
   STATUS      current
   DESCRIPTION
       " default: 1,
        0: disable
        1: enable"
   ::= { gs2310STPCISTNormalPortEntry 6 }

gs2310STPCISTNormalPortRestrictedRole OBJECT-TYPE
   SYNTAX      INTEGER { disable(0), enable(1) }
   MAX-ACCESS  read-write
   STATUS      current
   DESCRIPTION
       " default: 0,
        0: disable
        1: enable"
   ::= { gs2310STPCISTNormalPortEntry 7 }

gs2310STPCISTNormalPortRestrictedTCN OBJECT-TYPE
   SYNTAX      INTEGER { disable(0), enable(1) }
   MAX-ACCESS  read-write
   STATUS      current
   DESCRIPTION
       " default: 0,
        0: disable
        1: enable"
   ::= { gs2310STPCISTNormalPortEntry 8 }

gs2310STPCISTNormalPortBPDUGuard OBJECT-TYPE
   SYNTAX      INTEGER { disable(0), enable(1) }
   MAX-ACCESS  read-write
   STATUS      current
   DESCRIPTION
       " default: 0,
        0: disable
        1: enable"
   ::= { gs2310STPCISTNormalPortEntry 9 }

gs2310STPCISTNormalPortPointtoPoint OBJECT-TYPE
   SYNTAX      INTEGER { forcetrue(0), forcefalse(1), auto(2) }
   MAX-ACCESS  read-write
   STATUS      current
   DESCRIPTION
       " default: 2,
        0: Forced True
        1: Forced False
        2: Auto"
   ::= { gs2310STPCISTNormalPortEntry 10 }


gs2310STPMSTIPort                                                          OBJECT IDENTIFIER ::= { gs2310STP 7 }

gs2310STPMSTI1Port                                                         OBJECT IDENTIFIER ::= { gs2310STPMSTIPort 1 }

gs2310STPMSTI1AggregatedPort                                                OBJECT IDENTIFIER ::= { gs2310STPMSTI1Port 1 }

gs2310STPMSTI1AggregatedPortPathCost OBJECT-TYPE
   SYNTAX      Integer32(0..200000000)
   MAX-ACCESS  read-write
   STATUS      current
   DESCRIPTION
       " Auto: 0,
        Specific Path Cost range: 1 - 200000000."
   ::= { gs2310STPMSTI1AggregatedPort 1 }

gs2310STPMSTI1AggregatedPortPriority OBJECT-TYPE
   SYNTAX      Integer32(0..240)
   MAX-ACCESS  read-write
   STATUS      current
   DESCRIPTION
       " default: 128,
       Aggregated Port Priority (0/16/32/48/64/80/96/112/128/144/160/176/192/208/224/240)"
   ::= { gs2310STPMSTI1AggregatedPort 2 }

gs2310STPMSTI1NormalPortTable OBJECT-TYPE
   SYNTAX      SEQUENCE OF Gs2310STPMSTI1NormalPortEntry
   MAX-ACCESS  not-accessible
   STATUS      current
   DESCRIPTION
       " Show MSTI1 Normal Port Configurations. "
   ::= { gs2310STPMSTI1Port 2 }

gs2310STPMSTI1NormalPortEntry OBJECT-TYPE
   SYNTAX      Gs2310STPMSTI1NormalPortEntry
   MAX-ACCESS  not-accessible
   STATUS      current
   DESCRIPTION
       ""
   INDEX    { gs2310STPMSTI1NormalPortConfPort  }
   ::= { gs2310STPMSTI1NormalPortTable 1 }

Gs2310STPMSTI1NormalPortEntry ::= SEQUENCE {
   gs2310STPMSTI1NormalPortConfPort         Integer32,
   gs2310STPMSTI1NormalPortPathCost         Integer32,
   gs2310STPMSTI1NormalPortPriority         Integer32
}

gs2310STPMSTI1NormalPortConfPort OBJECT-TYPE
   SYNTAX      Integer32(1..4095)
   MAX-ACCESS  not-accessible
   STATUS      current
   DESCRIPTION
       " port, range : 1 - port number. "
   ::= { gs2310STPMSTI1NormalPortEntry 1 }

gs2310STPMSTI1NormalPortPathCost OBJECT-TYPE
   SYNTAX      Integer32(0..200000000)
   MAX-ACCESS  read-write
   STATUS      current
   DESCRIPTION
       " Auto: 0,
        Specific Path Cost range: 1 - 200000000."
   ::= { gs2310STPMSTI1NormalPortEntry 2 }

gs2310STPMSTI1NormalPortPriority OBJECT-TYPE
   SYNTAX      Integer32(0..240)
   MAX-ACCESS  read-write
   STATUS      current
   DESCRIPTION
       " default: 128,
       Aggregated Port Priority (0/16/32/48/64/80/96/112/128/144/160/176/192/208/224/240)"
   ::= { gs2310STPMSTI1NormalPortEntry 3 }

gs2310STPMSTI2Port                                                          OBJECT IDENTIFIER ::= { gs2310STPMSTIPort 2 }

gs2310STPMSTI2AggregatedPort                                                OBJECT IDENTIFIER ::= { gs2310STPMSTI2Port 1 }

gs2310STPMSTI2AggregatedPortPathCost OBJECT-TYPE
   SYNTAX      Integer32(0..200000000)
   MAX-ACCESS  read-write
   STATUS      current
   DESCRIPTION
       " Auto: 0,
        Specific Path Cost range: 1 - 200000000."
   ::= { gs2310STPMSTI2AggregatedPort 1 }

gs2310STPMSTI2AggregatedPortPriority OBJECT-TYPE
   SYNTAX      Integer32(0..240)
   MAX-ACCESS  read-write
   STATUS      current
   DESCRIPTION
       " default: 128,
       Aggregated Port Priority (0/16/32/48/64/80/96/112/128/144/160/176/192/208/224/240)"
   ::= { gs2310STPMSTI2AggregatedPort 2 }

gs2310STPMSTI2NormalPortTable OBJECT-TYPE
   SYNTAX      SEQUENCE OF Gs2310STPMSTI2NormalPortEntry
   MAX-ACCESS  not-accessible
   STATUS      current
   DESCRIPTION
       " Show MSTI2 Normal Port Configurations. "
   ::= { gs2310STPMSTI2Port 2 }

gs2310STPMSTI2NormalPortEntry OBJECT-TYPE
   SYNTAX      Gs2310STPMSTI2NormalPortEntry
   MAX-ACCESS  not-accessible
   STATUS      current
   DESCRIPTION
       ""
   INDEX    { gs2310STPMSTI2NormalPortConfPort  }
   ::= { gs2310STPMSTI2NormalPortTable 1 }

Gs2310STPMSTI2NormalPortEntry ::= SEQUENCE {
   gs2310STPMSTI2NormalPortConfPort         Integer32,
   gs2310STPMSTI2NormalPortPathCost         Integer32,
   gs2310STPMSTI2NormalPortPriority         Integer32
}

gs2310STPMSTI2NormalPortConfPort OBJECT-TYPE
   SYNTAX      Integer32(1..4095)
   MAX-ACCESS  not-accessible
   STATUS      current
   DESCRIPTION
       " port, range : 1 - port number. "
   ::= { gs2310STPMSTI2NormalPortEntry 1 }

gs2310STPMSTI2NormalPortPathCost OBJECT-TYPE
   SYNTAX      Integer32(0..200000000)
   MAX-ACCESS  read-write
   STATUS      current
   DESCRIPTION
       " Auto: 0,
        Specific Path Cost range: 1 - 200000000."
   ::= { gs2310STPMSTI2NormalPortEntry 2 }

gs2310STPMSTI2NormalPortPriority OBJECT-TYPE
   SYNTAX      Integer32(0..240)
   MAX-ACCESS  read-write
   STATUS      current
   DESCRIPTION
       " default: 128,
       Aggregated Port Priority (0/16/32/48/64/80/96/112/128/144/160/176/192/208/224/240)"
   ::= { gs2310STPMSTI2NormalPortEntry 3 }

gs2310STPMSTI3Port                                                          OBJECT IDENTIFIER ::= { gs2310STPMSTIPort 3 }

gs2310STPMSTI3AggregatedPort                                                OBJECT IDENTIFIER ::= { gs2310STPMSTI3Port 1 }

gs2310STPMSTI3AggregatedPortPathCost OBJECT-TYPE
   SYNTAX      Integer32(0..200000000)
   MAX-ACCESS  read-write
   STATUS      current
   DESCRIPTION
       " Auto: 0,
        Specific Path Cost range: 1 - 200000000."
   ::= { gs2310STPMSTI3AggregatedPort 1 }

gs2310STPMSTI3AggregatedPortPriority OBJECT-TYPE
   SYNTAX      Integer32(0..240)
   MAX-ACCESS  read-write
   STATUS      current
   DESCRIPTION
       " default: 128,
       Aggregated Port Priority (0/16/32/48/64/80/96/112/128/144/160/176/192/208/224/240)"
   ::= { gs2310STPMSTI3AggregatedPort 2 }

gs2310STPMSTI3NormalPortTable OBJECT-TYPE
   SYNTAX      SEQUENCE OF Gs2310STPMSTI3NormalPortEntry
   MAX-ACCESS  not-accessible
   STATUS      current
   DESCRIPTION
       " Show MSTI3 Normal Port Configurations. "
   ::= { gs2310STPMSTI3Port 2 }

gs2310STPMSTI3NormalPortEntry OBJECT-TYPE
   SYNTAX      Gs2310STPMSTI3NormalPortEntry
   MAX-ACCESS  not-accessible
   STATUS      current
   DESCRIPTION
       ""
   INDEX    { gs2310STPMSTI3NormalPortConfPort  }
   ::= { gs2310STPMSTI3NormalPortTable 1 }

Gs2310STPMSTI3NormalPortEntry ::= SEQUENCE {
   gs2310STPMSTI3NormalPortConfPort         Integer32,
   gs2310STPMSTI3NormalPortPathCost         Integer32,
   gs2310STPMSTI3NormalPortPriority         Integer32
}

gs2310STPMSTI3NormalPortConfPort OBJECT-TYPE
   SYNTAX      Integer32(1..4095)
   MAX-ACCESS  not-accessible
   STATUS      current
   DESCRIPTION
       " port, range : 1 - port number. "
   ::= { gs2310STPMSTI3NormalPortEntry 1 }

gs2310STPMSTI3NormalPortPathCost OBJECT-TYPE
   SYNTAX      Integer32(0..200000000)
   MAX-ACCESS  read-write
   STATUS      current
   DESCRIPTION
       " Auto: 0,
        Specific Path Cost range: 1 - 200000000."
   ::= { gs2310STPMSTI3NormalPortEntry 2 }

gs2310STPMSTI3NormalPortPriority OBJECT-TYPE
   SYNTAX      Integer32(0..240)
   MAX-ACCESS  read-write
   STATUS      current
   DESCRIPTION
       " default: 128,
       Aggregated Port Priority (0/16/32/48/64/80/96/112/128/144/160/176/192/208/224/240)"
   ::= { gs2310STPMSTI3NormalPortEntry 3 }

gs2310STPMSTI4Port                                                          OBJECT IDENTIFIER ::= { gs2310STPMSTIPort 4 }

gs2310STPMSTI4AggregatedPort                                                OBJECT IDENTIFIER ::= { gs2310STPMSTI4Port 1 }

gs2310STPMSTI4AggregatedPortPathCost OBJECT-TYPE
   SYNTAX      Integer32(0..200000000)
   MAX-ACCESS  read-write
   STATUS      current
   DESCRIPTION
       " Auto: 0,
        Specific Path Cost range: 1 - 200000000."
   ::= { gs2310STPMSTI4AggregatedPort 1 }

gs2310STPMSTI4AggregatedPortPriority OBJECT-TYPE
   SYNTAX      Integer32(0..240)
   MAX-ACCESS  read-write
   STATUS      current
   DESCRIPTION
       " default: 128,
       Aggregated Port Priority (0/16/32/48/64/80/96/112/128/144/160/176/192/208/224/240)"
   ::= { gs2310STPMSTI4AggregatedPort 2 }

gs2310STPMSTI4NormalPortTable OBJECT-TYPE
   SYNTAX      SEQUENCE OF Gs2310STPMSTI4NormalPortEntry
   MAX-ACCESS  not-accessible
   STATUS      current
   DESCRIPTION
       " Show MSTI4 Normal Port Configurations. "
   ::= { gs2310STPMSTI4Port 2 }

gs2310STPMSTI4NormalPortEntry OBJECT-TYPE
   SYNTAX      Gs2310STPMSTI4NormalPortEntry
   MAX-ACCESS  not-accessible
   STATUS      current
   DESCRIPTION
       ""
   INDEX    { gs2310STPMSTI4NormalPortConfPort  }
   ::= { gs2310STPMSTI4NormalPortTable 1 }

Gs2310STPMSTI4NormalPortEntry ::= SEQUENCE {
   gs2310STPMSTI4NormalPortConfPort         Integer32,
   gs2310STPMSTI4NormalPortPathCost         Integer32,
   gs2310STPMSTI4NormalPortPriority         Integer32
}

gs2310STPMSTI4NormalPortConfPort OBJECT-TYPE
   SYNTAX      Integer32(1..4095)
   MAX-ACCESS  not-accessible
   STATUS      current
   DESCRIPTION
       " port, range : 1 - port number. "
   ::= { gs2310STPMSTI4NormalPortEntry 1 }

gs2310STPMSTI4NormalPortPathCost OBJECT-TYPE
   SYNTAX      Integer32(0..200000000)
   MAX-ACCESS  read-write
   STATUS      current
   DESCRIPTION
       " Auto: 0,
        Specific Path Cost range: 1 - 200000000."
   ::= { gs2310STPMSTI4NormalPortEntry 2 }

gs2310STPMSTI4NormalPortPriority OBJECT-TYPE
   SYNTAX      Integer32(0..240)
   MAX-ACCESS  read-write
   STATUS      current
   DESCRIPTION
       " default: 128,
       Aggregated Port Priority (0/16/32/48/64/80/96/112/128/144/160/176/192/208/224/240)"
   ::= { gs2310STPMSTI4NormalPortEntry 3 }

gs2310STPMSTI5Port                                                          OBJECT IDENTIFIER ::= { gs2310STPMSTIPort 5 }

gs2310STPMSTI5AggregatedPort                                                OBJECT IDENTIFIER ::= { gs2310STPMSTI5Port 1 }

gs2310STPMSTI5AggregatedPortPathCost OBJECT-TYPE
   SYNTAX      Integer32(0..200000000)
   MAX-ACCESS  read-write
   STATUS      current
   DESCRIPTION
       " Auto: 0,
        Specific Path Cost range: 1 - 200000000."
   ::= { gs2310STPMSTI5AggregatedPort 1 }

gs2310STPMSTI5AggregatedPortPriority OBJECT-TYPE
   SYNTAX      Integer32(0..240)
   MAX-ACCESS  read-write
   STATUS      current
   DESCRIPTION
       " default: 128,
       Aggregated Port Priority (0/16/32/48/64/80/96/112/128/144/160/176/192/208/224/240)"
   ::= { gs2310STPMSTI5AggregatedPort 2 }

gs2310STPMSTI5NormalPortTable OBJECT-TYPE
   SYNTAX      SEQUENCE OF Gs2310STPMSTI5NormalPortEntry
   MAX-ACCESS  not-accessible
   STATUS      current
   DESCRIPTION
       " Show MSTI5 Normal Port Configurations. "
   ::= { gs2310STPMSTI5Port 2 }

gs2310STPMSTI5NormalPortEntry OBJECT-TYPE
   SYNTAX      Gs2310STPMSTI5NormalPortEntry
   MAX-ACCESS  not-accessible
   STATUS      current
   DESCRIPTION
       ""
   INDEX    { gs2310STPMSTI5NormalPortConfPort  }
   ::= { gs2310STPMSTI5NormalPortTable 1 }

Gs2310STPMSTI5NormalPortEntry ::= SEQUENCE {
   gs2310STPMSTI5NormalPortConfPort         Integer32,
   gs2310STPMSTI5NormalPortPathCost         Integer32,
   gs2310STPMSTI5NormalPortPriority         Integer32
}

gs2310STPMSTI5NormalPortConfPort OBJECT-TYPE
   SYNTAX      Integer32(1..4095)
   MAX-ACCESS  not-accessible
   STATUS      current
   DESCRIPTION
       " port, range : 1 - port number. "
   ::= { gs2310STPMSTI5NormalPortEntry 1 }

gs2310STPMSTI5NormalPortPathCost OBJECT-TYPE
   SYNTAX      Integer32(0..200000000)
   MAX-ACCESS  read-write
   STATUS      current
   DESCRIPTION
       " Auto: 0,
        Specific Path Cost range: 1 - 200000000."
   ::= { gs2310STPMSTI5NormalPortEntry 2 }

gs2310STPMSTI5NormalPortPriority OBJECT-TYPE
   SYNTAX      Integer32(0..240)
   MAX-ACCESS  read-write
   STATUS      current
   DESCRIPTION
       " default: 128,
       Aggregated Port Priority (0/16/32/48/64/80/96/112/128/144/160/176/192/208/224/240)"
   ::= { gs2310STPMSTI5NormalPortEntry 3 }

gs2310STPMSTI6Port                                                          OBJECT IDENTIFIER ::= { gs2310STPMSTIPort 6 }

gs2310STPMSTI6AggregatedPort                                                OBJECT IDENTIFIER ::= { gs2310STPMSTI6Port 1 }

gs2310STPMSTI6AggregatedPortPathCost OBJECT-TYPE
   SYNTAX      Integer32(0..200000000)
   MAX-ACCESS  read-write
   STATUS      current
   DESCRIPTION
       " Auto: 0,
        Specific Path Cost range: 1 - 200000000."
   ::= { gs2310STPMSTI6AggregatedPort 1 }

gs2310STPMSTI6AggregatedPortPriority OBJECT-TYPE
   SYNTAX      Integer32(0..240)
   MAX-ACCESS  read-write
   STATUS      current
   DESCRIPTION
       " default: 128,
       Aggregated Port Priority (0/16/32/48/64/80/96/112/128/144/160/176/192/208/224/240)"
   ::= { gs2310STPMSTI6AggregatedPort 2 }

gs2310STPMSTI6NormalPortTable OBJECT-TYPE
   SYNTAX      SEQUENCE OF Gs2310STPMSTI6NormalPortEntry
   MAX-ACCESS  not-accessible
   STATUS      current
   DESCRIPTION
       " Show MSTI6 Normal Port Configurations. "
   ::= { gs2310STPMSTI6Port 2 }

gs2310STPMSTI6NormalPortEntry OBJECT-TYPE
   SYNTAX      Gs2310STPMSTI6NormalPortEntry
   MAX-ACCESS  not-accessible
   STATUS      current
   DESCRIPTION
       ""
   INDEX    { gs2310STPMSTI6NormalPortConfPort  }
   ::= { gs2310STPMSTI6NormalPortTable 1 }

Gs2310STPMSTI6NormalPortEntry ::= SEQUENCE {
   gs2310STPMSTI6NormalPortConfPort         Integer32,
   gs2310STPMSTI6NormalPortPathCost         Integer32,
   gs2310STPMSTI6NormalPortPriority         Integer32
}

gs2310STPMSTI6NormalPortConfPort OBJECT-TYPE
   SYNTAX      Integer32(1..4095)
   MAX-ACCESS  not-accessible
   STATUS      current
   DESCRIPTION
       " port, range : 1 - port number. "
   ::= { gs2310STPMSTI6NormalPortEntry 1 }

gs2310STPMSTI6NormalPortPathCost OBJECT-TYPE
   SYNTAX      Integer32(0..200000000)
   MAX-ACCESS  read-write
   STATUS      current
   DESCRIPTION
       " Auto: 0,
        Specific Path Cost range: 1 - 200000000."
   ::= { gs2310STPMSTI6NormalPortEntry 2 }

gs2310STPMSTI6NormalPortPriority OBJECT-TYPE
   SYNTAX      Integer32(0..240)
   MAX-ACCESS  read-write
   STATUS      current
   DESCRIPTION
       " default: 128,
       Aggregated Port Priority (0/16/32/48/64/80/96/112/128/144/160/176/192/208/224/240)"
   ::= { gs2310STPMSTI6NormalPortEntry 3 }

gs2310STPMSTI7Port                                                          OBJECT IDENTIFIER ::= { gs2310STPMSTIPort 7 }

gs2310STPMSTI7AggregatedPort                                                OBJECT IDENTIFIER ::= { gs2310STPMSTI7Port 1 }

gs2310STPMSTI7AggregatedPortPathCost OBJECT-TYPE
   SYNTAX      Integer32(0..200000000)
   MAX-ACCESS  read-write
   STATUS      current
   DESCRIPTION
       " Auto: 0,
        Specific Path Cost range: 1 - 200000000."
   ::= { gs2310STPMSTI7AggregatedPort 1 }

gs2310STPMSTI7AggregatedPortPriority OBJECT-TYPE
   SYNTAX      Integer32(0..240)
   MAX-ACCESS  read-write
   STATUS      current
   DESCRIPTION
       " default: 128,
       Aggregated Port Priority (0/16/32/48/64/80/96/112/128/144/160/176/192/208/224/240)"
   ::= { gs2310STPMSTI7AggregatedPort 2 }

gs2310STPMSTI7NormalPortTable OBJECT-TYPE
   SYNTAX      SEQUENCE OF Gs2310STPMSTI7NormalPortEntry
   MAX-ACCESS  not-accessible
   STATUS      current
   DESCRIPTION
       " Show MSTI7 Normal Port Configurations. "
   ::= { gs2310STPMSTI7Port 2 }

gs2310STPMSTI7NormalPortEntry OBJECT-TYPE
   SYNTAX      Gs2310STPMSTI7NormalPortEntry
   MAX-ACCESS  not-accessible
   STATUS      current
   DESCRIPTION
       ""
   INDEX    { gs2310STPMSTI7NormalPortConfPort  }
   ::= { gs2310STPMSTI7NormalPortTable 1 }

Gs2310STPMSTI7NormalPortEntry ::= SEQUENCE {
   gs2310STPMSTI7NormalPortConfPort         Integer32,
   gs2310STPMSTI7NormalPortPathCost         Integer32,
   gs2310STPMSTI7NormalPortPriority         Integer32
}

gs2310STPMSTI7NormalPortConfPort OBJECT-TYPE
   SYNTAX      Integer32(1..4095)
   MAX-ACCESS  not-accessible
   STATUS      current
   DESCRIPTION
       " port, range : 1 - port number. "
   ::= { gs2310STPMSTI7NormalPortEntry 1 }

gs2310STPMSTI7NormalPortPathCost OBJECT-TYPE
   SYNTAX      Integer32(0..200000000)
   MAX-ACCESS  read-write
   STATUS      current
   DESCRIPTION
       " Auto: 0,
        Specific Path Cost range: 1 - 200000000."
   ::= { gs2310STPMSTI7NormalPortEntry 2 }

gs2310STPMSTI7NormalPortPriority OBJECT-TYPE
   SYNTAX      Integer32(0..240)
   MAX-ACCESS  read-write
   STATUS      current
   DESCRIPTION
       " default: 128,
       Aggregated Port Priority (0/16/32/48/64/80/96/112/128/144/160/176/192/208/224/240)"
   ::= { gs2310STPMSTI7NormalPortEntry 3 }


gs2310STPBridgeStatus                                                      OBJECT IDENTIFIER ::= { gs2310STP 8 }

gs2310CISTBridgeSTP                                                        OBJECT IDENTIFIER ::= { gs2310STPBridgeStatus 1 }

gs2310CISTBridgeSTPStatus                                                  OBJECT IDENTIFIER ::= { gs2310CISTBridgeSTP 1 }

gs2310CISTBridgeInstance OBJECT-TYPE
   SYNTAX       DisplayString
   MAX-ACCESS   read-only
   STATUS       current
   DESCRIPTION
       "The Bridge instance - CIST, MST1, ..."
   ::= { gs2310CISTBridgeSTPStatus 1 }

gs2310CISTBridgeID OBJECT-TYPE
   SYNTAX       DisplayString
   MAX-ACCESS   read-only
   STATUS       current
   DESCRIPTION
       "The Bridge ID of this Bridge instance."
   ::= { gs2310CISTBridgeSTPStatus 2 }

gs2310CISTRootID OBJECT-TYPE
   SYNTAX       DisplayString
   MAX-ACCESS   read-only
   STATUS       current
   DESCRIPTION
       "The Bridge ID of the currently elected root bridge."
   ::= { gs2310CISTBridgeSTPStatus 3 }

gs2310CISTRootPort OBJECT-TYPE
   SYNTAX       DisplayString
   MAX-ACCESS   read-only
   STATUS       current
   DESCRIPTION
       "The switch port currently assigned the root port role."
   ::= { gs2310CISTBridgeSTPStatus 4 }

gs2310CISTRootCost OBJECT-TYPE
   SYNTAX       Integer32(0..200000000)
   MAX-ACCESS   read-only
   STATUS       current
   DESCRIPTION
       "Root Path Cost."
   ::= { gs2310CISTBridgeSTPStatus 5 }

gs2310CISTRegionalRoot OBJECT-TYPE
   SYNTAX       DisplayString
   MAX-ACCESS   read-only
   STATUS       current
   DESCRIPTION
       "The Bridge ID of the currently elected regional root bridge, inside the MSTP region of this bridge."
   ::= { gs2310CISTBridgeSTPStatus 6 }

gs2310CISTInternalRootCost OBJECT-TYPE
   SYNTAX       Integer32(0..200000000)
   MAX-ACCESS   read-only
   STATUS       current
   DESCRIPTION
       "The Regional Root Path Cost."
   ::= { gs2310CISTBridgeSTPStatus 7 }

gs2310CISTTopologyFlag OBJECT-TYPE
   SYNTAX       DisplayString
   MAX-ACCESS   read-only
   STATUS       current
   DESCRIPTION
       "The current state of the Topology Change Flag of this Bridge instance."
   ::= { gs2310CISTBridgeSTPStatus 8 }

gs2310CISTTopologyChangeCount OBJECT-TYPE
   SYNTAX       Counter32
   MAX-ACCESS   read-only
   STATUS       current
   DESCRIPTION
       "The number of times where the topology change flag has been set."
   ::= { gs2310CISTBridgeSTPStatus 9 }

gs2310CISTTopologyChangeLast OBJECT-TYPE
   SYNTAX       DisplayString
   MAX-ACCESS   read-only
   STATUS       current
   DESCRIPTION
       "The time passed since the Topology Flag was last set."
   ::= { gs2310CISTBridgeSTPStatus 10 }

gs2310CISTPortStateTable OBJECT-TYPE
   SYNTAX      SEQUENCE OF Gs2310CISTPortStateEntry
   MAX-ACCESS  not-accessible
   STATUS      current
   DESCRIPTION
       " Show CIST Ports and Aggregations State Configurations. "
   ::= { gs2310CISTBridgeSTP 2 }

gs2310CISTPortStateEntry OBJECT-TYPE
   SYNTAX      Gs2310CISTPortStateEntry
   MAX-ACCESS  not-accessible
   STATUS      current
   DESCRIPTION
       ""
   INDEX    { gs2310CISTPortStateIndex  }
   ::= { gs2310CISTPortStateTable 1 }

Gs2310CISTPortStateEntry ::= SEQUENCE {
   gs2310CISTPortStateIndex        Integer32,
   gs2310CISTPortStatePort         DisplayString,
   gs2310CISTPortStatePortID       DisplayString,
   gs2310CISTPortStateRole         DisplayString,
   gs2310CISTPortStateState        DisplayString,
   gs2310CISTPortStatePathCost     Integer32,
   gs2310CISTPortStateEdge         DisplayString,
   gs2310CISTPortStatePoint2Point  DisplayString,
   gs2310CISTPortStateUptime       DisplayString
}

gs2310CISTPortStateIndex OBJECT-TYPE
   SYNTAX      Integer32(1..4095)
   MAX-ACCESS  not-accessible
   STATUS      current
   DESCRIPTION
       "table index."
   ::= { gs2310CISTPortStateEntry 1 }

gs2310CISTPortStatePort OBJECT-TYPE
   SYNTAX      DisplayString
   MAX-ACCESS  read-only
   STATUS      current
   DESCRIPTION
       "The switch port number of the logical STP port."
   ::= { gs2310CISTPortStateEntry 2 }

gs2310CISTPortStatePortID OBJECT-TYPE
   SYNTAX      DisplayString
   MAX-ACCESS  read-only
   STATUS      current
   DESCRIPTION
       "The port id as used by the STP protocol.
        This is the priority part and the logical port index of the bridge port."
   ::= { gs2310CISTPortStateEntry 3 }

gs2310CISTPortStateRole OBJECT-TYPE
   SYNTAX      DisplayString
   MAX-ACCESS  read-only
   STATUS      current
   DESCRIPTION
       "The current STP port role."
   ::= { gs2310CISTPortStateEntry 4 }

gs2310CISTPortStateState OBJECT-TYPE
   SYNTAX      DisplayString
   MAX-ACCESS  read-only
   STATUS      current
   DESCRIPTION
       "The current STP port state."
   ::= { gs2310CISTPortStateEntry 5 }

gs2310CISTPortStatePathCost OBJECT-TYPE
   SYNTAX      Integer32(0..200000000)
   MAX-ACCESS  read-only
   STATUS      current
   DESCRIPTION
       "The current STP port path cost."
   ::= { gs2310CISTPortStateEntry 6 }

gs2310CISTPortStateEdge OBJECT-TYPE
   SYNTAX      DisplayString
   MAX-ACCESS  read-only
   STATUS      current
   DESCRIPTION
       "The current STP port Edge Flag."
   ::= { gs2310CISTPortStateEntry 7 }

gs2310CISTPortStatePoint2Point OBJECT-TYPE
   SYNTAX      DisplayString
   MAX-ACCESS  read-only
   STATUS      current
   DESCRIPTION
       "The current STP port point-to-point flag."
   ::= { gs2310CISTPortStateEntry 8 }

gs2310CISTPortStateUptime OBJECT-TYPE
   SYNTAX      DisplayString
   MAX-ACCESS  read-only
   STATUS      current
   DESCRIPTION
       "The time since the bridge port was last initialized."
   ::= { gs2310CISTPortStateEntry 9 }

gs2310MSTI1BridgeSTP                                                        OBJECT IDENTIFIER ::= { gs2310STPBridgeStatus 2 }

gs2310MSTI1BridgeSTPStatus                                                  OBJECT IDENTIFIER ::= { gs2310MSTI1BridgeSTP 1 }

gs2310MSTI1BridgeInstance OBJECT-TYPE
   SYNTAX       DisplayString
   MAX-ACCESS   read-only
   STATUS       current
   DESCRIPTION
       "The Bridge instance - CIST, MST1, ..."
   ::= { gs2310MSTI1BridgeSTPStatus 1 }

gs2310MSTI1BridgeID OBJECT-TYPE
   SYNTAX       DisplayString
   MAX-ACCESS   read-only
   STATUS       current
   DESCRIPTION
       "The Bridge ID of this Bridge instance."
   ::= { gs2310MSTI1BridgeSTPStatus 2 }

gs2310MSTI1RootID OBJECT-TYPE
   SYNTAX       DisplayString
   MAX-ACCESS   read-only
   STATUS       current
   DESCRIPTION
       "The Bridge ID of the currently elected root bridge."
   ::= { gs2310MSTI1BridgeSTPStatus 3 }

gs2310MSTI1RootPort OBJECT-TYPE
   SYNTAX       DisplayString
   MAX-ACCESS   read-only
   STATUS       current
   DESCRIPTION
       "The switch port currently assigned the root port role."
   ::= { gs2310MSTI1BridgeSTPStatus 4 }

gs2310MSTI1RootCost OBJECT-TYPE
   SYNTAX       Integer32(0..200000000)
   MAX-ACCESS   read-only
   STATUS       current
   DESCRIPTION
       "Root Path Cost."
   ::= { gs2310MSTI1BridgeSTPStatus 5 }

gs2310MSTI1TopologyFlag OBJECT-TYPE
   SYNTAX       DisplayString
   MAX-ACCESS   read-only
   STATUS       current
   DESCRIPTION
       "The current state of the Topology Change Flag of this Bridge instance."
   ::= { gs2310MSTI1BridgeSTPStatus 8 }

gs2310MSTI1TopologyChangeCount OBJECT-TYPE
   SYNTAX       Counter32
   MAX-ACCESS   read-only
   STATUS       current
   DESCRIPTION
       "The number of times where the topology change flag has been set."
   ::= { gs2310MSTI1BridgeSTPStatus 9 }

gs2310MSTI1TopologyChangeLast OBJECT-TYPE
   SYNTAX       DisplayString
   MAX-ACCESS   read-only
   STATUS       current
   DESCRIPTION
       "The time passed since the Topology Flag was last set."
   ::= { gs2310MSTI1BridgeSTPStatus 10 }

gs2310MSTI1PortStateTable OBJECT-TYPE
   SYNTAX      SEQUENCE OF Gs2310MSTI1PortStateEntry
   MAX-ACCESS  not-accessible
   STATUS      current
   DESCRIPTION
       " Show MSTI1 Ports and Aggregations State Configurations. "
   ::= { gs2310MSTI1BridgeSTP 2 }

gs2310MSTI1PortStateEntry OBJECT-TYPE
   SYNTAX      Gs2310MSTI1PortStateEntry
   MAX-ACCESS  not-accessible
   STATUS      current
   DESCRIPTION
       ""
   INDEX    { gs2310MSTI1PortStateIndex  }
   ::= { gs2310MSTI1PortStateTable 1 }

Gs2310MSTI1PortStateEntry ::= SEQUENCE {
   gs2310MSTI1PortStateIndex        Integer32,
   gs2310MSTI1PortStatePort         DisplayString,
   gs2310MSTI1PortStatePortID       DisplayString,
   gs2310MSTI1PortStateRole         DisplayString,
   gs2310MSTI1PortStateState        DisplayString,
   gs2310MSTI1PortStatePathCost     Integer32,
   gs2310MSTI1PortStateEdge         DisplayString,
   gs2310MSTI1PortStatePoint2Point  DisplayString,
   gs2310MSTI1PortStateUptime       DisplayString
}

gs2310MSTI1PortStateIndex OBJECT-TYPE
   SYNTAX      Integer32(1..4095)
   MAX-ACCESS  not-accessible
   STATUS      current
   DESCRIPTION
       "table index."
   ::= { gs2310MSTI1PortStateEntry 1 }

gs2310MSTI1PortStatePort OBJECT-TYPE
   SYNTAX      DisplayString
   MAX-ACCESS  read-only
   STATUS      current
   DESCRIPTION
       "The switch port number of the logical STP port."
   ::= { gs2310MSTI1PortStateEntry 2 }

gs2310MSTI1PortStatePortID OBJECT-TYPE
   SYNTAX      DisplayString
   MAX-ACCESS  read-only
   STATUS      current
   DESCRIPTION
       "The port id as used by the STP protocol.
        This is the priority part and the logical port index of the bridge port."
   ::= { gs2310MSTI1PortStateEntry 3 }

gs2310MSTI1PortStateRole OBJECT-TYPE
   SYNTAX      DisplayString
   MAX-ACCESS  read-only
   STATUS      current
   DESCRIPTION
       "The current STP port role."
   ::= { gs2310MSTI1PortStateEntry 4 }

gs2310MSTI1PortStateState OBJECT-TYPE
   SYNTAX      DisplayString
   MAX-ACCESS  read-only
   STATUS      current
   DESCRIPTION
       "The current STP port state."
   ::= { gs2310MSTI1PortStateEntry 5 }

gs2310MSTI1PortStatePathCost OBJECT-TYPE
   SYNTAX      Integer32(0..200000000)
   MAX-ACCESS  read-only
   STATUS      current
   DESCRIPTION
       "The current STP port path cost."
   ::= { gs2310MSTI1PortStateEntry 6 }

gs2310MSTI1PortStateEdge OBJECT-TYPE
   SYNTAX      DisplayString
   MAX-ACCESS  read-only
   STATUS      current
   DESCRIPTION
       "The current STP port Edge Flag."
   ::= { gs2310MSTI1PortStateEntry 7 }

gs2310MSTI1PortStatePoint2Point OBJECT-TYPE
   SYNTAX      DisplayString
   MAX-ACCESS  read-only
   STATUS      current
   DESCRIPTION
       "The current STP port point-to-point flag."
   ::= { gs2310MSTI1PortStateEntry 8 }

gs2310MSTI1PortStateUptime OBJECT-TYPE
   SYNTAX      DisplayString
   MAX-ACCESS  read-only
   STATUS      current
   DESCRIPTION
       "The time since the bridge port was last initialized."
   ::= { gs2310MSTI1PortStateEntry 9 }

gs2310MSTI2BridgeSTP                                                        OBJECT IDENTIFIER ::= { gs2310STPBridgeStatus 3 }

gs2310MSTI2BridgeSTPStatus                                                  OBJECT IDENTIFIER ::= { gs2310MSTI2BridgeSTP 1 }

gs2310MSTI2BridgeInstance OBJECT-TYPE
   SYNTAX       DisplayString
   MAX-ACCESS   read-only
   STATUS       current
   DESCRIPTION
       "The Bridge instance - CIST, MST1, ..."
   ::= { gs2310MSTI2BridgeSTPStatus 1 }

gs2310MSTI2BridgeID OBJECT-TYPE
   SYNTAX       DisplayString
   MAX-ACCESS   read-only
   STATUS       current
   DESCRIPTION
       "The Bridge ID of this Bridge instance."
   ::= { gs2310MSTI2BridgeSTPStatus 2 }

gs2310MSTI2RootID OBJECT-TYPE
   SYNTAX       DisplayString
   MAX-ACCESS   read-only
   STATUS       current
   DESCRIPTION
       "The Bridge ID of the currently elected root bridge."
   ::= { gs2310MSTI2BridgeSTPStatus 3 }

gs2310MSTI2RootPort OBJECT-TYPE
   SYNTAX       DisplayString
   MAX-ACCESS   read-only
   STATUS       current
   DESCRIPTION
       "The switch port currently assigned the root port role."
   ::= { gs2310MSTI2BridgeSTPStatus 4 }

gs2310MSTI2RootCost OBJECT-TYPE
   SYNTAX       Integer32(0..200000000)
   MAX-ACCESS   read-only
   STATUS       current
   DESCRIPTION
       "Root Path Cost."
   ::= { gs2310MSTI2BridgeSTPStatus 5 }

gs2310MSTI2TopologyFlag OBJECT-TYPE
   SYNTAX       DisplayString
   MAX-ACCESS   read-only
   STATUS       current
   DESCRIPTION
       "The current state of the Topology Change Flag of this Bridge instance."
   ::= { gs2310MSTI2BridgeSTPStatus 8 }

gs2310MSTI2TopologyChangeCount OBJECT-TYPE
   SYNTAX       Counter32
   MAX-ACCESS   read-only
   STATUS       current
   DESCRIPTION
       "The number of times where the topology change flag has been set."
   ::= { gs2310MSTI2BridgeSTPStatus 9 }

gs2310MSTI2TopologyChangeLast OBJECT-TYPE
   SYNTAX       DisplayString
   MAX-ACCESS   read-only
   STATUS       current
   DESCRIPTION
       "The time passed since the Topology Flag was last set."
   ::= { gs2310MSTI2BridgeSTPStatus 10 }

gs2310MSTI2PortStateTable OBJECT-TYPE
   SYNTAX      SEQUENCE OF Gs2310MSTI2PortStateEntry
   MAX-ACCESS  not-accessible
   STATUS      current
   DESCRIPTION
       " Show MSTI2 Ports and Aggregations State Configurations. "
   ::= { gs2310MSTI2BridgeSTP 2 }

gs2310MSTI2PortStateEntry OBJECT-TYPE
   SYNTAX      Gs2310MSTI2PortStateEntry
   MAX-ACCESS  not-accessible
   STATUS      current
   DESCRIPTION
       ""
   INDEX    { gs2310MSTI2PortStateIndex  }
   ::= { gs2310MSTI2PortStateTable 1 }

Gs2310MSTI2PortStateEntry ::= SEQUENCE {
   gs2310MSTI2PortStateIndex        Integer32,
   gs2310MSTI2PortStatePort         DisplayString,
   gs2310MSTI2PortStatePortID       DisplayString,
   gs2310MSTI2PortStateRole         DisplayString,
   gs2310MSTI2PortStateState        DisplayString,
   gs2310MSTI2PortStatePathCost     Integer32,
   gs2310MSTI2PortStateEdge         DisplayString,
   gs2310MSTI2PortStatePoint2Point  DisplayString,
   gs2310MSTI2PortStateUptime       DisplayString
}

gs2310MSTI2PortStateIndex OBJECT-TYPE
   SYNTAX      Integer32(1..4095)
   MAX-ACCESS  not-accessible
   STATUS      current
   DESCRIPTION
       "table index."
   ::= { gs2310MSTI2PortStateEntry 1 }

gs2310MSTI2PortStatePort OBJECT-TYPE
   SYNTAX      DisplayString
   MAX-ACCESS  read-only
   STATUS      current
   DESCRIPTION
       "The switch port number of the logical STP port."
   ::= { gs2310MSTI2PortStateEntry 2 }

gs2310MSTI2PortStatePortID OBJECT-TYPE
   SYNTAX      DisplayString
   MAX-ACCESS  read-only
   STATUS      current
   DESCRIPTION
       "The port id as used by the STP protocol.
        This is the priority part and the logical port index of the bridge port."
   ::= { gs2310MSTI2PortStateEntry 3 }

gs2310MSTI2PortStateRole OBJECT-TYPE
   SYNTAX      DisplayString
   MAX-ACCESS  read-only
   STATUS      current
   DESCRIPTION
       "The current STP port role."
   ::= { gs2310MSTI2PortStateEntry 4 }

gs2310MSTI2PortStateState OBJECT-TYPE
   SYNTAX      DisplayString
   MAX-ACCESS  read-only
   STATUS      current
   DESCRIPTION
       "The current STP port state."
   ::= { gs2310MSTI2PortStateEntry 5 }

gs2310MSTI2PortStatePathCost OBJECT-TYPE
   SYNTAX      Integer32(0..200000000)
   MAX-ACCESS  read-only
   STATUS      current
   DESCRIPTION
       "The current STP port path cost."
   ::= { gs2310MSTI2PortStateEntry 6 }

gs2310MSTI2PortStateEdge OBJECT-TYPE
   SYNTAX      DisplayString
   MAX-ACCESS  read-only
   STATUS      current
   DESCRIPTION
       "The current STP port Edge Flag."
   ::= { gs2310MSTI2PortStateEntry 7 }

gs2310MSTI2PortStatePoint2Point OBJECT-TYPE
   SYNTAX      DisplayString
   MAX-ACCESS  read-only
   STATUS      current
   DESCRIPTION
       "The current STP port point-to-point flag."
   ::= { gs2310MSTI2PortStateEntry 8 }

gs2310MSTI2PortStateUptime OBJECT-TYPE
   SYNTAX      DisplayString
   MAX-ACCESS  read-only
   STATUS      current
   DESCRIPTION
       "The time since the bridge port was last initialized."
   ::= { gs2310MSTI2PortStateEntry 9 }

gs2310MSTI3BridgeSTP                                                        OBJECT IDENTIFIER ::= { gs2310STPBridgeStatus 4 }

gs2310MSTI3BridgeSTPStatus                                                  OBJECT IDENTIFIER ::= { gs2310MSTI3BridgeSTP 1 }

gs2310MSTI3BridgeInstance OBJECT-TYPE
   SYNTAX       DisplayString
   MAX-ACCESS   read-only
   STATUS       current
   DESCRIPTION
       "The Bridge instance - CIST, MST1, ..."
   ::= { gs2310MSTI3BridgeSTPStatus 1 }

gs2310MSTI3BridgeID OBJECT-TYPE
   SYNTAX       DisplayString
   MAX-ACCESS   read-only
   STATUS       current
   DESCRIPTION
       "The Bridge ID of this Bridge instance."
   ::= { gs2310MSTI3BridgeSTPStatus 2 }

gs2310MSTI3RootID OBJECT-TYPE
   SYNTAX       DisplayString
   MAX-ACCESS   read-only
   STATUS       current
   DESCRIPTION
       "The Bridge ID of the currently elected root bridge."
   ::= { gs2310MSTI3BridgeSTPStatus 3 }

gs2310MSTI3RootPort OBJECT-TYPE
   SYNTAX       DisplayString
   MAX-ACCESS   read-only
   STATUS       current
   DESCRIPTION
       "The switch port currently assigned the root port role."
   ::= { gs2310MSTI3BridgeSTPStatus 4 }

gs2310MSTI3RootCost OBJECT-TYPE
   SYNTAX       Integer32(0..200000000)
   MAX-ACCESS   read-only
   STATUS       current
   DESCRIPTION
       "Root Path Cost."
   ::= { gs2310MSTI3BridgeSTPStatus 5 }

gs2310MSTI3TopologyFlag OBJECT-TYPE
   SYNTAX       DisplayString
   MAX-ACCESS   read-only
   STATUS       current
   DESCRIPTION
       "The current state of the Topology Change Flag of this Bridge instance."
   ::= { gs2310MSTI3BridgeSTPStatus 8 }

gs2310MSTI3TopologyChangeCount OBJECT-TYPE
   SYNTAX       Counter32
   MAX-ACCESS   read-only
   STATUS       current
   DESCRIPTION
       "The number of times where the topology change flag has been set."
   ::= { gs2310MSTI3BridgeSTPStatus 9 }

gs2310MSTI3TopologyChangeLast OBJECT-TYPE
   SYNTAX       DisplayString
   MAX-ACCESS   read-only
   STATUS       current
   DESCRIPTION
       "The time passed since the Topology Flag was last set."
   ::= { gs2310MSTI3BridgeSTPStatus 10 }

gs2310MSTI3PortStateTable OBJECT-TYPE
   SYNTAX      SEQUENCE OF Gs2310MSTI3PortStateEntry
   MAX-ACCESS  not-accessible
   STATUS      current
   DESCRIPTION
       " Show MSTI3 Ports and Aggregations State Configurations. "
   ::= { gs2310MSTI3BridgeSTP 2 }

gs2310MSTI3PortStateEntry OBJECT-TYPE
   SYNTAX      Gs2310MSTI3PortStateEntry
   MAX-ACCESS  not-accessible
   STATUS      current
   DESCRIPTION
       ""
   INDEX    { gs2310MSTI3PortStateIndex  }
   ::= { gs2310MSTI3PortStateTable 1 }

Gs2310MSTI3PortStateEntry ::= SEQUENCE {
   gs2310MSTI3PortStateIndex        Integer32,
   gs2310MSTI3PortStatePort         DisplayString,
   gs2310MSTI3PortStatePortID       DisplayString,
   gs2310MSTI3PortStateRole         DisplayString,
   gs2310MSTI3PortStateState        DisplayString,
   gs2310MSTI3PortStatePathCost     Integer32,
   gs2310MSTI3PortStateEdge         DisplayString,
   gs2310MSTI3PortStatePoint2Point  DisplayString,
   gs2310MSTI3PortStateUptime       DisplayString
}

gs2310MSTI3PortStateIndex OBJECT-TYPE
   SYNTAX      Integer32(1..4095)
   MAX-ACCESS  not-accessible
   STATUS      current
   DESCRIPTION
       "table index."
   ::= { gs2310MSTI3PortStateEntry 1 }

gs2310MSTI3PortStatePort OBJECT-TYPE
   SYNTAX      DisplayString
   MAX-ACCESS  read-only
   STATUS      current
   DESCRIPTION
       "The switch port number of the logical STP port."
   ::= { gs2310MSTI3PortStateEntry 2 }

gs2310MSTI3PortStatePortID OBJECT-TYPE
   SYNTAX      DisplayString
   MAX-ACCESS  read-only
   STATUS      current
   DESCRIPTION
       "The port id as used by the STP protocol.
        This is the priority part and the logical port index of the bridge port."
   ::= { gs2310MSTI3PortStateEntry 3 }

gs2310MSTI3PortStateRole OBJECT-TYPE
   SYNTAX      DisplayString
   MAX-ACCESS  read-only
   STATUS      current
   DESCRIPTION
       "The current STP port role."
   ::= { gs2310MSTI3PortStateEntry 4 }

gs2310MSTI3PortStateState OBJECT-TYPE
   SYNTAX      DisplayString
   MAX-ACCESS  read-only
   STATUS      current
   DESCRIPTION
       "The current STP port state."
   ::= { gs2310MSTI3PortStateEntry 5 }

gs2310MSTI3PortStatePathCost OBJECT-TYPE
   SYNTAX      Integer32(0..200000000)
   MAX-ACCESS  read-only
   STATUS      current
   DESCRIPTION
       "The current STP port path cost."
   ::= { gs2310MSTI3PortStateEntry 6 }

gs2310MSTI3PortStateEdge OBJECT-TYPE
   SYNTAX      DisplayString
   MAX-ACCESS  read-only
   STATUS      current
   DESCRIPTION
       "The current STP port Edge Flag."
   ::= { gs2310MSTI3PortStateEntry 7 }

gs2310MSTI3PortStatePoint2Point OBJECT-TYPE
   SYNTAX      DisplayString
   MAX-ACCESS  read-only
   STATUS      current
   DESCRIPTION
       "The current STP port point-to-point flag."
   ::= { gs2310MSTI3PortStateEntry 8 }

gs2310MSTI3PortStateUptime OBJECT-TYPE
   SYNTAX      DisplayString
   MAX-ACCESS  read-only
   STATUS      current
   DESCRIPTION
       "The time since the bridge port was last initialized."
   ::= { gs2310MSTI3PortStateEntry 9 }

gs2310MSTI4BridgeSTP                                                        OBJECT IDENTIFIER ::= { gs2310STPBridgeStatus 5 }

gs2310MSTI4BridgeSTPStatus                                                  OBJECT IDENTIFIER ::= { gs2310MSTI4BridgeSTP 1 }

gs2310MSTI4BridgeInstance OBJECT-TYPE
   SYNTAX       DisplayString
   MAX-ACCESS   read-only
   STATUS       current
   DESCRIPTION
       "The Bridge instance - CIST, MST1, ..."
   ::= { gs2310MSTI4BridgeSTPStatus 1 }

gs2310MSTI4BridgeID OBJECT-TYPE
   SYNTAX       DisplayString
   MAX-ACCESS   read-only
   STATUS       current
   DESCRIPTION
       "The Bridge ID of this Bridge instance."
   ::= { gs2310MSTI4BridgeSTPStatus 2 }

gs2310MSTI4RootID OBJECT-TYPE
   SYNTAX       DisplayString
   MAX-ACCESS   read-only
   STATUS       current
   DESCRIPTION
       "The Bridge ID of the currently elected root bridge."
   ::= { gs2310MSTI4BridgeSTPStatus 3 }

gs2310MSTI4RootPort OBJECT-TYPE
   SYNTAX       DisplayString
   MAX-ACCESS   read-only
   STATUS       current
   DESCRIPTION
       "The switch port currently assigned the root port role."
   ::= { gs2310MSTI4BridgeSTPStatus 4 }

gs2310MSTI4RootCost OBJECT-TYPE
   SYNTAX       Integer32(0..200000000)
   MAX-ACCESS   read-only
   STATUS       current
   DESCRIPTION
       "Root Path Cost."
   ::= { gs2310MSTI4BridgeSTPStatus 5 }

gs2310MSTI4TopologyFlag OBJECT-TYPE
   SYNTAX       DisplayString
   MAX-ACCESS   read-only
   STATUS       current
   DESCRIPTION
       "The current state of the Topology Change Flag of this Bridge instance."
   ::= { gs2310MSTI4BridgeSTPStatus 8 }

gs2310MSTI4TopologyChangeCount OBJECT-TYPE
   SYNTAX       Counter32
   MAX-ACCESS   read-only
   STATUS       current
   DESCRIPTION
       "The number of times where the topology change flag has been set."
   ::= { gs2310MSTI4BridgeSTPStatus 9 }

gs2310MSTI4TopologyChangeLast OBJECT-TYPE
   SYNTAX       DisplayString
   MAX-ACCESS   read-only
   STATUS       current
   DESCRIPTION
       "The time passed since the Topology Flag was last set."
   ::= { gs2310MSTI4BridgeSTPStatus 10 }

gs2310MSTI4PortStateTable OBJECT-TYPE
   SYNTAX      SEQUENCE OF Gs2310MSTI4PortStateEntry
   MAX-ACCESS  not-accessible
   STATUS      current
   DESCRIPTION
       " Show MSTI4 Ports and Aggregations State Configurations. "
   ::= { gs2310MSTI4BridgeSTP 2 }

gs2310MSTI4PortStateEntry OBJECT-TYPE
   SYNTAX      Gs2310MSTI4PortStateEntry
   MAX-ACCESS  not-accessible
   STATUS      current
   DESCRIPTION
       ""
   INDEX    { gs2310MSTI4PortStateIndex  }
   ::= { gs2310MSTI4PortStateTable 1 }

Gs2310MSTI4PortStateEntry ::= SEQUENCE {
   gs2310MSTI4PortStateIndex        Integer32,
   gs2310MSTI4PortStatePort         DisplayString,
   gs2310MSTI4PortStatePortID       DisplayString,
   gs2310MSTI4PortStateRole         DisplayString,
   gs2310MSTI4PortStateState        DisplayString,
   gs2310MSTI4PortStatePathCost     Integer32,
   gs2310MSTI4PortStateEdge         DisplayString,
   gs2310MSTI4PortStatePoint2Point  DisplayString,
   gs2310MSTI4PortStateUptime       DisplayString
}

gs2310MSTI4PortStateIndex OBJECT-TYPE
   SYNTAX      Integer32(1..4095)
   MAX-ACCESS  not-accessible
   STATUS      current
   DESCRIPTION
       "table index."
   ::= { gs2310MSTI4PortStateEntry 1 }

gs2310MSTI4PortStatePort OBJECT-TYPE
   SYNTAX      DisplayString
   MAX-ACCESS  read-only
   STATUS      current
   DESCRIPTION
       "The switch port number of the logical STP port."
   ::= { gs2310MSTI4PortStateEntry 2 }

gs2310MSTI4PortStatePortID OBJECT-TYPE
   SYNTAX      DisplayString
   MAX-ACCESS  read-only
   STATUS      current
   DESCRIPTION
       "The port id as used by the STP protocol.
        This is the priority part and the logical port index of the bridge port."
   ::= { gs2310MSTI4PortStateEntry 3 }

gs2310MSTI4PortStateRole OBJECT-TYPE
   SYNTAX      DisplayString
   MAX-ACCESS  read-only
   STATUS      current
   DESCRIPTION
       "The current STP port role."
   ::= { gs2310MSTI4PortStateEntry 4 }

gs2310MSTI4PortStateState OBJECT-TYPE
   SYNTAX      DisplayString
   MAX-ACCESS  read-only
   STATUS      current
   DESCRIPTION
       "The current STP port state."
   ::= { gs2310MSTI4PortStateEntry 5 }

gs2310MSTI4PortStatePathCost OBJECT-TYPE
   SYNTAX      Integer32(0..200000000)
   MAX-ACCESS  read-only
   STATUS      current
   DESCRIPTION
       "The current STP port path cost."
   ::= { gs2310MSTI4PortStateEntry 6 }

gs2310MSTI4PortStateEdge OBJECT-TYPE
   SYNTAX      DisplayString
   MAX-ACCESS  read-only
   STATUS      current
   DESCRIPTION
       "The current STP port Edge Flag."
   ::= { gs2310MSTI4PortStateEntry 7 }

gs2310MSTI4PortStatePoint2Point OBJECT-TYPE
   SYNTAX      DisplayString
   MAX-ACCESS  read-only
   STATUS      current
   DESCRIPTION
       "The current STP port point-to-point flag."
   ::= { gs2310MSTI4PortStateEntry 8 }

gs2310MSTI4PortStateUptime OBJECT-TYPE
   SYNTAX      DisplayString
   MAX-ACCESS  read-only
   STATUS      current
   DESCRIPTION
       "The time since the bridge port was last initialized."
   ::= { gs2310MSTI4PortStateEntry 9 }

gs2310MSTI5BridgeSTP                                                        OBJECT IDENTIFIER ::= { gs2310STPBridgeStatus 6 }

gs2310MSTI5BridgeSTPStatus                                                  OBJECT IDENTIFIER ::= { gs2310MSTI5BridgeSTP 1 }

gs2310MSTI5BridgeInstance OBJECT-TYPE
   SYNTAX       DisplayString
   MAX-ACCESS   read-only
   STATUS       current
   DESCRIPTION
       "The Bridge instance - CIST, MST1, ..."
   ::= { gs2310MSTI5BridgeSTPStatus 1 }

gs2310MSTI5BridgeID OBJECT-TYPE
   SYNTAX       DisplayString
   MAX-ACCESS   read-only
   STATUS       current
   DESCRIPTION
       "The Bridge ID of this Bridge instance."
   ::= { gs2310MSTI5BridgeSTPStatus 2 }

gs2310MSTI5RootID OBJECT-TYPE
   SYNTAX       DisplayString
   MAX-ACCESS   read-only
   STATUS       current
   DESCRIPTION
       "The Bridge ID of the currently elected root bridge."
   ::= { gs2310MSTI5BridgeSTPStatus 3 }

gs2310MSTI5RootPort OBJECT-TYPE
   SYNTAX       DisplayString
   MAX-ACCESS   read-only
   STATUS       current
   DESCRIPTION
       "The switch port currently assigned the root port role."
   ::= { gs2310MSTI5BridgeSTPStatus 4 }

gs2310MSTI5RootCost OBJECT-TYPE
   SYNTAX       Integer32(0..200000000)
   MAX-ACCESS   read-only
   STATUS       current
   DESCRIPTION
       "Root Path Cost."
   ::= { gs2310MSTI5BridgeSTPStatus 5 }

gs2310MSTI5TopologyFlag OBJECT-TYPE
   SYNTAX       DisplayString
   MAX-ACCESS   read-only
   STATUS       current
   DESCRIPTION
       "The current state of the Topology Change Flag of this Bridge instance."
   ::= { gs2310MSTI5BridgeSTPStatus 8 }

gs2310MSTI5TopologyChangeCount OBJECT-TYPE
   SYNTAX       Counter32
   MAX-ACCESS   read-only
   STATUS       current
   DESCRIPTION
       "The number of times where the topology change flag has been set."
   ::= { gs2310MSTI5BridgeSTPStatus 9 }

gs2310MSTI5TopologyChangeLast OBJECT-TYPE
   SYNTAX       DisplayString
   MAX-ACCESS   read-only
   STATUS       current
   DESCRIPTION
       "The time passed since the Topology Flag was last set."
   ::= { gs2310MSTI5BridgeSTPStatus 10 }

gs2310MSTI5PortStateTable OBJECT-TYPE
   SYNTAX      SEQUENCE OF Gs2310MSTI5PortStateEntry
   MAX-ACCESS  not-accessible
   STATUS      current
   DESCRIPTION
       " Show MSTI5 Ports and Aggregations State Configurations. "
   ::= { gs2310MSTI5BridgeSTP 2 }

gs2310MSTI5PortStateEntry OBJECT-TYPE
   SYNTAX      Gs2310MSTI5PortStateEntry
   MAX-ACCESS  not-accessible
   STATUS      current
   DESCRIPTION
       ""
   INDEX    { gs2310MSTI5PortStateIndex  }
   ::= { gs2310MSTI5PortStateTable 1 }

Gs2310MSTI5PortStateEntry ::= SEQUENCE {
   gs2310MSTI5PortStateIndex        Integer32,
   gs2310MSTI5PortStatePort         DisplayString,
   gs2310MSTI5PortStatePortID       DisplayString,
   gs2310MSTI5PortStateRole         DisplayString,
   gs2310MSTI5PortStateState        DisplayString,
   gs2310MSTI5PortStatePathCost     Integer32,
   gs2310MSTI5PortStateEdge         DisplayString,
   gs2310MSTI5PortStatePoint2Point  DisplayString,
   gs2310MSTI5PortStateUptime       DisplayString
}

gs2310MSTI5PortStateIndex OBJECT-TYPE
   SYNTAX      Integer32(1..4095)
   MAX-ACCESS  not-accessible
   STATUS      current
   DESCRIPTION
       "table index."
   ::= { gs2310MSTI5PortStateEntry 1 }

gs2310MSTI5PortStatePort OBJECT-TYPE
   SYNTAX      DisplayString
   MAX-ACCESS  read-only
   STATUS      current
   DESCRIPTION
       "The switch port number of the logical STP port."
   ::= { gs2310MSTI5PortStateEntry 2 }

gs2310MSTI5PortStatePortID OBJECT-TYPE
   SYNTAX      DisplayString
   MAX-ACCESS  read-only
   STATUS      current
   DESCRIPTION
       "The port id as used by the STP protocol.
        This is the priority part and the logical port index of the bridge port."
   ::= { gs2310MSTI5PortStateEntry 3 }

gs2310MSTI5PortStateRole OBJECT-TYPE
   SYNTAX      DisplayString
   MAX-ACCESS  read-only
   STATUS      current
   DESCRIPTION
       "The current STP port role."
   ::= { gs2310MSTI5PortStateEntry 4 }

gs2310MSTI5PortStateState OBJECT-TYPE
   SYNTAX      DisplayString
   MAX-ACCESS  read-only
   STATUS      current
   DESCRIPTION
       "The current STP port state."
   ::= { gs2310MSTI5PortStateEntry 5 }

gs2310MSTI5PortStatePathCost OBJECT-TYPE
   SYNTAX      Integer32(0..200000000)
   MAX-ACCESS  read-only
   STATUS      current
   DESCRIPTION
       "The current STP port path cost."
   ::= { gs2310MSTI5PortStateEntry 6 }

gs2310MSTI5PortStateEdge OBJECT-TYPE
   SYNTAX      DisplayString
   MAX-ACCESS  read-only
   STATUS      current
   DESCRIPTION
       "The current STP port Edge Flag."
   ::= { gs2310MSTI5PortStateEntry 7 }

gs2310MSTI5PortStatePoint2Point OBJECT-TYPE
   SYNTAX      DisplayString
   MAX-ACCESS  read-only
   STATUS      current
   DESCRIPTION
       "The current STP port point-to-point flag."
   ::= { gs2310MSTI5PortStateEntry 8 }

gs2310MSTI5PortStateUptime OBJECT-TYPE
   SYNTAX      DisplayString
   MAX-ACCESS  read-only
   STATUS      current
   DESCRIPTION
       "The time since the bridge port was last initialized."
   ::= { gs2310MSTI5PortStateEntry 9 }

gs2310MSTI6BridgeSTP                                                        OBJECT IDENTIFIER ::= { gs2310STPBridgeStatus 7 }

gs2310MSTI6BridgeSTPStatus                                                  OBJECT IDENTIFIER ::= { gs2310MSTI6BridgeSTP 1 }

gs2310MSTI6BridgeInstance OBJECT-TYPE
   SYNTAX       DisplayString
   MAX-ACCESS   read-only
   STATUS       current
   DESCRIPTION
       "The Bridge instance - CIST, MST1, ..."
   ::= { gs2310MSTI6BridgeSTPStatus 1 }

gs2310MSTI6BridgeID OBJECT-TYPE
   SYNTAX       DisplayString
   MAX-ACCESS   read-only
   STATUS       current
   DESCRIPTION
       "The Bridge ID of this Bridge instance."
   ::= { gs2310MSTI6BridgeSTPStatus 2 }

gs2310MSTI6RootID OBJECT-TYPE
   SYNTAX       DisplayString
   MAX-ACCESS   read-only
   STATUS       current
   DESCRIPTION
       "The Bridge ID of the currently elected root bridge."
   ::= { gs2310MSTI6BridgeSTPStatus 3 }

gs2310MSTI6RootPort OBJECT-TYPE
   SYNTAX       DisplayString
   MAX-ACCESS   read-only
   STATUS       current
   DESCRIPTION
       "The switch port currently assigned the root port role."
   ::= { gs2310MSTI6BridgeSTPStatus 4 }

gs2310MSTI6RootCost OBJECT-TYPE
   SYNTAX       Integer32(0..200000000)
   MAX-ACCESS   read-only
   STATUS       current
   DESCRIPTION
       "Root Path Cost."
   ::= { gs2310MSTI6BridgeSTPStatus 5 }

gs2310MSTI6TopologyFlag OBJECT-TYPE
   SYNTAX       DisplayString
   MAX-ACCESS   read-only
   STATUS       current
   DESCRIPTION
       "The current state of the Topology Change Flag of this Bridge instance."
   ::= { gs2310MSTI6BridgeSTPStatus 8 }

gs2310MSTI6TopologyChangeCount OBJECT-TYPE
   SYNTAX       Counter32
   MAX-ACCESS   read-only
   STATUS       current
   DESCRIPTION
       "The number of times where the topology change flag has been set."
   ::= { gs2310MSTI6BridgeSTPStatus 9 }

gs2310MSTI6TopologyChangeLast OBJECT-TYPE
   SYNTAX       DisplayString
   MAX-ACCESS   read-only
   STATUS       current
   DESCRIPTION
       "The time passed since the Topology Flag was last set."
   ::= { gs2310MSTI6BridgeSTPStatus 10 }

gs2310MSTI6PortStateTable OBJECT-TYPE
   SYNTAX      SEQUENCE OF Gs2310MSTI6PortStateEntry
   MAX-ACCESS  not-accessible
   STATUS      current
   DESCRIPTION
       " Show MSTI6 Ports and Aggregations State Configurations. "
   ::= { gs2310MSTI6BridgeSTP 2 }

gs2310MSTI6PortStateEntry OBJECT-TYPE
   SYNTAX      Gs2310MSTI6PortStateEntry
   MAX-ACCESS  not-accessible
   STATUS      current
   DESCRIPTION
       ""
   INDEX    { gs2310MSTI6PortStateIndex  }
   ::= { gs2310MSTI6PortStateTable 1 }

Gs2310MSTI6PortStateEntry ::= SEQUENCE {
   gs2310MSTI6PortStateIndex        Integer32,
   gs2310MSTI6PortStatePort         DisplayString,
   gs2310MSTI6PortStatePortID       DisplayString,
   gs2310MSTI6PortStateRole         DisplayString,
   gs2310MSTI6PortStateState        DisplayString,
   gs2310MSTI6PortStatePathCost     Integer32,
   gs2310MSTI6PortStateEdge         DisplayString,
   gs2310MSTI6PortStatePoint2Point  DisplayString,
   gs2310MSTI6PortStateUptime       DisplayString
}

gs2310MSTI6PortStateIndex OBJECT-TYPE
   SYNTAX      Integer32(1..4095)
   MAX-ACCESS  not-accessible
   STATUS      current
   DESCRIPTION
       "table index."
   ::= { gs2310MSTI6PortStateEntry 1 }

gs2310MSTI6PortStatePort OBJECT-TYPE
   SYNTAX      DisplayString
   MAX-ACCESS  read-only
   STATUS      current
   DESCRIPTION
       "The switch port number of the logical STP port."
   ::= { gs2310MSTI6PortStateEntry 2 }

gs2310MSTI6PortStatePortID OBJECT-TYPE
   SYNTAX      DisplayString
   MAX-ACCESS  read-only
   STATUS      current
   DESCRIPTION
       "The port id as used by the STP protocol.
        This is the priority part and the logical port index of the bridge port."
   ::= { gs2310MSTI6PortStateEntry 3 }

gs2310MSTI6PortStateRole OBJECT-TYPE
   SYNTAX      DisplayString
   MAX-ACCESS  read-only
   STATUS      current
   DESCRIPTION
       "The current STP port role."
   ::= { gs2310MSTI6PortStateEntry 4 }

gs2310MSTI6PortStateState OBJECT-TYPE
   SYNTAX      DisplayString
   MAX-ACCESS  read-only
   STATUS      current
   DESCRIPTION
       "The current STP port state."
   ::= { gs2310MSTI6PortStateEntry 5 }

gs2310MSTI6PortStatePathCost OBJECT-TYPE
   SYNTAX      Integer32(0..200000000)
   MAX-ACCESS  read-only
   STATUS      current
   DESCRIPTION
       "The current STP port path cost."
   ::= { gs2310MSTI6PortStateEntry 6 }

gs2310MSTI6PortStateEdge OBJECT-TYPE
   SYNTAX      DisplayString
   MAX-ACCESS  read-only
   STATUS      current
   DESCRIPTION
       "The current STP port Edge Flag."
   ::= { gs2310MSTI6PortStateEntry 7 }

gs2310MSTI6PortStatePoint2Point OBJECT-TYPE
   SYNTAX      DisplayString
   MAX-ACCESS  read-only
   STATUS      current
   DESCRIPTION
       "The current STP port point-to-point flag."
   ::= { gs2310MSTI6PortStateEntry 8 }

gs2310MSTI6PortStateUptime OBJECT-TYPE
   SYNTAX      DisplayString
   MAX-ACCESS  read-only
   STATUS      current
   DESCRIPTION
       "The time since the bridge port was last initialized."
   ::= { gs2310MSTI6PortStateEntry 9 }

gs2310MSTI7BridgeSTP                                                        OBJECT IDENTIFIER ::= { gs2310STPBridgeStatus 8 }

gs2310MSTI7BridgeSTPStatus                                                  OBJECT IDENTIFIER ::= { gs2310MSTI7BridgeSTP 1 }

gs2310MSTI7BridgeInstance OBJECT-TYPE
   SYNTAX       DisplayString
   MAX-ACCESS   read-only
   STATUS       current
   DESCRIPTION
       "The Bridge instance - CIST, MST1, ..."
   ::= { gs2310MSTI7BridgeSTPStatus 1 }

gs2310MSTI7BridgeID OBJECT-TYPE
   SYNTAX       DisplayString
   MAX-ACCESS   read-only
   STATUS       current
   DESCRIPTION
       "The Bridge ID of this Bridge instance."
   ::= { gs2310MSTI7BridgeSTPStatus 2 }

gs2310MSTI7RootID OBJECT-TYPE
   SYNTAX       DisplayString
   MAX-ACCESS   read-only
   STATUS       current
   DESCRIPTION
       "The Bridge ID of the currently elected root bridge."
   ::= { gs2310MSTI7BridgeSTPStatus 3 }

gs2310MSTI7RootPort OBJECT-TYPE
   SYNTAX       DisplayString
   MAX-ACCESS   read-only
   STATUS       current
   DESCRIPTION
       "The switch port currently assigned the root port role."
   ::= { gs2310MSTI7BridgeSTPStatus 4 }

gs2310MSTI7RootCost OBJECT-TYPE
   SYNTAX       Integer32(0..200000000)
   MAX-ACCESS   read-only
   STATUS       current
   DESCRIPTION
       "Root Path Cost."
   ::= { gs2310MSTI7BridgeSTPStatus 5 }

gs2310MSTI7TopologyFlag OBJECT-TYPE
   SYNTAX       DisplayString
   MAX-ACCESS   read-only
   STATUS       current
   DESCRIPTION
       "The current state of the Topology Change Flag of this Bridge instance."
   ::= { gs2310MSTI7BridgeSTPStatus 8 }

gs2310MSTI7TopologyChangeCount OBJECT-TYPE
   SYNTAX       Counter32
   MAX-ACCESS   read-only
   STATUS       current
   DESCRIPTION
       "The number of times where the topology change flag has been set."
   ::= { gs2310MSTI7BridgeSTPStatus 9 }

gs2310MSTI7TopologyChangeLast OBJECT-TYPE
   SYNTAX       DisplayString
   MAX-ACCESS   read-only
   STATUS       current
   DESCRIPTION
       "The time passed since the Topology Flag was last set."
   ::= { gs2310MSTI7BridgeSTPStatus 10 }

gs2310MSTI7PortStateTable OBJECT-TYPE
   SYNTAX      SEQUENCE OF Gs2310MSTI7PortStateEntry
   MAX-ACCESS  not-accessible
   STATUS      current
   DESCRIPTION
       " Show MSTI7 Ports and Aggregations State Configurations. "
   ::= { gs2310MSTI7BridgeSTP 2 }

gs2310MSTI7PortStateEntry OBJECT-TYPE
   SYNTAX      Gs2310MSTI7PortStateEntry
   MAX-ACCESS  not-accessible
   STATUS      current
   DESCRIPTION
       ""
   INDEX    { gs2310MSTI7PortStateIndex  }
   ::= { gs2310MSTI7PortStateTable 1 }

Gs2310MSTI7PortStateEntry ::= SEQUENCE {
   gs2310MSTI7PortStateIndex        Integer32,
   gs2310MSTI7PortStatePort         DisplayString,
   gs2310MSTI7PortStatePortID       DisplayString,
   gs2310MSTI7PortStateRole         DisplayString,
   gs2310MSTI7PortStateState        DisplayString,
   gs2310MSTI7PortStatePathCost     Integer32,
   gs2310MSTI7PortStateEdge         DisplayString,
   gs2310MSTI7PortStatePoint2Point  DisplayString,
   gs2310MSTI7PortStateUptime       DisplayString
}

gs2310MSTI7PortStateIndex OBJECT-TYPE
   SYNTAX      Integer32(1..4095)
   MAX-ACCESS  not-accessible
   STATUS      current
   DESCRIPTION
       "table index."
   ::= { gs2310MSTI7PortStateEntry 1 }

gs2310MSTI7PortStatePort OBJECT-TYPE
   SYNTAX      DisplayString
   MAX-ACCESS  read-only
   STATUS      current
   DESCRIPTION
       "The switch port number of the logical STP port."
   ::= { gs2310MSTI7PortStateEntry 2 }

gs2310MSTI7PortStatePortID OBJECT-TYPE
   SYNTAX      DisplayString
   MAX-ACCESS  read-only
   STATUS      current
   DESCRIPTION
       "The port id as used by the STP protocol.
        This is the priority part and the logical port index of the bridge port."
   ::= { gs2310MSTI7PortStateEntry 3 }

gs2310MSTI7PortStateRole OBJECT-TYPE
   SYNTAX      DisplayString
   MAX-ACCESS  read-only
   STATUS      current
   DESCRIPTION
       "The current STP port role."
   ::= { gs2310MSTI7PortStateEntry 4 }

gs2310MSTI7PortStateState OBJECT-TYPE
   SYNTAX      DisplayString
   MAX-ACCESS  read-only
   STATUS      current
   DESCRIPTION
       "The current STP port state."
   ::= { gs2310MSTI7PortStateEntry 5 }

gs2310MSTI7PortStatePathCost OBJECT-TYPE
   SYNTAX      Integer32(0..200000000)
   MAX-ACCESS  read-only
   STATUS      current
   DESCRIPTION
       "The current STP port path cost."
   ::= { gs2310MSTI7PortStateEntry 6 }

gs2310MSTI7PortStateEdge OBJECT-TYPE
   SYNTAX      DisplayString
   MAX-ACCESS  read-only
   STATUS      current
   DESCRIPTION
       "The current STP port Edge Flag."
   ::= { gs2310MSTI7PortStateEntry 7 }

gs2310MSTI7PortStatePoint2Point OBJECT-TYPE
   SYNTAX      DisplayString
   MAX-ACCESS  read-only
   STATUS      current
   DESCRIPTION
       "The current STP port point-to-point flag."
   ::= { gs2310MSTI7PortStateEntry 8 }

gs2310MSTI7PortStateUptime OBJECT-TYPE
   SYNTAX      DisplayString
   MAX-ACCESS  read-only
   STATUS      current
   DESCRIPTION
       "The time since the bridge port was last initialized."
   ::= { gs2310MSTI7PortStateEntry 9 }

gs2310STPPortStatusTable OBJECT-TYPE
   SYNTAX      SEQUENCE OF Gs2310STPPortStatusEntry
   MAX-ACCESS  not-accessible
   STATUS      current
   DESCRIPTION
       " Show STP Port Status."
   ::= { gs2310STP 9 }

gs2310STPPortStatusEntry OBJECT-TYPE
   SYNTAX      Gs2310STPPortStatusEntry
   MAX-ACCESS  not-accessible
   STATUS      current
   DESCRIPTION
       ""
   INDEX    { gs2310STPPortStatusPort  }
   ::= { gs2310STPPortStatusTable 1 }

Gs2310STPPortStatusEntry ::= SEQUENCE {
   gs2310STPPortStatusPort         Integer32,
   gs2310STPPortStatusCISTRole     DisplayString,
   gs2310STPPortStatusCISTState    DisplayString,
   gs2310STPPortStatusUptime       DisplayString
}

gs2310STPPortStatusPort OBJECT-TYPE
   SYNTAX      Integer32(1..4095)
   MAX-ACCESS  not-accessible
   STATUS      current
   DESCRIPTION
       " port, range : 1 - port number. "
   ::= { gs2310STPPortStatusEntry 1 }

gs2310STPPortStatusCISTRole OBJECT-TYPE
   SYNTAX      DisplayString
   MAX-ACCESS  read-only
   STATUS      current
   DESCRIPTION
       " The current STP port role of the CIST port. "
   ::= { gs2310STPPortStatusEntry 2 }

gs2310STPPortStatusCISTState OBJECT-TYPE
   SYNTAX      DisplayString
   MAX-ACCESS  read-only
   STATUS      current
   DESCRIPTION
       " The current STP port state of the CIST port. "
   ::= { gs2310STPPortStatusEntry 3 }

gs2310STPPortStatusUptime OBJECT-TYPE
   SYNTAX      DisplayString
   MAX-ACCESS  read-only
   STATUS      current
   DESCRIPTION
       " The time since the bridge port was last initialized. "
   ::= { gs2310STPPortStatusEntry 4 }

gs2310STPPortStatisticsTable OBJECT-TYPE
   SYNTAX      SEQUENCE OF Gs2310STPPortStatisticsEntry
   MAX-ACCESS  not-accessible
   STATUS      current
   DESCRIPTION
       " Show STP Port Statistics."
   ::= { gs2310STP 10 }

gs2310STPPortStatisticsEntry OBJECT-TYPE
   SYNTAX      Gs2310STPPortStatisticsEntry
   MAX-ACCESS  not-accessible
   STATUS      current
   DESCRIPTION
       ""
   INDEX    { gs2310STPStatisticsIndex  }
   ::= { gs2310STPPortStatisticsTable 1 }

Gs2310STPPortStatisticsEntry ::= SEQUENCE {
   gs2310STPStatisticsIndex            Integer32,
   gs2310STPStatisticsPort             DisplayString,
   gs2310STPStatisticsTxMSTP           Counter32,
   gs2310STPStatisticsTxRSTP           Counter32,
   gs2310STPStatisticsTxSTP            Counter32,
   gs2310STPStatisticsTxTCN            Counter32,
   gs2310STPStatisticsRxMSTP           Counter32,
   gs2310STPStatisticsRxRSTP           Counter32,
   gs2310STPStatisticsRxSTP            Counter32,
   gs2310STPStatisticsRxTCN            Counter32,
   gs2310STPStatisticsDiscardedUnknown Counter32,
   gs2310STPStatisticsDiscardedIllegal Counter32
}

gs2310STPStatisticsIndex OBJECT-TYPE
   SYNTAX      Integer32(1..4095)
   MAX-ACCESS  not-accessible
   STATUS      current
   DESCRIPTION
       "table index."
   ::= { gs2310STPPortStatisticsEntry 1 }

gs2310STPStatisticsPort OBJECT-TYPE
   SYNTAX      DisplayString
   MAX-ACCESS  not-accessible
   STATUS      current
   DESCRIPTION
       " port, range : 1 - port number. "
   ::= { gs2310STPPortStatisticsEntry 2 }

gs2310STPStatisticsTxMSTP OBJECT-TYPE
   SYNTAX      Counter32
   MAX-ACCESS  read-only
   STATUS      current
   DESCRIPTION
       " The number of MSTP Configuration BPDU's received/transmitted on the port."
   ::= { gs2310STPPortStatisticsEntry 3 }

gs2310STPStatisticsTxRSTP OBJECT-TYPE
   SYNTAX      Counter32
   MAX-ACCESS  read-only
   STATUS      current
   DESCRIPTION
       " The number of RSTP Configuration BPDU's received/transmitted on the port. "
   ::= { gs2310STPPortStatisticsEntry 4 }

gs2310STPStatisticsTxSTP OBJECT-TYPE
   SYNTAX      Counter32
   MAX-ACCESS  read-only
   STATUS      current
   DESCRIPTION
       " The number of legacy STP Configuration BPDU's received/transmitted on the port. "
   ::= { gs2310STPPortStatisticsEntry 5 }

gs2310STPStatisticsTxTCN OBJECT-TYPE
   SYNTAX      Counter32
   MAX-ACCESS  read-only
   STATUS      current
   DESCRIPTION
       " The number of Topology Change Notification BPDU's received/transmitted on the port. "
   ::= { gs2310STPPortStatisticsEntry 6 }

gs2310STPStatisticsRxMSTP OBJECT-TYPE
   SYNTAX      Counter32
   MAX-ACCESS  read-only
   STATUS      current
   DESCRIPTION
       " The number of MSTP Configuration BPDU's received/transmitted on the port."
   ::= { gs2310STPPortStatisticsEntry 7 }

gs2310STPStatisticsRxRSTP OBJECT-TYPE
   SYNTAX      Counter32
   MAX-ACCESS  read-only
   STATUS      current
   DESCRIPTION
       " The number of RSTP Configuration BPDU's received/transmitted on the port. "
   ::= { gs2310STPPortStatisticsEntry 8 }

gs2310STPStatisticsRxSTP OBJECT-TYPE
   SYNTAX      Counter32
   MAX-ACCESS  read-only
   STATUS      current
   DESCRIPTION
       " The number of legacy STP Configuration BPDU's received/transmitted on the port. "
   ::= { gs2310STPPortStatisticsEntry 9 }

gs2310STPStatisticsRxTCN OBJECT-TYPE
   SYNTAX      Counter32
   MAX-ACCESS  read-only
   STATUS      current
   DESCRIPTION
       " The number of Topology Change Notification BPDU's received/transmitted on the port. "
   ::= { gs2310STPPortStatisticsEntry 10 }

gs2310STPStatisticsDiscardedUnknown OBJECT-TYPE
   SYNTAX      Counter32
   MAX-ACCESS  read-only
   STATUS      current
   DESCRIPTION
       " The number of unknown Spanning Tree BPDU's received and discarded on the port. "
   ::= { gs2310STPPortStatisticsEntry 11 }

gs2310STPStatisticsDiscardedIllegal OBJECT-TYPE
   SYNTAX      Counter32
   MAX-ACCESS  read-only
   STATUS      current
   DESCRIPTION
       " The number of illegal Spanning Tree BPDU's received and discarded on the port. "
   ::= { gs2310STPPortStatisticsEntry 12 }


gs2310FilteringDataBase                                                  OBJECT IDENTIFIER ::= { gs2310Configuration 21 }

gs2310FilteringDataBaseConfig                                            OBJECT IDENTIFIER ::= { gs2310FilteringDataBase 1 }

gs2310FilteringDataBaseAgingTime OBJECT-TYPE
   SYNTAX      Integer32(0..1000000)
   MAX-ACCESS  read-write
   STATUS      current
   DESCRIPTION
       "Configure aging time by entering a value here in seconds.
        default: 300,
        range: 10-1000000.
        Disable automatic aging : 0."
   ::= { gs2310FilteringDataBaseConfig 1 }

gs2310FilteringDataBaseConfigTable OBJECT-TYPE
   SYNTAX      SEQUENCE OF GS2310FilteringDataBaseConfigEntry
   MAX-ACCESS  not-accessible
   STATUS      current
   DESCRIPTION
       " "
   ::= { gs2310FilteringDataBaseConfig 2 }

gs2310FilteringDataBaseConfigEntry OBJECT-TYPE
   SYNTAX      GS2310FilteringDataBaseConfigEntry
   MAX-ACCESS  not-accessible
   STATUS      current
   DESCRIPTION
       ""
   INDEX    { gs2310FilteringDataBaseConfigPort  }
   ::= { gs2310FilteringDataBaseConfigTable 1 }

GS2310FilteringDataBaseConfigEntry ::= SEQUENCE {
   gs2310FilteringDataBaseConfigPort        Integer32,
   gs2310FilteringDataBaseConfigLearning    INTEGER
}

gs2310FilteringDataBaseConfigPort OBJECT-TYPE
   SYNTAX      Integer32(1..4095)
   MAX-ACCESS  not-accessible
   STATUS      current
   DESCRIPTION
       " "
   ::= { gs2310FilteringDataBaseConfigEntry 1 }

gs2310FilteringDataBaseConfigLearning OBJECT-TYPE
   SYNTAX      INTEGER { auto(0), disable(1), secure(2) }
   MAX-ACCESS  read-write
   STATUS      current
   DESCRIPTION
       "Configure learning mode of switch ports.
        default: 0,
        0: auto,
        1: disable,
        2: secure. "
   ::= { gs2310FilteringDataBaseConfigEntry 2 }


gs2310FilteringDataBaseStaticMAC                                OBJECT IDENTIFIER ::= { gs2310FilteringDataBaseConfig 3 }

gs2310FilteringDataBaseStaticMACCreate OBJECT-TYPE
   SYNTAX       INTEGER { none(0), create(1) }
   MAX-ACCESS   read-write
   STATUS       current
   DESCRIPTION
       "default: 0
        0 : None  (read only)
        1 : Create Static MAC Table"
   ::= { gs2310FilteringDataBaseStaticMAC 1 }

gs2310FilteringDataBaseStaticMACTable OBJECT-TYPE
   SYNTAX      SEQUENCE OF GS2310FilteringDataBaseStaticMACEntry
   MAX-ACCESS  not-accessible
   STATUS      current
   DESCRIPTION
       " "
   ::= { gs2310FilteringDataBaseStaticMAC 2 }

gs2310FilteringDataBaseStaticMACEntry OBJECT-TYPE
   SYNTAX      GS2310FilteringDataBaseStaticMACEntry
   MAX-ACCESS  not-accessible
   STATUS      current
   DESCRIPTION
       ""
   INDEX    { gs2310FilteringDataBaseStaticMACIndex  }
   ::= { gs2310FilteringDataBaseStaticMACTable 1 }

GS2310FilteringDataBaseStaticMACEntry ::= SEQUENCE {
   gs2310FilteringDataBaseStaticMACIndex	    Integer32,
   gs2310FilteringDataBaseStaticMACVLANId	    Integer32,
   gs2310FilteringDataBaseStaticMACAddress      MacAddress,
   gs2310FilteringDataBaseStaticMACPortMembers  DisplayString,
   gs2310FilteringDataBaseStaticMACRowStatus	INTEGER
}

gs2310FilteringDataBaseStaticMACIndex OBJECT-TYPE
   SYNTAX      Integer32(1..4095)
   MAX-ACCESS  not-accessible
   STATUS      current
   DESCRIPTION
       " "
   ::= { gs2310FilteringDataBaseStaticMACEntry 1 }

gs2310FilteringDataBaseStaticMACVLANId OBJECT-TYPE
   SYNTAX      Integer32(1..4094)
   MAX-ACCESS  read-write
   STATUS      current
   DESCRIPTION
       " VLAN ID, range: 1 - 4094. "
   ::= { gs2310FilteringDataBaseStaticMACEntry 2 }

gs2310FilteringDataBaseStaticMACAddress OBJECT-TYPE
   SYNTAX      MacAddress
   MAX-ACCESS  read-write
   STATUS      current
   DESCRIPTION
       " MAC address, format 0a 1b 2c 3d 4e 5f "
   ::= { gs2310FilteringDataBaseStaticMACEntry 3 }

gs2310FilteringDataBaseStaticMACPortMembers OBJECT-TYPE
   SYNTAX      DisplayString
   MAX-ACCESS  read-write
   STATUS      current
   DESCRIPTION
       "To include the ports in a Static MAC Table"
   ::= { gs2310FilteringDataBaseStaticMACEntry 4 }

gs2310FilteringDataBaseStaticMACRowStatus OBJECT-TYPE
   SYNTAX      INTEGER { active(1), notInservice(2), destroy(4), undo(5) }
   MAX-ACCESS  read-write
   STATUS      current
   DESCRIPTION
       "1: active
        2: notInservice
        4: destroy
        5: undo"
   ::= { gs2310FilteringDataBaseStaticMACEntry 5 }


gs2310FilteringDataBaseDynamicMACTable OBJECT-TYPE
   SYNTAX      SEQUENCE OF GS2310FilteringDataBaseDynamicMACEntry
   MAX-ACCESS  not-accessible
   STATUS      current
   DESCRIPTION
       " "
   ::= { gs2310FilteringDataBaseConfig 4 }

gs2310FilteringDataBaseDynamicMACEntry OBJECT-TYPE
   SYNTAX      GS2310FilteringDataBaseDynamicMACEntry
   MAX-ACCESS  not-accessible
   STATUS      current
   DESCRIPTION
       ""
   INDEX    { gs2310FilteringDataBaseDynamicMACIndex  }
   ::= { gs2310FilteringDataBaseDynamicMACTable 1 }

GS2310FilteringDataBaseDynamicMACEntry ::= SEQUENCE {
   gs2310FilteringDataBaseDynamicMACIndex	    Integer32,
   gs2310FilteringDataBaseDynamicMACType	    INTEGER,
   gs2310FilteringDataBaseDynamicMACVLAN	    Integer32,
   gs2310FilteringDataBaseDynamicMACAddress     MacAddress,
   gs2310FilteringDataBaseDynamicPortMembers    DisplayString
}

gs2310FilteringDataBaseDynamicMACIndex OBJECT-TYPE
   SYNTAX      Integer32(1..4095)
   MAX-ACCESS  not-accessible
   STATUS      current
   DESCRIPTION
       " "
   ::= { gs2310FilteringDataBaseDynamicMACEntry 1 }

gs2310FilteringDataBaseDynamicMACType OBJECT-TYPE
   SYNTAX      INTEGER { dynamic(0), static(1) }
   MAX-ACCESS  read-only
   STATUS      current
   DESCRIPTION
       "Indicates whether the entry is a static or a dynamic entry."
   ::= { gs2310FilteringDataBaseDynamicMACEntry 2 }

gs2310FilteringDataBaseDynamicMACVLAN OBJECT-TYPE
   SYNTAX      Integer32(1..4094)
   MAX-ACCESS  read-only
   STATUS      current
   DESCRIPTION
       "The VLAN ID of the entry."
   ::= { gs2310FilteringDataBaseDynamicMACEntry 3 }

gs2310FilteringDataBaseDynamicMACAddress OBJECT-TYPE
   SYNTAX      MacAddress
   MAX-ACCESS  read-only
   STATUS      current
   DESCRIPTION
       "The MAC address of the entry."
   ::= { gs2310FilteringDataBaseDynamicMACEntry 4 }

gs2310FilteringDataBaseDynamicPortMembers OBJECT-TYPE
   SYNTAX      DisplayString
   MAX-ACCESS  read-only
   STATUS      current
   DESCRIPTION
       "The ports that are members of the entry."
   ::= { gs2310FilteringDataBaseDynamicMACEntry 5 }


gs2310SFlowAgent                                                  OBJECT IDENTIFIER ::= { gs2310Configuration 22 }

gs2310SFlowAgentCollector                                            OBJECT IDENTIFIER ::= { gs2310SFlowAgent 1 }

gs2310SFlowAgentReceiverMode OBJECT-TYPE
   SYNTAX      INTEGER { disable(0), enable(1) }
   MAX-ACCESS  read-write
   STATUS      current
   DESCRIPTION
       "default: 0
       0: disable
       1: enable "
   ::= { gs2310SFlowAgentCollector 1 }


gs2310LMC                                                   OBJECT IDENTIFIER ::= { gs2310Configuration 1500 }

gs2310LMCOperating OBJECT-TYPE
   SYNTAX      INTEGER { disabled(0), enabled(1), try(2) }
   MAX-ACCESS  read-write
   STATUS      current
   DESCRIPTION
       "0: disabled
        1: enabled
        2: try"
   ::= { gs2310LMC 1 }

gs2310LMCConfigViaDhcp OBJECT-TYPE
   SYNTAX      INTEGER { disabled(0), enabled(1) }
   MAX-ACCESS  read-write
   STATUS      current
   DESCRIPTION
       "0: disabled
        1: enabled"
   ::= { gs2310LMC 2 }

gs2310LMCDomain OBJECT-TYPE
   SYNTAX      DisplayString(SIZE(0..255))
   MAX-ACCESS  read-write
   STATUS      current
   DESCRIPTION
       "0: disabled
        1: enabled"
   ::= { gs2310LMC 3 }

gs2310LMCDhcpClientAutoRenew OBJECT-TYPE
   SYNTAX      INTEGER { disabled(0), enabled(1) }
   MAX-ACCESS  read-write
   STATUS      current
   DESCRIPTION
       "0: disabled
        1: enabled"
   ::= { gs2310LMC 4 }

gs2310LMCZeroTouchSupport OBJECT-TYPE
   SYNTAX      INTEGER { No(0), Yes(1) }
   MAX-ACCESS  read-only
   STATUS      current
   DESCRIPTION
       "0: No
        1: Yes"
   ::= { gs2310LMC 50 }

gs2310LMCPairingTokenPresent OBJECT-TYPE
   SYNTAX      INTEGER { No(0), Yes(1) }
   MAX-ACCESS  read-only
   STATUS      current
   DESCRIPTION
       "0: No
        1: Yes"
   ::= { gs2310LMC 51 }

gs2310LMCClientStatus OBJECT-TYPE
   SYNTAX      DisplayString
   MAX-ACCESS  read-only
   STATUS      current
   DESCRIPTION
           ""
   ::= { gs2310LMC  52 }


gs2310LMCManagementStatus OBJECT-TYPE
   SYNTAX      INTEGER {Unpaired(0), Paired(1), PairedAndClaimed(14)}
   MAX-ACCESS  read-only
   STATUS      current
   DESCRIPTION
           "0: Unpaired
            1: Paired
            14: PairedAndClaimed"
   ::= { gs2310LMC  53 }

gs2310LMCControlStatus OBJECT-TYPE
   SYNTAX      INTEGER {Disabled(2), Operating(4)}
   MAX-ACCESS  read-only
   STATUS      current
   DESCRIPTION
           "2: Disabled
            4: Operating"
   ::= { gs2310LMC  54 }

gs2310pLMCMonitoringStatus OBJECT-TYPE
   SYNTAX      INTEGER {Disabled(2), Operating(4)}
   MAX-ACCESS  read-only
   STATUS      current
   DESCRIPTION
           "2: Disabled
            4: Operating"
   ::= { gs2310LMC  55 }

gs2310LMCConfigurationSource OBJECT-TYPE
   SYNTAX      DisplayString
   MAX-ACCESS  read-only
   STATUS      current
   DESCRIPTION
           ""
   ::= { gs2310LMC  56 }

gs2310LMCConfigModified OBJECT-TYPE
   SYNTAX      INTEGER { No(0), Yes(1) }
   MAX-ACCESS  read-only
   STATUS      current
   DESCRIPTION
       "0: No
        1: Yes"
   ::= { gs2310LMC 57 }

gs2310LMCDeviceID OBJECT-TYPE
   SYNTAX      DisplayString
   MAX-ACCESS  read-only
   STATUS      current
   DESCRIPTION
           ""
   ::= { gs2310LMC  58 }

gs2310LMCRoundTripTime OBJECT-TYPE
   SYNTAX      INTEGER
   MAX-ACCESS  read-only
   STATUS      current
   DESCRIPTION
           ""
   ::= { gs2310LMC  100 }
----------------------------------------------------------------------------------------------------------------------------
gs2310Security                                              OBJECT IDENTIFIER ::= { lancomGS2310 3 }

gs2310IPSourceGuard                                         OBJECT IDENTIFIER ::= { gs2310Security 1 }

gs2310IPSourceGuardConf                                     OBJECT IDENTIFIER ::= { gs2310IPSourceGuard 1 }

gs2310IPSourceGuardMode OBJECT-TYPE
   SYNTAX      INTEGER { disable(0), enable(1) }
   MAX-ACCESS  read-write
   STATUS      current
   DESCRIPTION
       " default:  0
        0: disable
        1: enable"
   ::= { gs2310IPSourceGuardConf 1 }

gs2310IPSourceGuardPortConfigTable OBJECT-TYPE
   SYNTAX      SEQUENCE OF GS2310IPSourceGuardPortConfigEntry
   MAX-ACCESS  not-accessible
   STATUS      current
   DESCRIPTION
       " "
   ::= { gs2310IPSourceGuardConf 2 }

gs2310IPSourceGuardPortConfigEntry OBJECT-TYPE
   SYNTAX      GS2310IPSourceGuardPortConfigEntry
   MAX-ACCESS  not-accessible
   STATUS      current
   DESCRIPTION
       ""
   INDEX    { gs2310IPSourceGuardPortConfigPort  }
   ::= { gs2310IPSourceGuardPortConfigTable 1 }

GS2310IPSourceGuardPortConfigEntry ::= SEQUENCE {
   gs2310IPSourceGuardPortConfigPort               Integer32,
   gs2310IPSourceGuardPortConfigMode               INTEGER,
   gs2310IPSourceGuardPortMaxDynamicClients        Integer32
}

gs2310IPSourceGuardPortConfigPort OBJECT-TYPE
   SYNTAX      Integer32(1..4095)
   MAX-ACCESS  not-accessible
   STATUS      current
   DESCRIPTION
       " "
   ::= { gs2310IPSourceGuardPortConfigEntry 1 }

gs2310IPSourceGuardPortConfigMode OBJECT-TYPE
   SYNTAX      INTEGER { disable(0), enable(1) }
   MAX-ACCESS  read-write
   STATUS      current
   DESCRIPTION
       "default: 0
       0:disable
       1:enable "
   ::= { gs2310IPSourceGuardPortConfigEntry 2 }

gs2310IPSourceGuardPortMaxDynamicClients OBJECT-TYPE
   SYNTAX      Integer32(0..2|99)
   MAX-ACCESS  read-write
   STATUS      current
   DESCRIPTION
       "default: 99
       0~2: Max Dynamic clients
       99:Unlimited "
   ::= { gs2310IPSourceGuardPortConfigEntry 3 }


gs2310IPSourceGuardStatic                                OBJECT IDENTIFIER ::= { gs2310IPSourceGuard 2 }

gs2310IPSourceGuardStaticCreate OBJECT-TYPE
   SYNTAX       INTEGER { none(0), create(1) }
   MAX-ACCESS   read-write
   STATUS       current
   DESCRIPTION
       "default: 0
        0 : None  (read only)
        1 : Create a IP Source Guard"
   ::= { gs2310IPSourceGuardStatic 1 }

gs2310IPSourceGuardStaticTable OBJECT-TYPE
   SYNTAX      SEQUENCE OF GS2310IPSourceGuardStaticEntry
   MAX-ACCESS  not-accessible
   STATUS      current
   DESCRIPTION
       " "
   ::= { gs2310IPSourceGuardStatic 2 }

gs2310IPSourceGuardStaticEntry OBJECT-TYPE
   SYNTAX      GS2310IPSourceGuardStaticEntry
   MAX-ACCESS  not-accessible
   STATUS      current
   DESCRIPTION
       ""
   INDEX    { gs2310IPSourceGuardStaticIndex  }
   ::= { gs2310IPSourceGuardStaticTable 1 }

GS2310IPSourceGuardStaticEntry ::= SEQUENCE {
   gs2310IPSourceGuardStaticIndex         Integer32,
   gs2310IPSourceGuardStaticPort          Integer32,
   gs2310IPSourceGuardStaticVLANId        Integer32,
   gs2310IPSourceGuardStaticIPAddress     IpAddress,
   gs2310IPSourceGuardStaticMACAddress    MacAddress,
   gs2310IPSourceGuardStaticRowStatus     INTEGER
}

gs2310IPSourceGuardStaticIndex OBJECT-TYPE
   SYNTAX      Integer32(1..28)
   MAX-ACCESS  not-accessible
   STATUS      current
   DESCRIPTION
       " "
   ::= { gs2310IPSourceGuardStaticEntry 1 }

gs2310IPSourceGuardStaticPort OBJECT-TYPE
   SYNTAX      Integer32(1..4095)
   MAX-ACCESS  read-write
   STATUS      current
   DESCRIPTION
       " Port, range: 1 - port number. "
   ::= { gs2310IPSourceGuardStaticEntry 2 }

gs2310IPSourceGuardStaticVLANId OBJECT-TYPE
   SYNTAX      Integer32(1..4094)
   MAX-ACCESS  read-write
   STATUS      current
   DESCRIPTION
       " VLAN ID, range: 1 - 4094. "
   ::= { gs2310IPSourceGuardStaticEntry 3 }

gs2310IPSourceGuardStaticIPAddress OBJECT-TYPE
   SYNTAX      IpAddress
   MAX-ACCESS  read-write
   STATUS      current
   DESCRIPTION
       " IP address allowed for doing IP source guard. "
   ::= { gs2310IPSourceGuardStaticEntry 4 }

gs2310IPSourceGuardStaticMACAddress OBJECT-TYPE
   SYNTAX      MacAddress
   MAX-ACCESS  read-write
   STATUS      current
   DESCRIPTION
       " Allowed Source MAC address, format 0a 1b 2c 3d 4e 5f "
   ::= { gs2310IPSourceGuardStaticEntry 5 }

gs2310IPSourceGuardStaticRowStatus OBJECT-TYPE
   SYNTAX      INTEGER { active(1), notInservice(2), edit(3), destroy(4), undo(5) }
   MAX-ACCESS  read-write
   STATUS      current
   DESCRIPTION
       "1: active
        2: notInservice
        3: edit
        4: destroy
        5: undo"
   ::= { gs2310IPSourceGuardStaticEntry 6 }

gs2310IPSourceGuardDynamicTable OBJECT-TYPE
   SYNTAX      SEQUENCE OF GS2310IPSourceGuardDynamicEntry
   MAX-ACCESS  not-accessible
   STATUS      current
   DESCRIPTION
       " "
   ::= { gs2310IPSourceGuard 3 }

gs2310IPSourceGuardDynamicEntry OBJECT-TYPE
   SYNTAX      GS2310IPSourceGuardDynamicEntry
   MAX-ACCESS  not-accessible
   STATUS      current
   DESCRIPTION
       ""
   INDEX    { gs2310IPSourceGuardDynamicIndex  }
   ::= { gs2310IPSourceGuardDynamicTable 1 }

GS2310IPSourceGuardDynamicEntry ::= SEQUENCE {
   gs2310IPSourceGuardDynamicIndex          Integer32,
   gs2310IPSourceGuardDynamicPort           Integer32,
   gs2310IPSourceGuardDynamicVLANId         Integer32,
   gs2310IPSourceGuardDynamicIPAddress      IpAddress,
   gs2310IPSourceGuardDynamicMACAddress     MacAddress
}

gs2310IPSourceGuardDynamicIndex OBJECT-TYPE
   SYNTAX      Integer32(1..4095)
   MAX-ACCESS  not-accessible
   STATUS      current
   DESCRIPTION
       " "
   ::= { gs2310IPSourceGuardDynamicEntry 1 }

gs2310IPSourceGuardDynamicPort OBJECT-TYPE
   SYNTAX      Integer32(1..10)
   MAX-ACCESS  read-only
   STATUS      current
   DESCRIPTION
       " "
   ::= { gs2310IPSourceGuardDynamicEntry 2 }

gs2310IPSourceGuardDynamicVLANId OBJECT-TYPE
   SYNTAX      Integer32(1..4094)
   MAX-ACCESS  read-only
   STATUS      current
   DESCRIPTION
       " "
   ::= { gs2310IPSourceGuardDynamicEntry 3 }

gs2310IPSourceGuardDynamicIPAddress OBJECT-TYPE
   SYNTAX      IpAddress
   MAX-ACCESS  read-only
   STATUS      current
   DESCRIPTION
       " "
   ::= { gs2310IPSourceGuardDynamicEntry 4 }

gs2310IPSourceGuardDynamicMACAddress OBJECT-TYPE
   SYNTAX      MacAddress
   MAX-ACCESS  read-only
   STATUS      current
   DESCRIPTION
       " "
   ::= { gs2310IPSourceGuardDynamicEntry 5 }

gs2310ARPInspection                                         OBJECT IDENTIFIER ::= { gs2310Security 2 }

gs2310ARPInspectionConf                                     OBJECT IDENTIFIER ::= { gs2310ARPInspection 1 }

gs2310ARPInspectionConfMode OBJECT-TYPE
   SYNTAX      INTEGER { disable(0), enable(1) }
   MAX-ACCESS  read-write
   STATUS      current
   DESCRIPTION
       "default: 0
        0: disable
        1: enable"
   ::= { gs2310ARPInspectionConf 1 }

gs2310ARPInspectionConfTable OBJECT-TYPE
   SYNTAX      SEQUENCE OF GS2310ARPInspectionConfEntry
   MAX-ACCESS  not-accessible
   STATUS      current
   DESCRIPTION
       " "
   ::= { gs2310ARPInspectionConf 2 }

gs2310ARPInspectionConfEntry OBJECT-TYPE
   SYNTAX      GS2310ARPInspectionConfEntry
   MAX-ACCESS  not-accessible
   STATUS      current
   DESCRIPTION
       ""
   INDEX    { gs2310ARPInspectionConfPortIndex  }
   ::= { gs2310ARPInspectionConfTable 1 }

GS2310ARPInspectionConfEntry ::= SEQUENCE {
   gs2310ARPInspectionConfPortIndex	Integer32,
   gs2310ARPInspectionConfPortMode	INTEGER
}

gs2310ARPInspectionConfPortIndex OBJECT-TYPE
   SYNTAX      Integer32(1..4095)
   MAX-ACCESS  not-accessible
   STATUS      current
   DESCRIPTION
       " "
   ::= { gs2310ARPInspectionConfEntry 1 }

gs2310ARPInspectionConfPortMode OBJECT-TYPE
   SYNTAX      INTEGER { disable(0), enable(1) }
   MAX-ACCESS  read-write
   STATUS      current
   DESCRIPTION
       "default: 0
        0: disable
        1: enable"
   ::= { gs2310ARPInspectionConfEntry 2 }


gs2310ARPInspectionStatic                                OBJECT IDENTIFIER ::= { gs2310ARPInspection 2 }

gs2310ARPInspectionStaticCreate OBJECT-TYPE
   SYNTAX      INTEGER { none(0), create(1) }
   MAX-ACCESS  read-write
   STATUS      current
   DESCRIPTION
       "default: 0
        0: none
        1: create"
   ::= { gs2310ARPInspectionStatic 1 }

gs2310ARPInspectionStaticTable OBJECT-TYPE
   SYNTAX      SEQUENCE OF GS2310ARPInspectionStaticEntry
   MAX-ACCESS  not-accessible
   STATUS      current
   DESCRIPTION
       " "
   ::= { gs2310ARPInspectionStatic 2 }

gs2310ARPInspectionStaticEntry OBJECT-TYPE
   SYNTAX      GS2310ARPInspectionStaticEntry
   MAX-ACCESS  not-accessible
   STATUS      current
   DESCRIPTION
       ""
   INDEX    { gs2310ARPInspectionStaticIndex  }
   ::= { gs2310ARPInspectionStaticTable 1 }

GS2310ARPInspectionStaticEntry ::= SEQUENCE {
   gs2310ARPInspectionStaticIndex       Integer32,
   gs2310ARPInspectionStaticPort        Integer32,
   gs2310ARPInspectionStaticVLANId      Integer32,
   gs2310ARPInspectionStaticIPAddress   IpAddress,
   gs2310ARPInspectionStaticMACAddress  MacAddress,
   gs2310ARPInspectionStaticRowStatus   INTEGER
}

gs2310ARPInspectionStaticIndex OBJECT-TYPE
   SYNTAX      Integer32(1..4095)
   MAX-ACCESS  not-accessible
   STATUS      current
   DESCRIPTION
       ""
   ::= { gs2310ARPInspectionStaticEntry 1 }

gs2310ARPInspectionStaticPort OBJECT-TYPE
   SYNTAX      Integer32(1..4095)
   MAX-ACCESS  read-write
   STATUS      current
   DESCRIPTION
       " Port, range: 1 - port number. "
   ::= { gs2310ARPInspectionStaticEntry 2 }

gs2310ARPInspectionStaticVLANId OBJECT-TYPE
   SYNTAX      Integer32(1..4094)
   MAX-ACCESS  read-write
   STATUS      current
   DESCRIPTION
       " VLAN ID, range: 1 - 4094. "
   ::= { gs2310ARPInspectionStaticEntry 3 }

gs2310ARPInspectionStaticIPAddress OBJECT-TYPE
   SYNTAX      IpAddress
   MAX-ACCESS  read-write
   STATUS      current
   DESCRIPTION
       " IP address allowed for doing ARP request. "
   ::= { gs2310ARPInspectionStaticEntry 4 }

gs2310ARPInspectionStaticMACAddress OBJECT-TYPE
   SYNTAX      MacAddress
   MAX-ACCESS  read-write
   STATUS      current
   DESCRIPTION
       " Allowed Source MAC address in ARP request packets, format 0a 1b 2c 3d 4e 5f "
   ::= { gs2310ARPInspectionStaticEntry 5 }

gs2310ARPInspectionStaticRowStatus OBJECT-TYPE
   SYNTAX     INTEGER { active(1), notInservice(2), edit(3), destroy(4), undo(5) }
   MAX-ACCESS  read-write
   STATUS      current
   DESCRIPTION
       "1: active
        2: notInservice
        3: edit
        4: destroy
        5: undo"
   ::= { gs2310ARPInspectionStaticEntry 6 }

gs2310ARPInspectionDynamicTable OBJECT-TYPE
   SYNTAX      SEQUENCE OF GS2310ARPInspectionDynamicEntry
   MAX-ACCESS  not-accessible
   STATUS      current
   DESCRIPTION
       " "
   ::= { gs2310ARPInspection 3 }

gs2310ARPInspectionDynamicEntry OBJECT-TYPE
   SYNTAX      GS2310ARPInspectionDynamicEntry
   MAX-ACCESS  not-accessible
   STATUS      current
   DESCRIPTION
       ""
   INDEX    { gs2310ARPInspectionDynamicIndex  }
   ::= { gs2310ARPInspectionDynamicTable 1 }

GS2310ARPInspectionDynamicEntry ::= SEQUENCE {
   gs2310ARPInspectionDynamicIndex          Integer32,
   gs2310ARPInspectionDynamicPort           Integer32,
   gs2310ARPInspectionDynamicVLANId         Integer32,
   gs2310ARPInspectionDynamicIPAddress      IpAddress,
   gs2310ARPInspectionDynamicMACAddress     MacAddress
}

gs2310ARPInspectionDynamicIndex OBJECT-TYPE
   SYNTAX      Integer32(1..4095)
   MAX-ACCESS  not-accessible
   STATUS      current
   DESCRIPTION
       " "
   ::= { gs2310ARPInspectionDynamicEntry 1 }

gs2310ARPInspectionDynamicPort OBJECT-TYPE
   SYNTAX      Integer32(1..4095)
   MAX-ACCESS  read-only
   STATUS      current
   DESCRIPTION
       ""
   ::= { gs2310ARPInspectionDynamicEntry 2 }

gs2310ARPInspectionDynamicVLANId OBJECT-TYPE
   SYNTAX      Integer32(1..4094)
   MAX-ACCESS  read-only
   STATUS      current
   DESCRIPTION
       ""
   ::= { gs2310ARPInspectionDynamicEntry 3 }

gs2310ARPInspectionDynamicIPAddress OBJECT-TYPE
   SYNTAX      IpAddress
   MAX-ACCESS  read-only
   STATUS      current
   DESCRIPTION
       ""
   ::= { gs2310ARPInspectionDynamicEntry 4 }

gs2310ARPInspectionDynamicMACAddress OBJECT-TYPE
   SYNTAX      MacAddress
   MAX-ACCESS  read-only
   STATUS      current
   DESCRIPTION
       ""
   ::= { gs2310ARPInspectionDynamicEntry 5 }

gs2310ARPStaticGatewayCtrl	                                OBJECT IDENTIFIER ::= { gs2310ARPInspection 6 }

gs2310ARPStaticGatewayCtrlSystemConf                                      OBJECT IDENTIFIER ::= { gs2310ARPStaticGatewayCtrl 1 }

gs2310ARPStaticGatewayCtrlMode OBJECT-TYPE
   SYNTAX      INTEGER { disable(0), enable(1) }
   MAX-ACCESS  read-write
   STATUS      current
   DESCRIPTION
       "default: 0
       0: disable
       1: enable "
   ::= { gs2310ARPStaticGatewayCtrlSystemConf 1 }

gs2310ARPStaticGatewayCtrlCreate OBJECT-TYPE
   SYNTAX      INTEGER { none(0), create(1) }
   MAX-ACCESS  read-write
   STATUS      current
   DESCRIPTION
       "default: 0
        0: none
        1: create"
   ::= { gs2310ARPStaticGatewayCtrl 2 }

gs2310ARPStaticGatewayCtrlTable OBJECT-TYPE
   SYNTAX      SEQUENCE OF GS2310ARPStaticGatewayCtrlEntry
   MAX-ACCESS  not-accessible
   STATUS      current
   DESCRIPTION
       " "
   ::= { gs2310ARPStaticGatewayCtrl 3 }

gs2310ARPStaticGatewayCtrlEntry OBJECT-TYPE
   SYNTAX      GS2310ARPStaticGatewayCtrlEntry
   MAX-ACCESS  not-accessible
   STATUS      current
   DESCRIPTION
       ""
   INDEX    { gs2310ARPStaticGatewayCtrlIndex  }
   ::= { gs2310ARPStaticGatewayCtrlTable 1 }

GS2310ARPStaticGatewayCtrlEntry ::= SEQUENCE {
   gs2310ARPStaticGatewayCtrlIndex       Integer32,
   gs2310ARPStaticGatewayCtrlIPAddress   IpAddress,
   gs2310ARPStaticGatewayCtrlMACAddress  MacAddress,
   gs2310ARPStaticGatewayCtrlPort        Integer32,
   gs2310ARPStaticGatewayCtrlAction      INTEGER,
   gs2310ARPStaticGatewayCtrlState       DisplayString,
   gs2310ARPStaticGatewayCtrlReOpen      INTEGER,
   gs2310ARPStaticGatewayCtrlRowStatus   INTEGER
}

gs2310ARPStaticGatewayCtrlIndex OBJECT-TYPE
   SYNTAX      Integer32(1..4)
   MAX-ACCESS  not-accessible
   STATUS      current
   DESCRIPTION
       ""
   ::= { gs2310ARPStaticGatewayCtrlEntry 1 }

gs2310ARPStaticGatewayCtrlIPAddress OBJECT-TYPE
   SYNTAX      IpAddress
   MAX-ACCESS  read-write
   STATUS      current
   DESCRIPTION
       " Source IP address. "
   ::= { gs2310ARPStaticGatewayCtrlEntry 2 }

gs2310ARPStaticGatewayCtrlMACAddress OBJECT-TYPE
   SYNTAX      MacAddress
   MAX-ACCESS  read-write
   STATUS      current
   DESCRIPTION
       " Source MAC address , format 0a 1b 2c 3d 4e 5f "
   ::= { gs2310ARPStaticGatewayCtrlEntry 3 }

gs2310ARPStaticGatewayCtrlPort OBJECT-TYPE
   SYNTAX      Integer32(1..4095)
   MAX-ACCESS  read-write
   STATUS      current
   DESCRIPTION
       " Port, range: 1 - port number. "
   ::= { gs2310ARPStaticGatewayCtrlEntry 4 }

gs2310ARPStaticGatewayCtrlAction OBJECT-TYPE
   SYNTAX      INTEGER {none(0),trap(1),dropAndTrap(2), shutdown(3), trapAndShutdown(4) }
   MAX-ACCESS  read-write
   STATUS      current
   DESCRIPTION
       "default: 0
       0: none
       1: trap
       2: drop&trap
       3: shutdown
       4: trap&shutdown"
   ::= { gs2310ARPStaticGatewayCtrlEntry 5 }

gs2310ARPStaticGatewayCtrlState OBJECT-TYPE
   SYNTAX      DisplayString
   MAX-ACCESS  read-only
   STATUS      current
   DESCRIPTION
       ""
   ::= { gs2310ARPStaticGatewayCtrlEntry 6 }

gs2310ARPStaticGatewayCtrlReOpen OBJECT-TYPE
   SYNTAX      INTEGER { none(0), reopen(1) }
   MAX-ACCESS  read-write
   STATUS      current
   DESCRIPTION
       "default: 0
       0: none
       1: reopen"
   ::= { gs2310ARPStaticGatewayCtrlEntry 7 }

gs2310ARPStaticGatewayCtrlRowStatus OBJECT-TYPE
   SYNTAX      INTEGER { active(1), notInservice(2), edit(3), destroy(4), undo(5) }
   MAX-ACCESS  read-write
   STATUS      current
   DESCRIPTION
       "1: active
        2: notInservice
        3: edit
        4: destroy
        5: undo"
   ::= { gs2310ARPStaticGatewayCtrlEntry 8 }

gs2310ARPSpoofingPrevention	                                OBJECT IDENTIFIER ::= { gs2310ARPInspection 7 }

gs2310ARPSpoofingPreventionSystemConf                                      OBJECT IDENTIFIER ::= { gs2310ARPSpoofingPrevention 1 }

gs2310ARPSpoofingPreventionMode OBJECT-TYPE
   SYNTAX      INTEGER { disable(0), enable(1) }
   MAX-ACCESS  read-write
   STATUS      current
   DESCRIPTION
       "default: 0
       0: disable
       1: enable "
   ::= { gs2310ARPSpoofingPreventionSystemConf 1 }

gs2310ARPSpoofingPreventionTable OBJECT-TYPE
   SYNTAX      SEQUENCE OF GS2310ARPSpoofingPreventionEntry
   MAX-ACCESS  not-accessible
   STATUS      current
   DESCRIPTION
       " "
   ::= { gs2310ARPSpoofingPrevention 2 }

gs2310ARPSpoofingPreventionEntry OBJECT-TYPE
   SYNTAX      GS2310ARPSpoofingPreventionEntry
   MAX-ACCESS  not-accessible
   STATUS      current
   DESCRIPTION
       ""
   INDEX    { gs2310ARPSpoofingPreventionPort  }
   ::= { gs2310ARPSpoofingPreventionTable 1 }

GS2310ARPSpoofingPreventionEntry ::= SEQUENCE {
   gs2310ARPSpoofingPreventionPort           Integer32,
   gs2310ARPSpoofingPreventionPortMode       INTEGER,
   gs2310ARPSpoofingPreventionPortLimit      Integer32,
   gs2310ARPSpoofingPreventionPortAction     INTEGER,
   gs2310ARPSpoofingPreventionPortState      DisplayString,
   gs2310ARPSpoofingPreventionPortReOpen     INTEGER
}

gs2310ARPSpoofingPreventionPort OBJECT-TYPE
   SYNTAX      Integer32(1..4095)
   MAX-ACCESS  not-accessible
   STATUS      current
   DESCRIPTION
       " "
   ::= { gs2310ARPSpoofingPreventionEntry 1 }

gs2310ARPSpoofingPreventionPortMode OBJECT-TYPE
   SYNTAX      INTEGER { disable(0), enable(1) }
   MAX-ACCESS  read-write
   STATUS      current
   DESCRIPTION
       "default: 0
       0: disable
       1: enable"
   ::= { gs2310ARPSpoofingPreventionEntry 2 }

gs2310ARPSpoofingPreventionPortLimit OBJECT-TYPE
   SYNTAX      Integer32(1..100)
   MAX-ACCESS  read-write
   STATUS      current
   DESCRIPTION
       "default: 1, range: 1-100"
   ::= { gs2310ARPSpoofingPreventionEntry 3 }

gs2310ARPSpoofingPreventionPortAction OBJECT-TYPE
   SYNTAX      INTEGER { none(0), trap(1), dropAndTrap(2), shutdown(3), trapAndShutdown(4) }
   MAX-ACCESS  read-write
   STATUS      current
   DESCRIPTION
       "default: 0
       0: none
       1: trap
       2: drop&trap
       3: shutdown
       4: trap&shutdown"
   ::= { gs2310ARPSpoofingPreventionEntry 4 }

gs2310ARPSpoofingPreventionPortState OBJECT-TYPE
   SYNTAX      DisplayString
   MAX-ACCESS  read-only
   STATUS      current
   DESCRIPTION
       ""
   ::= { gs2310ARPSpoofingPreventionEntry 5 }

gs2310ARPSpoofingPreventionPortReOpen OBJECT-TYPE
   SYNTAX      INTEGER { none(0), reopen(1) }
   MAX-ACCESS  read-write
   STATUS      current
   DESCRIPTION
       "default: 0
       0: none
       1: reopen"
   ::= { gs2310ARPSpoofingPreventionEntry 6 }

gs2310ARPIPDoSPrevention	                                OBJECT IDENTIFIER ::= { gs2310ARPInspection 8 }

gs2310ARPIPDoSPreventionTCPMode OBJECT-TYPE
   SYNTAX      INTEGER { disable(0), enable(1) }
   MAX-ACCESS  read-write
   STATUS      current
   DESCRIPTION
       "default: 0
       0: disable
       1: enable "
   ::= { gs2310ARPIPDoSPrevention 1 }

gs2310ARPIPDoSPreventionUDPMode OBJECT-TYPE
   SYNTAX      INTEGER { disable(0), enable(1) }
   MAX-ACCESS  read-write
   STATUS      current
   DESCRIPTION
       "default: 0
       0: disable
       1: enable "
   ::= { gs2310ARPIPDoSPrevention 2 }

gs2310ARPIPDoSPreventionICMPMode OBJECT-TYPE
   SYNTAX      INTEGER { disable(0), enable(1) }
   MAX-ACCESS  read-write
   STATUS      current
   DESCRIPTION
       "default: 0
       0: disable
       1: enable "
   ::= { gs2310ARPIPDoSPrevention 3 }

gs2310ARPIPDoSPreventionServerPort1 OBJECT-TYPE
   SYNTAX      Integer32(0..4094)
   MAX-ACCESS  read-write
   STATUS      current
   DESCRIPTION
       " Port, range: 0 - port number. 0: none. "
   ::= { gs2310ARPIPDoSPrevention 4 }

gs2310ARPIPDoSPreventionServerPort2 OBJECT-TYPE
   SYNTAX      Integer32(0..4094)
   MAX-ACCESS  read-write
   STATUS      current
   DESCRIPTION
       " Port, range: 0 - port number. 0: none. "
   ::= { gs2310ARPIPDoSPrevention 5 }

gs2310ARPIPDoSPreventionServerPort3 OBJECT-TYPE
   SYNTAX      Integer32(0..4094)
   MAX-ACCESS  read-write
   STATUS      current
   DESCRIPTION
       " Port, range: 0 - port number. 0: none. "
   ::= { gs2310ARPIPDoSPrevention 6 }

gs2310ARPIPDoSPreventionServerPort4 OBJECT-TYPE
   SYNTAX      Integer32(0..4094)
   MAX-ACCESS  read-write
   STATUS      current
   DESCRIPTION
       " Port, range: 0 - port number. 0: none. "
   ::= { gs2310ARPIPDoSPrevention 7 }

gs2310DHCPSnooping                                          OBJECT IDENTIFIER ::= { gs2310Security 3 }

gs2310DHCPSnoopingConf                                          OBJECT IDENTIFIER ::= { gs2310DHCPSnooping 1 }

gs2310DHCPSnoopingMode OBJECT-TYPE
   SYNTAX      INTEGER { disable(0), enable(1) }
   MAX-ACCESS  read-write
   STATUS      current
   DESCRIPTION
       "default: 0
       0: disable
       1: enable"
   ::= { gs2310DHCPSnoopingConf 1 }

gs2310DHCPSnoopingPortModeConfigurationTable OBJECT-TYPE
   SYNTAX      SEQUENCE OF GS2310DHCPSnoopingPortModeConfigurationEntry
   MAX-ACCESS  not-accessible
   STATUS      current
   DESCRIPTION
       " "
   ::= { gs2310DHCPSnoopingConf 2 }

gs2310DHCPSnoopingPortModeConfigurationEntry OBJECT-TYPE
   SYNTAX      GS2310DHCPSnoopingPortModeConfigurationEntry
   MAX-ACCESS  not-accessible
   STATUS      current
   DESCRIPTION
       ""
   INDEX    { gs2310DHCPSnoopingPortModeConfigurationPort  }
   ::= { gs2310DHCPSnoopingPortModeConfigurationTable 1 }

GS2310DHCPSnoopingPortModeConfigurationEntry ::= SEQUENCE {
   gs2310DHCPSnoopingPortModeConfigurationPort	Integer32,
   gs2310DHCPSnoopingPortModeConfigurationMode	INTEGER
}

gs2310DHCPSnoopingPortModeConfigurationPort OBJECT-TYPE
   SYNTAX      Integer32(1..4095)
   MAX-ACCESS  not-accessible
   STATUS      current
   DESCRIPTION
       " "
   ::= { gs2310DHCPSnoopingPortModeConfigurationEntry 1 }

gs2310DHCPSnoopingPortModeConfigurationMode OBJECT-TYPE
   SYNTAX      INTEGER { trust(0), untrust(1) }
   MAX-ACCESS  read-write
   STATUS      current
   DESCRIPTION
       "default: 1
       0: trust port mode
       1: untrust port mode"
   ::= { gs2310DHCPSnoopingPortModeConfigurationEntry 2 }

gs2310DHCPSnoopingStatisticsTable OBJECT-TYPE
   SYNTAX      SEQUENCE OF GS2310DHCPSnoopingStatisticsEntry
   MAX-ACCESS  not-accessible
   STATUS      current
   DESCRIPTION
       " "
   ::= { gs2310DHCPSnooping 2 }

gs2310DHCPSnoopingStatisticsEntry OBJECT-TYPE
   SYNTAX      GS2310DHCPSnoopingStatisticsEntry
   MAX-ACCESS  not-accessible
   STATUS      current
   DESCRIPTION
       ""
   INDEX    { gs2310DHCPSnoopingStatisticsPort  }
   ::= { gs2310DHCPSnoopingStatisticsTable 1 }

GS2310DHCPSnoopingStatisticsEntry ::= SEQUENCE {
   gs2310DHCPSnoopingStatisticsPort         Integer32,
   gs2310DHCPSnoopingStatisticsClear        INTEGER,
   gs2310DHCPSnoopingRxDiscover             Counter32,
   gs2310DHCPSnoopingRxOffer                Counter32,
   gs2310DHCPSnoopingRxRequest              Counter32,
   gs2310DHCPSnoopingRxDecline              Counter32,
   gs2310DHCPSnoopingRxACK                  Counter32,
   gs2310DHCPSnoopingRxNAK                  Counter32,
   gs2310DHCPSnoopingRxRelease              Counter32,
   gs2310DHCPSnoopingRxInform               Counter32,
   gs2310DHCPSnoopingRxLeaseQuery           Counter32,
   gs2310DHCPSnoopingRxLeaseUnassigned      Counter32,
   gs2310DHCPSnoopingRxLeaseUnknown         Counter32,
   gs2310DHCPSnoopingRxLeaseActive          Counter32,
   gs2310DHCPSnoopingTxDiscover             Counter32,
   gs2310DHCPSnoopingTxOffer                Counter32,
   gs2310DHCPSnoopingTxRequest              Counter32,
   gs2310DHCPSnoopingTxDecline              Counter32,
   gs2310DHCPSnoopingTxACK                  Counter32,
   gs2310DHCPSnoopingTxNAK                  Counter32,
   gs2310DHCPSnoopingTxRelease              Counter32,
   gs2310DHCPSnoopingTxInform               Counter32,
   gs2310DHCPSnoopingTxLeaseQuery           Counter32,
   gs2310DHCPSnoopingTxLeaseUnassigned      Counter32,
   gs2310DHCPSnoopingTxLeaseUnknown         Counter32,
   gs2310DHCPSnoopingTxLeaseActive          Counter32
}

gs2310DHCPSnoopingStatisticsPort OBJECT-TYPE
   SYNTAX      Integer32(1..4095)
   MAX-ACCESS  not-accessible
   STATUS      current
   DESCRIPTION
       " "
   ::= { gs2310DHCPSnoopingStatisticsEntry 1 }

gs2310DHCPSnoopingStatisticsClear OBJECT-TYPE
   SYNTAX      INTEGER { none(0), clear(1) }
   MAX-ACCESS  read-write
   STATUS      current
   DESCRIPTION
       "default: 0
       0: none
       1: clear"
   ::= { gs2310DHCPSnoopingStatisticsEntry 2 }

gs2310DHCPSnoopingRxDiscover OBJECT-TYPE
   SYNTAX      Counter32
   MAX-ACCESS  read-only
   STATUS      current
   DESCRIPTION
       " "
   ::= { gs2310DHCPSnoopingStatisticsEntry 3 }

gs2310DHCPSnoopingRxOffer OBJECT-TYPE
   SYNTAX      Counter32
   MAX-ACCESS  read-only
   STATUS      current
   DESCRIPTION
       " "
   ::= { gs2310DHCPSnoopingStatisticsEntry 4 }

gs2310DHCPSnoopingRxRequest OBJECT-TYPE
   SYNTAX      Counter32
   MAX-ACCESS  read-only
   STATUS      current
   DESCRIPTION
       " "
   ::= { gs2310DHCPSnoopingStatisticsEntry 5 }

gs2310DHCPSnoopingRxDecline OBJECT-TYPE
   SYNTAX      Counter32
   MAX-ACCESS  read-only
   STATUS      current
   DESCRIPTION
       " "
   ::= { gs2310DHCPSnoopingStatisticsEntry 6 }

gs2310DHCPSnoopingRxACK OBJECT-TYPE
   SYNTAX      Counter32
   MAX-ACCESS  read-only
   STATUS      current
   DESCRIPTION
       " "
   ::= { gs2310DHCPSnoopingStatisticsEntry 7 }

gs2310DHCPSnoopingRxNAK OBJECT-TYPE
   SYNTAX      Counter32
   MAX-ACCESS  read-only
   STATUS      current
   DESCRIPTION
       " "
   ::= { gs2310DHCPSnoopingStatisticsEntry 8 }

gs2310DHCPSnoopingRxRelease OBJECT-TYPE
   SYNTAX      Counter32
   MAX-ACCESS  read-only
   STATUS      current
   DESCRIPTION
       " "
   ::= { gs2310DHCPSnoopingStatisticsEntry 9 }

gs2310DHCPSnoopingRxInform OBJECT-TYPE
   SYNTAX      Counter32
   MAX-ACCESS  read-only
   STATUS      current
   DESCRIPTION
       " "
   ::= { gs2310DHCPSnoopingStatisticsEntry 10 }

gs2310DHCPSnoopingRxLeaseQuery OBJECT-TYPE
   SYNTAX      Counter32
   MAX-ACCESS  read-only
   STATUS      current
   DESCRIPTION
       " "
   ::= { gs2310DHCPSnoopingStatisticsEntry 11 }

gs2310DHCPSnoopingRxLeaseUnassigned OBJECT-TYPE
   SYNTAX      Counter32
   MAX-ACCESS  read-only
   STATUS      current
   DESCRIPTION
       " "
   ::= { gs2310DHCPSnoopingStatisticsEntry 12 }

gs2310DHCPSnoopingRxLeaseUnknown OBJECT-TYPE
   SYNTAX      Counter32
   MAX-ACCESS  read-only
   STATUS      current
   DESCRIPTION
       " "
   ::= { gs2310DHCPSnoopingStatisticsEntry 13 }

gs2310DHCPSnoopingRxLeaseActive OBJECT-TYPE
   SYNTAX      Counter32
   MAX-ACCESS  read-only
   STATUS      current
   DESCRIPTION
       " "
   ::= { gs2310DHCPSnoopingStatisticsEntry 14 }

gs2310DHCPSnoopingTxDiscover OBJECT-TYPE
   SYNTAX      Counter32
   MAX-ACCESS  read-only
   STATUS      current
   DESCRIPTION
       " "
   ::= { gs2310DHCPSnoopingStatisticsEntry 15 }

gs2310DHCPSnoopingTxOffer OBJECT-TYPE
   SYNTAX      Counter32
   MAX-ACCESS  read-only
   STATUS      current
   DESCRIPTION
       " "
   ::= { gs2310DHCPSnoopingStatisticsEntry 16 }

gs2310DHCPSnoopingTxRequest OBJECT-TYPE
   SYNTAX      Counter32
   MAX-ACCESS  read-only
   STATUS      current
   DESCRIPTION
       " "
   ::= { gs2310DHCPSnoopingStatisticsEntry 17 }

gs2310DHCPSnoopingTxDecline OBJECT-TYPE
   SYNTAX      Counter32
   MAX-ACCESS  read-only
   STATUS      current
   DESCRIPTION
       " "
   ::= { gs2310DHCPSnoopingStatisticsEntry 18 }

gs2310DHCPSnoopingTxACK OBJECT-TYPE
   SYNTAX      Counter32
   MAX-ACCESS  read-only
   STATUS      current
   DESCRIPTION
       " "
   ::= { gs2310DHCPSnoopingStatisticsEntry 19 }

gs2310DHCPSnoopingTxNAK OBJECT-TYPE
   SYNTAX      Counter32
   MAX-ACCESS  read-only
   STATUS      current
   DESCRIPTION
       " "
   ::= { gs2310DHCPSnoopingStatisticsEntry 20 }

gs2310DHCPSnoopingTxRelease OBJECT-TYPE
   SYNTAX      Counter32
   MAX-ACCESS  read-only
   STATUS      current
   DESCRIPTION
       " "
   ::= { gs2310DHCPSnoopingStatisticsEntry 21 }

gs2310DHCPSnoopingTxInform OBJECT-TYPE
   SYNTAX      Counter32
   MAX-ACCESS  read-only
   STATUS      current
   DESCRIPTION
       " "
   ::= { gs2310DHCPSnoopingStatisticsEntry 22 }

gs2310DHCPSnoopingTxLeaseQuery OBJECT-TYPE
   SYNTAX      Counter32
   MAX-ACCESS  read-only
   STATUS      current
   DESCRIPTION
       " "
   ::= { gs2310DHCPSnoopingStatisticsEntry 23 }

gs2310DHCPSnoopingTxLeaseUnassigned OBJECT-TYPE
   SYNTAX      Counter32
   MAX-ACCESS  read-only
   STATUS      current
   DESCRIPTION
       " "
   ::= { gs2310DHCPSnoopingStatisticsEntry 24 }

gs2310DHCPSnoopingTxLeaseUnknown OBJECT-TYPE
   SYNTAX      Counter32
   MAX-ACCESS  read-only
   STATUS      current
   DESCRIPTION
       " "
   ::= { gs2310DHCPSnoopingStatisticsEntry 25 }

gs2310DHCPSnoopingTxLeaseActive OBJECT-TYPE
   SYNTAX      Counter32
   MAX-ACCESS  read-only
   STATUS      current
   DESCRIPTION
       " "
   ::= { gs2310DHCPSnoopingStatisticsEntry 26 }


gs2310DHCPRelay                                             OBJECT IDENTIFIER ::= { gs2310Security 4 }

gs2310DHCPRelayConfiguration                                         OBJECT IDENTIFIER ::= { gs2310DHCPRelay 1 }

gs2310DHCPRelayMode OBJECT-TYPE
   SYNTAX      INTEGER { disable(0), enable(1) }
   MAX-ACCESS  read-write
   STATUS      current
   DESCRIPTION
       "default: 0
       0: disable
       1: enable
       We need at least one server"
   ::= { gs2310DHCPRelayConfiguration 1 }

gs2310DHCPRelayServer OBJECT-TYPE
   SYNTAX      IpAddress
   MAX-ACCESS  read-write
   STATUS      current
   DESCRIPTION
       " "
   ::= { gs2310DHCPRelayConfiguration 2 }

gs2310DHCPRelayInformationMode OBJECT-TYPE
   SYNTAX      INTEGER { disable(0), enable(1) }
   MAX-ACCESS  read-write
   STATUS      current
   DESCRIPTION
       "default: 0
       0: disable
       1: enable "
   ::= { gs2310DHCPRelayConfiguration 3 }

gs2310DHCPRelayInformationPolicy OBJECT-TYPE
   SYNTAX      INTEGER { replace(0), keep(1), drop(2) }
   MAX-ACCESS  read-write
   STATUS      current
   DESCRIPTION
       "default: 0
       0: replace
       1: keep
       2: drop "
   ::= { gs2310DHCPRelayConfiguration 4 }

gs2310DHCPRelayInformationCustom OBJECT-TYPE
   SYNTAX      DisplayString(SIZE(0..32))
   MAX-ACCESS  read-write
   STATUS      current
   DESCRIPTION
       "DHCP Option 82 Circuit ID custom information"
   ::= { gs2310DHCPRelayConfiguration 1500 }

gs2310DHCPRelayConfigurationGateways                                          OBJECT IDENTIFIER ::= { gs2310DHCPRelayConfiguration 5 }

gs2310DHCPRelayConfigurationGatewaysCreate OBJECT-TYPE
   SYNTAX       INTEGER { none(0), create(1) }
   MAX-ACCESS   read-write
   STATUS       current
   DESCRIPTION
       "default: 0
        0 : None  (read only)
        1 : Create entry"
   ::= { gs2310DHCPRelayConfigurationGateways 1 }

gs2310DHCPRelayConfigurationGatewaysTable OBJECT-TYPE
   SYNTAX      SEQUENCE OF Gs2310DHCPRelayConfigurationGatewaysEntry
   MAX-ACCESS  not-accessible
   STATUS      current
   DESCRIPTION
       " Create DHCP Relay Gateway IP address entry."
   ::= { gs2310DHCPRelayConfigurationGateways 2 }

gs2310DHCPRelayConfigurationGatewaysEntry OBJECT-TYPE
   SYNTAX      Gs2310DHCPRelayConfigurationGatewaysEntry
   MAX-ACCESS  not-accessible
   STATUS      current
   DESCRIPTION
       ""
   INDEX    { gs2310DHCPRelayConfigurationGatewaysIndex  }
   ::= { gs2310DHCPRelayConfigurationGatewaysTable 1 }

Gs2310DHCPRelayConfigurationGatewaysEntry ::= SEQUENCE {
   gs2310DHCPRelayConfigurationGatewaysIndex           Integer32,
   gs2310DHCPRelayConfigurationGatewaysVLANId          Integer32,
   gs2310DHCPRelayConfigurationGatewaysIP              IpAddress,
   gs2310DHCPRelayConfigurationGatewaysRowStatus       INTEGER
}

gs2310DHCPRelayConfigurationGatewaysIndex OBJECT-TYPE
   SYNTAX      Integer32(1..6)
   MAX-ACCESS  not-accessible
   STATUS      current
   DESCRIPTION
       " "
   ::= { gs2310DHCPRelayConfigurationGatewaysEntry 1 }

gs2310DHCPRelayConfigurationGatewaysVLANId OBJECT-TYPE
   SYNTAX      Integer32(1..4094)
   MAX-ACCESS  read-write
   STATUS      current
   DESCRIPTION
       " VLAN ID "
   ::= { gs2310DHCPRelayConfigurationGatewaysEntry 2 }

gs2310DHCPRelayConfigurationGatewaysIP OBJECT-TYPE
   SYNTAX      IpAddress
   MAX-ACCESS  read-write
   STATUS      current
   DESCRIPTION
       "DHCP GIADDR address."
   ::= { gs2310DHCPRelayConfigurationGatewaysEntry 3 }

gs2310DHCPRelayConfigurationGatewaysRowStatus OBJECT-TYPE
   SYNTAX      INTEGER { active(1), notInservice(2), destroy(4), undo(5) }
   MAX-ACCESS  read-write
   STATUS      current
   DESCRIPTION
       "1: active
        2: notInservice
        4: destroy
        5: undo"
   ::= { gs2310DHCPRelayConfigurationGatewaysEntry 4 }

gs2310DHCPRelayStatistics                                   OBJECT IDENTIFIER ::= { gs2310DHCPRelay 2 }

gs2310DHCPRelayServerStatistics                                   OBJECT IDENTIFIER ::= { gs2310DHCPRelayStatistics 1 }

gs2310ServerStatTransmitToServer OBJECT-TYPE
   SYNTAX      Counter32
   MAX-ACCESS  read-only
   STATUS      current
   DESCRIPTION
       " "
   ::= { gs2310DHCPRelayServerStatistics 1 }

gs2310ServerStatTransmitError OBJECT-TYPE
   SYNTAX      Counter32
   MAX-ACCESS  read-only
   STATUS      current
   DESCRIPTION
       " "
   ::= { gs2310DHCPRelayServerStatistics 2 }

gs2310ServerStatReceiveFromServer OBJECT-TYPE
   SYNTAX      Counter32
   MAX-ACCESS  read-only
   STATUS      current
   DESCRIPTION
       " "
   ::= { gs2310DHCPRelayServerStatistics 3 }

gs2310ServerStatReceiveMissingAgentOption OBJECT-TYPE
   SYNTAX      Counter32
   MAX-ACCESS  read-only
   STATUS      current
   DESCRIPTION
       " "
   ::= { gs2310DHCPRelayServerStatistics 4 }

gs2310ServerStatReceiveMissingCircuitID OBJECT-TYPE
   SYNTAX      Counter32
   MAX-ACCESS  read-only
   STATUS      current
   DESCRIPTION
       " "
   ::= { gs2310DHCPRelayServerStatistics 5 }

gs2310ServerStatReceiveMissingRemoteID OBJECT-TYPE
   SYNTAX      Counter32
   MAX-ACCESS  read-only
   STATUS      current
   DESCRIPTION
       " "
   ::= { gs2310DHCPRelayServerStatistics 6 }

gs2310ServerStatReceiveBadCircuitID OBJECT-TYPE
   SYNTAX      Counter32
   MAX-ACCESS  read-only
   STATUS      current
   DESCRIPTION
       " "
   ::= { gs2310DHCPRelayServerStatistics 7 }

gs2310ServerStatReceiveBadRemoteID OBJECT-TYPE
   SYNTAX      Counter32
   MAX-ACCESS  read-only
   STATUS      current
   DESCRIPTION
       " "
   ::= { gs2310DHCPRelayServerStatistics 8 }

gs2310DHCPRelayClientStatistics                                   OBJECT IDENTIFIER ::= { gs2310DHCPRelayStatistics 2 }

gs2310ClientStatTransmitToClient OBJECT-TYPE
   SYNTAX      Counter32
   MAX-ACCESS  read-only
   STATUS      current
   DESCRIPTION
       " "
   ::= { gs2310DHCPRelayClientStatistics 1 }

gs2310ClientStatTransmitError OBJECT-TYPE
   SYNTAX      Counter32
   MAX-ACCESS  read-only
   STATUS      current
   DESCRIPTION
       " "
   ::= { gs2310DHCPRelayClientStatistics 2 }

gs2310ClientStatReceivefromClient OBJECT-TYPE
   SYNTAX      Counter32
   MAX-ACCESS  read-only
   STATUS      current
   DESCRIPTION
       " "
   ::= { gs2310DHCPRelayClientStatistics 3 }

gs2310ClientStatReceiveAgentOption OBJECT-TYPE
   SYNTAX      Counter32
   MAX-ACCESS  read-only
   STATUS      current
   DESCRIPTION
       " "
   ::= { gs2310DHCPRelayClientStatistics 4 }

gs2310ClientStatReplaceAgentOption OBJECT-TYPE
   SYNTAX      Counter32
   MAX-ACCESS  read-only
   STATUS      current
   DESCRIPTION
       " "
   ::= { gs2310DHCPRelayClientStatistics 5 }

gs2310ClientStatKeepAgentOption OBJECT-TYPE
   SYNTAX      Counter32
   MAX-ACCESS  read-only
   STATUS      current
   DESCRIPTION
       " "
   ::= { gs2310DHCPRelayClientStatistics 6 }

gs2310ClientStatDropAgentOption OBJECT-TYPE
   SYNTAX      Counter32
   MAX-ACCESS  read-only
   STATUS      current
   DESCRIPTION
       " "
   ::= { gs2310DHCPRelayClientStatistics 7 }

gs2310PortSecurity                                          OBJECT IDENTIFIER ::= { gs2310Security 5 }

gs2310PortSecLimitCtrl                                      OBJECT IDENTIFIER ::= { gs2310PortSecurity 1 }

gs2310PortSecLimitCtrlSystemConf                                      OBJECT IDENTIFIER ::= { gs2310PortSecLimitCtrl 1 }

gs2310PortSecurityMode OBJECT-TYPE
   SYNTAX      INTEGER { disable(0), enable(1) }
   MAX-ACCESS  read-write
   STATUS      current
   DESCRIPTION
       "default: 0
       0: disable
       1: enable "
   ::= { gs2310PortSecLimitCtrlSystemConf 1 }

gs2310PortSecurityAging OBJECT-TYPE
   SYNTAX      INTEGER { disable(0), enable(1) }
   MAX-ACCESS  read-write
   STATUS      current
   DESCRIPTION
       "default: 0
       0: disable
       1: enable "
   ::= { gs2310PortSecLimitCtrlSystemConf 2 }

gs2310PortSecurityAgingPeriod OBJECT-TYPE
   SYNTAX      INTEGER(10..10000000)
   MAX-ACCESS  read-write
   STATUS      current
   DESCRIPTION
       "default: 3600, range: 10-10000000 "
   ::= { gs2310PortSecLimitCtrlSystemConf 3 }

gs2310PortSecLimitCtrlTable OBJECT-TYPE
   SYNTAX      SEQUENCE OF GS2310PortSecLimitCtrlEntry
   MAX-ACCESS  not-accessible
   STATUS      current
   DESCRIPTION
       " "
   ::= { gs2310PortSecLimitCtrl 2 }

gs2310PortSecLimitCtrlEntry OBJECT-TYPE
   SYNTAX      GS2310PortSecLimitCtrlEntry
   MAX-ACCESS  not-accessible
   STATUS      current
   DESCRIPTION
       ""
   INDEX    { gs2310PortSecLimitCtrlPort  }
   ::= { gs2310PortSecLimitCtrlTable 1 }

GS2310PortSecLimitCtrlEntry ::= SEQUENCE {
   gs2310PortSecLimitCtrlPort           Integer32,
   gs2310PortSecLimitCtrlPortMode       INTEGER,
   gs2310PortSecLimitCtrlPortLimit      Integer32,
   gs2310PortSecLimitCtrlPortAction     INTEGER,
   gs2310PortSecLimitCtrlPortState      DisplayString,
   gs2310PortSecLimitCtrlPortReOpen     INTEGER
}

gs2310PortSecLimitCtrlPort OBJECT-TYPE
   SYNTAX      Integer32(1..4095)
   MAX-ACCESS  not-accessible
   STATUS      current
   DESCRIPTION
       " "
   ::= { gs2310PortSecLimitCtrlEntry 1 }

gs2310PortSecLimitCtrlPortMode OBJECT-TYPE
   SYNTAX      INTEGER { disable(0), enable(1) }
   MAX-ACCESS  read-write
   STATUS      current
   DESCRIPTION
       "default: 0
       0: disable
       1: enable"
   ::= { gs2310PortSecLimitCtrlEntry 2 }

gs2310PortSecLimitCtrlPortLimit OBJECT-TYPE
   SYNTAX      Integer32(1..1024)
   MAX-ACCESS  read-write
   STATUS      current
   DESCRIPTION
       "default: 4, range: 1-1024"
   ::= { gs2310PortSecLimitCtrlEntry 3 }

gs2310PortSecLimitCtrlPortAction OBJECT-TYPE
   SYNTAX      INTEGER { none(0), trap(1), shutdown(2), trapShutdown(3) }
   MAX-ACCESS  read-write
   STATUS      current
   DESCRIPTION
       "default: 0
       0: none
       1: trap
       2: shutdown
       3: trap&shutdown"
   ::= { gs2310PortSecLimitCtrlEntry 4 }

gs2310PortSecLimitCtrlPortState OBJECT-TYPE
   SYNTAX      DisplayString
   MAX-ACCESS  read-only
   STATUS      current
   DESCRIPTION
       ""
   ::= { gs2310PortSecLimitCtrlEntry 5 }

gs2310PortSecLimitCtrlPortReOpen OBJECT-TYPE
   SYNTAX      INTEGER { none(0), reopen(1) }
   MAX-ACCESS  read-write
   STATUS      current
   DESCRIPTION
       "default: 0
       0: none
       1: reopen"
   ::= { gs2310PortSecLimitCtrlEntry 6 }

gs2310PortSecSwitchStatusTable OBJECT-TYPE
   SYNTAX      SEQUENCE OF GS2310PortSecSwitchStatusEntry
   MAX-ACCESS  not-accessible
   STATUS      current
   DESCRIPTION
       " "
   ::= { gs2310PortSecurity 2 }

gs2310PortSecSwitchStatusEntry OBJECT-TYPE
   SYNTAX      GS2310PortSecSwitchStatusEntry
   MAX-ACCESS  not-accessible
   STATUS      current
   DESCRIPTION
       ""
   INDEX    { gs2310PortSecSwitchStatusPort  }
   ::= { gs2310PortSecSwitchStatusTable 1 }

GS2310PortSecSwitchStatusEntry ::= SEQUENCE {
   gs2310PortSecSwitchStatusPort                Integer32,
   gs2310PortSecSwitchStatusUsers               DisplayString,
   gs2310PortSecSwitchStatusState               DisplayString,
   gs2310PortSecSwitchStatusMACCountCurrent     Integer32,
   gs2310PortSecSwitchStatusMACCountLimit       Integer32
}

gs2310PortSecSwitchStatusPort OBJECT-TYPE
   SYNTAX      Integer32(1..4095)
   MAX-ACCESS  not-accessible
   STATUS      current
   DESCRIPTION
       " "
   ::= { gs2310PortSecSwitchStatusEntry 1 }

gs2310PortSecSwitchStatusUsers OBJECT-TYPE
   SYNTAX      DisplayString
   MAX-ACCESS  read-only
   STATUS      current
   DESCRIPTION
       " Users Abbr: L = Limit Control, 8 = 802.1X, D = DHCP Snooping, V = Voice VLAN,
         '-' means that the corresponding user module is not enabled. "
   ::= { gs2310PortSecSwitchStatusEntry 2 }

gs2310PortSecSwitchStatusState OBJECT-TYPE
   SYNTAX      DisplayString
   MAX-ACCESS  read-only
   STATUS      current
   DESCRIPTION
       " Shows the current state of the port : Disabled, Ready, Limit Reached, Shutdown. "
   ::= { gs2310PortSecSwitchStatusEntry 3 }

gs2310PortSecSwitchStatusMACCountCurrent OBJECT-TYPE
   SYNTAX      Integer32(1..4095)
   MAX-ACCESS  read-only
   STATUS      current
   DESCRIPTION
       ""
   ::= { gs2310PortSecSwitchStatusEntry 4 }

gs2310PortSecSwitchStatusMACCountLimit OBJECT-TYPE
   SYNTAX      Integer32(1..4095)
   MAX-ACCESS  read-only
   STATUS      current
   DESCRIPTION
       ""
   ::= { gs2310PortSecSwitchStatusEntry 5 }

gs2310PortSecPortStatus                                      OBJECT IDENTIFIER ::= { gs2310PortSecurity 3 }

gs2310PortSecPortStatusPort OBJECT-TYPE
   SYNTAX       Integer32(1..4095)
   MAX-ACCESS   read-write
   STATUS       current
   DESCRIPTION
       "port number
        default: 1
        range: 1 - port number."
   ::= { gs2310PortSecPortStatus 1 }

gs2310PortSecPortStatusTable OBJECT-TYPE
   SYNTAX      SEQUENCE OF GS2310PortSecPortStatusEntry
   MAX-ACCESS  not-accessible
   STATUS      current
   DESCRIPTION
      " "
   ::= { gs2310PortSecPortStatus 2 }

gs2310PortSecPortStatusEntry OBJECT-TYPE
   SYNTAX      GS2310PortSecPortStatusEntry
   MAX-ACCESS  not-accessible
   STATUS      current
   DESCRIPTION
       ""
   INDEX    { gs2310PortSecPortStatusIndex  }
   ::= { gs2310PortSecPortStatusTable 1 }

GS2310PortSecPortStatusEntry ::= SEQUENCE {
   gs2310PortSecPortStatusIndex              Integer32,
   gs2310PortSecPortStatusMACAddress         MacAddress,
   gs2310PortSecPortStatusVLANId             Integer32,
   gs2310PortSecPortStatusState              DisplayString,
   gs2310PortSecPortStatusTimeOfAddition     DisplayString,
   gs2310PortSecPortStatusAgeAndHold         DisplayString
}

gs2310PortSecPortStatusIndex OBJECT-TYPE
   SYNTAX      Integer32(1..4095)
   MAX-ACCESS  not-accessible
   STATUS      current
   DESCRIPTION
       " "
   ::= { gs2310PortSecPortStatusEntry 1 }

gs2310PortSecPortStatusMACAddress OBJECT-TYPE
   SYNTAX      MacAddress
   MAX-ACCESS  read-only
   STATUS      current
   DESCRIPTION
       " "
   ::= { gs2310PortSecPortStatusEntry 2 }

gs2310PortSecPortStatusVLANId OBJECT-TYPE
   SYNTAX      Integer32(1..4094)
   MAX-ACCESS  read-only
   STATUS      current
   DESCRIPTION
       " "
   ::= { gs2310PortSecPortStatusEntry 3 }

gs2310PortSecPortStatusState OBJECT-TYPE
   SYNTAX      DisplayString
   MAX-ACCESS  read-only
   STATUS      current
   DESCRIPTION
       "Blocked / Forwarding "
   ::= { gs2310PortSecPortStatusEntry 4 }

gs2310PortSecPortStatusTimeOfAddition OBJECT-TYPE
   SYNTAX      DisplayString
   MAX-ACCESS  read-only
   STATUS      current
   DESCRIPTION
       " "
   ::= { gs2310PortSecPortStatusEntry 5 }

gs2310PortSecPortStatusAgeAndHold OBJECT-TYPE
   SYNTAX      DisplayString
   MAX-ACCESS  read-only
   STATUS      current
   DESCRIPTION
       " "
   ::= { gs2310PortSecPortStatusEntry 6 }


gs2310AccessManagement                                      OBJECT IDENTIFIER ::= { gs2310Security 6 }

gs2310AccessMgtConf                                         OBJECT IDENTIFIER ::= { gs2310AccessManagement 1 }

gs2310AccessMgtConfMode OBJECT-TYPE
   SYNTAX      INTEGER { disable(0), enable(1) }
   MAX-ACCESS  read-write
   STATUS      current
   DESCRIPTION
       "default: 0
       0: disable
       1: enable "
   ::= { gs2310AccessMgtConf 1 }

gs2310AccessMgtConfCreate OBJECT-TYPE
   SYNTAX      INTEGER { none(0), create(1) }
   MAX-ACCESS  read-write
   STATUS      current
   DESCRIPTION
       "default: 0
       0: none
       1: create "
   ::= { gs2310AccessMgtConf 2 }

gs2310AccessMgtConfTable OBJECT-TYPE
   SYNTAX      SEQUENCE OF GS2310AccessMgtConfEntry
   MAX-ACCESS  not-accessible
   STATUS      current
   DESCRIPTION
       " "
   ::= { gs2310AccessMgtConf 3 }

gs2310AccessMgtConfEntry OBJECT-TYPE
   SYNTAX      GS2310AccessMgtConfEntry
   MAX-ACCESS  not-accessible
   STATUS      current
   DESCRIPTION
       ""
   INDEX    { gs2310AccessMgtIndex  }
   ::= { gs2310AccessMgtConfTable 1 }

GS2310AccessMgtConfEntry ::= SEQUENCE {
   gs2310AccessMgtIndex             Integer32,
   gs2310AccessMgtAddresstype       INTEGER,
   gs2310AccessMgtStartIpAddress    DisplayString,
   gs2310AccessMgtEndIpAddress      DisplayString,
   gs2310AccessMgtHttpHttps         INTEGER,
   gs2310AccessMgtSNMP              INTEGER,
   gs2310AccessMgtTelnetSSH         INTEGER,
   gs2310AccessMgtRowStatus         INTEGER
}

gs2310AccessMgtIndex OBJECT-TYPE
   SYNTAX      Integer32(1..16)
   MAX-ACCESS  read-write
   STATUS      current
   DESCRIPTION
       "Set Access Management config index
        range : 1-16."
   ::= { gs2310AccessMgtConfEntry 1 }

gs2310AccessMgtAddresstype OBJECT-TYPE
   SYNTAX      INTEGER { ipv4(0), ipv6(1) }
   MAX-ACCESS  read-write
   STATUS      current
   DESCRIPTION
       "0: ipv4
        1: ipv6 "
   ::= { gs2310AccessMgtConfEntry 2 }

gs2310AccessMgtStartIpAddress OBJECT-TYPE
   SYNTAX      DisplayString
   MAX-ACCESS  read-write
   STATUS      current
   DESCRIPTION
       " Start IP address.
         IP address doesn't allowed all zero or all 'ff'H."
   ::= { gs2310AccessMgtConfEntry 3 }

gs2310AccessMgtEndIpAddress OBJECT-TYPE
   SYNTAX      DisplayString
   MAX-ACCESS  read-write
   STATUS      current
   DESCRIPTION
       " End IP address.
         IP address doesn't allowed all zero or all 'ff'H.
         End ip address is not less than start ip address."
   ::= { gs2310AccessMgtConfEntry 4 }

gs2310AccessMgtHttpHttps OBJECT-TYPE
   SYNTAX      INTEGER { disable(0), enable(1) }
   MAX-ACCESS  read-write
   STATUS      current
   DESCRIPTION
       "default: 0
       0: disable
       1: enable "
   ::= { gs2310AccessMgtConfEntry 5 }

gs2310AccessMgtSNMP OBJECT-TYPE
   SYNTAX      INTEGER { disable(0), enable(1) }
   MAX-ACCESS  read-write
   STATUS      current
   DESCRIPTION
       "default: 0
       0: disable
       1: enable "
   ::= { gs2310AccessMgtConfEntry 6 }

gs2310AccessMgtTelnetSSH OBJECT-TYPE
   SYNTAX      INTEGER { disable(0), enable(1) }
   MAX-ACCESS  read-write
   STATUS      current
   DESCRIPTION
       "default: 0
       0: disable
       1: enable "
   ::= { gs2310AccessMgtConfEntry 7 }

gs2310AccessMgtRowStatus OBJECT-TYPE
   SYNTAX      INTEGER { active(1), notInservice(2), edit(3),destroy(4), undo(5) }
   MAX-ACCESS  read-write
   STATUS      current
   DESCRIPTION
       "1: active
        2: notInservice
        3: edit
        4: destroy
        5: undo"
   ::= { gs2310AccessMgtConfEntry 8 }

gs2310AccessMgtStatistics                                   OBJECT IDENTIFIER ::= { gs2310AccessManagement 2 }

gs2310HttpReceivedPkts OBJECT-TYPE
   SYNTAX      Counter32
   MAX-ACCESS  read-only
   STATUS      current
   DESCRIPTION
       " "
   ::= { gs2310AccessMgtStatistics 1 }

gs2310HttpAllowedPkts OBJECT-TYPE
   SYNTAX      Counter32
   MAX-ACCESS  read-only
   STATUS      current
   DESCRIPTION
       " "
   ::= { gs2310AccessMgtStatistics 2 }

gs2310HttpDiscardedPkts OBJECT-TYPE
   SYNTAX      Counter32
   MAX-ACCESS  read-only
   STATUS      current
   DESCRIPTION
       " "
   ::= { gs2310AccessMgtStatistics 3 }

gs2310HttpsReceivedPkts OBJECT-TYPE
   SYNTAX      Counter32
   MAX-ACCESS  read-only
   STATUS      current
   DESCRIPTION
       " "
   ::= { gs2310AccessMgtStatistics 4 }

gs2310HttpsAllowedPkts OBJECT-TYPE
   SYNTAX      Counter32
   MAX-ACCESS  read-only
   STATUS      current
   DESCRIPTION
       " "
   ::= { gs2310AccessMgtStatistics 5 }

gs2310HttpsDiscardedPkts OBJECT-TYPE
   SYNTAX      Counter32
   MAX-ACCESS  read-only
   STATUS      current
   DESCRIPTION
       " "
   ::= { gs2310AccessMgtStatistics 6 }

gs2310SnmpReceivedPkts OBJECT-TYPE
   SYNTAX      Counter32
   MAX-ACCESS  read-only
   STATUS      current
   DESCRIPTION
       " "
   ::= { gs2310AccessMgtStatistics 7 }

gs2310SnmpAllowedPkts OBJECT-TYPE
   SYNTAX      Counter32
   MAX-ACCESS  read-only
   STATUS      current
   DESCRIPTION
       " "
   ::= { gs2310AccessMgtStatistics 8 }

gs2310SnmpDiscardedPkts OBJECT-TYPE
   SYNTAX      Counter32
   MAX-ACCESS  read-only
   STATUS      current
   DESCRIPTION
       " "
   ::= { gs2310AccessMgtStatistics 9 }

gs2310TelnetReceivedPkts OBJECT-TYPE
   SYNTAX      Counter32
   MAX-ACCESS  read-only
   STATUS      current
   DESCRIPTION
       " "
   ::= { gs2310AccessMgtStatistics 10 }

gs2310TelnetAllowedPkts OBJECT-TYPE
   SYNTAX      Counter32
   MAX-ACCESS  read-only
   STATUS      current
   DESCRIPTION
       " "
   ::= { gs2310AccessMgtStatistics 11 }

gs2310TelnetDiscardedPkts OBJECT-TYPE
   SYNTAX      Counter32
   MAX-ACCESS  read-only
   STATUS      current
   DESCRIPTION
       " "
   ::= { gs2310AccessMgtStatistics 12 }

gs2310SSHReceivedPkts OBJECT-TYPE
   SYNTAX      Counter32
   MAX-ACCESS  read-only
   STATUS      current
   DESCRIPTION
       " "
   ::= { gs2310AccessMgtStatistics 13 }

gs2310SSHAllowedPkts OBJECT-TYPE
   SYNTAX      Counter32
   MAX-ACCESS  read-only
   STATUS      current
   DESCRIPTION
       " "
   ::= { gs2310AccessMgtStatistics 14 }

gs2310SSHDiscardedPkts OBJECT-TYPE
   SYNTAX      Counter32
   MAX-ACCESS  read-only
   STATUS      current
   DESCRIPTION
       " "
   ::= { gs2310AccessMgtStatistics 15 }

gs2310AccessMgtStatisticsClearAll OBJECT-TYPE
   SYNTAX      INTEGER { none(0), clear(1) }
   MAX-ACCESS  read-write
   STATUS      current
   DESCRIPTION
       "0: none
        1: clear"
   ::= { gs2310AccessMgtStatistics 16 }

gs2310SSH                                                   OBJECT IDENTIFIER ::= { gs2310Security 7 }

gs2310SSHMode OBJECT-TYPE
   SYNTAX      INTEGER { disable(0), enable(1) }
   MAX-ACCESS  read-write
   STATUS      current
   DESCRIPTION
       "default: 1
        0: disable
        1: enable"
   ::= { gs2310SSH 1 }

gs2310HTTPS                                                 OBJECT IDENTIFIER ::= { gs2310Security 8 }

gs2310HTTPSMode OBJECT-TYPE
   SYNTAX      INTEGER { disable(0), enable(1) }
   MAX-ACCESS  read-write
   STATUS      current
   DESCRIPTION
       "default: 1
        0: disable
        1: enable"
   ::= { gs2310HTTPS 1 }

gs2310HTTPSAutoRedirect OBJECT-TYPE
   SYNTAX      INTEGER { disable(0), enable(1) }
   MAX-ACCESS  read-write
   STATUS      current
   DESCRIPTION
       "default: 0
        0: disable
        1: enable"
   ::= { gs2310HTTPS 2 }

gs2310HTTPSCertRenew OBJECT-TYPE
   SYNTAX      INTEGER { doNothing(0), renew(1) }
   MAX-ACCESS  read-write
   STATUS      current
   DESCRIPTION
       "default: 0 ,
        0: doNothing
        1: renew"
   ::= { gs2310HTTPS 3 }

gs2310HTTPSMinProtoVersion OBJECT-TYPE
   SYNTAX      INTEGER { SSLv3(0), TLSv1(1), TLSv11(2), TLSv12(3)}
   MAX-ACCESS  read-write
   STATUS      current
   DESCRIPTION
       "default: 1
        0: SSLv3
        1: TLSv1
        2: TLSv1.1
        3: TLSv1.2"
   ::= { gs2310HTTPS 4 }

gs2310HTTPMode OBJECT-TYPE
   SYNTAX      INTEGER { disable(0), enable(1) }
   MAX-ACCESS  read-write
   STATUS      current
   DESCRIPTION
       "default: 1
        0: disable
        1: enable"
   ::= { gs2310HTTPS 5 }

gs2310AuthMethod                                            OBJECT IDENTIFIER ::= { gs2310Security 9 }

gs2310ConsoleAuthMethod OBJECT-TYPE
   SYNTAX      INTEGER { none(0), local(1), radius(2), tacacsplus(3) }
   MAX-ACCESS  read-write
   STATUS      current
   DESCRIPTION
       "default: 1
        0: none
        1: local
        2: RADIUS
        3: TACACS+"
   ::= { gs2310AuthMethod 1 }

gs2310ConsoleFallback OBJECT-TYPE
   SYNTAX      INTEGER { disable(0), enable(1) }
   MAX-ACCESS  read-write
   STATUS      current
   DESCRIPTION
       "default: 0
        0:disable
        1:enable"
   ::= { gs2310AuthMethod 2 }

gs2310TelnetAuthMethod OBJECT-TYPE
   SYNTAX      INTEGER { none(0), local(1), radius(2), tacacsplus(3) }
   MAX-ACCESS  read-write
   STATUS      current
   DESCRIPTION
       "default: 1
        0: none
        1: local
        2: RADIUS
        3: TACACS+"
   ::= { gs2310AuthMethod 3 }

gs2310TelnetFallback OBJECT-TYPE
   SYNTAX      INTEGER { disable(0), enable(1) }
   MAX-ACCESS  read-write
   STATUS      current
   DESCRIPTION
       "default: 0
        0:disable
        1:enable"
   ::= { gs2310AuthMethod 4 }

gs2310SshAuthMethod OBJECT-TYPE
   SYNTAX      INTEGER { none(0), local(1), radius(2), tacacsplus(3) }
   MAX-ACCESS  read-write
   STATUS      current
   DESCRIPTION
       "default: 1
        0: none
        1: local
        2: RADIUS
        3: TACACS+"
   ::= { gs2310AuthMethod 5 }

gs2310SshFallback OBJECT-TYPE
   SYNTAX      INTEGER { disable(0), enable(1) }
   MAX-ACCESS  read-write
   STATUS      current
   DESCRIPTION
       "default: 0
        0:disable
        1:enable"
   ::= { gs2310AuthMethod 6 }

gs2310TftpAuthMethod OBJECT-TYPE
   SYNTAX      INTEGER { none(0), local(1), radius(2), tacacsplus(3) }
   MAX-ACCESS  read-write
   STATUS      current
   DESCRIPTION
       "default: 1
        0: none
        1: local
        2: RADIUS
        3: TACACS+"
   ::= { gs2310AuthMethod 9 }

gs2310TftpFallback OBJECT-TYPE
   SYNTAX      INTEGER { disable(0), enable(1) }
   MAX-ACCESS  read-write
   STATUS      current
   DESCRIPTION
       "default: 0
        0:disable
        1:enable"
   ::= { gs2310AuthMethod 10 }

gs2310LoginFailures OBJECT-TYPE
   SYNTAX      Integer32(0..99)
   MAX-ACCESS  read-write
   STATUS      current
   DESCRIPTION
       "When login failures mechanism is triggered,the lock minutes will prevent to login in this periods.
        The value '0' should deactivate this feature.
        range: 0-99.
        default: 5."
   ::= { gs2310AuthMethod 11 }

gs2310LockMinutes OBJECT-TYPE
   SYNTAX      Integer32(1..99)
   MAX-ACCESS  read-write
   STATUS      current
   DESCRIPTION
       "Lock time to login failures trigger.
        range: 1-99.
        default: 5."
   ::= { gs2310AuthMethod 12 }

gs2310HttpAuthMethod OBJECT-TYPE
   SYNTAX      INTEGER { none(0), local(1), radius(2), tacacsplus(3) }
   MAX-ACCESS  read-write
   STATUS      current
   DESCRIPTION
       "default: 1
        0: none
        1: local
        2: RADIUS
        3: TACACS+"
   ::= { gs2310AuthMethod 13 }

gs2310HttpFallback OBJECT-TYPE
   SYNTAX      INTEGER { disable(0), enable(1) }
   MAX-ACCESS  read-write
   STATUS      current
   DESCRIPTION
       "default: 0
        0:disable
        1:enable"
   ::= { gs2310AuthMethod 14 }

gs2310HttpsAuthMethod OBJECT-TYPE
   SYNTAX      INTEGER { none(0), local(1), radius(2), tacacsplus(3) }
   MAX-ACCESS  read-write
   STATUS      current
   DESCRIPTION
       "default: 1
        0: none
        1: local
        2: RADIUS
        3: TACACS+"
   ::= { gs2310AuthMethod 15 }

gs2310HttpsFallback OBJECT-TYPE
   SYNTAX      INTEGER { disable(0), enable(1) }
   MAX-ACCESS  read-write
   STATUS      current
   DESCRIPTION
       "default: 0
        0:disable
        1:enable"
   ::= { gs2310AuthMethod 16 }


gs2310AAA                                              OBJECT IDENTIFIER ::= { gs2310Security 10 }

gs2310AAACommonServer                                  OBJECT IDENTIFIER ::= { gs2310AAA 1 }

gs2310AAACommonServerTimeout OBJECT-TYPE
   SYNTAX      Integer32(3..3600)
   MAX-ACCESS  read-write
   STATUS      current
   DESCRIPTION
       "The Timeout, which can be set to a number between 3 and 3600 seconds, is
       the maximum time to wait for a reply from a server. If the server does not
       reply within this timeframe, we will consider it to be dead and continue
       with the next enabled server (if any). RADIUS servers are using the UDP
       protocol, which is unreliable by design. In order to cope with lost frames,
       the timeout interval is divided into 3 subintervals of equal length. If a
       reply is not received within the subinterval, the request is transmitted
       again. This algorithm causes the RADIUS server to be queried up to 3 times
       before it is considered to be dead.
        default: 15."
   ::= { gs2310AAACommonServer 1 }

gs2310AAACommonServerDeadTime OBJECT-TYPE
   SYNTAX      Integer32(0..3600)
   MAX-ACCESS  read-write
   STATUS      current
   DESCRIPTION
       "The Dead Time, which can be set to a number between 0 and 3600 seconds,
       is the period during which the switch will not send new requests to a
       server that has failed to respond to a previous request. This will stop
       the switch from continually trying to contact a server that it has already
       determined as dead.
       Setting the Dead Time to a value greater than 0 (zero) will enable this feature,
       but only if more than one server has been configured.
       default: 300."
   ::= { gs2310AAACommonServer 2 }

gs2310AAATACACSPlusAuthAndAccounting                  OBJECT IDENTIFIER ::= { gs2310AAA 2 }

gs2310AAAAuthorization OBJECT-TYPE
   SYNTAX      INTEGER { disable(0), enable(1) }
   MAX-ACCESS  read-write
   STATUS      current
   DESCRIPTION
       "Authorization is the action of determining what a user is allowed to do.
       An authorization request may indicate that the user is not authenticated.
       In this case it is up to the authorization agent to determine if an
       unauthenticated user is allowed the services in question. "
   ::= { gs2310AAATACACSPlusAuthAndAccounting 1 }

gs2310AAAFallbackToLocalAuthorization OBJECT-TYPE
   SYNTAX      INTEGER { disable(0), enable(1) }
   MAX-ACCESS  read-write
   STATUS      current
   DESCRIPTION
       "This function is an auxiliary function of Authorization. When the DUT
       cannot communicate with TACACS+ Server normally, it will check the right/
        permission level of the Local Account to execute the Authorization. "
   ::= { gs2310AAATACACSPlusAuthAndAccounting 2 }

gs2310AAAAccounting OBJECT-TYPE
   SYNTAX      INTEGER { disable(0), enable(1) }
   MAX-ACCESS  read-write
   STATUS      current
   DESCRIPTION
       "Accounting is typically the third action after authentication and
       authorization. Accounting is the action of recording what a user is doing,
       and/or has done. TACACS+ accounting records contain all the information
       used in the authorization records and resource usage information. "
   ::= { gs2310AAATACACSPlusAuthAndAccounting 3 }

gs2310RADIUSAuthenticationServerTable OBJECT-TYPE
   SYNTAX      SEQUENCE OF GS2310RADIUSAuthenticationServerEntry
   MAX-ACCESS  not-accessible
   STATUS      current
   DESCRIPTION
       " "
   ::= { gs2310AAA 3 }

gs2310RADIUSAuthenticationServerEntry OBJECT-TYPE
   SYNTAX      GS2310RADIUSAuthenticationServerEntry
   MAX-ACCESS  not-accessible
   STATUS      current
   DESCRIPTION
       ""
   INDEX    { gs2310RADIUSAuthenticationServerIndex  }
   ::= { gs2310RADIUSAuthenticationServerTable 1 }

GS2310RADIUSAuthenticationServerEntry ::= SEQUENCE {
   gs2310RADIUSAuthenticationServerIndex     Integer32,
   gs2310RADIUSAuthenticationServerEnable    INTEGER,
   gs2310RADIUSAuthenticationServerIP        DisplayString,
   gs2310RADIUSAuthenticationServerPort      Integer32,
   gs2310RADIUSAuthenticationServerSecret    DisplayString
}

gs2310RADIUSAuthenticationServerIndex OBJECT-TYPE
   SYNTAX      Integer32(1..5)
   MAX-ACCESS  not-accessible
   STATUS      current
   DESCRIPTION
       "RADIUS Authentication Server index
        range : 1-5."
   ::= { gs2310RADIUSAuthenticationServerEntry 1 }

gs2310RADIUSAuthenticationServerEnable OBJECT-TYPE
   SYNTAX      INTEGER { disable(0), enable(1) }
   MAX-ACCESS  read-write
   STATUS      current
   DESCRIPTION
       "Enable/Disable the RADIUS Authentication Server. the RADIUSAuthenticationServerEnable
       can be set, when IP and Secret have value "
   ::= { gs2310RADIUSAuthenticationServerEntry 2 }

gs2310RADIUSAuthenticationServerIP OBJECT-TYPE
   SYNTAX      DisplayString
   MAX-ACCESS  read-write
   STATUS      current
   DESCRIPTION
       "The IP address or hostname of the RADIUS Authentication Server.
       IP address is expressed in  dotted decimal notation. "
   ::= { gs2310RADIUSAuthenticationServerEntry 3 }

gs2310RADIUSAuthenticationServerPort OBJECT-TYPE
   SYNTAX      Integer32(0..65535)
   MAX-ACCESS  read-write
   STATUS      current
   DESCRIPTION
       "The UDP port to use on the RADIUS Authentication Server. If the port is
       set to 0 (zero), the default port (1812) is used on the RADIUS Authentication Server. "
   ::= { gs2310RADIUSAuthenticationServerEntry 4 }

gs2310RADIUSAuthenticationServerSecret OBJECT-TYPE
   SYNTAX      DisplayString
   MAX-ACCESS  read-write
   STATUS      current
   DESCRIPTION
       "The secret - up to 64 characters long - shared between the RADIUS Authentication Server and the switch. "
   ::= { gs2310RADIUSAuthenticationServerEntry 5 }


gs2310RADIUSAccountingServerTable OBJECT-TYPE
   SYNTAX      SEQUENCE OF GS2310RADIUSAccountingServerEntry
   MAX-ACCESS  not-accessible
   STATUS      current
   DESCRIPTION
       " "
   ::= { gs2310AAA 4 }

gs2310RADIUSAccountingServerEntry OBJECT-TYPE
   SYNTAX      GS2310RADIUSAccountingServerEntry
   MAX-ACCESS  not-accessible
   STATUS      current
   DESCRIPTION
       ""
   INDEX    { gs2310RADIUSAccountingServerIndex  }
   ::= { gs2310RADIUSAccountingServerTable 1 }

GS2310RADIUSAccountingServerEntry ::= SEQUENCE {
   gs2310RADIUSAccountingServerIndex     Integer32,
   gs2310RADIUSAccountingServerEnable    INTEGER,
   gs2310RADIUSAccountingServerIP        DisplayString,
   gs2310RADIUSAccountingServerPort      Integer32,
   gs2310RADIUSAccountingServerSecret    DisplayString
}

gs2310RADIUSAccountingServerIndex OBJECT-TYPE
   SYNTAX      Integer32(1..5)
   MAX-ACCESS  not-accessible
   STATUS      current
   DESCRIPTION
       "RADIUS Accounting Server index
        range : 1-5."
   ::= { gs2310RADIUSAccountingServerEntry 1 }

gs2310RADIUSAccountingServerEnable OBJECT-TYPE
   SYNTAX      INTEGER { disable(0), enable(1) }
   MAX-ACCESS  read-write
   STATUS      current
   DESCRIPTION
       "Enable/Disable the RADIUS Accounting Server. The RADIUSAccountingServerEnable
       can be set, when IP and Secret have value. "
   ::= { gs2310RADIUSAccountingServerEntry 2 }

gs2310RADIUSAccountingServerIP OBJECT-TYPE
   SYNTAX      DisplayString
   MAX-ACCESS  read-write
   STATUS      current
   DESCRIPTION
       "The IP address or hostname of the RADIUS Accounting Server.
       IP address is expressed in  dotted decimal notation. "
   ::= { gs2310RADIUSAccountingServerEntry 3 }

gs2310RADIUSAccountingServerPort OBJECT-TYPE
   SYNTAX      Integer32(0..65535)
   MAX-ACCESS  read-write
   STATUS      current
   DESCRIPTION
       "The UDP port to use on the RADIUS Accounting Server. If the port is
       set to 0 (zero), the default port (1812) is used on the RADIUS Accounting Server. "
   ::= { gs2310RADIUSAccountingServerEntry 4 }

gs2310RADIUSAccountingServerSecret OBJECT-TYPE
   SYNTAX      DisplayString
   MAX-ACCESS  read-write
   STATUS      current
   DESCRIPTION
       "The secret - up to 64 characters long - shared between the RADIUS Accounting Server and the switch. "
   ::= { gs2310RADIUSAccountingServerEntry 5 }

gs2310TACACSPlusAuthenticationServerTable OBJECT-TYPE
   SYNTAX      SEQUENCE OF GS2310TACACSPlusAuthenticationServerEntry
   MAX-ACCESS  not-accessible
   STATUS      current
   DESCRIPTION
       " "
   ::= { gs2310AAA 5 }

gs2310TACACSPlusAuthenticationServerEntry OBJECT-TYPE
   SYNTAX      GS2310TACACSPlusAuthenticationServerEntry
   MAX-ACCESS  not-accessible
   STATUS      current
   DESCRIPTION
       ""
   INDEX    { gs2310TACACSPlusAuthenticationServerIndex  }
   ::= { gs2310TACACSPlusAuthenticationServerTable 1 }

GS2310TACACSPlusAuthenticationServerEntry ::= SEQUENCE {
   gs2310TACACSPlusAuthenticationServerIndex     Integer32,
   gs2310TACACSPlusAuthenticationServerEnable    INTEGER,
   gs2310TACACSPlusAuthenticationServerIP        DisplayString,
   gs2310TACACSPlusAuthenticationServerPort      Integer32,
   gs2310TACACSPlusAuthenticationServerSecret    DisplayString
}

gs2310TACACSPlusAuthenticationServerIndex OBJECT-TYPE
   SYNTAX      Integer32(1..5)
   MAX-ACCESS  not-accessible
   STATUS      current
   DESCRIPTION
       "TACACSPlus Authentication Server index
        range : 1-5."
   ::= { gs2310TACACSPlusAuthenticationServerEntry 1 }

gs2310TACACSPlusAuthenticationServerEnable OBJECT-TYPE
   SYNTAX      INTEGER { disable(0), enable(1) }
   MAX-ACCESS  read-write
   STATUS      current
   DESCRIPTION
       "Enable/Disable the TACACSPlus Authentication Server. The
       TACACSPlusAuthenticationServerEnable can be set, when IP and Secret have
       value."
   ::= { gs2310TACACSPlusAuthenticationServerEntry 2 }

gs2310TACACSPlusAuthenticationServerIP OBJECT-TYPE
   SYNTAX      DisplayString
   MAX-ACCESS  read-write
   STATUS      current
   DESCRIPTION
       "The IP address or hostname of the TACACSPlus Authentication Server.
       IP address is expressed in  dotted decimal notation. "
   ::= { gs2310TACACSPlusAuthenticationServerEntry 3 }

gs2310TACACSPlusAuthenticationServerPort OBJECT-TYPE
   SYNTAX      Integer32(0..65535)
   MAX-ACCESS  read-write
   STATUS      current
   DESCRIPTION
       "The UDP port to use on the TACACSPlus Authentication Server. If the
       port is set to 0 (zero), the default port (1812) is used on the
       TACACSPlus Authentication Server. "
   ::= { gs2310TACACSPlusAuthenticationServerEntry 4 }

gs2310TACACSPlusAuthenticationServerSecret OBJECT-TYPE
   SYNTAX      DisplayString
   MAX-ACCESS  read-write
   STATUS      current
   DESCRIPTION
       "The secret - up to 64 characters long - shared between the TACACSPlus Authentication Server and the switch. "
   ::= { gs2310TACACSPlusAuthenticationServerEntry 5 }


gs2310RADIUSStatisticsTable OBJECT-TYPE
   SYNTAX      SEQUENCE OF GS2310RADIUSStatisticsEntry
   MAX-ACCESS  not-accessible
   STATUS      current
   DESCRIPTION
       " "
   ::= { gs2310AAA 6 }

gs2310RADIUSStatisticsEntry OBJECT-TYPE
   SYNTAX      GS2310RADIUSStatisticsEntry
   MAX-ACCESS  not-accessible
   STATUS      current
   DESCRIPTION
       ""
   INDEX    { gs2310RADIUSAuthStatisticsServerIndex  }
   ::= { gs2310RADIUSStatisticsTable 1 }

GS2310RADIUSStatisticsEntry ::= SEQUENCE {
   gs2310RADIUSAuthStatisticsServerIndex                           Integer32,
   gs2310RADIUSAuthStatisticsRecPktAccessAccepts                   Counter32,
   gs2310RADIUSAuthStatisticsRecPktAccessRejects                   Counter32,
   gs2310RADIUSAuthStatisticsRecPktAccessChallenges                Counter32,
   gs2310RADIUSAuthStatisticsRecPktMalformedAccResponses           Counter32,
   gs2310RADIUSAuthStatisticsRecPktBadAuthenticators               Counter32,
   gs2310RADIUSAuthStatisticsRecPktUnknownTypes                    Counter32,
   gs2310RADIUSAuthStatisticsRecPktDropped                         Counter32,
   gs2310RADIUSAuthStatisticsTransmitPktAccessRequests             Counter32,
   gs2310RADIUSAuthStatisticsTransmitPktAccessRetransmissions      Counter32,
   gs2310RADIUSAuthStatisticsTransmitPktPendingRequests            Counter32,
   gs2310RADIUSAuthStatisticsTransmitPktTimeouts                   Counter32,
   gs2310RADIUSAuthIP                                              DisplayString,
   gs2310RADIUSAuthState                                           DisplayString,
   gs2310RADIUSAuthRoundTripTime                                   DisplayString,

   gs2310RADIUSAccountingStatisticsRecPktResponses                 Counter32,
   gs2310RADIUSAccountingStatisticsRecPktMalformedResponses        Counter32,
   gs2310RADIUSAccountingStatisticsRecPktBadAuthenticators         Counter32,
   gs2310RADIUSAccountingStatisticsRecPktUnknownTypes              Counter32,
   gs2310RADIUSAccountingStatisticsRecPktDropped                   Counter32,
   gs2310RADIUSAccountingStatisticsTransmitPktRequests             Counter32,
   gs2310RADIUSAccountingStatisticsTransmitPktRetransmissions      Counter32,
   gs2310RADIUSAccountingStatisticsTransmitPktPendingRequests      Counter32,
   gs2310RADIUSAccountingStatisticsTransmitPktTimeouts             Counter32,
   gs2310RADIUSAccountingIP                                        DisplayString,
   gs2310RADIUSAccountingState                                     DisplayString,
   gs2310RADIUSAccountingRoundTripTime                             DisplayString,
   gs2310RADIUSStatisticsClear                                     INTEGER
}

gs2310RADIUSAuthStatisticsServerIndex OBJECT-TYPE
   SYNTAX      Integer32(1..5)
   MAX-ACCESS  not-accessible
   STATUS      current
   DESCRIPTION
       "RADIUS Authentication Server index
        range : 1-5."
   ::= { gs2310RADIUSStatisticsEntry 1 }

gs2310RADIUSAuthStatisticsRecPktAccessAccepts OBJECT-TYPE
   SYNTAX      Counter32
   MAX-ACCESS  read-only
   STATUS      current
   DESCRIPTION
       "The number of RADIUS Access-Accept packets (valid or invalid) received from the server."
   ::= { gs2310RADIUSStatisticsEntry 2 }

gs2310RADIUSAuthStatisticsRecPktAccessRejects OBJECT-TYPE
   SYNTAX      Counter32
   MAX-ACCESS  read-only
   STATUS      current
   DESCRIPTION
       "The number of RADIUS Access-Reject packets (valid or invalid) received from the server."
   ::= { gs2310RADIUSStatisticsEntry 3 }

gs2310RADIUSAuthStatisticsRecPktAccessChallenges OBJECT-TYPE
   SYNTAX      Counter32
   MAX-ACCESS  read-only
   STATUS      current
   DESCRIPTION
       "The number of RADIUS Access-Challenge packets (valid or invalid) received from the server. "
   ::= { gs2310RADIUSStatisticsEntry 4 }

gs2310RADIUSAuthStatisticsRecPktMalformedAccResponses OBJECT-TYPE
   SYNTAX      Counter32
   MAX-ACCESS  read-only
   STATUS      current
   DESCRIPTION
       "The number of malformed RADIUS Access-Response packets received from the
        server. Malformed packets include packets with an invalid length. Bad
        authenticators or Message Authenticator attributes or unknown types are
        not included as malformed access responses. "
   ::= { gs2310RADIUSStatisticsEntry 5 }

gs2310RADIUSAuthStatisticsRecPktBadAuthenticators OBJECT-TYPE
   SYNTAX      Counter32
   MAX-ACCESS  read-only
   STATUS      current
   DESCRIPTION
       "The number of RADIUS Access-Response packets containing invalid
       authenticators or Message Authenticator attributes received from the server."
   ::= { gs2310RADIUSStatisticsEntry 6 }

gs2310RADIUSAuthStatisticsRecPktUnknownTypes OBJECT-TYPE
   SYNTAX      Counter32
   MAX-ACCESS  read-only
   STATUS      current
   DESCRIPTION
       "The number of RADIUS packets that were received with unknown types from
       the server on the authentication port and dropped."
   ::= { gs2310RADIUSStatisticsEntry 7 }

gs2310RADIUSAuthStatisticsRecPktDropped OBJECT-TYPE
   SYNTAX      Counter32
   MAX-ACCESS  read-only
   STATUS      current
   DESCRIPTION
       "The number of RADIUS packets that were received from the server on the
       authentication port and dropped for some other reason."
   ::= { gs2310RADIUSStatisticsEntry 8 }

gs2310RADIUSAuthStatisticsTransmitPktAccessRequests OBJECT-TYPE
   SYNTAX      Counter32
   MAX-ACCESS  read-only
   STATUS      current
   DESCRIPTION
       "The number of RADIUS Access-Request packets sent to the server. This
       does not include retransmissions."
   ::= { gs2310RADIUSStatisticsEntry 9 }

gs2310RADIUSAuthStatisticsTransmitPktAccessRetransmissions OBJECT-TYPE
   SYNTAX      Counter32
   MAX-ACCESS  read-only
   STATUS      current
   DESCRIPTION
       "The number of RADIUS Access-Request packets retransmitted to the RADIUS
       authentication server."
   ::= { gs2310RADIUSStatisticsEntry 10 }

gs2310RADIUSAuthStatisticsTransmitPktPendingRequests OBJECT-TYPE
   SYNTAX      Counter32
   MAX-ACCESS  read-only
   STATUS      current
   DESCRIPTION
       "The number of RADIUS Access-Request packets destined for the server that
        have not yet timed out or received a response. This variable is
        incremented when an Access-Request is sent and decremented due to
        receipt of an Access-Accept, Access-Reject, Access-Challenge, timeout,
        or retransmission. "
   ::= { gs2310RADIUSStatisticsEntry 11 }

gs2310RADIUSAuthStatisticsTransmitPktTimeouts OBJECT-TYPE
   SYNTAX      Counter32
   MAX-ACCESS  read-only
   STATUS      current
   DESCRIPTION
       "The number of authentication timeouts to the server. After a timeout,
       the client may retry to the same server, send to a different server, or
       give up. A retry to the same server is counted as a retransmit as well as
        a timeout. A send to a different server is counted as a Request as well
        as a timeout. "
   ::= { gs2310RADIUSStatisticsEntry 12 }

gs2310RADIUSAuthIP OBJECT-TYPE
   SYNTAX      DisplayString
   MAX-ACCESS  read-only
   STATUS      current
   DESCRIPTION
       "IP address and UDP port for the authentication server in question."
   ::= { gs2310RADIUSStatisticsEntry 13 }

gs2310RADIUSAuthState OBJECT-TYPE
   SYNTAX      DisplayString
   MAX-ACCESS  read-only
   STATUS      current
   DESCRIPTION
       "Shows the state of the server. It takes one of the following values:
        Disabled: The selected server is disabled.
        Not Ready: The server is enabled, but IP communication is not yet up and running.
        Ready: The server is enabled, IP communication is up and running, and the RADIUS
         module is ready to accept access attempts.
        Dead (X seconds left): Access attempts were made to this server, but it did not
        reply within the configured timeout. The server has temporarily been disabled,
        but will get re-enabled when the dead-time expires. The number of seconds left
        before this occurs is displayed in parentheses. This state is only reachable
        when more than one server is enabled. "
   ::= { gs2310RADIUSStatisticsEntry 14 }

gs2310RADIUSAuthRoundTripTime OBJECT-TYPE
   SYNTAX      DisplayString
   MAX-ACCESS  read-only
   STATUS      current
   DESCRIPTION
       "The time interval (measured in milliseconds) between the most recent
       Access-Reply/Access-Challenge and the Access-Request that matched it from
        the RADIUS authentication server. The granularity of this measurement is
         100 ms. A value of 0 ms indicates that there hasn't been round-trip
         communication with the server yet. "
   ::= { gs2310RADIUSStatisticsEntry 15 }

gs2310RADIUSAccountingStatisticsRecPktResponses OBJECT-TYPE
   SYNTAX      Counter32
   MAX-ACCESS  read-only
   STATUS      current
   DESCRIPTION
       "The number of RADIUS packets (valid or invalid) received from the server."
   ::= { gs2310RADIUSStatisticsEntry 16 }

gs2310RADIUSAccountingStatisticsRecPktMalformedResponses OBJECT-TYPE
   SYNTAX      Counter32
   MAX-ACCESS  read-only
   STATUS      current
   DESCRIPTION
       "The number of malformed RADIUS packets received from the server.
       Malformed packets include packets with an invalid length. Bad
       authenticators or unknown types are not included as malformed access
       responses. "
   ::= { gs2310RADIUSStatisticsEntry 17 }

gs2310RADIUSAccountingStatisticsRecPktBadAuthenticators OBJECT-TYPE
   SYNTAX      Counter32
   MAX-ACCESS  read-only
   STATUS      current
   DESCRIPTION
       "The number of RADIUS packets containing invalid authenticators received
       from the server."
   ::= { gs2310RADIUSStatisticsEntry 18 }

gs2310RADIUSAccountingStatisticsRecPktUnknownTypes OBJECT-TYPE
   SYNTAX      Counter32
   MAX-ACCESS  read-only
   STATUS      current
   DESCRIPTION
       "The number of RADIUS packets of unknown types that were received from
       the server on the accounting port."
   ::= { gs2310RADIUSStatisticsEntry 19 }

gs2310RADIUSAccountingStatisticsRecPktDropped OBJECT-TYPE
   SYNTAX      Counter32
   MAX-ACCESS  read-only
   STATUS      current
   DESCRIPTION
       "The number of RADIUS packets that were received from the server on the
       accounting port and dropped for some other reason."
   ::= { gs2310RADIUSStatisticsEntry 20 }

gs2310RADIUSAccountingStatisticsTransmitPktRequests OBJECT-TYPE
   SYNTAX      Counter32
   MAX-ACCESS  read-only
   STATUS      current
   DESCRIPTION
       "The number of RADIUS packets sent to the server. This does not include
       retransmissions."
   ::= { gs2310RADIUSStatisticsEntry 21 }

gs2310RADIUSAccountingStatisticsTransmitPktRetransmissions OBJECT-TYPE
   SYNTAX      Counter32
   MAX-ACCESS  read-only
   STATUS      current
   DESCRIPTION
       "The number of RADIUS packets retransmitted to the RADIUS accounting server."
   ::= { gs2310RADIUSStatisticsEntry 22 }

gs2310RADIUSAccountingStatisticsTransmitPktPendingRequests OBJECT-TYPE
   SYNTAX      Counter32
   MAX-ACCESS  read-only
   STATUS      current
   DESCRIPTION
       "The number of RADIUS packets destined for the server that have not yet
       timed out or received a response. This variable is incremented when a
       Request is sent and decremented due to receipt of a Response, timeout,
       or retransmission. "
   ::= { gs2310RADIUSStatisticsEntry 23 }

gs2310RADIUSAccountingStatisticsTransmitPktTimeouts OBJECT-TYPE
   SYNTAX      Counter32
   MAX-ACCESS  read-only
   STATUS      current
   DESCRIPTION
       "The number of accounting timeouts to the server. After a timeout, the
       client may retry to the same server, send to a different server, or give
       up. A retry to the same server is counted as a retransmit as well as a
       timeout. A send to a different server is counted as a Request as well as
       a timeout. "
   ::= { gs2310RADIUSStatisticsEntry 24 }

gs2310RADIUSAccountingIP OBJECT-TYPE
   SYNTAX      DisplayString
   MAX-ACCESS  read-only
   STATUS      current
   DESCRIPTION
       "IP address and UDP port for the accounting server in question."
   ::= { gs2310RADIUSStatisticsEntry 25 }

gs2310RADIUSAccountingState OBJECT-TYPE
   SYNTAX      DisplayString
   MAX-ACCESS  read-only
   STATUS      current
   DESCRIPTION
       " Shows the state of the server. It takes one of the following values:
        Disabled: The selected server is disabled.
        Not Ready: The server is enabled, but IP communication is not yet up and running.
        Ready: The server is enabled, IP communication is up and running, and the RADIUS
        module is ready to accept accounting attempts.
        Dead (X seconds left): Accounting attempts were made to this server, but it did
        not reply within the configured timeout. The server has temporarily been
        disabled, but will get re-enabled when the dead-time expires. The number of
        seconds left before this occurs is displayed in parentheses. This state is only
        reachable when more than one server is enabled.  "
   ::= { gs2310RADIUSStatisticsEntry 26 }

gs2310RADIUSAccountingRoundTripTime OBJECT-TYPE
   SYNTAX      DisplayString
   MAX-ACCESS  read-only
   STATUS      current
   DESCRIPTION
       "The time interval (measured in milliseconds) between the most recent
       Response and the Request that matched it from the RADIUS accounting
       server. The granularity of this measurement is 100 ms. A value of 0 ms
       indicates that there hasn't been round-trip communication with the server
       yet. "
   ::= { gs2310RADIUSStatisticsEntry 27 }

gs2310RADIUSStatisticsClear OBJECT-TYPE
   SYNTAX      INTEGER(0|1)
   MAX-ACCESS  read-write
   STATUS      current
   DESCRIPTION
       "Clears the counters for the server.
       read: always 0
       clear: set 1"
   ::= { gs2310RADIUSStatisticsEntry 28 }


gs2310NAS                                              OBJECT IDENTIFIER ::= { gs2310Security 11 }

gs2310NASConfiguration                                 OBJECT IDENTIFIER ::= { gs2310NAS 1 }

gs2310NASConfigMode OBJECT-TYPE
   SYNTAX      INTEGER { disable(0), enable(1) }
   MAX-ACCESS  read-write
   STATUS      current
   DESCRIPTION
       "Indicates if NAS is globally enabled or disabled on the switch.
	    If globally disabled, all ports are allowed forwarding of frames."
   ::= { gs2310NASConfiguration 1 }

gs2310NASConfigReauthEnabled OBJECT-TYPE
   SYNTAX      INTEGER { disable(0), enable(1) }
   MAX-ACCESS  read-write
   STATUS      current
   DESCRIPTION
       "If checked, successfully authenticated supplicants/clients are
	    reauthenticated after the interval specified by the Reauthentication
		Period. Reauthentication for 802.1X-enabled ports can be used to
		detect if a new device is plugged into a switch port or if a
		supplicant is no longer attached.
		For MAC-based ports, reauthentication is only useful if the RADIUS
		server configuration has changed. It does not involve communication
		between the switch and the client, and therefore doesn't imply that
		a client is still present on a port."
   ::= { gs2310NASConfiguration 2 }

gs2310NASConfigReauthPeriod OBJECT-TYPE
   SYNTAX      Integer32(1..3600)
   MAX-ACCESS  read-write
   STATUS      current
   DESCRIPTION
       "Determines the period, in seconds, after which a connected client must
	    be reauthenticated. This is only active if the Reauthentication Enabled
		checkbox is checked.
		range: 1 - 3600 seconds."
   ::= { gs2310NASConfiguration 3 }

gs2310NASConfigEAPOLTimeout OBJECT-TYPE
   SYNTAX      Integer32(1..65535)
   MAX-ACCESS  read-write
   STATUS      current
   DESCRIPTION
       "Determines the time for retransmission of Request Identity EAPOL frames.
	    This has no effect for MAC-based ports.
		range: 1 - 65535 seconds."
   ::= { gs2310NASConfiguration 4 }

gs2310NASConfigAgingPeriod OBJECT-TYPE
   SYNTAX      Integer32(10..1000000)
   MAX-ACCESS  read-write
   STATUS      current
   DESCRIPTION
       "When the NAS module uses the Port Security module to secure MAC addresses,
	    the Port Security module needs to check for activity on the MAC address
		in question at regular intervals and free resources if no activity
		is seen within a given period of time.
		Admin State supported : Single, Multi and MAC-Based Auth. 802.1X.
		range: 10 - 1000000 seconds."
   ::= { gs2310NASConfiguration 5 }

gs2310NASConfigHoldTime OBJECT-TYPE
   SYNTAX      Integer32(10..1000000)
   MAX-ACCESS  read-write
   STATUS      current
   DESCRIPTION
       "If a client is denied access - either because the RADIUS server denies
	    the client access or because the RADIUS server request times out
		- the client is put on hold in the Unauthorized state. The hold timer
		does not count during an on-going authentication. In MAC-based Auth.
		mode, the switch will ignore new frames coming from the client during
		the hold time.
		Admin State supported : Single, Multi and MAC-Based Auth. 802.1X.
		range: 10 - 1000000 seconds."
   ::= { gs2310NASConfiguration 6 }

gs2310NASConfigRADIUSAssignedQoSEnabled OBJECT-TYPE
   SYNTAX      INTEGER { disable(0), enable(1) }
   MAX-ACCESS  read-write
   STATUS      current
   DESCRIPTION
       "RADIUS-assigned QoS provides a means to centrally control the
	    traffic class to which traffic coming from a successfully authenticated
		supplicant is assigned on the switch. The RADIUS server must be configured
		to transmit special RADIUS attributes to take advantage of this feature."
   ::= { gs2310NASConfiguration 7 }

gs2310NASConfigRADIUSAssignedVLANEnabled OBJECT-TYPE
   SYNTAX      INTEGER { disable(0), enable(1) }
   MAX-ACCESS  read-write
   STATUS      current
   DESCRIPTION
       "RADIUS-assigned VLAN provides a means to centrally control the VLAN on
	    which a successfully authenticated supplicant is placed on the switch.
	    Incoming traffic will be classified to and switched on the RADIUS-assigned
		VLAN. The RADIUS server must be configured to transmit special RADIUS
		attributes to take advantage of this feature.When enable, the individual
		ports' ditto setting determine whether RADIUS-assigned VLAN is enabled
		on that port. When disable, RADIUS-server assigned VLAN is disabled on
		all ports. "
   ::= { gs2310NASConfiguration 8 }

gs2310NASConfigGuestVLANEnabled OBJECT-TYPE
   SYNTAX      INTEGER { disable(0), enable(1) }
   MAX-ACCESS  read-write
   STATUS      current
   DESCRIPTION
       "A Guest VLAN is a special VLAN - typically with limited network access -
	   on which 802.1X-unaware clients are placed after a network administrator-defined
	   timeout. The switch follows a set of rules for entering and leaving the Guest
	   VLAN as listed below.When enable, the individual ports' ditto setting determines
	   whether the port can be moved into Guest VLAN. When disable, the ability to
	   move to the Guest VLAN is disabled on all ports. "
   ::= { gs2310NASConfiguration 9 }

gs2310NASConfigGuestVLANID OBJECT-TYPE
   SYNTAX      Integer32(1..4094)
   MAX-ACCESS  read-write
   STATUS      current
   DESCRIPTION
       "This is the value that a port's Port VLAN ID is set to if a port is moved into
	   the Guest VLAN. It is only changeable if the Guest VLAN option is globally enabled.
	   range: 1 - 4094."
   ::= { gs2310NASConfiguration 10 }

gs2310NASConfigMaxReauthCount OBJECT-TYPE
   SYNTAX      Integer32(1..255)
   MAX-ACCESS  read-write
   STATUS      current
   DESCRIPTION
       "The number of times the switch transmits an EAPOL Request Identity frame without
	   response before considering entering the Guest VLAN is adjusted with this setting.
	   The value can only be changed if the Guest VLAN option is globally enabled.
	   range: 1 - 255."
   ::= { gs2310NASConfiguration 11 }

gs2310NASConfigAllowGuestVLANEAPOLSeen OBJECT-TYPE
   SYNTAX      INTEGER { disable(0), enable(1) }
   MAX-ACCESS  read-write
   STATUS      current
   DESCRIPTION
       "The switch remembers if an EAPOL frame has been received on the port for the
	   life-time of the port. Once the switch considers whether to enter the Guest VLAN,
	   it will first check if this option is enabled or disabled. If disabled, the switch
	   will only enter the Guest VLAN if an EAPOL frame has not been received on the port
	   for the life-time of the port. If enabled (checked), the switch will consider
	   entering the Guest VLAN even if an EAPOL frame has been received on the port for
	   the life-time of the port.The value can only be changed if the Guest VLAN option
	   is globally enabled."
   ::= { gs2310NASConfiguration 12 }

gs2310NASConfigMacBasedUseEAP OBJECT-TYPE
   SYNTAX      INTEGER { disable(0), enable(1) }
   MAX-ACCESS  read-write
   STATUS      current
   DESCRIPTION
       "The switch can do the RADIUS authentication on behalf of the client in the
       MAC-based Auth. port authentication mode. It can either present itself as a
       normal 802.1X client to the RADIUS Server and use EAP, supporting only the
       MD5-Challenge, or alternativly can use plain RADIUS with username / passwort
       authentification without EAP if this setting is disabled."
   ::= { gs2310NASConfiguration 101 }

gs2310NASPortConfigTable OBJECT-TYPE
   SYNTAX      SEQUENCE OF GS2310NASPortConfigEntry
   MAX-ACCESS  not-accessible
   STATUS      current
   DESCRIPTION
       ""
   ::= { gs2310NASConfiguration 13 }

gs2310NASPortConfigEntry OBJECT-TYPE
   SYNTAX      GS2310NASPortConfigEntry
   MAX-ACCESS  not-accessible
   STATUS      current
   DESCRIPTION
       ""
   INDEX    { gs2310NASPortConfigPort }
   ::= { gs2310NASPortConfigTable 1 }

GS2310NASPortConfigEntry ::= SEQUENCE {
   gs2310NASPortConfigPort                       Integer32,
   gs2310NASPortConfigAdminState                 INTEGER,
   gs2310NASPortConfigRADIUSAssignedQoSEnabled	  INTEGER,
   gs2310NASPortConfigRADIUSAssignedVLANEnabled  INTEGER,
   gs2310NASPortConfigGuestVLANEnabled           INTEGER,
   gs2310NASPortConfigFallbackEnabled            INTEGER,
   gs2310NASPortConfigPortState                  DisplayString,
   gs2310NASPortConfigReauthenticate             INTEGER,
   gs2310NASPortConfigReinitialize               INTEGER
}

gs2310NASPortConfigPort OBJECT-TYPE
   SYNTAX      Integer32(1..255)
   MAX-ACCESS  not-accessible
   STATUS      current
   DESCRIPTION
       " port, range : 1 - port number. "
   ::= { gs2310NASPortConfigEntry 1 }

gs2310NASPortConfigAdminState OBJECT-TYPE
   SYNTAX      INTEGER{ forceAuthorized(1),
						forceUnauthorized(2),
						portBased(3),
						single(4),
						multi(5),
						macBased(6),
						macBasedSingle(7)
					  }
   MAX-ACCESS  read-write
   STATUS      current
   DESCRIPTION
       "This selection controls the port's authentication mode.
		1: Force Authorized,
		2: Force Unauthorized,
		3: Port-based 802.1X,
		4: Single 802.1X,
		5: Multi 802.1X,
		6: MAC-based Auth,
		7: MAC-based Single Auth."
   ::= { gs2310NASPortConfigEntry 2 }

gs2310NASPortConfigRADIUSAssignedQoSEnabled OBJECT-TYPE
   SYNTAX      INTEGER { disable(0), enable(1) }
   MAX-ACCESS  read-write
   STATUS      current
   DESCRIPTION
       "When RADIUS-Assigned QoS is both globally enabled and enabled (checked)
	    on a given port, the switch reacts to QoS Class information carried in
		the RADIUS Access-Accept packet transmitted by the RADIUS server when a
		supplicant is successfully authenticated. If present and valid, traffic
		received on the supplicant's port will be classified to the given QoS Class.
		Admin State supported : Port-based and Single 802.1X and MAC-based Single Auth."
   ::= { gs2310NASPortConfigEntry 3 }

gs2310NASPortConfigRADIUSAssignedVLANEnabled OBJECT-TYPE
   SYNTAX      INTEGER { disable(0), enable(1) }
   MAX-ACCESS  read-write
   STATUS      current
   DESCRIPTION
       "When RADIUS-Assigned VLAN is both globally enabled and enabled (checked)
	   for a given port, the switch reacts to VLAN ID information carried in the
	   RADIUS Access-Accept packet transmitted by the RADIUS server when a supplicant
	   is successfully authenticated. If present and valid, the port's Port VLAN ID
	   will be changed to this VLAN ID, the port will be set to be a member of that
	   VLAN ID, and the port will be forced into VLAN unaware mode. Once assigned,
	   all traffic arriving on the port will be classified and switched on the
	   RADIUS-assigned VLAN ID.
	   Admin State supported : Port-based and Single 802.1X and MAC-based Single Auth."
   ::= { gs2310NASPortConfigEntry 4 }

gs2310NASPortConfigGuestVLANEnabled OBJECT-TYPE
   SYNTAX      INTEGER { disable(0), enable(1) }
   MAX-ACCESS  read-write
   STATUS      current
   DESCRIPTION
       "When Guest VLAN is both globally enabled and enabled (checked) for a given port,
	   the switch considers moving the port into the Guest VLAN according to the rules
	   outlined below.
	   Admin State supported : Port-based , Single and Multi 802.1X."
   ::= { gs2310NASPortConfigEntry 5 }

gs2310NASPortConfigPortState OBJECT-TYPE
   SYNTAX      DisplayString
   MAX-ACCESS  read-only
   STATUS      current
   DESCRIPTION
       "Globally Disabled: NAS is globally disabled.
		Link Down: NAS is globally enabled, but there is no link on the port.
		Authorized: The port is in Force Authorized or a single-supplicant mode
		and the supplicant is authorized.
		Unauthorized: The port is in Force Unauthorized or a single-supplicant
		mode and the supplicant is not successfully authorized by the RADIUS server.
		X Auth/Y Unauth: The port is in a multi-supplicant mode. Currently X clients
		are authorized and Y are unauthorized."
   ::= { gs2310NASPortConfigEntry 6 }

gs2310NASPortConfigReauthenticate OBJECT-TYPE
   SYNTAX      INTEGER { doNothing(0), do(1) }
   MAX-ACCESS  read-write
   STATUS      current
   DESCRIPTION
       "Schedules a reauthentication whenever the quiet-period of the port runs out
	   (EAPOL-based authentication). For MAC-based authentication, reauthentication
	   will be attempted immediately.The button only has effect for successfully
	   authenticated clients on the port and will not cause the clients to get
	   temporarily unauthorized."
   ::= { gs2310NASPortConfigEntry 7 }

gs2310NASPortConfigReinitialize OBJECT-TYPE
   SYNTAX      INTEGER { doNothing(0), do(1) }
   MAX-ACCESS  read-write
   STATUS      current
   DESCRIPTION
       "Forces a reinitialization of the clients on the port and thereby a reauthentication
	   immediately. The clients will transfer to the unauthorized state while the
	   reauthentication is in progress."
   ::= { gs2310NASPortConfigEntry 8 }

gs2310NASPortConfigFallbackEnabled OBJECT-TYPE
   SYNTAX      INTEGER { disable(0), enable(1) }
   MAX-ACCESS  read-write
   STATUS      current
   DESCRIPTION
       "When Fallback is enabled, the switch will take over the supplicants role
       after max reauthentication count is reached and tries to authenticate the
       client on its behalf as described for MAC-based Auth.
       Admin State supported : Single and Multi 802.1X."
   ::= { gs2310NASPortConfigEntry 101 }

gs2310NASSwitchStatusTable OBJECT-TYPE
   SYNTAX      SEQUENCE OF GS2310NASSwitchStatusEntry
   MAX-ACCESS  not-accessible
   STATUS      current
   DESCRIPTION
       ""
   ::= { gs2310NAS 2 }

gs2310NASSwitchStatusEntry OBJECT-TYPE
   SYNTAX      GS2310NASSwitchStatusEntry
   MAX-ACCESS  not-accessible
   STATUS      current
   DESCRIPTION
       ""
   INDEX    { gs2310NASPortConfigPort }
   ::= { gs2310NASSwitchStatusTable 1 }

GS2310NASSwitchStatusEntry ::= SEQUENCE {
   gs2310NASSwitchStatusAdminState 	DisplayString,
   gs2310NASSwitchStatusPortState		DisplayString,
   gs2310NASSwitchStatusLastSource		DisplayString,
   gs2310NASSwitchStatusLastID			DisplayString,
   gs2310NASSwitchStatusQoSClass		DisplayString,
   gs2310NASSwitchStatusPortVlanID		DisplayString
}

gs2310NASSwitchStatusAdminState OBJECT-TYPE
   SYNTAX      DisplayString
   MAX-ACCESS  read-only
   STATUS      current
   DESCRIPTION
       "The port's current administrative state. Refer to NAS Admin State for a description of possible values."
   ::= { gs2310NASSwitchStatusEntry 2 }

gs2310NASSwitchStatusPortState OBJECT-TYPE
   SYNTAX      DisplayString
   MAX-ACCESS  read-only
   STATUS      current
   DESCRIPTION
       "The current state of the port. Refer to NAS Port State for a description of the individual states."
   ::= { gs2310NASSwitchStatusEntry 3 }

gs2310NASSwitchStatusLastSource OBJECT-TYPE
   SYNTAX      DisplayString
   MAX-ACCESS  read-only
   STATUS      current
   DESCRIPTION
       "The source MAC address carried in the most recently received EAPOL frame for EAPOL-based authentication,
	   and the most recently received frame from a new client for MAC-based authentication."
   ::= { gs2310NASSwitchStatusEntry 4 }

gs2310NASSwitchStatusLastID OBJECT-TYPE
   SYNTAX      DisplayString
   MAX-ACCESS  read-only
   STATUS      current
   DESCRIPTION
       "The user name (supplicant identity) carried in the most recently received Response Identity EAPOL frame
	   for EAPOL-based authentication, and the source MAC address from the most recently received frame from a
	   new client for MAC-based authentication."
   ::= { gs2310NASSwitchStatusEntry 5 }

gs2310NASSwitchStatusQoSClass OBJECT-TYPE
   SYNTAX      DisplayString
   MAX-ACCESS  read-only
   STATUS      current
   DESCRIPTION
       "QoS Class assigned to the port by the RADIUS server if enabled."
   ::= { gs2310NASSwitchStatusEntry 6 }

gs2310NASSwitchStatusPortVlanID OBJECT-TYPE
   SYNTAX      DisplayString
   MAX-ACCESS  read-only
   STATUS      current
   DESCRIPTION
       "The VLAN ID that NAS has put the port in. The field is blank, if the Port VLAN ID is not overridden by NAS."
   ::= { gs2310NASSwitchStatusEntry 7 }

gs2310NASPortStatus                                 OBJECT IDENTIFIER ::= { gs2310NAS 3 }

gs2310NASPortStatusCountersTable OBJECT-TYPE
   SYNTAX      SEQUENCE OF GS2310NASPortStatusCountersEntry
   MAX-ACCESS  not-accessible
   STATUS      current
   DESCRIPTION
       ""
   ::= { gs2310NASPortStatus 1 }

gs2310NASPortStatusCountersEntry OBJECT-TYPE
   SYNTAX      GS2310NASPortStatusCountersEntry
   MAX-ACCESS  not-accessible
   STATUS      current
   DESCRIPTION
       ""
   INDEX    { gs2310NASPortConfigPort }
   ::= { gs2310NASPortStatusCountersTable 1 }

GS2310NASPortStatusCountersEntry ::= SEQUENCE {
   gs2310NASRxCountersEAPOLTotal  	                  Counter32,
   gs2310NASRxCountersEAPOLResponseID	              Counter32,
   gs2310NASRxCountersEAPOLResponses	              Counter32,
   gs2310NASRxCountersEAPOLStart	                  Counter32,
   gs2310NASRxCountersEAPOLLogoff                    Counter32,
   gs2310NASRxCountersEAPOLInvalidType               Counter32,
   gs2310NASRxCountersEAPOLInvalidLength             Counter32,
   gs2310NASTxCountersEAPOLTotal                     Counter32,
   gs2310NASTxCountersEAPOLRequestID                 Counter32,
   gs2310NASTxCountersEAPOLRequests                  Counter32,
   gs2310NASRxBackendServerCountersAccessChallenges  Counter32,
   gs2310NASRxBackendServerCountersOtherRequests     Counter32,
   gs2310NASRxBackendServerCountersAuthSuccesses     Counter32,
   gs2310NASRxBackendServerCountersAuthFailures      Counter32,
   gs2310NASTxBackendServerCountersResponses         Counter32,
   gs2310NASLastSupplicantInfoMACAddress             DisplayString,
   gs2310NASLastSupplicantInfoVlanID                 Integer32,
   gs2310NASLastSupplicantInfoVersion                Integer32,
   gs2310NASLastSupplicantInfoIdentity               DisplayString,
   gs2310NASCountersDoClear                          INTEGER
}

gs2310NASRxCountersEAPOLTotal OBJECT-TYPE
   SYNTAX      Counter32
   MAX-ACCESS  read-only
   STATUS      current
   DESCRIPTION
       "The number of valid EAPOL frames of any type that have been received by the switch."
   ::= { gs2310NASPortStatusCountersEntry 2 }

gs2310NASRxCountersEAPOLResponseID OBJECT-TYPE
   SYNTAX      Counter32
   MAX-ACCESS  read-only
   STATUS      current
   DESCRIPTION
       "The number of valid EAPOL Response Identity frames that have been received by the switch."
   ::= { gs2310NASPortStatusCountersEntry 3 }

gs2310NASRxCountersEAPOLResponses OBJECT-TYPE
   SYNTAX      Counter32
   MAX-ACCESS  read-only
   STATUS      current
   DESCRIPTION
       "The number of valid EAPOL response frames (other than Response Identity frames)
	   that have been received by the switch."
   ::= { gs2310NASPortStatusCountersEntry 4 }

gs2310NASRxCountersEAPOLStart OBJECT-TYPE
   SYNTAX      Counter32
   MAX-ACCESS  read-only
   STATUS      current
   DESCRIPTION
       "The number of EAPOL Start frames that have been received by the switch."
   ::= { gs2310NASPortStatusCountersEntry 5 }

gs2310NASRxCountersEAPOLLogoff OBJECT-TYPE
   SYNTAX      Counter32
   MAX-ACCESS  read-only
   STATUS      current
   DESCRIPTION
       "The number of valid EAPOL Logoff frames that have been received by the switch."
   ::= { gs2310NASPortStatusCountersEntry 6 }

gs2310NASRxCountersEAPOLInvalidType OBJECT-TYPE
   SYNTAX      Counter32
   MAX-ACCESS  read-only
   STATUS      current
   DESCRIPTION
       "The number of EAPOL frames that have been received by the switch in which
	   the frame type is not recognized."
   ::= { gs2310NASPortStatusCountersEntry 7 }

gs2310NASRxCountersEAPOLInvalidLength OBJECT-TYPE
   SYNTAX      Counter32
   MAX-ACCESS  read-only
   STATUS      current
   DESCRIPTION
       "The number of EAPOL frames that have been received by the switch in which the
	   Packet Body Length field is invalid."
   ::= { gs2310NASPortStatusCountersEntry 8 }

gs2310NASTxCountersEAPOLTotal OBJECT-TYPE
   SYNTAX      Counter32
   MAX-ACCESS  read-only
   STATUS      current
   DESCRIPTION
       "The number of EAPOL frames of any type that have been transmitted by the switch."
   ::= { gs2310NASPortStatusCountersEntry 9 }

gs2310NASTxCountersEAPOLRequestID OBJECT-TYPE
   SYNTAX      Counter32
   MAX-ACCESS  read-only
   STATUS      current
   DESCRIPTION
       "The number of EAPOL Request Identity frames that have been transmitted by the switch."
   ::= { gs2310NASPortStatusCountersEntry 10 }

gs2310NASTxCountersEAPOLRequests OBJECT-TYPE
   SYNTAX      Counter32
   MAX-ACCESS  read-only
   STATUS      current
   DESCRIPTION
       "The number of valid EAPOL Request frames (other than Request Identity frames)
	   that have been transmitted by the switch."
   ::= { gs2310NASPortStatusCountersEntry 11 }

gs2310NASRxBackendServerCountersAccessChallenges OBJECT-TYPE
   SYNTAX      Counter32
   MAX-ACCESS  read-only
   STATUS      current
   DESCRIPTION
       "802.1X-based: Counts the number of times that the switch receives the first request
	   from the backend server following the first response from the supplicant.
	   MAC-based: Counts all Access Challenges received from the backend server for this
	   port or client."
   ::= { gs2310NASPortStatusCountersEntry 12 }

gs2310NASRxBackendServerCountersOtherRequests OBJECT-TYPE
   SYNTAX      Counter32
   MAX-ACCESS  read-only
   STATUS      current
   DESCRIPTION
       "802.1X-based: Counts the number of times that the switch sends an EAP Request
	   packet following the first to the supplicant.
	   MAC-based: Not applicable."
   ::= { gs2310NASPortStatusCountersEntry 13 }

gs2310NASRxBackendServerCountersAuthSuccesses OBJECT-TYPE
   SYNTAX      Counter32
   MAX-ACCESS  read-only
   STATUS      current
   DESCRIPTION
       "Counts the number of times that the switch receives a success indication.
	   Indicates that the supplicant/client has successfully authenticated to the
	   backend server."
   ::= { gs2310NASPortStatusCountersEntry 14 }

gs2310NASRxBackendServerCountersAuthFailures OBJECT-TYPE
   SYNTAX      Counter32
   MAX-ACCESS  read-only
   STATUS      current
   DESCRIPTION
       "Counts the number of times that the switch receives a failure message.
	   This indicates that the supplicant/client has not authenticated to the
	   backend server. "
   ::= { gs2310NASPortStatusCountersEntry 15 }

gs2310NASTxBackendServerCountersResponses OBJECT-TYPE
   SYNTAX      Counter32
   MAX-ACCESS  read-only
   STATUS      current
   DESCRIPTION
       "802.1X-based: Counts the number of times that the switch attempts to
	   send a supplicant's first response packet to the backend server. Indicates
	   the switch attempted communication with the backend server. Possible
	   retransmissions are not counted.
	   MAC-based: Counts all the backend server packets sent from the switch
	   towards the backend server for a given port or client. Possible
	   retransmissions are not counted."
   ::= { gs2310NASPortStatusCountersEntry 16 }

gs2310NASLastSupplicantInfoMACAddress OBJECT-TYPE
   SYNTAX      DisplayString
   MAX-ACCESS  read-only
   STATUS      current
   DESCRIPTION
       "The MAC address of the last supplicant/client."
   ::= { gs2310NASPortStatusCountersEntry 17 }

gs2310NASLastSupplicantInfoVlanID OBJECT-TYPE
   SYNTAX      Integer32
   MAX-ACCESS  read-only
   STATUS      current
   DESCRIPTION
       "The VLAN ID on which the last frame from the last supplicant/client was received."
   ::= { gs2310NASPortStatusCountersEntry 18 }

gs2310NASLastSupplicantInfoVersion OBJECT-TYPE
   SYNTAX      Integer32
   MAX-ACCESS  read-only
   STATUS      current
   DESCRIPTION
       "802.1X-based: The protocol version number carried in the most recently
	   received EAPOL frame.
	   MAC-based: Not applicable."
   ::= { gs2310NASPortStatusCountersEntry 19 }

gs2310NASLastSupplicantInfoIdentity OBJECT-TYPE
   SYNTAX      DisplayString
   MAX-ACCESS  read-only
   STATUS      current
   DESCRIPTION
       "802.1X-based: The user name (supplicant identity) carried in the most recently received
	   Response Identity EAPOL frame.
	   MAC-based: Not applicable."
   ::= { gs2310NASPortStatusCountersEntry 20 }

gs2310NASCountersDoClear OBJECT-TYPE
   SYNTAX      INTEGER { doNothing(0), do(1) }
   MAX-ACCESS  read-write
   STATUS      current
   DESCRIPTION
       "Clear the counters for the selected port."
   ::= { gs2310NASPortStatusCountersEntry 21 }

gs2310NASPortStatusClientsTable OBJECT-TYPE
   SYNTAX      SEQUENCE OF GS2310NASPortStatusClientsEntry
   MAX-ACCESS  not-accessible
   STATUS      current
   DESCRIPTION
       ""
   ::= { gs2310NASPortStatus 2 }

gs2310NASPortStatusClientsEntry OBJECT-TYPE
   SYNTAX      GS2310NASPortStatusClientsEntry
   MAX-ACCESS  not-accessible
   STATUS      current
   DESCRIPTION
       ""
   INDEX    { gs2310NASPortConfigPort,
		gs2310NASClientsIndex}
   ::= { gs2310NASPortStatusClientsTable 1 }

GS2310NASPortStatusClientsEntry ::= SEQUENCE {
   gs2310NASClientsIndex  	                  		    Integer32,
   gs2310NASClientsIdentity							DisplayString,
   gs2310NASClientsMACAddress  	                  	DisplayString,
   gs2310NASClientsVlanID		              			Integer32,
   gs2310NASClientsState	              				DisplayString,
   gs2310NASClientsLastAuth	                  		DisplayString,
   gs2310NASRxClientsEAPOLTotal  	                  	Counter32,
   gs2310NASRxClientsEAPOLResponseID	              	Counter32,
   gs2310NASRxClientsEAPOLResponses	              	Counter32,
   gs2310NASRxClientsEAPOLStart	                  	Counter32,
   gs2310NASRxClientsEAPOLLogoff                    	Counter32,
   gs2310NASRxClientsEAPOLInvalidType               	Counter32,
   gs2310NASRxClientsEAPOLInvalidLength             	Counter32,
   gs2310NASTxClientsEAPOLTotal                     	Counter32,
   gs2310NASTxClientsEAPOLRequestID                 	Counter32,
   gs2310NASTxClientsEAPOLRequests                  	Counter32,
   gs2310NASRxBackendServerClientsAccessChallenges  	Counter32,
   gs2310NASRxBackendServerClientsOtherRequests     	Counter32,
   gs2310NASRxBackendServerClientsAuthSuccesses     	Counter32,
   gs2310NASRxBackendServerClientsAuthFailures      	Counter32,
   gs2310NASTxBackendServerClientsResponses         	Counter32
}

gs2310NASClientsIndex OBJECT-TYPE
   SYNTAX      Integer32(1..255)
   MAX-ACCESS  not-accessible
   STATUS      current
   DESCRIPTION
       "Entry of client table in the port."
   ::= { gs2310NASPortStatusClientsEntry 1 }

gs2310NASClientsIdentity OBJECT-TYPE
   SYNTAX      DisplayString
   MAX-ACCESS  read-only
   STATUS      current
   DESCRIPTION
       "Shows the identity of the supplicant, as received in the Response Identity
	   EAPOL frame.This isn't available for MAC-based Auth."
   ::= { gs2310NASPortStatusClientsEntry 2 }

gs2310NASClientsMACAddress OBJECT-TYPE
   SYNTAX      DisplayString
   MAX-ACCESS  read-only
   STATUS      current
   DESCRIPTION
       "Multi 802.1X, this column holds the MAC address of the attached supplicant.
	   MAC-based Auth., this column holds the MAC address of the attached client."
   ::= { gs2310NASPortStatusClientsEntry 3 }

gs2310NASClientsVlanID OBJECT-TYPE
   SYNTAX      Integer32(1..4095)
   MAX-ACCESS  read-only
   STATUS      current
   DESCRIPTION
       "This column holds the VLAN ID that the corresponding client is currently
	   secured through the Port Security module."
   ::= { gs2310NASPortStatusClientsEntry 4 }

gs2310NASClientsState OBJECT-TYPE
   SYNTAX      DisplayString
   MAX-ACCESS  read-only
   STATUS      current
   DESCRIPTION
       "The client can either be authenticated or unauthenticated. In the authenticated
	   state, it is allowed to forward frames on the port, and in the unauthenticated
	   state, it is blocked."
   ::= { gs2310NASPortStatusClientsEntry 5 }

gs2310NASClientsLastAuth OBJECT-TYPE
   SYNTAX      DisplayString
   MAX-ACCESS  read-only
   STATUS      current
   DESCRIPTION
       "Shows the date and time of the last authentication of the client."
   ::= { gs2310NASPortStatusClientsEntry 6 }

gs2310NASRxClientsEAPOLTotal OBJECT-TYPE
   SYNTAX      Counter32
   MAX-ACCESS  read-only
   STATUS      current
   DESCRIPTION
       "The number of valid EAPOL frames of any type that have been received by the switch."
   ::= { gs2310NASPortStatusClientsEntry 7 }

gs2310NASRxClientsEAPOLResponseID OBJECT-TYPE
   SYNTAX      Counter32
   MAX-ACCESS  read-only
   STATUS      current
   DESCRIPTION
       "The number of valid EAPOL Response Identity frames that have been received by the switch."
   ::= { gs2310NASPortStatusClientsEntry 8 }

gs2310NASRxClientsEAPOLResponses OBJECT-TYPE
   SYNTAX      Counter32
   MAX-ACCESS  read-only
   STATUS      current
   DESCRIPTION
       "The number of valid EAPOL response frames (other than Response Identity frames)
	   that have been received by the switch."
   ::= { gs2310NASPortStatusClientsEntry 9 }

gs2310NASRxClientsEAPOLStart OBJECT-TYPE
   SYNTAX      Counter32
   MAX-ACCESS  read-only
   STATUS      current
   DESCRIPTION
       "The number of EAPOL Start frames that have been received by the switch."
   ::= { gs2310NASPortStatusClientsEntry 10 }

gs2310NASRxClientsEAPOLLogoff OBJECT-TYPE
   SYNTAX      Counter32
   MAX-ACCESS  read-only
   STATUS      current
   DESCRIPTION
       "The number of valid EAPOL Logoff frames that have been received by the switch."
   ::= { gs2310NASPortStatusClientsEntry 11 }

gs2310NASRxClientsEAPOLInvalidType OBJECT-TYPE
   SYNTAX      Counter32
   MAX-ACCESS  read-only
   STATUS      current
   DESCRIPTION
       "The number of EAPOL frames that have been received by the switch in which
	   the frame type is not recognized."
   ::= { gs2310NASPortStatusClientsEntry 12 }

gs2310NASRxClientsEAPOLInvalidLength OBJECT-TYPE
   SYNTAX      Counter32
   MAX-ACCESS  read-only
   STATUS      current
   DESCRIPTION
       "The number of EAPOL frames that have been received by the switch in which the
	   Packet Body Length field is invalid."
   ::= { gs2310NASPortStatusClientsEntry 13 }

gs2310NASTxClientsEAPOLTotal OBJECT-TYPE
   SYNTAX      Counter32
   MAX-ACCESS  read-only
   STATUS      current
   DESCRIPTION
       "The number of EAPOL frames of any type that have been transmitted by the switch."
   ::= { gs2310NASPortStatusClientsEntry 14 }

gs2310NASTxClientsEAPOLRequestID OBJECT-TYPE
   SYNTAX      Counter32
   MAX-ACCESS  read-only
   STATUS      current
   DESCRIPTION
       "The number of EAPOL Request Identity frames that have been transmitted by the switch."
   ::= { gs2310NASPortStatusClientsEntry 15 }

gs2310NASTxClientsEAPOLRequests OBJECT-TYPE
   SYNTAX      Counter32
   MAX-ACCESS  read-only
   STATUS      current
   DESCRIPTION
       "The number of valid EAPOL Request frames (other than Request Identity frames)
	   that have been transmitted by the switch."
   ::= { gs2310NASPortStatusClientsEntry 16 }

gs2310NASRxBackendServerClientsAccessChallenges OBJECT-TYPE
   SYNTAX      Counter32
   MAX-ACCESS  read-only
   STATUS      current
   DESCRIPTION
       "802.1X-based: Counts the number of times that the switch receives the first request
	   from the backend server following the first response from the supplicant.
	   MAC-based: Counts all Access Challenges received from the backend server for this
	   port or client."
   ::= { gs2310NASPortStatusClientsEntry 17 }

gs2310NASRxBackendServerClientsOtherRequests OBJECT-TYPE
   SYNTAX      Counter32
   MAX-ACCESS  read-only
   STATUS      current
   DESCRIPTION
       "802.1X-based: Counts the number of times that the switch sends an EAP Request
	   packet following the first to the supplicant.
	   MAC-based: Not applicable."
   ::= { gs2310NASPortStatusClientsEntry 18 }

gs2310NASRxBackendServerClientsAuthSuccesses OBJECT-TYPE
   SYNTAX      Counter32
   MAX-ACCESS  read-only
   STATUS      current
   DESCRIPTION
       "Counts the number of times that the switch receives a success indication.
	   Indicates that the supplicant/client has successfully authenticated to the
	   backend server."
   ::= { gs2310NASPortStatusClientsEntry 19 }

gs2310NASRxBackendServerClientsAuthFailures OBJECT-TYPE
   SYNTAX      Counter32
   MAX-ACCESS  read-only
   STATUS      current
   DESCRIPTION
       "Counts the number of times that the switch receives a failure message.
	   This indicates that the supplicant/client has not authenticated to the
	   backend server. "
   ::= { gs2310NASPortStatusClientsEntry 20 }

gs2310NASTxBackendServerClientsResponses OBJECT-TYPE
   SYNTAX      Counter32
   MAX-ACCESS  read-only
   STATUS      current
   DESCRIPTION
       "802.1X-based: Counts the number of times that the switch attempts to
	   send a supplicant's first response packet to the backend server. Indicates
	   the switch attempted communication with the backend server. Possible
	   retransmissions are not counted.
	   MAC-based: Counts all the backend server packets sent from the switch
	   towards the backend server for a given port or client. Possible
	   retransmissions are not counted."
   ::= { gs2310NASPortStatusClientsEntry 21 }


gs2310Maintenance                                           OBJECT IDENTIFIER ::= { lancomGS2310 4 }

gs2310RestartDevice OBJECT-TYPE
   SYNTAX      INTEGER { disable(0), enable(1) }
   MAX-ACCESS  read-write
   STATUS      current
   DESCRIPTION
       "default: 0
        0:none
        1:yes"
   ::= { gs2310Maintenance 1 }

gs2310ColdRestartDevice OBJECT-TYPE
   SYNTAX      INTEGER { disable(0), enable(1) }
   MAX-ACCESS  read-write
   STATUS      current
   DESCRIPTION
       "default: 0
        0:none
        1:yes"
   ::= { gs2310Maintenance 1500 }

gs2310Firmware                                         OBJECT IDENTIFIER ::= { gs2310Maintenance 2 }

gs2310FirmwareIpAddress OBJECT-TYPE
   SYNTAX       IpAddress
   MAX-ACCESS   read-write
   STATUS       current
   DESCRIPTION
        "Get/Set the firmware tftp server."
   ::= { gs2310Firmware 1 }

gs2310FirmwareFileName OBJECT-TYPE
   SYNTAX       DisplayString
   MAX-ACCESS   read-write
   STATUS       current
   DESCRIPTION
        "Get/Set the path and filename for firmware upgrading."
   ::= { gs2310Firmware 2 }

gs2310DoFirmwareUpgrade OBJECT-TYPE
   SYNTAX       INTEGER { doNothing(0), do(1) }
   MAX-ACCESS   read-write
   STATUS       current
   DESCRIPTION
        "Do firmware upgrade. Get this OID always return zero.
              1 - do firmware upgrade.
              0 - do nothing."
   ::= { gs2310Firmware 3 }

gs2310SaveOrRestore                                         OBJECT IDENTIFIER ::= { gs2310Maintenance 3 }

gs2310FactoryDefaults OBJECT-TYPE
   SYNTAX      INTEGER { none(0), yes(1) }
   MAX-ACCESS  read-write
   STATUS      current
   DESCRIPTION
       "default: 0
        0:none
        1:yes"
   ::= { gs2310SaveOrRestore 1 }

gs2310SaveStart OBJECT-TYPE
   SYNTAX      INTEGER { none(0), yes(1) }
   MAX-ACCESS  read-write
   STATUS      current
   DESCRIPTION
       "default: 0
        0:none
        1:yes"
   ::= { gs2310SaveOrRestore 2 }

gs2310SaveUser OBJECT-TYPE
   SYNTAX      INTEGER { none(0), yes(1) }
   MAX-ACCESS  read-write
   STATUS      current
   DESCRIPTION
       "default: 0
        0:none
        1:yes"
   ::= { gs2310SaveOrRestore 3 }

gs2310RestoreUser OBJECT-TYPE
   SYNTAX      INTEGER { none(0), yes(1) }
   MAX-ACCESS  read-write
   STATUS      current
   DESCRIPTION
       "default: 0
        0:none
        1:yes"
   ::= { gs2310SaveOrRestore 4 }


gs2310ExportOrImport                                        OBJECT IDENTIFIER ::= { gs2310Maintenance 4 }

gs2310ExportIpAddress OBJECT-TYPE
   SYNTAX       IpAddress
   MAX-ACCESS   read-write
   STATUS       current
   DESCRIPTION
        "Get/Set the export tftp server."
   ::= { gs2310ExportOrImport 1 }

gs2310ExportConfigName OBJECT-TYPE
   SYNTAX       DisplayString
   MAX-ACCESS   read-write
   STATUS       current
   DESCRIPTION
       "Get/Set the export file path and name."
   ::= { gs2310ExportOrImport 2 }

gs2310DoExportConfig OBJECT-TYPE
   SYNTAX       INTEGER{ doNothing(0), do(1) }
   MAX-ACCESS   read-write
   STATUS       current
   DESCRIPTION
        "Do export-config.
         Get this OID always return zero.
         1 - export."
   ::= { gs2310ExportOrImport 3 }

gs2310ImportIpAddress OBJECT-TYPE
   SYNTAX       IpAddress
   MAX-ACCESS   read-write
   STATUS       current
   DESCRIPTION
        "Get/Set the import tftp server."
   ::= { gs2310ExportOrImport 4 }

gs2310ImportConfigName OBJECT-TYPE
   SYNTAX      DisplayString
   MAX-ACCESS  read-write
   STATUS      current
   DESCRIPTION
       "Get/Set the import file path and name."
   ::= { gs2310ExportOrImport 5 }

gs2310DoImportConfig OBJECT-TYPE
   SYNTAX       INTEGER{ doNothing(0), do(1) }
   MAX-ACCESS   read-write
   STATUS       current
   DESCRIPTION
        "Do export-config.
         Get this OID always return zero.
         1 - import."
   ::= { gs2310ExportOrImport 6 }

gs2310Diagnostics                                           OBJECT IDENTIFIER ::= { gs2310Maintenance 5 }

gs2310PingIpAddress OBJECT-TYPE
   SYNTAX      IpAddress
   MAX-ACCESS  read-write
   STATUS      current
   DESCRIPTION
       " The destination IP Address. "
   ::= { gs2310Diagnostics 1 }

gs2310PingSize OBJECT-TYPE
   SYNTAX      Integer32(60..1400)
   MAX-ACCESS  read-write
   STATUS      current
   DESCRIPTION
       " Size of ICMP echo packet.
         range : 60-1400, default : 64. "
   ::= { gs2310Diagnostics 2 }

gs2310DoPingConfig OBJECT-TYPE
   SYNTAX       INTEGER{ doNothing(0), do(1) }
   MAX-ACCESS  read-write
   STATUS      current
   DESCRIPTION
       "Do ping-config.
         Get this OID always return zero.
         1 - ping. Uses the ICMP protocol's mandatory ECHO_REQUEST datagram
         to elicit an ICMP ECHO_RESPONSE from a host or gateway. "
   ::= { gs2310Diagnostics 3 }

gs2310PingResult OBJECT-TYPE
   SYNTAX      DisplayString
   MAX-ACCESS  read-only
   STATUS      current
   DESCRIPTION
       " Show ping result. "
   ::= { gs2310Diagnostics 4 }

gs2310Ping6IpAddress OBJECT-TYPE
   SYNTAX      DisplayString
   MAX-ACCESS  read-write
   STATUS      current
   DESCRIPTION
       " The destination IPv6 Address. "
   ::= { gs2310Diagnostics 5 }

gs2310Ping6Size OBJECT-TYPE
   SYNTAX      Integer32(60..1400)
   MAX-ACCESS  read-write
   STATUS      current
   DESCRIPTION
       " Size of ICMP echo packet.
         range : 60-1400. "
   ::= { gs2310Diagnostics 6 }

gs2310DoPing6Config OBJECT-TYPE
   SYNTAX       INTEGER{ doNothing(0), do(1) }
   MAX-ACCESS  read-write
   STATUS      current
   DESCRIPTION
       "Do ping-config.
         Get this OID always return zero.
         1 - ping. Uses the ICMP protocol's mandatory ECHO_REQUEST datagram
         to elicit an ICMP ECHO_RESPONSE from a host or gateway. "
   ::= { gs2310Diagnostics 7 }

gs2310Ping6Result OBJECT-TYPE
   SYNTAX      DisplayString
   MAX-ACCESS  read-only
   STATUS      current
   DESCRIPTION
       " Show ping result. "
   ::= { gs2310Diagnostics 8 }




------------------------------------------------------------------------------------------------------------------
gs2310Trap                                                  OBJECT IDENTIFIER ::= { lancomGS2310 5 }

gs2310TrapEvent                                             OBJECT IDENTIFIER ::= { gs2310Trap 1 }

gs2310Emergency NOTIFICATION-TYPE
  OBJECTS   { gs2310Information }
  STATUS        current
    DESCRIPTION
        "The severity level is Emergency. The system is unusable."
    ::= { gs2310TrapEvent 1 }

gs2310Alert NOTIFICATION-TYPE
  OBJECTS   { gs2310Information }
  STATUS        current
    DESCRIPTION
        "The severity level is Alert. The action must be taken immediately."
    ::= { gs2310TrapEvent 2 }

gs2310Critical NOTIFICATION-TYPE
  OBJECTS   { gs2310Information }
  STATUS        current
    DESCRIPTION
        "The severity level is Critical. Critical conditions."
    ::= { gs2310TrapEvent 3 }

gs2310Error NOTIFICATION-TYPE
  OBJECTS   { gs2310Information }
  STATUS        current
    DESCRIPTION
        "The severity level is Error. Error conditions."
    ::= { gs2310TrapEvent 4 }

gs2310Warning NOTIFICATION-TYPE
  OBJECTS   { gs2310Information }
  STATUS        current
    DESCRIPTION
        "The severity level is Warning. Warning conditions."
    ::= { gs2310TrapEvent 5 }

gs2310Notice NOTIFICATION-TYPE
  OBJECTS   { gs2310Information }
  STATUS        current
    DESCRIPTION
        "The severity level is Notice. Normal but significant condition."
    ::= { gs2310TrapEvent 6 }

gs2310Informational NOTIFICATION-TYPE
  OBJECTS   { gs2310Information }
  STATUS        current
    DESCRIPTION
        "The severity level is Informational. Informational messages."
    ::= { gs2310TrapEvent 7 }

gs2310Debug NOTIFICATION-TYPE
  OBJECTS   { gs2310Information }
  STATUS        current
    DESCRIPTION
        "The severity level is Debug. debug-level messages."
    ::= { gs2310TrapEvent 8 }

gs2310TrapVariable                                          OBJECT IDENTIFIER ::= { gs2310Trap 2 }

gs2310Information OBJECT-TYPE
    SYNTAX      DisplayString
    MAX-ACCESS  read-only
    STATUS      current
    DESCRIPTION
        "Trap information."
    ::= { gs2310TrapVariable 1 }


END
