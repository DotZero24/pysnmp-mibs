LANCOM-REF-MIB DEFINITIONS ::= BEGIN

-- Lancom  Reference MIB


IMPORTS
    MODULE-IDENTITY                     FROM SNMPv2-SMI
    TEXTUAL-CONVENTION                  FROM SNMPv2-TC
    enterprises                         FROM RFC1155-SMI;

    lcosSX2 MODULE-IDENTITY
        LAST-UPDATED "202004240000Z"
        ORGANIZATION "LANCOM Systems GmbH"
        CONTACT-INFO
            "
            Adenauerstrasse 20 / B2
            52146 Wuerselen
            Germany

            Phone:  +49 (0)2405 49 93 6 0
            Fax:    +49 (0)2405 49 93 6 99
            E-Mail: info@lancom.de"
        DESCRIPTION
        "Management information base definitions"
     REVISION      "202004240000Z"
        DESCRIPTION
        "Initial version of this MIB module."
    ::= { enterprises lancom-systems(2356) 16 }


-- New definitions
 fastPath                 OBJECT IDENTIFIER ::= { lcosSX2 1 }


-- New Textual Conventions
AgentPortMask ::= TEXTUAL-CONVENTION
   STATUS  current
   DESCRIPTION
       "Each octet within this value specifies a set of eight
        ports, with the first octet specifying ports 1 through
        8, the second octet specifying ports 9 through 16, etc.
        Within each octet, the most significant bit represents
        the lowest numbered port, and the least significant bit
        represents the highest numbered port.  Thus, each port
        of the bridge is represented by a single bit within the
        value of this object.  If that bit has a value of '1'
        then that port is included in the set of ports; the port
        is not included if its bit has a value of '0'

        When setting this value, the system will ignore
        configuration for ports not between the first and last
        valid ports.  Configuration of any port numbers between
        this range that are not valid ports return a failure
        message, but will still apply configuration for valid
        ports."
   SYNTAX  OCTET STRING


END
