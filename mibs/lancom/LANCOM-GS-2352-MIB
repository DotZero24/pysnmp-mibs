LANCOM-GS-2352-MIB DEFINITIONS ::= BEGIN

IMPORTS
    DisplayString,MacAddress FROM SNMPv2-TC
    MODULE-COMPLIANCE,OBJECT-GROUP, NOTIFICATION-GROUP       FROM SNMPv2-CONF
    ifIndex    FROM RFC1213-MIB
    enterprises,MODULE-IDENTITY,OBJECT-TYPE,NOTIFICATION-TYPE,Counter32,Counter64,IpAddress        FROM SNMPv2-SMI
    InetAddress                   FROM INET-ADDRESS-MIB
    MacAddress FROM BRIDGE-MIB;

lancom-systems MODULE-IDENTITY
        LAST-UPDATED "202002190000Z"
        ORGANIZATION "LANCOM Systems GmbH."
        CONTACT-INFO
            "Adenauerstrasse 20 / B2, 52146 Wuerselen, Germany
            Email: info@lancom.de
            TEL: +49 (0)2405 49936 0
            FAX: +49 (0)2405 49936 99"
        DESCRIPTION
            "The MIB module is for LANCOM Systems"
        ::= { enterprises 2356 }

switchingSystems                                                          OBJECT IDENTIFIER ::= { lancom-systems 800 }

gigabitEthernetSwitches                                             OBJECT IDENTIFIER ::= { switchingSystems 3 }

lancomGS2352                                                OBJECT IDENTIFIER ::= { gigabitEthernetSwitches 2352 }

gs2352System                                                OBJECT IDENTIFIER ::= { lancomGS2352 1 }

gs2352SystemInformation                                     OBJECT IDENTIFIER ::= { gs2352System 1 }

gs2352ModelName OBJECT-TYPE
   SYNTAX       DisplayString
   MAX-ACCESS   read-only
   STATUS       current
   DESCRIPTION
       ""
 ::= { gs2352SystemInformation 1 }

gs2352BIOSVersion OBJECT-TYPE
   SYNTAX       DisplayString
   MAX-ACCESS   read-only
   STATUS       current
   DESCRIPTION
       ""
   ::= { gs2352SystemInformation 2 }

gs2352FirmwareVersion OBJECT-TYPE
   SYNTAX       DisplayString
   MAX-ACCESS   read-only
   STATUS       current
   DESCRIPTION
       ""
   ::= { gs2352SystemInformation 3 }

gs2352HardwareMechanicalVersion OBJECT-TYPE
   SYNTAX       DisplayString
   MAX-ACCESS   read-only
   STATUS       current
   DESCRIPTION
       ""
   ::= { gs2352SystemInformation 4 }

gs2352SerialNumber OBJECT-TYPE
   SYNTAX       DisplayString
   MAX-ACCESS   read-only
   STATUS       current
   DESCRIPTION
       ""
   ::= { gs2352SystemInformation 5 }

gs2352HostMACAddress OBJECT-TYPE
   SYNTAX       MacAddress
   MAX-ACCESS   read-only
   STATUS       current
   DESCRIPTION
       ""
   ::= { gs2352SystemInformation 6 }

gs2352ConsoleBaudrate OBJECT-TYPE
   SYNTAX       DisplayString
   MAX-ACCESS   read-only
   STATUS       current
   DESCRIPTION
       ""
   ::= { gs2352SystemInformation 7 }

gs2352RAMSize OBJECT-TYPE
   SYNTAX       DisplayString
   MAX-ACCESS   read-only
   STATUS       current
   DESCRIPTION
       ""
   ::= { gs2352SystemInformation 8 }

gs2352FlashSize OBJECT-TYPE
   SYNTAX       DisplayString
   MAX-ACCESS   read-only
   STATUS       current
   DESCRIPTION
       ""
   ::= { gs2352SystemInformation 9 }

gs2352BridgeFDBSize OBJECT-TYPE
   SYNTAX       DisplayString
   MAX-ACCESS   read-only
   STATUS       current
   DESCRIPTION
       ""
   ::= { gs2352SystemInformation 10 }

gs2352TransmitQueue OBJECT-TYPE
   SYNTAX       DisplayString
   MAX-ACCESS   read-only
   STATUS       current
   DESCRIPTION
       ""
   ::= { gs2352SystemInformation 11 }

gs2352MaximumFrameSize OBJECT-TYPE
   SYNTAX       DisplayString
   MAX-ACCESS   read-only
   STATUS       current
   DESCRIPTION
       ""
   ::= { gs2352SystemInformation 12 }

gs2352CPULoad OBJECT-TYPE
   SYNTAX       DisplayString
   MAX-ACCESS   read-only
   STATUS       current
   DESCRIPTION
       ""
   ::= { gs2352SystemInformation 13 }

gs2352FanSpeed OBJECT-TYPE
   SYNTAX       DisplayString
   MAX-ACCESS   read-only
   STATUS       current
   DESCRIPTION
       ""
   ::= { gs2352SystemInformation 17 }

gs2352ACPower OBJECT-TYPE
   SYNTAX       DisplayString
   MAX-ACCESS   read-only
   STATUS       current
   DESCRIPTION
       ""
   ::= { gs2352SystemInformation 18 }

gs2352Temperature OBJECT-TYPE
   SYNTAX       DisplayString
   MAX-ACCESS   read-only
   STATUS       current
   DESCRIPTION
       ""
   ::= { gs2352SystemInformation 19 }

gs2352SystemDescription OBJECT-TYPE
   SYNTAX       DisplayString
   MAX-ACCESS   read-only
   STATUS       current
   DESCRIPTION
       ""
   ::= { gs2352SystemInformation 21 }

gs2352Location OBJECT-TYPE
   SYNTAX       DisplayString
   MAX-ACCESS   read-only
   STATUS       current
   DESCRIPTION
       ""
   ::= { gs2352SystemInformation 22 }

gs2352Contact OBJECT-TYPE
   SYNTAX       DisplayString
   MAX-ACCESS   read-only
   STATUS       current
   DESCRIPTION
       ""
   ::= { gs2352SystemInformation 23 }

gs2352DeviceName OBJECT-TYPE
   SYNTAX       DisplayString
   MAX-ACCESS   read-only
   STATUS       current
   DESCRIPTION
       ""
   ::= { gs2352SystemInformation 24 }

gs2352SystemDate OBJECT-TYPE
   SYNTAX       DisplayString
   MAX-ACCESS   read-only
   STATUS       current
   DESCRIPTION
       ""
   ::= { gs2352SystemInformation 25 }

gs2352SystemUptime OBJECT-TYPE
   SYNTAX       DisplayString
   MAX-ACCESS   read-only
   STATUS       current
   DESCRIPTION
       ""
   ::= { gs2352SystemInformation 26 }

gs2352SystemIPv4Address OBJECT-TYPE
   SYNTAX       DisplayString
   MAX-ACCESS   read-only
   STATUS       current
   DESCRIPTION
       ""
   ::= { gs2352SystemInformation 27 }

gs2352SystemIPv4SubnetMask OBJECT-TYPE
   SYNTAX       DisplayString
   MAX-ACCESS   read-only
   STATUS       current
   DESCRIPTION
       ""
   ::= { gs2352SystemInformation 28 }

gs2352SystemIPv4Gateway OBJECT-TYPE
   SYNTAX       DisplayString
   MAX-ACCESS   read-only
   STATUS       current
   DESCRIPTION
       ""
   ::= { gs2352SystemInformation 29 }

gs2352IPv6LinkLocalAddress OBJECT-TYPE
   SYNTAX       DisplayString
   MAX-ACCESS   read-only
   STATUS       current
   DESCRIPTION
       ""
   ::= { gs2352SystemInformation 30 }

gs2352IPv6Address OBJECT-TYPE
   SYNTAX       DisplayString
   MAX-ACCESS   read-only
   STATUS       current
   DESCRIPTION
       ""
   ::= { gs2352SystemInformation 31 }

gs2352IPv6Prefix OBJECT-TYPE
   SYNTAX       DisplayString
   MAX-ACCESS   read-only
   STATUS       current
   DESCRIPTION
       ""
   ::= { gs2352SystemInformation 32 }

gs2352IPv6Gateway OBJECT-TYPE
   SYNTAX       DisplayString
   MAX-ACCESS   read-only
   STATUS       current
   DESCRIPTION
       ""
   ::= { gs2352SystemInformation 33 }

gs2352LargestFreeMemBlock OBJECT-TYPE
   SYNTAX       Integer32
   MAX-ACCESS   read-only
   STATUS       current
   DESCRIPTION
       "Largest free memory block in Kb"
   ::= { gs2352SystemInformation 1500 }

gs2352MemFree  OBJECT-TYPE
   SYNTAX       Integer32
   MAX-ACCESS   read-only
   STATUS       current
   DESCRIPTION
       "Free memory in Kb"
   ::= { gs2352SystemInformation 1501 }

gs2352SystemTime                                            OBJECT IDENTIFIER ::= { gs2352System 2 }

gs2352SystemTimeManual                                      OBJECT IDENTIFIER ::= { gs2352SystemTime 1 }

gs2352SystemTimeManualClockSource OBJECT-TYPE
	SYNTAX	INTEGER {useLocal(0),useNTP(1)}
   MAX-ACCESS   read-write
   STATUS       current
   DESCRIPTION
       "default: 0,
        0 : Use Local Settings,
        1 : Use NTP Server."
   ::= { gs2352SystemTimeManual 1 }

gs2352SystemTimeManualLocaltime OBJECT-TYPE
   SYNTAX       DisplayString
   MAX-ACCESS   read-write
   STATUS       current
   DESCRIPTION
       "Get/Set the system time of the device.
        The input format is 'Year-Month-Day Hour:Minute:Second'.
        ex: 2011-01-01 05:43:05  means 2011/1/1 - 05:43:05 .
        The value range:
        Year    : 2010 - 2090,
        Mouth   : 1 - 12,
        Day     : 1 - 31,
        Hour    : 0 - 23,
        Minute  : 0 - 59,
        Sec     : 0 - 59."
   ::= { gs2352SystemTimeManual 2 }

gs2352SystemTimeManualTimeZoneOffset OBJECT-TYPE
   SYNTAX       INTEGER(-720..780)
   MAX-ACCESS   read-write
   STATUS       current
   DESCRIPTION
       "Get/Set the NTP Time Zone.
        The value range is between -720 and 780 (minutes)."
   ::= { gs2352SystemTimeManual 3 }

gs2352SystemTimeManualDaylightSavings OBJECT-TYPE
   SYNTAX       INTEGER { disable(0), enable(1) }
   MAX-ACCESS   read-write
   STATUS       current
   DESCRIPTION
       "default: 0,
        0 : Disable,
        1 : Enable."
   ::= { gs2352SystemTimeManual 4 }

gs2352SystemTimeManualTimeSetOffset OBJECT-TYPE
   SYNTAX       Integer32(1..1440)
   MAX-ACCESS   read-write
   STATUS       current
   DESCRIPTION
       "Get/Set the Daylight Saving Time.
        The value range is between 1 and 1440 (minutes),
        Default : 60 (minutes)."
   ::= { gs2352SystemTimeManual 5 }

gs2352SystemTimeManualDaylightSavingsType OBJECT-TYPE
   SYNTAX       INTEGER { byDates(0), recurring(1) }
   MAX-ACCESS   read-write
   STATUS       current
   DESCRIPTION
       "default: 0,
        0 : By dates,
        1 : Recurring."
   ::= { gs2352SystemTimeManual 6 }

gs2352SystemTimeManualDaylightSavingsBydatesFrom OBJECT-TYPE
   SYNTAX       DisplayString
   MAX-ACCESS   read-write
   STATUS       current
   DESCRIPTION
       "Get/Set the Start time of By dates Daylight Savings.
        The input format is 'Year-Month-Day Hour:Minute'.
        ex: 2011-01-01 05:43  means 2011/1/1 - 05:43 .
        The value range:
        Year    : 2010 - 2090,
        Mouth   : 1 - 12,
        Day     : 1 - 31,
        Hour    : 0 - 23,
        Minute  : 0 - 59."
   ::= { gs2352SystemTimeManual 7 }

gs2352SystemTimeManualDaylightSavingsBydatesTo OBJECT-TYPE
   SYNTAX       DisplayString
   MAX-ACCESS   read-write
   STATUS       current
   DESCRIPTION
       "Get/Set the End time of By dates Daylight Savings.
        The input format is 'Year-Month-Day Hour:Minute'.
        ex: 2011-01-01 05:43  means 2011/1/1 - 05:43 .
        The value range:
        Year    : 2010 - 2090,
        Mouth   : 1 - 12,
        Day     : 1 - 31,
        Hour    : 0 - 23,
        Minute  : 0 - 59."
   ::= { gs2352SystemTimeManual 8 }

gs2352SystemTimeManualDaylightSavingsRecurringDayFrom OBJECT-TYPE
   SYNTAX      INTEGER {
                        sunday(0),
                        monday(1),
                        tuseday(2),
                        wednesday(3),
                        thursday(4),
                        friday(5),
                        saturday(6)
                        }
   MAX-ACCESS   read-write
   STATUS       current
   DESCRIPTION
       "Get/Set the Daylight Saving Time Day From.
        0 : Sun, 1 : Mon, 2 : Tue, 3 : Wed, 4 : Thu, 5 : Fri, 6 : Sat."
   ::= { gs2352SystemTimeManual 9 }

gs2352SystemTimeManualDaylightSavingsRecurringWeekFrom OBJECT-TYPE
   SYNTAX       INTEGER{
                        firstWeek(1),
                        secondWeek(2),
                        thirdWeek(3),
                        fourthWeek(4),
                        listWeek(5)
                        }
   MAX-ACCESS   read-write
   STATUS       current
   DESCRIPTION
       "Get/Set the Daylight Saving Time Week From.
        1 : first week, 2, 3, 4, 5 : last week"
   ::= { gs2352SystemTimeManual 10 }

gs2352SystemTimeManualDaylightSavingsRecurringMonthFrom OBJECT-TYPE
   SYNTAX      INTEGER {
                        jan(1),
                        feb(2),
                        mar(3),
                        apr(4),
                        may(5),
                        jun(6),
                        jul(7),
                        aug(8),
                        sep(9),
                        oct(10),
                        nov(11),
                        dec(12)
                        }
   MAX-ACCESS   read-write
   STATUS       current
   DESCRIPTION
       "Get/Set the Daylight Saving Time Month From.
        1 : Jan, 2 : Feb, 3 : Mar, 4 : Apr, 5 : May, 6 : Jun,
        7 : Jul, 8 : Aug, 9 : Sep, 10 : Oct, 11 : Nov, 12 : Dec."
   ::= { gs2352SystemTimeManual 11 }

gs2352SystemTimeManualDaylightSavingsRecurringTimeFrom OBJECT-TYPE
   SYNTAX       DisplayString
   MAX-ACCESS   read-write
   STATUS       current
   DESCRIPTION
       "Get/Set the Start time of By dates Daylight Savings.
        The input format is 'Hour:Minute'.
        ex: 05:43.
        The value range:
        Hour    : 0 - 23,
        Minute  : 0 - 59."
   ::= { gs2352SystemTimeManual 12 }

gs2352SystemTimeManualDaylightSavingsRecurringDayTo OBJECT-TYPE
   SYNTAX      INTEGER {
                        sunday(0),
                        monday(1),
                        tuseday(2),
                        wednesday(3),
                        thursday(4),
                        friday(5),
                        saturday(6)
                        }
   MAX-ACCESS   read-write
   STATUS       current
   DESCRIPTION
       "Get/Set the Daylight Saving Time Day To.
        0 : Sun, 1 : Mon, 2 : Tue, 3 : Wed, 4 : Thu, 5 : Fri, 6 : Sat."
   ::= { gs2352SystemTimeManual 13 }

gs2352SystemTimeManualDaylightSavingsRecurringWeekTo OBJECT-TYPE
   SYNTAX       INTEGER{
                        firstWeek(1),
                        secondWeek(2),
                        thirdWeek(3),
                        fourthWeek(4),
                        listWeek(5)
                        }
   MAX-ACCESS   read-write
   STATUS       current
   DESCRIPTION
       "Get/Set the Daylight Saving Time Week To.
        1 : first week, 2, 3, 4, 5 : last week"
   ::= { gs2352SystemTimeManual 14 }

gs2352SystemTimeManualDaylightSavingsRecurringMonthTo OBJECT-TYPE
   SYNTAX      INTEGER {
                        jan(1),
                        feb(2),
                        mar(3),
                        apr(4),
                        may(5),
                        jun(6),
                        jul(7),
                        aug(8),
                        sep(9),
                        oct(10),
                        nov(11),
                        dec(12)
                        }
   MAX-ACCESS   read-write
   STATUS       current
   DESCRIPTION
       "Get/Set the Daylight Saving Time Month To.
        1 : Jan, 2 : Feb, 3 : Mar, 4 : Apr, 5 : May, 6 : Jun,
        7 : Jul, 8 : Aug, 9 : Sep, 10 : Oct, 11 : Nov, 12 : Dec."
   ::= { gs2352SystemTimeManual 15 }

gs2352SystemTimeManualDaylightSavingsRecurringTimeTo OBJECT-TYPE
   SYNTAX       DisplayString
   MAX-ACCESS   read-write
   STATUS       current
   DESCRIPTION
       "Get/Set the Start time of By dates Daylight Savings.
        The input format is 'Hour:Minute'.
        ex: 05:43.
        The value range:
        Hour    : 0 - 23,
        Minute  : 0 - 59."
   ::= { gs2352SystemTimeManual 16 }

gs2352SystemTimeNTP                                     OBJECT IDENTIFIER ::= { gs2352SystemTime 2 }

gs2352SystemTimeNTPTable OBJECT-TYPE
   SYNTAX      SEQUENCE OF GS2352SystemTimeNTPEntry
   MAX-ACCESS  not-accessible
   STATUS      current
   DESCRIPTION
       " "
   ::= { gs2352SystemTimeNTP 1 }

gs2352SystemTimeNTPEntry OBJECT-TYPE
   SYNTAX      GS2352SystemTimeNTPEntry
   MAX-ACCESS  not-accessible
   STATUS      current
   DESCRIPTION
       ""
   INDEX    { gs2352SystemTimeNTPIndex  }
   ::= { gs2352SystemTimeNTPTable 1 }

GS2352SystemTimeNTPEntry ::= SEQUENCE {
   gs2352SystemTimeNTPIndex             Integer32,
   gs2352SystemTimeNTPServerIPType      INTEGER,
   gs2352SystemTimeNTPServer            DisplayString,
   gs2352SystemTimeNTPCurrentMode       INTEGER
}

gs2352SystemTimeNTPIndex OBJECT-TYPE
   SYNTAX      Integer32(1..5)
   MAX-ACCESS  not-accessible
   STATUS      current
   DESCRIPTION
       " The index of the ntp entry. "
   ::= { gs2352SystemTimeNTPEntry 1 }

gs2352SystemTimeNTPServerIPType OBJECT-TYPE
   SYNTAX       INTEGER { ipv4(0), ipv6(1) }
   MAX-ACCESS   read-write
   STATUS       current
   DESCRIPTION
       "Default: 0,
        0 : IPv4,
        1 : IPv6."
   ::= { gs2352SystemTimeNTPEntry 2 }

gs2352SystemTimeNTPServer OBJECT-TYPE
   SYNTAX       DisplayString
   MAX-ACCESS   read-write
   STATUS       current
   DESCRIPTION
       "Get/Set the NTP Time Server1. You can use the IP address or domain name."
   ::= { gs2352SystemTimeNTPEntry 3 }

gs2352SystemTimeNTPCurrentMode OBJECT-TYPE
   SYNTAX      INTEGER { empty(0), active(1), edit(2), delete(3) }
   MAX-ACCESS  read-write
   STATUS      current
   DESCRIPTION
       " 0: Empty
        1: Active
        2: Edit
        3: Delete"
   ::= { gs2352SystemTimeNTPEntry 4 }

gs2352SystemTimeNTPRequestInterval OBJECT-TYPE
   SYNTAX       INTEGER(60..999999999)
   MAX-ACCESS   read-write
   STATUS       current
   DESCRIPTION
       "Get/Set the NTP Request Interval.
        Default : 86400.
        The value range is between 60 and 999999999 (seconds)."
   ::= { gs2352SystemTimeNTP 2 }

gs2352SystemTimeNTPTriesNumber OBJECT-TYPE
   SYNTAX       INTEGER(0..999999999)
   MAX-ACCESS   read-write
   STATUS       current
   DESCRIPTION
       "Get/Set the NTP Number of tries.
        Default : 4.
        The value range is between 0 and 999999999."
   ::= { gs2352SystemTimeNTP 3 }


gs2352SystemAccount                                         OBJECT IDENTIFIER ::= { gs2352System 3 }

gs2352SystemAccountUsers                                    OBJECT IDENTIFIER ::= { gs2352SystemAccount 1 }

gs2352SystemAccountUserCreate OBJECT-TYPE
   SYNTAX       INTEGER { none(0), create(1) }
   MAX-ACCESS   read-write
   STATUS       current
   DESCRIPTION
       "default: 0
        0 : None  (read only)
        1 : Create a user account"
   ::= { gs2352SystemAccountUsers 1 }

gs2352SystemAccountUsersTable OBJECT-TYPE
   SYNTAX      SEQUENCE OF GS2352SystemAccountUsersEntry
   MAX-ACCESS  not-accessible
   STATUS      current
   DESCRIPTION
       " "
   ::= { gs2352SystemAccountUsers 2 }

gs2352SystemAccountUsersEntry OBJECT-TYPE
   SYNTAX      GS2352SystemAccountUsersEntry
   MAX-ACCESS  not-accessible
   STATUS      current
   DESCRIPTION
       ""
   INDEX    { gs2352UserIndex  }
   ::= { gs2352SystemAccountUsersTable 1 }


GS2352SystemAccountUsersEntry ::= SEQUENCE {
   gs2352UserIndex              Integer32 ,
   gs2352UserName               DisplayString,
   gs2352Password               DisplayString,
   gs2352UserPrivilegeLevel     Integer32 ,
   gs2352AccountUserRowStatus   INTEGER
}


gs2352UserIndex OBJECT-TYPE
   SYNTAX      Integer32 (1..20)
   MAX-ACCESS  not-accessible
   STATUS      current
   DESCRIPTION
       " "
   ::= { gs2352SystemAccountUsersEntry 1 }

gs2352UserName OBJECT-TYPE
   SYNTAX      DisplayString (SIZE (1..32))
   MAX-ACCESS  read-write
   STATUS      current
   DESCRIPTION
       "Please use a combination of letters, numbers and underscores"
   ::= { gs2352SystemAccountUsersEntry 2 }

gs2352Password OBJECT-TYPE
   SYNTAX      DisplayString (SIZE (1..32))
   MAX-ACCESS  read-write
   STATUS      current
   DESCRIPTION
       "Please use ASCII printable code except Quotation mark, Colon (punctuation), Less-than sign, Greater-than sign, At sign, Question mark and Space (punctuation)"
   ::= { gs2352SystemAccountUsersEntry 3 }

gs2352UserPrivilegeLevel OBJECT-TYPE
   SYNTAX      Integer32 (1..15)
   MAX-ACCESS  read-write
   STATUS      current
   DESCRIPTION
       "default:1
        User privilege level range : 1 - 15"
   ::= { gs2352SystemAccountUsersEntry 4 }

gs2352AccountUserRowStatus OBJECT-TYPE
   SYNTAX      INTEGER { active(1), notInservice(2), edit(3), destroy(4), undo(5) }
   MAX-ACCESS  read-write
   STATUS      current
   DESCRIPTION
       " 1: active
        2: notInservice
        3: edit
        4: destroy
        5: undo"
   ::= { gs2352SystemAccountUsersEntry 5 }

gs2352SystemAccountUsersSuperUserPassword OBJECT-TYPE
   SYNTAX      OCTET STRING (SIZE (0..32))
   MAX-ACCESS read-write
   STATUS      current
   DESCRIPTION
        "Super-User Password"
   ::= { gs2352SystemAccountUsers 1500 }

gs2352SystemAccountEnforcePasswordRules OBJECT-TYPE
   SYNTAX       INTEGER { yes(0), no(1) }
   MAX-ACCESS   read-write
   STATUS       current
   DESCRIPTION
       "default: 0
        0 : Do not enforce rules
        1 : enforce rules"
   ::= { gs2352SystemAccountUsers 1501 }

gs2352SystemAccountPrivilegeLevel                           OBJECT IDENTIFIER ::= { gs2352SystemAccount 2 }

gs2352AccountPrivilegeLevel OBJECT-TYPE
   SYNTAX      Integer32 (1..15)
   MAX-ACCESS  read-write
   STATUS      current
   DESCRIPTION
       "Default:15, Range : 1-15. "
   ::= { gs2352SystemAccountPrivilegeLevel 1 }

gs2352AggregationPrivilegeLevel OBJECT-TYPE
   SYNTAX      Integer32 (1..15)
   MAX-ACCESS  read-write
   STATUS      current
   DESCRIPTION
       "Default:15, Range : 1-15. "
   ::= { gs2352SystemAccountPrivilegeLevel 2 }

gs2352DiagnosticsPrivilegeLevel OBJECT-TYPE
   SYNTAX      Integer32 (1..15)
   MAX-ACCESS  read-write
   STATUS      current
   DESCRIPTION
       "Default:15, Range : 1-15. "
   ::= { gs2352SystemAccountPrivilegeLevel 3 }

gs2352EasyportPrivilegeLevel OBJECT-TYPE
   SYNTAX      Integer32 (1..15)
   MAX-ACCESS  read-write
   STATUS      current
   DESCRIPTION
       "Default:15, Range : 1-15. "
   ::= { gs2352SystemAccountPrivilegeLevel 9 }

gs2352GARPPrivilegeLevel OBJECT-TYPE
   SYNTAX      Integer32 (1..15)
   MAX-ACCESS  read-write
   STATUS      current
   DESCRIPTION
       "Default:15, Range : 1-15. "
   ::= { gs2352SystemAccountPrivilegeLevel 10 }

gs2352GVRPPrivilegeLevel OBJECT-TYPE
   SYNTAX      Integer32 (1..15)
   MAX-ACCESS  read-write
   STATUS      current
   DESCRIPTION
       "Default:15, Range : 1-15. "
   ::= { gs2352SystemAccountPrivilegeLevel 11 }

gs2352IPPrivilegeLevel OBJECT-TYPE
   SYNTAX      Integer32 (1..15)
   MAX-ACCESS  read-write
   STATUS      current
   DESCRIPTION
       "Default:15, Range : 1-15. "
   ::= { gs2352SystemAccountPrivilegeLevel 12 }

gs2352IPMCSnoopingPrivilegeLevel OBJECT-TYPE
   SYNTAX      Integer32 (1..15)
   MAX-ACCESS  read-write
   STATUS      current
   DESCRIPTION
       "Default:15, Range : 1-15. "
   ::= { gs2352SystemAccountPrivilegeLevel 13 }

gs2352LACPPrivilegeLevel OBJECT-TYPE
   SYNTAX      Integer32 (1..15)
   MAX-ACCESS  read-write
   STATUS      current
   DESCRIPTION
       "Default:15, Range : 1-15. "
   ::= { gs2352SystemAccountPrivilegeLevel 14 }

gs2352LLDPPrivilegeLevel OBJECT-TYPE
   SYNTAX      Integer32 (1..15)
   MAX-ACCESS  read-write
   STATUS      current
   DESCRIPTION
       "Default:15, Range : 1-15. "
   ::= { gs2352SystemAccountPrivilegeLevel 15 }

gs2352LLDPMEDPrivilegeLevel OBJECT-TYPE
   SYNTAX      Integer32 (1..15)
   MAX-ACCESS  read-write
   STATUS      current
   DESCRIPTION
       "Default:15, Range : 1-15. "
   ::= { gs2352SystemAccountPrivilegeLevel 16 }

gs2352LoopProtectPrivilegeLevel OBJECT-TYPE
   SYNTAX      Integer32 (1..15)
   MAX-ACCESS  read-write
   STATUS      current
   DESCRIPTION
       "Default:15, Range : 1-15. "
   ::= { gs2352SystemAccountPrivilegeLevel 17 }

gs2352MACTablePrivilegeLevel OBJECT-TYPE
   SYNTAX      Integer32 (1..15)
   MAX-ACCESS  read-write
   STATUS      current
   DESCRIPTION
       "Default:15, Range : 1-15. "
   ::= { gs2352SystemAccountPrivilegeLevel 18 }

gs2352MVRPrivilegeLevel OBJECT-TYPE
   SYNTAX      Integer32 (1..15)
   MAX-ACCESS  read-write
   STATUS      current
   DESCRIPTION
       "Default:15, Range : 1-15. "
   ::= { gs2352SystemAccountPrivilegeLevel 22 }

gs2352MaintenancePrivilegeLevel OBJECT-TYPE
   SYNTAX      Integer32 (1..15)
   MAX-ACCESS  read-write
   STATUS      current
   DESCRIPTION
       "Default:15, Range : 1-15. "
   ::= { gs2352SystemAccountPrivilegeLevel 24 }

gs2352MirroringPrivilegeLevel OBJECT-TYPE
   SYNTAX      Integer32 (1..15)
   MAX-ACCESS  read-write
   STATUS      current
   DESCRIPTION
       "Default:15, Range : 1-15. "
   ::= { gs2352SystemAccountPrivilegeLevel 25 }

gs2352PortsPrivilegeLevel OBJECT-TYPE
   SYNTAX      Integer32 (1..15)
   MAX-ACCESS  read-write
   STATUS      current
   DESCRIPTION
       "Default:15, Range : 1-15. "
   ::= { gs2352SystemAccountPrivilegeLevel 27 }

gs2352PrivateVLANsPrivilegeLevel OBJECT-TYPE
   SYNTAX      Integer32 (1..15)
   MAX-ACCESS  read-write
   STATUS      current
   DESCRIPTION
       "Default:15, Range : 1-15. "
   ::= { gs2352SystemAccountPrivilegeLevel 28 }

gs2352QoSPrivilegeLevel OBJECT-TYPE
   SYNTAX      Integer32 (1..15)
   MAX-ACCESS  read-write
   STATUS      current
   DESCRIPTION
       "Default:15, Range : 1-15. "
   ::= { gs2352SystemAccountPrivilegeLevel 29 }

gs2352SFlowPrivilegeLevel OBJECT-TYPE
   SYNTAX      Integer32 (1..15)
   MAX-ACCESS  read-write
   STATUS      current
   DESCRIPTION
       "Default:15, Range : 1-15. "
   ::= { gs2352SystemAccountPrivilegeLevel 30 }

gs2352SMTPPrivilegeLevel OBJECT-TYPE
   SYNTAX      Integer32 (1..15)
   MAX-ACCESS  read-write
   STATUS      current
   DESCRIPTION
       "Default:15, Range : 1-15. "
   ::= { gs2352SystemAccountPrivilegeLevel 31 }

gs2352SNMPPrivilegeLevel OBJECT-TYPE
   SYNTAX      Integer32 (1..15)
   MAX-ACCESS  read-write
   STATUS      current
   DESCRIPTION
       "Default:15, Range : 1-15. "
   ::= { gs2352SystemAccountPrivilegeLevel 32 }

gs2352SecurityPrivilegeLevel OBJECT-TYPE
   SYNTAX      Integer32 (1..15)
   MAX-ACCESS  read-write
   STATUS      current
   DESCRIPTION
       "Default:15, Range : 1-15. "
   ::= { gs2352SystemAccountPrivilegeLevel 33 }

gs2352SingleIPPrivilegeLevel OBJECT-TYPE
   SYNTAX      Integer32 (1..15)
   MAX-ACCESS  read-write
   STATUS      current
   DESCRIPTION
       "Default:15, Range : 1-15. "
   ::= { gs2352SystemAccountPrivilegeLevel 34 }

gs2352SpanningTreePrivilegeLevel OBJECT-TYPE
   SYNTAX      Integer32 (1..15)
   MAX-ACCESS  read-write
   STATUS      current
   DESCRIPTION
       "Default:15, Range : 1-15. "
   ::= { gs2352SystemAccountPrivilegeLevel 35 }

gs2352SystemPrivilegeLevel OBJECT-TYPE
   SYNTAX      Integer32 (1..15)
   MAX-ACCESS  read-write
   STATUS      current
   DESCRIPTION
       "Default:15, Range : 1-15. "
   ::= { gs2352SystemAccountPrivilegeLevel 36 }

gs2352TrapEventPrivilegeLevel OBJECT-TYPE
   SYNTAX      Integer32 (1..15)
   MAX-ACCESS  read-write
   STATUS      current
   DESCRIPTION
       "Default:15, Range : 1-15. "
   ::= { gs2352SystemAccountPrivilegeLevel 37 }

gs2352UPnPPrivilegeLevel OBJECT-TYPE
   SYNTAX      Integer32 (1..15)
   MAX-ACCESS  read-write
   STATUS      current
   DESCRIPTION
       "Default:15, Range : 1-15. "
   ::= { gs2352SystemAccountPrivilegeLevel 38 }

gs2352VCLPrivilegeLevel OBJECT-TYPE
   SYNTAX      Integer32 (1..15)
   MAX-ACCESS  read-write
   STATUS      current
   DESCRIPTION
       "Default:15, Range : 1-15. "
   ::= { gs2352SystemAccountPrivilegeLevel 39 }

gs2352VLANsPrivilegeLevel OBJECT-TYPE
   SYNTAX      Integer32 (1..15)
   MAX-ACCESS  read-write
   STATUS      current
   DESCRIPTION
       "Default:15, Range : 1-15. "
   ::= { gs2352SystemAccountPrivilegeLevel 41 }

gs2352VoiceVLANPrivilegeLevel OBJECT-TYPE
   SYNTAX      Integer32 (1..15)
   MAX-ACCESS  read-write
   STATUS      current
   DESCRIPTION
       "Default:15, Range : 1-15. "
   ::= { gs2352SystemAccountPrivilegeLevel 42 }


gs2352IP                                                    OBJECT IDENTIFIER ::= { gs2352System 4 }

gs2352IPv4                                                  OBJECT IDENTIFIER ::= { gs2352IP 1 }

gs2352IPv4Configured                                                  OBJECT IDENTIFIER ::= { gs2352IPv4 1 }

gs2352Ipv4DHCPClient OBJECT-TYPE
   SYNTAX      INTEGER { disable(0), enable(1) }
   MAX-ACCESS  read-write
   STATUS      current
   DESCRIPTION
       "default:0
       0: disable
       1: enable"
   ::= { gs2352IPv4Configured 1 }

gs2352IPv4Address OBJECT-TYPE
   SYNTAX      IpAddress
   MAX-ACCESS  read-write
   STATUS      current
   DESCRIPTION
       ""
   ::= { gs2352IPv4Configured 2 }

gs2352IPv4Mask OBJECT-TYPE
   SYNTAX      IpAddress
   MAX-ACCESS  read-write
   STATUS      current
   DESCRIPTION
       ""
   ::= { gs2352IPv4Configured 3 }

gs2352IPv4Gateway OBJECT-TYPE
   SYNTAX      IpAddress
   MAX-ACCESS  read-write
   STATUS      current
   DESCRIPTION
       ""
   ::= { gs2352IPv4Configured 4 }

gs2352IPv4VLANId OBJECT-TYPE
   SYNTAX      Integer32(1..4094)
   MAX-ACCESS  read-write
   STATUS      current
   DESCRIPTION
       "default:1"
   ::= { gs2352IPv4Configured 5 }

gs2352IPv4DNSServer OBJECT-TYPE
   SYNTAX      IpAddress
   MAX-ACCESS  read-write
   STATUS      current
   DESCRIPTION
       ""
   ::= { gs2352IPv4Configured 6 }

gs2352IPv4DNSProxy OBJECT-TYPE
   SYNTAX      INTEGER { disable(0), enable(1) }
   MAX-ACCESS  read-write
   STATUS      current
   DESCRIPTION
       "0:disable, 1:enable "
   ::= { gs2352IPv4Configured 7 }

gs2352IPv4Current                                                  OBJECT IDENTIFIER ::= { gs2352IPv4 2 }

gs2352Ipv4CurrentDHCPClient OBJECT-TYPE
   SYNTAX      INTEGER { none(0), renew(1) }
   MAX-ACCESS  read-write
   STATUS      current
   DESCRIPTION
       "default:0
       0: none (for read)
       1: renew"
   ::= { gs2352IPv4Current 1 }

gs2352IPv4CurrentAddress OBJECT-TYPE
   SYNTAX      IpAddress
   MAX-ACCESS  read-only
   STATUS      current
   DESCRIPTION
       ""
   ::= { gs2352IPv4Current 2 }

gs2352IPv4CurrentMask OBJECT-TYPE
   SYNTAX      IpAddress
   MAX-ACCESS  read-only
   STATUS      current
   DESCRIPTION
       ""
   ::= { gs2352IPv4Current 3 }

gs2352IPv4CurrentGateway OBJECT-TYPE
   SYNTAX      IpAddress
   MAX-ACCESS  read-only
   STATUS      current
   DESCRIPTION
       ""
   ::= { gs2352IPv4Current 4 }

gs2352IPv4CurrentVLANId OBJECT-TYPE
   SYNTAX      Integer32(1..4094)
   MAX-ACCESS  read-only
   STATUS      current
   DESCRIPTION
       "default:1"
   ::= { gs2352IPv4Current 5 }

gs2352IPv4CurrentDNSServer OBJECT-TYPE
   SYNTAX      IpAddress
   MAX-ACCESS  read-only
   STATUS      current
   DESCRIPTION
       ""
   ::= { gs2352IPv4Current 6 }


gs2352IPv6                                                  OBJECT IDENTIFIER ::= { gs2352IP 2 }

gs2352IPv6Configured                                                  OBJECT IDENTIFIER ::= { gs2352IPv6 1 }

gs2352Ipv6AutoConfiguration OBJECT-TYPE
   SYNTAX      INTEGER { disable(0), enable(1) }
   MAX-ACCESS  read-write
   STATUS      current
   DESCRIPTION
       "default:0
       0: disable
       1: enable"
   ::= { gs2352IPv6Configured 1 }

gs2352Ipv6Address OBJECT-TYPE
   SYNTAX      DisplayString (SIZE (0..30))
   MAX-ACCESS  read-write
   STATUS      current
   DESCRIPTION
       ""
   ::= { gs2352IPv6Configured 2 }

gs2352Ipv6Prefix OBJECT-TYPE
   SYNTAX      Integer32 (1..128)
   MAX-ACCESS  read-write
   STATUS      current
   DESCRIPTION
       "default: 96"
   ::= { gs2352IPv6Configured 3 }

gs2352Ipv6Gateway OBJECT-TYPE
   SYNTAX      DisplayString (SIZE (0..30))
   MAX-ACCESS  read-write
   STATUS      current
   DESCRIPTION
       " "
   ::= { gs2352IPv6Configured 4 }

gs2352IPv6Current                                                  OBJECT IDENTIFIER ::= { gs2352IPv6 2 }

gs2352Ipv6CurrentAutoConfiguration OBJECT-TYPE
   SYNTAX      INTEGER { disable(0), enable(1) }
   MAX-ACCESS  read-only
   STATUS      current
   DESCRIPTION
       "default:0
       0: disable
       1: enable"
   ::= { gs2352IPv6Current 1 }

gs2352Ipv6CurrentAddress OBJECT-TYPE
   SYNTAX      DisplayString (SIZE (0..30))
   MAX-ACCESS  read-only
   STATUS      current
   DESCRIPTION
       ""
   ::= { gs2352IPv6Current 2 }


gs2352Ipv6CurrentLinkLocalAddress OBJECT-TYPE
   SYNTAX      DisplayString(SIZE (0..30))
   MAX-ACCESS  read-only
   STATUS      current
   DESCRIPTION
       ""
   ::= { gs2352IPv6Current 3 }


gs2352Ipv6CurrentPrefix OBJECT-TYPE
   SYNTAX      DisplayString(SIZE (0..64))
   MAX-ACCESS  read-only
   STATUS      current
   DESCRIPTION
       ""
   ::= { gs2352IPv6Current 4 }

gs2352Ipv6CurrentGateway OBJECT-TYPE
   SYNTAX      DisplayString (SIZE (0..30))
   MAX-ACCESS  read-only
   STATUS      current
   DESCRIPTION
       " "
   ::= { gs2352IPv6Current 5 }

gs2352Syslog                                                OBJECT IDENTIFIER ::= { gs2352System 5 }

gs2352SyslogConf                                            OBJECT IDENTIFIER ::= { gs2352Syslog 1 }

gs2352ServerMode OBJECT-TYPE
   SYNTAX      INTEGER { disable(0), enable(1) }
   MAX-ACCESS  read-write
   STATUS      current
   DESCRIPTION
       "default: 0
       0: disable
       1: enable "
   ::= { gs2352SyslogConf 1 }

gs2352ServerAddress1 OBJECT-TYPE
   SYNTAX      IpAddress
   MAX-ACCESS  read-write
   STATUS      current
   DESCRIPTION
       " "
   ::= { gs2352SyslogConf 2 }

gs2352ServerAddress2 OBJECT-TYPE
   SYNTAX      IpAddress
   MAX-ACCESS  read-write
   STATUS      current
   DESCRIPTION
       " "
   ::= { gs2352SyslogConf 3 }

gs2352SyslogLevel OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       "default: 6 (Info)
       0: Emergency
       1: Alert
       2: Critical
       3: Error
       4: Warning
       5: Notice
       6: Info
       7: Debug"
   ::= { gs2352SyslogConf 4 }

gs2352SyslogDetailedInfo                                    OBJECT IDENTIFIER ::= { gs2352Syslog 2 }

gs2352SyslogDetailedInfoClear OBJECT-TYPE
   SYNTAX      INTEGER { none(0), clear(1) }
   MAX-ACCESS  read-write
   STATUS      current
   DESCRIPTION
      "default: 0
       0 : None  (read only)
       1 : Clear Syslog"
   ::= { gs2352SyslogDetailedInfo 1 }

gs2352SyslogDetailedInfoTable OBJECT-TYPE
  SYNTAX      SEQUENCE OF GS2352SyslogDetailedInfoEntry
  MAX-ACCESS  not-accessible
  STATUS      current
  DESCRIPTION
           " "
       ::= { gs2352SyslogDetailedInfo 2 }

gs2352SyslogDetailedInfoEntry OBJECT-TYPE
   SYNTAX      GS2352SyslogDetailedInfoEntry
   MAX-ACCESS  not-accessible
   STATUS      current
   DESCRIPTION
           ""
   INDEX    { gs2352SyslogDetailedInfoIndex  }
   ::= { gs2352SyslogDetailedInfoTable 1 }

GS2352SyslogDetailedInfoEntry ::= SEQUENCE {
   gs2352SyslogDetailedInfoIndex       Integer32,
   gs2352SyslogDetailedInfoLevel       DisplayString,
   gs2352SyslogDetailedInfoTime        DisplayString,
   gs2352SyslogDetailedInfoMessage     DisplayString
}

gs2352SyslogDetailedInfoIndex OBJECT-TYPE
   SYNTAX      Integer32(1..1024)
   MAX-ACCESS  not-accessible
   STATUS      current
   DESCRIPTION
       " "
   ::= { gs2352SyslogDetailedInfoEntry 1 }

gs2352SyslogDetailedInfoLevel OBJECT-TYPE
   SYNTAX      DisplayString
   MAX-ACCESS  read-only
   STATUS      current
   DESCRIPTION
       " "
   ::= { gs2352SyslogDetailedInfoEntry 2 }

gs2352SyslogDetailedInfoTime OBJECT-TYPE
   SYNTAX      DisplayString(SIZE (0..20))
   MAX-ACCESS  read-only
   STATUS      current
   DESCRIPTION
       " "
   ::= { gs2352SyslogDetailedInfoEntry 3 }

gs2352SyslogDetailedInfoMessage OBJECT-TYPE
   SYNTAX      DisplayString
   MAX-ACCESS  read-only
   STATUS      current
   DESCRIPTION
       " "
   ::= { gs2352SyslogDetailedInfoEntry 4 }


gs2352Snmp                                                OBJECT IDENTIFIER ::= { gs2352System 6 }

gs2352SnmpConf                                            OBJECT IDENTIFIER ::= { gs2352Snmp 1 }

gs2352GetCommunityMode OBJECT-TYPE
   SYNTAX       INTEGER { disable(0), enable(1) }
   MAX-ACCESS   read-write
   STATUS       current
   DESCRIPTION
       "Get/Set the get-community mode of the SNMP.
        default : 1, 0: disable, 1: enable. "
   ::= { gs2352SnmpConf 1 }

gs2352GetCommunity OBJECT-TYPE
   SYNTAX       DisplayString
   MAX-ACCESS   read-write
   STATUS       current
   DESCRIPTION
       "Get/Set the get-community of the SNMP."
   ::= { gs2352SnmpConf 2 }

gs2352SetCommunityMode OBJECT-TYPE
   SYNTAX       INTEGER { disable(0), enable(1) }
   MAX-ACCESS   read-write
   STATUS       current
   DESCRIPTION
       "Get/Set the set-community mode of the SNMP.
        default : 1, 0: disable, 1: enable. "
   ::= { gs2352SnmpConf 3 }

gs2352SetCommunity OBJECT-TYPE
   SYNTAX       DisplayString
   MAX-ACCESS   read-write
   STATUS       current
   DESCRIPTION
       "Get/Set the set-community of the SNMP."
   ::= { gs2352SnmpConf 4 }

gs2352GetCommunityConfTable OBJECT-TYPE
   SYNTAX      SEQUENCE OF GS2352GetCommunityConfEntry
   MAX-ACCESS  not-accessible
   STATUS      current
   DESCRIPTION
       " Show get-community of the SNMP. "
   ::= { gs2352SnmpConf 5 }

gs2352GetCommunityConfEntry OBJECT-TYPE
   SYNTAX      GS2352GetCommunityConfEntry
   MAX-ACCESS  not-accessible
   STATUS      current
   DESCRIPTION
       ""
   INDEX    { gs2352CommunityConfIndex  }
   ::= { gs2352GetCommunityConfTable 1 }

GS2352GetCommunityConfEntry ::= SEQUENCE {
   gs2352CommunityConfIndex				Integer32,
   gs2352CommunityConfGetCommunity			DisplayString
}

gs2352CommunityConfIndex OBJECT-TYPE
   SYNTAX      Integer32(1..4095)
   MAX-ACCESS  not-accessible
   STATUS      current
   DESCRIPTION
       " index, range : 1 - 5. "
   ::= { gs2352GetCommunityConfEntry 1 }

gs2352CommunityConfGetCommunity OBJECT-TYPE
   SYNTAX      DisplayString
   MAX-ACCESS  read-write
   STATUS      current
   DESCRIPTION
       " Get/Set the get-community of the SNMP."
   ::= { gs2352GetCommunityConfEntry 2 }

gs2352TrapHostConfTable OBJECT-TYPE
   SYNTAX      SEQUENCE OF GS2352TrapHostConfEntry
   MAX-ACCESS  not-accessible
   STATUS      current
   DESCRIPTION
       "A list of trap host entry. The numbers of entries are given by the value of gs2352TrapHostConfNumber."
   ::= { gs2352SnmpConf 6 }

gs2352TrapHostConfEntry OBJECT-TYPE
   SYNTAX      GS2352TrapHostConfEntry
   MAX-ACCESS  not-accessible
   STATUS      current
   DESCRIPTION
       "This is the entry information for trap host."
   INDEX    { gs2352TrapHostConfIndex  }
   ::= { gs2352TrapHostConfTable 1 }

GS2352TrapHostConfEntry ::= SEQUENCE {
    gs2352TrapHostConfIndex             Integer32,
    gs2352TrapHostConfVersion           INTEGER,
    gs2352TrapHostConfIPType            INTEGER,
    gs2352TrapHostConfIP                DisplayString,
    gs2352TrapHostConfPort              Integer32,
    gs2352TrapHostConfCommunity         DisplayString,
    gs2352TrapHostConfSeverityLevel     INTEGER,
    gs2352TrapHostConfSecurityLevel     INTEGER,
    gs2352TrapHostConfAuthPtc           INTEGER,
    gs2352TrapHostConfAuthPassword      DisplayString,
    gs2352TrapHostConfPrivPtc           INTEGER,
    gs2352TrapHostConfPrivPassword      DisplayString,
    gs2352TrapHostConfCurrentMode       INTEGER
}

gs2352TrapHostConfIndex OBJECT-TYPE
   SYNTAX      Integer32(1..6)
   MAX-ACCESS  not-accessible
   STATUS      current
   DESCRIPTION
       " The index of the trap host entry. "
   ::= { gs2352TrapHostConfEntry 1 }

gs2352TrapHostConfVersion OBJECT-TYPE
   SYNTAX       INTEGER { snmpv2c(2), snmpv3(3) }
   MAX-ACCESS   read-write
   STATUS       current
   DESCRIPTION
       "The version of the Trap PDU. Version : 2(SNMPv2c), 3(SNMPv3)"
   ::= { gs2352TrapHostConfEntry 2 }

gs2352TrapHostConfIPType OBJECT-TYPE
   SYNTAX       INTEGER { ipv4(4), ipv6(6) }
   MAX-ACCESS   read-write
   STATUS       current
   DESCRIPTION
       "Server IP Type. Default: 4,
        4 : IPv4,
        6 : IPv6."
   ::= { gs2352TrapHostConfEntry 3 }

gs2352TrapHostConfIP OBJECT-TYPE
   SYNTAX       DisplayString
   MAX-ACCESS   read-write
   STATUS       current
   DESCRIPTION
       "This is the IP of the trap host."
   ::= { gs2352TrapHostConfEntry 4 }

gs2352TrapHostConfPort OBJECT-TYPE
   SYNTAX       Integer32(1..65535)
   MAX-ACCESS   read-write
   STATUS       current
   DESCRIPTION
       "This is the receiving-port number of the trap host.
        range : 1 - 65535."
   ::= { gs2352TrapHostConfEntry 5 }

gs2352TrapHostConfCommunity OBJECT-TYPE
   SYNTAX       DisplayString (SIZE (1..32))
   MAX-ACCESS   read-write
   STATUS       current
   DESCRIPTION
       "The community/security name for the trap PDU."
   ::= { gs2352TrapHostConfEntry 6 }

gs2352TrapHostConfSeverityLevel	OBJECT-TYPE
   SYNTAX      INTEGER {
                    emergency(0),
                    alert(1),
                    critical(2),
                    error(3),
                    warning(4),
                    notice(5),
                    info(6),
                    debug(7)
                }
   MAX-ACCESS   read-write
   STATUS       current
   DESCRIPTION
       "The Severity Level.
        0 : Emerg, 1 : Alert, 2 : Critical, 3 : Error, 4 : Warning, 5 : Notice, 6 : Info, 7 : Debug."
	::= { gs2352TrapHostConfEntry 7 }

gs2352TrapHostConfSecurityLevel	OBJECT-TYPE
   SYNTAX       INTEGER { noAuthNoPriv(1), authNoPriv(2), authPriv(3) }
   MAX-ACCESS   read-write
   STATUS       current
   DESCRIPTION
       "The Security Level, NoAuthNoPriv, AuthNoPriv, and AuthPriv.
        1 : NoAuthNoPriv, 2 : AuthNoPriv, 3 : AuthPriv.
        Privacy protocol will be configured as 'DES' automatically if security level is 3(AuthPriv)."
	::= { gs2352TrapHostConfEntry 8 }

gs2352TrapHostConfAuthPtc	OBJECT-TYPE
   SYNTAX       INTEGER { md5(1), sha(2) }
   MAX-ACCESS   read-write
   STATUS       current
   DESCRIPTION
       "Authentication Protocol, there are SHA and MD5 supported presently.
        1 : MD5, 2 : SHA."
	::= { gs2352TrapHostConfEntry 9 }

gs2352TrapHostConfAuthPassword	OBJECT-TYPE
   SYNTAX      DisplayString
   MAX-ACCESS  read-write
   STATUS		current
   DESCRIPTION
       "Authentication Password, is used for authenticating. The return value is always '********'.
        If the authentication protocol is MD5, the length of password should be 8 ~ 32 characters.
        If the authentication protocol is SHA, the length of password should be 8 ~ 40 characters."
   ::= { gs2352TrapHostConfEntry 10 }

gs2352TrapHostConfPrivPtc	OBJECT-TYPE
   SYNTAX       INTEGER { des(1) }
   MAX-ACCESS   read-write
   STATUS       current
   DESCRIPTION
       "This is the Privacy Protocol, which is used in AuthPriv. Only supports DES.
        An empty string will be returned if the security level is not 3(AuthPriv).
        1 : DES."
	::= { gs2352TrapHostConfEntry 11 }

gs2352TrapHostConfPrivPassword	OBJECT-TYPE
   SYNTAX       DisplayString
   MAX-ACCESS   read-write
   STATUS       current
   DESCRIPTION
       "The password is Privacy Key.  The return value is always '********'.  This Key
        must be more than 8 characters, and less than 32 characters."
   ::= { gs2352TrapHostConfEntry 12 }

gs2352TrapHostConfCurrentMode OBJECT-TYPE
   SYNTAX       INTEGER { empty(0), active(1), edit(2), delete(3) }
   MAX-ACCESS   read-write
   STATUS       current
   DESCRIPTION
       "0:Empty, 1:Active mode, 2:Edit mode, 3:Delete."
   ::= { gs2352TrapHostConfEntry 13 }


gs2352SnmpSystem                                          OBJECT IDENTIFIER ::= { gs2352Snmp 2 }

gs2352SnmpState OBJECT-TYPE
   SYNTAX       INTEGER { disable(0), enable(1) }
   MAX-ACCESS   read-write
   STATUS       current
   DESCRIPTION
       "Get/Set the state of the SNMP.
        default : 1, 0: disable, 1: enable. "
   ::= { gs2352SnmpSystem 1 }

gs2352SnmpEngineID OBJECT-TYPE
   SYNTAX       OCTET STRING (SIZE(5..32))
   MAX-ACCESS   read-write
   STATUS       current
   DESCRIPTION
       "Get/Set the Engine ID of the SNMP.
        An SNMP engine's administratively-unique identifier."
   ::= { gs2352SnmpSystem 2 }

gs2352SnmpCommunities                                          OBJECT IDENTIFIER ::= { gs2352Snmp 3 }

gs2352SnmpCommunitiesCreate OBJECT-TYPE
   SYNTAX       INTEGER { none(0), create(1) }
   MAX-ACCESS   read-write
   STATUS       current
   DESCRIPTION
       "default: 0
        0 : None  (read only)
        1 : Create entry"
   ::= { gs2352SnmpCommunities 1 }

gs2352SnmpCommunitiesTable OBJECT-TYPE
   SYNTAX      SEQUENCE OF GS2352SnmpCommunitiesEntry
   MAX-ACCESS  not-accessible
   STATUS      current
   DESCRIPTION
       " Create SNMPv1/v2 Communities entry."
   ::= { gs2352SnmpCommunities 2 }

gs2352SnmpCommunitiesEntry OBJECT-TYPE
   SYNTAX      GS2352SnmpCommunitiesEntry
   MAX-ACCESS  not-accessible
   STATUS      current
   DESCRIPTION
       ""
   INDEX    { gs2352SnmpCommunitiesIndex  }
   ::= { gs2352SnmpCommunitiesTable 1 }

GS2352SnmpCommunitiesEntry ::= SEQUENCE {
   gs2352SnmpCommunitiesIndex          Integer32,
   gs2352SnmpCommunitiesCommunity      DisplayString,
   gs2352SnmpCommunitiesUserName       DisplayString,
   gs2352SnmpCommunitiesSourceIP       IpAddress,
   gs2352SnmpCommunitiesSourceMask     IpAddress,
   gs2352SnmpCommunitiesRowStatus      INTEGER
}

gs2352SnmpCommunitiesIndex OBJECT-TYPE
   SYNTAX      Integer32(1..4)
   MAX-ACCESS  not-accessible
   STATUS      current
   DESCRIPTION
       " "
   ::= { gs2352SnmpCommunitiesEntry 1 }

gs2352SnmpCommunitiesCommunity OBJECT-TYPE
   SYNTAX      DisplayString (SIZE (1..32))
   MAX-ACCESS  read-write
   STATUS      current
   DESCRIPTION
       "Up to 32 characters describing Community."
   ::= { gs2352SnmpCommunitiesEntry 2 }

gs2352SnmpCommunitiesUserName OBJECT-TYPE
   SYNTAX      DisplayString (SIZE (1..32))
   MAX-ACCESS  read-write
   STATUS      current
   DESCRIPTION
       " Up to 32 characters describing User Name. "
   ::= { gs2352SnmpCommunitiesEntry 3 }

gs2352SnmpCommunitiesSourceIP OBJECT-TYPE
   SYNTAX      IpAddress
   MAX-ACCESS  read-write
   STATUS      current
   DESCRIPTION
       " SNMP access source ip. "
   ::= { gs2352SnmpCommunitiesEntry 4 }

gs2352SnmpCommunitiesSourceMask OBJECT-TYPE
   SYNTAX      IpAddress
   MAX-ACCESS  read-write
   STATUS      current
   DESCRIPTION
       " SNMP access source address mask. "
   ::= { gs2352SnmpCommunitiesEntry 5 }

gs2352SnmpCommunitiesRowStatus OBJECT-TYPE
   SYNTAX      INTEGER { active(1), notInservice(2), destroy(4), undo(5) }
   MAX-ACCESS  read-write
   STATUS      current
   DESCRIPTION
       "1: active
        2: notInservice
        4: destroy
        5: undo"
   ::= { gs2352SnmpCommunitiesEntry 6 }


gs2352SnmpUsers                                          OBJECT IDENTIFIER ::= { gs2352Snmp 4 }

gs2352SnmpUsersCreate OBJECT-TYPE
   SYNTAX       INTEGER { none(0), create(1) }
   MAX-ACCESS   read-write
   STATUS       current
   DESCRIPTION
       "default: 0
        0 : None  (read only)
        1 : Create entry"
   ::= { gs2352SnmpUsers 1 }

gs2352SnmpUsersTable OBJECT-TYPE
   SYNTAX      SEQUENCE OF GS2352SnmpUsersEntry
   MAX-ACCESS  not-accessible
   STATUS      current
   DESCRIPTION
       " Create SNMPv3 users entry."
   ::= { gs2352SnmpUsers 2 }

gs2352SnmpUsersEntry OBJECT-TYPE
   SYNTAX      GS2352SnmpUsersEntry
   MAX-ACCESS  not-accessible
   STATUS      current
   DESCRIPTION
       ""
   INDEX    { gs2352SnmpUsersIndex  }
   ::= { gs2352SnmpUsersTable 1 }

GS2352SnmpUsersEntry ::= SEQUENCE {
   gs2352SnmpUsersIndex                    Integer32,
   gs2352SnmpUsersUserName                 DisplayString,
   gs2352SnmpUsersSecurityLevel            INTEGER,
   gs2352SnmpUsersAuthenticationProtocol   INTEGER,
   gs2352SnmpUsersAuthenticationPassword   DisplayString,
   gs2352SnmpUsersPrivacyProtocol          INTEGER,
   gs2352SnmpUsersPrivacyPassword          DisplayString,
   gs2352SnmpUsersRowStatus                INTEGER
}

gs2352SnmpUsersIndex OBJECT-TYPE
   SYNTAX      Integer32(1..10)
   MAX-ACCESS  not-accessible
   STATUS      current
   DESCRIPTION
       " "
   ::= { gs2352SnmpUsersEntry 1 }

gs2352SnmpUsersUserName OBJECT-TYPE
   SYNTAX      DisplayString (SIZE (1..32))
   MAX-ACCESS  read-write
   STATUS      current
   DESCRIPTION
       "Up to 32 characters describing User Name."
   ::= { gs2352SnmpUsersEntry 2 }

gs2352SnmpUsersSecurityLevel OBJECT-TYPE
   SYNTAX      INTEGER { noauthnopriv(1), authnopriv(2), authpriv(3) }
   MAX-ACCESS  read-write
   STATUS      current
   DESCRIPTION
       " 1: No authentication and no privacy.
         2: Authentication and no privacy.
         3: Authentication and privacy. "
   ::= { gs2352SnmpUsersEntry 3 }

gs2352SnmpUsersAuthenticationProtocol OBJECT-TYPE
   SYNTAX      INTEGER { none(0), md5(1), sha(2) }
   MAX-ACCESS  read-write
   STATUS      current
   DESCRIPTION
       " 0: None.
         1: MD5.
         2: SHA "
   ::= { gs2352SnmpUsersEntry 4 }

gs2352SnmpUsersAuthenticationPassword OBJECT-TYPE
   SYNTAX      DisplayString
   MAX-ACCESS  read-write
   STATUS      current
   DESCRIPTION
       " Authentication Password, is used for authenticating. The return value is always '********'.
         If the authentication protocol is MD5, the length of password should be 8 ~ 32 characters.
         If the authentication protocol is SHA, the length of password should be 8 ~ 40 characters. "
   ::= { gs2352SnmpUsersEntry 5 }

gs2352SnmpUsersPrivacyProtocol OBJECT-TYPE
   SYNTAX      INTEGER { none(0), des(1), aes(2) }
   MAX-ACCESS  read-write
   STATUS      current
   DESCRIPTION
       " 0: None.
         1: DES.
         2: AES
         This is the Privacy Protocol, which is used in AuthPriv.
         An empty string will be returned if the security level is not 3(AuthPriv) "
   ::= { gs2352SnmpUsersEntry 6 }

gs2352SnmpUsersPrivacyPassword OBJECT-TYPE
   SYNTAX      DisplayString
   MAX-ACCESS  read-write
   STATUS      current
   DESCRIPTION
       " The password is Privacy Key.  The return value is always '********'.  This Key
        must be more than 8 characters, and less than 32 characters. "
   ::= { gs2352SnmpUsersEntry 7 }

gs2352SnmpUsersRowStatus OBJECT-TYPE
   SYNTAX      INTEGER { active(1), notInservice(2), destroy(4), undo(5) }
   MAX-ACCESS  read-write
   STATUS      current
   DESCRIPTION
       "1: active
        2: notInservice
        4: destroy
        5: undo"
   ::= { gs2352SnmpUsersEntry 8 }


gs2352SnmpGroups                                          OBJECT IDENTIFIER ::= { gs2352Snmp 5 }

gs2352SnmpGroupsCreate OBJECT-TYPE
   SYNTAX       INTEGER { none(0), create(1) }
   MAX-ACCESS   read-write
   STATUS       current
   DESCRIPTION
       "default: 0
        0 : None  (read only)
        1 : Create entry"
   ::= { gs2352SnmpGroups 1 }

gs2352SnmpGroupsTable OBJECT-TYPE
   SYNTAX      SEQUENCE OF GS2352SnmpGroupsEntry
   MAX-ACCESS  not-accessible
   STATUS      current
   DESCRIPTION
       " Create SNMPv3 groups entry."
   ::= { gs2352SnmpGroups 2 }

gs2352SnmpGroupsEntry OBJECT-TYPE
   SYNTAX      GS2352SnmpGroupsEntry
   MAX-ACCESS  not-accessible
   STATUS      current
   DESCRIPTION
       ""
   INDEX    { gs2352SnmpGroupsIndex  }
   ::= { gs2352SnmpGroupsTable 1 }

GS2352SnmpGroupsEntry ::= SEQUENCE {
   gs2352SnmpGroupsIndex           Integer32,
   gs2352SnmpGroupsSecurityModel   INTEGER,
   gs2352SnmpGroupsSecurityName    DisplayString,
   gs2352SnmpGroupsGroupName       DisplayString,
   gs2352SnmpGroupsRowStatus       INTEGER
}

gs2352SnmpGroupsIndex OBJECT-TYPE
   SYNTAX      Integer32(1..14)
   MAX-ACCESS  not-accessible
   STATUS      current
   DESCRIPTION
       " "
   ::= { gs2352SnmpGroupsEntry 1 }

gs2352SnmpGroupsSecurityModel OBJECT-TYPE
   SYNTAX      INTEGER { v1(1), v2c(2), usm(3) }
   MAX-ACCESS  read-write
   STATUS      current
   DESCRIPTION
       " 1: v1.
         2: v2c.
         3: usm."
   ::= { gs2352SnmpGroupsEntry 2 }

gs2352SnmpGroupsSecurityName OBJECT-TYPE
   SYNTAX      DisplayString (SIZE (1..32))
   MAX-ACCESS  read-write
   STATUS      current
   DESCRIPTION
       "Up to 32 characters describing User Name."
   ::= { gs2352SnmpGroupsEntry 3 }

gs2352SnmpGroupsGroupName OBJECT-TYPE
   SYNTAX      DisplayString (SIZE (1..32))
   MAX-ACCESS  read-write
   STATUS      current
   DESCRIPTION
       "Up to 32 characters describing Group Name."
   ::= { gs2352SnmpGroupsEntry 4 }

gs2352SnmpGroupsRowStatus OBJECT-TYPE
   SYNTAX      INTEGER { active(1), notInservice(2), destroy(4), undo(5) }
   MAX-ACCESS  read-write
   STATUS      current
   DESCRIPTION
       "1: active
        2: notInservice
        4: destroy
        5: undo"
   ::= { gs2352SnmpGroupsEntry 5 }

gs2352SnmpViews                                              OBJECT IDENTIFIER ::= { gs2352Snmp 6 }

gs2352SnmpViewsCreate OBJECT-TYPE
   SYNTAX       INTEGER { none(0), create(1) }
   MAX-ACCESS   read-write
   STATUS       current
   DESCRIPTION
       "default: 0
        0 : None  (read only)
        1 : Create entry"
   ::= { gs2352SnmpViews 1 }

gs2352SnmpViewsTable OBJECT-TYPE
   SYNTAX      SEQUENCE OF GS2352SnmpViewsEntry
   MAX-ACCESS  not-accessible
   STATUS      current
   DESCRIPTION
       " Create SNMPv1/v2 Views entry."
   ::= { gs2352SnmpViews 2 }

gs2352SnmpViewsEntry OBJECT-TYPE
   SYNTAX      GS2352SnmpViewsEntry
   MAX-ACCESS  not-accessible
   STATUS      current
   DESCRIPTION
       ""
   INDEX    { gs2352SnmpViewsIndex  }
   ::= { gs2352SnmpViewsTable 1 }

GS2352SnmpViewsEntry ::= SEQUENCE {
   gs2352SnmpViewsIndex        Integer32,
   gs2352SnmpViewsName         DisplayString,
   gs2352SnmpViewsType         INTEGER,
   gs2352SnmpViewsOIDSubtree   DisplayString,
   gs2352SnmpViewsRowStatus    INTEGER
}

gs2352SnmpViewsIndex OBJECT-TYPE
   SYNTAX      Integer32(1..4)
   MAX-ACCESS  not-accessible
   STATUS      current
   DESCRIPTION
       " "
   ::= { gs2352SnmpViewsEntry 1 }

gs2352SnmpViewsName OBJECT-TYPE
   SYNTAX      DisplayString (SIZE (1..32))
   MAX-ACCESS  read-write
   STATUS      current
   DESCRIPTION
       "Up to 32 characters describing view Name."
   ::= { gs2352SnmpViewsEntry 2 }

gs2352SnmpViewsType OBJECT-TYPE
   SYNTAX      INTEGER { included(1), excluded(2) }
   MAX-ACCESS  read-write
   STATUS      current
   DESCRIPTION
       "1: included, An optional flag to indicate that this view subtree should be included.
	   2: excluded, An optional flag to indicate that this view subtree should be excluded."
   ::= { gs2352SnmpViewsEntry 3 }

gs2352SnmpViewsOIDSubtree OBJECT-TYPE
   SYNTAX      DisplayString (SIZE (1..128))
   MAX-ACCESS  read-write
   STATUS      current
   DESCRIPTION
       "The OID defining the root of the subtree to add to the named view."
   ::= { gs2352SnmpViewsEntry 4 }

gs2352SnmpViewsRowStatus OBJECT-TYPE
   SYNTAX      INTEGER { active(1), notInservice(2), destroy(4), undo(5) }
   MAX-ACCESS  read-write
   STATUS      current
   DESCRIPTION
       "1: active
        2: notInservice
        4: destroy
        5: undo"
   ::= { gs2352SnmpViewsEntry 5 }


gs2352SnmpAccess                                          OBJECT IDENTIFIER ::= { gs2352Snmp 7 }

gs2352SnmpAccessCreate OBJECT-TYPE
   SYNTAX       INTEGER { none(0), create(1) }
   MAX-ACCESS   read-write
   STATUS       current
   DESCRIPTION
       "default: 0
        0 : None  (read only)
        1 : Create entry"
   ::= { gs2352SnmpAccess 1 }

gs2352SnmpAccessTable OBJECT-TYPE
   SYNTAX      SEQUENCE OF GS2352SnmpAccessEntry
   MAX-ACCESS  not-accessible
   STATUS      current
   DESCRIPTION
       " Create SNMPv3 Access entry."
   ::= { gs2352SnmpAccess 2 }

gs2352SnmpAccessEntry OBJECT-TYPE
   SYNTAX      GS2352SnmpAccessEntry
   MAX-ACCESS  not-accessible
   STATUS      current
   DESCRIPTION
       ""
   INDEX    { gs2352SnmpAccessIndex  }
   ::= { gs2352SnmpAccessTable 1 }

GS2352SnmpAccessEntry ::= SEQUENCE {
   gs2352SnmpAccessIndex             Integer32,
   gs2352SnmpAccessGroupName         DisplayString,
   gs2352SnmpAccessSecurityModel     INTEGER,
   gs2352SnmpAccessSecurityLevel     INTEGER,
   gs2352SnmpAccessReadViewName      DisplayString,
   gs2352SnmpAccessWriteViewName     DisplayString,
   gs2352SnmpAccessRowStatus         INTEGER
}

gs2352SnmpAccessIndex OBJECT-TYPE
   SYNTAX      Integer32(1..14)
   MAX-ACCESS  not-accessible
   STATUS      current
   DESCRIPTION
       " "
   ::= { gs2352SnmpAccessEntry 1 }

gs2352SnmpAccessGroupName OBJECT-TYPE
   SYNTAX      DisplayString (SIZE (1..32))
   MAX-ACCESS  read-write
   STATUS      current
   DESCRIPTION
       "Up to 32 characters describing Group Name."
   ::= { gs2352SnmpAccessEntry 2 }

gs2352SnmpAccessSecurityModel OBJECT-TYPE
   SYNTAX      INTEGER { any(0), v1(1), v2c(2), usm(3) }
   MAX-ACCESS  read-write
   STATUS      current
   DESCRIPTION
       " 0: any.
         1: v1.
         2: v2c.
         3: usm."
   ::= { gs2352SnmpAccessEntry 3 }

gs2352SnmpAccessSecurityLevel OBJECT-TYPE
   SYNTAX      INTEGER { noauthnopriv(1), authnopriv(2), authpriv(3) }
   MAX-ACCESS  read-write
   STATUS      current
   DESCRIPTION
       " 1: No authentication and no privacy.
         2: Authentication and no privacy.
         3: Authentication and privacy. "
   ::= { gs2352SnmpAccessEntry 4 }

gs2352SnmpAccessReadViewName OBJECT-TYPE
   SYNTAX      DisplayString (SIZE (1..32))
   MAX-ACCESS  read-write
   STATUS      current
   DESCRIPTION
       "Up to 32 characters describing Read View Name.
        None is reserved for Empty."
   ::= { gs2352SnmpAccessEntry 5 }

gs2352SnmpAccessWriteViewName OBJECT-TYPE
   SYNTAX      DisplayString (SIZE (1..32))
   MAX-ACCESS  read-write
   STATUS      current
   DESCRIPTION
       "Up to 32 characters describing Write View Name.
        None is reserved for Empty."
   ::= { gs2352SnmpAccessEntry 6 }

gs2352SnmpAccessRowStatus OBJECT-TYPE
   SYNTAX      INTEGER { active(1), notInservice(2), destroy(4), undo(5) }
   MAX-ACCESS  read-write
   STATUS      current
   DESCRIPTION
       "1: active
        2: notInservice
        4: destroy
        5: undo"
   ::= { gs2352SnmpAccessEntry 7 }

----------------------------------------------------------------------------------------------------

gs2352Configuration                                         OBJECT IDENTIFIER ::= { lancomGS2352 2 }

gs2352Port                                                  OBJECT IDENTIFIER ::= { gs2352Configuration 1 }

gs2352PortConfigurationTable OBJECT-TYPE
   SYNTAX      SEQUENCE OF GS2352PortConfigurationEntry
   MAX-ACCESS  not-accessible
   STATUS      current
   DESCRIPTION
       " Show port configurations. "
   ::= { gs2352Port 1 }

gs2352PortConfigurationEntry OBJECT-TYPE
   SYNTAX      GS2352PortConfigurationEntry
   MAX-ACCESS  not-accessible
   STATUS      current
   DESCRIPTION
       ""
   INDEX    { gs2352PortConfPort  }
   ::= { gs2352PortConfigurationTable 1 }

GS2352PortConfigurationEntry ::= SEQUENCE {
   gs2352PortConfPort                     Integer32,
   gs2352PortConfPortMedia                DisplayString,
   gs2352PortConfLink                     DisplayString,
   gs2352PortConfCurrentSpeed             DisplayString,
   gs2352PortConfSpeed                    INTEGER,
   gs2352PortConfCurrentFlowControlRx     INTEGER,
   gs2352PortConfCurrentFlowControlTx     INTEGER,
   gs2352PortConfFlowControl              INTEGER,
   gs2352PortConfMaxFrameSize             Integer32,
   gs2352PortConfExcessiveCollisionMode   INTEGER,
   gs2352PortConfPowerControl             INTEGER,
   gs2352PortConfDescription              DisplayString
}

gs2352PortConfPort OBJECT-TYPE
   SYNTAX      Integer32(1..4095)
   MAX-ACCESS  not-accessible
   STATUS      current
   DESCRIPTION
       " port, range : 1 - port number. "
   ::= { gs2352PortConfigurationEntry 1 }

gs2352PortConfPortMedia OBJECT-TYPE
   SYNTAX      DisplayString(SIZE (1..4))
   MAX-ACCESS  read-only
   STATUS      current
   DESCRIPTION
       " Show port media. "
   ::= { gs2352PortConfigurationEntry 2 }

gs2352PortConfLink OBJECT-TYPE
   SYNTAX      DisplayString(SIZE (2..4))
   MAX-ACCESS  read-only
   STATUS      current
   DESCRIPTION
       " The current link state. "
   ::= { gs2352PortConfigurationEntry 3 }

gs2352PortConfCurrentSpeed OBJECT-TYPE
   SYNTAX      DisplayString(SIZE (6..12))
   MAX-ACCESS  read-only
   STATUS      current
   DESCRIPTION
       " The current link speed of the port. "
   ::= { gs2352PortConfigurationEntry 4 }

gs2352PortConfSpeed OBJECT-TYPE
   SYNTAX      INTEGER {
                    disable(0),
                    auto(1),
                    speed10Half(2),
                    speed10Full(3),
                    speed100Half(4),
                    speed100Full(5),
                    speed1Gfull(6),
                    sfpAutoAMS(7),
                    speed100FXAMS(8),
                    speed1000XAMS(9),
                    speed100FX(10),
                    speed1000X(11),
                    speed10GFull(12)
                }
   MAX-ACCESS  read-write
   STATUS      current
   DESCRIPTION
       "default: 1,
        0: disable state,
        1: auto,
        2: 10 Half,
        3: 10 Full,
        4: 100 Half,
        5: 100 Full,
        6: 1G full,
        only 'Dual Media' port have 7-11 option.
        Dual Media port default: 7,
        7: SFP_Auto_AMS,
        8: 100FX_AMS,
        9: 1000X_AMS,
        10: 100FX,
        11: 1000X,
        12: 10G Full. "
   ::= { gs2352PortConfigurationEntry 5 }

gs2352PortConfCurrentFlowControlRx OBJECT-TYPE
   SYNTAX      INTEGER { disable(0), enable(1), noSupport(2) }
   MAX-ACCESS  read-only
   STATUS      current
   DESCRIPTION
       "0: disable
        1: enable
        2: no support.  "
   ::= { gs2352PortConfigurationEntry 6 }

gs2352PortConfCurrentFlowControlTx OBJECT-TYPE
   SYNTAX      INTEGER { disable(0), enable(1), noSupport(2) }
   MAX-ACCESS  read-only
   STATUS      current
   DESCRIPTION
       "0: disable
        1: enable
        2: no support.  "
   ::= { gs2352PortConfigurationEntry 7 }

gs2352PortConfFlowControl OBJECT-TYPE
   SYNTAX      INTEGER { disable(0), enable(1), noSupport(2) }
   MAX-ACCESS  read-write
   STATUS      current
   DESCRIPTION
       "default: 0,
        0: disable
        1: enable
        2: no support. "
   ::= { gs2352PortConfigurationEntry 8 }

gs2352PortConfMaxFrameSize OBJECT-TYPE
   SYNTAX      Integer32 (1518..9600)
   MAX-ACCESS  read-write
   STATUS      current
   DESCRIPTION
       "default: 9600 , range : 1518 - 9600 "
   ::= { gs2352PortConfigurationEntry 9 }

gs2352PortConfExcessiveCollisionMode OBJECT-TYPE
   SYNTAX      INTEGER { discard(0), restart(1), noSupport(2) }
   MAX-ACCESS  read-write
   STATUS      current
   DESCRIPTION
       "default: 0,
        Excessive Collision Mode :
        0: Discard,
        1: Restart,
        2: no support.
       "
   ::= { gs2352PortConfigurationEntry 10 }

gs2352PortConfPowerControl OBJECT-TYPE
   SYNTAX      INTEGER { disable(0), actiphy(1), dynamic(2), enable(3), noSupport(4) }
   MAX-ACCESS  read-write
   STATUS      current
   DESCRIPTION
       "default: 0,
        PowerControl :
        0: disable,
        1: Actiphy,
        2: Dynamic (perfectReach),
        3: Enable,
        4: no support.
       "
   ::= { gs2352PortConfigurationEntry 11 }

gs2352PortConfDescription OBJECT-TYPE
   SYNTAX      DisplayString
   MAX-ACCESS  read-write
   STATUS      current
   DESCRIPTION
       " Interface specific description.
         Up to 47 characters describing this interface. "
   ::= { gs2352PortConfigurationEntry 12 }


gs2352PortTrafficStatisticsTable OBJECT-TYPE
   SYNTAX      SEQUENCE OF GS2352PortTrafficStatisticsEntry
   MAX-ACCESS  not-accessible
   STATUS      current
   DESCRIPTION
       " "
   ::= { gs2352Port 2 }

gs2352PortTrafficStatisticsEntry OBJECT-TYPE
   SYNTAX      GS2352PortTrafficStatisticsEntry
   MAX-ACCESS  not-accessible
   STATUS      current
   DESCRIPTION
       ""
   INDEX    { gs2352PortTrafficStatisticsPort  }
   ::= { gs2352PortTrafficStatisticsTable 1 }

GS2352PortTrafficStatisticsEntry ::= SEQUENCE {
   gs2352PortTrafficStatisticsPort          Integer32,
   gs2352PortTrafficStatisticsClear         INTEGER,
   gs2352PortTrafficRxPackets               Counter64,
   gs2352PortTrafficRxOctets                Counter64,
   gs2352PortTrafficRxUnicast               Counter64,
   gs2352PortTrafficRxMulticast             Counter64,
   gs2352PortTrafficRxBroadcast             Counter64,
   gs2352PortTrafficRxPause                 Counter64,
   gs2352PortTrafficRx64Bytes               Counter64,
   gs2352PortTrafficRx65to127Bytes          Counter64,
   gs2352PortTrafficRx128to255Bytes         Counter64,
   gs2352PortTrafficRx256to511Bytes         Counter64,
   gs2352PortTrafficRx512to1023Bytes        Counter64,
   gs2352PortTrafficRx1024to1526Bytes       Counter64,
   gs2352PortTrafficRxExceecd1527Bytes      Counter64,
   gs2352PortTrafficRxQ0                    Counter64,
   gs2352PortTrafficRxQ1                    Counter64,
   gs2352PortTrafficRxQ2                    Counter64,
   gs2352PortTrafficRxQ3                    Counter64,
   gs2352PortTrafficRxQ4                    Counter64,
   gs2352PortTrafficRxQ5                    Counter64,
   gs2352PortTrafficRxQ6                    Counter64,
   gs2352PortTrafficRxQ7                    Counter64,
   gs2352PortTrafficRxDrops                 Counter64,
   gs2352PortTrafficRxCRCorAlignment        Counter64,
   gs2352PortTrafficRxUndersize             Counter64,
   gs2352PortTrafficRxOversize              Counter64,
   gs2352PortTrafficRxFragments             Counter64,
   gs2352PortTrafficRxJabber                Counter64,
   gs2352PortTrafficRxFiltered              Counter64,
   gs2352PortTrafficTxPackets               Counter64,
   gs2352PortTrafficTxOctets                Counter64,
   gs2352PortTrafficTxUnicast               Counter64,
   gs2352PortTrafficTxMulticast             Counter64,
   gs2352PortTrafficTxBroadcast             Counter64,
   gs2352PortTrafficTxPause                 Counter64,
   gs2352PortTrafficTx64Bytes               Counter64,
   gs2352PortTrafficTx65to127Bytes          Counter64,
   gs2352PortTrafficTx128to255Bytes         Counter64,
   gs2352PortTrafficTx256to511Bytes         Counter64,
   gs2352PortTrafficTx512to1023Bytes        Counter64,
   gs2352PortTrafficTx1024to1526Bytes       Counter64,
   gs2352PortTrafficTxExceecd1527Bytes      Counter64,
   gs2352PortTrafficTxQ0                    Counter64,
   gs2352PortTrafficTxQ1                    Counter64,
   gs2352PortTrafficTxQ2                    Counter64,
   gs2352PortTrafficTxQ3                    Counter64,
   gs2352PortTrafficTxQ4                    Counter64,
   gs2352PortTrafficTxQ5                    Counter64,
   gs2352PortTrafficTxQ6                    Counter64,
   gs2352PortTrafficTxQ7                    Counter64,
   gs2352PortTrafficTxDrops                 Counter64,
   gs2352PortTrafficTxLateOrExcColl         Counter64
}

gs2352PortTrafficStatisticsPort OBJECT-TYPE
   SYNTAX      Integer32 (1..4095)
   MAX-ACCESS  not-accessible
   STATUS      current
   DESCRIPTION
       " "
   ::= { gs2352PortTrafficStatisticsEntry 1 }

gs2352PortTrafficStatisticsClear OBJECT-TYPE
   SYNTAX      INTEGER { disable(0), enable(1) }
   MAX-ACCESS  read-write
   STATUS      current
   DESCRIPTION
       " "
   ::= { gs2352PortTrafficStatisticsEntry 2 }

gs2352PortTrafficRxPackets OBJECT-TYPE
   SYNTAX      Counter64
   MAX-ACCESS  read-only
   STATUS      current
   DESCRIPTION
       " "
   ::= { gs2352PortTrafficStatisticsEntry 3 }

gs2352PortTrafficRxOctets OBJECT-TYPE
   SYNTAX      Counter64
   MAX-ACCESS  read-only
   STATUS      current
   DESCRIPTION
       " "
   ::= { gs2352PortTrafficStatisticsEntry 4 }

gs2352PortTrafficRxUnicast OBJECT-TYPE
   SYNTAX      Counter64
   MAX-ACCESS  read-only
   STATUS      current
   DESCRIPTION
       " "
   ::= { gs2352PortTrafficStatisticsEntry 5 }

gs2352PortTrafficRxMulticast OBJECT-TYPE
   SYNTAX      Counter64
   MAX-ACCESS  read-only
   STATUS      current
   DESCRIPTION
       " "
   ::= { gs2352PortTrafficStatisticsEntry 6 }

gs2352PortTrafficRxBroadcast OBJECT-TYPE
   SYNTAX      Counter64
   MAX-ACCESS  read-only
   STATUS      current
   DESCRIPTION
       " "
   ::= { gs2352PortTrafficStatisticsEntry 7 }

gs2352PortTrafficRxPause OBJECT-TYPE
   SYNTAX      Counter64
   MAX-ACCESS  read-only
   STATUS      current
   DESCRIPTION
       " "
   ::= { gs2352PortTrafficStatisticsEntry 8 }

gs2352PortTrafficRx64Bytes OBJECT-TYPE
   SYNTAX      Counter64
   MAX-ACCESS  read-only
   STATUS      current
   DESCRIPTION
       " "
   ::= { gs2352PortTrafficStatisticsEntry 9 }

gs2352PortTrafficRx65to127Bytes OBJECT-TYPE
   SYNTAX      Counter64
   MAX-ACCESS  read-only
   STATUS      current
   DESCRIPTION
       " "
   ::= { gs2352PortTrafficStatisticsEntry 10 }

gs2352PortTrafficRx128to255Bytes OBJECT-TYPE
   SYNTAX      Counter64
   MAX-ACCESS  read-only
   STATUS      current
   DESCRIPTION
       " "
   ::= { gs2352PortTrafficStatisticsEntry 11 }

gs2352PortTrafficRx256to511Bytes OBJECT-TYPE
   SYNTAX      Counter64
   MAX-ACCESS  read-only
   STATUS      current
   DESCRIPTION
       " "
   ::= { gs2352PortTrafficStatisticsEntry 12 }

gs2352PortTrafficRx512to1023Bytes OBJECT-TYPE
   SYNTAX      Counter64
   MAX-ACCESS  read-only
   STATUS      current
   DESCRIPTION
       " "
   ::= { gs2352PortTrafficStatisticsEntry 13 }

gs2352PortTrafficRx1024to1526Bytes OBJECT-TYPE
   SYNTAX      Counter64
   MAX-ACCESS  read-only
   STATUS      current
   DESCRIPTION
       " "
   ::= { gs2352PortTrafficStatisticsEntry 14 }

gs2352PortTrafficRxExceecd1527Bytes OBJECT-TYPE
   SYNTAX      Counter64
   MAX-ACCESS  read-only
   STATUS      current
   DESCRIPTION
       " "
   ::= { gs2352PortTrafficStatisticsEntry 15 }

gs2352PortTrafficRxQ0 OBJECT-TYPE
   SYNTAX      Counter64
   MAX-ACCESS  read-only
   STATUS      current
   DESCRIPTION
       " "
   ::= { gs2352PortTrafficStatisticsEntry 16 }

gs2352PortTrafficRxQ1 OBJECT-TYPE
   SYNTAX      Counter64
   MAX-ACCESS  read-only
   STATUS      current
   DESCRIPTION
       " "
   ::= { gs2352PortTrafficStatisticsEntry 17 }

gs2352PortTrafficRxQ2 OBJECT-TYPE
   SYNTAX      Counter64
   MAX-ACCESS  read-only
   STATUS      current
   DESCRIPTION
       " "
   ::= { gs2352PortTrafficStatisticsEntry 18 }

gs2352PortTrafficRxQ3 OBJECT-TYPE
   SYNTAX      Counter64
   MAX-ACCESS  read-only
   STATUS      current
   DESCRIPTION
       " "
   ::= { gs2352PortTrafficStatisticsEntry 19 }

gs2352PortTrafficRxQ4 OBJECT-TYPE
   SYNTAX      Counter64
   MAX-ACCESS  read-only
   STATUS      current
   DESCRIPTION
       " "
   ::= { gs2352PortTrafficStatisticsEntry 20 }

gs2352PortTrafficRxQ5 OBJECT-TYPE
   SYNTAX      Counter64
   MAX-ACCESS  read-only
   STATUS      current
   DESCRIPTION
       " "
   ::= { gs2352PortTrafficStatisticsEntry 21 }

gs2352PortTrafficRxQ6 OBJECT-TYPE
   SYNTAX      Counter64
   MAX-ACCESS  read-only
   STATUS      current
   DESCRIPTION
       " "
   ::= { gs2352PortTrafficStatisticsEntry 22 }

gs2352PortTrafficRxQ7 OBJECT-TYPE
   SYNTAX      Counter64
   MAX-ACCESS  read-only
   STATUS      current
   DESCRIPTION
       " "
   ::= { gs2352PortTrafficStatisticsEntry 23 }

gs2352PortTrafficRxDrops OBJECT-TYPE
   SYNTAX      Counter64
   MAX-ACCESS  read-only
   STATUS      current
   DESCRIPTION
       " "
   ::= { gs2352PortTrafficStatisticsEntry 24 }

gs2352PortTrafficRxCRCorAlignment OBJECT-TYPE
   SYNTAX      Counter64
   MAX-ACCESS  read-only
   STATUS      current
   DESCRIPTION
       " "
   ::= { gs2352PortTrafficStatisticsEntry 25 }

gs2352PortTrafficRxUndersize OBJECT-TYPE
   SYNTAX      Counter64
   MAX-ACCESS  read-only
   STATUS      current
   DESCRIPTION
       " "
   ::= { gs2352PortTrafficStatisticsEntry 26 }

gs2352PortTrafficRxOversize OBJECT-TYPE
   SYNTAX      Counter64
   MAX-ACCESS  read-only
   STATUS      current
   DESCRIPTION
       " "
   ::= { gs2352PortTrafficStatisticsEntry 27 }

gs2352PortTrafficRxFragments OBJECT-TYPE
   SYNTAX      Counter64
   MAX-ACCESS  read-only
   STATUS      current
   DESCRIPTION
       " "
   ::= { gs2352PortTrafficStatisticsEntry 28 }

gs2352PortTrafficRxJabber OBJECT-TYPE
   SYNTAX      Counter64
   MAX-ACCESS  read-only
   STATUS      current
   DESCRIPTION
       " "
   ::= { gs2352PortTrafficStatisticsEntry 29 }

gs2352PortTrafficRxFiltered OBJECT-TYPE
   SYNTAX      Counter64
   MAX-ACCESS  read-only
   STATUS      current
   DESCRIPTION
       " "
   ::= { gs2352PortTrafficStatisticsEntry 30 }

gs2352PortTrafficTxPackets OBJECT-TYPE
   SYNTAX      Counter64
   MAX-ACCESS  read-only
   STATUS      current
   DESCRIPTION
       " "
   ::= { gs2352PortTrafficStatisticsEntry 31 }

gs2352PortTrafficTxOctets OBJECT-TYPE
   SYNTAX      Counter64
   MAX-ACCESS  read-only
   STATUS      current
   DESCRIPTION
       " "
   ::= { gs2352PortTrafficStatisticsEntry 32 }

gs2352PortTrafficTxUnicast OBJECT-TYPE
   SYNTAX      Counter64
   MAX-ACCESS  read-only
   STATUS      current
   DESCRIPTION
       " "
   ::= { gs2352PortTrafficStatisticsEntry 33 }

gs2352PortTrafficTxMulticast OBJECT-TYPE
   SYNTAX      Counter64
   MAX-ACCESS  read-only
   STATUS      current
   DESCRIPTION
       " "
   ::= { gs2352PortTrafficStatisticsEntry 34 }

gs2352PortTrafficTxBroadcast OBJECT-TYPE
   SYNTAX      Counter64
   MAX-ACCESS  read-only
   STATUS      current
   DESCRIPTION
       " "
   ::= { gs2352PortTrafficStatisticsEntry 35 }

gs2352PortTrafficTxPause OBJECT-TYPE
   SYNTAX      Counter64
   MAX-ACCESS  read-only
   STATUS      current
   DESCRIPTION
       " "
   ::= { gs2352PortTrafficStatisticsEntry 36 }

gs2352PortTrafficTx64Bytes OBJECT-TYPE
   SYNTAX      Counter64
   MAX-ACCESS  read-only
   STATUS      current
   DESCRIPTION
       " "
   ::= { gs2352PortTrafficStatisticsEntry 37 }

gs2352PortTrafficTx65to127Bytes OBJECT-TYPE
   SYNTAX      Counter64
   MAX-ACCESS  read-only
   STATUS      current
   DESCRIPTION
       " "
   ::= { gs2352PortTrafficStatisticsEntry 38 }

gs2352PortTrafficTx128to255Bytes OBJECT-TYPE
   SYNTAX      Counter64
   MAX-ACCESS  read-only
   STATUS      current
   DESCRIPTION
       " "
   ::= { gs2352PortTrafficStatisticsEntry 39 }

gs2352PortTrafficTx256to511Bytes OBJECT-TYPE
   SYNTAX      Counter64
   MAX-ACCESS  read-only
   STATUS      current
   DESCRIPTION
       " "
   ::= { gs2352PortTrafficStatisticsEntry 40 }

gs2352PortTrafficTx512to1023Bytes OBJECT-TYPE
   SYNTAX      Counter64
   MAX-ACCESS  read-only
   STATUS      current
   DESCRIPTION
       " "
   ::= { gs2352PortTrafficStatisticsEntry 41 }

gs2352PortTrafficTx1024to1526Bytes OBJECT-TYPE
   SYNTAX      Counter64
   MAX-ACCESS  read-only
   STATUS      current
   DESCRIPTION
       " "
   ::= { gs2352PortTrafficStatisticsEntry 42 }

gs2352PortTrafficTxExceecd1527Bytes OBJECT-TYPE
   SYNTAX      Counter64
   MAX-ACCESS  read-only
   STATUS      current
   DESCRIPTION
       " "
   ::= { gs2352PortTrafficStatisticsEntry 43 }

gs2352PortTrafficTxQ0 OBJECT-TYPE
   SYNTAX      Counter64
   MAX-ACCESS  read-only
   STATUS      current
   DESCRIPTION
       " "
   ::= { gs2352PortTrafficStatisticsEntry 44 }

gs2352PortTrafficTxQ1 OBJECT-TYPE
   SYNTAX      Counter64
   MAX-ACCESS  read-only
   STATUS      current
   DESCRIPTION
       " "
   ::= { gs2352PortTrafficStatisticsEntry 45 }

gs2352PortTrafficTxQ2 OBJECT-TYPE
   SYNTAX      Counter64
   MAX-ACCESS  read-only
   STATUS      current
   DESCRIPTION
       " "
   ::= { gs2352PortTrafficStatisticsEntry 46 }

gs2352PortTrafficTxQ3 OBJECT-TYPE
   SYNTAX      Counter64
   MAX-ACCESS  read-only
   STATUS      current
   DESCRIPTION
       " "
   ::= { gs2352PortTrafficStatisticsEntry 47 }

gs2352PortTrafficTxQ4 OBJECT-TYPE
   SYNTAX      Counter64
   MAX-ACCESS  read-only
   STATUS      current
   DESCRIPTION
       " "
   ::= { gs2352PortTrafficStatisticsEntry 48 }

gs2352PortTrafficTxQ5 OBJECT-TYPE
   SYNTAX      Counter64
   MAX-ACCESS  read-only
   STATUS      current
   DESCRIPTION
       " "
   ::= { gs2352PortTrafficStatisticsEntry 49 }

gs2352PortTrafficTxQ6 OBJECT-TYPE
   SYNTAX      Counter64
   MAX-ACCESS  read-only
   STATUS      current
   DESCRIPTION
       " "
   ::= { gs2352PortTrafficStatisticsEntry 50 }


gs2352PortTrafficTxQ7 OBJECT-TYPE
   SYNTAX      Counter64
   MAX-ACCESS  read-only
   STATUS      current
   DESCRIPTION
       " "
   ::= { gs2352PortTrafficStatisticsEntry 51 }

gs2352PortTrafficTxDrops OBJECT-TYPE
   SYNTAX      Counter64
   MAX-ACCESS  read-only
   STATUS      current
   DESCRIPTION
       " "
   ::= { gs2352PortTrafficStatisticsEntry 52 }

gs2352PortTrafficTxLateOrExcColl OBJECT-TYPE
   SYNTAX      Counter64
   MAX-ACCESS  read-only
   STATUS      current
   DESCRIPTION
       " "
   ::= { gs2352PortTrafficStatisticsEntry 53 }


gs2352PortQoSStatistics                                     OBJECT IDENTIFIER ::= { gs2352Port 3 }

gs2352PortQoSStatisticsClear OBJECT-TYPE
   SYNTAX      INTEGER { none(0), clear(1) }
   MAX-ACCESS  read-only
   STATUS      current
   DESCRIPTION
       "default: 0
       0: none
       1: clear "
   ::= { gs2352PortQoSStatistics 1 }

gs2352PortQoSStatisticsTable OBJECT-TYPE
   SYNTAX      SEQUENCE OF GS2352PortQoSStatisticsEntry
   MAX-ACCESS  not-accessible
   STATUS      current
   DESCRIPTION
       " "
   ::= { gs2352PortQoSStatistics 2 }

gs2352PortQoSStatisticsEntry OBJECT-TYPE
   SYNTAX      GS2352PortQoSStatisticsEntry
   MAX-ACCESS  not-accessible
   STATUS      current
   DESCRIPTION
       ""
   INDEX    { gs2352PortQoSStatisticsPort  }
   ::= { gs2352PortQoSStatisticsTable 1 }

GS2352PortQoSStatisticsEntry ::= SEQUENCE {
   gs2352PortQoSStatisticsPort      Integer32,
   gs2352PortQoSQ0Rx                Counter64,
   gs2352PortQoSQ0Tx                Counter64,
   gs2352PortQoSQ1Rx                Counter64,
   gs2352PortQoSQ1Tx                Counter64,
   gs2352PortQoSQ2Rx                Counter64,
   gs2352PortQoSQ2Tx                Counter64,
   gs2352PortQoSQ3Rx                Counter64,
   gs2352PortQoSQ3Tx                Counter64,
   gs2352PortQoSQ4Rx                Counter64,
   gs2352PortQoSQ4Tx                Counter64,
   gs2352PortQoSQ5Rx                Counter64,
   gs2352PortQoSQ5Tx                Counter64,
   gs2352PortQoSQ6Rx                Counter64,
   gs2352PortQoSQ6Tx                Counter64,
   gs2352PortQoSQ7Rx                Counter64,
   gs2352PortQoSQ7Tx                Counter64
}

gs2352PortQoSStatisticsPort OBJECT-TYPE
   SYNTAX      Integer32(1..4095)
   MAX-ACCESS  not-accessible
   STATUS      current
   DESCRIPTION
       " "
   ::= { gs2352PortQoSStatisticsEntry 1 }

gs2352PortQoSQ0Rx OBJECT-TYPE
   SYNTAX      Counter64
   MAX-ACCESS  read-only
   STATUS      current
   DESCRIPTION
       " "
   ::= { gs2352PortQoSStatisticsEntry 2 }

gs2352PortQoSQ0Tx OBJECT-TYPE
   SYNTAX      Counter64
   MAX-ACCESS  read-only
   STATUS      current
   DESCRIPTION
       " "
   ::= { gs2352PortQoSStatisticsEntry 3 }

gs2352PortQoSQ1Rx OBJECT-TYPE
   SYNTAX      Counter64
   MAX-ACCESS  read-only
   STATUS      current
   DESCRIPTION
       " "
   ::= { gs2352PortQoSStatisticsEntry 4 }

gs2352PortQoSQ1Tx OBJECT-TYPE
   SYNTAX      Counter64
   MAX-ACCESS  read-only
   STATUS      current
   DESCRIPTION
       " "
   ::= { gs2352PortQoSStatisticsEntry 5 }

gs2352PortQoSQ2Rx OBJECT-TYPE
   SYNTAX      Counter64
   MAX-ACCESS  read-only
   STATUS      current
   DESCRIPTION
       " "
   ::= { gs2352PortQoSStatisticsEntry 6 }

gs2352PortQoSQ2Tx OBJECT-TYPE
   SYNTAX      Counter64
   MAX-ACCESS  read-only
   STATUS      current
   DESCRIPTION
       " "
   ::= { gs2352PortQoSStatisticsEntry 7 }

gs2352PortQoSQ3Rx OBJECT-TYPE
   SYNTAX      Counter64
   MAX-ACCESS  read-only
   STATUS      current
   DESCRIPTION
       " "
   ::= { gs2352PortQoSStatisticsEntry 8 }

gs2352PortQoSQ3Tx OBJECT-TYPE
   SYNTAX      Counter64
   MAX-ACCESS  read-only
   STATUS      current
   DESCRIPTION
       " "
   ::= { gs2352PortQoSStatisticsEntry 9 }

gs2352PortQoSQ4Rx OBJECT-TYPE
   SYNTAX      Counter64
   MAX-ACCESS  read-only
   STATUS      current
   DESCRIPTION
       " "
   ::= { gs2352PortQoSStatisticsEntry 10 }

gs2352PortQoSQ4Tx OBJECT-TYPE
   SYNTAX      Counter64
   MAX-ACCESS  read-only
   STATUS      current
   DESCRIPTION
       " "
   ::= { gs2352PortQoSStatisticsEntry 11 }

gs2352PortQoSQ5Rx OBJECT-TYPE
   SYNTAX      Counter64
   MAX-ACCESS  read-only
   STATUS      current
   DESCRIPTION
       " "
   ::= { gs2352PortQoSStatisticsEntry 12 }

gs2352PortQoSQ5Tx OBJECT-TYPE
   SYNTAX      Counter64
   MAX-ACCESS  read-only
   STATUS      current
   DESCRIPTION
       " "
   ::= { gs2352PortQoSStatisticsEntry 13 }

gs2352PortQoSQ6Rx OBJECT-TYPE
   SYNTAX      Counter64
   MAX-ACCESS  read-only
   STATUS      current
   DESCRIPTION
       " "
   ::= { gs2352PortQoSStatisticsEntry 14 }

gs2352PortQoSQ6Tx OBJECT-TYPE
   SYNTAX      Counter64
   MAX-ACCESS  read-only
   STATUS      current
   DESCRIPTION
       " "
   ::= { gs2352PortQoSStatisticsEntry 15 }

gs2352PortQoSQ7Rx OBJECT-TYPE
   SYNTAX      Counter64
   MAX-ACCESS  read-only
   STATUS      current
   DESCRIPTION
       " "
   ::= { gs2352PortQoSStatisticsEntry 16 }

gs2352PortQoSQ7Tx OBJECT-TYPE
   SYNTAX      Counter64
   MAX-ACCESS  read-only
   STATUS      current
   DESCRIPTION
       " "
   ::= { gs2352PortQoSStatisticsEntry 17 }

gs2352SFPInfoTable OBJECT-TYPE
   SYNTAX      SEQUENCE OF GS2352SFPInfoEntry
   MAX-ACCESS  not-accessible
   STATUS      current
   DESCRIPTION
       " "
   ::= { gs2352Port 4 }

gs2352SFPInfoEntry OBJECT-TYPE
   SYNTAX      GS2352SFPInfoEntry
   MAX-ACCESS  not-accessible
   STATUS      current
   DESCRIPTION
       ""
   INDEX    { gs2352SFPInfoIndex }
   ::= { gs2352SFPInfoTable 1 }

GS2352SFPInfoEntry ::= SEQUENCE {
   gs2352SFPInfoIndex               Integer32,
   gs2352SFPInfoPort                DisplayString,
   gs2352SFPConnectorType           DisplayString,
   gs2352SFPFiberType               DisplayString,
   gs2352SFPTxCentralWavelength     DisplayString,
   gs2352SFPBaudRate                DisplayString,
   gs2352SFPVendorOUI               DisplayString,
   gs2352SFPVendorName              DisplayString,
   gs2352SFPVendorPN                DisplayString,
   gs2352SFPVendorRev               DisplayString,
   gs2352SFPVendorSN                DisplayString,
   gs2352SFPDateCode                DisplayString,
   gs2352SFPTemperature             DisplayString,
   gs2352SFPVcc                     DisplayString,
   gs2352SFPMon1Bias                DisplayString,
   gs2352SFPMon2TxPWR               DisplayString,
   gs2352SFPMon3RxPWR               DisplayString
}

gs2352SFPInfoIndex OBJECT-TYPE
   SYNTAX      Integer32(1..4095)
   MAX-ACCESS  not-accessible
   STATUS      current
   DESCRIPTION
       " "
   ::= { gs2352SFPInfoEntry 1 }

gs2352SFPInfoPort OBJECT-TYPE
   SYNTAX      DisplayString
   MAX-ACCESS  read-only
   STATUS      current
   DESCRIPTION
       " "
   ::= { gs2352SFPInfoEntry 2 }

gs2352SFPConnectorType OBJECT-TYPE
   SYNTAX      DisplayString
   MAX-ACCESS  read-only
   STATUS      current
   DESCRIPTION
       " "
   ::= { gs2352SFPInfoEntry 3 }

gs2352SFPFiberType OBJECT-TYPE
   SYNTAX      DisplayString
   MAX-ACCESS  read-only
   STATUS      current
   DESCRIPTION
       " "
   ::= { gs2352SFPInfoEntry 4 }

gs2352SFPTxCentralWavelength OBJECT-TYPE
   SYNTAX      DisplayString
   MAX-ACCESS  read-only
   STATUS      current
   DESCRIPTION
       " "
   ::= { gs2352SFPInfoEntry 5 }

gs2352SFPBaudRate OBJECT-TYPE
   SYNTAX      DisplayString
   MAX-ACCESS  read-only
   STATUS      current
   DESCRIPTION
       " "
   ::= { gs2352SFPInfoEntry 6 }

gs2352SFPVendorOUI OBJECT-TYPE
   SYNTAX      DisplayString
   MAX-ACCESS  read-only
   STATUS      current
   DESCRIPTION
       " "
   ::= { gs2352SFPInfoEntry 7 }

gs2352SFPVendorName OBJECT-TYPE
   SYNTAX      DisplayString
   MAX-ACCESS  read-only
   STATUS      current
   DESCRIPTION
       " "
   ::= { gs2352SFPInfoEntry 8 }

gs2352SFPVendorPN OBJECT-TYPE
   SYNTAX      DisplayString
   MAX-ACCESS  read-only
   STATUS      current
   DESCRIPTION
       " "
   ::= { gs2352SFPInfoEntry 9 }

gs2352SFPVendorRev OBJECT-TYPE
   SYNTAX      DisplayString
   MAX-ACCESS  read-only
   STATUS      current
   DESCRIPTION
       " "
   ::= { gs2352SFPInfoEntry 10 }

gs2352SFPVendorSN OBJECT-TYPE
   SYNTAX      DisplayString
   MAX-ACCESS  read-only
   STATUS      current
   DESCRIPTION
       " "
   ::= { gs2352SFPInfoEntry 11 }

gs2352SFPDateCode OBJECT-TYPE
   SYNTAX      DisplayString
   MAX-ACCESS  read-only
   STATUS      current
   DESCRIPTION
       " "
   ::= { gs2352SFPInfoEntry 12 }

gs2352SFPTemperature OBJECT-TYPE
   SYNTAX      DisplayString
   MAX-ACCESS  read-only
   STATUS      current
   DESCRIPTION
       " "
   ::= { gs2352SFPInfoEntry 13 }

gs2352SFPVcc OBJECT-TYPE
   SYNTAX      DisplayString
   MAX-ACCESS  read-only
   STATUS      current
   DESCRIPTION
       " "
   ::= { gs2352SFPInfoEntry 14 }

gs2352SFPMon1Bias OBJECT-TYPE
   SYNTAX      DisplayString
   MAX-ACCESS  read-only
   STATUS      current
   DESCRIPTION
       " "
   ::= { gs2352SFPInfoEntry 15 }

gs2352SFPMon2TxPWR OBJECT-TYPE
   SYNTAX      DisplayString
   MAX-ACCESS  read-only
   STATUS      current
   DESCRIPTION
       " "
   ::= { gs2352SFPInfoEntry 16 }

gs2352SFPMon3RxPWR OBJECT-TYPE
   SYNTAX      DisplayString
   MAX-ACCESS  read-only
   STATUS      current
   DESCRIPTION
       " "
   ::= { gs2352SFPInfoEntry 17 }


gs2352VoiceVLAN                                             OBJECT IDENTIFIER ::= { gs2352Configuration 2 }

gs2352VoiceVLANConf                                         OBJECT IDENTIFIER ::= { gs2352VoiceVLAN 1 }

gs2352VoiceVLANMode OBJECT-TYPE
   SYNTAX      INTEGER { disable(0), enable(1) }
   MAX-ACCESS  read-write
   STATUS      current
   DESCRIPTION
       " Voice VLAN mode operation.
       default: 0,
       0: disable
       1: enable"
   ::= { gs2352VoiceVLANConf 1 }

gs2352VoiceVLANVLANId OBJECT-TYPE
   SYNTAX      Integer32(1..4094)
   MAX-ACCESS  read-write
   STATUS      current
   DESCRIPTION
       "Voice VLAN ID.
        default: 1000,
        range : 1-4094. "
   ::= { gs2352VoiceVLANConf 2 }

gs2352VoiceVLANAgingTime OBJECT-TYPE
   SYNTAX      Integer32(10..1000000)
   MAX-ACCESS  read-write
   STATUS      current
   DESCRIPTION
       " Voice VLAN secure learning aging time.
         default: 86400,
         range : 10 - 10000000. "
   ::= { gs2352VoiceVLANConf 3 }

gs2352VoiceVLANTrafficClass OBJECT-TYPE
   SYNTAX      Integer32(0..7)
   MAX-ACCESS  read-write
   STATUS      current
   DESCRIPTION
       " Voice VLAN traffic class, all traffic on the Voice VLAN
         will apply this class, available value is from 0(Low)
         to 7(High).
         default: 7. "
   ::= { gs2352VoiceVLANConf 4 }


gs2352VoiceVLANPortTable OBJECT-TYPE
   SYNTAX      SEQUENCE OF GS2352VoiceVLANPortEntry
   MAX-ACCESS  not-accessible
   STATUS      current
   DESCRIPTION
       " Show Voice Vlan configuration. "
   ::= { gs2352VoiceVLANConf 5 }

gs2352VoiceVLANPortEntry OBJECT-TYPE
   SYNTAX      GS2352VoiceVLANPortEntry
   MAX-ACCESS  not-accessible
   STATUS      current
   DESCRIPTION
       ""
   INDEX    { gs2352VoiceVLANPort  }
   ::= { gs2352VoiceVLANPortTable 1 }

GS2352VoiceVLANPortEntry ::= SEQUENCE {
   gs2352VoiceVLANPort                    Integer32,
   gs2352VoiceVLANPortMode                INTEGER,
   gs2352VoiceVLANPortSecurity            INTEGER,
   gs2352VoiceVLANPortDiscoveryProtocol   INTEGER
}

gs2352VoiceVLANPort OBJECT-TYPE
   SYNTAX      Integer32(1..4095)
   MAX-ACCESS  not-accessible
   STATUS      current
   DESCRIPTION
       " port, range : 1 - port number. "
   ::= { gs2352VoiceVLANPortEntry 1 }

gs2352VoiceVLANPortMode OBJECT-TYPE
   SYNTAX      INTEGER { disable(0), auto(1), forced(2) }
   MAX-ACCESS  read-write
   STATUS      current
   DESCRIPTION
       " Voice VLAN port mode.
         default: 0,
         0: Disable (Disjoin from Voice VLAN.)
         1: Auto (Enable auto detect mode. It detects whether there is VoIP phone attached to the specific port and configures the Voice VLAN members automatically.)
         2: Forced (Force join to Voice VLAN.)"
   ::= { gs2352VoiceVLANPortEntry 2 }

gs2352VoiceVLANPortSecurity OBJECT-TYPE
   SYNTAX      INTEGER { disable(0), enable(1) }
   MAX-ACCESS  read-write
   STATUS      current
   DESCRIPTION
       " Voice VLAN port security mode.
         default: 0,
         0: Disable (Disjoin from Voice VLAN.)
         1: enable ( Enable Voice VLAN security mode. When the function is
                     enabled, all non-telephone MAC address in Voice VLAN
                     will be blocked 10 seconds.)"
   ::= { gs2352VoiceVLANPortEntry 3 }

gs2352VoiceVLANPortDiscoveryProtocol OBJECT-TYPE
   SYNTAX      INTEGER { oui(0), lldp(1), both(2) }
   MAX-ACCESS  read-write
   STATUS      current
   DESCRIPTION
       " Voice VLAN port discovery protocol.
         default: 0
         0: OUI (Detect telephony device by OUI address.)
         1: LLDP (Detect telephony device by LLDP.)
         2: Both (Both OUI and LLDP.) "
   ::= { gs2352VoiceVLANPortEntry 4 }

gs2352VoiceVLANSkipNAS OBJECT-TYPE
   SYNTAX      INTEGER { disable(0), enable(1) }
   MAX-ACCESS  read-write
   STATUS      current
   DESCRIPTION
       " Voice VLAN skip NAS mode.
         default: 0,
         0: Disable (Do not skip NAS on Voice VLAN.)
         1: enable (Enable skipping of NAS on Voice VLAN. When the function is
                    enabled, authentication through the NAS module is not
                    applied to the Voice VLAN, but clients are allowed without
                    authentication.)"
   ::= { gs2352VoiceVLANPortEntry 5 }


gs2352VoiceVLANOUI                                          OBJECT IDENTIFIER ::= { gs2352VoiceVLAN 2 }

gs2352VoiceVLANOUICreate OBJECT-TYPE
   SYNTAX       INTEGER { none(0), create(1) }
   MAX-ACCESS   read-write
   STATUS       current
   DESCRIPTION
       "default: 0
        0 : None  (read only)
        1 : Create an OUI entry"
   ::= { gs2352VoiceVLANOUI 1 }

gs2352VoiceVLANOUITable OBJECT-TYPE
   SYNTAX      SEQUENCE OF GS2352VoiceVLANOUIEntry
   MAX-ACCESS  not-accessible
   STATUS      current
   DESCRIPTION
       " Create Voice VLAN OUI entry. Modify OUI table will
         restart auto detect OUI process. "
   ::= { gs2352VoiceVLANOUI 2 }

gs2352VoiceVLANOUIEntry OBJECT-TYPE
   SYNTAX      GS2352VoiceVLANOUIEntry
   MAX-ACCESS  not-accessible
   STATUS      current
   DESCRIPTION
       ""
   INDEX    { gs2352VoiceVLANOUIIndex  }
   ::= { gs2352VoiceVLANOUITable 1 }

GS2352VoiceVLANOUIEntry ::= SEQUENCE {
   gs2352VoiceVLANOUIIndex         Integer32,
   gs2352VoiceVLANTelephonyOUI     OCTET STRING,
   gs2352VoiceVLANDescription      DisplayString,
   gs2352VoiceVLANOUIRowStatus     INTEGER
}

gs2352VoiceVLANOUIIndex OBJECT-TYPE
   SYNTAX      Integer32(1..16)
   MAX-ACCESS  not-accessible
   STATUS      current
   DESCRIPTION
       " "
   ::= { gs2352VoiceVLANOUIEntry 1 }

gs2352VoiceVLANTelephonyOUI OBJECT-TYPE
   SYNTAX      OCTET STRING (SIZE (1..32))
   MAX-ACCESS  read-write
   STATUS      current
   DESCRIPTION
       "OUI address, format : 0a 1b 2c "
   ::= { gs2352VoiceVLANOUIEntry 2 }

gs2352VoiceVLANDescription OBJECT-TYPE
   SYNTAX      DisplayString (SIZE (1..32))
   MAX-ACCESS  read-write
   STATUS      current
   DESCRIPTION
       " Up to 32 characters describing OUI address. "
   ::= { gs2352VoiceVLANOUIEntry 3 }

gs2352VoiceVLANOUIRowStatus OBJECT-TYPE
   SYNTAX      INTEGER { active(1), notInservice(2), destroy(4), undo(5) }
   MAX-ACCESS  read-write
   STATUS      current
   DESCRIPTION
       "1: active
        2: notInservice
        4: destroy
        5: undo"
   ::= { gs2352VoiceVLANOUIEntry 4 }

gs2352GARP                                                   OBJECT IDENTIFIER ::= { gs2352Configuration 3 }

gs2352GARPConfTable OBJECT-TYPE
   SYNTAX      SEQUENCE OF GS2352GARPConfEntry
   MAX-ACCESS  not-accessible
   STATUS      current
   DESCRIPTION
       " "
   ::= { gs2352GARP 1 }

gs2352GARPConfEntry OBJECT-TYPE
   SYNTAX      GS2352GARPConfEntry
   MAX-ACCESS  not-accessible
   STATUS      current
   DESCRIPTION
       ""
   INDEX    { gs2352GARPConfPort  }
   ::= { gs2352GARPConfTable 1 }

GS2352GARPConfEntry ::= SEQUENCE {
   gs2352GARPConfPort           Integer32,
   gs2352GARPJoinTimer          Integer32,
   gs2352GARPLeaveTimer         Integer32,
   gs2352GARPLeaveAllTimer      Integer32,
   gs2352GARPApplicantion       INTEGER,
   gs2352GARPAttributeType      INTEGER,
   gs2352GARPApplicant          INTEGER
}

gs2352GARPConfPort OBJECT-TYPE
   SYNTAX      Integer32(1..4095)
   MAX-ACCESS  not-accessible
   STATUS      current
   DESCRIPTION
       " "
   ::= { gs2352GARPConfEntry 1 }

gs2352GARPJoinTimer OBJECT-TYPE
   SYNTAX      Integer32(200..1000)
   MAX-ACCESS  read-write
   STATUS      current
   DESCRIPTION
       "default: 200, range : 200 - 1000 "
   ::= { gs2352GARPConfEntry 2 }

gs2352GARPLeaveTimer OBJECT-TYPE
   SYNTAX      Integer32(600..3000)
   MAX-ACCESS  read-write
   STATUS      current
   DESCRIPTION
       "default: 600 , range : 600 - 3000"
   ::= { gs2352GARPConfEntry 3 }

gs2352GARPLeaveAllTimer OBJECT-TYPE
   SYNTAX      Integer32(10000..50000)
   MAX-ACCESS  read-write
   STATUS      current
   DESCRIPTION
       "default: 10000, range : 10000 - 50000 "
   ::= { gs2352GARPConfEntry 4 }

gs2352GARPApplicantion OBJECT-TYPE
   SYNTAX      INTEGER { gvrp(1)}
   MAX-ACCESS  read-write
   STATUS      current
   DESCRIPTION
       "default: 1
       1: GVRP"
   ::= { gs2352GARPConfEntry 5 }

gs2352GARPAttributeType OBJECT-TYPE
   SYNTAX      INTEGER { vlan(1)}
   MAX-ACCESS  read-write
   STATUS      current
   DESCRIPTION
       "default: 1
       1: VLAN"
   ::= { gs2352GARPConfEntry 6 }

gs2352GARPApplicant OBJECT-TYPE
   SYNTAX      INTEGER { participant(0), nonParticipant(1) }
   MAX-ACCESS  read-write
   STATUS      current
   DESCRIPTION
       "default: 0
       0: normal-participant
       1: non-participant"
   ::= { gs2352GARPConfEntry 7 }

gs2352GARPStatisticsTable OBJECT-TYPE
   SYNTAX      SEQUENCE OF GS2352GARPStatisticsEntry
   MAX-ACCESS  not-accessible
   STATUS      current
   DESCRIPTION
       " Show the basic GARP port statistics. "
   ::= { gs2352GARP 2 }

gs2352GARPStatisticsEntry OBJECT-TYPE
   SYNTAX      GS2352GARPStatisticsEntry
   MAX-ACCESS  not-accessible
   STATUS      current
   DESCRIPTION
       ""
   INDEX    { gs2352GARPStatisticsPort  }
   ::= { gs2352GARPStatisticsTable 1 }

GS2352GARPStatisticsEntry ::= SEQUENCE {
   gs2352GARPStatisticsPort             Integer32,
   gs2352GARPStatisticsPeerMAC          DisplayString,
   gs2352GARPStatisticsFailedCount      Counter32
}

gs2352GARPStatisticsPort OBJECT-TYPE
   SYNTAX      Integer32(1..4095)
   MAX-ACCESS  not-accessible
   STATUS      current
   DESCRIPTION
       " port, range : 1 - port number. "
   ::= { gs2352GARPStatisticsEntry 1 }

gs2352GARPStatisticsPeerMAC OBJECT-TYPE
   SYNTAX      DisplayString
   MAX-ACCESS  read-only
   STATUS      current
   DESCRIPTION
       " Peer MAC is MAC address of the neighbour Switch from with GARP frame is received.  "
   ::= { gs2352GARPStatisticsEntry 2 }

gs2352GARPStatisticsFailedCount OBJECT-TYPE
   SYNTAX      Counter32
   MAX-ACCESS  read-only
   STATUS      current
   DESCRIPTION
       " explain Failed count here. "
   ::= { gs2352GARPStatisticsEntry 3 }

gs2352GVRP                                                   OBJECT IDENTIFIER ::= { gs2352Configuration 4 }

gs2352GVRPConf                                                   OBJECT IDENTIFIER ::= { gs2352GVRP 1 }

gs2352GVRPMode OBJECT-TYPE
   SYNTAX      INTEGER { disable(0), enable(1) }
   MAX-ACCESS  read-write
   STATUS      current
   DESCRIPTION
       "default: 0,
        0: disable,
        1: enable. "
   ::= { gs2352GVRPConf 1 }

gs2352GVRPConfTable OBJECT-TYPE
   SYNTAX      SEQUENCE OF GS2352GVRPConfEntry
   MAX-ACCESS  not-accessible
   STATUS      current
   DESCRIPTION
       " "
   ::= { gs2352GVRPConf 2 }

gs2352GVRPConfEntry OBJECT-TYPE
   SYNTAX      GS2352GVRPConfEntry
   MAX-ACCESS  not-accessible
   STATUS      current
   DESCRIPTION
       ""
   INDEX    { gs2352GVRPConfPort  }
   ::= { gs2352GVRPConfTable 1 }

GS2352GVRPConfEntry ::= SEQUENCE {
   gs2352GVRPConfPort           Integer32,
   gs2352GVRPConfPortMode       INTEGER,
   gs2352GVRPConfPortRRole      INTEGER
}

gs2352GVRPConfPort OBJECT-TYPE
   SYNTAX      Integer32(1..4095)
   MAX-ACCESS  not-accessible
   STATUS      current
   DESCRIPTION
       " "
   ::= { gs2352GVRPConfEntry 1 }

gs2352GVRPConfPortMode OBJECT-TYPE
   SYNTAX      INTEGER { disable(0), enable(1) }
   MAX-ACCESS  read-write
   STATUS      current
   DESCRIPTION
       "default: 0
       1: enable
       0: disable"
   ::= { gs2352GVRPConfEntry 2 }

gs2352GVRPConfPortRRole OBJECT-TYPE
   SYNTAX      INTEGER { disable(0), enable(1) }
   MAX-ACCESS  read-write
   STATUS      current
   DESCRIPTION
       "default: 0
       1: enable
       0: disable"
   ::= { gs2352GVRPConfEntry 3 }

gs2352GVRPStatisticsTable OBJECT-TYPE
   SYNTAX      SEQUENCE OF GS2352GVRPStatisticsEntry
   MAX-ACCESS  not-accessible
   STATUS      current
   DESCRIPTION
       " "
   ::= { gs2352GVRP 2 }

gs2352GVRPStatisticsEntry OBJECT-TYPE
   SYNTAX      GS2352GVRPStatisticsEntry
   MAX-ACCESS  not-accessible
   STATUS      current
   DESCRIPTION
       ""
   INDEX    { gs2352GVRPStatisticsPort  }
   ::= { gs2352GVRPStatisticsTable 1 }

GS2352GVRPStatisticsEntry ::= SEQUENCE {
   gs2352GVRPStatisticsPort         Integer32,
   gs2352GVRPStatisticsJoinTxCnt    Counter32,
   gs2352GVRPStatisticsLeaveTxCnt   Counter32
}

gs2352GVRPStatisticsPort OBJECT-TYPE
   SYNTAX      Integer32(1..4095)
   MAX-ACCESS  not-accessible
   STATUS      current
   DESCRIPTION
       " "
   ::= { gs2352GVRPStatisticsEntry 1 }

gs2352GVRPStatisticsJoinTxCnt OBJECT-TYPE
   SYNTAX      Counter32
   MAX-ACCESS  read-only
   STATUS      current
   DESCRIPTION
       ""
   ::= { gs2352GVRPStatisticsEntry 2 }

gs2352GVRPStatisticsLeaveTxCnt OBJECT-TYPE
   SYNTAX      Counter32
   MAX-ACCESS  read-only
   STATUS      current
   DESCRIPTION
       ""
   ::= { gs2352GVRPStatisticsEntry 3 }


gs2352Mirroring                                             OBJECT IDENTIFIER ::= { gs2352Configuration 6 }

gs2352PortToMirrorOn OBJECT-TYPE
   SYNTAX      Integer32(0..10)
   MAX-ACCESS  read-write
   STATUS      current
   DESCRIPTION
       "default: 0
        0: disable,
        range : 1 - port number. "
   ::= { gs2352Mirroring 1 }

gs2352MirrorTable OBJECT-TYPE
   SYNTAX      SEQUENCE OF GS2352MirrorEntry
   MAX-ACCESS  not-accessible
   STATUS      current
   DESCRIPTION
       " "
   ::= { gs2352Mirroring 2 }

gs2352MirrorEntry OBJECT-TYPE
   SYNTAX      GS2352MirrorEntry
   MAX-ACCESS  not-accessible
   STATUS      current
   DESCRIPTION
       ""
   INDEX    { gs2352MirrorPort  }
   ::= { gs2352MirrorTable 1 }

GS2352MirrorEntry ::= SEQUENCE {
   gs2352MirrorPort		Integer32,
   gs2352MirrorMode		INTEGER
}

gs2352MirrorPort OBJECT-TYPE
   SYNTAX      Integer32(1..4095)
   MAX-ACCESS  not-accessible
   STATUS      current
   DESCRIPTION
       " "
   ::= { gs2352MirrorEntry 1 }

gs2352MirrorMode OBJECT-TYPE
   SYNTAX      INTEGER { disable(0), enable(1), rxOnly(2), txOnly(3) }
   MAX-ACCESS  read-write
   STATUS      current
   DESCRIPTION
       "default: 0
       0: disable
       1: enable
       2: rx only
       3: tx only
       Setting Tx mirroring for analyzer port has no effect. Tx mirroring ignored"
   ::= { gs2352MirrorEntry 2 }

gs2352TrapEventSeverity                                             OBJECT IDENTIFIER ::= { gs2352Configuration 7 }

gs2352TrapEventSeverityACL OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  6(Info)
        0: Emergency
        1: Alert
        2: Critical
        3: Error
        4: Warning
        5: Notice
        6: Info
        7: Debug"
   ::= { gs2352TrapEventSeverity 1 }

gs2352TrapEventSeverityACLLog OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  7(Debug)
        0: Emergency
        1: Alert
        2: Critical
        3: Error
        4: Warning
        5: Notice
        6: Info
        7: Debug"
   ::= { gs2352TrapEventSeverity 2 }

gs2352TrapEventSeverityAccessMgmt OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  6(Info)
        0: Emergency
        1: Alert
        2: Critical
        3: Error
        4: Warning
        5: Notice
        6: Info
        7: Debug"
   ::= { gs2352TrapEventSeverity 3 }

gs2352TrapEventSeverityAuthFailed OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  4(Warning)
        0: Emergency
        1: Alert
        2: Critical
        3: Error
        4: Warning
        5: Notice
        6: Info
        7: Debug"
   ::= { gs2352TrapEventSeverity 4 }

gs2352TrapEventSeverityColdStart OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  4(Warning)
        0: Emergency
        1: Alert
        2: Critical
        3: Error
        4: Warning
        5: Notice
        6: Info
        7: Debug"
   ::= { gs2352TrapEventSeverity 5 }

gs2352TrapEventSeverityConfigInfo OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  6(Info)
        0: Emergency
        1: Alert
        2: Critical
        3: Error
        4: Warning
        5: Notice
        6: Info
        7: Debug"
   ::= { gs2352TrapEventSeverity 6 }

gs2352TrapEventSeverityFirmwareUpgrade OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  6(Info)
        0: Emergency
        1: Alert
        2: Critical
        3: Error
        4: Warning
        5: Notice
        6: Info
        7: Debug"
   ::= { gs2352TrapEventSeverity 7 }

gs2352TrapEventSeverityImportExport OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  6(Info)
        0: Emergency
        1: Alert
        2: Critical
        3: Error
        4: Warning
        5: Notice
        6: Info
        7: Debug"
   ::= { gs2352TrapEventSeverity 8 }

gs2352TrapEventSeverityLACP OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  6(Info)
        0: Emergency
        1: Alert
        2: Critical
        3: Error
        4: Warning
        5: Notice
        6: Info
        7: Debug"
   ::= { gs2352TrapEventSeverity 9 }

gs2352TrapEventSeverityLinkStatus OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  4(Warning)
        0: Emergency
        1: Alert
        2: Critical
        3: Error
        4: Warning
        5: Notice
        6: Info
        7: Debug"
   ::= { gs2352TrapEventSeverity 10 }

gs2352TrapEventSeverityLogin OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  6(Info)
        0: Emergency
        1: Alert
        2: Critical
        3: Error
        4: Warning
        5: Notice
        6: Info
        7: Debug"
   ::= { gs2352TrapEventSeverity 11 }

gs2352TrapEventSeverityLogout OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  6(Info)
        0: Emergency
        1: Alert
        2: Critical
        3: Error
        4: Warning
        5: Notice
        6: Info
        7: Debug"
   ::= { gs2352TrapEventSeverity 12 }

gs2352TrapEventSeverityLoopProtect OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  6(Info)
        0: Emergency
        1: Alert
        2: Critical
        3: Error
        4: Warning
        5: Notice
        6: Info
        7: Debug"
   ::= { gs2352TrapEventSeverity 13 }

gs2352TrapEventSeverityMgmtIPChange OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  6(Info)
        0: Emergency
        1: Alert
        2: Critical
        3: Error
        4: Warning
        5: Notice
        6: Info
        7: Debug"
   ::= { gs2352TrapEventSeverity 14 }

gs2352TrapEventSeverityModuleChange OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  5(Notice)
        0: Emergency
        1: Alert
        2: Critical
        3: Error
        4: Warning
        5: Notice
        6: Info
        7: Debug"
   ::= { gs2352TrapEventSeverity 15 }

gs2352TrapEventSeverityNAS OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  6(Info)
        0: Emergency
        1: Alert
        2: Critical
        3: Error
        4: Warning
        5: Notice
        6: Info
        7: Debug"
   ::= { gs2352TrapEventSeverity 16 }

gs2352TrapEventSeverityPasswordChange OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  6(Info)
        0: Emergency
        1: Alert
        2: Critical
        3: Error
        4: Warning
        5: Notice
        6: Info
        7: Debug"
   ::= { gs2352TrapEventSeverity 17 }

gs2352TrapEventSeverityPortSecurity OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  6(Info)
        0: Emergency
        1: Alert
        2: Critical
        3: Error
        4: Warning
        5: Notice
        6: Info
        7: Debug"
   ::= { gs2352TrapEventSeverity 18 }

gs2352TrapEventSeverityVLAN OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  6(Info)
        0: Emergency
        1: Alert
        2: Critical
        3: Error
        4: Warning
        5: Notice
        6: Info
        7: Debug"
   ::= { gs2352TrapEventSeverity 20 }

gs2352TrapEventSeverityWarmStart OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  4(Warning)
        0: Emergency
        1: Alert
        2: Critical
        3: Error
        4: Warning
        5: Notice
        6: Info
        7: Debug"
   ::= { gs2352TrapEventSeverity 21 }


gs2352TrapEventSeverityARPConflict OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  4(Warning)
        0: Emergency
        1: Alert
        2: Critical
        3: Error
        4: Warning
        5: Notice
        6: Info
        7: Debug"
   ::= { gs2352TrapEventSeverity 25 }

gs2352TrapEventSeveritySpoofingLimit OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  4(Warning)
        0: Emergency
        1: Alert
        2: Critical
        3: Error
        4: Warning
        5: Notice
        6: Info
        7: Debug"
   ::= { gs2352TrapEventSeverity 27 }

gs2352TrapEventSeverityStaticARPConflict	 OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  4(Warning)
        0: Emergency
        1: Alert
        2: Critical
        3: Error
        4: Warning
        5: Notice
        6: Info
        7: Debug"
   ::= { gs2352TrapEventSeverity 28 }

gs2352SMTP                                             OBJECT IDENTIFIER ::= { gs2352Configuration 8 }

gs2352SMTPMailServer OBJECT-TYPE
   SYNTAX      DisplayString
   MAX-ACCESS  read-write
   STATUS      current
   DESCRIPTION
       " Up to 47 characters describing email server. "
   ::= { gs2352SMTP 1 }

gs2352SMTPUserName OBJECT-TYPE
   SYNTAX      DisplayString
   MAX-ACCESS  read-write
   STATUS      current
   DESCRIPTION
       " Up to 47 characters describing user name. "
   ::= { gs2352SMTP 2 }

gs2352SMTPPassword OBJECT-TYPE
   SYNTAX      DisplayString
   MAX-ACCESS  read-write
   STATUS      current
   DESCRIPTION
       " Up to 47 characters describing password. "
   ::= { gs2352SMTP 3 }

gs2352SMTPServeriryLevel OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       "default: 6
       0: Emergency
       1: Alert
       2: Critical
       3: Error
       4: Warning
       5: Notice
       6: Info
       7: Debug"
   ::= { gs2352SMTP 4 }

gs2352SMTPSender OBJECT-TYPE
   SYNTAX      DisplayString
   MAX-ACCESS  read-write
   STATUS      current
   DESCRIPTION
       " Up to 47 characters describing sender. "
   ::= { gs2352SMTP 5 }

gs2352SMTPReturnPath OBJECT-TYPE
   SYNTAX      DisplayString
   MAX-ACCESS  read-write
   STATUS      current
   DESCRIPTION
       " Up to 47 characters describing return path. "
   ::= { gs2352SMTP 6 }

gs2352SMTPEmailAddress1 OBJECT-TYPE
   SYNTAX      DisplayString
   MAX-ACCESS  read-write
   STATUS      current
   DESCRIPTION
       " Up to 47 characters describing mail address. "
   ::= { gs2352SMTP 7 }

gs2352SMTPEmailAddress2 OBJECT-TYPE
   SYNTAX      DisplayString
   MAX-ACCESS  read-write
   STATUS      current
   DESCRIPTION
       " Up to 47 characters describing mail address. "
   ::= { gs2352SMTP 8 }

gs2352SMTPEmailAddress3 OBJECT-TYPE
   SYNTAX      DisplayString
   MAX-ACCESS  read-write
   STATUS      current
   DESCRIPTION
       " Up to 47 characters describing mail address. "
   ::= { gs2352SMTP 9 }

gs2352SMTPEmailAddress4 OBJECT-TYPE
   SYNTAX      DisplayString
   MAX-ACCESS  read-write
   STATUS      current
   DESCRIPTION
       " Up to 47 characters describing mail address. "
   ::= { gs2352SMTP 10 }

gs2352SMTPEmailAddress5 OBJECT-TYPE
   SYNTAX      DisplayString
   MAX-ACCESS  read-write
   STATUS      current
   DESCRIPTION
       " Up to 47 characters describing mail address. "
   ::= { gs2352SMTP 11 }

gs2352SMTPEmailAddress6 OBJECT-TYPE
   SYNTAX      DisplayString
   MAX-ACCESS  read-write
   STATUS      current
   DESCRIPTION
       " Up to 47 characters describing mail address. "
   ::= { gs2352SMTP 12 }


gs2352ACL                                                   OBJECT IDENTIFIER ::= { gs2352Configuration 9 }

gs2352ACLPortsConfTable OBJECT-TYPE
   SYNTAX      SEQUENCE OF GS2352ACLPortsConfEntry
   MAX-ACCESS  not-accessible
   STATUS      current
   DESCRIPTION
       " "
   ::= { gs2352ACL 1 }

gs2352ACLPortsConfEntry OBJECT-TYPE
   SYNTAX      GS2352ACLPortsConfEntry
   MAX-ACCESS  not-accessible
   STATUS      current
   DESCRIPTION
       ""
   INDEX    { gs2352ACLPortsConfPort  }
   ::= { gs2352ACLPortsConfTable 1 }

GS2352ACLPortsConfEntry ::= SEQUENCE {
   gs2352ACLPortsConfPort               Integer32,
   gs2352ACLPortsConfPolicyID           Integer32,
   gs2352ACLPortsConfAction             INTEGER,
   gs2352ACLPortsConfRateLimiterID      Integer32,
   gs2352ACLPortsConfPortRedirect       Integer32,
   gs2352ACLPortsConfLogging            INTEGER,
   gs2352ACLPortsConfShutdown           INTEGER,
   gs2352ACLPortsConfState              INTEGER,
   gs2352ACLPortsConfCounter            Counter32
}

gs2352ACLPortsConfPort OBJECT-TYPE
   SYNTAX      Integer32(1..4095)
   MAX-ACCESS  not-accessible
   STATUS      current
   DESCRIPTION
       " "
   ::= { gs2352ACLPortsConfEntry 1 }

gs2352ACLPortsConfPolicyID OBJECT-TYPE
   SYNTAX      Integer32(0..255)
   MAX-ACCESS  read-write
   STATUS      current
   DESCRIPTION
       "default: 0, range : 0 - 255 "
   ::= { gs2352ACLPortsConfEntry 2 }

gs2352ACLPortsConfAction OBJECT-TYPE
   SYNTAX      INTEGER { deny(0), permit(1) }
   MAX-ACCESS  read-write
   STATUS      current
   DESCRIPTION
       "default: 1,
        0: Deny
        1: Permit"
   ::= { gs2352ACLPortsConfEntry 3 }

gs2352ACLPortsConfRateLimiterID OBJECT-TYPE
   SYNTAX      Integer32(0..12)
   MAX-ACCESS  read-write
   STATUS      current
   DESCRIPTION
       "default: 0,
        0: Disable
        range : 0 - 12 "
   ::= { gs2352ACLPortsConfEntry 4 }

gs2352ACLPortsConfPortRedirect OBJECT-TYPE
   SYNTAX      Integer32(0..4095)
   MAX-ACCESS  read-write
   STATUS      current
   DESCRIPTION
       "default: 0
        0: Disable
        range : 0 - end port number "
   ::= { gs2352ACLPortsConfEntry 5 }

gs2352ACLPortsConfLogging OBJECT-TYPE
   SYNTAX      INTEGER { disable(0), enable(1) }
   MAX-ACCESS  read-write
   STATUS      current
   DESCRIPTION
       "default: 0
        0: Disable
        1: Enable "
   ::= { gs2352ACLPortsConfEntry 7 }

gs2352ACLPortsConfShutdown OBJECT-TYPE
   SYNTAX      INTEGER { disable(0), enable(1) }
   MAX-ACCESS  read-write
   STATUS      current
   DESCRIPTION
       "default: 0
        0: Disable
        1: Enable "
   ::= { gs2352ACLPortsConfEntry 8 }

gs2352ACLPortsConfState OBJECT-TYPE
   SYNTAX      INTEGER { disable(0), enable(1) }
   MAX-ACCESS  read-write
   STATUS      current
   DESCRIPTION
       "default: 1
        0: Disable
        1: Enable "
   ::= { gs2352ACLPortsConfEntry 9 }

gs2352ACLPortsConfCounter OBJECT-TYPE
   SYNTAX      Counter32
   MAX-ACCESS  read-only
   STATUS      current
   DESCRIPTION
       "Counts the number of frames that match this ACE. "
   ::= { gs2352ACLPortsConfEntry 10 }


gs2352ACLRateLimiterTable OBJECT-TYPE
   SYNTAX      SEQUENCE OF GS2352ACLRateLimiterEntry
   MAX-ACCESS  not-accessible
   STATUS      current
   DESCRIPTION
       " "
   ::= { gs2352ACL 2 }

gs2352ACLRateLimiterEntry OBJECT-TYPE
   SYNTAX      GS2352ACLRateLimiterEntry
   MAX-ACCESS  not-accessible
   STATUS      current
   DESCRIPTION
       ""
   INDEX    { gs2352ACLRateLimiterID  }
   ::= { gs2352ACLRateLimiterTable 1 }

GS2352ACLRateLimiterEntry ::= SEQUENCE {
   gs2352ACLRateLimiterID       Integer32,
   gs2352ACLRateLimiterRate     Integer32
}

gs2352ACLRateLimiterID OBJECT-TYPE
   SYNTAX      Integer32(1..12)
   MAX-ACCESS  not-accessible
   STATUS      current
   DESCRIPTION
       " Rate Limiter ID.
         range : 1-12 "
   ::= { gs2352ACLRateLimiterEntry 1 }

gs2352ACLRateLimiterRate OBJECT-TYPE
   SYNTAX      Integer32(0..3276700)
   MAX-ACCESS  read-write
   STATUS      current
   DESCRIPTION
       "default: 1,
        range : <0-3276700> pps
       "
   ::= { gs2352ACLRateLimiterEntry 3 }


gs2352ACLACE                                          OBJECT IDENTIFIER ::= { gs2352ACL 3 }

gs2352ACLACECreate OBJECT-TYPE
   SYNTAX       INTEGER { none(0), create(1) }
   MAX-ACCESS   read-write
   STATUS       current
   DESCRIPTION
       "default: 0
        0 : None  (read only)
        1 : Create an ACE entry"
   ::= { gs2352ACLACE 1 }

gs2352ACLACETable OBJECT-TYPE
   SYNTAX      SEQUENCE OF GS2352ACLACEEntry
   MAX-ACCESS  not-accessible
   STATUS      current
   DESCRIPTION
       " Create ACL ACE entry. "
   ::= { gs2352ACLACE 2 }

gs2352ACLACEEntry OBJECT-TYPE
   SYNTAX      GS2352ACLACEEntry
   MAX-ACCESS  not-accessible
   STATUS      current
   DESCRIPTION
       ""
   INDEX    { gs2352ACLACEIndex  }
   ::= { gs2352ACLACETable 1 }

GS2352ACLACEEntry ::= SEQUENCE {
   gs2352ACLACEIndex                Integer32,
   gs2352ACLACEID                   Integer32,
   gs2352ACLACENextID               Integer32,
   gs2352ACLACEIngressPort          DisplayString,
   gs2352ACLACEPortPolicyNumber     Integer32,

   gs2352ACLACEPortPolicyBitmask    Integer32,
   gs2352ACLACEFrameType            INTEGER,
   gs2352ACLACEAction               INTEGER,
   gs2352ACLACEDenyPortRedirect     DisplayString,
   gs2352ACLACELogging              INTEGER,

   gs2352ACLACERateLimiter          Integer32,
   gs2352ACLACEShutdown             INTEGER,
   gs2352ACLACEVLANTagPriority      Integer32,

   gs2352ACLACEVLANVID              Integer32,
   gs2352ACLACEEtherType            Integer32,
   gs2352ACLACESMAC                 DisplayString,
   gs2352ACLACEDMACType             INTEGER,
   gs2352ACLACEDMAC                 DisplayString,

   gs2352ACLACEArpOpcode            INTEGER,
   gs2352ACLACEArpFlagsRequestReply INTEGER,
   gs2352ACLACEArpFlagsArpSmac      INTEGER,
   gs2352ACLACEArpFlagsRarpDmac     INTEGER,
   gs2352ACLACEArpFlagsLength       INTEGER,

   gs2352ACLACEArpFlagsIp           INTEGER,
   gs2352ACLACEArpFlagsEthernet     INTEGER,
   gs2352ACLACESIPType              INTEGER,
   gs2352ACLACESIPIPAddress         IpAddress,
   gs2352ACLACESIPNetworkPrefix     Integer32,

   gs2352ACLACEDIPType              INTEGER,
   gs2352ACLACEDIPIPAddress         IpAddress,
   gs2352ACLACEDIPNetworkPrefix     Integer32,

   gs2352ACLACEIPProtocol           Integer32,
   gs2352ACLACEIPFlagsTTL           INTEGER,
   gs2352ACLACEIPFlagsOptions       INTEGER,
   gs2352ACLACEIPFlagsFragment      INTEGER,
   gs2352ACLACEICMPType             Integer32,

   gs2352ACLACEICMPCode             Integer32,
   gs2352ACLACESourcePortMin        Integer32,
   gs2352ACLACESourcePortMax        Integer32,
   gs2352ACLACEDestPortMin          Integer32,
   gs2352ACLACEDestPortMax          Integer32,

   gs2352ACLACETCPFlagsFin          INTEGER,
   gs2352ACLACETCPFlagsSyn          INTEGER,
   gs2352ACLACETCPFlagsRst          INTEGER,
   gs2352ACLACETCPFlagsPsh          INTEGER,
   gs2352ACLACETCPFlagsAck          INTEGER,

   gs2352ACLACETCPFlagsUrg          INTEGER,

   gs2352ACLACERowStatus            INTEGER
}

gs2352ACLACEIndex OBJECT-TYPE
   SYNTAX      Integer32 (1..256)
   MAX-ACCESS  not-accessible
   STATUS      current
   DESCRIPTION
       " "
   ::= { gs2352ACLACEEntry 1 }

gs2352ACLACEID OBJECT-TYPE
   SYNTAX      Integer32 (1..256)
   MAX-ACCESS  read-write
   STATUS      current
   DESCRIPTION
       " If the ACE ID is specified and an entry with this ACE ID
         already exists, the ACE will be modified. Otherwise, a
         new ACE will be added.
         range : 1 - 256. "
   ::= { gs2352ACLACEEntry 2 }

gs2352ACLACENextID OBJECT-TYPE
   SYNTAX      Integer32 (0..256)
   MAX-ACCESS  read-write
   STATUS      current
   DESCRIPTION
       " If the next ACE ID is non zero, the ACE will be placed
         before this ACE in the list. If the next ACE ID is zero,
         the ACE will be placed last in the list.
         range : 0 - 256. "
   ::= { gs2352ACLACEEntry 3 }

gs2352ACLACEIngressPort OBJECT-TYPE
   SYNTAX      DisplayString
   MAX-ACCESS  read-write
   STATUS      current
   DESCRIPTION
       " Indicates the ingress port of the ACE. Possible values are:
         All: The ACE will match all ingress port.
         Port: The ACE will match a specific ingress port.Format: 1,3,6."
   ::= { gs2352ACLACEEntry 4 }

gs2352ACLACEPortPolicyNumber OBJECT-TYPE
   SYNTAX      Integer32 (0..255)
   MAX-ACCESS  read-write
   STATUS      current
   DESCRIPTION
       " policy value.
         range : 0 - 255. "
   ::= { gs2352ACLACEEntry 5 }

gs2352ACLACEPortPolicyBitmask OBJECT-TYPE
   SYNTAX      Integer32 (0..255)
   MAX-ACCESS  read-write
   STATUS      current
   DESCRIPTION
       " policy bitmask.
         range : 0 - 255(0xff). "
   ::= { gs2352ACLACEEntry 6 }

gs2352ACLACEFrameType OBJECT-TYPE
   SYNTAX      INTEGER {
                        any(0),
                        arp(1),
                        etype(2),
                        icmp(3),
                        ipv4(4),
                        tcp(5),
                        udp(6)
                        }
   MAX-ACCESS  read-write
   STATUS      current
   DESCRIPTION
       " 0: any,
         1: arp,
         2: etype,
         3: icmp,
         4: ipv4,
         5: tcp,
         6: udp."
   ::= { gs2352ACLACEEntry 7 }

gs2352ACLACEAction OBJECT-TYPE
   SYNTAX      INTEGER { deny(0), permit(1) }
   MAX-ACCESS  read-write
   STATUS      current
   DESCRIPTION
       "default: 1,
        0: Deny
        1: Permit"
   ::= { gs2352ACLACEEntry 8 }

gs2352ACLACEDenyPortRedirect OBJECT-TYPE
   SYNTAX      DisplayString
   MAX-ACCESS  read-write
   STATUS      current
   DESCRIPTION
       " Frames that hit the ACE are redirected to the port number specified here.
         Disabled: indicates that the port redirect operation is disabled.
         Port Format: 1,3,6."
   ::= { gs2352ACLACEEntry 9 }

gs2352ACLACELogging OBJECT-TYPE
   SYNTAX      INTEGER { disable(0), enable(1) }
   MAX-ACCESS  read-write
   STATUS      current
   DESCRIPTION
       "default: 0,
        0: disable - Frames matching the ACE are not logged.
        1: enable - Frames matching the ACE are stored in the system log."
   ::= { gs2352ACLACEEntry 10 }

gs2352ACLACERateLimiter OBJECT-TYPE
   SYNTAX      Integer32(0..12)
   MAX-ACCESS  read-write
   STATUS      current
   DESCRIPTION
       "default: 0,
        0: Disable
        range : 0 - 12 "
   ::= { gs2352ACLACEEntry 12 }

gs2352ACLACEShutdown OBJECT-TYPE
   SYNTAX      INTEGER { disable(0), enable(1) }
   MAX-ACCESS  read-write
   STATUS      current
   DESCRIPTION
       "default: 0,
        0: disable - Port shut down is disabled for the AC.
        1: enable - If a frame matches the ACE, the ingress port will be disabled."
   ::= { gs2352ACLACEEntry 13 }

gs2352ACLACEVLANTagPriority OBJECT-TYPE
   SYNTAX      Integer32(0..8)
   MAX-ACCESS  read-write
   STATUS      current
   DESCRIPTION
       "Specify the tag priority for this ACE.
        The tag priority can't be set when 802.1Q Tagged is disabled
        default: 8,
        8: Any,
        range : 0 - 8 "
   ::= { gs2352ACLACEEntry 15 }

gs2352ACLACEVLANVID OBJECT-TYPE
   SYNTAX      Integer32(0..4094)
   MAX-ACCESS  read-write
   STATUS      current
   DESCRIPTION
       "Specify the VLAN ID filter for this ACE.
        The vid can't be set when 802.1Q Tagged is disabled.
        default: 0,
        0: Any - No VLAN ID filter is specified.
        range : 0 - 4094 "
   ::= { gs2352ACLACEEntry 16 }

gs2352ACLACEEtherType OBJECT-TYPE
   SYNTAX      Integer32(0..65535)
   MAX-ACCESS  read-write
   STATUS      current
   DESCRIPTION
       " 0: Any - Any but excluding 0x0800(IPv4) 0x0806(ARP) and 0x86DD(IPv6).
         range : 0 or 1536(0x0600)- 65535(0xffff). "
   ::= { gs2352ACLACEEntry 17 }

gs2352ACLACESMAC OBJECT-TYPE
   SYNTAX      DisplayString
   MAX-ACCESS  read-write
   STATUS      current
   DESCRIPTION
       " Configure source MAC address for this ACE.
         <mac-address>: A frame that hits this ACE matches this source MAC address value.
         Any: Don't care."
   ::= { gs2352ACLACEEntry 18 }

gs2352ACLACEDMACType OBJECT-TYPE
   SYNTAX      INTEGER { any(0), broadcast(1), unicast(2), multicast(3) , macaddress(4) }
   MAX-ACCESS  read-write
   STATUS      current
   DESCRIPTION
       "DMAC Type.
        default: 0,
        0: Any - Don't care.
        1: Broadcast - Frame must be broadcast.
        2: Unicast - Frame must be unicast.
        3: Multicast - Frame must be multicast.
        4: mac address
        range : 0 - 4 "
   ::= { gs2352ACLACEEntry 19 }

gs2352ACLACEDMAC OBJECT-TYPE
   SYNTAX      DisplayString
   MAX-ACCESS  read-write
   STATUS      current
   DESCRIPTION
       " Configure destination MAC address for this ACE.
         <mac-address>: A frame that hits this ACE matches this destination MAC address value.
         Any: Don't care.
         Broadcast: Frame must be broadcast.
         Unicast: Frame must be unicast.
         Multicast: Frame must be multicast. "
   ::= { gs2352ACLACEEntry 20 }

gs2352ACLACEArpOpcode OBJECT-TYPE
   SYNTAX      INTEGER { any(0), arp(1), rarp(2), other(3), noData(4) }
   MAX-ACCESS  read-write
   STATUS      current
   DESCRIPTION
       "Configure ARP opcode for this ACE.
        default: 0,
        0: Any - Don't care.
        1: arp.
        2: rarp.
        3: other.
        4: No data.
        range : 0 - 4 "
   ::= { gs2352ACLACEEntry 21 }

gs2352ACLACEArpFlagsRequestReply OBJECT-TYPE
   SYNTAX      INTEGER { reply(0), request(1), any(2), noData(3)}
   MAX-ACCESS  read-write
   STATUS      current
   DESCRIPTION
       "Specify the available ARP/RARP opcode (OP) flag for this ACE.
        default: 2,
        0: Frame must have ARP Reply or RARP Reply OP flag.
        1: Frame must have ARP Request or RARP Request OP flag set.
        2: Any - Don't care.
        3: No data.
        range : 0 - 3 "
   ::= { gs2352ACLACEEntry 22 }

gs2352ACLACEArpFlagsArpSmac OBJECT-TYPE
   SYNTAX      INTEGER { notEqualSMAC(0), equalSMAC(1), any(2), noData(3)}
   MAX-ACCESS  read-write
   STATUS      current
   DESCRIPTION
       "Specify whether frames can hit the action according to their sender hardware address field (SHA) settings.
        default: 2,
        0: ARP frames where SHA is not equal to the SMAC address.
        1: ARP frames where SHA is equal to the SMAC address.
        2: Any - Don't care.
        3: No data.
        range : 0 - 3 "
   ::= { gs2352ACLACEEntry 23 }

gs2352ACLACEArpFlagsRarpDmac OBJECT-TYPE
   SYNTAX      INTEGER { notEqualDMAC(0), equalDMAC(1), any(2), noData(3)}
   MAX-ACCESS  read-write
   STATUS      current
   DESCRIPTION
       "Specify whether frames can hit the action according to their target hardware address field (THA) settings.
        default: 2,
        0: RARP frames where THA is not equal to the DMAC address.
        1: RARP frames where THA is equal to the DMAC address.
        2: Any - Don't care.
        3: No data.
        range : 0 - 3 "
   ::= { gs2352ACLACEEntry 24 }

gs2352ACLACEArpFlagsLength OBJECT-TYPE
   SYNTAX      INTEGER(0..3)
   MAX-ACCESS  read-write
   STATUS      current
   DESCRIPTION
       "Specify whether frames can hit the action according to their ARP/RARP hardware address length (HLN) and
        protocol address length (PLN) settings.
        default: 2,
        0: ARP/RARP frames where the HLN is not equal to Ethernet(0x06) or the (PLN) is not equal to IPv4(0x04).
        1: ARP/RARP frames where the HLN is equal to Ethernet (0x06) and the (PLN) is equal to IPv4(0x04).
        2: Any - Don't care.
        3: No data.
        range : 0 - 3 "
   ::= { gs2352ACLACEEntry 25 }

gs2352ACLACEArpFlagsIp OBJECT-TYPE
   SYNTAX      INTEGER(0..3)
   MAX-ACCESS  read-write
   STATUS      current
   DESCRIPTION
       "Specify whether frames can hit the action according to their ARP/RARP hardware address space (HRD) settings.
        default: 2,
        0: ARP/RARP frames where the HLD is not equal to Ethernet(1).
        1: ARP/RARP frames where the HLD is equal to Ethernet(1).
        2: Any - Don't care.
        3: No data.
        range : 0 - 3 "
   ::= { gs2352ACLACEEntry 26 }

gs2352ACLACEArpFlagsEthernet OBJECT-TYPE
   SYNTAX      INTEGER(0..3)
   MAX-ACCESS  read-write
   STATUS      current
   DESCRIPTION
       "Specify whether frames can hit the action according to their ARP/RARP protocol address space (PRO) settings.
        default: 2,
        0: ARP/RARP frames where the PRO is not equal to IP\n(0x800).
        1: ARP/RARP frames where the PRO is equal to IP(0x800).
        2: Any - Don't care.
        3: No data.
        range : 0 - 3 "
   ::= { gs2352ACLACEEntry 27 }

gs2352ACLACESIPType OBJECT-TYPE
   SYNTAX      INTEGER { any(0), ip(1), noData(2) }
   MAX-ACCESS  read-write
   STATUS      current
   DESCRIPTION
       "Configure source IP address for this ACE.
        default: 0,
        0: Any - Don't care.
        1: IP Address.
        2: No data.
        range : 0 - 2"
   ::= { gs2352ACLACEEntry 28 }

gs2352ACLACESIPIPAddress OBJECT-TYPE
   SYNTAX      IpAddress
   MAX-ACCESS  read-write
   STATUS      current
   DESCRIPTION
       "A frame that hits this ACE matches this source IP address value."
   ::= { gs2352ACLACEEntry 29 }

gs2352ACLACESIPNetworkPrefix OBJECT-TYPE
   SYNTAX      Integer32(1..32)
   MAX-ACCESS  read-write
   STATUS      current
   DESCRIPTION
       "Network prefix.
        default: 32,
        0: No data.
        range : 1 - 32"
   ::= { gs2352ACLACEEntry 30 }


gs2352ACLACEDIPType OBJECT-TYPE
   SYNTAX      INTEGER { any(0), ip(1),noData(2) }
   MAX-ACCESS  read-write
   STATUS      current
   DESCRIPTION
       "Configure destination IP address for this ACE.
        default: 0,
        0: Any - Don't care.
        1: IP Address.
        2: No data.
        range : 0 - 1"
   ::= { gs2352ACLACEEntry 32 }

gs2352ACLACEDIPIPAddress OBJECT-TYPE
   SYNTAX      IpAddress
   MAX-ACCESS  read-write
   STATUS      current
   DESCRIPTION
       "A frame that hits this ACE matches this destination IP address value."
   ::= { gs2352ACLACEEntry 33 }

gs2352ACLACEDIPNetworkPrefix OBJECT-TYPE
   SYNTAX      Integer32(0..32)
   MAX-ACCESS  read-write
   STATUS      current
   DESCRIPTION
       "Network prefix.
        default: 32,
        0: No data.
        range : 1 - 32"
   ::= { gs2352ACLACEEntry 34 }


gs2352ACLACEIPProtocol OBJECT-TYPE
   SYNTAX      Integer32(0..257)
   MAX-ACCESS  read-write
   STATUS      current
   DESCRIPTION
       "Configure IP protocol for this ACE.
        default: 256,
        256: Any - Don't care.
        257: No data.
        range : 0 - 257"
   ::= { gs2352ACLACEEntry 36 }

gs2352ACLACEIPFlagsTTL OBJECT-TYPE
   SYNTAX      INTEGER (0..3)
   MAX-ACCESS  read-write
   STATUS      current
   DESCRIPTION
       "Configure IP Time-to-Live flags for this ACE.
        default: 2,
        0: IPv4 frames with a Time-to-Live field is equal to zero.
        1: IPv4 frames with a Time-to-Live field greater than zero.
        2: Any - Don't care.
        3: No data.
        range : 0 - 3 "
   ::= { gs2352ACLACEEntry 37 }

gs2352ACLACEIPFlagsOptions OBJECT-TYPE
   SYNTAX      INTEGER { unset(0), set(1), any(2), noData(3) }
   MAX-ACCESS  read-write
   STATUS      current
   DESCRIPTION
       "Configure IP options flag for this ACE.
        default: 2,
        0: IPv4 frames where the options flag is unset.
        1: IPv4 frames where the options flag is set.
        2: Any - Don't care.
        3: No data.
        range : 0 - 3 "
   ::= { gs2352ACLACEEntry 38 }

gs2352ACLACEIPFlagsFragment OBJECT-TYPE
   SYNTAX      INTEGER(0..3)
   MAX-ACCESS  read-write
   STATUS      current
   DESCRIPTION
       "Configure IP fragment offset flags for this ACE.
        default: 2,
        0: IPv4 frames where the MF bit is unset and the FRAG OFFSET field is equal zero.
        1: IPv4 frames where the MF bit is set or the FRAG OFFSET field is greater than zero.
        2: Any - Don't care.
        3: No data.
        range : 0 - 3 "
   ::= { gs2352ACLACEEntry 39 }

gs2352ACLACEICMPType OBJECT-TYPE
   SYNTAX      Integer32(0..257)
   MAX-ACCESS  read-write
   STATUS      current
   DESCRIPTION
       "Configure ICMP type for this ACE.
        default: 256,
        256: Any - Don't care.
        257: No data.
        range : 0 - 257"
   ::= { gs2352ACLACEEntry 40 }

gs2352ACLACEICMPCode OBJECT-TYPE
   SYNTAX      Integer32(0..257)
   MAX-ACCESS  read-write
   STATUS      current
   DESCRIPTION
       "Configure ICMP code for this ACE.
        default: 256,
        256: Any - Don't care.
        257: No data.
        range : 0 - 257"
   ::= { gs2352ACLACEEntry 41 }

gs2352ACLACESourcePortMin OBJECT-TYPE
   SYNTAX      Integer32(0..65536)
   MAX-ACCESS  read-write
   STATUS      current
   DESCRIPTION
       "Configure Source UDP/TCP port range for this ACE.
        default: 0,
        65536: No data.
        range : 0 - 65536"
   ::= { gs2352ACLACEEntry 42 }

gs2352ACLACESourcePortMax OBJECT-TYPE
   SYNTAX      Integer32(0..65536)
   MAX-ACCESS  read-write
   STATUS      current
   DESCRIPTION
       "Configure Source UDP/TCP port range for this ACE.
        default: 0,
        65536: No data.
        range : 0 - 65536"
   ::= { gs2352ACLACEEntry 43 }

gs2352ACLACEDestPortMin OBJECT-TYPE
   SYNTAX      Integer32(0..65536)
   MAX-ACCESS  read-write
   STATUS      current
   DESCRIPTION
       "Configure Destination UDP/TCP port range for this ACE.
        default: 0,
        65536: No data.
        range : 0 - 65536"
   ::= { gs2352ACLACEEntry 44 }

gs2352ACLACEDestPortMax OBJECT-TYPE
   SYNTAX      Integer32(0..65536)
   MAX-ACCESS  read-write
   STATUS      current
   DESCRIPTION
       "Configure Destination UDP/TCP port range for this ACE.
        default: 0,
        65536: No data.
        range : 0 - 65536"
   ::= { gs2352ACLACEEntry 45 }

gs2352ACLACETCPFlagsFin OBJECT-TYPE
   SYNTAX      INTEGER { unset(0), set(1), any(2), noData(3) }
   MAX-ACCESS  read-write
   STATUS      current
   DESCRIPTION
       "Configure TCP (FIN) flags for this ACE.
        default: 2,
        0: TCP frames where the FIN field is unset.
        1: TCP frames where the FIN field is set.
        2: Any - Don't care.
        3: No data.
        range : 0 - 3 "
   ::= { gs2352ACLACEEntry 46 }

gs2352ACLACETCPFlagsSyn OBJECT-TYPE
   SYNTAX      INTEGER { unset(0), set(1), any(2), noData(3) }
   MAX-ACCESS  read-write
   STATUS      current
   DESCRIPTION
       "Configure TCP (SYN) flags for this ACE.
        default: 2,
        0: TCP frames where the SYN field is unset.
        1: TCP frames where the SYN field is set.
        2: Any - Don't care.
        3: No data.
        range : 0 - 3 "
   ::= { gs2352ACLACEEntry 47 }

gs2352ACLACETCPFlagsRst OBJECT-TYPE
   SYNTAX      INTEGER { unset(0), set(1), any(2), noData(3) }
   MAX-ACCESS  read-write
   STATUS      current
   DESCRIPTION
       "Configure TCP (RST) flags for this ACE.
        default: 2,
        0: TCP frames where the RST field is unset.
        1: TCP frames where the RST field is set.
        2: Any - Don't care.
        3: No data.
        range : 0 - 3 "
   ::= { gs2352ACLACEEntry 48 }

gs2352ACLACETCPFlagsPsh OBJECT-TYPE
   SYNTAX      INTEGER { unset(0), set(1), any(2), noData(3) }
   MAX-ACCESS  read-write
   STATUS      current
   DESCRIPTION
       "Configure TCP (PSH) flags for this ACE.
        default: 2,
        0: TCP frames where the PSH field is unset.
        1: TCP frames where the PSH field is set.
        2: Any - Don't care.
        3: No data.
        range : 0 - 3 "
   ::= { gs2352ACLACEEntry 49 }

gs2352ACLACETCPFlagsAck OBJECT-TYPE
   SYNTAX      INTEGER { unset(0), set(1), any(2), noData(3) }
   MAX-ACCESS  read-write
   STATUS      current
   DESCRIPTION
       "Configure TCP (ACK) flags for this ACE.
        default: 2,
        0: TCP frames where the ACK field is unset.
        1: TCP frames where the ACK field is set.
        2: Any - Don't care.
        3: No data.
        range : 0 - 3 "
   ::= { gs2352ACLACEEntry 50 }

gs2352ACLACETCPFlagsUrg OBJECT-TYPE
   SYNTAX      INTEGER { unset(0), set(1), any(2), noData(3) }
   MAX-ACCESS  read-write
   STATUS      current
   DESCRIPTION
       "Configure TCP (URG) flags for this ACE.
        default: 2,
        0: TCP frames where the URG field is unset.
        1: TCP frames where the URG field is set.
        2: Any - Don't care.
        3: No data.
        range : 0 - 3 "
   ::= { gs2352ACLACEEntry 51 }

gs2352ACLACERowStatus OBJECT-TYPE
   SYNTAX      INTEGER { active(1), notInservice(2), destroy(4), undo(5) }
   MAX-ACCESS  read-write
   STATUS      current
   DESCRIPTION
       " 1: active
         2: notInservice
         4: destroy
         5: undo"
   ::= { gs2352ACLACEEntry 66 }


gs2352ACLACEClear OBJECT-TYPE
   SYNTAX       INTEGER { noAction(0), clear(1) }
   MAX-ACCESS   read-write
   STATUS       current
   DESCRIPTION
       "default: 0
        0 : No action
        1 : Clear all ACL counters."
   ::= { gs2352ACLACE 3 }

gs2352ACLACEMoveACEID OBJECT-TYPE
   SYNTAX       Integer32(0..256)
   MAX-ACCESS   read-write
   STATUS       current
   DESCRIPTION
       "Move ACE,
        default: 0
        ACE ID must be exist.
        range : 0 - 256."
   ::= { gs2352ACLACE 4 }

gs2352ACLACEMoveNextACEID OBJECT-TYPE
   SYNTAX       Integer32 (0..256)
   MAX-ACCESS   read-write
   STATUS       current
   DESCRIPTION
       "Move ACE,
        default: 0
        If the next ACE ID is non zero, the ACE will be placed before this ACE in the list. If the next ACE ID is zero,
        the ACE will be placed last in the list.
        range : 0 - 256."
   ::= { gs2352ACLACE 5 }

gs2352ACLACEStatusTable OBJECT-TYPE
   SYNTAX      SEQUENCE OF GS2352ACLACEStatusEntry
   MAX-ACCESS  not-accessible
   STATUS      current
   DESCRIPTION
       " ACL ACE Status entry. "
   ::= { gs2352ACLACE 6 }

gs2352ACLACEStatusEntry OBJECT-TYPE
   SYNTAX      GS2352ACLACEStatusEntry
   MAX-ACCESS  not-accessible
   STATUS      current
   DESCRIPTION
       ""
   INDEX    { gs2352ACLACEStatusIndex  }
   ::= { gs2352ACLACEStatusTable 1 }

GS2352ACLACEStatusEntry ::= SEQUENCE {
   gs2352ACLACEStatusIndex          Integer32,
   gs2352ACLACEStatusUser           DisplayString,
   gs2352ACLACEStatusID             Integer32,
   gs2352ACLACEStatusIngressPort    DisplayString,
   gs2352ACLACEStatusFrameType      DisplayString,
   gs2352ACLACEStatusAction         DisplayString,
   gs2352ACLACEStatusRateLimiter    DisplayString,
   gs2352ACLACEStatusPortCopy       DisplayString,
   gs2352ACLACEStatusMirror         DisplayString,
   gs2352ACLACEStatusCPU            DisplayString,
   gs2352ACLACEStatusCounter        Counter32,
   gs2352ACLACEStatusConflict       DisplayString
}

gs2352ACLACEStatusIndex OBJECT-TYPE
   SYNTAX      Integer32(1..256)
   MAX-ACCESS  not-accessible
   STATUS      current
   DESCRIPTION
       " "
   ::= { gs2352ACLACEStatusEntry 1 }

gs2352ACLACEStatusUser OBJECT-TYPE
   SYNTAX      DisplayString
   MAX-ACCESS  read-only
   STATUS      current
   DESCRIPTION
       " Indicates the ACL user.
         S : Static.
         IPMG : IP Management.
         IPSG : IP Source Guard.
         IPMC : IPMC.
         ARPI : Arp Inspection.
         UPnP : UPnP.
         DHCP : DHCP. "
   ::= { gs2352ACLACEStatusEntry 2 }

gs2352ACLACEStatusID OBJECT-TYPE
   SYNTAX      Integer32(1..256)
   MAX-ACCESS  read-only
   STATUS      current
   DESCRIPTION
       " ACE ID.
         range : 1 - 256. "
   ::= { gs2352ACLACEStatusEntry 3 }

gs2352ACLACEStatusIngressPort OBJECT-TYPE
   SYNTAX      DisplayString
   MAX-ACCESS  read-only
   STATUS      current
   DESCRIPTION
       " Indicates the ingress port of the ACE. Possible values are:
         All: The ACE will match all ingress port.
         Port: The ACE will match a specific ingress port. "
   ::= { gs2352ACLACEStatusEntry 4 }

gs2352ACLACEStatusFrameType OBJECT-TYPE
   SYNTAX      DisplayString
   MAX-ACCESS  read-only
   STATUS      current
   DESCRIPTION
       " Indicates the frame type of the ACE. "
   ::= { gs2352ACLACEStatusEntry 5 }

gs2352ACLACEStatusAction OBJECT-TYPE
   SYNTAX      DisplayString
   MAX-ACCESS  read-only
   STATUS      current
   DESCRIPTION
       " Indicates the forwarding action of the ACE. "
   ::= { gs2352ACLACEStatusEntry 6 }

gs2352ACLACEStatusRateLimiter OBJECT-TYPE
   SYNTAX      DisplayString
   MAX-ACCESS  read-only
   STATUS      current
   DESCRIPTION
       " Indicates the rate limiter number of the ACE. "
   ::= { gs2352ACLACEStatusEntry 7 }

gs2352ACLACEStatusPortCopy OBJECT-TYPE
   SYNTAX      DisplayString
   MAX-ACCESS  read-only
   STATUS      current
   DESCRIPTION
       " Indicates the port redirect operation of the ACE. Frames matching the ACE are redirected to the port number. "
   ::= { gs2352ACLACEStatusEntry 8 }

gs2352ACLACEStatusMirror OBJECT-TYPE
   SYNTAX      DisplayString
   MAX-ACCESS  read-only
   STATUS      current
   DESCRIPTION
       " Specify the mirror operation of this port. "
   ::= { gs2352ACLACEStatusEntry 9 }

gs2352ACLACEStatusCPU OBJECT-TYPE
   SYNTAX      DisplayString
   MAX-ACCESS  read-only
   STATUS      current
   DESCRIPTION
       " Forward packet that matched the specific ACE to CPU. "
   ::= { gs2352ACLACEStatusEntry 10 }

gs2352ACLACEStatusCounter OBJECT-TYPE
   SYNTAX      Counter32
   MAX-ACCESS  read-only
   STATUS      current
   DESCRIPTION
       " The counter indicates the number of times the ACE was hit by a frame. "
   ::= { gs2352ACLACEStatusEntry 11 }

gs2352ACLACEStatusConflict OBJECT-TYPE
   SYNTAX      DisplayString
   MAX-ACCESS  read-only
   STATUS      current
   DESCRIPTION
       " Indicates the hardware status of the specific ACE. The specific ACE is not applied to the hardware due to hardware limitations. "
   ::= { gs2352ACLACEStatusEntry 12 }

gs2352LoopProtection                                                  OBJECT IDENTIFIER ::= { gs2352Configuration 12 }

gs2352LoopProtectionConfig                                            OBJECT IDENTIFIER ::= { gs2352LoopProtection 1 }

gs2352LoopProtectionGlobalEnable OBJECT-TYPE
   SYNTAX      INTEGER { disable(0), enable(1) }
   MAX-ACCESS  read-write
   STATUS      current
   DESCRIPTION
       "Configure loop protection mode.
        0: disable,
        1: enable,
        default: disable. "
   ::= { gs2352LoopProtectionConfig 1 }

gs2352LoopProtectionTranmisstionTime OBJECT-TYPE
   SYNTAX      Integer32(1..10)
   MAX-ACCESS  read-write
   STATUS      current
   DESCRIPTION
       "Configure loop protection transmit interval.
        default: 5,
        range: 1-10. "
   ::= { gs2352LoopProtectionConfig 2 }

gs2352LoopProtectionShutdownTime OBJECT-TYPE
   SYNTAX      Integer32(0..604800)
   MAX-ACCESS  read-write
   STATUS      current
   DESCRIPTION
       "Configure loop protection shutdown time.
        default: 180,
        range: 0-604800. "
   ::= { gs2352LoopProtectionConfig 3 }

gs2352LoopProtectionConfigurationTable OBJECT-TYPE
   SYNTAX      SEQUENCE OF GS2352LoopProtectionConfigurationEntry
   MAX-ACCESS  not-accessible
   STATUS      current
   DESCRIPTION
       " Show Loop Protection configurations. "
   ::= { gs2352LoopProtectionConfig 4 }

gs2352LoopProtectionConfigurationEntry OBJECT-TYPE
   SYNTAX      GS2352LoopProtectionConfigurationEntry
   MAX-ACCESS  not-accessible
   STATUS      current
   DESCRIPTION
       ""
   INDEX    { gs2352LoopProtectionConfPort  }
   ::= { gs2352LoopProtectionConfigurationTable 1 }

GS2352LoopProtectionConfigurationEntry ::= SEQUENCE {
   gs2352LoopProtectionConfPort	    Integer32,
   gs2352LoopProtectionConfEnable	INTEGER,
   gs2352LoopProtectionConfAction	INTEGER,
   gs2352LoopProtectionConfTxmode	INTEGER
}

gs2352LoopProtectionConfPort OBJECT-TYPE
   SYNTAX      Integer32(1..4095)
   MAX-ACCESS  not-accessible
   STATUS      current
   DESCRIPTION
       " port, range : 1 - port number. "
   ::= { gs2352LoopProtectionConfigurationEntry 1 }

gs2352LoopProtectionConfEnable OBJECT-TYPE
   SYNTAX      INTEGER { disable(0), enable(1) }
   MAX-ACCESS  read-write
   STATUS      current
   DESCRIPTION
       "Configure loop protection port mode.
        0: disable,
        1: enable,
        default: enable. "
   ::= { gs2352LoopProtectionConfigurationEntry 2 }

gs2352LoopProtectionConfAction OBJECT-TYPE
   SYNTAX      INTEGER { shutdown(0), shutdownLog(1), log(2) }
   MAX-ACCESS  read-write
   STATUS      current
   DESCRIPTION
       " Configure loop protection port action.
         0: Shutdown port,
         1: Shutdown port and Log,
         2: Log Only,
         default: Shutdown port. "
   ::= { gs2352LoopProtectionConfigurationEntry 3 }

gs2352LoopProtectionConfTxmode OBJECT-TYPE
   SYNTAX      INTEGER { disable(0), enable(1) }
   MAX-ACCESS  read-write
   STATUS      current
   DESCRIPTION
       "Configure loop protection port transmit mode.
        0: disable,
        1: enable,
        default: enable. "
   ::= { gs2352LoopProtectionConfigurationEntry 4 }

gs2352LoopProtectionStatusTable OBJECT-TYPE
   SYNTAX      SEQUENCE OF GS2352LoopProtectionStatusEntry
   MAX-ACCESS  not-accessible
   STATUS      current
   DESCRIPTION
       " Show Loop Protection Status. "
   ::= { gs2352LoopProtection 2 }

gs2352LoopProtectionStatusEntry OBJECT-TYPE
   SYNTAX      GS2352LoopProtectionStatusEntry
   MAX-ACCESS  not-accessible
   STATUS      current
   DESCRIPTION
       ""
   INDEX    { gs2352LoopProtectionStatusPort  }
   ::= { gs2352LoopProtectionStatusTable 1 }

GS2352LoopProtectionStatusEntry ::= SEQUENCE {
   gs2352LoopProtectionStatusPort	       Integer32,
   gs2352LoopProtectionStatusAction	       DisplayString,
   gs2352LoopProtectionStatusTransmit	   DisplayString,
   gs2352LoopProtectionStatusLoops	       Integer32,
   gs2352LoopProtectionStatusStatus	       DisplayString,
   gs2352LoopProtectionStatusLoop	       DisplayString,
   gs2352LoopProtectionStatusTimeLastLoop  DisplayString
}

gs2352LoopProtectionStatusPort OBJECT-TYPE
   SYNTAX      Integer32(1..4095)
   MAX-ACCESS  not-accessible
   STATUS      current
   DESCRIPTION
       " port, range : 1 - port number. "
   ::= { gs2352LoopProtectionStatusEntry 1 }

gs2352LoopProtectionStatusAction OBJECT-TYPE
   SYNTAX      DisplayString
   MAX-ACCESS  read-only
   STATUS      current
   DESCRIPTION
       " The currently configured port action. "
   ::= { gs2352LoopProtectionStatusEntry 2 }

gs2352LoopProtectionStatusTransmit OBJECT-TYPE
   SYNTAX      DisplayString
   MAX-ACCESS  read-only
   STATUS      current
   DESCRIPTION
       " The currently configured port transmit mode. "
   ::= { gs2352LoopProtectionStatusEntry 3 }

gs2352LoopProtectionStatusLoops OBJECT-TYPE
   SYNTAX      Integer32(0..1000000)
   MAX-ACCESS  read-only
   STATUS      current
   DESCRIPTION
       " The number of loops detected on this port. "
   ::= { gs2352LoopProtectionStatusEntry 4 }

gs2352LoopProtectionStatusStatus OBJECT-TYPE
   SYNTAX      DisplayString
   MAX-ACCESS  read-only
   STATUS      current
   DESCRIPTION
       " The current loop protection status of the port. "
   ::= { gs2352LoopProtectionStatusEntry 5 }

gs2352LoopProtectionStatusLoop OBJECT-TYPE
   SYNTAX      DisplayString
   MAX-ACCESS  read-only
   STATUS      current
   DESCRIPTION
       " Whether a loop is currently detected on the port. "
   ::= { gs2352LoopProtectionStatusEntry 6 }

gs2352LoopProtectionStatusTimeLastLoop OBJECT-TYPE
   SYNTAX      DisplayString
   MAX-ACCESS  read-only
   STATUS      current
   DESCRIPTION
       " The time of the last loop event detected. "
   ::= { gs2352LoopProtectionStatusEntry 7 }

gs2352Qos                                                             OBJECT IDENTIFIER ::= { gs2352Configuration 14 }

gs2352QosPortClassification                                           OBJECT IDENTIFIER ::= { gs2352Qos 1 }

gs2352QosPortClassificationTable OBJECT-TYPE
   SYNTAX      SEQUENCE OF GS2352QosPortClassificationEntry
   MAX-ACCESS  not-accessible
   STATUS      current
   DESCRIPTION
       " QoS Ingress Port Classification . "
   ::= { gs2352QosPortClassification  1 }

gs2352QosPortClassificationEntry OBJECT-TYPE
   SYNTAX      GS2352QosPortClassificationEntry
   MAX-ACCESS  not-accessible
   STATUS      current
   DESCRIPTION
       ""
   INDEX    { gs2352QosPortClassificationPort  }
   ::= { gs2352QosPortClassificationTable 1 }

GS2352QosPortClassificationEntry ::= SEQUENCE {
   gs2352QosPortClassificationPort	        Integer32,
   gs2352QosPortClassificationQoSclass       Integer32,
   gs2352QosPortClassificationDPlevel	    Integer32,
   gs2352QosPortClassificationPCP	        Integer32,
   gs2352QosPortClassificationDEI	        INTEGER,
   gs2352QosPortClassificationTagClass	    INTEGER,
   gs2352QosPortClassificationDSCPBased      INTEGER
}

gs2352QosPortClassificationPort OBJECT-TYPE
   SYNTAX      Integer32(1..4095)
   MAX-ACCESS  not-accessible
   STATUS      current
   DESCRIPTION
       " port, range : 1 - port number. "
   ::= { gs2352QosPortClassificationEntry 1 }

gs2352QosPortClassificationQoSclass OBJECT-TYPE
   SYNTAX      Integer32(0..7)
   MAX-ACCESS  read-write
   STATUS      current
   DESCRIPTION
      "Controls the default QoS class, i.e., the QoS class
      for frames not classified in any other way. There is
      a one to one mapping between QoS class, queue and priority.
      A QoS class of 0 (zero) has the lowest priority.
      Note: If the QoS class has been dynamically changed, then
      the actual QoS class is shown in parentheses after the
      configured QoS class.

      Configure the default QoS class.
        range: 0-7,
        default: 0. "
   ::= { gs2352QosPortClassificationEntry 2 }

gs2352QosPortClassificationDPlevel OBJECT-TYPE
   SYNTAX      Integer32(0..3)
   MAX-ACCESS  read-write
   STATUS      current
   DESCRIPTION
       " DP level for frames not classified in any other way.
         range: 0-3,
         default: 0. "
   ::= { gs2352QosPortClassificationEntry 3 }

gs2352QosPortClassificationPCP OBJECT-TYPE
   SYNTAX      Integer32(0..7)
   MAX-ACCESS  read-write
   STATUS      current
   DESCRIPTION
      " Priority Code Point. It is a 3-bit field storing the priority level for the 802.1Q frame.
        range: 0-7,
        default: 0. "
   ::= { gs2352QosPortClassificationEntry 4 }

gs2352QosPortClassificationDEI OBJECT-TYPE
   SYNTAX      INTEGER { disable(0), enable(1) }
   MAX-ACCESS  read-write
   STATUS      current
   DESCRIPTION
      " Drop Eligible Indicator. It is a 1-bit field in the VLAN.
        range 0-1,
        default: 0. "
   ::= { gs2352QosPortClassificationEntry 5 }

gs2352QosPortClassificationTagClass OBJECT-TYPE
   SYNTAX      INTEGER { disable(0), enable(1) }
   MAX-ACCESS  read-write
   STATUS      current
   DESCRIPTION
      " Configure the classification mode for tagged frames.
        0: Disable,
        1: Enable,
        default: Disable. "
   ::= { gs2352QosPortClassificationEntry 6 }

gs2352QosPortClassificationDSCPBased OBJECT-TYPE
   SYNTAX      INTEGER { disable(0), enable(1) }
   MAX-ACCESS  read-write
   STATUS      current
   DESCRIPTION
      " Click to Enable DSCP Based QoS Ingress Port Classification.
        0: disable,
        1: enable,
        default: disable. "
   ::= { gs2352QosPortClassificationEntry 7 }

gs2352QoSIngressPortTagClassificationTable OBJECT-TYPE
   SYNTAX      SEQUENCE OF GS2352QoSIngressPortTagClassificationEntry
   MAX-ACCESS  not-accessible
   STATUS      current
   DESCRIPTION
       " Show QoS Ingress Port Tag Classification. "
   ::= { gs2352QosPortClassification 2 }

gs2352QoSIngressPortTagClassificationEntry OBJECT-TYPE
   SYNTAX      GS2352QoSIngressPortTagClassificationEntry
   MAX-ACCESS  not-accessible
   STATUS      current
   DESCRIPTION
       ""
   INDEX    { gs2352QoSIngressPortTagClassificationPort, gs2352QoSIngressPortTagPCP, gs2352QoSIngressPortTagDEI  }
   ::= { gs2352QoSIngressPortTagClassificationTable 1 }

GS2352QoSIngressPortTagClassificationEntry ::= SEQUENCE {
   gs2352QoSIngressPortTagClassificationPort		Integer32,
   gs2352QoSIngressPortTagPCP					INTEGER,
   gs2352QoSIngressPortTagDEI					INTEGER,
   gs2352QoSIngressPortTagQosClass				Integer32,
   gs2352QoSIngressPortTagDPLevel    Integer32
}

gs2352QoSIngressPortTagClassificationPort OBJECT-TYPE
   SYNTAX      Integer32(1..4095)
   MAX-ACCESS  not-accessible
   STATUS      current
   DESCRIPTION
       " port, range : 1 - port number. "
   ::= { gs2352QoSIngressPortTagClassificationEntry 1 }

gs2352QoSIngressPortTagPCP OBJECT-TYPE
   SYNTAX      INTEGER { pcp0(1), pcp1(2), pcp2(3), pcp3(4), pcp4(5), pcp5(6), pcp6(7), pcp7(8) }
   MAX-ACCESS  not-accessible
   STATUS      current
   DESCRIPTION
       " range: 1-8,
         PCP0:1, PCP1:2...  "
   ::= { gs2352QoSIngressPortTagClassificationEntry 2 }

gs2352QoSIngressPortTagDEI OBJECT-TYPE
   SYNTAX      INTEGER { dei0(1), dei1(2) }
   MAX-ACCESS  not-accessible
   STATUS      current
   DESCRIPTION
       " range: 1-2,
         DEI0:1, DEI1:2. "
   ::= { gs2352QoSIngressPortTagClassificationEntry 3 }

gs2352QoSIngressPortTagQosClass OBJECT-TYPE
   SYNTAX      Integer32(0..7)
   MAX-ACCESS  read-write
   STATUS      current
   DESCRIPTION
       " range: 0-7.  "
   ::= { gs2352QoSIngressPortTagClassificationEntry 4 }

gs2352QoSIngressPortTagDPLevel OBJECT-TYPE
   SYNTAX      Integer32(0..3)
   MAX-ACCESS  read-write
   STATUS      current
   DESCRIPTION
       " range: 0-3.  "
   ::= { gs2352QoSIngressPortTagClassificationEntry 5 }

gs2352QosPortPolicingTable OBJECT-TYPE
   SYNTAX      SEQUENCE OF GS2352QosPortPolicingEntry
   MAX-ACCESS  not-accessible
   STATUS      current
   DESCRIPTION
       "  configure the Policer settings for all switch ports. "
   ::= { gs2352Qos  2 }

gs2352QosPortPolicingEntry OBJECT-TYPE
   SYNTAX      GS2352QosPortPolicingEntry
   MAX-ACCESS  not-accessible
   STATUS      current
   DESCRIPTION
       ""
   INDEX    { gs2352QosPortPolicingPort  }
   ::= { gs2352QosPortPolicingTable 1 }

GS2352QosPortPolicingEntry ::= SEQUENCE {
   gs2352QosPortPolicingPort	        Integer32,
   gs2352QosPortPolicingMode           INTEGER,
   gs2352QosPortPolicingRate	        Integer32,
   gs2352QosPortPolicingUnit	        INTEGER,
   gs2352QosPortPolicingFlowControl	INTEGER
}

gs2352QosPortPolicingPort OBJECT-TYPE
   SYNTAX      Integer32(1..4095)
   MAX-ACCESS  not-accessible
   STATUS      current
   DESCRIPTION
       " port, range : 1 - port number. "
   ::= { gs2352QosPortPolicingEntry 1 }

gs2352QosPortPolicingMode OBJECT-TYPE
   SYNTAX      INTEGER { disable(0), enable(1) }
   MAX-ACCESS  read-write
   STATUS      current
   DESCRIPTION
      " Controls whether the policer is enabled on this switch port.
        0: disable,
        1: enable,
        default: disable. "
   ::= { gs2352QosPortPolicingEntry 2 }

gs2352QosPortPolicingRate OBJECT-TYPE
   SYNTAX      Integer32(100..10000000)
   MAX-ACCESS  read-write
   STATUS      current
   DESCRIPTION
       " Controls the rate for the policer.
         range: 100-10000000(kbps/fps),
         default: 500(kbps). "
   ::= { gs2352QosPortPolicingEntry 3 }

gs2352QosPortPolicingUnit OBJECT-TYPE
   SYNTAX      INTEGER { kbps(0), fps(1) }
   MAX-ACCESS  read-write
   STATUS      current
   DESCRIPTION
       " Controls the unit of measure for the policer rate.
         0: kbps,
         1: fps,
         default: kbps. "
   ::= { gs2352QosPortPolicingEntry 4 }

gs2352QosPortPolicingFlowControl OBJECT-TYPE
   SYNTAX      INTEGER { disable(0), enable(1) }
   MAX-ACCESS  read-write
   STATUS      current
   DESCRIPTION
       " If flow control is enabled and the port is in flow control mode,
        then pause frames are sent instead of discarding frames.
         0: disable,
         1: enable,
         default: disable. "
   ::= { gs2352QosPortPolicingEntry 5 }

gs2352QosPortScheduler                                           OBJECT IDENTIFIER ::= { gs2352Qos 3 }

gs2352QosPortSchedulerModeTable OBJECT-TYPE
   SYNTAX      SEQUENCE OF GS2352QosPortSchedulerModeEntry
   MAX-ACCESS  not-accessible
   STATUS      current
   DESCRIPTION
       " configure the basic QoS Port Scheduler Mode settings for all switch ports. "
   ::= { gs2352QosPortScheduler  1 }

gs2352QosPortSchedulerModeEntry OBJECT-TYPE
   SYNTAX      GS2352QosPortSchedulerModeEntry
   MAX-ACCESS  not-accessible
   STATUS      current
   DESCRIPTION
       ""
   INDEX    { gs2352QosSchedulerModePort  }
   ::= { gs2352QosPortSchedulerModeTable 1 }

GS2352QosPortSchedulerModeEntry ::= SEQUENCE {
   gs2352QosSchedulerModePort	                Integer32,
   gs2352QosSchedulerMode                        INTEGER,
   gs2352QosSchedulerShaper	                    INTEGER,
   gs2352QosSchedulerShaperRate                 Integer32
}

gs2352QosSchedulerModePort OBJECT-TYPE
   SYNTAX      Integer32(1..4095)
   MAX-ACCESS  not-accessible
   STATUS      current
   DESCRIPTION
       " port, range : 1 - port number. "
   ::= { gs2352QosPortSchedulerModeEntry 1 }

gs2352QosSchedulerMode OBJECT-TYPE
   SYNTAX      INTEGER { strictPriority(0), weighted(1) }
   MAX-ACCESS  read-write
   STATUS      current
   DESCRIPTION
       " Controls whether the scheduler mode is Strict Priority or Weighted
       on this switch port.
       0:Strict Priority
       1:Weighted
         default: Strict Priority. "
   ::= { gs2352QosPortSchedulerModeEntry 2 }

gs2352QosSchedulerShaper OBJECT-TYPE
   SYNTAX      INTEGER { disable(0), enable(1) }
   MAX-ACCESS  read-write
   STATUS      current
   DESCRIPTION
       " Controls whether the port shaper is enabled
         0: Disable
         1: Enable.
         default: disable. "
   ::= { gs2352QosPortSchedulerModeEntry 3 }

gs2352QosSchedulerShaperRate OBJECT-TYPE
   SYNTAX      Integer32(100..1000000)
   MAX-ACCESS  read-write
   STATUS      current
   DESCRIPTION
       " Controls the rate for the port shaper.
         range: 100-1000000
         default: 500 kbps. "
   ::= { gs2352QosPortSchedulerModeEntry 4 }

gs2352QosPortSchedulerTable OBJECT-TYPE
   SYNTAX      SEQUENCE OF GS2352QosPortSchedulerEntry
   MAX-ACCESS  not-accessible
   STATUS      current
   DESCRIPTION
       " Show Qos Port Scheduler. "
   ::= { gs2352QosPortScheduler 2 }

gs2352QosPortSchedulerEntry OBJECT-TYPE
   SYNTAX      GS2352QosPortSchedulerEntry
   MAX-ACCESS  not-accessible
   STATUS      current
   DESCRIPTION
       ""
   INDEX    { gs2352QosSchedulerPort, gs2352QosSchedulerPortQueue}
   ::= { gs2352QosPortSchedulerTable 1 }

GS2352QosPortSchedulerEntry ::= SEQUENCE {
   gs2352QosSchedulerPort						Integer32,
   gs2352QosSchedulerPortQueue					INTEGER,
   gs2352QosSchedulerPortQueueShaper				INTEGER,
   gs2352QosSchedulerPortQueueShaperRate			Integer32,
   gs2352QosSchedulerPortQueueShaperExcess		INTEGER,
   gs2352QosSchedulerPortQueueSchedulerWeight	Integer32,
   gs2352QosSchedulerPortQueueSchedulerPercent	DisplayString
}

gs2352QosSchedulerPort OBJECT-TYPE
   SYNTAX      Integer32(1..4095)
   MAX-ACCESS  not-accessible
   STATUS      current
   DESCRIPTION
       " port, range : 1 - port number. "
   ::= { gs2352QosPortSchedulerEntry 1 }

gs2352QosSchedulerPortQueue OBJECT-TYPE
   SYNTAX      INTEGER { q0(1), q1(2), q2(3), q3(4), q4(5), q5(6), q6(7), q7(8) }
   MAX-ACCESS  not-accessible
   STATUS      current
   DESCRIPTION
       " range: 1-8.
         Q0: 1, Q1: 2, ... "
   ::= { gs2352QosPortSchedulerEntry 2 }

gs2352QosSchedulerPortQueueShaper OBJECT-TYPE
   SYNTAX      INTEGER { disable(0), enable(1) }
   MAX-ACCESS  read-write
   STATUS      current
   DESCRIPTION
       " 0: disable  1:enable,
         default: 0.  "
   ::= { gs2352QosPortSchedulerEntry 3 }

gs2352QosSchedulerPortQueueShaperRate OBJECT-TYPE
   SYNTAX      Integer32(100..1000000)
   MAX-ACCESS  read-write
   STATUS      current
   DESCRIPTION
       " range: 100..1000000 kbps.  "
   ::= { gs2352QosPortSchedulerEntry 4 }

gs2352QosSchedulerPortQueueShaperExcess OBJECT-TYPE
   SYNTAX      INTEGER { disable(0), enable(1) }
   MAX-ACCESS  read-write
   STATUS      current
   DESCRIPTION
       " 0: disable  1:enable,
         default: 0.  "
   ::= { gs2352QosPortSchedulerEntry 5 }

gs2352QosSchedulerPortQueueSchedulerWeight OBJECT-TYPE
   SYNTAX      Integer32(0..100)
   MAX-ACCESS  read-write
   STATUS      current
   DESCRIPTION
       " range: 1-100,
         default: 17.
         Only use in Q0 - Q5.  Q6 & Q7 show 0 "
   ::= { gs2352QosPortSchedulerEntry 6 }

gs2352QosSchedulerPortQueueSchedulerPercent OBJECT-TYPE
   SYNTAX      DisplayString
   MAX-ACCESS  read-only
   STATUS      current
   DESCRIPTION
       " Only use in Q0 - Q5. Q6 & Q7 show empty "
   ::= { gs2352QosPortSchedulerEntry 7 }


gs2352QosPortEgressTagRemarking                                           OBJECT IDENTIFIER ::= { gs2352Qos 4 }

gs2352QosPortEgressTagRemarkingTable OBJECT-TYPE
   SYNTAX      SEQUENCE OF GS2352QosPortEgressTagRemarkingEntry
   MAX-ACCESS  not-accessible
   STATUS      current
   DESCRIPTION
       " configure the basic QoS Port Egress Tag Remark Configuration settings for all switch ports. "
   ::= { gs2352QosPortEgressTagRemarking  1 }

gs2352QosPortEgressTagRemarkingEntry OBJECT-TYPE
   SYNTAX      GS2352QosPortEgressTagRemarkingEntry
   MAX-ACCESS  not-accessible
   STATUS      current
   DESCRIPTION
       ""
   INDEX    { gs2352QosEgressTagRemarkingPort  }
   ::= { gs2352QosPortEgressTagRemarkingTable 1 }

GS2352QosPortEgressTagRemarkingEntry ::= SEQUENCE {
   gs2352QosEgressTagRemarkingPort	                Integer32,
   gs2352QosEgressTagRemarkingMode	                INTEGER
}

gs2352QosEgressTagRemarkingPort OBJECT-TYPE
   SYNTAX      Integer32(1..4095)
   MAX-ACCESS  not-accessible
   STATUS      current
   DESCRIPTION
       " port, range : 1 - port number. "
   ::= { gs2352QosPortEgressTagRemarkingEntry 1 }

gs2352QosEgressTagRemarkingMode OBJECT-TYPE
   SYNTAX      INTEGER { classified(0), default(1), mapped(2) }
   MAX-ACCESS  read-write
   STATUS      current
   DESCRIPTION
       " the tag remarking mode for this port.
       0:Classified, Use classified PCP/DEI values.
       1:Default, Use default PCP/DEI values.
       2:Mapped, Use mapped versions of QoS class and DP level."
   ::= { gs2352QosPortEgressTagRemarkingEntry 2 }


gs2352QosPortEgressTagRemarkingDefTable OBJECT-TYPE
   SYNTAX      SEQUENCE OF GS2352QosPortEgressTagRemarkingDefEntry
   MAX-ACCESS  not-accessible
   STATUS      current
   DESCRIPTION
       " configure the basic QoS Port Egress Tag Remark Configuration settings for all switch ports. "
   ::= { gs2352QosPortEgressTagRemarking  2 }

gs2352QosPortEgressTagRemarkingDefEntry OBJECT-TYPE
   SYNTAX      GS2352QosPortEgressTagRemarkingDefEntry
   MAX-ACCESS  not-accessible
   STATUS      current
   DESCRIPTION
       ""
   INDEX    { gs2352QosEgressTagRemarkingDefPort  }
   ::= { gs2352QosPortEgressTagRemarkingDefTable 1 }

GS2352QosPortEgressTagRemarkingDefEntry ::= SEQUENCE {
   gs2352QosEgressTagRemarkingDefPort	            Integer32,
   gs2352QosEgressTagRemarkingDefPCP	                Integer32,
   gs2352QosEgressTagRemarkingDefDEI	                INTEGER
}

gs2352QosEgressTagRemarkingDefPort OBJECT-TYPE
   SYNTAX      Integer32(1..4095)
   MAX-ACCESS  not-accessible
   STATUS      current
   DESCRIPTION
       " port, range : 1 - port number. "
   ::= { gs2352QosPortEgressTagRemarkingDefEntry 1 }

gs2352QosEgressTagRemarkingDefPCP OBJECT-TYPE
   SYNTAX      Integer32(0..7)
   MAX-ACCESS  read-write
   STATUS      current
   DESCRIPTION
       " Controls the default PCP
       Range : 0-7"
   ::= { gs2352QosPortEgressTagRemarkingDefEntry 2 }

gs2352QosEgressTagRemarkingDefDEI OBJECT-TYPE
   SYNTAX      INTEGER { disable(0), enable(1) }
   MAX-ACCESS  read-write
   STATUS      current
   DESCRIPTION
       " controls the DEI
       Range 0-1"
   ::= { gs2352QosPortEgressTagRemarkingDefEntry 3 }


gs2352QosPortEgressTagRemarkingMapDPTable OBJECT-TYPE
   SYNTAX      SEQUENCE OF GS2352QosPortEgressTagRemarkingMapDPEntry
   MAX-ACCESS  not-accessible
   STATUS      current
   DESCRIPTION
       " Show Qos Port Egress Tag Remarking Map DP. "
   ::= { gs2352QosPortEgressTagRemarking 3 }

gs2352QosPortEgressTagRemarkingMapDPEntry OBJECT-TYPE
   SYNTAX      GS2352QosPortEgressTagRemarkingMapDPEntry
   MAX-ACCESS  not-accessible
   STATUS      current
   DESCRIPTION
       ""
   INDEX    { gs2352QosPortEgressTagRemarkingDPPort, gs2352QosPortEgressTagRemarkingClassifiedDPLevel}
   ::= { gs2352QosPortEgressTagRemarkingMapDPTable 1 }

GS2352QosPortEgressTagRemarkingMapDPEntry ::= SEQUENCE {
   gs2352QosPortEgressTagRemarkingDPPort					Integer32,
   gs2352QosPortEgressTagRemarkingClassifiedDPLevel		Integer32,
   gs2352QosPortEgressTagRemarkingDPLevel				INTEGER
}

gs2352QosPortEgressTagRemarkingDPPort OBJECT-TYPE
   SYNTAX      Integer32(1..4095)
   MAX-ACCESS  not-accessible
   STATUS      current
   DESCRIPTION
       " port, range : 1 - port number. "
   ::= { gs2352QosPortEgressTagRemarkingMapDPEntry 1 }

gs2352QosPortEgressTagRemarkingClassifiedDPLevel OBJECT-TYPE
   SYNTAX      Integer32(1..4)
   MAX-ACCESS  not-accessible
   STATUS      current
   DESCRIPTION
       " range: 1-4. "
   ::= { gs2352QosPortEgressTagRemarkingMapDPEntry 2 }

gs2352QosPortEgressTagRemarkingDPLevel OBJECT-TYPE
   SYNTAX      INTEGER { disable(0), enable(1) }
   MAX-ACCESS  read-write
   STATUS      current
   DESCRIPTION
       " range: 0-1.  "
   ::= { gs2352QosPortEgressTagRemarkingMapDPEntry 3 }

gs2352QosPortEgressTagRemarkingMapTable OBJECT-TYPE
   SYNTAX      SEQUENCE OF GS2352QosPortEgressTagRemarkingMapEntry
   MAX-ACCESS  not-accessible
   STATUS      current
   DESCRIPTION
       " Show Qos Port Egress Tag Remarking Map. "
   ::= { gs2352QosPortEgressTagRemarking 4 }

gs2352QosPortEgressTagRemarkingMapEntry OBJECT-TYPE
   SYNTAX      GS2352QosPortEgressTagRemarkingMapEntry
   MAX-ACCESS  not-accessible
   STATUS      current
   DESCRIPTION
       ""
   INDEX    { gs2352QosPortEgressTagRemarkingMapPort, gs2352QosTagRemarkingQoSClass, gs2352QosTagRemarkingDPLevel  }
   ::= { gs2352QosPortEgressTagRemarkingMapTable 1 }

GS2352QosPortEgressTagRemarkingMapEntry ::= SEQUENCE {
   gs2352QosPortEgressTagRemarkingMapPort	Integer32,
   gs2352QosTagRemarkingQoSClass				INTEGER,
   gs2352QosTagRemarkingDPLevel				INTEGER,
   gs2352QosTagRemarkingPCP					Integer32,
   gs2352QosTagRemarkingDEI					INTEGER
}

gs2352QosPortEgressTagRemarkingMapPort OBJECT-TYPE
   SYNTAX      Integer32(1..4095)
   MAX-ACCESS  not-accessible
   STATUS      current
   DESCRIPTION
       " port, range : 1 - port number. "
   ::= { gs2352QosPortEgressTagRemarkingMapEntry 1 }

gs2352QosTagRemarkingQoSClass OBJECT-TYPE
   SYNTAX      INTEGER {
                        class0(1),
                        class1(2),
                        class2(3),
                        class3(4),
                        class4(5),
                        class5(6),
                        class6(7),
                        class7(8)
                        }
   MAX-ACCESS  not-accessible
   STATUS      current
   DESCRIPTION
       " range: 1-8,
         QoS Class0: 1, QoS Class1: 2...  "
   ::= { gs2352QosPortEgressTagRemarkingMapEntry 2 }

gs2352QosTagRemarkingDPLevel OBJECT-TYPE
   SYNTAX      INTEGER { level0(1), level1(2) }
   MAX-ACCESS  not-accessible
   STATUS      current
   DESCRIPTION
       " range: 1-2,
         DP Level0: 1, DP Level1: 2. "
   ::= { gs2352QosPortEgressTagRemarkingMapEntry 3 }

gs2352QosTagRemarkingPCP OBJECT-TYPE
   SYNTAX      Integer32(0..7)
   MAX-ACCESS  read-write
   STATUS      current
   DESCRIPTION
       " range: 0-7.  "
   ::= { gs2352QosPortEgressTagRemarkingMapEntry 4 }

gs2352QosTagRemarkingDEI OBJECT-TYPE
   SYNTAX      INTEGER (0|1)
   MAX-ACCESS  read-write
   STATUS      current
   DESCRIPTION
       " range: 0-1.  "
   ::= { gs2352QosPortEgressTagRemarkingMapEntry 5 }


gs2352QosPortDSCPTable OBJECT-TYPE
   SYNTAX      SEQUENCE OF GS2352QosPortDSCPEntry
   MAX-ACCESS  not-accessible
   STATUS      current
   DESCRIPTION
       " configure the basic QoS Port DSCP Configuration settings for all switch ports. "
   ::= { gs2352Qos  5 }

gs2352QosPortDSCPEntry OBJECT-TYPE
   SYNTAX      GS2352QosPortDSCPEntry
   MAX-ACCESS  not-accessible
   STATUS      current
   DESCRIPTION
       ""
   INDEX    { gs2352QosPortDSCPPort  }
   ::= { gs2352QosPortDSCPTable 1 }

GS2352QosPortDSCPEntry ::= SEQUENCE {
   gs2352QosPortDSCPPort	                Integer32,
   gs2352QosPortDSCPIngressTranslate       INTEGER,
   gs2352QosPortDSCPIngressClassify	    INTEGER,
   gs2352QosPortDSCPEgressRewrite	        INTEGER
}

gs2352QosPortDSCPPort OBJECT-TYPE
   SYNTAX      Integer32(1..4095)
   MAX-ACCESS  not-accessible
   STATUS      current
   DESCRIPTION
       " port, range : 1 - port number. "
   ::= { gs2352QosPortDSCPEntry 1 }

gs2352QosPortDSCPIngressTranslate OBJECT-TYPE
   SYNTAX      INTEGER { disable(0), enable(1) }
   MAX-ACCESS  read-write
   STATUS      current
   DESCRIPTION
      " Configure DSCP ingress translation mode.
        0: disable,
        1: enable,
        default: disable. "
   ::= { gs2352QosPortDSCPEntry 2 }

gs2352QosPortDSCPIngressClassify OBJECT-TYPE
   SYNTAX      INTEGER(0..3)
   MAX-ACCESS  read-write
   STATUS      current
   DESCRIPTION
       " Classification for a port have 4 different values.
         range: 0-3,
         0: disable,No Ingress DSCP Classification.
         1: DSCP=0,Classify if incoming (or translated if enabled) DSCP is 0.
         2: Selected,Classify only selected DSCP for which classification is
         enabled as specified in DSCP Translation window for the specific DSCP.
         3: All,Classify all DSCP.
         default: disable. "
   ::= { gs2352QosPortDSCPEntry 3 }

gs2352QosPortDSCPEgressRewrite OBJECT-TYPE
   SYNTAX      INTEGER { disable(0), enable(1), remap(2) }
   MAX-ACCESS  read-write
   STATUS      current
   DESCRIPTION
       " Configure the port egress rewriting mode.
         range: 0-2
         0: Disable,No Egress rewrite.
         1: Enable, Rewrite enabled without remapping.
         2: Remap , DSCP from analyzer is remapped and frame is remarked with
            remapped DSCP value.
         default: disable. "
   ::= { gs2352QosPortDSCPEntry 4 }

gs2352QosDSCPTable OBJECT-TYPE
   SYNTAX      SEQUENCE OF GS2352QosDSCPEntry
   MAX-ACCESS  not-accessible
   STATUS      current
   DESCRIPTION
       " configure the basic QoS DSCP based QoS Ingress Classification settings for all switches. "
   ::= { gs2352Qos  6 }

gs2352QosDSCPEntry OBJECT-TYPE
   SYNTAX      GS2352QosDSCPEntry
   MAX-ACCESS  not-accessible
   STATUS      current
   DESCRIPTION
       ""
   INDEX    { gs2352QosDSCPList  }
   ::= { gs2352QosDSCPTable 1 }

GS2352QosDSCPEntry ::= SEQUENCE {
   gs2352QosDSCPList       Integer32,
   gs2352QosDSCP           DisplayString,
   gs2352QosDSCPTrust      INTEGER,
   gs2352QosDSCPQosClass	  Integer32,
   gs2352QosDSCPDPL	      INTEGER
}

gs2352QosDSCPList OBJECT-TYPE
   SYNTAX      Integer32(1..64)
   MAX-ACCESS  not-accessible
   STATUS      current
   DESCRIPTION
      " DSCP mapping table index(1-64). "
   ::= { gs2352QosDSCPEntry 1 }

gs2352QosDSCP OBJECT-TYPE
   SYNTAX      DisplayString
   MAX-ACCESS  read-only
   STATUS      current
   DESCRIPTION
      "Maximum number of supported DSCP values are 64."
   ::= { gs2352QosDSCPEntry 2 }

gs2352QosDSCPTrust OBJECT-TYPE
   SYNTAX      INTEGER { disable(0), enable(1) }
   MAX-ACCESS  read-write
   STATUS      current
   DESCRIPTION
      " Controls whether a specific DSCP value is trusted. Only frames with
      trusted DSCP values are mapped to a specific QoS class and Drop Precedence
       Level. Frames with untrusted DSCP values are treated as a non-IP frame.
        0: disable,
        1: enable,
        default: disable. "
   ::= { gs2352QosDSCPEntry 3 }

gs2352QosDSCPQosClass OBJECT-TYPE
   SYNTAX      Integer32(0..7)
   MAX-ACCESS  read-write
   STATUS      current
   DESCRIPTION
      " QoS class.
        range: 0-7,
        default: 0. "
   ::= { gs2352QosDSCPEntry 4 }

gs2352QosDSCPDPL OBJECT-TYPE
   SYNTAX      INTEGER(0..3)
   MAX-ACCESS  read-write
   STATUS      current
   DESCRIPTION
      " Drop Precedence Level.
        range: 0-3,
        default: disable. "
   ::= { gs2352QosDSCPEntry 5 }


gs2352QosDSCPTranslationTable OBJECT-TYPE
   SYNTAX      SEQUENCE OF GS2352QosDSCPTranslationEntry
   MAX-ACCESS  not-accessible
   STATUS      current
   DESCRIPTION
       "  configure the basic QoS DSCP Translation settings for all switches. "
   ::= { gs2352Qos  7 }

gs2352QosDSCPTranslationEntry OBJECT-TYPE
   SYNTAX      GS2352QosDSCPTranslationEntry
   MAX-ACCESS  not-accessible
   STATUS      current
   DESCRIPTION
       ""
   INDEX    { gs2352QosDSCPTranslationList  }
   ::= { gs2352QosDSCPTranslationTable 1 }

GS2352QosDSCPTranslationEntry ::= SEQUENCE {
   gs2352QosDSCPTranslationList                 Integer32,
   gs2352QosDSCPTranslationDSCPBasedId          DisplayString,
   gs2352QosDSCPTranslationIngressTranslate     Integer32,
   gs2352QosDSCPTranslationIngressClassify      INTEGER,
   gs2352QosDSCPTranslationEgressRemap          Integer32
}

gs2352QosDSCPTranslationList OBJECT-TYPE
   SYNTAX      Integer32(1..64)
   MAX-ACCESS  not-accessible
   STATUS      current
   DESCRIPTION
      " DSCP translation table index(1-64). "
   ::= { gs2352QosDSCPTranslationEntry 1 }

gs2352QosDSCPTranslationDSCPBasedId OBJECT-TYPE
   SYNTAX      DisplayString
   MAX-ACCESS  read-write
   STATUS      current
   DESCRIPTION
      " Configure global ingress DSCP translation table. "
   ::= { gs2352QosDSCPTranslationEntry 2 }

gs2352QosDSCPTranslationIngressTranslate OBJECT-TYPE
   SYNTAX      Integer32(0..63)
   MAX-ACCESS  read-write
   STATUS      current
   DESCRIPTION
      " DSCP at Ingress side can be translated to any of DSCP values.
        range: 0-63,
        default: 0. "
   ::= { gs2352QosDSCPTranslationEntry 3 }

gs2352QosDSCPTranslationIngressClassify OBJECT-TYPE
   SYNTAX      INTEGER { disable(0), enable(1) }
   MAX-ACCESS  read-write
   STATUS      current
   DESCRIPTION
      " Configure DSCP ingress classification.
        0: disable,
        1: enable,
        default: disable. "
   ::= { gs2352QosDSCPTranslationEntry 4 }

gs2352QosDSCPTranslationEgressRemap OBJECT-TYPE
   SYNTAX      Integer32(0..63)
   MAX-ACCESS  read-write
   STATUS      current
   DESCRIPTION
      " Select the DSCP value from select menu to which you want to remap.
        range: 0-63,
        default: 0. "
   ::= { gs2352QosDSCPTranslationEntry 5 }


gs2352QosDSCPClassificationTable OBJECT-TYPE
   SYNTAX      SEQUENCE OF GS2352QosDSCPClassificationEntry
   MAX-ACCESS  not-accessible
   STATUS      current
   DESCRIPTION
       "   configure the mapping of QoS class  to DSCP value. "
   ::= { gs2352Qos  8 }

gs2352QosDSCPClassificationEntry OBJECT-TYPE
   SYNTAX      GS2352QosDSCPClassificationEntry
   MAX-ACCESS  not-accessible
   STATUS      current
   DESCRIPTION
       ""
   INDEX    { gs2352QosDSCPClassificationQoSClass  }
   ::= { gs2352QosDSCPClassificationTable 1 }

GS2352QosDSCPClassificationEntry ::= SEQUENCE {
   gs2352QosDSCPClassificationQoSClass   INTEGER,
   gs2352QosDSCPClassificationDSCP       Integer32
}

gs2352QosDSCPClassificationQoSClass OBJECT-TYPE
   SYNTAX      INTEGER {
                        class0(1),
                        class1(2),
                        class2(3),
                        class3(4),
                        class4(5),
                        class5(6),
                        class6(7),
                        class7(8)
                        }
   MAX-ACCESS  not-accessible
   STATUS      current
   DESCRIPTION
      " Actual QoS class. Index 1~8 mean Qos Class 0~7."
   ::= { gs2352QosDSCPClassificationEntry 1 }

gs2352QosDSCPClassificationDSCP OBJECT-TYPE
   SYNTAX      Integer32(0..63)
   MAX-ACCESS  read-write
   STATUS      current
   DESCRIPTION
      " Select the classified DSCP value.
        range: 0-63,
        default: 0. "
   ::= { gs2352QosDSCPClassificationEntry 3 }

gs2352QosControlList                                         OBJECT IDENTIFIER ::= { gs2352Qos 9 }

gs2352QosQceCreate OBJECT-TYPE
   SYNTAX       INTEGER { none(0), create(1) }
   MAX-ACCESS   read-write
   STATUS       current
   DESCRIPTION
       "default: 0
        0 : None  (read only)
        1 : Create an Qos entry"
   ::= { gs2352QosControlList 1 }

gs2352QosQceTable OBJECT-TYPE
   SYNTAX      SEQUENCE OF GS2352QosQceEntry
   MAX-ACCESS  not-accessible
   STATUS      current
   DESCRIPTION
       " Create Qos QCE entry. "
   ::= { gs2352QosControlList 2 }

gs2352QosQceEntry OBJECT-TYPE
   SYNTAX      GS2352QosQceEntry
   MAX-ACCESS  not-accessible
   STATUS      current
   DESCRIPTION
       ""
   INDEX    { gs2352QosQceIndex  }
   ::= { gs2352QosQceTable 1 }

GS2352QosQceEntry ::= SEQUENCE {
   gs2352QosQceIndex                Integer32,
   gs2352QosQceID                   Integer32,
   gs2352QosQceNextID               Integer32,
   gs2352QosQcePortMembers          DisplayString,

   gs2352QosQceTag                  DisplayString,
   gs2352QosQceVID                  DisplayString,
   gs2352QosPCP                     DisplayString,
   gs2352QosDEI                     DisplayString,
   gs2352QosSMAC                    DisplayString,
   gs2352QosDMACType                DisplayString,
   gs2352QosFrameType               INTEGER,

   gs2352QosMacEtherType            DisplayString,

   gs2352QosLLCSSAPAddr             DisplayString,
   gs2352QosLLCDSAPAddr             DisplayString,
   gs2352QosLLCControl              DisplayString,

   gs2352QosSNAPPID                 DisplayString,

   gs2352QosIpv4Protocol            DisplayString,
   gs2352QosIpv4ProtocolValue       Integer32,
   gs2352QosIpv4ProtocolUDPSport    DisplayString,
   gs2352QosIpv4ProtocolUDPDport    DisplayString,
   gs2352QosIpv4ProtocolTCPSport    DisplayString,
   gs2352QosIpv4ProtocolTCPDport    DisplayString,
   gs2352QosIpv4SourceIp            DisplayString,
   gs2352QosIpv4SourceMask          DisplayString,
   gs2352QosIpv4IPFragment          INTEGER,
   gs2352QosIpv4DSCP                DisplayString,


   gs2352QosIpv6Protocol            DisplayString,
   gs2352QosIpv6ProtocolValue       Integer32,
   gs2352QosIpv6ProtocolUDPSport    DisplayString,
   gs2352QosIpv6ProtocolUDPDport    DisplayString,
   gs2352QosIpv6ProtocolTCPSport    DisplayString,
   gs2352QosIpv6ProtocolTCPDport    DisplayString,
   gs2352QosIpv6SourceIp            DisplayString,
   gs2352QosIpv6SourceMask          DisplayString,
   gs2352QosIpv6DSCP                DisplayString,

   gs2352QosActionClass             Integer32,
   gs2352QosActionDPL               INTEGER,
   gs2352QosActionDSCP              Integer32,
   gs2352QosQceRowStatus            INTEGER
}

gs2352QosQceIndex OBJECT-TYPE
   SYNTAX      Integer32(1..256)
   MAX-ACCESS  not-accessible
   STATUS      current
   DESCRIPTION
       " "
   ::= { gs2352QosQceEntry 1 }

gs2352QosQceID OBJECT-TYPE
   SYNTAX      Integer32(1..256)
   MAX-ACCESS  read-write
   STATUS      current
   DESCRIPTION
       " If the QCE ID is specified and an entry with this QCE ID
         already exists, the QCE will be modified. Otherwise, a
         new QCE will be added.
         range : 1 - 256. "
   ::= { gs2352QosQceEntry 2 }

gs2352QosQceNextID OBJECT-TYPE
   SYNTAX      Integer32 (1..256)
   MAX-ACCESS  read-write
   STATUS      current
   DESCRIPTION
       " If the next QCE ID is non zero, the QCE will be placed
         before this QCE in the list. If the next QCE ID is zero,
         the QCE will be placed last in the list.
         range : 1 - 256. "
   ::= { gs2352QosQceEntry 3 }

gs2352QosQcePortMembers OBJECT-TYPE
   SYNTAX      DisplayString
   MAX-ACCESS  read-write
   STATUS      current
   DESCRIPTION
       " Indicates the ingress port of the QCE. Possible values are:
         All: The QCE will match all ingress port.
         Port: The QCE will match a specific ingress port.Format: 1,3-6."
   ::= { gs2352QosQceEntry 4 }

gs2352QosQceTag OBJECT-TYPE
   SYNTAX      DisplayString
   MAX-ACCESS  read-write
   STATUS      current
   DESCRIPTION
       " Value of Tag field can be 'Any', 'Untag' or 'Tag'. "
   ::= { gs2352QosQceEntry 5 }

gs2352QosQceVID OBJECT-TYPE
   SYNTAX      DisplayString
   MAX-ACCESS  read-write
   STATUS      current
   DESCRIPTION
       " Valid value of VLAN ID can be any value in 'Specific 1~4094' or 'range 1-4094' or 'Any'. "
   ::= { gs2352QosQceEntry 6 }

gs2352QosPCP OBJECT-TYPE
   SYNTAX      DisplayString
   MAX-ACCESS  read-write
   STATUS      current
   DESCRIPTION
       " Priority Code Point: Valid value PCP are specific(0, 1, 2, 3, 4, 5, 6, 7)
         or range(0-1, 2-3, 4-5, 6-7, 0-3, 4-7) or 'Any'. "
   ::= { gs2352QosQceEntry 7 }

gs2352QosDEI OBJECT-TYPE
   SYNTAX      DisplayString
   MAX-ACCESS  read-write
   STATUS      current
   DESCRIPTION
       " Drop Eligible Indicator: Valid value of DEI can be any of values between 0, 1 or 'Any'. "
   ::= { gs2352QosQceEntry 8 }

gs2352QosSMAC  OBJECT-TYPE
   SYNTAX      DisplayString
   MAX-ACCESS  read-write
   STATUS      current
   DESCRIPTION
       "  Source MAC address: 24 MS bits OUI(00-00-00 ~ FF-FF-FF) or 'Any'. "
   ::= { gs2352QosQceEntry 9 }

gs2352QosDMACType OBJECT-TYPE
   SYNTAX      DisplayString
   MAX-ACCESS  read-write
   STATUS      current
   DESCRIPTION
       " Destination MAC type: possible values are 'UC'(unicast), 'MC'(multicast), 'BC'(broadcast) or 'Any'. "
   ::= { gs2352QosQceEntry 10 }

gs2352QosFrameType OBJECT-TYPE
   SYNTAX      INTEGER {
                        any(1),
                        ethernet(2),
                        llc(3),
                        snap(4),
                        ipv4(5),
                        ipv6(6)
                        }
   MAX-ACCESS  read-write
   STATUS      current
   DESCRIPTION
       " Frame Type can have any of the following values:
         1: Any,
         2: Ethernet,
         3: LLC,
         4: SNAP,
         5: IPv4,
         6: IPv6. "
   ::= { gs2352QosQceEntry 11 }

gs2352QosMacEtherType OBJECT-TYPE
   SYNTAX      DisplayString
   MAX-ACCESS  read-write
   STATUS      current
   DESCRIPTION
       " Valid ethernet type can have a value within 0x600-0xFFFF or 'Any' ,
         but excluding 0x800(IPv4) and 0x86DD(IPv6),
         range: 0000-FFFF,
         default: Any."
   ::= { gs2352QosQceEntry 12 }

gs2352QosLLCSSAPAddr OBJECT-TYPE
   SYNTAX      DisplayString
   MAX-ACCESS  read-write
   STATUS      current
   DESCRIPTION
       " Valid SSAP(Source Service Access Point) can vary from 0x00 to 0xFF or 'Any',
         range: 00-FF,
         default: Any. "
   ::= { gs2352QosQceEntry 13 }

gs2352QosLLCDSAPAddr OBJECT-TYPE
   SYNTAX      DisplayString
   MAX-ACCESS  read-write
   STATUS      current
   DESCRIPTION
       " Valid DSAP(Destination Service Access Point) can vary from 0x00 to 0xFF or 'Any',
         range: 00-FF,
         default: Any. "
   ::= { gs2352QosQceEntry 14 }

gs2352QosLLCControl OBJECT-TYPE
   SYNTAX      DisplayString
   MAX-ACCESS  read-write
   STATUS      current
   DESCRIPTION
       " Valid Control field can vary from 0x00 to 0xFF or 'Any',
         range: 00-FF,
         default: Any. "
   ::= { gs2352QosQceEntry 15 }

gs2352QosSNAPPID OBJECT-TYPE
   SYNTAX      DisplayString
   MAX-ACCESS  read-write
   STATUS      current
   DESCRIPTION
       " Valid PID(a.k.a ethernet type) can have value within 0x00-0xFFFF or 'Any',
         range: 0000-FFFF,
         default: Any. "
   ::= { gs2352QosQceEntry 16 }

gs2352QosIpv4Protocol OBJECT-TYPE
   SYNTAX      DisplayString
   MAX-ACCESS  read-write
   STATUS      current
   DESCRIPTION
       " IP protocol number: (Other, TCP or UDP) or 'Any'. "
   ::= { gs2352QosQceEntry 17 }

gs2352QosIpv4ProtocolValue  OBJECT-TYPE
   SYNTAX      Integer32(0..255)
   MAX-ACCESS  read-write
   STATUS      current
   DESCRIPTION
       " Ipv4 Protocol is Other.
         range: 0-255
         default: 0. "
   ::= { gs2352QosQceEntry 18 }

gs2352QosIpv4ProtocolUDPSport OBJECT-TYPE
   SYNTAX      DisplayString
   MAX-ACCESS  read-write
   STATUS      current
   DESCRIPTION
       " Source  TCP/UDP port:(0-65535) or 'Any',
         specific or port range applicable for IP protocol UDP/TCP. "
   ::= { gs2352QosQceEntry 19 }

gs2352QosIpv4ProtocolUDPDport OBJECT-TYPE
   SYNTAX      DisplayString
   MAX-ACCESS  read-write
   STATUS      current
   DESCRIPTION
       " Destination TCP/UDP port:(0-65535) or 'Any',
         specific or port range applicable for IP protocol UDP/TCP. "
   ::= { gs2352QosQceEntry 20 }

gs2352QosIpv4ProtocolTCPSport OBJECT-TYPE
   SYNTAX      DisplayString
   MAX-ACCESS  read-write
   STATUS      current
   DESCRIPTION
       " Source TCP/UDP port:(0-65535) or 'Any',
         specific or port range applicable for IP protocol UDP/TCP. "
   ::= { gs2352QosQceEntry 21 }

gs2352QosIpv4ProtocolTCPDport OBJECT-TYPE
   SYNTAX      DisplayString
   MAX-ACCESS  read-write
   STATUS      current
   DESCRIPTION
       " Destination TCP/UDP port:(0-65535) or 'Any',
         specific or port range applicable for IP protocol UDP/TCP. "
   ::= { gs2352QosQceEntry 22 }

gs2352QosIpv4SourceIp OBJECT-TYPE
   SYNTAX      DisplayString
   MAX-ACCESS  read-write
   STATUS      current
   DESCRIPTION
       "  Specific Source IP address in value format or value 0.0.0.0 is 'Any'.
          if Ipv4 Mask value 0.0.0.0 is 'Any' ,IP address value also is 'Any'.
          (x.y.z.w),x=0 unless y.z.w also 0,x not is 127 or greater than 223."
   ::= { gs2352QosQceEntry 23 }

gs2352QosIpv4SourceMask OBJECT-TYPE
   SYNTAX      DisplayString
   MAX-ACCESS  read-write
   STATUS      current
   DESCRIPTION
       " Specific Source IP address in mask format or value 0.0.0.0 is 'Any'. "
   ::= { gs2352QosQceEntry 24 }

gs2352QosIpv4IPFragment OBJECT-TYPE
   SYNTAX      INTEGER { any(0), no(1), yes(2) }
   MAX-ACCESS  read-write
   STATUS      current
   DESCRIPTION
       " IPv4 frame fragmented option:
         2: yes,
         1: no,
         0: any. "
   ::= { gs2352QosQceEntry 25 }

gs2352QosIpv4DSCP OBJECT-TYPE
   SYNTAX      DisplayString
   MAX-ACCESS  read-write
   STATUS      current
   DESCRIPTION
       " Diffserv Code Point value (DSCP): It can be a specific value,
         range of values or 'Any'. DSCP values are in the range 0-63. "
   ::= { gs2352QosQceEntry 26 }

gs2352QosIpv6Protocol OBJECT-TYPE
   SYNTAX      DisplayString
   MAX-ACCESS  read-write
   STATUS      current
   DESCRIPTION
       " IP protocol number: (Other, TCP or UDP) or 'Any'. "
   ::= { gs2352QosQceEntry 27 }

gs2352QosIpv6ProtocolValue OBJECT-TYPE
   SYNTAX      Integer32(0..255)
   MAX-ACCESS  read-write
   STATUS      current
   DESCRIPTION
       " when IPv6 protocol is Other ,
         range: 0-255. "
   ::= { gs2352QosQceEntry 28 }

gs2352QosIpv6ProtocolUDPSport OBJECT-TYPE
   SYNTAX      DisplayString
   MAX-ACCESS  read-write
   STATUS      current
   DESCRIPTION
       " Source TCP/UDP port:(0-65535) or 'Any',
         specific or port range applicable for IP protocol UDP/TCP. "
   ::= { gs2352QosQceEntry 29 }

gs2352QosIpv6ProtocolUDPDport OBJECT-TYPE
   SYNTAX      DisplayString
   MAX-ACCESS  read-write
   STATUS      current
   DESCRIPTION
       " Destination TCP/UDP port:(0-65535) or 'Any',
         specific or port range applicable for IP protocol UDP/TCP. "
   ::= { gs2352QosQceEntry 30 }

gs2352QosIpv6ProtocolTCPSport OBJECT-TYPE
   SYNTAX      DisplayString
   MAX-ACCESS  read-write
   STATUS      current
   DESCRIPTION
       " Source TCP/UDP port:(0-65535) or 'Any',
         specific or port range applicable for IP protocol UDP/TCP. "
   ::= { gs2352QosQceEntry 31 }


gs2352QosIpv6ProtocolTCPDport OBJECT-TYPE
   SYNTAX      DisplayString
   MAX-ACCESS  read-write
   STATUS      current
   DESCRIPTION
       " Destination TCP/UDP port:(0-65535) or 'Any',
         specific or port range applicable for IP protocol UDP/TCP. "
   ::= { gs2352QosQceEntry 32 }

gs2352QosIpv6SourceIp OBJECT-TYPE
   SYNTAX      DisplayString
   MAX-ACCESS  read-write
   STATUS      current
   DESCRIPTION
       " IPv6 source address: (a.b.c.d) or value 0.0.0.0 is 'Any', 32 LS bits. "
   ::= { gs2352QosQceEntry 33 }

gs2352QosIpv6SourceMask OBJECT-TYPE
   SYNTAX      DisplayString
   MAX-ACCESS  read-write
   STATUS      current
   DESCRIPTION
       " IPv6 mask address: (a.b.c.d) or value 0.0.0.0 is 'Any', 32 LS bits. "
   ::= { gs2352QosQceEntry 34 }

gs2352QosIpv6DSCP OBJECT-TYPE
   SYNTAX      DisplayString
   MAX-ACCESS  read-write
   STATUS      current
   DESCRIPTION
       " Diffserv Code Point value (DSCP): It can be a specific value,
         range of values or 'Any'. DSCP values are in the range 0-63 including BE,
         CS1-CS7, EF or AF11-AF43. "
   ::= { gs2352QosQceEntry 35 }

gs2352QosActionClass  OBJECT-TYPE
   SYNTAX      Integer32(0..8)
   MAX-ACCESS  read-write
   STATUS      current
   DESCRIPTION
       " QoS class: (0-7) or 8: Default."
   ::= { gs2352QosQceEntry 36 }

gs2352QosActionDPL OBJECT-TYPE
   SYNTAX      INTEGER (0..4)
   MAX-ACCESS  read-write
   STATUS      current
   DESCRIPTION
       " DP Valid Drop Precedence Level can be (0-3) or 4: Default. "
   ::= { gs2352QosQceEntry 37 }

gs2352QosActionDSCP OBJECT-TYPE
   SYNTAX      Integer32(0..64)
   MAX-ACCESS  read-write
   STATUS      current
   DESCRIPTION
       " Valid DSCP value can be (0-63, BE, CS1-CS7, EF or AF11-AF43) or 64: Default. "
   ::= { gs2352QosQceEntry 38 }

gs2352QosQceRowStatus OBJECT-TYPE
   SYNTAX      INTEGER { active(1), notInservice(2), destroy(4) }
   MAX-ACCESS  read-write
   STATUS      current
   DESCRIPTION
       "  1: active2: notInservice 4: destroy"
   ::= { gs2352QosQceEntry 39 }

gs2352QosQceMoveID OBJECT-TYPE
   SYNTAX       Integer32(0..256)
   MAX-ACCESS   read-write
   STATUS       current
   DESCRIPTION
       " Move Qos,
         default: 0
         Qos ID must be exist.
         range : 0 - 256."
   ::= { gs2352QosControlList 3 }

gs2352QosQceMoveNextID OBJECT-TYPE
   SYNTAX       Integer32 (0..256)
   MAX-ACCESS   read-write
   STATUS       current
   DESCRIPTION
       " Move Qos,
         default: 0
         If the next Qos ID is non zero, the Qos will be placed before this Qos in the list.
         If the next Qos ID is zero,the Qos will be placed last in the list.
         range : 0 - 256. "
   ::= { gs2352QosControlList 4 }


gs2352QosQCLStatusTable OBJECT-TYPE
   SYNTAX      SEQUENCE OF GS2352QosQCLStatusEntry
   MAX-ACCESS  not-accessible
   STATUS      current
   DESCRIPTION
       "  configure the basic QoS DSCP Translation settings for all switches. "
   ::= { gs2352Qos  10 }

gs2352QosQCLStatusEntry OBJECT-TYPE
   SYNTAX      GS2352QosQCLStatusEntry
   MAX-ACCESS  not-accessible
   STATUS      current
   DESCRIPTION
       ""
   INDEX    { gs2352QosQCLStatusList  }
   ::= { gs2352QosQCLStatusTable 1 }

GS2352QosQCLStatusEntry ::= SEQUENCE {
   gs2352QosQCLStatusList               Integer32,
   gs2352QosQCLStatusUser               DisplayString,
   gs2352QosQCLStatusQCEId              DisplayString,
   gs2352QosQCLStatusFrameType          DisplayString,
   gs2352QosQCLStatusPortlist           DisplayString,
   gs2352QosQCLStatusActionClass	       DisplayString,
   gs2352QosQCLStatusActionDPL	       DisplayString,
   gs2352QosQCLStatusActionDSCP	       DisplayString,
   gs2352QosQCLStatusActionConflict     DisplayString
}

gs2352QosQCLStatusList OBJECT-TYPE
   SYNTAX      Integer32(1..4095)
   MAX-ACCESS  not-accessible
   STATUS      current
   DESCRIPTION
       " QCL table index. "
   ::= { gs2352QosQCLStatusEntry 1}

gs2352QosQCLStatusUser OBJECT-TYPE
   SYNTAX      DisplayString
   MAX-ACCESS  read-only
   STATUS      current
   DESCRIPTION
       " Indicates the QCL user. "
   ::= { gs2352QosQCLStatusEntry 2 }

gs2352QosQCLStatusQCEId OBJECT-TYPE
   SYNTAX      DisplayString
   MAX-ACCESS  read-only
   STATUS      current
   DESCRIPTION
      " Indicates the index of QCE. "
   ::= { gs2352QosQCLStatusEntry 3}

gs2352QosQCLStatusFrameType OBJECT-TYPE
   SYNTAX      DisplayString
   MAX-ACCESS  read-only
   STATUS      current
   DESCRIPTION
       " Indicates the type of frame to look for incomming frames.
       Any: The QCE will match all frame type.
       Ethernet: Only Ethernet frames (with Ether Type 0x600-0xFFFF) are allowed.
       LLC: Only (LLC) frames are allowed.
       SNAP: Only (SNAP) frames are allowed.
       IPv4: The QCE will match only IPV4 frames.
       IPv6: The QCE will match only IPV6 frames."
   ::= { gs2352QosQCLStatusEntry 4}

gs2352QosQCLStatusPortlist OBJECT-TYPE
   SYNTAX      DisplayString
   MAX-ACCESS  read-only
   STATUS      current
   DESCRIPTION
       " Indicates the list of ports configured with the QCE. "
   ::= { gs2352QosQCLStatusEntry 5}

gs2352QosQCLStatusActionClass OBJECT-TYPE
   SYNTAX      DisplayString
   MAX-ACCESS  read-only
   STATUS      current
   DESCRIPTION
       " Classified QoS class; if a frame matches the QCE it will be put in the
       queue. "
   ::= { gs2352QosQCLStatusEntry 6}

gs2352QosQCLStatusActionDPL OBJECT-TYPE
   SYNTAX      DisplayString
   MAX-ACCESS  read-only
   STATUS      current
   DESCRIPTION
       " Drop Precedence Level; if a frame matches the QCE then DP level will
       set to value displayed under DPL column."
   ::= { gs2352QosQCLStatusEntry 7}

gs2352QosQCLStatusActionDSCP OBJECT-TYPE
   SYNTAX      DisplayString
   MAX-ACCESS  read-only
   STATUS      current
   DESCRIPTION
       " If a frame matches the QCE then DSCP will be classified with the value
       displayed under DSCP column."
   ::= { gs2352QosQCLStatusEntry 8}

gs2352QosQCLStatusActionConflict OBJECT-TYPE
   SYNTAX      DisplayString
   MAX-ACCESS  read-only
   STATUS      current
   DESCRIPTION
       " If a frame matches the QCE then DSCP will be classified with the value
        displayed under DSCP column. "
   ::= { gs2352QosQCLStatusEntry 9}


gs2352QosStormControl                                           OBJECT IDENTIFIER ::= { gs2352Qos 11 }

gs2352QosStormControlTable OBJECT-TYPE
   SYNTAX      SEQUENCE OF GS2352QosStormControlEntry
   MAX-ACCESS  not-accessible
   STATUS      current
   DESCRIPTION
       "  configure the basic QoS DSCP Translation settings for all switches. "
   ::= { gs2352QosStormControl  1 }

gs2352QosStormControlEntry OBJECT-TYPE
   SYNTAX      GS2352QosStormControlEntry
   MAX-ACCESS  not-accessible
   STATUS      current
   DESCRIPTION
       ""
   INDEX    { gs2352QosStormControlPort  }
   ::= { gs2352QosStormControlTable 1 }

GS2352QosStormControlEntry ::= SEQUENCE {
   gs2352QosStormControlPort                    Integer32,
   gs2352QosStormControlUnicastEnabled          INTEGER,
   gs2352QosStormControlUnicastRate             Integer32,
   gs2352QosStormControlUnicastUnit             INTEGER,
   gs2352QosStormControlBroadcastEnabled        INTEGER,
   gs2352QosStormControlBroadcastRate           Integer32,
   gs2352QosStormControlBroadcastUnit           INTEGER,
   gs2352QosStormControlUnknownEnabled          INTEGER,
   gs2352QosStormControlUnknownRate             Integer32,
   gs2352QosStormControlUnknownUnit             INTEGER
}

gs2352QosStormControlPort OBJECT-TYPE
   SYNTAX      Integer32(1..4095)
   MAX-ACCESS  not-accessible
   STATUS      current
   DESCRIPTION
       " port, range : 1 - port number. "
   ::= { gs2352QosStormControlEntry 1 }

gs2352QosStormControlUnicastEnabled OBJECT-TYPE
   SYNTAX      INTEGER { disable(0), enable(1) }
   MAX-ACCESS  read-write
   STATUS      current
   DESCRIPTION
      " Controls whether the storm control is enabled on this switch port.
        0: disable,
        1: enable,
        default: disable. "
   ::= { gs2352QosStormControlEntry 2 }

gs2352QosStormControlUnicastRate OBJECT-TYPE
   SYNTAX      Integer32(100..10000000)
   MAX-ACCESS  read-write
   STATUS      current
   DESCRIPTION
       " Controls the rate for the unicast storm control.
         range: 100-10000000(kbps/fps),
         default: 500(kbps).  "
   ::= { gs2352QosStormControlEntry 3 }

gs2352QosStormControlUnicastUnit OBJECT-TYPE
   SYNTAX      INTEGER { kbps(0), fps(1) }
   MAX-ACCESS  read-write
   STATUS      current
   DESCRIPTION
       " Controls the unit of measure for the unicast storm control rate.
         0: kbps,
         1: fps,
         default: kbps. "
   ::= { gs2352QosStormControlEntry 4 }

gs2352QosStormControlBroadcastEnabled OBJECT-TYPE
   SYNTAX      INTEGER { disable(0), enable(1) }
   MAX-ACCESS  read-write
   STATUS      current
   DESCRIPTION
      " Controls whether the storm control is enabled on this switch port.
        0: disable,
        1: enable,
        default: disable. "
   ::= { gs2352QosStormControlEntry 5 }

gs2352QosStormControlBroadcastRate OBJECT-TYPE
   SYNTAX      Integer32(100..10000000)
   MAX-ACCESS  read-write
   STATUS      current
   DESCRIPTION
       " Controls the rate for the broadcast storm control.
         range: 100-10000000(kbps/fps),
         default: 500(kbps).  "
   ::= { gs2352QosStormControlEntry 6 }

gs2352QosStormControlBroadcastUnit OBJECT-TYPE
   SYNTAX      INTEGER { kbps(0), fps(1) }
   MAX-ACCESS  read-write
   STATUS      current
   DESCRIPTION
       " Controls the unit of measure for the broadcast storm control rate.
         0: kbps,
         1: fps,
         default: kbps. "
   ::= { gs2352QosStormControlEntry 7 }

gs2352QosStormControlUnknownEnabled OBJECT-TYPE
   SYNTAX      INTEGER { disable(0), enable(1) }
   MAX-ACCESS  read-write
   STATUS      current
   DESCRIPTION
      " Controls whether the storm control is enabled on this switch port.
        0: disable,
        1: enable,
        default: disable. "
   ::= { gs2352QosStormControlEntry 8 }

gs2352QosStormControlUnknownRate OBJECT-TYPE
   SYNTAX      Integer32(100..10000000)
   MAX-ACCESS  read-write
   STATUS      current
   DESCRIPTION
       " Controls the rate for the multicast storm control.
         range: 100-10000000(kbps/fps),
         default: 500(kbps).  "
   ::= { gs2352QosStormControlEntry 9 }

gs2352QosStormControlUnknownUnit OBJECT-TYPE
   SYNTAX      INTEGER { kbps(0), fps(1) }
   MAX-ACCESS  read-write
   STATUS      current
   DESCRIPTION
       " Controls the unit of measure for the multicast storm control rate.
         0: kbps,
         1: fps,
         default: kbps. "
   ::= { gs2352QosStormControlEntry 10 }


gs2352QosWREDTable OBJECT-TYPE
   SYNTAX      SEQUENCE OF GS2352QosWREDEntry
   MAX-ACCESS  not-accessible
   STATUS      current
   DESCRIPTION
       " configure the Random Early Detection (RED) settings for queue. "
   ::= { gs2352Qos  12 }

gs2352QosWREDEntry OBJECT-TYPE
   SYNTAX      GS2352QosWREDEntry
   MAX-ACCESS  not-accessible
   STATUS      current
   DESCRIPTION
       ""
   INDEX    { gs2352QosWREDQueueList  }
   ::= { gs2352QosWREDTable 1 }

GS2352QosWREDEntry ::= SEQUENCE {
   gs2352QosWREDQueueList       Integer32,
   gs2352QosWREDQueue           INTEGER,
   gs2352QosWREDMinThreshold    Integer32,
   gs2352QosWREDMaxDP1          Integer32,
   gs2352QosWREDMaxDP2          Integer32,
   gs2352QosWREDMaxDP3          Integer32
}

gs2352QosWREDQueueList OBJECT-TYPE
   SYNTAX      Integer32(1..6)
   MAX-ACCESS   not-accessible
   STATUS      current
   DESCRIPTION
       " The queue number (QoS class) for which the configuration below applies.
       Index 1~6 mean Queue 0~5."
   ::= { gs2352QosWREDEntry 1 }

gs2352QosWREDQueue OBJECT-TYPE
   SYNTAX      INTEGER { disable(0), enable(1) }
   MAX-ACCESS  read-write
   STATUS      current
   DESCRIPTION
       " Controls whether RED(Random Early Detection) for this queue.
         0: Disable,
         1: Enable,
         default: Disable. "
   ::= { gs2352QosWREDEntry 2 }

gs2352QosWREDMinThreshold OBJECT-TYPE
   SYNTAX      Integer32(0..100)
   MAX-ACCESS  read-write
   STATUS      current
   DESCRIPTION
       " Controls the lower RED(Random Early Detection) threshold.
       If the average queue filling level is below this threshold, the drop
       probability is zero.
         range: 0-100"
   ::= { gs2352QosWREDEntry 3 }

gs2352QosWREDMaxDP1 OBJECT-TYPE
   SYNTAX      Integer32(0..100)
   MAX-ACCESS  read-write
   STATUS      current
   DESCRIPTION
       " Controls the drop probability for frames marked with Drop Precedence
       Level 1 when the average queue filling level is 100%.
         range: 0-100,
         default: 1. "
   ::= { gs2352QosWREDEntry 4 }

gs2352QosWREDMaxDP2 OBJECT-TYPE
   SYNTAX      Integer32(0..100)
   MAX-ACCESS  read-write
   STATUS      current
   DESCRIPTION
       " Controls the drop probability for frames marked with Drop Precedence
       Level 2 when the average queue filling level is 100%.
         range: 0-100,
         default: 5. "
   ::= { gs2352QosWREDEntry 5 }

gs2352QosWREDMaxDP3 OBJECT-TYPE
   SYNTAX      Integer32(0..100)
   MAX-ACCESS  read-write
   STATUS      current
   DESCRIPTION
       " Controls the drop probability for frames marked with Drop Precedence
       Level 3 when the average queue filling level is 100%.
         range: 0-100,
         default: 10. "
   ::= { gs2352QosWREDEntry 6 }

gs2352Vlan                                                           OBJECT IDENTIFIER ::= { gs2352Configuration 15 }

gs2352VlanPorts                                                      OBJECT IDENTIFIER ::= { gs2352Vlan 1 }

gs2352VlanPortsTPIDforCustomSport  OBJECT-TYPE
   SYNTAX      OCTET STRING(SIZE(2))
   MAX-ACCESS  read-write
   STATUS      current
   DESCRIPTION
       "Configure the TPID used for Custom S-ports. This is a global setting for
       all the Custom S-ports.
       range: 0x0600-0xffff,
       default: 0x88a8. "
   ::= { gs2352VlanPorts 1 }

gs2352VlanPortsTable OBJECT-TYPE
   SYNTAX      SEQUENCE OF GS2352VlanPortsEntry
   MAX-ACCESS  not-accessible
   STATUS      current
   DESCRIPTION
       " Configure Vlan ports Configuration mode. "
   ::= { gs2352VlanPorts 2 }

gs2352VlanPortsEntry OBJECT-TYPE
   SYNTAX      GS2352VlanPortsEntry
   MAX-ACCESS  not-accessible
   STATUS      current
   DESCRIPTION
       ""
   INDEX    { gs2352VlanPortsPort  }
   ::= { gs2352VlanPortsTable 1 }

GS2352VlanPortsEntry ::= SEQUENCE {
   gs2352VlanPortsPort	         Integer32,
   gs2352VlanPortsPVID     Integer32,
   gs2352VlanPortsFrameType      INTEGER,
   gs2352VlanPortsIngressFilter  INTEGER,
   gs2352VlanPortsEgressRule     INTEGER,
   gs2352VlanPortsPortType       INTEGER
}

gs2352VlanPortsPort OBJECT-TYPE
   SYNTAX      Integer32(1..4094)
   MAX-ACCESS  not-accessible
   STATUS      current
   DESCRIPTION
       " port, range : 1 - port number. "
   ::= { gs2352VlanPortsEntry 1 }

gs2352VlanPortsPVID OBJECT-TYPE
   SYNTAX      Integer32(1..4094)
   MAX-ACCESS  read-write
   STATUS      current
   DESCRIPTION
       "Configure PVID.
        range: 1-4094,
        default: 1. "
   ::= { gs2352VlanPortsEntry 2 }

gs2352VlanPortsFrameType OBJECT-TYPE
   SYNTAX      INTEGER { all(0), tagged(1), untagged(2) }
   MAX-ACCESS  read-write
   STATUS      current
   DESCRIPTION
       "Configure frame type of switch ports.
        0: all,
        1: tagged,
        2: untagged,
        default: all.  "
   ::= { gs2352VlanPortsEntry 3 }

gs2352VlanPortsIngressFilter OBJECT-TYPE
   SYNTAX      INTEGER { disable(0), enable(1) }
   MAX-ACCESS  read-write
   STATUS      current
   DESCRIPTION
       "Configure ingress filtering of switch ports.
        0: disable,
        1: enable,
        default:disable . "
   ::= { gs2352VlanPortsEntry 4 }

gs2352VlanPortsEgressRule OBJECT-TYPE
   SYNTAX      INTEGER { access(0), hybrid(1), trunk(2) }
   MAX-ACCESS  read-write
   STATUS      current
   DESCRIPTION
       "Configure egress-rule of switch ports.
        0: access,
        1: hybrid,
        2: trunk"
   ::= { gs2352VlanPortsEntry 5 }

gs2352VlanPortsPortType OBJECT-TYPE
   SYNTAX      INTEGER { cPort(0), sCustomPort(1), sPort(2), unaware(3) }
   MAX-ACCESS  read-write
   STATUS      current
   DESCRIPTION
       "Configure port type of switch ports.
        0: c-port,
        1: s-custom-port,
        2: s-port,
        3: unaware.
        default: c-port. "
   ::= { gs2352VlanPortsEntry 6 }

gs2352VlanPrivateVLAN                                                              OBJECT IDENTIFIER ::= { gs2352Vlan 2 }

gs2352VlanPortIsolationTable OBJECT-TYPE
   SYNTAX      SEQUENCE OF Gs2352VlanPortIsolationEntry
   MAX-ACCESS  not-accessible
   STATUS      current
   DESCRIPTION
       " Configure Vlan Port Isolation Configuration. "
   ::= { gs2352VlanPrivateVLAN 2 }

gs2352VlanPortIsolationEntry OBJECT-TYPE
   SYNTAX      Gs2352VlanPortIsolationEntry
   MAX-ACCESS  not-accessible
   STATUS      current
   DESCRIPTION
       ""
   INDEX    { gs2352VlanPortIsolationPort  }
   ::= { gs2352VlanPortIsolationTable 1 }

Gs2352VlanPortIsolationEntry ::= SEQUENCE {
   gs2352VlanPortIsolationPort Integer32,
   gs2352VlanPortIsolation     INTEGER
}

gs2352VlanPortIsolationPort OBJECT-TYPE
   SYNTAX      Integer32(1..4094)
   MAX-ACCESS  not-accessible
   STATUS      current
   DESCRIPTION
       " port, range : 1 - port number. "
   ::= { gs2352VlanPortIsolationEntry 1 }

gs2352VlanPortIsolation OBJECT-TYPE
   SYNTAX      INTEGER{ disable(0), enable(1) }
   MAX-ACCESS  read-write
   STATUS      current
   DESCRIPTION
       "default: 0
        0:disable
        1:enable"
   ::= { gs2352VlanPortIsolationEntry 2 }


gs2352MACbasedVLAN                                                      OBJECT IDENTIFIER ::= { gs2352Vlan 3 }

gs2352MACbasedVLANConf                                                      OBJECT IDENTIFIER ::= { gs2352MACbasedVLAN 1 }

gs2352MACbasedVLANConfCreate OBJECT-TYPE
   SYNTAX       Integer32
   MAX-ACCESS   read-write
   STATUS       current
   DESCRIPTION
       "default: 0
       0 : None  (read only) 1 : Create MAC base vlan"
   ::= { gs2352MACbasedVLANConf 1 }

gs2352MACbasedVLANConfTable OBJECT-TYPE
   SYNTAX      SEQUENCE OF Gs2352MACbasedVLANConfEntry
   MAX-ACCESS  not-accessible
   STATUS      current
   DESCRIPTION
       " Configure Vlan Port Isolation Configuration. "
   ::= { gs2352MACbasedVLANConf 2 }

gs2352MACbasedVLANConfEntry OBJECT-TYPE
   SYNTAX      Gs2352MACbasedVLANConfEntry
   MAX-ACCESS  not-accessible
   STATUS      current
   DESCRIPTION
       ""
   INDEX    { gs2352MACbasedVLANIndex  }
   ::= { gs2352MACbasedVLANConfTable 1 }

Gs2352MACbasedVLANConfEntry ::= SEQUENCE {
   gs2352MACbasedVLANIndex         Integer32,
   gs2352MACbasedVLANMACAddress    MacAddress,
   gs2352MACbasedVLANID            Integer32,
   gs2352MACbasedMemberships       DisplayString,
   gs2352MACbaseRowStatus          INTEGER
}

gs2352MACbasedVLANIndex OBJECT-TYPE
   SYNTAX      Integer32(1..256)
   MAX-ACCESS  read-write
   STATUS      current
   DESCRIPTION
       "Indicates the VLAN ID. "
   ::= { gs2352MACbasedVLANConfEntry 1 }

gs2352MACbasedVLANMACAddress OBJECT-TYPE
   SYNTAX      MacAddress
   MAX-ACCESS  read-write
   STATUS      current
   DESCRIPTION
       "Indicates the MAC address.
       The CreateEntry can be modify, the other entry can't be modify."
   ::= { gs2352MACbasedVLANConfEntry 2 }

gs2352MACbasedVLANID OBJECT-TYPE
   SYNTAX      Integer32(1..4094)
   MAX-ACCESS  read-write
   STATUS      current
   DESCRIPTION
       "Indicates the VLAN ID. "
   ::= { gs2352MACbasedVLANConfEntry 3 }

gs2352MACbasedMemberships OBJECT-TYPE
   SYNTAX      DisplayString
   MAX-ACCESS  read-write
   STATUS      current
   DESCRIPTION
       "The ports are displayed for each MAC-based VLAN entry.
        To include the port in a MAC-based VLAN"
   ::= { gs2352MACbasedVLANConfEntry 4 }


gs2352MACbaseRowStatus OBJECT-TYPE
   SYNTAX      INTEGER { active(1), notInservice(2), destroy(4)}
   MAX-ACCESS  read-write
   STATUS      current
   DESCRIPTION
       "1: active
        2: notInservice
        4: destroy"
   ::= { gs2352MACbasedVLANConfEntry 5 }

gs2352IGMPSnooping                                                           OBJECT IDENTIFIER ::= { gs2352Configuration 16 }

gs2352IGMPSnoopingBasic                                                      OBJECT IDENTIFIER ::= { gs2352IGMPSnooping 1 }

gs2352IGMPSnoopingEnable  OBJECT-TYPE
   SYNTAX      INTEGER { disable(0), enable(1) }
   MAX-ACCESS  read-write
   STATUS      current
   DESCRIPTION
       "Enable/Disable the Global IGMP Snooping"
   ::= { gs2352IGMPSnoopingBasic 1 }

gs2352IGMPSnoopingUnregisteredIPMCv4Flooding  OBJECT-TYPE
   SYNTAX      INTEGER { disable(0), enable(1) }
   MAX-ACCESS  read-write
   STATUS      current
   DESCRIPTION
       "Enable/Disable unregistered IPMCv4 traffic flooding. "
   ::= { gs2352IGMPSnoopingBasic 2 }

gs2352IGMPSnoopingSSMIPRangeAddr  OBJECT-TYPE
   SYNTAX      DisplayString
   MAX-ACCESS  read-write
   STATUS      current
   DESCRIPTION
       "SSM (Source-Specific Multicast) Range allows the SSM-aware hosts and
       routers run the SSM service model for the groups in the address range. "
   ::= { gs2352IGMPSnoopingBasic 3 }

gs2352IGMPSnoopingSSMIPRangeValue  OBJECT-TYPE
   SYNTAX      Integer32(4..32)
   MAX-ACCESS  read-write
   STATUS      current
   DESCRIPTION
       "SSM (Source-Specific Multicast) Range allows the SSM-aware hosts and
       routers run the SSM service model for the groups in the address range value. "
   ::= { gs2352IGMPSnoopingBasic 4 }

gs2352IGMPSnoopingProxyEnabled  OBJECT-TYPE
   SYNTAX      INTEGER { disable(0), enable(1) }
   MAX-ACCESS  read-write
   STATUS      current
   DESCRIPTION
       "Enable/Disable IGMP Proxy. This feature can be used to avoid forwarding
       unnecessary join and leave messages to the router side. "
   ::= { gs2352IGMPSnoopingBasic 5 }

gs2352IGMPSnoopingPortRelatedTable OBJECT-TYPE
   SYNTAX      SEQUENCE OF Gs2352IGMPSnoopingPortRelatedEntry
   MAX-ACCESS  not-accessible
   STATUS      current
   DESCRIPTION
       " Configure IGMP Snooping Port Related Configuration. "
   ::= { gs2352IGMPSnoopingBasic 6 }

gs2352IGMPSnoopingPortRelatedEntry OBJECT-TYPE
   SYNTAX      Gs2352IGMPSnoopingPortRelatedEntry
   MAX-ACCESS  not-accessible
   STATUS      current
   DESCRIPTION
       ""
   INDEX    { ifIndex  }
   ::= { gs2352IGMPSnoopingPortRelatedTable 1 }

Gs2352IGMPSnoopingPortRelatedEntry ::= SEQUENCE {
   gs2352IGMPSnoopingRouterPort	INTEGER,
   gs2352IGMPSnoopingFastLeave  	INTEGER,
   gs2352IGMPSnoopingThrottling    Integer32
}

gs2352IGMPSnoopingRouterPort OBJECT-TYPE
   SYNTAX      INTEGER { disable(0), enable(1) }
   MAX-ACCESS  read-write
   STATUS      current
   DESCRIPTION
       "Specify which ports act as router ports. A router port is a port on the
       Ethernet switch that leads towards the Layer 3 multicast device or IGMP
       querier. If an aggregation member port is selected as a router port, the
       whole aggregation will act as a router port. "
   ::= { gs2352IGMPSnoopingPortRelatedEntry 1 }

gs2352IGMPSnoopingFastLeave OBJECT-TYPE
   SYNTAX      INTEGER { disable(0), enable(1) }
   MAX-ACCESS  read-write
   STATUS      current
   DESCRIPTION
       "Enable/Disable the fast leave on the port. "
   ::= { gs2352IGMPSnoopingPortRelatedEntry 2 }

gs2352IGMPSnoopingThrottling OBJECT-TYPE
   SYNTAX      Integer32(0..10)
   MAX-ACCESS  read-write
   STATUS      current
   DESCRIPTION
       "Enable to limit the number of multicast groups to which a switch port can belong.
       0: unlimited"
   ::= { gs2352IGMPSnoopingPortRelatedEntry 3 }

gs2352IGMPSnoopingVLANTable OBJECT-TYPE
   SYNTAX      SEQUENCE OF Gs2352IGMPSnoopingVLANEntry
   MAX-ACCESS  not-accessible
   STATUS      current
   DESCRIPTION
       " Configure IGMP Snooping Vlan Configuration. "
   ::= { gs2352IGMPSnooping 2 }

gs2352IGMPSnoopingVLANEntry OBJECT-TYPE
   SYNTAX      Gs2352IGMPSnoopingVLANEntry
   MAX-ACCESS  not-accessible
   STATUS      current
   DESCRIPTION
       ""
   INDEX    { gs2352IGMPSnoopingVLANID  }
   ::= { gs2352IGMPSnoopingVLANTable 1 }

Gs2352IGMPSnoopingVLANEntry ::= SEQUENCE {
   gs2352IGMPSnoopingVLANID        	Integer32,
   gs2352IGMPSnoopingVLANEnable    	INTEGER,
   gs2352IGMPSnoopingVLANIGMPQuerier   INTEGER,
   gs2352IGMPSnoopingVLANCompatibility INTEGER,
   gs2352IGMPSnoopingVLANRV        	Integer32,
   gs2352IGMPSnoopingVLANQI      	    Integer32,
   gs2352IGMPSnoopingVLANQRI   	    Integer32,
   gs2352IGMPSnoopingVLANLLQI   	    Integer32,
   gs2352IGMPSnoopingVLANURI    	    Integer32
}

gs2352IGMPSnoopingVLANID OBJECT-TYPE
   SYNTAX      Integer32(1..4095)
   MAX-ACCESS  read-write
   STATUS      current
   DESCRIPTION
       "The VLAN ID of the entry"
   ::= { gs2352IGMPSnoopingVLANEntry 1 }

gs2352IGMPSnoopingVLANEnable OBJECT-TYPE
   SYNTAX      INTEGER { disable(0), enable(1) }
   MAX-ACCESS  read-write
   STATUS      current
   DESCRIPTION
       "Enable/Disable the per-VLAN IGMP Snooping. Up to 32 VLANs can be
       selected for IGMP Snooping. "
   ::= { gs2352IGMPSnoopingVLANEntry 2 }

gs2352IGMPSnoopingVLANIGMPQuerier OBJECT-TYPE
   SYNTAX      INTEGER { disable(0), enable(1) }
   MAX-ACCESS  read-write
   STATUS      current
   DESCRIPTION
       "Enable/Disable the IGMP Querier in the VLAN. "
   ::= { gs2352IGMPSnoopingVLANEntry 3 }

gs2352IGMPSnoopingVLANCompatibility OBJECT-TYPE
   SYNTAX      INTEGER { igmpAuto(0), forcedIGMPv1(1), forcedIGMPv2(2), forcedIGMPv3(3), none(4) }
   MAX-ACCESS  read-write
   STATUS      current
   DESCRIPTION
       "Compatibility is maintained by hosts and routers taking appropriate
       actions depending on the versions of IGMP operating on hosts and routers
       within a network. The allowed selection is IGMP-Auto, Forced IGMPv1,
       Forced IGMPv2, Forced IGMPv3, default compatibility value is IGMP-Auto. "
   ::= { gs2352IGMPSnoopingVLANEntry 4 }

gs2352IGMPSnoopingVLANRV OBJECT-TYPE
   SYNTAX      Integer32(-1|1..255)
   MAX-ACCESS  read-write
   STATUS      current
   DESCRIPTION
       "Robustness Variable. The Robustness Variable allows tuning for the
       expected packet loss on a network. The allowed range is 1 to 255, default
        robustness variable value is 2. (-1: none)"
   ::= { gs2352IGMPSnoopingVLANEntry 5 }

gs2352IGMPSnoopingVLANQI OBJECT-TYPE
   SYNTAX      Integer32(-1|1..31744)
   MAX-ACCESS  read-write
   STATUS      current
   DESCRIPTION
       "Query Interval. The Query Interval is the interval between General
       Queries sent by the Querier. The allowed range is 1 to 31744 seconds,
       default query interval is 125 seconds.  (-1: none)"
   ::= { gs2352IGMPSnoopingVLANEntry 6 }

gs2352IGMPSnoopingVLANQRI OBJECT-TYPE
   SYNTAX      Integer32(-1|0..31744)
   MAX-ACCESS  read-write
   STATUS      current
   DESCRIPTION
       "Query Response Interval. The Maximum Response Delay used to calculate
       the Maximum Response Code inserted into the periodic General Queries. The
        allowed range is 0 to 31744 in tenths of seconds, default query response
         interval is 100 in tenths of seconds (10 seconds).   (-1: none)"
   ::= { gs2352IGMPSnoopingVLANEntry 7 }

gs2352IGMPSnoopingVLANLLQI OBJECT-TYPE
   SYNTAX      Integer32(-1|0..31744)
   MAX-ACCESS  read-write
   STATUS      current
   DESCRIPTION
       "LLQI (LMQI for IGMP).  Last Member Query Interval. The Last Member Query
       Time is the time value represented by the Last Member Query Interval,
       multiplied by the Last Member Query Count. The allowed range is 0 to
       31744 in tenths of seconds, default last member query interval is 10 in
       tenths of seconds (1 second).    (-1: none)"
   ::= { gs2352IGMPSnoopingVLANEntry 8 }

gs2352IGMPSnoopingVLANURI OBJECT-TYPE
   SYNTAX      Integer32(-1|0..31744)
   MAX-ACCESS  read-write
   STATUS      current
   DESCRIPTION
       "Unsolicited Report Interval. The Unsolicited Report Interval is the time
        between repetitions of a host's initial report of membership in a group.
         The allowed range is 0 to 31744 seconds, default unsolicited report
         interval is 1 second.    (-1: none)"
   ::= { gs2352IGMPSnoopingVLANEntry 9 }

gs2352IGMPSnoopingPortGroupFiltering                                                      OBJECT IDENTIFIER ::= { gs2352IGMPSnooping 3 }

gs2352IGMPSnoopingPortGroupFilteringCreate OBJECT-TYPE
   SYNTAX       Integer32
   MAX-ACCESS   read-write
   STATUS       current
   DESCRIPTION
       "default: 0
       0 : None  (read only) 1 : Create IGMP Snooping Port Group Filtering "
   ::= { gs2352IGMPSnoopingPortGroupFiltering 1 }

gs2352IGMPSnoopingPortGroupFilteringTable OBJECT-TYPE
   SYNTAX      SEQUENCE OF Gs2352IGMPSnoopingPortGroupFilteringEntry
   MAX-ACCESS  not-accessible
   STATUS      current
   DESCRIPTION
       " Configure IGMP Snooping port group filtering. "
   ::= { gs2352IGMPSnoopingPortGroupFiltering 2 }

gs2352IGMPSnoopingPortGroupFilteringEntry OBJECT-TYPE
   SYNTAX      Gs2352IGMPSnoopingPortGroupFilteringEntry
   MAX-ACCESS  not-accessible
   STATUS      current
   DESCRIPTION
       ""
   INDEX    { gs2352IGMPSnoopingPortGroupFilteringIndex  }
   ::= { gs2352IGMPSnoopingPortGroupFilteringTable 1 }

Gs2352IGMPSnoopingPortGroupFilteringEntry ::= SEQUENCE {
   gs2352IGMPSnoopingPortGroupFilteringIndex         Integer32,
   gs2352IGMPSnoopingPortGroupFilteringPort          Integer32,
   gs2352IGMPSnoopingPortGroupFilteringGroups        DisplayString,
   gs2352IGMPSnoopingPortGroupFilteringRowStatus     INTEGER
}

gs2352IGMPSnoopingPortGroupFilteringIndex OBJECT-TYPE
   SYNTAX      Integer32(1..65535)
   MAX-ACCESS  not-accessible
   STATUS      current
   DESCRIPTION
       "IGMP Snooping Port Group Filtering Configuration Index. "
   ::= { gs2352IGMPSnoopingPortGroupFilteringEntry 1 }

gs2352IGMPSnoopingPortGroupFilteringPort OBJECT-TYPE
   SYNTAX      Integer32(1..65535)
   MAX-ACCESS  read-write
   STATUS      current
   DESCRIPTION
       "The logical port for the settings. "
   ::= { gs2352IGMPSnoopingPortGroupFilteringEntry 2 }

gs2352IGMPSnoopingPortGroupFilteringGroups OBJECT-TYPE
   SYNTAX      DisplayString
   MAX-ACCESS  read-write
   STATUS      current
   DESCRIPTION
       "The IP Multicast Group that will be filtered. "
   ::= { gs2352IGMPSnoopingPortGroupFilteringEntry 3 }

gs2352IGMPSnoopingPortGroupFilteringRowStatus OBJECT-TYPE
   SYNTAX      INTEGER { active(1), notInservice(2), destroy(4)}
   MAX-ACCESS  read-write
   STATUS      current
   DESCRIPTION
       "1: active
        2: notInservice
        4: destroy"
   ::= { gs2352IGMPSnoopingPortGroupFilteringEntry 4 }

gs2352IGMPSnoopingStatus                                                      OBJECT IDENTIFIER ::= { gs2352IGMPSnooping 4 }

gs2352IGMPSnoopingstatisticClear OBJECT-TYPE
   SYNTAX      INTEGER { none(0), clear(1)}
   MAX-ACCESS  read-write
   STATUS      current
   DESCRIPTION
       "Clears all Statistics counters."
   ::= { gs2352IGMPSnoopingStatus 1 }


gs2352IGMPSnoopingstatisticTable OBJECT-TYPE
   SYNTAX      SEQUENCE OF Gs2352IGMPSnoopingstatisticEntry
   MAX-ACCESS  not-accessible
   STATUS      current
   DESCRIPTION
       " Configure Vlan Port Isolation Configuration. "
   ::= { gs2352IGMPSnoopingStatus 2 }

gs2352IGMPSnoopingstatisticEntry OBJECT-TYPE
   SYNTAX      Gs2352IGMPSnoopingstatisticEntry
   MAX-ACCESS  not-accessible
   STATUS      current
   DESCRIPTION
       ""
   INDEX    { gs2352IGMPSnoopingstatisticVLANID  }
   ::= { gs2352IGMPSnoopingstatisticTable 1 }

Gs2352IGMPSnoopingstatisticEntry ::= SEQUENCE {
   gs2352IGMPSnoopingstatisticVLANID              Integer32,
   gs2352IGMPSnoopingstatisticQuerierVersion      DisplayString,
   gs2352IGMPSnoopingstatisticHostVersion         DisplayString,
   gs2352IGMPSnoopingstatisticQuerierStatus       DisplayString,
   gs2352IGMPSnoopingstatisticQueriesTransmitted  Counter32,
   gs2352IGMPSnoopingstatisticQueriesReceived     Counter32,
   gs2352IGMPSnoopingstatisticV1ReportsReceived   Counter32,
   gs2352IGMPSnoopingstatisticV2ReportsReceived   Counter32,
   gs2352IGMPSnoopingstatisticV3ReportsReceived   Counter32,
   gs2352IGMPSnoopingstatisticV2LeavesReceived    Counter32
}


gs2352IGMPSnoopingstatisticVLANID OBJECT-TYPE
   SYNTAX      Integer32(1..4095)
   MAX-ACCESS  read-only
   STATUS      current
   DESCRIPTION
       "The VLAN ID of the entry. "
   ::= { gs2352IGMPSnoopingstatisticEntry 1 }

gs2352IGMPSnoopingstatisticQuerierVersion OBJECT-TYPE
   SYNTAX      DisplayString
   MAX-ACCESS  read-only
   STATUS      current
   DESCRIPTION
       "Working Querier Version currently. "
   ::= { gs2352IGMPSnoopingstatisticEntry 2 }

gs2352IGMPSnoopingstatisticHostVersion OBJECT-TYPE
   SYNTAX      DisplayString
   MAX-ACCESS  read-only
   STATUS      current
   DESCRIPTION
       "Working Host Version currently. "
   ::= { gs2352IGMPSnoopingstatisticEntry 3 }

gs2352IGMPSnoopingstatisticQuerierStatus OBJECT-TYPE
   SYNTAX      DisplayString
   MAX-ACCESS  read-only
   STATUS      current
   DESCRIPTION
       "Shows the Querier status is ACTIVE or IDLE. DISABLE denotes the specific
        interface is administratively disabled. "
   ::= { gs2352IGMPSnoopingstatisticEntry 4 }

gs2352IGMPSnoopingstatisticQueriesTransmitted OBJECT-TYPE
   SYNTAX      Counter32
   MAX-ACCESS  read-only
   STATUS      current
   DESCRIPTION
       "The number of Transmitted Queries. "
   ::= { gs2352IGMPSnoopingstatisticEntry 5 }

gs2352IGMPSnoopingstatisticQueriesReceived OBJECT-TYPE
   SYNTAX      Counter32
   MAX-ACCESS  read-only
   STATUS      current
   DESCRIPTION
       "The number of Received Queries. "
   ::= { gs2352IGMPSnoopingstatisticEntry 6 }

gs2352IGMPSnoopingstatisticV1ReportsReceived OBJECT-TYPE
   SYNTAX      Counter32
   MAX-ACCESS  read-only
   STATUS      current
   DESCRIPTION
       "The number of Received V1 Reports. "
   ::= { gs2352IGMPSnoopingstatisticEntry 7 }

gs2352IGMPSnoopingstatisticV2ReportsReceived OBJECT-TYPE
   SYNTAX      Counter32
   MAX-ACCESS  read-only
   STATUS      current
   DESCRIPTION
       "The number of Received V2 Reports. "
   ::= { gs2352IGMPSnoopingstatisticEntry 8 }

gs2352IGMPSnoopingstatisticV3ReportsReceived OBJECT-TYPE
   SYNTAX      Counter32
   MAX-ACCESS  read-only
   STATUS      current
   DESCRIPTION
       "The number of Received V3 Reports. "
   ::= { gs2352IGMPSnoopingstatisticEntry 9 }

gs2352IGMPSnoopingstatisticV2LeavesReceived OBJECT-TYPE
   SYNTAX      Counter32
   MAX-ACCESS  read-only
   STATUS      current
   DESCRIPTION
       "The number of Received V2 Leaves. "
   ::= { gs2352IGMPSnoopingstatisticEntry 10 }

gs2352IGMPSnoopingRouterPortTable OBJECT-TYPE
   SYNTAX      SEQUENCE OF Gs2352IGMPSnoopingRouterPortEntry
   MAX-ACCESS  not-accessible
   STATUS      current
   DESCRIPTION
       " Configure Vlan Port Isolation Configuration. "
   ::= { gs2352IGMPSnoopingStatus 3 }

gs2352IGMPSnoopingRouterPortEntry OBJECT-TYPE
   SYNTAX      Gs2352IGMPSnoopingRouterPortEntry
   MAX-ACCESS  not-accessible
   STATUS      current
   DESCRIPTION
       ""
   INDEX    { ifIndex  }
   ::= { gs2352IGMPSnoopingRouterPortTable 1 }

Gs2352IGMPSnoopingRouterPortEntry ::= SEQUENCE {
   gs2352IGMPSnoopingRouterPortStatus            DisplayString
}

gs2352IGMPSnoopingRouterPortStatus OBJECT-TYPE
   SYNTAX      DisplayString
   MAX-ACCESS  read-only
   STATUS      current
   DESCRIPTION
       "Display which ports act as router ports. A router port is a port on the
       Ethernet switch that leads towards the Layer 3 multicast device or IGMP
       querier.
       Static denotes the specific port is configured to be a router port.
       Dynamic denotes the specific port is learnt to be a router port.
       Both denote the specific port is configured or learnt to be a router port. "
   ::= { gs2352IGMPSnoopingRouterPortEntry 1 }

gs2352IGMPSnoopingGroupsTable OBJECT-TYPE
   SYNTAX      SEQUENCE OF Gs2352IGMPSnoopingGroupsEntry
   MAX-ACCESS  not-accessible
   STATUS      current
   DESCRIPTION
       "IGMP Snooping Groups Information . "
   ::= { gs2352IGMPSnooping 5 }

gs2352IGMPSnoopingGroupsEntry OBJECT-TYPE
   SYNTAX      Gs2352IGMPSnoopingGroupsEntry
   MAX-ACCESS  not-accessible
   STATUS      current
   DESCRIPTION
       ""
   INDEX    { gs2352IGMPSnoopingGroupsIndex  }
   ::= { gs2352IGMPSnoopingGroupsTable 1 }

Gs2352IGMPSnoopingGroupsEntry ::= SEQUENCE {
   gs2352IGMPSnoopingGroupsIndex          Integer32,
   gs2352IGMPSnoopingGroupsVLANID         Integer32,
   gs2352IGMPSnoopingGroups               InetAddress,
   gs2352IGMPSnoopingGroupsMemberships    DisplayString
}

gs2352IGMPSnoopingGroupsIndex OBJECT-TYPE
   SYNTAX      Integer32(1..65535)
   MAX-ACCESS  not-accessible
   STATUS      current
   DESCRIPTION
       "IGMP Snooping Groups Index"
   ::= { gs2352IGMPSnoopingGroupsEntry 1 }

gs2352IGMPSnoopingGroupsVLANID OBJECT-TYPE
   SYNTAX      Integer32(1..4095)
   MAX-ACCESS  read-only
   STATUS      current
   DESCRIPTION
       "VLAN ID of the group. "
   ::= { gs2352IGMPSnoopingGroupsEntry 2 }

gs2352IGMPSnoopingGroups OBJECT-TYPE
   SYNTAX      DisplayString
   MAX-ACCESS  read-only
   STATUS      current
   DESCRIPTION
       "Group address of the group displayed."
   ::= { gs2352IGMPSnoopingGroupsEntry 3 }

gs2352IGMPSnoopingGroupsMemberships OBJECT-TYPE
   SYNTAX      DisplayString
   MAX-ACCESS  read-only
   STATUS      current
   DESCRIPTION
       "Ports under this group."
   ::= { gs2352IGMPSnoopingGroupsEntry 4 }

gs2352IGMPSnoopingSSMTable OBJECT-TYPE
   SYNTAX      SEQUENCE OF Gs2352IGMPSnoopingSSMEntry
   MAX-ACCESS  not-accessible
   STATUS      current
   DESCRIPTION
       "The IGMP SFM (Source-Filtered Multicast) Information Table also contains
        the SSM (Source-Specific Multicast) information. This table is sorted
         first by VLAN ID, then by group, and then by Port. Different source
         addresses belong to the same group are treated as single entry."
   ::= { gs2352IGMPSnooping 6 }

gs2352IGMPSnoopingSSMEntry OBJECT-TYPE
   SYNTAX      Gs2352IGMPSnoopingSSMEntry
   MAX-ACCESS  not-accessible
   STATUS      current
   DESCRIPTION
       ""
   INDEX    { gs2352IGMPSnoopingSSMIndex  }
   ::= { gs2352IGMPSnoopingSSMTable 1 }

Gs2352IGMPSnoopingSSMEntry ::= SEQUENCE {
   gs2352IGMPSnoopingSSMIndex          Integer32,
   gs2352IGMPSnoopingSSMVLANID         Integer32,
   gs2352IGMPSnoopingSSMGroup          DisplayString,
   gs2352IGMPSnoopingSSMPort           Integer32,
   gs2352IGMPSnoopingSSMMode           DisplayString,
   gs2352IGMPSnoopingSSMSourceAddress  DisplayString,
   gs2352IGMPSnoopingSSMType           DisplayString
}

gs2352IGMPSnoopingSSMIndex OBJECT-TYPE
   SYNTAX      Integer32(1..65535)
   MAX-ACCESS  not-accessible
   STATUS      current
   DESCRIPTION
       "IGMP Snooping SSM Index"
   ::= { gs2352IGMPSnoopingSSMEntry 1 }

gs2352IGMPSnoopingSSMVLANID OBJECT-TYPE
   SYNTAX      Integer32(1..4095)
   MAX-ACCESS  read-only
   STATUS      current
   DESCRIPTION
       "VLAN ID of the group. "
   ::= { gs2352IGMPSnoopingSSMEntry 2 }

gs2352IGMPSnoopingSSMGroup OBJECT-TYPE
   SYNTAX      DisplayString
   MAX-ACCESS  read-only
   STATUS      current
   DESCRIPTION
       "Group address of the group displayed."
   ::= { gs2352IGMPSnoopingSSMEntry 3 }

gs2352IGMPSnoopingSSMPort OBJECT-TYPE
   SYNTAX      Integer32(1..65535)
   MAX-ACCESS  read-only
   STATUS      current
   DESCRIPTION
       "Ports under this group."
   ::= { gs2352IGMPSnoopingSSMEntry 4 }

gs2352IGMPSnoopingSSMMode OBJECT-TYPE
   SYNTAX      DisplayString
   MAX-ACCESS  read-only
   STATUS      current
   DESCRIPTION
       "Indicates the filtering mode maintained per (VLAN ID, port number,
       Group Address) basis. It can be either Include or Exclude."
   ::= { gs2352IGMPSnoopingSSMEntry 5 }

gs2352IGMPSnoopingSSMSourceAddress OBJECT-TYPE
   SYNTAX      DisplayString
   MAX-ACCESS  read-only
   STATUS      current
   DESCRIPTION
       "IP Address of the source. Currently, system limits the total number of
       IP source addresses for filtering to be 128."
   ::= { gs2352IGMPSnoopingSSMEntry 6 }

gs2352IGMPSnoopingSSMType OBJECT-TYPE
   SYNTAX      DisplayString
   MAX-ACCESS  read-only
   STATUS      current
   DESCRIPTION
       "Indicates the Type. It can be either Allow or Deny."
   ::= { gs2352IGMPSnoopingSSMEntry 7 }

gs2352MLDSnooping                                                           OBJECT IDENTIFIER ::= { gs2352Configuration 17 }

gs2352MLDSnoopingBasic                                                      OBJECT IDENTIFIER ::= { gs2352MLDSnooping 1 }

gs2352MLDSnoopingEnable  OBJECT-TYPE
   SYNTAX      INTEGER { disable(0), enable(1) }
   MAX-ACCESS  read-write
   STATUS      current
   DESCRIPTION
       "Enable/Disable the Global MLD Snooping"
   ::= { gs2352MLDSnoopingBasic 1 }

gs2352MLDSnoopingUnregisteredIPMCv6Flooding  OBJECT-TYPE
   SYNTAX      INTEGER { disable(0), enable(1) }
   MAX-ACCESS  read-write
   STATUS      current
   DESCRIPTION
       "Enable/Disable unregistered IPMCv6 traffic flooding. "
   ::= { gs2352MLDSnoopingBasic 2 }

gs2352MLDSnoopingSSMIPRangeAddr  OBJECT-TYPE
   SYNTAX      DisplayString
   MAX-ACCESS  read-write
   STATUS      current
   DESCRIPTION
       "SSM (Source-Specific Multicast) Range allows the SSM-aware hosts and
       routers run the SSM service model for the groups in the address range. "
   ::= { gs2352MLDSnoopingBasic 3 }

gs2352MLDSnoopingSSMIPRangeValue  OBJECT-TYPE
   SYNTAX      Integer32(8..128)
   MAX-ACCESS  read-write
   STATUS      current
   DESCRIPTION
       "SSM (Source-Specific Multicast) Range allows the SSM-aware hosts and
       routers run the SSM service model for the groups in the address range value. "
   ::= { gs2352MLDSnoopingBasic 4 }

gs2352MLDSnoopingProxyEnabled  OBJECT-TYPE
   SYNTAX      INTEGER { disable(0), enable(1) }
   MAX-ACCESS  read-write
   STATUS      current
   DESCRIPTION
       "Enable/Disable MLD Proxy. This feature can be used to avoid forwarding
       unnecessary join and leave messages to the router side. "
   ::= { gs2352MLDSnoopingBasic 5 }

gs2352MLDSnoopingPortRelatedTable OBJECT-TYPE
   SYNTAX      SEQUENCE OF Gs2352MLDSnoopingPortRelatedEntry
   MAX-ACCESS  not-accessible
   STATUS      current
   DESCRIPTION
       " Configure MLD Snooping Port Related Configuration. "
   ::= { gs2352MLDSnoopingBasic 6 }

gs2352MLDSnoopingPortRelatedEntry OBJECT-TYPE
   SYNTAX      Gs2352MLDSnoopingPortRelatedEntry
   MAX-ACCESS  not-accessible
   STATUS      current
   DESCRIPTION
       ""
   INDEX    { ifIndex  }
   ::= { gs2352MLDSnoopingPortRelatedTable 1 }

Gs2352MLDSnoopingPortRelatedEntry ::= SEQUENCE {
   gs2352MLDSnoopingRouterPort	INTEGER,
   gs2352MLDSnoopingFastLeave  	INTEGER,
   gs2352MLDSnoopingThrottling    Integer32
}

gs2352MLDSnoopingRouterPort OBJECT-TYPE
   SYNTAX      INTEGER { disable(0), enable(1) }
   MAX-ACCESS  read-write
   STATUS      current
   DESCRIPTION
       "Specify which ports act as router ports. A router port is a port on the
       Ethernet switch that leads towards the Layer 3 multicast device or IGMP
       querier. If an aggregation member port is selected as a router port, the
       whole aggregation will act as a router port. "
   ::= { gs2352MLDSnoopingPortRelatedEntry 1 }

gs2352MLDSnoopingFastLeave OBJECT-TYPE
   SYNTAX      INTEGER { disable(0), enable(1) }
   MAX-ACCESS  read-write
   STATUS      current
   DESCRIPTION
       "Enable/Disable the fast leave on the port. "
   ::= { gs2352MLDSnoopingPortRelatedEntry 2 }

gs2352MLDSnoopingThrottling OBJECT-TYPE
   SYNTAX      Integer32(0..10)
   MAX-ACCESS  read-write
   STATUS      current
   DESCRIPTION
       "Enable to limit the number of multicast groups to which a switch port can belong.
       0: unlimited"
   ::= { gs2352MLDSnoopingPortRelatedEntry 3 }

gs2352MLDSnoopingVLANTable OBJECT-TYPE
   SYNTAX      SEQUENCE OF Gs2352MLDSnoopingVLANEntry
   MAX-ACCESS  not-accessible
   STATUS      current
   DESCRIPTION
       " Configure MLD Snooping Vlan Configuration. "
   ::= { gs2352MLDSnooping 2 }

gs2352MLDSnoopingVLANEntry OBJECT-TYPE
   SYNTAX      Gs2352MLDSnoopingVLANEntry
   MAX-ACCESS  not-accessible
   STATUS      current
   DESCRIPTION
       ""
   INDEX    { gs2352MLDSnoopingVLANID  }
   ::= { gs2352MLDSnoopingVLANTable 1 }

Gs2352MLDSnoopingVLANEntry ::= SEQUENCE {
   gs2352MLDSnoopingVLANID        	Integer32,
   gs2352MLDSnoopingVLANEnable    	INTEGER,
   gs2352MLDSnoopingVLANIGMPQuerier   INTEGER,
   gs2352MLDSnoopingVLANCompatibility INTEGER,
   gs2352MLDSnoopingVLANRV        	Integer32,
   gs2352MLDSnoopingVLANQI      	    Integer32,
   gs2352MLDSnoopingVLANQRI   	    Integer32,
   gs2352MLDSnoopingVLANLLQI   	    Integer32,
   gs2352MLDSnoopingVLANURI    	    Integer32
}

gs2352MLDSnoopingVLANID OBJECT-TYPE
   SYNTAX      Integer32(1..4095)
   MAX-ACCESS  read-write
   STATUS      current
   DESCRIPTION
       "The VLAN ID of the entry"
   ::= { gs2352MLDSnoopingVLANEntry 1 }

gs2352MLDSnoopingVLANEnable OBJECT-TYPE
   SYNTAX      INTEGER { disable(0), enable(1) }
   MAX-ACCESS  read-write
   STATUS      current
   DESCRIPTION
       "Enable/Disable the per-VLAN MLD Snooping. Up to 32 VLANs can be
       selected for MLD Snooping. "
   ::= { gs2352MLDSnoopingVLANEntry 2 }

gs2352MLDSnoopingVLANIGMPQuerier OBJECT-TYPE
   SYNTAX      INTEGER { disable(0), enable(1) }
   MAX-ACCESS  read-write
   STATUS      current
   DESCRIPTION
       "Enable/Disable the MLD Querier in the VLAN. "
   ::= { gs2352MLDSnoopingVLANEntry 3 }

gs2352MLDSnoopingVLANCompatibility OBJECT-TYPE
   SYNTAX      INTEGER { mldAuto(0), forcedMLDv1(1), forcedMLDv2(2), none(3) }
   MAX-ACCESS  read-write
   STATUS      current
   DESCRIPTION
       "Compatibility is maintained by hosts and routers taking appropriate
       actions depending on the versions of IGMP operating on hosts and routers
       within a network. The allowed selection is MLD-Auto, Forced MLDv1,
       Forced MLDv2, default compatibility value is IGMP-Auto. "
   ::= { gs2352MLDSnoopingVLANEntry 4 }

gs2352MLDSnoopingVLANRV OBJECT-TYPE
   SYNTAX      Integer32(-1|1..255)
   MAX-ACCESS  read-write
   STATUS      current
   DESCRIPTION
       "Robustness Variable. The Robustness Variable allows tuning for the
       expected packet loss on a network. The allowed range is 1 to 255, default
        robustness variable value is 2. (-1: none)"
   ::= { gs2352MLDSnoopingVLANEntry 5 }

gs2352MLDSnoopingVLANQI OBJECT-TYPE
   SYNTAX      Integer32(-1|1..31744)
   MAX-ACCESS  read-write
   STATUS      current
   DESCRIPTION
       "Query Interval. The Query Interval is the interval between General
       Queries sent by the Querier. The allowed range is 1 to 31744 seconds,
       default query interval is 125 seconds.  (-1: none)"
   ::= { gs2352MLDSnoopingVLANEntry 6 }

gs2352MLDSnoopingVLANQRI OBJECT-TYPE
   SYNTAX      Integer32(-1|0..31744)
   MAX-ACCESS  read-write
   STATUS      current
   DESCRIPTION
       "Query Response Interval. The Maximum Response Delay used to calculate
       the Maximum Response Code inserted into the periodic General Queries. The
        allowed range is 0 to 31744 in tenths of seconds, default query response
         interval is 100 in tenths of seconds (10 seconds).   (-1: none)"
   ::= { gs2352MLDSnoopingVLANEntry 7 }

gs2352MLDSnoopingVLANLLQI OBJECT-TYPE
   SYNTAX      Integer32(-1|0..31744)
   MAX-ACCESS  read-write
   STATUS      current
   DESCRIPTION
       "LLQI (LMQI for MLD).  Last Member Query Interval. The Last Member Query
       Time is the time value represented by the Last Member Query Interval,
       multiplied by the Last Member Query Count. The allowed range is 0 to
       31744 in tenths of seconds, default last member query interval is 10 in
       tenths of seconds (1 second).    (-1: none)"
   ::= { gs2352MLDSnoopingVLANEntry 8 }

gs2352MLDSnoopingVLANURI OBJECT-TYPE
   SYNTAX      Integer32(-1|0..31744)
   MAX-ACCESS  read-write
   STATUS      current
   DESCRIPTION
       "Unsolicited Report Interval. The Unsolicited Report Interval is the time
        between repetitions of a host's initial report of membership in a group.
         The allowed range is 0 to 31744 seconds, default unsolicited report
         interval is 1 second.    (-1: none)"
   ::= { gs2352MLDSnoopingVLANEntry 9 }

gs2352MLDSnoopingPortGroupFiltering                                                      OBJECT IDENTIFIER ::= { gs2352MLDSnooping 3 }

gs2352MLDSnoopingPortGroupFilteringCreate OBJECT-TYPE
   SYNTAX       Integer32
   MAX-ACCESS   read-write
   STATUS       current
   DESCRIPTION
       "default: 0
       0 : None  (read only) 1 : Create MLD Snooping Port Group Filtering "
   ::= { gs2352MLDSnoopingPortGroupFiltering 1 }

gs2352MLDSnoopingPortGroupFilteringTable OBJECT-TYPE
   SYNTAX      SEQUENCE OF Gs2352MLDSnoopingPortGroupFilteringEntry
   MAX-ACCESS  not-accessible
   STATUS      current
   DESCRIPTION
       " Configure MLD Snooping port group filtering. "
   ::= { gs2352MLDSnoopingPortGroupFiltering 2 }

gs2352MLDSnoopingPortGroupFilteringEntry OBJECT-TYPE
   SYNTAX      Gs2352MLDSnoopingPortGroupFilteringEntry
   MAX-ACCESS  not-accessible
   STATUS      current
   DESCRIPTION
       ""
   INDEX    { gs2352MLDSnoopingPortGroupFilteringIndex  }
   ::= { gs2352MLDSnoopingPortGroupFilteringTable 1 }

Gs2352MLDSnoopingPortGroupFilteringEntry ::= SEQUENCE {
   gs2352MLDSnoopingPortGroupFilteringIndex         Integer32,
   gs2352MLDSnoopingPortGroupFilteringPort          Integer32,
   gs2352MLDSnoopingPortGroupFilteringGroups        DisplayString,
   gs2352MLDSnoopingPortGroupFilteringRowStatus     INTEGER
}

gs2352MLDSnoopingPortGroupFilteringIndex OBJECT-TYPE
   SYNTAX      Integer32(1..65535)
   MAX-ACCESS  not-accessible
   STATUS      current
   DESCRIPTION
       "MLD Snooping Port Group Filtering Configuration Index. "
   ::= { gs2352MLDSnoopingPortGroupFilteringEntry 1 }

gs2352MLDSnoopingPortGroupFilteringPort OBJECT-TYPE
   SYNTAX      Integer32(1..65535)
   MAX-ACCESS  read-write
   STATUS      current
   DESCRIPTION
       "The logical port for the settings. "
   ::= { gs2352MLDSnoopingPortGroupFilteringEntry 2 }

gs2352MLDSnoopingPortGroupFilteringGroups OBJECT-TYPE
   SYNTAX      DisplayString
   MAX-ACCESS  read-write
   STATUS      current
   DESCRIPTION
       "The IP Multicast Group that will be filtered. "
   ::= { gs2352MLDSnoopingPortGroupFilteringEntry 3 }

gs2352MLDSnoopingPortGroupFilteringRowStatus OBJECT-TYPE
   SYNTAX      INTEGER { active(1), notInservice(2), destroy(4)}
   MAX-ACCESS  read-write
   STATUS      current
   DESCRIPTION
       "1: active
        2: notInservice
        4: destroy"
   ::= { gs2352MLDSnoopingPortGroupFilteringEntry 4 }

gs2352MLDSnoopingStatus                                                      OBJECT IDENTIFIER ::= { gs2352MLDSnooping 4 }

gs2352MLDSnoopingstatisticClear OBJECT-TYPE
   SYNTAX      INTEGER { none(0), clear(1)}
   MAX-ACCESS  read-write
   STATUS      current
   DESCRIPTION
       "Clears all Statistics counters."
   ::= { gs2352MLDSnoopingStatus 1 }


gs2352MLDSnoopingstatisticTable OBJECT-TYPE
   SYNTAX      SEQUENCE OF Gs2352MLDSnoopingstatisticEntry
   MAX-ACCESS  not-accessible
   STATUS      current
   DESCRIPTION
       " Configure Vlan Port Isolation Configuration. "
   ::= { gs2352MLDSnoopingStatus 2 }

gs2352MLDSnoopingstatisticEntry OBJECT-TYPE
   SYNTAX      Gs2352MLDSnoopingstatisticEntry
   MAX-ACCESS  not-accessible
   STATUS      current
   DESCRIPTION
       ""
   INDEX    { gs2352MLDSnoopingstatisticVLANID  }
   ::= { gs2352MLDSnoopingstatisticTable 1 }

Gs2352MLDSnoopingstatisticEntry ::= SEQUENCE {
   gs2352MLDSnoopingstatisticVLANID              Integer32,
   gs2352MLDSnoopingstatisticQuerierVersion      DisplayString,
   gs2352MLDSnoopingstatisticHostVersion         DisplayString,
   gs2352MLDSnoopingstatisticQuerierStatus       DisplayString,
   gs2352MLDSnoopingstatisticQueriesTransmitted  Counter32,
   gs2352MLDSnoopingstatisticQueriesReceived     Counter32,
   gs2352MLDSnoopingstatisticV1ReportsReceived   Counter32,
   gs2352MLDSnoopingstatisticV2ReportsReceived   Counter32,
   gs2352MLDSnoopingstatisticV1LeavesReceived    Counter32
}


gs2352MLDSnoopingstatisticVLANID OBJECT-TYPE
   SYNTAX      Integer32(1..4095)
   MAX-ACCESS  read-only
   STATUS      current
   DESCRIPTION
       "The VLAN ID of the entry. "
   ::= { gs2352MLDSnoopingstatisticEntry 1 }

gs2352MLDSnoopingstatisticQuerierVersion OBJECT-TYPE
   SYNTAX      DisplayString
   MAX-ACCESS  read-only
   STATUS      current
   DESCRIPTION
       "Working Querier Version currently. "
   ::= { gs2352MLDSnoopingstatisticEntry 2 }

gs2352MLDSnoopingstatisticHostVersion OBJECT-TYPE
   SYNTAX      DisplayString
   MAX-ACCESS  read-only
   STATUS      current
   DESCRIPTION
       "Working Host Version currently. "
   ::= { gs2352MLDSnoopingstatisticEntry 3 }

gs2352MLDSnoopingstatisticQuerierStatus OBJECT-TYPE
   SYNTAX      DisplayString
   MAX-ACCESS  read-only
   STATUS      current
   DESCRIPTION
       "Shows the Querier status is ACTIVE or IDLE. DISABLE denotes the specific
        interface is administratively disabled. "
   ::= { gs2352MLDSnoopingstatisticEntry 4 }

gs2352MLDSnoopingstatisticQueriesTransmitted OBJECT-TYPE
   SYNTAX      Counter32
   MAX-ACCESS  read-only
   STATUS      current
   DESCRIPTION
       "The number of Transmitted Queries. "
   ::= { gs2352MLDSnoopingstatisticEntry 5 }

gs2352MLDSnoopingstatisticQueriesReceived OBJECT-TYPE
   SYNTAX      Counter32
   MAX-ACCESS  read-only
   STATUS      current
   DESCRIPTION
       "The number of Received Queries. "
   ::= { gs2352MLDSnoopingstatisticEntry 6 }

gs2352MLDSnoopingstatisticV1ReportsReceived OBJECT-TYPE
   SYNTAX      Counter32
   MAX-ACCESS  read-only
   STATUS      current
   DESCRIPTION
       "The number of Received V1 Reports. "
   ::= { gs2352MLDSnoopingstatisticEntry 7 }

gs2352MLDSnoopingstatisticV2ReportsReceived OBJECT-TYPE
   SYNTAX      Counter32
   MAX-ACCESS  read-only
   STATUS      current
   DESCRIPTION
       "The number of Received V2 Reports. "
   ::= { gs2352MLDSnoopingstatisticEntry 8 }

gs2352MLDSnoopingstatisticV1LeavesReceived OBJECT-TYPE
   SYNTAX      Counter32
   MAX-ACCESS  read-only
   STATUS      current
   DESCRIPTION
       "The number of Received V1 Leaves. "
   ::= { gs2352MLDSnoopingstatisticEntry 9 }

gs2352MLDSnoopingRouterPortTable OBJECT-TYPE
   SYNTAX      SEQUENCE OF Gs2352MLDSnoopingRouterPortEntry
   MAX-ACCESS  not-accessible
   STATUS      current
   DESCRIPTION
       " Configure Vlan Port Isolation Configuration. "
   ::= { gs2352MLDSnoopingStatus 3 }

gs2352MLDSnoopingRouterPortEntry OBJECT-TYPE
   SYNTAX      Gs2352MLDSnoopingRouterPortEntry
   MAX-ACCESS  not-accessible
   STATUS      current
   DESCRIPTION
       ""
   INDEX    { ifIndex  }
   ::= { gs2352MLDSnoopingRouterPortTable 1 }

Gs2352MLDSnoopingRouterPortEntry ::= SEQUENCE {
   gs2352MLDSnoopingRouterPortStatus            DisplayString
}

gs2352MLDSnoopingRouterPortStatus OBJECT-TYPE
   SYNTAX      DisplayString
   MAX-ACCESS  read-only
   STATUS      current
   DESCRIPTION
       "Display which ports act as router ports. A router port is a port on the
       Ethernet switch that leads towards the Layer 3 multicast device or IGMP
       querier.
       Static denotes the specific port is configured to be a router port.
       Dynamic denotes the specific port is learnt to be a router port.
       Both denote the specific port is configured or learnt to be a router port. "
   ::= { gs2352MLDSnoopingRouterPortEntry 1 }

gs2352MLDSnoopingGroupsTable OBJECT-TYPE
   SYNTAX      SEQUENCE OF Gs2352MLDSnoopingGroupsEntry
   MAX-ACCESS  not-accessible
   STATUS      current
   DESCRIPTION
       "MLD Snooping Groups Information . "
   ::= { gs2352MLDSnooping 5 }

gs2352MLDSnoopingGroupsEntry OBJECT-TYPE
   SYNTAX      Gs2352MLDSnoopingGroupsEntry
   MAX-ACCESS  not-accessible
   STATUS      current
   DESCRIPTION
       ""
   INDEX    { gs2352MLDSnoopingGroupsIndex  }
   ::= { gs2352MLDSnoopingGroupsTable 1 }

Gs2352MLDSnoopingGroupsEntry ::= SEQUENCE {
   gs2352MLDSnoopingGroupsIndex          Integer32,
   gs2352MLDSnoopingGroupsVLANID         Integer32,
   gs2352MLDSnoopingGroups               InetAddress,
   gs2352MLDSnoopingGroupsMemberships    DisplayString
}

gs2352MLDSnoopingGroupsIndex OBJECT-TYPE
   SYNTAX      Integer32(1..65535)
   MAX-ACCESS  not-accessible
   STATUS      current
   DESCRIPTION
       "MLD Snooping Groups Index"
   ::= { gs2352MLDSnoopingGroupsEntry 1 }

gs2352MLDSnoopingGroupsVLANID OBJECT-TYPE
   SYNTAX      Integer32(1..4095)
   MAX-ACCESS  read-only
   STATUS      current
   DESCRIPTION
       "VLAN ID of the group. "
   ::= { gs2352MLDSnoopingGroupsEntry 2 }

gs2352MLDSnoopingGroups OBJECT-TYPE
   SYNTAX      DisplayString
   MAX-ACCESS  read-only
   STATUS      current
   DESCRIPTION
       "Group address of the group displayed."
   ::= { gs2352MLDSnoopingGroupsEntry 3 }

gs2352MLDSnoopingGroupsMemberships OBJECT-TYPE
   SYNTAX      DisplayString
   MAX-ACCESS  read-only
   STATUS      current
   DESCRIPTION
       "Ports under this group."
   ::= { gs2352MLDSnoopingGroupsEntry 4 }

gs2352MLDSnoopingSSMTable OBJECT-TYPE
   SYNTAX      SEQUENCE OF Gs2352MLDSnoopingSSMEntry
   MAX-ACCESS  not-accessible
   STATUS      current
   DESCRIPTION
       "The MLD SFM (Source-Filtered Multicast) Information Table also contains
        the SSM (Source-Specific Multicast) information. This table is sorted
         first by VLAN ID, then by group, and then by Port. Different source
         addresses belong to the same group are treated as single entry."
   ::= { gs2352MLDSnooping 6 }

gs2352MLDSnoopingSSMEntry OBJECT-TYPE
   SYNTAX      Gs2352MLDSnoopingSSMEntry
   MAX-ACCESS  not-accessible
   STATUS      current
   DESCRIPTION
       ""
   INDEX    { gs2352MLDSnoopingSSMIndex  }
   ::= { gs2352MLDSnoopingSSMTable 1 }

Gs2352MLDSnoopingSSMEntry ::= SEQUENCE {
   gs2352MLDSnoopingSSMIndex          Integer32,
   gs2352MLDSnoopingSSMVLANID         Integer32,
   gs2352MLDSnoopingSSMGroup          DisplayString,
   gs2352MLDSnoopingSSMPort           Integer32,
   gs2352MLDSnoopingSSMMode           DisplayString,
   gs2352MLDSnoopingSSMSourceAddress  DisplayString,
   gs2352MLDSnoopingSSMType           DisplayString
}

gs2352MLDSnoopingSSMIndex OBJECT-TYPE
   SYNTAX      Integer32(1..65535)
   MAX-ACCESS  not-accessible
   STATUS      current
   DESCRIPTION
       "MLD Snooping SSM Index"
   ::= { gs2352MLDSnoopingSSMEntry 1 }

gs2352MLDSnoopingSSMVLANID OBJECT-TYPE
   SYNTAX      Integer32(1..4095)
   MAX-ACCESS  read-only
   STATUS      current
   DESCRIPTION
       "VLAN ID of the group. "
   ::= { gs2352MLDSnoopingSSMEntry 2 }

gs2352MLDSnoopingSSMGroup OBJECT-TYPE
   SYNTAX      DisplayString
   MAX-ACCESS  read-only
   STATUS      current
   DESCRIPTION
       "Group address of the group displayed."
   ::= { gs2352MLDSnoopingSSMEntry 3 }

gs2352MLDSnoopingSSMPort OBJECT-TYPE
   SYNTAX      Integer32(1..65535)
   MAX-ACCESS  read-only
   STATUS      current
   DESCRIPTION
       "Ports under this group."
   ::= { gs2352MLDSnoopingSSMEntry 4 }

gs2352MLDSnoopingSSMMode OBJECT-TYPE
   SYNTAX      DisplayString
   MAX-ACCESS  read-only
   STATUS      current
   DESCRIPTION
       "Indicates the filtering mode maintained per (VLAN ID, port number,
       Group Address) basis. It can be either Include or Exclude."
   ::= { gs2352MLDSnoopingSSMEntry 5 }

gs2352MLDSnoopingSSMSourceAddress OBJECT-TYPE
   SYNTAX      DisplayString
   MAX-ACCESS  read-only
   STATUS      current
   DESCRIPTION
       "IP Address of the source. Currently, system limits the total number of
       IP source addresses for filtering to be 128."
   ::= { gs2352MLDSnoopingSSMEntry 6 }

gs2352MLDSnoopingSSMType OBJECT-TYPE
   SYNTAX      DisplayString
   MAX-ACCESS  read-only
   STATUS      current
   DESCRIPTION
       "Indicates the Type. It can be either Allow or Deny."
   ::= { gs2352MLDSnoopingSSMEntry 7 }


gs2352MVR                                                                   OBJECT IDENTIFIER ::= { gs2352Configuration 18 }

gs2352MVRConfiguration                                                      OBJECT IDENTIFIER ::= { gs2352MVR 1 }

gs2352MVRMode  OBJECT-TYPE
   SYNTAX      INTEGER { disable(0), enable(1) }
   MAX-ACCESS  read-write
   STATUS      current
   DESCRIPTION
       "Enable/Disable the Global MVR. "
   ::= { gs2352MVRConfiguration 1 }

gs2352MVRVLANId  OBJECT-TYPE
   SYNTAX      Integer32(1..4094)
   MAX-ACCESS  read-write
   STATUS      current
   DESCRIPTION
       "Specify the Multicast VLAN ID. "
   ::= { gs2352MVRConfiguration 2 }

gs2352MVRPortConfigurationTable OBJECT-TYPE
   SYNTAX      SEQUENCE OF Gs2352MVRPortConfigurationEntry
   MAX-ACCESS  not-accessible
   STATUS      current
   DESCRIPTION
       " Configure MVR Port Configuration. "
   ::= { gs2352MVRConfiguration 3 }

gs2352MVRPortConfigurationEntry OBJECT-TYPE
   SYNTAX      Gs2352MVRPortConfigurationEntry
   MAX-ACCESS  not-accessible
   STATUS      current
   DESCRIPTION
       ""
   INDEX    { ifIndex  }
   ::= { gs2352MVRPortConfigurationTable 1 }

Gs2352MVRPortConfigurationEntry ::= SEQUENCE {
   gs2352MVRPortConfigurationMode	INTEGER,
   gs2352MVRPortConfigurationType  	INTEGER,
   gs2352MVRPortConfigurationImmediateLeave    INTEGER
}

gs2352MVRPortConfigurationMode OBJECT-TYPE
   SYNTAX      INTEGER { disable(0), enable(1) }
   MAX-ACCESS  read-write
   STATUS      current
   DESCRIPTION
       "Enable MVR on the port. "
   ::= { gs2352MVRPortConfigurationEntry 1 }

gs2352MVRPortConfigurationType OBJECT-TYPE
   SYNTAX      INTEGER { receiver(0), source(1) }
   MAX-ACCESS  read-write
   STATUS      current
   DESCRIPTION
       "Specify the MVR port type on the port. "
   ::= { gs2352MVRPortConfigurationEntry 2 }

gs2352MVRPortConfigurationImmediateLeave OBJECT-TYPE
   SYNTAX      INTEGER { disable(0), enable(1) }
   MAX-ACCESS  read-write
   STATUS      current
   DESCRIPTION
       "Enable the fast leave on the port. "
   ::= { gs2352MVRPortConfigurationEntry 3 }


gs2352MVRPortGroupFiltering                                                      OBJECT IDENTIFIER ::= { gs2352MVR 2 }

gs2352MVRPortGroupFilteringCreate OBJECT-TYPE
   SYNTAX       Integer32
   MAX-ACCESS   read-write
   STATUS       current
   DESCRIPTION
       "default: 0
       0 : None  (read only) 1 : Create MLD Snooping Port Group Filtering "
   ::= { gs2352MVRPortGroupFiltering 1 }

gs2352MVRPortGroupFilteringTable OBJECT-TYPE
   SYNTAX      SEQUENCE OF Gs2352MVRPortGroupFilteringEntry
   MAX-ACCESS  not-accessible
   STATUS      current
   DESCRIPTION
       " Configure MVR port group filtering. "
   ::= { gs2352MVRPortGroupFiltering 2 }

gs2352MVRPortGroupFilteringEntry OBJECT-TYPE
   SYNTAX      Gs2352MVRPortGroupFilteringEntry
   MAX-ACCESS  not-accessible
   STATUS      current
   DESCRIPTION
       ""
   INDEX    { gs2352MVRPortGroupFilteringIndex  }
   ::= { gs2352MVRPortGroupFilteringTable 1 }

Gs2352MVRPortGroupFilteringEntry ::= SEQUENCE {
   gs2352MVRPortGroupFilteringIndex         Integer32,
   gs2352MVRPortGroupFilteringPort          Integer32,
   gs2352MVRPortGroupFilteringStartGroups   DisplayString,
   gs2352MVRPortGroupFilteringEndGroups     DisplayString,
   gs2352MVRPortGroupFilteringRowStatus     INTEGER
}

gs2352MVRPortGroupFilteringIndex OBJECT-TYPE
   SYNTAX      Integer32(1..65535)
   MAX-ACCESS  not-accessible
   STATUS      current
   DESCRIPTION
       "MVR Port Group Filtering Configuration Index. "
   ::= { gs2352MVRPortGroupFilteringEntry 1 }

gs2352MVRPortGroupFilteringPort OBJECT-TYPE
   SYNTAX      Integer32(1..65535)
   MAX-ACCESS  read-write
   STATUS      current
   DESCRIPTION
       "The logical port for the settings. "
   ::= { gs2352MVRPortGroupFilteringEntry 2 }

gs2352MVRPortGroupFilteringStartGroups OBJECT-TYPE
   SYNTAX      DisplayString
   MAX-ACCESS  read-write
   STATUS      current
   DESCRIPTION
       "The IP Multicast Group that will be allowed. "
   ::= { gs2352MVRPortGroupFilteringEntry 3 }

gs2352MVRPortGroupFilteringEndGroups OBJECT-TYPE
   SYNTAX      DisplayString
   MAX-ACCESS  read-write
   STATUS      current
   DESCRIPTION
       "The IP Multicast Group that will be allowed. "
   ::= { gs2352MVRPortGroupFilteringEntry 4 }

gs2352MVRPortGroupFilteringRowStatus OBJECT-TYPE
   SYNTAX      INTEGER { active(1), notInservice(2), destroy(4)}
   MAX-ACCESS  read-write
   STATUS      current
   DESCRIPTION
       "1: active
        2: notInservice
        4: destroy"
   ::= { gs2352MVRPortGroupFilteringEntry 5 }

gs2352MVRGroupsTable OBJECT-TYPE
   SYNTAX      SEQUENCE OF Gs2352MVRGroupsEntry
   MAX-ACCESS  not-accessible
   STATUS      current
   DESCRIPTION
       "MVR Groups Information . "
   ::= { gs2352MVR 3 }

gs2352MVRGroupsEntry OBJECT-TYPE
   SYNTAX      Gs2352MVRGroupsEntry
   MAX-ACCESS  not-accessible
   STATUS      current
   DESCRIPTION
       ""
   INDEX    { gs2352MVRGroupsIndex  }
   ::= { gs2352MVRGroupsTable 1 }

Gs2352MVRGroupsEntry ::= SEQUENCE {
   gs2352MVRGroupsIndex          Integer32,
   gs2352MVRGroupsVLANID         Integer32,
   gs2352MVRGroups               InetAddress,
   gs2352MVRGroupsMemberships    DisplayString
}

gs2352MVRGroupsIndex OBJECT-TYPE
   SYNTAX      Integer32(1..65535)
   MAX-ACCESS  not-accessible
   STATUS      current
   DESCRIPTION
       "MVR Groups Index"
   ::= { gs2352MVRGroupsEntry 1 }

gs2352MVRGroupsVLANID OBJECT-TYPE
   SYNTAX      Integer32(1..4095)
   MAX-ACCESS  read-only
   STATUS      current
   DESCRIPTION
       "VLAN ID of the group. "
   ::= { gs2352MVRGroupsEntry 2 }

gs2352MVRGroups OBJECT-TYPE
   SYNTAX      DisplayString
   MAX-ACCESS  read-only
   STATUS      current
   DESCRIPTION
       "Group address of the group displayed."
   ::= { gs2352MVRGroupsEntry 3 }

gs2352MVRGroupsMemberships OBJECT-TYPE
   SYNTAX      DisplayString
   MAX-ACCESS  read-only
   STATUS      current
   DESCRIPTION
       "Ports under this group."
   ::= { gs2352MVRGroupsEntry 4 }


gs2352MVRStatus                                                      OBJECT IDENTIFIER ::= { gs2352MVR 4 }

gs2352MVRstatisticClear OBJECT-TYPE
   SYNTAX      INTEGER { none(0), clear(1)}
   MAX-ACCESS  read-write
   STATUS      current
   DESCRIPTION
       "Clears all Statistics counters."
   ::= { gs2352MVRStatus 1 }

gs2352MVRstatisticVLANID OBJECT-TYPE
   SYNTAX      Integer32(1..4095)
   MAX-ACCESS  read-only
   STATUS      current
   DESCRIPTION
       "The VLAN ID of the entry. "
   ::= { gs2352MVRStatus 2 }

gs2352MVRstatisticV1ReportsReceived OBJECT-TYPE
   SYNTAX      Counter32
   MAX-ACCESS  read-only
   STATUS      current
   DESCRIPTION
       "The number of Received V1 Reports. "
   ::= { gs2352MVRStatus 3 }

gs2352MVRstatisticV2ReportsReceived OBJECT-TYPE
   SYNTAX      Counter32
   MAX-ACCESS  read-only
   STATUS      current
   DESCRIPTION
       "The number of Received V2 Reports. "
   ::= { gs2352MVRStatus 4 }

gs2352MVRstatisticV3ReportsReceived OBJECT-TYPE
   SYNTAX      Counter32
   MAX-ACCESS  read-only
   STATUS      current
   DESCRIPTION
       "The number of Received V3 Reports. "
   ::= { gs2352MVRStatus 5 }

gs2352MVRstatisticV2LeavesReceived OBJECT-TYPE
   SYNTAX      Counter32
   MAX-ACCESS  read-only
   STATUS      current
   DESCRIPTION
       "The number of Received V2 Leaves. "
   ::= { gs2352MVRStatus 6 }

gs2352LACP                                                     OBJECT IDENTIFIER ::= { gs2352Configuration 19 }

gs2352LACPConf                                                 OBJECT IDENTIFIER ::= { gs2352LACP 1 }

gs2352LACPPortConfigurationTable OBJECT-TYPE
   SYNTAX      SEQUENCE OF Gs2352LACPPortConfigurationEntry
   MAX-ACCESS  not-accessible
   STATUS      current
   DESCRIPTION
       " "
   ::= { gs2352LACPConf 1 }

gs2352LACPPortConfigurationEntry OBJECT-TYPE
   SYNTAX      Gs2352LACPPortConfigurationEntry
   MAX-ACCESS  not-accessible
   STATUS      current
   DESCRIPTION
       ""
   INDEX    { gs2352LACPPortConfigurationPort  }
   ::= { gs2352LACPPortConfigurationTable 1 }

Gs2352LACPPortConfigurationEntry ::= SEQUENCE {
    gs2352LACPPortConfigurationPort         Integer32,
    gs2352LACPPortConfigurationMode         INTEGER,
    gs2352LACPPortConfigurationKey          Integer32,
    gs2352LACPPortConfigurationRole         INTEGER
}

gs2352LACPPortConfigurationPort OBJECT-TYPE
   SYNTAX      Integer32(1..4095)
   MAX-ACCESS  not-accessible
   STATUS      current
   DESCRIPTION
       " "
   ::= { gs2352LACPPortConfigurationEntry 1 }

gs2352LACPPortConfigurationMode OBJECT-TYPE
   SYNTAX      INTEGER { disable(0), enable(1) }
   MAX-ACCESS  read-write
   STATUS      current
   DESCRIPTION
       "Enable/Disable LACP Mode."
   ::= { gs2352LACPPortConfigurationEntry 2 }

gs2352LACPPortConfigurationKey OBJECT-TYPE
   SYNTAX      Integer32(0..65535)
   MAX-ACCESS  read-write
   STATUS      current
   DESCRIPTION
       "LACP key : 1-65535. 0 : Auto"
   ::= { gs2352LACPPortConfigurationEntry 3 }

gs2352LACPPortConfigurationRole OBJECT-TYPE
   SYNTAX      INTEGER { passive(0), active(1) }
   MAX-ACCESS  read-write
   STATUS      current
   DESCRIPTION
       "0 : passive, Listen for LACP packets.
        1 : active, Initiate LACP negotiation, and transmit LACP packets each second"
   ::= { gs2352LACPPortConfigurationEntry 4 }

gs2352LACPSystemStatusTable OBJECT-TYPE
   SYNTAX      SEQUENCE OF Gs2352LACPSystemStatusEntry
   MAX-ACCESS  not-accessible
   STATUS      current
   DESCRIPTION
       " "
   ::= { gs2352LACP 2 }

gs2352LACPSystemStatusEntry OBJECT-TYPE
   SYNTAX      Gs2352LACPSystemStatusEntry
   MAX-ACCESS  not-accessible
   STATUS      current
   DESCRIPTION
       ""
   INDEX    { gs2352LACPSystemStatusIndex  }
   ::= { gs2352LACPSystemStatusTable 1 }

Gs2352LACPSystemStatusEntry ::= SEQUENCE {
   gs2352LACPSystemStatusIndex             Integer32,
   gs2352LACPSystemStatusAggrID            DisplayString,
   gs2352LACPSystemStatusPartnerSystemID   MacAddress,
   gs2352LACPSystemStatusPartnerKey        DisplayString,
   gs2352LACPSystemStatusLastchanged       DisplayString,
   gs2352LACPSystemStatusLocalPorts        DisplayString
}

gs2352LACPSystemStatusIndex OBJECT-TYPE
   SYNTAX      Integer32(1..12)
   MAX-ACCESS  not-accessible
   STATUS      current
   DESCRIPTION
       " "
   ::= { gs2352LACPSystemStatusEntry 1 }

gs2352LACPSystemStatusAggrID OBJECT-TYPE
   SYNTAX      DisplayString
   MAX-ACCESS  read-only
   STATUS      current
   DESCRIPTION
       "The Aggregation ID associated with this aggregation instance."
   ::= { gs2352LACPSystemStatusEntry 2 }

gs2352LACPSystemStatusPartnerSystemID OBJECT-TYPE
   SYNTAX      MacAddress
   MAX-ACCESS  read-only
   STATUS      current
   DESCRIPTION
       "The system ID (MAC address) of the aggregation partner."
   ::= { gs2352LACPSystemStatusEntry 3 }

gs2352LACPSystemStatusPartnerKey OBJECT-TYPE
   SYNTAX      DisplayString
   MAX-ACCESS  read-only
   STATUS      current
   DESCRIPTION
       " The Key that the partner has assigned to this aggregation ID. "
   ::= { gs2352LACPSystemStatusEntry 4 }

gs2352LACPSystemStatusLastchanged OBJECT-TYPE
   SYNTAX      DisplayString
   MAX-ACCESS  read-only
   STATUS      current
   DESCRIPTION
       " The time since this aggregation changed. "
   ::= { gs2352LACPSystemStatusEntry 5 }

gs2352LACPSystemStatusLocalPorts OBJECT-TYPE
   SYNTAX      DisplayString
   MAX-ACCESS  read-only
   STATUS      current
   DESCRIPTION
       " Shows which ports are a part of this aggregation for this switch. "
   ::= { gs2352LACPSystemStatusEntry 6 }

gs2352LACPStatusTable OBJECT-TYPE
   SYNTAX      SEQUENCE OF Gs2352LACPStatusEntry
   MAX-ACCESS  not-accessible
   STATUS      current
   DESCRIPTION
       " "
   ::= { gs2352LACP 3 }

gs2352LACPStatusEntry OBJECT-TYPE
   SYNTAX      Gs2352LACPStatusEntry
   MAX-ACCESS  not-accessible
   STATUS      current
   DESCRIPTION
       ""
   INDEX    { gs2352LACPStatusPort  }
   ::= { gs2352LACPStatusTable 1 }

Gs2352LACPStatusEntry ::= SEQUENCE {
   gs2352LACPStatusPort                Integer32,
   gs2352LACPStatusLACP                DisplayString,
   gs2352LACPStatusKey                 DisplayString,
   gs2352LACPStatusAggrID              DisplayString,
   gs2352LACPStatusPartnerSystemID     DisplayString,
   gs2352LACPStatusPartnerPort         DisplayString
}

gs2352LACPStatusPort OBJECT-TYPE
   SYNTAX      Integer32(1..4095)
   MAX-ACCESS  not-accessible
   STATUS      current
   DESCRIPTION
       " "
   ::= { gs2352LACPStatusEntry 1 }

gs2352LACPStatusLACP OBJECT-TYPE
   SYNTAX      DisplayString
   MAX-ACCESS  read-only
   STATUS      current
   DESCRIPTION
       "Enabled means that LACP is enabled and the port link is up.
        Disabled means that LACP is not enabled or that the port link is down.
        Backup means that the port could not join the aggregation group but will join if other port leaves.
        Meanwhile it's LACP status is disabled."
   ::= { gs2352LACPStatusEntry 2 }

gs2352LACPStatusKey OBJECT-TYPE
   SYNTAX      DisplayString
   MAX-ACCESS  read-only
   STATUS      current
   DESCRIPTION
       "The key assigned to this port. Only ports with the same key can aggregate together."
   ::= { gs2352LACPStatusEntry 3 }

gs2352LACPStatusAggrID	 OBJECT-TYPE
   SYNTAX      DisplayString
   MAX-ACCESS  read-only
   STATUS      current
   DESCRIPTION
       " The Aggregation ID assigned to this aggregation group. "
   ::= { gs2352LACPStatusEntry 4 }

gs2352LACPStatusPartnerSystemID OBJECT-TYPE
   SYNTAX      DisplayString
   MAX-ACCESS  read-only
   STATUS      current
   DESCRIPTION
       " The partner's System ID. "
   ::= { gs2352LACPStatusEntry 5 }

gs2352LACPStatusPartnerPort OBJECT-TYPE
   SYNTAX      DisplayString
   MAX-ACCESS  read-only
   STATUS      current
   DESCRIPTION
       " The partner's port number connected to this port. "
   ::= { gs2352LACPStatusEntry 6 }


gs2352LACPStatisticsTable OBJECT-TYPE
   SYNTAX      SEQUENCE OF Gs2352LACPStatisticsEntry
   MAX-ACCESS  not-accessible
   STATUS      current
   DESCRIPTION
       " "
   ::= { gs2352LACP 4 }

gs2352LACPStatisticsEntry OBJECT-TYPE
   SYNTAX      Gs2352LACPStatisticsEntry
   MAX-ACCESS  not-accessible
   STATUS      current
   DESCRIPTION
       ""
   INDEX    { gs2352LACPStatisticsPort  }
   ::= { gs2352LACPStatisticsTable 1 }

Gs2352LACPStatisticsEntry ::= SEQUENCE {
   gs2352LACPStatisticsPort        Integer32,
   gs2352LACPReceived              Counter32,
   gs2352LACPTransmitted           Counter32,
   gs2352LACPDiscardedUnknown      Counter32,
   gs2352LACPDiscardedIllegal      Counter32
}

gs2352LACPStatisticsPort OBJECT-TYPE
   SYNTAX      Integer32(1..4095)
   MAX-ACCESS  not-accessible
   STATUS      current
   DESCRIPTION
       " "
   ::= { gs2352LACPStatisticsEntry 1 }

gs2352LACPReceived OBJECT-TYPE
   SYNTAX      Counter32
   MAX-ACCESS  read-only
   STATUS      current
   DESCRIPTION
       "Shows how many LACP frames have been received at each port. "
   ::= { gs2352LACPStatisticsEntry 2 }

gs2352LACPTransmitted OBJECT-TYPE
   SYNTAX      Counter32
   MAX-ACCESS  read-only
   STATUS      current
   DESCRIPTION
       " Shows how many LACP frames have been sent from each port. "
   ::= { gs2352LACPStatisticsEntry 3 }

gs2352LACPDiscardedUnknown OBJECT-TYPE
   SYNTAX      Counter32
   MAX-ACCESS  read-only
   STATUS      current
   DESCRIPTION
       " Shows how many unknown LACP frames have been discarded at each port. "
   ::= { gs2352LACPStatisticsEntry 4 }

gs2352LACPDiscardedIllegal OBJECT-TYPE
   SYNTAX      Counter32
   MAX-ACCESS  read-only
   STATUS      current
   DESCRIPTION
       " Shows how many illegal LACP frames have been discarded at each port. "
   ::= { gs2352LACPStatisticsEntry 5 }

gs2352LACPStatisticsClear OBJECT-TYPE
   SYNTAX      INTEGER { none(0), clear(1) }
   MAX-ACCESS  read-write
   STATUS      current
   DESCRIPTION
       "default: 0
       0: none
       1: clear"
   ::= { gs2352LACP 5 }

gs2352STP                                                     OBJECT IDENTIFIER ::= { gs2352Configuration 20 }

gs2352STPBridgeBasicConf                                                 OBJECT IDENTIFIER ::= { gs2352STP 1 }

gs2352STPBridgeProtocolVersion OBJECT-TYPE
   SYNTAX      INTEGER { stp(0), rstp(2), mstp(3) }
   MAX-ACCESS  read-write
   STATUS      current
   DESCRIPTION
       "default: 3,
       0: stp
       2: rstp
       3: mstp"
   ::= { gs2352STPBridgeBasicConf 1 }

gs2352STPBridgePriority OBJECT-TYPE
   SYNTAX      Integer32(0..61440)
   MAX-ACCESS  read-write
   STATUS      current
   DESCRIPTION
       " default: 32768,
       STP bridge priority (0/4096/8192/12288/16384/20480/24576/28672/32768/36864/40960/45056/49152/53248/57344/61440)"
   ::= { gs2352STPBridgeBasicConf 2 }

gs2352STPBridgeForwardDelay OBJECT-TYPE
   SYNTAX      Integer32(4..30)
   MAX-ACCESS  read-write
   STATUS      current
   DESCRIPTION
       " Forward Delay default: 15, range: 4 - 30.
         MaxAge must be <= (FwdDelay-1)*2."
   ::= { gs2352STPBridgeBasicConf 3 }

gs2352STPBridgeMaxAge OBJECT-TYPE
   SYNTAX      Integer32(6..40)
   MAX-ACCESS  read-write
   STATUS      current
   DESCRIPTION
       " Max Age default: 20, range: 6 - 40.
         MaxAge must be <= (FwdDelay-1)*2"
   ::= { gs2352STPBridgeBasicConf 4 }

gs2352STPBridgeMaximumHopCount OBJECT-TYPE
   SYNTAX      Integer32(6..40)
   MAX-ACCESS  read-write
   STATUS      current
   DESCRIPTION
       " Maximum Hop Count default: 20, range: 6 - 40."
   ::= { gs2352STPBridgeBasicConf 5 }

gs2352STPBridgeTransmitHoldCount OBJECT-TYPE
   SYNTAX      Integer32(1..10)
   MAX-ACCESS  read-write
   STATUS      current
   DESCRIPTION
       " Transmit Hold Count default: 6, range: 1 - 10."
   ::= { gs2352STPBridgeBasicConf 6 }

gs2352STPBridgeAdvancedConf                                                 OBJECT IDENTIFIER ::= { gs2352STP 2 }

gs2352STPBridgeEdgePortBPDUFiltering OBJECT-TYPE
   SYNTAX      INTEGER { disable(0), enable(1) }
   MAX-ACCESS  read-write
   STATUS      current
   DESCRIPTION
       " default: 0,
        0: disable
        1: enable"
   ::= { gs2352STPBridgeAdvancedConf 1 }

gs2352STPBridgeEdgePortBPDUGuard OBJECT-TYPE
   SYNTAX      INTEGER { disable(0), enable(1) }
   MAX-ACCESS  read-write
   STATUS      current
   DESCRIPTION
       " default: 0,
        0: disable
        1: enable"
   ::= { gs2352STPBridgeAdvancedConf 2 }

gs2352STPBridgePortErrorRecoveryTimeout OBJECT-TYPE
   SYNTAX      Integer32(0..86400)
   MAX-ACCESS  read-write
   STATUS      current
   DESCRIPTION
       " Port Error Recovery Timeout disable: 0, range: 30 - 86400."
   ::= { gs2352STPBridgeAdvancedConf 3 }

gs2352STPMSTIConf                                                 OBJECT IDENTIFIER ::= { gs2352STP 3 }

gs2352STPMSTIConfigurationName OBJECT-TYPE
   SYNTAX      DisplayString (SIZE (1..32))
   MAX-ACCESS  read-write
   STATUS      current
   DESCRIPTION
       "A text string up to 32 characters long."
   ::= { gs2352STPMSTIConf 1 }

gs2352STPMSTIConfigurationRevision   OBJECT-TYPE
   SYNTAX      Integer32(0..65535)
   MAX-ACCESS  read-write
   STATUS      current
   DESCRIPTION
       " Configuration Revision default: 0, range: 0 - 65535."
   ::= { gs2352STPMSTIConf 2 }

gs2352STPMSTIMappingConf                                                 OBJECT IDENTIFIER ::= { gs2352STP 4 }

gs2352STPMSTI1VLANsMapped OBJECT-TYPE
   SYNTAX      DisplayString (SIZE (1..4096))
   MAX-ACCESS  read-write
   STATUS      current
   DESCRIPTION
       "The list of VLANs mapped to the MSTI1.
       The VLANs must be separated with comma or space.
       An unused MSTI should just be left empty. "
   ::= { gs2352STPMSTIMappingConf 1 }

gs2352STPMSTI2VLANsMapped OBJECT-TYPE
   SYNTAX      DisplayString (SIZE (1..4096))
   MAX-ACCESS  read-write
   STATUS      current
   DESCRIPTION
       "The list of VLANs mapped to the MSTI2.
       The VLANs must be separated with comma or space.
       An unused MSTI should just be left empty. "
   ::= { gs2352STPMSTIMappingConf 2 }

gs2352STPMSTI3VLANsMapped OBJECT-TYPE
   SYNTAX      DisplayString (SIZE (1..4096))
   MAX-ACCESS  read-write
   STATUS      current
   DESCRIPTION
       "The list of VLANs mapped to the MSTI3.
       The VLANs must be separated with comma or space.
       An unused MSTI should just be left empty. "
   ::= { gs2352STPMSTIMappingConf 3 }

gs2352STPMSTI4VLANsMapped OBJECT-TYPE
   SYNTAX      DisplayString (SIZE (1..4096))
   MAX-ACCESS  read-write
   STATUS      current
   DESCRIPTION
       "The list of VLANs mapped to the MSTI4.
       The VLANs must be separated with comma or space.
       An unused MSTI should just be left empty. "
   ::= { gs2352STPMSTIMappingConf 4 }

gs2352STPMSTI5VLANsMapped OBJECT-TYPE
   SYNTAX      DisplayString (SIZE (1..4096))
   MAX-ACCESS  read-write
   STATUS      current
   DESCRIPTION
       "The list of VLANs mapped to the MSTI5.
       The VLANs must be separated with comma or space.
       An unused MSTI should just be left empty. "
   ::= { gs2352STPMSTIMappingConf 5 }

gs2352STPMSTI6VLANsMapped OBJECT-TYPE
   SYNTAX      DisplayString (SIZE (1..4096))
   MAX-ACCESS  read-write
   STATUS      current
   DESCRIPTION
       "The list of VLANs mapped to the MSTI6.
       The VLANs must be separated with comma or space.
       An unused MSTI should just be left empty. "
   ::= { gs2352STPMSTIMappingConf 6 }

gs2352STPMSTI7VLANsMapped OBJECT-TYPE
   SYNTAX      DisplayString (SIZE (1..4096))
   MAX-ACCESS  read-write
   STATUS      current
   DESCRIPTION
       "The list of VLANs mapped to the MSTI7.
       The VLANs must be separated with comma or space.
       An unused MSTI should just be left empty. "
   ::= { gs2352STPMSTIMappingConf 7 }

gs2352STPMSTIPriority                                                 OBJECT IDENTIFIER ::= { gs2352STP 5 }

gs2352STPCISTPriority OBJECT-TYPE
   SYNTAX      Integer32(0..61440)
   MAX-ACCESS  read-write
   STATUS      current
   DESCRIPTION
       " default: 32768,
       STP CIST priority (0/4096/8192/12288/16384/20480/24576/28672/32768/36864/40960/45056/49152/53248/57344/61440)"
   ::= { gs2352STPMSTIPriority 1 }

gs2352STPMSTI1Priority OBJECT-TYPE
   SYNTAX      Integer32(0..61440)
   MAX-ACCESS  read-write
   STATUS      current
   DESCRIPTION
       " default: 32768,
       STP CIST priority (0/4096/8192/12288/16384/20480/24576/28672/32768/36864/40960/45056/49152/53248/57344/61440)"
   ::= { gs2352STPMSTIPriority 2 }

gs2352STPMSTI2Priority OBJECT-TYPE
   SYNTAX      Integer32(0..61440)
   MAX-ACCESS  read-write
   STATUS      current
   DESCRIPTION
       " default: 32768,
       STP CIST priority (0/4096/8192/12288/16384/20480/24576/28672/32768/36864/40960/45056/49152/53248/57344/61440)"
   ::= { gs2352STPMSTIPriority 3 }

gs2352STPMSTI3Priority OBJECT-TYPE
   SYNTAX      Integer32(0..61440)
   MAX-ACCESS  read-write
   STATUS      current
   DESCRIPTION
       " default: 32768,
       STP CIST priority (0/4096/8192/12288/16384/20480/24576/28672/32768/36864/40960/45056/49152/53248/57344/61440)"
   ::= { gs2352STPMSTIPriority 4 }

gs2352STPMSTI4Priority OBJECT-TYPE
   SYNTAX      Integer32(0..61440)
   MAX-ACCESS  read-write
   STATUS      current
   DESCRIPTION
       " default: 32768,
       STP CIST priority (0/4096/8192/12288/16384/20480/24576/28672/32768/36864/40960/45056/49152/53248/57344/61440)"
   ::= { gs2352STPMSTIPriority 5 }

gs2352STPMSTI5Priority OBJECT-TYPE
   SYNTAX      Integer32(0..61440)
   MAX-ACCESS  read-write
   STATUS      current
   DESCRIPTION
       " default: 32768,
       STP CIST priority (0/4096/8192/12288/16384/20480/24576/28672/32768/36864/40960/45056/49152/53248/57344/61440)"
   ::= { gs2352STPMSTIPriority 6 }

gs2352STPMSTI6Priority OBJECT-TYPE
   SYNTAX      Integer32(0..61440)
   MAX-ACCESS  read-write
   STATUS      current
   DESCRIPTION
       " default: 32768,
       STP CIST priority (0/4096/8192/12288/16384/20480/24576/28672/32768/36864/40960/45056/49152/53248/57344/61440)"
   ::= { gs2352STPMSTIPriority 7 }

gs2352STPMSTI7Priority OBJECT-TYPE
   SYNTAX      Integer32(0..61440)
   MAX-ACCESS  read-write
   STATUS      current
   DESCRIPTION
       " default: 32768,
       STP CIST priority (0/4096/8192/12288/16384/20480/24576/28672/32768/36864/40960/45056/49152/53248/57344/61440)"
   ::= { gs2352STPMSTIPriority 8 }

gs2352STPCISTPort                                                          OBJECT IDENTIFIER ::= { gs2352STP 6 }

gs2352STPCISTAggregatedPort                                                OBJECT IDENTIFIER ::= { gs2352STPCISTPort 1 }

gs2352STPCISTAggregatedPortSTPEnabled OBJECT-TYPE
   SYNTAX      INTEGER { disable(0), enable(1) }
   MAX-ACCESS  read-write
   STATUS      current
   DESCRIPTION
       " default: 0,
        0: disable
        1: enable"
   ::= { gs2352STPCISTAggregatedPort 1 }

gs2352STPCISTAggregatedPortPathCost OBJECT-TYPE
   SYNTAX      Integer32(0..200000000)
   MAX-ACCESS  read-write
   STATUS      current
   DESCRIPTION
       " Auto: 0,
        Specific Path Cost range: 1 - 200000000."
   ::= { gs2352STPCISTAggregatedPort 2 }

gs2352STPCISTAggregatedPortPriority OBJECT-TYPE
   SYNTAX      Integer32(0..240)
   MAX-ACCESS  read-write
   STATUS      current
   DESCRIPTION
       " default: 128,
       CIST Aggregated Port Priority (0/16/32/48/64/80/96/112/128/144/160/176/192/208/224/240)"
   ::= { gs2352STPCISTAggregatedPort 3 }

gs2352STPCISTAggregatedPortAdminEdge OBJECT-TYPE
   SYNTAX      INTEGER { non-edge(0), edge(1) }
   MAX-ACCESS  read-write
   STATUS      current
   DESCRIPTION
       " default: 0,
        0: non-edge
        1: edge"
   ::= { gs2352STPCISTAggregatedPort 4 }

gs2352STPCISTAggregatedPortAutoEdge OBJECT-TYPE
   SYNTAX      INTEGER { disable(0), enable(1) }
   MAX-ACCESS  read-write
   STATUS      current
   DESCRIPTION
       " default: 1,
        0: disable
        1: enable"
   ::= { gs2352STPCISTAggregatedPort 5 }

gs2352STPCISTAggregatedPortRestrictedRole OBJECT-TYPE
   SYNTAX      INTEGER { disable(0), enable(1) }
   MAX-ACCESS  read-write
   STATUS      current
   DESCRIPTION
       " default: 0,
        0: disable
        1: enable"
   ::= { gs2352STPCISTAggregatedPort 6 }

gs2352STPCISTAggregatedPortRestrictedTCN OBJECT-TYPE
   SYNTAX      INTEGER { disable(0), enable(1) }
   MAX-ACCESS  read-write
   STATUS      current
   DESCRIPTION
       " default: 0,
        0: disable
        1: enable"
   ::= { gs2352STPCISTAggregatedPort 7 }

gs2352STPCISTAggregatedPortBPDUGuard OBJECT-TYPE
   SYNTAX      INTEGER { disable(0), enable(1) }
   MAX-ACCESS  read-write
   STATUS      current
   DESCRIPTION
       " default: 0,
        0: disable
        1: enable"
   ::= { gs2352STPCISTAggregatedPort 8 }

gs2352STPCISTAggregatedPortPointtoPoint OBJECT-TYPE
   SYNTAX      INTEGER { forcetrue(0), forcefalse(1), auto(2) }
   MAX-ACCESS  read-write
   STATUS      current
   DESCRIPTION
       " default: 0,
        0: Forced True
        1: Forced False
        2: Auto"
   ::= { gs2352STPCISTAggregatedPort 9 }

gs2352STPCISTNormalPortTable OBJECT-TYPE
   SYNTAX      SEQUENCE OF Gs2352STPCISTNormalPortEntry
   MAX-ACCESS  not-accessible
   STATUS      current
   DESCRIPTION
       " Show CIST Normal Port Configurations. "
   ::= { gs2352STPCISTPort 2 }

gs2352STPCISTNormalPortEntry OBJECT-TYPE
   SYNTAX      Gs2352STPCISTNormalPortEntry
   MAX-ACCESS  not-accessible
   STATUS      current
   DESCRIPTION
       ""
   INDEX    { gs2352STPCISTNormalPortConfPort  }
   ::= { gs2352STPCISTNormalPortTable 1 }

Gs2352STPCISTNormalPortEntry ::= SEQUENCE {
   gs2352STPCISTNormalPortConfPort         Integer32,
   gs2352STPCISTNormalPortSTPEnabled       INTEGER,
   gs2352STPCISTNormalPortPathCost         Integer32,
   gs2352STPCISTNormalPortPriority         Integer32,
   gs2352STPCISTNormalPortAdminEdge        INTEGER,
   gs2352STPCISTNormalPortAutoEdge         INTEGER,
   gs2352STPCISTNormalPortRestrictedRole   INTEGER,
   gs2352STPCISTNormalPortRestrictedTCN    INTEGER,
   gs2352STPCISTNormalPortBPDUGuard        INTEGER,
   gs2352STPCISTNormalPortPointtoPoint     INTEGER
}

gs2352STPCISTNormalPortConfPort OBJECT-TYPE
   SYNTAX      Integer32(1..4095)
   MAX-ACCESS  not-accessible
   STATUS      current
   DESCRIPTION
       " port, range : 1 - port number. "
   ::= { gs2352STPCISTNormalPortEntry 1 }

gs2352STPCISTNormalPortSTPEnabled OBJECT-TYPE
   SYNTAX      INTEGER { disable(0), enable(1) }
   MAX-ACCESS  read-write
   STATUS      current
   DESCRIPTION
       " default: 0,
        0: disable
        1: enable"
   ::= { gs2352STPCISTNormalPortEntry 2 }

gs2352STPCISTNormalPortPathCost OBJECT-TYPE
   SYNTAX      Integer32(0..200000000)
   MAX-ACCESS  read-write
   STATUS      current
   DESCRIPTION
       " Auto: 0,
        Specific Path Cost range: 1 - 200000000."
   ::= { gs2352STPCISTNormalPortEntry 3 }

gs2352STPCISTNormalPortPriority OBJECT-TYPE
   SYNTAX      Integer32(0..240)
   MAX-ACCESS  read-write
   STATUS      current
   DESCRIPTION
       " default: 128,
       CIST Aggregated Port Priority (0/16/32/48/64/80/96/112/128/144/160/176/192/208/224/240)"
   ::= { gs2352STPCISTNormalPortEntry 4 }

gs2352STPCISTNormalPortAdminEdge OBJECT-TYPE
   SYNTAX      INTEGER { non-edge(0), edge(1) }
   MAX-ACCESS  read-write
   STATUS      current
   DESCRIPTION
       " default: 0,
        0: non-edge
        1: edge"
   ::= { gs2352STPCISTNormalPortEntry 5 }

gs2352STPCISTNormalPortAutoEdge OBJECT-TYPE
   SYNTAX      INTEGER { disable(0), enable(1) }
   MAX-ACCESS  read-write
   STATUS      current
   DESCRIPTION
       " default: 1,
        0: disable
        1: enable"
   ::= { gs2352STPCISTNormalPortEntry 6 }

gs2352STPCISTNormalPortRestrictedRole OBJECT-TYPE
   SYNTAX      INTEGER { disable(0), enable(1) }
   MAX-ACCESS  read-write
   STATUS      current
   DESCRIPTION
       " default: 0,
        0: disable
        1: enable"
   ::= { gs2352STPCISTNormalPortEntry 7 }

gs2352STPCISTNormalPortRestrictedTCN OBJECT-TYPE
   SYNTAX      INTEGER { disable(0), enable(1) }
   MAX-ACCESS  read-write
   STATUS      current
   DESCRIPTION
       " default: 0,
        0: disable
        1: enable"
   ::= { gs2352STPCISTNormalPortEntry 8 }

gs2352STPCISTNormalPortBPDUGuard OBJECT-TYPE
   SYNTAX      INTEGER { disable(0), enable(1) }
   MAX-ACCESS  read-write
   STATUS      current
   DESCRIPTION
       " default: 0,
        0: disable
        1: enable"
   ::= { gs2352STPCISTNormalPortEntry 9 }

gs2352STPCISTNormalPortPointtoPoint OBJECT-TYPE
   SYNTAX      INTEGER { forcetrue(0), forcefalse(1), auto(2) }
   MAX-ACCESS  read-write
   STATUS      current
   DESCRIPTION
       " default: 2,
        0: Forced True
        1: Forced False
        2: Auto"
   ::= { gs2352STPCISTNormalPortEntry 10 }


gs2352STPMSTIPort                                                          OBJECT IDENTIFIER ::= { gs2352STP 7 }

gs2352STPMSTI1Port                                                         OBJECT IDENTIFIER ::= { gs2352STPMSTIPort 1 }

gs2352STPMSTI1AggregatedPort                                                OBJECT IDENTIFIER ::= { gs2352STPMSTI1Port 1 }

gs2352STPMSTI1AggregatedPortPathCost OBJECT-TYPE
   SYNTAX      Integer32(0..200000000)
   MAX-ACCESS  read-write
   STATUS      current
   DESCRIPTION
       " Auto: 0,
        Specific Path Cost range: 1 - 200000000."
   ::= { gs2352STPMSTI1AggregatedPort 1 }

gs2352STPMSTI1AggregatedPortPriority OBJECT-TYPE
   SYNTAX      Integer32(0..240)
   MAX-ACCESS  read-write
   STATUS      current
   DESCRIPTION
       " default: 128,
       Aggregated Port Priority (0/16/32/48/64/80/96/112/128/144/160/176/192/208/224/240)"
   ::= { gs2352STPMSTI1AggregatedPort 2 }

gs2352STPMSTI1NormalPortTable OBJECT-TYPE
   SYNTAX      SEQUENCE OF Gs2352STPMSTI1NormalPortEntry
   MAX-ACCESS  not-accessible
   STATUS      current
   DESCRIPTION
       " Show MSTI1 Normal Port Configurations. "
   ::= { gs2352STPMSTI1Port 2 }

gs2352STPMSTI1NormalPortEntry OBJECT-TYPE
   SYNTAX      Gs2352STPMSTI1NormalPortEntry
   MAX-ACCESS  not-accessible
   STATUS      current
   DESCRIPTION
       ""
   INDEX    { gs2352STPMSTI1NormalPortConfPort  }
   ::= { gs2352STPMSTI1NormalPortTable 1 }

Gs2352STPMSTI1NormalPortEntry ::= SEQUENCE {
   gs2352STPMSTI1NormalPortConfPort         Integer32,
   gs2352STPMSTI1NormalPortPathCost         Integer32,
   gs2352STPMSTI1NormalPortPriority         Integer32
}

gs2352STPMSTI1NormalPortConfPort OBJECT-TYPE
   SYNTAX      Integer32(1..4095)
   MAX-ACCESS  not-accessible
   STATUS      current
   DESCRIPTION
       " port, range : 1 - port number. "
   ::= { gs2352STPMSTI1NormalPortEntry 1 }

gs2352STPMSTI1NormalPortPathCost OBJECT-TYPE
   SYNTAX      Integer32(0..200000000)
   MAX-ACCESS  read-write
   STATUS      current
   DESCRIPTION
       " Auto: 0,
        Specific Path Cost range: 1 - 200000000."
   ::= { gs2352STPMSTI1NormalPortEntry 2 }

gs2352STPMSTI1NormalPortPriority OBJECT-TYPE
   SYNTAX      Integer32(0..240)
   MAX-ACCESS  read-write
   STATUS      current
   DESCRIPTION
       " default: 128,
       Aggregated Port Priority (0/16/32/48/64/80/96/112/128/144/160/176/192/208/224/240)"
   ::= { gs2352STPMSTI1NormalPortEntry 3 }

gs2352STPMSTI2Port                                                          OBJECT IDENTIFIER ::= { gs2352STPMSTIPort 2 }

gs2352STPMSTI2AggregatedPort                                                OBJECT IDENTIFIER ::= { gs2352STPMSTI2Port 1 }

gs2352STPMSTI2AggregatedPortPathCost OBJECT-TYPE
   SYNTAX      Integer32(0..200000000)
   MAX-ACCESS  read-write
   STATUS      current
   DESCRIPTION
       " Auto: 0,
        Specific Path Cost range: 1 - 200000000."
   ::= { gs2352STPMSTI2AggregatedPort 1 }

gs2352STPMSTI2AggregatedPortPriority OBJECT-TYPE
   SYNTAX      Integer32(0..240)
   MAX-ACCESS  read-write
   STATUS      current
   DESCRIPTION
       " default: 128,
       Aggregated Port Priority (0/16/32/48/64/80/96/112/128/144/160/176/192/208/224/240)"
   ::= { gs2352STPMSTI2AggregatedPort 2 }

gs2352STPMSTI2NormalPortTable OBJECT-TYPE
   SYNTAX      SEQUENCE OF Gs2352STPMSTI2NormalPortEntry
   MAX-ACCESS  not-accessible
   STATUS      current
   DESCRIPTION
       " Show MSTI2 Normal Port Configurations. "
   ::= { gs2352STPMSTI2Port 2 }

gs2352STPMSTI2NormalPortEntry OBJECT-TYPE
   SYNTAX      Gs2352STPMSTI2NormalPortEntry
   MAX-ACCESS  not-accessible
   STATUS      current
   DESCRIPTION
       ""
   INDEX    { gs2352STPMSTI2NormalPortConfPort  }
   ::= { gs2352STPMSTI2NormalPortTable 1 }

Gs2352STPMSTI2NormalPortEntry ::= SEQUENCE {
   gs2352STPMSTI2NormalPortConfPort         Integer32,
   gs2352STPMSTI2NormalPortPathCost         Integer32,
   gs2352STPMSTI2NormalPortPriority         Integer32
}

gs2352STPMSTI2NormalPortConfPort OBJECT-TYPE
   SYNTAX      Integer32(1..4095)
   MAX-ACCESS  not-accessible
   STATUS      current
   DESCRIPTION
       " port, range : 1 - port number. "
   ::= { gs2352STPMSTI2NormalPortEntry 1 }

gs2352STPMSTI2NormalPortPathCost OBJECT-TYPE
   SYNTAX      Integer32(0..200000000)
   MAX-ACCESS  read-write
   STATUS      current
   DESCRIPTION
       " Auto: 0,
        Specific Path Cost range: 1 - 200000000."
   ::= { gs2352STPMSTI2NormalPortEntry 2 }

gs2352STPMSTI2NormalPortPriority OBJECT-TYPE
   SYNTAX      Integer32(0..240)
   MAX-ACCESS  read-write
   STATUS      current
   DESCRIPTION
       " default: 128,
       Aggregated Port Priority (0/16/32/48/64/80/96/112/128/144/160/176/192/208/224/240)"
   ::= { gs2352STPMSTI2NormalPortEntry 3 }

gs2352STPMSTI3Port                                                          OBJECT IDENTIFIER ::= { gs2352STPMSTIPort 3 }

gs2352STPMSTI3AggregatedPort                                                OBJECT IDENTIFIER ::= { gs2352STPMSTI3Port 1 }

gs2352STPMSTI3AggregatedPortPathCost OBJECT-TYPE
   SYNTAX      Integer32(0..200000000)
   MAX-ACCESS  read-write
   STATUS      current
   DESCRIPTION
       " Auto: 0,
        Specific Path Cost range: 1 - 200000000."
   ::= { gs2352STPMSTI3AggregatedPort 1 }

gs2352STPMSTI3AggregatedPortPriority OBJECT-TYPE
   SYNTAX      Integer32(0..240)
   MAX-ACCESS  read-write
   STATUS      current
   DESCRIPTION
       " default: 128,
       Aggregated Port Priority (0/16/32/48/64/80/96/112/128/144/160/176/192/208/224/240)"
   ::= { gs2352STPMSTI3AggregatedPort 2 }

gs2352STPMSTI3NormalPortTable OBJECT-TYPE
   SYNTAX      SEQUENCE OF Gs2352STPMSTI3NormalPortEntry
   MAX-ACCESS  not-accessible
   STATUS      current
   DESCRIPTION
       " Show MSTI3 Normal Port Configurations. "
   ::= { gs2352STPMSTI3Port 2 }

gs2352STPMSTI3NormalPortEntry OBJECT-TYPE
   SYNTAX      Gs2352STPMSTI3NormalPortEntry
   MAX-ACCESS  not-accessible
   STATUS      current
   DESCRIPTION
       ""
   INDEX    { gs2352STPMSTI3NormalPortConfPort  }
   ::= { gs2352STPMSTI3NormalPortTable 1 }

Gs2352STPMSTI3NormalPortEntry ::= SEQUENCE {
   gs2352STPMSTI3NormalPortConfPort         Integer32,
   gs2352STPMSTI3NormalPortPathCost         Integer32,
   gs2352STPMSTI3NormalPortPriority         Integer32
}

gs2352STPMSTI3NormalPortConfPort OBJECT-TYPE
   SYNTAX      Integer32(1..4095)
   MAX-ACCESS  not-accessible
   STATUS      current
   DESCRIPTION
       " port, range : 1 - port number. "
   ::= { gs2352STPMSTI3NormalPortEntry 1 }

gs2352STPMSTI3NormalPortPathCost OBJECT-TYPE
   SYNTAX      Integer32(0..200000000)
   MAX-ACCESS  read-write
   STATUS      current
   DESCRIPTION
       " Auto: 0,
        Specific Path Cost range: 1 - 200000000."
   ::= { gs2352STPMSTI3NormalPortEntry 2 }

gs2352STPMSTI3NormalPortPriority OBJECT-TYPE
   SYNTAX      Integer32(0..240)
   MAX-ACCESS  read-write
   STATUS      current
   DESCRIPTION
       " default: 128,
       Aggregated Port Priority (0/16/32/48/64/80/96/112/128/144/160/176/192/208/224/240)"
   ::= { gs2352STPMSTI3NormalPortEntry 3 }

gs2352STPMSTI4Port                                                          OBJECT IDENTIFIER ::= { gs2352STPMSTIPort 4 }

gs2352STPMSTI4AggregatedPort                                                OBJECT IDENTIFIER ::= { gs2352STPMSTI4Port 1 }

gs2352STPMSTI4AggregatedPortPathCost OBJECT-TYPE
   SYNTAX      Integer32(0..200000000)
   MAX-ACCESS  read-write
   STATUS      current
   DESCRIPTION
       " Auto: 0,
        Specific Path Cost range: 1 - 200000000."
   ::= { gs2352STPMSTI4AggregatedPort 1 }

gs2352STPMSTI4AggregatedPortPriority OBJECT-TYPE
   SYNTAX      Integer32(0..240)
   MAX-ACCESS  read-write
   STATUS      current
   DESCRIPTION
       " default: 128,
       Aggregated Port Priority (0/16/32/48/64/80/96/112/128/144/160/176/192/208/224/240)"
   ::= { gs2352STPMSTI4AggregatedPort 2 }

gs2352STPMSTI4NormalPortTable OBJECT-TYPE
   SYNTAX      SEQUENCE OF Gs2352STPMSTI4NormalPortEntry
   MAX-ACCESS  not-accessible
   STATUS      current
   DESCRIPTION
       " Show MSTI4 Normal Port Configurations. "
   ::= { gs2352STPMSTI4Port 2 }

gs2352STPMSTI4NormalPortEntry OBJECT-TYPE
   SYNTAX      Gs2352STPMSTI4NormalPortEntry
   MAX-ACCESS  not-accessible
   STATUS      current
   DESCRIPTION
       ""
   INDEX    { gs2352STPMSTI4NormalPortConfPort  }
   ::= { gs2352STPMSTI4NormalPortTable 1 }

Gs2352STPMSTI4NormalPortEntry ::= SEQUENCE {
   gs2352STPMSTI4NormalPortConfPort         Integer32,
   gs2352STPMSTI4NormalPortPathCost         Integer32,
   gs2352STPMSTI4NormalPortPriority         Integer32
}

gs2352STPMSTI4NormalPortConfPort OBJECT-TYPE
   SYNTAX      Integer32(1..4095)
   MAX-ACCESS  not-accessible
   STATUS      current
   DESCRIPTION
       " port, range : 1 - port number. "
   ::= { gs2352STPMSTI4NormalPortEntry 1 }

gs2352STPMSTI4NormalPortPathCost OBJECT-TYPE
   SYNTAX      Integer32(0..200000000)
   MAX-ACCESS  read-write
   STATUS      current
   DESCRIPTION
       " Auto: 0,
        Specific Path Cost range: 1 - 200000000."
   ::= { gs2352STPMSTI4NormalPortEntry 2 }

gs2352STPMSTI4NormalPortPriority OBJECT-TYPE
   SYNTAX      Integer32(0..240)
   MAX-ACCESS  read-write
   STATUS      current
   DESCRIPTION
       " default: 128,
       Aggregated Port Priority (0/16/32/48/64/80/96/112/128/144/160/176/192/208/224/240)"
   ::= { gs2352STPMSTI4NormalPortEntry 3 }

gs2352STPMSTI5Port                                                          OBJECT IDENTIFIER ::= { gs2352STPMSTIPort 5 }

gs2352STPMSTI5AggregatedPort                                                OBJECT IDENTIFIER ::= { gs2352STPMSTI5Port 1 }

gs2352STPMSTI5AggregatedPortPathCost OBJECT-TYPE
   SYNTAX      Integer32(0..200000000)
   MAX-ACCESS  read-write
   STATUS      current
   DESCRIPTION
       " Auto: 0,
        Specific Path Cost range: 1 - 200000000."
   ::= { gs2352STPMSTI5AggregatedPort 1 }

gs2352STPMSTI5AggregatedPortPriority OBJECT-TYPE
   SYNTAX      Integer32(0..240)
   MAX-ACCESS  read-write
   STATUS      current
   DESCRIPTION
       " default: 128,
       Aggregated Port Priority (0/16/32/48/64/80/96/112/128/144/160/176/192/208/224/240)"
   ::= { gs2352STPMSTI5AggregatedPort 2 }

gs2352STPMSTI5NormalPortTable OBJECT-TYPE
   SYNTAX      SEQUENCE OF Gs2352STPMSTI5NormalPortEntry
   MAX-ACCESS  not-accessible
   STATUS      current
   DESCRIPTION
       " Show MSTI5 Normal Port Configurations. "
   ::= { gs2352STPMSTI5Port 2 }

gs2352STPMSTI5NormalPortEntry OBJECT-TYPE
   SYNTAX      Gs2352STPMSTI5NormalPortEntry
   MAX-ACCESS  not-accessible
   STATUS      current
   DESCRIPTION
       ""
   INDEX    { gs2352STPMSTI5NormalPortConfPort  }
   ::= { gs2352STPMSTI5NormalPortTable 1 }

Gs2352STPMSTI5NormalPortEntry ::= SEQUENCE {
   gs2352STPMSTI5NormalPortConfPort         Integer32,
   gs2352STPMSTI5NormalPortPathCost         Integer32,
   gs2352STPMSTI5NormalPortPriority         Integer32
}

gs2352STPMSTI5NormalPortConfPort OBJECT-TYPE
   SYNTAX      Integer32(1..4095)
   MAX-ACCESS  not-accessible
   STATUS      current
   DESCRIPTION
       " port, range : 1 - port number. "
   ::= { gs2352STPMSTI5NormalPortEntry 1 }

gs2352STPMSTI5NormalPortPathCost OBJECT-TYPE
   SYNTAX      Integer32(0..200000000)
   MAX-ACCESS  read-write
   STATUS      current
   DESCRIPTION
       " Auto: 0,
        Specific Path Cost range: 1 - 200000000."
   ::= { gs2352STPMSTI5NormalPortEntry 2 }

gs2352STPMSTI5NormalPortPriority OBJECT-TYPE
   SYNTAX      Integer32(0..240)
   MAX-ACCESS  read-write
   STATUS      current
   DESCRIPTION
       " default: 128,
       Aggregated Port Priority (0/16/32/48/64/80/96/112/128/144/160/176/192/208/224/240)"
   ::= { gs2352STPMSTI5NormalPortEntry 3 }

gs2352STPMSTI6Port                                                          OBJECT IDENTIFIER ::= { gs2352STPMSTIPort 6 }

gs2352STPMSTI6AggregatedPort                                                OBJECT IDENTIFIER ::= { gs2352STPMSTI6Port 1 }

gs2352STPMSTI6AggregatedPortPathCost OBJECT-TYPE
   SYNTAX      Integer32(0..200000000)
   MAX-ACCESS  read-write
   STATUS      current
   DESCRIPTION
       " Auto: 0,
        Specific Path Cost range: 1 - 200000000."
   ::= { gs2352STPMSTI6AggregatedPort 1 }

gs2352STPMSTI6AggregatedPortPriority OBJECT-TYPE
   SYNTAX      Integer32(0..240)
   MAX-ACCESS  read-write
   STATUS      current
   DESCRIPTION
       " default: 128,
       Aggregated Port Priority (0/16/32/48/64/80/96/112/128/144/160/176/192/208/224/240)"
   ::= { gs2352STPMSTI6AggregatedPort 2 }

gs2352STPMSTI6NormalPortTable OBJECT-TYPE
   SYNTAX      SEQUENCE OF Gs2352STPMSTI6NormalPortEntry
   MAX-ACCESS  not-accessible
   STATUS      current
   DESCRIPTION
       " Show MSTI6 Normal Port Configurations. "
   ::= { gs2352STPMSTI6Port 2 }

gs2352STPMSTI6NormalPortEntry OBJECT-TYPE
   SYNTAX      Gs2352STPMSTI6NormalPortEntry
   MAX-ACCESS  not-accessible
   STATUS      current
   DESCRIPTION
       ""
   INDEX    { gs2352STPMSTI6NormalPortConfPort  }
   ::= { gs2352STPMSTI6NormalPortTable 1 }

Gs2352STPMSTI6NormalPortEntry ::= SEQUENCE {
   gs2352STPMSTI6NormalPortConfPort         Integer32,
   gs2352STPMSTI6NormalPortPathCost         Integer32,
   gs2352STPMSTI6NormalPortPriority         Integer32
}

gs2352STPMSTI6NormalPortConfPort OBJECT-TYPE
   SYNTAX      Integer32(1..4095)
   MAX-ACCESS  not-accessible
   STATUS      current
   DESCRIPTION
       " port, range : 1 - port number. "
   ::= { gs2352STPMSTI6NormalPortEntry 1 }

gs2352STPMSTI6NormalPortPathCost OBJECT-TYPE
   SYNTAX      Integer32(0..200000000)
   MAX-ACCESS  read-write
   STATUS      current
   DESCRIPTION
       " Auto: 0,
        Specific Path Cost range: 1 - 200000000."
   ::= { gs2352STPMSTI6NormalPortEntry 2 }

gs2352STPMSTI6NormalPortPriority OBJECT-TYPE
   SYNTAX      Integer32(0..240)
   MAX-ACCESS  read-write
   STATUS      current
   DESCRIPTION
       " default: 128,
       Aggregated Port Priority (0/16/32/48/64/80/96/112/128/144/160/176/192/208/224/240)"
   ::= { gs2352STPMSTI6NormalPortEntry 3 }

gs2352STPMSTI7Port                                                          OBJECT IDENTIFIER ::= { gs2352STPMSTIPort 7 }

gs2352STPMSTI7AggregatedPort                                                OBJECT IDENTIFIER ::= { gs2352STPMSTI7Port 1 }

gs2352STPMSTI7AggregatedPortPathCost OBJECT-TYPE
   SYNTAX      Integer32(0..200000000)
   MAX-ACCESS  read-write
   STATUS      current
   DESCRIPTION
       " Auto: 0,
        Specific Path Cost range: 1 - 200000000."
   ::= { gs2352STPMSTI7AggregatedPort 1 }

gs2352STPMSTI7AggregatedPortPriority OBJECT-TYPE
   SYNTAX      Integer32(0..240)
   MAX-ACCESS  read-write
   STATUS      current
   DESCRIPTION
       " default: 128,
       Aggregated Port Priority (0/16/32/48/64/80/96/112/128/144/160/176/192/208/224/240)"
   ::= { gs2352STPMSTI7AggregatedPort 2 }

gs2352STPMSTI7NormalPortTable OBJECT-TYPE
   SYNTAX      SEQUENCE OF Gs2352STPMSTI7NormalPortEntry
   MAX-ACCESS  not-accessible
   STATUS      current
   DESCRIPTION
       " Show MSTI7 Normal Port Configurations. "
   ::= { gs2352STPMSTI7Port 2 }

gs2352STPMSTI7NormalPortEntry OBJECT-TYPE
   SYNTAX      Gs2352STPMSTI7NormalPortEntry
   MAX-ACCESS  not-accessible
   STATUS      current
   DESCRIPTION
       ""
   INDEX    { gs2352STPMSTI7NormalPortConfPort  }
   ::= { gs2352STPMSTI7NormalPortTable 1 }

Gs2352STPMSTI7NormalPortEntry ::= SEQUENCE {
   gs2352STPMSTI7NormalPortConfPort         Integer32,
   gs2352STPMSTI7NormalPortPathCost         Integer32,
   gs2352STPMSTI7NormalPortPriority         Integer32
}

gs2352STPMSTI7NormalPortConfPort OBJECT-TYPE
   SYNTAX      Integer32(1..4095)
   MAX-ACCESS  not-accessible
   STATUS      current
   DESCRIPTION
       " port, range : 1 - port number. "
   ::= { gs2352STPMSTI7NormalPortEntry 1 }

gs2352STPMSTI7NormalPortPathCost OBJECT-TYPE
   SYNTAX      Integer32(0..200000000)
   MAX-ACCESS  read-write
   STATUS      current
   DESCRIPTION
       " Auto: 0,
        Specific Path Cost range: 1 - 200000000."
   ::= { gs2352STPMSTI7NormalPortEntry 2 }

gs2352STPMSTI7NormalPortPriority OBJECT-TYPE
   SYNTAX      Integer32(0..240)
   MAX-ACCESS  read-write
   STATUS      current
   DESCRIPTION
       " default: 128,
       Aggregated Port Priority (0/16/32/48/64/80/96/112/128/144/160/176/192/208/224/240)"
   ::= { gs2352STPMSTI7NormalPortEntry 3 }


gs2352STPBridgeStatus                                                      OBJECT IDENTIFIER ::= { gs2352STP 8 }

gs2352CISTBridgeSTP                                                        OBJECT IDENTIFIER ::= { gs2352STPBridgeStatus 1 }

gs2352CISTBridgeSTPStatus                                                  OBJECT IDENTIFIER ::= { gs2352CISTBridgeSTP 1 }

gs2352CISTBridgeInstance OBJECT-TYPE
   SYNTAX       DisplayString
   MAX-ACCESS   read-only
   STATUS       current
   DESCRIPTION
       "The Bridge instance - CIST, MST1, ..."
   ::= { gs2352CISTBridgeSTPStatus 1 }

gs2352CISTBridgeID OBJECT-TYPE
   SYNTAX       DisplayString
   MAX-ACCESS   read-only
   STATUS       current
   DESCRIPTION
       "The Bridge ID of this Bridge instance."
   ::= { gs2352CISTBridgeSTPStatus 2 }

gs2352CISTRootID OBJECT-TYPE
   SYNTAX       DisplayString
   MAX-ACCESS   read-only
   STATUS       current
   DESCRIPTION
       "The Bridge ID of the currently elected root bridge."
   ::= { gs2352CISTBridgeSTPStatus 3 }

gs2352CISTRootPort OBJECT-TYPE
   SYNTAX       DisplayString
   MAX-ACCESS   read-only
   STATUS       current
   DESCRIPTION
       "The switch port currently assigned the root port role."
   ::= { gs2352CISTBridgeSTPStatus 4 }

gs2352CISTRootCost OBJECT-TYPE
   SYNTAX       Integer32(0..200000000)
   MAX-ACCESS   read-only
   STATUS       current
   DESCRIPTION
       "Root Path Cost."
   ::= { gs2352CISTBridgeSTPStatus 5 }

gs2352CISTRegionalRoot OBJECT-TYPE
   SYNTAX       DisplayString
   MAX-ACCESS   read-only
   STATUS       current
   DESCRIPTION
       "The Bridge ID of the currently elected regional root bridge, inside the MSTP region of this bridge."
   ::= { gs2352CISTBridgeSTPStatus 6 }

gs2352CISTInternalRootCost OBJECT-TYPE
   SYNTAX       Integer32(0..200000000)
   MAX-ACCESS   read-only
   STATUS       current
   DESCRIPTION
       "The Regional Root Path Cost."
   ::= { gs2352CISTBridgeSTPStatus 7 }

gs2352CISTTopologyFlag OBJECT-TYPE
   SYNTAX       DisplayString
   MAX-ACCESS   read-only
   STATUS       current
   DESCRIPTION
       "The current state of the Topology Change Flag of this Bridge instance."
   ::= { gs2352CISTBridgeSTPStatus 8 }

gs2352CISTTopologyChangeCount OBJECT-TYPE
   SYNTAX       Counter32
   MAX-ACCESS   read-only
   STATUS       current
   DESCRIPTION
       "The number of times where the topology change flag has been set."
   ::= { gs2352CISTBridgeSTPStatus 9 }

gs2352CISTTopologyChangeLast OBJECT-TYPE
   SYNTAX       DisplayString
   MAX-ACCESS   read-only
   STATUS       current
   DESCRIPTION
       "The time passed since the Topology Flag was last set."
   ::= { gs2352CISTBridgeSTPStatus 10 }

gs2352CISTPortStateTable OBJECT-TYPE
   SYNTAX      SEQUENCE OF Gs2352CISTPortStateEntry
   MAX-ACCESS  not-accessible
   STATUS      current
   DESCRIPTION
       " Show CIST Ports and Aggregations State Configurations. "
   ::= { gs2352CISTBridgeSTP 2 }

gs2352CISTPortStateEntry OBJECT-TYPE
   SYNTAX      Gs2352CISTPortStateEntry
   MAX-ACCESS  not-accessible
   STATUS      current
   DESCRIPTION
       ""
   INDEX    { gs2352CISTPortStateIndex  }
   ::= { gs2352CISTPortStateTable 1 }

Gs2352CISTPortStateEntry ::= SEQUENCE {
   gs2352CISTPortStateIndex        Integer32,
   gs2352CISTPortStatePort         DisplayString,
   gs2352CISTPortStatePortID       DisplayString,
   gs2352CISTPortStateRole         DisplayString,
   gs2352CISTPortStateState        DisplayString,
   gs2352CISTPortStatePathCost     Integer32,
   gs2352CISTPortStateEdge         DisplayString,
   gs2352CISTPortStatePoint2Point  DisplayString,
   gs2352CISTPortStateUptime       DisplayString
}

gs2352CISTPortStateIndex OBJECT-TYPE
   SYNTAX      Integer32(1..4095)
   MAX-ACCESS  not-accessible
   STATUS      current
   DESCRIPTION
       "table index."
   ::= { gs2352CISTPortStateEntry 1 }

gs2352CISTPortStatePort OBJECT-TYPE
   SYNTAX      DisplayString
   MAX-ACCESS  read-only
   STATUS      current
   DESCRIPTION
       "The switch port number of the logical STP port."
   ::= { gs2352CISTPortStateEntry 2 }

gs2352CISTPortStatePortID OBJECT-TYPE
   SYNTAX      DisplayString
   MAX-ACCESS  read-only
   STATUS      current
   DESCRIPTION
       "The port id as used by the STP protocol.
        This is the priority part and the logical port index of the bridge port."
   ::= { gs2352CISTPortStateEntry 3 }

gs2352CISTPortStateRole OBJECT-TYPE
   SYNTAX      DisplayString
   MAX-ACCESS  read-only
   STATUS      current
   DESCRIPTION
       "The current STP port role."
   ::= { gs2352CISTPortStateEntry 4 }

gs2352CISTPortStateState OBJECT-TYPE
   SYNTAX      DisplayString
   MAX-ACCESS  read-only
   STATUS      current
   DESCRIPTION
       "The current STP port state."
   ::= { gs2352CISTPortStateEntry 5 }

gs2352CISTPortStatePathCost OBJECT-TYPE
   SYNTAX      Integer32(0..200000000)
   MAX-ACCESS  read-only
   STATUS      current
   DESCRIPTION
       "The current STP port path cost."
   ::= { gs2352CISTPortStateEntry 6 }

gs2352CISTPortStateEdge OBJECT-TYPE
   SYNTAX      DisplayString
   MAX-ACCESS  read-only
   STATUS      current
   DESCRIPTION
       "The current STP port Edge Flag."
   ::= { gs2352CISTPortStateEntry 7 }

gs2352CISTPortStatePoint2Point OBJECT-TYPE
   SYNTAX      DisplayString
   MAX-ACCESS  read-only
   STATUS      current
   DESCRIPTION
       "The current STP port point-to-point flag."
   ::= { gs2352CISTPortStateEntry 8 }

gs2352CISTPortStateUptime OBJECT-TYPE
   SYNTAX      DisplayString
   MAX-ACCESS  read-only
   STATUS      current
   DESCRIPTION
       "The time since the bridge port was last initialized."
   ::= { gs2352CISTPortStateEntry 9 }

gs2352MSTI1BridgeSTP                                                        OBJECT IDENTIFIER ::= { gs2352STPBridgeStatus 2 }

gs2352MSTI1BridgeSTPStatus                                                  OBJECT IDENTIFIER ::= { gs2352MSTI1BridgeSTP 1 }

gs2352MSTI1BridgeInstance OBJECT-TYPE
   SYNTAX       DisplayString
   MAX-ACCESS   read-only
   STATUS       current
   DESCRIPTION
       "The Bridge instance - CIST, MST1, ..."
   ::= { gs2352MSTI1BridgeSTPStatus 1 }

gs2352MSTI1BridgeID OBJECT-TYPE
   SYNTAX       DisplayString
   MAX-ACCESS   read-only
   STATUS       current
   DESCRIPTION
       "The Bridge ID of this Bridge instance."
   ::= { gs2352MSTI1BridgeSTPStatus 2 }

gs2352MSTI1RootID OBJECT-TYPE
   SYNTAX       DisplayString
   MAX-ACCESS   read-only
   STATUS       current
   DESCRIPTION
       "The Bridge ID of the currently elected root bridge."
   ::= { gs2352MSTI1BridgeSTPStatus 3 }

gs2352MSTI1RootPort OBJECT-TYPE
   SYNTAX       DisplayString
   MAX-ACCESS   read-only
   STATUS       current
   DESCRIPTION
       "The switch port currently assigned the root port role."
   ::= { gs2352MSTI1BridgeSTPStatus 4 }

gs2352MSTI1RootCost OBJECT-TYPE
   SYNTAX       Integer32(0..200000000)
   MAX-ACCESS   read-only
   STATUS       current
   DESCRIPTION
       "Root Path Cost."
   ::= { gs2352MSTI1BridgeSTPStatus 5 }

gs2352MSTI1TopologyFlag OBJECT-TYPE
   SYNTAX       DisplayString
   MAX-ACCESS   read-only
   STATUS       current
   DESCRIPTION
       "The current state of the Topology Change Flag of this Bridge instance."
   ::= { gs2352MSTI1BridgeSTPStatus 8 }

gs2352MSTI1TopologyChangeCount OBJECT-TYPE
   SYNTAX       Counter32
   MAX-ACCESS   read-only
   STATUS       current
   DESCRIPTION
       "The number of times where the topology change flag has been set."
   ::= { gs2352MSTI1BridgeSTPStatus 9 }

gs2352MSTI1TopologyChangeLast OBJECT-TYPE
   SYNTAX       DisplayString
   MAX-ACCESS   read-only
   STATUS       current
   DESCRIPTION
       "The time passed since the Topology Flag was last set."
   ::= { gs2352MSTI1BridgeSTPStatus 10 }

gs2352MSTI1PortStateTable OBJECT-TYPE
   SYNTAX      SEQUENCE OF Gs2352MSTI1PortStateEntry
   MAX-ACCESS  not-accessible
   STATUS      current
   DESCRIPTION
       " Show MSTI1 Ports and Aggregations State Configurations. "
   ::= { gs2352MSTI1BridgeSTP 2 }

gs2352MSTI1PortStateEntry OBJECT-TYPE
   SYNTAX      Gs2352MSTI1PortStateEntry
   MAX-ACCESS  not-accessible
   STATUS      current
   DESCRIPTION
       ""
   INDEX    { gs2352MSTI1PortStateIndex  }
   ::= { gs2352MSTI1PortStateTable 1 }

Gs2352MSTI1PortStateEntry ::= SEQUENCE {
   gs2352MSTI1PortStateIndex        Integer32,
   gs2352MSTI1PortStatePort         DisplayString,
   gs2352MSTI1PortStatePortID       DisplayString,
   gs2352MSTI1PortStateRole         DisplayString,
   gs2352MSTI1PortStateState        DisplayString,
   gs2352MSTI1PortStatePathCost     Integer32,
   gs2352MSTI1PortStateEdge         DisplayString,
   gs2352MSTI1PortStatePoint2Point  DisplayString,
   gs2352MSTI1PortStateUptime       DisplayString
}

gs2352MSTI1PortStateIndex OBJECT-TYPE
   SYNTAX      Integer32(1..4095)
   MAX-ACCESS  not-accessible
   STATUS      current
   DESCRIPTION
       "table index."
   ::= { gs2352MSTI1PortStateEntry 1 }

gs2352MSTI1PortStatePort OBJECT-TYPE
   SYNTAX      DisplayString
   MAX-ACCESS  read-only
   STATUS      current
   DESCRIPTION
       "The switch port number of the logical STP port."
   ::= { gs2352MSTI1PortStateEntry 2 }

gs2352MSTI1PortStatePortID OBJECT-TYPE
   SYNTAX      DisplayString
   MAX-ACCESS  read-only
   STATUS      current
   DESCRIPTION
       "The port id as used by the STP protocol.
        This is the priority part and the logical port index of the bridge port."
   ::= { gs2352MSTI1PortStateEntry 3 }

gs2352MSTI1PortStateRole OBJECT-TYPE
   SYNTAX      DisplayString
   MAX-ACCESS  read-only
   STATUS      current
   DESCRIPTION
       "The current STP port role."
   ::= { gs2352MSTI1PortStateEntry 4 }

gs2352MSTI1PortStateState OBJECT-TYPE
   SYNTAX      DisplayString
   MAX-ACCESS  read-only
   STATUS      current
   DESCRIPTION
       "The current STP port state."
   ::= { gs2352MSTI1PortStateEntry 5 }

gs2352MSTI1PortStatePathCost OBJECT-TYPE
   SYNTAX      Integer32(0..200000000)
   MAX-ACCESS  read-only
   STATUS      current
   DESCRIPTION
       "The current STP port path cost."
   ::= { gs2352MSTI1PortStateEntry 6 }

gs2352MSTI1PortStateEdge OBJECT-TYPE
   SYNTAX      DisplayString
   MAX-ACCESS  read-only
   STATUS      current
   DESCRIPTION
       "The current STP port Edge Flag."
   ::= { gs2352MSTI1PortStateEntry 7 }

gs2352MSTI1PortStatePoint2Point OBJECT-TYPE
   SYNTAX      DisplayString
   MAX-ACCESS  read-only
   STATUS      current
   DESCRIPTION
       "The current STP port point-to-point flag."
   ::= { gs2352MSTI1PortStateEntry 8 }

gs2352MSTI1PortStateUptime OBJECT-TYPE
   SYNTAX      DisplayString
   MAX-ACCESS  read-only
   STATUS      current
   DESCRIPTION
       "The time since the bridge port was last initialized."
   ::= { gs2352MSTI1PortStateEntry 9 }

gs2352MSTI2BridgeSTP                                                        OBJECT IDENTIFIER ::= { gs2352STPBridgeStatus 3 }

gs2352MSTI2BridgeSTPStatus                                                  OBJECT IDENTIFIER ::= { gs2352MSTI2BridgeSTP 1 }

gs2352MSTI2BridgeInstance OBJECT-TYPE
   SYNTAX       DisplayString
   MAX-ACCESS   read-only
   STATUS       current
   DESCRIPTION
       "The Bridge instance - CIST, MST1, ..."
   ::= { gs2352MSTI2BridgeSTPStatus 1 }

gs2352MSTI2BridgeID OBJECT-TYPE
   SYNTAX       DisplayString
   MAX-ACCESS   read-only
   STATUS       current
   DESCRIPTION
       "The Bridge ID of this Bridge instance."
   ::= { gs2352MSTI2BridgeSTPStatus 2 }

gs2352MSTI2RootID OBJECT-TYPE
   SYNTAX       DisplayString
   MAX-ACCESS   read-only
   STATUS       current
   DESCRIPTION
       "The Bridge ID of the currently elected root bridge."
   ::= { gs2352MSTI2BridgeSTPStatus 3 }

gs2352MSTI2RootPort OBJECT-TYPE
   SYNTAX       DisplayString
   MAX-ACCESS   read-only
   STATUS       current
   DESCRIPTION
       "The switch port currently assigned the root port role."
   ::= { gs2352MSTI2BridgeSTPStatus 4 }

gs2352MSTI2RootCost OBJECT-TYPE
   SYNTAX       Integer32(0..200000000)
   MAX-ACCESS   read-only
   STATUS       current
   DESCRIPTION
       "Root Path Cost."
   ::= { gs2352MSTI2BridgeSTPStatus 5 }

gs2352MSTI2TopologyFlag OBJECT-TYPE
   SYNTAX       DisplayString
   MAX-ACCESS   read-only
   STATUS       current
   DESCRIPTION
       "The current state of the Topology Change Flag of this Bridge instance."
   ::= { gs2352MSTI2BridgeSTPStatus 8 }

gs2352MSTI2TopologyChangeCount OBJECT-TYPE
   SYNTAX       Counter32
   MAX-ACCESS   read-only
   STATUS       current
   DESCRIPTION
       "The number of times where the topology change flag has been set."
   ::= { gs2352MSTI2BridgeSTPStatus 9 }

gs2352MSTI2TopologyChangeLast OBJECT-TYPE
   SYNTAX       DisplayString
   MAX-ACCESS   read-only
   STATUS       current
   DESCRIPTION
       "The time passed since the Topology Flag was last set."
   ::= { gs2352MSTI2BridgeSTPStatus 10 }

gs2352MSTI2PortStateTable OBJECT-TYPE
   SYNTAX      SEQUENCE OF Gs2352MSTI2PortStateEntry
   MAX-ACCESS  not-accessible
   STATUS      current
   DESCRIPTION
       " Show MSTI2 Ports and Aggregations State Configurations. "
   ::= { gs2352MSTI2BridgeSTP 2 }

gs2352MSTI2PortStateEntry OBJECT-TYPE
   SYNTAX      Gs2352MSTI2PortStateEntry
   MAX-ACCESS  not-accessible
   STATUS      current
   DESCRIPTION
       ""
   INDEX    { gs2352MSTI2PortStateIndex  }
   ::= { gs2352MSTI2PortStateTable 1 }

Gs2352MSTI2PortStateEntry ::= SEQUENCE {
   gs2352MSTI2PortStateIndex        Integer32,
   gs2352MSTI2PortStatePort         DisplayString,
   gs2352MSTI2PortStatePortID       DisplayString,
   gs2352MSTI2PortStateRole         DisplayString,
   gs2352MSTI2PortStateState        DisplayString,
   gs2352MSTI2PortStatePathCost     Integer32,
   gs2352MSTI2PortStateEdge         DisplayString,
   gs2352MSTI2PortStatePoint2Point  DisplayString,
   gs2352MSTI2PortStateUptime       DisplayString
}

gs2352MSTI2PortStateIndex OBJECT-TYPE
   SYNTAX      Integer32(1..4095)
   MAX-ACCESS  not-accessible
   STATUS      current
   DESCRIPTION
       "table index."
   ::= { gs2352MSTI2PortStateEntry 1 }

gs2352MSTI2PortStatePort OBJECT-TYPE
   SYNTAX      DisplayString
   MAX-ACCESS  read-only
   STATUS      current
   DESCRIPTION
       "The switch port number of the logical STP port."
   ::= { gs2352MSTI2PortStateEntry 2 }

gs2352MSTI2PortStatePortID OBJECT-TYPE
   SYNTAX      DisplayString
   MAX-ACCESS  read-only
   STATUS      current
   DESCRIPTION
       "The port id as used by the STP protocol.
        This is the priority part and the logical port index of the bridge port."
   ::= { gs2352MSTI2PortStateEntry 3 }

gs2352MSTI2PortStateRole OBJECT-TYPE
   SYNTAX      DisplayString
   MAX-ACCESS  read-only
   STATUS      current
   DESCRIPTION
       "The current STP port role."
   ::= { gs2352MSTI2PortStateEntry 4 }

gs2352MSTI2PortStateState OBJECT-TYPE
   SYNTAX      DisplayString
   MAX-ACCESS  read-only
   STATUS      current
   DESCRIPTION
       "The current STP port state."
   ::= { gs2352MSTI2PortStateEntry 5 }

gs2352MSTI2PortStatePathCost OBJECT-TYPE
   SYNTAX      Integer32(0..200000000)
   MAX-ACCESS  read-only
   STATUS      current
   DESCRIPTION
       "The current STP port path cost."
   ::= { gs2352MSTI2PortStateEntry 6 }

gs2352MSTI2PortStateEdge OBJECT-TYPE
   SYNTAX      DisplayString
   MAX-ACCESS  read-only
   STATUS      current
   DESCRIPTION
       "The current STP port Edge Flag."
   ::= { gs2352MSTI2PortStateEntry 7 }

gs2352MSTI2PortStatePoint2Point OBJECT-TYPE
   SYNTAX      DisplayString
   MAX-ACCESS  read-only
   STATUS      current
   DESCRIPTION
       "The current STP port point-to-point flag."
   ::= { gs2352MSTI2PortStateEntry 8 }

gs2352MSTI2PortStateUptime OBJECT-TYPE
   SYNTAX      DisplayString
   MAX-ACCESS  read-only
   STATUS      current
   DESCRIPTION
       "The time since the bridge port was last initialized."
   ::= { gs2352MSTI2PortStateEntry 9 }

gs2352MSTI3BridgeSTP                                                        OBJECT IDENTIFIER ::= { gs2352STPBridgeStatus 4 }

gs2352MSTI3BridgeSTPStatus                                                  OBJECT IDENTIFIER ::= { gs2352MSTI3BridgeSTP 1 }

gs2352MSTI3BridgeInstance OBJECT-TYPE
   SYNTAX       DisplayString
   MAX-ACCESS   read-only
   STATUS       current
   DESCRIPTION
       "The Bridge instance - CIST, MST1, ..."
   ::= { gs2352MSTI3BridgeSTPStatus 1 }

gs2352MSTI3BridgeID OBJECT-TYPE
   SYNTAX       DisplayString
   MAX-ACCESS   read-only
   STATUS       current
   DESCRIPTION
       "The Bridge ID of this Bridge instance."
   ::= { gs2352MSTI3BridgeSTPStatus 2 }

gs2352MSTI3RootID OBJECT-TYPE
   SYNTAX       DisplayString
   MAX-ACCESS   read-only
   STATUS       current
   DESCRIPTION
       "The Bridge ID of the currently elected root bridge."
   ::= { gs2352MSTI3BridgeSTPStatus 3 }

gs2352MSTI3RootPort OBJECT-TYPE
   SYNTAX       DisplayString
   MAX-ACCESS   read-only
   STATUS       current
   DESCRIPTION
       "The switch port currently assigned the root port role."
   ::= { gs2352MSTI3BridgeSTPStatus 4 }

gs2352MSTI3RootCost OBJECT-TYPE
   SYNTAX       Integer32(0..200000000)
   MAX-ACCESS   read-only
   STATUS       current
   DESCRIPTION
       "Root Path Cost."
   ::= { gs2352MSTI3BridgeSTPStatus 5 }

gs2352MSTI3TopologyFlag OBJECT-TYPE
   SYNTAX       DisplayString
   MAX-ACCESS   read-only
   STATUS       current
   DESCRIPTION
       "The current state of the Topology Change Flag of this Bridge instance."
   ::= { gs2352MSTI3BridgeSTPStatus 8 }

gs2352MSTI3TopologyChangeCount OBJECT-TYPE
   SYNTAX       Counter32
   MAX-ACCESS   read-only
   STATUS       current
   DESCRIPTION
       "The number of times where the topology change flag has been set."
   ::= { gs2352MSTI3BridgeSTPStatus 9 }

gs2352MSTI3TopologyChangeLast OBJECT-TYPE
   SYNTAX       DisplayString
   MAX-ACCESS   read-only
   STATUS       current
   DESCRIPTION
       "The time passed since the Topology Flag was last set."
   ::= { gs2352MSTI3BridgeSTPStatus 10 }

gs2352MSTI3PortStateTable OBJECT-TYPE
   SYNTAX      SEQUENCE OF Gs2352MSTI3PortStateEntry
   MAX-ACCESS  not-accessible
   STATUS      current
   DESCRIPTION
       " Show MSTI3 Ports and Aggregations State Configurations. "
   ::= { gs2352MSTI3BridgeSTP 2 }

gs2352MSTI3PortStateEntry OBJECT-TYPE
   SYNTAX      Gs2352MSTI3PortStateEntry
   MAX-ACCESS  not-accessible
   STATUS      current
   DESCRIPTION
       ""
   INDEX    { gs2352MSTI3PortStateIndex  }
   ::= { gs2352MSTI3PortStateTable 1 }

Gs2352MSTI3PortStateEntry ::= SEQUENCE {
   gs2352MSTI3PortStateIndex        Integer32,
   gs2352MSTI3PortStatePort         DisplayString,
   gs2352MSTI3PortStatePortID       DisplayString,
   gs2352MSTI3PortStateRole         DisplayString,
   gs2352MSTI3PortStateState        DisplayString,
   gs2352MSTI3PortStatePathCost     Integer32,
   gs2352MSTI3PortStateEdge         DisplayString,
   gs2352MSTI3PortStatePoint2Point  DisplayString,
   gs2352MSTI3PortStateUptime       DisplayString
}

gs2352MSTI3PortStateIndex OBJECT-TYPE
   SYNTAX      Integer32(1..4095)
   MAX-ACCESS  not-accessible
   STATUS      current
   DESCRIPTION
       "table index."
   ::= { gs2352MSTI3PortStateEntry 1 }

gs2352MSTI3PortStatePort OBJECT-TYPE
   SYNTAX      DisplayString
   MAX-ACCESS  read-only
   STATUS      current
   DESCRIPTION
       "The switch port number of the logical STP port."
   ::= { gs2352MSTI3PortStateEntry 2 }

gs2352MSTI3PortStatePortID OBJECT-TYPE
   SYNTAX      DisplayString
   MAX-ACCESS  read-only
   STATUS      current
   DESCRIPTION
       "The port id as used by the STP protocol.
        This is the priority part and the logical port index of the bridge port."
   ::= { gs2352MSTI3PortStateEntry 3 }

gs2352MSTI3PortStateRole OBJECT-TYPE
   SYNTAX      DisplayString
   MAX-ACCESS  read-only
   STATUS      current
   DESCRIPTION
       "The current STP port role."
   ::= { gs2352MSTI3PortStateEntry 4 }

gs2352MSTI3PortStateState OBJECT-TYPE
   SYNTAX      DisplayString
   MAX-ACCESS  read-only
   STATUS      current
   DESCRIPTION
       "The current STP port state."
   ::= { gs2352MSTI3PortStateEntry 5 }

gs2352MSTI3PortStatePathCost OBJECT-TYPE
   SYNTAX      Integer32(0..200000000)
   MAX-ACCESS  read-only
   STATUS      current
   DESCRIPTION
       "The current STP port path cost."
   ::= { gs2352MSTI3PortStateEntry 6 }

gs2352MSTI3PortStateEdge OBJECT-TYPE
   SYNTAX      DisplayString
   MAX-ACCESS  read-only
   STATUS      current
   DESCRIPTION
       "The current STP port Edge Flag."
   ::= { gs2352MSTI3PortStateEntry 7 }

gs2352MSTI3PortStatePoint2Point OBJECT-TYPE
   SYNTAX      DisplayString
   MAX-ACCESS  read-only
   STATUS      current
   DESCRIPTION
       "The current STP port point-to-point flag."
   ::= { gs2352MSTI3PortStateEntry 8 }

gs2352MSTI3PortStateUptime OBJECT-TYPE
   SYNTAX      DisplayString
   MAX-ACCESS  read-only
   STATUS      current
   DESCRIPTION
       "The time since the bridge port was last initialized."
   ::= { gs2352MSTI3PortStateEntry 9 }

gs2352MSTI4BridgeSTP                                                        OBJECT IDENTIFIER ::= { gs2352STPBridgeStatus 5 }

gs2352MSTI4BridgeSTPStatus                                                  OBJECT IDENTIFIER ::= { gs2352MSTI4BridgeSTP 1 }

gs2352MSTI4BridgeInstance OBJECT-TYPE
   SYNTAX       DisplayString
   MAX-ACCESS   read-only
   STATUS       current
   DESCRIPTION
       "The Bridge instance - CIST, MST1, ..."
   ::= { gs2352MSTI4BridgeSTPStatus 1 }

gs2352MSTI4BridgeID OBJECT-TYPE
   SYNTAX       DisplayString
   MAX-ACCESS   read-only
   STATUS       current
   DESCRIPTION
       "The Bridge ID of this Bridge instance."
   ::= { gs2352MSTI4BridgeSTPStatus 2 }

gs2352MSTI4RootID OBJECT-TYPE
   SYNTAX       DisplayString
   MAX-ACCESS   read-only
   STATUS       current
   DESCRIPTION
       "The Bridge ID of the currently elected root bridge."
   ::= { gs2352MSTI4BridgeSTPStatus 3 }

gs2352MSTI4RootPort OBJECT-TYPE
   SYNTAX       DisplayString
   MAX-ACCESS   read-only
   STATUS       current
   DESCRIPTION
       "The switch port currently assigned the root port role."
   ::= { gs2352MSTI4BridgeSTPStatus 4 }

gs2352MSTI4RootCost OBJECT-TYPE
   SYNTAX       Integer32(0..200000000)
   MAX-ACCESS   read-only
   STATUS       current
   DESCRIPTION
       "Root Path Cost."
   ::= { gs2352MSTI4BridgeSTPStatus 5 }

gs2352MSTI4TopologyFlag OBJECT-TYPE
   SYNTAX       DisplayString
   MAX-ACCESS   read-only
   STATUS       current
   DESCRIPTION
       "The current state of the Topology Change Flag of this Bridge instance."
   ::= { gs2352MSTI4BridgeSTPStatus 8 }

gs2352MSTI4TopologyChangeCount OBJECT-TYPE
   SYNTAX       Counter32
   MAX-ACCESS   read-only
   STATUS       current
   DESCRIPTION
       "The number of times where the topology change flag has been set."
   ::= { gs2352MSTI4BridgeSTPStatus 9 }

gs2352MSTI4TopologyChangeLast OBJECT-TYPE
   SYNTAX       DisplayString
   MAX-ACCESS   read-only
   STATUS       current
   DESCRIPTION
       "The time passed since the Topology Flag was last set."
   ::= { gs2352MSTI4BridgeSTPStatus 10 }

gs2352MSTI4PortStateTable OBJECT-TYPE
   SYNTAX      SEQUENCE OF Gs2352MSTI4PortStateEntry
   MAX-ACCESS  not-accessible
   STATUS      current
   DESCRIPTION
       " Show MSTI4 Ports and Aggregations State Configurations. "
   ::= { gs2352MSTI4BridgeSTP 2 }

gs2352MSTI4PortStateEntry OBJECT-TYPE
   SYNTAX      Gs2352MSTI4PortStateEntry
   MAX-ACCESS  not-accessible
   STATUS      current
   DESCRIPTION
       ""
   INDEX    { gs2352MSTI4PortStateIndex  }
   ::= { gs2352MSTI4PortStateTable 1 }

Gs2352MSTI4PortStateEntry ::= SEQUENCE {
   gs2352MSTI4PortStateIndex        Integer32,
   gs2352MSTI4PortStatePort         DisplayString,
   gs2352MSTI4PortStatePortID       DisplayString,
   gs2352MSTI4PortStateRole         DisplayString,
   gs2352MSTI4PortStateState        DisplayString,
   gs2352MSTI4PortStatePathCost     Integer32,
   gs2352MSTI4PortStateEdge         DisplayString,
   gs2352MSTI4PortStatePoint2Point  DisplayString,
   gs2352MSTI4PortStateUptime       DisplayString
}

gs2352MSTI4PortStateIndex OBJECT-TYPE
   SYNTAX      Integer32(1..4095)
   MAX-ACCESS  not-accessible
   STATUS      current
   DESCRIPTION
       "table index."
   ::= { gs2352MSTI4PortStateEntry 1 }

gs2352MSTI4PortStatePort OBJECT-TYPE
   SYNTAX      DisplayString
   MAX-ACCESS  read-only
   STATUS      current
   DESCRIPTION
       "The switch port number of the logical STP port."
   ::= { gs2352MSTI4PortStateEntry 2 }

gs2352MSTI4PortStatePortID OBJECT-TYPE
   SYNTAX      DisplayString
   MAX-ACCESS  read-only
   STATUS      current
   DESCRIPTION
       "The port id as used by the STP protocol.
        This is the priority part and the logical port index of the bridge port."
   ::= { gs2352MSTI4PortStateEntry 3 }

gs2352MSTI4PortStateRole OBJECT-TYPE
   SYNTAX      DisplayString
   MAX-ACCESS  read-only
   STATUS      current
   DESCRIPTION
       "The current STP port role."
   ::= { gs2352MSTI4PortStateEntry 4 }

gs2352MSTI4PortStateState OBJECT-TYPE
   SYNTAX      DisplayString
   MAX-ACCESS  read-only
   STATUS      current
   DESCRIPTION
       "The current STP port state."
   ::= { gs2352MSTI4PortStateEntry 5 }

gs2352MSTI4PortStatePathCost OBJECT-TYPE
   SYNTAX      Integer32(0..200000000)
   MAX-ACCESS  read-only
   STATUS      current
   DESCRIPTION
       "The current STP port path cost."
   ::= { gs2352MSTI4PortStateEntry 6 }

gs2352MSTI4PortStateEdge OBJECT-TYPE
   SYNTAX      DisplayString
   MAX-ACCESS  read-only
   STATUS      current
   DESCRIPTION
       "The current STP port Edge Flag."
   ::= { gs2352MSTI4PortStateEntry 7 }

gs2352MSTI4PortStatePoint2Point OBJECT-TYPE
   SYNTAX      DisplayString
   MAX-ACCESS  read-only
   STATUS      current
   DESCRIPTION
       "The current STP port point-to-point flag."
   ::= { gs2352MSTI4PortStateEntry 8 }

gs2352MSTI4PortStateUptime OBJECT-TYPE
   SYNTAX      DisplayString
   MAX-ACCESS  read-only
   STATUS      current
   DESCRIPTION
       "The time since the bridge port was last initialized."
   ::= { gs2352MSTI4PortStateEntry 9 }

gs2352MSTI5BridgeSTP                                                        OBJECT IDENTIFIER ::= { gs2352STPBridgeStatus 6 }

gs2352MSTI5BridgeSTPStatus                                                  OBJECT IDENTIFIER ::= { gs2352MSTI5BridgeSTP 1 }

gs2352MSTI5BridgeInstance OBJECT-TYPE
   SYNTAX       DisplayString
   MAX-ACCESS   read-only
   STATUS       current
   DESCRIPTION
       "The Bridge instance - CIST, MST1, ..."
   ::= { gs2352MSTI5BridgeSTPStatus 1 }

gs2352MSTI5BridgeID OBJECT-TYPE
   SYNTAX       DisplayString
   MAX-ACCESS   read-only
   STATUS       current
   DESCRIPTION
       "The Bridge ID of this Bridge instance."
   ::= { gs2352MSTI5BridgeSTPStatus 2 }

gs2352MSTI5RootID OBJECT-TYPE
   SYNTAX       DisplayString
   MAX-ACCESS   read-only
   STATUS       current
   DESCRIPTION
       "The Bridge ID of the currently elected root bridge."
   ::= { gs2352MSTI5BridgeSTPStatus 3 }

gs2352MSTI5RootPort OBJECT-TYPE
   SYNTAX       DisplayString
   MAX-ACCESS   read-only
   STATUS       current
   DESCRIPTION
       "The switch port currently assigned the root port role."
   ::= { gs2352MSTI5BridgeSTPStatus 4 }

gs2352MSTI5RootCost OBJECT-TYPE
   SYNTAX       Integer32(0..200000000)
   MAX-ACCESS   read-only
   STATUS       current
   DESCRIPTION
       "Root Path Cost."
   ::= { gs2352MSTI5BridgeSTPStatus 5 }

gs2352MSTI5TopologyFlag OBJECT-TYPE
   SYNTAX       DisplayString
   MAX-ACCESS   read-only
   STATUS       current
   DESCRIPTION
       "The current state of the Topology Change Flag of this Bridge instance."
   ::= { gs2352MSTI5BridgeSTPStatus 8 }

gs2352MSTI5TopologyChangeCount OBJECT-TYPE
   SYNTAX       Counter32
   MAX-ACCESS   read-only
   STATUS       current
   DESCRIPTION
       "The number of times where the topology change flag has been set."
   ::= { gs2352MSTI5BridgeSTPStatus 9 }

gs2352MSTI5TopologyChangeLast OBJECT-TYPE
   SYNTAX       DisplayString
   MAX-ACCESS   read-only
   STATUS       current
   DESCRIPTION
       "The time passed since the Topology Flag was last set."
   ::= { gs2352MSTI5BridgeSTPStatus 10 }

gs2352MSTI5PortStateTable OBJECT-TYPE
   SYNTAX      SEQUENCE OF Gs2352MSTI5PortStateEntry
   MAX-ACCESS  not-accessible
   STATUS      current
   DESCRIPTION
       " Show MSTI5 Ports and Aggregations State Configurations. "
   ::= { gs2352MSTI5BridgeSTP 2 }

gs2352MSTI5PortStateEntry OBJECT-TYPE
   SYNTAX      Gs2352MSTI5PortStateEntry
   MAX-ACCESS  not-accessible
   STATUS      current
   DESCRIPTION
       ""
   INDEX    { gs2352MSTI5PortStateIndex  }
   ::= { gs2352MSTI5PortStateTable 1 }

Gs2352MSTI5PortStateEntry ::= SEQUENCE {
   gs2352MSTI5PortStateIndex        Integer32,
   gs2352MSTI5PortStatePort         DisplayString,
   gs2352MSTI5PortStatePortID       DisplayString,
   gs2352MSTI5PortStateRole         DisplayString,
   gs2352MSTI5PortStateState        DisplayString,
   gs2352MSTI5PortStatePathCost     Integer32,
   gs2352MSTI5PortStateEdge         DisplayString,
   gs2352MSTI5PortStatePoint2Point  DisplayString,
   gs2352MSTI5PortStateUptime       DisplayString
}

gs2352MSTI5PortStateIndex OBJECT-TYPE
   SYNTAX      Integer32(1..4095)
   MAX-ACCESS  not-accessible
   STATUS      current
   DESCRIPTION
       "table index."
   ::= { gs2352MSTI5PortStateEntry 1 }

gs2352MSTI5PortStatePort OBJECT-TYPE
   SYNTAX      DisplayString
   MAX-ACCESS  read-only
   STATUS      current
   DESCRIPTION
       "The switch port number of the logical STP port."
   ::= { gs2352MSTI5PortStateEntry 2 }

gs2352MSTI5PortStatePortID OBJECT-TYPE
   SYNTAX      DisplayString
   MAX-ACCESS  read-only
   STATUS      current
   DESCRIPTION
       "The port id as used by the STP protocol.
        This is the priority part and the logical port index of the bridge port."
   ::= { gs2352MSTI5PortStateEntry 3 }

gs2352MSTI5PortStateRole OBJECT-TYPE
   SYNTAX      DisplayString
   MAX-ACCESS  read-only
   STATUS      current
   DESCRIPTION
       "The current STP port role."
   ::= { gs2352MSTI5PortStateEntry 4 }

gs2352MSTI5PortStateState OBJECT-TYPE
   SYNTAX      DisplayString
   MAX-ACCESS  read-only
   STATUS      current
   DESCRIPTION
       "The current STP port state."
   ::= { gs2352MSTI5PortStateEntry 5 }

gs2352MSTI5PortStatePathCost OBJECT-TYPE
   SYNTAX      Integer32(0..200000000)
   MAX-ACCESS  read-only
   STATUS      current
   DESCRIPTION
       "The current STP port path cost."
   ::= { gs2352MSTI5PortStateEntry 6 }

gs2352MSTI5PortStateEdge OBJECT-TYPE
   SYNTAX      DisplayString
   MAX-ACCESS  read-only
   STATUS      current
   DESCRIPTION
       "The current STP port Edge Flag."
   ::= { gs2352MSTI5PortStateEntry 7 }

gs2352MSTI5PortStatePoint2Point OBJECT-TYPE
   SYNTAX      DisplayString
   MAX-ACCESS  read-only
   STATUS      current
   DESCRIPTION
       "The current STP port point-to-point flag."
   ::= { gs2352MSTI5PortStateEntry 8 }

gs2352MSTI5PortStateUptime OBJECT-TYPE
   SYNTAX      DisplayString
   MAX-ACCESS  read-only
   STATUS      current
   DESCRIPTION
       "The time since the bridge port was last initialized."
   ::= { gs2352MSTI5PortStateEntry 9 }

gs2352MSTI6BridgeSTP                                                        OBJECT IDENTIFIER ::= { gs2352STPBridgeStatus 7 }

gs2352MSTI6BridgeSTPStatus                                                  OBJECT IDENTIFIER ::= { gs2352MSTI6BridgeSTP 1 }

gs2352MSTI6BridgeInstance OBJECT-TYPE
   SYNTAX       DisplayString
   MAX-ACCESS   read-only
   STATUS       current
   DESCRIPTION
       "The Bridge instance - CIST, MST1, ..."
   ::= { gs2352MSTI6BridgeSTPStatus 1 }

gs2352MSTI6BridgeID OBJECT-TYPE
   SYNTAX       DisplayString
   MAX-ACCESS   read-only
   STATUS       current
   DESCRIPTION
       "The Bridge ID of this Bridge instance."
   ::= { gs2352MSTI6BridgeSTPStatus 2 }

gs2352MSTI6RootID OBJECT-TYPE
   SYNTAX       DisplayString
   MAX-ACCESS   read-only
   STATUS       current
   DESCRIPTION
       "The Bridge ID of the currently elected root bridge."
   ::= { gs2352MSTI6BridgeSTPStatus 3 }

gs2352MSTI6RootPort OBJECT-TYPE
   SYNTAX       DisplayString
   MAX-ACCESS   read-only
   STATUS       current
   DESCRIPTION
       "The switch port currently assigned the root port role."
   ::= { gs2352MSTI6BridgeSTPStatus 4 }

gs2352MSTI6RootCost OBJECT-TYPE
   SYNTAX       Integer32(0..200000000)
   MAX-ACCESS   read-only
   STATUS       current
   DESCRIPTION
       "Root Path Cost."
   ::= { gs2352MSTI6BridgeSTPStatus 5 }

gs2352MSTI6TopologyFlag OBJECT-TYPE
   SYNTAX       DisplayString
   MAX-ACCESS   read-only
   STATUS       current
   DESCRIPTION
       "The current state of the Topology Change Flag of this Bridge instance."
   ::= { gs2352MSTI6BridgeSTPStatus 8 }

gs2352MSTI6TopologyChangeCount OBJECT-TYPE
   SYNTAX       Counter32
   MAX-ACCESS   read-only
   STATUS       current
   DESCRIPTION
       "The number of times where the topology change flag has been set."
   ::= { gs2352MSTI6BridgeSTPStatus 9 }

gs2352MSTI6TopologyChangeLast OBJECT-TYPE
   SYNTAX       DisplayString
   MAX-ACCESS   read-only
   STATUS       current
   DESCRIPTION
       "The time passed since the Topology Flag was last set."
   ::= { gs2352MSTI6BridgeSTPStatus 10 }

gs2352MSTI6PortStateTable OBJECT-TYPE
   SYNTAX      SEQUENCE OF Gs2352MSTI6PortStateEntry
   MAX-ACCESS  not-accessible
   STATUS      current
   DESCRIPTION
       " Show MSTI6 Ports and Aggregations State Configurations. "
   ::= { gs2352MSTI6BridgeSTP 2 }

gs2352MSTI6PortStateEntry OBJECT-TYPE
   SYNTAX      Gs2352MSTI6PortStateEntry
   MAX-ACCESS  not-accessible
   STATUS      current
   DESCRIPTION
       ""
   INDEX    { gs2352MSTI6PortStateIndex  }
   ::= { gs2352MSTI6PortStateTable 1 }

Gs2352MSTI6PortStateEntry ::= SEQUENCE {
   gs2352MSTI6PortStateIndex        Integer32,
   gs2352MSTI6PortStatePort         DisplayString,
   gs2352MSTI6PortStatePortID       DisplayString,
   gs2352MSTI6PortStateRole         DisplayString,
   gs2352MSTI6PortStateState        DisplayString,
   gs2352MSTI6PortStatePathCost     Integer32,
   gs2352MSTI6PortStateEdge         DisplayString,
   gs2352MSTI6PortStatePoint2Point  DisplayString,
   gs2352MSTI6PortStateUptime       DisplayString
}

gs2352MSTI6PortStateIndex OBJECT-TYPE
   SYNTAX      Integer32(1..4095)
   MAX-ACCESS  not-accessible
   STATUS      current
   DESCRIPTION
       "table index."
   ::= { gs2352MSTI6PortStateEntry 1 }

gs2352MSTI6PortStatePort OBJECT-TYPE
   SYNTAX      DisplayString
   MAX-ACCESS  read-only
   STATUS      current
   DESCRIPTION
       "The switch port number of the logical STP port."
   ::= { gs2352MSTI6PortStateEntry 2 }

gs2352MSTI6PortStatePortID OBJECT-TYPE
   SYNTAX      DisplayString
   MAX-ACCESS  read-only
   STATUS      current
   DESCRIPTION
       "The port id as used by the STP protocol.
        This is the priority part and the logical port index of the bridge port."
   ::= { gs2352MSTI6PortStateEntry 3 }

gs2352MSTI6PortStateRole OBJECT-TYPE
   SYNTAX      DisplayString
   MAX-ACCESS  read-only
   STATUS      current
   DESCRIPTION
       "The current STP port role."
   ::= { gs2352MSTI6PortStateEntry 4 }

gs2352MSTI6PortStateState OBJECT-TYPE
   SYNTAX      DisplayString
   MAX-ACCESS  read-only
   STATUS      current
   DESCRIPTION
       "The current STP port state."
   ::= { gs2352MSTI6PortStateEntry 5 }

gs2352MSTI6PortStatePathCost OBJECT-TYPE
   SYNTAX      Integer32(0..200000000)
   MAX-ACCESS  read-only
   STATUS      current
   DESCRIPTION
       "The current STP port path cost."
   ::= { gs2352MSTI6PortStateEntry 6 }

gs2352MSTI6PortStateEdge OBJECT-TYPE
   SYNTAX      DisplayString
   MAX-ACCESS  read-only
   STATUS      current
   DESCRIPTION
       "The current STP port Edge Flag."
   ::= { gs2352MSTI6PortStateEntry 7 }

gs2352MSTI6PortStatePoint2Point OBJECT-TYPE
   SYNTAX      DisplayString
   MAX-ACCESS  read-only
   STATUS      current
   DESCRIPTION
       "The current STP port point-to-point flag."
   ::= { gs2352MSTI6PortStateEntry 8 }

gs2352MSTI6PortStateUptime OBJECT-TYPE
   SYNTAX      DisplayString
   MAX-ACCESS  read-only
   STATUS      current
   DESCRIPTION
       "The time since the bridge port was last initialized."
   ::= { gs2352MSTI6PortStateEntry 9 }

gs2352MSTI7BridgeSTP                                                        OBJECT IDENTIFIER ::= { gs2352STPBridgeStatus 8 }

gs2352MSTI7BridgeSTPStatus                                                  OBJECT IDENTIFIER ::= { gs2352MSTI7BridgeSTP 1 }

gs2352MSTI7BridgeInstance OBJECT-TYPE
   SYNTAX       DisplayString
   MAX-ACCESS   read-only
   STATUS       current
   DESCRIPTION
       "The Bridge instance - CIST, MST1, ..."
   ::= { gs2352MSTI7BridgeSTPStatus 1 }

gs2352MSTI7BridgeID OBJECT-TYPE
   SYNTAX       DisplayString
   MAX-ACCESS   read-only
   STATUS       current
   DESCRIPTION
       "The Bridge ID of this Bridge instance."
   ::= { gs2352MSTI7BridgeSTPStatus 2 }

gs2352MSTI7RootID OBJECT-TYPE
   SYNTAX       DisplayString
   MAX-ACCESS   read-only
   STATUS       current
   DESCRIPTION
       "The Bridge ID of the currently elected root bridge."
   ::= { gs2352MSTI7BridgeSTPStatus 3 }

gs2352MSTI7RootPort OBJECT-TYPE
   SYNTAX       DisplayString
   MAX-ACCESS   read-only
   STATUS       current
   DESCRIPTION
       "The switch port currently assigned the root port role."
   ::= { gs2352MSTI7BridgeSTPStatus 4 }

gs2352MSTI7RootCost OBJECT-TYPE
   SYNTAX       Integer32(0..200000000)
   MAX-ACCESS   read-only
   STATUS       current
   DESCRIPTION
       "Root Path Cost."
   ::= { gs2352MSTI7BridgeSTPStatus 5 }

gs2352MSTI7TopologyFlag OBJECT-TYPE
   SYNTAX       DisplayString
   MAX-ACCESS   read-only
   STATUS       current
   DESCRIPTION
       "The current state of the Topology Change Flag of this Bridge instance."
   ::= { gs2352MSTI7BridgeSTPStatus 8 }

gs2352MSTI7TopologyChangeCount OBJECT-TYPE
   SYNTAX       Counter32
   MAX-ACCESS   read-only
   STATUS       current
   DESCRIPTION
       "The number of times where the topology change flag has been set."
   ::= { gs2352MSTI7BridgeSTPStatus 9 }

gs2352MSTI7TopologyChangeLast OBJECT-TYPE
   SYNTAX       DisplayString
   MAX-ACCESS   read-only
   STATUS       current
   DESCRIPTION
       "The time passed since the Topology Flag was last set."
   ::= { gs2352MSTI7BridgeSTPStatus 10 }

gs2352MSTI7PortStateTable OBJECT-TYPE
   SYNTAX      SEQUENCE OF Gs2352MSTI7PortStateEntry
   MAX-ACCESS  not-accessible
   STATUS      current
   DESCRIPTION
       " Show MSTI7 Ports and Aggregations State Configurations. "
   ::= { gs2352MSTI7BridgeSTP 2 }

gs2352MSTI7PortStateEntry OBJECT-TYPE
   SYNTAX      Gs2352MSTI7PortStateEntry
   MAX-ACCESS  not-accessible
   STATUS      current
   DESCRIPTION
       ""
   INDEX    { gs2352MSTI7PortStateIndex  }
   ::= { gs2352MSTI7PortStateTable 1 }

Gs2352MSTI7PortStateEntry ::= SEQUENCE {
   gs2352MSTI7PortStateIndex        Integer32,
   gs2352MSTI7PortStatePort         DisplayString,
   gs2352MSTI7PortStatePortID       DisplayString,
   gs2352MSTI7PortStateRole         DisplayString,
   gs2352MSTI7PortStateState        DisplayString,
   gs2352MSTI7PortStatePathCost     Integer32,
   gs2352MSTI7PortStateEdge         DisplayString,
   gs2352MSTI7PortStatePoint2Point  DisplayString,
   gs2352MSTI7PortStateUptime       DisplayString
}

gs2352MSTI7PortStateIndex OBJECT-TYPE
   SYNTAX      Integer32(1..4095)
   MAX-ACCESS  not-accessible
   STATUS      current
   DESCRIPTION
       "table index."
   ::= { gs2352MSTI7PortStateEntry 1 }

gs2352MSTI7PortStatePort OBJECT-TYPE
   SYNTAX      DisplayString
   MAX-ACCESS  read-only
   STATUS      current
   DESCRIPTION
       "The switch port number of the logical STP port."
   ::= { gs2352MSTI7PortStateEntry 2 }

gs2352MSTI7PortStatePortID OBJECT-TYPE
   SYNTAX      DisplayString
   MAX-ACCESS  read-only
   STATUS      current
   DESCRIPTION
       "The port id as used by the STP protocol.
        This is the priority part and the logical port index of the bridge port."
   ::= { gs2352MSTI7PortStateEntry 3 }

gs2352MSTI7PortStateRole OBJECT-TYPE
   SYNTAX      DisplayString
   MAX-ACCESS  read-only
   STATUS      current
   DESCRIPTION
       "The current STP port role."
   ::= { gs2352MSTI7PortStateEntry 4 }

gs2352MSTI7PortStateState OBJECT-TYPE
   SYNTAX      DisplayString
   MAX-ACCESS  read-only
   STATUS      current
   DESCRIPTION
       "The current STP port state."
   ::= { gs2352MSTI7PortStateEntry 5 }

gs2352MSTI7PortStatePathCost OBJECT-TYPE
   SYNTAX      Integer32(0..200000000)
   MAX-ACCESS  read-only
   STATUS      current
   DESCRIPTION
       "The current STP port path cost."
   ::= { gs2352MSTI7PortStateEntry 6 }

gs2352MSTI7PortStateEdge OBJECT-TYPE
   SYNTAX      DisplayString
   MAX-ACCESS  read-only
   STATUS      current
   DESCRIPTION
       "The current STP port Edge Flag."
   ::= { gs2352MSTI7PortStateEntry 7 }

gs2352MSTI7PortStatePoint2Point OBJECT-TYPE
   SYNTAX      DisplayString
   MAX-ACCESS  read-only
   STATUS      current
   DESCRIPTION
       "The current STP port point-to-point flag."
   ::= { gs2352MSTI7PortStateEntry 8 }

gs2352MSTI7PortStateUptime OBJECT-TYPE
   SYNTAX      DisplayString
   MAX-ACCESS  read-only
   STATUS      current
   DESCRIPTION
       "The time since the bridge port was last initialized."
   ::= { gs2352MSTI7PortStateEntry 9 }

gs2352STPPortStatusTable OBJECT-TYPE
   SYNTAX      SEQUENCE OF Gs2352STPPortStatusEntry
   MAX-ACCESS  not-accessible
   STATUS      current
   DESCRIPTION
       " Show STP Port Status."
   ::= { gs2352STP 9 }

gs2352STPPortStatusEntry OBJECT-TYPE
   SYNTAX      Gs2352STPPortStatusEntry
   MAX-ACCESS  not-accessible
   STATUS      current
   DESCRIPTION
       ""
   INDEX    { gs2352STPPortStatusPort  }
   ::= { gs2352STPPortStatusTable 1 }

Gs2352STPPortStatusEntry ::= SEQUENCE {
   gs2352STPPortStatusPort         Integer32,
   gs2352STPPortStatusCISTRole     DisplayString,
   gs2352STPPortStatusCISTState    DisplayString,
   gs2352STPPortStatusUptime       DisplayString
}

gs2352STPPortStatusPort OBJECT-TYPE
   SYNTAX      Integer32(1..4095)
   MAX-ACCESS  not-accessible
   STATUS      current
   DESCRIPTION
       " port, range : 1 - port number. "
   ::= { gs2352STPPortStatusEntry 1 }

gs2352STPPortStatusCISTRole OBJECT-TYPE
   SYNTAX      DisplayString
   MAX-ACCESS  read-only
   STATUS      current
   DESCRIPTION
       " The current STP port role of the CIST port. "
   ::= { gs2352STPPortStatusEntry 2 }

gs2352STPPortStatusCISTState OBJECT-TYPE
   SYNTAX      DisplayString
   MAX-ACCESS  read-only
   STATUS      current
   DESCRIPTION
       " The current STP port state of the CIST port. "
   ::= { gs2352STPPortStatusEntry 3 }

gs2352STPPortStatusUptime OBJECT-TYPE
   SYNTAX      DisplayString
   MAX-ACCESS  read-only
   STATUS      current
   DESCRIPTION
       " The time since the bridge port was last initialized. "
   ::= { gs2352STPPortStatusEntry 4 }

gs2352STPPortStatisticsTable OBJECT-TYPE
   SYNTAX      SEQUENCE OF Gs2352STPPortStatisticsEntry
   MAX-ACCESS  not-accessible
   STATUS      current
   DESCRIPTION
       " Show STP Port Statistics."
   ::= { gs2352STP 10 }

gs2352STPPortStatisticsEntry OBJECT-TYPE
   SYNTAX      Gs2352STPPortStatisticsEntry
   MAX-ACCESS  not-accessible
   STATUS      current
   DESCRIPTION
       ""
   INDEX    { gs2352STPStatisticsIndex  }
   ::= { gs2352STPPortStatisticsTable 1 }

Gs2352STPPortStatisticsEntry ::= SEQUENCE {
   gs2352STPStatisticsIndex            Integer32,
   gs2352STPStatisticsPort             DisplayString,
   gs2352STPStatisticsTxMSTP           Counter32,
   gs2352STPStatisticsTxRSTP           Counter32,
   gs2352STPStatisticsTxSTP            Counter32,
   gs2352STPStatisticsTxTCN            Counter32,
   gs2352STPStatisticsRxMSTP           Counter32,
   gs2352STPStatisticsRxRSTP           Counter32,
   gs2352STPStatisticsRxSTP            Counter32,
   gs2352STPStatisticsRxTCN            Counter32,
   gs2352STPStatisticsDiscardedUnknown Counter32,
   gs2352STPStatisticsDiscardedIllegal Counter32
}

gs2352STPStatisticsIndex OBJECT-TYPE
   SYNTAX      Integer32(1..4095)
   MAX-ACCESS  not-accessible
   STATUS      current
   DESCRIPTION
       "table index."
   ::= { gs2352STPPortStatisticsEntry 1 }

gs2352STPStatisticsPort OBJECT-TYPE
   SYNTAX      DisplayString
   MAX-ACCESS  not-accessible
   STATUS      current
   DESCRIPTION
       " port, range : 1 - port number. "
   ::= { gs2352STPPortStatisticsEntry 2 }

gs2352STPStatisticsTxMSTP OBJECT-TYPE
   SYNTAX      Counter32
   MAX-ACCESS  read-only
   STATUS      current
   DESCRIPTION
       " The number of MSTP Configuration BPDU's received/transmitted on the port."
   ::= { gs2352STPPortStatisticsEntry 3 }

gs2352STPStatisticsTxRSTP OBJECT-TYPE
   SYNTAX      Counter32
   MAX-ACCESS  read-only
   STATUS      current
   DESCRIPTION
       " The number of RSTP Configuration BPDU's received/transmitted on the port. "
   ::= { gs2352STPPortStatisticsEntry 4 }

gs2352STPStatisticsTxSTP OBJECT-TYPE
   SYNTAX      Counter32
   MAX-ACCESS  read-only
   STATUS      current
   DESCRIPTION
       " The number of legacy STP Configuration BPDU's received/transmitted on the port. "
   ::= { gs2352STPPortStatisticsEntry 5 }

gs2352STPStatisticsTxTCN OBJECT-TYPE
   SYNTAX      Counter32
   MAX-ACCESS  read-only
   STATUS      current
   DESCRIPTION
       " The number of Topology Change Notification BPDU's received/transmitted on the port. "
   ::= { gs2352STPPortStatisticsEntry 6 }

gs2352STPStatisticsRxMSTP OBJECT-TYPE
   SYNTAX      Counter32
   MAX-ACCESS  read-only
   STATUS      current
   DESCRIPTION
       " The number of MSTP Configuration BPDU's received/transmitted on the port."
   ::= { gs2352STPPortStatisticsEntry 7 }

gs2352STPStatisticsRxRSTP OBJECT-TYPE
   SYNTAX      Counter32
   MAX-ACCESS  read-only
   STATUS      current
   DESCRIPTION
       " The number of RSTP Configuration BPDU's received/transmitted on the port. "
   ::= { gs2352STPPortStatisticsEntry 8 }

gs2352STPStatisticsRxSTP OBJECT-TYPE
   SYNTAX      Counter32
   MAX-ACCESS  read-only
   STATUS      current
   DESCRIPTION
       " The number of legacy STP Configuration BPDU's received/transmitted on the port. "
   ::= { gs2352STPPortStatisticsEntry 9 }

gs2352STPStatisticsRxTCN OBJECT-TYPE
   SYNTAX      Counter32
   MAX-ACCESS  read-only
   STATUS      current
   DESCRIPTION
       " The number of Topology Change Notification BPDU's received/transmitted on the port. "
   ::= { gs2352STPPortStatisticsEntry 10 }

gs2352STPStatisticsDiscardedUnknown OBJECT-TYPE
   SYNTAX      Counter32
   MAX-ACCESS  read-only
   STATUS      current
   DESCRIPTION
       " The number of unknown Spanning Tree BPDU's received and discarded on the port. "
   ::= { gs2352STPPortStatisticsEntry 11 }

gs2352STPStatisticsDiscardedIllegal OBJECT-TYPE
   SYNTAX      Counter32
   MAX-ACCESS  read-only
   STATUS      current
   DESCRIPTION
       " The number of illegal Spanning Tree BPDU's received and discarded on the port. "
   ::= { gs2352STPPortStatisticsEntry 12 }


gs2352FilteringDataBase                                                  OBJECT IDENTIFIER ::= { gs2352Configuration 21 }

gs2352FilteringDataBaseConfig                                            OBJECT IDENTIFIER ::= { gs2352FilteringDataBase 1 }

gs2352FilteringDataBaseAgingTime OBJECT-TYPE
   SYNTAX      Integer32(0..1000000)
   MAX-ACCESS  read-write
   STATUS      current
   DESCRIPTION
       "Configure aging time by entering a value here in seconds.
        default: 300,
        range: 10-1000000.
        Disable automatic aging : 0."
   ::= { gs2352FilteringDataBaseConfig 1 }

gs2352FilteringDataBaseConfigTable OBJECT-TYPE
   SYNTAX      SEQUENCE OF GS2352FilteringDataBaseConfigEntry
   MAX-ACCESS  not-accessible
   STATUS      current
   DESCRIPTION
       " "
   ::= { gs2352FilteringDataBaseConfig 2 }

gs2352FilteringDataBaseConfigEntry OBJECT-TYPE
   SYNTAX      GS2352FilteringDataBaseConfigEntry
   MAX-ACCESS  not-accessible
   STATUS      current
   DESCRIPTION
       ""
   INDEX    { gs2352FilteringDataBaseConfigPort  }
   ::= { gs2352FilteringDataBaseConfigTable 1 }

GS2352FilteringDataBaseConfigEntry ::= SEQUENCE {
   gs2352FilteringDataBaseConfigPort        Integer32,
   gs2352FilteringDataBaseConfigLearning    INTEGER
}

gs2352FilteringDataBaseConfigPort OBJECT-TYPE
   SYNTAX      Integer32(1..4095)
   MAX-ACCESS  not-accessible
   STATUS      current
   DESCRIPTION
       " "
   ::= { gs2352FilteringDataBaseConfigEntry 1 }

gs2352FilteringDataBaseConfigLearning OBJECT-TYPE
   SYNTAX      INTEGER { auto(0), disable(1), secure(2) }
   MAX-ACCESS  read-write
   STATUS      current
   DESCRIPTION
       "Configure learning mode of switch ports.
        default: 0,
        0: auto,
        1: disable,
        2: secure. "
   ::= { gs2352FilteringDataBaseConfigEntry 2 }


gs2352FilteringDataBaseStaticMAC                                OBJECT IDENTIFIER ::= { gs2352FilteringDataBaseConfig 3 }

gs2352FilteringDataBaseStaticMACCreate OBJECT-TYPE
   SYNTAX       INTEGER { none(0), create(1) }
   MAX-ACCESS   read-write
   STATUS       current
   DESCRIPTION
       "default: 0
        0 : None  (read only)
        1 : Create Static MAC Table"
   ::= { gs2352FilteringDataBaseStaticMAC 1 }

gs2352FilteringDataBaseStaticMACTable OBJECT-TYPE
   SYNTAX      SEQUENCE OF GS2352FilteringDataBaseStaticMACEntry
   MAX-ACCESS  not-accessible
   STATUS      current
   DESCRIPTION
       " "
   ::= { gs2352FilteringDataBaseStaticMAC 2 }

gs2352FilteringDataBaseStaticMACEntry OBJECT-TYPE
   SYNTAX      GS2352FilteringDataBaseStaticMACEntry
   MAX-ACCESS  not-accessible
   STATUS      current
   DESCRIPTION
       ""
   INDEX    { gs2352FilteringDataBaseStaticMACIndex  }
   ::= { gs2352FilteringDataBaseStaticMACTable 1 }

GS2352FilteringDataBaseStaticMACEntry ::= SEQUENCE {
   gs2352FilteringDataBaseStaticMACIndex	    Integer32,
   gs2352FilteringDataBaseStaticMACVLANId	    Integer32,
   gs2352FilteringDataBaseStaticMACAddress      MacAddress,
   gs2352FilteringDataBaseStaticMACPortMembers  DisplayString,
   gs2352FilteringDataBaseStaticMACRowStatus	INTEGER
}

gs2352FilteringDataBaseStaticMACIndex OBJECT-TYPE
   SYNTAX      Integer32(1..4095)
   MAX-ACCESS  not-accessible
   STATUS      current
   DESCRIPTION
       " "
   ::= { gs2352FilteringDataBaseStaticMACEntry 1 }

gs2352FilteringDataBaseStaticMACVLANId OBJECT-TYPE
   SYNTAX      Integer32(1..4094)
   MAX-ACCESS  read-write
   STATUS      current
   DESCRIPTION
       " VLAN ID, range: 1 - 4094. "
   ::= { gs2352FilteringDataBaseStaticMACEntry 2 }

gs2352FilteringDataBaseStaticMACAddress OBJECT-TYPE
   SYNTAX      MacAddress
   MAX-ACCESS  read-write
   STATUS      current
   DESCRIPTION
       " MAC address, format 0a 1b 2c 3d 4e 5f "
   ::= { gs2352FilteringDataBaseStaticMACEntry 3 }

gs2352FilteringDataBaseStaticMACPortMembers OBJECT-TYPE
   SYNTAX      DisplayString
   MAX-ACCESS  read-write
   STATUS      current
   DESCRIPTION
       "To include the ports in a Static MAC Table"
   ::= { gs2352FilteringDataBaseStaticMACEntry 4 }

gs2352FilteringDataBaseStaticMACRowStatus OBJECT-TYPE
   SYNTAX      INTEGER { active(1), notInservice(2), destroy(4), undo(5) }
   MAX-ACCESS  read-write
   STATUS      current
   DESCRIPTION
       "1: active
        2: notInservice
        4: destroy
        5: undo"
   ::= { gs2352FilteringDataBaseStaticMACEntry 5 }


gs2352FilteringDataBaseDynamicMACTable OBJECT-TYPE
   SYNTAX      SEQUENCE OF GS2352FilteringDataBaseDynamicMACEntry
   MAX-ACCESS  not-accessible
   STATUS      current
   DESCRIPTION
       " "
   ::= { gs2352FilteringDataBaseConfig 4 }

gs2352FilteringDataBaseDynamicMACEntry OBJECT-TYPE
   SYNTAX      GS2352FilteringDataBaseDynamicMACEntry
   MAX-ACCESS  not-accessible
   STATUS      current
   DESCRIPTION
       ""
   INDEX    { gs2352FilteringDataBaseDynamicMACIndex  }
   ::= { gs2352FilteringDataBaseDynamicMACTable 1 }

GS2352FilteringDataBaseDynamicMACEntry ::= SEQUENCE {
   gs2352FilteringDataBaseDynamicMACIndex	    Integer32,
   gs2352FilteringDataBaseDynamicMACType	    INTEGER,
   gs2352FilteringDataBaseDynamicMACVLAN	    Integer32,
   gs2352FilteringDataBaseDynamicMACAddress     MacAddress,
   gs2352FilteringDataBaseDynamicPortMembers    DisplayString
}

gs2352FilteringDataBaseDynamicMACIndex OBJECT-TYPE
   SYNTAX      Integer32(1..4095)
   MAX-ACCESS  not-accessible
   STATUS      current
   DESCRIPTION
       " "
   ::= { gs2352FilteringDataBaseDynamicMACEntry 1 }

gs2352FilteringDataBaseDynamicMACType OBJECT-TYPE
   SYNTAX      INTEGER { dynamic(0), static(1) }
   MAX-ACCESS  read-only
   STATUS      current
   DESCRIPTION
       "Indicates whether the entry is a static or a dynamic entry."
   ::= { gs2352FilteringDataBaseDynamicMACEntry 2 }

gs2352FilteringDataBaseDynamicMACVLAN OBJECT-TYPE
   SYNTAX      Integer32(1..4094)
   MAX-ACCESS  read-only
   STATUS      current
   DESCRIPTION
       "The VLAN ID of the entry."
   ::= { gs2352FilteringDataBaseDynamicMACEntry 3 }

gs2352FilteringDataBaseDynamicMACAddress OBJECT-TYPE
   SYNTAX      MacAddress
   MAX-ACCESS  read-only
   STATUS      current
   DESCRIPTION
       "The MAC address of the entry."
   ::= { gs2352FilteringDataBaseDynamicMACEntry 4 }

gs2352FilteringDataBaseDynamicPortMembers OBJECT-TYPE
   SYNTAX      DisplayString
   MAX-ACCESS  read-only
   STATUS      current
   DESCRIPTION
       "The ports that are members of the entry."
   ::= { gs2352FilteringDataBaseDynamicMACEntry 5 }


gs2352SFlowAgent                                                  OBJECT IDENTIFIER ::= { gs2352Configuration 22 }

gs2352SFlowAgentCollector                                            OBJECT IDENTIFIER ::= { gs2352SFlowAgent 1 }

gs2352SFlowAgentReceiverMode OBJECT-TYPE
   SYNTAX      INTEGER { disable(0), enable(1) }
   MAX-ACCESS  read-write
   STATUS      current
   DESCRIPTION
       "default: 0
       0: disable
       1: enable "
   ::= { gs2352SFlowAgentCollector 1 }


gs2352LMC                                                   OBJECT IDENTIFIER ::= { gs2352Configuration 1500 }

gs2352LMCOperating OBJECT-TYPE
   SYNTAX      INTEGER { disabled(0), enabled(1), try(2) }
   MAX-ACCESS  read-write
   STATUS      current
   DESCRIPTION
       "0: disabled
        1: enabled
        2: try"
   ::= { gs2352LMC 1 }

gs2352LMCConfigViaDhcp OBJECT-TYPE
   SYNTAX      INTEGER { disabled(0), enabled(1) }
   MAX-ACCESS  read-write
   STATUS      current
   DESCRIPTION
       "0: disabled
        1: enabled"
   ::= { gs2352LMC 2 }

gs2352LMCDomain OBJECT-TYPE
   SYNTAX      DisplayString(SIZE(0..255))
   MAX-ACCESS  read-write
   STATUS      current
   DESCRIPTION
       "0: disabled
        1: enabled"
   ::= { gs2352LMC 3 }

gs2352LMCDhcpClientAutoRenew OBJECT-TYPE
   SYNTAX      INTEGER { disabled(0), enabled(1) }
   MAX-ACCESS  read-write
   STATUS      current
   DESCRIPTION
       "0: disabled
        1: enabled"
   ::= { gs2352LMC 4 }


gs2352LMCZeroTouchSupport OBJECT-TYPE
   SYNTAX      INTEGER { No(0), Yes(1) }
   MAX-ACCESS  read-only
   STATUS      current
   DESCRIPTION
       "0: No
        1: Yes"
   ::= { gs2352LMC 50 }

gs2352LMCPairingTokenPresent OBJECT-TYPE
   SYNTAX      INTEGER { No(0), Yes(1) }
   MAX-ACCESS  read-only
   STATUS      current
   DESCRIPTION
       "0: No
        1: Yes"
   ::= { gs2352LMC 51 }

gs2352LMCClientStatus OBJECT-TYPE
   SYNTAX      DisplayString
   MAX-ACCESS  read-only
   STATUS      current
   DESCRIPTION
           ""
   ::= { gs2352LMC  52 }


gs2352LMCManagementStatus OBJECT-TYPE
   SYNTAX      INTEGER {Unpaired(0), Paired(1), PairedAndClaimed(14)}
   MAX-ACCESS  read-only
   STATUS      current
   DESCRIPTION
           "0: Unpaired
            1: Paired
            14: PairedAndClaimed"
   ::= { gs2352LMC  53 }

gs2352LMCControlStatus OBJECT-TYPE
   SYNTAX      INTEGER {Disabled(2), Operating(4)}
   MAX-ACCESS  read-only
   STATUS      current
   DESCRIPTION
           "2: Disabled
            4: Operating"
   ::= { gs2352LMC  54 }

gs2352LMCMonitoringStatus OBJECT-TYPE
   SYNTAX      INTEGER {Disabled(2), Operating(4)}
   MAX-ACCESS  read-only
   STATUS      current
   DESCRIPTION
           "2: Disabled
            4: Operating"
   ::= { gs2352LMC  55 }

gs2352LMCConfigurationSource OBJECT-TYPE
   SYNTAX      DisplayString
   MAX-ACCESS  read-only
   STATUS      current
   DESCRIPTION
           ""
   ::= { gs2352LMC  56 }

gs2352LMCConfigModified OBJECT-TYPE
   SYNTAX      INTEGER { No(0), Yes(1) }
   MAX-ACCESS  read-only
   STATUS      current
   DESCRIPTION
       "0: No
        1: Yes"
   ::= { gs2352LMC 57 }

gs2352LMCDeviceID OBJECT-TYPE
   SYNTAX      DisplayString
   MAX-ACCESS  read-only
   STATUS      current
   DESCRIPTION
           ""
   ::= { gs2352LMC  58 }

gs2352LMCRoundTripTime OBJECT-TYPE
   SYNTAX      INTEGER
   MAX-ACCESS  read-only
   STATUS      current
   DESCRIPTION
           ""
   ::= { gs2352LMC  100 }
----------------------------------------------------------------------------------------------------------------------------
gs2352Security                                              OBJECT IDENTIFIER ::= { lancomGS2352 3 }

gs2352IPSourceGuard                                         OBJECT IDENTIFIER ::= { gs2352Security 1 }

gs2352IPSourceGuardConf                                     OBJECT IDENTIFIER ::= { gs2352IPSourceGuard 1 }

gs2352IPSourceGuardMode OBJECT-TYPE
   SYNTAX      INTEGER { disable(0), enable(1) }
   MAX-ACCESS  read-write
   STATUS      current
   DESCRIPTION
       " default:  0
        0: disable
        1: enable"
   ::= { gs2352IPSourceGuardConf 1 }

gs2352IPSourceGuardPortConfigTable OBJECT-TYPE
   SYNTAX      SEQUENCE OF GS2352IPSourceGuardPortConfigEntry
   MAX-ACCESS  not-accessible
   STATUS      current
   DESCRIPTION
       " "
   ::= { gs2352IPSourceGuardConf 2 }

gs2352IPSourceGuardPortConfigEntry OBJECT-TYPE
   SYNTAX      GS2352IPSourceGuardPortConfigEntry
   MAX-ACCESS  not-accessible
   STATUS      current
   DESCRIPTION
       ""
   INDEX    { gs2352IPSourceGuardPortConfigPort  }
   ::= { gs2352IPSourceGuardPortConfigTable 1 }

GS2352IPSourceGuardPortConfigEntry ::= SEQUENCE {
   gs2352IPSourceGuardPortConfigPort               Integer32,
   gs2352IPSourceGuardPortConfigMode               INTEGER,
   gs2352IPSourceGuardPortMaxDynamicClients        Integer32
}

gs2352IPSourceGuardPortConfigPort OBJECT-TYPE
   SYNTAX      Integer32(1..4095)
   MAX-ACCESS  not-accessible
   STATUS      current
   DESCRIPTION
       " "
   ::= { gs2352IPSourceGuardPortConfigEntry 1 }

gs2352IPSourceGuardPortConfigMode OBJECT-TYPE
   SYNTAX      INTEGER { disable(0), enable(1) }
   MAX-ACCESS  read-write
   STATUS      current
   DESCRIPTION
       "default: 0
       0:disable
       1:enable "
   ::= { gs2352IPSourceGuardPortConfigEntry 2 }

gs2352IPSourceGuardPortMaxDynamicClients OBJECT-TYPE
   SYNTAX      Integer32(0..2|99)
   MAX-ACCESS  read-write
   STATUS      current
   DESCRIPTION
       "default: 99
       0~2: Max Dynamic clients
       99:Unlimited "
   ::= { gs2352IPSourceGuardPortConfigEntry 3 }


gs2352IPSourceGuardStatic                                OBJECT IDENTIFIER ::= { gs2352IPSourceGuard 2 }

gs2352IPSourceGuardStaticCreate OBJECT-TYPE
   SYNTAX       INTEGER { none(0), create(1) }
   MAX-ACCESS   read-write
   STATUS       current
   DESCRIPTION
       "default: 0
        0 : None  (read only)
        1 : Create a IP Source Guard"
   ::= { gs2352IPSourceGuardStatic 1 }

gs2352IPSourceGuardStaticTable OBJECT-TYPE
   SYNTAX      SEQUENCE OF GS2352IPSourceGuardStaticEntry
   MAX-ACCESS  not-accessible
   STATUS      current
   DESCRIPTION
       " "
   ::= { gs2352IPSourceGuardStatic 2 }

gs2352IPSourceGuardStaticEntry OBJECT-TYPE
   SYNTAX      GS2352IPSourceGuardStaticEntry
   MAX-ACCESS  not-accessible
   STATUS      current
   DESCRIPTION
       ""
   INDEX    { gs2352IPSourceGuardStaticIndex  }
   ::= { gs2352IPSourceGuardStaticTable 1 }

GS2352IPSourceGuardStaticEntry ::= SEQUENCE {
   gs2352IPSourceGuardStaticIndex         Integer32,
   gs2352IPSourceGuardStaticPort          Integer32,
   gs2352IPSourceGuardStaticVLANId        Integer32,
   gs2352IPSourceGuardStaticIPAddress     IpAddress,
   gs2352IPSourceGuardStaticMACAddress    MacAddress,
   gs2352IPSourceGuardStaticRowStatus     INTEGER
}

gs2352IPSourceGuardStaticIndex OBJECT-TYPE
   SYNTAX      Integer32(1..28)
   MAX-ACCESS  not-accessible
   STATUS      current
   DESCRIPTION
       " "
   ::= { gs2352IPSourceGuardStaticEntry 1 }

gs2352IPSourceGuardStaticPort OBJECT-TYPE
   SYNTAX      Integer32(1..4095)
   MAX-ACCESS  read-write
   STATUS      current
   DESCRIPTION
       " Port, range: 1 - port number. "
   ::= { gs2352IPSourceGuardStaticEntry 2 }

gs2352IPSourceGuardStaticVLANId OBJECT-TYPE
   SYNTAX      Integer32(1..4094)
   MAX-ACCESS  read-write
   STATUS      current
   DESCRIPTION
       " VLAN ID, range: 1 - 4094. "
   ::= { gs2352IPSourceGuardStaticEntry 3 }

gs2352IPSourceGuardStaticIPAddress OBJECT-TYPE
   SYNTAX      IpAddress
   MAX-ACCESS  read-write
   STATUS      current
   DESCRIPTION
       " IP address allowed for doing IP source guard. "
   ::= { gs2352IPSourceGuardStaticEntry 4 }

gs2352IPSourceGuardStaticMACAddress OBJECT-TYPE
   SYNTAX      MacAddress
   MAX-ACCESS  read-write
   STATUS      current
   DESCRIPTION
       " Allowed Source MAC address, format 0a 1b 2c 3d 4e 5f "
   ::= { gs2352IPSourceGuardStaticEntry 5 }

gs2352IPSourceGuardStaticRowStatus OBJECT-TYPE
   SYNTAX      INTEGER { active(1), notInservice(2), edit(3), destroy(4), undo(5) }
   MAX-ACCESS  read-write
   STATUS      current
   DESCRIPTION
       "1: active
        2: notInservice
        3: edit
        4: destroy
        5: undo"
   ::= { gs2352IPSourceGuardStaticEntry 6 }

gs2352IPSourceGuardDynamicTable OBJECT-TYPE
   SYNTAX      SEQUENCE OF GS2352IPSourceGuardDynamicEntry
   MAX-ACCESS  not-accessible
   STATUS      current
   DESCRIPTION
       " "
   ::= { gs2352IPSourceGuard 3 }

gs2352IPSourceGuardDynamicEntry OBJECT-TYPE
   SYNTAX      GS2352IPSourceGuardDynamicEntry
   MAX-ACCESS  not-accessible
   STATUS      current
   DESCRIPTION
       ""
   INDEX    { gs2352IPSourceGuardDynamicIndex  }
   ::= { gs2352IPSourceGuardDynamicTable 1 }

GS2352IPSourceGuardDynamicEntry ::= SEQUENCE {
   gs2352IPSourceGuardDynamicIndex          Integer32,
   gs2352IPSourceGuardDynamicPort           Integer32,
   gs2352IPSourceGuardDynamicVLANId         Integer32,
   gs2352IPSourceGuardDynamicIPAddress      IpAddress,
   gs2352IPSourceGuardDynamicMACAddress     MacAddress
}

gs2352IPSourceGuardDynamicIndex OBJECT-TYPE
   SYNTAX      Integer32(1..4095)
   MAX-ACCESS  not-accessible
   STATUS      current
   DESCRIPTION
       " "
   ::= { gs2352IPSourceGuardDynamicEntry 1 }

gs2352IPSourceGuardDynamicPort OBJECT-TYPE
   SYNTAX      Integer32(1..10)
   MAX-ACCESS  read-only
   STATUS      current
   DESCRIPTION
       " "
   ::= { gs2352IPSourceGuardDynamicEntry 2 }

gs2352IPSourceGuardDynamicVLANId OBJECT-TYPE
   SYNTAX      Integer32(1..4094)
   MAX-ACCESS  read-only
   STATUS      current
   DESCRIPTION
       " "
   ::= { gs2352IPSourceGuardDynamicEntry 3 }

gs2352IPSourceGuardDynamicIPAddress OBJECT-TYPE
   SYNTAX      IpAddress
   MAX-ACCESS  read-only
   STATUS      current
   DESCRIPTION
       " "
   ::= { gs2352IPSourceGuardDynamicEntry 4 }

gs2352IPSourceGuardDynamicMACAddress OBJECT-TYPE
   SYNTAX      MacAddress
   MAX-ACCESS  read-only
   STATUS      current
   DESCRIPTION
       " "
   ::= { gs2352IPSourceGuardDynamicEntry 5 }

gs2352ARPInspection                                         OBJECT IDENTIFIER ::= { gs2352Security 2 }

gs2352ARPInspectionConf                                     OBJECT IDENTIFIER ::= { gs2352ARPInspection 1 }

gs2352ARPInspectionConfMode OBJECT-TYPE
   SYNTAX      INTEGER { disable(0), enable(1) }
   MAX-ACCESS  read-write
   STATUS      current
   DESCRIPTION
       "default: 0
        0: disable
        1: enable"
   ::= { gs2352ARPInspectionConf 1 }

gs2352ARPInspectionConfTable OBJECT-TYPE
   SYNTAX      SEQUENCE OF GS2352ARPInspectionConfEntry
   MAX-ACCESS  not-accessible
   STATUS      current
   DESCRIPTION
       " "
   ::= { gs2352ARPInspectionConf 2 }

gs2352ARPInspectionConfEntry OBJECT-TYPE
   SYNTAX      GS2352ARPInspectionConfEntry
   MAX-ACCESS  not-accessible
   STATUS      current
   DESCRIPTION
       ""
   INDEX    { gs2352ARPInspectionConfPortIndex  }
   ::= { gs2352ARPInspectionConfTable 1 }

GS2352ARPInspectionConfEntry ::= SEQUENCE {
   gs2352ARPInspectionConfPortIndex	Integer32,
   gs2352ARPInspectionConfPortMode	INTEGER
}

gs2352ARPInspectionConfPortIndex OBJECT-TYPE
   SYNTAX      Integer32(1..4095)
   MAX-ACCESS  not-accessible
   STATUS      current
   DESCRIPTION
       " "
   ::= { gs2352ARPInspectionConfEntry 1 }

gs2352ARPInspectionConfPortMode OBJECT-TYPE
   SYNTAX      INTEGER { disable(0), enable(1) }
   MAX-ACCESS  read-write
   STATUS      current
   DESCRIPTION
       "default: 0
        0: disable
        1: enable"
   ::= { gs2352ARPInspectionConfEntry 2 }


gs2352ARPInspectionStatic                                OBJECT IDENTIFIER ::= { gs2352ARPInspection 2 }

gs2352ARPInspectionStaticCreate OBJECT-TYPE
   SYNTAX      INTEGER { none(0), create(1) }
   MAX-ACCESS  read-write
   STATUS      current
   DESCRIPTION
       "default: 0
        0: none
        1: create"
   ::= { gs2352ARPInspectionStatic 1 }

gs2352ARPInspectionStaticTable OBJECT-TYPE
   SYNTAX      SEQUENCE OF GS2352ARPInspectionStaticEntry
   MAX-ACCESS  not-accessible
   STATUS      current
   DESCRIPTION
       " "
   ::= { gs2352ARPInspectionStatic 2 }

gs2352ARPInspectionStaticEntry OBJECT-TYPE
   SYNTAX      GS2352ARPInspectionStaticEntry
   MAX-ACCESS  not-accessible
   STATUS      current
   DESCRIPTION
       ""
   INDEX    { gs2352ARPInspectionStaticIndex  }
   ::= { gs2352ARPInspectionStaticTable 1 }

GS2352ARPInspectionStaticEntry ::= SEQUENCE {
   gs2352ARPInspectionStaticIndex       Integer32,
   gs2352ARPInspectionStaticPort        Integer32,
   gs2352ARPInspectionStaticVLANId      Integer32,
   gs2352ARPInspectionStaticIPAddress   IpAddress,
   gs2352ARPInspectionStaticMACAddress  MacAddress,
   gs2352ARPInspectionStaticRowStatus   INTEGER
}

gs2352ARPInspectionStaticIndex OBJECT-TYPE
   SYNTAX      Integer32(1..4095)
   MAX-ACCESS  not-accessible
   STATUS      current
   DESCRIPTION
       ""
   ::= { gs2352ARPInspectionStaticEntry 1 }

gs2352ARPInspectionStaticPort OBJECT-TYPE
   SYNTAX      Integer32(1..4095)
   MAX-ACCESS  read-write
   STATUS      current
   DESCRIPTION
       " Port, range: 1 - port number. "
   ::= { gs2352ARPInspectionStaticEntry 2 }

gs2352ARPInspectionStaticVLANId OBJECT-TYPE
   SYNTAX      Integer32(1..4094)
   MAX-ACCESS  read-write
   STATUS      current
   DESCRIPTION
       " VLAN ID, range: 1 - 4094. "
   ::= { gs2352ARPInspectionStaticEntry 3 }

gs2352ARPInspectionStaticIPAddress OBJECT-TYPE
   SYNTAX      IpAddress
   MAX-ACCESS  read-write
   STATUS      current
   DESCRIPTION
       " IP address allowed for doing ARP request. "
   ::= { gs2352ARPInspectionStaticEntry 4 }

gs2352ARPInspectionStaticMACAddress OBJECT-TYPE
   SYNTAX      MacAddress
   MAX-ACCESS  read-write
   STATUS      current
   DESCRIPTION
       " Allowed Source MAC address in ARP request packets, format 0a 1b 2c 3d 4e 5f "
   ::= { gs2352ARPInspectionStaticEntry 5 }

gs2352ARPInspectionStaticRowStatus OBJECT-TYPE
   SYNTAX     INTEGER { active(1), notInservice(2), edit(3), destroy(4), undo(5) }
   MAX-ACCESS  read-write
   STATUS      current
   DESCRIPTION
       "1: active
        2: notInservice
        3: edit
        4: destroy
        5: undo"
   ::= { gs2352ARPInspectionStaticEntry 6 }

gs2352ARPInspectionDynamicTable OBJECT-TYPE
   SYNTAX      SEQUENCE OF GS2352ARPInspectionDynamicEntry
   MAX-ACCESS  not-accessible
   STATUS      current
   DESCRIPTION
       " "
   ::= { gs2352ARPInspection 3 }

gs2352ARPInspectionDynamicEntry OBJECT-TYPE
   SYNTAX      GS2352ARPInspectionDynamicEntry
   MAX-ACCESS  not-accessible
   STATUS      current
   DESCRIPTION
       ""
   INDEX    { gs2352ARPInspectionDynamicIndex  }
   ::= { gs2352ARPInspectionDynamicTable 1 }

GS2352ARPInspectionDynamicEntry ::= SEQUENCE {
   gs2352ARPInspectionDynamicIndex          Integer32,
   gs2352ARPInspectionDynamicPort           Integer32,
   gs2352ARPInspectionDynamicVLANId         Integer32,
   gs2352ARPInspectionDynamicIPAddress      IpAddress,
   gs2352ARPInspectionDynamicMACAddress     MacAddress
}

gs2352ARPInspectionDynamicIndex OBJECT-TYPE
   SYNTAX      Integer32(1..4095)
   MAX-ACCESS  not-accessible
   STATUS      current
   DESCRIPTION
       " "
   ::= { gs2352ARPInspectionDynamicEntry 1 }

gs2352ARPInspectionDynamicPort OBJECT-TYPE
   SYNTAX      Integer32(1..4095)
   MAX-ACCESS  read-only
   STATUS      current
   DESCRIPTION
       ""
   ::= { gs2352ARPInspectionDynamicEntry 2 }

gs2352ARPInspectionDynamicVLANId OBJECT-TYPE
   SYNTAX      Integer32(1..4094)
   MAX-ACCESS  read-only
   STATUS      current
   DESCRIPTION
       ""
   ::= { gs2352ARPInspectionDynamicEntry 3 }

gs2352ARPInspectionDynamicIPAddress OBJECT-TYPE
   SYNTAX      IpAddress
   MAX-ACCESS  read-only
   STATUS      current
   DESCRIPTION
       ""
   ::= { gs2352ARPInspectionDynamicEntry 4 }

gs2352ARPInspectionDynamicMACAddress OBJECT-TYPE
   SYNTAX      MacAddress
   MAX-ACCESS  read-only
   STATUS      current
   DESCRIPTION
       ""
   ::= { gs2352ARPInspectionDynamicEntry 5 }

gs2352ARPStaticGatewayCtrl	                                OBJECT IDENTIFIER ::= { gs2352ARPInspection 6 }

gs2352ARPStaticGatewayCtrlSystemConf                                      OBJECT IDENTIFIER ::= { gs2352ARPStaticGatewayCtrl 1 }

gs2352ARPStaticGatewayCtrlMode OBJECT-TYPE
   SYNTAX      INTEGER { disable(0), enable(1) }
   MAX-ACCESS  read-write
   STATUS      current
   DESCRIPTION
       "default: 0
       0: disable
       1: enable "
   ::= { gs2352ARPStaticGatewayCtrlSystemConf 1 }

gs2352ARPStaticGatewayCtrlCreate OBJECT-TYPE
   SYNTAX      INTEGER { none(0), create(1) }
   MAX-ACCESS  read-write
   STATUS      current
   DESCRIPTION
       "default: 0
        0: none
        1: create"
   ::= { gs2352ARPStaticGatewayCtrl 2 }

gs2352ARPStaticGatewayCtrlTable OBJECT-TYPE
   SYNTAX      SEQUENCE OF GS2352ARPStaticGatewayCtrlEntry
   MAX-ACCESS  not-accessible
   STATUS      current
   DESCRIPTION
       " "
   ::= { gs2352ARPStaticGatewayCtrl 3 }

gs2352ARPStaticGatewayCtrlEntry OBJECT-TYPE
   SYNTAX      GS2352ARPStaticGatewayCtrlEntry
   MAX-ACCESS  not-accessible
   STATUS      current
   DESCRIPTION
       ""
   INDEX    { gs2352ARPStaticGatewayCtrlIndex  }
   ::= { gs2352ARPStaticGatewayCtrlTable 1 }

GS2352ARPStaticGatewayCtrlEntry ::= SEQUENCE {
   gs2352ARPStaticGatewayCtrlIndex       Integer32,
   gs2352ARPStaticGatewayCtrlIPAddress   IpAddress,
   gs2352ARPStaticGatewayCtrlMACAddress  MacAddress,
   gs2352ARPStaticGatewayCtrlPort        Integer32,
   gs2352ARPStaticGatewayCtrlAction      INTEGER,
   gs2352ARPStaticGatewayCtrlState       DisplayString,
   gs2352ARPStaticGatewayCtrlReOpen      INTEGER,
   gs2352ARPStaticGatewayCtrlRowStatus   INTEGER
}

gs2352ARPStaticGatewayCtrlIndex OBJECT-TYPE
   SYNTAX      Integer32(1..4)
   MAX-ACCESS  not-accessible
   STATUS      current
   DESCRIPTION
       ""
   ::= { gs2352ARPStaticGatewayCtrlEntry 1 }

gs2352ARPStaticGatewayCtrlIPAddress OBJECT-TYPE
   SYNTAX      IpAddress
   MAX-ACCESS  read-write
   STATUS      current
   DESCRIPTION
       " Source IP address. "
   ::= { gs2352ARPStaticGatewayCtrlEntry 2 }

gs2352ARPStaticGatewayCtrlMACAddress OBJECT-TYPE
   SYNTAX      MacAddress
   MAX-ACCESS  read-write
   STATUS      current
   DESCRIPTION
       " Source MAC address , format 0a 1b 2c 3d 4e 5f "
   ::= { gs2352ARPStaticGatewayCtrlEntry 3 }

gs2352ARPStaticGatewayCtrlPort OBJECT-TYPE
   SYNTAX      Integer32(1..4095)
   MAX-ACCESS  read-write
   STATUS      current
   DESCRIPTION
       " Port, range: 1 - port number. "
   ::= { gs2352ARPStaticGatewayCtrlEntry 4 }

gs2352ARPStaticGatewayCtrlAction OBJECT-TYPE
   SYNTAX      INTEGER {none(0),trap(1),dropAndTrap(2), shutdown(3), trapAndShutdown(4) }
   MAX-ACCESS  read-write
   STATUS      current
   DESCRIPTION
       "default: 0
       0: none
       1: trap
       2: drop&trap
       3: shutdown
       4: trap&shutdown"
   ::= { gs2352ARPStaticGatewayCtrlEntry 5 }

gs2352ARPStaticGatewayCtrlState OBJECT-TYPE
   SYNTAX      DisplayString
   MAX-ACCESS  read-only
   STATUS      current
   DESCRIPTION
       ""
   ::= { gs2352ARPStaticGatewayCtrlEntry 6 }

gs2352ARPStaticGatewayCtrlReOpen OBJECT-TYPE
   SYNTAX      INTEGER { none(0), reopen(1) }
   MAX-ACCESS  read-write
   STATUS      current
   DESCRIPTION
       "default: 0
       0: none
       1: reopen"
   ::= { gs2352ARPStaticGatewayCtrlEntry 7 }

gs2352ARPStaticGatewayCtrlRowStatus OBJECT-TYPE
   SYNTAX      INTEGER { active(1), notInservice(2), edit(3), destroy(4), undo(5) }
   MAX-ACCESS  read-write
   STATUS      current
   DESCRIPTION
       "1: active
        2: notInservice
        3: edit
        4: destroy
        5: undo"
   ::= { gs2352ARPStaticGatewayCtrlEntry 8 }

gs2352ARPSpoofingPrevention	                                OBJECT IDENTIFIER ::= { gs2352ARPInspection 7 }

gs2352ARPSpoofingPreventionSystemConf                                      OBJECT IDENTIFIER ::= { gs2352ARPSpoofingPrevention 1 }

gs2352ARPSpoofingPreventionMode OBJECT-TYPE
   SYNTAX      INTEGER { disable(0), enable(1) }
   MAX-ACCESS  read-write
   STATUS      current
   DESCRIPTION
       "default: 0
       0: disable
       1: enable "
   ::= { gs2352ARPSpoofingPreventionSystemConf 1 }

gs2352ARPSpoofingPreventionTable OBJECT-TYPE
   SYNTAX      SEQUENCE OF GS2352ARPSpoofingPreventionEntry
   MAX-ACCESS  not-accessible
   STATUS      current
   DESCRIPTION
       " "
   ::= { gs2352ARPSpoofingPrevention 2 }

gs2352ARPSpoofingPreventionEntry OBJECT-TYPE
   SYNTAX      GS2352ARPSpoofingPreventionEntry
   MAX-ACCESS  not-accessible
   STATUS      current
   DESCRIPTION
       ""
   INDEX    { gs2352ARPSpoofingPreventionPort  }
   ::= { gs2352ARPSpoofingPreventionTable 1 }

GS2352ARPSpoofingPreventionEntry ::= SEQUENCE {
   gs2352ARPSpoofingPreventionPort           Integer32,
   gs2352ARPSpoofingPreventionPortMode       INTEGER,
   gs2352ARPSpoofingPreventionPortLimit      Integer32,
   gs2352ARPSpoofingPreventionPortAction     INTEGER,
   gs2352ARPSpoofingPreventionPortState      DisplayString,
   gs2352ARPSpoofingPreventionPortReOpen     INTEGER
}

gs2352ARPSpoofingPreventionPort OBJECT-TYPE
   SYNTAX      Integer32(1..4095)
   MAX-ACCESS  not-accessible
   STATUS      current
   DESCRIPTION
       " "
   ::= { gs2352ARPSpoofingPreventionEntry 1 }

gs2352ARPSpoofingPreventionPortMode OBJECT-TYPE
   SYNTAX      INTEGER { disable(0), enable(1) }
   MAX-ACCESS  read-write
   STATUS      current
   DESCRIPTION
       "default: 0
       0: disable
       1: enable"
   ::= { gs2352ARPSpoofingPreventionEntry 2 }

gs2352ARPSpoofingPreventionPortLimit OBJECT-TYPE
   SYNTAX      Integer32(1..100)
   MAX-ACCESS  read-write
   STATUS      current
   DESCRIPTION
       "default: 1, range: 1-100"
   ::= { gs2352ARPSpoofingPreventionEntry 3 }

gs2352ARPSpoofingPreventionPortAction OBJECT-TYPE
   SYNTAX      INTEGER { none(0), trap(1), dropAndTrap(2), shutdown(3), trapAndShutdown(4) }
   MAX-ACCESS  read-write
   STATUS      current
   DESCRIPTION
       "default: 0
       0: none
       1: trap
       2: drop&trap
       3: shutdown
       4: trap&shutdown"
   ::= { gs2352ARPSpoofingPreventionEntry 4 }

gs2352ARPSpoofingPreventionPortState OBJECT-TYPE
   SYNTAX      DisplayString
   MAX-ACCESS  read-only
   STATUS      current
   DESCRIPTION
       ""
   ::= { gs2352ARPSpoofingPreventionEntry 5 }

gs2352ARPSpoofingPreventionPortReOpen OBJECT-TYPE
   SYNTAX      INTEGER { none(0), reopen(1) }
   MAX-ACCESS  read-write
   STATUS      current
   DESCRIPTION
       "default: 0
       0: none
       1: reopen"
   ::= { gs2352ARPSpoofingPreventionEntry 6 }

gs2352ARPIPDoSPrevention	                                OBJECT IDENTIFIER ::= { gs2352ARPInspection 8 }

gs2352ARPIPDoSPreventionTCPMode OBJECT-TYPE
   SYNTAX      INTEGER { disable(0), enable(1) }
   MAX-ACCESS  read-write
   STATUS      current
   DESCRIPTION
       "default: 0
       0: disable
       1: enable "
   ::= { gs2352ARPIPDoSPrevention 1 }

gs2352ARPIPDoSPreventionUDPMode OBJECT-TYPE
   SYNTAX      INTEGER { disable(0), enable(1) }
   MAX-ACCESS  read-write
   STATUS      current
   DESCRIPTION
       "default: 0
       0: disable
       1: enable "
   ::= { gs2352ARPIPDoSPrevention 2 }

gs2352ARPIPDoSPreventionICMPMode OBJECT-TYPE
   SYNTAX      INTEGER { disable(0), enable(1) }
   MAX-ACCESS  read-write
   STATUS      current
   DESCRIPTION
       "default: 0
       0: disable
       1: enable "
   ::= { gs2352ARPIPDoSPrevention 3 }

gs2352ARPIPDoSPreventionServerPort1 OBJECT-TYPE
   SYNTAX      Integer32(0..4094)
   MAX-ACCESS  read-write
   STATUS      current
   DESCRIPTION
       " Port, range: 0 - port number. 0: none. "
   ::= { gs2352ARPIPDoSPrevention 4 }

gs2352ARPIPDoSPreventionServerPort2 OBJECT-TYPE
   SYNTAX      Integer32(0..4094)
   MAX-ACCESS  read-write
   STATUS      current
   DESCRIPTION
       " Port, range: 0 - port number. 0: none. "
   ::= { gs2352ARPIPDoSPrevention 5 }

gs2352ARPIPDoSPreventionServerPort3 OBJECT-TYPE
   SYNTAX      Integer32(0..4094)
   MAX-ACCESS  read-write
   STATUS      current
   DESCRIPTION
       " Port, range: 0 - port number. 0: none. "
   ::= { gs2352ARPIPDoSPrevention 6 }

gs2352ARPIPDoSPreventionServerPort4 OBJECT-TYPE
   SYNTAX      Integer32(0..4094)
   MAX-ACCESS  read-write
   STATUS      current
   DESCRIPTION
       " Port, range: 0 - port number. 0: none. "
   ::= { gs2352ARPIPDoSPrevention 7 }

gs2352DHCPSnooping                                          OBJECT IDENTIFIER ::= { gs2352Security 3 }

gs2352DHCPSnoopingConf                                          OBJECT IDENTIFIER ::= { gs2352DHCPSnooping 1 }

gs2352DHCPSnoopingMode OBJECT-TYPE
   SYNTAX      INTEGER { disable(0), enable(1) }
   MAX-ACCESS  read-write
   STATUS      current
   DESCRIPTION
       "default: 0
       0: disable
       1: enable"
   ::= { gs2352DHCPSnoopingConf 1 }

gs2352DHCPSnoopingPortModeConfigurationTable OBJECT-TYPE
   SYNTAX      SEQUENCE OF GS2352DHCPSnoopingPortModeConfigurationEntry
   MAX-ACCESS  not-accessible
   STATUS      current
   DESCRIPTION
       " "
   ::= { gs2352DHCPSnoopingConf 2 }

gs2352DHCPSnoopingPortModeConfigurationEntry OBJECT-TYPE
   SYNTAX      GS2352DHCPSnoopingPortModeConfigurationEntry
   MAX-ACCESS  not-accessible
   STATUS      current
   DESCRIPTION
       ""
   INDEX    { gs2352DHCPSnoopingPortModeConfigurationPort  }
   ::= { gs2352DHCPSnoopingPortModeConfigurationTable 1 }

GS2352DHCPSnoopingPortModeConfigurationEntry ::= SEQUENCE {
   gs2352DHCPSnoopingPortModeConfigurationPort	Integer32,
   gs2352DHCPSnoopingPortModeConfigurationMode	INTEGER
}

gs2352DHCPSnoopingPortModeConfigurationPort OBJECT-TYPE
   SYNTAX      Integer32(1..4095)
   MAX-ACCESS  not-accessible
   STATUS      current
   DESCRIPTION
       " "
   ::= { gs2352DHCPSnoopingPortModeConfigurationEntry 1 }

gs2352DHCPSnoopingPortModeConfigurationMode OBJECT-TYPE
   SYNTAX      INTEGER { trust(0), untrust(1) }
   MAX-ACCESS  read-write
   STATUS      current
   DESCRIPTION
       "default: 1
       0: trust port mode
       1: untrust port mode"
   ::= { gs2352DHCPSnoopingPortModeConfigurationEntry 2 }

gs2352DHCPSnoopingStatisticsTable OBJECT-TYPE
   SYNTAX      SEQUENCE OF GS2352DHCPSnoopingStatisticsEntry
   MAX-ACCESS  not-accessible
   STATUS      current
   DESCRIPTION
       " "
   ::= { gs2352DHCPSnooping 2 }

gs2352DHCPSnoopingStatisticsEntry OBJECT-TYPE
   SYNTAX      GS2352DHCPSnoopingStatisticsEntry
   MAX-ACCESS  not-accessible
   STATUS      current
   DESCRIPTION
       ""
   INDEX    { gs2352DHCPSnoopingStatisticsPort  }
   ::= { gs2352DHCPSnoopingStatisticsTable 1 }

GS2352DHCPSnoopingStatisticsEntry ::= SEQUENCE {
   gs2352DHCPSnoopingStatisticsPort         Integer32,
   gs2352DHCPSnoopingStatisticsClear        INTEGER,
   gs2352DHCPSnoopingRxDiscover             Counter32,
   gs2352DHCPSnoopingRxOffer                Counter32,
   gs2352DHCPSnoopingRxRequest              Counter32,
   gs2352DHCPSnoopingRxDecline              Counter32,
   gs2352DHCPSnoopingRxACK                  Counter32,
   gs2352DHCPSnoopingRxNAK                  Counter32,
   gs2352DHCPSnoopingRxRelease              Counter32,
   gs2352DHCPSnoopingRxInform               Counter32,
   gs2352DHCPSnoopingRxLeaseQuery           Counter32,
   gs2352DHCPSnoopingRxLeaseUnassigned      Counter32,
   gs2352DHCPSnoopingRxLeaseUnknown         Counter32,
   gs2352DHCPSnoopingRxLeaseActive          Counter32,
   gs2352DHCPSnoopingTxDiscover             Counter32,
   gs2352DHCPSnoopingTxOffer                Counter32,
   gs2352DHCPSnoopingTxRequest              Counter32,
   gs2352DHCPSnoopingTxDecline              Counter32,
   gs2352DHCPSnoopingTxACK                  Counter32,
   gs2352DHCPSnoopingTxNAK                  Counter32,
   gs2352DHCPSnoopingTxRelease              Counter32,
   gs2352DHCPSnoopingTxInform               Counter32,
   gs2352DHCPSnoopingTxLeaseQuery           Counter32,
   gs2352DHCPSnoopingTxLeaseUnassigned      Counter32,
   gs2352DHCPSnoopingTxLeaseUnknown         Counter32,
   gs2352DHCPSnoopingTxLeaseActive          Counter32
}

gs2352DHCPSnoopingStatisticsPort OBJECT-TYPE
   SYNTAX      Integer32(1..4095)
   MAX-ACCESS  not-accessible
   STATUS      current
   DESCRIPTION
       " "
   ::= { gs2352DHCPSnoopingStatisticsEntry 1 }

gs2352DHCPSnoopingStatisticsClear OBJECT-TYPE
   SYNTAX      INTEGER { none(0), clear(1) }
   MAX-ACCESS  read-write
   STATUS      current
   DESCRIPTION
       "default: 0
       0: none
       1: clear"
   ::= { gs2352DHCPSnoopingStatisticsEntry 2 }

gs2352DHCPSnoopingRxDiscover OBJECT-TYPE
   SYNTAX      Counter32
   MAX-ACCESS  read-only
   STATUS      current
   DESCRIPTION
       " "
   ::= { gs2352DHCPSnoopingStatisticsEntry 3 }

gs2352DHCPSnoopingRxOffer OBJECT-TYPE
   SYNTAX      Counter32
   MAX-ACCESS  read-only
   STATUS      current
   DESCRIPTION
       " "
   ::= { gs2352DHCPSnoopingStatisticsEntry 4 }

gs2352DHCPSnoopingRxRequest OBJECT-TYPE
   SYNTAX      Counter32
   MAX-ACCESS  read-only
   STATUS      current
   DESCRIPTION
       " "
   ::= { gs2352DHCPSnoopingStatisticsEntry 5 }

gs2352DHCPSnoopingRxDecline OBJECT-TYPE
   SYNTAX      Counter32
   MAX-ACCESS  read-only
   STATUS      current
   DESCRIPTION
       " "
   ::= { gs2352DHCPSnoopingStatisticsEntry 6 }

gs2352DHCPSnoopingRxACK OBJECT-TYPE
   SYNTAX      Counter32
   MAX-ACCESS  read-only
   STATUS      current
   DESCRIPTION
       " "
   ::= { gs2352DHCPSnoopingStatisticsEntry 7 }

gs2352DHCPSnoopingRxNAK OBJECT-TYPE
   SYNTAX      Counter32
   MAX-ACCESS  read-only
   STATUS      current
   DESCRIPTION
       " "
   ::= { gs2352DHCPSnoopingStatisticsEntry 8 }

gs2352DHCPSnoopingRxRelease OBJECT-TYPE
   SYNTAX      Counter32
   MAX-ACCESS  read-only
   STATUS      current
   DESCRIPTION
       " "
   ::= { gs2352DHCPSnoopingStatisticsEntry 9 }

gs2352DHCPSnoopingRxInform OBJECT-TYPE
   SYNTAX      Counter32
   MAX-ACCESS  read-only
   STATUS      current
   DESCRIPTION
       " "
   ::= { gs2352DHCPSnoopingStatisticsEntry 10 }

gs2352DHCPSnoopingRxLeaseQuery OBJECT-TYPE
   SYNTAX      Counter32
   MAX-ACCESS  read-only
   STATUS      current
   DESCRIPTION
       " "
   ::= { gs2352DHCPSnoopingStatisticsEntry 11 }

gs2352DHCPSnoopingRxLeaseUnassigned OBJECT-TYPE
   SYNTAX      Counter32
   MAX-ACCESS  read-only
   STATUS      current
   DESCRIPTION
       " "
   ::= { gs2352DHCPSnoopingStatisticsEntry 12 }

gs2352DHCPSnoopingRxLeaseUnknown OBJECT-TYPE
   SYNTAX      Counter32
   MAX-ACCESS  read-only
   STATUS      current
   DESCRIPTION
       " "
   ::= { gs2352DHCPSnoopingStatisticsEntry 13 }

gs2352DHCPSnoopingRxLeaseActive OBJECT-TYPE
   SYNTAX      Counter32
   MAX-ACCESS  read-only
   STATUS      current
   DESCRIPTION
       " "
   ::= { gs2352DHCPSnoopingStatisticsEntry 14 }

gs2352DHCPSnoopingTxDiscover OBJECT-TYPE
   SYNTAX      Counter32
   MAX-ACCESS  read-only
   STATUS      current
   DESCRIPTION
       " "
   ::= { gs2352DHCPSnoopingStatisticsEntry 15 }

gs2352DHCPSnoopingTxOffer OBJECT-TYPE
   SYNTAX      Counter32
   MAX-ACCESS  read-only
   STATUS      current
   DESCRIPTION
       " "
   ::= { gs2352DHCPSnoopingStatisticsEntry 16 }

gs2352DHCPSnoopingTxRequest OBJECT-TYPE
   SYNTAX      Counter32
   MAX-ACCESS  read-only
   STATUS      current
   DESCRIPTION
       " "
   ::= { gs2352DHCPSnoopingStatisticsEntry 17 }

gs2352DHCPSnoopingTxDecline OBJECT-TYPE
   SYNTAX      Counter32
   MAX-ACCESS  read-only
   STATUS      current
   DESCRIPTION
       " "
   ::= { gs2352DHCPSnoopingStatisticsEntry 18 }

gs2352DHCPSnoopingTxACK OBJECT-TYPE
   SYNTAX      Counter32
   MAX-ACCESS  read-only
   STATUS      current
   DESCRIPTION
       " "
   ::= { gs2352DHCPSnoopingStatisticsEntry 19 }

gs2352DHCPSnoopingTxNAK OBJECT-TYPE
   SYNTAX      Counter32
   MAX-ACCESS  read-only
   STATUS      current
   DESCRIPTION
       " "
   ::= { gs2352DHCPSnoopingStatisticsEntry 20 }

gs2352DHCPSnoopingTxRelease OBJECT-TYPE
   SYNTAX      Counter32
   MAX-ACCESS  read-only
   STATUS      current
   DESCRIPTION
       " "
   ::= { gs2352DHCPSnoopingStatisticsEntry 21 }

gs2352DHCPSnoopingTxInform OBJECT-TYPE
   SYNTAX      Counter32
   MAX-ACCESS  read-only
   STATUS      current
   DESCRIPTION
       " "
   ::= { gs2352DHCPSnoopingStatisticsEntry 22 }

gs2352DHCPSnoopingTxLeaseQuery OBJECT-TYPE
   SYNTAX      Counter32
   MAX-ACCESS  read-only
   STATUS      current
   DESCRIPTION
       " "
   ::= { gs2352DHCPSnoopingStatisticsEntry 23 }

gs2352DHCPSnoopingTxLeaseUnassigned OBJECT-TYPE
   SYNTAX      Counter32
   MAX-ACCESS  read-only
   STATUS      current
   DESCRIPTION
       " "
   ::= { gs2352DHCPSnoopingStatisticsEntry 24 }

gs2352DHCPSnoopingTxLeaseUnknown OBJECT-TYPE
   SYNTAX      Counter32
   MAX-ACCESS  read-only
   STATUS      current
   DESCRIPTION
       " "
   ::= { gs2352DHCPSnoopingStatisticsEntry 25 }

gs2352DHCPSnoopingTxLeaseActive OBJECT-TYPE
   SYNTAX      Counter32
   MAX-ACCESS  read-only
   STATUS      current
   DESCRIPTION
       " "
   ::= { gs2352DHCPSnoopingStatisticsEntry 26 }


gs2352DHCPRelay                                             OBJECT IDENTIFIER ::= { gs2352Security 4 }

gs2352DHCPRelayConfiguration                                         OBJECT IDENTIFIER ::= { gs2352DHCPRelay 1 }

gs2352DHCPRelayMode OBJECT-TYPE
   SYNTAX      INTEGER { disable(0), enable(1) }
   MAX-ACCESS  read-write
   STATUS      current
   DESCRIPTION
       "default: 0
       0: disable
       1: enable
       We need at least one server"
   ::= { gs2352DHCPRelayConfiguration 1 }

gs2352DHCPRelayServer OBJECT-TYPE
   SYNTAX      IpAddress
   MAX-ACCESS  read-write
   STATUS      current
   DESCRIPTION
       " "
   ::= { gs2352DHCPRelayConfiguration 2 }

gs2352DHCPRelayInformationMode OBJECT-TYPE
   SYNTAX      INTEGER { disable(0), enable(1) }
   MAX-ACCESS  read-write
   STATUS      current
   DESCRIPTION
       "default: 0
       0: disable
       1: enable "
   ::= { gs2352DHCPRelayConfiguration 3 }

gs2352DHCPRelayInformationPolicy OBJECT-TYPE
   SYNTAX      INTEGER { replace(0), keep(1), drop(2) }
   MAX-ACCESS  read-write
   STATUS      current
   DESCRIPTION
       "default: 0
       0: replace
       1: keep
       2: drop "
   ::= { gs2352DHCPRelayConfiguration 4 }

gs2352DHCPRelayInformationCustom OBJECT-TYPE
   SYNTAX      DisplayString(SIZE(0..32))
   MAX-ACCESS  read-write
   STATUS      current
   DESCRIPTION
       "DHCP Option 82 Circuit ID custom information"
   ::= { gs2352DHCPRelayConfiguration 1500 }

gs2352DHCPRelayConfigurationGateways                                          OBJECT IDENTIFIER ::= { gs2352DHCPRelayConfiguration 5 }

gs2352DHCPRelayConfigurationGatewaysCreate OBJECT-TYPE
   SYNTAX       INTEGER { none(0), create(1) }
   MAX-ACCESS   read-write
   STATUS       current
   DESCRIPTION
       "default: 0
        0 : None  (read only)
        1 : Create entry"
   ::= { gs2352DHCPRelayConfigurationGateways 1 }

gs2352DHCPRelayConfigurationGatewaysTable OBJECT-TYPE
   SYNTAX      SEQUENCE OF Gs2352DHCPRelayConfigurationGatewaysEntry
   MAX-ACCESS  not-accessible
   STATUS      current
   DESCRIPTION
       " Create DHCP Relay Gateway IP address entry."
   ::= { gs2352DHCPRelayConfigurationGateways 2 }

gs2352DHCPRelayConfigurationGatewaysEntry OBJECT-TYPE
   SYNTAX      Gs2352DHCPRelayConfigurationGatewaysEntry
   MAX-ACCESS  not-accessible
   STATUS      current
   DESCRIPTION
       ""
   INDEX    { gs2352DHCPRelayConfigurationGatewaysIndex  }
   ::= { gs2352DHCPRelayConfigurationGatewaysTable 1 }

Gs2352DHCPRelayConfigurationGatewaysEntry ::= SEQUENCE {
   gs2352DHCPRelayConfigurationGatewaysIndex           Integer32,
   gs2352DHCPRelayConfigurationGatewaysVLANId          Integer32,
   gs2352DHCPRelayConfigurationGatewaysIP              IpAddress,
   gs2352DHCPRelayConfigurationGatewaysRowStatus       INTEGER
}

gs2352DHCPRelayConfigurationGatewaysIndex OBJECT-TYPE
   SYNTAX      Integer32(1..6)
   MAX-ACCESS  not-accessible
   STATUS      current
   DESCRIPTION
       " "
   ::= { gs2352DHCPRelayConfigurationGatewaysEntry 1 }

gs2352DHCPRelayConfigurationGatewaysVLANId OBJECT-TYPE
   SYNTAX      Integer32(1..4094)
   MAX-ACCESS  read-write
   STATUS      current
   DESCRIPTION
       " VLAN ID "
   ::= { gs2352DHCPRelayConfigurationGatewaysEntry 2 }

gs2352DHCPRelayConfigurationGatewaysIP OBJECT-TYPE
   SYNTAX      IpAddress
   MAX-ACCESS  read-write
   STATUS      current
   DESCRIPTION
       "DHCP GIADDR address."
   ::= { gs2352DHCPRelayConfigurationGatewaysEntry 3 }

gs2352DHCPRelayConfigurationGatewaysRowStatus OBJECT-TYPE
   SYNTAX      INTEGER { active(1), notInservice(2), destroy(4), undo(5) }
   MAX-ACCESS  read-write
   STATUS      current
   DESCRIPTION
       "1: active
        2: notInservice
        4: destroy
        5: undo"
   ::= { gs2352DHCPRelayConfigurationGatewaysEntry 4 }


gs2352DHCPRelayStatistics                                   OBJECT IDENTIFIER ::= { gs2352DHCPRelay 2 }

gs2352DHCPRelayServerStatistics                                   OBJECT IDENTIFIER ::= { gs2352DHCPRelayStatistics 1 }

gs2352ServerStatTransmitToServer OBJECT-TYPE
   SYNTAX      Counter32
   MAX-ACCESS  read-only
   STATUS      current
   DESCRIPTION
       " "
   ::= { gs2352DHCPRelayServerStatistics 1 }

gs2352ServerStatTransmitError OBJECT-TYPE
   SYNTAX      Counter32
   MAX-ACCESS  read-only
   STATUS      current
   DESCRIPTION
       " "
   ::= { gs2352DHCPRelayServerStatistics 2 }

gs2352ServerStatReceiveFromServer OBJECT-TYPE
   SYNTAX      Counter32
   MAX-ACCESS  read-only
   STATUS      current
   DESCRIPTION
       " "
   ::= { gs2352DHCPRelayServerStatistics 3 }

gs2352ServerStatReceiveMissingAgentOption OBJECT-TYPE
   SYNTAX      Counter32
   MAX-ACCESS  read-only
   STATUS      current
   DESCRIPTION
       " "
   ::= { gs2352DHCPRelayServerStatistics 4 }

gs2352ServerStatReceiveMissingCircuitID OBJECT-TYPE
   SYNTAX      Counter32
   MAX-ACCESS  read-only
   STATUS      current
   DESCRIPTION
       " "
   ::= { gs2352DHCPRelayServerStatistics 5 }

gs2352ServerStatReceiveMissingRemoteID OBJECT-TYPE
   SYNTAX      Counter32
   MAX-ACCESS  read-only
   STATUS      current
   DESCRIPTION
       " "
   ::= { gs2352DHCPRelayServerStatistics 6 }

gs2352ServerStatReceiveBadCircuitID OBJECT-TYPE
   SYNTAX      Counter32
   MAX-ACCESS  read-only
   STATUS      current
   DESCRIPTION
       " "
   ::= { gs2352DHCPRelayServerStatistics 7 }

gs2352ServerStatReceiveBadRemoteID OBJECT-TYPE
   SYNTAX      Counter32
   MAX-ACCESS  read-only
   STATUS      current
   DESCRIPTION
       " "
   ::= { gs2352DHCPRelayServerStatistics 8 }

gs2352DHCPRelayClientStatistics                                   OBJECT IDENTIFIER ::= { gs2352DHCPRelayStatistics 2 }

gs2352ClientStatTransmitToClient OBJECT-TYPE
   SYNTAX      Counter32
   MAX-ACCESS  read-only
   STATUS      current
   DESCRIPTION
       " "
   ::= { gs2352DHCPRelayClientStatistics 1 }

gs2352ClientStatTransmitError OBJECT-TYPE
   SYNTAX      Counter32
   MAX-ACCESS  read-only
   STATUS      current
   DESCRIPTION
       " "
   ::= { gs2352DHCPRelayClientStatistics 2 }

gs2352ClientStatReceivefromClient OBJECT-TYPE
   SYNTAX      Counter32
   MAX-ACCESS  read-only
   STATUS      current
   DESCRIPTION
       " "
   ::= { gs2352DHCPRelayClientStatistics 3 }

gs2352ClientStatReceiveAgentOption OBJECT-TYPE
   SYNTAX      Counter32
   MAX-ACCESS  read-only
   STATUS      current
   DESCRIPTION
       " "
   ::= { gs2352DHCPRelayClientStatistics 4 }

gs2352ClientStatReplaceAgentOption OBJECT-TYPE
   SYNTAX      Counter32
   MAX-ACCESS  read-only
   STATUS      current
   DESCRIPTION
       " "
   ::= { gs2352DHCPRelayClientStatistics 5 }

gs2352ClientStatKeepAgentOption OBJECT-TYPE
   SYNTAX      Counter32
   MAX-ACCESS  read-only
   STATUS      current
   DESCRIPTION
       " "
   ::= { gs2352DHCPRelayClientStatistics 6 }

gs2352ClientStatDropAgentOption OBJECT-TYPE
   SYNTAX      Counter32
   MAX-ACCESS  read-only
   STATUS      current
   DESCRIPTION
       " "
   ::= { gs2352DHCPRelayClientStatistics 7 }

gs2352PortSecurity                                          OBJECT IDENTIFIER ::= { gs2352Security 5 }

gs2352PortSecLimitCtrl                                      OBJECT IDENTIFIER ::= { gs2352PortSecurity 1 }

gs2352PortSecLimitCtrlSystemConf                                      OBJECT IDENTIFIER ::= { gs2352PortSecLimitCtrl 1 }

gs2352PortSecurityMode OBJECT-TYPE
   SYNTAX      INTEGER { disable(0), enable(1) }
   MAX-ACCESS  read-write
   STATUS      current
   DESCRIPTION
       "default: 0
       0: disable
       1: enable "
   ::= { gs2352PortSecLimitCtrlSystemConf 1 }

gs2352PortSecurityAging OBJECT-TYPE
   SYNTAX      INTEGER { disable(0), enable(1) }
   MAX-ACCESS  read-write
   STATUS      current
   DESCRIPTION
       "default: 0
       0: disable
       1: enable "
   ::= { gs2352PortSecLimitCtrlSystemConf 2 }

gs2352PortSecurityAgingPeriod OBJECT-TYPE
   SYNTAX      INTEGER(10..10000000)
   MAX-ACCESS  read-write
   STATUS      current
   DESCRIPTION
       "default: 3600, range: 10-10000000 "
   ::= { gs2352PortSecLimitCtrlSystemConf 3 }

gs2352PortSecLimitCtrlTable OBJECT-TYPE
   SYNTAX      SEQUENCE OF GS2352PortSecLimitCtrlEntry
   MAX-ACCESS  not-accessible
   STATUS      current
   DESCRIPTION
       " "
   ::= { gs2352PortSecLimitCtrl 2 }

gs2352PortSecLimitCtrlEntry OBJECT-TYPE
   SYNTAX      GS2352PortSecLimitCtrlEntry
   MAX-ACCESS  not-accessible
   STATUS      current
   DESCRIPTION
       ""
   INDEX    { gs2352PortSecLimitCtrlPort  }
   ::= { gs2352PortSecLimitCtrlTable 1 }

GS2352PortSecLimitCtrlEntry ::= SEQUENCE {
   gs2352PortSecLimitCtrlPort           Integer32,
   gs2352PortSecLimitCtrlPortMode       INTEGER,
   gs2352PortSecLimitCtrlPortLimit      Integer32,
   gs2352PortSecLimitCtrlPortAction     INTEGER,
   gs2352PortSecLimitCtrlPortState      DisplayString,
   gs2352PortSecLimitCtrlPortReOpen     INTEGER
}

gs2352PortSecLimitCtrlPort OBJECT-TYPE
   SYNTAX      Integer32(1..4095)
   MAX-ACCESS  not-accessible
   STATUS      current
   DESCRIPTION
       " "
   ::= { gs2352PortSecLimitCtrlEntry 1 }

gs2352PortSecLimitCtrlPortMode OBJECT-TYPE
   SYNTAX      INTEGER { disable(0), enable(1) }
   MAX-ACCESS  read-write
   STATUS      current
   DESCRIPTION
       "default: 0
       0: disable
       1: enable"
   ::= { gs2352PortSecLimitCtrlEntry 2 }

gs2352PortSecLimitCtrlPortLimit OBJECT-TYPE
   SYNTAX      Integer32(1..1024)
   MAX-ACCESS  read-write
   STATUS      current
   DESCRIPTION
       "default: 4, range: 1-1024"
   ::= { gs2352PortSecLimitCtrlEntry 3 }

gs2352PortSecLimitCtrlPortAction OBJECT-TYPE
   SYNTAX      INTEGER { none(0), trap(1), shutdown(2), trapShutdown(3) }
   MAX-ACCESS  read-write
   STATUS      current
   DESCRIPTION
       "default: 0
       0: none
       1: trap
       2: shutdown
       3: trap&shutdown"
   ::= { gs2352PortSecLimitCtrlEntry 4 }

gs2352PortSecLimitCtrlPortState OBJECT-TYPE
   SYNTAX      DisplayString
   MAX-ACCESS  read-only
   STATUS      current
   DESCRIPTION
       ""
   ::= { gs2352PortSecLimitCtrlEntry 5 }

gs2352PortSecLimitCtrlPortReOpen OBJECT-TYPE
   SYNTAX      INTEGER { none(0), reopen(1) }
   MAX-ACCESS  read-write
   STATUS      current
   DESCRIPTION
       "default: 0
       0: none
       1: reopen"
   ::= { gs2352PortSecLimitCtrlEntry 6 }

gs2352PortSecSwitchStatusTable OBJECT-TYPE
   SYNTAX      SEQUENCE OF GS2352PortSecSwitchStatusEntry
   MAX-ACCESS  not-accessible
   STATUS      current
   DESCRIPTION
       " "
   ::= { gs2352PortSecurity 2 }

gs2352PortSecSwitchStatusEntry OBJECT-TYPE
   SYNTAX      GS2352PortSecSwitchStatusEntry
   MAX-ACCESS  not-accessible
   STATUS      current
   DESCRIPTION
       ""
   INDEX    { gs2352PortSecSwitchStatusPort  }
   ::= { gs2352PortSecSwitchStatusTable 1 }

GS2352PortSecSwitchStatusEntry ::= SEQUENCE {
   gs2352PortSecSwitchStatusPort                Integer32,
   gs2352PortSecSwitchStatusUsers               DisplayString,
   gs2352PortSecSwitchStatusState               DisplayString,
   gs2352PortSecSwitchStatusMACCountCurrent     Integer32,
   gs2352PortSecSwitchStatusMACCountLimit       Integer32
}

gs2352PortSecSwitchStatusPort OBJECT-TYPE
   SYNTAX      Integer32(1..4095)
   MAX-ACCESS  not-accessible
   STATUS      current
   DESCRIPTION
       " "
   ::= { gs2352PortSecSwitchStatusEntry 1 }

gs2352PortSecSwitchStatusUsers OBJECT-TYPE
   SYNTAX      DisplayString
   MAX-ACCESS  read-only
   STATUS      current
   DESCRIPTION
       " Users Abbr: L = Limit Control, 8 = 802.1X, D = DHCP Snooping, V = Voice VLAN,
         '-' means that the corresponding user module is not enabled. "
   ::= { gs2352PortSecSwitchStatusEntry 2 }

gs2352PortSecSwitchStatusState OBJECT-TYPE
   SYNTAX      DisplayString
   MAX-ACCESS  read-only
   STATUS      current
   DESCRIPTION
       " Shows the current state of the port : Disabled, Ready, Limit Reached, Shutdown. "
   ::= { gs2352PortSecSwitchStatusEntry 3 }

gs2352PortSecSwitchStatusMACCountCurrent OBJECT-TYPE
   SYNTAX      Integer32(1..4095)
   MAX-ACCESS  read-only
   STATUS      current
   DESCRIPTION
       ""
   ::= { gs2352PortSecSwitchStatusEntry 4 }

gs2352PortSecSwitchStatusMACCountLimit OBJECT-TYPE
   SYNTAX      Integer32(1..4095)
   MAX-ACCESS  read-only
   STATUS      current
   DESCRIPTION
       ""
   ::= { gs2352PortSecSwitchStatusEntry 5 }

gs2352PortSecPortStatus                                      OBJECT IDENTIFIER ::= { gs2352PortSecurity 3 }

gs2352PortSecPortStatusPort OBJECT-TYPE
   SYNTAX       Integer32(1..4095)
   MAX-ACCESS   read-write
   STATUS       current
   DESCRIPTION
       "port number
        default: 1
        range: 1 - port number."
   ::= { gs2352PortSecPortStatus 1 }

gs2352PortSecPortStatusTable OBJECT-TYPE
   SYNTAX      SEQUENCE OF GS2352PortSecPortStatusEntry
   MAX-ACCESS  not-accessible
   STATUS      current
   DESCRIPTION
      " "
   ::= { gs2352PortSecPortStatus 2 }

gs2352PortSecPortStatusEntry OBJECT-TYPE
   SYNTAX      GS2352PortSecPortStatusEntry
   MAX-ACCESS  not-accessible
   STATUS      current
   DESCRIPTION
       ""
   INDEX    { gs2352PortSecPortStatusIndex  }
   ::= { gs2352PortSecPortStatusTable 1 }

GS2352PortSecPortStatusEntry ::= SEQUENCE {
   gs2352PortSecPortStatusIndex              Integer32,
   gs2352PortSecPortStatusMACAddress         MacAddress,
   gs2352PortSecPortStatusVLANId             Integer32,
   gs2352PortSecPortStatusState              DisplayString,
   gs2352PortSecPortStatusTimeOfAddition     DisplayString,
   gs2352PortSecPortStatusAgeAndHold         DisplayString
}

gs2352PortSecPortStatusIndex OBJECT-TYPE
   SYNTAX      Integer32(1..4095)
   MAX-ACCESS  not-accessible
   STATUS      current
   DESCRIPTION
       " "
   ::= { gs2352PortSecPortStatusEntry 1 }

gs2352PortSecPortStatusMACAddress OBJECT-TYPE
   SYNTAX      MacAddress
   MAX-ACCESS  read-only
   STATUS      current
   DESCRIPTION
       " "
   ::= { gs2352PortSecPortStatusEntry 2 }

gs2352PortSecPortStatusVLANId OBJECT-TYPE
   SYNTAX      Integer32(1..4094)
   MAX-ACCESS  read-only
   STATUS      current
   DESCRIPTION
       " "
   ::= { gs2352PortSecPortStatusEntry 3 }

gs2352PortSecPortStatusState OBJECT-TYPE
   SYNTAX      DisplayString
   MAX-ACCESS  read-only
   STATUS      current
   DESCRIPTION
       "Blocked / Forwarding "
   ::= { gs2352PortSecPortStatusEntry 4 }

gs2352PortSecPortStatusTimeOfAddition OBJECT-TYPE
   SYNTAX      DisplayString
   MAX-ACCESS  read-only
   STATUS      current
   DESCRIPTION
       " "
   ::= { gs2352PortSecPortStatusEntry 5 }

gs2352PortSecPortStatusAgeAndHold OBJECT-TYPE
   SYNTAX      DisplayString
   MAX-ACCESS  read-only
   STATUS      current
   DESCRIPTION
       " "
   ::= { gs2352PortSecPortStatusEntry 6 }


gs2352AccessManagement                                      OBJECT IDENTIFIER ::= { gs2352Security 6 }

gs2352AccessMgtConf                                         OBJECT IDENTIFIER ::= { gs2352AccessManagement 1 }

gs2352AccessMgtConfMode OBJECT-TYPE
   SYNTAX      INTEGER { disable(0), enable(1) }
   MAX-ACCESS  read-write
   STATUS      current
   DESCRIPTION
       "default: 0
       0: disable
       1: enable "
   ::= { gs2352AccessMgtConf 1 }

gs2352AccessMgtConfCreate OBJECT-TYPE
   SYNTAX      INTEGER { none(0), create(1) }
   MAX-ACCESS  read-write
   STATUS      current
   DESCRIPTION
       "default: 0
       0: none
       1: create "
   ::= { gs2352AccessMgtConf 2 }

gs2352AccessMgtConfTable OBJECT-TYPE
   SYNTAX      SEQUENCE OF GS2352AccessMgtConfEntry
   MAX-ACCESS  not-accessible
   STATUS      current
   DESCRIPTION
       " "
   ::= { gs2352AccessMgtConf 3 }

gs2352AccessMgtConfEntry OBJECT-TYPE
   SYNTAX      GS2352AccessMgtConfEntry
   MAX-ACCESS  not-accessible
   STATUS      current
   DESCRIPTION
       ""
   INDEX    { gs2352AccessMgtIndex  }
   ::= { gs2352AccessMgtConfTable 1 }

GS2352AccessMgtConfEntry ::= SEQUENCE {
   gs2352AccessMgtIndex             Integer32,
   gs2352AccessMgtAddresstype       INTEGER,
   gs2352AccessMgtStartIpAddress    DisplayString,
   gs2352AccessMgtEndIpAddress      DisplayString,
   gs2352AccessMgtHttpHttps         INTEGER,
   gs2352AccessMgtSNMP              INTEGER,
   gs2352AccessMgtTelnetSSH         INTEGER,
   gs2352AccessMgtRowStatus         INTEGER
}

gs2352AccessMgtIndex OBJECT-TYPE
   SYNTAX      Integer32(1..16)
   MAX-ACCESS  read-write
   STATUS      current
   DESCRIPTION
       "Set Access Management config index
        range : 1-16."
   ::= { gs2352AccessMgtConfEntry 1 }

gs2352AccessMgtAddresstype OBJECT-TYPE
   SYNTAX      INTEGER { ipv4(0), ipv6(1) }
   MAX-ACCESS  read-write
   STATUS      current
   DESCRIPTION
       "0: ipv4
        1: ipv6 "
   ::= { gs2352AccessMgtConfEntry 2 }

gs2352AccessMgtStartIpAddress OBJECT-TYPE
   SYNTAX      DisplayString
   MAX-ACCESS  read-write
   STATUS      current
   DESCRIPTION
       " Start IP address.
         IP address doesn't allowed all zero or all 'ff'H."
   ::= { gs2352AccessMgtConfEntry 3 }

gs2352AccessMgtEndIpAddress OBJECT-TYPE
   SYNTAX      DisplayString
   MAX-ACCESS  read-write
   STATUS      current
   DESCRIPTION
       " End IP address.
         IP address doesn't allowed all zero or all 'ff'H.
         End ip address is not less than start ip address."
   ::= { gs2352AccessMgtConfEntry 4 }

gs2352AccessMgtHttpHttps OBJECT-TYPE
   SYNTAX      INTEGER { disable(0), enable(1) }
   MAX-ACCESS  read-write
   STATUS      current
   DESCRIPTION
       "default: 0
       0: disable
       1: enable "
   ::= { gs2352AccessMgtConfEntry 5 }

gs2352AccessMgtSNMP OBJECT-TYPE
   SYNTAX      INTEGER { disable(0), enable(1) }
   MAX-ACCESS  read-write
   STATUS      current
   DESCRIPTION
       "default: 0
       0: disable
       1: enable "
   ::= { gs2352AccessMgtConfEntry 6 }

gs2352AccessMgtTelnetSSH OBJECT-TYPE
   SYNTAX      INTEGER { disable(0), enable(1) }
   MAX-ACCESS  read-write
   STATUS      current
   DESCRIPTION
       "default: 0
       0: disable
       1: enable "
   ::= { gs2352AccessMgtConfEntry 7 }

gs2352AccessMgtRowStatus OBJECT-TYPE
   SYNTAX      INTEGER { active(1), notInservice(2), edit(3),destroy(4), undo(5) }
   MAX-ACCESS  read-write
   STATUS      current
   DESCRIPTION
       "1: active
        2: notInservice
        3: edit
        4: destroy
        5: undo"
   ::= { gs2352AccessMgtConfEntry 8 }

gs2352AccessMgtStatistics                                   OBJECT IDENTIFIER ::= { gs2352AccessManagement 2 }

gs2352HttpReceivedPkts OBJECT-TYPE
   SYNTAX      Counter32
   MAX-ACCESS  read-only
   STATUS      current
   DESCRIPTION
       " "
   ::= { gs2352AccessMgtStatistics 1 }

gs2352HttpAllowedPkts OBJECT-TYPE
   SYNTAX      Counter32
   MAX-ACCESS  read-only
   STATUS      current
   DESCRIPTION
       " "
   ::= { gs2352AccessMgtStatistics 2 }

gs2352HttpDiscardedPkts OBJECT-TYPE
   SYNTAX      Counter32
   MAX-ACCESS  read-only
   STATUS      current
   DESCRIPTION
       " "
   ::= { gs2352AccessMgtStatistics 3 }

gs2352HttpsReceivedPkts OBJECT-TYPE
   SYNTAX      Counter32
   MAX-ACCESS  read-only
   STATUS      current
   DESCRIPTION
       " "
   ::= { gs2352AccessMgtStatistics 4 }

gs2352HttpsAllowedPkts OBJECT-TYPE
   SYNTAX      Counter32
   MAX-ACCESS  read-only
   STATUS      current
   DESCRIPTION
       " "
   ::= { gs2352AccessMgtStatistics 5 }

gs2352HttpsDiscardedPkts OBJECT-TYPE
   SYNTAX      Counter32
   MAX-ACCESS  read-only
   STATUS      current
   DESCRIPTION
       " "
   ::= { gs2352AccessMgtStatistics 6 }

gs2352SnmpReceivedPkts OBJECT-TYPE
   SYNTAX      Counter32
   MAX-ACCESS  read-only
   STATUS      current
   DESCRIPTION
       " "
   ::= { gs2352AccessMgtStatistics 7 }

gs2352SnmpAllowedPkts OBJECT-TYPE
   SYNTAX      Counter32
   MAX-ACCESS  read-only
   STATUS      current
   DESCRIPTION
       " "
   ::= { gs2352AccessMgtStatistics 8 }

gs2352SnmpDiscardedPkts OBJECT-TYPE
   SYNTAX      Counter32
   MAX-ACCESS  read-only
   STATUS      current
   DESCRIPTION
       " "
   ::= { gs2352AccessMgtStatistics 9 }

gs2352TelnetReceivedPkts OBJECT-TYPE
   SYNTAX      Counter32
   MAX-ACCESS  read-only
   STATUS      current
   DESCRIPTION
       " "
   ::= { gs2352AccessMgtStatistics 10 }

gs2352TelnetAllowedPkts OBJECT-TYPE
   SYNTAX      Counter32
   MAX-ACCESS  read-only
   STATUS      current
   DESCRIPTION
       " "
   ::= { gs2352AccessMgtStatistics 11 }

gs2352TelnetDiscardedPkts OBJECT-TYPE
   SYNTAX      Counter32
   MAX-ACCESS  read-only
   STATUS      current
   DESCRIPTION
       " "
   ::= { gs2352AccessMgtStatistics 12 }

gs2352SSHReceivedPkts OBJECT-TYPE
   SYNTAX      Counter32
   MAX-ACCESS  read-only
   STATUS      current
   DESCRIPTION
       " "
   ::= { gs2352AccessMgtStatistics 13 }

gs2352SSHAllowedPkts OBJECT-TYPE
   SYNTAX      Counter32
   MAX-ACCESS  read-only
   STATUS      current
   DESCRIPTION
       " "
   ::= { gs2352AccessMgtStatistics 14 }

gs2352SSHDiscardedPkts OBJECT-TYPE
   SYNTAX      Counter32
   MAX-ACCESS  read-only
   STATUS      current
   DESCRIPTION
       " "
   ::= { gs2352AccessMgtStatistics 15 }

gs2352AccessMgtStatisticsClearAll OBJECT-TYPE
   SYNTAX      INTEGER { none(0), clear(1) }
   MAX-ACCESS  read-write
   STATUS      current
   DESCRIPTION
       "0: none
        1: clear"
   ::= { gs2352AccessMgtStatistics 16 }

gs2352SSH                                                   OBJECT IDENTIFIER ::= { gs2352Security 7 }

gs2352SSHMode OBJECT-TYPE
   SYNTAX      INTEGER { disable(0), enable(1) }
   MAX-ACCESS  read-write
   STATUS      current
   DESCRIPTION
       "default: 1
        0: disable
        1: enable"
   ::= { gs2352SSH 1 }

gs2352HTTPS                                                 OBJECT IDENTIFIER ::= { gs2352Security 8 }

gs2352HTTPSMode OBJECT-TYPE
   SYNTAX      INTEGER { disable(0), enable(1) }
   MAX-ACCESS  read-write
   STATUS      current
   DESCRIPTION
       "default: 1
        0: disable
        1: enable"
   ::= { gs2352HTTPS 1 }

gs2352HTTPSAutoRedirect OBJECT-TYPE
   SYNTAX      INTEGER { disable(0), enable(1) }
   MAX-ACCESS  read-write
   STATUS      current
   DESCRIPTION
       "default: 0
        0: disable
        1: enable"
   ::= { gs2352HTTPS 2 }

gs2352HTTPSCertRenew OBJECT-TYPE
   SYNTAX      INTEGER { doNothing(0), renew(1) }
   MAX-ACCESS  read-write
   STATUS      current
   DESCRIPTION
       "default: 0 ,
        0: doNothing
        1: renew"
   ::= { gs2352HTTPS 3 }

gs2352HTTPSMinProtoVersion OBJECT-TYPE
   SYNTAX      INTEGER { SSLv3(0), TLSv1(1), TLSv11(2), TLSv12(3)}
   MAX-ACCESS  read-write
   STATUS      current
   DESCRIPTION
       "default: 1
        0: SSLv3
        1: TLSv1
        2: TLSv1.1
        3: TLSv1.2"
   ::= { gs2352HTTPS 4 }

gs2352HTTPMode OBJECT-TYPE
   SYNTAX      INTEGER { disable(0), enable(1) }
   MAX-ACCESS  read-write
   STATUS      current
   DESCRIPTION
       "default: 1
        0: disable
        1: enable"
   ::= { gs2352HTTPS 5 }

gs2352AuthMethod                                            OBJECT IDENTIFIER ::= { gs2352Security 9 }

gs2352ConsoleAuthMethod OBJECT-TYPE
   SYNTAX      INTEGER { none(0), local(1), radius(2), tacacsplus(3) }
   MAX-ACCESS  read-write
   STATUS      current
   DESCRIPTION
       "default: 1
        0: none
        1: local
        2: RADIUS
        3: TACACS+"
   ::= { gs2352AuthMethod 1 }

gs2352ConsoleFallback OBJECT-TYPE
   SYNTAX      INTEGER { disable(0), enable(1) }
   MAX-ACCESS  read-write
   STATUS      current
   DESCRIPTION
       "default: 0
        0:disable
        1:enable"
   ::= { gs2352AuthMethod 2 }

gs2352TelnetAuthMethod OBJECT-TYPE
   SYNTAX      INTEGER { none(0), local(1), radius(2), tacacsplus(3) }
   MAX-ACCESS  read-write
   STATUS      current
   DESCRIPTION
       "default: 1
        0: none
        1: local
        2: RADIUS
        3: TACACS+"
   ::= { gs2352AuthMethod 3 }

gs2352TelnetFallback OBJECT-TYPE
   SYNTAX      INTEGER { disable(0), enable(1) }
   MAX-ACCESS  read-write
   STATUS      current
   DESCRIPTION
       "default: 0
        0:disable
        1:enable"
   ::= { gs2352AuthMethod 4 }

gs2352SshAuthMethod OBJECT-TYPE
   SYNTAX      INTEGER { none(0), local(1), radius(2), tacacsplus(3) }
   MAX-ACCESS  read-write
   STATUS      current
   DESCRIPTION
       "default: 1
        0: none
        1: local
        2: RADIUS
        3: TACACS+"
   ::= { gs2352AuthMethod 5 }

gs2352SshFallback OBJECT-TYPE
   SYNTAX      INTEGER { disable(0), enable(1) }
   MAX-ACCESS  read-write
   STATUS      current
   DESCRIPTION
       "default: 0
        0:disable
        1:enable"
   ::= { gs2352AuthMethod 6 }

gs2352TftpAuthMethod OBJECT-TYPE
   SYNTAX      INTEGER { none(0), local(1), radius(2), tacacsplus(3) }
   MAX-ACCESS  read-write
   STATUS      current
   DESCRIPTION
       "default: 1
        0: none
        1: local
        2: RADIUS
        3: TACACS+"
   ::= { gs2352AuthMethod 9 }

gs2352TftpFallback OBJECT-TYPE
   SYNTAX      INTEGER { disable(0), enable(1) }
   MAX-ACCESS  read-write
   STATUS      current
   DESCRIPTION
       "default: 0
        0:disable
        1:enable"
   ::= { gs2352AuthMethod 10 }

gs2352LoginFailures OBJECT-TYPE
   SYNTAX      Integer32(0..99)
   MAX-ACCESS  read-write
   STATUS      current
   DESCRIPTION
       "When login failures mechanism is triggered,the lock minutes will prevent to login in this periods.
        The value '0' should deactivate this feature.
        range: 0-99.
        default: 5."
   ::= { gs2352AuthMethod 11 }

gs2352LockMinutes OBJECT-TYPE
   SYNTAX      Integer32(1..99)
   MAX-ACCESS  read-write
   STATUS      current
   DESCRIPTION
       "Lock time to login failures trigger.
        range: 1-99.
        default: 5."
   ::= { gs2352AuthMethod 12 }

gs2352HttpAuthMethod OBJECT-TYPE
   SYNTAX      INTEGER { none(0), local(1), radius(2), tacacsplus(3) }
   MAX-ACCESS  read-write
   STATUS      current
   DESCRIPTION
       "default: 1
        0: none
        1: local
        2: RADIUS
        3: TACACS+"
   ::= { gs2352AuthMethod 13 }

gs2352HttpFallback OBJECT-TYPE
   SYNTAX      INTEGER { disable(0), enable(1) }
   MAX-ACCESS  read-write
   STATUS      current
   DESCRIPTION
       "default: 0
        0:disable
        1:enable"
   ::= { gs2352AuthMethod 14 }

gs2352HttpsAuthMethod OBJECT-TYPE
   SYNTAX      INTEGER { none(0), local(1), radius(2), tacacsplus(3) }
   MAX-ACCESS  read-write
   STATUS      current
   DESCRIPTION
       "default: 1
        0: none
        1: local
        2: RADIUS
        3: TACACS+"
   ::= { gs2352AuthMethod 15 }

gs2352HttpsFallback OBJECT-TYPE
   SYNTAX      INTEGER { disable(0), enable(1) }
   MAX-ACCESS  read-write
   STATUS      current
   DESCRIPTION
       "default: 0
        0:disable
        1:enable"
   ::= { gs2352AuthMethod 16 }


gs2352AAA                                              OBJECT IDENTIFIER ::= { gs2352Security 10 }

gs2352AAACommonServer                                  OBJECT IDENTIFIER ::= { gs2352AAA 1 }

gs2352AAACommonServerTimeout OBJECT-TYPE
   SYNTAX      Integer32(3..3600)
   MAX-ACCESS  read-write
   STATUS      current
   DESCRIPTION
       "The Timeout, which can be set to a number between 3 and 3600 seconds, is
       the maximum time to wait for a reply from a server. If the server does not
       reply within this timeframe, we will consider it to be dead and continue
       with the next enabled server (if any). RADIUS servers are using the UDP
       protocol, which is unreliable by design. In order to cope with lost frames,
       the timeout interval is divided into 3 subintervals of equal length. If a
       reply is not received within the subinterval, the request is transmitted
       again. This algorithm causes the RADIUS server to be queried up to 3 times
       before it is considered to be dead.
        default: 15."
   ::= { gs2352AAACommonServer 1 }

gs2352AAACommonServerDeadTime OBJECT-TYPE
   SYNTAX      Integer32(0..3600)
   MAX-ACCESS  read-write
   STATUS      current
   DESCRIPTION
       "The Dead Time, which can be set to a number between 0 and 3600 seconds,
       is the period during which the switch will not send new requests to a
       server that has failed to respond to a previous request. This will stop
       the switch from continually trying to contact a server that it has already
       determined as dead.
       Setting the Dead Time to a value greater than 0 (zero) will enable this feature,
       but only if more than one server has been configured.
       default: 300."
   ::= { gs2352AAACommonServer 2 }

gs2352AAATACACSPlusAuthAndAccounting                  OBJECT IDENTIFIER ::= { gs2352AAA 2 }

gs2352AAAAuthorization OBJECT-TYPE
   SYNTAX      INTEGER { disable(0), enable(1) }
   MAX-ACCESS  read-write
   STATUS      current
   DESCRIPTION
       "Authorization is the action of determining what a user is allowed to do.
       An authorization request may indicate that the user is not authenticated.
       In this case it is up to the authorization agent to determine if an
       unauthenticated user is allowed the services in question. "
   ::= { gs2352AAATACACSPlusAuthAndAccounting 1 }

gs2352AAAFallbackToLocalAuthorization OBJECT-TYPE
   SYNTAX      INTEGER { disable(0), enable(1) }
   MAX-ACCESS  read-write
   STATUS      current
   DESCRIPTION
       "This function is an auxiliary function of Authorization. When the DUT
       cannot communicate with TACACS+ Server normally, it will check the right/
        permission level of the Local Account to execute the Authorization. "
   ::= { gs2352AAATACACSPlusAuthAndAccounting 2 }

gs2352AAAAccounting OBJECT-TYPE
   SYNTAX      INTEGER { disable(0), enable(1) }
   MAX-ACCESS  read-write
   STATUS      current
   DESCRIPTION
       "Accounting is typically the third action after authentication and
       authorization. Accounting is the action of recording what a user is doing,
       and/or has done. TACACS+ accounting records contain all the information
       used in the authorization records and resource usage information. "
   ::= { gs2352AAATACACSPlusAuthAndAccounting 3 }

gs2352RADIUSAuthenticationServerTable OBJECT-TYPE
   SYNTAX      SEQUENCE OF Gs2352RADIUSAuthenticationServerEntry
   MAX-ACCESS  not-accessible
   STATUS      current
   DESCRIPTION
       " "
   ::= { gs2352AAA 3 }

gs2352RADIUSAuthenticationServerEntry OBJECT-TYPE
   SYNTAX      Gs2352RADIUSAuthenticationServerEntry
   MAX-ACCESS  not-accessible
   STATUS      current
   DESCRIPTION
       ""
   INDEX    { gs2352RADIUSAuthenticationServerIndex  }
   ::= { gs2352RADIUSAuthenticationServerTable 1 }

Gs2352RADIUSAuthenticationServerEntry ::= SEQUENCE {
   gs2352RADIUSAuthenticationServerIndex     Integer32,
   gs2352RADIUSAuthenticationServerEnable    INTEGER,
   gs2352RADIUSAuthenticationServerIP        DisplayString,
   gs2352RADIUSAuthenticationServerPort      Integer32,
   gs2352RADIUSAuthenticationServerSecret    DisplayString
}

gs2352RADIUSAuthenticationServerIndex OBJECT-TYPE
   SYNTAX      Integer32(1..5)
   MAX-ACCESS  not-accessible
   STATUS      current
   DESCRIPTION
       "RADIUS Authentication Server index
        range : 1-5."
   ::= { gs2352RADIUSAuthenticationServerEntry 1 }

gs2352RADIUSAuthenticationServerEnable OBJECT-TYPE
   SYNTAX      INTEGER { disable(0), enable(1) }
   MAX-ACCESS  read-write
   STATUS      current
   DESCRIPTION
       "Enable/Disable the RADIUS Authentication Server. the RADIUSAuthenticationServerEnable
       can be set, when IP and Secret have value "
   ::= { gs2352RADIUSAuthenticationServerEntry 2 }

gs2352RADIUSAuthenticationServerIP OBJECT-TYPE
   SYNTAX      DisplayString
   MAX-ACCESS  read-write
   STATUS      current
   DESCRIPTION
       "The IP address or hostname of the RADIUS Authentication Server.
       IP address is expressed in  dotted decimal notation. "
   ::= { gs2352RADIUSAuthenticationServerEntry 3 }

gs2352RADIUSAuthenticationServerPort OBJECT-TYPE
   SYNTAX      Integer32(0..65535)
   MAX-ACCESS  read-write
   STATUS      current
   DESCRIPTION
       "The UDP port to use on the RADIUS Authentication Server. If the port is
       set to 0 (zero), the default port (1812) is used on the RADIUS Authentication Server. "
   ::= { gs2352RADIUSAuthenticationServerEntry 4 }

gs2352RADIUSAuthenticationServerSecret OBJECT-TYPE
   SYNTAX      DisplayString
   MAX-ACCESS  read-write
   STATUS      current
   DESCRIPTION
       "The secret - up to 64 characters long - shared between the RADIUS Authentication Server and the switch. "
   ::= { gs2352RADIUSAuthenticationServerEntry 5 }


gs2352RADIUSAccountingServerTable OBJECT-TYPE
   SYNTAX      SEQUENCE OF Gs2352RADIUSAccountingServerEntry
   MAX-ACCESS  not-accessible
   STATUS      current
   DESCRIPTION
       " "
   ::= { gs2352AAA 4 }

gs2352RADIUSAccountingServerEntry OBJECT-TYPE
   SYNTAX      Gs2352RADIUSAccountingServerEntry
   MAX-ACCESS  not-accessible
   STATUS      current
   DESCRIPTION
       ""
   INDEX    { gs2352RADIUSAccountingServerIndex  }
   ::= { gs2352RADIUSAccountingServerTable 1 }

Gs2352RADIUSAccountingServerEntry ::= SEQUENCE {
   gs2352RADIUSAccountingServerIndex     Integer32,
   gs2352RADIUSAccountingServerEnable    INTEGER,
   gs2352RADIUSAccountingServerIP        DisplayString,
   gs2352RADIUSAccountingServerPort      Integer32,
   gs2352RADIUSAccountingServerSecret    DisplayString
}

gs2352RADIUSAccountingServerIndex OBJECT-TYPE
   SYNTAX      Integer32(1..5)
   MAX-ACCESS  not-accessible
   STATUS      current
   DESCRIPTION
       "RADIUS Accounting Server index
        range : 1-5."
   ::= { gs2352RADIUSAccountingServerEntry 1 }

gs2352RADIUSAccountingServerEnable OBJECT-TYPE
   SYNTAX      INTEGER { disable(0), enable(1) }
   MAX-ACCESS  read-write
   STATUS      current
   DESCRIPTION
       "Enable/Disable the RADIUS Accounting Server. The RADIUSAccountingServerEnable
       can be set, when IP and Secret have value. "
   ::= { gs2352RADIUSAccountingServerEntry 2 }

gs2352RADIUSAccountingServerIP OBJECT-TYPE
   SYNTAX      DisplayString
   MAX-ACCESS  read-write
   STATUS      current
   DESCRIPTION
       "The IP address or hostname of the RADIUS Accounting Server.
       IP address is expressed in  dotted decimal notation. "
   ::= { gs2352RADIUSAccountingServerEntry 3 }

gs2352RADIUSAccountingServerPort OBJECT-TYPE
   SYNTAX      Integer32(0..65535)
   MAX-ACCESS  read-write
   STATUS      current
   DESCRIPTION
       "The UDP port to use on the RADIUS Accounting Server. If the port is
       set to 0 (zero), the default port (1812) is used on the RADIUS Accounting Server. "
   ::= { gs2352RADIUSAccountingServerEntry 4 }

gs2352RADIUSAccountingServerSecret OBJECT-TYPE
   SYNTAX      DisplayString
   MAX-ACCESS  read-write
   STATUS      current
   DESCRIPTION
       "The secret - up to 64 characters long - shared between the RADIUS Accounting Server and the switch. "
   ::= { gs2352RADIUSAccountingServerEntry 5 }

gs2352TACACSPlusAuthenticationServerTable OBJECT-TYPE
   SYNTAX      SEQUENCE OF Gs2352TACACSPlusAuthenticationServerEntry
   MAX-ACCESS  not-accessible
   STATUS      current
   DESCRIPTION
       " "
   ::= { gs2352AAA 5 }

gs2352TACACSPlusAuthenticationServerEntry OBJECT-TYPE
   SYNTAX      Gs2352TACACSPlusAuthenticationServerEntry
   MAX-ACCESS  not-accessible
   STATUS      current
   DESCRIPTION
       ""
   INDEX    { gs2352TACACSPlusAuthenticationServerIndex  }
   ::= { gs2352TACACSPlusAuthenticationServerTable 1 }

Gs2352TACACSPlusAuthenticationServerEntry ::= SEQUENCE {
   gs2352TACACSPlusAuthenticationServerIndex     Integer32,
   gs2352TACACSPlusAuthenticationServerEnable    INTEGER,
   gs2352TACACSPlusAuthenticationServerIP        DisplayString,
   gs2352TACACSPlusAuthenticationServerPort      Integer32,
   gs2352TACACSPlusAuthenticationServerSecret    DisplayString
}

gs2352TACACSPlusAuthenticationServerIndex OBJECT-TYPE
   SYNTAX      Integer32(1..5)
   MAX-ACCESS  not-accessible
   STATUS      current
   DESCRIPTION
       "TACACSPlus Authentication Server index
        range : 1-5."
   ::= { gs2352TACACSPlusAuthenticationServerEntry 1 }

gs2352TACACSPlusAuthenticationServerEnable OBJECT-TYPE
   SYNTAX      INTEGER { disable(0), enable(1) }
   MAX-ACCESS  read-write
   STATUS      current
   DESCRIPTION
       "Enable/Disable the TACACSPlus Authentication Server. The
       TACACSPlusAuthenticationServerEnable can be set, when IP and Secret have
       value."
   ::= { gs2352TACACSPlusAuthenticationServerEntry 2 }

gs2352TACACSPlusAuthenticationServerIP OBJECT-TYPE
   SYNTAX      DisplayString
   MAX-ACCESS  read-write
   STATUS      current
   DESCRIPTION
       "The IP address or hostname of the TACACSPlus Authentication Server.
       IP address is expressed in  dotted decimal notation. "
   ::= { gs2352TACACSPlusAuthenticationServerEntry 3 }

gs2352TACACSPlusAuthenticationServerPort OBJECT-TYPE
   SYNTAX      Integer32(0..65535)
   MAX-ACCESS  read-write
   STATUS      current
   DESCRIPTION
       "The UDP port to use on the TACACSPlus Authentication Server. If the
       port is set to 0 (zero), the default port (1812) is used on the
       TACACSPlus Authentication Server. "
   ::= { gs2352TACACSPlusAuthenticationServerEntry 4 }

gs2352TACACSPlusAuthenticationServerSecret OBJECT-TYPE
   SYNTAX      DisplayString
   MAX-ACCESS  read-write
   STATUS      current
   DESCRIPTION
       "The secret - up to 64 characters long - shared between the TACACSPlus Authentication Server and the switch. "
   ::= { gs2352TACACSPlusAuthenticationServerEntry 5 }


gs2352RADIUSStatisticsTable OBJECT-TYPE
   SYNTAX      SEQUENCE OF Gs2352RADIUSStatisticsEntry
   MAX-ACCESS  not-accessible
   STATUS      current
   DESCRIPTION
       " "
   ::= { gs2352AAA 6 }

gs2352RADIUSStatisticsEntry OBJECT-TYPE
   SYNTAX      Gs2352RADIUSStatisticsEntry
   MAX-ACCESS  not-accessible
   STATUS      current
   DESCRIPTION
       ""
   INDEX    { gs2352RADIUSAuthStatisticsServerIndex  }
   ::= { gs2352RADIUSStatisticsTable 1 }

Gs2352RADIUSStatisticsEntry ::= SEQUENCE {
   gs2352RADIUSAuthStatisticsServerIndex                           Integer32,
   gs2352RADIUSAuthStatisticsRecPktAccessAccepts                   Counter32,
   gs2352RADIUSAuthStatisticsRecPktAccessRejects                   Counter32,
   gs2352RADIUSAuthStatisticsRecPktAccessChallenges                Counter32,
   gs2352RADIUSAuthStatisticsRecPktMalformedAccResponses           Counter32,
   gs2352RADIUSAuthStatisticsRecPktBadAuthenticators               Counter32,
   gs2352RADIUSAuthStatisticsRecPktUnknownTypes                    Counter32,
   gs2352RADIUSAuthStatisticsRecPktDropped                         Counter32,
   gs2352RADIUSAuthStatisticsTransmitPktAccessRequests             Counter32,
   gs2352RADIUSAuthStatisticsTransmitPktAccessRetransmissions      Counter32,
   gs2352RADIUSAuthStatisticsTransmitPktPendingRequests            Counter32,
   gs2352RADIUSAuthStatisticsTransmitPktTimeouts                   Counter32,
   gs2352RADIUSAuthIP                                              DisplayString,
   gs2352RADIUSAuthState                                           DisplayString,
   gs2352RADIUSAuthRoundTripTime                                   DisplayString,

   gs2352RADIUSAccountingStatisticsRecPktResponses                 Counter32,
   gs2352RADIUSAccountingStatisticsRecPktMalformedResponses        Counter32,
   gs2352RADIUSAccountingStatisticsRecPktBadAuthenticators         Counter32,
   gs2352RADIUSAccountingStatisticsRecPktUnknownTypes              Counter32,
   gs2352RADIUSAccountingStatisticsRecPktDropped                   Counter32,
   gs2352RADIUSAccountingStatisticsTransmitPktRequests             Counter32,
   gs2352RADIUSAccountingStatisticsTransmitPktRetransmissions      Counter32,
   gs2352RADIUSAccountingStatisticsTransmitPktPendingRequests      Counter32,
   gs2352RADIUSAccountingStatisticsTransmitPktTimeouts             Counter32,
   gs2352RADIUSAccountingIP                                        DisplayString,
   gs2352RADIUSAccountingState                                     DisplayString,
   gs2352RADIUSAccountingRoundTripTime                             DisplayString,
   gs2352RADIUSStatisticsClear                                     INTEGER
}

gs2352RADIUSAuthStatisticsServerIndex OBJECT-TYPE
   SYNTAX      Integer32(1..5)
   MAX-ACCESS  not-accessible
   STATUS      current
   DESCRIPTION
       "RADIUS Authentication Server index
        range : 1-5."
   ::= { gs2352RADIUSStatisticsEntry 1 }

gs2352RADIUSAuthStatisticsRecPktAccessAccepts OBJECT-TYPE
   SYNTAX      Counter32
   MAX-ACCESS  read-only
   STATUS      current
   DESCRIPTION
       "The number of RADIUS Access-Accept packets (valid or invalid) received from the server."
   ::= { gs2352RADIUSStatisticsEntry 2 }

gs2352RADIUSAuthStatisticsRecPktAccessRejects OBJECT-TYPE
   SYNTAX      Counter32
   MAX-ACCESS  read-only
   STATUS      current
   DESCRIPTION
       "The number of RADIUS Access-Reject packets (valid or invalid) received from the server."
   ::= { gs2352RADIUSStatisticsEntry 3 }

gs2352RADIUSAuthStatisticsRecPktAccessChallenges OBJECT-TYPE
   SYNTAX      Counter32
   MAX-ACCESS  read-only
   STATUS      current
   DESCRIPTION
       "The number of RADIUS Access-Challenge packets (valid or invalid) received from the server. "
   ::= { gs2352RADIUSStatisticsEntry 4 }

gs2352RADIUSAuthStatisticsRecPktMalformedAccResponses OBJECT-TYPE
   SYNTAX      Counter32
   MAX-ACCESS  read-only
   STATUS      current
   DESCRIPTION
       "The number of malformed RADIUS Access-Response packets received from the
        server. Malformed packets include packets with an invalid length. Bad
        authenticators or Message Authenticator attributes or unknown types are
        not included as malformed access responses. "
   ::= { gs2352RADIUSStatisticsEntry 5 }

gs2352RADIUSAuthStatisticsRecPktBadAuthenticators OBJECT-TYPE
   SYNTAX      Counter32
   MAX-ACCESS  read-only
   STATUS      current
   DESCRIPTION
       "The number of RADIUS Access-Response packets containing invalid
       authenticators or Message Authenticator attributes received from the server."
   ::= { gs2352RADIUSStatisticsEntry 6 }

gs2352RADIUSAuthStatisticsRecPktUnknownTypes OBJECT-TYPE
   SYNTAX      Counter32
   MAX-ACCESS  read-only
   STATUS      current
   DESCRIPTION
       "The number of RADIUS packets that were received with unknown types from
       the server on the authentication port and dropped."
   ::= { gs2352RADIUSStatisticsEntry 7 }

gs2352RADIUSAuthStatisticsRecPktDropped OBJECT-TYPE
   SYNTAX      Counter32
   MAX-ACCESS  read-only
   STATUS      current
   DESCRIPTION
       "The number of RADIUS packets that were received from the server on the
       authentication port and dropped for some other reason."
   ::= { gs2352RADIUSStatisticsEntry 8 }

gs2352RADIUSAuthStatisticsTransmitPktAccessRequests OBJECT-TYPE
   SYNTAX      Counter32
   MAX-ACCESS  read-only
   STATUS      current
   DESCRIPTION
       "The number of RADIUS Access-Request packets sent to the server. This
       does not include retransmissions."
   ::= { gs2352RADIUSStatisticsEntry 9 }

gs2352RADIUSAuthStatisticsTransmitPktAccessRetransmissions OBJECT-TYPE
   SYNTAX      Counter32
   MAX-ACCESS  read-only
   STATUS      current
   DESCRIPTION
       "The number of RADIUS Access-Request packets retransmitted to the RADIUS
       authentication server."
   ::= { gs2352RADIUSStatisticsEntry 10 }

gs2352RADIUSAuthStatisticsTransmitPktPendingRequests OBJECT-TYPE
   SYNTAX      Counter32
   MAX-ACCESS  read-only
   STATUS      current
   DESCRIPTION
       "The number of RADIUS Access-Request packets destined for the server that
        have not yet timed out or received a response. This variable is
        incremented when an Access-Request is sent and decremented due to
        receipt of an Access-Accept, Access-Reject, Access-Challenge, timeout,
        or retransmission. "
   ::= { gs2352RADIUSStatisticsEntry 11 }

gs2352RADIUSAuthStatisticsTransmitPktTimeouts OBJECT-TYPE
   SYNTAX      Counter32
   MAX-ACCESS  read-only
   STATUS      current
   DESCRIPTION
       "The number of authentication timeouts to the server. After a timeout,
       the client may retry to the same server, send to a different server, or
       give up. A retry to the same server is counted as a retransmit as well as
        a timeout. A send to a different server is counted as a Request as well
        as a timeout. "
   ::= { gs2352RADIUSStatisticsEntry 12 }

gs2352RADIUSAuthIP OBJECT-TYPE
   SYNTAX      DisplayString
   MAX-ACCESS  read-only
   STATUS      current
   DESCRIPTION
       "IP address and UDP port for the authentication server in question."
   ::= { gs2352RADIUSStatisticsEntry 13 }

gs2352RADIUSAuthState OBJECT-TYPE
   SYNTAX      DisplayString
   MAX-ACCESS  read-only
   STATUS      current
   DESCRIPTION
       "Shows the state of the server. It takes one of the following values:
        Disabled: The selected server is disabled.
        Not Ready: The server is enabled, but IP communication is not yet up and running.
        Ready: The server is enabled, IP communication is up and running, and the RADIUS
         module is ready to accept access attempts.
        Dead (X seconds left): Access attempts were made to this server, but it did not
        reply within the configured timeout. The server has temporarily been disabled,
        but will get re-enabled when the dead-time expires. The number of seconds left
        before this occurs is displayed in parentheses. This state is only reachable
        when more than one server is enabled. "
   ::= { gs2352RADIUSStatisticsEntry 14 }

gs2352RADIUSAuthRoundTripTime OBJECT-TYPE
   SYNTAX      DisplayString
   MAX-ACCESS  read-only
   STATUS      current
   DESCRIPTION
       "The time interval (measured in milliseconds) between the most recent
       Access-Reply/Access-Challenge and the Access-Request that matched it from
        the RADIUS authentication server. The granularity of this measurement is
         100 ms. A value of 0 ms indicates that there hasn't been round-trip
         communication with the server yet. "
   ::= { gs2352RADIUSStatisticsEntry 15 }

gs2352RADIUSAccountingStatisticsRecPktResponses OBJECT-TYPE
   SYNTAX      Counter32
   MAX-ACCESS  read-only
   STATUS      current
   DESCRIPTION
       "The number of RADIUS packets (valid or invalid) received from the server."
   ::= { gs2352RADIUSStatisticsEntry 16 }

gs2352RADIUSAccountingStatisticsRecPktMalformedResponses OBJECT-TYPE
   SYNTAX      Counter32
   MAX-ACCESS  read-only
   STATUS      current
   DESCRIPTION
       "The number of malformed RADIUS packets received from the server.
       Malformed packets include packets with an invalid length. Bad
       authenticators or unknown types are not included as malformed access
       responses. "
   ::= { gs2352RADIUSStatisticsEntry 17 }

gs2352RADIUSAccountingStatisticsRecPktBadAuthenticators OBJECT-TYPE
   SYNTAX      Counter32
   MAX-ACCESS  read-only
   STATUS      current
   DESCRIPTION
       "The number of RADIUS packets containing invalid authenticators received
       from the server."
   ::= { gs2352RADIUSStatisticsEntry 18 }

gs2352RADIUSAccountingStatisticsRecPktUnknownTypes OBJECT-TYPE
   SYNTAX      Counter32
   MAX-ACCESS  read-only
   STATUS      current
   DESCRIPTION
       "The number of RADIUS packets of unknown types that were received from
       the server on the accounting port."
   ::= { gs2352RADIUSStatisticsEntry 19 }

gs2352RADIUSAccountingStatisticsRecPktDropped OBJECT-TYPE
   SYNTAX      Counter32
   MAX-ACCESS  read-only
   STATUS      current
   DESCRIPTION
       "The number of RADIUS packets that were received from the server on the
       accounting port and dropped for some other reason."
   ::= { gs2352RADIUSStatisticsEntry 20 }

gs2352RADIUSAccountingStatisticsTransmitPktRequests OBJECT-TYPE
   SYNTAX      Counter32
   MAX-ACCESS  read-only
   STATUS      current
   DESCRIPTION
       "The number of RADIUS packets sent to the server. This does not include
       retransmissions."
   ::= { gs2352RADIUSStatisticsEntry 21 }

gs2352RADIUSAccountingStatisticsTransmitPktRetransmissions OBJECT-TYPE
   SYNTAX      Counter32
   MAX-ACCESS  read-only
   STATUS      current
   DESCRIPTION
       "The number of RADIUS packets retransmitted to the RADIUS accounting server."
   ::= { gs2352RADIUSStatisticsEntry 22 }

gs2352RADIUSAccountingStatisticsTransmitPktPendingRequests OBJECT-TYPE
   SYNTAX      Counter32
   MAX-ACCESS  read-only
   STATUS      current
   DESCRIPTION
       "The number of RADIUS packets destined for the server that have not yet
       timed out or received a response. This variable is incremented when a
       Request is sent and decremented due to receipt of a Response, timeout,
       or retransmission. "
   ::= { gs2352RADIUSStatisticsEntry 23 }

gs2352RADIUSAccountingStatisticsTransmitPktTimeouts OBJECT-TYPE
   SYNTAX      Counter32
   MAX-ACCESS  read-only
   STATUS      current
   DESCRIPTION
       "The number of accounting timeouts to the server. After a timeout, the
       client may retry to the same server, send to a different server, or give
       up. A retry to the same server is counted as a retransmit as well as a
       timeout. A send to a different server is counted as a Request as well as
       a timeout. "
   ::= { gs2352RADIUSStatisticsEntry 24 }

gs2352RADIUSAccountingIP OBJECT-TYPE
   SYNTAX      DisplayString
   MAX-ACCESS  read-only
   STATUS      current
   DESCRIPTION
       "IP address and UDP port for the accounting server in question."
   ::= { gs2352RADIUSStatisticsEntry 25 }

gs2352RADIUSAccountingState OBJECT-TYPE
   SYNTAX      DisplayString
   MAX-ACCESS  read-only
   STATUS      current
   DESCRIPTION
       " Shows the state of the server. It takes one of the following values:
        Disabled: The selected server is disabled.
        Not Ready: The server is enabled, but IP communication is not yet up and running.
        Ready: The server is enabled, IP communication is up and running, and the RADIUS
        module is ready to accept accounting attempts.
        Dead (X seconds left): Accounting attempts were made to this server, but it did
        not reply within the configured timeout. The server has temporarily been
        disabled, but will get re-enabled when the dead-time expires. The number of
        seconds left before this occurs is displayed in parentheses. This state is only
        reachable when more than one server is enabled.  "
   ::= { gs2352RADIUSStatisticsEntry 26 }

gs2352RADIUSAccountingRoundTripTime OBJECT-TYPE
   SYNTAX      DisplayString
   MAX-ACCESS  read-only
   STATUS      current
   DESCRIPTION
       "The time interval (measured in milliseconds) between the most recent
       Response and the Request that matched it from the RADIUS accounting
       server. The granularity of this measurement is 100 ms. A value of 0 ms
       indicates that there hasn't been round-trip communication with the server
       yet. "
   ::= { gs2352RADIUSStatisticsEntry 27 }

gs2352RADIUSStatisticsClear OBJECT-TYPE
   SYNTAX      INTEGER(0|1)
   MAX-ACCESS  read-write
   STATUS      current
   DESCRIPTION
       "Clears the counters for the server.
       read: always 0
       clear: set 1"
   ::= { gs2352RADIUSStatisticsEntry 28 }


gs2352NAS                                              OBJECT IDENTIFIER ::= { gs2352Security 11 }

gs2352NASConfiguration                                 OBJECT IDENTIFIER ::= { gs2352NAS 1 }

gs2352NASConfigMode OBJECT-TYPE
   SYNTAX      INTEGER { disable(0), enable(1) }
   MAX-ACCESS  read-write
   STATUS      current
   DESCRIPTION
       "Indicates if NAS is globally enabled or disabled on the switch.
	    If globally disabled, all ports are allowed forwarding of frames."
   ::= { gs2352NASConfiguration 1 }

gs2352NASConfigReauthEnabled OBJECT-TYPE
   SYNTAX      INTEGER { disable(0), enable(1) }
   MAX-ACCESS  read-write
   STATUS      current
   DESCRIPTION
       "If checked, successfully authenticated supplicants/clients are
	    reauthenticated after the interval specified by the Reauthentication
		Period. Reauthentication for 802.1X-enabled ports can be used to
		detect if a new device is plugged into a switch port or if a
		supplicant is no longer attached.
		For MAC-based ports, reauthentication is only useful if the RADIUS
		server configuration has changed. It does not involve communication
		between the switch and the client, and therefore doesn't imply that
		a client is still present on a port."
   ::= { gs2352NASConfiguration 2 }

gs2352NASConfigReauthPeriod OBJECT-TYPE
   SYNTAX      Integer32(1..3600)
   MAX-ACCESS  read-write
   STATUS      current
   DESCRIPTION
       "Determines the period, in seconds, after which a connected client must
	    be reauthenticated. This is only active if the Reauthentication Enabled
		checkbox is checked.
		range: 1 - 3600 seconds."
   ::= { gs2352NASConfiguration 3 }

gs2352NASConfigEAPOLTimeout OBJECT-TYPE
   SYNTAX      Integer32(1..65535)
   MAX-ACCESS  read-write
   STATUS      current
   DESCRIPTION
       "Determines the time for retransmission of Request Identity EAPOL frames.
	    This has no effect for MAC-based ports.
		range: 1 - 65535 seconds."
   ::= { gs2352NASConfiguration 4 }

gs2352NASConfigAgingPeriod OBJECT-TYPE
   SYNTAX      Integer32(10..1000000)
   MAX-ACCESS  read-write
   STATUS      current
   DESCRIPTION
       "When the NAS module uses the Port Security module to secure MAC addresses,
	    the Port Security module needs to check for activity on the MAC address
		in question at regular intervals and free resources if no activity
		is seen within a given period of time.
		Admin State supported : Single, Multi and MAC-Based Auth. 802.1X.
		range: 10 - 1000000 seconds."
   ::= { gs2352NASConfiguration 5 }

gs2352NASConfigHoldTime OBJECT-TYPE
   SYNTAX      Integer32(10..1000000)
   MAX-ACCESS  read-write
   STATUS      current
   DESCRIPTION
       "If a client is denied access - either because the RADIUS server denies
	    the client access or because the RADIUS server request times out
		- the client is put on hold in the Unauthorized state. The hold timer
		does not count during an on-going authentication. In MAC-based Auth.
		mode, the switch will ignore new frames coming from the client during
		the hold time.
		Admin State supported : Single, Multi and MAC-Based Auth. 802.1X.
		range: 10 - 1000000 seconds."
   ::= { gs2352NASConfiguration 6 }

gs2352NASConfigRADIUSAssignedQoSEnabled OBJECT-TYPE
   SYNTAX      INTEGER { disable(0), enable(1) }
   MAX-ACCESS  read-write
   STATUS      current
   DESCRIPTION
       "RADIUS-assigned QoS provides a means to centrally control the
	    traffic class to which traffic coming from a successfully authenticated
		supplicant is assigned on the switch. The RADIUS server must be configured
		to transmit special RADIUS attributes to take advantage of this feature."
   ::= { gs2352NASConfiguration 7 }

gs2352NASConfigRADIUSAssignedVLANEnabled OBJECT-TYPE
   SYNTAX      INTEGER { disable(0), enable(1) }
   MAX-ACCESS  read-write
   STATUS      current
   DESCRIPTION
       "RADIUS-assigned VLAN provides a means to centrally control the VLAN on
	    which a successfully authenticated supplicant is placed on the switch.
	    Incoming traffic will be classified to and switched on the RADIUS-assigned
		VLAN. The RADIUS server must be configured to transmit special RADIUS
		attributes to take advantage of this feature.When enable, the individual
		ports' ditto setting determine whether RADIUS-assigned VLAN is enabled
		on that port. When disable, RADIUS-server assigned VLAN is disabled on
		all ports. "
   ::= { gs2352NASConfiguration 8 }

gs2352NASConfigGuestVLANEnabled OBJECT-TYPE
   SYNTAX      INTEGER { disable(0), enable(1) }
   MAX-ACCESS  read-write
   STATUS      current
   DESCRIPTION
       "A Guest VLAN is a special VLAN - typically with limited network access -
	   on which 802.1X-unaware clients are placed after a network administrator-defined
	   timeout. The switch follows a set of rules for entering and leaving the Guest
	   VLAN as listed below.When enable, the individual ports' ditto setting determines
	   whether the port can be moved into Guest VLAN. When disable, the ability to
	   move to the Guest VLAN is disabled on all ports. "
   ::= { gs2352NASConfiguration 9 }

gs2352NASConfigGuestVLANID OBJECT-TYPE
   SYNTAX      Integer32(1..4094)
   MAX-ACCESS  read-write
   STATUS      current
   DESCRIPTION
       "This is the value that a port's Port VLAN ID is set to if a port is moved into
	   the Guest VLAN. It is only changeable if the Guest VLAN option is globally enabled.
	   range: 1 - 4094."
   ::= { gs2352NASConfiguration 10 }

gs2352NASConfigMaxReauthCount OBJECT-TYPE
   SYNTAX      Integer32(1..255)
   MAX-ACCESS  read-write
   STATUS      current
   DESCRIPTION
       "The number of times the switch transmits an EAPOL Request Identity frame without
	   response before considering entering the Guest VLAN is adjusted with this setting.
	   The value can only be changed if the Guest VLAN option is globally enabled.
	   range: 1 - 255."
   ::= { gs2352NASConfiguration 11 }

gs2352NASConfigAllowGuestVLANEAPOLSeen OBJECT-TYPE
   SYNTAX      INTEGER { disable(0), enable(1) }
   MAX-ACCESS  read-write
   STATUS      current
   DESCRIPTION
       "The switch remembers if an EAPOL frame has been received on the port for the
	   life-time of the port. Once the switch considers whether to enter the Guest VLAN,
	   it will first check if this option is enabled or disabled. If disabled, the switch
	   will only enter the Guest VLAN if an EAPOL frame has not been received on the port
	   for the life-time of the port. If enabled (checked), the switch will consider
	   entering the Guest VLAN even if an EAPOL frame has been received on the port for
	   the life-time of the port.The value can only be changed if the Guest VLAN option
	   is globally enabled."
   ::= { gs2352NASConfiguration 12 }

gs2352NASConfigMacBasedUseEAP OBJECT-TYPE
   SYNTAX      INTEGER { disable(0), enable(1) }
   MAX-ACCESS  read-write
   STATUS      current
   DESCRIPTION
       "The switch can do the RADIUS authentication on behalf of the client in the
       MAC-based Auth. port authentication mode. It can either present itself as a
       normal 802.1X client to the RADIUS Server and use EAP, supporting only the
       MD5-Challenge, or alternativly can use plain RADIUS with username / passwort
       authentification without EAP if this setting is disabled."
   ::= { gs2352NASConfiguration 101 }

gs2352NASPortConfigTable OBJECT-TYPE
   SYNTAX      SEQUENCE OF Gs2352NASPortConfigEntry
   MAX-ACCESS  not-accessible
   STATUS      current
   DESCRIPTION
       ""
   ::= { gs2352NASConfiguration 13 }

gs2352NASPortConfigEntry OBJECT-TYPE
   SYNTAX      Gs2352NASPortConfigEntry
   MAX-ACCESS  not-accessible
   STATUS      current
   DESCRIPTION
       ""
   INDEX    { gs2352NASPortConfigPort }
   ::= { gs2352NASPortConfigTable 1 }

Gs2352NASPortConfigEntry ::= SEQUENCE {
   gs2352NASPortConfigPort                       Integer32,
   gs2352NASPortConfigAdminState                 INTEGER,
   gs2352NASPortConfigRADIUSAssignedQoSEnabled	  INTEGER,
   gs2352NASPortConfigRADIUSAssignedVLANEnabled  INTEGER,
   gs2352NASPortConfigGuestVLANEnabled           INTEGER,
   gs2352NASPortConfigFallbackEnabled            INTEGER,
   gs2352NASPortConfigPortState                  DisplayString,
   gs2352NASPortConfigReauthenticate             INTEGER,
   gs2352NASPortConfigReinitialize               INTEGER
}

gs2352NASPortConfigPort OBJECT-TYPE
   SYNTAX      Integer32(1..255)
   MAX-ACCESS  not-accessible
   STATUS      current
   DESCRIPTION
       " port, range : 1 - port number. "
   ::= { gs2352NASPortConfigEntry 1 }

gs2352NASPortConfigAdminState OBJECT-TYPE
   SYNTAX      INTEGER{ forceAuthorized(1),
						forceUnauthorized(2),
						portBased(3),
						single(4),
						multi(5),
						macBased(6),
						macBasedSingle(7)
					  }
   MAX-ACCESS  read-write
   STATUS      current
   DESCRIPTION
       "This selection controls the port's authentication mode.
		1: Force Authorized,
		2: Force Unauthorized,
		3: Port-based 802.1X,
		4: Single 802.1X,
		5: Multi 802.1X,
		6: MAC-based Auth,
		7: MAC-based Single Auth."
   ::= { gs2352NASPortConfigEntry 2 }

gs2352NASPortConfigRADIUSAssignedQoSEnabled OBJECT-TYPE
   SYNTAX      INTEGER { disable(0), enable(1) }
   MAX-ACCESS  read-write
   STATUS      current
   DESCRIPTION
       "When RADIUS-Assigned QoS is both globally enabled and enabled (checked)
	    on a given port, the switch reacts to QoS Class information carried in
		the RADIUS Access-Accept packet transmitted by the RADIUS server when a
		supplicant is successfully authenticated. If present and valid, traffic
		received on the supplicant's port will be classified to the given QoS Class.
		Admin State supported : Port-based and Single 802.1X and MAC-based Single Auth."
   ::= { gs2352NASPortConfigEntry 3 }

gs2352NASPortConfigRADIUSAssignedVLANEnabled OBJECT-TYPE
   SYNTAX      INTEGER { disable(0), enable(1) }
   MAX-ACCESS  read-write
   STATUS      current
   DESCRIPTION
       "When RADIUS-Assigned VLAN is both globally enabled and enabled (checked)
	   for a given port, the switch reacts to VLAN ID information carried in the
	   RADIUS Access-Accept packet transmitted by the RADIUS server when a supplicant
	   is successfully authenticated. If present and valid, the port's Port VLAN ID
	   will be changed to this VLAN ID, the port will be set to be a member of that
	   VLAN ID, and the port will be forced into VLAN unaware mode. Once assigned,
	   all traffic arriving on the port will be classified and switched on the
	   RADIUS-assigned VLAN ID.
	   Admin State supported : Port-based and Single 802.1X and MAC-based Single Auth."
   ::= { gs2352NASPortConfigEntry 4 }

gs2352NASPortConfigGuestVLANEnabled OBJECT-TYPE
   SYNTAX      INTEGER { disable(0), enable(1) }
   MAX-ACCESS  read-write
   STATUS      current
   DESCRIPTION
       "When Guest VLAN is both globally enabled and enabled (checked) for a given port,
	   the switch considers moving the port into the Guest VLAN according to the rules
	   outlined below.
	   Admin State supported : Port-based , Single and Multi 802.1X."
   ::= { gs2352NASPortConfigEntry 5 }

gs2352NASPortConfigPortState OBJECT-TYPE
   SYNTAX      DisplayString
   MAX-ACCESS  read-only
   STATUS      current
   DESCRIPTION
       "Globally Disabled: NAS is globally disabled.
		Link Down: NAS is globally enabled, but there is no link on the port.
		Authorized: The port is in Force Authorized or a single-supplicant mode
		and the supplicant is authorized.
		Unauthorized: The port is in Force Unauthorized or a single-supplicant
		mode and the supplicant is not successfully authorized by the RADIUS server.
		X Auth/Y Unauth: The port is in a multi-supplicant mode. Currently X clients
		are authorized and Y are unauthorized."
   ::= { gs2352NASPortConfigEntry 6 }

gs2352NASPortConfigReauthenticate OBJECT-TYPE
   SYNTAX      INTEGER { doNothing(0), do(1) }
   MAX-ACCESS  read-write
   STATUS      current
   DESCRIPTION
       "Schedules a reauthentication whenever the quiet-period of the port runs out
	   (EAPOL-based authentication). For MAC-based authentication, reauthentication
	   will be attempted immediately.The button only has effect for successfully
	   authenticated clients on the port and will not cause the clients to get
	   temporarily unauthorized."
   ::= { gs2352NASPortConfigEntry 7 }

gs2352NASPortConfigReinitialize OBJECT-TYPE
   SYNTAX      INTEGER { doNothing(0), do(1) }
   MAX-ACCESS  read-write
   STATUS      current
   DESCRIPTION
       "Forces a reinitialization of the clients on the port and thereby a reauthentication
	   immediately. The clients will transfer to the unauthorized state while the
	   reauthentication is in progress."
   ::= { gs2352NASPortConfigEntry 8 }

gs2352NASPortConfigFallbackEnabled OBJECT-TYPE
   SYNTAX      INTEGER { disable(0), enable(1) }
   MAX-ACCESS  read-write
   STATUS      current
   DESCRIPTION
       "When Fallback is enabled, the switch will take over the supplicants role
       after max reauthentication count is reached and tries to authenticate the
       client on its behalf as described for MAC-based Auth.
       Admin State supported : Single and Multi 802.1X."
   ::= { gs2352NASPortConfigEntry 101 }

gs2352NASSwitchStatusTable OBJECT-TYPE
   SYNTAX      SEQUENCE OF Gs2352NASSwitchStatusEntry
   MAX-ACCESS  not-accessible
   STATUS      current
   DESCRIPTION
       ""
   ::= { gs2352NAS 2 }

gs2352NASSwitchStatusEntry OBJECT-TYPE
   SYNTAX      Gs2352NASSwitchStatusEntry
   MAX-ACCESS  not-accessible
   STATUS      current
   DESCRIPTION
       ""
   INDEX    { gs2352NASPortConfigPort }
   ::= { gs2352NASSwitchStatusTable 1 }

Gs2352NASSwitchStatusEntry ::= SEQUENCE {
   gs2352NASSwitchStatusAdminState 	DisplayString,
   gs2352NASSwitchStatusPortState		DisplayString,
   gs2352NASSwitchStatusLastSource		DisplayString,
   gs2352NASSwitchStatusLastID			DisplayString,
   gs2352NASSwitchStatusQoSClass		DisplayString,
   gs2352NASSwitchStatusPortVlanID		DisplayString
}

gs2352NASSwitchStatusAdminState OBJECT-TYPE
   SYNTAX      DisplayString
   MAX-ACCESS  read-only
   STATUS      current
   DESCRIPTION
       "The port's current administrative state. Refer to NAS Admin State for a description of possible values."
   ::= { gs2352NASSwitchStatusEntry 2 }

gs2352NASSwitchStatusPortState OBJECT-TYPE
   SYNTAX      DisplayString
   MAX-ACCESS  read-only
   STATUS      current
   DESCRIPTION
       "The current state of the port. Refer to NAS Port State for a description of the individual states."
   ::= { gs2352NASSwitchStatusEntry 3 }

gs2352NASSwitchStatusLastSource OBJECT-TYPE
   SYNTAX      DisplayString
   MAX-ACCESS  read-only
   STATUS      current
   DESCRIPTION
       "The source MAC address carried in the most recently received EAPOL frame for EAPOL-based authentication,
	   and the most recently received frame from a new client for MAC-based authentication."
   ::= { gs2352NASSwitchStatusEntry 4 }

gs2352NASSwitchStatusLastID OBJECT-TYPE
   SYNTAX      DisplayString
   MAX-ACCESS  read-only
   STATUS      current
   DESCRIPTION
       "The user name (supplicant identity) carried in the most recently received Response Identity EAPOL frame
	   for EAPOL-based authentication, and the source MAC address from the most recently received frame from a
	   new client for MAC-based authentication."
   ::= { gs2352NASSwitchStatusEntry 5 }

gs2352NASSwitchStatusQoSClass OBJECT-TYPE
   SYNTAX      DisplayString
   MAX-ACCESS  read-only
   STATUS      current
   DESCRIPTION
       "QoS Class assigned to the port by the RADIUS server if enabled."
   ::= { gs2352NASSwitchStatusEntry 6 }

gs2352NASSwitchStatusPortVlanID OBJECT-TYPE
   SYNTAX      DisplayString
   MAX-ACCESS  read-only
   STATUS      current
   DESCRIPTION
       "The VLAN ID that NAS has put the port in. The field is blank, if the Port VLAN ID is not overridden by NAS."
   ::= { gs2352NASSwitchStatusEntry 7 }

gs2352NASPortStatus                                 OBJECT IDENTIFIER ::= { gs2352NAS 3 }

gs2352NASPortStatusCountersTable OBJECT-TYPE
   SYNTAX      SEQUENCE OF Gs2352NASPortStatusCountersEntry
   MAX-ACCESS  not-accessible
   STATUS      current
   DESCRIPTION
       ""
   ::= { gs2352NASPortStatus 1 }

gs2352NASPortStatusCountersEntry OBJECT-TYPE
   SYNTAX      Gs2352NASPortStatusCountersEntry
   MAX-ACCESS  not-accessible
   STATUS      current
   DESCRIPTION
       ""
   INDEX    { gs2352NASPortConfigPort }
   ::= { gs2352NASPortStatusCountersTable 1 }

Gs2352NASPortStatusCountersEntry ::= SEQUENCE {
   gs2352NASRxCountersEAPOLTotal  	                  Counter32,
   gs2352NASRxCountersEAPOLResponseID	              Counter32,
   gs2352NASRxCountersEAPOLResponses	              Counter32,
   gs2352NASRxCountersEAPOLStart	                  Counter32,
   gs2352NASRxCountersEAPOLLogoff                    Counter32,
   gs2352NASRxCountersEAPOLInvalidType               Counter32,
   gs2352NASRxCountersEAPOLInvalidLength             Counter32,
   gs2352NASTxCountersEAPOLTotal                     Counter32,
   gs2352NASTxCountersEAPOLRequestID                 Counter32,
   gs2352NASTxCountersEAPOLRequests                  Counter32,
   gs2352NASRxBackendServerCountersAccessChallenges  Counter32,
   gs2352NASRxBackendServerCountersOtherRequests     Counter32,
   gs2352NASRxBackendServerCountersAuthSuccesses     Counter32,
   gs2352NASRxBackendServerCountersAuthFailures      Counter32,
   gs2352NASTxBackendServerCountersResponses         Counter32,
   gs2352NASLastSupplicantInfoMACAddress             DisplayString,
   gs2352NASLastSupplicantInfoVlanID                 Integer32,
   gs2352NASLastSupplicantInfoVersion                Integer32,
   gs2352NASLastSupplicantInfoIdentity               DisplayString,
   gs2352NASCountersDoClear                          INTEGER
}

gs2352NASRxCountersEAPOLTotal OBJECT-TYPE
   SYNTAX      Counter32
   MAX-ACCESS  read-only
   STATUS      current
   DESCRIPTION
       "The number of valid EAPOL frames of any type that have been received by the switch."
   ::= { gs2352NASPortStatusCountersEntry 2 }

gs2352NASRxCountersEAPOLResponseID OBJECT-TYPE
   SYNTAX      Counter32
   MAX-ACCESS  read-only
   STATUS      current
   DESCRIPTION
       "The number of valid EAPOL Response Identity frames that have been received by the switch."
   ::= { gs2352NASPortStatusCountersEntry 3 }

gs2352NASRxCountersEAPOLResponses OBJECT-TYPE
   SYNTAX      Counter32
   MAX-ACCESS  read-only
   STATUS      current
   DESCRIPTION
       "The number of valid EAPOL response frames (other than Response Identity frames)
	   that have been received by the switch."
   ::= { gs2352NASPortStatusCountersEntry 4 }

gs2352NASRxCountersEAPOLStart OBJECT-TYPE
   SYNTAX      Counter32
   MAX-ACCESS  read-only
   STATUS      current
   DESCRIPTION
       "The number of EAPOL Start frames that have been received by the switch."
   ::= { gs2352NASPortStatusCountersEntry 5 }

gs2352NASRxCountersEAPOLLogoff OBJECT-TYPE
   SYNTAX      Counter32
   MAX-ACCESS  read-only
   STATUS      current
   DESCRIPTION
       "The number of valid EAPOL Logoff frames that have been received by the switch."
   ::= { gs2352NASPortStatusCountersEntry 6 }

gs2352NASRxCountersEAPOLInvalidType OBJECT-TYPE
   SYNTAX      Counter32
   MAX-ACCESS  read-only
   STATUS      current
   DESCRIPTION
       "The number of EAPOL frames that have been received by the switch in which
	   the frame type is not recognized."
   ::= { gs2352NASPortStatusCountersEntry 7 }

gs2352NASRxCountersEAPOLInvalidLength OBJECT-TYPE
   SYNTAX      Counter32
   MAX-ACCESS  read-only
   STATUS      current
   DESCRIPTION
       "The number of EAPOL frames that have been received by the switch in which the
	   Packet Body Length field is invalid."
   ::= { gs2352NASPortStatusCountersEntry 8 }

gs2352NASTxCountersEAPOLTotal OBJECT-TYPE
   SYNTAX      Counter32
   MAX-ACCESS  read-only
   STATUS      current
   DESCRIPTION
       "The number of EAPOL frames of any type that have been transmitted by the switch."
   ::= { gs2352NASPortStatusCountersEntry 9 }

gs2352NASTxCountersEAPOLRequestID OBJECT-TYPE
   SYNTAX      Counter32
   MAX-ACCESS  read-only
   STATUS      current
   DESCRIPTION
       "The number of EAPOL Request Identity frames that have been transmitted by the switch."
   ::= { gs2352NASPortStatusCountersEntry 10 }

gs2352NASTxCountersEAPOLRequests OBJECT-TYPE
   SYNTAX      Counter32
   MAX-ACCESS  read-only
   STATUS      current
   DESCRIPTION
       "The number of valid EAPOL Request frames (other than Request Identity frames)
	   that have been transmitted by the switch."
   ::= { gs2352NASPortStatusCountersEntry 11 }

gs2352NASRxBackendServerCountersAccessChallenges OBJECT-TYPE
   SYNTAX      Counter32
   MAX-ACCESS  read-only
   STATUS      current
   DESCRIPTION
       "802.1X-based: Counts the number of times that the switch receives the first request
	   from the backend server following the first response from the supplicant.
	   MAC-based: Counts all Access Challenges received from the backend server for this
	   port or client."
   ::= { gs2352NASPortStatusCountersEntry 12 }

gs2352NASRxBackendServerCountersOtherRequests OBJECT-TYPE
   SYNTAX      Counter32
   MAX-ACCESS  read-only
   STATUS      current
   DESCRIPTION
       "802.1X-based: Counts the number of times that the switch sends an EAP Request
	   packet following the first to the supplicant.
	   MAC-based: Not applicable."
   ::= { gs2352NASPortStatusCountersEntry 13 }

gs2352NASRxBackendServerCountersAuthSuccesses OBJECT-TYPE
   SYNTAX      Counter32
   MAX-ACCESS  read-only
   STATUS      current
   DESCRIPTION
       "Counts the number of times that the switch receives a success indication.
	   Indicates that the supplicant/client has successfully authenticated to the
	   backend server."
   ::= { gs2352NASPortStatusCountersEntry 14 }

gs2352NASRxBackendServerCountersAuthFailures OBJECT-TYPE
   SYNTAX      Counter32
   MAX-ACCESS  read-only
   STATUS      current
   DESCRIPTION
       "Counts the number of times that the switch receives a failure message.
	   This indicates that the supplicant/client has not authenticated to the
	   backend server. "
   ::= { gs2352NASPortStatusCountersEntry 15 }

gs2352NASTxBackendServerCountersResponses OBJECT-TYPE
   SYNTAX      Counter32
   MAX-ACCESS  read-only
   STATUS      current
   DESCRIPTION
       "802.1X-based: Counts the number of times that the switch attempts to
	   send a supplicant's first response packet to the backend server. Indicates
	   the switch attempted communication with the backend server. Possible
	   retransmissions are not counted.
	   MAC-based: Counts all the backend server packets sent from the switch
	   towards the backend server for a given port or client. Possible
	   retransmissions are not counted."
   ::= { gs2352NASPortStatusCountersEntry 16 }

gs2352NASLastSupplicantInfoMACAddress OBJECT-TYPE
   SYNTAX      DisplayString
   MAX-ACCESS  read-only
   STATUS      current
   DESCRIPTION
       "The MAC address of the last supplicant/client."
   ::= { gs2352NASPortStatusCountersEntry 17 }

gs2352NASLastSupplicantInfoVlanID OBJECT-TYPE
   SYNTAX      Integer32
   MAX-ACCESS  read-only
   STATUS      current
   DESCRIPTION
       "The VLAN ID on which the last frame from the last supplicant/client was received."
   ::= { gs2352NASPortStatusCountersEntry 18 }

gs2352NASLastSupplicantInfoVersion OBJECT-TYPE
   SYNTAX      Integer32
   MAX-ACCESS  read-only
   STATUS      current
   DESCRIPTION
       "802.1X-based: The protocol version number carried in the most recently
	   received EAPOL frame.
	   MAC-based: Not applicable."
   ::= { gs2352NASPortStatusCountersEntry 19 }

gs2352NASLastSupplicantInfoIdentity OBJECT-TYPE
   SYNTAX      DisplayString
   MAX-ACCESS  read-only
   STATUS      current
   DESCRIPTION
       "802.1X-based: The user name (supplicant identity) carried in the most recently received
	   Response Identity EAPOL frame.
	   MAC-based: Not applicable."
   ::= { gs2352NASPortStatusCountersEntry 20 }

gs2352NASCountersDoClear OBJECT-TYPE
   SYNTAX      INTEGER { doNothing(0), do(1) }
   MAX-ACCESS  read-write
   STATUS      current
   DESCRIPTION
       "Clear the counters for the selected port."
   ::= { gs2352NASPortStatusCountersEntry 21 }

gs2352NASPortStatusClientsTable OBJECT-TYPE
   SYNTAX      SEQUENCE OF Gs2352NASPortStatusClientsEntry
   MAX-ACCESS  not-accessible
   STATUS      current
   DESCRIPTION
       ""
   ::= { gs2352NASPortStatus 2 }

gs2352NASPortStatusClientsEntry OBJECT-TYPE
   SYNTAX      Gs2352NASPortStatusClientsEntry
   MAX-ACCESS  not-accessible
   STATUS      current
   DESCRIPTION
       ""
   INDEX    { gs2352NASPortConfigPort,
		gs2352NASClientsIndex}
   ::= { gs2352NASPortStatusClientsTable 1 }

Gs2352NASPortStatusClientsEntry ::= SEQUENCE {
   gs2352NASClientsIndex  	                  		    Integer32,
   gs2352NASClientsIdentity							DisplayString,
   gs2352NASClientsMACAddress  	                  	DisplayString,
   gs2352NASClientsVlanID		              			Integer32,
   gs2352NASClientsState	              				DisplayString,
   gs2352NASClientsLastAuth	                  		DisplayString,
   gs2352NASRxClientsEAPOLTotal  	                  	Counter32,
   gs2352NASRxClientsEAPOLResponseID	              	Counter32,
   gs2352NASRxClientsEAPOLResponses	              	Counter32,
   gs2352NASRxClientsEAPOLStart	                  	Counter32,
   gs2352NASRxClientsEAPOLLogoff                    	Counter32,
   gs2352NASRxClientsEAPOLInvalidType               	Counter32,
   gs2352NASRxClientsEAPOLInvalidLength             	Counter32,
   gs2352NASTxClientsEAPOLTotal                     	Counter32,
   gs2352NASTxClientsEAPOLRequestID                 	Counter32,
   gs2352NASTxClientsEAPOLRequests                  	Counter32,
   gs2352NASRxBackendServerClientsAccessChallenges  	Counter32,
   gs2352NASRxBackendServerClientsOtherRequests     	Counter32,
   gs2352NASRxBackendServerClientsAuthSuccesses     	Counter32,
   gs2352NASRxBackendServerClientsAuthFailures      	Counter32,
   gs2352NASTxBackendServerClientsResponses         	Counter32
}

gs2352NASClientsIndex OBJECT-TYPE
   SYNTAX      Integer32(1..255)
   MAX-ACCESS  not-accessible
   STATUS      current
   DESCRIPTION
       "Entry of client table in the port."
   ::= { gs2352NASPortStatusClientsEntry 1 }

gs2352NASClientsIdentity OBJECT-TYPE
   SYNTAX      DisplayString
   MAX-ACCESS  read-only
   STATUS      current
   DESCRIPTION
       "Shows the identity of the supplicant, as received in the Response Identity
	   EAPOL frame.This isn't available for MAC-based Auth."
   ::= { gs2352NASPortStatusClientsEntry 2 }

gs2352NASClientsMACAddress OBJECT-TYPE
   SYNTAX      DisplayString
   MAX-ACCESS  read-only
   STATUS      current
   DESCRIPTION
       "Multi 802.1X, this column holds the MAC address of the attached supplicant.
	   MAC-based Auth., this column holds the MAC address of the attached client."
   ::= { gs2352NASPortStatusClientsEntry 3 }

gs2352NASClientsVlanID OBJECT-TYPE
   SYNTAX      Integer32(1..4095)
   MAX-ACCESS  read-only
   STATUS      current
   DESCRIPTION
       "This column holds the VLAN ID that the corresponding client is currently
	   secured through the Port Security module."
   ::= { gs2352NASPortStatusClientsEntry 4 }

gs2352NASClientsState OBJECT-TYPE
   SYNTAX      DisplayString
   MAX-ACCESS  read-only
   STATUS      current
   DESCRIPTION
       "The client can either be authenticated or unauthenticated. In the authenticated
	   state, it is allowed to forward frames on the port, and in the unauthenticated
	   state, it is blocked."
   ::= { gs2352NASPortStatusClientsEntry 5 }

gs2352NASClientsLastAuth OBJECT-TYPE
   SYNTAX      DisplayString
   MAX-ACCESS  read-only
   STATUS      current
   DESCRIPTION
       "Shows the date and time of the last authentication of the client."
   ::= { gs2352NASPortStatusClientsEntry 6 }

gs2352NASRxClientsEAPOLTotal OBJECT-TYPE
   SYNTAX      Counter32
   MAX-ACCESS  read-only
   STATUS      current
   DESCRIPTION
       "The number of valid EAPOL frames of any type that have been received by the switch."
   ::= { gs2352NASPortStatusClientsEntry 7 }

gs2352NASRxClientsEAPOLResponseID OBJECT-TYPE
   SYNTAX      Counter32
   MAX-ACCESS  read-only
   STATUS      current
   DESCRIPTION
       "The number of valid EAPOL Response Identity frames that have been received by the switch."
   ::= { gs2352NASPortStatusClientsEntry 8 }

gs2352NASRxClientsEAPOLResponses OBJECT-TYPE
   SYNTAX      Counter32
   MAX-ACCESS  read-only
   STATUS      current
   DESCRIPTION
       "The number of valid EAPOL response frames (other than Response Identity frames)
	   that have been received by the switch."
   ::= { gs2352NASPortStatusClientsEntry 9 }

gs2352NASRxClientsEAPOLStart OBJECT-TYPE
   SYNTAX      Counter32
   MAX-ACCESS  read-only
   STATUS      current
   DESCRIPTION
       "The number of EAPOL Start frames that have been received by the switch."
   ::= { gs2352NASPortStatusClientsEntry 10 }

gs2352NASRxClientsEAPOLLogoff OBJECT-TYPE
   SYNTAX      Counter32
   MAX-ACCESS  read-only
   STATUS      current
   DESCRIPTION
       "The number of valid EAPOL Logoff frames that have been received by the switch."
   ::= { gs2352NASPortStatusClientsEntry 11 }

gs2352NASRxClientsEAPOLInvalidType OBJECT-TYPE
   SYNTAX      Counter32
   MAX-ACCESS  read-only
   STATUS      current
   DESCRIPTION
       "The number of EAPOL frames that have been received by the switch in which
	   the frame type is not recognized."
   ::= { gs2352NASPortStatusClientsEntry 12 }

gs2352NASRxClientsEAPOLInvalidLength OBJECT-TYPE
   SYNTAX      Counter32
   MAX-ACCESS  read-only
   STATUS      current
   DESCRIPTION
       "The number of EAPOL frames that have been received by the switch in which the
	   Packet Body Length field is invalid."
   ::= { gs2352NASPortStatusClientsEntry 13 }

gs2352NASTxClientsEAPOLTotal OBJECT-TYPE
   SYNTAX      Counter32
   MAX-ACCESS  read-only
   STATUS      current
   DESCRIPTION
       "The number of EAPOL frames of any type that have been transmitted by the switch."
   ::= { gs2352NASPortStatusClientsEntry 14 }

gs2352NASTxClientsEAPOLRequestID OBJECT-TYPE
   SYNTAX      Counter32
   MAX-ACCESS  read-only
   STATUS      current
   DESCRIPTION
       "The number of EAPOL Request Identity frames that have been transmitted by the switch."
   ::= { gs2352NASPortStatusClientsEntry 15 }

gs2352NASTxClientsEAPOLRequests OBJECT-TYPE
   SYNTAX      Counter32
   MAX-ACCESS  read-only
   STATUS      current
   DESCRIPTION
       "The number of valid EAPOL Request frames (other than Request Identity frames)
	   that have been transmitted by the switch."
   ::= { gs2352NASPortStatusClientsEntry 16 }

gs2352NASRxBackendServerClientsAccessChallenges OBJECT-TYPE
   SYNTAX      Counter32
   MAX-ACCESS  read-only
   STATUS      current
   DESCRIPTION
       "802.1X-based: Counts the number of times that the switch receives the first request
	   from the backend server following the first response from the supplicant.
	   MAC-based: Counts all Access Challenges received from the backend server for this
	   port or client."
   ::= { gs2352NASPortStatusClientsEntry 17 }

gs2352NASRxBackendServerClientsOtherRequests OBJECT-TYPE
   SYNTAX      Counter32
   MAX-ACCESS  read-only
   STATUS      current
   DESCRIPTION
       "802.1X-based: Counts the number of times that the switch sends an EAP Request
	   packet following the first to the supplicant.
	   MAC-based: Not applicable."
   ::= { gs2352NASPortStatusClientsEntry 18 }

gs2352NASRxBackendServerClientsAuthSuccesses OBJECT-TYPE
   SYNTAX      Counter32
   MAX-ACCESS  read-only
   STATUS      current
   DESCRIPTION
       "Counts the number of times that the switch receives a success indication.
	   Indicates that the supplicant/client has successfully authenticated to the
	   backend server."
   ::= { gs2352NASPortStatusClientsEntry 19 }

gs2352NASRxBackendServerClientsAuthFailures OBJECT-TYPE
   SYNTAX      Counter32
   MAX-ACCESS  read-only
   STATUS      current
   DESCRIPTION
       "Counts the number of times that the switch receives a failure message.
	   This indicates that the supplicant/client has not authenticated to the
	   backend server. "
   ::= { gs2352NASPortStatusClientsEntry 20 }

gs2352NASTxBackendServerClientsResponses OBJECT-TYPE
   SYNTAX      Counter32
   MAX-ACCESS  read-only
   STATUS      current
   DESCRIPTION
       "802.1X-based: Counts the number of times that the switch attempts to
	   send a supplicant's first response packet to the backend server. Indicates
	   the switch attempted communication with the backend server. Possible
	   retransmissions are not counted.
	   MAC-based: Counts all the backend server packets sent from the switch
	   towards the backend server for a given port or client. Possible
	   retransmissions are not counted."
   ::= { gs2352NASPortStatusClientsEntry 21 }


gs2352Maintenance                                           OBJECT IDENTIFIER ::= { lancomGS2352 4 }

gs2352RestartDevice OBJECT-TYPE
   SYNTAX      INTEGER { disable(0), enable(1) }
   MAX-ACCESS  read-write
   STATUS      current
   DESCRIPTION
       "default: 0
        0:none
        1:yes"
   ::= { gs2352Maintenance 1 }

gs2352ColdRestartDevice OBJECT-TYPE
   SYNTAX      INTEGER { disable(0), enable(1) }
   MAX-ACCESS  read-write
   STATUS      current
   DESCRIPTION
       "default: 0
        0:none
        1:yes"
   ::= { gs2352Maintenance 1500 }

gs2352Firmware                                         OBJECT IDENTIFIER ::= { gs2352Maintenance 2 }

gs2352FirmwareIpAddress OBJECT-TYPE
   SYNTAX       IpAddress
   MAX-ACCESS   read-write
   STATUS       current
   DESCRIPTION
        "Get/Set the firmware tftp server."
   ::= { gs2352Firmware 1 }

gs2352FirmwareFileName OBJECT-TYPE
   SYNTAX       DisplayString
   MAX-ACCESS   read-write
   STATUS       current
   DESCRIPTION
        "Get/Set the path and filename for firmware upgrading."
   ::= { gs2352Firmware 2 }

gs2352DoFirmwareUpgrade OBJECT-TYPE
   SYNTAX       INTEGER { doNothing(0), do(1) }
   MAX-ACCESS   read-write
   STATUS       current
   DESCRIPTION
        "Do firmware upgrade. Get this OID always return zero.
              1 - do firmware upgrade.
              0 - do nothing."
   ::= { gs2352Firmware 3 }

gs2352SaveOrRestore                                         OBJECT IDENTIFIER ::= { gs2352Maintenance 3 }

gs2352FactoryDefaults OBJECT-TYPE
   SYNTAX      INTEGER { none(0), yes(1) }
   MAX-ACCESS  read-write
   STATUS      current
   DESCRIPTION
       "default: 0
        0:none
        1:yes"
   ::= { gs2352SaveOrRestore 1 }

gs2352SaveStart OBJECT-TYPE
   SYNTAX      INTEGER { none(0), yes(1) }
   MAX-ACCESS  read-write
   STATUS      current
   DESCRIPTION
       "default: 0
        0:none
        1:yes"
   ::= { gs2352SaveOrRestore 2 }

gs2352SaveUser OBJECT-TYPE
   SYNTAX      INTEGER { none(0), yes(1) }
   MAX-ACCESS  read-write
   STATUS      current
   DESCRIPTION
       "default: 0
        0:none
        1:yes"
   ::= { gs2352SaveOrRestore 3 }

gs2352RestoreUser OBJECT-TYPE
   SYNTAX      INTEGER { none(0), yes(1) }
   MAX-ACCESS  read-write
   STATUS      current
   DESCRIPTION
       "default: 0
        0:none
        1:yes"
   ::= { gs2352SaveOrRestore 4 }


gs2352ExportOrImport                                        OBJECT IDENTIFIER ::= { gs2352Maintenance 4 }

gs2352ExportIpAddress OBJECT-TYPE
   SYNTAX       IpAddress
   MAX-ACCESS   read-write
   STATUS       current
   DESCRIPTION
        "Get/Set the export tftp server."
   ::= { gs2352ExportOrImport 1 }

gs2352ExportConfigName OBJECT-TYPE
   SYNTAX       DisplayString
   MAX-ACCESS   read-write
   STATUS       current
   DESCRIPTION
       "Get/Set the export file path and name."
   ::= { gs2352ExportOrImport 2 }

gs2352DoExportConfig OBJECT-TYPE
   SYNTAX       INTEGER{ doNothing(0), do(1) }
   MAX-ACCESS   read-write
   STATUS       current
   DESCRIPTION
        "Do export-config.
         Get this OID always return zero.
         1 - export."
   ::= { gs2352ExportOrImport 3 }

gs2352ImportIpAddress OBJECT-TYPE
   SYNTAX       IpAddress
   MAX-ACCESS   read-write
   STATUS       current
   DESCRIPTION
        "Get/Set the import tftp server."
   ::= { gs2352ExportOrImport 4 }

gs2352ImportConfigName OBJECT-TYPE
   SYNTAX      DisplayString
   MAX-ACCESS  read-write
   STATUS      current
   DESCRIPTION
       "Get/Set the import file path and name."
   ::= { gs2352ExportOrImport 5 }

gs2352DoImportConfig OBJECT-TYPE
   SYNTAX       INTEGER{ doNothing(0), do(1) }
   MAX-ACCESS   read-write
   STATUS       current
   DESCRIPTION
        "Do export-config.
         Get this OID always return zero.
         1 - import."
   ::= { gs2352ExportOrImport 6 }

gs2352Diagnostics                                           OBJECT IDENTIFIER ::= { gs2352Maintenance 5 }

gs2352PingIpAddress OBJECT-TYPE
   SYNTAX      IpAddress
   MAX-ACCESS  read-write
   STATUS      current
   DESCRIPTION
       " The destination IP Address. "
   ::= { gs2352Diagnostics 1 }

gs2352PingSize OBJECT-TYPE
   SYNTAX      Integer32(0|60..1400)
   MAX-ACCESS  read-write
   STATUS      current
   DESCRIPTION
       " Size of ICMP echo packet.
         range : 60-1400, default : 64. "
   ::= { gs2352Diagnostics 2 }

gs2352DoPingConfig OBJECT-TYPE
   SYNTAX       INTEGER{ doNothing(0), do(1) }
   MAX-ACCESS  read-write
   STATUS      current
   DESCRIPTION
       "Do ping-config.
         Get this OID always return zero.
         1 - ping. Uses the ICMP protocol's mandatory ECHO_REQUEST datagram
         to elicit an ICMP ECHO_RESPONSE from a host or gateway. "
   ::= { gs2352Diagnostics 3 }

gs2352PingResult OBJECT-TYPE
   SYNTAX      DisplayString
   MAX-ACCESS  read-only
   STATUS      current
   DESCRIPTION
       " Show ping result. "
   ::= { gs2352Diagnostics 4 }

gs2352Ping6IpAddress OBJECT-TYPE
   SYNTAX      DisplayString
   MAX-ACCESS  read-write
   STATUS      current
   DESCRIPTION
       " The destination IPv6 Address. "
   ::= { gs2352Diagnostics 5 }

gs2352Ping6Size OBJECT-TYPE
   SYNTAX      Integer32(60..1400)
   MAX-ACCESS  read-write
   STATUS      current
   DESCRIPTION
       " Size of ICMP echo packet.
         range : 60-1400. "
   ::= { gs2352Diagnostics 6 }

gs2352DoPing6Config OBJECT-TYPE
   SYNTAX       INTEGER{ doNothing(0), do(1) }
   MAX-ACCESS  read-write
   STATUS      current
   DESCRIPTION
       "Do ping-config.
         Get this OID always return zero.
         1 - ping. Uses the ICMP protocol's mandatory ECHO_REQUEST datagram
         to elicit an ICMP ECHO_RESPONSE from a host or gateway. "
   ::= { gs2352Diagnostics 7 }

gs2352Ping6Result OBJECT-TYPE
   SYNTAX      DisplayString
   MAX-ACCESS  read-only
   STATUS      current
   DESCRIPTION
       " Show ping result. "
   ::= { gs2352Diagnostics 8 }


gs2352VeriPHY                                           OBJECT IDENTIFIER ::= { gs2352Diagnostics 9 }

gs2352VeriPHYTest OBJECT-TYPE
   SYNTAX      Integer32 (1..4095)
   MAX-ACCESS  read-write
   STATUS      current
   DESCRIPTION
       "Run VeriPHY Cable Diagnostics.
        port, range : 0 - port number.
        0 : ALL "
   ::= { gs2352VeriPHY 1 }

gs2352VeriPHYTable OBJECT-TYPE
   SYNTAX      SEQUENCE OF GS2352VeriPHYEntry
   MAX-ACCESS  not-accessible
   STATUS      current
   DESCRIPTION
       " "
   ::= { gs2352VeriPHY 2 }

gs2352VeriPHYEntry OBJECT-TYPE
   SYNTAX      GS2352VeriPHYEntry
   MAX-ACCESS  not-accessible
   STATUS      current
   DESCRIPTION
       ""
   INDEX    { gs2352VeriPHYPort  }
   ::= { gs2352VeriPHYTable 1 }

GS2352VeriPHYEntry ::= SEQUENCE {
   gs2352VeriPHYPort        Integer32,
   gs2352VeriPHYPairA       DisplayString,
   gs2352VeriPHYLengthA     DisplayString,
   gs2352VeriPHYPairB       DisplayString,
   gs2352VeriPHYLengthB     DisplayString,
   gs2352VeriPHYPairC       DisplayString,
   gs2352VeriPHYLengthC     DisplayString,
   gs2352VeriPHYPairD       DisplayString,
   gs2352VeriPHYLengthD     DisplayString
}

gs2352VeriPHYPort OBJECT-TYPE
   SYNTAX      Integer32(1..4095)
   MAX-ACCESS  not-accessible
   STATUS      current
   DESCRIPTION
       " The length (in meters) of the cable pair. "
   ::= { gs2352VeriPHYEntry 1 }

gs2352VeriPHYPairA OBJECT-TYPE
   SYNTAX      DisplayString
   MAX-ACCESS  read-only
   STATUS      current
   DESCRIPTION
       " The status of the cable pair. "
   ::= { gs2352VeriPHYEntry 2 }

gs2352VeriPHYLengthA OBJECT-TYPE
   SYNTAX      DisplayString
   MAX-ACCESS  read-only
   STATUS      current
   DESCRIPTION
       " The length (in meters) of the cable pair. "
   ::= { gs2352VeriPHYEntry 3 }

gs2352VeriPHYPairB OBJECT-TYPE
   SYNTAX      DisplayString
   MAX-ACCESS  read-only
   STATUS      current
   DESCRIPTION
       " The status of the cable pair. "
   ::= { gs2352VeriPHYEntry 4 }

gs2352VeriPHYLengthB OBJECT-TYPE
   SYNTAX      DisplayString
   MAX-ACCESS  read-only
   STATUS      current
   DESCRIPTION
       " The length (in meters) of the cable pair. "
   ::= { gs2352VeriPHYEntry 5 }

gs2352VeriPHYPairC OBJECT-TYPE
   SYNTAX      DisplayString
   MAX-ACCESS  read-only
   STATUS      current
   DESCRIPTION
       " The status of the cable pair. "
   ::= { gs2352VeriPHYEntry 6 }

gs2352VeriPHYLengthC OBJECT-TYPE
   SYNTAX      DisplayString
   MAX-ACCESS  read-only
   STATUS      current
   DESCRIPTION
       " The length (in meters) of the cable pair. "
   ::= { gs2352VeriPHYEntry 7 }

gs2352VeriPHYPairD OBJECT-TYPE
   SYNTAX      DisplayString
   MAX-ACCESS  read-only
   STATUS      current
   DESCRIPTION
       " The status of the cable pair. "
   ::= { gs2352VeriPHYEntry 8 }

gs2352VeriPHYLengthD OBJECT-TYPE
   SYNTAX      DisplayString
   MAX-ACCESS  read-only
   STATUS      current
   DESCRIPTION
       " The length (in meters) of the cable pair. "
   ::= { gs2352VeriPHYEntry 9 }


------------------------------------------------------------------------------------------------------------------
gs2352Trap                                                  OBJECT IDENTIFIER ::= { lancomGS2352 5 }

gs2352TrapEvent                                             OBJECT IDENTIFIER ::= { gs2352Trap 1 }

gs2352Emergency NOTIFICATION-TYPE
  OBJECTS   { gs2352Information }
  STATUS        current
    DESCRIPTION
        "The severity level is Emergency. The system is unusable."
    ::= { gs2352TrapEvent 1 }

gs2352Alert NOTIFICATION-TYPE
  OBJECTS   { gs2352Information }
  STATUS        current
    DESCRIPTION
        "The severity level is Alert. The action must be taken immediately."
    ::= { gs2352TrapEvent 2 }

gs2352Critical NOTIFICATION-TYPE
  OBJECTS   { gs2352Information }
  STATUS        current
    DESCRIPTION
        "The severity level is Critical. Critical conditions."
    ::= { gs2352TrapEvent 3 }

gs2352Error NOTIFICATION-TYPE
  OBJECTS   { gs2352Information }
  STATUS        current
    DESCRIPTION
        "The severity level is Error. Error conditions."
    ::= { gs2352TrapEvent 4 }

gs2352Warning NOTIFICATION-TYPE
  OBJECTS   { gs2352Information }
  STATUS        current
    DESCRIPTION
        "The severity level is Warning. Warning conditions."
    ::= { gs2352TrapEvent 5 }

gs2352Notice NOTIFICATION-TYPE
  OBJECTS   { gs2352Information }
  STATUS        current
    DESCRIPTION
        "The severity level is Notice. Normal but significant condition."
    ::= { gs2352TrapEvent 6 }

gs2352Informational NOTIFICATION-TYPE
  OBJECTS   { gs2352Information }
  STATUS        current
    DESCRIPTION
        "The severity level is Informational. Informational messages."
    ::= { gs2352TrapEvent 7 }

gs2352Debug NOTIFICATION-TYPE
  OBJECTS   { gs2352Information }
  STATUS        current
    DESCRIPTION
        "The severity level is Debug. debug-level messages."
    ::= { gs2352TrapEvent 8 }

gs2352TrapVariable                                          OBJECT IDENTIFIER ::= { gs2352Trap 2 }

gs2352Information OBJECT-TYPE
    SYNTAX      DisplayString
    MAX-ACCESS  read-only
    STATUS      current
    DESCRIPTION
        "Trap information."
    ::= { gs2352TrapVariable 1 }


END
