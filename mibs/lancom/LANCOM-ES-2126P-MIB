LANCOM-ES-2126P-MIB DEFINITIONS ::= BEGIN

IMPORTS
    DisplayString FROM SNMPv2-TC
    MODULE-COMPLIANCE,OBJECT-GROUP, NOTIFICATION-GROUP       FROM SNMPv2-CONF
    enterprises,MODULE-IDENTITY,OBJECT-TYPE,NOTIFICATION-TYPE,Counter32,IpAddress        FROM SNMPv2-SMI
    MacAddress FROM BRIDGE-MIB
    ifIndex    FROM RFC1213-MIB;

-- @ENTERPRISE-SECTION-START
lancomSystems MODULE-IDENTITY
    LAST-UPDATED "201003230000Z"
        ORGANIZATION "LANCOM Systems GmbH"
        CONTACT-INFO
            "Adenauerstrasse 20 / B2, 52146 Wuerselen, Germany
                 Email: info@lancom.de
                 TEL: +49 (0)2405 49936 0
                 FAX: +49 (0)2405 49936 99"
        DESCRIPTION
                "The MIB module is for LANCOM Systems"
        ::= { enterprises 2356 }

switchingSystems               OBJECT IDENTIFIER ::= { lancomSystems 800 }

fastEthernetSwitches            OBJECT IDENTIFIER ::= { switchingSystems 2 }

lancomES2126P           OBJECT IDENTIFIER ::= { fastEthernetSwitches 2127 }

-- @ENTERPRISE-SECTION-END
es2126pProduces            OBJECT IDENTIFIER ::= { lancomES2126P 1 }

es2126pSystem               OBJECT IDENTIFIER ::= { es2126pProduces 1 }

es2126pCommonSys            OBJECT IDENTIFIER ::= { es2126pSystem 1 }

es2126pReboot OBJECT-TYPE
    SYNTAX      INTEGER(0|1|2)
    MAX-ACCESS      read-write
    STATUS      current
    DESCRIPTION
        "Reboot the system. Get this OID always return zero.
            0 - do nothing
            1 - Reboot without saving start
            2 - Reboot with saving start"
    ::= { es2126pCommonSys 1 }

es2126pBiosVsersion OBJECT-TYPE
    SYNTAX      DisplayString
    MAX-ACCESS      read-only
    STATUS      current
    DESCRIPTION
        "Get the BIOS version of the system."
    ::= { es2126pCommonSys 2 }

es2126pFirmwareVersion  OBJECT-TYPE
    SYNTAX      DisplayString
    MAX-ACCESS      read-only
    STATUS      current
    DESCRIPTION
        "Get the firmware version of the system."
    ::= { es2126pCommonSys 3 }

es2126pHardwareVersion  OBJECT-TYPE
    SYNTAX      DisplayString
    MAX-ACCESS      read-only
    STATUS      current
    DESCRIPTION
        "Get the hardware version of the system."
    ::= { es2126pCommonSys 4 }

es2126pMechanicalVersion OBJECT-TYPE
    SYNTAX      DisplayString
    MAX-ACCESS      read-only
    STATUS      current
    DESCRIPTION
        "Get the mechanical version of the system."
    ::= { es2126pCommonSys 5 }

es2126pSerialNumber OBJECT-TYPE
    SYNTAX      DisplayString
    MAX-ACCESS      read-only
    STATUS      current
    DESCRIPTION
        "Get the Serial number of the system."
    ::= { es2126pCommonSys 6 }

es2126pHostMacAddress   OBJECT-TYPE
    SYNTAX      DisplayString
    MAX-ACCESS      read-only
    STATUS      current
    DESCRIPTION
        "Get the MAC address of the system."
    ::= { es2126pCommonSys 7 }

es2126pDevicePort   OBJECT-TYPE
    SYNTAX      DisplayString
    MAX-ACCESS      read-only
    STATUS      current
    DESCRIPTION
        "Get the quantity of ports that this system owns now."
    ::= { es2126pCommonSys 8 }

es2126pRamSize  OBJECT-TYPE
    SYNTAX      DisplayString
    MAX-ACCESS      read-only
    STATUS      current
    DESCRIPTION
        "Get the RAM size of the system."
    ::= { es2126pCommonSys 9 }

es2126pFlashSize  OBJECT-TYPE
    SYNTAX      DisplayString
    MAX-ACCESS      read-only
    STATUS      current
    DESCRIPTION
        "Get the flash size of the system."
    ::= { es2126pCommonSys 10 }

es2126pSystemDescription  OBJECT-TYPE
    SYNTAX      DisplayString
    MAX-ACCESS      read-only
    STATUS      current
    DESCRIPTION
        "Get the system description."
    ::= { es2126pCommonSys 11 }

es2126pDeviceName  OBJECT-TYPE
    SYNTAX      DisplayString
    MAX-ACCESS      read-write
    STATUS      current
    DESCRIPTION
        "Get/Set the device Name."
    ::= { es2126pCommonSys 12 }

es2126pIP               OBJECT IDENTIFIER ::= { es2126pSystem 2 }

es2126pDhcpSetting OBJECT-TYPE
    SYNTAX          INTEGER(0|1)
    MAX-ACCESS          read-write
    STATUS          current
    DESCRIPTION
        "Get/Set DHCP status of the system.
            0 - DHCP disable
            1 - DHCP enable"
    ::= { es2126pIP 1 }

es2126pIPAddress OBJECT-TYPE
    SYNTAX      IpAddress
    MAX-ACCESS      read-write
    STATUS      current
    DESCRIPTION
        "Get/Set the IP address of the system.
         You can't set this OID if DHCP status is enabled."
    ::= { es2126pIP 2 }

es2126pNetMask OBJECT-TYPE
    SYNTAX      IpAddress
    MAX-ACCESS      read-write
    STATUS      current
    DESCRIPTION
        "Get/Set the subnet mask of the system.
         You can't set this OID if DHCP status is enabled."
    ::= { es2126pIP 3 }

es2126pDefaultGateway OBJECT-TYPE
    SYNTAX      IpAddress
    MAX-ACCESS      read-write
    STATUS      current
    DESCRIPTION
        "Get/Set the default gateway of the system.
         You can't set this OID if DHCP status is enabled."
    ::= { es2126pIP 4 }

es2126pDnsSetting OBJECT-TYPE
    SYNTAX      INTEGER(0|1)
    MAX-ACCESS      read-write
    STATUS      current
    DESCRIPTION
        "Get/Set the source of DNS server.
         You can't set this OID if DHCP status is disabled.
            0 - manual, the DNS server is from manual setting
            1 - Auto, the DNS server is assigned by DHCP server."
    ::= { es2126pIP 5 }

es2126pDnsServer OBJECT-TYPE
    SYNTAX      IpAddress
    MAX-ACCESS      read-write
    STATUS      current
    DESCRIPTION
        "Get/Set the DNS server of the system."
    ::= { es2126pIP 6 }

es2126pTime             OBJECT IDENTIFIER ::= { es2126pSystem 3 }

es2126pSystemCurrentTime OBJECT-TYPE
    SYNTAX      DisplayString
    MAX-ACCESS      read-only
    STATUS      current
    DESCRIPTION
        "Get the current time of the system."
    ::= { es2126pTime 1 }

es2126pManualTimeSetting OBJECT-TYPE
    SYNTAX      DisplayString
    MAX-ACCESS      read-write
    STATUS      current
    DESCRIPTION
        "Get/Set the system time of the device.
        The input format is 'Year/Month/Day/Hour/Minute/Second'.
        Ex: 2004/1/1/12/34/25 means 2004/1/1 - 12:24:25.
        Value range:
        Year    : 2000 - 2036,
        Mouth   : 1 - 12,
        Day     : 1 - 31,
        Hour    : 0 - 23,
        Minute  : 0 - 59,
        Sec     : 0 - 59."
    ::= { es2126pTime 2 }

es2126pNTPServer OBJECT-TYPE
    SYNTAX      DisplayString
    MAX-ACCESS      read-write
    STATUS      current
    DESCRIPTION
        "Get/Set the NTP Time Server. You can use the IP address or domain name."
    ::= { es2126pTime 3 }

es2126pNTPTimeZone OBJECT-TYPE
    SYNTAX      INTEGER(-12..13)
    MAX-ACCESS      read-write
    STATUS      current
    DESCRIPTION
        "Get/Set the NTP Time Zone.
        Value range is between -12 and 13
        -12 - GMT -12:00,
        -11 - GMT -11:00,
        -10 - GMT -10:00,
         -9 - GMT -09:00,
         -8 - GMT -08:00,
         -7 - GMT -07:00,
         -6 - GMT -06:00,
         -5 - GMT -05:00,
         -4 - GMT -04:00,
         -3 - GMT -03:00,
         -2 - GMT -02:00,
         -1 - GMT -01:00,
          0 - GMT +00:00,
          1 - GMT +01:00,
          2 - GMT +02:00,
          3 - GMT +03:00,
          4 - GMT +04:00,
          5 - GMT +05:00,
          6 - GMT +06:00,
          7 - GMT +07:00,
          8 - GMT +08:00,
          9 - GMT +09:00,
         10 - GMT +10:00,
         11 - GMT +11:00,
         12 - GMT +12:00,
         13 - GMT +13:00. "
    ::= { es2126pTime 4 }

es2126pNTPTimeSync OBJECT-TYPE
    SYNTAX      INTEGER(0|1)
    MAX-ACCESS      read-write
    STATUS      current
    DESCRIPTION
        "Sync time from NTP Server. Get this OID always return zero.
        Set the Time Server and Time Zone before doing time sync.
        Notice that time server must be correct!
        Value range (1|0):
        1 - Sync.
        0 - do nothing."
    ::= { es2126pTime 5 }

es2126pDaylightSavingTime OBJECT-TYPE
    SYNTAX      INTEGER(-5..5)
    MAX-ACCESS      read-write
    STATUS      current
    DESCRIPTION
        "Get/Set the daylight saving time.
        Value range is between -5 and 5. Unit: hour. "
    ::= { es2126pTime 6 }

es2126pDaylightStartTime OBJECT-TYPE
    SYNTAX      DisplayString
    MAX-ACCESS      read-write
    STATUS      current
    DESCRIPTION
        "Get/Set the Start time of Daylight Saving.
        The input format is 'MM/DD/HH',
        and daylight saving start month can't equal end month.
        Example: month/day/hour   10/01/00
        Month: 01~12, day: 01~31, hour: 00~23."
    ::= { es2126pTime 7 }

es2126pDaylightEndTime OBJECT-TYPE
    SYNTAX      DisplayString
    MAX-ACCESS      read-write
    STATUS      current
    DESCRIPTION
        "Get/Set the End time of Daylight Saving.
        The input format is 'MM/DD/HH',
        and daylight saving start month can't equal end month.
        Example: month/day/hour   04/01/00
        Month: 01~12, day: 01~31, hour: 00~23."
    ::= { es2126pTime 8 }

es2126pAccount              OBJECT IDENTIFIER ::= { es2126pSystem 4 }

es2126pAccountNumber OBJECT-TYPE
    SYNTAX      INTEGER(1..5)
    MAX-ACCESS      read-only
    STATUS      current
    DESCRIPTION
        "Get the current account number(s) of the system."
    ::= { es2126pAccount 1 }

es2126pAccountTable OBJECT-TYPE
    SYNTAX      SEQUENCE OF ES2126PAccountEntry
    MAX-ACCESS  not-accessible
    STATUS      current
    DESCRIPTION
        "This is a list of es2126pAccountEntry. The numbers of entries are given by
        the value of es2126pAccountNumber."
    ::= { es2126pAccount 2 }

es2126pAccountEntry OBJECT-TYPE
    SYNTAX      ES2126PAccountEntry
    MAX-ACCESS      not-accessible
    STATUS      current
    DESCRIPTION
        "This is the Entry(s) for account information."
    INDEX {es2126pAccountIndex}
    ::= { es2126pAccountTable 1 }

ES2126PAccountEntry ::=
SEQUENCE {
    es2126pAccountIndex         INTEGER,
    es2126pAccountAuthorization DisplayString,
    es2126pAccountName             DisplayString,
    es2126pAccountPassword         DisplayString
}

es2126pAccountIndex OBJECT-TYPE
    SYNTAX      INTEGER(1..5)
    MAX-ACCESS      read-only
    STATUS      current
    DESCRIPTION
        "This is the index of the account entry."
    ::= { es2126pAccountEntry 1 }

es2126pAccountAuthorization OBJECT-TYPE
    SYNTAX      DisplayString
    MAX-ACCESS      read-only
    STATUS      current
    DESCRIPTION
        "This is the authorization of the account entry."
    ::= { es2126pAccountEntry 2 }

es2126pAccountName  OBJECT-TYPE
    SYNTAX      DisplayString
    MAX-ACCESS      read-write
    STATUS      current
    DESCRIPTION
        "This is the username of the account entry."
    ::= { es2126pAccountEntry 3 }

es2126pAccountPassword  OBJECT-TYPE
    SYNTAX      DisplayString
    MAX-ACCESS      read-write
    STATUS      current
    DESCRIPTION
        "This is the password of the account entry. The return value is always '********'."
    ::= { es2126pAccountEntry 4 }

es2126pAccountAddName OBJECT-TYPE
    SYNTAX      DisplayString
    MAX-ACCESS      read-write
    STATUS      current
    DESCRIPTION
        "This is the account name for adding operation."
    ::= { es2126pAccount 3 }

es2126pAccountAddPassword OBJECT-TYPE
    SYNTAX      DisplayString
    MAX-ACCESS      read-write
    STATUS      current
    DESCRIPTION
        "This is the account password for adding operation. The return value is always '********'."
    ::= { es2126pAccount 4 }

es2126pDoAccountAdd OBJECT-TYPE
    SYNTAX      INTEGER(0|1)
    MAX-ACCESS      read-write
    STATUS      current
    DESCRIPTION
        "Add account name. OID es2126pAccountAddName and es2126pAccountAddPassword must be
        filled first. Get this OID always return zero.
            1 - Add account.
            0 - do nothing."
    ::= { es2126pAccount 5 }

es2126pAccountDel   OBJECT-TYPE
    SYNTAX      INTEGER(2..5)
    MAX-ACCESS      read-write
    STATUS      current
    DESCRIPTION
        "Delete account. The value is valid es2126pAccountIndex(Can't delete administrator)."
    ::= { es2126pAccount 6 }

es2126pSnmp             OBJECT IDENTIFIER ::= { es2126pProduces 2 }

es2126pGetCommunity OBJECT-TYPE
    SYNTAX      DisplayString
    MAX-ACCESS      read-write
    STATUS      current
    DESCRIPTION
        "Get/Set the get-community of the SNMP."
    ::= { es2126pSnmp 1 }

es2126pSetCommunity OBJECT-TYPE
    SYNTAX      DisplayString
    MAX-ACCESS      read-write
    STATUS      current
    DESCRIPTION
        "Get/Set the set-community of the SNMP."
    ::= { es2126pSnmp 2 }

es2126pTrapHostNumber OBJECT-TYPE
    SYNTAX      INTEGER(1..6)
    MAX-ACCESS      read-only
    STATUS      current
    DESCRIPTION
        "Get the number of trap hosts."
    ::= { es2126pSnmp 3 }

es2126pTrapHostTable    OBJECT-TYPE
    SYNTAX      SEQUENCE OF ES2126PTrapHostEntry
    MAX-ACCESS  not-accessible
    STATUS      current
    DESCRIPTION
        "This is a list of trap host entry. The numbers of entries are given by the value of es2126pTrapHostNumber."
    ::= { es2126pSnmp 4 }

es2126pTrapHostEntry    OBJECT-TYPE
    SYNTAX      ES2126PTrapHostEntry
    MAX-ACCESS      not-accessible
    STATUS      current
    DESCRIPTION
        "This is the Entry Information for trap host."
    INDEX {es2126pTrapHostIndex}
    ::= { es2126pTrapHostTable 1 }

ES2126PTrapHostEntry ::=
SEQUENCE {
    es2126pTrapHostIndex            INTEGER,
    es2126pTrapHostIP           IpAddress,
    es2126pTrapHostPort            INTEGER,
    es2126pTrapHostCommunity       DisplayString
}

es2126pTrapHostIndex    OBJECT-TYPE
    SYNTAX      INTEGER(1..6)
    MAX-ACCESS      read-only
    STATUS      current
    DESCRIPTION
        "The index of the trap host entry."
    ::= { es2126pTrapHostEntry 1 }

es2126pTrapHostIP   OBJECT-TYPE
    SYNTAX      IpAddress
    MAX-ACCESS      read-write
    STATUS      current
    DESCRIPTION
        "This is the IP of the trap host."
    ::= { es2126pTrapHostEntry 2 }


es2126pTrapHostPort OBJECT-TYPE
    SYNTAX      INTEGER(1..65535)
    MAX-ACCESS      read-write
    STATUS      current
    DESCRIPTION
        "This is the receiving-port number of the trap host."
    ::= { es2126pTrapHostEntry 3 }


es2126pTrapHostCommunity    OBJECT-TYPE
    SYNTAX      DisplayString
    MAX-ACCESS      read-write
    STATUS      current
    DESCRIPTION
        "The community name for the trap PDU."
    ::= { es2126pTrapHostEntry 4 }

es2126pRegisterMonitor OBJECT-TYPE
                SYNTAX DisplayString
                MAX-ACCESS read-write
                STATUS current
                DESCRIPTION "Register-Monitor"
                ::= {  es2126pSnmp 5 }

es2126pDeleteMonitor OBJECT-TYPE
               SYNTAX DisplayString
               MAX-ACCESS read-write
               STATUS current
               DESCRIPTION "Delete-Monitor"
               ::= {  es2126pSnmp 6 }

es2126pMonitorTable OBJECT-TYPE
                    SYNTAX SEQUENCE OF ES2126PMonitorEntry
                    MAX-ACCESS not-accessible
                    STATUS current
                    DESCRIPTION "Monitor-Table"
                    ::= {  es2126pSnmp 7 }

ES2126PMonitorEntry ::= SEQUENCE {
                    es2126pMonitorTableIp IpAddress,
                    es2126pMonitorTableMac DisplayString
                   }

es2126pMonitorEntry OBJECT-TYPE
                    SYNTAX ES2126PMonitorEntry
                    MAX-ACCESS not-accessible
                    STATUS current
                    DESCRIPTION "entry in table"
                    INDEX { es2126pMonitorTableIp }
                    ::= {  es2126pMonitorTable 1 }

es2126pMonitorTableIp OBJECT-TYPE
                  SYNTAX IpAddress
                  MAX-ACCESS read-only
                  STATUS current
                  DESCRIPTION "IP-Address"
                  ::= {  es2126pMonitorEntry 1 }

es2126pMonitorTableMac OBJECT-TYPE
                  SYNTAX DisplayString
                  MAX-ACCESS read-only
                  STATUS current
                  DESCRIPTION "MAC-Address"
                  ::= {  es2126pMonitorEntry 2 }

es2126pTrapBootDelayTime OBJECT-TYPE
    SYNTAX      INTEGER(0..120)
    MAX-ACCESS      read-write
    STATUS      current
    DESCRIPTION
        "Get/Set trap boot delay time in second. Default: 0"
    ::= { es2126pSnmp 8 }

es2126pAlarm            OBJECT IDENTIFIER ::= { es2126pProduces 3 }

es2126pEvent            OBJECT IDENTIFIER ::= { es2126pAlarm 1 }

es2126pEventNumber OBJECT-TYPE
    SYNTAX      INTEGER(1..2147483647)
    MAX-ACCESS      read-only
    STATUS      current
    DESCRIPTION
        "Get the total number of alarm events."
    ::= { es2126pEvent 1 }

es2126pEventTable   OBJECT-TYPE
    SYNTAX      SEQUENCE OF ES2126PEventEntry
    MAX-ACCESS  not-accessible
    STATUS      current
    DESCRIPTION
        "This is a list of alarm event entry. The numbers of entries are given by the value of es2126pEventNumber."
    ::= { es2126pEvent 2 }

es2126pEventEntry   OBJECT-TYPE
    SYNTAX      ES2126PEventEntry
    MAX-ACCESS      not-accessible
    STATUS      current
    DESCRIPTION
        "This is the entry information for alarm event."
    INDEX {es2126pEventIndex}
    ::= { es2126pEventTable 1 }

ES2126PEventEntry ::=
SEQUENCE {
    es2126pEventIndex           INTEGER,
    es2126pEventName            DisplayString,
    es2126pEventSendEmail      INTEGER,
    es2126pEventSendTrap       INTEGER
}

es2126pEventIndex   OBJECT-TYPE
    SYNTAX      INTEGER(1..2147483647)
    MAX-ACCESS      read-only
    STATUS      current
    DESCRIPTION
        "This is the index of the alarm event entry."
    ::= { es2126pEventEntry 1 }

es2126pEventName    OBJECT-TYPE
    SYNTAX      DisplayString
    MAX-ACCESS      read-only
    STATUS      current
    DESCRIPTION
        "This is the alarm event name."
    ::= { es2126pEventEntry 2 }

es2126pEventSendEmail   OBJECT-TYPE
    SYNTAX      INTEGER(0|1)
    MAX-ACCESS      read-write
    STATUS      current
    DESCRIPTION
        "Send email when alarm event is triggered."
    ::= { es2126pEventEntry 3 }

es2126pEventSendTrap    OBJECT-TYPE
    SYNTAX      INTEGER(0|1)
    MAX-ACCESS      read-write
    STATUS      current
    DESCRIPTION
        "Send trap when alarm event is triggered."
    ::= { es2126pEventEntry 4 }


es2126pEmail            OBJECT IDENTIFIER ::= { es2126pAlarm 2 }

es2126pEmailServer OBJECT-TYPE
    SYNTAX      DisplayString
    MAX-ACCESS      read-write
    STATUS      current
    DESCRIPTION
        "This is the SMTP server for alarm event."
    ::= { es2126pEmail 1 }

es2126pEmailUsername OBJECT-TYPE
    SYNTAX      DisplayString
    MAX-ACCESS      read-write
    STATUS      current
    DESCRIPTION
        "This is the Username of SMTP server."
    ::= { es2126pEmail 2 }

es2126pEmailPassword OBJECT-TYPE
    SYNTAX      DisplayString
    MAX-ACCESS      read-write
    STATUS      current
    DESCRIPTION
        "This is the User Password of SMTP server."
    ::= { es2126pEmail 3 }

es2126pEmailSender OBJECT-TYPE
	SYNTAX      DisplayString
	MAX-ACCESS	    read-write
	STATUS		current
	DESCRIPTION
		"This is the Sender of SMTP server."
	::= { es2126pEmail 4 }

es2126pEmailReturnPath OBJECT-TYPE
	SYNTAX      DisplayString
	MAX-ACCESS	    read-write
	STATUS		current
	DESCRIPTION
		"This is the return path of mail."
	::= { es2126pEmail 5 }

es2126pEmailUserNumber OBJECT-TYPE
    SYNTAX      INTEGER(1..6)
    MAX-ACCESS      read-only
    STATUS      current
    DESCRIPTION
        "The number of the email users that you want to send the alarm notification."
    ::= { es2126pEmail 6 }

es2126pEmailUserTable   OBJECT-TYPE
    SYNTAX      SEQUENCE OF ES2126PEmailUserEntry
    MAX-ACCESS  not-accessible
    STATUS      current
    DESCRIPTION
        "This is a list of email user entry. The numbers of entries are given by the value of es2126pEmailUserNumber."
    ::= { es2126pEmail 7 }

es2126pEmailUserEntry   OBJECT-TYPE
    SYNTAX      ES2126PEmailUserEntry
    MAX-ACCESS      not-accessible
    STATUS      current
    DESCRIPTION
        "This is the Entry information for email user entry."
    INDEX {es2126pEmailUserIndex}
    ::= { es2126pEmailUserTable 1 }

ES2126PEmailUserEntry ::=
SEQUENCE {
    es2126pEmailUserIndex           INTEGER,
    es2126pEmailUserAddress         DisplayString
}

es2126pEmailUserIndex   OBJECT-TYPE
    SYNTAX      INTEGER(1..6)
    MAX-ACCESS      read-only
    STATUS      current
    DESCRIPTION
        "This is the index of the email user entry."
    ::= { es2126pEmailUserEntry 1 }

es2126pEmailUserAddress OBJECT-TYPE
    SYNTAX      DisplayString
    MAX-ACCESS      read-write
    STATUS      current
    DESCRIPTION
        "This is the email address of the email user entry."
    ::= { es2126pEmailUserEntry 2 }

es2126pTftp             OBJECT IDENTIFIER ::= { es2126pProduces 4 }

es2126pRemoteTftpServer OBJECT-TYPE
    SYNTAX      IpAddress
    MAX-ACCESS      read-write
    STATUS      current
    DESCRIPTION
        "Get/Set the remote tftp server."
    ::= { es2126pTftp 1 }

es2126pInternalTftpServerState OBJECT-TYPE
    SYNTAX      INTEGER(0|1)
    MAX-ACCESS      read-write
    STATUS      current
    DESCRIPTION
        "Get/Set internal tftp server state.
         0 : Disable
         1 : Enable
        "
    ::= { es2126pTftp 2 }

es2126pConfiguration            OBJECT IDENTIFIER ::= { es2126pProduces 5 }

es2126pSaveRestore              OBJECT IDENTIFIER ::= { es2126pConfiguration 1 }

es2126pSaveStart OBJECT-TYPE
    SYNTAX      INTEGER(0|1)
    MAX-ACCESS      read-write
    STATUS      current
    DESCRIPTION
        "Save current configuration into flash memory (Save as Start Configuration).
        Get this OID always return zero.
            1 - Save.
            0 - do nothing. "
    ::= { es2126pSaveRestore 1 }

es2126pSaveUser OBJECT-TYPE
    SYNTAX      INTEGER(0|1)
    MAX-ACCESS      read-write
    STATUS      current
    DESCRIPTION
        "Save current configuration into flash memory (Save as User Configuration).
        Get this OID always return zero.
            1 - Save.
            0 - do nothing. "
    ::= { es2126pSaveRestore 2 }

es2126pRestoreDefault OBJECT-TYPE
    SYNTAX      INTEGER(0|1|2)
    MAX-ACCESS      read-write
    STATUS      current
    DESCRIPTION
        "Restore factory default configuration.
        Get this OID always return zero.
            2 - Restore default included default ip address.
        1 - Restore default without changing current ip address.
            0 - do nothing. "
    ::= { es2126pSaveRestore 3 }

es2126pRestoreUser OBJECT-TYPE
    SYNTAX      INTEGER(0|1)
    MAX-ACCESS      read-write
    STATUS      current
    DESCRIPTION
        "Restore user configuration.
        Get this OID always return zero.
            1 - Restore.
            0 - do nothing. "
    ::= { es2126pSaveRestore 4 }


es2126pConfigFile               OBJECT IDENTIFIER ::= { es2126pConfiguration 2 }

es2126pExportConfigName OBJECT-TYPE
    SYNTAX      DisplayString
    MAX-ACCESS      read-write
    STATUS      current
    DESCRIPTION
        "Get/Set the export file path and name."
    ::= { es2126pConfigFile 1 }

es2126pDoExportConfig OBJECT-TYPE
    SYNTAX      INTEGER(1|2)
    MAX-ACCESS      read-write
    STATUS      current
    DESCRIPTION
        "Do export-config.
        Get this OID always return zero.
            1   -   Export start section.
            2   -   Export user-conf section."
    ::= { es2126pConfigFile 2 }

es2126pImportConfigName OBJECT-TYPE
    SYNTAX      DisplayString
    MAX-ACCESS      read-write
    STATUS      current
    DESCRIPTION
        "Get/Set the import file path and name."
    ::= { es2126pConfigFile 3 }

es2126pDoImportConfig OBJECT-TYPE
    SYNTAX      INTEGER(1..3)
    MAX-ACCESS      read-write
    STATUS      current
    DESCRIPTION
        "Do import-config.
        Get this OID always return zero.
            1   -   Import start section.
            2   -   Import user-conf section.
            3   -   Import start and overwrite current ip."
    ::= { es2126pConfigFile 4 }

es2126pDiagnostic               OBJECT IDENTIFIER ::= { es2126pProduces 6 }

es2126pEEPROMTest OBJECT-TYPE
    SYNTAX      DisplayString
    MAX-ACCESS      read-only
    STATUS      current
    DESCRIPTION
        "EEPROM access test."
    ::= { es2126pDiagnostic 1 }

es2126pUartTest OBJECT-TYPE
    SYNTAX      DisplayString
    MAX-ACCESS      read-only
    STATUS      current
    DESCRIPTION
        "UART access test."
    ::= { es2126pDiagnostic 2 }

es2126pDramTest OBJECT-TYPE
    SYNTAX      DisplayString
    MAX-ACCESS      read-only
    STATUS      current
    DESCRIPTION
        "DRAM access test."
    ::= { es2126pDiagnostic 3 }

es2126pFlashTest OBJECT-TYPE
    SYNTAX      DisplayString
    MAX-ACCESS      read-only
    STATUS      current
    DESCRIPTION
        "Flash memory access test."
    ::= { es2126pDiagnostic 4 }

es2126pInternalLoopbackTest OBJECT-TYPE
    SYNTAX      DisplayString
    MAX-ACCESS      read-only
    STATUS      current
    DESCRIPTION
        "Internal loop back test."
    ::= { es2126pDiagnostic 5 }

es2126pExternalLoopbackTest OBJECT-TYPE
    SYNTAX      DisplayString
    MAX-ACCESS      read-only
    STATUS      current
    DESCRIPTION
        "External loop back test."
    ::= { es2126pDiagnostic 6 }

es2126pPingTest OBJECT-TYPE
    SYNTAX      DisplayString
    MAX-ACCESS      read-write
    STATUS      current
    DESCRIPTION
        "Set the host address that you want to ping and the system will return the test result."
    ::= { es2126pDiagnostic 7 }


es2126pLog              OBJECT IDENTIFIER ::= { es2126pProduces 7 }

es2126pClearLog OBJECT-TYPE
    SYNTAX      INTEGER(0|1)
    MAX-ACCESS      read-write
    STATUS      current
    DESCRIPTION
        "Clear system log.
        Get this OID always return zero.
            1 - Clear log.
            0 - do nothing. "
    ::= { es2126pLog 1 }

es2126pUploadLog OBJECT-TYPE
    SYNTAX      INTEGER(0|1)
    MAX-ACCESS      read-write
    STATUS      current
    DESCRIPTION
        "Upload current system log. Set the correct tftp server first.
        The format of log file is 'ModelName_SerialNumbuer_YYMMDD_HHMM'.
        Get this OID always return zero.
            1 - Upload log
            0 - do nothing. "
    ::= { es2126pLog 2 }

es2126pAutoUploadLogState OBJECT-TYPE
    SYNTAX      INTEGER(0|1)
    MAX-ACCESS      read-write
    STATUS      current
    DESCRIPTION
        "Enable auto-upload log function. Set the correct tftp server first.
        The format of log file is 'ModelName_SerialNumbuer_YYMMDD_HHMM'.
        Get this OID always return zero.
            1 - Enable auto-upload
            0 - do nothing. "
    ::= { es2126pLog 3 }

es2126pLogNumber OBJECT-TYPE
    SYNTAX      INTEGER(0..120)
    MAX-ACCESS      read-only
    STATUS      current
    DESCRIPTION
        "Get the number of current system log. "
    ::= { es2126pLog 4 }

es2126pLogTable OBJECT-TYPE
    SYNTAX      SEQUENCE OF ES2126PLogEntry
    MAX-ACCESS  not-accessible
    STATUS      current
    DESCRIPTION
        "This is a list of log entry. The numbers of entries are given by the value of es2126pLogNumber."
    ::= { es2126pLog 5 }

es2126pLogEntry OBJECT-TYPE
    SYNTAX      ES2126PLogEntry
    MAX-ACCESS      not-accessible
    STATUS      current
    DESCRIPTION
        "This is the Entry information for system log."
    INDEX {es2126pLogIndex}
    ::= { es2126pLogTable 1 }

ES2126PLogEntry ::=
SEQUENCE {
    es2126pLogIndex         INTEGER,
    es2126pLogEvent             DisplayString
}

es2126pLogIndex OBJECT-TYPE
    SYNTAX      INTEGER(1..120)
    MAX-ACCESS      read-only
    STATUS      current
    DESCRIPTION
        "This is the index of the log entry."
    ::= { es2126pLogEntry 1 }

es2126pLogEvent OBJECT-TYPE
    SYNTAX      DisplayString
    MAX-ACCESS      read-only
    STATUS      current
    DESCRIPTION
        "This is the detail information of the log entry."
    ::= { es2126pLogEntry 2 }

es2126pFirmware             OBJECT IDENTIFIER ::= { es2126pProduces 8 }

es2126pFirmwareFileName OBJECT-TYPE
    SYNTAX      DisplayString
    MAX-ACCESS      read-write
    STATUS      current
    DESCRIPTION
        "Get/Set the path and filename for firmware upgrading."
    ::= { es2126pFirmware 1 }

es2126pDoFirmwareUpgrade OBJECT-TYPE
    SYNTAX      INTEGER(0|1)
    MAX-ACCESS      read-write
    STATUS      current
    DESCRIPTION
        "Do firmware upgrade. Get this OID always return zero.
            1 - Do firmware upgrade.
            0 - do nothing."
    ::= { es2126pFirmware 2 }

es2126pPort             OBJECT IDENTIFIER ::= { es2126pProduces 9 }

es2126pPortStatus               OBJECT IDENTIFIER ::= { es2126pPort 1 }

es2126pPortStatusNumber OBJECT-TYPE
    SYNTAX      INTEGER(1..2147483647)
    MAX-ACCESS      read-only
    STATUS      current
    DESCRIPTION
        "Get the number of port."
    ::= { es2126pPortStatus 1 }

es2126pPortStatusTable  OBJECT-TYPE
    SYNTAX      SEQUENCE OF ES2126PPortStatusEntry
    MAX-ACCESS  not-accessible
    STATUS      current
    DESCRIPTION
        "This is a list of port status entry. The numbers of entries are given by the value of es2126pPortStatusNumber."
    ::= { es2126pPortStatus 2 }

es2126pPortStatusEntry  OBJECT-TYPE
    SYNTAX      ES2126PPortStatusEntry
    MAX-ACCESS      not-accessible
    STATUS      current
    DESCRIPTION
        "This is the entry(s) for port status information."
    INDEX {es2126pPortStatusIndex}
    ::= { es2126pPortStatusTable 1 }

ES2126PPortStatusEntry ::=
SEQUENCE {
    es2126pPortStatusIndex          INTEGER,
    es2126pPortStatusMedia          DisplayString,
    es2126pPortStatusLink           DisplayString,
    es2126pPortStatusPortState      DisplayString,
    es2126pPortStatusAutoNego       DisplayString,
    es2126pPortStatusSpdDpx         DisplayString,
    es2126pPortStatusRxPause        DisplayString,
    es2126pPortStatusTxPause        DisplayString,
    es2126pPortStatusDescription     DisplayString
}

es2126pPortStatusIndex  OBJECT-TYPE
    SYNTAX      INTEGER(1..2147483647)
    MAX-ACCESS      read-only
    STATUS      current
    DESCRIPTION
        "This is the index of the port status entry."
    ::= { es2126pPortStatusEntry 1 }

es2126pPortStatusMedia  OBJECT-TYPE
    SYNTAX      DisplayString
    MAX-ACCESS      read-only
    STATUS      current
    DESCRIPTION
        "The port media type of the port status entry."
    ::= { es2126pPortStatusEntry 2 }

es2126pPortStatusLink   OBJECT-TYPE
    SYNTAX      DisplayString
    MAX-ACCESS      read-only
    STATUS      current
    DESCRIPTION
        "This is the port link of the port status entry."
    ::= { es2126pPortStatusEntry 3 }

es2126pPortStatusPortState  OBJECT-TYPE
    SYNTAX      DisplayString
    MAX-ACCESS      read-only
    STATUS      current
    DESCRIPTION
        "This is the port state of the port status entry."
    ::= { es2126pPortStatusEntry 4 }

es2126pPortStatusAutoNego   OBJECT-TYPE
    SYNTAX      DisplayString
    MAX-ACCESS      read-only
    STATUS      current
    DESCRIPTION
        "This is the auto negotiation of the port status entry."
    ::= { es2126pPortStatusEntry 5 }

es2126pPortStatusSpdDpx     OBJECT-TYPE
    SYNTAX      DisplayString
    MAX-ACCESS      read-only
    STATUS      current
    DESCRIPTION
        "This is the speed/duplex of the port status entry."
    ::= { es2126pPortStatusEntry 6 }

es2126pPortStatusRxPause    OBJECT-TYPE
    SYNTAX      DisplayString
    MAX-ACCESS      read-only
    STATUS      current
    DESCRIPTION
        "The Rx Pause of the port status entry."
    ::= { es2126pPortStatusEntry 7 }

es2126pPortStatusTxPause    OBJECT-TYPE
    SYNTAX      DisplayString
    MAX-ACCESS      read-only
    STATUS      current
    DESCRIPTION
        "The Tx Pause of the port status entry."
    ::= { es2126pPortStatusEntry 8 }

es2126pPortStatusDescription    OBJECT-TYPE
    SYNTAX      DisplayString
    MAX-ACCESS      read-only
    STATUS      current
    DESCRIPTION
        "This is the description of port."
    ::= { es2126pPortStatusEntry 9 }

es2126pPortConf             OBJECT IDENTIFIER ::= { es2126pPort 2 }

es2126pPortConfNumber OBJECT-TYPE
    SYNTAX      INTEGER(1..2147483647)
    MAX-ACCESS      read-only
    STATUS      current
    DESCRIPTION
        "Get the number of port configuration."
    ::= { es2126pPortConf 1 }

es2126pPortConfTable    OBJECT-TYPE
    SYNTAX      SEQUENCE OF ES2126PPortConfEntry
    MAX-ACCESS  not-accessible
    STATUS      current
    DESCRIPTION
        "This is a list of port configuration entry. The numbers of entries are given by the value of es2126pPortConfNumber."
    ::= { es2126pPortConf 2 }

es2126pPortConfEntry    OBJECT-TYPE
    SYNTAX      ES2126PPortConfEntry
    MAX-ACCESS      not-accessible
    STATUS      current
    DESCRIPTION
        "This is the Entry(s) for port configuration information."
    INDEX {es2126pPortConfIndex}
    ::= { es2126pPortConfTable 1 }

ES2126PPortConfEntry ::=
SEQUENCE {
    es2126pPortConfIndex        INTEGER,
    es2126pPortConfPortState        INTEGER,
    es2126pPortConfSpdDpx           INTEGER,
    es2126pPortConfFlwCtrl          INTEGER,
    es2126pPortConfDescription      DisplayString
}

es2126pPortConfIndex    OBJECT-TYPE
    SYNTAX      INTEGER(1..2147483647)
    MAX-ACCESS      read-only
    STATUS      current
    DESCRIPTION
        "This is the index of the port configuration entry."
    ::= { es2126pPortConfEntry 1 }

es2126pPortConfPortState    OBJECT-TYPE
    SYNTAX      INTEGER(0|1)
    MAX-ACCESS      read-write
    STATUS      current
    DESCRIPTION
        "This is the port state of the port configuration entry.
         0 - disabled.
         1 - enabled. "
    ::= { es2126pPortConfEntry 2 }

es2126pPortConfSpdDpx   OBJECT-TYPE
    SYNTAX      INTEGER(0..5)
    MAX-ACCESS      read-write
    STATUS      current
    DESCRIPTION
        "This is the speed/duplex of the port configuration entry.
         0 - auto.
         1 - 10M/Half.
         2 - 10M/Full.
         3 - 100M/Half.
         4 - 100M/Full.
         5 - 1G/Full.  "
    ::= { es2126pPortConfEntry 3 }

es2126pPortConfFlwCtrl  OBJECT-TYPE
    SYNTAX      INTEGER(0|1)
    MAX-ACCESS      read-write
    STATUS      current
    DESCRIPTION
        "This is the flow control of the port configuration entry.
         0 - asymmetric.
         1 - symmetric.  "
    ::= { es2126pPortConfEntry 4 }

es2126pPortConfDescription  OBJECT-TYPE
    SYNTAX      DisplayString
    MAX-ACCESS      read-write
    STATUS      current
    DESCRIPTION
        "This is the description of port."
    ::= { es2126pPortConfEntry 5 }


es2126pPortBandwidth            OBJECT IDENTIFIER ::= { es2126pPort 3 }

es2126pPortBandwidthTable   OBJECT-TYPE
    SYNTAX      SEQUENCE OF ES2126PPortBandwidthEntry
    MAX-ACCESS  not-accessible
    STATUS      current
    DESCRIPTION
        "This is a list of port bandwidth entry."
    ::= { es2126pPortBandwidth 1 }

ES2126PPortBandwidthEntry ::=
SEQUENCE {
    es2126pPortBandwidthIndex                 INTEGER,
    es2126pPortBandwidthIngressRate        INTEGER,
    es2126pPortBandwidthEgressRate         INTEGER
}

es2126pPortBandwidthEntry   OBJECT-TYPE
    SYNTAX      ES2126PPortBandwidthEntry
    MAX-ACCESS      not-accessible
    STATUS      current
    DESCRIPTION
        "This is the Entry(s) for port bandwidth configuration."
    INDEX {es2126pPortBandwidthIndex}
    ::= { es2126pPortBandwidthTable 1 }

es2126pPortBandwidthIndex   OBJECT-TYPE
    SYNTAX      INTEGER(1..26)
    MAX-ACCESS      read-only
    STATUS      current
    DESCRIPTION
        "This is the index of the port bandwidth entry."
    ::= { es2126pPortBandwidthEntry 1 }

es2126pPortBandwidthIngressRate OBJECT-TYPE
    SYNTAX      INTEGER(66..1024000)
    MAX-ACCESS      read-write
    STATUS      current
    DESCRIPTION
        "Get/Set the port bandwidth ingress rate.
         Fast Ethernet port range: 66~102400(Kb)
         Gigabit Ethernet port range: 66~1024000(Kb)"
    ::= { es2126pPortBandwidthEntry 2 }

es2126pPortBandwidthEgressRate  OBJECT-TYPE
    SYNTAX      INTEGER(66..1024000)
    MAX-ACCESS      read-write
    STATUS      current
    DESCRIPTION
        "Get/Set the port bandwidth egress rate.
         Fast Ethernet port range: 66~102400(Kb)
         Gigabit Ethernet port range: 66~1024000(Kb)"
    ::= { es2126pPortBandwidthEntry 3 }

es2126pPortBandwidthStormType   OBJECT-TYPE
    SYNTAX      INTEGER(0..4)
    MAX-ACCESS      read-write
    STATUS      current
    DESCRIPTION
        "This is the bandwidth storm type.
        0:Disable
                1:Broadcast Storm Control
                2:Multicast Storm Control
                3:Unknown Unicast Storm Control
                4:Broadcast, Multicast, and Unknown Unicast Storm Control"
    ::= { es2126pPortBandwidth 2 }

es2126pPortBandwidthStormRate   OBJECT-TYPE
    SYNTAX      INTEGER(1..100)
    MAX-ACCESS      read-write
    STATUS      current
    DESCRIPTION
        "This is the storm rate."
    ::= { es2126pPortBandwidth 3 }

es2126pPortSFPInfo               OBJECT IDENTIFIER ::= { es2126pPort 4 }

es2126pPortSFPInfoNumber OBJECT-TYPE
    SYNTAX      INTEGER(1..2147483647)
    MAX-ACCESS      read-only
    STATUS      current
    DESCRIPTION
        "Get the number of sfp info entry."
    ::= { es2126pPortSFPInfo 1 }

es2126pPortSFPInfoTable  OBJECT-TYPE
    SYNTAX      SEQUENCE OF ES2126PPORTSFPInfoEntry
    MAX-ACCESS  not-accessible
    STATUS      current
    DESCRIPTION
        "A list of sfp info entry. The numbers of entries are given by the value of es2126pPortSFPInfoNumber."
    ::= { es2126pPortSFPInfo 2 }

ES2126PPORTSFPInfoEntry ::=
SEQUENCE {
    es2126pPortSFPInfoIndex      INTEGER,
    es2126pPortSFPConnectorType  DisplayString,
    es2126pPortSFPFiberType      DisplayString,
    es2126pPortSFPWavelength     DisplayString,
    es2126pPortSFPBaudRate       DisplayString,
    es2126pPortSFPVendorOUI      DisplayString,
    es2126pPortSFPVendorName     DisplayString,
    es2126pPortSFPVendorPN       DisplayString,
    es2126pPortSFPVendorRev      DisplayString,
    es2126pPortSFPVendorSN       DisplayString,
    es2126pPortSFPDateCode       DisplayString,
    es2126pPortSFPTemperature    DisplayString,
    es2126pPortSFPVcc            DisplayString,
    es2126pPortSFPTxBias         DisplayString,
    es2126pPortSFPTxPWR          DisplayString,
    es2126pPortSFPRxPWR          DisplayString
}

es2126pPortSFPInfoEntry  OBJECT-TYPE
    SYNTAX      ES2126PPORTSFPInfoEntry
    MAX-ACCESS      not-accessible
    STATUS      current
    DESCRIPTION
        "Entry(s) for SFP information."
    INDEX {es2126pPortSFPInfoIndex}
    ::= { es2126pPortSFPInfoTable 1 }

es2126pPortSFPInfoIndex  OBJECT-TYPE
    SYNTAX      INTEGER(1..2147483647)
    MAX-ACCESS      read-only
    STATUS      current
    DESCRIPTION
        "The index of the sfp info entry."
    ::= { es2126pPortSFPInfoEntry 1 }

es2126pPortSFPConnectorType  OBJECT-TYPE
    SYNTAX      DisplayString
    MAX-ACCESS      read-only
    STATUS      current
    DESCRIPTION
        "Get connector type of the sfp."
    ::= { es2126pPortSFPInfoEntry 2 }

es2126pPortSFPFiberType  OBJECT-TYPE
    SYNTAX      DisplayString
    MAX-ACCESS      read-only
    STATUS      current
    DESCRIPTION
        "Get fiber type of the sfp."
    ::= { es2126pPortSFPInfoEntry 3 }

es2126pPortSFPWavelength OBJECT-TYPE
    SYNTAX      DisplayString
    MAX-ACCESS      read-only
    STATUS      current
    DESCRIPTION
        "Get tx central wavelength of the sfp."
    ::= { es2126pPortSFPInfoEntry 4 }

es2126pPortSFPBaudRate   OBJECT-TYPE
    SYNTAX      DisplayString
    MAX-ACCESS      read-only
    STATUS      current
    DESCRIPTION
        "Get baud rate of the sfp."
    ::= { es2126pPortSFPInfoEntry 5 }

es2126pPortSFPVendorOUI  OBJECT-TYPE
    SYNTAX      DisplayString
    MAX-ACCESS      read-only
    STATUS      current
    DESCRIPTION
        "Get vendor OUI of the sfp."
    ::= { es2126pPortSFPInfoEntry 6 }

es2126pPortSFPVendorName OBJECT-TYPE
    SYNTAX      DisplayString
    MAX-ACCESS      read-only
    STATUS      current
    DESCRIPTION
        "Get vendor name of the sfp."
    ::= { es2126pPortSFPInfoEntry 7 }

es2126pPortSFPVendorPN   OBJECT-TYPE
    SYNTAX      DisplayString
    MAX-ACCESS      read-only
    STATUS      current
    DESCRIPTION
        "Get vendor part number of the sfp."
    ::= { es2126pPortSFPInfoEntry 8 }

es2126pPortSFPVendorRev  OBJECT-TYPE
    SYNTAX      DisplayString
    MAX-ACCESS      read-only
    STATUS      current
    DESCRIPTION
        "Get vendor revision number of the sfp."
    ::= { es2126pPortSFPInfoEntry 9 }

es2126pPortSFPVendorSN   OBJECT-TYPE
    SYNTAX      DisplayString
    MAX-ACCESS      read-only
    STATUS      current
    DESCRIPTION
        "Get vendor serial number of the sfp."
    ::= { es2126pPortSFPInfoEntry 10 }

es2126pPortSFPDateCode   OBJECT-TYPE
    SYNTAX      DisplayString
    MAX-ACCESS      read-only
    STATUS      current
    DESCRIPTION
        "Get data code of the sfp."
    ::= { es2126pPortSFPInfoEntry 11 }

es2126pPortSFPTemperature    OBJECT-TYPE
    SYNTAX      DisplayString
    MAX-ACCESS      read-only
    STATUS      current
    DESCRIPTION
        "Get current temperature of the sfp."
    ::= { es2126pPortSFPInfoEntry 12 }

es2126pPortSFPVcc    OBJECT-TYPE
    SYNTAX      DisplayString
    MAX-ACCESS      read-only
    STATUS      current
    DESCRIPTION
        "Get current internal supply voltage of the sfp."
    ::= { es2126pPortSFPInfoEntry 13 }

es2126pPortSFPTxBias OBJECT-TYPE
    SYNTAX      DisplayString
    MAX-ACCESS      read-only
    STATUS      current
    DESCRIPTION
        "Get current TX Bias of the sfp."
    ::= { es2126pPortSFPInfoEntry 14 }

es2126pPortSFPTxPWR  OBJECT-TYPE
    SYNTAX      DisplayString
    MAX-ACCESS      read-only
    STATUS      current
    DESCRIPTION
        "Get current TX output power of the sfp."
    ::= { es2126pPortSFPInfoEntry 15 }

es2126pPortSFPRxPWR  OBJECT-TYPE
    SYNTAX      DisplayString
    MAX-ACCESS      read-only
    STATUS      current
    DESCRIPTION
        "Get current Received Power of the sfp."
    ::= { es2126pPortSFPInfoEntry 16 }


es2126pLoopDetectedConf             OBJECT IDENTIFIER ::= { es2126pProduces 10 }

es2126pLoopDetectedNumber OBJECT-TYPE
    SYNTAX      INTEGER(1..2147483647)
    MAX-ACCESS      read-only
    STATUS      current
    DESCRIPTION
        "Get the number of loop detected entry."
    ::= { es2126pLoopDetectedConf 1 }

es2126pLoopDetectedTable    OBJECT-TYPE
    SYNTAX      SEQUENCE OF ES2126PLoopDetectedEntry
    MAX-ACCESS  not-accessible
    STATUS      current
    DESCRIPTION
        "This is a list of loop detected entry. The number of entries are given by the value of es2126pLoopDetectedNumber."
    ::= { es2126pLoopDetectedConf 2 }

es2126pLoopDetectedEntry    OBJECT-TYPE
    SYNTAX      ES2126PLoopDetectedEntry
    MAX-ACCESS      not-accessible
    STATUS      current
    DESCRIPTION
        "Entry(s) for loop detected information."
    INDEX {es2126pLoopDetectedfIndex}
    ::= { es2126pLoopDetectedTable 1 }

ES2126PLoopDetectedEntry ::=
SEQUENCE {
    es2126pLoopDetectedfIndex           INTEGER,
    es2126pLoopDetectedStateEbl         INTEGER,
    es2126pLoopDetectedCurrentStatus    INTEGER,
    es2126pLoopDetectedResumed          INTEGER
}

es2126pLoopDetectedfIndex   OBJECT-TYPE
    SYNTAX      INTEGER(1..2147483647)
    MAX-ACCESS      read-only
    STATUS      current
    DESCRIPTION
        "This is the index of the loop detected entry."
    ::= { es2126pLoopDetectedEntry 1 }

es2126pLoopDetectedStateEbl OBJECT-TYPE
    SYNTAX      INTEGER(0|1)
    MAX-ACCESS      read-write
    STATUS      current
    DESCRIPTION
        "The state of the loop detected entry.
         0 - disabled.
         1 - enabled. "
    ::= { es2126pLoopDetectedEntry 2 }

es2126pLoopDetectedCurrentStatus    OBJECT-TYPE
    SYNTAX      INTEGER(0|1)
    MAX-ACCESS      read-only
    STATUS      current
    DESCRIPTION
        "The current status of the loop detected port.
         0 - Unlocked
         1 - Locked due to the loop condition "
    ::= { es2126pLoopDetectedEntry 3 }

es2126pLoopDetectedResumed  OBJECT-TYPE
    SYNTAX      INTEGER(0|1)
    MAX-ACCESS      read-write
    STATUS      current
    DESCRIPTION
        "Unlock the port which is locked due to loop condition. Get this OID always return zero.
         1 - Unlock the port,
         0 - do nothing."
    ::= { es2126pLoopDetectedEntry 4 }

es2126pLoopDetectedAction OBJECT-TYPE
    SYNTAX      INTEGER(0|1)
    MAX-ACCESS      read-write
    STATUS      current
    DESCRIPTION
        "Set the corresponding action while loop is detected.
         1 - Lock the loop port,
         0 - do nothing."
    ::= { es2126pLoopDetectedConf 3 }

es2126pMacTableInfo             OBJECT IDENTIFIER ::= { es2126pProduces 11 }

es2126pMacTableMaintenance       OBJECT IDENTIFIER ::= { es2126pMacTableInfo 1 }

es2126pMacTableAgingTime  OBJECT-TYPE
    SYNTAX      INTEGER(0|10..1000000)
    MAX-ACCESS  read-write
    STATUS      current
    DESCRIPTION
        "Set the Mac Table Aging Time (10~1000000 Secs).
         0 : Disable.
        "
    ::= { es2126pMacTableMaintenance 1 }

es2126pMacTableFlush  OBJECT-TYPE
    SYNTAX      INTEGER(0|1)
    MAX-ACCESS  read-write
    STATUS      current
    DESCRIPTION
        "1 : Flush Mac Table."
    ::= { es2126pMacTableMaintenance 2 }

es2126pMacTableLearnPortLimitTable  OBJECT-TYPE
    SYNTAX      SEQUENCE OF ES2126PMacTableLearnPortLimitEntry
    MAX-ACCESS  not-accessible
    STATUS      current
    DESCRIPTION
        "This is a list of MAC Learning Limitentry."
    ::= { es2126pMacTableMaintenance 3 }

ES2126PMacTableLearnPortLimitEntry ::=
SEQUENCE {
    es2126pMacTableLearnPortLimitIndex   INTEGER,
    es2126pMacTableLearnPortLimit           INTEGER
}

es2126pMacTableLearnPortLimitEntry  OBJECT-TYPE
    SYNTAX      ES2126PMacTableLearnPortLimitEntry
    MAX-ACCESS  not-accessible
    STATUS      current
    DESCRIPTION
        "Entry(s) for Mac Table Port Learning Limit."
    INDEX {es2126pMacTableLearnPortLimitIndex}
    ::= { es2126pMacTableLearnPortLimitTable 1 }

es2126pMacTableLearnPortLimitIndex  OBJECT-TYPE
    SYNTAX      INTEGER(1..26)
    MAX-ACCESS  not-accessible
    STATUS      current
    DESCRIPTION
        "The index of the Mac Table Learning Limit entry."
    ::= { es2126pMacTableLearnPortLimitEntry 1 }

es2126pMacTableLearnPortLimit  OBJECT-TYPE
    SYNTAX      INTEGER(0..8191)
    MAX-ACCESS  read-write
    STATUS      current
    DESCRIPTION
        "Port Learning Limit (0~8191)."
    ::= { es2126pMacTableLearnPortLimitEntry 2 }

es2126pMacTableStaticMac       OBJECT IDENTIFIER ::= { es2126pMacTableInfo 3 }

es2126pMacTableStaticMacNumber  OBJECT-TYPE
    SYNTAX      INTEGER(0..1024)
    MAX-ACCESS  read-only
    STATUS      current
    DESCRIPTION
        "This is number of static Mac table entry"
    ::= { es2126pMacTableStaticMac 1 }

es2126pMacTableStaticMacEntryCreate  OBJECT-TYPE
    SYNTAX      INTEGER(0..1024)
    MAX-ACCESS  read-write
    STATUS      current
    DESCRIPTION
        "Creat a static mac entry.
         Set 1: add a new entry,
         Get: the number means index."
    ::= { es2126pMacTableStaticMac 2 }

es2126pMacTableStaticMacTable  OBJECT-TYPE
    SYNTAX      SEQUENCE OF ES2126PMacTableStaticMacEntry
    MAX-ACCESS  not-accessible
    STATUS      current
    DESCRIPTION
        "This is a list of static MAC table."
    ::= { es2126pMacTableStaticMac 3 }

ES2126PMacTableStaticMacEntry ::=
SEQUENCE {
    es2126pMacTableStaticMacIndex        INTEGER,
    es2126pMacTableStaticMacAddress      DisplayString,
    es2126pMacTableStaticMacVid           INTEGER,
    es2126pMacTableStaticMacQueue           INTEGER,
    es2126pMacTableStaticMacFwRule          INTEGER,
    es2126pMacTableStaticMacPort        INTEGER,
    es2126pMacTableStaticMacEntryAction     INTEGER
}

es2126pMacTableStaticMacEntry  OBJECT-TYPE
    SYNTAX      ES2126PMacTableStaticMacEntry
    MAX-ACCESS  not-accessible
    STATUS      current
    DESCRIPTION
        "Entry(s) for Static Mac Table."
    INDEX {es2126pMacTableStaticMacIndex}
    ::= { es2126pMacTableStaticMacTable 1 }

es2126pMacTableStaticMacIndex  OBJECT-TYPE
    SYNTAX      INTEGER(1..1024)
    MAX-ACCESS      not-accessible
    STATUS      current
    DESCRIPTION
        "The index of the static Mac Table."
    ::= { es2126pMacTableStaticMacEntry 1 }

es2126pMacTableStaticMacAddress  OBJECT-TYPE
    SYNTAX      DisplayString
    MAX-ACCESS  read-write
    STATUS      current
    DESCRIPTION
        "The mac address of the static mac table entry."
    ::= { es2126pMacTableStaticMacEntry 2 }

es2126pMacTableStaticMacVid  OBJECT-TYPE
    SYNTAX      INTEGER(1..4094)
    MAX-ACCESS  read-write
    STATUS      current
    DESCRIPTION
        "The vlan id of the static mac table entry."
    ::= { es2126pMacTableStaticMacEntry 3 }

es2126pMacTableStaticMacQueue  OBJECT-TYPE
    SYNTAX      INTEGER(0..3)
    MAX-ACCESS  read-write
    STATUS      current
    DESCRIPTION
        "The queue of the static mac table entry."
    ::= { es2126pMacTableStaticMacEntry 4 }

es2126pMacTableStaticMacFwRule  OBJECT-TYPE
    SYNTAX      INTEGER(0..2)
    MAX-ACCESS  read-write
    STATUS      current
    DESCRIPTION
        "The forwarding rule of the static mac table entry.
         0 : static
         1 : Static with Destination Drop
         2 : Static with Source Drop
        "
    ::= { es2126pMacTableStaticMacEntry 5 }

es2126pMacTableStaticMacPort  OBJECT-TYPE
    SYNTAX      INTEGER(1..26)
    MAX-ACCESS  read-write
    STATUS      current
    DESCRIPTION
        "The port of the static mac table entry."
    ::= { es2126pMacTableStaticMacEntry 6 }

es2126pMacTableStaticMacEntryAction  OBJECT-TYPE
    SYNTAX      INTEGER(1..3)
    MAX-ACCESS  read-write
    STATUS      current
    DESCRIPTION
        "The action of the static mac table entry.
         1:action
         2:non-action
         3:delete"
    ::= { es2126pMacTableStaticMacEntry 7 }

es2126pMacTableMacAlias       OBJECT IDENTIFIER ::= { es2126pMacTableInfo 4 }

es2126pMacTableMacAliasNumber  OBJECT-TYPE
    SYNTAX      INTEGER(0..8192)
    MAX-ACCESS  read-only
    STATUS      current
    DESCRIPTION
        "This is number of static Mac table entry"
    ::= { es2126pMacTableMacAlias 1 }

es2126pMacTableMacAliasEntryCreate  OBJECT-TYPE
    SYNTAX      INTEGER(0..8192)
    MAX-ACCESS  read-write
    STATUS      current
    DESCRIPTION
        "Creat a static mac alias entry.
         Set 1: add a new entry,
         Get: the number means index."
    ::= { es2126pMacTableMacAlias 2 }

es2126pMacTableMacAliasTable  OBJECT-TYPE
    SYNTAX      SEQUENCE OF ES2126PMacTableMacAliasEntry
    MAX-ACCESS  not-accessible
    STATUS      current
    DESCRIPTION
        "This is a list of MAC Alias table."
    ::= { es2126pMacTableMacAlias 3 }

ES2126PMacTableMacAliasEntry ::=
SEQUENCE {
    es2126pMacTableMacAliasIndex        INTEGER,
    es2126pMacTableMacAliasAddress      DisplayString,
    es2126pMacTableMacAliasAlias        DisplayString,
    es2126pMacTableMacAliasEntryAction  INTEGER
}

es2126pMacTableMacAliasEntry  OBJECT-TYPE
    SYNTAX      ES2126PMacTableMacAliasEntry
    MAX-ACCESS  not-accessible
    STATUS      current
    DESCRIPTION
        "Entry(s) for Alias Mac Table."
    INDEX {es2126pMacTableMacAliasIndex}
    ::= { es2126pMacTableMacAliasTable 1 }

es2126pMacTableMacAliasIndex  OBJECT-TYPE
    SYNTAX      INTEGER(1..1024)
    MAX-ACCESS      not-accessible
    STATUS      current
    DESCRIPTION
        "The index of the Alias Mac Table."
    ::= { es2126pMacTableMacAliasEntry 1 }

es2126pMacTableMacAliasAddress  OBJECT-TYPE
    SYNTAX      DisplayString
    MAX-ACCESS      read-write
    STATUS      current
    DESCRIPTION
        "The Mac address of the Alias Mac Table."
    ::= { es2126pMacTableMacAliasEntry 2 }

es2126pMacTableMacAliasAlias  OBJECT-TYPE
    SYNTAX      DisplayString
    MAX-ACCESS      read-write
    STATUS      current
    DESCRIPTION
        "The Mac Alias of the Alias Mac Table."
    ::= { es2126pMacTableMacAliasEntry 3 }

es2126pMacTableMacAliasEntryAction  OBJECT-TYPE
    SYNTAX      INTEGER(1..3)
    MAX-ACCESS  read-write
    STATUS      current
    DESCRIPTION
        "The action of the alias mac table entry.
         1:action
         2:non-action
         3:delete"
    ::= { es2126pMacTableMacAliasEntry 4 }

es2126pGVRPInfo             OBJECT IDENTIFIER ::= { es2126pProduces 12 }

es2126pGvrpConf             OBJECT IDENTIFIER ::= { es2126pGVRPInfo 1 }

es2126pGvrpConfState OBJECT-TYPE
    SYNTAX      INTEGER(0|1)
    MAX-ACCESS      read-write
    STATUS      current
    DESCRIPTION
        "The state of GVRP.
         0 - Disable
         1 - Enable
    "
    ::= { es2126pGvrpConf 1 }

es2126pGvrpConfTable    OBJECT-TYPE
    SYNTAX      SEQUENCE OF ES2126PGvrpConfEntry
    MAX-ACCESS  not-accessible
    STATUS      current
    DESCRIPTION
        "This is a list of the GVRP conf table."
    ::= { es2126pGvrpConf 2 }

ES2126PGvrpConfEntry ::=
SEQUENCE {
    es2126pGvrpConfIndex             INTEGER,
    es2126pGvrpConfJoinTime          INTEGER,
    es2126pGvrpConfLeaveTime         INTEGER,
    es2126pGvrpConfLeaveAllTime      INTEGER,
    es2126pGvrpConfDefaultAppMode    INTEGER,
    es2126pGvrpConfDefaultRegMode    INTEGER,
    es2126pGvrpConfRestrictedMode    INTEGER
}

es2126pGvrpConfEntry    OBJECT-TYPE
    SYNTAX      ES2126PGvrpConfEntry
    MAX-ACCESS      not-accessible
    STATUS      current
    DESCRIPTION
        "Entry(s) for the GVRP conf table."
    INDEX {es2126pGvrpConfIndex}
    ::= { es2126pGvrpConfTable 1 }

es2126pGvrpConfIndex    OBJECT-TYPE
    SYNTAX      INTEGER(1..26)
    MAX-ACCESS      not-accessible
    STATUS      current
    DESCRIPTION
        "The index of the GVRP conf table."
    ::= { es2126pGvrpConfEntry 1 }

es2126pGvrpConfJoinTime OBJECT-TYPE
    SYNTAX      INTEGER(20..100)
    MAX-ACCESS      read-write
    STATUS      current
    DESCRIPTION
        "The join time of the GVRP entry.
         range: 20~100
         default 20 centisecond"
    ::= { es2126pGvrpConfEntry 2 }

es2126pGvrpConfLeaveTime    OBJECT-TYPE
    SYNTAX      INTEGER(60..300)
    MAX-ACCESS      read-write
    STATUS      current
    DESCRIPTION
        "The leave time of the GVRP entry.
         range: 60~300
        default:60 centisecond"
    ::= { es2126pGvrpConfEntry 3 }

es2126pGvrpConfLeaveAllTime OBJECT-TYPE
    SYNTAX      INTEGER(1000..5000)
    MAX-ACCESS      read-write
    STATUS      current
    DESCRIPTION
        "The leave all time of the GVRP entry.
         range: 1000~5000
         default: 1000 unit time"
    ::= { es2126pGvrpConfEntry 4 }

es2126pGvrpConfDefaultAppMode   OBJECT-TYPE
    SYNTAX      INTEGER(0|1)
    MAX-ACCESS      read-write
    STATUS      current
    DESCRIPTION
        "The default application mode of the GVRP entry.
         0 - Normal
         1 - Non-Participant
         default: Normal"
    ::= { es2126pGvrpConfEntry 5 }

es2126pGvrpConfDefaultRegMode   OBJECT-TYPE
    SYNTAX      INTEGER(0|1|2)
    MAX-ACCESS      read-write
    STATUS      current
    DESCRIPTION
        "The default registrar mode of the GVRP entry.
         0 - Normal
         1 - Fixed
         2 - Forbidden
         default: Normal"
    ::= { es2126pGvrpConfEntry 6 }

es2126pGvrpConfRestrictedMode   OBJECT-TYPE
    SYNTAX      INTEGER(0|1)
    MAX-ACCESS      read-write
    STATUS      current
    DESCRIPTION
        "The restricted mode of the GVRP entry.
         0 - Disable
         1 - Enable
         default: Disable"
    ::= { es2126pGvrpConfEntry 7 }

es2126pGvrpCounter              OBJECT IDENTIFIER ::= { es2126pGVRPInfo 2 }

es2126pGvrpCounterTable OBJECT-TYPE
    SYNTAX      SEQUENCE OF ES2126PGvrpCounterEntry
    MAX-ACCESS  not-accessible
    STATUS      current
    DESCRIPTION
        "This is a list of the GVRP counter table."
    ::= { es2126pGvrpCounter 1 }

ES2126PGvrpCounterEntry ::=
SEQUENCE {
    es2126pGvrpCounterIndex              INTEGER,
    es2126pGvrpCounterRxTotalGvrpPkts    Counter32,
    es2126pGvrpCounterRxInvalidGvrpPkts  Counter32,
    es2126pGvrpCounterRxLeaveAllMsg      Counter32,
    es2126pGvrpCounterRxJoinEmptyMsg     Counter32,
    es2126pGvrpCounterRxJoinInMsg        Counter32,
    es2126pGvrpCounterRxLeaveEmptyMsg    Counter32,
    es2126pGvrpCounterRxEmptyMsg         Counter32,
    es2126pGvrpCounterTxTotalGvrpPkts    Counter32,
    es2126pGvrpCounterTxLeaveAllMsg      Counter32,
    es2126pGvrpCounterTxJoinEmptyMsg     Counter32,
    es2126pGvrpCounterTxJoinInMsg        Counter32,
    es2126pGvrpCounterTxLeaveEmptyMsg    Counter32,
    es2126pGvrpCounterTxEmptyMsg         Counter32
}

es2126pGvrpCounterEntry OBJECT-TYPE
    SYNTAX      ES2126PGvrpCounterEntry
    MAX-ACCESS      not-accessible
    STATUS      current
    DESCRIPTION
        "Entry(s) for the GVRP counter table."
    INDEX {es2126pGvrpCounterIndex}
    ::= { es2126pGvrpCounterTable 1 }

es2126pGvrpCounterIndex OBJECT-TYPE
    SYNTAX      INTEGER(1..26)
    MAX-ACCESS      not-accessible
    STATUS      current
    DESCRIPTION
        "The port index of the GVRP counter table."
    ::= { es2126pGvrpCounterEntry 1 }

es2126pGvrpCounterRxTotalGvrpPkts   OBJECT-TYPE
    SYNTAX      Counter32
    MAX-ACCESS      read-only
    STATUS      current
    DESCRIPTION
        "This is Rx Total GVRP packet counters."
    ::= { es2126pGvrpCounterEntry 2 }

es2126pGvrpCounterRxInvalidGvrpPkts OBJECT-TYPE
    SYNTAX      Counter32
    MAX-ACCESS      read-only
    STATUS      current
    DESCRIPTION
        "This is Rx Invalid GVRP packet counters."
    ::= { es2126pGvrpCounterEntry 3 }

es2126pGvrpCounterRxLeaveAllMsg OBJECT-TYPE
    SYNTAX      Counter32
    MAX-ACCESS      read-only
    STATUS      current
    DESCRIPTION
        "This is Rx LeaveAll message packet counters."
    ::= { es2126pGvrpCounterEntry 4 }

es2126pGvrpCounterRxJoinEmptyMsg    OBJECT-TYPE
    SYNTAX      Counter32
    MAX-ACCESS      read-only
    STATUS      current
    DESCRIPTION
        "This is Rx JoinEmpty message packet counters."
    ::= { es2126pGvrpCounterEntry 5 }

es2126pGvrpCounterRxJoinInMsg   OBJECT-TYPE
    SYNTAX      Counter32
    MAX-ACCESS      read-only
    STATUS      current
    DESCRIPTION
        "This is Rx JoinIn message packet counters."
    ::= { es2126pGvrpCounterEntry 6 }

es2126pGvrpCounterRxLeaveEmptyMsg   OBJECT-TYPE
    SYNTAX      Counter32
    MAX-ACCESS      read-only
    STATUS      current
    DESCRIPTION
        "This is Rx LeaveEmpty message packet counters."
    ::= { es2126pGvrpCounterEntry 7 }

es2126pGvrpCounterRxEmptyMsg    OBJECT-TYPE
    SYNTAX      Counter32
    MAX-ACCESS      read-only
    STATUS      current
    DESCRIPTION
        "This is Rx Empty message packet counters."
    ::= { es2126pGvrpCounterEntry 8 }

es2126pGvrpCounterTxTotalGvrpPkts   OBJECT-TYPE
    SYNTAX      Counter32
    MAX-ACCESS      read-only
    STATUS      current
    DESCRIPTION
        "This is Tx Total GVRP packet counters."
    ::= { es2126pGvrpCounterEntry 9 }

es2126pGvrpCounterTxLeaveAllMsg OBJECT-TYPE
    SYNTAX      Counter32
    MAX-ACCESS      read-only
    STATUS      current
    DESCRIPTION
        "This is Tx LeaveAll message packet counters."
    ::= { es2126pGvrpCounterEntry 10 }

es2126pGvrpCounterTxJoinEmptyMsg    OBJECT-TYPE
    SYNTAX      Counter32
    MAX-ACCESS      read-only
    STATUS      current
    DESCRIPTION
        "This is Tx JoinEmpty message packet counters."
    ::= { es2126pGvrpCounterEntry 11 }

es2126pGvrpCounterTxJoinInMsg   OBJECT-TYPE
    SYNTAX      Counter32
    MAX-ACCESS      read-only
    STATUS      current
    DESCRIPTION
        "This is Tx JoinIn message packet counters."
    ::= { es2126pGvrpCounterEntry 12 }

es2126pGvrpCounterTxLeaveEmptyMsg   OBJECT-TYPE
    SYNTAX      Counter32
    MAX-ACCESS      read-only
    STATUS      current
    DESCRIPTION
        "This is Tx LeaveEmpty message packet counters."
    ::= { es2126pGvrpCounterEntry 13 }

es2126pGvrpCounterTxEmptyMsg    OBJECT-TYPE
    SYNTAX      Counter32
    MAX-ACCESS      read-only
    STATUS      current
    DESCRIPTION
        "This is Tx Empty message packet counters."
    ::= { es2126pGvrpCounterEntry 14 }

es2126pGvrpGroup            OBJECT IDENTIFIER ::= { es2126pGVRPInfo 3 }

es2126pGvrpGroupNumber  OBJECT-TYPE
    SYNTAX      INTEGER(0..4094)
    MAX-ACCESS      read-only
    STATUS      current
    DESCRIPTION
        "This is number of the GVRP group table entry."
    ::= { es2126pGvrpGroup 1 }

es2126pGvrpGroupTable   OBJECT-TYPE
    SYNTAX      SEQUENCE OF ES2126PGvrpGroupEntry
    MAX-ACCESS  not-accessible
    STATUS      current
    DESCRIPTION
        "This is a list of the GVRP group table."
    ::= { es2126pGvrpGroup 2 }

ES2126PGvrpGroupEntry ::=
SEQUENCE {
    es2126pGvrpGroupId            INTEGER,
    es2126pGvrpGroupVid           INTEGER,
    es2126pGvrpGroupMemberPort    DisplayString
}

es2126pGvrpGroupEntry   OBJECT-TYPE
    SYNTAX      ES2126PGvrpGroupEntry
    MAX-ACCESS      not-accessible
    STATUS      current
    DESCRIPTION
        "Entry(s) for the GVRP group table."
    INDEX {es2126pGvrpGroupId}
    ::= { es2126pGvrpGroupTable 1 }

es2126pGvrpGroupId  OBJECT-TYPE
    SYNTAX      INTEGER(1..4094)
    MAX-ACCESS      read-only
    STATUS      current
    DESCRIPTION
        "The index of the GVRP group table."
    ::= { es2126pGvrpGroupEntry 1 }

es2126pGvrpGroupVid OBJECT-TYPE
    SYNTAX      INTEGER(1..4094)
    MAX-ACCESS      read-only
    STATUS      current
    DESCRIPTION
        "This is vid of GVRP group."
    ::= { es2126pGvrpGroupEntry 2 }

es2126pGvrpGroupMemberPort  OBJECT-TYPE
    SYNTAX      DisplayString
    MAX-ACCESS      read-only
    STATUS      current
    DESCRIPTION
        "This is the member port of GVRP group."
    ::= { es2126pGvrpGroupEntry 3 }

es2126pSecurity             OBJECT IDENTIFIER ::= { es2126pProduces 13 }

es2126pIsolatedPortGroup OBJECT-TYPE
    SYNTAX      DisplayString
    MAX-ACCESS      read-write
    STATUS      current
    DESCRIPTION
        "This is isolated group.
         0: Disable"
    ::= { es2126pSecurity 1 }

es2126pMirror               OBJECT IDENTIFIER ::= { es2126pSecurity 2 }

es2126pMirrorMode OBJECT-TYPE
    SYNTAX      INTEGER(0|1)
    MAX-ACCESS      read-write
    STATUS      current
    DESCRIPTION
        "This is mirror mode.
         0 - Disable
         1 - Enable
    "
    ::= { es2126pMirror 1 }

es2126pMonitoringPort OBJECT-TYPE
    SYNTAX      INTEGER(1..26)
    MAX-ACCESS      read-write
    STATUS      current
    DESCRIPTION
        "This is monitoring port."
    ::= { es2126pMirror 2 }

es2126pMonitoredIngressPort OBJECT-TYPE
    SYNTAX      DisplayString
    MAX-ACCESS      read-write
    STATUS      current
    DESCRIPTION
        "This is monitored ingress ports."
    ::= { es2126pMirror 3 }

es2126pMonitoredEgressPort OBJECT-TYPE
    SYNTAX      DisplayString
    MAX-ACCESS      read-write
    STATUS      current
    DESCRIPTION
        "This is monitored egress ports."
    ::= { es2126pMirror 4 }

es2126pVirtualStack        OBJECT IDENTIFIER ::= { es2126pProduces 14 }

es2126pVirtualStackState   OBJECT-TYPE
    SYNTAX      INTEGER(0|1)
    MAX-ACCESS  read-write
    STATUS      current
    DESCRIPTION
        "Set the Virtual Stack State.
         0 : disable,
         1 : enable
        "
    ::= { es2126pVirtualStack 1 }

es2126pVirtualStackRole   OBJECT-TYPE
    SYNTAX      INTEGER(0|1)
    MAX-ACCESS  read-write
    STATUS      current
    DESCRIPTION
        "Set the Virtual Stack Role.
         0 : slave,
         1 : master
        "
    ::= { es2126pVirtualStack 2 }

es2126pVirtualStackGroupID  OBJECT-TYPE
    SYNTAX      DisplayString
    MAX-ACCESS  read-write
    STATUS      current
    DESCRIPTION
        "Set the Virtual Stack Group ID."
    ::= { es2126pVirtualStack 3 }

es2126pManagementSecurity               OBJECT IDENTIFIER ::= { es2126pProduces 15 }

es2126pManagementSecurityNumber OBJECT-TYPE
    SYNTAX      INTEGER(0..64)
    MAX-ACCESS      read-only
    STATUS      current
    DESCRIPTION
        "This is number of the management security table entry."
    ::= { es2126pManagementSecurity 1 }

es2126pManagementSecurityEntryCreate OBJECT-TYPE
    SYNTAX      INTEGER(0..64)
    MAX-ACCESS      read-write
    STATUS      current
    DESCRIPTION
        "Creat a management security entry.
         Set 1: add a new entry,
         Get: the number means index."
    ::= { es2126pManagementSecurity 2 }

es2126pManagementSecurityTable  OBJECT-TYPE
    SYNTAX      SEQUENCE OF ES2126PManagementSecurityEntry
    MAX-ACCESS  not-accessible
    STATUS      current
    DESCRIPTION
        "This is a list of the management security table."
    ::= { es2126pManagementSecurity 3 }

ES2126PManagementSecurityEntry ::=
SEQUENCE {
    es2126pManagementSecurityIndex          INTEGER,
    es2126pManagementSecurityName           DisplayString,
    es2126pManagementSecurityVid            INTEGER,
    es2126pManagementSecurityIpRange        DisplayString,
    es2126pManagementSecurityIncomigPort    DisplayString,
    es2126pManagementSecurityAccessType     DisplayString,
    es2126pManagementSecurityAction         INTEGER,
    es2126pManagementSecurityEntryAction    INTEGER
}

es2126pManagementSecurityEntry  OBJECT-TYPE
    SYNTAX      ES2126PManagementSecurityEntry
    MAX-ACCESS      not-accessible
    STATUS      current
    DESCRIPTION
        "Entry(s) for the management security table."
    INDEX {es2126pManagementSecurityIndex}
    ::= { es2126pManagementSecurityTable 1 }

es2126pManagementSecurityIndex  OBJECT-TYPE
    SYNTAX      INTEGER(1..64)
    MAX-ACCESS      not-accessible
    STATUS      current
    DESCRIPTION
        "The index of the management security table."
    ::= { es2126pManagementSecurityEntry 1 }

es2126pManagementSecurityName   OBJECT-TYPE
    SYNTAX      DisplayString
    MAX-ACCESS      read-write
    STATUS      current
    DESCRIPTION
        "The name of the management security entry."
    ::= { es2126pManagementSecurityEntry 2 }

es2126pManagementSecurityVid    OBJECT-TYPE
    SYNTAX      INTEGER(0..4094)
    MAX-ACCESS      read-write
    STATUS      current
    DESCRIPTION
        "This is the vid of the management security entry.
         0: any VID."
    ::= { es2126pManagementSecurityEntry 3 }

es2126pManagementSecurityIpRange    OBJECT-TYPE
    SYNTAX      DisplayString
    MAX-ACCESS      read-write
    STATUS      current
    DESCRIPTION
        "This is the IP range of the management security entry.
         0: any IP."
    ::= { es2126pManagementSecurityEntry 4 }

es2126pManagementSecurityIncomigPort    OBJECT-TYPE
    SYNTAX      DisplayString
    MAX-ACCESS      read-write
    STATUS      current
    DESCRIPTION
        "This is the ports of the management security entry.
         0: any incoming port."
    ::= { es2126pManagementSecurityEntry 5 }

es2126pManagementSecurityAccessType OBJECT-TYPE
    SYNTAX      DisplayString
    MAX-ACCESS      read-write
    STATUS      current
    DESCRIPTION
        "This is the access type of the management security entry.
         for example: http,snmp,telnet,https,ssh
         for example: http,telnet
         for example: any
         any means http,snmp and telnet."
    ::= { es2126pManagementSecurityEntry 6 }

es2126pManagementSecurityAction OBJECT-TYPE
    SYNTAX      INTEGER(0|1)
    MAX-ACCESS      read-write
    STATUS      current
    DESCRIPTION
        "This is the action of the management security entry.
         0:deny
         1:accept"
    ::= { es2126pManagementSecurityEntry 7 }

es2126pManagementSecurityEntryAction    OBJECT-TYPE
    SYNTAX      INTEGER(0..3)
    MAX-ACCESS      read-write
    STATUS      current
    DESCRIPTION
        "The action the management security entry.
         1:action
         2:non-action
         3:delete"
    ::= { es2126pManagementSecurityEntry 8 }

es2126pQoS              OBJECT IDENTIFIER ::= { es2126pProduces 16 }

es2126pQoSGlobalConfig              OBJECT IDENTIFIER ::= { es2126pQoS 1 }

es2126pQoSMode OBJECT-TYPE
    SYNTAX      INTEGER(0|1)
    MAX-ACCESS      read-write
    STATUS      current
    DESCRIPTION
        "The mode of QoS.
         0 - Disable
         1 - Enable
    "
    ::= { es2126pQoSGlobalConfig 1 }

es2126pQosPriorityControl1p OBJECT-TYPE
    SYNTAX      INTEGER(0|1)
    MAX-ACCESS      read-write
    STATUS      current
    DESCRIPTION
        "This is the priority control for 802.1p.
         0 - Disable
         1 - Enable
    "
    ::= { es2126pQoSGlobalConfig 2 }

es2126pQosPriorityControlTOS OBJECT-TYPE
    SYNTAX      INTEGER(0|1)
    MAX-ACCESS      read-write
    STATUS      current
    DESCRIPTION
        "This is the priority control for TOS.
         0 - Disable
         1 - Enable
    "
    ::= { es2126pQoSGlobalConfig 3 }

es2126pQosPriorityControlDSCP OBJECT-TYPE
    SYNTAX      INTEGER(0|1)
    MAX-ACCESS      read-write
    STATUS      current
    DESCRIPTION
        "This is the priority control for DSCP.
         0 - Disable
         1 - Enable
    "
    ::= { es2126pQoSGlobalConfig 4 }

es2126pQoSSchedulingMethod OBJECT-TYPE
    SYNTAX      INTEGER(0|1)
    MAX-ACCESS      read-write
    STATUS      current
    DESCRIPTION
        "This is the scheduling method.
         0 - WRR
         1 - Strict
    "
    ::= { es2126pQoSGlobalConfig 5 }

es2126pQoSWeightQ0 OBJECT-TYPE
    SYNTAX      INTEGER(1..55)
    MAX-ACCESS      read-write
    STATUS      current
    DESCRIPTION
        "This is the weigtht of Queue0."
    ::= { es2126pQoSGlobalConfig 6 }

es2126pQoSWeightQ1 OBJECT-TYPE
    SYNTAX      INTEGER(1..55)
    MAX-ACCESS      read-write
    STATUS      current
    DESCRIPTION
        "This is the weigtht of Queue1."
    ::= { es2126pQoSGlobalConfig 7 }

es2126pQoSWeightQ2 OBJECT-TYPE
    SYNTAX      INTEGER(1..55)
    MAX-ACCESS      read-write
    STATUS      current
    DESCRIPTION
        "This is the weigtht of Queue2."
    ::= { es2126pQoSGlobalConfig 8 }

es2126pQoSWeightQ3 OBJECT-TYPE
    SYNTAX      INTEGER(1..55)
    MAX-ACCESS      read-write
    STATUS      current
    DESCRIPTION
        "This is the weigtht of Queue3."
    ::= { es2126pQoSGlobalConfig 9 }

es2126pQoSVIPPort OBJECT-TYPE
    SYNTAX      DisplayString
    MAX-ACCESS      read-write
    STATUS      current
    DESCRIPTION
        "This is the VIP group for QoS."
    ::= { es2126pQoS 2 }

es2126pQoS1pPriority            OBJECT IDENTIFIER ::= { es2126pQoS 3 }

es2126pQoS1pPriorityTable   OBJECT-TYPE
    SYNTAX      SEQUENCE OF ES2126PQoS1pPriorityEntry
    MAX-ACCESS  not-accessible
    STATUS      current
    DESCRIPTION
        "This is a list of the 802.1p."
    ::= { es2126pQoS1pPriority 1 }

ES2126PQoS1pPriorityEntry ::=
SEQUENCE {
    es2126pQoS1pPriorityIndex    INTEGER,
    es2126pQoS1pPriorityValue    INTEGER,
    es2126pQoS1pPriorityQueue    INTEGER
}

es2126pQoS1pPriorityEntry   OBJECT-TYPE
    SYNTAX      ES2126PQoS1pPriorityEntry
    MAX-ACCESS      not-accessible
    STATUS      current
    DESCRIPTION
        "Entry(s) for the 802.1p priority table."
    INDEX {es2126pQoS1pPriorityIndex}
    ::= { es2126pQoS1pPriorityTable 1 }

es2126pQoS1pPriorityIndex   OBJECT-TYPE
    SYNTAX      INTEGER(1..8)
    MAX-ACCESS      not-accessible
    STATUS      current
    DESCRIPTION
        "The index of the 802.1p priority table."
    ::= { es2126pQoS1pPriorityEntry 1 }

es2126pQoS1pPriorityValue   OBJECT-TYPE
    SYNTAX      INTEGER(0..7)
    MAX-ACCESS      read-only
    STATUS      current
    DESCRIPTION
        "The value of 802.1p priority entry."
    ::= { es2126pQoS1pPriorityEntry 2 }

es2126pQoS1pPriorityQueue   OBJECT-TYPE
    SYNTAX      INTEGER(0..3)
    MAX-ACCESS      read-write
    STATUS      current
    DESCRIPTION
        "The queue of 802.1p priority entry."
    ::= { es2126pQoS1pPriorityEntry 3 }

es2126pQoSDTypeTOSPriority              OBJECT IDENTIFIER ::= { es2126pQoS 4 }

es2126pQoSDTypeTOSPriorityTable OBJECT-TYPE
    SYNTAX      SEQUENCE OF ES2126PQoSDTypeTOSPriorityEntry
    MAX-ACCESS  not-accessible
    STATUS      current
    DESCRIPTION
        "This is a list of the TOS delay priority mapping entry."
    ::= { es2126pQoSDTypeTOSPriority 1 }

ES2126PQoSDTypeTOSPriorityEntry ::=
SEQUENCE {
    es2126pQoSDTypeTOSPriorityIndex    INTEGER,
    es2126pQoSDTypeTOSPriorityValue    INTEGER,
    es2126pQoSDTypeTOSPriorityQueue    INTEGER
}

es2126pQoSDTypeTOSPriorityEntry OBJECT-TYPE
    SYNTAX      ES2126PQoSDTypeTOSPriorityEntry
    MAX-ACCESS      not-accessible
    STATUS      current
    DESCRIPTION
        "Entry(s) for the ToS delay priority mapping entry."
    INDEX {es2126pQoSDTypeTOSPriorityIndex}
    ::= { es2126pQoSDTypeTOSPriorityTable 1 }

es2126pQoSDTypeTOSPriorityIndex OBJECT-TYPE
    SYNTAX      INTEGER(1..8)
    MAX-ACCESS      not-accessible
    STATUS      current
    DESCRIPTION
        "The index of the ToS delay priority mapping table."
    ::= { es2126pQoSDTypeTOSPriorityEntry 1 }

es2126pQoSDTypeTOSPriorityValue OBJECT-TYPE
    SYNTAX      INTEGER(0..7)
    MAX-ACCESS      read-only
    STATUS      current
    DESCRIPTION
        "The value of ToS delay priority mapping entry."
    ::= { es2126pQoSDTypeTOSPriorityEntry 2 }

es2126pQoSDTypeTOSPriorityQueue OBJECT-TYPE
    SYNTAX      INTEGER(0..3)
    MAX-ACCESS      read-write
    STATUS      current
    DESCRIPTION
        "The queue of ToS delay priority mapping entry."
    ::= { es2126pQoSDTypeTOSPriorityEntry 3 }

es2126pQoSTTypeTOSPriority              OBJECT IDENTIFIER ::= { es2126pQoS 5 }

es2126pQoSTTypeTOSPriorityTable OBJECT-TYPE
    SYNTAX      SEQUENCE OF ES2126PQoSTTypeTOSPriorityEntry
    MAX-ACCESS  not-accessible
    STATUS      current
    DESCRIPTION
        "This is a list of the ToS throughput priority mapping entry."
    ::= { es2126pQoSTTypeTOSPriority 1 }

ES2126PQoSTTypeTOSPriorityEntry ::=
SEQUENCE {
    es2126pQoSTTypeTOSPriorityIndex    INTEGER,
    es2126pQoSTTypeTOSPriorityValue    INTEGER,
    es2126pQoSTTypeTOSPriorityQueue    INTEGER
}

es2126pQoSTTypeTOSPriorityEntry OBJECT-TYPE
    SYNTAX      ES2126PQoSTTypeTOSPriorityEntry
    MAX-ACCESS      not-accessible
    STATUS      current
    DESCRIPTION
        "Entry(s) for the TOS Throughput mapping entry."
    INDEX {es2126pQoSTTypeTOSPriorityIndex}
    ::= { es2126pQoSTTypeTOSPriorityTable 1 }

es2126pQoSTTypeTOSPriorityIndex OBJECT-TYPE
    SYNTAX      INTEGER(1..8)
    MAX-ACCESS      not-accessible
    STATUS      current
    DESCRIPTION
        "The index of the TOS throughput priority mapping table."
    ::= { es2126pQoSTTypeTOSPriorityEntry 1 }

es2126pQoSTTypeTOSPriorityValue OBJECT-TYPE
    SYNTAX      INTEGER(0..7)
    MAX-ACCESS      read-only
    STATUS      current
    DESCRIPTION
        "The value of TOS throughput priority mapping entry."
    ::= { es2126pQoSTTypeTOSPriorityEntry 2 }

es2126pQoSTTypeTOSPriorityQueue OBJECT-TYPE
    SYNTAX      INTEGER(0..3)
    MAX-ACCESS      read-write
    STATUS      current
    DESCRIPTION
        "The queue of TOS throughput priority mapping entry."
    ::= { es2126pQoSTTypeTOSPriorityEntry 3 }

es2126pQoSRTypeTOSPriority              OBJECT IDENTIFIER ::= { es2126pQoS 6 }

es2126pQoSRTypeTOSPriorityTable OBJECT-TYPE
    SYNTAX      SEQUENCE OF ES2126PQoSRTypeTOSPriorityEntry
    MAX-ACCESS  not-accessible
    STATUS      current
    DESCRIPTION
        "This is a list of the ToS reliability priority mapping entry."
    ::= { es2126pQoSRTypeTOSPriority 1 }

ES2126PQoSRTypeTOSPriorityEntry ::=
SEQUENCE {
    es2126pQoSRTypeTOSPriorityIndex    INTEGER,
    es2126pQoSRTypeTOSPriorityValue    INTEGER,
    es2126pQoSRTypeTOSPriorityQueue    INTEGER
}

es2126pQoSRTypeTOSPriorityEntry OBJECT-TYPE
    SYNTAX      ES2126PQoSRTypeTOSPriorityEntry
    MAX-ACCESS      not-accessible
    STATUS      current
    DESCRIPTION
        "Entry(s) for the TOS reliability mapping entry."
    INDEX {es2126pQoSRTypeTOSPriorityIndex}
    ::= { es2126pQoSRTypeTOSPriorityTable 1 }

es2126pQoSRTypeTOSPriorityIndex OBJECT-TYPE
    SYNTAX      INTEGER(1..8)
    MAX-ACCESS      not-accessible
    STATUS      current
    DESCRIPTION
        "The index of the TOS reliability priority mapping table."
    ::= { es2126pQoSRTypeTOSPriorityEntry 1 }

es2126pQoSRTypeTOSPriorityValue OBJECT-TYPE
    SYNTAX      INTEGER(0..7)
    MAX-ACCESS      read-only
    STATUS      current
    DESCRIPTION
        "The value of TOS reliability priority mapping entry."
    ::= { es2126pQoSRTypeTOSPriorityEntry 2 }

es2126pQoSRTypeTOSPriorityQueue OBJECT-TYPE
    SYNTAX      INTEGER(0..3)
    MAX-ACCESS      read-write
    STATUS      current
    DESCRIPTION
        "The queue of TOS reliability priority mapping entry."
    ::= { es2126pQoSRTypeTOSPriorityEntry 3 }

es2126pQoSMTypeTOSPriority              OBJECT IDENTIFIER ::= { es2126pQoS 7 }

es2126pQoSMTypeTOSPriorityTable OBJECT-TYPE
    SYNTAX      SEQUENCE OF ES2126PQoSMTypeTOSPriorityEntry
    MAX-ACCESS  not-accessible
    STATUS      current
    DESCRIPTION
        "This is a list of the ToS monetary cost priority mapping entry."
    ::= { es2126pQoSMTypeTOSPriority 1 }

ES2126PQoSMTypeTOSPriorityEntry ::=
SEQUENCE {
    es2126pQoSMTypeTOSPriorityIndex    INTEGER,
    es2126pQoSMTypeTOSPriorityValue    INTEGER,
    es2126pQoSMTypeTOSPriorityQueue    INTEGER
}

es2126pQoSMTypeTOSPriorityEntry OBJECT-TYPE
    SYNTAX      ES2126PQoSMTypeTOSPriorityEntry
    MAX-ACCESS      not-accessible
    STATUS      current
    DESCRIPTION
        "Entry(s) for the TOS monetary cost mapping entry."
    INDEX {es2126pQoSMTypeTOSPriorityIndex}
    ::= { es2126pQoSMTypeTOSPriorityTable 1 }

es2126pQoSMTypeTOSPriorityIndex OBJECT-TYPE
    SYNTAX      INTEGER(1..8)
    MAX-ACCESS      not-accessible
    STATUS      current
    DESCRIPTION
        "The index of the TOS monetary cost priority mapping table."
    ::= { es2126pQoSMTypeTOSPriorityEntry 1 }

es2126pQoSMTypeTOSPriorityValue OBJECT-TYPE
    SYNTAX      INTEGER(0..7)
    MAX-ACCESS      read-only
    STATUS      current
    DESCRIPTION
        "The value of TOS monetary cost priority mapping entry."
    ::= { es2126pQoSMTypeTOSPriorityEntry 2 }

es2126pQoSMTypeTOSPriorityQueue OBJECT-TYPE
    SYNTAX      INTEGER(0..3)
    MAX-ACCESS      read-write
    STATUS      current
    DESCRIPTION
        "The queue of TOS monetary cost priority mapping entry."
    ::= { es2126pQoSMTypeTOSPriorityEntry 3 }

es2126pQoSDSCPPriority              OBJECT IDENTIFIER ::= { es2126pQoS 8 }

es2126pQoSDSCPPriorityTable OBJECT-TYPE
    SYNTAX      SEQUENCE OF ES2126PQoSDSCPPriorityEntry
    MAX-ACCESS  not-accessible
    STATUS      current
    DESCRIPTION
        "This is a list of the DSCP priority entry."
    ::= { es2126pQoSDSCPPriority 1 }

ES2126PQoSDSCPPriorityEntry ::=
SEQUENCE {
    es2126pQoSDSCPPriorityIndex    INTEGER,
    es2126pQoSDSCPPriorityValue    INTEGER,
    es2126pQoSDSCPPriorityQueue    INTEGER
}

es2126pQoSDSCPPriorityEntry OBJECT-TYPE
    SYNTAX      ES2126PQoSDSCPPriorityEntry
    MAX-ACCESS      not-accessible
    STATUS      current
    DESCRIPTION
        "Entry(s) for the DSCP priority mapping entry."
    INDEX {es2126pQoSDSCPPriorityIndex}
    ::= { es2126pQoSDSCPPriorityTable 1 }

es2126pQoSDSCPPriorityIndex OBJECT-TYPE
    SYNTAX      INTEGER(1..64)
    MAX-ACCESS      not-accessible
    STATUS      current
    DESCRIPTION
        "The index of the DSCP priority priority mapping table."
    ::= { es2126pQoSDSCPPriorityEntry 1 }

es2126pQoSDSCPPriorityValue OBJECT-TYPE
    SYNTAX      INTEGER(0..63)
    MAX-ACCESS      read-only
    STATUS      current
    DESCRIPTION
        "The value of DSCP priority priority mapping entry."
    ::= { es2126pQoSDSCPPriorityEntry 2 }

es2126pQoSDSCPPriorityQueue OBJECT-TYPE
    SYNTAX      INTEGER(0..3)
    MAX-ACCESS      read-write
    STATUS      current
    DESCRIPTION
        "The queue of DSCP priority priority mapping entry."
    ::= { es2126pQoSDSCPPriorityEntry 3 }

es2126pVlan      OBJECT IDENTIFIER ::= { es2126pProduces 17 }

es2126pVlanModeConfig      OBJECT IDENTIFIER ::= { es2126pVlan 1 }

es2126pVlanMode  OBJECT-TYPE
    SYNTAX      INTEGER(0..2)
    MAX-ACCESS  read-write
    STATUS      current
    DESCRIPTION
        "0:Tag-based, 1:Port-based, 2:Metro mode"
    ::= { es2126pVlanModeConfig 1 }

es2126pSymmetricVlan  OBJECT-TYPE
    SYNTAX      INTEGER(0|1)
    MAX-ACCESS  read-write
    STATUS      current
    DESCRIPTION
        "Symmetric VLAN: for tag-based
        0:disable, 1:enable"
    ::= { es2126pVlanModeConfig 2 }

es2126pVlanSVL  OBJECT-TYPE
    SYNTAX      INTEGER(0|1)
    MAX-ACCESS  read-write
    STATUS      current
    DESCRIPTION
        "SVL: : for tag-based
        0:disable, 1:enable"
    ::= { es2126pVlanModeConfig 3 }

es2126pDoubleTag  OBJECT-TYPE
    SYNTAX      INTEGER(0|1)
    MAX-ACCESS  read-write
    STATUS      current
    DESCRIPTION
        "Double Tag: for tag-based
        0:disable, 1:enable"
    ::= { es2126pVlanModeConfig 4 }

es2126pUpLinkPort  OBJECT-TYPE
    SYNTAX      INTEGER(0..2)
    MAX-ACCESS  read-write
    STATUS      current
    DESCRIPTION
        "Up link Port: for Metro mode
        0:Port 25, 1:Port 26, 2:Port 25 & 26"
    ::= { es2126pVlanModeConfig 5 }

es2126pTagBasedVlanGroup      OBJECT IDENTIFIER ::= { es2126pVlan 2 }

es2126pTagBasedVlanNumbers  OBJECT-TYPE
    SYNTAX      INTEGER(1..4094)
    MAX-ACCESS  read-only
    STATUS      current
    DESCRIPTION
        "Total numbers for tag-based vlan."
    ::= { es2126pTagBasedVlanGroup 1 }

es2126pTagBasedCreateStatus  OBJECT-TYPE
    SYNTAX      INTEGER(0..4094)
    MAX-ACCESS  read-write
    STATUS      current
    DESCRIPTION
        "Creat a temp vlan in tag-based vlan table.
         0 : none,
         1~4094 : creat with this vid.
        "
    ::= { es2126pTagBasedVlanGroup 2 }

es2126pTagBasedVlanTable  OBJECT-TYPE
    SYNTAX      SEQUENCE OF ES2126PTagBasedVlanEntry
    MAX-ACCESS  not-accessible
    STATUS      current
    DESCRIPTION
        " "
    ::= { es2126pTagBasedVlanGroup 3 }

ES2126PTagBasedVlanEntry ::=
SEQUENCE {
    es2126pTagBasedVlanVid              INTEGER,
    es2126pTagBasedVlanName                 DisplayString,
    es2126pTagBasedVlanMember               DisplayString,
    es2126pTagBasedVlanUntag                DisplayString,
    es2126pTagBasedVlanRowStatus                INTEGER
}

es2126pTagBasedVlanEntry OBJECT-TYPE
    SYNTAX      ES2126PTagBasedVlanEntry
    MAX-ACCESS  not-accessible
    STATUS      current
    DESCRIPTION
        "Entry(s) for tag-based vlan table."
    INDEX {es2126pTagBasedVlanVid}
    ::= { es2126pTagBasedVlanTable 1 }

es2126pTagBasedVlanVid  OBJECT-TYPE
    SYNTAX      INTEGER(1..4094)
    MAX-ACCESS  not-accessible
    STATUS      current
    DESCRIPTION
        "The vid of vlan."
    ::= { es2126pTagBasedVlanEntry 1 }

es2126pTagBasedVlanName  OBJECT-TYPE
    SYNTAX      DisplayString
    MAX-ACCESS  read-write
    STATUS      current
    DESCRIPTION
        "The name of vlan."
    ::= { es2126pTagBasedVlanEntry 2 }

es2126pTagBasedVlanMember  OBJECT-TYPE
    SYNTAX      DisplayString
    MAX-ACCESS  read-write
    STATUS      current
    DESCRIPTION
        "The member of vlan."
    ::= { es2126pTagBasedVlanEntry 3 }

es2126pTagBasedVlanUntag  OBJECT-TYPE
    SYNTAX      DisplayString
    MAX-ACCESS  read-write
    STATUS      current
    DESCRIPTION
        "The untag port of vlan."
    ::= { es2126pTagBasedVlanEntry 4 }

es2126pTagBasedVlanRowStatus  OBJECT-TYPE
    SYNTAX      INTEGER(1..3)
    MAX-ACCESS  read-write
    STATUS      current
    DESCRIPTION
        "The row status of vlan.
         1 : active,
         2 : not-inService,
         3 : delete
        "
    ::= { es2126pTagBasedVlanEntry 5 }

es2126pVlanPvid      OBJECT IDENTIFIER ::= { es2126pVlan 3 }

es2126pVlanPvidTable  OBJECT-TYPE
    SYNTAX      SEQUENCE OF ES2126PVlanPvidEntry
    MAX-ACCESS  not-accessible
    STATUS      current
    DESCRIPTION
        " "
    ::= { es2126pVlanPvid 1 }

ES2126PVlanPvidEntry ::=
SEQUENCE {
    es2126pVlanPvidPort             INTEGER,
    es2126pVlanPvidValue            INTEGER,
    es2126pVlanPvidDefaultPriority              INTEGER,
    es2126pVlanPvidDropUntag            INTEGER
}

es2126pVlanPvidEntry OBJECT-TYPE
    SYNTAX      ES2126PVlanPvidEntry
    MAX-ACCESS  not-accessible
    STATUS      current
    DESCRIPTION
        "Entry(s) for Vlan Pvid."
    INDEX {es2126pVlanPvidPort}
    ::= { es2126pVlanPvidTable 1 }

es2126pVlanPvidPort  OBJECT-TYPE
    SYNTAX      INTEGER(1..26)
    MAX-ACCESS  not-accessible
    STATUS      current
    DESCRIPTION
        "The port number of pvid entry."
    ::= { es2126pVlanPvidEntry 1 }

es2126pVlanPvidValue  OBJECT-TYPE
    SYNTAX      INTEGER(1..4094)
    MAX-ACCESS  read-write
    STATUS      current
    DESCRIPTION
        "The pvid value of port."
    ::= { es2126pVlanPvidEntry 2 }

es2126pVlanPvidDefaultPriority  OBJECT-TYPE
    SYNTAX      INTEGER(0..7)
    MAX-ACCESS  read-write
    STATUS      current
    DESCRIPTION
        "The default priority of port ."
    ::= { es2126pVlanPvidEntry 3 }

es2126pVlanPvidDropUntag  OBJECT-TYPE
    SYNTAX      INTEGER(0..7)
    MAX-ACCESS  read-write
    STATUS      current
    DESCRIPTION
        "The drop untag of port ."
    ::= { es2126pVlanPvidEntry 4 }

es2126pPortBasedVlanGroup      OBJECT IDENTIFIER ::= { es2126pVlan 4 }

es2126pPortBasedVlanNumbers  OBJECT-TYPE
    SYNTAX      INTEGER(1..26)
    MAX-ACCESS  read-only
    STATUS      current
    DESCRIPTION
        "Total numbers for tag-based vlan."
    ::= { es2126pPortBasedVlanGroup 1 }

es2126pPortBasedCreateStatus  OBJECT-TYPE
    SYNTAX      INTEGER(0|1)
    MAX-ACCESS  read-write
    STATUS      current
    DESCRIPTION
        "Creat a temp vlan in port-based vlan table.
         0 : none,
         1 : creat a new port-based vlan.
        "
    ::= { es2126pPortBasedVlanGroup 2 }

es2126pPortBasedVlanTable  OBJECT-TYPE
    SYNTAX      SEQUENCE OF ES2126PPortBasedVlanEntry
    MAX-ACCESS  not-accessible
    STATUS      current
    DESCRIPTION
        " "
    ::= { es2126pPortBasedVlanGroup 3 }

ES2126PPortBasedVlanEntry ::=
SEQUENCE {
    es2126pPortBasedVlanIndex               INTEGER,
    es2126pPortBasedVlanName                DisplayString,
    es2126pPortBasedVlanMember                  DisplayString,
    es2126pPortBasedVlanRowStatus           INTEGER
}

es2126pPortBasedVlanEntry OBJECT-TYPE
    SYNTAX      ES2126PPortBasedVlanEntry
    MAX-ACCESS  not-accessible
    STATUS      current
    DESCRIPTION
        "Entry(s) for port-based vlan table."
    INDEX {es2126pPortBasedVlanIndex}
    ::= { es2126pPortBasedVlanTable 1 }

es2126pPortBasedVlanIndex  OBJECT-TYPE
    SYNTAX      INTEGER(1..26)
    MAX-ACCESS  not-accessible
    STATUS      current
    DESCRIPTION
        "The index of vlan."
    ::= { es2126pPortBasedVlanEntry 1 }

es2126pPortBasedVlanName  OBJECT-TYPE
    SYNTAX      DisplayString
    MAX-ACCESS  read-write
    STATUS      current
    DESCRIPTION
        "The name of vlan."
    ::= { es2126pPortBasedVlanEntry 2 }

es2126pPortBasedVlanMember  OBJECT-TYPE
    SYNTAX      DisplayString
    MAX-ACCESS  read-write
    STATUS      current
    DESCRIPTION
        "The member of vlan."
    ::= { es2126pPortBasedVlanEntry 3 }

es2126pPortBasedVlanRowStatus  OBJECT-TYPE
    SYNTAX      INTEGER(1..3)
    MAX-ACCESS  read-write
    STATUS      current
    DESCRIPTION
        "The row status of vlan.
         1 : active,
         2 : not-inService,
         3 : delete
        "
    ::= { es2126pPortBasedVlanEntry 4 }

es2126pManagementVlan      OBJECT IDENTIFIER ::= { es2126pVlan 5 }

es2126pManagementVlanState  OBJECT-TYPE
    SYNTAX      INTEGER(0|1)
    MAX-ACCESS  read-write
    STATUS      current
    DESCRIPTION
        "The stat of management vlan. (for tag-base)
         0 : Disable,
         1 : Enable.
        "
    ::= { es2126pManagementVlan 1 }

es2126pManagementVlanVid  OBJECT-TYPE
    SYNTAX      INTEGER(1..4094)
    MAX-ACCESS  read-write
    STATUS      current
    DESCRIPTION
        "The vid value of management vlan."
    ::= { es2126pManagementVlan 2 }

es2126pDot1X        OBJECT IDENTIFIER ::= { es2126pProduces 18 }

es2126pDot1XStateSetting      OBJECT IDENTIFIER ::= { es2126pDot1X 1 }

es2126pRadiusServer OBJECT-TYPE
    SYNTAX         IpAddress
    MAX-ACCESS     read-write
    STATUS         current
    DESCRIPTION
        "Set radius server ip"
    ::= { es2126pDot1XStateSetting 1 }

es2126pDot1XPort OBJECT-TYPE
    SYNTAX         INTEGER(1..65535)
    MAX-ACCESS     read-write
    STATUS         current
    DESCRIPTION
        "Set 802.1X port number"
    ::= { es2126pDot1XStateSetting 2 }

es2126pSecretKey  OBJECT-TYPE
    SYNTAX         DisplayString
    MAX-ACCESS     read-write
    STATUS         current
    DESCRIPTION
        "Set 802.1X secret key"
    ::= { es2126pDot1XStateSetting 3 }

es2126pAccountingService  OBJECT-TYPE
    SYNTAX         INTEGER(0|1)
    MAX-ACCESS     read-write
    STATUS         current
    DESCRIPTION
        "Set 802.1X accounting service
         0 : disable
         1 : enable
        "
    ::= { es2126pDot1XStateSetting 4 }

es2126pAccountingServer  OBJECT-TYPE
    SYNTAX         IpAddress
    MAX-ACCESS     read-write
    STATUS         current
    DESCRIPTION
        "Set 802.1X accounting server"
    ::= { es2126pDot1XStateSetting 5 }

es2126pAccountingPort  OBJECT-TYPE
    SYNTAX         INTEGER(1..65535)
    MAX-ACCESS     read-write
    STATUS         current
    DESCRIPTION
        "Set 802.1X accounting port number"
    ::= { es2126pDot1XStateSetting 6 }

es2126pDot1XPortSecurityManagement      OBJECT IDENTIFIER ::= { es2126pDot1X 2 }

es2126pDot1XPortSecurityTable  OBJECT-TYPE
    SYNTAX      SEQUENCE OF ES2126PDot1XPortSecurityEntry
    MAX-ACCESS  not-accessible
    STATUS      current
    DESCRIPTION
        "This is a list of the 802.1x port security entry."
    ::= { es2126pDot1XPortSecurityManagement 1 }

ES2126PDot1XPortSecurityEntry ::=
SEQUENCE {
    es2126pDot1XPortSecurityPortIndex               INTEGER,
    es2126pDot1XPortSecurityMode                    INTEGER,
    es2126pDot1XPortSecurityPortControl             INTEGER,
    es2126pDot1XPortSecurityReAuthMax               INTEGER,
    es2126pDot1XPortSecurityTxPeriod                    INTEGER,
    es2126pDot1XPortSecurityQuietPeriod             INTEGER,
    es2126pDot1XPortSecurityReAuthEnabled           INTEGER,
    es2126pDot1XPortSecurityReAuthPeriod            INTEGER,
    es2126pDot1XPortSecurityMaxRequest              INTEGER,
    es2126pDot1XPortSecuritySuppTimeout             INTEGER,
    es2126pDot1XPortSecurityServerTimeout           INTEGER,
    es2126pDot1XPortSecurityStatus                  DisplayString
}

es2126pDot1XPortSecurityEntry OBJECT-TYPE
    SYNTAX      ES2126PDot1XPortSecurityEntry
    MAX-ACCESS  not-accessible
    STATUS      current
    DESCRIPTION
        "Entry(s) for 802.1x port security management table."
    INDEX {es2126pDot1XPortSecurityPortIndex}
    ::= { es2126pDot1XPortSecurityTable 1 }

es2126pDot1XPortSecurityPortIndex  OBJECT-TYPE
    SYNTAX      INTEGER(1..26)
    MAX-ACCESS  not-accessible
    STATUS      current
    DESCRIPTION
        "The port index of 802.1x port security."
    ::= { es2126pDot1XPortSecurityEntry 1 }

es2126pDot1XPortSecurityMode  OBJECT-TYPE
    SYNTAX      INTEGER(0..2)
    MAX-ACCESS  read-write
    STATUS      current
    DESCRIPTION
        "The mode of 802.1x port security.
         0 : Disable,
         1 : Normal,
         2 : Advanced 802.1X
        "
    ::= { es2126pDot1XPortSecurityEntry 2 }

es2126pDot1XPortSecurityPortControl  OBJECT-TYPE
    SYNTAX      INTEGER(0..2)
    MAX-ACCESS  read-write
    STATUS      current
    DESCRIPTION
        "The port control of 802.1x port security.
           0 : ForceUnauthorized,
           1 : ForceAuthorized,
           2 : Auto
        "
    ::= { es2126pDot1XPortSecurityEntry 3 }

es2126pDot1XPortSecurityReAuthMax  OBJECT-TYPE
    SYNTAX      INTEGER(1..10)
    MAX-ACCESS  read-write
    STATUS      current
    DESCRIPTION
        "The reAuthMax(1~10) of 802.1x port security."
    ::= { es2126pDot1XPortSecurityEntry 4 }

es2126pDot1XPortSecurityTxPeriod  OBJECT-TYPE
    SYNTAX      INTEGER(1..65535)
    MAX-ACCESS  read-write
    STATUS      current
    DESCRIPTION
        "The txPeriod(1~65535) of 802.1x port security."
    ::= { es2126pDot1XPortSecurityEntry 5 }

es2126pDot1XPortSecurityQuietPeriod  OBJECT-TYPE
    SYNTAX      INTEGER(0..65535)
    MAX-ACCESS  read-write
    STATUS      current
    DESCRIPTION
        "The quiet period(0~65535) of 802.1x port security."
    ::= { es2126pDot1XPortSecurityEntry 6 }

es2126pDot1XPortSecurityReAuthEnabled  OBJECT-TYPE
    SYNTAX      INTEGER(0|1)
    MAX-ACCESS  read-write
    STATUS      current
    DESCRIPTION
        "The reAuthEnabled of 802.1x port security.
         0 : off,
         1 : on.
        "
    ::= { es2126pDot1XPortSecurityEntry 7 }

es2126pDot1XPortSecurityReAuthPeriod  OBJECT-TYPE
    SYNTAX      INTEGER(1..65535)
    MAX-ACCESS  read-write
    STATUS      current
    DESCRIPTION
        "The reAuthPeriod(1~65535) of 802.1x port security."
    ::= { es2126pDot1XPortSecurityEntry 8 }

es2126pDot1XPortSecurityMaxRequest  OBJECT-TYPE
    SYNTAX      INTEGER(1..10)
    MAX-ACCESS  read-write
    STATUS      current
    DESCRIPTION
        "The max.request(1~10) of 802.1x port security."
    ::= { es2126pDot1XPortSecurityEntry 9 }

es2126pDot1XPortSecuritySuppTimeout  OBJECT-TYPE
    SYNTAX      INTEGER(1..65535)
    MAX-ACCESS  read-write
    STATUS      current
    DESCRIPTION
        "The suppTimeout(1~65535) of 802.1x port security."
    ::= { es2126pDot1XPortSecurityEntry 10 }

es2126pDot1XPortSecurityServerTimeout  OBJECT-TYPE
    SYNTAX      INTEGER(1..65535)
    MAX-ACCESS  read-write
    STATUS      current
    DESCRIPTION
        "The server timeout(1~65535) of 802.1x port security."
    ::= { es2126pDot1XPortSecurityEntry 11 }

es2126pDot1XPortSecurityStatus  OBJECT-TYPE
    SYNTAX      DisplayString
    MAX-ACCESS  read-only
    STATUS      current
    DESCRIPTION
        "The status of 802.1x port security."
    ::= { es2126pDot1XPortSecurityEntry 12 }


es2126pTrunkInfo       OBJECT IDENTIFIER ::= { es2126pProduces 19 }

es2126pTrunkPort      OBJECT IDENTIFIER ::= { es2126pTrunkInfo 1 }

es2126pTrunkPortTable  OBJECT-TYPE
    SYNTAX      SEQUENCE OF ES2126PTrunkPortEntry
    MAX-ACCESS  not-accessible
    STATUS      current
    DESCRIPTION
        " "
    ::= { es2126pTrunkPort 1 }

ES2126PTrunkPortEntry ::=
SEQUENCE {
    es2126pTrunkPortIndex               INTEGER,
    es2126pTrunkPortMethod                  INTEGER,
    es2126pTrunkPortGroup               INTEGER,
    es2126pTrunkPortActiveLacp              INTEGER,
    es2126pTrunkPortAggtr               INTEGER,
    es2126pTrunkPortStatus              INTEGER,
    es2126pTrunkPortCurrentMode             INTEGER
}

es2126pTrunkPortEntry OBJECT-TYPE
    SYNTAX      ES2126PTrunkPortEntry
    MAX-ACCESS  not-accessible
    STATUS      current
    DESCRIPTION
        "Entry(s) for trunk table."
    INDEX {es2126pTrunkPortIndex}
    ::= { es2126pTrunkPortTable 1 }

es2126pTrunkPortIndex  OBJECT-TYPE
    SYNTAX      INTEGER(1..26)
    MAX-ACCESS  not-accessible
    STATUS      current
    DESCRIPTION
        "The port index of trunk table."
    ::= { es2126pTrunkPortEntry 1 }

es2126pTrunkPortMethod  OBJECT-TYPE
    SYNTAX      INTEGER(0..2)
    MAX-ACCESS  read-write
    STATUS      current
    DESCRIPTION
        "The method of trunk port.
     0 : None,
     1 : LACP,
     2 : Static.
        "
    ::= { es2126pTrunkPortEntry 2 }

es2126pTrunkPortGroup  OBJECT-TYPE
    SYNTAX      INTEGER(0..3)
    MAX-ACCESS  read-write
    STATUS      current
    DESCRIPTION
        "The group(0~3) of trunk port.  Each group just can have one method.
         Rule1: Maximum 3 groups are allowed.
         Rule2: The members of each group cannot exceed more than 4 ports.
         Rule3: Group 1 and 2 cannot exist member 25 and 26 port.
         Rule4: Group 3 cannot exist member from 1 to 24 port.   "
    ::= { es2126pTrunkPortEntry 3 }

es2126pTrunkPortActiveLacp  OBJECT-TYPE
    SYNTAX      INTEGER(0|1)
    MAX-ACCESS  read-write
    STATUS      current
    DESCRIPTION
        "The active lacp mode of trunk port.
     0 : Passive,
     1 : Active.
        "
    ::= { es2126pTrunkPortEntry 4 }

es2126pTrunkPortAggtr  OBJECT-TYPE
    SYNTAX      INTEGER(1..26)
    MAX-ACCESS  read-only
    STATUS      current
    DESCRIPTION
        "The Aggtr of trunk port."
    ::= { es2126pTrunkPortEntry 5 }

es2126pTrunkPortStatus  OBJECT-TYPE
    SYNTAX      INTEGER(0|1)
    MAX-ACCESS  read-only
    STATUS      current
    DESCRIPTION
        "The status of trunk port.
         0 : None,
         1 : Ready.
        "
    ::= { es2126pTrunkPortEntry 6 }

es2126pTrunkPortCurrentMode  OBJECT-TYPE
    SYNTAX      INTEGER(0..2)
    MAX-ACCESS  read-write
    STATUS      current
    DESCRIPTION
        "The current mode of trunk port entry.
     0 : Active mode,
     1 : Edit mode,
     2 : Do edit.
        "
    ::= { es2126pTrunkPortEntry 7 }

es2126pAggregatorView      OBJECT IDENTIFIER ::= { es2126pTrunkInfo 2 }

es2126pAggregatorViewTable  OBJECT-TYPE
    SYNTAX      SEQUENCE OF ES2126PAggregatorViewEntry
    MAX-ACCESS  not-accessible
    STATUS      current
    DESCRIPTION
        " "
    ::= { es2126pAggregatorView 1 }

ES2126PAggregatorViewEntry ::=
SEQUENCE {
    es2126pAggregatorViewIndex              INTEGER,
    es2126pAggregatorViewMethod                 INTEGER,
    es2126pAggregatorViewMemberPorts            DisplayString,
    es2126pAggregatorViewReadyPorts         DisplayString
}

es2126pAggregatorViewEntry OBJECT-TYPE
    SYNTAX      ES2126PAggregatorViewEntry
    MAX-ACCESS  not-accessible
    STATUS      current
    DESCRIPTION
        "Entry(s) for aggregator view table."
    INDEX {es2126pAggregatorViewIndex}
    ::= { es2126pAggregatorViewTable 1 }

es2126pAggregatorViewIndex  OBJECT-TYPE
    SYNTAX      INTEGER(1..26)
    MAX-ACCESS  not-accessible
    STATUS      current
    DESCRIPTION
        "The port index of aggregator view table."
    ::= { es2126pAggregatorViewEntry 1 }

es2126pAggregatorViewMethod  OBJECT-TYPE
    SYNTAX      INTEGER(0..2)
    MAX-ACCESS  read-only
    STATUS      current
    DESCRIPTION
        "The method of aggregator view table.
         0 : None,
     1 : LACP,
     2 : Static.
        "
    ::= { es2126pAggregatorViewEntry 2 }

es2126pAggregatorViewMemberPorts  OBJECT-TYPE
    SYNTAX      DisplayString
    MAX-ACCESS  read-only
    STATUS      current
    DESCRIPTION
        "The member ports of aggregator view table."
    ::= { es2126pAggregatorViewEntry 3 }

es2126pAggregatorViewReadyPorts  OBJECT-TYPE
    SYNTAX      DisplayString
    MAX-ACCESS  read-only
    STATUS      current
    DESCRIPTION
        "The ready ports of aggregator view table."
    ::= { es2126pAggregatorViewEntry 4 }

es2126pLacpSystemConfiguration     OBJECT IDENTIFIER ::= { es2126pTrunkInfo 3 }

es2126pLacpSystemPriority  OBJECT-TYPE
    SYNTAX      INTEGER(1..65535)
    MAX-ACCESS  read-write
    STATUS      current
    DESCRIPTION
        "The priority of LACP system."
    ::= { es2126pLacpSystemConfiguration 1 }

es2126pLacpSystemHashMethod  OBJECT-TYPE
    SYNTAX      INTEGER(0..2)
    MAX-ACCESS  read-write
    STATUS      current
    DESCRIPTION
        "The hash method of LACP system.
         0 : DA and SA
         1 : SA
         2 : DA
        "
    ::= { es2126pLacpSystemConfiguration 2 }

es2126pTrapEntry           OBJECT IDENTIFIER ::= { es2126pProduces 20 }

es2126pModuleInserted NOTIFICATION-TYPE
    OBJECTS { ifIndex }
    STATUS    current
    DESCRIPTION
        "Send the trap when a module is inserted to the system. The OID value means
         the port number."
    ::= { es2126pTrapEntry 1 }

es2126pModuleRemoved NOTIFICATION-TYPE
    OBJECTS { ifIndex }
    STATUS    current
    DESCRIPTION
        "Send the trap when a module is removed from the system. The OID value means
         the port number."
    ::= { es2126pTrapEntry 2 }

es2126pDualMediaSwapped NOTIFICATION-TYPE
    OBJECTS { ifIndex }
    STATUS    current
DESCRIPTION
        "Send the trap when the dual media port changed. The OID value means the port number."
    ::= { es2126pTrapEntry 3 }

es2126pPoEFailure NOTIFICATION-TYPE
    STATUS    current
    DESCRIPTION
        "Send the trap while detecting the malfunction of PoE chips."
    ::= { es2126pTrapEntry 4 }

es2126pLoopDetected NOTIFICATION-TYPE
    OBJECTS { ifIndex }
    STATUS    current
    DESCRIPTION
        "Send the trap when loop condition has been detected. The OID value means the port number."
    ::= { es2126pTrapEntry 5 }

es2126pLoginProtected NOTIFICATION-TYPE
    OBJECTS { loginProtectInfo }
    STATUS    current
    DESCRIPTION
        "Send the trap when login protect has been detected."
    ::= { es2126pTrapEntry 6 }

es2126pStpStateDisabled NOTIFICATION-TYPE
    STATUS      current
    DESCRIPTION
       "Send the trap when the operational state of STP is from enabled to disabled. "
    ::= { es2126pTrapEntry 100 }

es2126pStpStateEnabled NOTIFICATION-TYPE
    STATUS      current
    DESCRIPTION
       "Send the trap when the operational state of STP is from disabled to enabled. "
    ::= { es2126pTrapEntry 101 }

es2126pStpTopologyChanged NOTIFICATION-TYPE
    OBJECTS { ifIndex }
    STATUS      current
    DESCRIPTION
       "Send the trap when RSTP determines a port should enter the FORWARDING state
        (a topology change occurs). The OID value is the ifIndex of the port that
        produces the topology change."
    ::= { es2126pTrapEntry 102 }

es2126pRmonRisingAlarm NOTIFICATION-TYPE
    STATUS      current
    DESCRIPTION
       "Send the trap when an RMON rising alarm happened. The OID value is the value
        of another OID variable sampled by the RMON Alarm Group that exceeds its
        own RisingThreshold "
    ::= { es2126pTrapEntry 110 }

es2126pRmonFallingAlarm NOTIFICATION-TYPE
    STATUS      current
    DESCRIPTION
           "Send the trap when an RMON falling alarm happened. The OID value is the value
        of another OID variable sampled by the RMON Alarm Group that is smaller than its
        own FallingThreshold "
    ::= { es2126pTrapEntry 111 }

es2126pLacpStateDisabled NOTIFICATION-TYPE
    OBJECTS {ifIndex, groupId}
    STATUS      current
    DESCRIPTION
       "Send the trap when the operational state of LACP is from enabled to disabled.
        The OID value means the disabled Group ID."
    ::= { es2126pTrapEntry 120 }

es2126pLacpStateEnabled NOTIFICATION-TYPE
    OBJECTS {ifIndex, groupId}
    STATUS      current
    DESCRIPTION
       "Send the trap when the operational state of LACP is from disabled to enabled.
        The OID value means the disabled Group ID."
    ::= { es2126pTrapEntry 121 }

es2126pLacpPortAdded NOTIFICATION-TYPE
    OBJECTS   { ifIndex, actorkey, partnerkey }
    STATUS      current
    DESCRIPTION
       "Send the trap when the state of port is in 'trunk ready'."
    ::= { es2126pTrapEntry 123 }

es2126pLacpPortTrunkFailure NOTIFICATION-TYPE
    OBJECTS   { ifIndex, actorkey, partnerkey}
    STATUS      current
    DESCRIPTION
       "Send the trap when one port is not able to be aggregated
        due to duplex-mode of the port. "
    ::= { es2126pTrapEntry 124 }

es2126pGvrpStateDisabled NOTIFICATION-TYPE
    STATUS      current
    DESCRIPTION
       "Send the trap when the operational state of GVRP is from enabled to disabled. "
    ::= { es2126pTrapEntry 140 }

es2126pGvrpStateEnabled NOTIFICATION-TYPE
    STATUS      current
    DESCRIPTION
       "Send the trap when the operational state of LACP is from disabled to enabled. "
    ::= { es2126pTrapEntry 141 }

es2126pVlanPortBaseEnabled NOTIFICATION-TYPE
    STATUS      current
    DESCRIPTION
       "Send the trap when the operational state of vlan is changed to port-based vlan."
    ::= { es2126pTrapEntry 151 }

es2126pVlanTagBaseEnabled NOTIFICATION-TYPE
    STATUS      current
    DESCRIPTION
       "Send the trap when the operational state of vlan is changed to tag-based vlan."
    ::= { es2126pTrapEntry 152 }

es2126pVlanMetroBaseEnabled NOTIFICATION-TYPE
    STATUS      current
    DESCRIPTION
       "Send this trap when the operational state of vlan is changed to metro-based vlan."
    ::= { es2126pTrapEntry 153 }

es2126pUserLogin NOTIFICATION-TYPE
    OBJECTS   {username}
    STATUS      current
    DESCRIPTION
       "Send the trap when one user logins the system."
    ::= { es2126pTrapEntry 200 }

es2126pUserLogout NOTIFICATION-TYPE
    OBJECTS   {username}
    STATUS      current
    DESCRIPTION
       "Send the trap when one user logouts the system."
    ::= { es2126pTrapEntry 201 }

es2126pTrapVariable OBJECT IDENTIFIER ::= { es2126pProduces 21 }

username OBJECT-TYPE
    SYNTAX      DisplayString
    MAX-ACCESS  read-only
    STATUS      current
    DESCRIPTION
        "System account name."
    ::= { es2126pTrapVariable 1 }

groupId OBJECT-TYPE
    SYNTAX      INTEGER(1..8)
    MAX-ACCESS  read-only
    STATUS      current
    DESCRIPTION
        "The Trunk group ID of LACP."
    ::= { es2126pTrapVariable 2 }

actorkey OBJECT-TYPE
    SYNTAX  INTEGER(1..2147483647)
    MAX-ACCESS  read-only
    STATUS      current
    DESCRIPTION
        "The actor key information for LACP."
    ::= { es2126pTrapVariable 3 }

partnerkey OBJECT-TYPE
    SYNTAX  INTEGER(1..2147483647)
    MAX-ACCESS  read-only
    STATUS      current
    DESCRIPTION
        "The partner key information for LACP."
    ::= { es2126pTrapVariable 4 }

uplink OBJECT-TYPE
    SYNTAX  DisplayString
    MAX-ACCESS  read-only
    STATUS      current
    DESCRIPTION
        "Uplink port(s) in the metro-mode vlan."
    ::= { es2126pTrapVariable 5 }

loginProtectInfo OBJECT-TYPE
    SYNTAX  DisplayString
    MAX-ACCESS  read-only
    STATUS      current
    DESCRIPTION
        "Loging protect information."
    ::= { es2126pTrapVariable 6 }

es2126pPoE              OBJECT IDENTIFIER ::= { es2126pProduces 22 }

es2126pPoEStatus            OBJECT IDENTIFIER ::= { es2126pPoE 1 }

es2126pPoEStatusVmain OBJECT-TYPE
    SYNTAX      DisplayString
    MAX-ACCESS  read-only
    STATUS      current
    DESCRIPTION
        "Current PoE Voltage status"
    ::= { es2126pPoEStatus 1 }

es2126pPoEStatusImain OBJECT-TYPE
    SYNTAX      DisplayString
    MAX-ACCESS  read-only
    STATUS      current
    DESCRIPTION
        "Current PoE Current status"
    ::= { es2126pPoEStatus 2 }

es2126pPoEStatusPconsume OBJECT-TYPE
    SYNTAX      DisplayString
    MAX-ACCESS  read-only
    STATUS      current
    DESCRIPTION
        "Current PoE consuming power status"
    ::= { es2126pPoEStatus 3 }

es2126pPoEStatusPowerLimit OBJECT-TYPE
    SYNTAX      DisplayString
    MAX-ACCESS  read-only
    STATUS      current
    DESCRIPTION
        "Current PoE power limit status"
    ::= { es2126pPoEStatus 4 }

es2126pPoEStatusTemperature OBJECT-TYPE
    SYNTAX      DisplayString
    MAX-ACCESS  read-only
    STATUS      current
    DESCRIPTION
        "Current PoE temperature status"
    ::= { es2126pPoEStatus 5 }


es2126pPoEStatusTable   OBJECT-TYPE
    SYNTAX      SEQUENCE OF ES2126PPoEStatusEntry
    MAX-ACCESS  not-accessible
    STATUS      current
    DESCRIPTION
        "A list of PoE Status entry. The number of entries are given by Ports."
    ::= { es2126pPoEStatus 6 }

es2126pPoEStatusEntry   OBJECT-TYPE
    SYNTAX      ES2126PPoEStatusEntry
    MAX-ACCESS      not-accessible
    STATUS      current
    DESCRIPTION
        "Entry(s) for PoE Status."
    INDEX {es2126pPoEStatusPortNum}
    ::= { es2126pPoEStatusTable 1 }

ES2126PPoEStatusEntry ::=
SEQUENCE {
    es2126pPoEStatusPortNum                 INTEGER,
    es2126pPoEStatusPortOn                  INTEGER,
    es2126pPoEStatusACPortOff               INTEGER,
    es2126pPoEStatusDCPortOff           INTEGER,
    es2126pPoEStatusOverloadPortOff         INTEGER,
    es2126pPoEStatusShortCircuitPortOff     INTEGER,
    es2126pPoEStatusOverTemperature         INTEGER,
    es2126pPoEStatusPowerManagePortOff      INTEGER
}

es2126pPoEStatusPortNum OBJECT-TYPE
    SYNTAX      INTEGER(1..24)
    MAX-ACCESS  not-accessible
    STATUS      current
    DESCRIPTION
        "The index(Port number) of the PoE status entry."
    ::= { es2126pPoEStatusEntry 1 }

es2126pPoEStatusPortOn  OBJECT-TYPE
    SYNTAX      INTEGER(0|1)
    MAX-ACCESS      read-only
    STATUS      current
    DESCRIPTION
        "PD on this port is on."
    ::= { es2126pPoEStatusEntry 2 }

es2126pPoEStatusACPortOff   OBJECT-TYPE
    SYNTAX      INTEGER(0|8)
    MAX-ACCESS      read-only
    STATUS      current
    DESCRIPTION
        "Possitive value means PSE has been supplied power and is no supplying now, while zero
         means PSE has never supplied power or is supplying now."
    ::= { es2126pPoEStatusEntry 3 }

es2126pPoEStatusDCPortOff   OBJECT-TYPE
    SYNTAX      INTEGER(0|1)
    MAX-ACCESS      read-only
    STATUS      current
    DESCRIPTION
        "PD on this port is DC off."
    ::= { es2126pPoEStatusEntry 4 }

es2126pPoEStatusOverloadPortOff OBJECT-TYPE
    SYNTAX      INTEGER(0|32)
    MAX-ACCESS      read-only
    STATUS      current
    DESCRIPTION
        "Possitive value means PSE status overloaded now. Zero means PSE is not overloaded."
    ::= { es2126pPoEStatusEntry 5 }

es2126pPoEStatusShortCircuitPortOff OBJECT-TYPE
    SYNTAX      INTEGER(0|1)
    MAX-ACCESS      read-only
    STATUS      current
    DESCRIPTION
        "PD on this port is short circuit off."
    ::= { es2126pPoEStatusEntry 6 }

es2126pPoEStatusOverTemperature OBJECT-TYPE
    SYNTAX      INTEGER(0|1)
    MAX-ACCESS      read-only
    STATUS      current
    DESCRIPTION
        "PD on this port is over temperature."
    ::= { es2126pPoEStatusEntry 7 }

es2126pPoEStatusPowerManagePortOff  OBJECT-TYPE
    SYNTAX      INTEGER(0|1)
    MAX-ACCESS      read-only
    STATUS      current
    DESCRIPTION
        "PD on this port is powered off by management."
    ::= { es2126pPoEStatusEntry 8 }

es2126pPoEConfTable OBJECT-TYPE
    SYNTAX      SEQUENCE OF ES2126PPoEConfEntry
    MAX-ACCESS  not-accessible
    STATUS      current
    DESCRIPTION
        "A list of PoE Configuration entry. The number of entries are given by Ports."
    ::= { es2126pPoE 2 }

es2126pPoEConfEntry OBJECT-TYPE
    SYNTAX      ES2126PPoEConfEntry
    MAX-ACCESS      not-accessible
    STATUS      current
    DESCRIPTION
        "Entry(s) for PoE Configuration."
    INDEX {es2126pPoEConfPortNum}
    ::= { es2126pPoEConfTable 1 }

ES2126PPoEConfEntry ::=
SEQUENCE {
    es2126pPoEConfPortNum                   INTEGER,
    es2126pPoEConfStatus                    INTEGER,
    es2126pPoEConfState                 INTEGER,
    es2126pPoEConfPriority                  INTEGER,
    es2126pPoEConfPower                 DisplayString,
    es2126pPoEConfCurrent                   INTEGER,
    es2126pPoEConfClass                 INTEGER
}

es2126pPoEConfPortNum   OBJECT-TYPE
    SYNTAX      INTEGER(1..24)
    MAX-ACCESS  not-accessible
    STATUS      current
    DESCRIPTION
        "The index(Port number) of the PoE Configuration entry."
    ::= { es2126pPoEConfEntry 1 }

es2126pPoEConfStatus    OBJECT-TYPE
    SYNTAX      INTEGER(0|1)
    MAX-ACCESS      read-only
    STATUS      current
    DESCRIPTION
        "0:Normal ; 1:Active"
    ::= { es2126pPoEConfEntry 2 }

es2126pPoEConfState OBJECT-TYPE
    SYNTAX      INTEGER(0|1)
    MAX-ACCESS      read-write
    STATUS      current
    DESCRIPTION
        "0:Disable ; 1:Enable"
    ::= { es2126pPoEConfEntry 3 }

es2126pPoEConfPriority  OBJECT-TYPE
    SYNTAX      INTEGER(0..2)
    MAX-ACCESS      read-write
    STATUS      current
    DESCRIPTION
        "0:Low ; 1:Normal ; 2:High"
    ::= { es2126pPoEConfEntry 4 }

es2126pPoEConfPower OBJECT-TYPE
    SYNTAX      DisplayString
    MAX-ACCESS      read-only
    STATUS      current
    DESCRIPTION
        "The power provides for the PD."
    ::= { es2126pPoEConfEntry 5 }

es2126pPoEConfCurrent   OBJECT-TYPE
    SYNTAX      INTEGER(0..2147483647)
    MAX-ACCESS      read-only
    STATUS      current
    DESCRIPTION
        "The current provides for the PD."
    ::= { es2126pPoEConfEntry 6 }

es2126pPoEConfClass OBJECT-TYPE
    SYNTAX      INTEGER(0..2147483647)
    MAX-ACCESS      read-only
    STATUS      current
    DESCRIPTION
        "The class of the PD."
    ::= { es2126pPoEConfEntry 7 }

es2126pLoginProtect           OBJECT IDENTIFIER ::= { es2126pProduces 23 }

es2126pLockMinutes OBJECT-TYPE
    SYNTAX      INTEGER(0..10)
    MAX-ACCESS      read-write
    STATUS      current
    DESCRIPTION
        "Set the login lock time. Available from 0 to 10 (minutes)
         Set 0 as disabled.
        "
    ::= { es2126pLoginProtect 1 }

es2126pLoginErrors OBJECT-TYPE
    SYNTAX      INTEGER(0..10)
    MAX-ACCESS      read-write
    STATUS      current
    DESCRIPTION
        "Set login error count. Available from 0 to 10 (times)
         Set 0 as disabled.
        "
    ::= { es2126pLoginProtect 2 }

es2126pIgmpSnooping        OBJECT IDENTIFIER ::= { es2126pProduces 24 }

es2126pIgmpSnoopingMode   OBJECT-TYPE
    SYNTAX      INTEGER(0|1|2)
    MAX-ACCESS  read-write
    STATUS      current
    DESCRIPTION
        "Set Igmp Snooping Mode.
         0 : disable,
         1 : active,
         2 : passive
        "
    ::= { es2126pIgmpSnooping 1 }

es2126pIgmpVlanGroupAllow      OBJECT IDENTIFIER ::= { es2126pIgmpSnooping 2 }

es2126pIgmpVlanGroupAllowState   OBJECT-TYPE
    SYNTAX      INTEGER(0|1)
    MAX-ACCESS  read-write
    STATUS      current
    DESCRIPTION
        "Set Igmp Vlan Group Allow State.
         0 : disable,
         1 : enable,
        "
    ::= { es2126pIgmpVlanGroupAllow 1 }

es2126pIgmpVlanGroupAllowNumber  OBJECT-TYPE
    SYNTAX      INTEGER(0..1024)
    MAX-ACCESS  read-only
    STATUS      current
    DESCRIPTION
        "This is number of Igmp Vlan Group Allow table entry"
    ::= { es2126pIgmpVlanGroupAllow 2 }

es2126pIgmpVlanGroupAllowEntryCreate  OBJECT-TYPE
    SYNTAX      INTEGER(0..1024)
    MAX-ACCESS  read-write
    STATUS      current
    DESCRIPTION
        "Creat a Igmp Vlan Group Allow entry.
         Set 1: add a new entry,
         Get: the number means index."
    ::= { es2126pIgmpVlanGroupAllow 3 }

es2126pIgmpVlanGroupAlloTable  OBJECT-TYPE
    SYNTAX      SEQUENCE OF ES2126PIgmpVlanGroupAllowEntry
    MAX-ACCESS  not-accessible
    STATUS      current
    DESCRIPTION
        "This is a list of Igmp Vlan Group Allow table."
    ::= { es2126pIgmpVlanGroupAllow 4 }

ES2126PIgmpVlanGroupAllowEntry ::=
SEQUENCE {
    es2126pIgmpVlanGroupAllowIndex        INTEGER,
    es2126pIgmpVlanGroupAllowIpRange     DisplayString,
    es2126pIgmpVlanGroupAllowVid           INTEGER,
    es2126pIgmpVlanGroupAllowPort        INTEGER,
    es2126pIgmpVlanGroupAllowEntryAction     INTEGER
}

ES2126PIgmpVlanGroupAllowEntry  OBJECT-TYPE
    SYNTAX      ES2126PIgmpVlanGroupAllowEntry
    MAX-ACCESS  not-accessible
    STATUS      current
    DESCRIPTION
        "Entry(s) for Igmp Vlan Group Allow Table."
    INDEX {es2126pIgmpVlanGroupAllowIndex}
    ::= { es2126pIgmpVlanGroupAlloTable 1 }

es2126pIgmpVlanGroupAllowIndex  OBJECT-TYPE
    SYNTAX      INTEGER(1..1024)
    MAX-ACCESS      not-accessible
    STATUS      current
    DESCRIPTION
        "The index of Igmp Vlan Group Allow Table."
    ::= { ES2126PIgmpVlanGroupAllowEntry 1 }

es2126pIgmpVlanGroupAllowIpRange  OBJECT-TYPE
    SYNTAX      DisplayString
    MAX-ACCESS  read-write
    STATUS      current
    DESCRIPTION
        "The start address of Igmp Vlan Group Allow table entry."
    ::= { ES2126PIgmpVlanGroupAllowEntry 2 }

es2126pIgmpVlanGroupAllowVid  OBJECT-TYPE
    SYNTAX      INTEGER(0..4094)
    MAX-ACCESS  read-write
    STATUS      current
    DESCRIPTION
        "The vlan id of Igmp Vlan Group Allow table entry. 0: any VID."
    ::= { ES2126PIgmpVlanGroupAllowEntry 3 }

es2126pIgmpVlanGroupAllowPort  OBJECT-TYPE
    SYNTAX      DisplayString
    MAX-ACCESS  read-write
    STATUS      current
    DESCRIPTION
        "The port of Igmp Vlan Group Allow table entry."
    ::= { ES2126PIgmpVlanGroupAllowEntry 4 }

es2126pIgmpVlanGroupAllowEntryAction  OBJECT-TYPE
    SYNTAX      INTEGER(1..3)
    MAX-ACCESS  read-write
    STATUS      current
    DESCRIPTION
        "The action of Igmp Vlan Group Allow table entry.
         1:action
         2:non-action
         3:delete"
    ::= { ES2126PIgmpVlanGroupAllowEntry 5 }

es2126pIgmpStaticIpMulticast      OBJECT IDENTIFIER ::= { es2126pIgmpSnooping 3 }

es2126pIgmpStaticIpMulticastNumber  OBJECT-TYPE
    SYNTAX      INTEGER(0..1024)
    MAX-ACCESS  read-only
    STATUS      current
    DESCRIPTION
        "This is number of Igmp Static IP Multicast table entry"
    ::= { es2126pIgmpStaticIpMulticast 1 }

es2126pIgmpStaticIpMulticastEntryCreate  OBJECT-TYPE
    SYNTAX      INTEGER(0..1024)
    MAX-ACCESS  read-write
    STATUS      current
    DESCRIPTION
        "Creat a Igmp Static IP Multicast entry.
         Set 1: add a new entry,
         Get: the number means index."
    ::= { es2126pIgmpStaticIpMulticast 2 }


es2126pIgmpStaticIpMulticastTable  OBJECT-TYPE
    SYNTAX      SEQUENCE OF ES2126PIgmpStaticIpMulticastEntry
    MAX-ACCESS  not-accessible
    STATUS      current
    DESCRIPTION
        "This is a list of Igmp Static IP Multicast table."
    ::= { es2126pIgmpStaticIpMulticast 3 }

ES2126PIgmpStaticIpMulticastEntry ::=
SEQUENCE {
    es2126pIgmpStaticIpMulticastIndex        INTEGER,
    es2126pIgmpStaticIpMulticastIp     DisplayString,
    es2126pIgmpStaticIpMulticastVid           INTEGER,
    es2126pIgmpStaticIpMulticastPort        INTEGER,
    es2126pIgmpStaticIpMulticastEntryAction     INTEGER
}

ES2126PIgmpStaticIpMulticastEntry  OBJECT-TYPE
    SYNTAX      ES2126PIgmpStaticIpMulticastEntry
    MAX-ACCESS  not-accessible
    STATUS      current
    DESCRIPTION
        "Entry(s) for Igmp Static IP Multicast Table."
    INDEX {es2126pIgmpStaticIpMulticastIndex}
    ::= { es2126pIgmpStaticIpMulticastTable 1 }

es2126pIgmpStaticIpMulticastIndex  OBJECT-TYPE
    SYNTAX      INTEGER(1..1024)
    MAX-ACCESS      not-accessible
    STATUS      current
    DESCRIPTION
        "The index of Igmp Static IP Multicast Table."
    ::= { ES2126PIgmpStaticIpMulticastEntry 1 }

es2126pIgmpStaticIpMulticastIp  OBJECT-TYPE
    SYNTAX      DisplayString
    MAX-ACCESS  read-write
    STATUS      current
    DESCRIPTION
        "The IP address of Igmp Static IP Multicast table entry."
    ::= { ES2126PIgmpStaticIpMulticastEntry 2 }

es2126pIgmpStaticIpMulticastVid  OBJECT-TYPE
    SYNTAX      INTEGER(1..4094)
    MAX-ACCESS  read-write
    STATUS      current
    DESCRIPTION
        "The vlan id of Igmp Static IP Multicast table entry."
    ::= { ES2126PIgmpStaticIpMulticastEntry 3 }

es2126pIgmpStaticIpMulticastPort  OBJECT-TYPE
    SYNTAX      DisplayString
    MAX-ACCESS  read-write
    STATUS      current
    DESCRIPTION
        "The port of Igmp Static IP Multicast table entry."
    ::= { ES2126PIgmpStaticIpMulticastEntry 4 }

es2126pIgmpStaticIpMulticastEntryAction  OBJECT-TYPE
    SYNTAX      INTEGER(1..3)
    MAX-ACCESS  read-write
    STATUS      current
    DESCRIPTION
        "The action of Igmp Static IP Multicast table entry.
         1:action
         2:non-action
         3:delete"
    ::= { ES2126PIgmpStaticIpMulticastEntry 5 }

es2126pRadiusIgmpSetting      OBJECT IDENTIFIER ::= { es2126pIgmpSnooping 4 }

es2126pRadiusIgmpServer1 OBJECT-TYPE
    SYNTAX      DisplayString
    MAX-ACCESS  read-write
    STATUS      current
    DESCRIPTION
        "Radius Igmp Server1"
    ::= { es2126pRadiusIgmpSetting 1 }

es2126pRadiusIgmpPortNumber1 OBJECT-TYPE
    SYNTAX      INTEGER(1..65535)
    MAX-ACCESS  read-write
    STATUS      current
    DESCRIPTION
        "Set Radius Igmp port number1.
         port number: from 1 to 65535"
    ::= { es2126pRadiusIgmpSetting 2 }

es2126pRadiusIgmpServer2 OBJECT-TYPE
    SYNTAX      DisplayString
    MAX-ACCESS  read-write
    STATUS      current
    DESCRIPTION
        "Radius Igmp Server2"
    ::= { es2126pRadiusIgmpSetting 3 }

es2126pRadiusIgmpPortNumber2 OBJECT-TYPE
    SYNTAX      INTEGER(1..65535)
    MAX-ACCESS  read-write
    STATUS      current
    DESCRIPTION
        "Set Radius Igmp port number2.
         port number: from 1 to 65535"
    ::= { es2126pRadiusIgmpSetting 4 }

es2126pRadiusIgmpResponseTimeout OBJECT-TYPE
    SYNTAX      INTEGER(2..60)
    MAX-ACCESS  read-write
    STATUS      current
    DESCRIPTION
        "Set radius-igmp timeout.
         time: 2 ~ 60 seconds"
    ::= { es2126pRadiusIgmpSetting 5 }

es2126pRadiusIgmpNumberOfRetry OBJECT-TYPE
    SYNTAX      INTEGER(0..10)
    MAX-ACCESS  read-write
    STATUS      current
    DESCRIPTION
        "Set radius-igmp number of retry.
         value: 0 ~ 10 times"
    ::= { es2126pRadiusIgmpSetting 6 }

es2126pRadiusIgmpSecretKey  OBJECT-TYPE
    SYNTAX         DisplayString
    MAX-ACCESS     read-write
    STATUS         current
    DESCRIPTION
        "Set Radius Igmp secret key.
        The length of secret-key is from 1 to 31"
    ::= { es2126pRadiusIgmpSetting 7 }

es2126pRadiusIgmpPortMember  OBJECT-TYPE
    SYNTAX      DisplayString
    MAX-ACCESS  read-write
    STATUS      current
    DESCRIPTION
        "The Port Member of  Radius Igmp."
    ::= { es2126pRadiusIgmpSetting 8 }

es2126pMulticastStatus      OBJECT IDENTIFIER ::= { es2126pIgmpSnooping 5 }

es2126pMulticastStatusTable  OBJECT-TYPE
    SYNTAX      SEQUENCE OF ES2126PMulticastStatusEntry
    MAX-ACCESS  not-accessible
    STATUS      current
    DESCRIPTION
        " "
    ::= { es2126pMulticastStatus 1 }

es2126pMulticastStatusEntry OBJECT-TYPE
    SYNTAX      ES2126PMulticastStatusEntry
    MAX-ACCESS  not-accessible
    STATUS      current
    DESCRIPTION
        "Entry(s) for Multicast Status table."
    INDEX {es2126pMulticastStatusIndex}
    ::= { es2126pMulticastStatusTable 1 }

ES2126PMulticastStatusEntry ::=
SEQUENCE {
    es2126pMulticastStatusIndex				INTEGER,
    es2126pMulticastStatusVid   				INTEGER,
    es2126pMulticastStatusMulticastGroup 				IpAddress,
    es2126pMulticastStatusPortMember				DisplayString
}

es2126pMulticastStatusIndex  OBJECT-TYPE
    SYNTAX      INTEGER(1..256)
    MAX-ACCESS  not-accessible
    STATUS      current
    DESCRIPTION
        "The index of multicast status table."
    ::= { es2126pMulticastStatusEntry 1 }

es2126pMulticastStatusVid OBJECT-TYPE
    SYNTAX         INTEGER(1..4094)
    MAX-ACCESS     read-only
    STATUS         current
    DESCRIPTION
        "The Vid of multicast status table."
    ::= { es2126pMulticastStatusEntry 2 }

es2126pMulticastStatusMulticastGroup OBJECT-TYPE
    SYNTAX      IpAddress
    MAX-ACCESS  read-only
    STATUS      current
    DESCRIPTION
        "The Multicast Group of multicast status table."
    ::= { es2126pMulticastStatusEntry 3 }

es2126pMulticastStatusPortMember  OBJECT-TYPE
    SYNTAX      DisplayString
    MAX-ACCESS  read-only
    STATUS      current
    DESCRIPTION
        "The Port Member of multicast status table."
    ::= { es2126pMulticastStatusEntry 4 }

END
