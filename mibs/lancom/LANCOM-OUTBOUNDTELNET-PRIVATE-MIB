-- OUTBOUND TELNET MIB overview:
-- OUTBOUND TELNET MIB falls under fastPath MIB node of the private subtree.



LANCOM-OUTBOUNDTELNET-PRIVATE-MIB DEFINITIONS ::= BEGIN

-- Broadcom FASTPATH OUTBOUND TELNET MIB
-- Copyright 2016-2020 Broadcom.
-- This SNMP Management Information Specification
-- embodies Broadcom's confidential and proprietary
-- intellectual property.  Broadcom retains all title
-- and ownership in the Specification including any revisions.

-- This Specification is supplied "AS IS", Broadcom
-- makes no warranty, either expressed or implied,
-- as to the use, operation, condition, or performance of the
-- Specification.



IMPORTS
    MODULE-IDENTITY, OBJECT-TYPE, Integer32               FROM SNMPv2-SMI
    fastPath                                              FROM LANCOM-REF-MIB;

    fastPathOutboundTelnetPrivate MODULE-IDENTITY
           LAST-UPDATED "201101260000Z" -- 26 January 2011 12:00:00 GMT
           ORGANIZATION "Broadcom "
           CONTACT-INFO
           "                      Customer Support
           Postal:                Broadcom
                                  1030 Swabia Court
                                  Suite 400
                                  Durham, NC 27703
           Tel:                   +1 919 865 2700"
      DESCRIPTION
          "The Broadcom Private MIB for FASTPATH Outbound Telnet"

      -- Revision history.
      REVISION
          "201101260000Z" -- 26 January 2011 12:00:00 GMT
      DESCRIPTION
          "Add new Postal address change."
      REVISION
          "200705230000Z" -- 23 May 2007 12:00:00 GMT
      DESCRIPTION
          "Broadcom branding related changes."

      ::= { fastPath 19 }


     --**************************************************************************************
    -- agentOutboundTelnetGroup -> contains MIB objects displaying various properties of a Outbound Telnet
    --
    --**************************************************************************************

    agentOutboundTelnetGroup       OBJECT IDENTIFIER ::= { fastPathOutboundTelnetPrivate 1 }

    agentOutboundTelnetAdminMode OBJECT-TYPE
      SYNTAX      INTEGER {
                  enable(1),
                  disable(2)
                  }
      MAX-ACCESS read-write
      STATUS     current
      DESCRIPTION
       " Admin-mode of the Outbound Telnet."
      DEFVAL { enable }
    ::= { agentOutboundTelnetGroup 1 }


    agentOutboundTelnetMaxNoOfSessions OBJECT-TYPE
      SYNTAX     INTEGER (0..5)
      MAX-ACCESS read-write
      STATUS     current
      DESCRIPTION
       " The maximum no. of Outbound Telnet sessions allowed."
      DEFVAL { 5 }
    ::= { agentOutboundTelnetGroup 2 }

    agentOutboundTelnetTimeout OBJECT-TYPE
      SYNTAX     INTEGER (1..160)
      MAX-ACCESS read-write
      STATUS     current
      DESCRIPTION
       " The login inactivity timeout value for Outbound Telnet."
      DEFVAL { 5 }
    ::= { agentOutboundTelnetGroup 3 }
END
