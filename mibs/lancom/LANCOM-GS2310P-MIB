LANCOM-GS2310P-MIB DEFINITIONS ::= BEGIN

IMPORTS
    DisplayString,MacAddress FROM SNMPv2-TC
    MODULE-COMPLIANCE,OBJECT-GROUP, NOTIFICATION-GROUP       FROM SNMPv2-CONF
    ifIndex    FROM RFC1213-MIB
    enterprises,MODULE-IDENTITY,OBJECT-TYPE,NOTIFICATION-TYPE,Counter32,Counter64,IpAddress        FROM SNMPv2-SMI
    InetAddress                   FROM INET-ADDRESS-MIB
    MacAddress FROM BRIDGE-MIB;

lancom-systems MODULE-IDENTITY
        LAST-UPDATED "202002190000Z"
        ORGANIZATION "LANCOM Systems GmbH."
        CONTACT-INFO
            "Adenauerstrasse 20 / B2, 52146 Wuerselen, Germany
            Email: info@lancom.de
            TEL: +49 (0)2405 49936 0
            FAX: +49 (0)2405 49936 99"
        DESCRIPTION
            "The MIB module is for LANCOM Systems"
        ::= { enterprises 2356 }

switchingSystems                                                          OBJECT IDENTIFIER ::= { lancom-systems 800 }

gigabitEthernetSwitches                                             OBJECT IDENTIFIER ::= { switchingSystems 3 }

lancomGS2310P                                                OBJECT IDENTIFIER ::= { gigabitEthernetSwitches 2311 }

gs2310pSystem                                     OBJECT IDENTIFIER ::= { lancomGS2310P 1 }

gs2310pSystemInformation                                     OBJECT IDENTIFIER ::= { gs2310pSystem 1 }

gs2310pModelName OBJECT-TYPE
   SYNTAX       DisplayString
   MAX-ACCESS   read-only
   STATUS       current
   DESCRIPTION
       ""
 ::= { gs2310pSystemInformation 1 }

gs2310pBIOSVersion OBJECT-TYPE
   SYNTAX       DisplayString
   MAX-ACCESS   read-only
   STATUS       current
   DESCRIPTION
       ""
   ::= { gs2310pSystemInformation 2 }

gs2310pFirmwareVersion OBJECT-TYPE
   SYNTAX       DisplayString
   MAX-ACCESS   read-only
   STATUS       current
   DESCRIPTION
       ""
   ::= { gs2310pSystemInformation 3 }

gs2310pHardwareMechanicalVersion OBJECT-TYPE
   SYNTAX       DisplayString
   MAX-ACCESS   read-only
   STATUS       current
   DESCRIPTION
       ""
   ::= { gs2310pSystemInformation 4 }

gs2310pSerialNumber OBJECT-TYPE
   SYNTAX       DisplayString
   MAX-ACCESS   read-only
   STATUS       current
   DESCRIPTION
       ""
   ::= { gs2310pSystemInformation 5 }

gs2310pHostMACAddress OBJECT-TYPE
   SYNTAX       MacAddress
   MAX-ACCESS   read-only
   STATUS       current
   DESCRIPTION
       ""
   ::= { gs2310pSystemInformation 6 }

gs2310pConsoleBaudrate OBJECT-TYPE
   SYNTAX       DisplayString
   MAX-ACCESS   read-only
   STATUS       current
   DESCRIPTION
       ""
   ::= { gs2310pSystemInformation 7 }

gs2310pRAMSize OBJECT-TYPE
   SYNTAX       DisplayString
   MAX-ACCESS   read-only
   STATUS       current
   DESCRIPTION
       ""
   ::= { gs2310pSystemInformation 8 }

gs2310pFlashSize OBJECT-TYPE
   SYNTAX       DisplayString
   MAX-ACCESS   read-only
   STATUS       current
   DESCRIPTION
       ""
   ::= { gs2310pSystemInformation 9 }

gs2310pBridgeFDBSize OBJECT-TYPE
   SYNTAX       DisplayString
   MAX-ACCESS   read-only
   STATUS       current
   DESCRIPTION
       ""
   ::= { gs2310pSystemInformation 10 }

gs2310pTransmitQueue OBJECT-TYPE
   SYNTAX       DisplayString
   MAX-ACCESS   read-only
   STATUS       current
   DESCRIPTION
       ""
   ::= { gs2310pSystemInformation 11 }

gs2310pMaximumFrameSize OBJECT-TYPE
   SYNTAX       DisplayString
   MAX-ACCESS   read-only
   STATUS       current
   DESCRIPTION
       ""
   ::= { gs2310pSystemInformation 12 }

gs2310pCPULoad OBJECT-TYPE
   SYNTAX       DisplayString
   MAX-ACCESS   read-only
   STATUS       current
   DESCRIPTION
       ""
   ::= { gs2310pSystemInformation 13 }

gs2310pSystemDescription OBJECT-TYPE
   SYNTAX       DisplayString
   MAX-ACCESS   read-only
   STATUS       current
   DESCRIPTION
       ""
   ::= { gs2310pSystemInformation 21 }

gs2310pLocation OBJECT-TYPE
   SYNTAX       DisplayString
   MAX-ACCESS   read-only
   STATUS       current
   DESCRIPTION
       ""
   ::= { gs2310pSystemInformation 22 }

gs2310pContact OBJECT-TYPE
   SYNTAX       DisplayString
   MAX-ACCESS   read-only
   STATUS       current
   DESCRIPTION
       ""
   ::= { gs2310pSystemInformation 23 }

gs2310pDeviceName OBJECT-TYPE
   SYNTAX       DisplayString
   MAX-ACCESS   read-only
   STATUS       current
   DESCRIPTION
       ""
   ::= { gs2310pSystemInformation 24 }

gs2310pSystemDate OBJECT-TYPE
   SYNTAX       DisplayString
   MAX-ACCESS   read-only
   STATUS       current
   DESCRIPTION
       ""
   ::= { gs2310pSystemInformation 25 }

gs2310pSystemUptime OBJECT-TYPE
   SYNTAX       DisplayString
   MAX-ACCESS   read-only
   STATUS       current
   DESCRIPTION
       ""
   ::= { gs2310pSystemInformation 26 }

gs2310pSystemIPv4Address OBJECT-TYPE
   SYNTAX       DisplayString
   MAX-ACCESS   read-only
   STATUS       current
   DESCRIPTION
       ""
   ::= { gs2310pSystemInformation 27 }

gs2310pSystemIPv4SubnetMask OBJECT-TYPE
   SYNTAX       DisplayString
   MAX-ACCESS   read-only
   STATUS       current
   DESCRIPTION
       ""
   ::= { gs2310pSystemInformation 28 }

gs2310pSystemIPv4Gateway OBJECT-TYPE
   SYNTAX       DisplayString
   MAX-ACCESS   read-only
   STATUS       current
   DESCRIPTION
       ""
   ::= { gs2310pSystemInformation 29 }

gs2310pIPv6LinkLocalAddress OBJECT-TYPE
   SYNTAX       DisplayString
   MAX-ACCESS   read-only
   STATUS       current
   DESCRIPTION
       ""
   ::= { gs2310pSystemInformation 30 }

gs2310pIPv6Address OBJECT-TYPE
   SYNTAX       DisplayString
   MAX-ACCESS   read-only
   STATUS       current
   DESCRIPTION
       ""
   ::= { gs2310pSystemInformation 31 }

gs2310pIPv6Prefix OBJECT-TYPE
   SYNTAX       DisplayString
   MAX-ACCESS   read-only
   STATUS       current
   DESCRIPTION
       ""
   ::= { gs2310pSystemInformation 32 }

gs2310pIPv6Gateway OBJECT-TYPE
   SYNTAX       DisplayString
   MAX-ACCESS   read-only
   STATUS       current
   DESCRIPTION
       ""
   ::= { gs2310pSystemInformation 33 }

gs2310pLargestFreeMemBlock OBJECT-TYPE
   SYNTAX       Integer32
   MAX-ACCESS   read-only
   STATUS       current
   DESCRIPTION
       "Largest free memory block in Kb"
   ::= { gs2310pSystemInformation 1500 }

gs2310pMemFree  OBJECT-TYPE
   SYNTAX       Integer32
   MAX-ACCESS   read-only
   STATUS       current
   DESCRIPTION
       "Free memory in Kb"
   ::= { gs2310pSystemInformation 1501 }


gs2310pSystemTime                                            OBJECT IDENTIFIER ::= { gs2310pSystem 2 }

gs2310pSystemTimeManual                                      OBJECT IDENTIFIER ::= { gs2310pSystemTime 1 }

gs2310pSystemTimeManualClockSource OBJECT-TYPE
   SYNTAX	INTEGER {useLocal(0),useNTP(1)}
   MAX-ACCESS   read-write
   STATUS       current
   DESCRIPTION
       "default: 0,
        0 : Use Local Settings,
        1 : Use NTP Server."
   ::= { gs2310pSystemTimeManual 1 }

gs2310pSystemTimeManualLocaltime OBJECT-TYPE
   SYNTAX       DisplayString
   MAX-ACCESS   read-write
   STATUS       current
   DESCRIPTION
       "Get/Set the system time of the device.
        The input format is 'Year-Month-Day Hour:Minute:Second'.
        ex: 2011-01-01 05:43:05  means 2011/1/1 - 05:43:05 .
        The value range:
        Year    : 2010 - 2090,
        Mouth   : 1 - 12,
        Day     : 1 - 31,
        Hour    : 0 - 23,
        Minute  : 0 - 59,
        Sec     : 0 - 59."
   ::= { gs2310pSystemTimeManual 2 }

gs2310pSystemTimeManualTimeZoneOffset OBJECT-TYPE
   SYNTAX       INTEGER(-720..780)
   MAX-ACCESS   read-write
   STATUS       current
   DESCRIPTION
       "Get/Set the NTP Time Zone.
        The value range is between -720 and 780 (minutes)."
   ::= { gs2310pSystemTimeManual 3 }

gs2310pSystemTimeManualDaylightSavings OBJECT-TYPE
   SYNTAX       INTEGER { disable(0), enable(1) }
   MAX-ACCESS   read-write
   STATUS       current
   DESCRIPTION
       "default: 0,
        0 : Disable,
        1 : Enable."
   ::= { gs2310pSystemTimeManual 4 }

gs2310pSystemTimeManualTimeSetOffset OBJECT-TYPE
   SYNTAX       Integer32(1..1440)
   MAX-ACCESS   read-write
   STATUS       current
   DESCRIPTION
       "Get/Set the Daylight Saving Time.
        The value range is between 1 and 1440 (minutes),
        Default : 60 (minutes)."
   ::= { gs2310pSystemTimeManual 5 }

gs2310pSystemTimeManualDaylightSavingsType OBJECT-TYPE
   SYNTAX       INTEGER { byDates(0), recurring(1) }
   MAX-ACCESS   read-write
   STATUS       current
   DESCRIPTION
       "default: 0,
        0 : By dates,
        1 : Recurring."
   ::= { gs2310pSystemTimeManual 6 }

gs2310pSystemTimeManualDaylightSavingsBydatesFrom OBJECT-TYPE
   SYNTAX       DisplayString
   MAX-ACCESS   read-write
   STATUS       current
   DESCRIPTION
       "Get/Set the Start time of By dates Daylight Savings.
        The input format is 'Year-Month-Day Hour:Minute'.
        ex: 2011-01-01 05:43  means 2011/1/1 - 05:43 .
        The value range:
        Year    : 2010 - 2090,
        Mouth   : 1 - 12,
        Day     : 1 - 31,
        Hour    : 0 - 23,
        Minute  : 0 - 59."
   ::= { gs2310pSystemTimeManual 7 }

gs2310pSystemTimeManualDaylightSavingsBydatesTo OBJECT-TYPE
   SYNTAX       DisplayString
   MAX-ACCESS   read-write
   STATUS       current
   DESCRIPTION
       "Get/Set the End time of By dates Daylight Savings.
        The input format is 'Year-Month-Day Hour:Minute'.
        ex: 2011-01-01 05:43  means 2011/1/1 - 05:43 .
        The value range:
        Year    : 2010 - 2090,
        Mouth   : 1 - 12,
        Day     : 1 - 31,
        Hour    : 0 - 23,
        Minute  : 0 - 59."
   ::= { gs2310pSystemTimeManual 8 }

gs2310pSystemTimeManualDaylightSavingsRecurringDayFrom OBJECT-TYPE
   SYNTAX      INTEGER {
                        sunday(0),
                        monday(1),
                        tuseday(2),
                        wednesday(3),
                        thursday(4),
                        friday(5),
                        saturday(6)
                        }
   MAX-ACCESS   read-write
   STATUS       current
   DESCRIPTION
       "Get/Set the Daylight Saving Time Day From.
        0 : Sun, 1 : Mon, 2 : Tue, 3 : Wed, 4 : Thu, 5 : Fri, 6 : Sat."
   ::= { gs2310pSystemTimeManual 9 }

gs2310pSystemTimeManualDaylightSavingsRecurringWeekFrom OBJECT-TYPE
   SYNTAX       INTEGER{
                        firstWeek(1),
                        secondWeek(2),
                        thirdWeek(3),
                        fourthWeek(4),
                        listWeek(5)
                        }
   MAX-ACCESS   read-write
   STATUS       current
   DESCRIPTION
       "Get/Set the Daylight Saving Time Week From.
        1 : first week, 2, 3, 4, 5 : last week"
   ::= { gs2310pSystemTimeManual 10 }

gs2310pSystemTimeManualDaylightSavingsRecurringMonthFrom OBJECT-TYPE
   SYNTAX      INTEGER {
                        jan(1),
                        feb(2),
                        mar(3),
                        apr(4),
                        may(5),
                        jun(6),
                        jul(7),
                        aug(8),
                        sep(9),
                        oct(10),
                        nov(11),
                        dec(12)
                        }
   MAX-ACCESS   read-write
   STATUS       current
   DESCRIPTION
       "Get/Set the Daylight Saving Time Month From.
        1 : Jan, 2 : Feb, 3 : Mar, 4 : Apr, 5 : May, 6 : Jun,
        7 : Jul, 8 : Aug, 9 : Sep, 10 : Oct, 11 : Nov, 12 : Dec."
   ::= { gs2310pSystemTimeManual 11 }

gs2310pSystemTimeManualDaylightSavingsRecurringTimeFrom OBJECT-TYPE
   SYNTAX       DisplayString
   MAX-ACCESS   read-write
   STATUS       current
   DESCRIPTION
       "Get/Set the Start time of By dates Daylight Savings.
        The input format is 'Hour:Minute'.
        ex: 05:43.
        The value range:
        Hour    : 0 - 23,
        Minute  : 0 - 59."
   ::= { gs2310pSystemTimeManual 12 }

gs2310pSystemTimeManualDaylightSavingsRecurringDayTo OBJECT-TYPE
   SYNTAX      INTEGER {
                        sunday(0),
                        monday(1),
                        tuseday(2),
                        wednesday(3),
                        thursday(4),
                        friday(5),
                        saturday(6)
                        }
   MAX-ACCESS   read-write
   STATUS       current
   DESCRIPTION
       "Get/Set the Daylight Saving Time Day To.
        0 : Sun, 1 : Mon, 2 : Tue, 3 : Wed, 4 : Thu, 5 : Fri, 6 : Sat."
   ::= { gs2310pSystemTimeManual 13 }

gs2310pSystemTimeManualDaylightSavingsRecurringWeekTo OBJECT-TYPE
   SYNTAX       INTEGER{
                        firstWeek(1),
                        secondWeek(2),
                        thirdWeek(3),
                        fourthWeek(4),
                        listWeek(5)
                        }
   MAX-ACCESS   read-write
   STATUS       current
   DESCRIPTION
       "Get/Set the Daylight Saving Time Week To.
        1 : first week, 2, 3, 4, 5 : last week"
   ::= { gs2310pSystemTimeManual 14 }

gs2310pSystemTimeManualDaylightSavingsRecurringMonthTo OBJECT-TYPE
   SYNTAX      INTEGER {
                        jan(1),
                        feb(2),
                        mar(3),
                        apr(4),
                        may(5),
                        jun(6),
                        jul(7),
                        aug(8),
                        sep(9),
                        oct(10),
                        nov(11),
                        dec(12)
                        }
   MAX-ACCESS   read-write
   STATUS       current
   DESCRIPTION
       "Get/Set the Daylight Saving Time Month To.
        1 : Jan, 2 : Feb, 3 : Mar, 4 : Apr, 5 : May, 6 : Jun,
        7 : Jul, 8 : Aug, 9 : Sep, 10 : Oct, 11 : Nov, 12 : Dec."
   ::= { gs2310pSystemTimeManual 15 }

gs2310pSystemTimeManualDaylightSavingsRecurringTimeTo OBJECT-TYPE
   SYNTAX       DisplayString
   MAX-ACCESS   read-write
   STATUS       current
   DESCRIPTION
       "Get/Set the Start time of By dates Daylight Savings.
        The input format is 'Hour:Minute'.
        ex: 05:43.
        The value range:
        Hour    : 0 - 23,
        Minute  : 0 - 59."
   ::= { gs2310pSystemTimeManual 16 }

gs2310pSystemTimeNTP                                     OBJECT IDENTIFIER ::= { gs2310pSystemTime 2 }

gs2310pSystemTimeNTPTable OBJECT-TYPE
   SYNTAX      SEQUENCE OF Gs2310pSystemTimeNTPEntry
   MAX-ACCESS  not-accessible
   STATUS      current
   DESCRIPTION
       " "
   ::= { gs2310pSystemTimeNTP 1 }

gs2310pSystemTimeNTPEntry OBJECT-TYPE
   SYNTAX      Gs2310pSystemTimeNTPEntry
   MAX-ACCESS  not-accessible
   STATUS      current
   DESCRIPTION
       ""
   INDEX    { gs2310pSystemTimeNTPIndex  }
   ::= { gs2310pSystemTimeNTPTable 1 }

Gs2310pSystemTimeNTPEntry ::= SEQUENCE {
   gs2310pSystemTimeNTPIndex             Integer32,
   gs2310pSystemTimeNTPServerIPType      INTEGER,
   gs2310pSystemTimeNTPServer            DisplayString,
   gs2310pSystemTimeNTPCurrentMode       INTEGER
}

gs2310pSystemTimeNTPIndex OBJECT-TYPE
   SYNTAX      Integer32(1..5)
   MAX-ACCESS  not-accessible
   STATUS      current
   DESCRIPTION
       " The index of the ntp entry. "
   ::= { gs2310pSystemTimeNTPEntry 1 }

gs2310pSystemTimeNTPServerIPType OBJECT-TYPE
   SYNTAX       INTEGER { ipv4(0), ipv6(1) }
   MAX-ACCESS   read-write
   STATUS       current
   DESCRIPTION
       "Default: 0,
        0 : IPv4,
        1 : IPv6."
   ::= { gs2310pSystemTimeNTPEntry 2 }

gs2310pSystemTimeNTPServer OBJECT-TYPE
   SYNTAX       DisplayString
   MAX-ACCESS   read-write
   STATUS       current
   DESCRIPTION
       "Get/Set the NTP Time Server1. You can use the IP address or domain name."
   ::= { gs2310pSystemTimeNTPEntry 3 }

gs2310pSystemTimeNTPCurrentMode OBJECT-TYPE
   SYNTAX      INTEGER { empty(0), active(1), edit(2), delete(3) }
   MAX-ACCESS  read-write
   STATUS      current
   DESCRIPTION
       " 0: Empty
        1: Active
        2: Edit
        3: Delete"
   ::= { gs2310pSystemTimeNTPEntry 4 }

gs2310pSystemTimeNTPRequestInterval OBJECT-TYPE
   SYNTAX       INTEGER(60..999999999)
   MAX-ACCESS   read-write
   STATUS       current
   DESCRIPTION
       "Get/Set the NTP Request Interval.
        Default : 86400.
        The value range is between 60 and 999999999 (seconds)."
   ::= { gs2310pSystemTimeNTP 2 }

gs2310pSystemTimeNTPTriesNumber OBJECT-TYPE
   SYNTAX       INTEGER(0..999999999)
   MAX-ACCESS   read-write
   STATUS       current
   DESCRIPTION
       "Get/Set the NTP Number of tries.
        Default : 4.
        The value range is between 0 and 999999999."
   ::= { gs2310pSystemTimeNTP 3 }


gs2310pSystemAccount                                         OBJECT IDENTIFIER ::= { gs2310pSystem 3 }

gs2310pSystemAccountUsers                                    OBJECT IDENTIFIER ::= { gs2310pSystemAccount 1 }

gs2310pSystemAccountUserCreate OBJECT-TYPE
   SYNTAX       INTEGER { none(0), create(1) }
   MAX-ACCESS   read-write
   STATUS       current
   DESCRIPTION
       "default: 0
        0 : None  (read only)
        1 : Create a user account"
   ::= { gs2310pSystemAccountUsers 1 }

gs2310pSystemAccountUsersTable OBJECT-TYPE
   SYNTAX      SEQUENCE OF Gs2310pSystemAccountUsersEntry
   MAX-ACCESS  not-accessible
   STATUS      current
   DESCRIPTION
       " "
   ::= { gs2310pSystemAccountUsers 2 }

gs2310pSystemAccountUsersEntry OBJECT-TYPE
   SYNTAX      Gs2310pSystemAccountUsersEntry
   MAX-ACCESS  not-accessible
   STATUS      current
   DESCRIPTION
       ""
   INDEX    { gs2310pUserIndex  }
   ::= { gs2310pSystemAccountUsersTable 1 }


Gs2310pSystemAccountUsersEntry ::= SEQUENCE {
   gs2310pUserIndex              Integer32 ,
   gs2310pUserName               DisplayString,
   gs2310pPassword               DisplayString,
   gs2310pUserPrivilegeLevel     Integer32 ,
   gs2310pAccountUserRowStatus   INTEGER
}


gs2310pUserIndex OBJECT-TYPE
   SYNTAX      Integer32 (1..20)
   MAX-ACCESS  not-accessible
   STATUS      current
   DESCRIPTION
       " "
   ::= { gs2310pSystemAccountUsersEntry 1 }

gs2310pUserName OBJECT-TYPE
   SYNTAX      DisplayString (SIZE (1..32))
   MAX-ACCESS  read-write
   STATUS      current
   DESCRIPTION
       "Please use a combination of letters, numbers and underscores"
   ::= { gs2310pSystemAccountUsersEntry 2 }

gs2310pPassword OBJECT-TYPE
   SYNTAX      DisplayString (SIZE (1..32))
   MAX-ACCESS  read-write
   STATUS      current
   DESCRIPTION
       "Please use ASCII printable code except Quotation mark, Colon (punctuation), Less-than sign, Greater-than sign, At sign, Question mark and Space (punctuation)"
   ::= { gs2310pSystemAccountUsersEntry 3 }

gs2310pUserPrivilegeLevel OBJECT-TYPE
   SYNTAX      Integer32 (1..15)
   MAX-ACCESS  read-write
   STATUS      current
   DESCRIPTION
       "default:1
        User privilege level range : 1 - 15"
   ::= { gs2310pSystemAccountUsersEntry 4 }

gs2310pAccountUserRowStatus OBJECT-TYPE
   SYNTAX      INTEGER { active(1), notInservice(2), edit(3), destroy(4), undo(5) }
   MAX-ACCESS  read-write
   STATUS      current
   DESCRIPTION
       " 1: active
        2: notInservice
        3: edit
        4: destroy
        5: undo"
   ::= { gs2310pSystemAccountUsersEntry 5 }

gs2310pSystemAccountUsersSuperUserPassword OBJECT-TYPE
   SYNTAX      OCTET STRING (SIZE (0..32))
   MAX-ACCESS read-write
   STATUS      current
   DESCRIPTION
        "Super-User Password"
   ::= { gs2310pSystemAccountUsers 1500 }

gs2310pSystemAccountEnforcePasswordRules OBJECT-TYPE
   SYNTAX       INTEGER { yes(0), no(1) }
   MAX-ACCESS   read-write
   STATUS       current
   DESCRIPTION
       "default: 0
        0 : Do not enforce rules
        1 : enforce rules"
   ::= { gs2310pSystemAccountUsers 1501 }

gs2310pSystemAccountPrivilegeLevel                           OBJECT IDENTIFIER ::= { gs2310pSystemAccount 2 }

gs2310pAccountPrivilegeLevel OBJECT-TYPE
   SYNTAX      Integer32 (1..15)
   MAX-ACCESS  read-write
   STATUS      current
   DESCRIPTION
       "Default:15, Range : 1-15. "
   ::= { gs2310pSystemAccountPrivilegeLevel 1 }

gs2310pAggregationPrivilegeLevel OBJECT-TYPE
   SYNTAX      Integer32 (1..15)
   MAX-ACCESS  read-write
   STATUS      current
   DESCRIPTION
       "Default:15, Range : 1-15. "
   ::= { gs2310pSystemAccountPrivilegeLevel 2 }

gs2310pDiagnosticsPrivilegeLevel OBJECT-TYPE
   SYNTAX      Integer32 (1..15)
   MAX-ACCESS  read-write
   STATUS      current
   DESCRIPTION
       "Default:15, Range : 1-15. "
   ::= { gs2310pSystemAccountPrivilegeLevel 3 }

gs2310pEEEPrivilegeLevel OBJECT-TYPE
   SYNTAX      Integer32 (1..15)
   MAX-ACCESS  read-write
   STATUS      current
   DESCRIPTION
       "Default:15, Range : 1-15. "
   ::= { gs2310pSystemAccountPrivilegeLevel 4 }

gs2310pEasyportPrivilegeLevel OBJECT-TYPE
   SYNTAX      Integer32 (1..15)
   MAX-ACCESS  read-write
   STATUS      current
   DESCRIPTION
       "Default:15, Range : 1-15. "
   ::= { gs2310pSystemAccountPrivilegeLevel 9 }

gs2310pGARPPrivilegeLevel OBJECT-TYPE
   SYNTAX      Integer32 (1..15)
   MAX-ACCESS  read-write
   STATUS      current
   DESCRIPTION
       "Default:15, Range : 1-15. "
   ::= { gs2310pSystemAccountPrivilegeLevel 10 }

gs2310pGVRPPrivilegeLevel OBJECT-TYPE
   SYNTAX      Integer32 (1..15)
   MAX-ACCESS  read-write
   STATUS      current
   DESCRIPTION
       "Default:15, Range : 1-15. "
   ::= { gs2310pSystemAccountPrivilegeLevel 11 }

gs2310pIPPrivilegeLevel OBJECT-TYPE
   SYNTAX      Integer32 (1..15)
   MAX-ACCESS  read-write
   STATUS      current
   DESCRIPTION
       "Default:15, Range : 1-15. "
   ::= { gs2310pSystemAccountPrivilegeLevel 12 }

gs2310pIPMCSnoopingPrivilegeLevel OBJECT-TYPE
   SYNTAX      Integer32 (1..15)
   MAX-ACCESS  read-write
   STATUS      current
   DESCRIPTION
       "Default:15, Range : 1-15. "
   ::= { gs2310pSystemAccountPrivilegeLevel 13 }

gs2310pLACPPrivilegeLevel OBJECT-TYPE
   SYNTAX      Integer32 (1..15)
   MAX-ACCESS  read-write
   STATUS      current
   DESCRIPTION
       "Default:15, Range : 1-15. "
   ::= { gs2310pSystemAccountPrivilegeLevel 14 }

gs2310pLLDPPrivilegeLevel OBJECT-TYPE
   SYNTAX      Integer32 (1..15)
   MAX-ACCESS  read-write
   STATUS      current
   DESCRIPTION
       "Default:15, Range : 1-15. "
   ::= { gs2310pSystemAccountPrivilegeLevel 15 }

gs2310pLLDPMEDPrivilegeLevel OBJECT-TYPE
   SYNTAX      Integer32 (1..15)
   MAX-ACCESS  read-write
   STATUS      current
   DESCRIPTION
       "Default:15, Range : 1-15. "
   ::= { gs2310pSystemAccountPrivilegeLevel 16 }

gs2310pLoopProtectPrivilegeLevel OBJECT-TYPE
   SYNTAX      Integer32 (1..15)
   MAX-ACCESS  read-write
   STATUS      current
   DESCRIPTION
       "Default:15, Range : 1-15. "
   ::= { gs2310pSystemAccountPrivilegeLevel 17 }

gs2310pMACTablePrivilegeLevel OBJECT-TYPE
   SYNTAX      Integer32 (1..15)
   MAX-ACCESS  read-write
   STATUS      current
   DESCRIPTION
       "Default:15, Range : 1-15. "
   ::= { gs2310pSystemAccountPrivilegeLevel 18 }

gs2310pMVRPrivilegeLevel OBJECT-TYPE
   SYNTAX      Integer32 (1..15)
   MAX-ACCESS  read-write
   STATUS      current
   DESCRIPTION
       "Default:15, Range : 1-15. "
   ::= { gs2310pSystemAccountPrivilegeLevel 22 }

gs2310pMaintenancePrivilegeLevel OBJECT-TYPE
   SYNTAX      Integer32 (1..15)
   MAX-ACCESS  read-write
   STATUS      current
   DESCRIPTION
       "Default:15, Range : 1-15. "
   ::= { gs2310pSystemAccountPrivilegeLevel 24 }

gs2310pMirroringPrivilegeLevel OBJECT-TYPE
   SYNTAX      Integer32 (1..15)
   MAX-ACCESS  read-write
   STATUS      current
   DESCRIPTION
       "Default:15, Range : 1-15. "
   ::= { gs2310pSystemAccountPrivilegeLevel 25 }

gs2310pPortsPrivilegeLevel OBJECT-TYPE
   SYNTAX      Integer32 (1..15)
   MAX-ACCESS  read-write
   STATUS      current
   DESCRIPTION
       "Default:15, Range : 1-15. "
   ::= { gs2310pSystemAccountPrivilegeLevel 27 }

gs2310pPrivateVLANsPrivilegeLevel OBJECT-TYPE
   SYNTAX      Integer32 (1..15)
   MAX-ACCESS  read-write
   STATUS      current
   DESCRIPTION
       "Default:15, Range : 1-15. "
   ::= { gs2310pSystemAccountPrivilegeLevel 28 }

gs2310pQoSPrivilegeLevel OBJECT-TYPE
   SYNTAX      Integer32 (1..15)
   MAX-ACCESS  read-write
   STATUS      current
   DESCRIPTION
       "Default:15, Range : 1-15. "
   ::= { gs2310pSystemAccountPrivilegeLevel 29 }

gs2310pSFlowPrivilegeLevel OBJECT-TYPE
   SYNTAX      Integer32 (1..15)
   MAX-ACCESS  read-write
   STATUS      current
   DESCRIPTION
       "Default:15, Range : 1-15. "
   ::= { gs2310pSystemAccountPrivilegeLevel 30 }

gs2310pSMTPPrivilegeLevel OBJECT-TYPE
   SYNTAX      Integer32 (1..15)
   MAX-ACCESS  read-write
   STATUS      current
   DESCRIPTION
       "Default:15, Range : 1-15. "
   ::= { gs2310pSystemAccountPrivilegeLevel 31 }

gs2310pSNMPPrivilegeLevel OBJECT-TYPE
   SYNTAX      Integer32 (1..15)
   MAX-ACCESS  read-write
   STATUS      current
   DESCRIPTION
       "Default:15, Range : 1-15. "
   ::= { gs2310pSystemAccountPrivilegeLevel 32 }

gs2310pSecurityPrivilegeLevel OBJECT-TYPE
   SYNTAX      Integer32 (1..15)
   MAX-ACCESS  read-write
   STATUS      current
   DESCRIPTION
       "Default:15, Range : 1-15. "
   ::= { gs2310pSystemAccountPrivilegeLevel 33 }

gs2310pSingleIPPrivilegeLevel OBJECT-TYPE
   SYNTAX      Integer32 (1..15)
   MAX-ACCESS  read-write
   STATUS      current
   DESCRIPTION
       "Default:15, Range : 1-15. "
   ::= { gs2310pSystemAccountPrivilegeLevel 34 }

gs2310pSpanningTreePrivilegeLevel OBJECT-TYPE
   SYNTAX      Integer32 (1..15)
   MAX-ACCESS  read-write
   STATUS      current
   DESCRIPTION
       "Default:15, Range : 1-15. "
   ::= { gs2310pSystemAccountPrivilegeLevel 35 }

gs2310pSystemPrivilegeLevel OBJECT-TYPE
   SYNTAX      Integer32 (1..15)
   MAX-ACCESS  read-write
   STATUS      current
   DESCRIPTION
       "Default:15, Range : 1-15. "
   ::= { gs2310pSystemAccountPrivilegeLevel 36 }

gs2310pTrapEventPrivilegeLevel OBJECT-TYPE
   SYNTAX      Integer32 (1..15)
   MAX-ACCESS  read-write
   STATUS      current
   DESCRIPTION
       "Default:15, Range : 1-15. "
   ::= { gs2310pSystemAccountPrivilegeLevel 37 }

gs2310pUPnPPrivilegeLevel OBJECT-TYPE
   SYNTAX      Integer32 (1..15)
   MAX-ACCESS  read-write
   STATUS      current
   DESCRIPTION
       "Default:15, Range : 1-15. "
   ::= { gs2310pSystemAccountPrivilegeLevel 38 }

gs2310pVCLPrivilegeLevel OBJECT-TYPE
   SYNTAX      Integer32 (1..15)
   MAX-ACCESS  read-write
   STATUS      current
   DESCRIPTION
       "Default:15, Range : 1-15. "
   ::= { gs2310pSystemAccountPrivilegeLevel 39 }

gs2310pVLANsPrivilegeLevel OBJECT-TYPE
   SYNTAX      Integer32 (1..15)
   MAX-ACCESS  read-write
   STATUS      current
   DESCRIPTION
       "Default:15, Range : 1-15. "
   ::= { gs2310pSystemAccountPrivilegeLevel 41 }

gs2310pVoiceVLANPrivilegeLevel OBJECT-TYPE
   SYNTAX      Integer32 (1..15)
   MAX-ACCESS  read-write
   STATUS      current
   DESCRIPTION
       "Default:15, Range : 1-15. "
   ::= { gs2310pSystemAccountPrivilegeLevel 42 }

gs2310pPOEPrivilegeLevel OBJECT-TYPE
   SYNTAX      Integer32 (1..15)
   MAX-ACCESS  read-write
   STATUS      current
   DESCRIPTION
       "Default:15, Range : 1-15. "
   ::= { gs2310pSystemAccountPrivilegeLevel 43 }

gs2310pIP                                                    OBJECT IDENTIFIER ::= { gs2310pSystem 4 }

gs2310pIPv4                                                  OBJECT IDENTIFIER ::= { gs2310pIP 1 }

gs2310pIPv4Configured                                                  OBJECT IDENTIFIER ::= { gs2310pIPv4 1 }

gs2310pIpv4DHCPClient OBJECT-TYPE
   SYNTAX      INTEGER { disable(0), enable(1) }
   MAX-ACCESS  read-write
   STATUS      current
   DESCRIPTION
       "default:0
       0: disable
       1: enable"
   ::= { gs2310pIPv4Configured 1 }

gs2310pIPv4Address OBJECT-TYPE
   SYNTAX      IpAddress
   MAX-ACCESS  read-write
   STATUS      current
   DESCRIPTION
       ""
   ::= { gs2310pIPv4Configured 2 }

gs2310pIPv4Mask OBJECT-TYPE
   SYNTAX      IpAddress
   MAX-ACCESS  read-write
   STATUS      current
   DESCRIPTION
       ""
   ::= { gs2310pIPv4Configured 3 }

gs2310pIPv4Gateway OBJECT-TYPE
   SYNTAX      IpAddress
   MAX-ACCESS  read-write
   STATUS      current
   DESCRIPTION
       ""
   ::= { gs2310pIPv4Configured 4 }

gs2310pIPv4VLANId OBJECT-TYPE
   SYNTAX      Integer32(1..4094)
   MAX-ACCESS  read-write
   STATUS      current
   DESCRIPTION
       "default:1"
   ::= { gs2310pIPv4Configured 5 }

gs2310pIPv4DNSServer OBJECT-TYPE
   SYNTAX      IpAddress
   MAX-ACCESS  read-write
   STATUS      current
   DESCRIPTION
       ""
   ::= { gs2310pIPv4Configured 6 }

gs2310pIPv4DNSProxy OBJECT-TYPE
   SYNTAX      INTEGER { disable(0), enable(1) }
   MAX-ACCESS  read-write
   STATUS      current
   DESCRIPTION
       "0:disable, 1:enable "
   ::= { gs2310pIPv4Configured 7 }

gs2310pIPv4Current                                                  OBJECT IDENTIFIER ::= { gs2310pIPv4 2 }

gs2310pIpv4CurrentDHCPClient OBJECT-TYPE
   SYNTAX      INTEGER { none(0), renew(1) }
   MAX-ACCESS  read-write
   STATUS      current
   DESCRIPTION
       "default:0
       0: none (for read)
       1: renew"
   ::= { gs2310pIPv4Current 1 }

gs2310pIPv4CurrentAddress OBJECT-TYPE
   SYNTAX      IpAddress
   MAX-ACCESS  read-only
   STATUS      current
   DESCRIPTION
       ""
   ::= { gs2310pIPv4Current 2 }

gs2310pIPv4CurrentMask OBJECT-TYPE
   SYNTAX      IpAddress
   MAX-ACCESS  read-only
   STATUS      current
   DESCRIPTION
       ""
   ::= { gs2310pIPv4Current 3 }

gs2310pIPv4CurrentGateway OBJECT-TYPE
   SYNTAX      IpAddress
   MAX-ACCESS  read-only
   STATUS      current
   DESCRIPTION
       ""
   ::= { gs2310pIPv4Current 4 }

gs2310pIPv4CurrentVLANId OBJECT-TYPE
   SYNTAX      Integer32(1..4094)
   MAX-ACCESS  read-only
   STATUS      current
   DESCRIPTION
       "default:1"
   ::= { gs2310pIPv4Current 5 }

gs2310pIPv4CurrentDNSServer OBJECT-TYPE
   SYNTAX      IpAddress
   MAX-ACCESS  read-only
   STATUS      current
   DESCRIPTION
       ""
   ::= { gs2310pIPv4Current 6 }


gs2310pIPv6                                                  OBJECT IDENTIFIER ::= { gs2310pIP 2 }

gs2310pIPv6Configured                                                  OBJECT IDENTIFIER ::= { gs2310pIPv6 1 }

gs2310pIpv6AutoConfiguration OBJECT-TYPE
   SYNTAX      INTEGER { disable(0), enable(1) }
   MAX-ACCESS  read-write
   STATUS      current
   DESCRIPTION
       "default:0
       0: disable
       1: enable"
   ::= { gs2310pIPv6Configured 1 }

gs2310pIpv6Address OBJECT-TYPE
   SYNTAX      DisplayString (SIZE (0..30))
   MAX-ACCESS  read-write
   STATUS      current
   DESCRIPTION
       ""
   ::= { gs2310pIPv6Configured 2 }

gs2310pIpv6Prefix OBJECT-TYPE
   SYNTAX      Integer32 (1..128)
   MAX-ACCESS  read-write
   STATUS      current
   DESCRIPTION
       "default: 96"
   ::= { gs2310pIPv6Configured 3 }

gs2310pIpv6Gateway OBJECT-TYPE
   SYNTAX      DisplayString (SIZE (0..30))
   MAX-ACCESS  read-write
   STATUS      current
   DESCRIPTION
       " "
   ::= { gs2310pIPv6Configured 4 }

gs2310pIPv6Current                                                  OBJECT IDENTIFIER ::= { gs2310pIPv6 2 }

gs2310pIpv6CurrentAutoConfiguration OBJECT-TYPE
   SYNTAX      INTEGER { disable(0), enable(1) }
   MAX-ACCESS  read-only
   STATUS      current
   DESCRIPTION
       "default:0
       0: disable
       1: enable"
   ::= { gs2310pIPv6Current 1 }

gs2310pIpv6CurrentAddress OBJECT-TYPE
   SYNTAX      DisplayString (SIZE (0..30))
   MAX-ACCESS  read-only
   STATUS      current
   DESCRIPTION
       ""
   ::= { gs2310pIPv6Current 2 }


gs2310pIpv6CurrentLinkLocalAddress OBJECT-TYPE
   SYNTAX      DisplayString(SIZE (0..30))
   MAX-ACCESS  read-only
   STATUS      current
   DESCRIPTION
       ""
   ::= { gs2310pIPv6Current 3 }


gs2310pIpv6CurrentPrefix OBJECT-TYPE
   SYNTAX      DisplayString(SIZE (0..64))
   MAX-ACCESS  read-only
   STATUS      current
   DESCRIPTION
       ""
   ::= { gs2310pIPv6Current 4 }

gs2310pIpv6CurrentGateway OBJECT-TYPE
   SYNTAX      DisplayString (SIZE (0..30))
   MAX-ACCESS  read-only
   STATUS      current
   DESCRIPTION
       " "
   ::= { gs2310pIPv6Current 5 }

gs2310pSyslog                                                OBJECT IDENTIFIER ::= { gs2310pSystem 5 }

gs2310pSyslogConf                                            OBJECT IDENTIFIER ::= { gs2310pSyslog 1 }

gs2310pServerMode OBJECT-TYPE
   SYNTAX      INTEGER { disable(0), enable(1) }
   MAX-ACCESS  read-write
   STATUS      current
   DESCRIPTION
       "default: 0
       0: disable
       1: enable "
   ::= { gs2310pSyslogConf 1 }

gs2310pServerAddress1 OBJECT-TYPE
   SYNTAX      IpAddress
   MAX-ACCESS  read-write
   STATUS      current
   DESCRIPTION
       " "
   ::= { gs2310pSyslogConf 2 }

gs2310pServerAddress2 OBJECT-TYPE
   SYNTAX      IpAddress
   MAX-ACCESS  read-write
   STATUS      current
   DESCRIPTION
       " "
   ::= { gs2310pSyslogConf 3 }

gs2310pSyslogLevel OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       "default: 6 (Info)
       0: Emergency
       1: Alert
       2: Critical
       3: Error
       4: Warning
       5: Notice
       6: Info
       7: Debug"
   ::= { gs2310pSyslogConf 4 }

gs2310pSyslogDetailedInfo                                    OBJECT IDENTIFIER ::= { gs2310pSyslog 2 }

gs2310pSyslogDetailedInfoClear OBJECT-TYPE
   SYNTAX      INTEGER { none(0), clear(1) }
   MAX-ACCESS  read-write
   STATUS      current
   DESCRIPTION
      "default: 0
       0 : None  (read only)
       1 : Clear Syslog"
   ::= { gs2310pSyslogDetailedInfo 1 }

gs2310pSyslogDetailedInfoTable OBJECT-TYPE
  SYNTAX      SEQUENCE OF Gs2310pSyslogDetailedInfoEntry
  MAX-ACCESS  not-accessible
  STATUS      current
  DESCRIPTION
           " "
       ::= { gs2310pSyslogDetailedInfo 2 }

gs2310pSyslogDetailedInfoEntry OBJECT-TYPE
   SYNTAX      Gs2310pSyslogDetailedInfoEntry
   MAX-ACCESS  not-accessible
   STATUS      current
   DESCRIPTION
           ""
   INDEX    { gs2310pSyslogDetailedInfoIndex  }
   ::= { gs2310pSyslogDetailedInfoTable 1 }

Gs2310pSyslogDetailedInfoEntry ::= SEQUENCE {
   gs2310pSyslogDetailedInfoIndex       Integer32,
   gs2310pSyslogDetailedInfoLevel       DisplayString,
   gs2310pSyslogDetailedInfoTime        DisplayString,
   gs2310pSyslogDetailedInfoMessage     DisplayString
}

gs2310pSyslogDetailedInfoIndex OBJECT-TYPE
   SYNTAX      Integer32(1..1024)
   MAX-ACCESS  not-accessible
   STATUS      current
   DESCRIPTION
       " "
   ::= { gs2310pSyslogDetailedInfoEntry 1 }

gs2310pSyslogDetailedInfoLevel OBJECT-TYPE
   SYNTAX      DisplayString
   MAX-ACCESS  read-only
   STATUS      current
   DESCRIPTION
       " "
   ::= { gs2310pSyslogDetailedInfoEntry 2 }

gs2310pSyslogDetailedInfoTime OBJECT-TYPE
   SYNTAX      DisplayString(SIZE (0..20))
   MAX-ACCESS  read-only
   STATUS      current
   DESCRIPTION
       " "
   ::= { gs2310pSyslogDetailedInfoEntry 3 }

gs2310pSyslogDetailedInfoMessage OBJECT-TYPE
   SYNTAX      DisplayString
   MAX-ACCESS  read-only
   STATUS      current
   DESCRIPTION
       " "
   ::= { gs2310pSyslogDetailedInfoEntry 4 }


gs2310pSnmp                                                OBJECT IDENTIFIER ::= { gs2310pSystem 6 }

gs2310pSnmpConf                                            OBJECT IDENTIFIER ::= { gs2310pSnmp 1 }

gs2310pGetCommunityMode OBJECT-TYPE
   SYNTAX       INTEGER { disable(0), enable(1) }
   MAX-ACCESS   read-write
   STATUS       current
   DESCRIPTION
       "Get/Set the get-community mode of the SNMP.
        default : 1, 0: disable, 1: enable. "
   ::= { gs2310pSnmpConf 1 }

gs2310pGetCommunity OBJECT-TYPE
   SYNTAX       DisplayString
   MAX-ACCESS   read-write
   STATUS       current
   DESCRIPTION
       "Get/Set the get-community of the SNMP."
   ::= { gs2310pSnmpConf 2 }

gs2310pSetCommunityMode OBJECT-TYPE
   SYNTAX       INTEGER { disable(0), enable(1) }
   MAX-ACCESS   read-write
   STATUS       current
   DESCRIPTION
       "Get/Set the set-community mode of the SNMP.
        default : 1, 0: disable, 1: enable. "
   ::= { gs2310pSnmpConf 3 }

gs2310pSetCommunity OBJECT-TYPE
   SYNTAX       DisplayString
   MAX-ACCESS   read-write
   STATUS       current
   DESCRIPTION
       "Get/Set the set-community of the SNMP."
   ::= { gs2310pSnmpConf 4 }

gs2310pGetCommunityConfTable OBJECT-TYPE
   SYNTAX      SEQUENCE OF GS2310PGetCommunityConfEntry
   MAX-ACCESS  not-accessible
   STATUS      current
   DESCRIPTION
       " Show get-community of the SNMP. "
   ::= { gs2310pSnmpConf 5 }

gs2310pGetCommunityConfEntry OBJECT-TYPE
   SYNTAX      GS2310PGetCommunityConfEntry
   MAX-ACCESS  not-accessible
   STATUS      current
   DESCRIPTION
       ""
   INDEX    { gs2310pCommunityConfIndex  }
   ::= { gs2310pGetCommunityConfTable 1 }

GS2310PGetCommunityConfEntry ::= SEQUENCE {
   gs2310pCommunityConfIndex				Integer32,
   gs2310pCommunityConfGetCommunity			DisplayString
}

gs2310pCommunityConfIndex OBJECT-TYPE
   SYNTAX      Integer32(1..4095)
   MAX-ACCESS  not-accessible
   STATUS      current
   DESCRIPTION
       " index, range : 1 - 5. "
   ::= { gs2310pGetCommunityConfEntry 1 }

gs2310pCommunityConfGetCommunity OBJECT-TYPE
   SYNTAX      DisplayString
   MAX-ACCESS  read-write
   STATUS      current
   DESCRIPTION
       " Get/Set the get-community of the SNMP."
   ::= { gs2310pGetCommunityConfEntry 2 }

gs2310pTrapHostConfTable OBJECT-TYPE
   SYNTAX      SEQUENCE OF GS2310PTrapHostConfEntry
   MAX-ACCESS  not-accessible
   STATUS      current
   DESCRIPTION
       "A list of trap host entry. The numbers of entries are given by the value of gs2310pTrapHostConfNumber."
   ::= { gs2310pSnmpConf 6 }

gs2310pTrapHostConfEntry OBJECT-TYPE
   SYNTAX      GS2310PTrapHostConfEntry
   MAX-ACCESS  not-accessible
   STATUS      current
   DESCRIPTION
       "This is the entry information for trap host."
   INDEX    { gs2310pTrapHostConfIndex  }
   ::= { gs2310pTrapHostConfTable 1 }

GS2310PTrapHostConfEntry ::= SEQUENCE {
    gs2310pTrapHostConfIndex             Integer32,
    gs2310pTrapHostConfVersion           INTEGER,
    gs2310pTrapHostConfIPType            INTEGER,
    gs2310pTrapHostConfIP                DisplayString,
    gs2310pTrapHostConfPort              Integer32,
    gs2310pTrapHostConfCommunity         DisplayString,
    gs2310pTrapHostConfSeverityLevel     INTEGER,
    gs2310pTrapHostConfSecurityLevel     INTEGER,
    gs2310pTrapHostConfAuthPtc           INTEGER,
    gs2310pTrapHostConfAuthPassword      DisplayString,
    gs2310pTrapHostConfPrivPtc           INTEGER,
    gs2310pTrapHostConfPrivPassword      DisplayString,
    gs2310pTrapHostConfCurrentMode       INTEGER
}

gs2310pTrapHostConfIndex OBJECT-TYPE
   SYNTAX      Integer32(1..6)
   MAX-ACCESS  not-accessible
   STATUS      current
   DESCRIPTION
       " The index of the trap host entry. "
   ::= { gs2310pTrapHostConfEntry 1 }

gs2310pTrapHostConfVersion OBJECT-TYPE
   SYNTAX       INTEGER { snmpv2c(2), snmpv3(3) }
   MAX-ACCESS   read-write
   STATUS       current
   DESCRIPTION
       "The version of the Trap PDU. Version : 2(SNMPv2c), 3(SNMPv3)"
   ::= { gs2310pTrapHostConfEntry 2 }

gs2310pTrapHostConfIPType OBJECT-TYPE
   SYNTAX       INTEGER { ipv4(4), ipv6(6) }
   MAX-ACCESS   read-write
   STATUS       current
   DESCRIPTION
       "Server IP Type. Default: 4,
        4 : IPv4,
        6 : IPv6."
   ::= { gs2310pTrapHostConfEntry 3 }

gs2310pTrapHostConfIP OBJECT-TYPE
   SYNTAX       DisplayString
   MAX-ACCESS   read-write
   STATUS       current
   DESCRIPTION
       "This is the IP of the trap host."
   ::= { gs2310pTrapHostConfEntry 4 }

gs2310pTrapHostConfPort OBJECT-TYPE
   SYNTAX       Integer32(1..65535)
   MAX-ACCESS   read-write
   STATUS       current
   DESCRIPTION
       "This is the receiving-port number of the trap host.
        range : 1 - 65535."
   ::= { gs2310pTrapHostConfEntry 5 }

gs2310pTrapHostConfCommunity OBJECT-TYPE
   SYNTAX       DisplayString (SIZE (1..32))
   MAX-ACCESS   read-write
   STATUS       current
   DESCRIPTION
       "The community/security name for the trap PDU."
   ::= { gs2310pTrapHostConfEntry 6 }

gs2310pTrapHostConfSeverityLevel	OBJECT-TYPE
   SYNTAX      INTEGER {
                    emergency(0),
                    alert(1),
                    critical(2),
                    error(3),
                    warning(4),
                    notice(5),
                    info(6),
                    debug(7)
                }
   MAX-ACCESS   read-write
   STATUS       current
   DESCRIPTION
       "The Severity Level.
        0 : Emerg, 1 : Alert, 2 : Critical, 3 : Error, 4 : Warning, 5 : Notice, 6 : Info, 7 : Debug."
	::= { gs2310pTrapHostConfEntry 7 }

gs2310pTrapHostConfSecurityLevel	OBJECT-TYPE
   SYNTAX       INTEGER { noAuthNoPriv(1), authNoPriv(2), authPriv(3) }
   MAX-ACCESS   read-write
   STATUS       current
   DESCRIPTION
       "The Security Level, NoAuthNoPriv, AuthNoPriv, and AuthPriv.
        1 : NoAuthNoPriv, 2 : AuthNoPriv, 3 : AuthPriv.
        Privacy protocol will be configured as 'DES' automatically if security level is 3(AuthPriv)."
	::= { gs2310pTrapHostConfEntry 8 }

gs2310pTrapHostConfAuthPtc	OBJECT-TYPE
   SYNTAX       INTEGER { md5(1), sha(2) }
   MAX-ACCESS   read-write
   STATUS       current
   DESCRIPTION
       "Authentication Protocol, there are SHA and MD5 supported presently.
        1 : MD5, 2 : SHA."
	::= { gs2310pTrapHostConfEntry 9 }

gs2310pTrapHostConfAuthPassword	OBJECT-TYPE
   SYNTAX      DisplayString
   MAX-ACCESS  read-write
   STATUS		current
   DESCRIPTION
       "Authentication Password, is used for authenticating. The return value is always '********'.
        If the authentication protocol is MD5, the length of password should be 8 ~ 32 characters.
        If the authentication protocol is SHA, the length of password should be 8 ~ 40 characters."
   ::= { gs2310pTrapHostConfEntry 10 }

gs2310pTrapHostConfPrivPtc	OBJECT-TYPE
   SYNTAX       INTEGER { des(1) }
   MAX-ACCESS   read-write
   STATUS       current
   DESCRIPTION
       "This is the Privacy Protocol, which is used in AuthPriv. Only supports DES.
        An empty string will be returned if the security level is not 3(AuthPriv).
        1 : DES."
	::= { gs2310pTrapHostConfEntry 11 }

gs2310pTrapHostConfPrivPassword	OBJECT-TYPE
   SYNTAX       DisplayString
   MAX-ACCESS   read-write
   STATUS       current
   DESCRIPTION
       "The password is Privacy Key.  The return value is always '********'.  This Key
        must be more than 8 characters, and less than 32 characters."
   ::= { gs2310pTrapHostConfEntry 12 }

gs2310pTrapHostConfCurrentMode OBJECT-TYPE
   SYNTAX       INTEGER { empty(0), active(1), edit(2), delete(3) }
   MAX-ACCESS   read-write
   STATUS       current
   DESCRIPTION
       "0:Empty, 1:Active mode, 2:Edit mode, 3:Delete."
   ::= { gs2310pTrapHostConfEntry 13 }


gs2310pSnmpSystem                                          OBJECT IDENTIFIER ::= { gs2310pSnmp 2 }

gs2310pSnmpState OBJECT-TYPE
   SYNTAX       INTEGER { disable(0), enable(1) }
   MAX-ACCESS   read-write
   STATUS       current
   DESCRIPTION
       "Get/Set the state of the SNMP.
        default : 1, 0: disable, 1: enable. "
   ::= { gs2310pSnmpSystem 1 }

gs2310pSnmpEngineID OBJECT-TYPE
   SYNTAX       OCTET STRING (SIZE(5..32))
   MAX-ACCESS   read-write
   STATUS       current
   DESCRIPTION
       "Get/Set the Engine ID of the SNMP.
        An SNMP engine's administratively-unique identifier."
   ::= { gs2310pSnmpSystem 2 }

gs2310pSnmpCommunities                                          OBJECT IDENTIFIER ::= { gs2310pSnmp 3 }

gs2310pSnmpCommunitiesCreate OBJECT-TYPE
   SYNTAX       INTEGER { none(0), create(1) }
   MAX-ACCESS   read-write
   STATUS       current
   DESCRIPTION
       "default: 0
        0 : None  (read only)
        1 : Create entry"
   ::= { gs2310pSnmpCommunities 1 }

gs2310pSnmpCommunitiesTable OBJECT-TYPE
   SYNTAX      SEQUENCE OF GS2310PSnmpCommunitiesEntry
   MAX-ACCESS  not-accessible
   STATUS      current
   DESCRIPTION
       " Create SNMPv1/v2 Communities entry."
   ::= { gs2310pSnmpCommunities 2 }

gs2310pSnmpCommunitiesEntry OBJECT-TYPE
   SYNTAX      GS2310PSnmpCommunitiesEntry
   MAX-ACCESS  not-accessible
   STATUS      current
   DESCRIPTION
       ""
   INDEX    { gs2310pSnmpCommunitiesIndex  }
   ::= { gs2310pSnmpCommunitiesTable 1 }

GS2310PSnmpCommunitiesEntry ::= SEQUENCE {
   gs2310pSnmpCommunitiesIndex          Integer32,
   gs2310pSnmpCommunitiesCommunity      DisplayString,
   gs2310pSnmpCommunitiesUserName       DisplayString,
   gs2310pSnmpCommunitiesSourceIP       IpAddress,
   gs2310pSnmpCommunitiesSourceMask     IpAddress,
   gs2310pSnmpCommunitiesRowStatus      INTEGER
}

gs2310pSnmpCommunitiesIndex OBJECT-TYPE
   SYNTAX      Integer32(1..4)
   MAX-ACCESS  not-accessible
   STATUS      current
   DESCRIPTION
       " "
   ::= { gs2310pSnmpCommunitiesEntry 1 }

gs2310pSnmpCommunitiesCommunity OBJECT-TYPE
   SYNTAX      DisplayString (SIZE (1..32))
   MAX-ACCESS  read-write
   STATUS      current
   DESCRIPTION
       "Up to 32 characters describing Community."
   ::= { gs2310pSnmpCommunitiesEntry 2 }

gs2310pSnmpCommunitiesUserName OBJECT-TYPE
   SYNTAX      DisplayString (SIZE (1..32))
   MAX-ACCESS  read-write
   STATUS      current
   DESCRIPTION
       " Up to 32 characters describing User Name. "
   ::= { gs2310pSnmpCommunitiesEntry 3 }

gs2310pSnmpCommunitiesSourceIP OBJECT-TYPE
   SYNTAX      IpAddress
   MAX-ACCESS  read-write
   STATUS      current
   DESCRIPTION
       " SNMP access source ip. "
   ::= { gs2310pSnmpCommunitiesEntry 4 }

gs2310pSnmpCommunitiesSourceMask OBJECT-TYPE
   SYNTAX      IpAddress
   MAX-ACCESS  read-write
   STATUS      current
   DESCRIPTION
       " SNMP access source address mask. "
   ::= { gs2310pSnmpCommunitiesEntry 5 }

gs2310pSnmpCommunitiesRowStatus OBJECT-TYPE
   SYNTAX      INTEGER { active(1), notInservice(2), destroy(4), undo(5) }
   MAX-ACCESS  read-write
   STATUS      current
   DESCRIPTION
       "1: active
        2: notInservice
        4: destroy
        5: undo"
   ::= { gs2310pSnmpCommunitiesEntry 6 }


gs2310pSnmpUsers                                          OBJECT IDENTIFIER ::= { gs2310pSnmp 4 }

gs2310pSnmpUsersCreate OBJECT-TYPE
   SYNTAX       INTEGER { none(0), create(1) }
   MAX-ACCESS   read-write
   STATUS       current
   DESCRIPTION
       "default: 0
        0 : None  (read only)
        1 : Create entry"
   ::= { gs2310pSnmpUsers 1 }

gs2310pSnmpUsersTable OBJECT-TYPE
   SYNTAX      SEQUENCE OF GS2310PSnmpUsersEntry
   MAX-ACCESS  not-accessible
   STATUS      current
   DESCRIPTION
       " Create SNMPv3 users entry."
   ::= { gs2310pSnmpUsers 2 }

gs2310pSnmpUsersEntry OBJECT-TYPE
   SYNTAX      GS2310PSnmpUsersEntry
   MAX-ACCESS  not-accessible
   STATUS      current
   DESCRIPTION
       ""
   INDEX    { gs2310pSnmpUsersIndex  }
   ::= { gs2310pSnmpUsersTable 1 }

GS2310PSnmpUsersEntry ::= SEQUENCE {
   gs2310pSnmpUsersIndex                    Integer32,
   gs2310pSnmpUsersUserName                 DisplayString,
   gs2310pSnmpUsersSecurityLevel            INTEGER,
   gs2310pSnmpUsersAuthenticationProtocol   INTEGER,
   gs2310pSnmpUsersAuthenticationPassword   DisplayString,
   gs2310pSnmpUsersPrivacyProtocol          INTEGER,
   gs2310pSnmpUsersPrivacyPassword          DisplayString,
   gs2310pSnmpUsersRowStatus                INTEGER
}

gs2310pSnmpUsersIndex OBJECT-TYPE
   SYNTAX      Integer32(1..10)
   MAX-ACCESS  not-accessible
   STATUS      current
   DESCRIPTION
       " "
   ::= { gs2310pSnmpUsersEntry 1 }

gs2310pSnmpUsersUserName OBJECT-TYPE
   SYNTAX      DisplayString (SIZE (1..32))
   MAX-ACCESS  read-write
   STATUS      current
   DESCRIPTION
       "Up to 32 characters describing User Name."
   ::= { gs2310pSnmpUsersEntry 2 }

gs2310pSnmpUsersSecurityLevel OBJECT-TYPE
   SYNTAX      INTEGER { noauthnopriv(1), authnopriv(2), authpriv(3) }
   MAX-ACCESS  read-write
   STATUS      current
   DESCRIPTION
       " 1: No authentication and no privacy.
         2: Authentication and no privacy.
         3: Authentication and privacy. "
   ::= { gs2310pSnmpUsersEntry 3 }

gs2310pSnmpUsersAuthenticationProtocol OBJECT-TYPE
   SYNTAX      INTEGER { none(0), md5(1), sha(2) }
   MAX-ACCESS  read-write
   STATUS      current
   DESCRIPTION
       " 0: None.
         1: MD5.
         2: SHA "
   ::= { gs2310pSnmpUsersEntry 4 }

gs2310pSnmpUsersAuthenticationPassword OBJECT-TYPE
   SYNTAX      DisplayString
   MAX-ACCESS  read-write
   STATUS      current
   DESCRIPTION
       " Authentication Password, is used for authenticating. The return value is always '********'.
         If the authentication protocol is MD5, the length of password should be 8 ~ 32 characters.
         If the authentication protocol is SHA, the length of password should be 8 ~ 40 characters. "
   ::= { gs2310pSnmpUsersEntry 5 }

gs2310pSnmpUsersPrivacyProtocol OBJECT-TYPE
   SYNTAX      INTEGER { none(0), des(1), aes(2) }
   MAX-ACCESS  read-write
   STATUS      current
   DESCRIPTION
       " 0: None.
         1: DES.
         2: AES
         This is the Privacy Protocol, which is used in AuthPriv.
         An empty string will be returned if the security level is not 3(AuthPriv) "
   ::= { gs2310pSnmpUsersEntry 6 }

gs2310pSnmpUsersPrivacyPassword OBJECT-TYPE
   SYNTAX      DisplayString
   MAX-ACCESS  read-write
   STATUS      current
   DESCRIPTION
       " The password is Privacy Key.  The return value is always '********'.  This Key
        must be more than 8 characters, and less than 32 characters. "
   ::= { gs2310pSnmpUsersEntry 7 }

gs2310pSnmpUsersRowStatus OBJECT-TYPE
   SYNTAX      INTEGER { active(1), notInservice(2), destroy(4), undo(5) }
   MAX-ACCESS  read-write
   STATUS      current
   DESCRIPTION
       "1: active
        2: notInservice
        4: destroy
        5: undo"
   ::= { gs2310pSnmpUsersEntry 8 }


gs2310pSnmpGroups                                          OBJECT IDENTIFIER ::= { gs2310pSnmp 5 }

gs2310pSnmpGroupsCreate OBJECT-TYPE
   SYNTAX       INTEGER { none(0), create(1) }
   MAX-ACCESS   read-write
   STATUS       current
   DESCRIPTION
       "default: 0
        0 : None  (read only)
        1 : Create entry"
   ::= { gs2310pSnmpGroups 1 }

gs2310pSnmpGroupsTable OBJECT-TYPE
   SYNTAX      SEQUENCE OF GS2310PSnmpGroupsEntry
   MAX-ACCESS  not-accessible
   STATUS      current
   DESCRIPTION
       " Create SNMPv3 groups entry."
   ::= { gs2310pSnmpGroups 2 }

gs2310pSnmpGroupsEntry OBJECT-TYPE
   SYNTAX      GS2310PSnmpGroupsEntry
   MAX-ACCESS  not-accessible
   STATUS      current
   DESCRIPTION
       ""
   INDEX    { gs2310pSnmpGroupsIndex  }
   ::= { gs2310pSnmpGroupsTable 1 }

GS2310PSnmpGroupsEntry ::= SEQUENCE {
   gs2310pSnmpGroupsIndex           Integer32,
   gs2310pSnmpGroupsSecurityModel   INTEGER,
   gs2310pSnmpGroupsSecurityName    DisplayString,
   gs2310pSnmpGroupsGroupName       DisplayString,
   gs2310pSnmpGroupsRowStatus       INTEGER
}

gs2310pSnmpGroupsIndex OBJECT-TYPE
   SYNTAX      Integer32(1..14)
   MAX-ACCESS  not-accessible
   STATUS      current
   DESCRIPTION
       " "
   ::= { gs2310pSnmpGroupsEntry 1 }

gs2310pSnmpGroupsSecurityModel OBJECT-TYPE
   SYNTAX      INTEGER { v1(1), v2c(2), usm(3) }
   MAX-ACCESS  read-write
   STATUS      current
   DESCRIPTION
       " 1: v1.
         2: v2c.
         3: usm."
   ::= { gs2310pSnmpGroupsEntry 2 }

gs2310pSnmpGroupsSecurityName OBJECT-TYPE
   SYNTAX      DisplayString (SIZE (1..32))
   MAX-ACCESS  read-write
   STATUS      current
   DESCRIPTION
       "Up to 32 characters describing User Name."
   ::= { gs2310pSnmpGroupsEntry 3 }

gs2310pSnmpGroupsGroupName OBJECT-TYPE
   SYNTAX      DisplayString (SIZE (1..32))
   MAX-ACCESS  read-write
   STATUS      current
   DESCRIPTION
       "Up to 32 characters describing Group Name."
   ::= { gs2310pSnmpGroupsEntry 4 }

gs2310pSnmpGroupsRowStatus OBJECT-TYPE
   SYNTAX      INTEGER { active(1), notInservice(2), destroy(4), undo(5) }
   MAX-ACCESS  read-write
   STATUS      current
   DESCRIPTION
       "1: active
        2: notInservice
        4: destroy
        5: undo"
   ::= { gs2310pSnmpGroupsEntry 5 }

gs2310pSnmpViews                                              OBJECT IDENTIFIER ::= { gs2310pSnmp 6 }

gs2310pSnmpViewsCreate OBJECT-TYPE
   SYNTAX       INTEGER { none(0), create(1) }
   MAX-ACCESS   read-write
   STATUS       current
   DESCRIPTION
       "default: 0
        0 : None  (read only)
        1 : Create entry"
   ::= { gs2310pSnmpViews 1 }

gs2310pSnmpViewsTable OBJECT-TYPE
   SYNTAX      SEQUENCE OF GS2310PSnmpViewsEntry
   MAX-ACCESS  not-accessible
   STATUS      current
   DESCRIPTION
       " Create SNMPv1/v2 Views entry."
   ::= { gs2310pSnmpViews 2 }

gs2310pSnmpViewsEntry OBJECT-TYPE
   SYNTAX      GS2310PSnmpViewsEntry
   MAX-ACCESS  not-accessible
   STATUS      current
   DESCRIPTION
       ""
   INDEX    { gs2310pSnmpViewsIndex  }
   ::= { gs2310pSnmpViewsTable 1 }

GS2310PSnmpViewsEntry ::= SEQUENCE {
   gs2310pSnmpViewsIndex        Integer32,
   gs2310pSnmpViewsName         DisplayString,
   gs2310pSnmpViewsType         INTEGER,
   gs2310pSnmpViewsOIDSubtree   DisplayString,
   gs2310pSnmpViewsRowStatus    INTEGER
}

gs2310pSnmpViewsIndex OBJECT-TYPE
   SYNTAX      Integer32(1..4)
   MAX-ACCESS  not-accessible
   STATUS      current
   DESCRIPTION
       " "
   ::= { gs2310pSnmpViewsEntry 1 }

gs2310pSnmpViewsName OBJECT-TYPE
   SYNTAX      DisplayString (SIZE (1..32))
   MAX-ACCESS  read-write
   STATUS      current
   DESCRIPTION
       "Up to 32 characters describing view Name."
   ::= { gs2310pSnmpViewsEntry 2 }

gs2310pSnmpViewsType OBJECT-TYPE
   SYNTAX      INTEGER { included(1), excluded(2) }
   MAX-ACCESS  read-write
   STATUS      current
   DESCRIPTION
       "1: included, An optional flag to indicate that this view subtree should be included.
	   2: excluded, An optional flag to indicate that this view subtree should be excluded."
   ::= { gs2310pSnmpViewsEntry 3 }

gs2310pSnmpViewsOIDSubtree OBJECT-TYPE
   SYNTAX      DisplayString (SIZE (1..128))
   MAX-ACCESS  read-write
   STATUS      current
   DESCRIPTION
       "The OID defining the root of the subtree to add to the named view."
   ::= { gs2310pSnmpViewsEntry 4 }

gs2310pSnmpViewsRowStatus OBJECT-TYPE
   SYNTAX      INTEGER { active(1), notInservice(2), destroy(4), undo(5) }
   MAX-ACCESS  read-write
   STATUS      current
   DESCRIPTION
       "1: active
        2: notInservice
        4: destroy
        5: undo"
   ::= { gs2310pSnmpViewsEntry 5 }


gs2310pSnmpAccess                                          OBJECT IDENTIFIER ::= { gs2310pSnmp 7 }

gs2310pSnmpAccessCreate OBJECT-TYPE
   SYNTAX       INTEGER { none(0), create(1) }
   MAX-ACCESS   read-write
   STATUS       current
   DESCRIPTION
       "default: 0
        0 : None  (read only)
        1 : Create entry"
   ::= { gs2310pSnmpAccess 1 }

gs2310pSnmpAccessTable OBJECT-TYPE
   SYNTAX      SEQUENCE OF GS2310PSnmpAccessEntry
   MAX-ACCESS  not-accessible
   STATUS      current
   DESCRIPTION
       " Create SNMPv3 Access entry."
   ::= { gs2310pSnmpAccess 2 }

gs2310pSnmpAccessEntry OBJECT-TYPE
   SYNTAX      GS2310PSnmpAccessEntry
   MAX-ACCESS  not-accessible
   STATUS      current
   DESCRIPTION
       ""
   INDEX    { gs2310pSnmpAccessIndex  }
   ::= { gs2310pSnmpAccessTable 1 }

GS2310PSnmpAccessEntry ::= SEQUENCE {
   gs2310pSnmpAccessIndex             Integer32,
   gs2310pSnmpAccessGroupName         DisplayString,
   gs2310pSnmpAccessSecurityModel     INTEGER,
   gs2310pSnmpAccessSecurityLevel     INTEGER,
   gs2310pSnmpAccessReadViewName      DisplayString,
   gs2310pSnmpAccessWriteViewName     DisplayString,
   gs2310pSnmpAccessRowStatus         INTEGER
}

gs2310pSnmpAccessIndex OBJECT-TYPE
   SYNTAX      Integer32(1..14)
   MAX-ACCESS  not-accessible
   STATUS      current
   DESCRIPTION
       " "
   ::= { gs2310pSnmpAccessEntry 1 }

gs2310pSnmpAccessGroupName OBJECT-TYPE
   SYNTAX      DisplayString (SIZE (1..32))
   MAX-ACCESS  read-write
   STATUS      current
   DESCRIPTION
       "Up to 32 characters describing Group Name."
   ::= { gs2310pSnmpAccessEntry 2 }

gs2310pSnmpAccessSecurityModel OBJECT-TYPE
   SYNTAX      INTEGER { any(0), v1(1), v2c(2), usm(3) }
   MAX-ACCESS  read-write
   STATUS      current
   DESCRIPTION
       " 0: any.
         1: v1.
         2: v2c.
         3: usm."
   ::= { gs2310pSnmpAccessEntry 3 }

gs2310pSnmpAccessSecurityLevel OBJECT-TYPE
   SYNTAX      INTEGER { noauthnopriv(1), authnopriv(2), authpriv(3) }
   MAX-ACCESS  read-write
   STATUS      current
   DESCRIPTION
       " 1: No authentication and no privacy.
         2: Authentication and no privacy.
         3: Authentication and privacy. "
   ::= { gs2310pSnmpAccessEntry 4 }

gs2310pSnmpAccessReadViewName OBJECT-TYPE
   SYNTAX      DisplayString (SIZE (1..32))
   MAX-ACCESS  read-write
   STATUS      current
   DESCRIPTION
       "Up to 32 characters describing Read View Name.
        None is reserved for Empty."
   ::= { gs2310pSnmpAccessEntry 5 }

gs2310pSnmpAccessWriteViewName OBJECT-TYPE
   SYNTAX      DisplayString (SIZE (1..32))
   MAX-ACCESS  read-write
   STATUS      current
   DESCRIPTION
       "Up to 32 characters describing Write View Name.
        None is reserved for Empty."
   ::= { gs2310pSnmpAccessEntry 6 }

gs2310pSnmpAccessRowStatus OBJECT-TYPE
   SYNTAX      INTEGER { active(1), notInservice(2), destroy(4), undo(5) }
   MAX-ACCESS  read-write
   STATUS      current
   DESCRIPTION
       "1: active
        2: notInservice
        4: destroy
        5: undo"
   ::= { gs2310pSnmpAccessEntry 7 }


----------------------------------------------------------------------------------------------------

gs2310pConfiguration                                         OBJECT IDENTIFIER ::= { lancomGS2310P 2 }

gs2310pPort                                                  OBJECT IDENTIFIER ::= { gs2310pConfiguration 1 }

gs2310pPortConfigurationTable OBJECT-TYPE
   SYNTAX      SEQUENCE OF Gs2310pPortConfigurationEntry
   MAX-ACCESS  not-accessible
   STATUS      current
   DESCRIPTION
       " Show port configurations. "
   ::= { gs2310pPort 1 }

gs2310pPortConfigurationEntry OBJECT-TYPE
   SYNTAX      Gs2310pPortConfigurationEntry
   MAX-ACCESS  not-accessible
   STATUS      current
   DESCRIPTION
       ""
   INDEX    { gs2310pPortConfPort  }
   ::= { gs2310pPortConfigurationTable 1 }

Gs2310pPortConfigurationEntry ::= SEQUENCE {
   gs2310pPortConfPort                     Integer32,
   gs2310pPortConfPortMedia                DisplayString,
   gs2310pPortConfLink                     DisplayString,
   gs2310pPortConfCurrentSpeed             DisplayString,
   gs2310pPortConfSpeed                    INTEGER,
   gs2310pPortConfCurrentFlowControlRx     INTEGER,
   gs2310pPortConfCurrentFlowControlTx     INTEGER,
   gs2310pPortConfFlowControl              INTEGER,
   gs2310pPortConfMaxFrameSize             Integer32,
   gs2310pPortConfExcessiveCollisionMode   INTEGER,
   gs2310pPortConfPowerControl             INTEGER,
   gs2310pPortConfDescription              DisplayString
}

gs2310pPortConfPort OBJECT-TYPE
   SYNTAX      Integer32(1..4095)
   MAX-ACCESS  not-accessible
   STATUS      current
   DESCRIPTION
       " port, range : 1 - port number. "
   ::= { gs2310pPortConfigurationEntry 1 }

gs2310pPortConfPortMedia OBJECT-TYPE
   SYNTAX      DisplayString(SIZE (1..4))
   MAX-ACCESS  read-only
   STATUS      current
   DESCRIPTION
       " Show port media. "
   ::= { gs2310pPortConfigurationEntry 2 }

gs2310pPortConfLink OBJECT-TYPE
   SYNTAX      DisplayString(SIZE (2..4))
   MAX-ACCESS  read-only
   STATUS      current
   DESCRIPTION
       " The current link state. "
   ::= { gs2310pPortConfigurationEntry 3 }

gs2310pPortConfCurrentSpeed OBJECT-TYPE
   SYNTAX      DisplayString(SIZE (6..12))
   MAX-ACCESS  read-only
   STATUS      current
   DESCRIPTION
       " The current link speed of the port. "
   ::= { gs2310pPortConfigurationEntry 4 }

gs2310pPortConfSpeed OBJECT-TYPE
   SYNTAX      INTEGER {
                    disable(0),
                    auto(1),
                    speed10Half(2),
                    speed10Full(3),
                    speed100Half(4),
                    speed100Full(5),
                    speed1Gfull(6),
                    sfpAutoAMS(7),
                    speed100FXAMS(8),
                    speed1000XAMS(9),
                    speed100FX(10),
                    speed1000X(11)
                }
   MAX-ACCESS  read-write
   STATUS      current
   DESCRIPTION
       "default: 1,
        0: disable state,
        1: auto,
        2: 10 Half,
        3: 10 Full,
        4: 100 Half,
        5: 100 Full,
        6: 1G full,
        only 'Dual Media' port have 7-11 option.
        Dual Media port default: 7,
        7: SFP_Auto_AMS,
        8: 100FX_AMS,
        9: 1000X_AMS,
        10: 100FX,
        11: 1000X "
   ::= { gs2310pPortConfigurationEntry 5 }

gs2310pPortConfCurrentFlowControlRx OBJECT-TYPE
   SYNTAX      INTEGER { disable(0), enable(1), noSupport(2) }
   MAX-ACCESS  read-only
   STATUS      current
   DESCRIPTION
       "0: disable
        1: enable
        2: no support.  "
   ::= { gs2310pPortConfigurationEntry 6 }

gs2310pPortConfCurrentFlowControlTx OBJECT-TYPE
   SYNTAX      INTEGER { disable(0), enable(1), noSupport(2) }
   MAX-ACCESS  read-only
   STATUS      current
   DESCRIPTION
       "0: disable
        1: enable
        2: no support.  "
   ::= { gs2310pPortConfigurationEntry 7 }

gs2310pPortConfFlowControl OBJECT-TYPE
   SYNTAX      INTEGER { disable(0), enable(1), noSupport(2) }
   MAX-ACCESS  read-write
   STATUS      current
   DESCRIPTION
       "default: 0,
        0: disable
        1: enable
        2: no support. "
   ::= { gs2310pPortConfigurationEntry 8 }

gs2310pPortConfMaxFrameSize OBJECT-TYPE
   SYNTAX      Integer32 (1518..9600)
   MAX-ACCESS  read-write
   STATUS      current
   DESCRIPTION
       "default: 9600 , range : 1518 - 9600 "
   ::= { gs2310pPortConfigurationEntry 9 }

gs2310pPortConfExcessiveCollisionMode OBJECT-TYPE
   SYNTAX      INTEGER { discard(0), restart(1), noSupport(2) }
   MAX-ACCESS  read-write
   STATUS      current
   DESCRIPTION
       "default: 0,
        Excessive Collision Mode :
        0: Discard,
        1: Restart,
        2: no support.
       "
   ::= { gs2310pPortConfigurationEntry 10 }

gs2310pPortConfPowerControl OBJECT-TYPE
   SYNTAX      INTEGER { disable(0), actiphy(1), dynamic(2), enable(3), noSupport(4) }
   MAX-ACCESS  read-write
   STATUS      current
   DESCRIPTION
       "default: 0,
        PowerControl :
        0: disable,
        1: Actiphy,
        2: Dynamic (perfectReach),
        3: Enable,
        4: no support.
       "
   ::= { gs2310pPortConfigurationEntry 11 }

gs2310pPortConfDescription OBJECT-TYPE
   SYNTAX      DisplayString
   MAX-ACCESS  read-write
   STATUS      current
   DESCRIPTION
       " Interface specific description.
         Up to 47 characters describing this interface. "
   ::= { gs2310pPortConfigurationEntry 12 }


gs2310pPortTrafficStatisticsTable OBJECT-TYPE
   SYNTAX      SEQUENCE OF Gs2310pPortTrafficStatisticsEntry
   MAX-ACCESS  not-accessible
   STATUS      current
   DESCRIPTION
       " "
   ::= { gs2310pPort 2 }

gs2310pPortTrafficStatisticsEntry OBJECT-TYPE
   SYNTAX      Gs2310pPortTrafficStatisticsEntry
   MAX-ACCESS  not-accessible
   STATUS      current
   DESCRIPTION
       ""
   INDEX    { gs2310pPortTrafficStatisticsPort  }
   ::= { gs2310pPortTrafficStatisticsTable 1 }

Gs2310pPortTrafficStatisticsEntry ::= SEQUENCE {
   gs2310pPortTrafficStatisticsPort          Integer32,
   gs2310pPortTrafficStatisticsClear         INTEGER,
   gs2310pPortTrafficRxPackets               Counter64,
   gs2310pPortTrafficRxOctets                Counter64,
   gs2310pPortTrafficRxUnicast               Counter64,
   gs2310pPortTrafficRxMulticast             Counter64,
   gs2310pPortTrafficRxBroadcast             Counter64,
   gs2310pPortTrafficRxPause                 Counter64,
   gs2310pPortTrafficRx64Bytes               Counter64,
   gs2310pPortTrafficRx65to127Bytes          Counter64,
   gs2310pPortTrafficRx128to255Bytes         Counter64,
   gs2310pPortTrafficRx256to511Bytes         Counter64,
   gs2310pPortTrafficRx512to1023Bytes        Counter64,
   gs2310pPortTrafficRx1024to1526Bytes       Counter64,
   gs2310pPortTrafficRxExceecd1527Bytes      Counter64,
   gs2310pPortTrafficRxQ0                    Counter64,
   gs2310pPortTrafficRxQ1                    Counter64,
   gs2310pPortTrafficRxQ2                    Counter64,
   gs2310pPortTrafficRxQ3                    Counter64,
   gs2310pPortTrafficRxQ4                    Counter64,
   gs2310pPortTrafficRxQ5                    Counter64,
   gs2310pPortTrafficRxQ6                    Counter64,
   gs2310pPortTrafficRxQ7                    Counter64,
   gs2310pPortTrafficRxDrops                 Counter64,
   gs2310pPortTrafficRxCRCorAlignment        Counter64,
   gs2310pPortTrafficRxUndersize             Counter64,
   gs2310pPortTrafficRxOversize              Counter64,
   gs2310pPortTrafficRxFragments             Counter64,
   gs2310pPortTrafficRxJabber                Counter64,
   gs2310pPortTrafficRxFiltered              Counter64,
   gs2310pPortTrafficTxPackets               Counter64,
   gs2310pPortTrafficTxOctets                Counter64,
   gs2310pPortTrafficTxUnicast               Counter64,
   gs2310pPortTrafficTxMulticast             Counter64,
   gs2310pPortTrafficTxBroadcast             Counter64,
   gs2310pPortTrafficTxPause                 Counter64,
   gs2310pPortTrafficTx64Bytes               Counter64,
   gs2310pPortTrafficTx65to127Bytes          Counter64,
   gs2310pPortTrafficTx128to255Bytes         Counter64,
   gs2310pPortTrafficTx256to511Bytes         Counter64,
   gs2310pPortTrafficTx512to1023Bytes        Counter64,
   gs2310pPortTrafficTx1024to1526Bytes       Counter64,
   gs2310pPortTrafficTxExceecd1527Bytes      Counter64,
   gs2310pPortTrafficTxQ0                    Counter64,
   gs2310pPortTrafficTxQ1                    Counter64,
   gs2310pPortTrafficTxQ2                    Counter64,
   gs2310pPortTrafficTxQ3                    Counter64,
   gs2310pPortTrafficTxQ4                    Counter64,
   gs2310pPortTrafficTxQ5                    Counter64,
   gs2310pPortTrafficTxQ6                    Counter64,
   gs2310pPortTrafficTxQ7                    Counter64,
   gs2310pPortTrafficTxDrops                 Counter64,
   gs2310pPortTrafficTxLateOrExcColl         Counter64
}

gs2310pPortTrafficStatisticsPort OBJECT-TYPE
   SYNTAX      Integer32 (1..4095)
   MAX-ACCESS  not-accessible
   STATUS      current
   DESCRIPTION
       " "
   ::= { gs2310pPortTrafficStatisticsEntry 1 }

gs2310pPortTrafficStatisticsClear OBJECT-TYPE
   SYNTAX      INTEGER { disable(0), enable(1) }
   MAX-ACCESS  read-write
   STATUS      current
   DESCRIPTION
       " "
   ::= { gs2310pPortTrafficStatisticsEntry 2 }

gs2310pPortTrafficRxPackets OBJECT-TYPE
   SYNTAX      Counter64
   MAX-ACCESS  read-only
   STATUS      current
   DESCRIPTION
       " "
   ::= { gs2310pPortTrafficStatisticsEntry 3 }

gs2310pPortTrafficRxOctets OBJECT-TYPE
   SYNTAX      Counter64
   MAX-ACCESS  read-only
   STATUS      current
   DESCRIPTION
       " "
   ::= { gs2310pPortTrafficStatisticsEntry 4 }

gs2310pPortTrafficRxUnicast OBJECT-TYPE
   SYNTAX      Counter64
   MAX-ACCESS  read-only
   STATUS      current
   DESCRIPTION
       " "
   ::= { gs2310pPortTrafficStatisticsEntry 5 }

gs2310pPortTrafficRxMulticast OBJECT-TYPE
   SYNTAX      Counter64
   MAX-ACCESS  read-only
   STATUS      current
   DESCRIPTION
       " "
   ::= { gs2310pPortTrafficStatisticsEntry 6 }

gs2310pPortTrafficRxBroadcast OBJECT-TYPE
   SYNTAX      Counter64
   MAX-ACCESS  read-only
   STATUS      current
   DESCRIPTION
       " "
   ::= { gs2310pPortTrafficStatisticsEntry 7 }

gs2310pPortTrafficRxPause OBJECT-TYPE
   SYNTAX      Counter64
   MAX-ACCESS  read-only
   STATUS      current
   DESCRIPTION
       " "
   ::= { gs2310pPortTrafficStatisticsEntry 8 }

gs2310pPortTrafficRx64Bytes OBJECT-TYPE
   SYNTAX      Counter64
   MAX-ACCESS  read-only
   STATUS      current
   DESCRIPTION
       " "
   ::= { gs2310pPortTrafficStatisticsEntry 9 }

gs2310pPortTrafficRx65to127Bytes OBJECT-TYPE
   SYNTAX      Counter64
   MAX-ACCESS  read-only
   STATUS      current
   DESCRIPTION
       " "
   ::= { gs2310pPortTrafficStatisticsEntry 10 }

gs2310pPortTrafficRx128to255Bytes OBJECT-TYPE
   SYNTAX      Counter64
   MAX-ACCESS  read-only
   STATUS      current
   DESCRIPTION
       " "
   ::= { gs2310pPortTrafficStatisticsEntry 11 }

gs2310pPortTrafficRx256to511Bytes OBJECT-TYPE
   SYNTAX      Counter64
   MAX-ACCESS  read-only
   STATUS      current
   DESCRIPTION
       " "
   ::= { gs2310pPortTrafficStatisticsEntry 12 }

gs2310pPortTrafficRx512to1023Bytes OBJECT-TYPE
   SYNTAX      Counter64
   MAX-ACCESS  read-only
   STATUS      current
   DESCRIPTION
       " "
   ::= { gs2310pPortTrafficStatisticsEntry 13 }

gs2310pPortTrafficRx1024to1526Bytes OBJECT-TYPE
   SYNTAX      Counter64
   MAX-ACCESS  read-only
   STATUS      current
   DESCRIPTION
       " "
   ::= { gs2310pPortTrafficStatisticsEntry 14 }

gs2310pPortTrafficRxExceecd1527Bytes OBJECT-TYPE
   SYNTAX      Counter64
   MAX-ACCESS  read-only
   STATUS      current
   DESCRIPTION
       " "
   ::= { gs2310pPortTrafficStatisticsEntry 15 }

gs2310pPortTrafficRxQ0 OBJECT-TYPE
   SYNTAX      Counter64
   MAX-ACCESS  read-only
   STATUS      current
   DESCRIPTION
       " "
   ::= { gs2310pPortTrafficStatisticsEntry 16 }

gs2310pPortTrafficRxQ1 OBJECT-TYPE
   SYNTAX      Counter64
   MAX-ACCESS  read-only
   STATUS      current
   DESCRIPTION
       " "
   ::= { gs2310pPortTrafficStatisticsEntry 17 }

gs2310pPortTrafficRxQ2 OBJECT-TYPE
   SYNTAX      Counter64
   MAX-ACCESS  read-only
   STATUS      current
   DESCRIPTION
       " "
   ::= { gs2310pPortTrafficStatisticsEntry 18 }

gs2310pPortTrafficRxQ3 OBJECT-TYPE
   SYNTAX      Counter64
   MAX-ACCESS  read-only
   STATUS      current
   DESCRIPTION
       " "
   ::= { gs2310pPortTrafficStatisticsEntry 19 }

gs2310pPortTrafficRxQ4 OBJECT-TYPE
   SYNTAX      Counter64
   MAX-ACCESS  read-only
   STATUS      current
   DESCRIPTION
       " "
   ::= { gs2310pPortTrafficStatisticsEntry 20 }

gs2310pPortTrafficRxQ5 OBJECT-TYPE
   SYNTAX      Counter64
   MAX-ACCESS  read-only
   STATUS      current
   DESCRIPTION
       " "
   ::= { gs2310pPortTrafficStatisticsEntry 21 }

gs2310pPortTrafficRxQ6 OBJECT-TYPE
   SYNTAX      Counter64
   MAX-ACCESS  read-only
   STATUS      current
   DESCRIPTION
       " "
   ::= { gs2310pPortTrafficStatisticsEntry 22 }

gs2310pPortTrafficRxQ7 OBJECT-TYPE
   SYNTAX      Counter64
   MAX-ACCESS  read-only
   STATUS      current
   DESCRIPTION
       " "
   ::= { gs2310pPortTrafficStatisticsEntry 23 }

gs2310pPortTrafficRxDrops OBJECT-TYPE
   SYNTAX      Counter64
   MAX-ACCESS  read-only
   STATUS      current
   DESCRIPTION
       " "
   ::= { gs2310pPortTrafficStatisticsEntry 24 }

gs2310pPortTrafficRxCRCorAlignment OBJECT-TYPE
   SYNTAX      Counter64
   MAX-ACCESS  read-only
   STATUS      current
   DESCRIPTION
       " "
   ::= { gs2310pPortTrafficStatisticsEntry 25 }

gs2310pPortTrafficRxUndersize OBJECT-TYPE
   SYNTAX      Counter64
   MAX-ACCESS  read-only
   STATUS      current
   DESCRIPTION
       " "
   ::= { gs2310pPortTrafficStatisticsEntry 26 }

gs2310pPortTrafficRxOversize OBJECT-TYPE
   SYNTAX      Counter64
   MAX-ACCESS  read-only
   STATUS      current
   DESCRIPTION
       " "
   ::= { gs2310pPortTrafficStatisticsEntry 27 }

gs2310pPortTrafficRxFragments OBJECT-TYPE
   SYNTAX      Counter64
   MAX-ACCESS  read-only
   STATUS      current
   DESCRIPTION
       " "
   ::= { gs2310pPortTrafficStatisticsEntry 28 }

gs2310pPortTrafficRxJabber OBJECT-TYPE
   SYNTAX      Counter64
   MAX-ACCESS  read-only
   STATUS      current
   DESCRIPTION
       " "
   ::= { gs2310pPortTrafficStatisticsEntry 29 }

gs2310pPortTrafficRxFiltered OBJECT-TYPE
   SYNTAX      Counter64
   MAX-ACCESS  read-only
   STATUS      current
   DESCRIPTION
       " "
   ::= { gs2310pPortTrafficStatisticsEntry 30 }

gs2310pPortTrafficTxPackets OBJECT-TYPE
   SYNTAX      Counter64
   MAX-ACCESS  read-only
   STATUS      current
   DESCRIPTION
       " "
   ::= { gs2310pPortTrafficStatisticsEntry 31 }

gs2310pPortTrafficTxOctets OBJECT-TYPE
   SYNTAX      Counter64
   MAX-ACCESS  read-only
   STATUS      current
   DESCRIPTION
       " "
   ::= { gs2310pPortTrafficStatisticsEntry 32 }

gs2310pPortTrafficTxUnicast OBJECT-TYPE
   SYNTAX      Counter64
   MAX-ACCESS  read-only
   STATUS      current
   DESCRIPTION
       " "
   ::= { gs2310pPortTrafficStatisticsEntry 33 }

gs2310pPortTrafficTxMulticast OBJECT-TYPE
   SYNTAX      Counter64
   MAX-ACCESS  read-only
   STATUS      current
   DESCRIPTION
       " "
   ::= { gs2310pPortTrafficStatisticsEntry 34 }

gs2310pPortTrafficTxBroadcast OBJECT-TYPE
   SYNTAX      Counter64
   MAX-ACCESS  read-only
   STATUS      current
   DESCRIPTION
       " "
   ::= { gs2310pPortTrafficStatisticsEntry 35 }

gs2310pPortTrafficTxPause OBJECT-TYPE
   SYNTAX      Counter64
   MAX-ACCESS  read-only
   STATUS      current
   DESCRIPTION
       " "
   ::= { gs2310pPortTrafficStatisticsEntry 36 }

gs2310pPortTrafficTx64Bytes OBJECT-TYPE
   SYNTAX      Counter64
   MAX-ACCESS  read-only
   STATUS      current
   DESCRIPTION
       " "
   ::= { gs2310pPortTrafficStatisticsEntry 37 }

gs2310pPortTrafficTx65to127Bytes OBJECT-TYPE
   SYNTAX      Counter64
   MAX-ACCESS  read-only
   STATUS      current
   DESCRIPTION
       " "
   ::= { gs2310pPortTrafficStatisticsEntry 38 }

gs2310pPortTrafficTx128to255Bytes OBJECT-TYPE
   SYNTAX      Counter64
   MAX-ACCESS  read-only
   STATUS      current
   DESCRIPTION
       " "
   ::= { gs2310pPortTrafficStatisticsEntry 39 }

gs2310pPortTrafficTx256to511Bytes OBJECT-TYPE
   SYNTAX      Counter64
   MAX-ACCESS  read-only
   STATUS      current
   DESCRIPTION
       " "
   ::= { gs2310pPortTrafficStatisticsEntry 40 }

gs2310pPortTrafficTx512to1023Bytes OBJECT-TYPE
   SYNTAX      Counter64
   MAX-ACCESS  read-only
   STATUS      current
   DESCRIPTION
       " "
   ::= { gs2310pPortTrafficStatisticsEntry 41 }

gs2310pPortTrafficTx1024to1526Bytes OBJECT-TYPE
   SYNTAX      Counter64
   MAX-ACCESS  read-only
   STATUS      current
   DESCRIPTION
       " "
   ::= { gs2310pPortTrafficStatisticsEntry 42 }

gs2310pPortTrafficTxExceecd1527Bytes OBJECT-TYPE
   SYNTAX      Counter64
   MAX-ACCESS  read-only
   STATUS      current
   DESCRIPTION
       " "
   ::= { gs2310pPortTrafficStatisticsEntry 43 }

gs2310pPortTrafficTxQ0 OBJECT-TYPE
   SYNTAX      Counter64
   MAX-ACCESS  read-only
   STATUS      current
   DESCRIPTION
       " "
   ::= { gs2310pPortTrafficStatisticsEntry 44 }

gs2310pPortTrafficTxQ1 OBJECT-TYPE
   SYNTAX      Counter64
   MAX-ACCESS  read-only
   STATUS      current
   DESCRIPTION
       " "
   ::= { gs2310pPortTrafficStatisticsEntry 45 }

gs2310pPortTrafficTxQ2 OBJECT-TYPE
   SYNTAX      Counter64
   MAX-ACCESS  read-only
   STATUS      current
   DESCRIPTION
       " "
   ::= { gs2310pPortTrafficStatisticsEntry 46 }

gs2310pPortTrafficTxQ3 OBJECT-TYPE
   SYNTAX      Counter64
   MAX-ACCESS  read-only
   STATUS      current
   DESCRIPTION
       " "
   ::= { gs2310pPortTrafficStatisticsEntry 47 }

gs2310pPortTrafficTxQ4 OBJECT-TYPE
   SYNTAX      Counter64
   MAX-ACCESS  read-only
   STATUS      current
   DESCRIPTION
       " "
   ::= { gs2310pPortTrafficStatisticsEntry 48 }

gs2310pPortTrafficTxQ5 OBJECT-TYPE
   SYNTAX      Counter64
   MAX-ACCESS  read-only
   STATUS      current
   DESCRIPTION
       " "
   ::= { gs2310pPortTrafficStatisticsEntry 49 }

gs2310pPortTrafficTxQ6 OBJECT-TYPE
   SYNTAX      Counter64
   MAX-ACCESS  read-only
   STATUS      current
   DESCRIPTION
       " "
   ::= { gs2310pPortTrafficStatisticsEntry 50 }


gs2310pPortTrafficTxQ7 OBJECT-TYPE
   SYNTAX      Counter64
   MAX-ACCESS  read-only
   STATUS      current
   DESCRIPTION
       " "
   ::= { gs2310pPortTrafficStatisticsEntry 51 }

gs2310pPortTrafficTxDrops OBJECT-TYPE
   SYNTAX      Counter64
   MAX-ACCESS  read-only
   STATUS      current
   DESCRIPTION
       " "
   ::= { gs2310pPortTrafficStatisticsEntry 52 }

gs2310pPortTrafficTxLateOrExcColl OBJECT-TYPE
   SYNTAX      Counter64
   MAX-ACCESS  read-only
   STATUS      current
   DESCRIPTION
       " "
   ::= { gs2310pPortTrafficStatisticsEntry 53 }


gs2310pPortQoSStatistics                                     OBJECT IDENTIFIER ::= { gs2310pPort 3 }

gs2310pPortQoSStatisticsClear OBJECT-TYPE
   SYNTAX      INTEGER { none(0), clear(1) }
   MAX-ACCESS  read-only
   STATUS      current
   DESCRIPTION
       "default: 0
       0: none
       1: clear "
   ::= { gs2310pPortQoSStatistics 1 }

gs2310pPortQoSStatisticsTable OBJECT-TYPE
   SYNTAX      SEQUENCE OF Gs2310pPortQoSStatisticsEntry
   MAX-ACCESS  not-accessible
   STATUS      current
   DESCRIPTION
       " "
   ::= { gs2310pPortQoSStatistics 2 }

gs2310pPortQoSStatisticsEntry OBJECT-TYPE
   SYNTAX      Gs2310pPortQoSStatisticsEntry
   MAX-ACCESS  not-accessible
   STATUS      current
   DESCRIPTION
       ""
   INDEX    { gs2310pPortQoSStatisticsPort  }
   ::= { gs2310pPortQoSStatisticsTable 1 }

Gs2310pPortQoSStatisticsEntry ::= SEQUENCE {
   gs2310pPortQoSStatisticsPort      Integer32,
   gs2310pPortQoSQ0Rx                Counter64,
   gs2310pPortQoSQ0Tx                Counter64,
   gs2310pPortQoSQ1Rx                Counter64,
   gs2310pPortQoSQ1Tx                Counter64,
   gs2310pPortQoSQ2Rx                Counter64,
   gs2310pPortQoSQ2Tx                Counter64,
   gs2310pPortQoSQ3Rx                Counter64,
   gs2310pPortQoSQ3Tx                Counter64,
   gs2310pPortQoSQ4Rx                Counter64,
   gs2310pPortQoSQ4Tx                Counter64,
   gs2310pPortQoSQ5Rx                Counter64,
   gs2310pPortQoSQ5Tx                Counter64,
   gs2310pPortQoSQ6Rx                Counter64,
   gs2310pPortQoSQ6Tx                Counter64,
   gs2310pPortQoSQ7Rx                Counter64,
   gs2310pPortQoSQ7Tx                Counter64
}

gs2310pPortQoSStatisticsPort OBJECT-TYPE
   SYNTAX      Integer32(1..4095)
   MAX-ACCESS  not-accessible
   STATUS      current
   DESCRIPTION
       " "
   ::= { gs2310pPortQoSStatisticsEntry 1 }

gs2310pPortQoSQ0Rx OBJECT-TYPE
   SYNTAX      Counter64
   MAX-ACCESS  read-only
   STATUS      current
   DESCRIPTION
       " "
   ::= { gs2310pPortQoSStatisticsEntry 2 }

gs2310pPortQoSQ0Tx OBJECT-TYPE
   SYNTAX      Counter64
   MAX-ACCESS  read-only
   STATUS      current
   DESCRIPTION
       " "
   ::= { gs2310pPortQoSStatisticsEntry 3 }

gs2310pPortQoSQ1Rx OBJECT-TYPE
   SYNTAX      Counter64
   MAX-ACCESS  read-only
   STATUS      current
   DESCRIPTION
       " "
   ::= { gs2310pPortQoSStatisticsEntry 4 }

gs2310pPortQoSQ1Tx OBJECT-TYPE
   SYNTAX      Counter64
   MAX-ACCESS  read-only
   STATUS      current
   DESCRIPTION
       " "
   ::= { gs2310pPortQoSStatisticsEntry 5 }

gs2310pPortQoSQ2Rx OBJECT-TYPE
   SYNTAX      Counter64
   MAX-ACCESS  read-only
   STATUS      current
   DESCRIPTION
       " "
   ::= { gs2310pPortQoSStatisticsEntry 6 }

gs2310pPortQoSQ2Tx OBJECT-TYPE
   SYNTAX      Counter64
   MAX-ACCESS  read-only
   STATUS      current
   DESCRIPTION
       " "
   ::= { gs2310pPortQoSStatisticsEntry 7 }

gs2310pPortQoSQ3Rx OBJECT-TYPE
   SYNTAX      Counter64
   MAX-ACCESS  read-only
   STATUS      current
   DESCRIPTION
       " "
   ::= { gs2310pPortQoSStatisticsEntry 8 }

gs2310pPortQoSQ3Tx OBJECT-TYPE
   SYNTAX      Counter64
   MAX-ACCESS  read-only
   STATUS      current
   DESCRIPTION
       " "
   ::= { gs2310pPortQoSStatisticsEntry 9 }

gs2310pPortQoSQ4Rx OBJECT-TYPE
   SYNTAX      Counter64
   MAX-ACCESS  read-only
   STATUS      current
   DESCRIPTION
       " "
   ::= { gs2310pPortQoSStatisticsEntry 10 }

gs2310pPortQoSQ4Tx OBJECT-TYPE
   SYNTAX      Counter64
   MAX-ACCESS  read-only
   STATUS      current
   DESCRIPTION
       " "
   ::= { gs2310pPortQoSStatisticsEntry 11 }

gs2310pPortQoSQ5Rx OBJECT-TYPE
   SYNTAX      Counter64
   MAX-ACCESS  read-only
   STATUS      current
   DESCRIPTION
       " "
   ::= { gs2310pPortQoSStatisticsEntry 12 }

gs2310pPortQoSQ5Tx OBJECT-TYPE
   SYNTAX      Counter64
   MAX-ACCESS  read-only
   STATUS      current
   DESCRIPTION
       " "
   ::= { gs2310pPortQoSStatisticsEntry 13 }

gs2310pPortQoSQ6Rx OBJECT-TYPE
   SYNTAX      Counter64
   MAX-ACCESS  read-only
   STATUS      current
   DESCRIPTION
       " "
   ::= { gs2310pPortQoSStatisticsEntry 14 }

gs2310pPortQoSQ6Tx OBJECT-TYPE
   SYNTAX      Counter64
   MAX-ACCESS  read-only
   STATUS      current
   DESCRIPTION
       " "
   ::= { gs2310pPortQoSStatisticsEntry 15 }

gs2310pPortQoSQ7Rx OBJECT-TYPE
   SYNTAX      Counter64
   MAX-ACCESS  read-only
   STATUS      current
   DESCRIPTION
       " "
   ::= { gs2310pPortQoSStatisticsEntry 16 }

gs2310pPortQoSQ7Tx OBJECT-TYPE
   SYNTAX      Counter64
   MAX-ACCESS  read-only
   STATUS      current
   DESCRIPTION
       " "
   ::= { gs2310pPortQoSStatisticsEntry 17 }

gs2310pSFPInfoTable OBJECT-TYPE
   SYNTAX      SEQUENCE OF Gs2310pSFPInfoEntry
   MAX-ACCESS  not-accessible
   STATUS      current
   DESCRIPTION
       " "
   ::= { gs2310pPort 4 }

gs2310pSFPInfoEntry OBJECT-TYPE
   SYNTAX      Gs2310pSFPInfoEntry
   MAX-ACCESS  not-accessible
   STATUS      current
   DESCRIPTION
       ""
   INDEX    { gs2310pSFPInfoIndex }
   ::= { gs2310pSFPInfoTable 1 }

Gs2310pSFPInfoEntry ::= SEQUENCE {
   gs2310pSFPInfoIndex               Integer32,
   gs2310pSFPInfoPort                DisplayString,
   gs2310pSFPConnectorType           DisplayString,
   gs2310pSFPFiberType               DisplayString,
   gs2310pSFPTxCentralWavelength     DisplayString,
   gs2310pSFPBaudRate                DisplayString,
   gs2310pSFPVendorOUI               DisplayString,
   gs2310pSFPVendorName              DisplayString,
   gs2310pSFPVendorPN                DisplayString,
   gs2310pSFPVendorRev               DisplayString,
   gs2310pSFPVendorSN                DisplayString,
   gs2310pSFPDateCode                DisplayString,
   gs2310pSFPTemperature             DisplayString,
   gs2310pSFPVcc                     DisplayString,
   gs2310pSFPMon1Bias                DisplayString,
   gs2310pSFPMon2TxPWR               DisplayString,
   gs2310pSFPMon3RxPWR               DisplayString
}

gs2310pSFPInfoIndex OBJECT-TYPE
   SYNTAX      Integer32(1..4095)
   MAX-ACCESS  not-accessible
   STATUS      current
   DESCRIPTION
       " "
   ::= { gs2310pSFPInfoEntry 1 }

gs2310pSFPInfoPort OBJECT-TYPE
   SYNTAX      DisplayString
   MAX-ACCESS  read-only
   STATUS      current
   DESCRIPTION
       " "
   ::= { gs2310pSFPInfoEntry 2 }

gs2310pSFPConnectorType OBJECT-TYPE
   SYNTAX      DisplayString
   MAX-ACCESS  read-only
   STATUS      current
   DESCRIPTION
       " "
   ::= { gs2310pSFPInfoEntry 3 }

gs2310pSFPFiberType OBJECT-TYPE
   SYNTAX      DisplayString
   MAX-ACCESS  read-only
   STATUS      current
   DESCRIPTION
       " "
   ::= { gs2310pSFPInfoEntry 4 }

gs2310pSFPTxCentralWavelength OBJECT-TYPE
   SYNTAX      DisplayString
   MAX-ACCESS  read-only
   STATUS      current
   DESCRIPTION
       " "
   ::= { gs2310pSFPInfoEntry 5 }

gs2310pSFPBaudRate OBJECT-TYPE
   SYNTAX      DisplayString
   MAX-ACCESS  read-only
   STATUS      current
   DESCRIPTION
       " "
   ::= { gs2310pSFPInfoEntry 6 }

gs2310pSFPVendorOUI OBJECT-TYPE
   SYNTAX      DisplayString
   MAX-ACCESS  read-only
   STATUS      current
   DESCRIPTION
       " "
   ::= { gs2310pSFPInfoEntry 7 }

gs2310pSFPVendorName OBJECT-TYPE
   SYNTAX      DisplayString
   MAX-ACCESS  read-only
   STATUS      current
   DESCRIPTION
       " "
   ::= { gs2310pSFPInfoEntry 8 }

gs2310pSFPVendorPN OBJECT-TYPE
   SYNTAX      DisplayString
   MAX-ACCESS  read-only
   STATUS      current
   DESCRIPTION
       " "
   ::= { gs2310pSFPInfoEntry 9 }

gs2310pSFPVendorRev OBJECT-TYPE
   SYNTAX      DisplayString
   MAX-ACCESS  read-only
   STATUS      current
   DESCRIPTION
       " "
   ::= { gs2310pSFPInfoEntry 10 }

gs2310pSFPVendorSN OBJECT-TYPE
   SYNTAX      DisplayString
   MAX-ACCESS  read-only
   STATUS      current
   DESCRIPTION
       " "
   ::= { gs2310pSFPInfoEntry 11 }

gs2310pSFPDateCode OBJECT-TYPE
   SYNTAX      DisplayString
   MAX-ACCESS  read-only
   STATUS      current
   DESCRIPTION
       " "
   ::= { gs2310pSFPInfoEntry 12 }

gs2310pSFPTemperature OBJECT-TYPE
   SYNTAX      DisplayString
   MAX-ACCESS  read-only
   STATUS      current
   DESCRIPTION
       " "
   ::= { gs2310pSFPInfoEntry 13 }

gs2310pSFPVcc OBJECT-TYPE
   SYNTAX      DisplayString
   MAX-ACCESS  read-only
   STATUS      current
   DESCRIPTION
       " "
   ::= { gs2310pSFPInfoEntry 14 }

gs2310pSFPMon1Bias OBJECT-TYPE
   SYNTAX      DisplayString
   MAX-ACCESS  read-only
   STATUS      current
   DESCRIPTION
       " "
   ::= { gs2310pSFPInfoEntry 15 }

gs2310pSFPMon2TxPWR OBJECT-TYPE
   SYNTAX      DisplayString
   MAX-ACCESS  read-only
   STATUS      current
   DESCRIPTION
       " "
   ::= { gs2310pSFPInfoEntry 16 }

gs2310pSFPMon3RxPWR OBJECT-TYPE
   SYNTAX      DisplayString
   MAX-ACCESS  read-only
   STATUS      current
   DESCRIPTION
       " "
   ::= { gs2310pSFPInfoEntry 17 }


gs2310pPortEEETable OBJECT-TYPE
   SYNTAX      SEQUENCE OF Gs2310pPortEEEEntry
   MAX-ACCESS  not-accessible
   STATUS      current
   DESCRIPTION
      " "
   ::= { gs2310pPort 5 }

gs2310pPortEEEEntry OBJECT-TYPE
   SYNTAX      Gs2310pPortEEEEntry
   MAX-ACCESS  not-accessible
   STATUS      current
   DESCRIPTION
       ""
   INDEX    { gs2310pPortEEEPort }
   ::= { gs2310pPortEEETable 1 }

Gs2310pPortEEEEntry ::= SEQUENCE {
   gs2310pPortEEEPort		        Integer32,
   gs2310pPortEEEMode		        INTEGER,
   gs2310pPortEEEUrgentQueue1		INTEGER,
   gs2310pPortEEEUrgentQueue2		INTEGER,
   gs2310pPortEEEUrgentQueue3		INTEGER,
   gs2310pPortEEEUrgentQueue4		INTEGER,
   gs2310pPortEEEUrgentQueue5		INTEGER,
   gs2310pPortEEEUrgentQueue6		INTEGER,
   gs2310pPortEEEUrgentQueue7		INTEGER,
   gs2310pPortEEEUrgentQueue8		INTEGER
}

gs2310pPortEEEPort OBJECT-TYPE
   SYNTAX      Integer32(1..4095)
   MAX-ACCESS  not-accessible
   STATUS      current
   DESCRIPTION
       " "
   ::= { gs2310pPortEEEEntry 1 }

gs2310pPortEEEMode OBJECT-TYPE
   SYNTAX      INTEGER { disable(0), enable(1) }
   MAX-ACCESS  read-write
   STATUS      current
   DESCRIPTION
       "default: 0
       0:disable
       1:enable "
   ::= { gs2310pPortEEEEntry 2 }

gs2310pPortEEEUrgentQueue1 OBJECT-TYPE
   SYNTAX      INTEGER { disable(0), enable(1) }
   MAX-ACCESS  read-write
   STATUS      current
   DESCRIPTION
       "default: 0
       0:disable
       1:enable "
   ::= { gs2310pPortEEEEntry 3 }

gs2310pPortEEEUrgentQueue2 OBJECT-TYPE
   SYNTAX      INTEGER { disable(0), enable(1) }
   MAX-ACCESS  read-write
   STATUS      current
   DESCRIPTION
       "default: 0
       0:disable
       1:enable "
   ::= { gs2310pPortEEEEntry 4 }

gs2310pPortEEEUrgentQueue3 OBJECT-TYPE
   SYNTAX      INTEGER { disable(0), enable(1) }
   MAX-ACCESS  read-write
   STATUS      current
   DESCRIPTION
       "default: 0
       0:disable
       1:enable "
   ::= { gs2310pPortEEEEntry 5 }

gs2310pPortEEEUrgentQueue4 OBJECT-TYPE
   SYNTAX      INTEGER { disable(0), enable(1) }
   MAX-ACCESS  read-write
   STATUS      current
   DESCRIPTION
       "default: 0
       0:disable
       1:enable "
   ::= { gs2310pPortEEEEntry 6 }

gs2310pPortEEEUrgentQueue5 OBJECT-TYPE
   SYNTAX      INTEGER { disable(0), enable(1) }
   MAX-ACCESS  read-write
   STATUS      current
   DESCRIPTION
       "default: 0
       0:disable
       1:enable "
   ::= { gs2310pPortEEEEntry 7 }

gs2310pPortEEEUrgentQueue6 OBJECT-TYPE
   SYNTAX      INTEGER { disable(0), enable(1) }
   MAX-ACCESS  read-write
   STATUS      current
   DESCRIPTION
       "default: 0
       0:disable
       1:enable "
   ::= { gs2310pPortEEEEntry 8 }

gs2310pPortEEEUrgentQueue7 OBJECT-TYPE
   SYNTAX      INTEGER { disable(0), enable(1) }
   MAX-ACCESS  read-write
   STATUS      current
   DESCRIPTION
       "default: 0
       0:disable
       1:enable "
   ::= { gs2310pPortEEEEntry 9 }

gs2310pPortEEEUrgentQueue8 OBJECT-TYPE
   SYNTAX      INTEGER { disable(0), enable(1) }
   MAX-ACCESS  read-write
   STATUS      current
   DESCRIPTION
       "default: 0
       0:disable
       1:enable "
   ::= { gs2310pPortEEEEntry 10 }


gs2310pVoiceVLAN                                             OBJECT IDENTIFIER ::= { gs2310pConfiguration 2 }

gs2310pVoiceVLANConf                                         OBJECT IDENTIFIER ::= { gs2310pVoiceVLAN 1 }

gs2310pVoiceVLANMode OBJECT-TYPE
   SYNTAX      INTEGER { disable(0), enable(1) }
   MAX-ACCESS  read-write
   STATUS      current
   DESCRIPTION
       " Voice VLAN mode operation.
       default: 0,
       0: disable
       1: enable"
   ::= { gs2310pVoiceVLANConf 1 }

gs2310pVoiceVLANVLANId OBJECT-TYPE
   SYNTAX      Integer32(1..4094)
   MAX-ACCESS  read-write
   STATUS      current
   DESCRIPTION
       "Voice VLAN ID.
        default: 1000,
        range : 1-4094. "
   ::= { gs2310pVoiceVLANConf 2 }

gs2310pVoiceVLANAgingTime OBJECT-TYPE
   SYNTAX      Integer32(10..1000000)
   MAX-ACCESS  read-write
   STATUS      current
   DESCRIPTION
       " Voice VLAN secure learning aging time.
         default: 86400,
         range : 10 - 10000000. "
   ::= { gs2310pVoiceVLANConf 3 }

gs2310pVoiceVLANTrafficClass OBJECT-TYPE
   SYNTAX      Integer32(0..7)
   MAX-ACCESS  read-write
   STATUS      current
   DESCRIPTION
       " Voice VLAN traffic class, all traffic on the Voice VLAN
         will apply this class, available value is from 0(Low)
         to 7(High).
         default: 7. "
   ::= { gs2310pVoiceVLANConf 4 }


gs2310pVoiceVLANPortTable OBJECT-TYPE
   SYNTAX      SEQUENCE OF Gs2310pVoiceVLANPortEntry
   MAX-ACCESS  not-accessible
   STATUS      current
   DESCRIPTION
       " Show Voice Vlan configuration. "
   ::= { gs2310pVoiceVLANConf 5 }

gs2310pVoiceVLANPortEntry OBJECT-TYPE
   SYNTAX      Gs2310pVoiceVLANPortEntry
   MAX-ACCESS  not-accessible
   STATUS      current
   DESCRIPTION
       ""
   INDEX    { gs2310pVoiceVLANPort  }
   ::= { gs2310pVoiceVLANPortTable 1 }

Gs2310pVoiceVLANPortEntry ::= SEQUENCE {
   gs2310pVoiceVLANPort                    Integer32,
   gs2310pVoiceVLANPortMode                INTEGER,
   gs2310pVoiceVLANPortSecurity            INTEGER,
   gs2310pVoiceVLANPortDiscoveryProtocol   INTEGER
}

gs2310pVoiceVLANPort OBJECT-TYPE
   SYNTAX      Integer32(1..4095)
   MAX-ACCESS  not-accessible
   STATUS      current
   DESCRIPTION
       " port, range : 1 - port number. "
   ::= { gs2310pVoiceVLANPortEntry 1 }

gs2310pVoiceVLANPortMode OBJECT-TYPE
   SYNTAX      INTEGER { disable(0), auto(1), forced(2) }
   MAX-ACCESS  read-write
   STATUS      current
   DESCRIPTION
       " Voice VLAN port mode.
         default: 0,
         0: Disable (Disjoin from Voice VLAN.)
         1: Auto (Enable auto detect mode. It detects whether there is VoIP phone attached to the specific port and configures the Voice VLAN members automatically.)
         2: Forced (Force join to Voice VLAN.)"
   ::= { gs2310pVoiceVLANPortEntry 2 }

gs2310pVoiceVLANPortSecurity OBJECT-TYPE
   SYNTAX      INTEGER { disable(0), enable(1) }
   MAX-ACCESS  read-write
   STATUS      current
   DESCRIPTION
       " Voice VLAN port security mode.
         default: 0,
         0: Disable (Disjoin from Voice VLAN.)
         1: enable ( Enable Voice VLAN security mode. When the function is
                     enabled, all non-telephone MAC address in Voice VLAN
                     will be blocked 10 seconds.)"
   ::= { gs2310pVoiceVLANPortEntry 3 }

gs2310pVoiceVLANPortDiscoveryProtocol OBJECT-TYPE
   SYNTAX      INTEGER { oui(0), lldp(1), both(2) }
   MAX-ACCESS  read-write
   STATUS      current
   DESCRIPTION
       " Voice VLAN port discovery protocol.
         default: 0
         0: OUI (Detect telephony device by OUI address.)
         1: LLDP (Detect telephony device by LLDP.)
         2: Both (Both OUI and LLDP.) "
   ::= { gs2310pVoiceVLANPortEntry 4 }

gs2310pVoiceVLANSkipNAS OBJECT-TYPE
   SYNTAX      INTEGER { disable(0), enable(1) }
   MAX-ACCESS  read-write
   STATUS      current
   DESCRIPTION
       " Voice VLAN skip NAS mode.
         default: 0,
         0: Disable (Do not skip NAS on Voice VLAN.)
         1: enable (Enable skipping of NAS on Voice VLAN. When the function is
                    enabled, authentication through the NAS module is not
                    applied to the Voice VLAN, but clients are allowed without
                    authentication.)"
   ::= { gs2310pVoiceVLANPortEntry 5 }


gs2310pVoiceVLANOUI                                          OBJECT IDENTIFIER ::= { gs2310pVoiceVLAN 2 }

gs2310pVoiceVLANOUICreate OBJECT-TYPE
   SYNTAX       INTEGER { none(0), create(1) }
   MAX-ACCESS   read-write
   STATUS       current
   DESCRIPTION
       "default: 0
        0 : None  (read only)
        1 : Create an OUI entry"
   ::= { gs2310pVoiceVLANOUI 1 }

gs2310pVoiceVLANOUITable OBJECT-TYPE
   SYNTAX      SEQUENCE OF Gs2310pVoiceVLANOUIEntry
   MAX-ACCESS  not-accessible
   STATUS      current
   DESCRIPTION
       " Create Voice VLAN OUI entry. Modify OUI table will
         restart auto detect OUI process. "
   ::= { gs2310pVoiceVLANOUI 2 }

gs2310pVoiceVLANOUIEntry OBJECT-TYPE
   SYNTAX      Gs2310pVoiceVLANOUIEntry
   MAX-ACCESS  not-accessible
   STATUS      current
   DESCRIPTION
       ""
   INDEX    { gs2310pVoiceVLANOUIIndex  }
   ::= { gs2310pVoiceVLANOUITable 1 }

Gs2310pVoiceVLANOUIEntry ::= SEQUENCE {
   gs2310pVoiceVLANOUIIndex         Integer32,
   gs2310pVoiceVLANTelephonyOUI     OCTET STRING,
   gs2310pVoiceVLANDescription      DisplayString,
   gs2310pVoiceVLANOUIRowStatus     INTEGER
}

gs2310pVoiceVLANOUIIndex OBJECT-TYPE
   SYNTAX      Integer32(1..16)
   MAX-ACCESS  not-accessible
   STATUS      current
   DESCRIPTION
       " "
   ::= { gs2310pVoiceVLANOUIEntry 1 }

gs2310pVoiceVLANTelephonyOUI OBJECT-TYPE
   SYNTAX      OCTET STRING (SIZE (1..32))
   MAX-ACCESS  read-write
   STATUS      current
   DESCRIPTION
       "OUI address, format : 0a 1b 2c "
   ::= { gs2310pVoiceVLANOUIEntry 2 }

gs2310pVoiceVLANDescription OBJECT-TYPE
   SYNTAX      DisplayString (SIZE (1..32))
   MAX-ACCESS  read-write
   STATUS      current
   DESCRIPTION
       " Up to 32 characters describing OUI address. "
   ::= { gs2310pVoiceVLANOUIEntry 3 }

gs2310pVoiceVLANOUIRowStatus OBJECT-TYPE
   SYNTAX      INTEGER { active(1), notInservice(2), destroy(4), undo(5) }
   MAX-ACCESS  read-write
   STATUS      current
   DESCRIPTION
       "1: active
        2: notInservice
        4: destroy
        5: undo"
   ::= { gs2310pVoiceVLANOUIEntry 4 }

gs2310pGARP                                                   OBJECT IDENTIFIER ::= { gs2310pConfiguration 3 }

gs2310pGARPConfTable OBJECT-TYPE
   SYNTAX      SEQUENCE OF Gs2310pGARPConfEntry
   MAX-ACCESS  not-accessible
   STATUS      current
   DESCRIPTION
       " "
   ::= { gs2310pGARP 1 }

gs2310pGARPConfEntry OBJECT-TYPE
   SYNTAX      Gs2310pGARPConfEntry
   MAX-ACCESS  not-accessible
   STATUS      current
   DESCRIPTION
       ""
   INDEX    { gs2310pGARPConfPort  }
   ::= { gs2310pGARPConfTable 1 }

Gs2310pGARPConfEntry ::= SEQUENCE {
   gs2310pGARPConfPort           Integer32,
   gs2310pGARPJoinTimer          Integer32,
   gs2310pGARPLeaveTimer         Integer32,
   gs2310pGARPLeaveAllTimer      Integer32,
   gs2310pGARPApplicantion       INTEGER,
   gs2310pGARPAttributeType      INTEGER,
   gs2310pGARPApplicant          INTEGER
}

gs2310pGARPConfPort OBJECT-TYPE
   SYNTAX      Integer32(1..4095)
   MAX-ACCESS  not-accessible
   STATUS      current
   DESCRIPTION
       " "
   ::= { gs2310pGARPConfEntry 1 }

gs2310pGARPJoinTimer OBJECT-TYPE
   SYNTAX      Integer32(200..1000)
   MAX-ACCESS  read-write
   STATUS      current
   DESCRIPTION
       "default: 200, range : 200 - 1000 "
   ::= { gs2310pGARPConfEntry 2 }

gs2310pGARPLeaveTimer OBJECT-TYPE
   SYNTAX      Integer32(600..3000)
   MAX-ACCESS  read-write
   STATUS      current
   DESCRIPTION
       "default: 600 , range : 600 - 3000"
   ::= { gs2310pGARPConfEntry 3 }

gs2310pGARPLeaveAllTimer OBJECT-TYPE
   SYNTAX      Integer32(10000..50000)
   MAX-ACCESS  read-write
   STATUS      current
   DESCRIPTION
       "default: 10000, range : 10000 - 50000 "
   ::= { gs2310pGARPConfEntry 4 }

gs2310pGARPApplicantion OBJECT-TYPE
   SYNTAX      INTEGER { gvrp(1)}
   MAX-ACCESS  read-write
   STATUS      current
   DESCRIPTION
       "default: 1
       1: GVRP"
   ::= { gs2310pGARPConfEntry 5 }

gs2310pGARPAttributeType OBJECT-TYPE
   SYNTAX      INTEGER { vlan(1)}
   MAX-ACCESS  read-write
   STATUS      current
   DESCRIPTION
       "default: 1
       1: VLAN"
   ::= { gs2310pGARPConfEntry 6 }

gs2310pGARPApplicant OBJECT-TYPE
   SYNTAX      INTEGER { participant(0), nonParticipant(1) }
   MAX-ACCESS  read-write
   STATUS      current
   DESCRIPTION
       "default: 0
       0: normal-participant
       1: non-participant"
   ::= { gs2310pGARPConfEntry 7 }

gs2310pGARPStatisticsTable OBJECT-TYPE
   SYNTAX      SEQUENCE OF Gs2310pGARPStatisticsEntry
   MAX-ACCESS  not-accessible
   STATUS      current
   DESCRIPTION
       " Show the basic GARP port statistics. "
   ::= { gs2310pGARP 2 }

gs2310pGARPStatisticsEntry OBJECT-TYPE
   SYNTAX      Gs2310pGARPStatisticsEntry
   MAX-ACCESS  not-accessible
   STATUS      current
   DESCRIPTION
       ""
   INDEX    { gs2310pGARPStatisticsPort  }
   ::= { gs2310pGARPStatisticsTable 1 }

Gs2310pGARPStatisticsEntry ::= SEQUENCE {
   gs2310pGARPStatisticsPort             Integer32,
   gs2310pGARPStatisticsPeerMAC          DisplayString,
   gs2310pGARPStatisticsFailedCount      Counter32
}

gs2310pGARPStatisticsPort OBJECT-TYPE
   SYNTAX      Integer32(1..4095)
   MAX-ACCESS  not-accessible
   STATUS      current
   DESCRIPTION
       " port, range : 1 - port number. "
   ::= { gs2310pGARPStatisticsEntry 1 }

gs2310pGARPStatisticsPeerMAC OBJECT-TYPE
   SYNTAX      DisplayString
   MAX-ACCESS  read-only
   STATUS      current
   DESCRIPTION
       " Peer MAC is MAC address of the neighbour Switch from with GARP frame is received.  "
   ::= { gs2310pGARPStatisticsEntry 2 }

gs2310pGARPStatisticsFailedCount OBJECT-TYPE
   SYNTAX      Counter32
   MAX-ACCESS  read-only
   STATUS      current
   DESCRIPTION
       " explain Failed count here. "
   ::= { gs2310pGARPStatisticsEntry 3 }

gs2310pGVRP                                                   OBJECT IDENTIFIER ::= { gs2310pConfiguration 4 }

gs2310pGVRPConf                                                   OBJECT IDENTIFIER ::= { gs2310pGVRP 1 }

gs2310pGVRPMode OBJECT-TYPE
   SYNTAX      INTEGER { disable(0), enable(1) }
   MAX-ACCESS  read-write
   STATUS      current
   DESCRIPTION
       "default: 0,
        0: disable,
        1: enable. "
   ::= { gs2310pGVRPConf 1 }

gs2310pGVRPConfTable OBJECT-TYPE
   SYNTAX      SEQUENCE OF Gs2310pGVRPConfEntry
   MAX-ACCESS  not-accessible
   STATUS      current
   DESCRIPTION
       " "
   ::= { gs2310pGVRPConf 2 }

gs2310pGVRPConfEntry OBJECT-TYPE
   SYNTAX      Gs2310pGVRPConfEntry
   MAX-ACCESS  not-accessible
   STATUS      current
   DESCRIPTION
       ""
   INDEX    { gs2310pGVRPConfPort  }
   ::= { gs2310pGVRPConfTable 1 }

Gs2310pGVRPConfEntry ::= SEQUENCE {
   gs2310pGVRPConfPort           Integer32,
   gs2310pGVRPConfPortMode       INTEGER,
   gs2310pGVRPConfPortRRole      INTEGER
}

gs2310pGVRPConfPort OBJECT-TYPE
   SYNTAX      Integer32(1..4095)
   MAX-ACCESS  not-accessible
   STATUS      current
   DESCRIPTION
       " "
   ::= { gs2310pGVRPConfEntry 1 }

gs2310pGVRPConfPortMode OBJECT-TYPE
   SYNTAX      INTEGER { disable(0), enable(1) }
   MAX-ACCESS  read-write
   STATUS      current
   DESCRIPTION
       "default: 0
       1: enable
       0: disable"
   ::= { gs2310pGVRPConfEntry 2 }

gs2310pGVRPConfPortRRole OBJECT-TYPE
   SYNTAX      INTEGER { disable(0), enable(1) }
   MAX-ACCESS  read-write
   STATUS      current
   DESCRIPTION
       "default: 0
       1: enable
       0: disable"
   ::= { gs2310pGVRPConfEntry 3 }

gs2310pGVRPStatisticsTable OBJECT-TYPE
   SYNTAX      SEQUENCE OF Gs2310pGVRPStatisticsEntry
   MAX-ACCESS  not-accessible
   STATUS      current
   DESCRIPTION
       " "
   ::= { gs2310pGVRP 2 }

gs2310pGVRPStatisticsEntry OBJECT-TYPE
   SYNTAX      Gs2310pGVRPStatisticsEntry
   MAX-ACCESS  not-accessible
   STATUS      current
   DESCRIPTION
       ""
   INDEX    { gs2310pGVRPStatisticsPort  }
   ::= { gs2310pGVRPStatisticsTable 1 }

Gs2310pGVRPStatisticsEntry ::= SEQUENCE {
   gs2310pGVRPStatisticsPort         Integer32,
   gs2310pGVRPStatisticsJoinTxCnt    Counter32,
   gs2310pGVRPStatisticsLeaveTxCnt   Counter32
}

gs2310pGVRPStatisticsPort OBJECT-TYPE
   SYNTAX      Integer32(1..4095)
   MAX-ACCESS  not-accessible
   STATUS      current
   DESCRIPTION
       " "
   ::= { gs2310pGVRPStatisticsEntry 1 }

gs2310pGVRPStatisticsJoinTxCnt OBJECT-TYPE
   SYNTAX      Counter32
   MAX-ACCESS  read-only
   STATUS      current
   DESCRIPTION
       ""
   ::= { gs2310pGVRPStatisticsEntry 2 }

gs2310pGVRPStatisticsLeaveTxCnt OBJECT-TYPE
   SYNTAX      Counter32
   MAX-ACCESS  read-only
   STATUS      current
   DESCRIPTION
       ""
   ::= { gs2310pGVRPStatisticsEntry 3 }


gs2310pMirroring                                             OBJECT IDENTIFIER ::= { gs2310pConfiguration 6 }

gs2310pPortToMirrorOn OBJECT-TYPE
   SYNTAX      Integer32(0..10)
   MAX-ACCESS  read-write
   STATUS      current
   DESCRIPTION
       "default: 0
        0: disable,
        range : 1 - port number. "
   ::= { gs2310pMirroring 1 }

gs2310pMirrorTable OBJECT-TYPE
   SYNTAX      SEQUENCE OF Gs2310pMirrorEntry
   MAX-ACCESS  not-accessible
   STATUS      current
   DESCRIPTION
       " "
   ::= { gs2310pMirroring 2 }

gs2310pMirrorEntry OBJECT-TYPE
   SYNTAX      Gs2310pMirrorEntry
   MAX-ACCESS  not-accessible
   STATUS      current
   DESCRIPTION
       ""
   INDEX    { gs2310pMirrorPort  }
   ::= { gs2310pMirrorTable 1 }

Gs2310pMirrorEntry ::= SEQUENCE {
   gs2310pMirrorPort		Integer32,
   gs2310pMirrorMode		INTEGER
}

gs2310pMirrorPort OBJECT-TYPE
   SYNTAX      Integer32(1..4095)
   MAX-ACCESS  not-accessible
   STATUS      current
   DESCRIPTION
       " "
   ::= { gs2310pMirrorEntry 1 }

gs2310pMirrorMode OBJECT-TYPE
   SYNTAX      INTEGER { disable(0), enable(1), rxOnly(2), txOnly(3) }
   MAX-ACCESS  read-write
   STATUS      current
   DESCRIPTION
       "default: 0
       0: disable
       1: enable
       2: rx only
       3: tx only
       Setting Tx mirroring for analyzer port has no effect. Tx mirroring ignored"
   ::= { gs2310pMirrorEntry 2 }

gs2310pTrapEventSeverity                                             OBJECT IDENTIFIER ::= { gs2310pConfiguration 7 }

gs2310pTrapEventSeverityACL OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  6(Info)
        0: Emergency
        1: Alert
        2: Critical
        3: Error
        4: Warning
        5: Notice
        6: Info
        7: Debug"
   ::= { gs2310pTrapEventSeverity 1 }

gs2310pTrapEventSeverityACLLog OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  7(Debug)
        0: Emergency
        1: Alert
        2: Critical
        3: Error
        4: Warning
        5: Notice
        6: Info
        7: Debug"
   ::= { gs2310pTrapEventSeverity 2 }

gs2310pTrapEventSeverityAccessMgmt OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  6(Info)
        0: Emergency
        1: Alert
        2: Critical
        3: Error
        4: Warning
        5: Notice
        6: Info
        7: Debug"
   ::= { gs2310pTrapEventSeverity 3 }

gs2310pTrapEventSeverityAuthFailed OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  4(Warning)
        0: Emergency
        1: Alert
        2: Critical
        3: Error
        4: Warning
        5: Notice
        6: Info
        7: Debug"
   ::= { gs2310pTrapEventSeverity 4 }

gs2310pTrapEventSeverityColdStart OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  4(Warning)
        0: Emergency
        1: Alert
        2: Critical
        3: Error
        4: Warning
        5: Notice
        6: Info
        7: Debug"
   ::= { gs2310pTrapEventSeverity 5 }

gs2310pTrapEventSeverityConfigInfo OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  6(Info)
        0: Emergency
        1: Alert
        2: Critical
        3: Error
        4: Warning
        5: Notice
        6: Info
        7: Debug"
   ::= { gs2310pTrapEventSeverity 6 }

gs2310pTrapEventSeverityFirmwareUpgrade OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  6(Info)
        0: Emergency
        1: Alert
        2: Critical
        3: Error
        4: Warning
        5: Notice
        6: Info
        7: Debug"
   ::= { gs2310pTrapEventSeverity 7 }

gs2310pTrapEventSeverityImportExport OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  6(Info)
        0: Emergency
        1: Alert
        2: Critical
        3: Error
        4: Warning
        5: Notice
        6: Info
        7: Debug"
   ::= { gs2310pTrapEventSeverity 8 }

gs2310pTrapEventSeverityLACP OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  6(Info)
        0: Emergency
        1: Alert
        2: Critical
        3: Error
        4: Warning
        5: Notice
        6: Info
        7: Debug"
   ::= { gs2310pTrapEventSeverity 9 }

gs2310pTrapEventSeverityLinkStatus OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  4(Warning)
        0: Emergency
        1: Alert
        2: Critical
        3: Error
        4: Warning
        5: Notice
        6: Info
        7: Debug"
   ::= { gs2310pTrapEventSeverity 10 }

gs2310pTrapEventSeverityLogin OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  6(Info)
        0: Emergency
        1: Alert
        2: Critical
        3: Error
        4: Warning
        5: Notice
        6: Info
        7: Debug"
   ::= { gs2310pTrapEventSeverity 11 }

gs2310pTrapEventSeverityLogout OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  6(Info)
        0: Emergency
        1: Alert
        2: Critical
        3: Error
        4: Warning
        5: Notice
        6: Info
        7: Debug"
   ::= { gs2310pTrapEventSeverity 12 }

gs2310pTrapEventSeverityLoopProtect OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  6(Info)
        0: Emergency
        1: Alert
        2: Critical
        3: Error
        4: Warning
        5: Notice
        6: Info
        7: Debug"
   ::= { gs2310pTrapEventSeverity 13 }

gs2310pTrapEventSeverityMgmtIPChange OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  6(Info)
        0: Emergency
        1: Alert
        2: Critical
        3: Error
        4: Warning
        5: Notice
        6: Info
        7: Debug"
   ::= { gs2310pTrapEventSeverity 14 }

gs2310pTrapEventSeverityModuleChange OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  5(Notice)
        0: Emergency
        1: Alert
        2: Critical
        3: Error
        4: Warning
        5: Notice
        6: Info
        7: Debug"
   ::= { gs2310pTrapEventSeverity 15 }

gs2310pTrapEventSeverityNAS OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  6(Info)
        0: Emergency
        1: Alert
        2: Critical
        3: Error
        4: Warning
        5: Notice
        6: Info
        7: Debug"
   ::= { gs2310pTrapEventSeverity 16 }

gs2310pTrapEventSeverityPasswordChange OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  6(Info)
        0: Emergency
        1: Alert
        2: Critical
        3: Error
        4: Warning
        5: Notice
        6: Info
        7: Debug"
   ::= { gs2310pTrapEventSeverity 17 }

gs2310pTrapEventSeverityPortSecurity OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  6(Info)
        0: Emergency
        1: Alert
        2: Critical
        3: Error
        4: Warning
        5: Notice
        6: Info
        7: Debug"
   ::= { gs2310pTrapEventSeverity 18 }

gs2310pTrapEventSeverityVLAN OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  6(Info)
        0: Emergency
        1: Alert
        2: Critical
        3: Error
        4: Warning
        5: Notice
        6: Info
        7: Debug"
   ::= { gs2310pTrapEventSeverity 20 }

gs2310pTrapEventSeverityWarmStart OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  4(Warning)
        0: Emergency
        1: Alert
        2: Critical
        3: Error
        4: Warning
        5: Notice
        6: Info
        7: Debug"
   ::= { gs2310pTrapEventSeverity 21 }

gs2310pTrapEventSeverityPoEAutoCheck OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  4(Warning)
        0: Emergency
        1: Alert
        2: Critical
        3: Error
        4: Warning
        5: Notice
        6: Info
        7: Debug"
   ::= { gs2310pTrapEventSeverity 22 }

gs2310pTrapEventSeverityARPConflict OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  4(Warning)
        0: Emergency
        1: Alert
        2: Critical
        3: Error
        4: Warning
        5: Notice
        6: Info
        7: Debug"
   ::= { gs2310pTrapEventSeverity 25 }

gs2310pTrapEventSeveritySpoofingLimit OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  4(Warning)
        0: Emergency
        1: Alert
        2: Critical
        3: Error
        4: Warning
        5: Notice
        6: Info
        7: Debug"
   ::= { gs2310pTrapEventSeverity 27 }

gs2310pTrapEventSeverityStaticARPConflict	 OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  4(Warning)
        0: Emergency
        1: Alert
        2: Critical
        3: Error
        4: Warning
        5: Notice
        6: Info
        7: Debug"
   ::= { gs2310pTrapEventSeverity 28 }

gs2310pSMTP                                             OBJECT IDENTIFIER ::= { gs2310pConfiguration 8 }

gs2310pSMTPMailServer OBJECT-TYPE
   SYNTAX      DisplayString
   MAX-ACCESS  read-write
   STATUS      current
   DESCRIPTION
       " Up to 47 characters describing email server. "
   ::= { gs2310pSMTP 1 }

gs2310pSMTPUserName OBJECT-TYPE
   SYNTAX      DisplayString
   MAX-ACCESS  read-write
   STATUS      current
   DESCRIPTION
       " Up to 47 characters describing user name. "
   ::= { gs2310pSMTP 2 }

gs2310pSMTPPassword OBJECT-TYPE
   SYNTAX      DisplayString
   MAX-ACCESS  read-write
   STATUS      current
   DESCRIPTION
       " Up to 47 characters describing password. "
   ::= { gs2310pSMTP 3 }

gs2310pSMTPServeriryLevel OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       "default: 6
       0: Emergency
       1: Alert
       2: Critical
       3: Error
       4: Warning
       5: Notice
       6: Info
       7: Debug"
   ::= { gs2310pSMTP 4 }

gs2310pSMTPSender OBJECT-TYPE
   SYNTAX      DisplayString
   MAX-ACCESS  read-write
   STATUS      current
   DESCRIPTION
       " Up to 47 characters describing sender. "
   ::= { gs2310pSMTP 5 }

gs2310pSMTPReturnPath OBJECT-TYPE
   SYNTAX      DisplayString
   MAX-ACCESS  read-write
   STATUS      current
   DESCRIPTION
       " Up to 47 characters describing return path. "
   ::= { gs2310pSMTP 6 }

gs2310pSMTPEmailAddress1 OBJECT-TYPE
   SYNTAX      DisplayString
   MAX-ACCESS  read-write
   STATUS      current
   DESCRIPTION
       " Up to 47 characters describing mail address. "
   ::= { gs2310pSMTP 7 }

gs2310pSMTPEmailAddress2 OBJECT-TYPE
   SYNTAX      DisplayString
   MAX-ACCESS  read-write
   STATUS      current
   DESCRIPTION
       " Up to 47 characters describing mail address. "
   ::= { gs2310pSMTP 8 }

gs2310pSMTPEmailAddress3 OBJECT-TYPE
   SYNTAX      DisplayString
   MAX-ACCESS  read-write
   STATUS      current
   DESCRIPTION
       " Up to 47 characters describing mail address. "
   ::= { gs2310pSMTP 9 }

gs2310pSMTPEmailAddress4 OBJECT-TYPE
   SYNTAX      DisplayString
   MAX-ACCESS  read-write
   STATUS      current
   DESCRIPTION
       " Up to 47 characters describing mail address. "
   ::= { gs2310pSMTP 10 }

gs2310pSMTPEmailAddress5 OBJECT-TYPE
   SYNTAX      DisplayString
   MAX-ACCESS  read-write
   STATUS      current
   DESCRIPTION
       " Up to 47 characters describing mail address. "
   ::= { gs2310pSMTP 11 }

gs2310pSMTPEmailAddress6 OBJECT-TYPE
   SYNTAX      DisplayString
   MAX-ACCESS  read-write
   STATUS      current
   DESCRIPTION
       " Up to 47 characters describing mail address. "
   ::= { gs2310pSMTP 12 }


gs2310pACL                                                   OBJECT IDENTIFIER ::= { gs2310pConfiguration 9 }

gs2310pACLPortsConfTable OBJECT-TYPE
   SYNTAX      SEQUENCE OF Gs2310pACLPortsConfEntry
   MAX-ACCESS  not-accessible
   STATUS      current
   DESCRIPTION
       " "
   ::= { gs2310pACL 1 }

gs2310pACLPortsConfEntry OBJECT-TYPE
   SYNTAX      Gs2310pACLPortsConfEntry
   MAX-ACCESS  not-accessible
   STATUS      current
   DESCRIPTION
       ""
   INDEX    { gs2310pACLPortsConfPort  }
   ::= { gs2310pACLPortsConfTable 1 }

Gs2310pACLPortsConfEntry ::= SEQUENCE {
   gs2310pACLPortsConfPort               Integer32,
   gs2310pACLPortsConfPolicyID           Integer32,
   gs2310pACLPortsConfAction             INTEGER,
   gs2310pACLPortsConfRateLimiterID      Integer32,
   gs2310pACLPortsConfPortRedirect       Integer32,
   gs2310pACLPortsConfMirror             INTEGER,
   gs2310pACLPortsConfLogging            INTEGER,
   gs2310pACLPortsConfShutdown           INTEGER,
   gs2310pACLPortsConfState              INTEGER,
   gs2310pACLPortsConfCounter            Counter32
}

gs2310pACLPortsConfPort OBJECT-TYPE
   SYNTAX      Integer32 (1..4095)
   MAX-ACCESS  not-accessible
   STATUS      current
   DESCRIPTION
       " "
   ::= { gs2310pACLPortsConfEntry 1 }

gs2310pACLPortsConfPolicyID OBJECT-TYPE
   SYNTAX      Integer32 (0..255)
   MAX-ACCESS  read-write
   STATUS      current
   DESCRIPTION
       "default: 0, range : 0 - 255 "
   ::= { gs2310pACLPortsConfEntry 2 }

gs2310pACLPortsConfAction OBJECT-TYPE
   SYNTAX      INTEGER { deny(0), permit(1) }
   MAX-ACCESS  read-write
   STATUS      current
   DESCRIPTION
       "default: 1,
        0: Deny
        1: Permit"
   ::= { gs2310pACLPortsConfEntry 3 }

gs2310pACLPortsConfRateLimiterID OBJECT-TYPE
   SYNTAX      Integer32 (0..12)
   MAX-ACCESS  read-write
   STATUS      current
   DESCRIPTION
       "default: 0,
        0: Disable
        range : 0 - 12 "
   ::= { gs2310pACLPortsConfEntry 4 }

gs2310pACLPortsConfPortRedirect OBJECT-TYPE
   SYNTAX      Integer32 (0..4095)
   MAX-ACCESS  read-write
   STATUS      current
   DESCRIPTION
       "default: 0
        0: Disable
        range : 0 - end port number "
   ::= { gs2310pACLPortsConfEntry 5 }

gs2310pACLPortsConfMirror OBJECT-TYPE
   SYNTAX      INTEGER { disable(0), enable(1) }
   MAX-ACCESS  read-write
   STATUS      current
   DESCRIPTION
       "default: 0
        0: Disable
        1: Enable "
   ::= { gs2310pACLPortsConfEntry 6 }

gs2310pACLPortsConfLogging OBJECT-TYPE
   SYNTAX      INTEGER { disable(0), enable(1) }
   MAX-ACCESS  read-write
   STATUS      current
   DESCRIPTION
       "default: 0
        0: Disable
        1: Enable "
   ::= { gs2310pACLPortsConfEntry 7 }

gs2310pACLPortsConfShutdown OBJECT-TYPE
   SYNTAX      INTEGER { disable(0), enable(1) }
   MAX-ACCESS  read-write
   STATUS      current
   DESCRIPTION
       "default: 0
        0: Disable
        1: Enable "
   ::= { gs2310pACLPortsConfEntry 8 }

gs2310pACLPortsConfState OBJECT-TYPE
   SYNTAX      INTEGER { disable(0), enable(1) }
   MAX-ACCESS  read-write
   STATUS      current
   DESCRIPTION
       "default: 1
        0: Disable
        1: Enable "
   ::= { gs2310pACLPortsConfEntry 9 }

gs2310pACLPortsConfCounter OBJECT-TYPE
   SYNTAX      Counter32
   MAX-ACCESS  read-only
   STATUS      current
   DESCRIPTION
       "Counts the number of frames that match this ACE. "
   ::= { gs2310pACLPortsConfEntry 10 }


gs2310pACLRateLimiterTable OBJECT-TYPE
   SYNTAX      SEQUENCE OF Gs2310pACLRateLimiterEntry
   MAX-ACCESS  not-accessible
   STATUS      current
   DESCRIPTION
       " "
   ::= { gs2310pACL 2 }

gs2310pACLRateLimiterEntry OBJECT-TYPE
   SYNTAX      Gs2310pACLRateLimiterEntry
   MAX-ACCESS  not-accessible
   STATUS      current
   DESCRIPTION
       ""
   INDEX    { gs2310pACLRateLimiterID  }
   ::= { gs2310pACLRateLimiterTable 1 }

Gs2310pACLRateLimiterEntry ::= SEQUENCE {
   gs2310pACLRateLimiterID       Integer32,
   gs2310pACLRateLimiterUnit     INTEGER,
   gs2310pACLRateLimiterRate     Integer32
}

gs2310pACLRateLimiterID OBJECT-TYPE
   SYNTAX      Integer32 (1..12)
   MAX-ACCESS  not-accessible
   STATUS      current
   DESCRIPTION
       " Rate Limiter ID.
         range : 1-12 "
   ::= { gs2310pACLRateLimiterEntry 1 }

gs2310pACLRateLimiterUnit OBJECT-TYPE
   SYNTAX      INTEGER { pps(0), kbps(1) }
   MAX-ACCESS  read-write
   STATUS      current
   DESCRIPTION
       "default: 0,
        0: pps
        1: kbps"
   ::= { gs2310pACLRateLimiterEntry 2 }

gs2310pACLRateLimiterRate OBJECT-TYPE
   SYNTAX      Integer32(0..3276700)
   MAX-ACCESS  read-write
   STATUS      current
   DESCRIPTION
       "default: 1,
        range : <0-3276700> pps
                <0-10000> kbps"
   ::= { gs2310pACLRateLimiterEntry 3 }


gs2310pACLACE                                          OBJECT IDENTIFIER ::= { gs2310pACL 3 }

gs2310pACLACECreate OBJECT-TYPE
   SYNTAX       INTEGER { none(0), create(1) }
   MAX-ACCESS   read-write
   STATUS       current
   DESCRIPTION
       "default: 0
        0 : None  (read only)
        1 : Create an ACE entry"
   ::= { gs2310pACLACE 1 }

gs2310pACLACETable OBJECT-TYPE
   SYNTAX      SEQUENCE OF Gs2310pACLACEEntry
   MAX-ACCESS  not-accessible
   STATUS      current
   DESCRIPTION
       " Create ACL ACE entry. "
   ::= { gs2310pACLACE 2 }

gs2310pACLACEEntry OBJECT-TYPE
   SYNTAX      Gs2310pACLACEEntry
   MAX-ACCESS  not-accessible
   STATUS      current
   DESCRIPTION
       ""
   INDEX    { gs2310pACLACEIndex  }
   ::= { gs2310pACLACETable 1 }

Gs2310pACLACEEntry ::= SEQUENCE {
   gs2310pACLACEIndex                Integer32,
   gs2310pACLACEID                   Integer32,
   gs2310pACLACENextID               Integer32,
   gs2310pACLACEIngressPort          DisplayString,
   gs2310pACLACEPortPolicyNumber     Integer32,

   gs2310pACLACEPortPolicyBitmask    Integer32,
   gs2310pACLACEFrameType            INTEGER,
   gs2310pACLACEAction               INTEGER,
   gs2310pACLACEDenyPortRedirect     DisplayString,
   gs2310pACLACELogging              INTEGER,

   gs2310pACLACEMirror               INTEGER,
   gs2310pACLACERateLimiter          Integer32,
   gs2310pACLACEShutdown             INTEGER,
   gs2310pACLACEVLAN8021QTagged      INTEGER,
   gs2310pACLACEVLANTagPriority      Integer32,

   gs2310pACLACEVLANVID              Integer32,
   gs2310pACLACEEtherType            Integer32,
   gs2310pACLACESMAC                 DisplayString,
   gs2310pACLACEDMACType             INTEGER,
   gs2310pACLACEDMAC                 DisplayString,

   gs2310pACLACEArpOpcode            INTEGER,
   gs2310pACLACEArpFlagsRequestReply INTEGER,
   gs2310pACLACEArpFlagsArpSmac      INTEGER,
   gs2310pACLACEArpFlagsRarpDmac     INTEGER,
   gs2310pACLACEArpFlagsLength       INTEGER,

   gs2310pACLACEArpFlagsIp           INTEGER,
   gs2310pACLACEArpFlagsEthernet     INTEGER,
   gs2310pACLACESIPType              INTEGER,
   gs2310pACLACESIPIPAddress         IpAddress,
   gs2310pACLACESIPNetworkPrefix     Integer32,

   gs2310pACLACEDIPType              INTEGER,
   gs2310pACLACEDIPIPAddress         IpAddress,
   gs2310pACLACEDIPNetworkPrefix     Integer32,

   gs2310pACLACEIPProtocol           Integer32,
   gs2310pACLACEIPFlagsTTL           INTEGER,
   gs2310pACLACEIPFlagsOptions       INTEGER,
   gs2310pACLACEIPFlagsFragment      INTEGER,
   gs2310pACLACEICMPType             Integer32,

   gs2310pACLACEICMPCode             Integer32,
   gs2310pACLACESourcePortMin        Integer32,
   gs2310pACLACESourcePortMax        Integer32,
   gs2310pACLACEDestPortMin          Integer32,
   gs2310pACLACEDestPortMax          Integer32,

   gs2310pACLACETCPFlagsFin          INTEGER,
   gs2310pACLACETCPFlagsSyn          INTEGER,
   gs2310pACLACETCPFlagsRst          INTEGER,
   gs2310pACLACETCPFlagsPsh          INTEGER,
   gs2310pACLACETCPFlagsAck          INTEGER,

   gs2310pACLACETCPFlagsUrg          INTEGER,

   gs2310pACLACERowStatus            INTEGER
}

gs2310pACLACEIndex OBJECT-TYPE
   SYNTAX      Integer32(1..256)
   MAX-ACCESS  not-accessible
   STATUS      current
   DESCRIPTION
       " "
   ::= { gs2310pACLACEEntry 1 }

gs2310pACLACEID OBJECT-TYPE
   SYNTAX      Integer32(1..256)
   MAX-ACCESS  read-write
   STATUS      current
   DESCRIPTION
       " If the ACE ID is specified and an entry with this ACE ID
         already exists, the ACE will be modified. Otherwise, a
         new ACE will be added.
         range : 1 - 256. "
   ::= { gs2310pACLACEEntry 2 }

gs2310pACLACENextID OBJECT-TYPE
   SYNTAX      Integer32 (0..256)
   MAX-ACCESS  read-write
   STATUS      current
   DESCRIPTION
       " If the next ACE ID is non zero, the ACE will be placed
         before this ACE in the list. If the next ACE ID is zero,
         the ACE will be placed last in the list.
         range : 0 - 256. "
   ::= { gs2310pACLACEEntry 3 }

gs2310pACLACEIngressPort OBJECT-TYPE
   SYNTAX      DisplayString
   MAX-ACCESS  read-write
   STATUS      current
   DESCRIPTION
       " Indicates the ingress port of the ACE. Possible values are:
         All: The ACE will match all ingress port.
         Port: The ACE will match a specific ingress port.Format: 1,3,6."
   ::= { gs2310pACLACEEntry 4 }

gs2310pACLACEPortPolicyNumber OBJECT-TYPE
   SYNTAX      Integer32(0..255)
   MAX-ACCESS  read-write
   STATUS      current
   DESCRIPTION
       " policy value.
         range : 0 - 255. "
   ::= { gs2310pACLACEEntry 5 }

gs2310pACLACEPortPolicyBitmask OBJECT-TYPE
   SYNTAX      Integer32(0..255)
   MAX-ACCESS  read-write
   STATUS      current
   DESCRIPTION
       " policy bitmask.
         range : 0 - 255(0xff). "
   ::= { gs2310pACLACEEntry 6 }

gs2310pACLACEFrameType OBJECT-TYPE
   SYNTAX      INTEGER {
                        any(0),
                        arp(1),
                        etype(2),
                        icmp(3),
                        ipv4(4),
                        tcp(5),
                        udp(6)
                        }
   MAX-ACCESS  read-write
   STATUS      current
   DESCRIPTION
       " 0: any,
         1: arp,
         2: etype,
         3: icmp,
         4: ipv4,
         5: tcp,
         6: udp."
   ::= { gs2310pACLACEEntry 7 }

gs2310pACLACEAction OBJECT-TYPE
   SYNTAX      INTEGER { deny(0), permit(1) }
   MAX-ACCESS  read-write
   STATUS      current
   DESCRIPTION
       "default: 1,
        0: Deny
        1: Permit"
   ::= { gs2310pACLACEEntry 8 }

gs2310pACLACEDenyPortRedirect OBJECT-TYPE
   SYNTAX      DisplayString
   MAX-ACCESS  read-write
   STATUS      current
   DESCRIPTION
       " Frames that hit the ACE are redirected to the port number specified here.
         Disabled: indicates that the port redirect operation is disabled.
         Port Format: 1,3,6."
   ::= { gs2310pACLACEEntry 9 }

gs2310pACLACELogging OBJECT-TYPE
   SYNTAX      INTEGER { disable(0), enable(1) }
   MAX-ACCESS  read-write
   STATUS      current
   DESCRIPTION
       "default: 0,
        0: disable - Frames matching the ACE are not logged.
        1: enable - Frames matching the ACE are stored in the system log."
   ::= { gs2310pACLACEEntry 10 }

gs2310pACLACEMirror OBJECT-TYPE
   SYNTAX      INTEGER { disable(0), enable(1) }
   MAX-ACCESS  read-write
   STATUS      current
   DESCRIPTION
       "default: 0,
        0: disable - Frames matching the ACE are not mirrored.
        1: enable - Frames matching the ACE are mirrored."
   ::= { gs2310pACLACEEntry 11 }

gs2310pACLACERateLimiter OBJECT-TYPE
   SYNTAX      Integer32(0..12)
   MAX-ACCESS  read-write
   STATUS      current
   DESCRIPTION
       "default: 0,
        0: Disable
        range : 0 - 12 "
   ::= { gs2310pACLACEEntry 12 }

gs2310pACLACEShutdown OBJECT-TYPE
   SYNTAX      INTEGER { disable(0), enable(1) }
   MAX-ACCESS  read-write
   STATUS      current
   DESCRIPTION
       "default: 0,
        0: disable - Port shut down is disabled for the AC.
        1: enable - If a frame matches the ACE, the ingress port will be disabled."
   ::= { gs2310pACLACEEntry 13 }

gs2310pACLACEVLAN8021QTagged OBJECT-TYPE
   SYNTAX      INTEGER { disable(0), enable(1), any(2) }
   MAX-ACCESS  read-write
   STATUS      current
   DESCRIPTION
       "Specify whether frames can hit the action according to the 802.1Q tagged.
        default: 2,
        0: disable - Untagged frame only.
        1: enable - Tagged frame only.
        2: Any - Any value is allowed. "
   ::= { gs2310pACLACEEntry 14 }

gs2310pACLACEVLANTagPriority OBJECT-TYPE
   SYNTAX      Integer32(0..8)
   MAX-ACCESS  read-write
   STATUS      current
   DESCRIPTION
       "Specify the tag priority for this ACE.
        The tag priority can't be set when 802.1Q Tagged is disabled
        default: 8,
        8: Any,
        range : 0 - 8 "
   ::= { gs2310pACLACEEntry 15 }

gs2310pACLACEVLANVID OBJECT-TYPE
   SYNTAX      Integer32(0..4094)
   MAX-ACCESS  read-write
   STATUS      current
   DESCRIPTION
       "Specify the VLAN ID filter for this ACE.
        The vid can't be set when 802.1Q Tagged is disabled.
        default: 0,
        0: Any - No VLAN ID filter is specified.
        range : 0 - 4094 "
   ::= { gs2310pACLACEEntry 16 }

gs2310pACLACEEtherType OBJECT-TYPE
   SYNTAX      Integer32(0..65535)
   MAX-ACCESS  read-write
   STATUS      current
   DESCRIPTION
       " 0: Any - Any but excluding 0x0800(IPv4) 0x0806(ARP) and 0x86DD(IPv6).
         range : 0 or 1536(0x0600)- 65535(0xffff). "
   ::= { gs2310pACLACEEntry 17 }

gs2310pACLACESMAC OBJECT-TYPE
   SYNTAX      DisplayString
   MAX-ACCESS  read-write
   STATUS      current
   DESCRIPTION
       " Configure source MAC address for this ACE.
         <mac-address>: A frame that hits this ACE matches this source MAC address value.
         Any: Don't care."
   ::= { gs2310pACLACEEntry 18 }

gs2310pACLACEDMACType OBJECT-TYPE
   SYNTAX      INTEGER { any(0), broadcast(1), unicast(2), multicast(3) , macAddress(4) }
   MAX-ACCESS  read-write
   STATUS      current
   DESCRIPTION
       "DMAC Type.
        default: 0,
        0: Any - Don't care.
        1: Broadcast - Frame must be broadcast.
        2: Unicast - Frame must be unicast.
        3: Multicast - Frame must be multicast.
        4: mac address.
        range : 0 - 4 "
   ::= { gs2310pACLACEEntry 19 }

gs2310pACLACEDMAC OBJECT-TYPE
   SYNTAX      DisplayString
   MAX-ACCESS  read-write
   STATUS      current
   DESCRIPTION
       " Configure destination MAC address for this ACE.
         <mac-address>: A frame that hits this ACE matches this destination MAC address value.
         Any: Don't care.
         Broadcast: Frame must be broadcast.
         Unicast: Frame must be unicast.
         Multicast: Frame must be multicast. "
   ::= { gs2310pACLACEEntry 20 }

gs2310pACLACEArpOpcode OBJECT-TYPE
   SYNTAX      INTEGER { any(0), arp(1), rarp(2), other(3), noData(4) }
   MAX-ACCESS  read-write
   STATUS      current
   DESCRIPTION
       "Configure ARP opcode for this ACE.
        default: 0,
        0: Any - Don't care.
        1: arp.
        2: rarp.
        3: other.
        4: No data.
        range : 0 - 4 "
   ::= { gs2310pACLACEEntry 21 }

gs2310pACLACEArpFlagsRequestReply OBJECT-TYPE
   SYNTAX      INTEGER { reply(0), request(1), any(2), noData(3)}
   MAX-ACCESS  read-write
   STATUS      current
   DESCRIPTION
       "Specify the available ARP/RARP opcode (OP) flag for this ACE.
        default: 2,
        0: Frame must have ARP Reply or RARP Reply OP flag.
        1: Frame must have ARP Request or RARP Request OP flag set.
        2: Any - Don't care.
        3: No data.
        range : 0 - 3 "
   ::= { gs2310pACLACEEntry 22 }

gs2310pACLACEArpFlagsArpSmac OBJECT-TYPE
   SYNTAX      INTEGER { notEqualSMAC(0), equalSMAC(1), any(2), noData(3)}
   MAX-ACCESS  read-write
   STATUS      current
   DESCRIPTION
       "Specify whether frames can hit the action according to their sender hardware address field (SHA) settings.
        default: 2,
        0: ARP frames where SHA is not equal to the SMAC address.
        1: ARP frames where SHA is equal to the SMAC address.
        2: Any - Don't care.
        3: No data.
        range : 0 - 3 "
   ::= { gs2310pACLACEEntry 23 }

gs2310pACLACEArpFlagsRarpDmac OBJECT-TYPE
   SYNTAX      INTEGER { notEqualDMAC(0), equalDMAC(1), any(2), noData(3)}
   MAX-ACCESS  read-write
   STATUS      current
   DESCRIPTION
       "Specify whether frames can hit the action according to their target hardware address field (THA) settings.
        default: 2,
        0: RARP frames where THA is not equal to the DMAC address.
        1: RARP frames where THA is equal to the DMAC address.
        2: Any - Don't care.
        3: No data.
        range : 0 - 3 "
   ::= { gs2310pACLACEEntry 24 }

gs2310pACLACEArpFlagsLength OBJECT-TYPE
   SYNTAX      INTEGER(0..3)
   MAX-ACCESS  read-write
   STATUS      current
   DESCRIPTION
       "Specify whether frames can hit the action according to their ARP/RARP hardware address length (HLN) and
        protocol address length (PLN) settings.
        default: 2,
        0: ARP/RARP frames where the HLN is not equal to Ethernet(0x06) or the (PLN) is not equal to IPv4(0x04).
        1: ARP/RARP frames where the HLN is equal to Ethernet (0x06) and the (PLN) is equal to IPv4(0x04).
        2: Any - Don't care.
        3: No data.
        range : 0 - 3 "
   ::= { gs2310pACLACEEntry 25 }

gs2310pACLACEArpFlagsIp OBJECT-TYPE
   SYNTAX      INTEGER(0..3)
   MAX-ACCESS  read-write
   STATUS      current
   DESCRIPTION
       "Specify whether frames can hit the action according to their ARP/RARP hardware address space (HRD) settings.
        default: 2,
        0: ARP/RARP frames where the HLD is not equal to Ethernet(1).
        1: ARP/RARP frames where the HLD is equal to Ethernet(1).
        2: Any - Don't care.
        3: No data.
        range : 0 - 3 "
   ::= { gs2310pACLACEEntry 26 }

gs2310pACLACEArpFlagsEthernet OBJECT-TYPE
   SYNTAX      INTEGER(0..3)
   MAX-ACCESS  read-write
   STATUS      current
   DESCRIPTION
       "Specify whether frames can hit the action according to their ARP/RARP protocol address space (PRO) settings.
        default: 2,
        0: ARP/RARP frames where the PRO is not equal to IP\n(0x800).
        1: ARP/RARP frames where the PRO is equal to IP(0x800).
        2: Any - Don't care.
        3: No data.
        range : 0 - 3 "
   ::= { gs2310pACLACEEntry 27 }

gs2310pACLACESIPType OBJECT-TYPE
   SYNTAX      INTEGER { any(0), ip(1), noData(2) }
   MAX-ACCESS  read-write
   STATUS      current
   DESCRIPTION
       "Configure source IP address for this ACE.
        default: 0,
        0: Any - Don't care.
        1: IP Address.
        2: No data.
        range : 0 - 1"
   ::= { gs2310pACLACEEntry 28 }

gs2310pACLACESIPIPAddress OBJECT-TYPE
   SYNTAX      IpAddress
   MAX-ACCESS  read-write
   STATUS      current
   DESCRIPTION
       "A frame that hits this ACE matches this source IP address value."
   ::= { gs2310pACLACEEntry 29 }

gs2310pACLACESIPNetworkPrefix OBJECT-TYPE
   SYNTAX      Integer32(0..32)
   MAX-ACCESS  read-write
   STATUS      current
   DESCRIPTION
       "Network prefix.
        default: 32,
        0: No data.
        range : 1 - 32"
   ::= { gs2310pACLACEEntry 30 }


gs2310pACLACEDIPType OBJECT-TYPE
   SYNTAX      INTEGER { any(0), ip(1),noData(2) }
   MAX-ACCESS  read-write
   STATUS      current
   DESCRIPTION
       "Configure destination IP address for this ACE.
        default: 0,
        0: Any - Don't care.
        1: IP Address.
        2: No data.
        range : 0 - 1"
   ::= { gs2310pACLACEEntry 32 }

gs2310pACLACEDIPIPAddress OBJECT-TYPE
   SYNTAX      IpAddress
   MAX-ACCESS  read-write
   STATUS      current
   DESCRIPTION
       "A frame that hits this ACE matches this destination IP address value."
   ::= { gs2310pACLACEEntry 33 }

gs2310pACLACEDIPNetworkPrefix OBJECT-TYPE
   SYNTAX      Integer32(0..32)
   MAX-ACCESS  read-write
   STATUS      current
   DESCRIPTION
       "Network prefix.
        default: 32,
        0: No data.
        range : 1 - 32"
   ::= { gs2310pACLACEEntry 34 }


gs2310pACLACEIPProtocol OBJECT-TYPE
   SYNTAX      Integer32(0..257)
   MAX-ACCESS  read-write
   STATUS      current
   DESCRIPTION
       "Configure IP protocol for this ACE.
        default: 256,
        256: Any - Don't care.
        257: No data.
        range : 0 - 256"
   ::= { gs2310pACLACEEntry 36 }

gs2310pACLACEIPFlagsTTL OBJECT-TYPE
   SYNTAX      INTEGER (0..3)
   MAX-ACCESS  read-write
   STATUS      current
   DESCRIPTION
       "Configure IP Time-to-Live flags for this ACE.
        default: 2,
        0: IPv4 frames with a Time-to-Live field is equal to zero.
        1: IPv4 frames with a Time-to-Live field greater than zero.
        2: Any - Don't care.
        3: No data.
        range : 0 - 3 "
   ::= { gs2310pACLACEEntry 37 }

gs2310pACLACEIPFlagsOptions OBJECT-TYPE
   SYNTAX      INTEGER { unset(0), set(1), any(2), noData(3) }
   MAX-ACCESS  read-write
   STATUS      current
   DESCRIPTION
       "Configure IP options flag for this ACE.
        default: 2,
        0: IPv4 frames where the options flag is unset.
        1: IPv4 frames where the options flag is set.
        2: Any - Don't care.
        3: No data.
        range : 0 - 3 "
   ::= { gs2310pACLACEEntry 38 }

gs2310pACLACEIPFlagsFragment OBJECT-TYPE
   SYNTAX      INTEGER(0..3)
   MAX-ACCESS  read-write
   STATUS      current
   DESCRIPTION
       "Configure IP fragment offset flags for this ACE.
        default: 2,
        0: IPv4 frames where the MF bit is unset and the FRAG OFFSET field is equal zero.
        1: IPv4 frames where the MF bit is set or the FRAG OFFSET field is greater than zero.
        2: Any - Don't care.
        3: No data.
        range : 0 - 3 "
   ::= { gs2310pACLACEEntry 39 }

gs2310pACLACEICMPType OBJECT-TYPE
   SYNTAX      Integer32(0..257)
   MAX-ACCESS  read-write
   STATUS      current
   DESCRIPTION
       "Configure ICMP type for this ACE.
        default: 256,
        256: Any - Don't care.
        257: No data.
        range : 0 - 256"
   ::= { gs2310pACLACEEntry 40 }

gs2310pACLACEICMPCode OBJECT-TYPE
   SYNTAX      Integer32(0..257)
   MAX-ACCESS  read-write
   STATUS      current
   DESCRIPTION
       "Configure ICMP code for this ACE.
        default: 256,
        256: Any - Don't care.
        257: No data.
        range : 0 - 257"
   ::= { gs2310pACLACEEntry 41 }

gs2310pACLACESourcePortMin OBJECT-TYPE
   SYNTAX      Integer32(0..65536)
   MAX-ACCESS  read-write
   STATUS      current
   DESCRIPTION
       "Configure Source UDP/TCP port range for this ACE.
        default: 0,
        65536: No data.
        range : 0 - 65536"
   ::= { gs2310pACLACEEntry 42 }

gs2310pACLACESourcePortMax OBJECT-TYPE
   SYNTAX      Integer32(0..65536)
   MAX-ACCESS  read-write
   STATUS      current
   DESCRIPTION
       "Configure Source UDP/TCP port range for this ACE.
        default: 0,
        65536: No data.
        range : 0 - 65536"
   ::= { gs2310pACLACEEntry 43 }

gs2310pACLACEDestPortMin OBJECT-TYPE
   SYNTAX      Integer32(0..65536)
   MAX-ACCESS  read-write
   STATUS      current
   DESCRIPTION
       "Configure Destination UDP/TCP port range for this ACE.
        default: 0,
        65536: No data.
        range : 0 - 65535"
   ::= { gs2310pACLACEEntry 44 }

gs2310pACLACEDestPortMax OBJECT-TYPE
   SYNTAX      Integer32(0..65536)
   MAX-ACCESS  read-write
   STATUS      current
   DESCRIPTION
       "Configure Destination UDP/TCP port range for this ACE.
        default: 0,
        65536: No data.
        range : 0 - 65535"
   ::= { gs2310pACLACEEntry 45 }

gs2310pACLACETCPFlagsFin OBJECT-TYPE
   SYNTAX      INTEGER { unset(0), set(1), any(2), noData(3) }
   MAX-ACCESS  read-write
   STATUS      current
   DESCRIPTION
       "Configure TCP (FIN) flags for this ACE.
        default: 2,
        0: TCP frames where the FIN field is unset.
        1: TCP frames where the FIN field is set.
        2: Any - Don't care.
        3: No data.
        range : 0 - 3 "
   ::= { gs2310pACLACEEntry 46 }

gs2310pACLACETCPFlagsSyn OBJECT-TYPE
   SYNTAX      INTEGER { unset(0), set(1), any(2), noData(3) }
   MAX-ACCESS  read-write
   STATUS      current
   DESCRIPTION
       "Configure TCP (SYN) flags for this ACE.
        default: 2,
        0: TCP frames where the SYN field is unset.
        1: TCP frames where the SYN field is set.
        2: Any - Don't care.
        3: No data.
        range : 0 - 3 "
   ::= { gs2310pACLACEEntry 47 }

gs2310pACLACETCPFlagsRst OBJECT-TYPE
   SYNTAX      INTEGER { unset(0), set(1), any(2), noData(3) }
   MAX-ACCESS  read-write
   STATUS      current
   DESCRIPTION
       "Configure TCP (RST) flags for this ACE.
        default: 2,
        0: TCP frames where the RST field is unset.
        1: TCP frames where the RST field is set.
        2: Any - Don't care.
        3: No data.
        range : 0 - 3 "
   ::= { gs2310pACLACEEntry 48 }

gs2310pACLACETCPFlagsPsh OBJECT-TYPE
   SYNTAX      INTEGER { unset(0), set(1), any(2), noData(3) }
   MAX-ACCESS  read-write
   STATUS      current
   DESCRIPTION
       "Configure TCP (PSH) flags for this ACE.
        default: 2,
        0: TCP frames where the PSH field is unset.
        1: TCP frames where the PSH field is set.
        2: Any - Don't care.
        3: No data.
        range : 0 - 3 "
   ::= { gs2310pACLACEEntry 49 }

gs2310pACLACETCPFlagsAck OBJECT-TYPE
   SYNTAX      INTEGER { unset(0), set(1), any(2), noData(3) }
   MAX-ACCESS  read-write
   STATUS      current
   DESCRIPTION
       "Configure TCP (ACK) flags for this ACE.
        default: 2,
        0: TCP frames where the ACK field is unset.
        1: TCP frames where the ACK field is set.
        2: Any - Don't care.
        3: No data.
        range : 0 - 3 "
   ::= { gs2310pACLACEEntry 50 }

gs2310pACLACETCPFlagsUrg OBJECT-TYPE
   SYNTAX      INTEGER { unset(0), set(1), any(2), noData(3) }
   MAX-ACCESS  read-write
   STATUS      current
   DESCRIPTION
       "Configure TCP (URG) flags for this ACE.
        default: 2,
        0: TCP frames where the URG field is unset.
        1: TCP frames where the URG field is set.
        2: Any - Don't care.
        3: No data.
        range : 0 - 3 "
   ::= { gs2310pACLACEEntry 51 }

gs2310pACLACERowStatus OBJECT-TYPE
   SYNTAX      INTEGER { active(1), notInservice(2), destroy(4), undo(5) }
   MAX-ACCESS  read-write
   STATUS      current
   DESCRIPTION
       " 1: active
         2: notInservice
         4: destroy
         5: undo"
   ::= { gs2310pACLACEEntry 66 }


gs2310pACLACEClear OBJECT-TYPE
   SYNTAX       INTEGER { noAction(0), clear(1) }
   MAX-ACCESS   read-write
   STATUS       current
   DESCRIPTION
       "default: 0
        0 : No action
        1 : Clear all ACL counters."
   ::= { gs2310pACLACE 3 }

gs2310pACLACEMoveACEID OBJECT-TYPE
   SYNTAX       Integer32(0..256)
   MAX-ACCESS   read-write
   STATUS       current
   DESCRIPTION
       "Move ACE,
        default: 0
        ACE ID must be exist.
        range : 1 - 256."
   ::= { gs2310pACLACE 4 }

gs2310pACLACEMoveNextACEID OBJECT-TYPE
   SYNTAX       Integer32(0..256)
   MAX-ACCESS   read-write
   STATUS       current
   DESCRIPTION
       "Move ACE,
        default: 0
        If the next ACE ID is non zero, the ACE will be placed before this ACE in the list. If the next ACE ID is zero,
        the ACE will be placed last in the list.
        range : 0 - 256."
   ::= { gs2310pACLACE 5 }

gs2310pACLACEStatusTable OBJECT-TYPE
   SYNTAX      SEQUENCE OF Gs2310pACLACEStatusEntry
   MAX-ACCESS  not-accessible
   STATUS      current
   DESCRIPTION
       " ACL ACE Status entry. "
   ::= { gs2310pACLACE 6 }

gs2310pACLACEStatusEntry OBJECT-TYPE
   SYNTAX      Gs2310pACLACEStatusEntry
   MAX-ACCESS  not-accessible
   STATUS      current
   DESCRIPTION
       ""
   INDEX    { gs2310pACLACEStatusIndex  }
   ::= { gs2310pACLACEStatusTable 1 }

Gs2310pACLACEStatusEntry ::= SEQUENCE {
   gs2310pACLACEStatusIndex          Integer32,
   gs2310pACLACEStatusUser           DisplayString,
   gs2310pACLACEStatusID             Integer32,
   gs2310pACLACEStatusIngressPort    DisplayString,
   gs2310pACLACEStatusFrameType      DisplayString,
   gs2310pACLACEStatusAction         DisplayString,
   gs2310pACLACEStatusRateLimiter    DisplayString,
   gs2310pACLACEStatusPortCopy       DisplayString,
   gs2310pACLACEStatusMirror         DisplayString,
   gs2310pACLACEStatusCPU            DisplayString,
   gs2310pACLACEStatusCounter        Counter32,
   gs2310pACLACEStatusConflict       DisplayString
}

gs2310pACLACEStatusIndex OBJECT-TYPE
   SYNTAX      Integer32(1..256)
   MAX-ACCESS  not-accessible
   STATUS      current
   DESCRIPTION
       " "
   ::= { gs2310pACLACEStatusEntry 1 }

gs2310pACLACEStatusUser OBJECT-TYPE
   SYNTAX      DisplayString
   MAX-ACCESS  read-only
   STATUS      current
   DESCRIPTION
       " Indicates the ACL user.
         S : Static.
         IPMG : IP Management.
         IPSG : IP Source Guard.
         IPMC : IPMC.
         ARPI : Arp Inspection.
         UPnP : UPnP.
         DHCP : DHCP. "
   ::= { gs2310pACLACEStatusEntry 2 }

gs2310pACLACEStatusID OBJECT-TYPE
   SYNTAX      Integer32(1..256)
   MAX-ACCESS  read-only
   STATUS      current
   DESCRIPTION
       " ACE ID.
         range : 1 - 256. "
   ::= { gs2310pACLACEStatusEntry 3 }

gs2310pACLACEStatusIngressPort OBJECT-TYPE
   SYNTAX      DisplayString
   MAX-ACCESS  read-only
   STATUS      current
   DESCRIPTION
       " Indicates the ingress port of the ACE. Possible values are:
         All: The ACE will match all ingress port.
         Port: The ACE will match a specific ingress port. "
   ::= { gs2310pACLACEStatusEntry 4 }

gs2310pACLACEStatusFrameType OBJECT-TYPE
   SYNTAX      DisplayString
   MAX-ACCESS  read-only
   STATUS      current
   DESCRIPTION
       " Indicates the frame type of the ACE. "
   ::= { gs2310pACLACEStatusEntry 5 }

gs2310pACLACEStatusAction OBJECT-TYPE
   SYNTAX      DisplayString
   MAX-ACCESS  read-only
   STATUS      current
   DESCRIPTION
       " Indicates the forwarding action of the ACE. "
   ::= { gs2310pACLACEStatusEntry 6 }

gs2310pACLACEStatusRateLimiter OBJECT-TYPE
   SYNTAX      DisplayString
   MAX-ACCESS  read-only
   STATUS      current
   DESCRIPTION
       " Indicates the rate limiter number of the ACE. "
   ::= { gs2310pACLACEStatusEntry 7 }

gs2310pACLACEStatusPortCopy OBJECT-TYPE
   SYNTAX      DisplayString
   MAX-ACCESS  read-only
   STATUS      current
   DESCRIPTION
       " Indicates the port redirect operation of the ACE. Frames matching the ACE are redirected to the port number. "
   ::= { gs2310pACLACEStatusEntry 8 }

gs2310pACLACEStatusMirror OBJECT-TYPE
   SYNTAX      DisplayString
   MAX-ACCESS  read-only
   STATUS      current
   DESCRIPTION
       " Specify the mirror operation of this port. "
   ::= { gs2310pACLACEStatusEntry 9 }

gs2310pACLACEStatusCPU OBJECT-TYPE
   SYNTAX      DisplayString
   MAX-ACCESS  read-only
   STATUS      current
   DESCRIPTION
       " Forward packet that matched the specific ACE to CPU. "
   ::= { gs2310pACLACEStatusEntry 10 }

gs2310pACLACEStatusCounter OBJECT-TYPE
   SYNTAX      Counter32
   MAX-ACCESS  read-only
   STATUS      current
   DESCRIPTION
       " The counter indicates the number of times the ACE was hit by a frame. "
   ::= { gs2310pACLACEStatusEntry 11 }

gs2310pACLACEStatusConflict OBJECT-TYPE
   SYNTAX      DisplayString
   MAX-ACCESS  read-only
   STATUS      current
   DESCRIPTION
       " Indicates the hardware status of the specific ACE. The specific ACE is not applied to the hardware due to hardware limitations. "
   ::= { gs2310pACLACEStatusEntry 12 }

gs2310pLoopProtection                                                  OBJECT IDENTIFIER ::= { gs2310pConfiguration 12 }

gs2310pLoopProtectionConfig                                            OBJECT IDENTIFIER ::= { gs2310pLoopProtection 1 }

gs2310pLoopProtectionGlobalEnable OBJECT-TYPE
   SYNTAX      INTEGER { disable(0), enable(1) }
   MAX-ACCESS  read-write
   STATUS      current
   DESCRIPTION
       "Configure loop protection mode.
        0: disable,
        1: enable,
        default: disable. "
   ::= { gs2310pLoopProtectionConfig 1 }

gs2310pLoopProtectionTranmisstionTime OBJECT-TYPE
   SYNTAX      Integer32(1..10)
   MAX-ACCESS  read-write
   STATUS      current
   DESCRIPTION
       "Configure loop protection transmit interval.
        default: 5,
        range: 1-10. "
   ::= { gs2310pLoopProtectionConfig 2 }

gs2310pLoopProtectionShutdownTime OBJECT-TYPE
   SYNTAX      Integer32(0..604800)
   MAX-ACCESS  read-write
   STATUS      current
   DESCRIPTION
       "Configure loop protection shutdown time.
        default: 180,
        range: 0-604800. "
   ::= { gs2310pLoopProtectionConfig 3 }

gs2310pLoopProtectionConfigurationTable OBJECT-TYPE
   SYNTAX      SEQUENCE OF Gs2310pLoopProtectionConfigurationEntry
   MAX-ACCESS  not-accessible
   STATUS      current
   DESCRIPTION
       " Show Loop Protection configurations. "
   ::= { gs2310pLoopProtectionConfig 4 }

gs2310pLoopProtectionConfigurationEntry OBJECT-TYPE
   SYNTAX      Gs2310pLoopProtectionConfigurationEntry
   MAX-ACCESS  not-accessible
   STATUS      current
   DESCRIPTION
       ""
   INDEX    { gs2310pLoopProtectionConfPort  }
   ::= { gs2310pLoopProtectionConfigurationTable 1 }

Gs2310pLoopProtectionConfigurationEntry ::= SEQUENCE {
   gs2310pLoopProtectionConfPort	    Integer32,
   gs2310pLoopProtectionConfEnable	INTEGER,
   gs2310pLoopProtectionConfAction	INTEGER,
   gs2310pLoopProtectionConfTxmode	INTEGER
}

gs2310pLoopProtectionConfPort OBJECT-TYPE
   SYNTAX      Integer32(1..4095)
   MAX-ACCESS  not-accessible
   STATUS      current
   DESCRIPTION
       " port, range : 1 - port number. "
   ::= { gs2310pLoopProtectionConfigurationEntry 1 }

gs2310pLoopProtectionConfEnable OBJECT-TYPE
   SYNTAX      INTEGER { disable(0), enable(1) }
   MAX-ACCESS  read-write
   STATUS      current
   DESCRIPTION
       "Configure loop protection port mode.
        0: disable,
        1: enable,
        default: enable. "
   ::= { gs2310pLoopProtectionConfigurationEntry 2 }

gs2310pLoopProtectionConfAction OBJECT-TYPE
   SYNTAX      INTEGER { shutdown(0), shutdownLog(1), log(2) }
   MAX-ACCESS  read-write
   STATUS      current
   DESCRIPTION
       " Configure loop protection port action.
         0: Shutdown port,
         1: Shutdown port and Log,
         2: Log Only,
         default: Shutdown port. "
   ::= { gs2310pLoopProtectionConfigurationEntry 3 }

gs2310pLoopProtectionConfTxmode OBJECT-TYPE
   SYNTAX      INTEGER { disable(0), enable(1) }
   MAX-ACCESS  read-write
   STATUS      current
   DESCRIPTION
       "Configure loop protection port transmit mode.
        0: disable,
        1: enable,
        default: enable. "
   ::= { gs2310pLoopProtectionConfigurationEntry 4 }

gs2310pLoopProtectionStatusTable OBJECT-TYPE
   SYNTAX      SEQUENCE OF Gs2310pLoopProtectionStatusEntry
   MAX-ACCESS  not-accessible
   STATUS      current
   DESCRIPTION
       " Show Loop Protection Status. "
   ::= { gs2310pLoopProtection 2 }

gs2310pLoopProtectionStatusEntry OBJECT-TYPE
   SYNTAX      Gs2310pLoopProtectionStatusEntry
   MAX-ACCESS  not-accessible
   STATUS      current
   DESCRIPTION
       ""
   INDEX    { gs2310pLoopProtectionStatusPort  }
   ::= { gs2310pLoopProtectionStatusTable 1 }

Gs2310pLoopProtectionStatusEntry ::= SEQUENCE {
   gs2310pLoopProtectionStatusPort	       Integer32,
   gs2310pLoopProtectionStatusAction	       DisplayString,
   gs2310pLoopProtectionStatusTransmit	   DisplayString,
   gs2310pLoopProtectionStatusLoops	       Integer32,
   gs2310pLoopProtectionStatusStatus	       DisplayString,
   gs2310pLoopProtectionStatusLoop	       DisplayString,
   gs2310pLoopProtectionStatusTimeLastLoop  DisplayString
}

gs2310pLoopProtectionStatusPort OBJECT-TYPE
   SYNTAX      Integer32(1..4095)
   MAX-ACCESS  not-accessible
   STATUS      current
   DESCRIPTION
       " port, range : 1 - port number. "
   ::= { gs2310pLoopProtectionStatusEntry 1 }

gs2310pLoopProtectionStatusAction OBJECT-TYPE
   SYNTAX      DisplayString
   MAX-ACCESS  read-only
   STATUS      current
   DESCRIPTION
       " The currently configured port action. "
   ::= { gs2310pLoopProtectionStatusEntry 2 }

gs2310pLoopProtectionStatusTransmit OBJECT-TYPE
   SYNTAX      DisplayString
   MAX-ACCESS  read-only
   STATUS      current
   DESCRIPTION
       " The currently configured port transmit mode. "
   ::= { gs2310pLoopProtectionStatusEntry 3 }

gs2310pLoopProtectionStatusLoops OBJECT-TYPE
   SYNTAX      Integer32(0..1000000)
   MAX-ACCESS  read-only
   STATUS      current
   DESCRIPTION
       " The number of loops detected on this port. "
   ::= { gs2310pLoopProtectionStatusEntry 4 }

gs2310pLoopProtectionStatusStatus OBJECT-TYPE
   SYNTAX      DisplayString
   MAX-ACCESS  read-only
   STATUS      current
   DESCRIPTION
       " The current loop protection status of the port. "
   ::= { gs2310pLoopProtectionStatusEntry 5 }

gs2310pLoopProtectionStatusLoop OBJECT-TYPE
   SYNTAX      DisplayString
   MAX-ACCESS  read-only
   STATUS      current
   DESCRIPTION
       " Whether a loop is currently detected on the port. "
   ::= { gs2310pLoopProtectionStatusEntry 6 }

gs2310pLoopProtectionStatusTimeLastLoop OBJECT-TYPE
   SYNTAX      DisplayString
   MAX-ACCESS  read-only
   STATUS      current
   DESCRIPTION
       " The time of the last loop event detected. "
   ::= { gs2310pLoopProtectionStatusEntry 7 }

gs2310pPoe                                                           OBJECT IDENTIFIER ::= { gs2310pConfiguration 13 }

gs2310pPoeStatus                                            OBJECT IDENTIFIER ::= { gs2310pPoe 1 }

gs2310pPoeStatusTable OBJECT-TYPE
   SYNTAX      SEQUENCE OF Gs2310pPoeStatusEntry
   MAX-ACCESS  not-accessible
   STATUS      current
   DESCRIPTION
       " Configure PoE Scheduling Table. "
   ::= { gs2310pPoeStatus 1 }

gs2310pPoeStatusEntry OBJECT-TYPE
   SYNTAX      Gs2310pPoeStatusEntry
   MAX-ACCESS  not-accessible
   STATUS      current
   DESCRIPTION
       ""
   INDEX    { gs2310pPoeStatusLocalPort }
   ::= { gs2310pPoeStatusTable 1 }

Gs2310pPoeStatusEntry ::= SEQUENCE {
   gs2310pPoeStatusLocalPort	        Integer32,
   gs2310pPoeStatusPDclass	        INTEGER,
   gs2310pPoeStatusPowerRequested	    DisplayString,
   gs2310pPoeStatusPowerAllocated     DisplayString,
   gs2310pPoeStatusPowerUsed          DisplayString,
   gs2310pPoeStatusCurrentUsed        DisplayString,
   gs2310pPoeStatusPriority           DisplayString,
   gs2310pPoeStatusPortStatus         DisplayString
}

gs2310pPoeStatusLocalPort OBJECT-TYPE
   SYNTAX      Integer32(1..4094)
   MAX-ACCESS  not-accessible
   STATUS      current
   DESCRIPTION
       " port, range : 1 - port number. "
   ::= { gs2310pPoeStatusEntry 1}

gs2310pPoeStatusPDclass OBJECT-TYPE
   SYNTAX      INTEGER (0..4)
   MAX-ACCESS  read-only
   STATUS      current
   DESCRIPTION
       " Indicates the QCL user.
         0: Max. power 15.4 W,
         1: Max. power 4.0 W,
         2: Max. power 7.0 W,
         3: Max. power 15.4 W,
         4: Max. power 30.0 W. "
   ::= { gs2310pPoeStatusEntry 2 }

gs2310pPoeStatusPowerRequested OBJECT-TYPE
   SYNTAX      DisplayString
   MAX-ACCESS  read-only
   STATUS      current
   DESCRIPTION
      " The Power Requested shows the requested amount of power the PD wants to be reserved. "
   ::= { gs2310pPoeStatusEntry 3}

gs2310pPoeStatusPowerAllocated OBJECT-TYPE
   SYNTAX      DisplayString
   MAX-ACCESS  read-only
   STATUS      current
   DESCRIPTION
      " The Power Allocated shows the amount of power the switch has allocated for the PD. "
   ::= { gs2310pPoeStatusEntry 4}

gs2310pPoeStatusPowerUsed OBJECT-TYPE
   SYNTAX      DisplayString
   MAX-ACCESS  read-only
   STATUS      current
   DESCRIPTION
      " The Power Used shows how much power the PD currently is using. "
   ::= { gs2310pPoeStatusEntry 5}

gs2310pPoeStatusCurrentUsed OBJECT-TYPE
   SYNTAX      DisplayString
   MAX-ACCESS  read-only
   STATUS      current
   DESCRIPTION
      " The Power Used shows how much current the PD currently is using. "
   ::= { gs2310pPoeStatusEntry 6}

gs2310pPoeStatusPriority OBJECT-TYPE
   SYNTAX      DisplayString
   MAX-ACCESS  read-only
   STATUS      current
   DESCRIPTION
      " The Priority shows the port's priority configured by the user.  "
   ::= { gs2310pPoeStatusEntry 7}

gs2310pPoeStatusPortStatus OBJECT-TYPE
   SYNTAX      DisplayString
   MAX-ACCESS  read-only
   STATUS      current
   DESCRIPTION
      " The Port Status shows the port's status.  "
   ::= { gs2310pPoeStatusEntry 8}


gs2310pPoeStatusTotalPowerRequested OBJECT-TYPE
   SYNTAX      DisplayString
   MAX-ACCESS  read-only
   STATUS      current
   DESCRIPTION
      " Total Power Requested."
   ::= { gs2310pPoeStatus 2}

gs2310pPoeStatusTotalPowerAllocated OBJECT-TYPE
   SYNTAX      DisplayString
   MAX-ACCESS  read-only
   STATUS      current
   DESCRIPTION
      " Total Power allocated."
   ::= { gs2310pPoeStatus 3}

gs2310pPoeStatusTotalPowerUsed OBJECT-TYPE
   SYNTAX      DisplayString
   MAX-ACCESS  read-only
   STATUS      current
   DESCRIPTION
      " Total Power Used."
   ::= { gs2310pPoeStatus 4}

gs2310pPoeStatusTotalCurrentUsed OBJECT-TYPE
   SYNTAX      DisplayString
   MAX-ACCESS  read-only
   STATUS      current
   DESCRIPTION
      " Total Current Used."
   ::= { gs2310pPoeStatus 5}

gs2310pPoeMcuVersion OBJECT-TYPE
   SYNTAX      DisplayString
   MAX-ACCESS  read-only
   STATUS      current
   DESCRIPTION
      " PoE MCU version."
   ::= { gs2310pPoeStatus 6 }

gs2310pPoePowerDelay                                                 OBJECT IDENTIFIER ::= { gs2310pPoe 2 }

gs2310pPoePowerDelayTable OBJECT-TYPE
   SYNTAX      SEQUENCE OF Gs2310pPoePowerDelayEntry
   MAX-ACCESS  not-accessible
   STATUS      current
   DESCRIPTION
       " Configure PoE Power Delay mode. "
   ::= { gs2310pPoePowerDelay 1 }

gs2310pPoePowerDelayEntry OBJECT-TYPE
   SYNTAX      Gs2310pPoePowerDelayEntry
   MAX-ACCESS  not-accessible
   STATUS      current
   DESCRIPTION
       ""
   INDEX    { gs2310pPoePowerDelayPort  }
   ::= { gs2310pPoePowerDelayTable 1 }

Gs2310pPoePowerDelayEntry ::= SEQUENCE {
   gs2310pPoePowerDelayPort	        Integer32,
   gs2310pPoePowerDelayMode	        INTEGER,
   gs2310pPoePowerDelayTime         Integer32
}

gs2310pPoePowerDelayPort OBJECT-TYPE
   SYNTAX      Integer32(1..4094)
   MAX-ACCESS  not-accessible
   STATUS      current
   DESCRIPTION
       " port, range : 1 - port number. "
   ::= { gs2310pPoePowerDelayEntry 1 }

gs2310pPoePowerDelayMode OBJECT-TYPE
   SYNTAX      INTEGER { disable(0), enable(1) }
   MAX-ACCESS  read-write
   STATUS      current
   DESCRIPTION
       "Turn on / off the power delay function,
        0: disable,
        1: enable,
        default: disable. "
   ::= { gs2310pPoePowerDelayEntry 2 }

gs2310pPoePowerDelayTime OBJECT-TYPE
   SYNTAX      Integer32(0..300)
   MAX-ACCESS  read-write
   STATUS      current
   DESCRIPTION
       "set Delay Time,
        default: 0,
        range: 0-300 sec. "
   ::= { gs2310pPoePowerDelayEntry 3 }

gs2310pPoeAutoCheck                                                 OBJECT IDENTIFIER ::= { gs2310pPoe 3 }

gs2310pPoeAutoCheckPingCheck OBJECT-TYPE
   SYNTAX      INTEGER { disable(0), enable(1) }
   MAX-ACCESS  read-write
   STATUS      current
   DESCRIPTION
       "connection between PoE port and power device.
        0: disable,
        1: enable,
        default: disable. "
   ::= { gs2310pPoeAutoCheck 1 }

gs2310pPoeAutoCheckTable OBJECT-TYPE
   SYNTAX      SEQUENCE OF Gs2310pPoeAutoCheckEntry
   MAX-ACCESS  not-accessible
   STATUS      current
   DESCRIPTION
       " Configure PoE Power Delay mode. "
   ::= { gs2310pPoeAutoCheck 2 }

gs2310pPoeAutoCheckEntry OBJECT-TYPE
   SYNTAX      Gs2310pPoeAutoCheckEntry
   MAX-ACCESS  not-accessible
   STATUS      current
   DESCRIPTION
       ""
   INDEX    { gs2310pPoeAutoCheckPort  }
   ::= { gs2310pPoeAutoCheckTable 1 }

Gs2310pPoeAutoCheckEntry ::= SEQUENCE {
   gs2310pPoeAutoCheckPort	       Integer32,
   gs2310pPoeAutoCheckPingIPAddress  DisplayString,
   gs2310pPoeAutoCheckIntervalTime   Integer32,
   gs2310pPoeAutoCheckRetryTime      Integer32,
   gs2310pPoeAutoCheckFailureLog     DisplayString,
   gs2310pPoeAutoCheckFailureAction  INTEGER,
   gs2310pPoeAutoCheckRebootTime     Integer32
}

gs2310pPoeAutoCheckPort OBJECT-TYPE
   SYNTAX      Integer32(1..4094)
   MAX-ACCESS  not-accessible
   STATUS      current
   DESCRIPTION
       " port, range : 1 - port number. "
   ::= { gs2310pPoeAutoCheckEntry 1 }

gs2310pPoeAutoCheckPingIPAddress OBJECT-TYPE
   SYNTAX      DisplayString
   MAX-ACCESS  read-write
   STATUS      current
   DESCRIPTION
       "IP Address the system should ping.
        default: 0.0.0.0 . "
   ::= { gs2310pPoeAutoCheckEntry 2 }

gs2310pPoeAutoCheckIntervalTime OBJECT-TYPE
   SYNTAX      Integer32(10..120)
   MAX-ACCESS  read-write
   STATUS      current
   DESCRIPTION
       "Device will send checking message to PD each interval time.
        default: 30,
        range: 10-120 sec.  "
   ::= { gs2310pPoeAutoCheckEntry 3 }

gs2310pPoeAutoCheckRetryTime OBJECT-TYPE
   SYNTAX      Integer32(1..5)
   MAX-ACCESS  read-write
   STATUS      current
   DESCRIPTION
       "It will retry to send detection again.
        default: 3,
        range: 1-5.  "
   ::= { gs2310pPoeAutoCheckEntry 4 }

gs2310pPoeAutoCheckFailureLog OBJECT-TYPE
   SYNTAX      DisplayString
   MAX-ACCESS  read-only
   STATUS      current
   DESCRIPTION
       "Failure loggings counter. "
   ::= { gs2310pPoeAutoCheckEntry 5 }

gs2310pPoeAutoCheckFailureAction OBJECT-TYPE
   SYNTAX      INTEGER { nothing(0), reboot(1) }
   MAX-ACCESS  read-write
   STATUS      current
   DESCRIPTION
       "It will retry to send detection again,
        0: Nothing,
        1: Reboot Remote PD,
        default: Nothing. "
   ::= { gs2310pPoeAutoCheckEntry 6 }

gs2310pPoeAutoCheckRebootTime OBJECT-TYPE
   SYNTAX      Integer32(3..120)
   MAX-ACCESS  read-write
   STATUS      current
   DESCRIPTION
       "When PD has been rebooted, the PoE port restored power after the specified time.
        default: 15,
        range: 3-120 sec. "
   ::= { gs2310pPoeAutoCheckEntry 7 }

gs2310pPoeScheduling                                                 OBJECT IDENTIFIER ::= { gs2310pPoe 4 }

gs2310pPoeSchedulingTable OBJECT-TYPE
   SYNTAX      SEQUENCE OF Gs2310pPoeSchedulingEntry
   MAX-ACCESS  not-accessible
   STATUS      current
   DESCRIPTION
       " Configure PoE Scheduling Table. "
   ::= { gs2310pPoeScheduling 1 }

gs2310pPoeSchedulingEntry OBJECT-TYPE
   SYNTAX      Gs2310pPoeSchedulingEntry
   MAX-ACCESS  not-accessible
   STATUS      current
   DESCRIPTION
       ""
   INDEX    { gs2310pPoeSchedulingPort }
   ::= { gs2310pPoeSchedulingTable 1 }

Gs2310pPoeSchedulingEntry ::= SEQUENCE {
   gs2310pPoeSchedulingPort	        Integer32,
   gs2310pPoeSchedulingStatus	        INTEGER
}

gs2310pPoeSchedulingPort OBJECT-TYPE
   SYNTAX      Integer32(1..4094)
   MAX-ACCESS  not-accessible
   STATUS      current
   DESCRIPTION
       " port, range : 1 - port number. "
   ::= { gs2310pPoeSchedulingEntry 1 }

gs2310pPoeSchedulingStatus OBJECT-TYPE
   SYNTAX      INTEGER { disable(0), enable(1) }
   MAX-ACCESS  read-write
   STATUS      current
   DESCRIPTION
       "PoE Scheduling Status.
        0: Disable,
        1: Enable,
        default: Disable. "
   ::= { gs2310pPoeSchedulingEntry 2 }

gs2310pPoeSchedulingTimeTable OBJECT-TYPE
   SYNTAX      SEQUENCE OF Gs2310pPoeSchedulingTimeEntry
   MAX-ACCESS  not-accessible
   STATUS      current
   DESCRIPTION
       " Show Poe Scheduling Time Config. "
   ::= { gs2310pPoeScheduling 2 }

gs2310pPoeSchedulingTimeEntry OBJECT-TYPE
   SYNTAX      Gs2310pPoeSchedulingTimeEntry
   MAX-ACCESS  not-accessible
   STATUS      current
   DESCRIPTION
       ""
   INDEX    { gs2310pPoeSchedulingTimePort, gs2310pPoeSchedulingTimeWeek, gs2310pPoeSchedulingTimeHour  }
   ::= { gs2310pPoeSchedulingTimeTable 1 }

Gs2310pPoeSchedulingTimeEntry ::= SEQUENCE {
   gs2310pPoeSchedulingTimePort		Integer32,
   gs2310pPoeSchedulingTimeWeek		INTEGER,
   gs2310pPoeSchedulingTimeHour		Integer32,
   gs2310pPoeSchedulingProvidePower	INTEGER
}

gs2310pPoeSchedulingTimePort OBJECT-TYPE
   SYNTAX      Integer32(1..4095)
   MAX-ACCESS  not-accessible
   STATUS      current
   DESCRIPTION
       " port, range : 1 - port number. "
   ::= { gs2310pPoeSchedulingTimeEntry 1 }

gs2310pPoeSchedulingTimeWeek OBJECT-TYPE
   SYNTAX      INTEGER {
                        monday(1),
                        tuseday(2),
                        wednesday(3),
                        thursday(4),
                        friday(5),
                        saturday(6),
                        sunday(7)
                        }
   MAX-ACCESS  not-accessible
   STATUS      current
   DESCRIPTION
       " range: 1-7,
         Sunday:7, Monday:1, Tuseday:2, Wednesday:3, Thursday:4, Friday:5, Saturday:6.  "
   ::= { gs2310pPoeSchedulingTimeEntry 2 }

gs2310pPoeSchedulingTimeHour OBJECT-TYPE
   SYNTAX      Integer32(1..24)
   MAX-ACCESS  not-accessible
   STATUS      current
   DESCRIPTION
       " range: 1-24,
         24: hour 0, 1: hour 1, 2: hour2..."
   ::= { gs2310pPoeSchedulingTimeEntry 3 }

gs2310pPoeSchedulingProvidePower OBJECT-TYPE
   SYNTAX      INTEGER { disable(0), enable(1) }
   MAX-ACCESS  read-write
   STATUS      current
   DESCRIPTION
       " 0: disable,
         1: enable,
         default: disable.  "
   ::= { gs2310pPoeSchedulingTimeEntry 4 }

gs2310pPoeConfiguration                                                 OBJECT IDENTIFIER ::= { gs2310pPoe 5 }

gs2310pPoeConfigurationPrimaryPowerSupply  OBJECT-TYPE
   SYNTAX      Integer32(0..1000)
   MAX-ACCESS  read-only
   STATUS      current
   DESCRIPTION
       "It must be defined what amount of power the primary and backup power sources
        can deliver. "
   ::= { gs2310pPoeConfiguration 1 }

gs2310pPoeConfigurationRetryTime OBJECT-TYPE
   SYNTAX      Integer32(0|5|10|20|30|40|50|60)
   MAX-ACCESS  read-write
   STATUS      current
   DESCRIPTION
       "The period (in seconds) for trying to turn on an overloaded PoE port.
        0: disable,
        5 sec,10 sec,20 sec,30 sec,40 sec,50 sec,60 sec,
        default: 60 sec. "
   ::= { gs2310pPoeConfiguration 2 }

gs2310pPoeConfigurationTable OBJECT-TYPE
   SYNTAX      SEQUENCE OF Gs2310pPoeConfigurationEntry
   MAX-ACCESS  not-accessible
   STATUS      current
   DESCRIPTION
       " Configure PoE Configuration mode. "
   ::= { gs2310pPoeConfiguration 3 }

gs2310pPoeConfigurationEntry OBJECT-TYPE
   SYNTAX      Gs2310pPoeConfigurationEntry
   MAX-ACCESS  not-accessible
   STATUS      current
   DESCRIPTION
       ""
   INDEX    { gs2310pPoeConfigurationPort  }
   ::= { gs2310pPoeConfigurationTable 1 }

Gs2310pPoeConfigurationEntry ::= SEQUENCE {
   gs2310pPoeConfigurationPort	       Integer32,
   gs2310pPoeConfigurationPoEMode       INTEGER,
   gs2310pPoeConfigurationPriority      INTEGER,
   gs2310pPoeConfigurationMaximumPower  DisplayString,
   gs2310pPoeConfigurationDetection     INTEGER,
   gs2310pPoeConfigurationReset         INTEGER
}

gs2310pPoeConfigurationPort OBJECT-TYPE
   SYNTAX      Integer32(1..4094)
   MAX-ACCESS  not-accessible
   STATUS      current
   DESCRIPTION
       " port, range : 1 - port number. "
   ::= { gs2310pPoeConfigurationEntry 1 }

gs2310pPoeConfigurationPoEMode OBJECT-TYPE
   SYNTAX      INTEGER { disable(0), enable(1) }
   MAX-ACCESS  read-write
   STATUS      current
   DESCRIPTION
       "The PoE Mode represents the PoE operating mode for the port.
        0: Disable,
        1: Enable,
        default: Enable. "
   ::= { gs2310pPoeConfigurationEntry 2 }

gs2310pPoeConfigurationPriority OBJECT-TYPE
   SYNTAX      INTEGER { low(0), high(1), critical(2) }
   MAX-ACCESS  read-write
   STATUS      current
   DESCRIPTION
       "The Priority represents the ports priority. There are three levels of power priority named Low, High and Critical.
        0: Low,
        1: High,
        2: Critical,
        default: Low.  "
   ::= { gs2310pPoeConfigurationEntry 3 }

gs2310pPoeConfigurationMaximumPower OBJECT-TYPE
   SYNTAX      DisplayString
   MAX-ACCESS  read-write
   STATUS      current
   DESCRIPTION
       "The Maximum Power value contains a numerical value that indicates the maximum
        power in watts that can be delivered to a remote device.
        default: 15.4[W],
        max: 30[W]. "
   ::= { gs2310pPoeConfigurationEntry 4 }

gs2310pPoeConfigurationDetection OBJECT-TYPE
   SYNTAX      INTEGER(0..5)
   MAX-ACCESS  read-write
   STATUS      current
   DESCRIPTION
       "Configure PoE port capacitor detection.
        0: No Detection(read only),
        1: legacy,
        2: 4-point,
        3: 4-point-legacy,
        4: 2-point,
        5: 2-point-legacy,
        default: 4-point. "
   ::= { gs2310pPoeConfigurationEntry 5 }

gs2310pPoeConfigurationReset OBJECT-TYPE
   SYNTAX      INTEGER { disable(0), enable(1) }
   MAX-ACCESS  read-write
   STATUS      current
   DESCRIPTION
       "Reset the specific PoE port.
        0: Disable,
        1: Enable,
        default: Disable. "
   ::= { gs2310pPoeConfigurationEntry 6 }

gs2310pPoeConfigurationLegacyMode  OBJECT-TYPE
   SYNTAX      INTEGER { disable(0), enable(1) }
   MAX-ACCESS  read-write
   STATUS      current
   DESCRIPTION
       "Legacy Detection.
        0: Disable,
        1: Enable,
        default: Disable. "
   ::= { gs2310pPoeConfiguration 4 }


gs2310pQos                                                             OBJECT IDENTIFIER ::= { gs2310pConfiguration 14 }

gs2310pQosPortClassification                                           OBJECT IDENTIFIER ::= { gs2310pQos 1 }

gs2310pQosPortClassificationTable OBJECT-TYPE
   SYNTAX      SEQUENCE OF Gs2310pQosPortClassificationEntry
   MAX-ACCESS  not-accessible
   STATUS      current
   DESCRIPTION
       " QoS Ingress Port Classification . "
   ::= { gs2310pQosPortClassification  1 }

gs2310pQosPortClassificationEntry OBJECT-TYPE
   SYNTAX      Gs2310pQosPortClassificationEntry
   MAX-ACCESS  not-accessible
   STATUS      current
   DESCRIPTION
       ""
   INDEX    { gs2310pQosPortClassificationPort  }
   ::= { gs2310pQosPortClassificationTable 1 }

Gs2310pQosPortClassificationEntry ::= SEQUENCE {
   gs2310pQosPortClassificationPort	        Integer32,
   gs2310pQosPortClassificationQoSclass       Integer32,
   gs2310pQosPortClassificationDPlevel	    Integer32,
   gs2310pQosPortClassificationPCP	        Integer32,
   gs2310pQosPortClassificationDEI	        INTEGER,
   gs2310pQosPortClassificationTagClass	    INTEGER,
   gs2310pQosPortClassificationDSCPBased    INTEGER,
   gs2310pQosPortClassificationAddressMode  INTEGER
}

gs2310pQosPortClassificationPort OBJECT-TYPE
   SYNTAX      Integer32(1..4095)
   MAX-ACCESS  not-accessible
   STATUS      current
   DESCRIPTION
       " port, range : 1 - port number. "
   ::= { gs2310pQosPortClassificationEntry 1 }

gs2310pQosPortClassificationQoSclass OBJECT-TYPE
   SYNTAX      Integer32(0..7)
   MAX-ACCESS  read-write
   STATUS      current
   DESCRIPTION
      "Controls the default QoS class, i.e., the QoS class
      for frames not classified in any other way. There is
      a one to one mapping between QoS class, queue and priority.
      A QoS class of 0 (zero) has the lowest priority.
      Note: If the QoS class has been dynamically changed, then
      the actual QoS class is shown in parentheses after the
      configured QoS class.

      Configure the default QoS class.
        range: 0-7,
        default: 0. "
   ::= { gs2310pQosPortClassificationEntry 2 }

gs2310pQosPortClassificationDPlevel OBJECT-TYPE
   SYNTAX      Integer32(0|1)
   MAX-ACCESS  read-write
   STATUS      current
   DESCRIPTION
       " DP level for frames not classified in any other way.
         range: 0-1,
         default: 0. "
   ::= { gs2310pQosPortClassificationEntry 3 }

gs2310pQosPortClassificationPCP OBJECT-TYPE
   SYNTAX      Integer32(0..7)
   MAX-ACCESS  read-write
   STATUS      current
   DESCRIPTION
      " Priority Code Point. It is a 3-bit field storing the priority level for the 802.1Q frame.
        range: 0-7,
        default: 0. "
   ::= { gs2310pQosPortClassificationEntry 4 }

gs2310pQosPortClassificationDEI OBJECT-TYPE
   SYNTAX      INTEGER { disable(0), enable(1) }
   MAX-ACCESS  read-write
   STATUS      current
   DESCRIPTION
      " Drop Eligible Indicator. It is a 1-bit field in the VLAN.
        range 0-1,
        default: 0. "
   ::= { gs2310pQosPortClassificationEntry 5 }

gs2310pQosPortClassificationTagClass OBJECT-TYPE
   SYNTAX      INTEGER { disable(0), enable(1) }
   MAX-ACCESS  read-write
   STATUS      current
   DESCRIPTION
      " Configure the classification mode for tagged frames.
        0: Disable,
        1: Enable,
        default: Disable. "
   ::= { gs2310pQosPortClassificationEntry 6 }

gs2310pQosPortClassificationDSCPBased OBJECT-TYPE
   SYNTAX      INTEGER { disable(0), enable(1) }
   MAX-ACCESS  read-write
   STATUS      current
   DESCRIPTION
      " Click to Enable DSCP Based QoS Ingress Port Classification.
        0: disable,
        1: enable,
        default: disable. "
   ::= { gs2310pQosPortClassificationEntry 7 }

gs2310pQosPortClassificationAddressMode OBJECT-TYPE
   SYNTAX      INTEGER { source(0), destination(1) }
   MAX-ACCESS  read-write
   STATUS      current
   DESCRIPTION
      "The IP/MAC address mode specifying whether the QCL classification
       must be based on source (SMAC/SIP) or destination (DMAC/DIP)
       addresses on this port.
        0: source,
        1: destination,
        default: source. "
   ::= { gs2310pQosPortClassificationEntry 8 }

gs2310pQoSIngressPortTagClassificationTable OBJECT-TYPE
   SYNTAX      SEQUENCE OF Gs2310pQoSIngressPortTagClassificationEntry
   MAX-ACCESS  not-accessible
   STATUS      current
   DESCRIPTION
       " Show QoS Ingress Port Tag Classification. "
   ::= { gs2310pQosPortClassification 2 }

gs2310pQoSIngressPortTagClassificationEntry OBJECT-TYPE
   SYNTAX      Gs2310pQoSIngressPortTagClassificationEntry
   MAX-ACCESS  not-accessible
   STATUS      current
   DESCRIPTION
       ""
   INDEX    { gs2310pQoSIngressPortTagClassificationPort, gs2310pQoSIngressPortTagPCP, gs2310pQoSIngressPortTagDEI  }
   ::= { gs2310pQoSIngressPortTagClassificationTable 1 }

Gs2310pQoSIngressPortTagClassificationEntry ::= SEQUENCE {
   gs2310pQoSIngressPortTagClassificationPort	Integer32,
   gs2310pQoSIngressPortTagPCP					INTEGER,
   gs2310pQoSIngressPortTagDEI					INTEGER,
   gs2310pQoSIngressPortTagQosClass				Integer32,
   gs2310pQoSIngressPortTagDPLevel				Integer32
}

gs2310pQoSIngressPortTagClassificationPort OBJECT-TYPE
   SYNTAX      Integer32(1..4095)
   MAX-ACCESS  not-accessible
   STATUS      current
   DESCRIPTION
       " port, range : 1 - port number. "
   ::= { gs2310pQoSIngressPortTagClassificationEntry 1 }

gs2310pQoSIngressPortTagPCP OBJECT-TYPE
   SYNTAX      INTEGER { pcp0(1), pcp1(2), pcp2(3), pcp3(4), pcp4(5), pcp5(6), pcp6(7), pcp7(8) }
   MAX-ACCESS  not-accessible
   STATUS      current
   DESCRIPTION
       " range: 1-8,
         PCP0:1, PCP1:2...  "
   ::= { gs2310pQoSIngressPortTagClassificationEntry 2 }

gs2310pQoSIngressPortTagDEI OBJECT-TYPE
   SYNTAX      INTEGER { dei0(1), dei1(2) }
   MAX-ACCESS  not-accessible
   STATUS      current
   DESCRIPTION
       " range: 1-2,
         DEI0:1, DEI1:2. "
   ::= { gs2310pQoSIngressPortTagClassificationEntry 3 }

gs2310pQoSIngressPortTagQosClass OBJECT-TYPE
   SYNTAX      Integer32 (0..7)
   MAX-ACCESS  read-write
   STATUS      current
   DESCRIPTION
       " range: 0-7.  "
   ::= { gs2310pQoSIngressPortTagClassificationEntry 4 }

gs2310pQoSIngressPortTagDPLevel OBJECT-TYPE
   SYNTAX      Integer32 (0|1)
   MAX-ACCESS  read-write
   STATUS      current
   DESCRIPTION
       " range: 0-1.  "
   ::= { gs2310pQoSIngressPortTagClassificationEntry 5 }


gs2310pQosPortPolicingTable OBJECT-TYPE
   SYNTAX      SEQUENCE OF Gs2310pQosPortPolicingEntry
   MAX-ACCESS  not-accessible
   STATUS      current
   DESCRIPTION
       "  configure the Policer settings for all switch ports. "
   ::= { gs2310pQos  2 }

gs2310pQosPortPolicingEntry OBJECT-TYPE
   SYNTAX      Gs2310pQosPortPolicingEntry
   MAX-ACCESS  not-accessible
   STATUS      current
   DESCRIPTION
       ""
   INDEX    { gs2310pQosPortPolicingPort  }
   ::= { gs2310pQosPortPolicingTable 1 }

Gs2310pQosPortPolicingEntry ::= SEQUENCE {
   gs2310pQosPortPolicingPort	        Integer32,
   gs2310pQosPortPolicingMode           INTEGER,
   gs2310pQosPortPolicingRate	        Integer32,
   gs2310pQosPortPolicingUnit	        INTEGER,
   gs2310pQosPortPolicingFlowControl	INTEGER
}

gs2310pQosPortPolicingPort OBJECT-TYPE
   SYNTAX      Integer32 (1..4095)
   MAX-ACCESS  not-accessible
   STATUS      current
   DESCRIPTION
       " port, range : 1 - port number. "
   ::= { gs2310pQosPortPolicingEntry 1 }

gs2310pQosPortPolicingMode OBJECT-TYPE
   SYNTAX      INTEGER { disable(0), enable(1) }
   MAX-ACCESS  read-write
   STATUS      current
   DESCRIPTION
      " Controls whether the policer is enabled on this switch port.
        0: disable,
        1: enable,
        default: disable. "
   ::= { gs2310pQosPortPolicingEntry 2 }

gs2310pQosPortPolicingRate OBJECT-TYPE
   SYNTAX      Integer32(100..10000000)
   MAX-ACCESS  read-write
   STATUS      current
   DESCRIPTION
       " Controls the rate for the policer.
         range: 100-10000000(kbps/fps),
         default: 500(kbps). "
   ::= { gs2310pQosPortPolicingEntry 3 }

gs2310pQosPortPolicingUnit OBJECT-TYPE
   SYNTAX      INTEGER { kbps(0), fps(1) }
   MAX-ACCESS  read-write
   STATUS      current
   DESCRIPTION
       " Controls the unit of measure for the policer rate.
         0: kbps,
         1: fps,
         default: kbps. "
   ::= { gs2310pQosPortPolicingEntry 4 }

gs2310pQosPortPolicingFlowControl OBJECT-TYPE
   SYNTAX      INTEGER { disable(0), enable(1) }
   MAX-ACCESS  read-write
   STATUS      current
   DESCRIPTION
       " If flow control is enabled and the port is in flow control mode,
        then pause frames are sent instead of discarding frames.
         0: disable,
         1: enable,
         default: disable. "
   ::= { gs2310pQosPortPolicingEntry 5 }

gs2310pQosPortScheduler                                           OBJECT IDENTIFIER ::= { gs2310pQos 3 }

gs2310pQosPortSchedulerModeTable OBJECT-TYPE
   SYNTAX      SEQUENCE OF Gs2310pQosPortSchedulerModeEntry
   MAX-ACCESS  not-accessible
   STATUS      current
   DESCRIPTION
       " configure the basic QoS Port Scheduler Mode settings for all switch ports. "
   ::= { gs2310pQosPortScheduler  1 }

gs2310pQosPortSchedulerModeEntry OBJECT-TYPE
   SYNTAX      Gs2310pQosPortSchedulerModeEntry
   MAX-ACCESS  not-accessible
   STATUS      current
   DESCRIPTION
       ""
   INDEX    { gs2310pQosSchedulerModePort  }
   ::= { gs2310pQosPortSchedulerModeTable 1 }

Gs2310pQosPortSchedulerModeEntry ::= SEQUENCE {
   gs2310pQosSchedulerModePort	                Integer32,
   gs2310pQosSchedulerMode                        INTEGER,
   gs2310pQosSchedulerShaper	                    INTEGER,
   gs2310pQosSchedulerShaperRate	                Integer32
}

gs2310pQosSchedulerModePort OBJECT-TYPE
   SYNTAX      Integer32 (1..4095)
   MAX-ACCESS  not-accessible
   STATUS      current
   DESCRIPTION
       " port, range : 1 - port number. "
   ::= { gs2310pQosPortSchedulerModeEntry 1 }

gs2310pQosSchedulerMode OBJECT-TYPE
   SYNTAX      INTEGER { strictPriority(0), weighted(1) }
   MAX-ACCESS  read-write
   STATUS      current
   DESCRIPTION
       " Controls whether the scheduler mode is Strict Priority or Weighted
       on this switch port.
       0:Strict Priority
       1:Weighted
         default: Strict Priority. "
   ::= { gs2310pQosPortSchedulerModeEntry 2 }

gs2310pQosSchedulerShaper OBJECT-TYPE
   SYNTAX      INTEGER { disable(0), enable(1) }
   MAX-ACCESS  read-write
   STATUS      current
   DESCRIPTION
       " Controls whether the port shaper is enabled
         0: Disable
         1: Enable.
         default: disable. "
   ::= { gs2310pQosPortSchedulerModeEntry 3 }

gs2310pQosSchedulerShaperRate OBJECT-TYPE
   SYNTAX      Integer32(100..1000000)
   MAX-ACCESS  read-write
   STATUS      current
   DESCRIPTION
       " Controls the rate for the port shaper.
         range: 100-1000000
         default: 500 kbps. "
   ::= { gs2310pQosPortSchedulerModeEntry 4 }

gs2310pQosPortSchedulerTable OBJECT-TYPE
   SYNTAX      SEQUENCE OF Gs2310pQosPortSchedulerEntry
   MAX-ACCESS  not-accessible
   STATUS      current
   DESCRIPTION
       " Show Qos Port Scheduler. "
   ::= { gs2310pQosPortScheduler 2 }

gs2310pQosPortSchedulerEntry OBJECT-TYPE
   SYNTAX      Gs2310pQosPortSchedulerEntry
   MAX-ACCESS  not-accessible
   STATUS      current
   DESCRIPTION
       ""
   INDEX    { gs2310pQosSchedulerPort, gs2310pQosSchedulerPortQueue}
   ::= { gs2310pQosPortSchedulerTable 1 }

Gs2310pQosPortSchedulerEntry ::= SEQUENCE {
   gs2310pQosSchedulerPort						Integer32,
   gs2310pQosSchedulerPortQueue					INTEGER,
   gs2310pQosSchedulerPortQueueShaper				INTEGER,
   gs2310pQosSchedulerPortQueueShaperRate			Integer32,
   gs2310pQosSchedulerPortQueueShaperExcess		INTEGER,
   gs2310pQosSchedulerPortQueueSchedulerWeight	Integer32,
   gs2310pQosSchedulerPortQueueSchedulerPercent	DisplayString
}

gs2310pQosSchedulerPort OBJECT-TYPE
   SYNTAX      Integer32 (1..4095)
   MAX-ACCESS  not-accessible
   STATUS      current
   DESCRIPTION
       " port, range : 1 - port number. "
   ::= { gs2310pQosPortSchedulerEntry 1 }

gs2310pQosSchedulerPortQueue OBJECT-TYPE
   SYNTAX      INTEGER { q0(1), q1(2), q2(3), q3(4), q4(5), q5(6), q6(7), q7(8) }
   MAX-ACCESS  not-accessible
   STATUS      current
   DESCRIPTION
       " range: 1-8.
         Q0: 1, Q1: 2, ... "
   ::= { gs2310pQosPortSchedulerEntry 2 }

gs2310pQosSchedulerPortQueueShaper OBJECT-TYPE
   SYNTAX      INTEGER { disable(0), enable(1) }
   MAX-ACCESS  read-write
   STATUS      current
   DESCRIPTION
       " 0: disable  1:enable,
         default: 0.  "
   ::= { gs2310pQosPortSchedulerEntry 3 }

gs2310pQosSchedulerPortQueueShaperRate OBJECT-TYPE
   SYNTAX      Integer32(100..1000000)
   MAX-ACCESS  read-write
   STATUS      current
   DESCRIPTION
       " range: 100..1000000 kbps.  "
   ::= { gs2310pQosPortSchedulerEntry 4 }

gs2310pQosSchedulerPortQueueShaperExcess OBJECT-TYPE
   SYNTAX      INTEGER { disable(0), enable(1) }
   MAX-ACCESS  read-write
   STATUS      current
   DESCRIPTION
       " 0: disable  1:enable,
         default: 0.  "
   ::= { gs2310pQosPortSchedulerEntry 5 }

gs2310pQosSchedulerPortQueueSchedulerWeight OBJECT-TYPE
   SYNTAX      Integer32(0..100)
   MAX-ACCESS  read-write
   STATUS      current
   DESCRIPTION
       " range: 1-100,
         default: 17.
         Only use in Q0 - Q5.  Q6 & Q7 show 0 "
   ::= { gs2310pQosPortSchedulerEntry 6 }

gs2310pQosSchedulerPortQueueSchedulerPercent OBJECT-TYPE
   SYNTAX      DisplayString
   MAX-ACCESS  read-only
   STATUS      current
   DESCRIPTION
       " Only use in Q0 - Q5. Q6 & Q7 show empty "
   ::= { gs2310pQosPortSchedulerEntry 7 }

gs2310pQosPortEgressTagRemarking                                           OBJECT IDENTIFIER ::= { gs2310pQos 4 }

gs2310pQosPortEgressTagRemarkingTable OBJECT-TYPE
   SYNTAX      SEQUENCE OF Gs2310pQosPortEgressTagRemarkingEntry
   MAX-ACCESS  not-accessible
   STATUS      current
   DESCRIPTION
       " configure the basic QoS Port Egress Tag Remark Configuration settings for all switch ports. "
   ::= { gs2310pQosPortEgressTagRemarking  1 }

gs2310pQosPortEgressTagRemarkingEntry OBJECT-TYPE
   SYNTAX      Gs2310pQosPortEgressTagRemarkingEntry
   MAX-ACCESS  not-accessible
   STATUS      current
   DESCRIPTION
       ""
   INDEX    { gs2310pQosEgressTagRemarkingPort  }
   ::= { gs2310pQosPortEgressTagRemarkingTable 1 }

Gs2310pQosPortEgressTagRemarkingEntry ::= SEQUENCE {
   gs2310pQosEgressTagRemarkingPort	                Integer32,
   gs2310pQosEgressTagRemarkingMode	                INTEGER
}

gs2310pQosEgressTagRemarkingPort OBJECT-TYPE
   SYNTAX      Integer32 (1..4095)
   MAX-ACCESS  not-accessible
   STATUS      current
   DESCRIPTION
       " port, range : 1 - port number. "
   ::= { gs2310pQosPortEgressTagRemarkingEntry 1 }

gs2310pQosEgressTagRemarkingMode OBJECT-TYPE
   SYNTAX      INTEGER { classified(0), default(1), mapped(2) }
   MAX-ACCESS  read-write
   STATUS      current
   DESCRIPTION
       " the tag remarking mode for this port.
       0:Classified, Use classified PCP/DEI values.
       1:Default, Use default PCP/DEI values.
       2:Mapped, Use mapped versions of QoS class and DP level."
   ::= { gs2310pQosPortEgressTagRemarkingEntry 2 }


gs2310pQosPortEgressTagRemarkingDefTable OBJECT-TYPE
   SYNTAX      SEQUENCE OF Gs2310pQosPortEgressTagRemarkingDefEntry
   MAX-ACCESS  not-accessible
   STATUS      current
   DESCRIPTION
       " configure the basic QoS Port Egress Tag Remark Configuration settings for all switch ports. "
   ::= { gs2310pQosPortEgressTagRemarking  2 }

gs2310pQosPortEgressTagRemarkingDefEntry OBJECT-TYPE
   SYNTAX      Gs2310pQosPortEgressTagRemarkingDefEntry
   MAX-ACCESS  not-accessible
   STATUS      current
   DESCRIPTION
       ""
   INDEX    { gs2310pQosEgressTagRemarkingDefPort  }
   ::= { gs2310pQosPortEgressTagRemarkingDefTable 1 }

Gs2310pQosPortEgressTagRemarkingDefEntry ::= SEQUENCE {
   gs2310pQosEgressTagRemarkingDefPort	            Integer32,
   gs2310pQosEgressTagRemarkingDefPCP	                Integer32,
   gs2310pQosEgressTagRemarkingDefDEI	                INTEGER
}

gs2310pQosEgressTagRemarkingDefPort OBJECT-TYPE
   SYNTAX      Integer32(1..4095)
   MAX-ACCESS  not-accessible
   STATUS      current
   DESCRIPTION
       " port, range : 1 - port number. "
   ::= { gs2310pQosPortEgressTagRemarkingDefEntry 1 }

gs2310pQosEgressTagRemarkingDefPCP OBJECT-TYPE
   SYNTAX      Integer32(0..7)
   MAX-ACCESS  read-write
   STATUS      current
   DESCRIPTION
       " Controls the default PCP
       Range : 0-7"
   ::= { gs2310pQosPortEgressTagRemarkingDefEntry 2 }

gs2310pQosEgressTagRemarkingDefDEI OBJECT-TYPE
   SYNTAX      INTEGER { disable(0), enable(1) }
   MAX-ACCESS  read-write
   STATUS      current
   DESCRIPTION
       " controls the DEI
       Range 0-1"
   ::= { gs2310pQosPortEgressTagRemarkingDefEntry 3 }

gs2310pQosPortEgressTagRemarkingMapTable OBJECT-TYPE
   SYNTAX      SEQUENCE OF Gs2310pQosPortEgressTagRemarkingMapEntry
   MAX-ACCESS  not-accessible
   STATUS      current
   DESCRIPTION
       " Show Qos Port Egress Tag Remarking Map. "
   ::= { gs2310pQosPortEgressTagRemarking 4 }

gs2310pQosPortEgressTagRemarkingMapEntry OBJECT-TYPE
   SYNTAX      Gs2310pQosPortEgressTagRemarkingMapEntry
   MAX-ACCESS  not-accessible
   STATUS      current
   DESCRIPTION
       ""
   INDEX    { gs2310pQosPortEgressTagRemarkingMapPort, gs2310pQosTagRemarkingQoSClass, gs2310pQosTagRemarkingDPLevel  }
   ::= { gs2310pQosPortEgressTagRemarkingMapTable 1 }

Gs2310pQosPortEgressTagRemarkingMapEntry ::= SEQUENCE {
   gs2310pQosPortEgressTagRemarkingMapPort	Integer32,
   gs2310pQosTagRemarkingQoSClass			INTEGER,
   gs2310pQosTagRemarkingDPLevel				INTEGER,
   gs2310pQosTagRemarkingPCP					Integer32,
   gs2310pQosTagRemarkingDEI					INTEGER
}

gs2310pQosPortEgressTagRemarkingMapPort OBJECT-TYPE
   SYNTAX      Integer32 (1..4095)
   MAX-ACCESS  not-accessible
   STATUS      current
   DESCRIPTION
       " port, range : 1 - port number. "
   ::= { gs2310pQosPortEgressTagRemarkingMapEntry 1 }

gs2310pQosTagRemarkingQoSClass OBJECT-TYPE
   SYNTAX      INTEGER {
                        class0(1),
                        class1(2),
                        class2(3),
                        class3(4),
                        class4(5),
                        class5(6),
                        class6(7),
                        class7(8)
                        }
   MAX-ACCESS  not-accessible
   STATUS      current
   DESCRIPTION
       " range: 1-8,
         QoS Class0: 1, QoS Class1: 2...  "
   ::= { gs2310pQosPortEgressTagRemarkingMapEntry 2 }

gs2310pQosTagRemarkingDPLevel OBJECT-TYPE
   SYNTAX      INTEGER { level0(1), level1(2) }
   MAX-ACCESS  not-accessible
   STATUS      current
   DESCRIPTION
       " range: 1-2,
         DP Level0: 1, DP Level1: 2. "
   ::= { gs2310pQosPortEgressTagRemarkingMapEntry 3 }

gs2310pQosTagRemarkingPCP OBJECT-TYPE
   SYNTAX      Integer32 (0..7)
   MAX-ACCESS  read-write
   STATUS      current
   DESCRIPTION
       " range: 0-7.  "
   ::= { gs2310pQosPortEgressTagRemarkingMapEntry 4 }

gs2310pQosTagRemarkingDEI OBJECT-TYPE
   SYNTAX      INTEGER (0|1)
   MAX-ACCESS  read-write
   STATUS      current
   DESCRIPTION
       " range: 0-1.  "
   ::= { gs2310pQosPortEgressTagRemarkingMapEntry 5 }


gs2310pQosPortDSCPTable OBJECT-TYPE
   SYNTAX      SEQUENCE OF Gs2310pQosPortDSCPEntry
   MAX-ACCESS  not-accessible
   STATUS      current
   DESCRIPTION
       " configure the basic QoS Port DSCP Configuration settings for all switch ports. "
   ::= { gs2310pQos  5 }

gs2310pQosPortDSCPEntry OBJECT-TYPE
   SYNTAX      Gs2310pQosPortDSCPEntry
   MAX-ACCESS  not-accessible
   STATUS      current
   DESCRIPTION
       ""
   INDEX    { gs2310pQosPortDSCPPort  }
   ::= { gs2310pQosPortDSCPTable 1 }

Gs2310pQosPortDSCPEntry ::= SEQUENCE {
   gs2310pQosPortDSCPPort	                Integer32,
   gs2310pQosPortDSCPIngressTranslate       INTEGER,
   gs2310pQosPortDSCPIngressClassify	    INTEGER,
   gs2310pQosPortDSCPEgressRewrite	        INTEGER
}

gs2310pQosPortDSCPPort OBJECT-TYPE
   SYNTAX      Integer32 (1..4095)
   MAX-ACCESS  not-accessible
   STATUS      current
   DESCRIPTION
       " port, range : 1 - port number. "
   ::= { gs2310pQosPortDSCPEntry 1 }

gs2310pQosPortDSCPIngressTranslate OBJECT-TYPE
   SYNTAX      INTEGER { disable(0), enable(1) }
   MAX-ACCESS  read-write
   STATUS      current
   DESCRIPTION
      " Configure DSCP ingress translation mode.
        0: disable,
        1: enable,
        default: disable. "
   ::= { gs2310pQosPortDSCPEntry 2 }

gs2310pQosPortDSCPIngressClassify OBJECT-TYPE
   SYNTAX      INTEGER(0..3)
   MAX-ACCESS  read-write
   STATUS      current
   DESCRIPTION
       " Classification for a port have 4 different values.
         range: 0-3,
         0: disable,No Ingress DSCP Classification.
         1: DSCP=0,Classify if incoming (or translated if enabled) DSCP is 0.
         2: Selected,Classify only selected DSCP for which classification is
         enabled as specified in DSCP Translation window for the specific DSCP.
         3: All,Classify all DSCP.
         default: disable. "
   ::= { gs2310pQosPortDSCPEntry 3 }

gs2310pQosPortDSCPEgressRewrite OBJECT-TYPE
   SYNTAX      INTEGER(0..3)
   MAX-ACCESS  read-write
   STATUS      current
   DESCRIPTION
       " Configure the port egress rewriting mode.
         range: 0-2
         0: Disable,No Egress rewrite.
         1: Enable, Rewrite enabled without remapping.
         2: Remap DP Unaware , DSCP from analyzer is remapped and frame is
         remarked with remapped DSCP value. The remapped DSCP value is always
         taken from the DSCP Translation->Egress Remap DP0 table.
         3: Remap DP Aware: DSCP from analyzer is remapped and frame is remarked
          with remapped DSCP value. Depending on the DP level of the frame, the
          remapped DSCP value is either taken from the DSCP Translation->Egress
          Remap DP0 table or from the DSCP Translation->Egress Remap DP1 table.
         default: disable. "
   ::= { gs2310pQosPortDSCPEntry 4 }


gs2310pQosDSCPTable OBJECT-TYPE
   SYNTAX      SEQUENCE OF Gs2310pQosDSCPEntry
   MAX-ACCESS  not-accessible
   STATUS      current
   DESCRIPTION
       " configure the basic QoS DSCP based QoS Ingress Classification settings for all switches. "
   ::= { gs2310pQos  6 }

gs2310pQosDSCPEntry OBJECT-TYPE
   SYNTAX      Gs2310pQosDSCPEntry
   MAX-ACCESS  not-accessible
   STATUS      current
   DESCRIPTION
       ""
   INDEX    { gs2310pQosDSCPList  }
   ::= { gs2310pQosDSCPTable 1 }

Gs2310pQosDSCPEntry ::= SEQUENCE {
   gs2310pQosDSCPList       Integer32,
   gs2310pQosDSCP           DisplayString,
   gs2310pQosDSCPTrust      INTEGER,
   gs2310pQosDSCPQosClass	  Integer32,
   gs2310pQosDSCPDPL	      INTEGER
}

gs2310pQosDSCPList OBJECT-TYPE
   SYNTAX      Integer32(1..64)
   MAX-ACCESS  not-accessible
   STATUS      current
   DESCRIPTION
      " DSCP mapping table index(1-64). "
   ::= { gs2310pQosDSCPEntry 1 }

gs2310pQosDSCP OBJECT-TYPE
   SYNTAX      DisplayString
   MAX-ACCESS  read-only
   STATUS      current
   DESCRIPTION
      "Maximum number of supported DSCP values are 64."
   ::= { gs2310pQosDSCPEntry 2 }

gs2310pQosDSCPTrust OBJECT-TYPE
   SYNTAX      INTEGER { disable(0), enable(1) }
   MAX-ACCESS  read-write
   STATUS      current
   DESCRIPTION
      " Controls whether a specific DSCP value is trusted. Only frames with
      trusted DSCP values are mapped to a specific QoS class and Drop Precedence
       Level. Frames with untrusted DSCP values are treated as a non-IP frame.
        0: disable,
        1: enable,
        default: disable. "
   ::= { gs2310pQosDSCPEntry 3 }

gs2310pQosDSCPQosClass OBJECT-TYPE
   SYNTAX      Integer32(0..7)
   MAX-ACCESS  read-write
   STATUS      current
   DESCRIPTION
      " QoS class.
        range: 0-7,
        default: 0. "
   ::= { gs2310pQosDSCPEntry 4 }

gs2310pQosDSCPDPL OBJECT-TYPE
   SYNTAX      INTEGER(0|1)
   MAX-ACCESS  read-write
   STATUS      current
   DESCRIPTION
      " Drop Precedence Level.
        range: 0-1,
        default: disable. "
   ::= { gs2310pQosDSCPEntry 5 }

gs2310pQosDSCPTranslationTable OBJECT-TYPE
   SYNTAX      SEQUENCE OF Gs2310pQosDSCPTranslationEntry
   MAX-ACCESS  not-accessible
   STATUS      current
   DESCRIPTION
       "  configure the basic QoS DSCP Translation settings for all switches. "
   ::= { gs2310pQos  7 }

gs2310pQosDSCPTranslationEntry OBJECT-TYPE
   SYNTAX      Gs2310pQosDSCPTranslationEntry
   MAX-ACCESS  not-accessible
   STATUS      current
   DESCRIPTION
       ""
   INDEX    { gs2310pQosDSCPTranslationList  }
   ::= { gs2310pQosDSCPTranslationTable 1 }

Gs2310pQosDSCPTranslationEntry ::= SEQUENCE {
   gs2310pQosDSCPTranslationList                 Integer32,
   gs2310pQosDSCPTranslationDSCPBasedId          DisplayString,
   gs2310pQosDSCPTranslationIngressTranslate     Integer32,
   gs2310pQosDSCPTranslationIngressClassify      INTEGER,
   gs2310pQosDSCPTranslationEgressRemapDP0       Integer32,
   gs2310pQosDSCPTranslationEgressRemapDP1       Integer32
}

gs2310pQosDSCPTranslationList OBJECT-TYPE
   SYNTAX      Integer32(1..64)
   MAX-ACCESS  not-accessible
   STATUS      current
   DESCRIPTION
      " DSCP translation table index(1-64). "
   ::= { gs2310pQosDSCPTranslationEntry 1 }

gs2310pQosDSCPTranslationDSCPBasedId OBJECT-TYPE
   SYNTAX      DisplayString
   MAX-ACCESS  read-write
   STATUS      current
   DESCRIPTION
      " Configure global ingress DSCP translation table. "
   ::= { gs2310pQosDSCPTranslationEntry 2 }

gs2310pQosDSCPTranslationIngressTranslate OBJECT-TYPE
   SYNTAX      Integer32(0..63)
   MAX-ACCESS  read-write
   STATUS      current
   DESCRIPTION
      " DSCP at Ingress side can be translated to any of DSCP values.
        range: 0-63,
        default: 0. "
   ::= { gs2310pQosDSCPTranslationEntry 3 }

gs2310pQosDSCPTranslationIngressClassify OBJECT-TYPE
   SYNTAX      INTEGER { disable(0), enable(1) }
   MAX-ACCESS  read-write
   STATUS      current
   DESCRIPTION
      " Configure DSCP ingress classification.
        0: disable,
        1: enable,
        default: disable. "
   ::= { gs2310pQosDSCPTranslationEntry 4 }

gs2310pQosDSCPTranslationEgressRemapDP0 OBJECT-TYPE
   SYNTAX      Integer32(0..63)
   MAX-ACCESS  read-write
   STATUS      current
   DESCRIPTION
      "Controls the remapping for frames with DP level 0.
      Select the DSCP value from select menu to which you want to remap.
        range: 0-63,
        default: 0. "
   ::= { gs2310pQosDSCPTranslationEntry 5 }

gs2310pQosDSCPTranslationEgressRemapDP1 OBJECT-TYPE
   SYNTAX      Integer32(0..63)
   MAX-ACCESS  read-write
   STATUS      current
   DESCRIPTION
      "Controls the remapping for frames with DP level 1.
      Select the DSCP value from select menu to which you want to remap.
        range: 0-63,
        default: 0. "
   ::= { gs2310pQosDSCPTranslationEntry 6 }


gs2310pQosDSCPClassificationTable OBJECT-TYPE
   SYNTAX      SEQUENCE OF Gs2310pQosDSCPClassificationEntry
   MAX-ACCESS  not-accessible
   STATUS      current
   DESCRIPTION
       "   configure the mapping of QoS class  to DSCP value. "
   ::= { gs2310pQos  8 }

gs2310pQosDSCPClassificationEntry OBJECT-TYPE
   SYNTAX      Gs2310pQosDSCPClassificationEntry
   MAX-ACCESS  not-accessible
   STATUS      current
   DESCRIPTION
       ""
   INDEX    { gs2310pQosDSCPClassificationQoSClass, gs2310pQosDSCPClassificationDPL }
   ::= { gs2310pQosDSCPClassificationTable 1 }

Gs2310pQosDSCPClassificationEntry ::= SEQUENCE {
   gs2310pQosDSCPClassificationQoSClass		INTEGER,
   gs2310pQosDSCPClassificationDPL			INTEGER,
   gs2310pQosDSCPClassificationDSCP			Integer32
}

gs2310pQosDSCPClassificationQoSClass OBJECT-TYPE
   SYNTAX      INTEGER {
                        class0(1),
                        class1(2),
                        class2(3),
                        class3(4),
                        class4(5),
                        class5(6),
                        class6(7),
                        class7(8)
                        }
   MAX-ACCESS  not-accessible
   STATUS      current
   DESCRIPTION
      " Actual QoS class. Index 1~8 mean Qos Class 0~7."
   ::= { gs2310pQosDSCPClassificationEntry 1 }

gs2310pQosDSCPClassificationDPL OBJECT-TYPE
   SYNTAX      INTEGER(1|2)
   MAX-ACCESS  not-accessible
   STATUS      current
   DESCRIPTION
      " DPL. Index 1~2 mean DPL 0~1."
   ::= { gs2310pQosDSCPClassificationEntry 2 }

gs2310pQosDSCPClassificationDSCP OBJECT-TYPE
   SYNTAX      Integer32(0..63)
   MAX-ACCESS  read-write
   STATUS      current
   DESCRIPTION
      " Select the classified DSCP value.
        range: 0-63,
        default: 0. "
   ::= { gs2310pQosDSCPClassificationEntry 3 }

gs2310pQosControlList                                         OBJECT IDENTIFIER ::= { gs2310pQos 9 }

gs2310pQosQceCreate OBJECT-TYPE
   SYNTAX       INTEGER { none(0), create(1) }
   MAX-ACCESS   read-write
   STATUS       current
   DESCRIPTION
       "default: 0
        0 : None  (read only)
        1 : Create an Qos entry"
   ::= { gs2310pQosControlList 1 }

gs2310pQosQceTable OBJECT-TYPE
   SYNTAX      SEQUENCE OF Gs2310pQosQceEntry
   MAX-ACCESS  not-accessible
   STATUS      current
   DESCRIPTION
       " Create Qos QCE entry. "
   ::= { gs2310pQosControlList 2 }

gs2310pQosQceEntry OBJECT-TYPE
   SYNTAX      Gs2310pQosQceEntry
   MAX-ACCESS  not-accessible
   STATUS      current
   DESCRIPTION
       ""
   INDEX    { gs2310pQosQceIndex  }
   ::= { gs2310pQosQceTable 1 }

Gs2310pQosQceEntry ::= SEQUENCE {
   gs2310pQosQceIndex                Integer32,
   gs2310pQosQceID                   Integer32,
   gs2310pQosQceNextID               Integer32,
   gs2310pQosQcePortMembers          DisplayString,

   gs2310pQosQceTag                  DisplayString,
   gs2310pQosQceVID                  DisplayString,
   gs2310pQosPCP                     DisplayString,
   gs2310pQosDEI                     DisplayString,
   gs2310pQosSMAC                    DisplayString,
   gs2310pQosDMACType                DisplayString,
   gs2310pQosFrameType               INTEGER,

   gs2310pQosMacEtherType            DisplayString,

   gs2310pQosLLCSSAPAddr             DisplayString,
   gs2310pQosLLCDSAPAddr             DisplayString,
   gs2310pQosLLCControl              DisplayString,

   gs2310pQosSNAPPID                 DisplayString,

   gs2310pQosIpv4Protocol            DisplayString,
   gs2310pQosIpv4ProtocolValue       Integer32,
   gs2310pQosIpv4ProtocolUDPSport    DisplayString,
   gs2310pQosIpv4ProtocolUDPDport    DisplayString,
   gs2310pQosIpv4ProtocolTCPSport    DisplayString,
   gs2310pQosIpv4ProtocolTCPDport    DisplayString,
   gs2310pQosIpv4Ip                  DisplayString,
   gs2310pQosIpv4Mask                DisplayString,
   gs2310pQosIpv4IPFragment          INTEGER,
   gs2310pQosIpv4DSCP                DisplayString,


   gs2310pQosIpv6Protocol            DisplayString,
   gs2310pQosIpv6ProtocolValue       Integer32,
   gs2310pQosIpv6ProtocolUDPSport    DisplayString,
   gs2310pQosIpv6ProtocolUDPDport    DisplayString,
   gs2310pQosIpv6ProtocolTCPSport    DisplayString,
   gs2310pQosIpv6ProtocolTCPDport    DisplayString,
   gs2310pQosIpv6Ip                  DisplayString,
   gs2310pQosIpv6Mask                DisplayString,
   gs2310pQosIpv6DSCP                DisplayString,

   gs2310pQosActionClass             Integer32,
   gs2310pQosActionDPL               INTEGER,
   gs2310pQosActionDSCP              Integer32,
   gs2310pQosQceRowStatus            INTEGER
}

gs2310pQosQceIndex OBJECT-TYPE
   SYNTAX      Integer32(1..256)
   MAX-ACCESS  not-accessible
   STATUS      current
   DESCRIPTION
       " "
   ::= { gs2310pQosQceEntry 1 }

gs2310pQosQceID OBJECT-TYPE
   SYNTAX      Integer32(1..256)
   MAX-ACCESS  read-write
   STATUS      current
   DESCRIPTION
       " If the QCE ID is specified and an entry with this QCE ID
         already exists, the QCE will be modified. Otherwise, a
         new QCE will be added.
         range : 1 - 256. "
   ::= { gs2310pQosQceEntry 2 }

gs2310pQosQceNextID OBJECT-TYPE
   SYNTAX      Integer32(1..256)
   MAX-ACCESS  read-write
   STATUS      current
   DESCRIPTION
       " If the next QCE ID is non zero, the QCE will be placed
         before this QCE in the list. If the next QCE ID is zero,
         the QCE will be placed last in the list.
         range : 1 - 256. "
   ::= { gs2310pQosQceEntry 3 }

gs2310pQosQcePortMembers OBJECT-TYPE
   SYNTAX      DisplayString
   MAX-ACCESS  read-write
   STATUS      current
   DESCRIPTION
       " Indicates the ingress port of the QCE. Possible values are:
         All: The QCE will match all ingress port.
         Port: The QCE will match a specific ingress port.Format: 1,3-6."
   ::= { gs2310pQosQceEntry 4 }

gs2310pQosQceTag OBJECT-TYPE
   SYNTAX      DisplayString
   MAX-ACCESS  read-write
   STATUS      current
   DESCRIPTION
       " Value of Tag field can be 'Any', 'Untag' or 'Tag'. "
   ::= { gs2310pQosQceEntry 5 }

gs2310pQosQceVID OBJECT-TYPE
   SYNTAX      DisplayString
   MAX-ACCESS  read-write
   STATUS      current
   DESCRIPTION
       " Valid value of VLAN ID can be any value in 'Specific 1~4094' or 'range 1-4094' or 'Any'. "
   ::= { gs2310pQosQceEntry 6 }

gs2310pQosPCP OBJECT-TYPE
   SYNTAX      DisplayString
   MAX-ACCESS  read-write
   STATUS      current
   DESCRIPTION
       " Priority Code Point: Valid value PCP are specific(0, 1, 2, 3, 4, 5, 6, 7)
         or range(0-1, 2-3, 4-5, 6-7, 0-3, 4-7) or 'Any'. "
   ::= { gs2310pQosQceEntry 7 }

gs2310pQosDEI OBJECT-TYPE
   SYNTAX      DisplayString
   MAX-ACCESS  read-write
   STATUS      current
   DESCRIPTION
       " Drop Eligible Indicator: Valid value of DEI can be any of values between 0, 1 or 'Any'. "
   ::= { gs2310pQosQceEntry 8 }

gs2310pQosSMAC  OBJECT-TYPE
   SYNTAX      DisplayString
   MAX-ACCESS  read-write
   STATUS      current
   DESCRIPTION
       "  Source MAC address: 24 MS bits OUI(00-00-00 ~ FF-FF-FF) or 'Any'. "
   ::= { gs2310pQosQceEntry 9 }

gs2310pQosDMACType OBJECT-TYPE
   SYNTAX      DisplayString
   MAX-ACCESS  read-write
   STATUS      current
   DESCRIPTION
       " Destination MAC type: possible values are 'UC'(unicast), 'MC'(multicast), 'BC'(broadcast) or 'Any'. "
   ::= { gs2310pQosQceEntry 10 }

gs2310pQosFrameType OBJECT-TYPE
   SYNTAX      INTEGER {
                        any(1),
                        ethernet(2),
                        llc(3),
                        snap(4),
                        ipv4(5),
                        ipv6(6)
                        }
   MAX-ACCESS  read-write
   STATUS      current
   DESCRIPTION
       " Frame Type can have any of the following values:
         1: Any,
         2: Ethernet,
         3: LLC,
         4: SNAP,
         5: IPv4,
         6: IPv6. "
   ::= { gs2310pQosQceEntry 11 }

gs2310pQosMacEtherType OBJECT-TYPE
   SYNTAX      DisplayString
   MAX-ACCESS  read-write
   STATUS      current
   DESCRIPTION
       " Valid ethernet type can have a value within 0x600-0xFFFF or 'Any' ,
         but excluding 0x800(IPv4) and 0x86DD(IPv6),
         range: 0000-FFFF,
         default: Any."
   ::= { gs2310pQosQceEntry 12 }

gs2310pQosLLCSSAPAddr OBJECT-TYPE
   SYNTAX      DisplayString
   MAX-ACCESS  read-write
   STATUS      current
   DESCRIPTION
       " Valid SSAP(Source Service Access Point) can vary from 0x00 to 0xFF or 'Any',
         range: 00-FF,
         default: Any. "
   ::= { gs2310pQosQceEntry 13 }

gs2310pQosLLCDSAPAddr OBJECT-TYPE
   SYNTAX      DisplayString
   MAX-ACCESS  read-write
   STATUS      current
   DESCRIPTION
       " Valid DSAP(Destination Service Access Point) can vary from 0x00 to 0xFF or 'Any',
         range: 00-FF,
         default: Any. "
   ::= { gs2310pQosQceEntry 14 }

gs2310pQosLLCControl OBJECT-TYPE
   SYNTAX      DisplayString
   MAX-ACCESS  read-write
   STATUS      current
   DESCRIPTION
       " Valid Control field can vary from 0x00 to 0xFF or 'Any',
         range: 00-FF,
         default: Any. "
   ::= { gs2310pQosQceEntry 15 }

gs2310pQosSNAPPID OBJECT-TYPE
   SYNTAX      DisplayString
   MAX-ACCESS  read-write
   STATUS      current
   DESCRIPTION
       " Valid PID(a.k.a ethernet type) can have value within 0x00-0xFFFF or 'Any',
         range: 0000-FFFF,
         default: Any. "
   ::= { gs2310pQosQceEntry 16 }

gs2310pQosIpv4Protocol OBJECT-TYPE
   SYNTAX      DisplayString
   MAX-ACCESS  read-write
   STATUS      current
   DESCRIPTION
       " IP protocol number: (Other, TCP or UDP) or 'Any'. "
   ::= { gs2310pQosQceEntry 17 }

gs2310pQosIpv4ProtocolValue  OBJECT-TYPE
   SYNTAX      Integer32(0..255)
   MAX-ACCESS  read-write
   STATUS      current
   DESCRIPTION
       " Ipv4 Protocol is Other.
         range: 0-255
         default: 0. "
   ::= { gs2310pQosQceEntry 18 }

gs2310pQosIpv4ProtocolUDPSport OBJECT-TYPE
   SYNTAX      DisplayString
   MAX-ACCESS  read-write
   STATUS      current
   DESCRIPTION
       " Source  TCP/UDP port:(0-65535) or 'Any',
         specific or port range applicable for IP protocol UDP/TCP. "
   ::= { gs2310pQosQceEntry 19 }

gs2310pQosIpv4ProtocolUDPDport OBJECT-TYPE
   SYNTAX      DisplayString
   MAX-ACCESS  read-write
   STATUS      current
   DESCRIPTION
       " Destination TCP/UDP port:(0-65535) or 'Any',
         specific or port range applicable for IP protocol UDP/TCP. "
   ::= { gs2310pQosQceEntry 20 }

gs2310pQosIpv4ProtocolTCPSport OBJECT-TYPE
   SYNTAX      DisplayString
   MAX-ACCESS  read-write
   STATUS      current
   DESCRIPTION
       " Source TCP/UDP port:(0-65535) or 'Any',
         specific or port range applicable for IP protocol UDP/TCP. "
   ::= { gs2310pQosQceEntry 21 }

gs2310pQosIpv4ProtocolTCPDport OBJECT-TYPE
   SYNTAX      DisplayString
   MAX-ACCESS  read-write
   STATUS      current
   DESCRIPTION
       " Destination TCP/UDP port:(0-65535) or 'Any',
         specific or port range applicable for IP protocol UDP/TCP. "
   ::= { gs2310pQosQceEntry 22 }

gs2310pQosIpv4Ip OBJECT-TYPE
   SYNTAX      DisplayString
   MAX-ACCESS  read-write
   STATUS      current
   DESCRIPTION
       "  Specific Source IP address in value format or value 0.0.0.0 is 'Any'.
          if Ipv4 Mask value 0.0.0.0 is 'Any' ,IP address value also is 'Any'.
          (x.y.z.w),x=0 unless y.z.w also 0,x not is 127 or greater than 223.
          If a port is configured to match on DMAC/DIP, this field is the
          Destination IP address."
   ::= { gs2310pQosQceEntry 23 }

gs2310pQosIpv4Mask OBJECT-TYPE
   SYNTAX      DisplayString
   MAX-ACCESS  read-write
   STATUS      current
   DESCRIPTION
       " Specific IP address in mask format or value 0.0.0.0 is 'Any'. "
   ::= { gs2310pQosQceEntry 24 }

gs2310pQosIpv4IPFragment OBJECT-TYPE
   SYNTAX      INTEGER { any(0), no(1), yes(2) }
   MAX-ACCESS  read-write
   STATUS      current
   DESCRIPTION
       " IPv4 frame fragmented option:
         2: yes,
         1: no,
         0: any. "
   ::= { gs2310pQosQceEntry 25 }

gs2310pQosIpv4DSCP OBJECT-TYPE
   SYNTAX      DisplayString
   MAX-ACCESS  read-write
   STATUS      current
   DESCRIPTION
       " Diffserv Code Point value (DSCP): It can be a specific value,
         range of values or 'Any'. DSCP values are in the range 0-63. "
   ::= { gs2310pQosQceEntry 26 }

gs2310pQosIpv6Protocol OBJECT-TYPE
   SYNTAX      DisplayString
   MAX-ACCESS  read-write
   STATUS      current
   DESCRIPTION
       " IP protocol number: (Other, TCP or UDP) or 'Any'. "
   ::= { gs2310pQosQceEntry 27 }

gs2310pQosIpv6ProtocolValue OBJECT-TYPE
   SYNTAX      Integer32(0..255)
   MAX-ACCESS  read-write
   STATUS      current
   DESCRIPTION
       " when IPv6 protocol is Other ,
         range: 0-255. "
   ::= { gs2310pQosQceEntry 28 }

gs2310pQosIpv6ProtocolUDPSport OBJECT-TYPE
   SYNTAX      DisplayString
   MAX-ACCESS  read-write
   STATUS      current
   DESCRIPTION
       " Source TCP/UDP port:(0-65535) or 'Any',
         specific or port range applicable for IP protocol UDP/TCP. "
   ::= { gs2310pQosQceEntry 29 }

gs2310pQosIpv6ProtocolUDPDport OBJECT-TYPE
   SYNTAX      DisplayString
   MAX-ACCESS  read-write
   STATUS      current
   DESCRIPTION
       " Destination TCP/UDP port:(0-65535) or 'Any',
         specific or port range applicable for IP protocol UDP/TCP. "
   ::= { gs2310pQosQceEntry 30 }

gs2310pQosIpv6ProtocolTCPSport OBJECT-TYPE
   SYNTAX      DisplayString
   MAX-ACCESS  read-write
   STATUS      current
   DESCRIPTION
       " Source TCP/UDP port:(0-65535) or 'Any',
         specific or port range applicable for IP protocol UDP/TCP. "
   ::= { gs2310pQosQceEntry 31 }


gs2310pQosIpv6ProtocolTCPDport OBJECT-TYPE
   SYNTAX      DisplayString
   MAX-ACCESS  read-write
   STATUS      current
   DESCRIPTION
       " Destination TCP/UDP port:(0-65535) or 'Any',
         specific or port range applicable for IP protocol UDP/TCP. "
   ::= { gs2310pQosQceEntry 32 }

gs2310pQosIpv6Ip OBJECT-TYPE
   SYNTAX      DisplayString
   MAX-ACCESS  read-write
   STATUS      current
   DESCRIPTION
       " IPv6 source address: (a.b.c.d) or value 0.0.0.0 is 'Any', 32 LS bits.
         If a port is configured to match on DMAC/DIP, this field is the
         Destination IP address."
   ::= { gs2310pQosQceEntry 33 }

gs2310pQosIpv6Mask OBJECT-TYPE
   SYNTAX      DisplayString
   MAX-ACCESS  read-write
   STATUS      current
   DESCRIPTION
       " IPv6 mask address: (a.b.c.d) or value 0.0.0.0 is 'Any', 32 LS bits. "
   ::= { gs2310pQosQceEntry 34 }

gs2310pQosIpv6DSCP OBJECT-TYPE
   SYNTAX      DisplayString
   MAX-ACCESS  read-write
   STATUS      current
   DESCRIPTION
       " Diffserv Code Point value (DSCP): It can be a specific value,
         range of values or 'Any'. DSCP values are in the range 0-63 including BE,
         CS1-CS7, EF or AF11-AF43. "
   ::= { gs2310pQosQceEntry 35 }

gs2310pQosActionClass  OBJECT-TYPE
   SYNTAX      Integer32(0..8)
   MAX-ACCESS  read-write
   STATUS      current
   DESCRIPTION
       " QoS class: (0-7) or 8: Default."
   ::= { gs2310pQosQceEntry 36 }

gs2310pQosActionDPL OBJECT-TYPE
   SYNTAX      INTEGER (0..4)
   MAX-ACCESS  read-write
   STATUS      current
   DESCRIPTION
       " DP Valid Drop Precedence Level can be (0-3) or 4: Default. "
   ::= { gs2310pQosQceEntry 37 }

gs2310pQosActionDSCP OBJECT-TYPE
   SYNTAX      Integer32(0..64)
   MAX-ACCESS  read-write
   STATUS      current
   DESCRIPTION
       " Valid DSCP value can be (0-63, BE, CS1-CS7, EF or AF11-AF43) or 64: Default. "
   ::= { gs2310pQosQceEntry 38 }

gs2310pQosQceRowStatus OBJECT-TYPE
   SYNTAX      INTEGER { active(1), notInservice(2), destroy(4) }
   MAX-ACCESS  read-write
   STATUS      current
   DESCRIPTION
       "  1: active2: notInservice 4: destroy"
   ::= { gs2310pQosQceEntry 39 }

gs2310pQosQceMoveID OBJECT-TYPE
   SYNTAX       Integer32(0..256)
   MAX-ACCESS   read-write
   STATUS       current
   DESCRIPTION
       " Move Qos,
         default: 0
         Qos ID must be exist.
         range : 0 - 256."
   ::= { gs2310pQosControlList 3 }

gs2310pQosQceMoveNextID OBJECT-TYPE
   SYNTAX       Integer32(0..256)
   MAX-ACCESS   read-write
   STATUS       current
   DESCRIPTION
       " Move Qos,
         default: 0
         If the next Qos ID is non zero, the Qos will be placed before this Qos in the list.
         If the next Qos ID is zero,the Qos will be placed last in the list.
         range : 0 - 256. "
   ::= { gs2310pQosControlList 4 }


gs2310pQosQCLStatusTable OBJECT-TYPE
   SYNTAX      SEQUENCE OF Gs2310pQosQCLStatusEntry
   MAX-ACCESS  not-accessible
   STATUS      current
   DESCRIPTION
       "  configure the basic QoS DSCP Translation settings for all switches. "
   ::= { gs2310pQos  10 }

gs2310pQosQCLStatusEntry OBJECT-TYPE
   SYNTAX      Gs2310pQosQCLStatusEntry
   MAX-ACCESS  not-accessible
   STATUS      current
   DESCRIPTION
       ""
   INDEX    { gs2310pQosQCLStatusList  }
   ::= { gs2310pQosQCLStatusTable 1 }

Gs2310pQosQCLStatusEntry ::= SEQUENCE {
   gs2310pQosQCLStatusList               Integer32,
   gs2310pQosQCLStatusUser               DisplayString,
   gs2310pQosQCLStatusQCEId              DisplayString,
   gs2310pQosQCLStatusFrameType          DisplayString,
   gs2310pQosQCLStatusPortlist           DisplayString,
   gs2310pQosQCLStatusActionClass	       DisplayString,
   gs2310pQosQCLStatusActionDPL	       DisplayString,
   gs2310pQosQCLStatusActionDSCP	       DisplayString,
   gs2310pQosQCLStatusActionConflict     DisplayString
}

gs2310pQosQCLStatusList OBJECT-TYPE
   SYNTAX      Integer32(1..4095)
   MAX-ACCESS  not-accessible
   STATUS      current
   DESCRIPTION
       " QCL table index. "
   ::= { gs2310pQosQCLStatusEntry 1}

gs2310pQosQCLStatusUser OBJECT-TYPE
   SYNTAX      DisplayString
   MAX-ACCESS  read-only
   STATUS      current
   DESCRIPTION
       " Indicates the QCL user. "
   ::= { gs2310pQosQCLStatusEntry 2 }

gs2310pQosQCLStatusQCEId OBJECT-TYPE
   SYNTAX      DisplayString
   MAX-ACCESS  read-only
   STATUS      current
   DESCRIPTION
      " Indicates the index of QCE. "
   ::= { gs2310pQosQCLStatusEntry 3}

gs2310pQosQCLStatusFrameType OBJECT-TYPE
   SYNTAX      DisplayString
   MAX-ACCESS  read-only
   STATUS      current
   DESCRIPTION
       " Indicates the type of frame to look for incomming frames.
       Any: The QCE will match all frame type.
       Ethernet: Only Ethernet frames (with Ether Type 0x600-0xFFFF) are allowed.
       LLC: Only (LLC) frames are allowed.
       SNAP: Only (SNAP) frames are allowed.
       IPv4: The QCE will match only IPV4 frames.
       IPv6: The QCE will match only IPV6 frames."
   ::= { gs2310pQosQCLStatusEntry 4}

gs2310pQosQCLStatusPortlist OBJECT-TYPE
   SYNTAX      DisplayString
   MAX-ACCESS  read-only
   STATUS      current
   DESCRIPTION
       " Indicates the list of ports configured with the QCE. "
   ::= { gs2310pQosQCLStatusEntry 5}

gs2310pQosQCLStatusActionClass OBJECT-TYPE
   SYNTAX      DisplayString
   MAX-ACCESS  read-only
   STATUS      current
   DESCRIPTION
       " Classified QoS class; if a frame matches the QCE it will be put in the
       queue. "
   ::= { gs2310pQosQCLStatusEntry 6}

gs2310pQosQCLStatusActionDPL OBJECT-TYPE
   SYNTAX      DisplayString
   MAX-ACCESS  read-only
   STATUS      current
   DESCRIPTION
       " Drop Precedence Level; if a frame matches the QCE then DP level will
       set to value displayed under DPL column."
   ::= { gs2310pQosQCLStatusEntry 7}

gs2310pQosQCLStatusActionDSCP OBJECT-TYPE
   SYNTAX      DisplayString
   MAX-ACCESS  read-only
   STATUS      current
   DESCRIPTION
       " If a frame matches the QCE then DSCP will be classified with the value
       displayed under DSCP column."
   ::= { gs2310pQosQCLStatusEntry 8}

gs2310pQosQCLStatusActionConflict OBJECT-TYPE
   SYNTAX      DisplayString
   MAX-ACCESS  read-only
   STATUS      current
   DESCRIPTION
       " If a frame matches the QCE then DSCP will be classified with the value
        displayed under DSCP column. "
   ::= { gs2310pQosQCLStatusEntry 9}


gs2310pQosStormControl                                           OBJECT IDENTIFIER ::= { gs2310pQos 11 }

gs2310pQoSStormControlUC OBJECT-TYPE
   SYNTAX      INTEGER { disable(0), enable(1) }
   MAX-ACCESS  read-write
   STATUS      current
   DESCRIPTION
       "Enable or disable the storm control status for the Unicast frame type.
       default:  0
        0: disable
        1: enable"
   ::= { gs2310pQosStormControl 2 }

gs2310pQoSStormControlUCRate OBJECT-TYPE
   SYNTAX      DisplayString
   MAX-ACCESS  read-write
   STATUS      current
   DESCRIPTION
       "The rate unit is packets per second (pps). Valid values are: 1, 2, 4, 8,
        16, 32, 64, 128, 256, 512, 1K, 2K, 4K, 8K, 16K, 32K, 64K, 128K, 256K,
        512K or 1024K."
   ::= { gs2310pQosStormControl 3 }

gs2310pQoSStormControlMC OBJECT-TYPE
   SYNTAX      INTEGER { disable(0), enable(1) }
   MAX-ACCESS  read-write
   STATUS      current
   DESCRIPTION
       "Enable or disable the storm control status for the Multicast frame type.
       default:  0
        0: disable
        1: enable"
   ::= { gs2310pQosStormControl 4 }

gs2310pQoSStormControlMCRate OBJECT-TYPE
   SYNTAX      DisplayString
   MAX-ACCESS  read-write
   STATUS      current
   DESCRIPTION
       "The rate unit is packets per second (pps). Valid values are: 1, 2, 4, 8,
        16, 32, 64, 128, 256, 512, 1K, 2K, 4K, 8K, 16K, 32K, 64K, 128K, 256K,
        512K or 1024K."
   ::= { gs2310pQosStormControl 5 }

gs2310pQoSStormControlBC OBJECT-TYPE
   SYNTAX      INTEGER { disable(0), enable(1) }
   MAX-ACCESS  read-write
   STATUS      current
   DESCRIPTION
       "Enable or disable the storm control status for the Broadcast frame type.
       default:  0
        0: disable
        1: enable"
   ::= { gs2310pQosStormControl 6 }

gs2310pQoSStormControlBCRate OBJECT-TYPE
   SYNTAX      DisplayString
   MAX-ACCESS  read-write
   STATUS      current
   DESCRIPTION
       "The rate unit is packets per second (pps). Valid values are: 1, 2, 4, 8,
        16, 32, 64, 128, 256, 512, 1K, 2K, 4K, 8K, 16K, 32K, 64K, 128K, 256K,
        512K or 1024K."
   ::= { gs2310pQosStormControl 7 }


gs2310pVlan                                                           OBJECT IDENTIFIER ::= { gs2310pConfiguration 15 }

gs2310pVlanPorts                                                      OBJECT IDENTIFIER ::= { gs2310pVlan 1 }

gs2310pVlanPortsTPIDforCustomSport  OBJECT-TYPE
   SYNTAX      OCTET STRING(SIZE(2))
   MAX-ACCESS  read-write
   STATUS      current
   DESCRIPTION
       "Configure the TPID used for Custom S-ports. This is a global setting for
       all the Custom S-ports.
       range: 0x0600-0xffff,
       default: 0x88a8. "
   ::= { gs2310pVlanPorts 1 }

gs2310pVlanPortsTable OBJECT-TYPE
   SYNTAX      SEQUENCE OF Gs2310pVlanPortsEntry
   MAX-ACCESS  not-accessible
   STATUS      current
   DESCRIPTION
       " Configure Vlan ports Configuration mode. "
   ::= { gs2310pVlanPorts 2 }

gs2310pVlanPortsEntry OBJECT-TYPE
   SYNTAX      Gs2310pVlanPortsEntry
   MAX-ACCESS  not-accessible
   STATUS      current
   DESCRIPTION
       ""
   INDEX    { gs2310pVlanPortsPort  }
   ::= { gs2310pVlanPortsTable 1 }

Gs2310pVlanPortsEntry ::= SEQUENCE {
   gs2310pVlanPortsPort	         Integer32,
   gs2310pVlanPortsPVID     Integer32,
   gs2310pVlanPortsFrameType      INTEGER,
   gs2310pVlanPortsIngressFilter  INTEGER,
   gs2310pVlanPortsEgressRule     INTEGER,
   gs2310pVlanPortsPortType       INTEGER
}

gs2310pVlanPortsPort OBJECT-TYPE
   SYNTAX      Integer32(1..4094)
   MAX-ACCESS  not-accessible
   STATUS      current
   DESCRIPTION
       " port, range : 1 - port number. "
   ::= { gs2310pVlanPortsEntry 1 }

gs2310pVlanPortsPVID OBJECT-TYPE
   SYNTAX      Integer32(1..4094)
   MAX-ACCESS  read-write
   STATUS      current
   DESCRIPTION
       "Configure PVID.
        range: 1-4094,
        default: 1. "
   ::= { gs2310pVlanPortsEntry 2 }

gs2310pVlanPortsFrameType OBJECT-TYPE
   SYNTAX      INTEGER { all(0), tagged(1), untagged(2) }
   MAX-ACCESS  read-write
   STATUS      current
   DESCRIPTION
       "Configure frame type of switch ports.
        0: all,
        1: tagged,
        2: untagged,
        default: all.  "
   ::= { gs2310pVlanPortsEntry 3 }

gs2310pVlanPortsIngressFilter OBJECT-TYPE
   SYNTAX      INTEGER { disable(0), enable(1) }
   MAX-ACCESS  read-write
   STATUS      current
   DESCRIPTION
       "Configure ingress filtering of switch ports.
        0: disable,
        1: enable,
        default:disable . "
   ::= { gs2310pVlanPortsEntry 4 }

gs2310pVlanPortsEgressRule OBJECT-TYPE
   SYNTAX      INTEGER { access(0), hybrid(1), trunk(2) }
   MAX-ACCESS  read-write
   STATUS      current
   DESCRIPTION
       "Configure egress-rule of switch ports.
        0: access,
        1: hybrid,
        2: trunk"
   ::= { gs2310pVlanPortsEntry 5 }

gs2310pVlanPortsPortType OBJECT-TYPE
   SYNTAX      INTEGER { cPort(0), sCustomPort(1), sPort(2), unaware(3) }
   MAX-ACCESS  read-write
   STATUS      current
   DESCRIPTION
       "Configure port type of switch ports.
        0: c-port,
        1: s-custom-port,
        2: s-port,
        3: unaware.
        default: c-port. "
   ::= { gs2310pVlanPortsEntry 6 }

gs2310pVlanPrivateVLAN                                                              OBJECT IDENTIFIER ::= { gs2310pVlan 2 }

gs2310pVlanPrivateVLANMembership                                                    OBJECT IDENTIFIER ::= { gs2310pVlanPrivateVLAN 1 }

gs2310pVlanPrivateVLANMembershipCreate OBJECT-TYPE
   SYNTAX       Integer32(1..4094)
   MAX-ACCESS   read-write
   STATUS       current
   DESCRIPTION
       "default: 0
        0 : None  (read only)
        1 : Create a pvlan"
   ::= { gs2310pVlanPrivateVLANMembership 1 }

gs2310pVlanPrivateVLANMembershipTable OBJECT-TYPE
   SYNTAX      SEQUENCE OF Gs2310pVlanPrivateVLANMembershipEntry
   MAX-ACCESS  not-accessible
   STATUS      current
   DESCRIPTION
       " Configure Private Vlan Configuration. "
   ::= { gs2310pVlanPrivateVLANMembership 2 }

gs2310pVlanPrivateVLANMembershipEntry OBJECT-TYPE
   SYNTAX      Gs2310pVlanPrivateVLANMembershipEntry
   MAX-ACCESS  not-accessible
   STATUS      current
   DESCRIPTION
       ""
   INDEX    { gs2310pVlanPrivateVLANIndex  }
   ::= { gs2310pVlanPrivateVLANMembershipTable 1 }

Gs2310pVlanPrivateVLANMembershipEntry ::= SEQUENCE {
   gs2310pVlanPrivateVLANIndex          Integer32,
   gs2310pVlanPrivateVLANID             Integer32,
   gs2310pVlanPrivateVLANMemberships    DisplayString,
   gs2310pVlanPrivateVLANRowStatus      INTEGER
}

gs2310pVlanPrivateVLANIndex OBJECT-TYPE
   SYNTAX      Integer32(1..52)
   MAX-ACCESS  not-accessible
   STATUS      current
   DESCRIPTION
       "private VLAN Index. "
   ::= { gs2310pVlanPrivateVLANMembershipEntry 1 }

gs2310pVlanPrivateVLANID OBJECT-TYPE
   SYNTAX      Integer32(1..52)
   MAX-ACCESS  read-write
   STATUS      current
   DESCRIPTION
       "Indicates the ID of this particular private VLAN.
       The CreateEntry can be modify, the other entry can't be modify."
   ::= { gs2310pVlanPrivateVLANMembershipEntry 2 }

gs2310pVlanPrivateVLANMemberships OBJECT-TYPE
   SYNTAX      DisplayString
   MAX-ACCESS  read-write
   STATUS      current
   DESCRIPTION
       "To include the ports in a Private VLAN"
   ::= { gs2310pVlanPrivateVLANMembershipEntry 3 }

gs2310pVlanPrivateVLANRowStatus OBJECT-TYPE
   SYNTAX      INTEGER { active(1), notInservice(2), destroy(4) }
   MAX-ACCESS  read-write
   STATUS      current
   DESCRIPTION
       "1: active
        2: notInservice
        4: destroy"
   ::= { gs2310pVlanPrivateVLANMembershipEntry 4 }

gs2310pVlanPortIsolationTable OBJECT-TYPE
   SYNTAX      SEQUENCE OF Gs2310pVlanPortIsolationEntry
   MAX-ACCESS  not-accessible
   STATUS      current
   DESCRIPTION
       " Configure Vlan Port Isolation Configuration. "
   ::= { gs2310pVlanPrivateVLAN 2 }

gs2310pVlanPortIsolationEntry OBJECT-TYPE
   SYNTAX      Gs2310pVlanPortIsolationEntry
   MAX-ACCESS  not-accessible
   STATUS      current
   DESCRIPTION
       ""
   INDEX    { gs2310pVlanPortIsolationPort  }
   ::= { gs2310pVlanPortIsolationTable 1 }

Gs2310pVlanPortIsolationEntry ::= SEQUENCE {
   gs2310pVlanPortIsolationPort Integer32,
   gs2310pVlanPortIsolation     INTEGER
}

gs2310pVlanPortIsolationPort OBJECT-TYPE
   SYNTAX      Integer32(1..4094)
   MAX-ACCESS  not-accessible
   STATUS      current
   DESCRIPTION
       " port, range : 1 - port number. "
   ::= { gs2310pVlanPortIsolationEntry 1 }

gs2310pVlanPortIsolation OBJECT-TYPE
   SYNTAX      INTEGER{ disable(0), enable(1) }
   MAX-ACCESS  read-write
   STATUS      current
   DESCRIPTION
       "default: 0
        0:disable
        1:enable"
   ::= { gs2310pVlanPortIsolationEntry 2 }


gs2310pMACbasedVLAN                                                      OBJECT IDENTIFIER ::= { gs2310pVlan 3 }

gs2310pMACbasedVLANConf                                                      OBJECT IDENTIFIER ::= { gs2310pMACbasedVLAN 1 }

gs2310pMACbasedVLANConfCreate OBJECT-TYPE
   SYNTAX       Integer32
   MAX-ACCESS   read-write
   STATUS       current
   DESCRIPTION
       "default: 0
       0 : None  (read only) 1 : Create MAC base vlan"
   ::= { gs2310pMACbasedVLANConf 1 }

gs2310pMACbasedVLANConfTable OBJECT-TYPE
   SYNTAX      SEQUENCE OF Gs2310pMACbasedVLANConfEntry
   MAX-ACCESS  not-accessible
   STATUS      current
   DESCRIPTION
       " Configure Vlan Port Isolation Configuration. "
   ::= { gs2310pMACbasedVLANConf 2 }

gs2310pMACbasedVLANConfEntry OBJECT-TYPE
   SYNTAX      Gs2310pMACbasedVLANConfEntry
   MAX-ACCESS  not-accessible
   STATUS      current
   DESCRIPTION
       ""
   INDEX    { gs2310pMACbasedVLANIndex  }
   ::= { gs2310pMACbasedVLANConfTable 1 }

Gs2310pMACbasedVLANConfEntry ::= SEQUENCE {
   gs2310pMACbasedVLANIndex         Integer32,
   gs2310pMACbasedVLANMACAddress    MacAddress,
   gs2310pMACbasedVLANID            Integer32,
   gs2310pMACbasedMemberships       DisplayString,
   gs2310pMACbaseRowStatus          INTEGER
}

gs2310pMACbasedVLANIndex OBJECT-TYPE
   SYNTAX      Integer32(1..256)
   MAX-ACCESS  read-write
   STATUS      current
   DESCRIPTION
       "Indicates the VLAN ID. "
   ::= { gs2310pMACbasedVLANConfEntry 1 }

gs2310pMACbasedVLANMACAddress OBJECT-TYPE
   SYNTAX      MacAddress
   MAX-ACCESS  read-write
   STATUS      current
   DESCRIPTION
       "Indicates the MAC address.
       The CreateEntry can be modify, the other entry can't be modify."
   ::= { gs2310pMACbasedVLANConfEntry 2 }

gs2310pMACbasedVLANID OBJECT-TYPE
   SYNTAX      Integer32(1..4094)
   MAX-ACCESS  read-write
   STATUS      current
   DESCRIPTION
       "Indicates the VLAN ID. "
   ::= { gs2310pMACbasedVLANConfEntry 3 }

gs2310pMACbasedMemberships OBJECT-TYPE
   SYNTAX      DisplayString
   MAX-ACCESS  read-write
   STATUS      current
   DESCRIPTION
       "The ports are displayed for each MAC-based VLAN entry.
        To include the port in a MAC-based VLAN"
   ::= { gs2310pMACbasedVLANConfEntry 4 }


gs2310pMACbaseRowStatus OBJECT-TYPE
   SYNTAX      INTEGER { active(1), notInservice(2), destroy(4)}
   MAX-ACCESS  read-write
   STATUS      current
   DESCRIPTION
       "1: active
        2: notInservice
        4: destroy"
   ::= { gs2310pMACbasedVLANConfEntry 5 }


gs2310pIGMPSnooping                                                           OBJECT IDENTIFIER ::= { gs2310pConfiguration 16 }

gs2310pIGMPSnoopingBasic                                                      OBJECT IDENTIFIER ::= { gs2310pIGMPSnooping 1 }

gs2310pIGMPSnoopingEnable  OBJECT-TYPE
   SYNTAX      INTEGER { disable(0), enable(1) }
   MAX-ACCESS  read-write
   STATUS      current
   DESCRIPTION
       "Enable/Disable the Global IGMP Snooping"
   ::= { gs2310pIGMPSnoopingBasic 1 }

gs2310pIGMPSnoopingUnregisteredIPMCv4Flooding  OBJECT-TYPE
   SYNTAX      INTEGER { disable(0), enable(1) }
   MAX-ACCESS  read-write
   STATUS      current
   DESCRIPTION
       "Enable/Disable unregistered IPMCv4 traffic flooding. "
   ::= { gs2310pIGMPSnoopingBasic 2 }

gs2310pIGMPSnoopingSSMIPRangeAddr  OBJECT-TYPE
   SYNTAX      DisplayString
   MAX-ACCESS  read-write
   STATUS      current
   DESCRIPTION
       "SSM (Source-Specific Multicast) Range allows the SSM-aware hosts and
       routers run the SSM service model for the groups in the address range. "
   ::= { gs2310pIGMPSnoopingBasic 3 }

gs2310pIGMPSnoopingSSMIPRangeValue  OBJECT-TYPE
   SYNTAX      Integer32(4..32)
   MAX-ACCESS  read-write
   STATUS      current
   DESCRIPTION
       "SSM (Source-Specific Multicast) Range allows the SSM-aware hosts and
       routers run the SSM service model for the groups in the address range value. "
   ::= { gs2310pIGMPSnoopingBasic 4 }

gs2310pIGMPSnoopingProxyEnabled  OBJECT-TYPE
   SYNTAX      INTEGER { disable(0), enable(1) }
   MAX-ACCESS  read-write
   STATUS      current
   DESCRIPTION
       "Enable/Disable IGMP Proxy. This feature can be used to avoid forwarding
       unnecessary join and leave messages to the router side. "
   ::= { gs2310pIGMPSnoopingBasic 5 }

gs2310pIGMPSnoopingPortRelatedTable OBJECT-TYPE
   SYNTAX      SEQUENCE OF Gs2310pIGMPSnoopingPortRelatedEntry
   MAX-ACCESS  not-accessible
   STATUS      current
   DESCRIPTION
       " Configure IGMP Snooping Port Related Configuration. "
   ::= { gs2310pIGMPSnoopingBasic 6 }

gs2310pIGMPSnoopingPortRelatedEntry OBJECT-TYPE
   SYNTAX      Gs2310pIGMPSnoopingPortRelatedEntry
   MAX-ACCESS  not-accessible
   STATUS      current
   DESCRIPTION
       ""
   INDEX    { ifIndex  }
   ::= { gs2310pIGMPSnoopingPortRelatedTable 1 }

Gs2310pIGMPSnoopingPortRelatedEntry ::= SEQUENCE {
   gs2310pIGMPSnoopingRouterPort	INTEGER,
   gs2310pIGMPSnoopingFastLeave  	INTEGER,
   gs2310pIGMPSnoopingThrottling    Integer32
}

gs2310pIGMPSnoopingRouterPort OBJECT-TYPE
   SYNTAX      INTEGER { disable(0), enable(1) }
   MAX-ACCESS  read-write
   STATUS      current
   DESCRIPTION
       "Specify which ports act as router ports. A router port is a port on the
       Ethernet switch that leads towards the Layer 3 multicast device or IGMP
       querier. If an aggregation member port is selected as a router port, the
       whole aggregation will act as a router port. "
   ::= { gs2310pIGMPSnoopingPortRelatedEntry 1 }

gs2310pIGMPSnoopingFastLeave OBJECT-TYPE
   SYNTAX      INTEGER { disable(0), enable(1) }
   MAX-ACCESS  read-write
   STATUS      current
   DESCRIPTION
       "Enable/Disable the fast leave on the port. "
   ::= { gs2310pIGMPSnoopingPortRelatedEntry 2 }

gs2310pIGMPSnoopingThrottling OBJECT-TYPE
   SYNTAX      Integer32(0..10)
   MAX-ACCESS  read-write
   STATUS      current
   DESCRIPTION
       "Enable to limit the number of multicast groups to which a switch port can belong.
       0: unlimited"
   ::= { gs2310pIGMPSnoopingPortRelatedEntry 3 }

gs2310pIGMPSnoopingVLANTable OBJECT-TYPE
   SYNTAX      SEQUENCE OF Gs2310pIGMPSnoopingVLANEntry
   MAX-ACCESS  not-accessible
   STATUS      current
   DESCRIPTION
       " Configure IGMP Snooping Vlan Configuration. "
   ::= { gs2310pIGMPSnooping 2 }

gs2310pIGMPSnoopingVLANEntry OBJECT-TYPE
   SYNTAX      Gs2310pIGMPSnoopingVLANEntry
   MAX-ACCESS  not-accessible
   STATUS      current
   DESCRIPTION
       ""
   INDEX    { gs2310pIGMPSnoopingVLANID  }
   ::= { gs2310pIGMPSnoopingVLANTable 1 }

Gs2310pIGMPSnoopingVLANEntry ::= SEQUENCE {
   gs2310pIGMPSnoopingVLANID        	Integer32,
   gs2310pIGMPSnoopingVLANEnable    	INTEGER,
   gs2310pIGMPSnoopingVLANIGMPQuerier   INTEGER,
   gs2310pIGMPSnoopingVLANCompatibility INTEGER,
   gs2310pIGMPSnoopingVLANRV        	Integer32,
   gs2310pIGMPSnoopingVLANQI      	    Integer32,
   gs2310pIGMPSnoopingVLANQRI   	    Integer32,
   gs2310pIGMPSnoopingVLANLLQI   	    Integer32,
   gs2310pIGMPSnoopingVLANURI    	    Integer32
}

gs2310pIGMPSnoopingVLANID OBJECT-TYPE
   SYNTAX      Integer32(1..4095)
   MAX-ACCESS  read-write
   STATUS      current
   DESCRIPTION
       "The VLAN ID of the entry"
   ::= { gs2310pIGMPSnoopingVLANEntry 1 }

gs2310pIGMPSnoopingVLANEnable OBJECT-TYPE
   SYNTAX      INTEGER { disable(0), enable(1) }
   MAX-ACCESS  read-write
   STATUS      current
   DESCRIPTION
       "Enable/Disable the per-VLAN IGMP Snooping. Up to 32 VLANs can be
       selected for IGMP Snooping. "
   ::= { gs2310pIGMPSnoopingVLANEntry 2 }

gs2310pIGMPSnoopingVLANIGMPQuerier OBJECT-TYPE
   SYNTAX      INTEGER { disable(0), enable(1) }
   MAX-ACCESS  read-write
   STATUS      current
   DESCRIPTION
       "Enable/Disable the IGMP Querier in the VLAN. "
   ::= { gs2310pIGMPSnoopingVLANEntry 3 }

gs2310pIGMPSnoopingVLANCompatibility OBJECT-TYPE
   SYNTAX      INTEGER { igmpAuto(0), forcedIGMPv1(1), forcedIGMPv2(2), forcedIGMPv3(3), none(4) }
   MAX-ACCESS  read-write
   STATUS      current
   DESCRIPTION
       "Compatibility is maintained by hosts and routers taking appropriate
       actions depending on the versions of IGMP operating on hosts and routers
       within a network. The allowed selection is IGMP-Auto, Forced IGMPv1,
       Forced IGMPv2, Forced IGMPv3, default compatibility value is IGMP-Auto. "
   ::= { gs2310pIGMPSnoopingVLANEntry 4 }

gs2310pIGMPSnoopingVLANRV OBJECT-TYPE
   SYNTAX      Integer32(-1|1..255)
   MAX-ACCESS  read-write
   STATUS      current
   DESCRIPTION
       "Robustness Variable. The Robustness Variable allows tuning for the
       expected packet loss on a network. The allowed range is 1 to 255, default
        robustness variable value is 2. (-1: none)"
   ::= { gs2310pIGMPSnoopingVLANEntry 5 }

gs2310pIGMPSnoopingVLANQI OBJECT-TYPE
   SYNTAX      Integer32(-1|1..31744)
   MAX-ACCESS  read-write
   STATUS      current
   DESCRIPTION
       "Query Interval. The Query Interval is the interval between General
       Queries sent by the Querier. The allowed range is 1 to 31744 seconds,
       default query interval is 125 seconds.  (-1: none)"
   ::= { gs2310pIGMPSnoopingVLANEntry 6 }

gs2310pIGMPSnoopingVLANQRI OBJECT-TYPE
   SYNTAX      Integer32(-1|0..31744)
   MAX-ACCESS  read-write
   STATUS      current
   DESCRIPTION
       "Query Response Interval. The Maximum Response Delay used to calculate
       the Maximum Response Code inserted into the periodic General Queries. The
        allowed range is 0 to 31744 in tenths of seconds, default query response
         interval is 100 in tenths of seconds (10 seconds).   (-1: none)"
   ::= { gs2310pIGMPSnoopingVLANEntry 7 }

gs2310pIGMPSnoopingVLANLLQI OBJECT-TYPE
   SYNTAX      Integer32(-1|0..31744)
   MAX-ACCESS  read-write
   STATUS      current
   DESCRIPTION
       "LLQI (LMQI for IGMP).  Last Member Query Interval. The Last Member Query
       Time is the time value represented by the Last Member Query Interval,
       multiplied by the Last Member Query Count. The allowed range is 0 to
       31744 in tenths of seconds, default last member query interval is 10 in
       tenths of seconds (1 second).    (-1: none)"
   ::= { gs2310pIGMPSnoopingVLANEntry 8 }

gs2310pIGMPSnoopingVLANURI OBJECT-TYPE
   SYNTAX      Integer32(-1|0..31744)
   MAX-ACCESS  read-write
   STATUS      current
   DESCRIPTION
       "Unsolicited Report Interval. The Unsolicited Report Interval is the time
        between repetitions of a host's initial report of membership in a group.
         The allowed range is 0 to 31744 seconds, default unsolicited report
         interval is 1 second.    (-1: none)"
   ::= { gs2310pIGMPSnoopingVLANEntry 9 }

gs2310pIGMPSnoopingPortGroupFiltering                                                      OBJECT IDENTIFIER ::= { gs2310pIGMPSnooping 3 }

gs2310pIGMPSnoopingPortGroupFilteringCreate OBJECT-TYPE
   SYNTAX       Integer32
   MAX-ACCESS   read-write
   STATUS       current
   DESCRIPTION
       "default: 0
       0 : None  (read only) 1 : Create IGMP Snooping Port Group Filtering "
   ::= { gs2310pIGMPSnoopingPortGroupFiltering 1 }

gs2310pIGMPSnoopingPortGroupFilteringTable OBJECT-TYPE
   SYNTAX      SEQUENCE OF Gs2310pIGMPSnoopingPortGroupFilteringEntry
   MAX-ACCESS  not-accessible
   STATUS      current
   DESCRIPTION
       " Configure IGMP Snooping port group filtering. "
   ::= { gs2310pIGMPSnoopingPortGroupFiltering 2 }

gs2310pIGMPSnoopingPortGroupFilteringEntry OBJECT-TYPE
   SYNTAX      Gs2310pIGMPSnoopingPortGroupFilteringEntry
   MAX-ACCESS  not-accessible
   STATUS      current
   DESCRIPTION
       ""
   INDEX    { gs2310pIGMPSnoopingPortGroupFilteringIndex  }
   ::= { gs2310pIGMPSnoopingPortGroupFilteringTable 1 }

Gs2310pIGMPSnoopingPortGroupFilteringEntry ::= SEQUENCE {
   gs2310pIGMPSnoopingPortGroupFilteringIndex         Integer32,
   gs2310pIGMPSnoopingPortGroupFilteringPort          Integer32,
   gs2310pIGMPSnoopingPortGroupFilteringGroups        DisplayString,
   gs2310pIGMPSnoopingPortGroupFilteringRowStatus     INTEGER
}

gs2310pIGMPSnoopingPortGroupFilteringIndex OBJECT-TYPE
   SYNTAX      Integer32(1..65535)
   MAX-ACCESS  not-accessible
   STATUS      current
   DESCRIPTION
       "IGMP Snooping Port Group Filtering Configuration Index. "
   ::= { gs2310pIGMPSnoopingPortGroupFilteringEntry 1 }

gs2310pIGMPSnoopingPortGroupFilteringPort OBJECT-TYPE
   SYNTAX      Integer32(1..65535)
   MAX-ACCESS  read-write
   STATUS      current
   DESCRIPTION
       "The logical port for the settings. "
   ::= { gs2310pIGMPSnoopingPortGroupFilteringEntry 2 }

gs2310pIGMPSnoopingPortGroupFilteringGroups OBJECT-TYPE
   SYNTAX      DisplayString
   MAX-ACCESS  read-write
   STATUS      current
   DESCRIPTION
       "The IP Multicast Group that will be filtered. "
   ::= { gs2310pIGMPSnoopingPortGroupFilteringEntry 3 }

gs2310pIGMPSnoopingPortGroupFilteringRowStatus OBJECT-TYPE
   SYNTAX      INTEGER { active(1), notInservice(2), destroy(4)}
   MAX-ACCESS  read-write
   STATUS      current
   DESCRIPTION
       "1: active
        2: notInservice
        4: destroy"
   ::= { gs2310pIGMPSnoopingPortGroupFilteringEntry 4 }

gs2310pIGMPSnoopingStatus                                                      OBJECT IDENTIFIER ::= { gs2310pIGMPSnooping 4 }

gs2310pIGMPSnoopingstatisticClear OBJECT-TYPE
   SYNTAX      INTEGER { none(0), clear(1)}
   MAX-ACCESS  read-write
   STATUS      current
   DESCRIPTION
       "Clears all Statistics counters."
   ::= { gs2310pIGMPSnoopingStatus 1 }


gs2310pIGMPSnoopingstatisticTable OBJECT-TYPE
   SYNTAX      SEQUENCE OF Gs2310pIGMPSnoopingstatisticEntry
   MAX-ACCESS  not-accessible
   STATUS      current
   DESCRIPTION
       " Configure Vlan Port Isolation Configuration. "
   ::= { gs2310pIGMPSnoopingStatus 2 }

gs2310pIGMPSnoopingstatisticEntry OBJECT-TYPE
   SYNTAX      Gs2310pIGMPSnoopingstatisticEntry
   MAX-ACCESS  not-accessible
   STATUS      current
   DESCRIPTION
       ""
   INDEX    { gs2310pIGMPSnoopingstatisticVLANID  }
   ::= { gs2310pIGMPSnoopingstatisticTable 1 }

Gs2310pIGMPSnoopingstatisticEntry ::= SEQUENCE {
   gs2310pIGMPSnoopingstatisticVLANID              Integer32,
   gs2310pIGMPSnoopingstatisticQuerierVersion      DisplayString,
   gs2310pIGMPSnoopingstatisticHostVersion         DisplayString,
   gs2310pIGMPSnoopingstatisticQuerierStatus       DisplayString,
   gs2310pIGMPSnoopingstatisticQueriesTransmitted  Counter32,
   gs2310pIGMPSnoopingstatisticQueriesReceived     Counter32,
   gs2310pIGMPSnoopingstatisticV1ReportsReceived   Counter32,
   gs2310pIGMPSnoopingstatisticV2ReportsReceived   Counter32,
   gs2310pIGMPSnoopingstatisticV3ReportsReceived   Counter32,
   gs2310pIGMPSnoopingstatisticV2LeavesReceived    Counter32
}


gs2310pIGMPSnoopingstatisticVLANID OBJECT-TYPE
   SYNTAX      Integer32(1..4095)
   MAX-ACCESS  read-only
   STATUS      current
   DESCRIPTION
       "The VLAN ID of the entry. "
   ::= { gs2310pIGMPSnoopingstatisticEntry 1 }

gs2310pIGMPSnoopingstatisticQuerierVersion OBJECT-TYPE
   SYNTAX      DisplayString
   MAX-ACCESS  read-only
   STATUS      current
   DESCRIPTION
       "Working Querier Version currently. "
   ::= { gs2310pIGMPSnoopingstatisticEntry 2 }

gs2310pIGMPSnoopingstatisticHostVersion OBJECT-TYPE
   SYNTAX      DisplayString
   MAX-ACCESS  read-only
   STATUS      current
   DESCRIPTION
       "Working Host Version currently. "
   ::= { gs2310pIGMPSnoopingstatisticEntry 3 }

gs2310pIGMPSnoopingstatisticQuerierStatus OBJECT-TYPE
   SYNTAX      DisplayString
   MAX-ACCESS  read-only
   STATUS      current
   DESCRIPTION
       "Shows the Querier status is ACTIVE or IDLE. DISABLE denotes the specific
        interface is administratively disabled. "
   ::= { gs2310pIGMPSnoopingstatisticEntry 4 }

gs2310pIGMPSnoopingstatisticQueriesTransmitted OBJECT-TYPE
   SYNTAX      Counter32
   MAX-ACCESS  read-only
   STATUS      current
   DESCRIPTION
       "The number of Transmitted Queries. "
   ::= { gs2310pIGMPSnoopingstatisticEntry 5 }

gs2310pIGMPSnoopingstatisticQueriesReceived OBJECT-TYPE
   SYNTAX      Counter32
   MAX-ACCESS  read-only
   STATUS      current
   DESCRIPTION
       "The number of Received Queries. "
   ::= { gs2310pIGMPSnoopingstatisticEntry 6 }

gs2310pIGMPSnoopingstatisticV1ReportsReceived OBJECT-TYPE
   SYNTAX      Counter32
   MAX-ACCESS  read-only
   STATUS      current
   DESCRIPTION
       "The number of Received V1 Reports. "
   ::= { gs2310pIGMPSnoopingstatisticEntry 7 }

gs2310pIGMPSnoopingstatisticV2ReportsReceived OBJECT-TYPE
   SYNTAX      Counter32
   MAX-ACCESS  read-only
   STATUS      current
   DESCRIPTION
       "The number of Received V2 Reports. "
   ::= { gs2310pIGMPSnoopingstatisticEntry 8 }

gs2310pIGMPSnoopingstatisticV3ReportsReceived OBJECT-TYPE
   SYNTAX      Counter32
   MAX-ACCESS  read-only
   STATUS      current
   DESCRIPTION
       "The number of Received V3 Reports. "
   ::= { gs2310pIGMPSnoopingstatisticEntry 9 }

gs2310pIGMPSnoopingstatisticV2LeavesReceived OBJECT-TYPE
   SYNTAX      Counter32
   MAX-ACCESS  read-only
   STATUS      current
   DESCRIPTION
       "The number of Received V2 Leaves. "
   ::= { gs2310pIGMPSnoopingstatisticEntry 10 }

gs2310pIGMPSnoopingRouterPortTable OBJECT-TYPE
   SYNTAX      SEQUENCE OF Gs2310pIGMPSnoopingRouterPortEntry
   MAX-ACCESS  not-accessible
   STATUS      current
   DESCRIPTION
       " Configure Vlan Port Isolation Configuration. "
   ::= { gs2310pIGMPSnoopingStatus 3 }

gs2310pIGMPSnoopingRouterPortEntry OBJECT-TYPE
   SYNTAX      Gs2310pIGMPSnoopingRouterPortEntry
   MAX-ACCESS  not-accessible
   STATUS      current
   DESCRIPTION
       ""
   INDEX    { ifIndex  }
   ::= { gs2310pIGMPSnoopingRouterPortTable 1 }

Gs2310pIGMPSnoopingRouterPortEntry ::= SEQUENCE {
   gs2310pIGMPSnoopingRouterPortStatus            DisplayString
}

gs2310pIGMPSnoopingRouterPortStatus OBJECT-TYPE
   SYNTAX      DisplayString
   MAX-ACCESS  read-only
   STATUS      current
   DESCRIPTION
       "Display which ports act as router ports. A router port is a port on the
       Ethernet switch that leads towards the Layer 3 multicast device or IGMP
       querier.
       Static denotes the specific port is configured to be a router port.
       Dynamic denotes the specific port is learnt to be a router port.
       Both denote the specific port is configured or learnt to be a router port. "
   ::= { gs2310pIGMPSnoopingRouterPortEntry 1 }

gs2310pIGMPSnoopingGroupsTable OBJECT-TYPE
   SYNTAX      SEQUENCE OF Gs2310pIGMPSnoopingGroupsEntry
   MAX-ACCESS  not-accessible
   STATUS      current
   DESCRIPTION
       "IGMP Snooping Groups Information . "
   ::= { gs2310pIGMPSnooping 5 }

gs2310pIGMPSnoopingGroupsEntry OBJECT-TYPE
   SYNTAX      Gs2310pIGMPSnoopingGroupsEntry
   MAX-ACCESS  not-accessible
   STATUS      current
   DESCRIPTION
       ""
   INDEX    { gs2310pIGMPSnoopingGroupsIndex  }
   ::= { gs2310pIGMPSnoopingGroupsTable 1 }

Gs2310pIGMPSnoopingGroupsEntry ::= SEQUENCE {
   gs2310pIGMPSnoopingGroupsIndex          Integer32,
   gs2310pIGMPSnoopingGroupsVLANID         Integer32,
   gs2310pIGMPSnoopingGroups               InetAddress,
   gs2310pIGMPSnoopingGroupsMemberships    DisplayString
}

gs2310pIGMPSnoopingGroupsIndex OBJECT-TYPE
   SYNTAX      Integer32(1..65535)
   MAX-ACCESS  not-accessible
   STATUS      current
   DESCRIPTION
       "IGMP Snooping Groups Index"
   ::= { gs2310pIGMPSnoopingGroupsEntry 1 }

gs2310pIGMPSnoopingGroupsVLANID OBJECT-TYPE
   SYNTAX      Integer32(1..4095)
   MAX-ACCESS  read-only
   STATUS      current
   DESCRIPTION
       "VLAN ID of the group. "
   ::= { gs2310pIGMPSnoopingGroupsEntry 2 }

gs2310pIGMPSnoopingGroups OBJECT-TYPE
   SYNTAX      DisplayString
   MAX-ACCESS  read-only
   STATUS      current
   DESCRIPTION
       "Group address of the group displayed."
   ::= { gs2310pIGMPSnoopingGroupsEntry 3 }

gs2310pIGMPSnoopingGroupsMemberships OBJECT-TYPE
   SYNTAX      DisplayString
   MAX-ACCESS  read-only
   STATUS      current
   DESCRIPTION
       "Ports under this group."
   ::= { gs2310pIGMPSnoopingGroupsEntry 4 }

gs2310pIGMPSnoopingSSMTable OBJECT-TYPE
   SYNTAX      SEQUENCE OF Gs2310pIGMPSnoopingSSMEntry
   MAX-ACCESS  not-accessible
   STATUS      current
   DESCRIPTION
       "The IGMP SFM (Source-Filtered Multicast) Information Table also contains
        the SSM (Source-Specific Multicast) information. This table is sorted
         first by VLAN ID, then by group, and then by Port. Different source
         addresses belong to the same group are treated as single entry."
   ::= { gs2310pIGMPSnooping 6 }

gs2310pIGMPSnoopingSSMEntry OBJECT-TYPE
   SYNTAX      Gs2310pIGMPSnoopingSSMEntry
   MAX-ACCESS  not-accessible
   STATUS      current
   DESCRIPTION
       ""
   INDEX    { gs2310pIGMPSnoopingSSMIndex  }
   ::= { gs2310pIGMPSnoopingSSMTable 1 }

Gs2310pIGMPSnoopingSSMEntry ::= SEQUENCE {
   gs2310pIGMPSnoopingSSMIndex          Integer32,
   gs2310pIGMPSnoopingSSMVLANID         Integer32,
   gs2310pIGMPSnoopingSSMGroup          DisplayString,
   gs2310pIGMPSnoopingSSMPort           Integer32,
   gs2310pIGMPSnoopingSSMMode           DisplayString,
   gs2310pIGMPSnoopingSSMSourceAddress  DisplayString,
   gs2310pIGMPSnoopingSSMType           DisplayString
}

gs2310pIGMPSnoopingSSMIndex OBJECT-TYPE
   SYNTAX      Integer32(1..65535)
   MAX-ACCESS  not-accessible
   STATUS      current
   DESCRIPTION
       "IGMP Snooping SSM Index"
   ::= { gs2310pIGMPSnoopingSSMEntry 1 }

gs2310pIGMPSnoopingSSMVLANID OBJECT-TYPE
   SYNTAX      Integer32(1..4095)
   MAX-ACCESS  read-only
   STATUS      current
   DESCRIPTION
       "VLAN ID of the group. "
   ::= { gs2310pIGMPSnoopingSSMEntry 2 }

gs2310pIGMPSnoopingSSMGroup OBJECT-TYPE
   SYNTAX      DisplayString
   MAX-ACCESS  read-only
   STATUS      current
   DESCRIPTION
       "Group address of the group displayed."
   ::= { gs2310pIGMPSnoopingSSMEntry 3 }

gs2310pIGMPSnoopingSSMPort OBJECT-TYPE
   SYNTAX      Integer32(1..65535)
   MAX-ACCESS  read-only
   STATUS      current
   DESCRIPTION
       "Ports under this group."
   ::= { gs2310pIGMPSnoopingSSMEntry 4 }

gs2310pIGMPSnoopingSSMMode OBJECT-TYPE
   SYNTAX      DisplayString
   MAX-ACCESS  read-only
   STATUS      current
   DESCRIPTION
       "Indicates the filtering mode maintained per (VLAN ID, port number,
       Group Address) basis. It can be either Include or Exclude."
   ::= { gs2310pIGMPSnoopingSSMEntry 5 }

gs2310pIGMPSnoopingSSMSourceAddress OBJECT-TYPE
   SYNTAX      DisplayString
   MAX-ACCESS  read-only
   STATUS      current
   DESCRIPTION
       "IP Address of the source. Currently, system limits the total number of
       IP source addresses for filtering to be 128."
   ::= { gs2310pIGMPSnoopingSSMEntry 6 }

gs2310pIGMPSnoopingSSMType OBJECT-TYPE
   SYNTAX      DisplayString
   MAX-ACCESS  read-only
   STATUS      current
   DESCRIPTION
       "Indicates the Type. It can be either Allow or Deny."
   ::= { gs2310pIGMPSnoopingSSMEntry 7 }

gs2310pMLDSnooping                                                           OBJECT IDENTIFIER ::= { gs2310pConfiguration 17 }

gs2310pMLDSnoopingBasic                                                      OBJECT IDENTIFIER ::= { gs2310pMLDSnooping 1 }

gs2310pMLDSnoopingEnable  OBJECT-TYPE
   SYNTAX      INTEGER { disable(0), enable(1) }
   MAX-ACCESS  read-write
   STATUS      current
   DESCRIPTION
       "Enable/Disable the Global MLD Snooping"
   ::= { gs2310pMLDSnoopingBasic 1 }

gs2310pMLDSnoopingUnregisteredIPMCv6Flooding  OBJECT-TYPE
   SYNTAX      INTEGER { disable(0), enable(1) }
   MAX-ACCESS  read-write
   STATUS      current
   DESCRIPTION
       "Enable/Disable unregistered IPMCv6 traffic flooding. "
   ::= { gs2310pMLDSnoopingBasic 2 }

gs2310pMLDSnoopingSSMIPRangeAddr  OBJECT-TYPE
   SYNTAX      DisplayString
   MAX-ACCESS  read-write
   STATUS      current
   DESCRIPTION
       "SSM (Source-Specific Multicast) Range allows the SSM-aware hosts and
       routers run the SSM service model for the groups in the address range. "
   ::= { gs2310pMLDSnoopingBasic 3 }

gs2310pMLDSnoopingSSMIPRangeValue  OBJECT-TYPE
   SYNTAX      Integer32(8..128)
   MAX-ACCESS  read-write
   STATUS      current
   DESCRIPTION
       "SSM (Source-Specific Multicast) Range allows the SSM-aware hosts and
       routers run the SSM service model for the groups in the address range value. "
   ::= { gs2310pMLDSnoopingBasic 4 }

gs2310pMLDSnoopingProxyEnabled  OBJECT-TYPE
   SYNTAX      INTEGER { disable(0), enable(1) }
   MAX-ACCESS  read-write
   STATUS      current
   DESCRIPTION
       "Enable/Disable MLD Proxy. This feature can be used to avoid forwarding
       unnecessary join and leave messages to the router side. "
   ::= { gs2310pMLDSnoopingBasic 5 }

gs2310pMLDSnoopingPortRelatedTable OBJECT-TYPE
   SYNTAX      SEQUENCE OF Gs2310pMLDSnoopingPortRelatedEntry
   MAX-ACCESS  not-accessible
   STATUS      current
   DESCRIPTION
       " Configure MLD Snooping Port Related Configuration. "
   ::= { gs2310pMLDSnoopingBasic 6 }

gs2310pMLDSnoopingPortRelatedEntry OBJECT-TYPE
   SYNTAX      Gs2310pMLDSnoopingPortRelatedEntry
   MAX-ACCESS  not-accessible
   STATUS      current
   DESCRIPTION
       ""
   INDEX    { ifIndex  }
   ::= { gs2310pMLDSnoopingPortRelatedTable 1 }

Gs2310pMLDSnoopingPortRelatedEntry ::= SEQUENCE {
   gs2310pMLDSnoopingRouterPort	INTEGER,
   gs2310pMLDSnoopingFastLeave  	INTEGER,
   gs2310pMLDSnoopingThrottling    Integer32
}

gs2310pMLDSnoopingRouterPort OBJECT-TYPE
   SYNTAX      INTEGER { disable(0), enable(1) }
   MAX-ACCESS  read-write
   STATUS      current
   DESCRIPTION
       "Specify which ports act as router ports. A router port is a port on the
       Ethernet switch that leads towards the Layer 3 multicast device or IGMP
       querier. If an aggregation member port is selected as a router port, the
       whole aggregation will act as a router port. "
   ::= { gs2310pMLDSnoopingPortRelatedEntry 1 }

gs2310pMLDSnoopingFastLeave OBJECT-TYPE
   SYNTAX      INTEGER { disable(0), enable(1) }
   MAX-ACCESS  read-write
   STATUS      current
   DESCRIPTION
       "Enable/Disable the fast leave on the port. "
   ::= { gs2310pMLDSnoopingPortRelatedEntry 2 }

gs2310pMLDSnoopingThrottling OBJECT-TYPE
   SYNTAX      Integer32(0..10)
   MAX-ACCESS  read-write
   STATUS      current
   DESCRIPTION
       "Enable to limit the number of multicast groups to which a switch port can belong.
       0: unlimited"
   ::= { gs2310pMLDSnoopingPortRelatedEntry 3 }

gs2310pMLDSnoopingVLANTable OBJECT-TYPE
   SYNTAX      SEQUENCE OF Gs2310pMLDSnoopingVLANEntry
   MAX-ACCESS  not-accessible
   STATUS      current
   DESCRIPTION
       " Configure MLD Snooping Vlan Configuration. "
   ::= { gs2310pMLDSnooping 2 }

gs2310pMLDSnoopingVLANEntry OBJECT-TYPE
   SYNTAX      Gs2310pMLDSnoopingVLANEntry
   MAX-ACCESS  not-accessible
   STATUS      current
   DESCRIPTION
       ""
   INDEX    { gs2310pMLDSnoopingVLANID  }
   ::= { gs2310pMLDSnoopingVLANTable 1 }

Gs2310pMLDSnoopingVLANEntry ::= SEQUENCE {
   gs2310pMLDSnoopingVLANID        	Integer32,
   gs2310pMLDSnoopingVLANEnable    	INTEGER,
   gs2310pMLDSnoopingVLANIGMPQuerier   INTEGER,
   gs2310pMLDSnoopingVLANCompatibility INTEGER,
   gs2310pMLDSnoopingVLANRV        	Integer32,
   gs2310pMLDSnoopingVLANQI      	    Integer32,
   gs2310pMLDSnoopingVLANQRI   	    Integer32,
   gs2310pMLDSnoopingVLANLLQI   	    Integer32,
   gs2310pMLDSnoopingVLANURI    	    Integer32
}

gs2310pMLDSnoopingVLANID OBJECT-TYPE
   SYNTAX      Integer32(1..4095)
   MAX-ACCESS  read-write
   STATUS      current
   DESCRIPTION
       "The VLAN ID of the entry"
   ::= { gs2310pMLDSnoopingVLANEntry 1 }

gs2310pMLDSnoopingVLANEnable OBJECT-TYPE
   SYNTAX      INTEGER { disable(0), enable(1) }
   MAX-ACCESS  read-write
   STATUS      current
   DESCRIPTION
       "Enable/Disable the per-VLAN MLD Snooping. Up to 32 VLANs can be
       selected for MLD Snooping. "
   ::= { gs2310pMLDSnoopingVLANEntry 2 }

gs2310pMLDSnoopingVLANIGMPQuerier OBJECT-TYPE
   SYNTAX      INTEGER { disable(0), enable(1) }
   MAX-ACCESS  read-write
   STATUS      current
   DESCRIPTION
       "Enable/Disable the MLD Querier in the VLAN. "
   ::= { gs2310pMLDSnoopingVLANEntry 3 }

gs2310pMLDSnoopingVLANCompatibility OBJECT-TYPE
   SYNTAX      INTEGER { mldAuto(0), forcedMLDv1(1), forcedMLDv2(2), none(3) }
   MAX-ACCESS  read-write
   STATUS      current
   DESCRIPTION
       "Compatibility is maintained by hosts and routers taking appropriate
       actions depending on the versions of IGMP operating on hosts and routers
       within a network. The allowed selection is MLD-Auto, Forced MLDv1,
       Forced MLDv2, default compatibility value is IGMP-Auto. "
   ::= { gs2310pMLDSnoopingVLANEntry 4 }

gs2310pMLDSnoopingVLANRV OBJECT-TYPE
   SYNTAX      Integer32(-1|1..255)
   MAX-ACCESS  read-write
   STATUS      current
   DESCRIPTION
       "Robustness Variable. The Robustness Variable allows tuning for the
       expected packet loss on a network. The allowed range is 1 to 255, default
        robustness variable value is 2. (-1: none)"
   ::= { gs2310pMLDSnoopingVLANEntry 5 }

gs2310pMLDSnoopingVLANQI OBJECT-TYPE
   SYNTAX      Integer32(-1|1..31744)
   MAX-ACCESS  read-write
   STATUS      current
   DESCRIPTION
       "Query Interval. The Query Interval is the interval between General
       Queries sent by the Querier. The allowed range is 1 to 31744 seconds,
       default query interval is 125 seconds.  (-1: none)"
   ::= { gs2310pMLDSnoopingVLANEntry 6 }

gs2310pMLDSnoopingVLANQRI OBJECT-TYPE
   SYNTAX      Integer32(-1|0..31744)
   MAX-ACCESS  read-write
   STATUS      current
   DESCRIPTION
       "Query Response Interval. The Maximum Response Delay used to calculate
       the Maximum Response Code inserted into the periodic General Queries. The
        allowed range is 0 to 31744 in tenths of seconds, default query response
         interval is 100 in tenths of seconds (10 seconds).   (-1: none)"
   ::= { gs2310pMLDSnoopingVLANEntry 7 }

gs2310pMLDSnoopingVLANLLQI OBJECT-TYPE
   SYNTAX      Integer32(-1|0..31744)
   MAX-ACCESS  read-write
   STATUS      current
   DESCRIPTION
       "LLQI (LMQI for MLD).  Last Member Query Interval. The Last Member Query
       Time is the time value represented by the Last Member Query Interval,
       multiplied by the Last Member Query Count. The allowed range is 0 to
       31744 in tenths of seconds, default last member query interval is 10 in
       tenths of seconds (1 second).    (-1: none)"
   ::= { gs2310pMLDSnoopingVLANEntry 8 }

gs2310pMLDSnoopingVLANURI OBJECT-TYPE
   SYNTAX      Integer32(-1|0..31744)
   MAX-ACCESS  read-write
   STATUS      current
   DESCRIPTION
       "Unsolicited Report Interval. The Unsolicited Report Interval is the time
        between repetitions of a host's initial report of membership in a group.
         The allowed range is 0 to 31744 seconds, default unsolicited report
         interval is 1 second.    (-1: none)"
   ::= { gs2310pMLDSnoopingVLANEntry 9 }

gs2310pMLDSnoopingPortGroupFiltering                                                      OBJECT IDENTIFIER ::= { gs2310pMLDSnooping 3 }

gs2310pMLDSnoopingPortGroupFilteringCreate OBJECT-TYPE
   SYNTAX       Integer32
   MAX-ACCESS   read-write
   STATUS       current
   DESCRIPTION
       "default: 0
       0 : None  (read only) 1 : Create MLD Snooping Port Group Filtering "
   ::= { gs2310pMLDSnoopingPortGroupFiltering 1 }

gs2310pMLDSnoopingPortGroupFilteringTable OBJECT-TYPE
   SYNTAX      SEQUENCE OF Gs2310pMLDSnoopingPortGroupFilteringEntry
   MAX-ACCESS  not-accessible
   STATUS      current
   DESCRIPTION
       " Configure MLD Snooping port group filtering. "
   ::= { gs2310pMLDSnoopingPortGroupFiltering 2 }

gs2310pMLDSnoopingPortGroupFilteringEntry OBJECT-TYPE
   SYNTAX      Gs2310pMLDSnoopingPortGroupFilteringEntry
   MAX-ACCESS  not-accessible
   STATUS      current
   DESCRIPTION
       ""
   INDEX    { gs2310pMLDSnoopingPortGroupFilteringIndex  }
   ::= { gs2310pMLDSnoopingPortGroupFilteringTable 1 }

Gs2310pMLDSnoopingPortGroupFilteringEntry ::= SEQUENCE {
   gs2310pMLDSnoopingPortGroupFilteringIndex         Integer32,
   gs2310pMLDSnoopingPortGroupFilteringPort          Integer32,
   gs2310pMLDSnoopingPortGroupFilteringGroups        DisplayString,
   gs2310pMLDSnoopingPortGroupFilteringRowStatus     INTEGER
}

gs2310pMLDSnoopingPortGroupFilteringIndex OBJECT-TYPE
   SYNTAX      Integer32(1..65535)
   MAX-ACCESS  not-accessible
   STATUS      current
   DESCRIPTION
       "MLD Snooping Port Group Filtering Configuration Index. "
   ::= { gs2310pMLDSnoopingPortGroupFilteringEntry 1 }

gs2310pMLDSnoopingPortGroupFilteringPort OBJECT-TYPE
   SYNTAX      Integer32(1..65535)
   MAX-ACCESS  read-write
   STATUS      current
   DESCRIPTION
       "The logical port for the settings. "
   ::= { gs2310pMLDSnoopingPortGroupFilteringEntry 2 }

gs2310pMLDSnoopingPortGroupFilteringGroups OBJECT-TYPE
   SYNTAX      DisplayString
   MAX-ACCESS  read-write
   STATUS      current
   DESCRIPTION
       "The IP Multicast Group that will be filtered. "
   ::= { gs2310pMLDSnoopingPortGroupFilteringEntry 3 }

gs2310pMLDSnoopingPortGroupFilteringRowStatus OBJECT-TYPE
   SYNTAX      INTEGER { active(1), notInservice(2), destroy(4)}
   MAX-ACCESS  read-write
   STATUS      current
   DESCRIPTION
       "1: active
        2: notInservice
        4: destroy"
   ::= { gs2310pMLDSnoopingPortGroupFilteringEntry 4 }

gs2310pMLDSnoopingStatus                                                      OBJECT IDENTIFIER ::= { gs2310pMLDSnooping 4 }

gs2310pMLDSnoopingstatisticClear OBJECT-TYPE
   SYNTAX      INTEGER { none(0), clear(1)}
   MAX-ACCESS  read-write
   STATUS      current
   DESCRIPTION
       "Clears all Statistics counters."
   ::= { gs2310pMLDSnoopingStatus 1 }


gs2310pMLDSnoopingstatisticTable OBJECT-TYPE
   SYNTAX      SEQUENCE OF Gs2310pMLDSnoopingstatisticEntry
   MAX-ACCESS  not-accessible
   STATUS      current
   DESCRIPTION
       " Configure Vlan Port Isolation Configuration. "
   ::= { gs2310pMLDSnoopingStatus 2 }

gs2310pMLDSnoopingstatisticEntry OBJECT-TYPE
   SYNTAX      Gs2310pMLDSnoopingstatisticEntry
   MAX-ACCESS  not-accessible
   STATUS      current
   DESCRIPTION
       ""
   INDEX    { gs2310pMLDSnoopingstatisticVLANID  }
   ::= { gs2310pMLDSnoopingstatisticTable 1 }

Gs2310pMLDSnoopingstatisticEntry ::= SEQUENCE {
   gs2310pMLDSnoopingstatisticVLANID              Integer32,
   gs2310pMLDSnoopingstatisticQuerierVersion      DisplayString,
   gs2310pMLDSnoopingstatisticHostVersion         DisplayString,
   gs2310pMLDSnoopingstatisticQuerierStatus       DisplayString,
   gs2310pMLDSnoopingstatisticQueriesTransmitted  Counter32,
   gs2310pMLDSnoopingstatisticQueriesReceived     Counter32,
   gs2310pMLDSnoopingstatisticV1ReportsReceived   Counter32,
   gs2310pMLDSnoopingstatisticV2ReportsReceived   Counter32,
   gs2310pMLDSnoopingstatisticV1LeavesReceived    Counter32
}


gs2310pMLDSnoopingstatisticVLANID OBJECT-TYPE
   SYNTAX      Integer32(1..4095)
   MAX-ACCESS  read-only
   STATUS      current
   DESCRIPTION
       "The VLAN ID of the entry. "
   ::= { gs2310pMLDSnoopingstatisticEntry 1 }

gs2310pMLDSnoopingstatisticQuerierVersion OBJECT-TYPE
   SYNTAX      DisplayString
   MAX-ACCESS  read-only
   STATUS      current
   DESCRIPTION
       "Working Querier Version currently. "
   ::= { gs2310pMLDSnoopingstatisticEntry 2 }

gs2310pMLDSnoopingstatisticHostVersion OBJECT-TYPE
   SYNTAX      DisplayString
   MAX-ACCESS  read-only
   STATUS      current
   DESCRIPTION
       "Working Host Version currently. "
   ::= { gs2310pMLDSnoopingstatisticEntry 3 }

gs2310pMLDSnoopingstatisticQuerierStatus OBJECT-TYPE
   SYNTAX      DisplayString
   MAX-ACCESS  read-only
   STATUS      current
   DESCRIPTION
       "Shows the Querier status is ACTIVE or IDLE. DISABLE denotes the specific
        interface is administratively disabled. "
   ::= { gs2310pMLDSnoopingstatisticEntry 4 }

gs2310pMLDSnoopingstatisticQueriesTransmitted OBJECT-TYPE
   SYNTAX      Counter32
   MAX-ACCESS  read-only
   STATUS      current
   DESCRIPTION
       "The number of Transmitted Queries. "
   ::= { gs2310pMLDSnoopingstatisticEntry 5 }

gs2310pMLDSnoopingstatisticQueriesReceived OBJECT-TYPE
   SYNTAX      Counter32
   MAX-ACCESS  read-only
   STATUS      current
   DESCRIPTION
       "The number of Received Queries. "
   ::= { gs2310pMLDSnoopingstatisticEntry 6 }

gs2310pMLDSnoopingstatisticV1ReportsReceived OBJECT-TYPE
   SYNTAX      Counter32
   MAX-ACCESS  read-only
   STATUS      current
   DESCRIPTION
       "The number of Received V1 Reports. "
   ::= { gs2310pMLDSnoopingstatisticEntry 7 }

gs2310pMLDSnoopingstatisticV2ReportsReceived OBJECT-TYPE
   SYNTAX      Counter32
   MAX-ACCESS  read-only
   STATUS      current
   DESCRIPTION
       "The number of Received V2 Reports. "
   ::= { gs2310pMLDSnoopingstatisticEntry 8 }

gs2310pMLDSnoopingstatisticV1LeavesReceived OBJECT-TYPE
   SYNTAX      Counter32
   MAX-ACCESS  read-only
   STATUS      current
   DESCRIPTION
       "The number of Received V1 Leaves. "
   ::= { gs2310pMLDSnoopingstatisticEntry 9 }

gs2310pMLDSnoopingRouterPortTable OBJECT-TYPE
   SYNTAX      SEQUENCE OF Gs2310pMLDSnoopingRouterPortEntry
   MAX-ACCESS  not-accessible
   STATUS      current
   DESCRIPTION
       " Configure Vlan Port Isolation Configuration. "
   ::= { gs2310pMLDSnoopingStatus 3 }

gs2310pMLDSnoopingRouterPortEntry OBJECT-TYPE
   SYNTAX      Gs2310pMLDSnoopingRouterPortEntry
   MAX-ACCESS  not-accessible
   STATUS      current
   DESCRIPTION
       ""
   INDEX    { ifIndex  }
   ::= { gs2310pMLDSnoopingRouterPortTable 1 }

Gs2310pMLDSnoopingRouterPortEntry ::= SEQUENCE {
   gs2310pMLDSnoopingRouterPortStatus            DisplayString
}

gs2310pMLDSnoopingRouterPortStatus OBJECT-TYPE
   SYNTAX      DisplayString
   MAX-ACCESS  read-only
   STATUS      current
   DESCRIPTION
       "Display which ports act as router ports. A router port is a port on the
       Ethernet switch that leads towards the Layer 3 multicast device or IGMP
       querier.
       Static denotes the specific port is configured to be a router port.
       Dynamic denotes the specific port is learnt to be a router port.
       Both denote the specific port is configured or learnt to be a router port. "
   ::= { gs2310pMLDSnoopingRouterPortEntry 1 }

gs2310pMLDSnoopingGroupsTable OBJECT-TYPE
   SYNTAX      SEQUENCE OF Gs2310pMLDSnoopingGroupsEntry
   MAX-ACCESS  not-accessible
   STATUS      current
   DESCRIPTION
       "MLD Snooping Groups Information . "
   ::= { gs2310pMLDSnooping 5 }

gs2310pMLDSnoopingGroupsEntry OBJECT-TYPE
   SYNTAX      Gs2310pMLDSnoopingGroupsEntry
   MAX-ACCESS  not-accessible
   STATUS      current
   DESCRIPTION
       ""
   INDEX    { gs2310pMLDSnoopingGroupsIndex  }
   ::= { gs2310pMLDSnoopingGroupsTable 1 }

Gs2310pMLDSnoopingGroupsEntry ::= SEQUENCE {
   gs2310pMLDSnoopingGroupsIndex          Integer32,
   gs2310pMLDSnoopingGroupsVLANID         Integer32,
   gs2310pMLDSnoopingGroups               InetAddress,
   gs2310pMLDSnoopingGroupsMemberships    DisplayString
}

gs2310pMLDSnoopingGroupsIndex OBJECT-TYPE
   SYNTAX      Integer32(1..65535)
   MAX-ACCESS  not-accessible
   STATUS      current
   DESCRIPTION
       "MLD Snooping Groups Index"
   ::= { gs2310pMLDSnoopingGroupsEntry 1 }

gs2310pMLDSnoopingGroupsVLANID OBJECT-TYPE
   SYNTAX      Integer32(1..4095)
   MAX-ACCESS  read-only
   STATUS      current
   DESCRIPTION
       "VLAN ID of the group. "
   ::= { gs2310pMLDSnoopingGroupsEntry 2 }

gs2310pMLDSnoopingGroups OBJECT-TYPE
   SYNTAX      DisplayString
   MAX-ACCESS  read-only
   STATUS      current
   DESCRIPTION
       "Group address of the group displayed."
   ::= { gs2310pMLDSnoopingGroupsEntry 3 }

gs2310pMLDSnoopingGroupsMemberships OBJECT-TYPE
   SYNTAX      DisplayString
   MAX-ACCESS  read-only
   STATUS      current
   DESCRIPTION
       "Ports under this group."
   ::= { gs2310pMLDSnoopingGroupsEntry 4 }

gs2310pMLDSnoopingSSMTable OBJECT-TYPE
   SYNTAX      SEQUENCE OF Gs2310pMLDSnoopingSSMEntry
   MAX-ACCESS  not-accessible
   STATUS      current
   DESCRIPTION
       "The MLD SFM (Source-Filtered Multicast) Information Table also contains
        the SSM (Source-Specific Multicast) information. This table is sorted
         first by VLAN ID, then by group, and then by Port. Different source
         addresses belong to the same group are treated as single entry."
   ::= { gs2310pMLDSnooping 6 }

gs2310pMLDSnoopingSSMEntry OBJECT-TYPE
   SYNTAX      Gs2310pMLDSnoopingSSMEntry
   MAX-ACCESS  not-accessible
   STATUS      current
   DESCRIPTION
       ""
   INDEX    { gs2310pMLDSnoopingSSMIndex  }
   ::= { gs2310pMLDSnoopingSSMTable 1 }

Gs2310pMLDSnoopingSSMEntry ::= SEQUENCE {
   gs2310pMLDSnoopingSSMIndex          Integer32,
   gs2310pMLDSnoopingSSMVLANID         Integer32,
   gs2310pMLDSnoopingSSMGroup          DisplayString,
   gs2310pMLDSnoopingSSMPort           Integer32,
   gs2310pMLDSnoopingSSMMode           DisplayString,
   gs2310pMLDSnoopingSSMSourceAddress  DisplayString,
   gs2310pMLDSnoopingSSMType           DisplayString
}

gs2310pMLDSnoopingSSMIndex OBJECT-TYPE
   SYNTAX      Integer32(1..65535)
   MAX-ACCESS  not-accessible
   STATUS      current
   DESCRIPTION
       "MLD Snooping SSM Index"
   ::= { gs2310pMLDSnoopingSSMEntry 1 }

gs2310pMLDSnoopingSSMVLANID OBJECT-TYPE
   SYNTAX      Integer32(1..4095)
   MAX-ACCESS  read-only
   STATUS      current
   DESCRIPTION
       "VLAN ID of the group. "
   ::= { gs2310pMLDSnoopingSSMEntry 2 }

gs2310pMLDSnoopingSSMGroup OBJECT-TYPE
   SYNTAX      DisplayString
   MAX-ACCESS  read-only
   STATUS      current
   DESCRIPTION
       "Group address of the group displayed."
   ::= { gs2310pMLDSnoopingSSMEntry 3 }

gs2310pMLDSnoopingSSMPort OBJECT-TYPE
   SYNTAX      Integer32(1..65535)
   MAX-ACCESS  read-only
   STATUS      current
   DESCRIPTION
       "Ports under this group."
   ::= { gs2310pMLDSnoopingSSMEntry 4 }

gs2310pMLDSnoopingSSMMode OBJECT-TYPE
   SYNTAX      DisplayString
   MAX-ACCESS  read-only
   STATUS      current
   DESCRIPTION
       "Indicates the filtering mode maintained per (VLAN ID, port number,
       Group Address) basis. It can be either Include or Exclude."
   ::= { gs2310pMLDSnoopingSSMEntry 5 }

gs2310pMLDSnoopingSSMSourceAddress OBJECT-TYPE
   SYNTAX      DisplayString
   MAX-ACCESS  read-only
   STATUS      current
   DESCRIPTION
       "IP Address of the source. Currently, system limits the total number of
       IP source addresses for filtering to be 128."
   ::= { gs2310pMLDSnoopingSSMEntry 6 }

gs2310pMLDSnoopingSSMType OBJECT-TYPE
   SYNTAX      DisplayString
   MAX-ACCESS  read-only
   STATUS      current
   DESCRIPTION
       "Indicates the Type. It can be either Allow or Deny."
   ::= { gs2310pMLDSnoopingSSMEntry 7 }


gs2310pMVR                                                                   OBJECT IDENTIFIER ::= { gs2310pConfiguration 18 }

gs2310pMVRConfiguration                                                      OBJECT IDENTIFIER ::= { gs2310pMVR 1 }

gs2310pMVRMode  OBJECT-TYPE
   SYNTAX      INTEGER { disable(0), enable(1) }
   MAX-ACCESS  read-write
   STATUS      current
   DESCRIPTION
       "Enable/Disable the Global MVR. "
   ::= { gs2310pMVRConfiguration 1 }

gs2310pMVRVLANId  OBJECT-TYPE
   SYNTAX      Integer32(1..4094)
   MAX-ACCESS  read-write
   STATUS      current
   DESCRIPTION
       "Specify the Multicast VLAN ID. "
   ::= { gs2310pMVRConfiguration 2 }

gs2310pMVRPortConfigurationTable OBJECT-TYPE
   SYNTAX      SEQUENCE OF Gs2310pMVRPortConfigurationEntry
   MAX-ACCESS  not-accessible
   STATUS      current
   DESCRIPTION
       " Configure MVR Port Configuration. "
   ::= { gs2310pMVRConfiguration 3 }

gs2310pMVRPortConfigurationEntry OBJECT-TYPE
   SYNTAX      Gs2310pMVRPortConfigurationEntry
   MAX-ACCESS  not-accessible
   STATUS      current
   DESCRIPTION
       ""
   INDEX    { ifIndex  }
   ::= { gs2310pMVRPortConfigurationTable 1 }

Gs2310pMVRPortConfigurationEntry ::= SEQUENCE {
   gs2310pMVRPortConfigurationMode	INTEGER,
   gs2310pMVRPortConfigurationType  	INTEGER,
   gs2310pMVRPortConfigurationImmediateLeave    INTEGER
}

gs2310pMVRPortConfigurationMode OBJECT-TYPE
   SYNTAX      INTEGER { disable(0), enable(1) }
   MAX-ACCESS  read-write
   STATUS      current
   DESCRIPTION
       "Enable MVR on the port. "
   ::= { gs2310pMVRPortConfigurationEntry 1 }

gs2310pMVRPortConfigurationType OBJECT-TYPE
   SYNTAX      INTEGER { receiver(0), source(1) }
   MAX-ACCESS  read-write
   STATUS      current
   DESCRIPTION
       "Specify the MVR port type on the port. "
   ::= { gs2310pMVRPortConfigurationEntry 2 }

gs2310pMVRPortConfigurationImmediateLeave OBJECT-TYPE
   SYNTAX      INTEGER { disable(0), enable(1) }
   MAX-ACCESS  read-write
   STATUS      current
   DESCRIPTION
       "Enable the fast leave on the port. "
   ::= { gs2310pMVRPortConfigurationEntry 3 }


gs2310pMVRPortGroupFiltering                                                      OBJECT IDENTIFIER ::= { gs2310pMVR 2 }

gs2310pMVRPortGroupFilteringCreate OBJECT-TYPE
   SYNTAX       Integer32
   MAX-ACCESS   read-write
   STATUS       current
   DESCRIPTION
       "default: 0
       0 : None  (read only) 1 : Create MLD Snooping Port Group Filtering "
   ::= { gs2310pMVRPortGroupFiltering 1 }

gs2310pMVRPortGroupFilteringTable OBJECT-TYPE
   SYNTAX      SEQUENCE OF Gs2310pMVRPortGroupFilteringEntry
   MAX-ACCESS  not-accessible
   STATUS      current
   DESCRIPTION
       " Configure MVR port group filtering. "
   ::= { gs2310pMVRPortGroupFiltering 2 }

gs2310pMVRPortGroupFilteringEntry OBJECT-TYPE
   SYNTAX      Gs2310pMVRPortGroupFilteringEntry
   MAX-ACCESS  not-accessible
   STATUS      current
   DESCRIPTION
       ""
   INDEX    { gs2310pMVRPortGroupFilteringIndex  }
   ::= { gs2310pMVRPortGroupFilteringTable 1 }

Gs2310pMVRPortGroupFilteringEntry ::= SEQUENCE {
   gs2310pMVRPortGroupFilteringIndex         Integer32,
   gs2310pMVRPortGroupFilteringPort          Integer32,
   gs2310pMVRPortGroupFilteringStartGroups   DisplayString,
   gs2310pMVRPortGroupFilteringEndGroups     DisplayString,
   gs2310pMVRPortGroupFilteringRowStatus     INTEGER
}

gs2310pMVRPortGroupFilteringIndex OBJECT-TYPE
   SYNTAX      Integer32(1..65535)
   MAX-ACCESS  not-accessible
   STATUS      current
   DESCRIPTION
       "MVR Port Group Filtering Configuration Index. "
   ::= { gs2310pMVRPortGroupFilteringEntry 1 }

gs2310pMVRPortGroupFilteringPort OBJECT-TYPE
   SYNTAX      Integer32(1..65535)
   MAX-ACCESS  read-write
   STATUS      current
   DESCRIPTION
       "The logical port for the settings. "
   ::= { gs2310pMVRPortGroupFilteringEntry 2 }

gs2310pMVRPortGroupFilteringStartGroups OBJECT-TYPE
   SYNTAX      DisplayString
   MAX-ACCESS  read-write
   STATUS      current
   DESCRIPTION
       "The IP Multicast Group that will be allowed. "
   ::= { gs2310pMVRPortGroupFilteringEntry 3 }

gs2310pMVRPortGroupFilteringEndGroups OBJECT-TYPE
   SYNTAX      DisplayString
   MAX-ACCESS  read-write
   STATUS      current
   DESCRIPTION
       "The IP Multicast Group that will be allowed. "
   ::= { gs2310pMVRPortGroupFilteringEntry 4 }

gs2310pMVRPortGroupFilteringRowStatus OBJECT-TYPE
   SYNTAX      INTEGER { active(1), notInservice(2), destroy(4)}
   MAX-ACCESS  read-write
   STATUS      current
   DESCRIPTION
       "1: active
        2: notInservice
        4: destroy"
   ::= { gs2310pMVRPortGroupFilteringEntry 5 }

gs2310pMVRGroupsTable OBJECT-TYPE
   SYNTAX      SEQUENCE OF Gs2310pMVRGroupsEntry
   MAX-ACCESS  not-accessible
   STATUS      current
   DESCRIPTION
       "MVR Groups Information . "
   ::= { gs2310pMVR 3 }

gs2310pMVRGroupsEntry OBJECT-TYPE
   SYNTAX      Gs2310pMVRGroupsEntry
   MAX-ACCESS  not-accessible
   STATUS      current
   DESCRIPTION
       ""
   INDEX    { gs2310pMVRGroupsIndex  }
   ::= { gs2310pMVRGroupsTable 1 }

Gs2310pMVRGroupsEntry ::= SEQUENCE {
   gs2310pMVRGroupsIndex          Integer32,
   gs2310pMVRGroupsVLANID         Integer32,
   gs2310pMVRGroups               InetAddress,
   gs2310pMVRGroupsMemberships    DisplayString
}

gs2310pMVRGroupsIndex OBJECT-TYPE
   SYNTAX      Integer32(1..65535)
   MAX-ACCESS  not-accessible
   STATUS      current
   DESCRIPTION
       "MVR Groups Index"
   ::= { gs2310pMVRGroupsEntry 1 }

gs2310pMVRGroupsVLANID OBJECT-TYPE
   SYNTAX      Integer32(1..4095)
   MAX-ACCESS  read-only
   STATUS      current
   DESCRIPTION
       "VLAN ID of the group. "
   ::= { gs2310pMVRGroupsEntry 2 }

gs2310pMVRGroups OBJECT-TYPE
   SYNTAX      DisplayString
   MAX-ACCESS  read-only
   STATUS      current
   DESCRIPTION
       "Group address of the group displayed."
   ::= { gs2310pMVRGroupsEntry 3 }

gs2310pMVRGroupsMemberships OBJECT-TYPE
   SYNTAX      DisplayString
   MAX-ACCESS  read-only
   STATUS      current
   DESCRIPTION
       "Ports under this group."
   ::= { gs2310pMVRGroupsEntry 4 }


gs2310pMVRStatus                                                      OBJECT IDENTIFIER ::= { gs2310pMVR 4 }

gs2310pMVRstatisticClear OBJECT-TYPE
   SYNTAX      INTEGER { none(0), clear(1)}
   MAX-ACCESS  read-write
   STATUS      current
   DESCRIPTION
       "Clears all Statistics counters."
   ::= { gs2310pMVRStatus 1 }

gs2310pMVRstatisticVLANID OBJECT-TYPE
   SYNTAX      Integer32(1..4095)
   MAX-ACCESS  read-only
   STATUS      current
   DESCRIPTION
       "The VLAN ID of the entry. "
   ::= { gs2310pMVRStatus 2 }

gs2310pMVRstatisticV1ReportsReceived OBJECT-TYPE
   SYNTAX      Counter32
   MAX-ACCESS  read-only
   STATUS      current
   DESCRIPTION
       "The number of Received V1 Reports. "
   ::= { gs2310pMVRStatus 3 }

gs2310pMVRstatisticV2ReportsReceived OBJECT-TYPE
   SYNTAX      Counter32
   MAX-ACCESS  read-only
   STATUS      current
   DESCRIPTION
       "The number of Received V2 Reports. "
   ::= { gs2310pMVRStatus 4 }

gs2310pMVRstatisticV3ReportsReceived OBJECT-TYPE
   SYNTAX      Counter32
   MAX-ACCESS  read-only
   STATUS      current
   DESCRIPTION
       "The number of Received V3 Reports. "
   ::= { gs2310pMVRStatus 5 }

gs2310pMVRstatisticV2LeavesReceived OBJECT-TYPE
   SYNTAX      Counter32
   MAX-ACCESS  read-only
   STATUS      current
   DESCRIPTION
       "The number of Received V2 Leaves. "
   ::= { gs2310pMVRStatus 6 }


gs2310pLACP                                                     OBJECT IDENTIFIER ::= { gs2310pConfiguration 19 }

gs2310pLACPConf                                                 OBJECT IDENTIFIER ::= { gs2310pLACP 1 }

gs2310pLACPPortConfigurationTable OBJECT-TYPE
   SYNTAX      SEQUENCE OF Gs2310pLACPPortConfigurationEntry
   MAX-ACCESS  not-accessible
   STATUS      current
   DESCRIPTION
       " "
   ::= { gs2310pLACPConf 1 }

gs2310pLACPPortConfigurationEntry OBJECT-TYPE
   SYNTAX      Gs2310pLACPPortConfigurationEntry
   MAX-ACCESS  not-accessible
   STATUS      current
   DESCRIPTION
       ""
   INDEX    { gs2310pLACPPortConfigurationPort  }
   ::= { gs2310pLACPPortConfigurationTable 1 }

Gs2310pLACPPortConfigurationEntry ::= SEQUENCE {
    gs2310pLACPPortConfigurationPort         Integer32,
    gs2310pLACPPortConfigurationMode         INTEGER,
    gs2310pLACPPortConfigurationKey          Integer32,
    gs2310pLACPPortConfigurationRole         INTEGER
}

gs2310pLACPPortConfigurationPort OBJECT-TYPE
   SYNTAX      Integer32(1..4095)
   MAX-ACCESS  not-accessible
   STATUS      current
   DESCRIPTION
       " "
   ::= { gs2310pLACPPortConfigurationEntry 1 }

gs2310pLACPPortConfigurationMode OBJECT-TYPE
   SYNTAX      INTEGER { disable(0), enable(1) }
   MAX-ACCESS  read-write
   STATUS      current
   DESCRIPTION
       "Enable/Disable LACP Mode."
   ::= { gs2310pLACPPortConfigurationEntry 2 }

gs2310pLACPPortConfigurationKey OBJECT-TYPE
   SYNTAX      Integer32(0..65535)
   MAX-ACCESS  read-write
   STATUS      current
   DESCRIPTION
       "LACP key : 1-65535. 0 : Auto"
   ::= { gs2310pLACPPortConfigurationEntry 3 }

gs2310pLACPPortConfigurationRole OBJECT-TYPE
   SYNTAX      INTEGER { passive(0), active(1) }
   MAX-ACCESS  read-write
   STATUS      current
   DESCRIPTION
       "0 : passive, Listen for LACP packets.
        1 : active, Initiate LACP negotiation, and transmit LACP packets each second"
   ::= { gs2310pLACPPortConfigurationEntry 4 }

gs2310pLACPSystemStatusTable OBJECT-TYPE
   SYNTAX      SEQUENCE OF Gs2310pLACPSystemStatusEntry
   MAX-ACCESS  not-accessible
   STATUS      current
   DESCRIPTION
       " "
   ::= { gs2310pLACP 2 }

gs2310pLACPSystemStatusEntry OBJECT-TYPE
   SYNTAX      Gs2310pLACPSystemStatusEntry
   MAX-ACCESS  not-accessible
   STATUS      current
   DESCRIPTION
       ""
   INDEX    { gs2310pLACPSystemStatusIndex  }
   ::= { gs2310pLACPSystemStatusTable 1 }

Gs2310pLACPSystemStatusEntry ::= SEQUENCE {
   gs2310pLACPSystemStatusIndex             Integer32,
   gs2310pLACPSystemStatusAggrID            DisplayString,
   gs2310pLACPSystemStatusPartnerSystemID   MacAddress,
   gs2310pLACPSystemStatusPartnerKey        DisplayString,
   gs2310pLACPSystemStatusLastchanged       DisplayString,
   gs2310pLACPSystemStatusLocalPorts        DisplayString
}

gs2310pLACPSystemStatusIndex OBJECT-TYPE
   SYNTAX      Integer32(1..12)
   MAX-ACCESS  not-accessible
   STATUS      current
   DESCRIPTION
       " "
   ::= { gs2310pLACPSystemStatusEntry 1 }

gs2310pLACPSystemStatusAggrID OBJECT-TYPE
   SYNTAX      DisplayString
   MAX-ACCESS  read-only
   STATUS      current
   DESCRIPTION
       "The Aggregation ID associated with this aggregation instance."
   ::= { gs2310pLACPSystemStatusEntry 2 }

gs2310pLACPSystemStatusPartnerSystemID OBJECT-TYPE
   SYNTAX      MacAddress
   MAX-ACCESS  read-only
   STATUS      current
   DESCRIPTION
       "The system ID (MAC address) of the aggregation partner."
   ::= { gs2310pLACPSystemStatusEntry 3 }

gs2310pLACPSystemStatusPartnerKey OBJECT-TYPE
   SYNTAX      DisplayString
   MAX-ACCESS  read-only
   STATUS      current
   DESCRIPTION
       " The Key that the partner has assigned to this aggregation ID. "
   ::= { gs2310pLACPSystemStatusEntry 4 }

gs2310pLACPSystemStatusLastchanged OBJECT-TYPE
   SYNTAX      DisplayString
   MAX-ACCESS  read-only
   STATUS      current
   DESCRIPTION
       " The time since this aggregation changed. "
   ::= { gs2310pLACPSystemStatusEntry 5 }

gs2310pLACPSystemStatusLocalPorts OBJECT-TYPE
   SYNTAX      DisplayString
   MAX-ACCESS  read-only
   STATUS      current
   DESCRIPTION
       " Shows which ports are a part of this aggregation for this switch. "
   ::= { gs2310pLACPSystemStatusEntry 6 }

gs2310pLACPStatusTable OBJECT-TYPE
   SYNTAX      SEQUENCE OF Gs2310pLACPStatusEntry
   MAX-ACCESS  not-accessible
   STATUS      current
   DESCRIPTION
       " "
   ::= { gs2310pLACP 3 }

gs2310pLACPStatusEntry OBJECT-TYPE
   SYNTAX      Gs2310pLACPStatusEntry
   MAX-ACCESS  not-accessible
   STATUS      current
   DESCRIPTION
       ""
   INDEX    { gs2310pLACPStatusPort  }
   ::= { gs2310pLACPStatusTable 1 }

Gs2310pLACPStatusEntry ::= SEQUENCE {
   gs2310pLACPStatusPort                Integer32,
   gs2310pLACPStatusLACP                DisplayString,
   gs2310pLACPStatusKey                 DisplayString,
   gs2310pLACPStatusAggrID              DisplayString,
   gs2310pLACPStatusPartnerSystemID     DisplayString,
   gs2310pLACPStatusPartnerPort         DisplayString
}

gs2310pLACPStatusPort OBJECT-TYPE
   SYNTAX      Integer32(1..4095)
   MAX-ACCESS  not-accessible
   STATUS      current
   DESCRIPTION
       " "
   ::= { gs2310pLACPStatusEntry 1 }

gs2310pLACPStatusLACP OBJECT-TYPE
   SYNTAX      DisplayString
   MAX-ACCESS  read-only
   STATUS      current
   DESCRIPTION
       "Enabled means that LACP is enabled and the port link is up.
        Disabled means that LACP is not enabled or that the port link is down.
        Backup means that the port could not join the aggregation group but will join if other port leaves.
        Meanwhile it's LACP status is disabled."
   ::= { gs2310pLACPStatusEntry 2 }

gs2310pLACPStatusKey OBJECT-TYPE
   SYNTAX      DisplayString
   MAX-ACCESS  read-only
   STATUS      current
   DESCRIPTION
       "The key assigned to this port. Only ports with the same key can aggregate together."
   ::= { gs2310pLACPStatusEntry 3 }

gs2310pLACPStatusAggrID	 OBJECT-TYPE
   SYNTAX      DisplayString
   MAX-ACCESS  read-only
   STATUS      current
   DESCRIPTION
       " The Aggregation ID assigned to this aggregation group. "
   ::= { gs2310pLACPStatusEntry 4 }

gs2310pLACPStatusPartnerSystemID OBJECT-TYPE
   SYNTAX      DisplayString
   MAX-ACCESS  read-only
   STATUS      current
   DESCRIPTION
       " The partner's System ID. "
   ::= { gs2310pLACPStatusEntry 5 }

gs2310pLACPStatusPartnerPort OBJECT-TYPE
   SYNTAX      DisplayString
   MAX-ACCESS  read-only
   STATUS      current
   DESCRIPTION
       " The partner's port number connected to this port. "
   ::= { gs2310pLACPStatusEntry 6 }


gs2310pLACPStatisticsTable OBJECT-TYPE
   SYNTAX      SEQUENCE OF Gs2310pLACPStatisticsEntry
   MAX-ACCESS  not-accessible
   STATUS      current
   DESCRIPTION
       " "
   ::= { gs2310pLACP 4 }

gs2310pLACPStatisticsEntry OBJECT-TYPE
   SYNTAX      Gs2310pLACPStatisticsEntry
   MAX-ACCESS  not-accessible
   STATUS      current
   DESCRIPTION
       ""
   INDEX    { gs2310pLACPStatisticsPort  }
   ::= { gs2310pLACPStatisticsTable 1 }

Gs2310pLACPStatisticsEntry ::= SEQUENCE {
   gs2310pLACPStatisticsPort        Integer32,
   gs2310pLACPReceived              Counter32,
   gs2310pLACPTransmitted           Counter32,
   gs2310pLACPDiscardedUnknown      Counter32,
   gs2310pLACPDiscardedIllegal      Counter32
}

gs2310pLACPStatisticsPort OBJECT-TYPE
   SYNTAX      Integer32(1..4095)
   MAX-ACCESS  not-accessible
   STATUS      current
   DESCRIPTION
       " "
   ::= { gs2310pLACPStatisticsEntry 1 }

gs2310pLACPReceived OBJECT-TYPE
   SYNTAX      Counter32
   MAX-ACCESS  read-only
   STATUS      current
   DESCRIPTION
       "Shows how many LACP frames have been received at each port. "
   ::= { gs2310pLACPStatisticsEntry 2 }

gs2310pLACPTransmitted OBJECT-TYPE
   SYNTAX      Counter32
   MAX-ACCESS  read-only
   STATUS      current
   DESCRIPTION
       " Shows how many LACP frames have been sent from each port. "
   ::= { gs2310pLACPStatisticsEntry 3 }

gs2310pLACPDiscardedUnknown OBJECT-TYPE
   SYNTAX      Counter32
   MAX-ACCESS  read-only
   STATUS      current
   DESCRIPTION
       " Shows how many unknown LACP frames have been discarded at each port. "
   ::= { gs2310pLACPStatisticsEntry 4 }

gs2310pLACPDiscardedIllegal OBJECT-TYPE
   SYNTAX      Counter32
   MAX-ACCESS  read-only
   STATUS      current
   DESCRIPTION
       " Shows how many illegal LACP frames have been discarded at each port. "
   ::= { gs2310pLACPStatisticsEntry 5 }

gs2310pLACPStatisticsClear OBJECT-TYPE
   SYNTAX      INTEGER { none(0), clear(1) }
   MAX-ACCESS  read-write
   STATUS      current
   DESCRIPTION
       "default: 0
       0: none
       1: clear"
   ::= { gs2310pLACP 5 }

gs2310pSTP                                                     OBJECT IDENTIFIER ::= { gs2310pConfiguration 20 }

gs2310pSTPBridgeBasicConf                                                 OBJECT IDENTIFIER ::= { gs2310pSTP 1 }

gs2310pSTPBridgeProtocolVersion OBJECT-TYPE
   SYNTAX      INTEGER { stp(0), rstp(2), mstp(3) }
   MAX-ACCESS  read-write
   STATUS      current
   DESCRIPTION
       "default: 3,
       0: stp
       2: rstp
       3: mstp"
   ::= { gs2310pSTPBridgeBasicConf 1 }

gs2310pSTPBridgePriority OBJECT-TYPE
   SYNTAX      Integer32(0..61440)
   MAX-ACCESS  read-write
   STATUS      current
   DESCRIPTION
       " default: 32768,
       STP bridge priority (0/4096/8192/12288/16384/20480/24576/28672/32768/36864/40960/45056/49152/53248/57344/61440)"
   ::= { gs2310pSTPBridgeBasicConf 2 }

gs2310pSTPBridgeForwardDelay OBJECT-TYPE
   SYNTAX      Integer32(4..30)
   MAX-ACCESS  read-write
   STATUS      current
   DESCRIPTION
       " Forward Delay default: 15, range: 4 - 30.
         MaxAge must be <= (FwdDelay-1)*2."
   ::= { gs2310pSTPBridgeBasicConf 3 }

gs2310pSTPBridgeMaxAge OBJECT-TYPE
   SYNTAX      Integer32(6..40)
   MAX-ACCESS  read-write
   STATUS      current
   DESCRIPTION
       " Max Age default: 20, range: 6 - 40.
         MaxAge must be <= (FwdDelay-1)*2"
   ::= { gs2310pSTPBridgeBasicConf 4 }

gs2310pSTPBridgeMaximumHopCount OBJECT-TYPE
   SYNTAX      Integer32(6..40)
   MAX-ACCESS  read-write
   STATUS      current
   DESCRIPTION
       " Maximum Hop Count default: 20, range: 6 - 40."
   ::= { gs2310pSTPBridgeBasicConf 5 }

gs2310pSTPBridgeTransmitHoldCount OBJECT-TYPE
   SYNTAX      Integer32(1..10)
   MAX-ACCESS  read-write
   STATUS      current
   DESCRIPTION
       " Transmit Hold Count default: 6, range: 1 - 10."
   ::= { gs2310pSTPBridgeBasicConf 6 }

gs2310pSTPBridgeAdvancedConf                                                 OBJECT IDENTIFIER ::= { gs2310pSTP 2 }

gs2310pSTPBridgeEdgePortBPDUFiltering OBJECT-TYPE
   SYNTAX      INTEGER { disable(0), enable(1) }
   MAX-ACCESS  read-write
   STATUS      current
   DESCRIPTION
       " default: 0,
        0: disable
        1: enable"
   ::= { gs2310pSTPBridgeAdvancedConf 1 }

gs2310pSTPBridgeEdgePortBPDUGuard OBJECT-TYPE
   SYNTAX      INTEGER { disable(0), enable(1) }
   MAX-ACCESS  read-write
   STATUS      current
   DESCRIPTION
       " default: 0,
        0: disable
        1: enable"
   ::= { gs2310pSTPBridgeAdvancedConf 2 }

gs2310pSTPBridgePortErrorRecoveryTimeout OBJECT-TYPE
   SYNTAX      Integer32(0..86400)
   MAX-ACCESS  read-write
   STATUS      current
   DESCRIPTION
       " Port Error Recovery Timeout disable: 0, range: 30 - 86400."
   ::= { gs2310pSTPBridgeAdvancedConf 3 }

gs2310pSTPMSTIConf                                                 OBJECT IDENTIFIER ::= { gs2310pSTP 3 }

gs2310pSTPMSTIConfigurationName OBJECT-TYPE
   SYNTAX      DisplayString (SIZE (1..32))
   MAX-ACCESS  read-write
   STATUS      current
   DESCRIPTION
       "A text string up to 32 characters long."
   ::= { gs2310pSTPMSTIConf 1 }

gs2310pSTPMSTIConfigurationRevision   OBJECT-TYPE
   SYNTAX      Integer32(0..65535)
   MAX-ACCESS  read-write
   STATUS      current
   DESCRIPTION
       " Configuration Revision default: 0, range: 0 - 65535."
   ::= { gs2310pSTPMSTIConf 2 }

gs2310pSTPMSTIMappingConf                                                 OBJECT IDENTIFIER ::= { gs2310pSTP 4 }

gs2310pSTPMSTI1VLANsMapped OBJECT-TYPE
   SYNTAX      DisplayString (SIZE (1..4096))
   MAX-ACCESS  read-write
   STATUS      current
   DESCRIPTION
       "The list of VLANs mapped to the MSTI1.
       The VLANs must be separated with comma or space.
       An unused MSTI should just be left empty. "
   ::= { gs2310pSTPMSTIMappingConf 1 }

gs2310pSTPMSTI2VLANsMapped OBJECT-TYPE
   SYNTAX      DisplayString (SIZE (1..4096))
   MAX-ACCESS  read-write
   STATUS      current
   DESCRIPTION
       "The list of VLANs mapped to the MSTI2.
       The VLANs must be separated with comma or space.
       An unused MSTI should just be left empty. "
   ::= { gs2310pSTPMSTIMappingConf 2 }

gs2310pSTPMSTI3VLANsMapped OBJECT-TYPE
   SYNTAX      DisplayString (SIZE (1..4096))
   MAX-ACCESS  read-write
   STATUS      current
   DESCRIPTION
       "The list of VLANs mapped to the MSTI3.
       The VLANs must be separated with comma or space.
       An unused MSTI should just be left empty. "
   ::= { gs2310pSTPMSTIMappingConf 3 }

gs2310pSTPMSTI4VLANsMapped OBJECT-TYPE
   SYNTAX      DisplayString (SIZE (1..4096))
   MAX-ACCESS  read-write
   STATUS      current
   DESCRIPTION
       "The list of VLANs mapped to the MSTI4.
       The VLANs must be separated with comma or space.
       An unused MSTI should just be left empty. "
   ::= { gs2310pSTPMSTIMappingConf 4 }

gs2310pSTPMSTI5VLANsMapped OBJECT-TYPE
   SYNTAX      DisplayString (SIZE (1..4096))
   MAX-ACCESS  read-write
   STATUS      current
   DESCRIPTION
       "The list of VLANs mapped to the MSTI5.
       The VLANs must be separated with comma or space.
       An unused MSTI should just be left empty. "
   ::= { gs2310pSTPMSTIMappingConf 5 }

gs2310pSTPMSTI6VLANsMapped OBJECT-TYPE
   SYNTAX      DisplayString (SIZE (1..4096))
   MAX-ACCESS  read-write
   STATUS      current
   DESCRIPTION
       "The list of VLANs mapped to the MSTI6.
       The VLANs must be separated with comma or space.
       An unused MSTI should just be left empty. "
   ::= { gs2310pSTPMSTIMappingConf 6 }

gs2310pSTPMSTI7VLANsMapped OBJECT-TYPE
   SYNTAX      DisplayString (SIZE (1..4096))
   MAX-ACCESS  read-write
   STATUS      current
   DESCRIPTION
       "The list of VLANs mapped to the MSTI7.
       The VLANs must be separated with comma or space.
       An unused MSTI should just be left empty. "
   ::= { gs2310pSTPMSTIMappingConf 7 }

gs2310pSTPMSTIPriority                                                 OBJECT IDENTIFIER ::= { gs2310pSTP 5 }

gs2310pSTPCISTPriority OBJECT-TYPE
   SYNTAX      Integer32(0..61440)
   MAX-ACCESS  read-write
   STATUS      current
   DESCRIPTION
       " default: 32768,
       STP CIST priority (0/4096/8192/12288/16384/20480/24576/28672/32768/36864/40960/45056/49152/53248/57344/61440)"
   ::= { gs2310pSTPMSTIPriority 1 }

gs2310pSTPMSTI1Priority OBJECT-TYPE
   SYNTAX      Integer32(0..61440)
   MAX-ACCESS  read-write
   STATUS      current
   DESCRIPTION
       " default: 32768,
       STP CIST priority (0/4096/8192/12288/16384/20480/24576/28672/32768/36864/40960/45056/49152/53248/57344/61440)"
   ::= { gs2310pSTPMSTIPriority 2 }

gs2310pSTPMSTI2Priority OBJECT-TYPE
   SYNTAX      Integer32(0..61440)
   MAX-ACCESS  read-write
   STATUS      current
   DESCRIPTION
       " default: 32768,
       STP CIST priority (0/4096/8192/12288/16384/20480/24576/28672/32768/36864/40960/45056/49152/53248/57344/61440)"
   ::= { gs2310pSTPMSTIPriority 3 }

gs2310pSTPMSTI3Priority OBJECT-TYPE
   SYNTAX      Integer32(0..61440)
   MAX-ACCESS  read-write
   STATUS      current
   DESCRIPTION
       " default: 32768,
       STP CIST priority (0/4096/8192/12288/16384/20480/24576/28672/32768/36864/40960/45056/49152/53248/57344/61440)"
   ::= { gs2310pSTPMSTIPriority 4 }

gs2310pSTPMSTI4Priority OBJECT-TYPE
   SYNTAX      Integer32(0..61440)
   MAX-ACCESS  read-write
   STATUS      current
   DESCRIPTION
       " default: 32768,
       STP CIST priority (0/4096/8192/12288/16384/20480/24576/28672/32768/36864/40960/45056/49152/53248/57344/61440)"
   ::= { gs2310pSTPMSTIPriority 5 }

gs2310pSTPMSTI5Priority OBJECT-TYPE
   SYNTAX      Integer32(0..61440)
   MAX-ACCESS  read-write
   STATUS      current
   DESCRIPTION
       " default: 32768,
       STP CIST priority (0/4096/8192/12288/16384/20480/24576/28672/32768/36864/40960/45056/49152/53248/57344/61440)"
   ::= { gs2310pSTPMSTIPriority 6 }

gs2310pSTPMSTI6Priority OBJECT-TYPE
   SYNTAX      Integer32(0..61440)
   MAX-ACCESS  read-write
   STATUS      current
   DESCRIPTION
       " default: 32768,
       STP CIST priority (0/4096/8192/12288/16384/20480/24576/28672/32768/36864/40960/45056/49152/53248/57344/61440)"
   ::= { gs2310pSTPMSTIPriority 7 }

gs2310pSTPMSTI7Priority OBJECT-TYPE
   SYNTAX      Integer32(0..61440)
   MAX-ACCESS  read-write
   STATUS      current
   DESCRIPTION
       " default: 32768,
       STP CIST priority (0/4096/8192/12288/16384/20480/24576/28672/32768/36864/40960/45056/49152/53248/57344/61440)"
   ::= { gs2310pSTPMSTIPriority 8 }

gs2310pSTPCISTPort                                                          OBJECT IDENTIFIER ::= { gs2310pSTP 6 }

gs2310pSTPCISTAggregatedPort                                                OBJECT IDENTIFIER ::= { gs2310pSTPCISTPort 1 }

gs2310pSTPCISTAggregatedPortSTPEnabled OBJECT-TYPE
   SYNTAX      INTEGER { disable(0), enable(1) }
   MAX-ACCESS  read-write
   STATUS      current
   DESCRIPTION
       " default: 0,
        0: disable
        1: enable"
   ::= { gs2310pSTPCISTAggregatedPort 1 }

gs2310pSTPCISTAggregatedPortPathCost OBJECT-TYPE
   SYNTAX      Integer32(0..200000000)
   MAX-ACCESS  read-write
   STATUS      current
   DESCRIPTION
       " Auto: 0,
        Specific Path Cost range: 1 - 200000000."
   ::= { gs2310pSTPCISTAggregatedPort 2 }

gs2310pSTPCISTAggregatedPortPriority OBJECT-TYPE
   SYNTAX      Integer32(0..240)
   MAX-ACCESS  read-write
   STATUS      current
   DESCRIPTION
       " default: 128,
       CIST Aggregated Port Priority (0/16/32/48/64/80/96/112/128/144/160/176/192/208/224/240)"
   ::= { gs2310pSTPCISTAggregatedPort 3 }

gs2310pSTPCISTAggregatedPortAdminEdge OBJECT-TYPE
   SYNTAX      INTEGER { non-edge(0), edge(1) }
   MAX-ACCESS  read-write
   STATUS      current
   DESCRIPTION
       " default: 0,
        0: non-edge
        1: edge"
   ::= { gs2310pSTPCISTAggregatedPort 4 }

gs2310pSTPCISTAggregatedPortAutoEdge OBJECT-TYPE
   SYNTAX      INTEGER { disable(0), enable(1) }
   MAX-ACCESS  read-write
   STATUS      current
   DESCRIPTION
       " default: 1,
        0: disable
        1: enable"
   ::= { gs2310pSTPCISTAggregatedPort 5 }

gs2310pSTPCISTAggregatedPortRestrictedRole OBJECT-TYPE
   SYNTAX      INTEGER { disable(0), enable(1) }
   MAX-ACCESS  read-write
   STATUS      current
   DESCRIPTION
       " default: 0,
        0: disable
        1: enable"
   ::= { gs2310pSTPCISTAggregatedPort 6 }

gs2310pSTPCISTAggregatedPortRestrictedTCN OBJECT-TYPE
   SYNTAX      INTEGER { disable(0), enable(1) }
   MAX-ACCESS  read-write
   STATUS      current
   DESCRIPTION
       " default: 0,
        0: disable
        1: enable"
   ::= { gs2310pSTPCISTAggregatedPort 7 }

gs2310pSTPCISTAggregatedPortBPDUGuard OBJECT-TYPE
   SYNTAX      INTEGER { disable(0), enable(1) }
   MAX-ACCESS  read-write
   STATUS      current
   DESCRIPTION
       " default: 0,
        0: disable
        1: enable"
   ::= { gs2310pSTPCISTAggregatedPort 8 }

gs2310pSTPCISTAggregatedPortPointtoPoint OBJECT-TYPE
   SYNTAX      INTEGER { forcetrue(0), forcefalse(1), auto(2) }
   MAX-ACCESS  read-write
   STATUS      current
   DESCRIPTION
       " default: 0,
        0: Forced True
        1: Forced False
        2: Auto"
   ::= { gs2310pSTPCISTAggregatedPort 9 }

gs2310pSTPCISTNormalPortTable OBJECT-TYPE
   SYNTAX      SEQUENCE OF Gs2310pSTPCISTNormalPortEntry
   MAX-ACCESS  not-accessible
   STATUS      current
   DESCRIPTION
       " Show CIST Normal Port Configurations. "
   ::= { gs2310pSTPCISTPort 2 }

gs2310pSTPCISTNormalPortEntry OBJECT-TYPE
   SYNTAX      Gs2310pSTPCISTNormalPortEntry
   MAX-ACCESS  not-accessible
   STATUS      current
   DESCRIPTION
       ""
   INDEX    { gs2310pSTPCISTNormalPortConfPort  }
   ::= { gs2310pSTPCISTNormalPortTable 1 }

Gs2310pSTPCISTNormalPortEntry ::= SEQUENCE {
   gs2310pSTPCISTNormalPortConfPort         Integer32,
   gs2310pSTPCISTNormalPortSTPEnabled       INTEGER,
   gs2310pSTPCISTNormalPortPathCost         Integer32,
   gs2310pSTPCISTNormalPortPriority         Integer32,
   gs2310pSTPCISTNormalPortAdminEdge        INTEGER,
   gs2310pSTPCISTNormalPortAutoEdge         INTEGER,
   gs2310pSTPCISTNormalPortRestrictedRole   INTEGER,
   gs2310pSTPCISTNormalPortRestrictedTCN    INTEGER,
   gs2310pSTPCISTNormalPortBPDUGuard        INTEGER,
   gs2310pSTPCISTNormalPortPointtoPoint     INTEGER
}

gs2310pSTPCISTNormalPortConfPort OBJECT-TYPE
   SYNTAX      Integer32(1..4095)
   MAX-ACCESS  not-accessible
   STATUS      current
   DESCRIPTION
       " port, range : 1 - port number. "
   ::= { gs2310pSTPCISTNormalPortEntry 1 }

gs2310pSTPCISTNormalPortSTPEnabled OBJECT-TYPE
   SYNTAX      INTEGER { disable(0), enable(1) }
   MAX-ACCESS  read-write
   STATUS      current
   DESCRIPTION
       " default: 0,
        0: disable
        1: enable"
   ::= { gs2310pSTPCISTNormalPortEntry 2 }

gs2310pSTPCISTNormalPortPathCost OBJECT-TYPE
   SYNTAX      Integer32(0..200000000)
   MAX-ACCESS  read-write
   STATUS      current
   DESCRIPTION
       " Auto: 0,
        Specific Path Cost range: 1 - 200000000."
   ::= { gs2310pSTPCISTNormalPortEntry 3 }

gs2310pSTPCISTNormalPortPriority OBJECT-TYPE
   SYNTAX      Integer32(0..240)
   MAX-ACCESS  read-write
   STATUS      current
   DESCRIPTION
       " default: 128,
       CIST Aggregated Port Priority (0/16/32/48/64/80/96/112/128/144/160/176/192/208/224/240)"
   ::= { gs2310pSTPCISTNormalPortEntry 4 }

gs2310pSTPCISTNormalPortAdminEdge OBJECT-TYPE
   SYNTAX      INTEGER { non-edge(0), edge(1) }
   MAX-ACCESS  read-write
   STATUS      current
   DESCRIPTION
       " default: 0,
        0: non-edge
        1: edge"
   ::= { gs2310pSTPCISTNormalPortEntry 5 }

gs2310pSTPCISTNormalPortAutoEdge OBJECT-TYPE
   SYNTAX      INTEGER { disable(0), enable(1) }
   MAX-ACCESS  read-write
   STATUS      current
   DESCRIPTION
       " default: 1,
        0: disable
        1: enable"
   ::= { gs2310pSTPCISTNormalPortEntry 6 }

gs2310pSTPCISTNormalPortRestrictedRole OBJECT-TYPE
   SYNTAX      INTEGER { disable(0), enable(1) }
   MAX-ACCESS  read-write
   STATUS      current
   DESCRIPTION
       " default: 0,
        0: disable
        1: enable"
   ::= { gs2310pSTPCISTNormalPortEntry 7 }

gs2310pSTPCISTNormalPortRestrictedTCN OBJECT-TYPE
   SYNTAX      INTEGER { disable(0), enable(1) }
   MAX-ACCESS  read-write
   STATUS      current
   DESCRIPTION
       " default: 0,
        0: disable
        1: enable"
   ::= { gs2310pSTPCISTNormalPortEntry 8 }

gs2310pSTPCISTNormalPortBPDUGuard OBJECT-TYPE
   SYNTAX      INTEGER { disable(0), enable(1) }
   MAX-ACCESS  read-write
   STATUS      current
   DESCRIPTION
       " default: 0,
        0: disable
        1: enable"
   ::= { gs2310pSTPCISTNormalPortEntry 9 }

gs2310pSTPCISTNormalPortPointtoPoint OBJECT-TYPE
   SYNTAX      INTEGER { forcetrue(0), forcefalse(1), auto(2) }
   MAX-ACCESS  read-write
   STATUS      current
   DESCRIPTION
       " default: 2,
        0: Forced True
        1: Forced False
        2: Auto"
   ::= { gs2310pSTPCISTNormalPortEntry 10 }


gs2310pSTPMSTIPort                                                          OBJECT IDENTIFIER ::= { gs2310pSTP 7 }

gs2310pSTPMSTI1Port                                                         OBJECT IDENTIFIER ::= { gs2310pSTPMSTIPort 1 }

gs2310pSTPMSTI1AggregatedPort                                                OBJECT IDENTIFIER ::= { gs2310pSTPMSTI1Port 1 }

gs2310pSTPMSTI1AggregatedPortPathCost OBJECT-TYPE
   SYNTAX      Integer32(0..200000000)
   MAX-ACCESS  read-write
   STATUS      current
   DESCRIPTION
       " Auto: 0,
        Specific Path Cost range: 1 - 200000000."
   ::= { gs2310pSTPMSTI1AggregatedPort 1 }

gs2310pSTPMSTI1AggregatedPortPriority OBJECT-TYPE
   SYNTAX      Integer32(0..240)
   MAX-ACCESS  read-write
   STATUS      current
   DESCRIPTION
       " default: 128,
       Aggregated Port Priority (0/16/32/48/64/80/96/112/128/144/160/176/192/208/224/240)"
   ::= { gs2310pSTPMSTI1AggregatedPort 2 }

gs2310pSTPMSTI1NormalPortTable OBJECT-TYPE
   SYNTAX      SEQUENCE OF Gs2310pSTPMSTI1NormalPortEntry
   MAX-ACCESS  not-accessible
   STATUS      current
   DESCRIPTION
       " Show MSTI1 Normal Port Configurations. "
   ::= { gs2310pSTPMSTI1Port 2 }

gs2310pSTPMSTI1NormalPortEntry OBJECT-TYPE
   SYNTAX      Gs2310pSTPMSTI1NormalPortEntry
   MAX-ACCESS  not-accessible
   STATUS      current
   DESCRIPTION
       ""
   INDEX    { gs2310pSTPMSTI1NormalPortConfPort  }
   ::= { gs2310pSTPMSTI1NormalPortTable 1 }

Gs2310pSTPMSTI1NormalPortEntry ::= SEQUENCE {
   gs2310pSTPMSTI1NormalPortConfPort         Integer32,
   gs2310pSTPMSTI1NormalPortPathCost         Integer32,
   gs2310pSTPMSTI1NormalPortPriority         Integer32
}

gs2310pSTPMSTI1NormalPortConfPort OBJECT-TYPE
   SYNTAX      Integer32(1..4095)
   MAX-ACCESS  not-accessible
   STATUS      current
   DESCRIPTION
       " port, range : 1 - port number. "
   ::= { gs2310pSTPMSTI1NormalPortEntry 1 }

gs2310pSTPMSTI1NormalPortPathCost OBJECT-TYPE
   SYNTAX      Integer32(0..200000000)
   MAX-ACCESS  read-write
   STATUS      current
   DESCRIPTION
       " Auto: 0,
        Specific Path Cost range: 1 - 200000000."
   ::= { gs2310pSTPMSTI1NormalPortEntry 2 }

gs2310pSTPMSTI1NormalPortPriority OBJECT-TYPE
   SYNTAX      Integer32(0..240)
   MAX-ACCESS  read-write
   STATUS      current
   DESCRIPTION
       " default: 128,
       Aggregated Port Priority (0/16/32/48/64/80/96/112/128/144/160/176/192/208/224/240)"
   ::= { gs2310pSTPMSTI1NormalPortEntry 3 }

gs2310pSTPMSTI2Port                                                          OBJECT IDENTIFIER ::= { gs2310pSTPMSTIPort 2 }

gs2310pSTPMSTI2AggregatedPort                                                OBJECT IDENTIFIER ::= { gs2310pSTPMSTI2Port 1 }

gs2310pSTPMSTI2AggregatedPortPathCost OBJECT-TYPE
   SYNTAX      Integer32(0..200000000)
   MAX-ACCESS  read-write
   STATUS      current
   DESCRIPTION
       " Auto: 0,
        Specific Path Cost range: 1 - 200000000."
   ::= { gs2310pSTPMSTI2AggregatedPort 1 }

gs2310pSTPMSTI2AggregatedPortPriority OBJECT-TYPE
   SYNTAX      Integer32(0..240)
   MAX-ACCESS  read-write
   STATUS      current
   DESCRIPTION
       " default: 128,
       Aggregated Port Priority (0/16/32/48/64/80/96/112/128/144/160/176/192/208/224/240)"
   ::= { gs2310pSTPMSTI2AggregatedPort 2 }

gs2310pSTPMSTI2NormalPortTable OBJECT-TYPE
   SYNTAX      SEQUENCE OF Gs2310pSTPMSTI2NormalPortEntry
   MAX-ACCESS  not-accessible
   STATUS      current
   DESCRIPTION
       " Show MSTI2 Normal Port Configurations. "
   ::= { gs2310pSTPMSTI2Port 2 }

gs2310pSTPMSTI2NormalPortEntry OBJECT-TYPE
   SYNTAX      Gs2310pSTPMSTI2NormalPortEntry
   MAX-ACCESS  not-accessible
   STATUS      current
   DESCRIPTION
       ""
   INDEX    { gs2310pSTPMSTI2NormalPortConfPort  }
   ::= { gs2310pSTPMSTI2NormalPortTable 1 }

Gs2310pSTPMSTI2NormalPortEntry ::= SEQUENCE {
   gs2310pSTPMSTI2NormalPortConfPort         Integer32,
   gs2310pSTPMSTI2NormalPortPathCost         Integer32,
   gs2310pSTPMSTI2NormalPortPriority         Integer32
}

gs2310pSTPMSTI2NormalPortConfPort OBJECT-TYPE
   SYNTAX      Integer32(1..4095)
   MAX-ACCESS  not-accessible
   STATUS      current
   DESCRIPTION
       " port, range : 1 - port number. "
   ::= { gs2310pSTPMSTI2NormalPortEntry 1 }

gs2310pSTPMSTI2NormalPortPathCost OBJECT-TYPE
   SYNTAX      Integer32(0..200000000)
   MAX-ACCESS  read-write
   STATUS      current
   DESCRIPTION
       " Auto: 0,
        Specific Path Cost range: 1 - 200000000."
   ::= { gs2310pSTPMSTI2NormalPortEntry 2 }

gs2310pSTPMSTI2NormalPortPriority OBJECT-TYPE
   SYNTAX      Integer32(0..240)
   MAX-ACCESS  read-write
   STATUS      current
   DESCRIPTION
       " default: 128,
       Aggregated Port Priority (0/16/32/48/64/80/96/112/128/144/160/176/192/208/224/240)"
   ::= { gs2310pSTPMSTI2NormalPortEntry 3 }

gs2310pSTPMSTI3Port                                                          OBJECT IDENTIFIER ::= { gs2310pSTPMSTIPort 3 }

gs2310pSTPMSTI3AggregatedPort                                                OBJECT IDENTIFIER ::= { gs2310pSTPMSTI3Port 1 }

gs2310pSTPMSTI3AggregatedPortPathCost OBJECT-TYPE
   SYNTAX      Integer32(0..200000000)
   MAX-ACCESS  read-write
   STATUS      current
   DESCRIPTION
       " Auto: 0,
        Specific Path Cost range: 1 - 200000000."
   ::= { gs2310pSTPMSTI3AggregatedPort 1 }

gs2310pSTPMSTI3AggregatedPortPriority OBJECT-TYPE
   SYNTAX      Integer32(0..240)
   MAX-ACCESS  read-write
   STATUS      current
   DESCRIPTION
       " default: 128,
       Aggregated Port Priority (0/16/32/48/64/80/96/112/128/144/160/176/192/208/224/240)"
   ::= { gs2310pSTPMSTI3AggregatedPort 2 }

gs2310pSTPMSTI3NormalPortTable OBJECT-TYPE
   SYNTAX      SEQUENCE OF Gs2310pSTPMSTI3NormalPortEntry
   MAX-ACCESS  not-accessible
   STATUS      current
   DESCRIPTION
       " Show MSTI3 Normal Port Configurations. "
   ::= { gs2310pSTPMSTI3Port 2 }

gs2310pSTPMSTI3NormalPortEntry OBJECT-TYPE
   SYNTAX      Gs2310pSTPMSTI3NormalPortEntry
   MAX-ACCESS  not-accessible
   STATUS      current
   DESCRIPTION
       ""
   INDEX    { gs2310pSTPMSTI3NormalPortConfPort  }
   ::= { gs2310pSTPMSTI3NormalPortTable 1 }

Gs2310pSTPMSTI3NormalPortEntry ::= SEQUENCE {
   gs2310pSTPMSTI3NormalPortConfPort         Integer32,
   gs2310pSTPMSTI3NormalPortPathCost         Integer32,
   gs2310pSTPMSTI3NormalPortPriority         Integer32
}

gs2310pSTPMSTI3NormalPortConfPort OBJECT-TYPE
   SYNTAX      Integer32(1..4095)
   MAX-ACCESS  not-accessible
   STATUS      current
   DESCRIPTION
       " port, range : 1 - port number. "
   ::= { gs2310pSTPMSTI3NormalPortEntry 1 }

gs2310pSTPMSTI3NormalPortPathCost OBJECT-TYPE
   SYNTAX      Integer32(0..200000000)
   MAX-ACCESS  read-write
   STATUS      current
   DESCRIPTION
       " Auto: 0,
        Specific Path Cost range: 1 - 200000000."
   ::= { gs2310pSTPMSTI3NormalPortEntry 2 }

gs2310pSTPMSTI3NormalPortPriority OBJECT-TYPE
   SYNTAX      Integer32(0..240)
   MAX-ACCESS  read-write
   STATUS      current
   DESCRIPTION
       " default: 128,
       Aggregated Port Priority (0/16/32/48/64/80/96/112/128/144/160/176/192/208/224/240)"
   ::= { gs2310pSTPMSTI3NormalPortEntry 3 }

gs2310pSTPMSTI4Port                                                          OBJECT IDENTIFIER ::= { gs2310pSTPMSTIPort 4 }

gs2310pSTPMSTI4AggregatedPort                                                OBJECT IDENTIFIER ::= { gs2310pSTPMSTI4Port 1 }

gs2310pSTPMSTI4AggregatedPortPathCost OBJECT-TYPE
   SYNTAX      Integer32(0..200000000)
   MAX-ACCESS  read-write
   STATUS      current
   DESCRIPTION
       " Auto: 0,
        Specific Path Cost range: 1 - 200000000."
   ::= { gs2310pSTPMSTI4AggregatedPort 1 }

gs2310pSTPMSTI4AggregatedPortPriority OBJECT-TYPE
   SYNTAX      Integer32(0..240)
   MAX-ACCESS  read-write
   STATUS      current
   DESCRIPTION
       " default: 128,
       Aggregated Port Priority (0/16/32/48/64/80/96/112/128/144/160/176/192/208/224/240)"
   ::= { gs2310pSTPMSTI4AggregatedPort 2 }

gs2310pSTPMSTI4NormalPortTable OBJECT-TYPE
   SYNTAX      SEQUENCE OF Gs2310pSTPMSTI4NormalPortEntry
   MAX-ACCESS  not-accessible
   STATUS      current
   DESCRIPTION
       " Show MSTI4 Normal Port Configurations. "
   ::= { gs2310pSTPMSTI4Port 2 }

gs2310pSTPMSTI4NormalPortEntry OBJECT-TYPE
   SYNTAX      Gs2310pSTPMSTI4NormalPortEntry
   MAX-ACCESS  not-accessible
   STATUS      current
   DESCRIPTION
       ""
   INDEX    { gs2310pSTPMSTI4NormalPortConfPort  }
   ::= { gs2310pSTPMSTI4NormalPortTable 1 }

Gs2310pSTPMSTI4NormalPortEntry ::= SEQUENCE {
   gs2310pSTPMSTI4NormalPortConfPort         Integer32,
   gs2310pSTPMSTI4NormalPortPathCost         Integer32,
   gs2310pSTPMSTI4NormalPortPriority         Integer32
}

gs2310pSTPMSTI4NormalPortConfPort OBJECT-TYPE
   SYNTAX      Integer32(1..4095)
   MAX-ACCESS  not-accessible
   STATUS      current
   DESCRIPTION
       " port, range : 1 - port number. "
   ::= { gs2310pSTPMSTI4NormalPortEntry 1 }

gs2310pSTPMSTI4NormalPortPathCost OBJECT-TYPE
   SYNTAX      Integer32(0..200000000)
   MAX-ACCESS  read-write
   STATUS      current
   DESCRIPTION
       " Auto: 0,
        Specific Path Cost range: 1 - 200000000."
   ::= { gs2310pSTPMSTI4NormalPortEntry 2 }

gs2310pSTPMSTI4NormalPortPriority OBJECT-TYPE
   SYNTAX      Integer32(0..240)
   MAX-ACCESS  read-write
   STATUS      current
   DESCRIPTION
       " default: 128,
       Aggregated Port Priority (0/16/32/48/64/80/96/112/128/144/160/176/192/208/224/240)"
   ::= { gs2310pSTPMSTI4NormalPortEntry 3 }

gs2310pSTPMSTI5Port                                                          OBJECT IDENTIFIER ::= { gs2310pSTPMSTIPort 5 }

gs2310pSTPMSTI5AggregatedPort                                                OBJECT IDENTIFIER ::= { gs2310pSTPMSTI5Port 1 }

gs2310pSTPMSTI5AggregatedPortPathCost OBJECT-TYPE
   SYNTAX      Integer32(0..200000000)
   MAX-ACCESS  read-write
   STATUS      current
   DESCRIPTION
       " Auto: 0,
        Specific Path Cost range: 1 - 200000000."
   ::= { gs2310pSTPMSTI5AggregatedPort 1 }

gs2310pSTPMSTI5AggregatedPortPriority OBJECT-TYPE
   SYNTAX      Integer32(0..240)
   MAX-ACCESS  read-write
   STATUS      current
   DESCRIPTION
       " default: 128,
       Aggregated Port Priority (0/16/32/48/64/80/96/112/128/144/160/176/192/208/224/240)"
   ::= { gs2310pSTPMSTI5AggregatedPort 2 }

gs2310pSTPMSTI5NormalPortTable OBJECT-TYPE
   SYNTAX      SEQUENCE OF Gs2310pSTPMSTI5NormalPortEntry
   MAX-ACCESS  not-accessible
   STATUS      current
   DESCRIPTION
       " Show MSTI5 Normal Port Configurations. "
   ::= { gs2310pSTPMSTI5Port 2 }

gs2310pSTPMSTI5NormalPortEntry OBJECT-TYPE
   SYNTAX      Gs2310pSTPMSTI5NormalPortEntry
   MAX-ACCESS  not-accessible
   STATUS      current
   DESCRIPTION
       ""
   INDEX    { gs2310pSTPMSTI5NormalPortConfPort  }
   ::= { gs2310pSTPMSTI5NormalPortTable 1 }

Gs2310pSTPMSTI5NormalPortEntry ::= SEQUENCE {
   gs2310pSTPMSTI5NormalPortConfPort         Integer32,
   gs2310pSTPMSTI5NormalPortPathCost         Integer32,
   gs2310pSTPMSTI5NormalPortPriority         Integer32
}

gs2310pSTPMSTI5NormalPortConfPort OBJECT-TYPE
   SYNTAX      Integer32(1..4095)
   MAX-ACCESS  not-accessible
   STATUS      current
   DESCRIPTION
       " port, range : 1 - port number. "
   ::= { gs2310pSTPMSTI5NormalPortEntry 1 }

gs2310pSTPMSTI5NormalPortPathCost OBJECT-TYPE
   SYNTAX      Integer32(0..200000000)
   MAX-ACCESS  read-write
   STATUS      current
   DESCRIPTION
       " Auto: 0,
        Specific Path Cost range: 1 - 200000000."
   ::= { gs2310pSTPMSTI5NormalPortEntry 2 }

gs2310pSTPMSTI5NormalPortPriority OBJECT-TYPE
   SYNTAX      Integer32(0..240)
   MAX-ACCESS  read-write
   STATUS      current
   DESCRIPTION
       " default: 128,
       Aggregated Port Priority (0/16/32/48/64/80/96/112/128/144/160/176/192/208/224/240)"
   ::= { gs2310pSTPMSTI5NormalPortEntry 3 }

gs2310pSTPMSTI6Port                                                          OBJECT IDENTIFIER ::= { gs2310pSTPMSTIPort 6 }

gs2310pSTPMSTI6AggregatedPort                                                OBJECT IDENTIFIER ::= { gs2310pSTPMSTI6Port 1 }

gs2310pSTPMSTI6AggregatedPortPathCost OBJECT-TYPE
   SYNTAX      Integer32(0..200000000)
   MAX-ACCESS  read-write
   STATUS      current
   DESCRIPTION
       " Auto: 0,
        Specific Path Cost range: 1 - 200000000."
   ::= { gs2310pSTPMSTI6AggregatedPort 1 }

gs2310pSTPMSTI6AggregatedPortPriority OBJECT-TYPE
   SYNTAX      Integer32(0..240)
   MAX-ACCESS  read-write
   STATUS      current
   DESCRIPTION
       " default: 128,
       Aggregated Port Priority (0/16/32/48/64/80/96/112/128/144/160/176/192/208/224/240)"
   ::= { gs2310pSTPMSTI6AggregatedPort 2 }

gs2310pSTPMSTI6NormalPortTable OBJECT-TYPE
   SYNTAX      SEQUENCE OF Gs2310pSTPMSTI6NormalPortEntry
   MAX-ACCESS  not-accessible
   STATUS      current
   DESCRIPTION
       " Show MSTI6 Normal Port Configurations. "
   ::= { gs2310pSTPMSTI6Port 2 }

gs2310pSTPMSTI6NormalPortEntry OBJECT-TYPE
   SYNTAX      Gs2310pSTPMSTI6NormalPortEntry
   MAX-ACCESS  not-accessible
   STATUS      current
   DESCRIPTION
       ""
   INDEX    { gs2310pSTPMSTI6NormalPortConfPort  }
   ::= { gs2310pSTPMSTI6NormalPortTable 1 }

Gs2310pSTPMSTI6NormalPortEntry ::= SEQUENCE {
   gs2310pSTPMSTI6NormalPortConfPort         Integer32,
   gs2310pSTPMSTI6NormalPortPathCost         Integer32,
   gs2310pSTPMSTI6NormalPortPriority         Integer32
}

gs2310pSTPMSTI6NormalPortConfPort OBJECT-TYPE
   SYNTAX      Integer32(1..4095)
   MAX-ACCESS  not-accessible
   STATUS      current
   DESCRIPTION
       " port, range : 1 - port number. "
   ::= { gs2310pSTPMSTI6NormalPortEntry 1 }

gs2310pSTPMSTI6NormalPortPathCost OBJECT-TYPE
   SYNTAX      Integer32(0..200000000)
   MAX-ACCESS  read-write
   STATUS      current
   DESCRIPTION
       " Auto: 0,
        Specific Path Cost range: 1 - 200000000."
   ::= { gs2310pSTPMSTI6NormalPortEntry 2 }

gs2310pSTPMSTI6NormalPortPriority OBJECT-TYPE
   SYNTAX      Integer32(0..240)
   MAX-ACCESS  read-write
   STATUS      current
   DESCRIPTION
       " default: 128,
       Aggregated Port Priority (0/16/32/48/64/80/96/112/128/144/160/176/192/208/224/240)"
   ::= { gs2310pSTPMSTI6NormalPortEntry 3 }

gs2310pSTPMSTI7Port                                                          OBJECT IDENTIFIER ::= { gs2310pSTPMSTIPort 7 }

gs2310pSTPMSTI7AggregatedPort                                                OBJECT IDENTIFIER ::= { gs2310pSTPMSTI7Port 1 }

gs2310pSTPMSTI7AggregatedPortPathCost OBJECT-TYPE
   SYNTAX      Integer32(0..200000000)
   MAX-ACCESS  read-write
   STATUS      current
   DESCRIPTION
       " Auto: 0,
        Specific Path Cost range: 1 - 200000000."
   ::= { gs2310pSTPMSTI7AggregatedPort 1 }

gs2310pSTPMSTI7AggregatedPortPriority OBJECT-TYPE
   SYNTAX      Integer32(0..240)
   MAX-ACCESS  read-write
   STATUS      current
   DESCRIPTION
       " default: 128,
       Aggregated Port Priority (0/16/32/48/64/80/96/112/128/144/160/176/192/208/224/240)"
   ::= { gs2310pSTPMSTI7AggregatedPort 2 }

gs2310pSTPMSTI7NormalPortTable OBJECT-TYPE
   SYNTAX      SEQUENCE OF Gs2310pSTPMSTI7NormalPortEntry
   MAX-ACCESS  not-accessible
   STATUS      current
   DESCRIPTION
       " Show MSTI7 Normal Port Configurations. "
   ::= { gs2310pSTPMSTI7Port 2 }

gs2310pSTPMSTI7NormalPortEntry OBJECT-TYPE
   SYNTAX      Gs2310pSTPMSTI7NormalPortEntry
   MAX-ACCESS  not-accessible
   STATUS      current
   DESCRIPTION
       ""
   INDEX    { gs2310pSTPMSTI7NormalPortConfPort  }
   ::= { gs2310pSTPMSTI7NormalPortTable 1 }

Gs2310pSTPMSTI7NormalPortEntry ::= SEQUENCE {
   gs2310pSTPMSTI7NormalPortConfPort         Integer32,
   gs2310pSTPMSTI7NormalPortPathCost         Integer32,
   gs2310pSTPMSTI7NormalPortPriority         Integer32
}

gs2310pSTPMSTI7NormalPortConfPort OBJECT-TYPE
   SYNTAX      Integer32(1..4095)
   MAX-ACCESS  not-accessible
   STATUS      current
   DESCRIPTION
       " port, range : 1 - port number. "
   ::= { gs2310pSTPMSTI7NormalPortEntry 1 }

gs2310pSTPMSTI7NormalPortPathCost OBJECT-TYPE
   SYNTAX      Integer32(0..200000000)
   MAX-ACCESS  read-write
   STATUS      current
   DESCRIPTION
       " Auto: 0,
        Specific Path Cost range: 1 - 200000000."
   ::= { gs2310pSTPMSTI7NormalPortEntry 2 }

gs2310pSTPMSTI7NormalPortPriority OBJECT-TYPE
   SYNTAX      Integer32(0..240)
   MAX-ACCESS  read-write
   STATUS      current
   DESCRIPTION
       " default: 128,
       Aggregated Port Priority (0/16/32/48/64/80/96/112/128/144/160/176/192/208/224/240)"
   ::= { gs2310pSTPMSTI7NormalPortEntry 3 }


gs2310pSTPBridgeStatus                                                      OBJECT IDENTIFIER ::= { gs2310pSTP 8 }

gs2310pCISTBridgeSTP                                                        OBJECT IDENTIFIER ::= { gs2310pSTPBridgeStatus 1 }

gs2310pCISTBridgeSTPStatus                                                  OBJECT IDENTIFIER ::= { gs2310pCISTBridgeSTP 1 }

gs2310pCISTBridgeInstance OBJECT-TYPE
   SYNTAX       DisplayString
   MAX-ACCESS   read-only
   STATUS       current
   DESCRIPTION
       "The Bridge instance - CIST, MST1, ..."
   ::= { gs2310pCISTBridgeSTPStatus 1 }

gs2310pCISTBridgeID OBJECT-TYPE
   SYNTAX       DisplayString
   MAX-ACCESS   read-only
   STATUS       current
   DESCRIPTION
       "The Bridge ID of this Bridge instance."
   ::= { gs2310pCISTBridgeSTPStatus 2 }

gs2310pCISTRootID OBJECT-TYPE
   SYNTAX       DisplayString
   MAX-ACCESS   read-only
   STATUS       current
   DESCRIPTION
       "The Bridge ID of the currently elected root bridge."
   ::= { gs2310pCISTBridgeSTPStatus 3 }

gs2310pCISTRootPort OBJECT-TYPE
   SYNTAX       DisplayString
   MAX-ACCESS   read-only
   STATUS       current
   DESCRIPTION
       "The switch port currently assigned the root port role."
   ::= { gs2310pCISTBridgeSTPStatus 4 }

gs2310pCISTRootCost OBJECT-TYPE
   SYNTAX       Integer32(0..200000000)
   MAX-ACCESS   read-only
   STATUS       current
   DESCRIPTION
       "Root Path Cost."
   ::= { gs2310pCISTBridgeSTPStatus 5 }

gs2310pCISTRegionalRoot OBJECT-TYPE
   SYNTAX       DisplayString
   MAX-ACCESS   read-only
   STATUS       current
   DESCRIPTION
       "The Bridge ID of the currently elected regional root bridge, inside the MSTP region of this bridge."
   ::= { gs2310pCISTBridgeSTPStatus 6 }

gs2310pCISTInternalRootCost OBJECT-TYPE
   SYNTAX       Integer32(0..200000000)
   MAX-ACCESS   read-only
   STATUS       current
   DESCRIPTION
       "The Regional Root Path Cost."
   ::= { gs2310pCISTBridgeSTPStatus 7 }

gs2310pCISTTopologyFlag OBJECT-TYPE
   SYNTAX       DisplayString
   MAX-ACCESS   read-only
   STATUS       current
   DESCRIPTION
       "The current state of the Topology Change Flag of this Bridge instance."
   ::= { gs2310pCISTBridgeSTPStatus 8 }

gs2310pCISTTopologyChangeCount OBJECT-TYPE
   SYNTAX       Counter32
   MAX-ACCESS   read-only
   STATUS       current
   DESCRIPTION
       "The number of times where the topology change flag has been set."
   ::= { gs2310pCISTBridgeSTPStatus 9 }

gs2310pCISTTopologyChangeLast OBJECT-TYPE
   SYNTAX       DisplayString
   MAX-ACCESS   read-only
   STATUS       current
   DESCRIPTION
       "The time passed since the Topology Flag was last set."
   ::= { gs2310pCISTBridgeSTPStatus 10 }

gs2310pCISTPortStateTable OBJECT-TYPE
   SYNTAX      SEQUENCE OF Gs2310pCISTPortStateEntry
   MAX-ACCESS  not-accessible
   STATUS      current
   DESCRIPTION
       " Show CIST Ports and Aggregations State Configurations. "
   ::= { gs2310pCISTBridgeSTP 2 }

gs2310pCISTPortStateEntry OBJECT-TYPE
   SYNTAX      Gs2310pCISTPortStateEntry
   MAX-ACCESS  not-accessible
   STATUS      current
   DESCRIPTION
       ""
   INDEX    { gs2310pCISTPortStateIndex  }
   ::= { gs2310pCISTPortStateTable 1 }

Gs2310pCISTPortStateEntry ::= SEQUENCE {
   gs2310pCISTPortStateIndex        Integer32,
   gs2310pCISTPortStatePort         DisplayString,
   gs2310pCISTPortStatePortID       DisplayString,
   gs2310pCISTPortStateRole         DisplayString,
   gs2310pCISTPortStateState        DisplayString,
   gs2310pCISTPortStatePathCost     Integer32,
   gs2310pCISTPortStateEdge         DisplayString,
   gs2310pCISTPortStatePoint2Point  DisplayString,
   gs2310pCISTPortStateUptime       DisplayString
}

gs2310pCISTPortStateIndex OBJECT-TYPE
   SYNTAX      Integer32(1..4095)
   MAX-ACCESS  not-accessible
   STATUS      current
   DESCRIPTION
       "table index."
   ::= { gs2310pCISTPortStateEntry 1 }

gs2310pCISTPortStatePort OBJECT-TYPE
   SYNTAX      DisplayString
   MAX-ACCESS  read-only
   STATUS      current
   DESCRIPTION
       "The switch port number of the logical STP port."
   ::= { gs2310pCISTPortStateEntry 2 }

gs2310pCISTPortStatePortID OBJECT-TYPE
   SYNTAX      DisplayString
   MAX-ACCESS  read-only
   STATUS      current
   DESCRIPTION
       "The port id as used by the STP protocol.
        This is the priority part and the logical port index of the bridge port."
   ::= { gs2310pCISTPortStateEntry 3 }

gs2310pCISTPortStateRole OBJECT-TYPE
   SYNTAX      DisplayString
   MAX-ACCESS  read-only
   STATUS      current
   DESCRIPTION
       "The current STP port role."
   ::= { gs2310pCISTPortStateEntry 4 }

gs2310pCISTPortStateState OBJECT-TYPE
   SYNTAX      DisplayString
   MAX-ACCESS  read-only
   STATUS      current
   DESCRIPTION
       "The current STP port state."
   ::= { gs2310pCISTPortStateEntry 5 }

gs2310pCISTPortStatePathCost OBJECT-TYPE
   SYNTAX      Integer32(0..200000000)
   MAX-ACCESS  read-only
   STATUS      current
   DESCRIPTION
       "The current STP port path cost."
   ::= { gs2310pCISTPortStateEntry 6 }

gs2310pCISTPortStateEdge OBJECT-TYPE
   SYNTAX      DisplayString
   MAX-ACCESS  read-only
   STATUS      current
   DESCRIPTION
       "The current STP port Edge Flag."
   ::= { gs2310pCISTPortStateEntry 7 }

gs2310pCISTPortStatePoint2Point OBJECT-TYPE
   SYNTAX      DisplayString
   MAX-ACCESS  read-only
   STATUS      current
   DESCRIPTION
       "The current STP port point-to-point flag."
   ::= { gs2310pCISTPortStateEntry 8 }

gs2310pCISTPortStateUptime OBJECT-TYPE
   SYNTAX      DisplayString
   MAX-ACCESS  read-only
   STATUS      current
   DESCRIPTION
       "The time since the bridge port was last initialized."
   ::= { gs2310pCISTPortStateEntry 9 }

gs2310pMSTI1BridgeSTP                                                        OBJECT IDENTIFIER ::= { gs2310pSTPBridgeStatus 2 }

gs2310pMSTI1BridgeSTPStatus                                                  OBJECT IDENTIFIER ::= { gs2310pMSTI1BridgeSTP 1 }

gs2310pMSTI1BridgeInstance OBJECT-TYPE
   SYNTAX       DisplayString
   MAX-ACCESS   read-only
   STATUS       current
   DESCRIPTION
       "The Bridge instance - CIST, MST1, ..."
   ::= { gs2310pMSTI1BridgeSTPStatus 1 }

gs2310pMSTI1BridgeID OBJECT-TYPE
   SYNTAX       DisplayString
   MAX-ACCESS   read-only
   STATUS       current
   DESCRIPTION
       "The Bridge ID of this Bridge instance."
   ::= { gs2310pMSTI1BridgeSTPStatus 2 }

gs2310pMSTI1RootID OBJECT-TYPE
   SYNTAX       DisplayString
   MAX-ACCESS   read-only
   STATUS       current
   DESCRIPTION
       "The Bridge ID of the currently elected root bridge."
   ::= { gs2310pMSTI1BridgeSTPStatus 3 }

gs2310pMSTI1RootPort OBJECT-TYPE
   SYNTAX       DisplayString
   MAX-ACCESS   read-only
   STATUS       current
   DESCRIPTION
       "The switch port currently assigned the root port role."
   ::= { gs2310pMSTI1BridgeSTPStatus 4 }

gs2310pMSTI1RootCost OBJECT-TYPE
   SYNTAX       Integer32(0..200000000)
   MAX-ACCESS   read-only
   STATUS       current
   DESCRIPTION
       "Root Path Cost."
   ::= { gs2310pMSTI1BridgeSTPStatus 5 }

gs2310pMSTI1TopologyFlag OBJECT-TYPE
   SYNTAX       DisplayString
   MAX-ACCESS   read-only
   STATUS       current
   DESCRIPTION
       "The current state of the Topology Change Flag of this Bridge instance."
   ::= { gs2310pMSTI1BridgeSTPStatus 8 }

gs2310pMSTI1TopologyChangeCount OBJECT-TYPE
   SYNTAX       Counter32
   MAX-ACCESS   read-only
   STATUS       current
   DESCRIPTION
       "The number of times where the topology change flag has been set."
   ::= { gs2310pMSTI1BridgeSTPStatus 9 }

gs2310pMSTI1TopologyChangeLast OBJECT-TYPE
   SYNTAX       DisplayString
   MAX-ACCESS   read-only
   STATUS       current
   DESCRIPTION
       "The time passed since the Topology Flag was last set."
   ::= { gs2310pMSTI1BridgeSTPStatus 10 }

gs2310pMSTI1PortStateTable OBJECT-TYPE
   SYNTAX      SEQUENCE OF Gs2310pMSTI1PortStateEntry
   MAX-ACCESS  not-accessible
   STATUS      current
   DESCRIPTION
       " Show MSTI1 Ports and Aggregations State Configurations. "
   ::= { gs2310pMSTI1BridgeSTP 2 }

gs2310pMSTI1PortStateEntry OBJECT-TYPE
   SYNTAX      Gs2310pMSTI1PortStateEntry
   MAX-ACCESS  not-accessible
   STATUS      current
   DESCRIPTION
       ""
   INDEX    { gs2310pMSTI1PortStateIndex  }
   ::= { gs2310pMSTI1PortStateTable 1 }

Gs2310pMSTI1PortStateEntry ::= SEQUENCE {
   gs2310pMSTI1PortStateIndex        Integer32,
   gs2310pMSTI1PortStatePort         DisplayString,
   gs2310pMSTI1PortStatePortID       DisplayString,
   gs2310pMSTI1PortStateRole         DisplayString,
   gs2310pMSTI1PortStateState        DisplayString,
   gs2310pMSTI1PortStatePathCost     Integer32,
   gs2310pMSTI1PortStateEdge         DisplayString,
   gs2310pMSTI1PortStatePoint2Point  DisplayString,
   gs2310pMSTI1PortStateUptime       DisplayString
}

gs2310pMSTI1PortStateIndex OBJECT-TYPE
   SYNTAX      Integer32(1..4095)
   MAX-ACCESS  not-accessible
   STATUS      current
   DESCRIPTION
       "table index."
   ::= { gs2310pMSTI1PortStateEntry 1 }

gs2310pMSTI1PortStatePort OBJECT-TYPE
   SYNTAX      DisplayString
   MAX-ACCESS  read-only
   STATUS      current
   DESCRIPTION
       "The switch port number of the logical STP port."
   ::= { gs2310pMSTI1PortStateEntry 2 }

gs2310pMSTI1PortStatePortID OBJECT-TYPE
   SYNTAX      DisplayString
   MAX-ACCESS  read-only
   STATUS      current
   DESCRIPTION
       "The port id as used by the STP protocol.
        This is the priority part and the logical port index of the bridge port."
   ::= { gs2310pMSTI1PortStateEntry 3 }

gs2310pMSTI1PortStateRole OBJECT-TYPE
   SYNTAX      DisplayString
   MAX-ACCESS  read-only
   STATUS      current
   DESCRIPTION
       "The current STP port role."
   ::= { gs2310pMSTI1PortStateEntry 4 }

gs2310pMSTI1PortStateState OBJECT-TYPE
   SYNTAX      DisplayString
   MAX-ACCESS  read-only
   STATUS      current
   DESCRIPTION
       "The current STP port state."
   ::= { gs2310pMSTI1PortStateEntry 5 }

gs2310pMSTI1PortStatePathCost OBJECT-TYPE
   SYNTAX      Integer32(0..200000000)
   MAX-ACCESS  read-only
   STATUS      current
   DESCRIPTION
       "The current STP port path cost."
   ::= { gs2310pMSTI1PortStateEntry 6 }

gs2310pMSTI1PortStateEdge OBJECT-TYPE
   SYNTAX      DisplayString
   MAX-ACCESS  read-only
   STATUS      current
   DESCRIPTION
       "The current STP port Edge Flag."
   ::= { gs2310pMSTI1PortStateEntry 7 }

gs2310pMSTI1PortStatePoint2Point OBJECT-TYPE
   SYNTAX      DisplayString
   MAX-ACCESS  read-only
   STATUS      current
   DESCRIPTION
       "The current STP port point-to-point flag."
   ::= { gs2310pMSTI1PortStateEntry 8 }

gs2310pMSTI1PortStateUptime OBJECT-TYPE
   SYNTAX      DisplayString
   MAX-ACCESS  read-only
   STATUS      current
   DESCRIPTION
       "The time since the bridge port was last initialized."
   ::= { gs2310pMSTI1PortStateEntry 9 }

gs2310pMSTI2BridgeSTP                                                        OBJECT IDENTIFIER ::= { gs2310pSTPBridgeStatus 3 }

gs2310pMSTI2BridgeSTPStatus                                                  OBJECT IDENTIFIER ::= { gs2310pMSTI2BridgeSTP 1 }

gs2310pMSTI2BridgeInstance OBJECT-TYPE
   SYNTAX       DisplayString
   MAX-ACCESS   read-only
   STATUS       current
   DESCRIPTION
       "The Bridge instance - CIST, MST1, ..."
   ::= { gs2310pMSTI2BridgeSTPStatus 1 }

gs2310pMSTI2BridgeID OBJECT-TYPE
   SYNTAX       DisplayString
   MAX-ACCESS   read-only
   STATUS       current
   DESCRIPTION
       "The Bridge ID of this Bridge instance."
   ::= { gs2310pMSTI2BridgeSTPStatus 2 }

gs2310pMSTI2RootID OBJECT-TYPE
   SYNTAX       DisplayString
   MAX-ACCESS   read-only
   STATUS       current
   DESCRIPTION
       "The Bridge ID of the currently elected root bridge."
   ::= { gs2310pMSTI2BridgeSTPStatus 3 }

gs2310pMSTI2RootPort OBJECT-TYPE
   SYNTAX       DisplayString
   MAX-ACCESS   read-only
   STATUS       current
   DESCRIPTION
       "The switch port currently assigned the root port role."
   ::= { gs2310pMSTI2BridgeSTPStatus 4 }

gs2310pMSTI2RootCost OBJECT-TYPE
   SYNTAX       Integer32(0..200000000)
   MAX-ACCESS   read-only
   STATUS       current
   DESCRIPTION
       "Root Path Cost."
   ::= { gs2310pMSTI2BridgeSTPStatus 5 }

gs2310pMSTI2TopologyFlag OBJECT-TYPE
   SYNTAX       DisplayString
   MAX-ACCESS   read-only
   STATUS       current
   DESCRIPTION
       "The current state of the Topology Change Flag of this Bridge instance."
   ::= { gs2310pMSTI2BridgeSTPStatus 8 }

gs2310pMSTI2TopologyChangeCount OBJECT-TYPE
   SYNTAX       Counter32
   MAX-ACCESS   read-only
   STATUS       current
   DESCRIPTION
       "The number of times where the topology change flag has been set."
   ::= { gs2310pMSTI2BridgeSTPStatus 9 }

gs2310pMSTI2TopologyChangeLast OBJECT-TYPE
   SYNTAX       DisplayString
   MAX-ACCESS   read-only
   STATUS       current
   DESCRIPTION
       "The time passed since the Topology Flag was last set."
   ::= { gs2310pMSTI2BridgeSTPStatus 10 }

gs2310pMSTI2PortStateTable OBJECT-TYPE
   SYNTAX      SEQUENCE OF Gs2310pMSTI2PortStateEntry
   MAX-ACCESS  not-accessible
   STATUS      current
   DESCRIPTION
       " Show MSTI2 Ports and Aggregations State Configurations. "
   ::= { gs2310pMSTI2BridgeSTP 2 }

gs2310pMSTI2PortStateEntry OBJECT-TYPE
   SYNTAX      Gs2310pMSTI2PortStateEntry
   MAX-ACCESS  not-accessible
   STATUS      current
   DESCRIPTION
       ""
   INDEX    { gs2310pMSTI2PortStateIndex  }
   ::= { gs2310pMSTI2PortStateTable 1 }

Gs2310pMSTI2PortStateEntry ::= SEQUENCE {
   gs2310pMSTI2PortStateIndex        Integer32,
   gs2310pMSTI2PortStatePort         DisplayString,
   gs2310pMSTI2PortStatePortID       DisplayString,
   gs2310pMSTI2PortStateRole         DisplayString,
   gs2310pMSTI2PortStateState        DisplayString,
   gs2310pMSTI2PortStatePathCost     Integer32,
   gs2310pMSTI2PortStateEdge         DisplayString,
   gs2310pMSTI2PortStatePoint2Point  DisplayString,
   gs2310pMSTI2PortStateUptime       DisplayString
}

gs2310pMSTI2PortStateIndex OBJECT-TYPE
   SYNTAX      Integer32(1..4095)
   MAX-ACCESS  not-accessible
   STATUS      current
   DESCRIPTION
       "table index."
   ::= { gs2310pMSTI2PortStateEntry 1 }

gs2310pMSTI2PortStatePort OBJECT-TYPE
   SYNTAX      DisplayString
   MAX-ACCESS  read-only
   STATUS      current
   DESCRIPTION
       "The switch port number of the logical STP port."
   ::= { gs2310pMSTI2PortStateEntry 2 }

gs2310pMSTI2PortStatePortID OBJECT-TYPE
   SYNTAX      DisplayString
   MAX-ACCESS  read-only
   STATUS      current
   DESCRIPTION
       "The port id as used by the STP protocol.
        This is the priority part and the logical port index of the bridge port."
   ::= { gs2310pMSTI2PortStateEntry 3 }

gs2310pMSTI2PortStateRole OBJECT-TYPE
   SYNTAX      DisplayString
   MAX-ACCESS  read-only
   STATUS      current
   DESCRIPTION
       "The current STP port role."
   ::= { gs2310pMSTI2PortStateEntry 4 }

gs2310pMSTI2PortStateState OBJECT-TYPE
   SYNTAX      DisplayString
   MAX-ACCESS  read-only
   STATUS      current
   DESCRIPTION
       "The current STP port state."
   ::= { gs2310pMSTI2PortStateEntry 5 }

gs2310pMSTI2PortStatePathCost OBJECT-TYPE
   SYNTAX      Integer32(0..200000000)
   MAX-ACCESS  read-only
   STATUS      current
   DESCRIPTION
       "The current STP port path cost."
   ::= { gs2310pMSTI2PortStateEntry 6 }

gs2310pMSTI2PortStateEdge OBJECT-TYPE
   SYNTAX      DisplayString
   MAX-ACCESS  read-only
   STATUS      current
   DESCRIPTION
       "The current STP port Edge Flag."
   ::= { gs2310pMSTI2PortStateEntry 7 }

gs2310pMSTI2PortStatePoint2Point OBJECT-TYPE
   SYNTAX      DisplayString
   MAX-ACCESS  read-only
   STATUS      current
   DESCRIPTION
       "The current STP port point-to-point flag."
   ::= { gs2310pMSTI2PortStateEntry 8 }

gs2310pMSTI2PortStateUptime OBJECT-TYPE
   SYNTAX      DisplayString
   MAX-ACCESS  read-only
   STATUS      current
   DESCRIPTION
       "The time since the bridge port was last initialized."
   ::= { gs2310pMSTI2PortStateEntry 9 }

gs2310pMSTI3BridgeSTP                                                        OBJECT IDENTIFIER ::= { gs2310pSTPBridgeStatus 4 }

gs2310pMSTI3BridgeSTPStatus                                                  OBJECT IDENTIFIER ::= { gs2310pMSTI3BridgeSTP 1 }

gs2310pMSTI3BridgeInstance OBJECT-TYPE
   SYNTAX       DisplayString
   MAX-ACCESS   read-only
   STATUS       current
   DESCRIPTION
       "The Bridge instance - CIST, MST1, ..."
   ::= { gs2310pMSTI3BridgeSTPStatus 1 }

gs2310pMSTI3BridgeID OBJECT-TYPE
   SYNTAX       DisplayString
   MAX-ACCESS   read-only
   STATUS       current
   DESCRIPTION
       "The Bridge ID of this Bridge instance."
   ::= { gs2310pMSTI3BridgeSTPStatus 2 }

gs2310pMSTI3RootID OBJECT-TYPE
   SYNTAX       DisplayString
   MAX-ACCESS   read-only
   STATUS       current
   DESCRIPTION
       "The Bridge ID of the currently elected root bridge."
   ::= { gs2310pMSTI3BridgeSTPStatus 3 }

gs2310pMSTI3RootPort OBJECT-TYPE
   SYNTAX       DisplayString
   MAX-ACCESS   read-only
   STATUS       current
   DESCRIPTION
       "The switch port currently assigned the root port role."
   ::= { gs2310pMSTI3BridgeSTPStatus 4 }

gs2310pMSTI3RootCost OBJECT-TYPE
   SYNTAX       Integer32(0..200000000)
   MAX-ACCESS   read-only
   STATUS       current
   DESCRIPTION
       "Root Path Cost."
   ::= { gs2310pMSTI3BridgeSTPStatus 5 }

gs2310pMSTI3TopologyFlag OBJECT-TYPE
   SYNTAX       DisplayString
   MAX-ACCESS   read-only
   STATUS       current
   DESCRIPTION
       "The current state of the Topology Change Flag of this Bridge instance."
   ::= { gs2310pMSTI3BridgeSTPStatus 8 }

gs2310pMSTI3TopologyChangeCount OBJECT-TYPE
   SYNTAX       Counter32
   MAX-ACCESS   read-only
   STATUS       current
   DESCRIPTION
       "The number of times where the topology change flag has been set."
   ::= { gs2310pMSTI3BridgeSTPStatus 9 }

gs2310pMSTI3TopologyChangeLast OBJECT-TYPE
   SYNTAX       DisplayString
   MAX-ACCESS   read-only
   STATUS       current
   DESCRIPTION
       "The time passed since the Topology Flag was last set."
   ::= { gs2310pMSTI3BridgeSTPStatus 10 }

gs2310pMSTI3PortStateTable OBJECT-TYPE
   SYNTAX      SEQUENCE OF Gs2310pMSTI3PortStateEntry
   MAX-ACCESS  not-accessible
   STATUS      current
   DESCRIPTION
       " Show MSTI3 Ports and Aggregations State Configurations. "
   ::= { gs2310pMSTI3BridgeSTP 2 }

gs2310pMSTI3PortStateEntry OBJECT-TYPE
   SYNTAX      Gs2310pMSTI3PortStateEntry
   MAX-ACCESS  not-accessible
   STATUS      current
   DESCRIPTION
       ""
   INDEX    { gs2310pMSTI3PortStateIndex  }
   ::= { gs2310pMSTI3PortStateTable 1 }

Gs2310pMSTI3PortStateEntry ::= SEQUENCE {
   gs2310pMSTI3PortStateIndex        Integer32,
   gs2310pMSTI3PortStatePort         DisplayString,
   gs2310pMSTI3PortStatePortID       DisplayString,
   gs2310pMSTI3PortStateRole         DisplayString,
   gs2310pMSTI3PortStateState        DisplayString,
   gs2310pMSTI3PortStatePathCost     Integer32,
   gs2310pMSTI3PortStateEdge         DisplayString,
   gs2310pMSTI3PortStatePoint2Point  DisplayString,
   gs2310pMSTI3PortStateUptime       DisplayString
}

gs2310pMSTI3PortStateIndex OBJECT-TYPE
   SYNTAX      Integer32(1..4095)
   MAX-ACCESS  not-accessible
   STATUS      current
   DESCRIPTION
       "table index."
   ::= { gs2310pMSTI3PortStateEntry 1 }

gs2310pMSTI3PortStatePort OBJECT-TYPE
   SYNTAX      DisplayString
   MAX-ACCESS  read-only
   STATUS      current
   DESCRIPTION
       "The switch port number of the logical STP port."
   ::= { gs2310pMSTI3PortStateEntry 2 }

gs2310pMSTI3PortStatePortID OBJECT-TYPE
   SYNTAX      DisplayString
   MAX-ACCESS  read-only
   STATUS      current
   DESCRIPTION
       "The port id as used by the STP protocol.
        This is the priority part and the logical port index of the bridge port."
   ::= { gs2310pMSTI3PortStateEntry 3 }

gs2310pMSTI3PortStateRole OBJECT-TYPE
   SYNTAX      DisplayString
   MAX-ACCESS  read-only
   STATUS      current
   DESCRIPTION
       "The current STP port role."
   ::= { gs2310pMSTI3PortStateEntry 4 }

gs2310pMSTI3PortStateState OBJECT-TYPE
   SYNTAX      DisplayString
   MAX-ACCESS  read-only
   STATUS      current
   DESCRIPTION
       "The current STP port state."
   ::= { gs2310pMSTI3PortStateEntry 5 }

gs2310pMSTI3PortStatePathCost OBJECT-TYPE
   SYNTAX      Integer32(0..200000000)
   MAX-ACCESS  read-only
   STATUS      current
   DESCRIPTION
       "The current STP port path cost."
   ::= { gs2310pMSTI3PortStateEntry 6 }

gs2310pMSTI3PortStateEdge OBJECT-TYPE
   SYNTAX      DisplayString
   MAX-ACCESS  read-only
   STATUS      current
   DESCRIPTION
       "The current STP port Edge Flag."
   ::= { gs2310pMSTI3PortStateEntry 7 }

gs2310pMSTI3PortStatePoint2Point OBJECT-TYPE
   SYNTAX      DisplayString
   MAX-ACCESS  read-only
   STATUS      current
   DESCRIPTION
       "The current STP port point-to-point flag."
   ::= { gs2310pMSTI3PortStateEntry 8 }

gs2310pMSTI3PortStateUptime OBJECT-TYPE
   SYNTAX      DisplayString
   MAX-ACCESS  read-only
   STATUS      current
   DESCRIPTION
       "The time since the bridge port was last initialized."
   ::= { gs2310pMSTI3PortStateEntry 9 }

gs2310pMSTI4BridgeSTP                                                        OBJECT IDENTIFIER ::= { gs2310pSTPBridgeStatus 5 }

gs2310pMSTI4BridgeSTPStatus                                                  OBJECT IDENTIFIER ::= { gs2310pMSTI4BridgeSTP 1 }

gs2310pMSTI4BridgeInstance OBJECT-TYPE
   SYNTAX       DisplayString
   MAX-ACCESS   read-only
   STATUS       current
   DESCRIPTION
       "The Bridge instance - CIST, MST1, ..."
   ::= { gs2310pMSTI4BridgeSTPStatus 1 }

gs2310pMSTI4BridgeID OBJECT-TYPE
   SYNTAX       DisplayString
   MAX-ACCESS   read-only
   STATUS       current
   DESCRIPTION
       "The Bridge ID of this Bridge instance."
   ::= { gs2310pMSTI4BridgeSTPStatus 2 }

gs2310pMSTI4RootID OBJECT-TYPE
   SYNTAX       DisplayString
   MAX-ACCESS   read-only
   STATUS       current
   DESCRIPTION
       "The Bridge ID of the currently elected root bridge."
   ::= { gs2310pMSTI4BridgeSTPStatus 3 }

gs2310pMSTI4RootPort OBJECT-TYPE
   SYNTAX       DisplayString
   MAX-ACCESS   read-only
   STATUS       current
   DESCRIPTION
       "The switch port currently assigned the root port role."
   ::= { gs2310pMSTI4BridgeSTPStatus 4 }

gs2310pMSTI4RootCost OBJECT-TYPE
   SYNTAX       Integer32(0..200000000)
   MAX-ACCESS   read-only
   STATUS       current
   DESCRIPTION
       "Root Path Cost."
   ::= { gs2310pMSTI4BridgeSTPStatus 5 }

gs2310pMSTI4TopologyFlag OBJECT-TYPE
   SYNTAX       DisplayString
   MAX-ACCESS   read-only
   STATUS       current
   DESCRIPTION
       "The current state of the Topology Change Flag of this Bridge instance."
   ::= { gs2310pMSTI4BridgeSTPStatus 8 }

gs2310pMSTI4TopologyChangeCount OBJECT-TYPE
   SYNTAX       Counter32
   MAX-ACCESS   read-only
   STATUS       current
   DESCRIPTION
       "The number of times where the topology change flag has been set."
   ::= { gs2310pMSTI4BridgeSTPStatus 9 }

gs2310pMSTI4TopologyChangeLast OBJECT-TYPE
   SYNTAX       DisplayString
   MAX-ACCESS   read-only
   STATUS       current
   DESCRIPTION
       "The time passed since the Topology Flag was last set."
   ::= { gs2310pMSTI4BridgeSTPStatus 10 }

gs2310pMSTI4PortStateTable OBJECT-TYPE
   SYNTAX      SEQUENCE OF Gs2310pMSTI4PortStateEntry
   MAX-ACCESS  not-accessible
   STATUS      current
   DESCRIPTION
       " Show MSTI4 Ports and Aggregations State Configurations. "
   ::= { gs2310pMSTI4BridgeSTP 2 }

gs2310pMSTI4PortStateEntry OBJECT-TYPE
   SYNTAX      Gs2310pMSTI4PortStateEntry
   MAX-ACCESS  not-accessible
   STATUS      current
   DESCRIPTION
       ""
   INDEX    { gs2310pMSTI4PortStateIndex  }
   ::= { gs2310pMSTI4PortStateTable 1 }

Gs2310pMSTI4PortStateEntry ::= SEQUENCE {
   gs2310pMSTI4PortStateIndex        Integer32,
   gs2310pMSTI4PortStatePort         DisplayString,
   gs2310pMSTI4PortStatePortID       DisplayString,
   gs2310pMSTI4PortStateRole         DisplayString,
   gs2310pMSTI4PortStateState        DisplayString,
   gs2310pMSTI4PortStatePathCost     Integer32,
   gs2310pMSTI4PortStateEdge         DisplayString,
   gs2310pMSTI4PortStatePoint2Point  DisplayString,
   gs2310pMSTI4PortStateUptime       DisplayString
}

gs2310pMSTI4PortStateIndex OBJECT-TYPE
   SYNTAX      Integer32(1..4095)
   MAX-ACCESS  not-accessible
   STATUS      current
   DESCRIPTION
       "table index."
   ::= { gs2310pMSTI4PortStateEntry 1 }

gs2310pMSTI4PortStatePort OBJECT-TYPE
   SYNTAX      DisplayString
   MAX-ACCESS  read-only
   STATUS      current
   DESCRIPTION
       "The switch port number of the logical STP port."
   ::= { gs2310pMSTI4PortStateEntry 2 }

gs2310pMSTI4PortStatePortID OBJECT-TYPE
   SYNTAX      DisplayString
   MAX-ACCESS  read-only
   STATUS      current
   DESCRIPTION
       "The port id as used by the STP protocol.
        This is the priority part and the logical port index of the bridge port."
   ::= { gs2310pMSTI4PortStateEntry 3 }

gs2310pMSTI4PortStateRole OBJECT-TYPE
   SYNTAX      DisplayString
   MAX-ACCESS  read-only
   STATUS      current
   DESCRIPTION
       "The current STP port role."
   ::= { gs2310pMSTI4PortStateEntry 4 }

gs2310pMSTI4PortStateState OBJECT-TYPE
   SYNTAX      DisplayString
   MAX-ACCESS  read-only
   STATUS      current
   DESCRIPTION
       "The current STP port state."
   ::= { gs2310pMSTI4PortStateEntry 5 }

gs2310pMSTI4PortStatePathCost OBJECT-TYPE
   SYNTAX      Integer32(0..200000000)
   MAX-ACCESS  read-only
   STATUS      current
   DESCRIPTION
       "The current STP port path cost."
   ::= { gs2310pMSTI4PortStateEntry 6 }

gs2310pMSTI4PortStateEdge OBJECT-TYPE
   SYNTAX      DisplayString
   MAX-ACCESS  read-only
   STATUS      current
   DESCRIPTION
       "The current STP port Edge Flag."
   ::= { gs2310pMSTI4PortStateEntry 7 }

gs2310pMSTI4PortStatePoint2Point OBJECT-TYPE
   SYNTAX      DisplayString
   MAX-ACCESS  read-only
   STATUS      current
   DESCRIPTION
       "The current STP port point-to-point flag."
   ::= { gs2310pMSTI4PortStateEntry 8 }

gs2310pMSTI4PortStateUptime OBJECT-TYPE
   SYNTAX      DisplayString
   MAX-ACCESS  read-only
   STATUS      current
   DESCRIPTION
       "The time since the bridge port was last initialized."
   ::= { gs2310pMSTI4PortStateEntry 9 }

gs2310pMSTI5BridgeSTP                                                        OBJECT IDENTIFIER ::= { gs2310pSTPBridgeStatus 6 }

gs2310pMSTI5BridgeSTPStatus                                                  OBJECT IDENTIFIER ::= { gs2310pMSTI5BridgeSTP 1 }

gs2310pMSTI5BridgeInstance OBJECT-TYPE
   SYNTAX       DisplayString
   MAX-ACCESS   read-only
   STATUS       current
   DESCRIPTION
       "The Bridge instance - CIST, MST1, ..."
   ::= { gs2310pMSTI5BridgeSTPStatus 1 }

gs2310pMSTI5BridgeID OBJECT-TYPE
   SYNTAX       DisplayString
   MAX-ACCESS   read-only
   STATUS       current
   DESCRIPTION
       "The Bridge ID of this Bridge instance."
   ::= { gs2310pMSTI5BridgeSTPStatus 2 }

gs2310pMSTI5RootID OBJECT-TYPE
   SYNTAX       DisplayString
   MAX-ACCESS   read-only
   STATUS       current
   DESCRIPTION
       "The Bridge ID of the currently elected root bridge."
   ::= { gs2310pMSTI5BridgeSTPStatus 3 }

gs2310pMSTI5RootPort OBJECT-TYPE
   SYNTAX       DisplayString
   MAX-ACCESS   read-only
   STATUS       current
   DESCRIPTION
       "The switch port currently assigned the root port role."
   ::= { gs2310pMSTI5BridgeSTPStatus 4 }

gs2310pMSTI5RootCost OBJECT-TYPE
   SYNTAX       Integer32(0..200000000)
   MAX-ACCESS   read-only
   STATUS       current
   DESCRIPTION
       "Root Path Cost."
   ::= { gs2310pMSTI5BridgeSTPStatus 5 }

gs2310pMSTI5TopologyFlag OBJECT-TYPE
   SYNTAX       DisplayString
   MAX-ACCESS   read-only
   STATUS       current
   DESCRIPTION
       "The current state of the Topology Change Flag of this Bridge instance."
   ::= { gs2310pMSTI5BridgeSTPStatus 8 }

gs2310pMSTI5TopologyChangeCount OBJECT-TYPE
   SYNTAX       Counter32
   MAX-ACCESS   read-only
   STATUS       current
   DESCRIPTION
       "The number of times where the topology change flag has been set."
   ::= { gs2310pMSTI5BridgeSTPStatus 9 }

gs2310pMSTI5TopologyChangeLast OBJECT-TYPE
   SYNTAX       DisplayString
   MAX-ACCESS   read-only
   STATUS       current
   DESCRIPTION
       "The time passed since the Topology Flag was last set."
   ::= { gs2310pMSTI5BridgeSTPStatus 10 }

gs2310pMSTI5PortStateTable OBJECT-TYPE
   SYNTAX      SEQUENCE OF Gs2310pMSTI5PortStateEntry
   MAX-ACCESS  not-accessible
   STATUS      current
   DESCRIPTION
       " Show MSTI5 Ports and Aggregations State Configurations. "
   ::= { gs2310pMSTI5BridgeSTP 2 }

gs2310pMSTI5PortStateEntry OBJECT-TYPE
   SYNTAX      Gs2310pMSTI5PortStateEntry
   MAX-ACCESS  not-accessible
   STATUS      current
   DESCRIPTION
       ""
   INDEX    { gs2310pMSTI5PortStateIndex  }
   ::= { gs2310pMSTI5PortStateTable 1 }

Gs2310pMSTI5PortStateEntry ::= SEQUENCE {
   gs2310pMSTI5PortStateIndex        Integer32,
   gs2310pMSTI5PortStatePort         DisplayString,
   gs2310pMSTI5PortStatePortID       DisplayString,
   gs2310pMSTI5PortStateRole         DisplayString,
   gs2310pMSTI5PortStateState        DisplayString,
   gs2310pMSTI5PortStatePathCost     Integer32,
   gs2310pMSTI5PortStateEdge         DisplayString,
   gs2310pMSTI5PortStatePoint2Point  DisplayString,
   gs2310pMSTI5PortStateUptime       DisplayString
}

gs2310pMSTI5PortStateIndex OBJECT-TYPE
   SYNTAX      Integer32(1..4095)
   MAX-ACCESS  not-accessible
   STATUS      current
   DESCRIPTION
       "table index."
   ::= { gs2310pMSTI5PortStateEntry 1 }

gs2310pMSTI5PortStatePort OBJECT-TYPE
   SYNTAX      DisplayString
   MAX-ACCESS  read-only
   STATUS      current
   DESCRIPTION
       "The switch port number of the logical STP port."
   ::= { gs2310pMSTI5PortStateEntry 2 }

gs2310pMSTI5PortStatePortID OBJECT-TYPE
   SYNTAX      DisplayString
   MAX-ACCESS  read-only
   STATUS      current
   DESCRIPTION
       "The port id as used by the STP protocol.
        This is the priority part and the logical port index of the bridge port."
   ::= { gs2310pMSTI5PortStateEntry 3 }

gs2310pMSTI5PortStateRole OBJECT-TYPE
   SYNTAX      DisplayString
   MAX-ACCESS  read-only
   STATUS      current
   DESCRIPTION
       "The current STP port role."
   ::= { gs2310pMSTI5PortStateEntry 4 }

gs2310pMSTI5PortStateState OBJECT-TYPE
   SYNTAX      DisplayString
   MAX-ACCESS  read-only
   STATUS      current
   DESCRIPTION
       "The current STP port state."
   ::= { gs2310pMSTI5PortStateEntry 5 }

gs2310pMSTI5PortStatePathCost OBJECT-TYPE
   SYNTAX      Integer32(0..200000000)
   MAX-ACCESS  read-only
   STATUS      current
   DESCRIPTION
       "The current STP port path cost."
   ::= { gs2310pMSTI5PortStateEntry 6 }

gs2310pMSTI5PortStateEdge OBJECT-TYPE
   SYNTAX      DisplayString
   MAX-ACCESS  read-only
   STATUS      current
   DESCRIPTION
       "The current STP port Edge Flag."
   ::= { gs2310pMSTI5PortStateEntry 7 }

gs2310pMSTI5PortStatePoint2Point OBJECT-TYPE
   SYNTAX      DisplayString
   MAX-ACCESS  read-only
   STATUS      current
   DESCRIPTION
       "The current STP port point-to-point flag."
   ::= { gs2310pMSTI5PortStateEntry 8 }

gs2310pMSTI5PortStateUptime OBJECT-TYPE
   SYNTAX      DisplayString
   MAX-ACCESS  read-only
   STATUS      current
   DESCRIPTION
       "The time since the bridge port was last initialized."
   ::= { gs2310pMSTI5PortStateEntry 9 }

gs2310pMSTI6BridgeSTP                                                        OBJECT IDENTIFIER ::= { gs2310pSTPBridgeStatus 7 }

gs2310pMSTI6BridgeSTPStatus                                                  OBJECT IDENTIFIER ::= { gs2310pMSTI6BridgeSTP 1 }

gs2310pMSTI6BridgeInstance OBJECT-TYPE
   SYNTAX       DisplayString
   MAX-ACCESS   read-only
   STATUS       current
   DESCRIPTION
       "The Bridge instance - CIST, MST1, ..."
   ::= { gs2310pMSTI6BridgeSTPStatus 1 }

gs2310pMSTI6BridgeID OBJECT-TYPE
   SYNTAX       DisplayString
   MAX-ACCESS   read-only
   STATUS       current
   DESCRIPTION
       "The Bridge ID of this Bridge instance."
   ::= { gs2310pMSTI6BridgeSTPStatus 2 }

gs2310pMSTI6RootID OBJECT-TYPE
   SYNTAX       DisplayString
   MAX-ACCESS   read-only
   STATUS       current
   DESCRIPTION
       "The Bridge ID of the currently elected root bridge."
   ::= { gs2310pMSTI6BridgeSTPStatus 3 }

gs2310pMSTI6RootPort OBJECT-TYPE
   SYNTAX       DisplayString
   MAX-ACCESS   read-only
   STATUS       current
   DESCRIPTION
       "The switch port currently assigned the root port role."
   ::= { gs2310pMSTI6BridgeSTPStatus 4 }

gs2310pMSTI6RootCost OBJECT-TYPE
   SYNTAX       Integer32(0..200000000)
   MAX-ACCESS   read-only
   STATUS       current
   DESCRIPTION
       "Root Path Cost."
   ::= { gs2310pMSTI6BridgeSTPStatus 5 }

gs2310pMSTI6TopologyFlag OBJECT-TYPE
   SYNTAX       DisplayString
   MAX-ACCESS   read-only
   STATUS       current
   DESCRIPTION
       "The current state of the Topology Change Flag of this Bridge instance."
   ::= { gs2310pMSTI6BridgeSTPStatus 8 }

gs2310pMSTI6TopologyChangeCount OBJECT-TYPE
   SYNTAX       Counter32
   MAX-ACCESS   read-only
   STATUS       current
   DESCRIPTION
       "The number of times where the topology change flag has been set."
   ::= { gs2310pMSTI6BridgeSTPStatus 9 }

gs2310pMSTI6TopologyChangeLast OBJECT-TYPE
   SYNTAX       DisplayString
   MAX-ACCESS   read-only
   STATUS       current
   DESCRIPTION
       "The time passed since the Topology Flag was last set."
   ::= { gs2310pMSTI6BridgeSTPStatus 10 }

gs2310pMSTI6PortStateTable OBJECT-TYPE
   SYNTAX      SEQUENCE OF Gs2310pMSTI6PortStateEntry
   MAX-ACCESS  not-accessible
   STATUS      current
   DESCRIPTION
       " Show MSTI6 Ports and Aggregations State Configurations. "
   ::= { gs2310pMSTI6BridgeSTP 2 }

gs2310pMSTI6PortStateEntry OBJECT-TYPE
   SYNTAX      Gs2310pMSTI6PortStateEntry
   MAX-ACCESS  not-accessible
   STATUS      current
   DESCRIPTION
       ""
   INDEX    { gs2310pMSTI6PortStateIndex  }
   ::= { gs2310pMSTI6PortStateTable 1 }

Gs2310pMSTI6PortStateEntry ::= SEQUENCE {
   gs2310pMSTI6PortStateIndex        Integer32,
   gs2310pMSTI6PortStatePort         DisplayString,
   gs2310pMSTI6PortStatePortID       DisplayString,
   gs2310pMSTI6PortStateRole         DisplayString,
   gs2310pMSTI6PortStateState        DisplayString,
   gs2310pMSTI6PortStatePathCost     Integer32,
   gs2310pMSTI6PortStateEdge         DisplayString,
   gs2310pMSTI6PortStatePoint2Point  DisplayString,
   gs2310pMSTI6PortStateUptime       DisplayString
}

gs2310pMSTI6PortStateIndex OBJECT-TYPE
   SYNTAX      Integer32(1..4095)
   MAX-ACCESS  not-accessible
   STATUS      current
   DESCRIPTION
       "table index."
   ::= { gs2310pMSTI6PortStateEntry 1 }

gs2310pMSTI6PortStatePort OBJECT-TYPE
   SYNTAX      DisplayString
   MAX-ACCESS  read-only
   STATUS      current
   DESCRIPTION
       "The switch port number of the logical STP port."
   ::= { gs2310pMSTI6PortStateEntry 2 }

gs2310pMSTI6PortStatePortID OBJECT-TYPE
   SYNTAX      DisplayString
   MAX-ACCESS  read-only
   STATUS      current
   DESCRIPTION
       "The port id as used by the STP protocol.
        This is the priority part and the logical port index of the bridge port."
   ::= { gs2310pMSTI6PortStateEntry 3 }

gs2310pMSTI6PortStateRole OBJECT-TYPE
   SYNTAX      DisplayString
   MAX-ACCESS  read-only
   STATUS      current
   DESCRIPTION
       "The current STP port role."
   ::= { gs2310pMSTI6PortStateEntry 4 }

gs2310pMSTI6PortStateState OBJECT-TYPE
   SYNTAX      DisplayString
   MAX-ACCESS  read-only
   STATUS      current
   DESCRIPTION
       "The current STP port state."
   ::= { gs2310pMSTI6PortStateEntry 5 }

gs2310pMSTI6PortStatePathCost OBJECT-TYPE
   SYNTAX      Integer32(0..200000000)
   MAX-ACCESS  read-only
   STATUS      current
   DESCRIPTION
       "The current STP port path cost."
   ::= { gs2310pMSTI6PortStateEntry 6 }

gs2310pMSTI6PortStateEdge OBJECT-TYPE
   SYNTAX      DisplayString
   MAX-ACCESS  read-only
   STATUS      current
   DESCRIPTION
       "The current STP port Edge Flag."
   ::= { gs2310pMSTI6PortStateEntry 7 }

gs2310pMSTI6PortStatePoint2Point OBJECT-TYPE
   SYNTAX      DisplayString
   MAX-ACCESS  read-only
   STATUS      current
   DESCRIPTION
       "The current STP port point-to-point flag."
   ::= { gs2310pMSTI6PortStateEntry 8 }

gs2310pMSTI6PortStateUptime OBJECT-TYPE
   SYNTAX      DisplayString
   MAX-ACCESS  read-only
   STATUS      current
   DESCRIPTION
       "The time since the bridge port was last initialized."
   ::= { gs2310pMSTI6PortStateEntry 9 }

gs2310pMSTI7BridgeSTP                                                        OBJECT IDENTIFIER ::= { gs2310pSTPBridgeStatus 8 }

gs2310pMSTI7BridgeSTPStatus                                                  OBJECT IDENTIFIER ::= { gs2310pMSTI7BridgeSTP 1 }

gs2310pMSTI7BridgeInstance OBJECT-TYPE
   SYNTAX       DisplayString
   MAX-ACCESS   read-only
   STATUS       current
   DESCRIPTION
       "The Bridge instance - CIST, MST1, ..."
   ::= { gs2310pMSTI7BridgeSTPStatus 1 }

gs2310pMSTI7BridgeID OBJECT-TYPE
   SYNTAX       DisplayString
   MAX-ACCESS   read-only
   STATUS       current
   DESCRIPTION
       "The Bridge ID of this Bridge instance."
   ::= { gs2310pMSTI7BridgeSTPStatus 2 }

gs2310pMSTI7RootID OBJECT-TYPE
   SYNTAX       DisplayString
   MAX-ACCESS   read-only
   STATUS       current
   DESCRIPTION
       "The Bridge ID of the currently elected root bridge."
   ::= { gs2310pMSTI7BridgeSTPStatus 3 }

gs2310pMSTI7RootPort OBJECT-TYPE
   SYNTAX       DisplayString
   MAX-ACCESS   read-only
   STATUS       current
   DESCRIPTION
       "The switch port currently assigned the root port role."
   ::= { gs2310pMSTI7BridgeSTPStatus 4 }

gs2310pMSTI7RootCost OBJECT-TYPE
   SYNTAX       Integer32(0..200000000)
   MAX-ACCESS   read-only
   STATUS       current
   DESCRIPTION
       "Root Path Cost."
   ::= { gs2310pMSTI7BridgeSTPStatus 5 }

gs2310pMSTI7TopologyFlag OBJECT-TYPE
   SYNTAX       DisplayString
   MAX-ACCESS   read-only
   STATUS       current
   DESCRIPTION
       "The current state of the Topology Change Flag of this Bridge instance."
   ::= { gs2310pMSTI7BridgeSTPStatus 8 }

gs2310pMSTI7TopologyChangeCount OBJECT-TYPE
   SYNTAX       Counter32
   MAX-ACCESS   read-only
   STATUS       current
   DESCRIPTION
       "The number of times where the topology change flag has been set."
   ::= { gs2310pMSTI7BridgeSTPStatus 9 }

gs2310pMSTI7TopologyChangeLast OBJECT-TYPE
   SYNTAX       DisplayString
   MAX-ACCESS   read-only
   STATUS       current
   DESCRIPTION
       "The time passed since the Topology Flag was last set."
   ::= { gs2310pMSTI7BridgeSTPStatus 10 }

gs2310pMSTI7PortStateTable OBJECT-TYPE
   SYNTAX      SEQUENCE OF Gs2310pMSTI7PortStateEntry
   MAX-ACCESS  not-accessible
   STATUS      current
   DESCRIPTION
       " Show MSTI7 Ports and Aggregations State Configurations. "
   ::= { gs2310pMSTI7BridgeSTP 2 }

gs2310pMSTI7PortStateEntry OBJECT-TYPE
   SYNTAX      Gs2310pMSTI7PortStateEntry
   MAX-ACCESS  not-accessible
   STATUS      current
   DESCRIPTION
       ""
   INDEX    { gs2310pMSTI7PortStateIndex  }
   ::= { gs2310pMSTI7PortStateTable 1 }

Gs2310pMSTI7PortStateEntry ::= SEQUENCE {
   gs2310pMSTI7PortStateIndex        Integer32,
   gs2310pMSTI7PortStatePort         DisplayString,
   gs2310pMSTI7PortStatePortID       DisplayString,
   gs2310pMSTI7PortStateRole         DisplayString,
   gs2310pMSTI7PortStateState        DisplayString,
   gs2310pMSTI7PortStatePathCost     Integer32,
   gs2310pMSTI7PortStateEdge         DisplayString,
   gs2310pMSTI7PortStatePoint2Point  DisplayString,
   gs2310pMSTI7PortStateUptime       DisplayString
}

gs2310pMSTI7PortStateIndex OBJECT-TYPE
   SYNTAX      Integer32(1..4095)
   MAX-ACCESS  not-accessible
   STATUS      current
   DESCRIPTION
       "table index."
   ::= { gs2310pMSTI7PortStateEntry 1 }

gs2310pMSTI7PortStatePort OBJECT-TYPE
   SYNTAX      DisplayString
   MAX-ACCESS  read-only
   STATUS      current
   DESCRIPTION
       "The switch port number of the logical STP port."
   ::= { gs2310pMSTI7PortStateEntry 2 }

gs2310pMSTI7PortStatePortID OBJECT-TYPE
   SYNTAX      DisplayString
   MAX-ACCESS  read-only
   STATUS      current
   DESCRIPTION
       "The port id as used by the STP protocol.
        This is the priority part and the logical port index of the bridge port."
   ::= { gs2310pMSTI7PortStateEntry 3 }

gs2310pMSTI7PortStateRole OBJECT-TYPE
   SYNTAX      DisplayString
   MAX-ACCESS  read-only
   STATUS      current
   DESCRIPTION
       "The current STP port role."
   ::= { gs2310pMSTI7PortStateEntry 4 }

gs2310pMSTI7PortStateState OBJECT-TYPE
   SYNTAX      DisplayString
   MAX-ACCESS  read-only
   STATUS      current
   DESCRIPTION
       "The current STP port state."
   ::= { gs2310pMSTI7PortStateEntry 5 }

gs2310pMSTI7PortStatePathCost OBJECT-TYPE
   SYNTAX      Integer32(0..200000000)
   MAX-ACCESS  read-only
   STATUS      current
   DESCRIPTION
       "The current STP port path cost."
   ::= { gs2310pMSTI7PortStateEntry 6 }

gs2310pMSTI7PortStateEdge OBJECT-TYPE
   SYNTAX      DisplayString
   MAX-ACCESS  read-only
   STATUS      current
   DESCRIPTION
       "The current STP port Edge Flag."
   ::= { gs2310pMSTI7PortStateEntry 7 }

gs2310pMSTI7PortStatePoint2Point OBJECT-TYPE
   SYNTAX      DisplayString
   MAX-ACCESS  read-only
   STATUS      current
   DESCRIPTION
       "The current STP port point-to-point flag."
   ::= { gs2310pMSTI7PortStateEntry 8 }

gs2310pMSTI7PortStateUptime OBJECT-TYPE
   SYNTAX      DisplayString
   MAX-ACCESS  read-only
   STATUS      current
   DESCRIPTION
       "The time since the bridge port was last initialized."
   ::= { gs2310pMSTI7PortStateEntry 9 }


gs2310pSTPPortStatusTable OBJECT-TYPE
   SYNTAX      SEQUENCE OF Gs2310pSTPPortStatusEntry
   MAX-ACCESS  not-accessible
   STATUS      current
   DESCRIPTION
       " Show STP Port Status."
   ::= { gs2310pSTP 9 }

gs2310pSTPPortStatusEntry OBJECT-TYPE
   SYNTAX      Gs2310pSTPPortStatusEntry
   MAX-ACCESS  not-accessible
   STATUS      current
   DESCRIPTION
       ""
   INDEX    { gs2310pSTPPortStatusPort  }
   ::= { gs2310pSTPPortStatusTable 1 }

Gs2310pSTPPortStatusEntry ::= SEQUENCE {
   gs2310pSTPPortStatusPort         Integer32,
   gs2310pSTPPortStatusCISTRole     DisplayString,
   gs2310pSTPPortStatusCISTState    DisplayString,
   gs2310pSTPPortStatusUptime       DisplayString
}

gs2310pSTPPortStatusPort OBJECT-TYPE
   SYNTAX      Integer32(1..4095)
   MAX-ACCESS  not-accessible
   STATUS      current
   DESCRIPTION
       " port, range : 1 - port number. "
   ::= { gs2310pSTPPortStatusEntry 1 }

gs2310pSTPPortStatusCISTRole OBJECT-TYPE
   SYNTAX      DisplayString
   MAX-ACCESS  read-only
   STATUS      current
   DESCRIPTION
       " The current STP port role of the CIST port. "
   ::= { gs2310pSTPPortStatusEntry 2 }

gs2310pSTPPortStatusCISTState OBJECT-TYPE
   SYNTAX      DisplayString
   MAX-ACCESS  read-only
   STATUS      current
   DESCRIPTION
       " The current STP port state of the CIST port. "
   ::= { gs2310pSTPPortStatusEntry 3 }

gs2310pSTPPortStatusUptime OBJECT-TYPE
   SYNTAX      DisplayString
   MAX-ACCESS  read-only
   STATUS      current
   DESCRIPTION
       " The time since the bridge port was last initialized. "
   ::= { gs2310pSTPPortStatusEntry 4 }

gs2310pSTPPortStatisticsTable OBJECT-TYPE
   SYNTAX      SEQUENCE OF Gs2310pSTPPortStatisticsEntry
   MAX-ACCESS  not-accessible
   STATUS      current
   DESCRIPTION
       " Show STP Port Statistics."
   ::= { gs2310pSTP 10 }

gs2310pSTPPortStatisticsEntry OBJECT-TYPE
   SYNTAX      Gs2310pSTPPortStatisticsEntry
   MAX-ACCESS  not-accessible
   STATUS      current
   DESCRIPTION
       ""
   INDEX    { gs2310pSTPStatisticsIndex  }
   ::= { gs2310pSTPPortStatisticsTable 1 }

Gs2310pSTPPortStatisticsEntry ::= SEQUENCE {
   gs2310pSTPStatisticsIndex            Integer32,
   gs2310pSTPStatisticsPort             DisplayString,
   gs2310pSTPStatisticsTxMSTP           Counter32,
   gs2310pSTPStatisticsTxRSTP           Counter32,
   gs2310pSTPStatisticsTxSTP            Counter32,
   gs2310pSTPStatisticsTxTCN            Counter32,
   gs2310pSTPStatisticsRxMSTP           Counter32,
   gs2310pSTPStatisticsRxRSTP           Counter32,
   gs2310pSTPStatisticsRxSTP            Counter32,
   gs2310pSTPStatisticsRxTCN            Counter32,
   gs2310pSTPStatisticsDiscardedUnknown Counter32,
   gs2310pSTPStatisticsDiscardedIllegal Counter32
}

gs2310pSTPStatisticsIndex OBJECT-TYPE
   SYNTAX      Integer32(1..4095)
   MAX-ACCESS  not-accessible
   STATUS      current
   DESCRIPTION
       "table index."
   ::= { gs2310pSTPPortStatisticsEntry 1 }

gs2310pSTPStatisticsPort OBJECT-TYPE
   SYNTAX      DisplayString
   MAX-ACCESS  not-accessible
   STATUS      current
   DESCRIPTION
       " port, range : 1 - port number. "
   ::= { gs2310pSTPPortStatisticsEntry 2 }

gs2310pSTPStatisticsTxMSTP OBJECT-TYPE
   SYNTAX      Counter32
   MAX-ACCESS  read-only
   STATUS      current
   DESCRIPTION
       " The number of MSTP Configuration BPDU's received/transmitted on the port."
   ::= { gs2310pSTPPortStatisticsEntry 3 }

gs2310pSTPStatisticsTxRSTP OBJECT-TYPE
   SYNTAX      Counter32
   MAX-ACCESS  read-only
   STATUS      current
   DESCRIPTION
       " The number of RSTP Configuration BPDU's received/transmitted on the port. "
   ::= { gs2310pSTPPortStatisticsEntry 4 }

gs2310pSTPStatisticsTxSTP OBJECT-TYPE
   SYNTAX      Counter32
   MAX-ACCESS  read-only
   STATUS      current
   DESCRIPTION
       " The number of legacy STP Configuration BPDU's received/transmitted on the port. "
   ::= { gs2310pSTPPortStatisticsEntry 5 }

gs2310pSTPStatisticsTxTCN OBJECT-TYPE
   SYNTAX      Counter32
   MAX-ACCESS  read-only
   STATUS      current
   DESCRIPTION
       " The number of Topology Change Notification BPDU's received/transmitted on the port. "
   ::= { gs2310pSTPPortStatisticsEntry 6 }

gs2310pSTPStatisticsRxMSTP OBJECT-TYPE
   SYNTAX      Counter32
   MAX-ACCESS  read-only
   STATUS      current
   DESCRIPTION
       " The number of MSTP Configuration BPDU's received/transmitted on the port."
   ::= { gs2310pSTPPortStatisticsEntry 7 }

gs2310pSTPStatisticsRxRSTP OBJECT-TYPE
   SYNTAX      Counter32
   MAX-ACCESS  read-only
   STATUS      current
   DESCRIPTION
       " The number of RSTP Configuration BPDU's received/transmitted on the port. "
   ::= { gs2310pSTPPortStatisticsEntry 8 }

gs2310pSTPStatisticsRxSTP OBJECT-TYPE
   SYNTAX      Counter32
   MAX-ACCESS  read-only
   STATUS      current
   DESCRIPTION
       " The number of legacy STP Configuration BPDU's received/transmitted on the port. "
   ::= { gs2310pSTPPortStatisticsEntry 9 }

gs2310pSTPStatisticsRxTCN OBJECT-TYPE
   SYNTAX      Counter32
   MAX-ACCESS  read-only
   STATUS      current
   DESCRIPTION
       " The number of Topology Change Notification BPDU's received/transmitted on the port. "
   ::= { gs2310pSTPPortStatisticsEntry 10 }

gs2310pSTPStatisticsDiscardedUnknown OBJECT-TYPE
   SYNTAX      Counter32
   MAX-ACCESS  read-only
   STATUS      current
   DESCRIPTION
       " The number of unknown Spanning Tree BPDU's received and discarded on the port. "
   ::= { gs2310pSTPPortStatisticsEntry 11 }

gs2310pSTPStatisticsDiscardedIllegal OBJECT-TYPE
   SYNTAX      Counter32
   MAX-ACCESS  read-only
   STATUS      current
   DESCRIPTION
       " The number of illegal Spanning Tree BPDU's received and discarded on the port. "
   ::= { gs2310pSTPPortStatisticsEntry 12 }


gs2310pFilteringDataBase                                                  OBJECT IDENTIFIER ::= { gs2310pConfiguration 21 }

gs2310pFilteringDataBaseConfig                                            OBJECT IDENTIFIER ::= { gs2310pFilteringDataBase 1 }

gs2310pFilteringDataBaseAgingTime OBJECT-TYPE
   SYNTAX      Integer32(0..1000000)
   MAX-ACCESS  read-write
   STATUS      current
   DESCRIPTION
       "Configure aging time by entering a value here in seconds.
        default: 300,
        range: 10-1000000.
        Disable automatic aging : 0."
   ::= { gs2310pFilteringDataBaseConfig 1 }

gs2310pFilteringDataBaseConfigTable OBJECT-TYPE
   SYNTAX      SEQUENCE OF GS2310PFilteringDataBaseConfigEntry
   MAX-ACCESS  not-accessible
   STATUS      current
   DESCRIPTION
       " "
   ::= { gs2310pFilteringDataBaseConfig 2 }

gs2310pFilteringDataBaseConfigEntry OBJECT-TYPE
   SYNTAX      GS2310PFilteringDataBaseConfigEntry
   MAX-ACCESS  not-accessible
   STATUS      current
   DESCRIPTION
       ""
   INDEX    { gs2310pFilteringDataBaseConfigPort  }
   ::= { gs2310pFilteringDataBaseConfigTable 1 }

GS2310PFilteringDataBaseConfigEntry ::= SEQUENCE {
   gs2310pFilteringDataBaseConfigPort        Integer32,
   gs2310pFilteringDataBaseConfigLearning    INTEGER
}

gs2310pFilteringDataBaseConfigPort OBJECT-TYPE
   SYNTAX      Integer32(1..4095)
   MAX-ACCESS  not-accessible
   STATUS      current
   DESCRIPTION
       " "
   ::= { gs2310pFilteringDataBaseConfigEntry 1 }

gs2310pFilteringDataBaseConfigLearning OBJECT-TYPE
   SYNTAX      INTEGER { auto(0), disable(1), secure(2) }
   MAX-ACCESS  read-write
   STATUS      current
   DESCRIPTION
       "Configure learning mode of switch ports.
        default: 0,
        0: auto,
        1: disable,
        2: secure. "
   ::= { gs2310pFilteringDataBaseConfigEntry 2 }


gs2310pFilteringDataBaseStaticMAC                                OBJECT IDENTIFIER ::= { gs2310pFilteringDataBaseConfig 3 }

gs2310pFilteringDataBaseStaticMACCreate OBJECT-TYPE
   SYNTAX       INTEGER { none(0), create(1) }
   MAX-ACCESS   read-write
   STATUS       current
   DESCRIPTION
       "default: 0
        0 : None  (read only)
        1 : Create Static MAC Table"
   ::= { gs2310pFilteringDataBaseStaticMAC 1 }

gs2310pFilteringDataBaseStaticMACTable OBJECT-TYPE
   SYNTAX      SEQUENCE OF GS2310PFilteringDataBaseStaticMACEntry
   MAX-ACCESS  not-accessible
   STATUS      current
   DESCRIPTION
       " "
   ::= { gs2310pFilteringDataBaseStaticMAC 2 }

gs2310pFilteringDataBaseStaticMACEntry OBJECT-TYPE
   SYNTAX      GS2310PFilteringDataBaseStaticMACEntry
   MAX-ACCESS  not-accessible
   STATUS      current
   DESCRIPTION
       ""
   INDEX    { gs2310pFilteringDataBaseStaticMACIndex  }
   ::= { gs2310pFilteringDataBaseStaticMACTable 1 }

GS2310PFilteringDataBaseStaticMACEntry ::= SEQUENCE {
   gs2310pFilteringDataBaseStaticMACIndex	    Integer32,
   gs2310pFilteringDataBaseStaticMACVLANId	    Integer32,
   gs2310pFilteringDataBaseStaticMACAddress      MacAddress,
   gs2310pFilteringDataBaseStaticMACPortMembers  DisplayString,
   gs2310pFilteringDataBaseStaticMACRowStatus	INTEGER
}

gs2310pFilteringDataBaseStaticMACIndex OBJECT-TYPE
   SYNTAX      Integer32(1..4095)
   MAX-ACCESS  not-accessible
   STATUS      current
   DESCRIPTION
       " "
   ::= { gs2310pFilteringDataBaseStaticMACEntry 1 }

gs2310pFilteringDataBaseStaticMACVLANId OBJECT-TYPE
   SYNTAX      Integer32(1..4094)
   MAX-ACCESS  read-write
   STATUS      current
   DESCRIPTION
       " VLAN ID, range: 1 - 4094. "
   ::= { gs2310pFilteringDataBaseStaticMACEntry 2 }

gs2310pFilteringDataBaseStaticMACAddress OBJECT-TYPE
   SYNTAX      MacAddress
   MAX-ACCESS  read-write
   STATUS      current
   DESCRIPTION
       " MAC address, format 0a 1b 2c 3d 4e 5f "
   ::= { gs2310pFilteringDataBaseStaticMACEntry 3 }

gs2310pFilteringDataBaseStaticMACPortMembers OBJECT-TYPE
   SYNTAX      DisplayString
   MAX-ACCESS  read-write
   STATUS      current
   DESCRIPTION
       "To include the ports in a Static MAC Table"
   ::= { gs2310pFilteringDataBaseStaticMACEntry 4 }

gs2310pFilteringDataBaseStaticMACRowStatus OBJECT-TYPE
   SYNTAX      INTEGER { active(1), notInservice(2), destroy(4), undo(5) }
   MAX-ACCESS  read-write
   STATUS      current
   DESCRIPTION
       "1: active
        2: notInservice
        4: destroy
        5: undo"
   ::= { gs2310pFilteringDataBaseStaticMACEntry 5 }


gs2310pFilteringDataBaseDynamicMACTable OBJECT-TYPE
   SYNTAX      SEQUENCE OF GS2310PFilteringDataBaseDynamicMACEntry
   MAX-ACCESS  not-accessible
   STATUS      current
   DESCRIPTION
       " "
   ::= { gs2310pFilteringDataBaseConfig 4 }

gs2310pFilteringDataBaseDynamicMACEntry OBJECT-TYPE
   SYNTAX      GS2310PFilteringDataBaseDynamicMACEntry
   MAX-ACCESS  not-accessible
   STATUS      current
   DESCRIPTION
       ""
   INDEX    { gs2310pFilteringDataBaseDynamicMACIndex  }
   ::= { gs2310pFilteringDataBaseDynamicMACTable 1 }

GS2310PFilteringDataBaseDynamicMACEntry ::= SEQUENCE {
   gs2310pFilteringDataBaseDynamicMACIndex	    Integer32,
   gs2310pFilteringDataBaseDynamicMACType	    INTEGER,
   gs2310pFilteringDataBaseDynamicMACVLAN	    Integer32,
   gs2310pFilteringDataBaseDynamicMACAddress     MacAddress,
   gs2310pFilteringDataBaseDynamicPortMembers    DisplayString
}

gs2310pFilteringDataBaseDynamicMACIndex OBJECT-TYPE
   SYNTAX      Integer32(1..4095)
   MAX-ACCESS  not-accessible
   STATUS      current
   DESCRIPTION
       " "
   ::= { gs2310pFilteringDataBaseDynamicMACEntry 1 }

gs2310pFilteringDataBaseDynamicMACType OBJECT-TYPE
   SYNTAX      INTEGER { dynamic(0), static(1) }
   MAX-ACCESS  read-only
   STATUS      current
   DESCRIPTION
       "Indicates whether the entry is a static or a dynamic entry."
   ::= { gs2310pFilteringDataBaseDynamicMACEntry 2 }

gs2310pFilteringDataBaseDynamicMACVLAN OBJECT-TYPE
   SYNTAX      Integer32(1..4094)
   MAX-ACCESS  read-only
   STATUS      current
   DESCRIPTION
       "The VLAN ID of the entry."
   ::= { gs2310pFilteringDataBaseDynamicMACEntry 3 }

gs2310pFilteringDataBaseDynamicMACAddress OBJECT-TYPE
   SYNTAX      MacAddress
   MAX-ACCESS  read-only
   STATUS      current
   DESCRIPTION
       "The MAC address of the entry."
   ::= { gs2310pFilteringDataBaseDynamicMACEntry 4 }

gs2310pFilteringDataBaseDynamicPortMembers OBJECT-TYPE
   SYNTAX      DisplayString
   MAX-ACCESS  read-only
   STATUS      current
   DESCRIPTION
       "The ports that are members of the entry."
   ::= { gs2310pFilteringDataBaseDynamicMACEntry 5 }


gs2310pSFlowAgent                                                  OBJECT IDENTIFIER ::= { gs2310pConfiguration 22 }

gs2310pSFlowAgentCollector                                            OBJECT IDENTIFIER ::= { gs2310pSFlowAgent 1 }

gs2310pSFlowAgentReceiverMode OBJECT-TYPE
   SYNTAX      INTEGER { disable(0), enable(1) }
   MAX-ACCESS  read-write
   STATUS      current
   DESCRIPTION
       "default: 0
       0: disable
       1: enable "
   ::= { gs2310pSFlowAgentCollector 1 }


gs2310pLMC                                                   OBJECT IDENTIFIER ::= { gs2310pConfiguration 1500 }

gs2310pLMCOperating OBJECT-TYPE
   SYNTAX      INTEGER { disabled(0), enabled(1), try(2) }
   MAX-ACCESS  read-write
   STATUS      current
   DESCRIPTION
       "0: disabled
        1: enabled
        2: try"
   ::= { gs2310pLMC 1 }

gs2310pLMCConfigViaDhcp OBJECT-TYPE
   SYNTAX      INTEGER { disabled(0), enabled(1) }
   MAX-ACCESS  read-write
   STATUS      current
   DESCRIPTION
       "0: disabled
        1: enabled"
   ::= { gs2310pLMC 2 }

gs2310pLMCDomain OBJECT-TYPE
   SYNTAX      DisplayString(SIZE(0..255))
   MAX-ACCESS  read-write
   STATUS      current
   DESCRIPTION
       "0: disabled
        1: enabled"
   ::= { gs2310pLMC 3 }

gs2310pLMCDhcpClientAutoRenew OBJECT-TYPE
   SYNTAX      INTEGER { disabled(0), enabled(1) }
   MAX-ACCESS  read-write
   STATUS      current
   DESCRIPTION
       "0: disabled
        1: enabled"
   ::= { gs2310pLMC 4 }

gs2310pLMCZeroTouchSupport OBJECT-TYPE
   SYNTAX      INTEGER { No(0), Yes(1) }
   MAX-ACCESS  read-only
   STATUS      current
   DESCRIPTION
       "0: No
        1: Yes"
   ::= { gs2310pLMC 50 }

gs2310pLMCPairingTokenPresent OBJECT-TYPE
   SYNTAX      INTEGER { No(0), Yes(1) }
   MAX-ACCESS  read-only
   STATUS      current
   DESCRIPTION
       "0: No
        1: Yes"
   ::= { gs2310pLMC 51 }

gs2310pLMCClientStatus OBJECT-TYPE
   SYNTAX      DisplayString
   MAX-ACCESS  read-only
   STATUS      current
   DESCRIPTION
           ""
   ::= { gs2310pLMC  52 }


gs2310pLMCManagementStatus OBJECT-TYPE
   SYNTAX      INTEGER {Unpaired(0), Paired(1), PairedAndClaimed(14)}
   MAX-ACCESS  read-only
   STATUS      current
   DESCRIPTION
           "0: Unpaired
            1: Paired
            14: PairedAndClaimed"
   ::= { gs2310pLMC  53 }

gs2310pLMCControlStatus OBJECT-TYPE
   SYNTAX      INTEGER {Disabled(2), Operating(4)}
   MAX-ACCESS  read-only
   STATUS      current
   DESCRIPTION
           "2: Disabled
            4: Operating"
   ::= { gs2310pLMC  54 }

gs2310pLMCMonitoringStatus OBJECT-TYPE
   SYNTAX      INTEGER {Disabled(2), Operating(4)}
   MAX-ACCESS  read-only
   STATUS      current
   DESCRIPTION
           "2: Disabled
            4: Operating"
   ::= { gs2310pLMC  55 }

gs2310pLMCConfigurationSource OBJECT-TYPE
   SYNTAX      DisplayString
   MAX-ACCESS  read-only
   STATUS      current
   DESCRIPTION
           ""
   ::= { gs2310pLMC  56 }

gs2310pLMCConfigModified OBJECT-TYPE
   SYNTAX      INTEGER { No(0), Yes(1) }
   MAX-ACCESS  read-only
   STATUS      current
   DESCRIPTION
       "0: No
        1: Yes"
   ::= { gs2310pLMC 57 }

gs2310pLMCDeviceID OBJECT-TYPE
   SYNTAX      DisplayString
   MAX-ACCESS  read-only
   STATUS      current
   DESCRIPTION
           ""
   ::= { gs2310pLMC  58 }

gs2310pLMCRoundTripTime OBJECT-TYPE
   SYNTAX      INTEGER
   MAX-ACCESS  read-only
   STATUS      current
   DESCRIPTION
           ""
   ::= { gs2310pLMC  100 }

----------------------------------------------------------------------------------------------------------------------------
gs2310pSecurity                                              OBJECT IDENTIFIER ::= { lancomGS2310P 3 }

gs2310pIPSourceGuard                                         OBJECT IDENTIFIER ::= { gs2310pSecurity 1 }

gs2310pIPSourceGuardConf                                     OBJECT IDENTIFIER ::= { gs2310pIPSourceGuard 1 }

gs2310pIPSourceGuardMode OBJECT-TYPE
   SYNTAX      INTEGER { disable(0), enable(1) }
   MAX-ACCESS  read-write
   STATUS      current
   DESCRIPTION
       " default:  0
        0: disable
        1: enable"
   ::= { gs2310pIPSourceGuardConf 1 }

gs2310pIPSourceGuardPortConfigTable OBJECT-TYPE
   SYNTAX      SEQUENCE OF Gs2310pIPSourceGuardPortConfigEntry
   MAX-ACCESS  not-accessible
   STATUS      current
   DESCRIPTION
       " "
   ::= { gs2310pIPSourceGuardConf 2 }

gs2310pIPSourceGuardPortConfigEntry OBJECT-TYPE
   SYNTAX      Gs2310pIPSourceGuardPortConfigEntry
   MAX-ACCESS  not-accessible
   STATUS      current
   DESCRIPTION
       ""
   INDEX    { gs2310pIPSourceGuardPortConfigPort  }
   ::= { gs2310pIPSourceGuardPortConfigTable 1 }

Gs2310pIPSourceGuardPortConfigEntry ::= SEQUENCE {
   gs2310pIPSourceGuardPortConfigPort               Integer32,
   gs2310pIPSourceGuardPortConfigMode               INTEGER,
   gs2310pIPSourceGuardPortMaxDynamicClients        Integer32
}

gs2310pIPSourceGuardPortConfigPort OBJECT-TYPE
   SYNTAX      Integer32(1..4095)
   MAX-ACCESS  not-accessible
   STATUS      current
   DESCRIPTION
       " "
   ::= { gs2310pIPSourceGuardPortConfigEntry 1 }

gs2310pIPSourceGuardPortConfigMode OBJECT-TYPE
   SYNTAX      INTEGER { disable(0), enable(1) }
   MAX-ACCESS  read-write
   STATUS      current
   DESCRIPTION
       "default: 0
       0:disable
       1:enable "
   ::= { gs2310pIPSourceGuardPortConfigEntry 2 }

gs2310pIPSourceGuardPortMaxDynamicClients OBJECT-TYPE
   SYNTAX      Integer32(0..2|99)
   MAX-ACCESS  read-write
   STATUS      current
   DESCRIPTION
       "default: 99
       0~2: Max Dynamic clients
       99:Unlimited "
   ::= { gs2310pIPSourceGuardPortConfigEntry 3 }


gs2310pIPSourceGuardStatic                                OBJECT IDENTIFIER ::= { gs2310pIPSourceGuard 2 }

gs2310pIPSourceGuardStaticCreate OBJECT-TYPE
   SYNTAX       INTEGER { none(0), create(1) }
   MAX-ACCESS   read-write
   STATUS       current
   DESCRIPTION
       "default: 0
        0 : None  (read only)
        1 : Create a IP Source Guard"
   ::= { gs2310pIPSourceGuardStatic 1 }

gs2310pIPSourceGuardStaticTable OBJECT-TYPE
   SYNTAX      SEQUENCE OF Gs2310pIPSourceGuardStaticEntry
   MAX-ACCESS  not-accessible
   STATUS      current
   DESCRIPTION
       " "
   ::= { gs2310pIPSourceGuardStatic 2 }

gs2310pIPSourceGuardStaticEntry OBJECT-TYPE
   SYNTAX      Gs2310pIPSourceGuardStaticEntry
   MAX-ACCESS  not-accessible
   STATUS      current
   DESCRIPTION
       ""
   INDEX    { gs2310pIPSourceGuardStaticIndex  }
   ::= { gs2310pIPSourceGuardStaticTable 1 }

Gs2310pIPSourceGuardStaticEntry ::= SEQUENCE {
   gs2310pIPSourceGuardStaticIndex         Integer32,
   gs2310pIPSourceGuardStaticPort          Integer32,
   gs2310pIPSourceGuardStaticVLANId        Integer32,
   gs2310pIPSourceGuardStaticIPAddress     IpAddress,
   gs2310pIPSourceGuardStaticMACAddress    MacAddress,
   gs2310pIPSourceGuardStaticRowStatus     INTEGER
}

gs2310pIPSourceGuardStaticIndex OBJECT-TYPE
   SYNTAX      Integer32(1..28)
   MAX-ACCESS  not-accessible
   STATUS      current
   DESCRIPTION
       " "
   ::= { gs2310pIPSourceGuardStaticEntry 1 }

gs2310pIPSourceGuardStaticPort OBJECT-TYPE
   SYNTAX      Integer32(1..4095)
   MAX-ACCESS  read-write
   STATUS      current
   DESCRIPTION
       " Port, range: 1 - port number. "
   ::= { gs2310pIPSourceGuardStaticEntry 2 }

gs2310pIPSourceGuardStaticVLANId OBJECT-TYPE
   SYNTAX      Integer32(1..4094)
   MAX-ACCESS  read-write
   STATUS      current
   DESCRIPTION
       " VLAN ID, range: 1 - 4094. "
   ::= { gs2310pIPSourceGuardStaticEntry 3 }

gs2310pIPSourceGuardStaticIPAddress OBJECT-TYPE
   SYNTAX      IpAddress
   MAX-ACCESS  read-write
   STATUS      current
   DESCRIPTION
       " IP address allowed for doing IP source guard. "
   ::= { gs2310pIPSourceGuardStaticEntry 4 }

gs2310pIPSourceGuardStaticMACAddress OBJECT-TYPE
   SYNTAX      MacAddress
   MAX-ACCESS  read-write
   STATUS      current
   DESCRIPTION
       " Allowed Source MAC address, format 0a 1b 2c 3d 4e 5f "
   ::= { gs2310pIPSourceGuardStaticEntry 5 }

gs2310pIPSourceGuardStaticRowStatus OBJECT-TYPE
   SYNTAX      INTEGER { active(1), notInservice(2), edit(3), destroy(4), undo(5) }
   MAX-ACCESS  read-write
   STATUS      current
   DESCRIPTION
       "1: active
        2: notInservice
        3: edit
        4: destroy
        5: undo"
   ::= { gs2310pIPSourceGuardStaticEntry 6 }

gs2310pIPSourceGuardDynamicTable OBJECT-TYPE
   SYNTAX      SEQUENCE OF Gs2310pIPSourceGuardDynamicEntry
   MAX-ACCESS  not-accessible
   STATUS      current
   DESCRIPTION
       " "
   ::= { gs2310pIPSourceGuard 3 }

gs2310pIPSourceGuardDynamicEntry OBJECT-TYPE
   SYNTAX      Gs2310pIPSourceGuardDynamicEntry
   MAX-ACCESS  not-accessible
   STATUS      current
   DESCRIPTION
       ""
   INDEX    { gs2310pIPSourceGuardDynamicIndex  }
   ::= { gs2310pIPSourceGuardDynamicTable 1 }

Gs2310pIPSourceGuardDynamicEntry ::= SEQUENCE {
   gs2310pIPSourceGuardDynamicIndex          Integer32,
   gs2310pIPSourceGuardDynamicPort           Integer32,
   gs2310pIPSourceGuardDynamicVLANId         Integer32,
   gs2310pIPSourceGuardDynamicIPAddress      IpAddress,
   gs2310pIPSourceGuardDynamicMACAddress     MacAddress
}

gs2310pIPSourceGuardDynamicIndex OBJECT-TYPE
   SYNTAX      Integer32(1..4095)
   MAX-ACCESS  not-accessible
   STATUS      current
   DESCRIPTION
       " "
   ::= { gs2310pIPSourceGuardDynamicEntry 1 }

gs2310pIPSourceGuardDynamicPort OBJECT-TYPE
   SYNTAX      Integer32(1..10)
   MAX-ACCESS  read-only
   STATUS      current
   DESCRIPTION
       " "
   ::= { gs2310pIPSourceGuardDynamicEntry 2 }

gs2310pIPSourceGuardDynamicVLANId OBJECT-TYPE
   SYNTAX      Integer32(1..4094)
   MAX-ACCESS  read-only
   STATUS      current
   DESCRIPTION
       " "
   ::= { gs2310pIPSourceGuardDynamicEntry 3 }

gs2310pIPSourceGuardDynamicIPAddress OBJECT-TYPE
   SYNTAX      IpAddress
   MAX-ACCESS  read-only
   STATUS      current
   DESCRIPTION
       " "
   ::= { gs2310pIPSourceGuardDynamicEntry 4 }

gs2310pIPSourceGuardDynamicMACAddress OBJECT-TYPE
   SYNTAX      MacAddress
   MAX-ACCESS  read-only
   STATUS      current
   DESCRIPTION
       " "
   ::= { gs2310pIPSourceGuardDynamicEntry 5 }

gs2310pARPInspection                                         OBJECT IDENTIFIER ::= { gs2310pSecurity 2 }

gs2310pARPInspectionConf                                     OBJECT IDENTIFIER ::= { gs2310pARPInspection 1 }

gs2310pARPInspectionConfMode OBJECT-TYPE
   SYNTAX      INTEGER { disable(0), enable(1) }
   MAX-ACCESS  read-write
   STATUS      current
   DESCRIPTION
       "default: 0
        0: disable
        1: enable"
   ::= { gs2310pARPInspectionConf 1 }

gs2310pARPInspectionConfTable OBJECT-TYPE
   SYNTAX      SEQUENCE OF Gs2310pARPInspectionConfEntry
   MAX-ACCESS  not-accessible
   STATUS      current
   DESCRIPTION
       " "
   ::= { gs2310pARPInspectionConf 2 }

gs2310pARPInspectionConfEntry OBJECT-TYPE
   SYNTAX      Gs2310pARPInspectionConfEntry
   MAX-ACCESS  not-accessible
   STATUS      current
   DESCRIPTION
       ""
   INDEX    { gs2310pARPInspectionConfPortIndex  }
   ::= { gs2310pARPInspectionConfTable 1 }

Gs2310pARPInspectionConfEntry ::= SEQUENCE {
   gs2310pARPInspectionConfPortIndex	Integer32,
   gs2310pARPInspectionConfPortMode	INTEGER
}

gs2310pARPInspectionConfPortIndex OBJECT-TYPE
   SYNTAX      Integer32(1..4095)
   MAX-ACCESS  not-accessible
   STATUS      current
   DESCRIPTION
       " "
   ::= { gs2310pARPInspectionConfEntry 1 }

gs2310pARPInspectionConfPortMode OBJECT-TYPE
   SYNTAX      INTEGER { disable(0), enable(1) }
   MAX-ACCESS  read-write
   STATUS      current
   DESCRIPTION
       "default: 0
        0: disable
        1: enable"
   ::= { gs2310pARPInspectionConfEntry 2 }


gs2310pARPInspectionStatic                                OBJECT IDENTIFIER ::= { gs2310pARPInspection 2 }

gs2310pARPInspectionStaticCreate OBJECT-TYPE
   SYNTAX      INTEGER { none(0), create(1) }
   MAX-ACCESS  read-write
   STATUS      current
   DESCRIPTION
       "default: 0
        0: none
        1: create"
   ::= { gs2310pARPInspectionStatic 1 }

gs2310pARPInspectionStaticTable OBJECT-TYPE
   SYNTAX      SEQUENCE OF Gs2310pARPInspectionStaticEntry
   MAX-ACCESS  not-accessible
   STATUS      current
   DESCRIPTION
       " "
   ::= { gs2310pARPInspectionStatic 2 }

gs2310pARPInspectionStaticEntry OBJECT-TYPE
   SYNTAX      Gs2310pARPInspectionStaticEntry
   MAX-ACCESS  not-accessible
   STATUS      current
   DESCRIPTION
       ""
   INDEX    { gs2310pARPInspectionStaticIndex  }
   ::= { gs2310pARPInspectionStaticTable 1 }

Gs2310pARPInspectionStaticEntry ::= SEQUENCE {
   gs2310pARPInspectionStaticIndex       Integer32,
   gs2310pARPInspectionStaticPort        Integer32,
   gs2310pARPInspectionStaticVLANId      Integer32,
   gs2310pARPInspectionStaticIPAddress   IpAddress,
   gs2310pARPInspectionStaticMACAddress  MacAddress,
   gs2310pARPInspectionStaticRowStatus   INTEGER
}

gs2310pARPInspectionStaticIndex OBJECT-TYPE
   SYNTAX      Integer32(1..4095)
   MAX-ACCESS  not-accessible
   STATUS      current
   DESCRIPTION
       ""
   ::= { gs2310pARPInspectionStaticEntry 1 }

gs2310pARPInspectionStaticPort OBJECT-TYPE
   SYNTAX      Integer32(1..4095)
   MAX-ACCESS  read-write
   STATUS      current
   DESCRIPTION
       " Port, range: 1 - port number. "
   ::= { gs2310pARPInspectionStaticEntry 2 }

gs2310pARPInspectionStaticVLANId OBJECT-TYPE
   SYNTAX      Integer32(1..4094)
   MAX-ACCESS  read-write
   STATUS      current
   DESCRIPTION
       " VLAN ID, range: 1 - 4094. "
   ::= { gs2310pARPInspectionStaticEntry 3 }

gs2310pARPInspectionStaticIPAddress OBJECT-TYPE
   SYNTAX      IpAddress
   MAX-ACCESS  read-write
   STATUS      current
   DESCRIPTION
       " IP address allowed for doing ARP request. "
   ::= { gs2310pARPInspectionStaticEntry 4 }

gs2310pARPInspectionStaticMACAddress OBJECT-TYPE
   SYNTAX      MacAddress
   MAX-ACCESS  read-write
   STATUS      current
   DESCRIPTION
       " Allowed Source MAC address in ARP request packets, format 0a 1b 2c 3d 4e 5f "
   ::= { gs2310pARPInspectionStaticEntry 5 }

gs2310pARPInspectionStaticRowStatus OBJECT-TYPE
   SYNTAX     INTEGER { active(1), notInservice(2), edit(3), destroy(4), undo(5) }
   MAX-ACCESS  read-write
   STATUS      current
   DESCRIPTION
       "1: active
        2: notInservice
        3: edit
        4: destroy
        5: undo"
   ::= { gs2310pARPInspectionStaticEntry 6 }

gs2310pARPInspectionDynamicTable OBJECT-TYPE
   SYNTAX      SEQUENCE OF Gs2310pARPInspectionDynamicEntry
   MAX-ACCESS  not-accessible
   STATUS      current
   DESCRIPTION
       " "
   ::= { gs2310pARPInspection 3 }

gs2310pARPInspectionDynamicEntry OBJECT-TYPE
   SYNTAX      Gs2310pARPInspectionDynamicEntry
   MAX-ACCESS  not-accessible
   STATUS      current
   DESCRIPTION
       ""
   INDEX    { gs2310pARPInspectionDynamicIndex  }
   ::= { gs2310pARPInspectionDynamicTable 1 }

Gs2310pARPInspectionDynamicEntry ::= SEQUENCE {
   gs2310pARPInspectionDynamicIndex          Integer32,
   gs2310pARPInspectionDynamicPort           Integer32,
   gs2310pARPInspectionDynamicVLANId         Integer32,
   gs2310pARPInspectionDynamicIPAddress      IpAddress,
   gs2310pARPInspectionDynamicMACAddress     MacAddress
}

gs2310pARPInspectionDynamicIndex OBJECT-TYPE
   SYNTAX      Integer32(1..4095)
   MAX-ACCESS  not-accessible
   STATUS      current
   DESCRIPTION
       " "
   ::= { gs2310pARPInspectionDynamicEntry 1 }

gs2310pARPInspectionDynamicPort OBJECT-TYPE
   SYNTAX      Integer32(1..4095)
   MAX-ACCESS  read-only
   STATUS      current
   DESCRIPTION
       ""
   ::= { gs2310pARPInspectionDynamicEntry 2 }

gs2310pARPInspectionDynamicVLANId OBJECT-TYPE
   SYNTAX      Integer32(1..4094)
   MAX-ACCESS  read-only
   STATUS      current
   DESCRIPTION
       ""
   ::= { gs2310pARPInspectionDynamicEntry 3 }

gs2310pARPInspectionDynamicIPAddress OBJECT-TYPE
   SYNTAX      IpAddress
   MAX-ACCESS  read-only
   STATUS      current
   DESCRIPTION
       ""
   ::= { gs2310pARPInspectionDynamicEntry 4 }

gs2310pARPInspectionDynamicMACAddress OBJECT-TYPE
   SYNTAX      MacAddress
   MAX-ACCESS  read-only
   STATUS      current
   DESCRIPTION
       ""
   ::= { gs2310pARPInspectionDynamicEntry 5 }

gs2310pARPStaticGatewayCtrl	                                OBJECT IDENTIFIER ::= { gs2310pARPInspection 6 }

gs2310pARPStaticGatewayCtrlSystemConf                                      OBJECT IDENTIFIER ::= { gs2310pARPStaticGatewayCtrl 1 }

gs2310pARPStaticGatewayCtrlMode OBJECT-TYPE
   SYNTAX      INTEGER { disable(0), enable(1) }
   MAX-ACCESS  read-write
   STATUS      current
   DESCRIPTION
       "default: 0
       0: disable
       1: enable "
   ::= { gs2310pARPStaticGatewayCtrlSystemConf 1 }

gs2310pARPStaticGatewayCtrlCreate OBJECT-TYPE
   SYNTAX      INTEGER { none(0), create(1) }
   MAX-ACCESS  read-write
   STATUS      current
   DESCRIPTION
       "default: 0
        0: none
        1: create"
   ::= { gs2310pARPStaticGatewayCtrl 2 }

gs2310pARPStaticGatewayCtrlTable OBJECT-TYPE
   SYNTAX      SEQUENCE OF Gs2310pARPStaticGatewayCtrlEntry
   MAX-ACCESS  not-accessible
   STATUS      current
   DESCRIPTION
       " "
   ::= { gs2310pARPStaticGatewayCtrl 3 }

gs2310pARPStaticGatewayCtrlEntry OBJECT-TYPE
   SYNTAX      Gs2310pARPStaticGatewayCtrlEntry
   MAX-ACCESS  not-accessible
   STATUS      current
   DESCRIPTION
       ""
   INDEX    { gs2310pARPStaticGatewayCtrlIndex  }
   ::= { gs2310pARPStaticGatewayCtrlTable 1 }

Gs2310pARPStaticGatewayCtrlEntry ::= SEQUENCE {
   gs2310pARPStaticGatewayCtrlIndex       Integer32,
   gs2310pARPStaticGatewayCtrlIPAddress   IpAddress,
   gs2310pARPStaticGatewayCtrlMACAddress  MacAddress,
   gs2310pARPStaticGatewayCtrlPort        Integer32,
   gs2310pARPStaticGatewayCtrlAction      INTEGER,
   gs2310pARPStaticGatewayCtrlState       DisplayString,
   gs2310pARPStaticGatewayCtrlReOpen      INTEGER,
   gs2310pARPStaticGatewayCtrlRowStatus   INTEGER
}

gs2310pARPStaticGatewayCtrlIndex OBJECT-TYPE
   SYNTAX      Integer32(1..4)
   MAX-ACCESS  not-accessible
   STATUS      current
   DESCRIPTION
       ""
   ::= { gs2310pARPStaticGatewayCtrlEntry 1 }

gs2310pARPStaticGatewayCtrlIPAddress OBJECT-TYPE
   SYNTAX      IpAddress
   MAX-ACCESS  read-write
   STATUS      current
   DESCRIPTION
       " Source IP address. "
   ::= { gs2310pARPStaticGatewayCtrlEntry 2 }

gs2310pARPStaticGatewayCtrlMACAddress OBJECT-TYPE
   SYNTAX      MacAddress
   MAX-ACCESS  read-write
   STATUS      current
   DESCRIPTION
       " Source MAC address , format 0a 1b 2c 3d 4e 5f "
   ::= { gs2310pARPStaticGatewayCtrlEntry 3 }

gs2310pARPStaticGatewayCtrlPort OBJECT-TYPE
   SYNTAX      Integer32(1..4095)
   MAX-ACCESS  read-write
   STATUS      current
   DESCRIPTION
       " Port, range: 1 - port number. "
   ::= { gs2310pARPStaticGatewayCtrlEntry 4 }

gs2310pARPStaticGatewayCtrlAction OBJECT-TYPE
   SYNTAX      INTEGER {none(0),trap(1),dropAndTrap(2), shutdown(3), trapAndShutdown(4) }
   MAX-ACCESS  read-write
   STATUS      current
   DESCRIPTION
       "default: 0
       0: none
       1: trap
       2: drop&trap
       3: shutdown
       4: trap&shutdown"
   ::= { gs2310pARPStaticGatewayCtrlEntry 5 }

gs2310pARPStaticGatewayCtrlState OBJECT-TYPE
   SYNTAX      DisplayString
   MAX-ACCESS  read-only
   STATUS      current
   DESCRIPTION
       ""
   ::= { gs2310pARPStaticGatewayCtrlEntry 6 }

gs2310pARPStaticGatewayCtrlReOpen OBJECT-TYPE
   SYNTAX      INTEGER { none(0), reopen(1) }
   MAX-ACCESS  read-write
   STATUS      current
   DESCRIPTION
       "default: 0
       0: none
       1: reopen"
   ::= { gs2310pARPStaticGatewayCtrlEntry 7 }

gs2310pARPStaticGatewayCtrlRowStatus OBJECT-TYPE
   SYNTAX      INTEGER { active(1), notInservice(2), edit(3), destroy(4), undo(5) }
   MAX-ACCESS  read-write
   STATUS      current
   DESCRIPTION
       "1: active
        2: notInservice
        3: edit
        4: destroy
        5: undo"
   ::= { gs2310pARPStaticGatewayCtrlEntry 8 }

gs2310pARPSpoofingPrevention	                                OBJECT IDENTIFIER ::= { gs2310pARPInspection 7 }

gs2310pARPSpoofingPreventionSystemConf                                      OBJECT IDENTIFIER ::= { gs2310pARPSpoofingPrevention 1 }

gs2310pARPSpoofingPreventionMode OBJECT-TYPE
   SYNTAX      INTEGER { disable(0), enable(1) }
   MAX-ACCESS  read-write
   STATUS      current
   DESCRIPTION
       "default: 0
       0: disable
       1: enable "
   ::= { gs2310pARPSpoofingPreventionSystemConf 1 }

gs2310pARPSpoofingPreventionTable OBJECT-TYPE
   SYNTAX      SEQUENCE OF Gs2310pARPSpoofingPreventionEntry
   MAX-ACCESS  not-accessible
   STATUS      current
   DESCRIPTION
       " "
   ::= { gs2310pARPSpoofingPrevention 2 }

gs2310pARPSpoofingPreventionEntry OBJECT-TYPE
   SYNTAX      Gs2310pARPSpoofingPreventionEntry
   MAX-ACCESS  not-accessible
   STATUS      current
   DESCRIPTION
       ""
   INDEX    { gs2310pARPSpoofingPreventionPort  }
   ::= { gs2310pARPSpoofingPreventionTable 1 }

Gs2310pARPSpoofingPreventionEntry ::= SEQUENCE {
   gs2310pARPSpoofingPreventionPort           Integer32,
   gs2310pARPSpoofingPreventionPortMode       INTEGER,
   gs2310pARPSpoofingPreventionPortLimit      Integer32,
   gs2310pARPSpoofingPreventionPortAction     INTEGER,
   gs2310pARPSpoofingPreventionPortState      DisplayString,
   gs2310pARPSpoofingPreventionPortReOpen     INTEGER
}

gs2310pARPSpoofingPreventionPort OBJECT-TYPE
   SYNTAX      Integer32(1..4095)
   MAX-ACCESS  not-accessible
   STATUS      current
   DESCRIPTION
       " "
   ::= { gs2310pARPSpoofingPreventionEntry 1 }

gs2310pARPSpoofingPreventionPortMode OBJECT-TYPE
   SYNTAX      INTEGER { disable(0), enable(1) }
   MAX-ACCESS  read-write
   STATUS      current
   DESCRIPTION
       "default: 0
       0: disable
       1: enable"
   ::= { gs2310pARPSpoofingPreventionEntry 2 }

gs2310pARPSpoofingPreventionPortLimit OBJECT-TYPE
   SYNTAX      Integer32(1..100)
   MAX-ACCESS  read-write
   STATUS      current
   DESCRIPTION
       "default: 1, range: 1-100"
   ::= { gs2310pARPSpoofingPreventionEntry 3 }

gs2310pARPSpoofingPreventionPortAction OBJECT-TYPE
   SYNTAX      INTEGER { none(0), trap(1), dropAndTrap(2), shutdown(3), trapAndShutdown(4) }
   MAX-ACCESS  read-write
   STATUS      current
   DESCRIPTION
       "default: 0
       0: none
       1: trap
       2: drop&trap
       3: shutdown
       4: trap&shutdown"
   ::= { gs2310pARPSpoofingPreventionEntry 4 }

gs2310pARPSpoofingPreventionPortState OBJECT-TYPE
   SYNTAX      DisplayString
   MAX-ACCESS  read-only
   STATUS      current
   DESCRIPTION
       ""
   ::= { gs2310pARPSpoofingPreventionEntry 5 }

gs2310pARPSpoofingPreventionPortReOpen OBJECT-TYPE
   SYNTAX      INTEGER { none(0), reopen(1) }
   MAX-ACCESS  read-write
   STATUS      current
   DESCRIPTION
       "default: 0
       0: none
       1: reopen"
   ::= { gs2310pARPSpoofingPreventionEntry 6 }

gs2310pARPIPDoSPrevention	                                OBJECT IDENTIFIER ::= { gs2310pARPInspection 8 }

gs2310pARPIPDoSPreventionTCPMode OBJECT-TYPE
   SYNTAX      INTEGER { disable(0), enable(1) }
   MAX-ACCESS  read-write
   STATUS      current
   DESCRIPTION
       "default: 0
       0: disable
       1: enable "
   ::= { gs2310pARPIPDoSPrevention 1 }

gs2310pARPIPDoSPreventionUDPMode OBJECT-TYPE
   SYNTAX      INTEGER { disable(0), enable(1) }
   MAX-ACCESS  read-write
   STATUS      current
   DESCRIPTION
       "default: 0
       0: disable
       1: enable "
   ::= { gs2310pARPIPDoSPrevention 2 }

gs2310pARPIPDoSPreventionICMPMode OBJECT-TYPE
   SYNTAX      INTEGER { disable(0), enable(1) }
   MAX-ACCESS  read-write
   STATUS      current
   DESCRIPTION
       "default: 0
       0: disable
       1: enable "
   ::= { gs2310pARPIPDoSPrevention 3 }

gs2310pARPIPDoSPreventionServerPort1 OBJECT-TYPE
   SYNTAX      Integer32(0..4094)
   MAX-ACCESS  read-write
   STATUS      current
   DESCRIPTION
       " Port, range: 0 - port number. 0: none. "
   ::= { gs2310pARPIPDoSPrevention 4 }

gs2310pARPIPDoSPreventionServerPort2 OBJECT-TYPE
   SYNTAX      Integer32(0..4094)
   MAX-ACCESS  read-write
   STATUS      current
   DESCRIPTION
       " Port, range: 0 - port number. 0: none. "
   ::= { gs2310pARPIPDoSPrevention 5 }

gs2310pARPIPDoSPreventionServerPort3 OBJECT-TYPE
   SYNTAX      Integer32(0..4094)
   MAX-ACCESS  read-write
   STATUS      current
   DESCRIPTION
       " Port, range: 0 - port number. 0: none. "
   ::= { gs2310pARPIPDoSPrevention 6 }

gs2310pARPIPDoSPreventionServerPort4 OBJECT-TYPE
   SYNTAX      Integer32(0..4094)
   MAX-ACCESS  read-write
   STATUS      current
   DESCRIPTION
       " Port, range: 0 - port number. 0: none. "
   ::= { gs2310pARPIPDoSPrevention 7 }

gs2310pDHCPSnooping                                          OBJECT IDENTIFIER ::= { gs2310pSecurity 3 }

gs2310pDHCPSnoopingConf                                          OBJECT IDENTIFIER ::= { gs2310pDHCPSnooping 1 }

gs2310pDHCPSnoopingMode OBJECT-TYPE
   SYNTAX      INTEGER { disable(0), enable(1) }
   MAX-ACCESS  read-write
   STATUS      current
   DESCRIPTION
       "default: 0
       0: disable
       1: enable"
   ::= { gs2310pDHCPSnoopingConf 1 }

gs2310pDHCPSnoopingPortModeConfigurationTable OBJECT-TYPE
   SYNTAX      SEQUENCE OF Gs2310pDHCPSnoopingPortModeConfigurationEntry
   MAX-ACCESS  not-accessible
   STATUS      current
   DESCRIPTION
       " "
   ::= { gs2310pDHCPSnoopingConf 2 }

gs2310pDHCPSnoopingPortModeConfigurationEntry OBJECT-TYPE
   SYNTAX      Gs2310pDHCPSnoopingPortModeConfigurationEntry
   MAX-ACCESS  not-accessible
   STATUS      current
   DESCRIPTION
       ""
   INDEX    { gs2310pDHCPSnoopingPortModeConfigurationPort  }
   ::= { gs2310pDHCPSnoopingPortModeConfigurationTable 1 }

Gs2310pDHCPSnoopingPortModeConfigurationEntry ::= SEQUENCE {
   gs2310pDHCPSnoopingPortModeConfigurationPort	Integer32,
   gs2310pDHCPSnoopingPortModeConfigurationMode	INTEGER
}

gs2310pDHCPSnoopingPortModeConfigurationPort OBJECT-TYPE
   SYNTAX      Integer32(1..4095)
   MAX-ACCESS  not-accessible
   STATUS      current
   DESCRIPTION
       " "
   ::= { gs2310pDHCPSnoopingPortModeConfigurationEntry 1 }

gs2310pDHCPSnoopingPortModeConfigurationMode OBJECT-TYPE
   SYNTAX      INTEGER { trust(0), untrust(1) }
   MAX-ACCESS  read-write
   STATUS      current
   DESCRIPTION
       "default: 1
       0: trust port mode
       1: untrust port mode"
   ::= { gs2310pDHCPSnoopingPortModeConfigurationEntry 2 }

gs2310pDHCPSnoopingStatisticsTable OBJECT-TYPE
   SYNTAX      SEQUENCE OF Gs2310pDHCPSnoopingStatisticsEntry
   MAX-ACCESS  not-accessible
   STATUS      current
   DESCRIPTION
       " "
   ::= { gs2310pDHCPSnooping 2 }

gs2310pDHCPSnoopingStatisticsEntry OBJECT-TYPE
   SYNTAX      Gs2310pDHCPSnoopingStatisticsEntry
   MAX-ACCESS  not-accessible
   STATUS      current
   DESCRIPTION
       ""
   INDEX    { gs2310pDHCPSnoopingStatisticsPort  }
   ::= { gs2310pDHCPSnoopingStatisticsTable 1 }

Gs2310pDHCPSnoopingStatisticsEntry ::= SEQUENCE {
   gs2310pDHCPSnoopingStatisticsPort         Integer32,
   gs2310pDHCPSnoopingStatisticsClear        INTEGER,
   gs2310pDHCPSnoopingRxDiscover             Counter32,
   gs2310pDHCPSnoopingRxOffer                Counter32,
   gs2310pDHCPSnoopingRxRequest              Counter32,
   gs2310pDHCPSnoopingRxDecline              Counter32,
   gs2310pDHCPSnoopingRxACK                  Counter32,
   gs2310pDHCPSnoopingRxNAK                  Counter32,
   gs2310pDHCPSnoopingRxRelease              Counter32,
   gs2310pDHCPSnoopingRxInform               Counter32,
   gs2310pDHCPSnoopingRxLeaseQuery           Counter32,
   gs2310pDHCPSnoopingRxLeaseUnassigned      Counter32,
   gs2310pDHCPSnoopingRxLeaseUnknown         Counter32,
   gs2310pDHCPSnoopingRxLeaseActive          Counter32,
   gs2310pDHCPSnoopingTxDiscover             Counter32,
   gs2310pDHCPSnoopingTxOffer                Counter32,
   gs2310pDHCPSnoopingTxRequest              Counter32,
   gs2310pDHCPSnoopingTxDecline              Counter32,
   gs2310pDHCPSnoopingTxACK                  Counter32,
   gs2310pDHCPSnoopingTxNAK                  Counter32,
   gs2310pDHCPSnoopingTxRelease              Counter32,
   gs2310pDHCPSnoopingTxInform               Counter32,
   gs2310pDHCPSnoopingTxLeaseQuery           Counter32,
   gs2310pDHCPSnoopingTxLeaseUnassigned      Counter32,
   gs2310pDHCPSnoopingTxLeaseUnknown         Counter32,
   gs2310pDHCPSnoopingTxLeaseActive          Counter32
}

gs2310pDHCPSnoopingStatisticsPort OBJECT-TYPE
   SYNTAX      Integer32(1..4095)
   MAX-ACCESS  not-accessible
   STATUS      current
   DESCRIPTION
       " "
   ::= { gs2310pDHCPSnoopingStatisticsEntry 1 }

gs2310pDHCPSnoopingStatisticsClear OBJECT-TYPE
   SYNTAX      INTEGER { none(0), clear(1) }
   MAX-ACCESS  read-write
   STATUS      current
   DESCRIPTION
       "default: 0
       0: none
       1: clear"
   ::= { gs2310pDHCPSnoopingStatisticsEntry 2 }

gs2310pDHCPSnoopingRxDiscover OBJECT-TYPE
   SYNTAX      Counter32
   MAX-ACCESS  read-only
   STATUS      current
   DESCRIPTION
       " "
   ::= { gs2310pDHCPSnoopingStatisticsEntry 3 }

gs2310pDHCPSnoopingRxOffer OBJECT-TYPE
   SYNTAX      Counter32
   MAX-ACCESS  read-only
   STATUS      current
   DESCRIPTION
       " "
   ::= { gs2310pDHCPSnoopingStatisticsEntry 4 }

gs2310pDHCPSnoopingRxRequest OBJECT-TYPE
   SYNTAX      Counter32
   MAX-ACCESS  read-only
   STATUS      current
   DESCRIPTION
       " "
   ::= { gs2310pDHCPSnoopingStatisticsEntry 5 }

gs2310pDHCPSnoopingRxDecline OBJECT-TYPE
   SYNTAX      Counter32
   MAX-ACCESS  read-only
   STATUS      current
   DESCRIPTION
       " "
   ::= { gs2310pDHCPSnoopingStatisticsEntry 6 }

gs2310pDHCPSnoopingRxACK OBJECT-TYPE
   SYNTAX      Counter32
   MAX-ACCESS  read-only
   STATUS      current
   DESCRIPTION
       " "
   ::= { gs2310pDHCPSnoopingStatisticsEntry 7 }

gs2310pDHCPSnoopingRxNAK OBJECT-TYPE
   SYNTAX      Counter32
   MAX-ACCESS  read-only
   STATUS      current
   DESCRIPTION
       " "
   ::= { gs2310pDHCPSnoopingStatisticsEntry 8 }

gs2310pDHCPSnoopingRxRelease OBJECT-TYPE
   SYNTAX      Counter32
   MAX-ACCESS  read-only
   STATUS      current
   DESCRIPTION
       " "
   ::= { gs2310pDHCPSnoopingStatisticsEntry 9 }

gs2310pDHCPSnoopingRxInform OBJECT-TYPE
   SYNTAX      Counter32
   MAX-ACCESS  read-only
   STATUS      current
   DESCRIPTION
       " "
   ::= { gs2310pDHCPSnoopingStatisticsEntry 10 }

gs2310pDHCPSnoopingRxLeaseQuery OBJECT-TYPE
   SYNTAX      Counter32
   MAX-ACCESS  read-only
   STATUS      current
   DESCRIPTION
       " "
   ::= { gs2310pDHCPSnoopingStatisticsEntry 11 }

gs2310pDHCPSnoopingRxLeaseUnassigned OBJECT-TYPE
   SYNTAX      Counter32
   MAX-ACCESS  read-only
   STATUS      current
   DESCRIPTION
       " "
   ::= { gs2310pDHCPSnoopingStatisticsEntry 12 }

gs2310pDHCPSnoopingRxLeaseUnknown OBJECT-TYPE
   SYNTAX      Counter32
   MAX-ACCESS  read-only
   STATUS      current
   DESCRIPTION
       " "
   ::= { gs2310pDHCPSnoopingStatisticsEntry 13 }

gs2310pDHCPSnoopingRxLeaseActive OBJECT-TYPE
   SYNTAX      Counter32
   MAX-ACCESS  read-only
   STATUS      current
   DESCRIPTION
       " "
   ::= { gs2310pDHCPSnoopingStatisticsEntry 14 }

gs2310pDHCPSnoopingTxDiscover OBJECT-TYPE
   SYNTAX      Counter32
   MAX-ACCESS  read-only
   STATUS      current
   DESCRIPTION
       " "
   ::= { gs2310pDHCPSnoopingStatisticsEntry 15 }

gs2310pDHCPSnoopingTxOffer OBJECT-TYPE
   SYNTAX      Counter32
   MAX-ACCESS  read-only
   STATUS      current
   DESCRIPTION
       " "
   ::= { gs2310pDHCPSnoopingStatisticsEntry 16 }

gs2310pDHCPSnoopingTxRequest OBJECT-TYPE
   SYNTAX      Counter32
   MAX-ACCESS  read-only
   STATUS      current
   DESCRIPTION
       " "
   ::= { gs2310pDHCPSnoopingStatisticsEntry 17 }

gs2310pDHCPSnoopingTxDecline OBJECT-TYPE
   SYNTAX      Counter32
   MAX-ACCESS  read-only
   STATUS      current
   DESCRIPTION
       " "
   ::= { gs2310pDHCPSnoopingStatisticsEntry 18 }

gs2310pDHCPSnoopingTxACK OBJECT-TYPE
   SYNTAX      Counter32
   MAX-ACCESS  read-only
   STATUS      current
   DESCRIPTION
       " "
   ::= { gs2310pDHCPSnoopingStatisticsEntry 19 }

gs2310pDHCPSnoopingTxNAK OBJECT-TYPE
   SYNTAX      Counter32
   MAX-ACCESS  read-only
   STATUS      current
   DESCRIPTION
       " "
   ::= { gs2310pDHCPSnoopingStatisticsEntry 20 }

gs2310pDHCPSnoopingTxRelease OBJECT-TYPE
   SYNTAX      Counter32
   MAX-ACCESS  read-only
   STATUS      current
   DESCRIPTION
       " "
   ::= { gs2310pDHCPSnoopingStatisticsEntry 21 }

gs2310pDHCPSnoopingTxInform OBJECT-TYPE
   SYNTAX      Counter32
   MAX-ACCESS  read-only
   STATUS      current
   DESCRIPTION
       " "
   ::= { gs2310pDHCPSnoopingStatisticsEntry 22 }

gs2310pDHCPSnoopingTxLeaseQuery OBJECT-TYPE
   SYNTAX      Counter32
   MAX-ACCESS  read-only
   STATUS      current
   DESCRIPTION
       " "
   ::= { gs2310pDHCPSnoopingStatisticsEntry 23 }

gs2310pDHCPSnoopingTxLeaseUnassigned OBJECT-TYPE
   SYNTAX      Counter32
   MAX-ACCESS  read-only
   STATUS      current
   DESCRIPTION
       " "
   ::= { gs2310pDHCPSnoopingStatisticsEntry 24 }

gs2310pDHCPSnoopingTxLeaseUnknown OBJECT-TYPE
   SYNTAX      Counter32
   MAX-ACCESS  read-only
   STATUS      current
   DESCRIPTION
       " "
   ::= { gs2310pDHCPSnoopingStatisticsEntry 25 }

gs2310pDHCPSnoopingTxLeaseActive OBJECT-TYPE
   SYNTAX      Counter32
   MAX-ACCESS  read-only
   STATUS      current
   DESCRIPTION
       " "
   ::= { gs2310pDHCPSnoopingStatisticsEntry 26 }


gs2310pDHCPRelay                                             OBJECT IDENTIFIER ::= { gs2310pSecurity 4 }

gs2310pDHCPRelayConfiguration                                         OBJECT IDENTIFIER ::= { gs2310pDHCPRelay 1 }

gs2310pDHCPRelayMode OBJECT-TYPE
   SYNTAX      INTEGER { disable(0), enable(1) }
   MAX-ACCESS  read-write
   STATUS      current
   DESCRIPTION
       "default: 0
       0: disable
       1: enable
       We need at least one server"
   ::= { gs2310pDHCPRelayConfiguration 1 }

gs2310pDHCPRelayServer OBJECT-TYPE
   SYNTAX      IpAddress
   MAX-ACCESS  read-write
   STATUS      current
   DESCRIPTION
       " "
   ::= { gs2310pDHCPRelayConfiguration 2 }

gs2310pDHCPRelayInformationMode OBJECT-TYPE
   SYNTAX      INTEGER { disable(0), enable(1) }
   MAX-ACCESS  read-write
   STATUS      current
   DESCRIPTION
       "default: 0
       0: disable
       1: enable "
   ::= { gs2310pDHCPRelayConfiguration 3 }

gs2310pDHCPRelayInformationPolicy OBJECT-TYPE
   SYNTAX      INTEGER { replace(0), keep(1), drop(2) }
   MAX-ACCESS  read-write
   STATUS      current
   DESCRIPTION
       "default: 0
       0: replace
       1: keep
       2: drop "
   ::= { gs2310pDHCPRelayConfiguration 4 }

gs2310pDHCPRelayInformationCustom OBJECT-TYPE
   SYNTAX      DisplayString(SIZE(0..32))
   MAX-ACCESS  read-write
   STATUS      current
   DESCRIPTION
       "DHCP Option 82 Circuit ID custom information"
   ::= { gs2310pDHCPRelayConfiguration 1500 }

gs2310pDHCPRelayConfigurationGateways                                          OBJECT IDENTIFIER ::= { gs2310pDHCPRelayConfiguration 5 }

gs2310pDHCPRelayConfigurationGatewaysCreate OBJECT-TYPE
   SYNTAX       INTEGER { none(0), create(1) }
   MAX-ACCESS   read-write
   STATUS       current
   DESCRIPTION
       "default: 0
        0 : None  (read only)
        1 : Create entry"
   ::= { gs2310pDHCPRelayConfigurationGateways 1 }

gs2310pDHCPRelayConfigurationGatewaysTable OBJECT-TYPE
   SYNTAX      SEQUENCE OF Gs2310pDHCPRelayConfigurationGatewaysEntry
   MAX-ACCESS  not-accessible
   STATUS      current
   DESCRIPTION
       " Create DHCP Relay Gateway IP address entry."
   ::= { gs2310pDHCPRelayConfigurationGateways 2 }

gs2310pDHCPRelayConfigurationGatewaysEntry OBJECT-TYPE
   SYNTAX      Gs2310pDHCPRelayConfigurationGatewaysEntry
   MAX-ACCESS  not-accessible
   STATUS      current
   DESCRIPTION
       ""
   INDEX    { gs2310pDHCPRelayConfigurationGatewaysIndex  }
   ::= { gs2310pDHCPRelayConfigurationGatewaysTable 1 }

Gs2310pDHCPRelayConfigurationGatewaysEntry ::= SEQUENCE {
   gs2310pDHCPRelayConfigurationGatewaysIndex           Integer32,
   gs2310pDHCPRelayConfigurationGatewaysVLANId          Integer32,
   gs2310pDHCPRelayConfigurationGatewaysIP              IpAddress,
   gs2310pDHCPRelayConfigurationGatewaysRowStatus       INTEGER
}

gs2310pDHCPRelayConfigurationGatewaysIndex OBJECT-TYPE
   SYNTAX      Integer32(1..6)
   MAX-ACCESS  not-accessible
   STATUS      current
   DESCRIPTION
       " "
   ::= { gs2310pDHCPRelayConfigurationGatewaysEntry 1 }

gs2310pDHCPRelayConfigurationGatewaysVLANId OBJECT-TYPE
   SYNTAX      Integer32(1..4094)
   MAX-ACCESS  read-write
   STATUS      current
   DESCRIPTION
       " VLAN ID "
   ::= { gs2310pDHCPRelayConfigurationGatewaysEntry 2 }

gs2310pDHCPRelayConfigurationGatewaysIP OBJECT-TYPE
   SYNTAX      IpAddress
   MAX-ACCESS  read-write
   STATUS      current
   DESCRIPTION
       "DHCP GIADDR address."
   ::= { gs2310pDHCPRelayConfigurationGatewaysEntry 3 }

gs2310pDHCPRelayConfigurationGatewaysRowStatus OBJECT-TYPE
   SYNTAX      INTEGER { active(1), notInservice(2), destroy(4), undo(5) }
   MAX-ACCESS  read-write
   STATUS      current
   DESCRIPTION
       "1: active
        2: notInservice
        4: destroy
        5: undo"
   ::= { gs2310pDHCPRelayConfigurationGatewaysEntry 4 }


gs2310pDHCPRelayStatistics                                   OBJECT IDENTIFIER ::= { gs2310pDHCPRelay 2 }

gs2310pDHCPRelayServerStatistics                                   OBJECT IDENTIFIER ::= { gs2310pDHCPRelayStatistics 1 }

gs2310pServerStatTransmitToServer OBJECT-TYPE
   SYNTAX      Counter32
   MAX-ACCESS  read-only
   STATUS      current
   DESCRIPTION
       " "
   ::= { gs2310pDHCPRelayServerStatistics 1 }

gs2310pServerStatTransmitError OBJECT-TYPE
   SYNTAX      Counter32
   MAX-ACCESS  read-only
   STATUS      current
   DESCRIPTION
       " "
   ::= { gs2310pDHCPRelayServerStatistics 2 }

gs2310pServerStatReceiveFromServer OBJECT-TYPE
   SYNTAX      Counter32
   MAX-ACCESS  read-only
   STATUS      current
   DESCRIPTION
       " "
   ::= { gs2310pDHCPRelayServerStatistics 3 }

gs2310pServerStatReceiveMissingAgentOption OBJECT-TYPE
   SYNTAX      Counter32
   MAX-ACCESS  read-only
   STATUS      current
   DESCRIPTION
       " "
   ::= { gs2310pDHCPRelayServerStatistics 4 }

gs2310pServerStatReceiveMissingCircuitID OBJECT-TYPE
   SYNTAX      Counter32
   MAX-ACCESS  read-only
   STATUS      current
   DESCRIPTION
       " "
   ::= { gs2310pDHCPRelayServerStatistics 5 }

gs2310pServerStatReceiveMissingRemoteID OBJECT-TYPE
   SYNTAX      Counter32
   MAX-ACCESS  read-only
   STATUS      current
   DESCRIPTION
       " "
   ::= { gs2310pDHCPRelayServerStatistics 6 }

gs2310pServerStatReceiveBadCircuitID OBJECT-TYPE
   SYNTAX      Counter32
   MAX-ACCESS  read-only
   STATUS      current
   DESCRIPTION
       " "
   ::= { gs2310pDHCPRelayServerStatistics 7 }

gs2310pServerStatReceiveBadRemoteID OBJECT-TYPE
   SYNTAX      Counter32
   MAX-ACCESS  read-only
   STATUS      current
   DESCRIPTION
       " "
   ::= { gs2310pDHCPRelayServerStatistics 8 }

gs2310pDHCPRelayClientStatistics                                   OBJECT IDENTIFIER ::= { gs2310pDHCPRelayStatistics 2 }

gs2310pClientStatTransmitToClient OBJECT-TYPE
   SYNTAX      Counter32
   MAX-ACCESS  read-only
   STATUS      current
   DESCRIPTION
       " "
   ::= { gs2310pDHCPRelayClientStatistics 1 }

gs2310pClientStatTransmitError OBJECT-TYPE
   SYNTAX      Counter32
   MAX-ACCESS  read-only
   STATUS      current
   DESCRIPTION
       " "
   ::= { gs2310pDHCPRelayClientStatistics 2 }

gs2310pClientStatReceivefromClient OBJECT-TYPE
   SYNTAX      Counter32
   MAX-ACCESS  read-only
   STATUS      current
   DESCRIPTION
       " "
   ::= { gs2310pDHCPRelayClientStatistics 3 }

gs2310pClientStatReceiveAgentOption OBJECT-TYPE
   SYNTAX      Counter32
   MAX-ACCESS  read-only
   STATUS      current
   DESCRIPTION
       " "
   ::= { gs2310pDHCPRelayClientStatistics 4 }

gs2310pClientStatReplaceAgentOption OBJECT-TYPE
   SYNTAX      Counter32
   MAX-ACCESS  read-only
   STATUS      current
   DESCRIPTION
       " "
   ::= { gs2310pDHCPRelayClientStatistics 5 }

gs2310pClientStatKeepAgentOption OBJECT-TYPE
   SYNTAX      Counter32
   MAX-ACCESS  read-only
   STATUS      current
   DESCRIPTION
       " "
   ::= { gs2310pDHCPRelayClientStatistics 6 }

gs2310pClientStatDropAgentOption OBJECT-TYPE
   SYNTAX      Counter32
   MAX-ACCESS  read-only
   STATUS      current
   DESCRIPTION
       " "
   ::= { gs2310pDHCPRelayClientStatistics 7 }

gs2310pPortSecurity                                          OBJECT IDENTIFIER ::= { gs2310pSecurity 5 }

gs2310pPortSecLimitCtrl                                      OBJECT IDENTIFIER ::= { gs2310pPortSecurity 1 }

gs2310pPortSecLimitCtrlSystemConf                                      OBJECT IDENTIFIER ::= { gs2310pPortSecLimitCtrl 1 }

gs2310pPortSecurityMode OBJECT-TYPE
   SYNTAX      INTEGER { disable(0), enable(1) }
   MAX-ACCESS  read-write
   STATUS      current
   DESCRIPTION
       "default: 0
       0: disable
       1: enable "
   ::= { gs2310pPortSecLimitCtrlSystemConf 1 }

gs2310pPortSecurityAging OBJECT-TYPE
   SYNTAX      INTEGER { disable(0), enable(1) }
   MAX-ACCESS  read-write
   STATUS      current
   DESCRIPTION
       "default: 0
       0: disable
       1: enable "
   ::= { gs2310pPortSecLimitCtrlSystemConf 2 }

gs2310pPortSecurityAgingPeriod OBJECT-TYPE
   SYNTAX      INTEGER(10..10000000)
   MAX-ACCESS  read-write
   STATUS      current
   DESCRIPTION
       "default: 3600, range: 10-10000000 "
   ::= { gs2310pPortSecLimitCtrlSystemConf 3 }

gs2310pPortSecLimitCtrlTable OBJECT-TYPE
   SYNTAX      SEQUENCE OF Gs2310pPortSecLimitCtrlEntry
   MAX-ACCESS  not-accessible
   STATUS      current
   DESCRIPTION
       " "
   ::= { gs2310pPortSecLimitCtrl 2 }

gs2310pPortSecLimitCtrlEntry OBJECT-TYPE
   SYNTAX      Gs2310pPortSecLimitCtrlEntry
   MAX-ACCESS  not-accessible
   STATUS      current
   DESCRIPTION
       ""
   INDEX    { gs2310pPortSecLimitCtrlPort  }
   ::= { gs2310pPortSecLimitCtrlTable 1 }

Gs2310pPortSecLimitCtrlEntry ::= SEQUENCE {
   gs2310pPortSecLimitCtrlPort           Integer32,
   gs2310pPortSecLimitCtrlPortMode       INTEGER,
   gs2310pPortSecLimitCtrlPortLimit      Integer32,
   gs2310pPortSecLimitCtrlPortAction     INTEGER,
   gs2310pPortSecLimitCtrlPortState      DisplayString,
   gs2310pPortSecLimitCtrlPortReOpen     INTEGER
}

gs2310pPortSecLimitCtrlPort OBJECT-TYPE
   SYNTAX      Integer32(1..4095)
   MAX-ACCESS  not-accessible
   STATUS      current
   DESCRIPTION
       " "
   ::= { gs2310pPortSecLimitCtrlEntry 1 }

gs2310pPortSecLimitCtrlPortMode OBJECT-TYPE
   SYNTAX      INTEGER { disable(0), enable(1) }
   MAX-ACCESS  read-write
   STATUS      current
   DESCRIPTION
       "default: 0
       0: disable
       1: enable"
   ::= { gs2310pPortSecLimitCtrlEntry 2 }

gs2310pPortSecLimitCtrlPortLimit OBJECT-TYPE
   SYNTAX      Integer32(1..1024)
   MAX-ACCESS  read-write
   STATUS      current
   DESCRIPTION
       "default: 4, range: 1-1024"
   ::= { gs2310pPortSecLimitCtrlEntry 3 }

gs2310pPortSecLimitCtrlPortAction OBJECT-TYPE
   SYNTAX      INTEGER { none(0), trap(1), shutdown(2), trapShutdown(3) }
   MAX-ACCESS  read-write
   STATUS      current
   DESCRIPTION
       "default: 0
       0: none
       1: trap
       2: shutdown
       3: trap&shutdown"
   ::= { gs2310pPortSecLimitCtrlEntry 4 }

gs2310pPortSecLimitCtrlPortState OBJECT-TYPE
   SYNTAX      DisplayString
   MAX-ACCESS  read-only
   STATUS      current
   DESCRIPTION
       ""
   ::= { gs2310pPortSecLimitCtrlEntry 5 }

gs2310pPortSecLimitCtrlPortReOpen OBJECT-TYPE
   SYNTAX      INTEGER { none(0), reopen(1) }
   MAX-ACCESS  read-write
   STATUS      current
   DESCRIPTION
       "default: 0
       0: none
       1: reopen"
   ::= { gs2310pPortSecLimitCtrlEntry 6 }

gs2310pPortSecSwitchStatusTable OBJECT-TYPE
   SYNTAX      SEQUENCE OF Gs2310pPortSecSwitchStatusEntry
   MAX-ACCESS  not-accessible
   STATUS      current
   DESCRIPTION
       " "
   ::= { gs2310pPortSecurity 2 }

gs2310pPortSecSwitchStatusEntry OBJECT-TYPE
   SYNTAX      Gs2310pPortSecSwitchStatusEntry
   MAX-ACCESS  not-accessible
   STATUS      current
   DESCRIPTION
       ""
   INDEX    { gs2310pPortSecSwitchStatusPort  }
   ::= { gs2310pPortSecSwitchStatusTable 1 }

Gs2310pPortSecSwitchStatusEntry ::= SEQUENCE {
   gs2310pPortSecSwitchStatusPort                Integer32,
   gs2310pPortSecSwitchStatusUsers               DisplayString,
   gs2310pPortSecSwitchStatusState               DisplayString,
   gs2310pPortSecSwitchStatusMACCountCurrent     Integer32,
   gs2310pPortSecSwitchStatusMACCountLimit       Integer32
}

gs2310pPortSecSwitchStatusPort OBJECT-TYPE
   SYNTAX      Integer32(1..4095)
   MAX-ACCESS  not-accessible
   STATUS      current
   DESCRIPTION
       " "
   ::= { gs2310pPortSecSwitchStatusEntry 1 }

gs2310pPortSecSwitchStatusUsers OBJECT-TYPE
   SYNTAX      DisplayString
   MAX-ACCESS  read-only
   STATUS      current
   DESCRIPTION
       " Users Abbr: L = Limit Control, 8 = 802.1X, D = DHCP Snooping, V = Voice VLAN,
         '-' means that the corresponding user module is not enabled. "
   ::= { gs2310pPortSecSwitchStatusEntry 2 }

gs2310pPortSecSwitchStatusState OBJECT-TYPE
   SYNTAX      DisplayString
   MAX-ACCESS  read-only
   STATUS      current
   DESCRIPTION
       " Shows the current state of the port : Disabled, Ready, Limit Reached, Shutdown. "
   ::= { gs2310pPortSecSwitchStatusEntry 3 }

gs2310pPortSecSwitchStatusMACCountCurrent OBJECT-TYPE
   SYNTAX      Integer32(1..4095)
   MAX-ACCESS  read-only
   STATUS      current
   DESCRIPTION
       ""
   ::= { gs2310pPortSecSwitchStatusEntry 4 }

gs2310pPortSecSwitchStatusMACCountLimit OBJECT-TYPE
   SYNTAX      Integer32(1..4095)
   MAX-ACCESS  read-only
   STATUS      current
   DESCRIPTION
       ""
   ::= { gs2310pPortSecSwitchStatusEntry 5 }

gs2310pPortSecPortStatus                                      OBJECT IDENTIFIER ::= { gs2310pPortSecurity 3 }

gs2310pPortSecPortStatusPort OBJECT-TYPE
   SYNTAX       Integer32(1..4095)
   MAX-ACCESS   read-write
   STATUS       current
   DESCRIPTION
       "port number
        default: 1
        range: 1 - port number."
   ::= { gs2310pPortSecPortStatus 1 }

gs2310pPortSecPortStatusTable OBJECT-TYPE
   SYNTAX      SEQUENCE OF Gs2310pPortSecPortStatusEntry
   MAX-ACCESS  not-accessible
   STATUS      current
   DESCRIPTION
      " "
   ::= { gs2310pPortSecPortStatus 2 }

gs2310pPortSecPortStatusEntry OBJECT-TYPE
   SYNTAX      Gs2310pPortSecPortStatusEntry
   MAX-ACCESS  not-accessible
   STATUS      current
   DESCRIPTION
       ""
   INDEX    { gs2310pPortSecPortStatusIndex  }
   ::= { gs2310pPortSecPortStatusTable 1 }

Gs2310pPortSecPortStatusEntry ::= SEQUENCE {
   gs2310pPortSecPortStatusIndex              Integer32,
   gs2310pPortSecPortStatusMACAddress         MacAddress,
   gs2310pPortSecPortStatusVLANId             Integer32,
   gs2310pPortSecPortStatusState              DisplayString,
   gs2310pPortSecPortStatusTimeOfAddition     DisplayString,
   gs2310pPortSecPortStatusAgeAndHold         DisplayString
}

gs2310pPortSecPortStatusIndex OBJECT-TYPE
   SYNTAX      Integer32(1..4095)
   MAX-ACCESS  not-accessible
   STATUS      current
   DESCRIPTION
       " "
   ::= { gs2310pPortSecPortStatusEntry 1 }

gs2310pPortSecPortStatusMACAddress OBJECT-TYPE
   SYNTAX      MacAddress
   MAX-ACCESS  read-only
   STATUS      current
   DESCRIPTION
       " "
   ::= { gs2310pPortSecPortStatusEntry 2 }

gs2310pPortSecPortStatusVLANId OBJECT-TYPE
   SYNTAX      Integer32(1..4094)
   MAX-ACCESS  read-only
   STATUS      current
   DESCRIPTION
       " "
   ::= { gs2310pPortSecPortStatusEntry 3 }

gs2310pPortSecPortStatusState OBJECT-TYPE
   SYNTAX      DisplayString
   MAX-ACCESS  read-only
   STATUS      current
   DESCRIPTION
       "Blocked / Forwarding "
   ::= { gs2310pPortSecPortStatusEntry 4 }

gs2310pPortSecPortStatusTimeOfAddition OBJECT-TYPE
   SYNTAX      DisplayString
   MAX-ACCESS  read-only
   STATUS      current
   DESCRIPTION
       " "
   ::= { gs2310pPortSecPortStatusEntry 5 }

gs2310pPortSecPortStatusAgeAndHold OBJECT-TYPE
   SYNTAX      DisplayString
   MAX-ACCESS  read-only
   STATUS      current
   DESCRIPTION
       " "
   ::= { gs2310pPortSecPortStatusEntry 6 }


gs2310pAccessManagement                                      OBJECT IDENTIFIER ::= { gs2310pSecurity 6 }

gs2310pAccessMgtConf                                         OBJECT IDENTIFIER ::= { gs2310pAccessManagement 1 }

gs2310pAccessMgtConfMode OBJECT-TYPE
   SYNTAX      INTEGER { disable(0), enable(1) }
   MAX-ACCESS  read-write
   STATUS      current
   DESCRIPTION
       "default: 0
       0: disable
       1: enable "
   ::= { gs2310pAccessMgtConf 1 }

gs2310pAccessMgtConfCreate OBJECT-TYPE
   SYNTAX      INTEGER { none(0), create(1) }
   MAX-ACCESS  read-write
   STATUS      current
   DESCRIPTION
       "default: 0
       0: none
       1: create "
   ::= { gs2310pAccessMgtConf 2 }

gs2310pAccessMgtConfTable OBJECT-TYPE
   SYNTAX      SEQUENCE OF Gs2310pAccessMgtConfEntry
   MAX-ACCESS  not-accessible
   STATUS      current
   DESCRIPTION
       " "
   ::= { gs2310pAccessMgtConf 3 }

gs2310pAccessMgtConfEntry OBJECT-TYPE
   SYNTAX      Gs2310pAccessMgtConfEntry
   MAX-ACCESS  not-accessible
   STATUS      current
   DESCRIPTION
       ""
   INDEX    { gs2310pAccessMgtIndex  }
   ::= { gs2310pAccessMgtConfTable 1 }

Gs2310pAccessMgtConfEntry ::= SEQUENCE {
   gs2310pAccessMgtIndex             Integer32,
   gs2310pAccessMgtAddresstype       INTEGER,
   gs2310pAccessMgtStartIpAddress    DisplayString,
   gs2310pAccessMgtEndIpAddress      DisplayString,
   gs2310pAccessMgtHttpHttps         INTEGER,
   gs2310pAccessMgtSNMP              INTEGER,
   gs2310pAccessMgtTelnetSSH         INTEGER,
   gs2310pAccessMgtRowStatus         INTEGER
}

gs2310pAccessMgtIndex OBJECT-TYPE
   SYNTAX      Integer32(1..16)
   MAX-ACCESS  read-write
   STATUS      current
   DESCRIPTION
       "Set Access Management config index
        range : 1-16."
   ::= { gs2310pAccessMgtConfEntry 1 }

gs2310pAccessMgtAddresstype OBJECT-TYPE
   SYNTAX      INTEGER { ipv4(0), ipv6(1) }
   MAX-ACCESS  read-write
   STATUS      current
   DESCRIPTION
       "0: ipv4
        1: ipv6 "
   ::= { gs2310pAccessMgtConfEntry 2 }

gs2310pAccessMgtStartIpAddress OBJECT-TYPE
   SYNTAX      DisplayString
   MAX-ACCESS  read-write
   STATUS      current
   DESCRIPTION
       " Start IP address.
         IP address doesn't allowed all zero or all 'ff'H."
   ::= { gs2310pAccessMgtConfEntry 3 }

gs2310pAccessMgtEndIpAddress OBJECT-TYPE
   SYNTAX      DisplayString
   MAX-ACCESS  read-write
   STATUS      current
   DESCRIPTION
       " End IP address.
         IP address doesn't allowed all zero or all 'ff'H.
         End ip address is not less than start ip address."
   ::= { gs2310pAccessMgtConfEntry 4 }

gs2310pAccessMgtHttpHttps OBJECT-TYPE
   SYNTAX      INTEGER { disable(0), enable(1) }
   MAX-ACCESS  read-write
   STATUS      current
   DESCRIPTION
       "default: 0
       0: disable
       1: enable "
   ::= { gs2310pAccessMgtConfEntry 5 }

gs2310pAccessMgtSNMP OBJECT-TYPE
   SYNTAX      INTEGER { disable(0), enable(1) }
   MAX-ACCESS  read-write
   STATUS      current
   DESCRIPTION
       "default: 0
       0: disable
       1: enable "
   ::= { gs2310pAccessMgtConfEntry 6 }

gs2310pAccessMgtTelnetSSH OBJECT-TYPE
   SYNTAX      INTEGER { disable(0), enable(1) }
   MAX-ACCESS  read-write
   STATUS      current
   DESCRIPTION
       "default: 0
       0: disable
       1: enable "
   ::= { gs2310pAccessMgtConfEntry 7 }

gs2310pAccessMgtRowStatus OBJECT-TYPE
   SYNTAX      INTEGER { active(1), notInservice(2), edit(3),destroy(4), undo(5) }
   MAX-ACCESS  read-write
   STATUS      current
   DESCRIPTION
       "1: active
        2: notInservice
        3: edit
        4: destroy
        5: undo"
   ::= { gs2310pAccessMgtConfEntry 8 }

gs2310pAccessMgtStatistics                                   OBJECT IDENTIFIER ::= { gs2310pAccessManagement 2 }

gs2310pHttpReceivedPkts OBJECT-TYPE
   SYNTAX      Counter32
   MAX-ACCESS  read-only
   STATUS      current
   DESCRIPTION
       " "
   ::= { gs2310pAccessMgtStatistics 1 }

gs2310pHttpAllowedPkts OBJECT-TYPE
   SYNTAX      Counter32
   MAX-ACCESS  read-only
   STATUS      current
   DESCRIPTION
       " "
   ::= { gs2310pAccessMgtStatistics 2 }

gs2310pHttpDiscardedPkts OBJECT-TYPE
   SYNTAX      Counter32
   MAX-ACCESS  read-only
   STATUS      current
   DESCRIPTION
       " "
   ::= { gs2310pAccessMgtStatistics 3 }

gs2310pHttpsReceivedPkts OBJECT-TYPE
   SYNTAX      Counter32
   MAX-ACCESS  read-only
   STATUS      current
   DESCRIPTION
       " "
   ::= { gs2310pAccessMgtStatistics 4 }

gs2310pHttpsAllowedPkts OBJECT-TYPE
   SYNTAX      Counter32
   MAX-ACCESS  read-only
   STATUS      current
   DESCRIPTION
       " "
   ::= { gs2310pAccessMgtStatistics 5 }

gs2310pHttpsDiscardedPkts OBJECT-TYPE
   SYNTAX      Counter32
   MAX-ACCESS  read-only
   STATUS      current
   DESCRIPTION
       " "
   ::= { gs2310pAccessMgtStatistics 6 }

gs2310pSnmpReceivedPkts OBJECT-TYPE
   SYNTAX      Counter32
   MAX-ACCESS  read-only
   STATUS      current
   DESCRIPTION
       " "
   ::= { gs2310pAccessMgtStatistics 7 }

gs2310pSnmpAllowedPkts OBJECT-TYPE
   SYNTAX      Counter32
   MAX-ACCESS  read-only
   STATUS      current
   DESCRIPTION
       " "
   ::= { gs2310pAccessMgtStatistics 8 }

gs2310pSnmpDiscardedPkts OBJECT-TYPE
   SYNTAX      Counter32
   MAX-ACCESS  read-only
   STATUS      current
   DESCRIPTION
       " "
   ::= { gs2310pAccessMgtStatistics 9 }

gs2310pTelnetReceivedPkts OBJECT-TYPE
   SYNTAX      Counter32
   MAX-ACCESS  read-only
   STATUS      current
   DESCRIPTION
       " "
   ::= { gs2310pAccessMgtStatistics 10 }

gs2310pTelnetAllowedPkts OBJECT-TYPE
   SYNTAX      Counter32
   MAX-ACCESS  read-only
   STATUS      current
   DESCRIPTION
       " "
   ::= { gs2310pAccessMgtStatistics 11 }

gs2310pTelnetDiscardedPkts OBJECT-TYPE
   SYNTAX      Counter32
   MAX-ACCESS  read-only
   STATUS      current
   DESCRIPTION
       " "
   ::= { gs2310pAccessMgtStatistics 12 }

gs2310pSSHReceivedPkts OBJECT-TYPE
   SYNTAX      Counter32
   MAX-ACCESS  read-only
   STATUS      current
   DESCRIPTION
       " "
   ::= { gs2310pAccessMgtStatistics 13 }

gs2310pSSHAllowedPkts OBJECT-TYPE
   SYNTAX      Counter32
   MAX-ACCESS  read-only
   STATUS      current
   DESCRIPTION
       " "
   ::= { gs2310pAccessMgtStatistics 14 }

gs2310pSSHDiscardedPkts OBJECT-TYPE
   SYNTAX      Counter32
   MAX-ACCESS  read-only
   STATUS      current
   DESCRIPTION
       " "
   ::= { gs2310pAccessMgtStatistics 15 }

gs2310pAccessMgtStatisticsClearAll OBJECT-TYPE
   SYNTAX      INTEGER { none(0), clear(1) }
   MAX-ACCESS  read-write
   STATUS      current
   DESCRIPTION
       "0: none
        1: clear"
   ::= { gs2310pAccessMgtStatistics 16 }

gs2310pSSH                                                   OBJECT IDENTIFIER ::= { gs2310pSecurity 7 }

gs2310pSSHMode OBJECT-TYPE
   SYNTAX      INTEGER { disable(0), enable(1) }
   MAX-ACCESS  read-write
   STATUS      current
   DESCRIPTION
       "default: 1
        0: disable
        1: enable"
   ::= { gs2310pSSH 1 }

gs2310pHTTPS                                                 OBJECT IDENTIFIER ::= { gs2310pSecurity 8 }

gs2310pHTTPSMode OBJECT-TYPE
   SYNTAX      INTEGER { disable(0), enable(1) }
   MAX-ACCESS  read-write
   STATUS      current
   DESCRIPTION
       "default: 1
        0: disable
        1: enable"
   ::= { gs2310pHTTPS 1 }

gs2310pHTTPSAutoRedirect OBJECT-TYPE
   SYNTAX      INTEGER { disable(0), enable(1) }
   MAX-ACCESS  read-write
   STATUS      current
   DESCRIPTION
       "default: 0
        0: disable
        1: enable"
   ::= { gs2310pHTTPS 2 }

gs2310pHTTPSCertRenew OBJECT-TYPE
   SYNTAX      INTEGER { doNothing(0), renew(1) }
   MAX-ACCESS  read-write
   STATUS      current
   DESCRIPTION
       "default: 0 ,
        0: doNothing
        1: renew"
   ::= { gs2310pHTTPS 3 }

gs2310pHTTPSMinProtoVersion OBJECT-TYPE
   SYNTAX      INTEGER { SSLv3(0), TLSv1(1), TLSv11(2), TLSv12(3)}
   MAX-ACCESS  read-write
   STATUS      current
   DESCRIPTION
       "default: 1
        0: SSLv3
        1: TLSv1
        2: TLSv1.1
        3: TLSv1.2"
   ::= { gs2310pHTTPS 4 }

gs2310pHTTPMode OBJECT-TYPE
   SYNTAX      INTEGER { disable(0), enable(1) }
   MAX-ACCESS  read-write
   STATUS      current
   DESCRIPTION
       "default: 1
        0: disable
        1: enable"
   ::= { gs2310pHTTPS 5 }

gs2310pAuthMethod                                            OBJECT IDENTIFIER ::= { gs2310pSecurity 9 }

gs2310pConsoleAuthMethod OBJECT-TYPE
   SYNTAX      INTEGER { none(0), local(1), radius(2), tacacsplus(3) }
   MAX-ACCESS  read-write
   STATUS      current
   DESCRIPTION
       "default: 1
        0: none
        1: local
        2: RADIUS
        3: TACACS+"
   ::= { gs2310pAuthMethod 1 }

gs2310pConsoleFallback OBJECT-TYPE
   SYNTAX      INTEGER { disable(0), enable(1) }
   MAX-ACCESS  read-write
   STATUS      current
   DESCRIPTION
       "default: 0
        0:disable
        1:enable"
   ::= { gs2310pAuthMethod 2 }

gs2310pTelnetAuthMethod OBJECT-TYPE
   SYNTAX      INTEGER { none(0), local(1), radius(2), tacacsplus(3) }
   MAX-ACCESS  read-write
   STATUS      current
   DESCRIPTION
       "default: 1
        0: none
        1: local
        2: RADIUS
        3: TACACS+"
   ::= { gs2310pAuthMethod 3 }

gs2310pTelnetFallback OBJECT-TYPE
   SYNTAX      INTEGER { disable(0), enable(1) }
   MAX-ACCESS  read-write
   STATUS      current
   DESCRIPTION
       "default: 0
        0:disable
        1:enable"
   ::= { gs2310pAuthMethod 4 }

gs2310pSshAuthMethod OBJECT-TYPE
   SYNTAX      INTEGER { none(0), local(1), radius(2), tacacsplus(3) }
   MAX-ACCESS  read-write
   STATUS      current
   DESCRIPTION
       "default: 1
        0: none
        1: local
        2: RADIUS
        3: TACACS+"
   ::= { gs2310pAuthMethod 5 }

gs2310pSshFallback OBJECT-TYPE
   SYNTAX      INTEGER { disable(0), enable(1) }
   MAX-ACCESS  read-write
   STATUS      current
   DESCRIPTION
       "default: 0
        0:disable
        1:enable"
   ::= { gs2310pAuthMethod 6 }

gs2310pTftpAuthMethod OBJECT-TYPE
   SYNTAX      INTEGER { none(0), local(1), radius(2), tacacsplus(3) }
   MAX-ACCESS  read-write
   STATUS      current
   DESCRIPTION
       "default: 1
        0: none
        1: local
        2: RADIUS
        3: TACACS+"
   ::= { gs2310pAuthMethod 9 }

gs2310pTftpFallback OBJECT-TYPE
   SYNTAX      INTEGER { disable(0), enable(1) }
   MAX-ACCESS  read-write
   STATUS      current
   DESCRIPTION
       "default: 0
        0:disable
        1:enable"
   ::= { gs2310pAuthMethod 10 }

gs2310pLoginFailures OBJECT-TYPE
   SYNTAX      Integer32(0..99)
   MAX-ACCESS  read-write
   STATUS      current
   DESCRIPTION
       "When login failures mechanism is triggered,the lock minutes will prevent to login in this periods.
        The value '0' should deactivate this feature.
        range: 0-99.
        default: 5."
   ::= { gs2310pAuthMethod 11 }

gs2310pLockMinutes OBJECT-TYPE
   SYNTAX      Integer32(1..99)
   MAX-ACCESS  read-write
   STATUS      current
   DESCRIPTION
       "Lock time to login failures trigger.
        range: 1-99.
        default: 5."
   ::= { gs2310pAuthMethod 12 }

gs2310pHttpAuthMethod OBJECT-TYPE
   SYNTAX      INTEGER { none(0), local(1), radius(2), tacacsplus(3) }
   MAX-ACCESS  read-write
   STATUS      current
   DESCRIPTION
       "default: 1
        0: none
        1: local
        2: RADIUS
        3: TACACS+"
   ::= { gs2310pAuthMethod 13 }

gs2310pHttpFallback OBJECT-TYPE
   SYNTAX      INTEGER { disable(0), enable(1) }
   MAX-ACCESS  read-write
   STATUS      current
   DESCRIPTION
       "default: 0
        0:disable
        1:enable"
   ::= { gs2310pAuthMethod 14 }

gs2310pHttpsAuthMethod OBJECT-TYPE
   SYNTAX      INTEGER { none(0), local(1), radius(2), tacacsplus(3) }
   MAX-ACCESS  read-write
   STATUS      current
   DESCRIPTION
       "default: 1
        0: none
        1: local
        2: RADIUS
        3: TACACS+"
   ::= { gs2310pAuthMethod 15 }

gs2310pHttpsFallback OBJECT-TYPE
   SYNTAX      INTEGER { disable(0), enable(1) }
   MAX-ACCESS  read-write
   STATUS      current
   DESCRIPTION
       "default: 0
        0:disable
        1:enable"
   ::= { gs2310pAuthMethod 16 }


gs2310pAAA                                              OBJECT IDENTIFIER ::= { gs2310pSecurity 10 }

gs2310pAAACommonServer                                  OBJECT IDENTIFIER ::= { gs2310pAAA 1 }

gs2310pAAACommonServerTimeout OBJECT-TYPE
   SYNTAX      Integer32(3..3600)
   MAX-ACCESS  read-write
   STATUS      current
   DESCRIPTION
       "The Timeout, which can be set to a number between 3 and 3600 seconds, is
       the maximum time to wait for a reply from a server. If the server does not
       reply within this timeframe, we will consider it to be dead and continue
       with the next enabled server (if any). RADIUS servers are using the UDP
       protocol, which is unreliable by design. In order to cope with lost frames,
       the timeout interval is divided into 3 subintervals of equal length. If a
       reply is not received within the subinterval, the request is transmitted
       again. This algorithm causes the RADIUS server to be queried up to 3 times
       before it is considered to be dead.
        default: 15."
   ::= { gs2310pAAACommonServer 1 }

gs2310pAAACommonServerDeadTime OBJECT-TYPE
   SYNTAX      Integer32(0..3600)
   MAX-ACCESS  read-write
   STATUS      current
   DESCRIPTION
       "The Dead Time, which can be set to a number between 0 and 3600 seconds,
       is the period during which the switch will not send new requests to a
       server that has failed to respond to a previous request. This will stop
       the switch from continually trying to contact a server that it has already
       determined as dead.
       Setting the Dead Time to a value greater than 0 (zero) will enable this feature,
       but only if more than one server has been configured.
       default: 300."
   ::= { gs2310pAAACommonServer 2 }

gs2310pAAATACACSPlusAuthAndAccounting                  OBJECT IDENTIFIER ::= { gs2310pAAA 2 }

gs2310pAAAAuthorization OBJECT-TYPE
   SYNTAX      INTEGER { disable(0), enable(1) }
   MAX-ACCESS  read-write
   STATUS      current
   DESCRIPTION
       "Authorization is the action of determining what a user is allowed to do.
       An authorization request may indicate that the user is not authenticated.
       In this case it is up to the authorization agent to determine if an
       unauthenticated user is allowed the services in question. "
   ::= { gs2310pAAATACACSPlusAuthAndAccounting 1 }

gs2310pAAAFallbackToLocalAuthorization OBJECT-TYPE
   SYNTAX      INTEGER { disable(0), enable(1) }
   MAX-ACCESS  read-write
   STATUS      current
   DESCRIPTION
       "This function is an auxiliary function of Authorization. When the DUT
       cannot communicate with TACACS+ Server normally, it will check the right/
        permission level of the Local Account to execute the Authorization. "
   ::= { gs2310pAAATACACSPlusAuthAndAccounting 2 }

gs2310pAAAAccounting OBJECT-TYPE
   SYNTAX      INTEGER { disable(0), enable(1) }
   MAX-ACCESS  read-write
   STATUS      current
   DESCRIPTION
       "Accounting is typically the third action after authentication and
       authorization. Accounting is the action of recording what a user is doing,
       and/or has done. TACACS+ accounting records contain all the information
       used in the authorization records and resource usage information. "
   ::= { gs2310pAAATACACSPlusAuthAndAccounting 3 }

gs2310pRADIUSAuthenticationServerTable OBJECT-TYPE
   SYNTAX      SEQUENCE OF Gs2310pRADIUSAuthenticationServerEntry
   MAX-ACCESS  not-accessible
   STATUS      current
   DESCRIPTION
       " "
   ::= { gs2310pAAA 3 }

gs2310pRADIUSAuthenticationServerEntry OBJECT-TYPE
   SYNTAX      Gs2310pRADIUSAuthenticationServerEntry
   MAX-ACCESS  not-accessible
   STATUS      current
   DESCRIPTION
       ""
   INDEX    { gs2310pRADIUSAuthenticationServerIndex  }
   ::= { gs2310pRADIUSAuthenticationServerTable 1 }

Gs2310pRADIUSAuthenticationServerEntry ::= SEQUENCE {
   gs2310pRADIUSAuthenticationServerIndex     Integer32,
   gs2310pRADIUSAuthenticationServerEnable    INTEGER,
   gs2310pRADIUSAuthenticationServerIP        DisplayString,
   gs2310pRADIUSAuthenticationServerPort      Integer32,
   gs2310pRADIUSAuthenticationServerSecret    DisplayString
}

gs2310pRADIUSAuthenticationServerIndex OBJECT-TYPE
   SYNTAX      Integer32(1..5)
   MAX-ACCESS  not-accessible
   STATUS      current
   DESCRIPTION
       "RADIUS Authentication Server index
        range : 1-5."
   ::= { gs2310pRADIUSAuthenticationServerEntry 1 }

gs2310pRADIUSAuthenticationServerEnable OBJECT-TYPE
   SYNTAX      INTEGER { disable(0), enable(1) }
   MAX-ACCESS  read-write
   STATUS      current
   DESCRIPTION
       "Enable/Disable the RADIUS Authentication Server. the RADIUSAuthenticationServerEnable
       can be set, when IP and Secret have value "
   ::= { gs2310pRADIUSAuthenticationServerEntry 2 }

gs2310pRADIUSAuthenticationServerIP OBJECT-TYPE
   SYNTAX      DisplayString
   MAX-ACCESS  read-write
   STATUS      current
   DESCRIPTION
       "The IP address or hostname of the RADIUS Authentication Server.
       IP address is expressed in  dotted decimal notation. "
   ::= { gs2310pRADIUSAuthenticationServerEntry 3 }

gs2310pRADIUSAuthenticationServerPort OBJECT-TYPE
   SYNTAX      Integer32(0..65535)
   MAX-ACCESS  read-write
   STATUS      current
   DESCRIPTION
       "The UDP port to use on the RADIUS Authentication Server. If the port is
       set to 0 (zero), the default port (1812) is used on the RADIUS Authentication Server. "
   ::= { gs2310pRADIUSAuthenticationServerEntry 4 }

gs2310pRADIUSAuthenticationServerSecret OBJECT-TYPE
   SYNTAX      DisplayString
   MAX-ACCESS  read-write
   STATUS      current
   DESCRIPTION
       "The secret - up to 64 characters long - shared between the RADIUS Authentication Server and the switch. "
   ::= { gs2310pRADIUSAuthenticationServerEntry 5 }


gs2310pRADIUSAccountingServerTable OBJECT-TYPE
   SYNTAX      SEQUENCE OF Gs2310pRADIUSAccountingServerEntry
   MAX-ACCESS  not-accessible
   STATUS      current
   DESCRIPTION
       " "
   ::= { gs2310pAAA 4 }

gs2310pRADIUSAccountingServerEntry OBJECT-TYPE
   SYNTAX      Gs2310pRADIUSAccountingServerEntry
   MAX-ACCESS  not-accessible
   STATUS      current
   DESCRIPTION
       ""
   INDEX    { gs2310pRADIUSAccountingServerIndex  }
   ::= { gs2310pRADIUSAccountingServerTable 1 }

Gs2310pRADIUSAccountingServerEntry ::= SEQUENCE {
   gs2310pRADIUSAccountingServerIndex     Integer32,
   gs2310pRADIUSAccountingServerEnable    INTEGER,
   gs2310pRADIUSAccountingServerIP        DisplayString,
   gs2310pRADIUSAccountingServerPort      Integer32,
   gs2310pRADIUSAccountingServerSecret    DisplayString
}

gs2310pRADIUSAccountingServerIndex OBJECT-TYPE
   SYNTAX      Integer32(1..5)
   MAX-ACCESS  not-accessible
   STATUS      current
   DESCRIPTION
       "RADIUS Accounting Server index
        range : 1-5."
   ::= { gs2310pRADIUSAccountingServerEntry 1 }

gs2310pRADIUSAccountingServerEnable OBJECT-TYPE
   SYNTAX      INTEGER { disable(0), enable(1) }
   MAX-ACCESS  read-write
   STATUS      current
   DESCRIPTION
       "Enable/Disable the RADIUS Accounting Server. The RADIUSAccountingServerEnable
       can be set, when IP and Secret have value. "
   ::= { gs2310pRADIUSAccountingServerEntry 2 }

gs2310pRADIUSAccountingServerIP OBJECT-TYPE
   SYNTAX      DisplayString
   MAX-ACCESS  read-write
   STATUS      current
   DESCRIPTION
       "The IP address or hostname of the RADIUS Accounting Server.
       IP address is expressed in  dotted decimal notation. "
   ::= { gs2310pRADIUSAccountingServerEntry 3 }

gs2310pRADIUSAccountingServerPort OBJECT-TYPE
   SYNTAX      Integer32(0..65535)
   MAX-ACCESS  read-write
   STATUS      current
   DESCRIPTION
       "The UDP port to use on the RADIUS Accounting Server. If the port is
       set to 0 (zero), the default port (1812) is used on the RADIUS Accounting Server. "
   ::= { gs2310pRADIUSAccountingServerEntry 4 }

gs2310pRADIUSAccountingServerSecret OBJECT-TYPE
   SYNTAX      DisplayString
   MAX-ACCESS  read-write
   STATUS      current
   DESCRIPTION
       "The secret - up to 64 characters long - shared between the RADIUS Accounting Server and the switch. "
   ::= { gs2310pRADIUSAccountingServerEntry 5 }

gs2310pTACACSPlusAuthenticationServerTable OBJECT-TYPE
   SYNTAX      SEQUENCE OF Gs2310pTACACSPlusAuthenticationServerEntry
   MAX-ACCESS  not-accessible
   STATUS      current
   DESCRIPTION
       " "
   ::= { gs2310pAAA 5 }

gs2310pTACACSPlusAuthenticationServerEntry OBJECT-TYPE
   SYNTAX      Gs2310pTACACSPlusAuthenticationServerEntry
   MAX-ACCESS  not-accessible
   STATUS      current
   DESCRIPTION
       ""
   INDEX    { gs2310pTACACSPlusAuthenticationServerIndex  }
   ::= { gs2310pTACACSPlusAuthenticationServerTable 1 }

Gs2310pTACACSPlusAuthenticationServerEntry ::= SEQUENCE {
   gs2310pTACACSPlusAuthenticationServerIndex     Integer32,
   gs2310pTACACSPlusAuthenticationServerEnable    INTEGER,
   gs2310pTACACSPlusAuthenticationServerIP        DisplayString,
   gs2310pTACACSPlusAuthenticationServerPort      Integer32,
   gs2310pTACACSPlusAuthenticationServerSecret    DisplayString
}

gs2310pTACACSPlusAuthenticationServerIndex OBJECT-TYPE
   SYNTAX      Integer32(1..5)
   MAX-ACCESS  not-accessible
   STATUS      current
   DESCRIPTION
       "TACACSPlus Authentication Server index
        range : 1-5."
   ::= { gs2310pTACACSPlusAuthenticationServerEntry 1 }

gs2310pTACACSPlusAuthenticationServerEnable OBJECT-TYPE
   SYNTAX      INTEGER { disable(0), enable(1) }
   MAX-ACCESS  read-write
   STATUS      current
   DESCRIPTION
       "Enable/Disable the TACACSPlus Authentication Server. The
       TACACSPlusAuthenticationServerEnable can be set, when IP and Secret have
       value."
   ::= { gs2310pTACACSPlusAuthenticationServerEntry 2 }

gs2310pTACACSPlusAuthenticationServerIP OBJECT-TYPE
   SYNTAX      DisplayString
   MAX-ACCESS  read-write
   STATUS      current
   DESCRIPTION
       "The IP address or hostname of the TACACSPlus Authentication Server.
       IP address is expressed in  dotted decimal notation. "
   ::= { gs2310pTACACSPlusAuthenticationServerEntry 3 }

gs2310pTACACSPlusAuthenticationServerPort OBJECT-TYPE
   SYNTAX      Integer32(0..65535)
   MAX-ACCESS  read-write
   STATUS      current
   DESCRIPTION
       "The UDP port to use on the TACACSPlus Authentication Server. If the
       port is set to 0 (zero), the default port (1812) is used on the
       TACACSPlus Authentication Server. "
   ::= { gs2310pTACACSPlusAuthenticationServerEntry 4 }

gs2310pTACACSPlusAuthenticationServerSecret OBJECT-TYPE
   SYNTAX      DisplayString
   MAX-ACCESS  read-write
   STATUS      current
   DESCRIPTION
       "The secret - up to 64 characters long - shared between the TACACSPlus Authentication Server and the switch. "
   ::= { gs2310pTACACSPlusAuthenticationServerEntry 5 }


gs2310pRADIUSStatisticsTable OBJECT-TYPE
   SYNTAX      SEQUENCE OF Gs2310pRADIUSStatisticsEntry
   MAX-ACCESS  not-accessible
   STATUS      current
   DESCRIPTION
       " "
   ::= { gs2310pAAA 6 }

gs2310pRADIUSStatisticsEntry OBJECT-TYPE
   SYNTAX      Gs2310pRADIUSStatisticsEntry
   MAX-ACCESS  not-accessible
   STATUS      current
   DESCRIPTION
       ""
   INDEX    { gs2310pRADIUSAuthStatisticsServerIndex  }
   ::= { gs2310pRADIUSStatisticsTable 1 }

Gs2310pRADIUSStatisticsEntry ::= SEQUENCE {
   gs2310pRADIUSAuthStatisticsServerIndex                           Integer32,
   gs2310pRADIUSAuthStatisticsRecPktAccessAccepts                   Counter32,
   gs2310pRADIUSAuthStatisticsRecPktAccessRejects                   Counter32,
   gs2310pRADIUSAuthStatisticsRecPktAccessChallenges                Counter32,
   gs2310pRADIUSAuthStatisticsRecPktMalformedAccResponses           Counter32,
   gs2310pRADIUSAuthStatisticsRecPktBadAuthenticators               Counter32,
   gs2310pRADIUSAuthStatisticsRecPktUnknownTypes                    Counter32,
   gs2310pRADIUSAuthStatisticsRecPktDropped                         Counter32,
   gs2310pRADIUSAuthStatisticsTransmitPktAccessRequests             Counter32,
   gs2310pRADIUSAuthStatisticsTransmitPktAccessRetransmissions      Counter32,
   gs2310pRADIUSAuthStatisticsTransmitPktPendingRequests            Counter32,
   gs2310pRADIUSAuthStatisticsTransmitPktTimeouts                   Counter32,
   gs2310pRADIUSAuthIP                                              DisplayString,
   gs2310pRADIUSAuthState                                           DisplayString,
   gs2310pRADIUSAuthRoundTripTime                                   DisplayString,

   gs2310pRADIUSAccountingStatisticsRecPktResponses                 Counter32,
   gs2310pRADIUSAccountingStatisticsRecPktMalformedResponses        Counter32,
   gs2310pRADIUSAccountingStatisticsRecPktBadAuthenticators         Counter32,
   gs2310pRADIUSAccountingStatisticsRecPktUnknownTypes              Counter32,
   gs2310pRADIUSAccountingStatisticsRecPktDropped                   Counter32,
   gs2310pRADIUSAccountingStatisticsTransmitPktRequests             Counter32,
   gs2310pRADIUSAccountingStatisticsTransmitPktRetransmissions      Counter32,
   gs2310pRADIUSAccountingStatisticsTransmitPktPendingRequests      Counter32,
   gs2310pRADIUSAccountingStatisticsTransmitPktTimeouts             Counter32,
   gs2310pRADIUSAccountingIP                                        DisplayString,
   gs2310pRADIUSAccountingState                                     DisplayString,
   gs2310pRADIUSAccountingRoundTripTime                             DisplayString,
   gs2310pRADIUSStatisticsClear                                     INTEGER
}

gs2310pRADIUSAuthStatisticsServerIndex OBJECT-TYPE
   SYNTAX      Integer32(1..5)
   MAX-ACCESS  not-accessible
   STATUS      current
   DESCRIPTION
       "RADIUS Authentication Server index
        range : 1-5."
   ::= { gs2310pRADIUSStatisticsEntry 1 }

gs2310pRADIUSAuthStatisticsRecPktAccessAccepts OBJECT-TYPE
   SYNTAX      Counter32
   MAX-ACCESS  read-only
   STATUS      current
   DESCRIPTION
       "The number of RADIUS Access-Accept packets (valid or invalid) received from the server."
   ::= { gs2310pRADIUSStatisticsEntry 2 }

gs2310pRADIUSAuthStatisticsRecPktAccessRejects OBJECT-TYPE
   SYNTAX      Counter32
   MAX-ACCESS  read-only
   STATUS      current
   DESCRIPTION
       "The number of RADIUS Access-Reject packets (valid or invalid) received from the server."
   ::= { gs2310pRADIUSStatisticsEntry 3 }

gs2310pRADIUSAuthStatisticsRecPktAccessChallenges OBJECT-TYPE
   SYNTAX      Counter32
   MAX-ACCESS  read-only
   STATUS      current
   DESCRIPTION
       "The number of RADIUS Access-Challenge packets (valid or invalid) received from the server. "
   ::= { gs2310pRADIUSStatisticsEntry 4 }

gs2310pRADIUSAuthStatisticsRecPktMalformedAccResponses OBJECT-TYPE
   SYNTAX      Counter32
   MAX-ACCESS  read-only
   STATUS      current
   DESCRIPTION
       "The number of malformed RADIUS Access-Response packets received from the
        server. Malformed packets include packets with an invalid length. Bad
        authenticators or Message Authenticator attributes or unknown types are
        not included as malformed access responses. "
   ::= { gs2310pRADIUSStatisticsEntry 5 }

gs2310pRADIUSAuthStatisticsRecPktBadAuthenticators OBJECT-TYPE
   SYNTAX      Counter32
   MAX-ACCESS  read-only
   STATUS      current
   DESCRIPTION
       "The number of RADIUS Access-Response packets containing invalid
       authenticators or Message Authenticator attributes received from the server."
   ::= { gs2310pRADIUSStatisticsEntry 6 }

gs2310pRADIUSAuthStatisticsRecPktUnknownTypes OBJECT-TYPE
   SYNTAX      Counter32
   MAX-ACCESS  read-only
   STATUS      current
   DESCRIPTION
       "The number of RADIUS packets that were received with unknown types from
       the server on the authentication port and dropped."
   ::= { gs2310pRADIUSStatisticsEntry 7 }

gs2310pRADIUSAuthStatisticsRecPktDropped OBJECT-TYPE
   SYNTAX      Counter32
   MAX-ACCESS  read-only
   STATUS      current
   DESCRIPTION
       "The number of RADIUS packets that were received from the server on the
       authentication port and dropped for some other reason."
   ::= { gs2310pRADIUSStatisticsEntry 8 }

gs2310pRADIUSAuthStatisticsTransmitPktAccessRequests OBJECT-TYPE
   SYNTAX      Counter32
   MAX-ACCESS  read-only
   STATUS      current
   DESCRIPTION
       "The number of RADIUS Access-Request packets sent to the server. This
       does not include retransmissions."
   ::= { gs2310pRADIUSStatisticsEntry 9 }

gs2310pRADIUSAuthStatisticsTransmitPktAccessRetransmissions OBJECT-TYPE
   SYNTAX      Counter32
   MAX-ACCESS  read-only
   STATUS      current
   DESCRIPTION
       "The number of RADIUS Access-Request packets retransmitted to the RADIUS
       authentication server."
   ::= { gs2310pRADIUSStatisticsEntry 10 }

gs2310pRADIUSAuthStatisticsTransmitPktPendingRequests OBJECT-TYPE
   SYNTAX      Counter32
   MAX-ACCESS  read-only
   STATUS      current
   DESCRIPTION
       "The number of RADIUS Access-Request packets destined for the server that
        have not yet timed out or received a response. This variable is
        incremented when an Access-Request is sent and decremented due to
        receipt of an Access-Accept, Access-Reject, Access-Challenge, timeout,
        or retransmission. "
   ::= { gs2310pRADIUSStatisticsEntry 11 }

gs2310pRADIUSAuthStatisticsTransmitPktTimeouts OBJECT-TYPE
   SYNTAX      Counter32
   MAX-ACCESS  read-only
   STATUS      current
   DESCRIPTION
       "The number of authentication timeouts to the server. After a timeout,
       the client may retry to the same server, send to a different server, or
       give up. A retry to the same server is counted as a retransmit as well as
        a timeout. A send to a different server is counted as a Request as well
        as a timeout. "
   ::= { gs2310pRADIUSStatisticsEntry 12 }

gs2310pRADIUSAuthIP OBJECT-TYPE
   SYNTAX      DisplayString
   MAX-ACCESS  read-only
   STATUS      current
   DESCRIPTION
       "IP address and UDP port for the authentication server in question."
   ::= { gs2310pRADIUSStatisticsEntry 13 }

gs2310pRADIUSAuthState OBJECT-TYPE
   SYNTAX      DisplayString
   MAX-ACCESS  read-only
   STATUS      current
   DESCRIPTION
       "Shows the state of the server. It takes one of the following values:
        Disabled: The selected server is disabled.
        Not Ready: The server is enabled, but IP communication is not yet up and running.
        Ready: The server is enabled, IP communication is up and running, and the RADIUS
         module is ready to accept access attempts.
        Dead (X seconds left): Access attempts were made to this server, but it did not
        reply within the configured timeout. The server has temporarily been disabled,
        but will get re-enabled when the dead-time expires. The number of seconds left
        before this occurs is displayed in parentheses. This state is only reachable
        when more than one server is enabled. "
   ::= { gs2310pRADIUSStatisticsEntry 14 }

gs2310pRADIUSAuthRoundTripTime OBJECT-TYPE
   SYNTAX      DisplayString
   MAX-ACCESS  read-only
   STATUS      current
   DESCRIPTION
       "The time interval (measured in milliseconds) between the most recent
       Access-Reply/Access-Challenge and the Access-Request that matched it from
        the RADIUS authentication server. The granularity of this measurement is
         100 ms. A value of 0 ms indicates that there hasn't been round-trip
         communication with the server yet. "
   ::= { gs2310pRADIUSStatisticsEntry 15 }

gs2310pRADIUSAccountingStatisticsRecPktResponses OBJECT-TYPE
   SYNTAX      Counter32
   MAX-ACCESS  read-only
   STATUS      current
   DESCRIPTION
       "The number of RADIUS packets (valid or invalid) received from the server."
   ::= { gs2310pRADIUSStatisticsEntry 16 }

gs2310pRADIUSAccountingStatisticsRecPktMalformedResponses OBJECT-TYPE
   SYNTAX      Counter32
   MAX-ACCESS  read-only
   STATUS      current
   DESCRIPTION
       "The number of malformed RADIUS packets received from the server.
       Malformed packets include packets with an invalid length. Bad
       authenticators or unknown types are not included as malformed access
       responses. "
   ::= { gs2310pRADIUSStatisticsEntry 17 }

gs2310pRADIUSAccountingStatisticsRecPktBadAuthenticators OBJECT-TYPE
   SYNTAX      Counter32
   MAX-ACCESS  read-only
   STATUS      current
   DESCRIPTION
       "The number of RADIUS packets containing invalid authenticators received
       from the server."
   ::= { gs2310pRADIUSStatisticsEntry 18 }

gs2310pRADIUSAccountingStatisticsRecPktUnknownTypes OBJECT-TYPE
   SYNTAX      Counter32
   MAX-ACCESS  read-only
   STATUS      current
   DESCRIPTION
       "The number of RADIUS packets of unknown types that were received from
       the server on the accounting port."
   ::= { gs2310pRADIUSStatisticsEntry 19 }

gs2310pRADIUSAccountingStatisticsRecPktDropped OBJECT-TYPE
   SYNTAX      Counter32
   MAX-ACCESS  read-only
   STATUS      current
   DESCRIPTION
       "The number of RADIUS packets that were received from the server on the
       accounting port and dropped for some other reason."
   ::= { gs2310pRADIUSStatisticsEntry 20 }

gs2310pRADIUSAccountingStatisticsTransmitPktRequests OBJECT-TYPE
   SYNTAX      Counter32
   MAX-ACCESS  read-only
   STATUS      current
   DESCRIPTION
       "The number of RADIUS packets sent to the server. This does not include
       retransmissions."
   ::= { gs2310pRADIUSStatisticsEntry 21 }

gs2310pRADIUSAccountingStatisticsTransmitPktRetransmissions OBJECT-TYPE
   SYNTAX      Counter32
   MAX-ACCESS  read-only
   STATUS      current
   DESCRIPTION
       "The number of RADIUS packets retransmitted to the RADIUS accounting server."
   ::= { gs2310pRADIUSStatisticsEntry 22 }

gs2310pRADIUSAccountingStatisticsTransmitPktPendingRequests OBJECT-TYPE
   SYNTAX      Counter32
   MAX-ACCESS  read-only
   STATUS      current
   DESCRIPTION
       "The number of RADIUS packets destined for the server that have not yet
       timed out or received a response. This variable is incremented when a
       Request is sent and decremented due to receipt of a Response, timeout,
       or retransmission. "
   ::= { gs2310pRADIUSStatisticsEntry 23 }

gs2310pRADIUSAccountingStatisticsTransmitPktTimeouts OBJECT-TYPE
   SYNTAX      Counter32
   MAX-ACCESS  read-only
   STATUS      current
   DESCRIPTION
       "The number of accounting timeouts to the server. After a timeout, the
       client may retry to the same server, send to a different server, or give
       up. A retry to the same server is counted as a retransmit as well as a
       timeout. A send to a different server is counted as a Request as well as
       a timeout. "
   ::= { gs2310pRADIUSStatisticsEntry 24 }

gs2310pRADIUSAccountingIP OBJECT-TYPE
   SYNTAX      DisplayString
   MAX-ACCESS  read-only
   STATUS      current
   DESCRIPTION
       "IP address and UDP port for the accounting server in question."
   ::= { gs2310pRADIUSStatisticsEntry 25 }

gs2310pRADIUSAccountingState OBJECT-TYPE
   SYNTAX      DisplayString
   MAX-ACCESS  read-only
   STATUS      current
   DESCRIPTION
       " Shows the state of the server. It takes one of the following values:
        Disabled: The selected server is disabled.
        Not Ready: The server is enabled, but IP communication is not yet up and running.
        Ready: The server is enabled, IP communication is up and running, and the RADIUS
        module is ready to accept accounting attempts.
        Dead (X seconds left): Accounting attempts were made to this server, but it did
        not reply within the configured timeout. The server has temporarily been
        disabled, but will get re-enabled when the dead-time expires. The number of
        seconds left before this occurs is displayed in parentheses. This state is only
        reachable when more than one server is enabled.  "
   ::= { gs2310pRADIUSStatisticsEntry 26 }

gs2310pRADIUSAccountingRoundTripTime OBJECT-TYPE
   SYNTAX      DisplayString
   MAX-ACCESS  read-only
   STATUS      current
   DESCRIPTION
       "The time interval (measured in milliseconds) between the most recent
       Response and the Request that matched it from the RADIUS accounting
       server. The granularity of this measurement is 100 ms. A value of 0 ms
       indicates that there hasn't been round-trip communication with the server
       yet. "
   ::= { gs2310pRADIUSStatisticsEntry 27 }

gs2310pRADIUSStatisticsClear OBJECT-TYPE
   SYNTAX      INTEGER(0|1)
   MAX-ACCESS  read-write
   STATUS      current
   DESCRIPTION
       "Clears the counters for the server.
       read: always 0
       clear: set 1"
   ::= { gs2310pRADIUSStatisticsEntry 28 }

gs2310pNAS                                              OBJECT IDENTIFIER ::= { gs2310pSecurity 11 }

gs2310pNASConfiguration                                 OBJECT IDENTIFIER ::= { gs2310pNAS 1 }

gs2310pNASConfigMode OBJECT-TYPE
   SYNTAX      INTEGER { disable(0), enable(1) }
   MAX-ACCESS  read-write
   STATUS      current
   DESCRIPTION
       "Indicates if NAS is globally enabled or disabled on the switch.
	    If globally disabled, all ports are allowed forwarding of frames."
   ::= { gs2310pNASConfiguration 1 }

gs2310pNASConfigReauthEnabled OBJECT-TYPE
   SYNTAX      INTEGER { disable(0), enable(1) }
   MAX-ACCESS  read-write
   STATUS      current
   DESCRIPTION
       "If checked, successfully authenticated supplicants/clients are
	    reauthenticated after the interval specified by the Reauthentication
		Period. Reauthentication for 802.1X-enabled ports can be used to
		detect if a new device is plugged into a switch port or if a
		supplicant is no longer attached.
		For MAC-based ports, reauthentication is only useful if the RADIUS
		server configuration has changed. It does not involve communication
		between the switch and the client, and therefore doesn't imply that
		a client is still present on a port."
   ::= { gs2310pNASConfiguration 2 }

gs2310pNASConfigReauthPeriod OBJECT-TYPE
   SYNTAX      Integer32(1..3600)
   MAX-ACCESS  read-write
   STATUS      current
   DESCRIPTION
       "Determines the period, in seconds, after which a connected client must
	    be reauthenticated. This is only active if the Reauthentication Enabled
		checkbox is checked.
		range: 1 - 3600 seconds."
   ::= { gs2310pNASConfiguration 3 }

gs2310pNASConfigEAPOLTimeout OBJECT-TYPE
   SYNTAX      Integer32(1..65535)
   MAX-ACCESS  read-write
   STATUS      current
   DESCRIPTION
       "Determines the time for retransmission of Request Identity EAPOL frames.
	    This has no effect for MAC-based ports.
		range: 1 - 65535 seconds."
   ::= { gs2310pNASConfiguration 4 }

gs2310pNASConfigAgingPeriod OBJECT-TYPE
   SYNTAX      Integer32(10..1000000)
   MAX-ACCESS  read-write
   STATUS      current
   DESCRIPTION
       "When the NAS module uses the Port Security module to secure MAC addresses,
	    the Port Security module needs to check for activity on the MAC address
		in question at regular intervals and free resources if no activity
		is seen within a given period of time.
		Admin State supported : Single, Multi and MAC-Based Auth. 802.1X.
		range: 10 - 1000000 seconds."
   ::= { gs2310pNASConfiguration 5 }

gs2310pNASConfigHoldTime OBJECT-TYPE
   SYNTAX      Integer32(10..1000000)
   MAX-ACCESS  read-write
   STATUS      current
   DESCRIPTION
       "If a client is denied access - either because the RADIUS server denies
	    the client access or because the RADIUS server request times out
		- the client is put on hold in the Unauthorized state. The hold timer
		does not count during an on-going authentication. In MAC-based Auth.
		mode, the switch will ignore new frames coming from the client during
		the hold time.
		Admin State supported : Single, Multi and MAC-Based Auth. 802.1X.
		range: 10 - 1000000 seconds."
   ::= { gs2310pNASConfiguration 6 }

gs2310pNASConfigRADIUSAssignedQoSEnabled OBJECT-TYPE
   SYNTAX      INTEGER { disable(0), enable(1) }
   MAX-ACCESS  read-write
   STATUS      current
   DESCRIPTION
       "RADIUS-assigned QoS provides a means to centrally control the
	    traffic class to which traffic coming from a successfully authenticated
		supplicant is assigned on the switch. The RADIUS server must be configured
		to transmit special RADIUS attributes to take advantage of this feature."
   ::= { gs2310pNASConfiguration 7 }

gs2310pNASConfigRADIUSAssignedVLANEnabled OBJECT-TYPE
   SYNTAX      INTEGER { disable(0), enable(1) }
   MAX-ACCESS  read-write
   STATUS      current
   DESCRIPTION
       "RADIUS-assigned VLAN provides a means to centrally control the VLAN on
	    which a successfully authenticated supplicant is placed on the switch.
	    Incoming traffic will be classified to and switched on the RADIUS-assigned
		VLAN. The RADIUS server must be configured to transmit special RADIUS
		attributes to take advantage of this feature.When enable, the individual
		ports' ditto setting determine whether RADIUS-assigned VLAN is enabled
		on that port. When disable, RADIUS-server assigned VLAN is disabled on
		all ports. "
   ::= { gs2310pNASConfiguration 8 }

gs2310pNASConfigGuestVLANEnabled OBJECT-TYPE
   SYNTAX      INTEGER { disable(0), enable(1) }
   MAX-ACCESS  read-write
   STATUS      current
   DESCRIPTION
       "A Guest VLAN is a special VLAN - typically with limited network access -
	   on which 802.1X-unaware clients are placed after a network administrator-defined
	   timeout. The switch follows a set of rules for entering and leaving the Guest
	   VLAN as listed below.When enable, the individual ports' ditto setting determines
	   whether the port can be moved into Guest VLAN. When disable, the ability to
	   move to the Guest VLAN is disabled on all ports. "
   ::= { gs2310pNASConfiguration 9 }

gs2310pNASConfigGuestVLANID OBJECT-TYPE
   SYNTAX      Integer32(1..4094)
   MAX-ACCESS  read-write
   STATUS      current
   DESCRIPTION
       "This is the value that a port's Port VLAN ID is set to if a port is moved into
	   the Guest VLAN. It is only changeable if the Guest VLAN option is globally enabled.
	   range: 1 - 4094."
   ::= { gs2310pNASConfiguration 10 }

gs2310pNASConfigMaxReauthCount OBJECT-TYPE
   SYNTAX      Integer32(1..255)
   MAX-ACCESS  read-write
   STATUS      current
   DESCRIPTION
       "The number of times the switch transmits an EAPOL Request Identity frame without
	   response before considering entering the Guest VLAN is adjusted with this setting.
	   The value can only be changed if the Guest VLAN option is globally enabled.
	   range: 1 - 255."
   ::= { gs2310pNASConfiguration 11 }

gs2310pNASConfigAllowGuestVLANEAPOLSeen OBJECT-TYPE
   SYNTAX      INTEGER { disable(0), enable(1) }
   MAX-ACCESS  read-write
   STATUS      current
   DESCRIPTION
       "The switch remembers if an EAPOL frame has been received on the port for the
	   life-time of the port. Once the switch considers whether to enter the Guest VLAN,
	   it will first check if this option is enabled or disabled. If disabled, the switch
	   will only enter the Guest VLAN if an EAPOL frame has not been received on the port
	   for the life-time of the port. If enabled (checked), the switch will consider
	   entering the Guest VLAN even if an EAPOL frame has been received on the port for
	   the life-time of the port.The value can only be changed if the Guest VLAN option
	   is globally enabled."
   ::= { gs2310pNASConfiguration 12 }

gs2310pNASConfigMacBasedUseEAP OBJECT-TYPE
   SYNTAX      INTEGER { disable(0), enable(1) }
   MAX-ACCESS  read-write
   STATUS      current
   DESCRIPTION
       "The switch can do the RADIUS authentication on behalf of the client in the
       MAC-based Auth. port authentication mode. It can either present itself as a
       normal 802.1X client to the RADIUS Server and use EAP, supporting only the
       MD5-Challenge, or alternativly can use plain RADIUS with username / passwort
       authentification without EAP if this setting is disabled."
   ::= { gs2310pNASConfiguration 101 }

gs2310pNASPortConfigTable OBJECT-TYPE
   SYNTAX      SEQUENCE OF Gs2310pNASPortConfigEntry
   MAX-ACCESS  not-accessible
   STATUS      current
   DESCRIPTION
       ""
   ::= { gs2310pNASConfiguration 13 }

gs2310pNASPortConfigEntry OBJECT-TYPE
   SYNTAX      Gs2310pNASPortConfigEntry
   MAX-ACCESS  not-accessible
   STATUS      current
   DESCRIPTION
       ""
   INDEX    { gs2310pNASPortConfigPort }
   ::= { gs2310pNASPortConfigTable 1 }

Gs2310pNASPortConfigEntry ::= SEQUENCE {
   gs2310pNASPortConfigPort                       Integer32,
   gs2310pNASPortConfigAdminState                 INTEGER,
   gs2310pNASPortConfigRADIUSAssignedQoSEnabled	  INTEGER,
   gs2310pNASPortConfigRADIUSAssignedVLANEnabled  INTEGER,
   gs2310pNASPortConfigGuestVLANEnabled           INTEGER,
   gs2310pNASPortConfigFallbackEnabled            INTEGER,
   gs2310pNASPortConfigPortState                  DisplayString,
   gs2310pNASPortConfigReauthenticate             INTEGER,
   gs2310pNASPortConfigReinitialize               INTEGER
}

gs2310pNASPortConfigPort OBJECT-TYPE
   SYNTAX      Integer32(1..255)
   MAX-ACCESS  not-accessible
   STATUS      current
   DESCRIPTION
       " port, range : 1 - port number. "
   ::= { gs2310pNASPortConfigEntry 1 }

gs2310pNASPortConfigAdminState OBJECT-TYPE
   SYNTAX      INTEGER{ forceAuthorized(1),
						forceUnauthorized(2),
						portBased(3),
						single(4),
						multi(5),
						macBased(6),
						macBasedSingle(7)
					  }
   MAX-ACCESS  read-write
   STATUS      current
   DESCRIPTION
       "This selection controls the port's authentication mode.
		1: Force Authorized,
		2: Force Unauthorized,
		3: Port-based 802.1X,
		4: Single 802.1X,
		5: Multi 802.1X,
		6: MAC-based Auth,
		7: MAC-based Single Auth."
   ::= { gs2310pNASPortConfigEntry 2 }

gs2310pNASPortConfigRADIUSAssignedQoSEnabled OBJECT-TYPE
   SYNTAX      INTEGER { disable(0), enable(1) }
   MAX-ACCESS  read-write
   STATUS      current
   DESCRIPTION
       "When RADIUS-Assigned QoS is both globally enabled and enabled (checked)
	    on a given port, the switch reacts to QoS Class information carried in
		the RADIUS Access-Accept packet transmitted by the RADIUS server when a
		supplicant is successfully authenticated. If present and valid, traffic
		received on the supplicant's port will be classified to the given QoS Class.
		Admin State supported : Port-based and Single 802.1X and MAC-based Single Auth."
   ::= { gs2310pNASPortConfigEntry 3 }

gs2310pNASPortConfigRADIUSAssignedVLANEnabled OBJECT-TYPE
   SYNTAX      INTEGER { disable(0), enable(1) }
   MAX-ACCESS  read-write
   STATUS      current
   DESCRIPTION
       "When RADIUS-Assigned VLAN is both globally enabled and enabled (checked)
	   for a given port, the switch reacts to VLAN ID information carried in the
	   RADIUS Access-Accept packet transmitted by the RADIUS server when a supplicant
	   is successfully authenticated. If present and valid, the port's Port VLAN ID
	   will be changed to this VLAN ID, the port will be set to be a member of that
	   VLAN ID, and the port will be forced into VLAN unaware mode. Once assigned,
	   all traffic arriving on the port will be classified and switched on the
	   RADIUS-assigned VLAN ID.
	   Admin State supported : Port-based and Single 802.1X and MAC-based Single Auth."
   ::= { gs2310pNASPortConfigEntry 4 }

gs2310pNASPortConfigGuestVLANEnabled OBJECT-TYPE
   SYNTAX      INTEGER { disable(0), enable(1) }
   MAX-ACCESS  read-write
   STATUS      current
   DESCRIPTION
       "When Guest VLAN is both globally enabled and enabled (checked) for a given port,
	   the switch considers moving the port into the Guest VLAN according to the rules
	   outlined below.
	   Admin State supported : Port-based , Single and Multi 802.1X."
   ::= { gs2310pNASPortConfigEntry 5 }

gs2310pNASPortConfigPortState OBJECT-TYPE
   SYNTAX      DisplayString
   MAX-ACCESS  read-only
   STATUS      current
   DESCRIPTION
       "Globally Disabled: NAS is globally disabled.
		Link Down: NAS is globally enabled, but there is no link on the port.
		Authorized: The port is in Force Authorized or a single-supplicant mode
		and the supplicant is authorized.
		Unauthorized: The port is in Force Unauthorized or a single-supplicant
		mode and the supplicant is not successfully authorized by the RADIUS server.
		X Auth/Y Unauth: The port is in a multi-supplicant mode. Currently X clients
		are authorized and Y are unauthorized."
   ::= { gs2310pNASPortConfigEntry 6 }

gs2310pNASPortConfigReauthenticate OBJECT-TYPE
   SYNTAX      INTEGER { doNothing(0), do(1) }
   MAX-ACCESS  read-write
   STATUS      current
   DESCRIPTION
       "Schedules a reauthentication whenever the quiet-period of the port runs out
	   (EAPOL-based authentication). For MAC-based authentication, reauthentication
	   will be attempted immediately.The button only has effect for successfully
	   authenticated clients on the port and will not cause the clients to get
	   temporarily unauthorized."
   ::= { gs2310pNASPortConfigEntry 7 }

gs2310pNASPortConfigReinitialize OBJECT-TYPE
   SYNTAX      INTEGER { doNothing(0), do(1) }
   MAX-ACCESS  read-write
   STATUS      current
   DESCRIPTION
       "Forces a reinitialization of the clients on the port and thereby a reauthentication
	   immediately. The clients will transfer to the unauthorized state while the
	   reauthentication is in progress."
   ::= { gs2310pNASPortConfigEntry 8 }

gs2310pNASPortConfigFallbackEnabled OBJECT-TYPE
   SYNTAX      INTEGER { disable(0), enable(1) }
   MAX-ACCESS  read-write
   STATUS      current
   DESCRIPTION
       "When Fallback is enabled, the switch will take over the supplicants role
       after max reauthentication count is reached and tries to authenticate the
       client on its behalf as described for MAC-based Auth.
       Admin State supported : Single and Multi 802.1X."
   ::= { gs2310pNASPortConfigEntry 101 }

gs2310pNASSwitchStatusTable OBJECT-TYPE
   SYNTAX      SEQUENCE OF Gs2310pNASSwitchStatusEntry
   MAX-ACCESS  not-accessible
   STATUS      current
   DESCRIPTION
       ""
   ::= { gs2310pNAS 2 }

gs2310pNASSwitchStatusEntry OBJECT-TYPE
   SYNTAX      Gs2310pNASSwitchStatusEntry
   MAX-ACCESS  not-accessible
   STATUS      current
   DESCRIPTION
       ""
   INDEX    { gs2310pNASPortConfigPort }
   ::= { gs2310pNASSwitchStatusTable 1 }

Gs2310pNASSwitchStatusEntry ::= SEQUENCE {
   gs2310pNASSwitchStatusAdminState 	DisplayString,
   gs2310pNASSwitchStatusPortState		DisplayString,
   gs2310pNASSwitchStatusLastSource		DisplayString,
   gs2310pNASSwitchStatusLastID			DisplayString,
   gs2310pNASSwitchStatusQoSClass		DisplayString,
   gs2310pNASSwitchStatusPortVlanID		DisplayString
}

gs2310pNASSwitchStatusAdminState OBJECT-TYPE
   SYNTAX      DisplayString
   MAX-ACCESS  read-only
   STATUS      current
   DESCRIPTION
       "The port's current administrative state. Refer to NAS Admin State for a description of possible values."
   ::= { gs2310pNASSwitchStatusEntry 2 }

gs2310pNASSwitchStatusPortState OBJECT-TYPE
   SYNTAX      DisplayString
   MAX-ACCESS  read-only
   STATUS      current
   DESCRIPTION
       "The current state of the port. Refer to NAS Port State for a description of the individual states."
   ::= { gs2310pNASSwitchStatusEntry 3 }

gs2310pNASSwitchStatusLastSource OBJECT-TYPE
   SYNTAX      DisplayString
   MAX-ACCESS  read-only
   STATUS      current
   DESCRIPTION
       "The source MAC address carried in the most recently received EAPOL frame for EAPOL-based authentication,
	   and the most recently received frame from a new client for MAC-based authentication."
   ::= { gs2310pNASSwitchStatusEntry 4 }

gs2310pNASSwitchStatusLastID OBJECT-TYPE
   SYNTAX      DisplayString
   MAX-ACCESS  read-only
   STATUS      current
   DESCRIPTION
       "The user name (supplicant identity) carried in the most recently received Response Identity EAPOL frame
	   for EAPOL-based authentication, and the source MAC address from the most recently received frame from a
	   new client for MAC-based authentication."
   ::= { gs2310pNASSwitchStatusEntry 5 }

gs2310pNASSwitchStatusQoSClass OBJECT-TYPE
   SYNTAX      DisplayString
   MAX-ACCESS  read-only
   STATUS      current
   DESCRIPTION
       "QoS Class assigned to the port by the RADIUS server if enabled."
   ::= { gs2310pNASSwitchStatusEntry 6 }

gs2310pNASSwitchStatusPortVlanID OBJECT-TYPE
   SYNTAX      DisplayString
   MAX-ACCESS  read-only
   STATUS      current
   DESCRIPTION
       "The VLAN ID that NAS has put the port in. The field is blank, if the Port VLAN ID is not overridden by NAS."
   ::= { gs2310pNASSwitchStatusEntry 7 }

gs2310pNASPortStatus                                 OBJECT IDENTIFIER ::= { gs2310pNAS 3 }

gs2310pNASPortStatusCountersTable OBJECT-TYPE
   SYNTAX      SEQUENCE OF Gs2310pNASPortStatusCountersEntry
   MAX-ACCESS  not-accessible
   STATUS      current
   DESCRIPTION
       ""
   ::= { gs2310pNASPortStatus 1 }

gs2310pNASPortStatusCountersEntry OBJECT-TYPE
   SYNTAX      Gs2310pNASPortStatusCountersEntry
   MAX-ACCESS  not-accessible
   STATUS      current
   DESCRIPTION
       ""
   INDEX    { gs2310pNASPortConfigPort }
   ::= { gs2310pNASPortStatusCountersTable 1 }

Gs2310pNASPortStatusCountersEntry ::= SEQUENCE {
   gs2310pNASRxCountersEAPOLTotal  	                  Counter32,
   gs2310pNASRxCountersEAPOLResponseID	              Counter32,
   gs2310pNASRxCountersEAPOLResponses	              Counter32,
   gs2310pNASRxCountersEAPOLStart	                  Counter32,
   gs2310pNASRxCountersEAPOLLogoff                    Counter32,
   gs2310pNASRxCountersEAPOLInvalidType               Counter32,
   gs2310pNASRxCountersEAPOLInvalidLength             Counter32,
   gs2310pNASTxCountersEAPOLTotal                     Counter32,
   gs2310pNASTxCountersEAPOLRequestID                 Counter32,
   gs2310pNASTxCountersEAPOLRequests                  Counter32,
   gs2310pNASRxBackendServerCountersAccessChallenges  Counter32,
   gs2310pNASRxBackendServerCountersOtherRequests     Counter32,
   gs2310pNASRxBackendServerCountersAuthSuccesses     Counter32,
   gs2310pNASRxBackendServerCountersAuthFailures      Counter32,
   gs2310pNASTxBackendServerCountersResponses         Counter32,
   gs2310pNASLastSupplicantInfoMACAddress             DisplayString,
   gs2310pNASLastSupplicantInfoVlanID                 Integer32,
   gs2310pNASLastSupplicantInfoVersion                Integer32,
   gs2310pNASLastSupplicantInfoIdentity               DisplayString,
   gs2310pNASCountersDoClear                          INTEGER
}

gs2310pNASRxCountersEAPOLTotal OBJECT-TYPE
   SYNTAX      Counter32
   MAX-ACCESS  read-only
   STATUS      current
   DESCRIPTION
       "The number of valid EAPOL frames of any type that have been received by the switch."
   ::= { gs2310pNASPortStatusCountersEntry 2 }

gs2310pNASRxCountersEAPOLResponseID OBJECT-TYPE
   SYNTAX      Counter32
   MAX-ACCESS  read-only
   STATUS      current
   DESCRIPTION
       "The number of valid EAPOL Response Identity frames that have been received by the switch."
   ::= { gs2310pNASPortStatusCountersEntry 3 }

gs2310pNASRxCountersEAPOLResponses OBJECT-TYPE
   SYNTAX      Counter32
   MAX-ACCESS  read-only
   STATUS      current
   DESCRIPTION
       "The number of valid EAPOL response frames (other than Response Identity frames)
	   that have been received by the switch."
   ::= { gs2310pNASPortStatusCountersEntry 4 }

gs2310pNASRxCountersEAPOLStart OBJECT-TYPE
   SYNTAX      Counter32
   MAX-ACCESS  read-only
   STATUS      current
   DESCRIPTION
       "The number of EAPOL Start frames that have been received by the switch."
   ::= { gs2310pNASPortStatusCountersEntry 5 }

gs2310pNASRxCountersEAPOLLogoff OBJECT-TYPE
   SYNTAX      Counter32
   MAX-ACCESS  read-only
   STATUS      current
   DESCRIPTION
       "The number of valid EAPOL Logoff frames that have been received by the switch."
   ::= { gs2310pNASPortStatusCountersEntry 6 }

gs2310pNASRxCountersEAPOLInvalidType OBJECT-TYPE
   SYNTAX      Counter32
   MAX-ACCESS  read-only
   STATUS      current
   DESCRIPTION
       "The number of EAPOL frames that have been received by the switch in which
	   the frame type is not recognized."
   ::= { gs2310pNASPortStatusCountersEntry 7 }

gs2310pNASRxCountersEAPOLInvalidLength OBJECT-TYPE
   SYNTAX      Counter32
   MAX-ACCESS  read-only
   STATUS      current
   DESCRIPTION
       "The number of EAPOL frames that have been received by the switch in which the
	   Packet Body Length field is invalid."
   ::= { gs2310pNASPortStatusCountersEntry 8 }

gs2310pNASTxCountersEAPOLTotal OBJECT-TYPE
   SYNTAX      Counter32
   MAX-ACCESS  read-only
   STATUS      current
   DESCRIPTION
       "The number of EAPOL frames of any type that have been transmitted by the switch."
   ::= { gs2310pNASPortStatusCountersEntry 9 }

gs2310pNASTxCountersEAPOLRequestID OBJECT-TYPE
   SYNTAX      Counter32
   MAX-ACCESS  read-only
   STATUS      current
   DESCRIPTION
       "The number of EAPOL Request Identity frames that have been transmitted by the switch."
   ::= { gs2310pNASPortStatusCountersEntry 10 }

gs2310pNASTxCountersEAPOLRequests OBJECT-TYPE
   SYNTAX      Counter32
   MAX-ACCESS  read-only
   STATUS      current
   DESCRIPTION
       "The number of valid EAPOL Request frames (other than Request Identity frames)
	   that have been transmitted by the switch."
   ::= { gs2310pNASPortStatusCountersEntry 11 }

gs2310pNASRxBackendServerCountersAccessChallenges OBJECT-TYPE
   SYNTAX      Counter32
   MAX-ACCESS  read-only
   STATUS      current
   DESCRIPTION
       "802.1X-based: Counts the number of times that the switch receives the first request
	   from the backend server following the first response from the supplicant.
	   MAC-based: Counts all Access Challenges received from the backend server for this
	   port or client."
   ::= { gs2310pNASPortStatusCountersEntry 12 }

gs2310pNASRxBackendServerCountersOtherRequests OBJECT-TYPE
   SYNTAX      Counter32
   MAX-ACCESS  read-only
   STATUS      current
   DESCRIPTION
       "802.1X-based: Counts the number of times that the switch sends an EAP Request
	   packet following the first to the supplicant.
	   MAC-based: Not applicable."
   ::= { gs2310pNASPortStatusCountersEntry 13 }

gs2310pNASRxBackendServerCountersAuthSuccesses OBJECT-TYPE
   SYNTAX      Counter32
   MAX-ACCESS  read-only
   STATUS      current
   DESCRIPTION
       "Counts the number of times that the switch receives a success indication.
	   Indicates that the supplicant/client has successfully authenticated to the
	   backend server."
   ::= { gs2310pNASPortStatusCountersEntry 14 }

gs2310pNASRxBackendServerCountersAuthFailures OBJECT-TYPE
   SYNTAX      Counter32
   MAX-ACCESS  read-only
   STATUS      current
   DESCRIPTION
       "Counts the number of times that the switch receives a failure message.
	   This indicates that the supplicant/client has not authenticated to the
	   backend server. "
   ::= { gs2310pNASPortStatusCountersEntry 15 }

gs2310pNASTxBackendServerCountersResponses OBJECT-TYPE
   SYNTAX      Counter32
   MAX-ACCESS  read-only
   STATUS      current
   DESCRIPTION
       "802.1X-based: Counts the number of times that the switch attempts to
	   send a supplicant's first response packet to the backend server. Indicates
	   the switch attempted communication with the backend server. Possible
	   retransmissions are not counted.
	   MAC-based: Counts all the backend server packets sent from the switch
	   towards the backend server for a given port or client. Possible
	   retransmissions are not counted."
   ::= { gs2310pNASPortStatusCountersEntry 16 }

gs2310pNASLastSupplicantInfoMACAddress OBJECT-TYPE
   SYNTAX      DisplayString
   MAX-ACCESS  read-only
   STATUS      current
   DESCRIPTION
       "The MAC address of the last supplicant/client."
   ::= { gs2310pNASPortStatusCountersEntry 17 }

gs2310pNASLastSupplicantInfoVlanID OBJECT-TYPE
   SYNTAX      Integer32
   MAX-ACCESS  read-only
   STATUS      current
   DESCRIPTION
       "The VLAN ID on which the last frame from the last supplicant/client was received."
   ::= { gs2310pNASPortStatusCountersEntry 18 }

gs2310pNASLastSupplicantInfoVersion OBJECT-TYPE
   SYNTAX      Integer32
   MAX-ACCESS  read-only
   STATUS      current
   DESCRIPTION
       "802.1X-based: The protocol version number carried in the most recently
	   received EAPOL frame.
	   MAC-based: Not applicable."
   ::= { gs2310pNASPortStatusCountersEntry 19 }

gs2310pNASLastSupplicantInfoIdentity OBJECT-TYPE
   SYNTAX      DisplayString
   MAX-ACCESS  read-only
   STATUS      current
   DESCRIPTION
       "802.1X-based: The user name (supplicant identity) carried in the most recently received
	   Response Identity EAPOL frame.
	   MAC-based: Not applicable."
   ::= { gs2310pNASPortStatusCountersEntry 20 }

gs2310pNASCountersDoClear OBJECT-TYPE
   SYNTAX      INTEGER { doNothing(0), do(1) }
   MAX-ACCESS  read-write
   STATUS      current
   DESCRIPTION
       "Clear the counters for the selected port."
   ::= { gs2310pNASPortStatusCountersEntry 21 }

gs2310pNASPortStatusClientsTable OBJECT-TYPE
   SYNTAX      SEQUENCE OF Gs2310pNASPortStatusClientsEntry
   MAX-ACCESS  not-accessible
   STATUS      current
   DESCRIPTION
       ""
   ::= { gs2310pNASPortStatus 2 }

gs2310pNASPortStatusClientsEntry OBJECT-TYPE
   SYNTAX      Gs2310pNASPortStatusClientsEntry
   MAX-ACCESS  not-accessible
   STATUS      current
   DESCRIPTION
       ""
   INDEX    { gs2310pNASPortConfigPort,
		gs2310pNASClientsIndex}
   ::= { gs2310pNASPortStatusClientsTable 1 }

Gs2310pNASPortStatusClientsEntry ::= SEQUENCE {
   gs2310pNASClientsIndex  	                  		    Integer32,
   gs2310pNASClientsIdentity							DisplayString,
   gs2310pNASClientsMACAddress  	                  	DisplayString,
   gs2310pNASClientsVlanID		              			Integer32,
   gs2310pNASClientsState	              				DisplayString,
   gs2310pNASClientsLastAuth	                  		DisplayString,
   gs2310pNASRxClientsEAPOLTotal  	                  	Counter32,
   gs2310pNASRxClientsEAPOLResponseID	              	Counter32,
   gs2310pNASRxClientsEAPOLResponses	              	Counter32,
   gs2310pNASRxClientsEAPOLStart	                  	Counter32,
   gs2310pNASRxClientsEAPOLLogoff                    	Counter32,
   gs2310pNASRxClientsEAPOLInvalidType               	Counter32,
   gs2310pNASRxClientsEAPOLInvalidLength             	Counter32,
   gs2310pNASTxClientsEAPOLTotal                     	Counter32,
   gs2310pNASTxClientsEAPOLRequestID                 	Counter32,
   gs2310pNASTxClientsEAPOLRequests                  	Counter32,
   gs2310pNASRxBackendServerClientsAccessChallenges  	Counter32,
   gs2310pNASRxBackendServerClientsOtherRequests     	Counter32,
   gs2310pNASRxBackendServerClientsAuthSuccesses     	Counter32,
   gs2310pNASRxBackendServerClientsAuthFailures      	Counter32,
   gs2310pNASTxBackendServerClientsResponses         	Counter32
}

gs2310pNASClientsIndex OBJECT-TYPE
   SYNTAX      Integer32(1..255)
   MAX-ACCESS  not-accessible
   STATUS      current
   DESCRIPTION
       "Entry of client table in the port."
   ::= { gs2310pNASPortStatusClientsEntry 1 }

gs2310pNASClientsIdentity OBJECT-TYPE
   SYNTAX      DisplayString
   MAX-ACCESS  read-only
   STATUS      current
   DESCRIPTION
       "Shows the identity of the supplicant, as received in the Response Identity
	   EAPOL frame.This isn't available for MAC-based Auth."
   ::= { gs2310pNASPortStatusClientsEntry 2 }

gs2310pNASClientsMACAddress OBJECT-TYPE
   SYNTAX      DisplayString
   MAX-ACCESS  read-only
   STATUS      current
   DESCRIPTION
       "Multi 802.1X, this column holds the MAC address of the attached supplicant.
	   MAC-based Auth., this column holds the MAC address of the attached client."
   ::= { gs2310pNASPortStatusClientsEntry 3 }

gs2310pNASClientsVlanID OBJECT-TYPE
   SYNTAX      Integer32(1..4095)
   MAX-ACCESS  read-only
   STATUS      current
   DESCRIPTION
       "This column holds the VLAN ID that the corresponding client is currently
	   secured through the Port Security module."
   ::= { gs2310pNASPortStatusClientsEntry 4 }

gs2310pNASClientsState OBJECT-TYPE
   SYNTAX      DisplayString
   MAX-ACCESS  read-only
   STATUS      current
   DESCRIPTION
       "The client can either be authenticated or unauthenticated. In the authenticated
	   state, it is allowed to forward frames on the port, and in the unauthenticated
	   state, it is blocked."
   ::= { gs2310pNASPortStatusClientsEntry 5 }

gs2310pNASClientsLastAuth OBJECT-TYPE
   SYNTAX      DisplayString
   MAX-ACCESS  read-only
   STATUS      current
   DESCRIPTION
       "Shows the date and time of the last authentication of the client."
   ::= { gs2310pNASPortStatusClientsEntry 6 }

gs2310pNASRxClientsEAPOLTotal OBJECT-TYPE
   SYNTAX      Counter32
   MAX-ACCESS  read-only
   STATUS      current
   DESCRIPTION
       "The number of valid EAPOL frames of any type that have been received by the switch."
   ::= { gs2310pNASPortStatusClientsEntry 7 }

gs2310pNASRxClientsEAPOLResponseID OBJECT-TYPE
   SYNTAX      Counter32
   MAX-ACCESS  read-only
   STATUS      current
   DESCRIPTION
       "The number of valid EAPOL Response Identity frames that have been received by the switch."
   ::= { gs2310pNASPortStatusClientsEntry 8 }

gs2310pNASRxClientsEAPOLResponses OBJECT-TYPE
   SYNTAX      Counter32
   MAX-ACCESS  read-only
   STATUS      current
   DESCRIPTION
       "The number of valid EAPOL response frames (other than Response Identity frames)
	   that have been received by the switch."
   ::= { gs2310pNASPortStatusClientsEntry 9 }

gs2310pNASRxClientsEAPOLStart OBJECT-TYPE
   SYNTAX      Counter32
   MAX-ACCESS  read-only
   STATUS      current
   DESCRIPTION
       "The number of EAPOL Start frames that have been received by the switch."
   ::= { gs2310pNASPortStatusClientsEntry 10 }

gs2310pNASRxClientsEAPOLLogoff OBJECT-TYPE
   SYNTAX      Counter32
   MAX-ACCESS  read-only
   STATUS      current
   DESCRIPTION
       "The number of valid EAPOL Logoff frames that have been received by the switch."
   ::= { gs2310pNASPortStatusClientsEntry 11 }

gs2310pNASRxClientsEAPOLInvalidType OBJECT-TYPE
   SYNTAX      Counter32
   MAX-ACCESS  read-only
   STATUS      current
   DESCRIPTION
       "The number of EAPOL frames that have been received by the switch in which
	   the frame type is not recognized."
   ::= { gs2310pNASPortStatusClientsEntry 12 }

gs2310pNASRxClientsEAPOLInvalidLength OBJECT-TYPE
   SYNTAX      Counter32
   MAX-ACCESS  read-only
   STATUS      current
   DESCRIPTION
       "The number of EAPOL frames that have been received by the switch in which the
	   Packet Body Length field is invalid."
   ::= { gs2310pNASPortStatusClientsEntry 13 }

gs2310pNASTxClientsEAPOLTotal OBJECT-TYPE
   SYNTAX      Counter32
   MAX-ACCESS  read-only
   STATUS      current
   DESCRIPTION
       "The number of EAPOL frames of any type that have been transmitted by the switch."
   ::= { gs2310pNASPortStatusClientsEntry 14 }

gs2310pNASTxClientsEAPOLRequestID OBJECT-TYPE
   SYNTAX      Counter32
   MAX-ACCESS  read-only
   STATUS      current
   DESCRIPTION
       "The number of EAPOL Request Identity frames that have been transmitted by the switch."
   ::= { gs2310pNASPortStatusClientsEntry 15 }

gs2310pNASTxClientsEAPOLRequests OBJECT-TYPE
   SYNTAX      Counter32
   MAX-ACCESS  read-only
   STATUS      current
   DESCRIPTION
       "The number of valid EAPOL Request frames (other than Request Identity frames)
	   that have been transmitted by the switch."
   ::= { gs2310pNASPortStatusClientsEntry 16 }

gs2310pNASRxBackendServerClientsAccessChallenges OBJECT-TYPE
   SYNTAX      Counter32
   MAX-ACCESS  read-only
   STATUS      current
   DESCRIPTION
       "802.1X-based: Counts the number of times that the switch receives the first request
	   from the backend server following the first response from the supplicant.
	   MAC-based: Counts all Access Challenges received from the backend server for this
	   port or client."
   ::= { gs2310pNASPortStatusClientsEntry 17 }

gs2310pNASRxBackendServerClientsOtherRequests OBJECT-TYPE
   SYNTAX      Counter32
   MAX-ACCESS  read-only
   STATUS      current
   DESCRIPTION
       "802.1X-based: Counts the number of times that the switch sends an EAP Request
	   packet following the first to the supplicant.
	   MAC-based: Not applicable."
   ::= { gs2310pNASPortStatusClientsEntry 18 }

gs2310pNASRxBackendServerClientsAuthSuccesses OBJECT-TYPE
   SYNTAX      Counter32
   MAX-ACCESS  read-only
   STATUS      current
   DESCRIPTION
       "Counts the number of times that the switch receives a success indication.
	   Indicates that the supplicant/client has successfully authenticated to the
	   backend server."
   ::= { gs2310pNASPortStatusClientsEntry 19 }

gs2310pNASRxBackendServerClientsAuthFailures OBJECT-TYPE
   SYNTAX      Counter32
   MAX-ACCESS  read-only
   STATUS      current
   DESCRIPTION
       "Counts the number of times that the switch receives a failure message.
	   This indicates that the supplicant/client has not authenticated to the
	   backend server. "
   ::= { gs2310pNASPortStatusClientsEntry 20 }

gs2310pNASTxBackendServerClientsResponses OBJECT-TYPE
   SYNTAX      Counter32
   MAX-ACCESS  read-only
   STATUS      current
   DESCRIPTION
       "802.1X-based: Counts the number of times that the switch attempts to
	   send a supplicant's first response packet to the backend server. Indicates
	   the switch attempted communication with the backend server. Possible
	   retransmissions are not counted.
	   MAC-based: Counts all the backend server packets sent from the switch
	   towards the backend server for a given port or client. Possible
	   retransmissions are not counted."
   ::= { gs2310pNASPortStatusClientsEntry 21 }


gs2310pMaintenance                                           OBJECT IDENTIFIER ::= { lancomGS2310P 4 }

gs2310pRestartDevice OBJECT-TYPE
   SYNTAX      INTEGER { disable(0), enable(1) }
   MAX-ACCESS  read-write
   STATUS      current
   DESCRIPTION
       "default: 0
        0:none
        1:yes"
   ::= { gs2310pMaintenance 1 }

gs2310pColdRestartDevice OBJECT-TYPE
   SYNTAX      INTEGER { disable(0), enable(1) }
   MAX-ACCESS  read-write
   STATUS      current
   DESCRIPTION
       "default: 0
        0:none
        1:yes"
   ::= { gs2310pMaintenance 1500 }

gs2310pFirmware                                         OBJECT IDENTIFIER ::= { gs2310pMaintenance 2 }

gs2310pFirmwareIpAddress OBJECT-TYPE
   SYNTAX       IpAddress
   MAX-ACCESS   read-write
   STATUS       current
   DESCRIPTION
        "Get/Set the firmware tftp server."
   ::= { gs2310pFirmware 1 }

gs2310pFirmwareFileName OBJECT-TYPE
   SYNTAX       DisplayString
   MAX-ACCESS   read-write
   STATUS       current
   DESCRIPTION
        "Get/Set the path and filename for firmware upgrading."
   ::= { gs2310pFirmware 2 }

gs2310pDoFirmwareUpgrade OBJECT-TYPE
   SYNTAX       INTEGER { doNothing(0), do(1) }
   MAX-ACCESS   read-write
   STATUS       current
   DESCRIPTION
        "Do firmware upgrade. Get this OID always return zero.
              1 - do firmware upgrade.
              0 - do nothing."
   ::= { gs2310pFirmware 3 }

gs2310pSaveOrRestore                                         OBJECT IDENTIFIER ::= { gs2310pMaintenance 3 }

gs2310pFactoryDefaults OBJECT-TYPE
   SYNTAX      INTEGER { none(0), yes(1) }
   MAX-ACCESS  read-write
   STATUS      current
   DESCRIPTION
       "default: 0
        0:none
        1:yes"
   ::= { gs2310pSaveOrRestore 1 }

gs2310pSaveStart OBJECT-TYPE
   SYNTAX      INTEGER { none(0), yes(1) }
   MAX-ACCESS  read-write
   STATUS      current
   DESCRIPTION
       "default: 0
        0:none
        1:yes"
   ::= { gs2310pSaveOrRestore 2 }

gs2310pSaveUser OBJECT-TYPE
   SYNTAX      INTEGER { none(0), yes(1) }
   MAX-ACCESS  read-write
   STATUS      current
   DESCRIPTION
       "default: 0
        0:none
        1:yes"
   ::= { gs2310pSaveOrRestore 3 }

gs2310pRestoreUser OBJECT-TYPE
   SYNTAX      INTEGER { none(0), yes(1) }
   MAX-ACCESS  read-write
   STATUS      current
   DESCRIPTION
       "default: 0
        0:none
        1:yes"
   ::= { gs2310pSaveOrRestore 4 }


gs2310pExportOrImport                                        OBJECT IDENTIFIER ::= { gs2310pMaintenance 4 }

gs2310pExportIpAddress OBJECT-TYPE
   SYNTAX       IpAddress
   MAX-ACCESS   read-write
   STATUS       current
   DESCRIPTION
        "Get/Set the export tftp server."
   ::= { gs2310pExportOrImport 1 }

gs2310pExportConfigName OBJECT-TYPE
   SYNTAX       DisplayString
   MAX-ACCESS   read-write
   STATUS       current
   DESCRIPTION
       "Get/Set the export file path and name."
   ::= { gs2310pExportOrImport 2 }

gs2310pDoExportConfig OBJECT-TYPE
   SYNTAX       INTEGER{ doNothing(0), do(1) }
   MAX-ACCESS   read-write
   STATUS       current
   DESCRIPTION
        "Do export-config.
         Get this OID always return zero.
         1 - export."
   ::= { gs2310pExportOrImport 3 }

gs2310pImportIpAddress OBJECT-TYPE
   SYNTAX       IpAddress
   MAX-ACCESS   read-write
   STATUS       current
   DESCRIPTION
        "Get/Set the import tftp server."
   ::= { gs2310pExportOrImport 4 }

gs2310pImportConfigName OBJECT-TYPE
   SYNTAX      DisplayString
   MAX-ACCESS  read-write
   STATUS      current
   DESCRIPTION
       "Get/Set the import file path and name."
   ::= { gs2310pExportOrImport 5 }

gs2310pDoImportConfig OBJECT-TYPE
   SYNTAX       INTEGER{ doNothing(0), do(1) }
   MAX-ACCESS   read-write
   STATUS       current
   DESCRIPTION
        "Do export-config.
         Get this OID always return zero.
         1 - import."
   ::= { gs2310pExportOrImport 6 }

gs2310pDiagnostics                                           OBJECT IDENTIFIER ::= { gs2310pMaintenance 5 }

gs2310pPingIpAddress OBJECT-TYPE
   SYNTAX      IpAddress
   MAX-ACCESS  read-write
   STATUS      current
   DESCRIPTION
       " The destination IP Address. "
   ::= { gs2310pDiagnostics 1 }

gs2310pPingSize OBJECT-TYPE
   SYNTAX      Integer32(60..1400)
   MAX-ACCESS  read-write
   STATUS      current
   DESCRIPTION
       " Size of ICMP echo packet.
         range : 60-1400, default : 64. "
   ::= { gs2310pDiagnostics 2 }

gs2310pDoPingConfig OBJECT-TYPE
   SYNTAX       INTEGER{ doNothing(0), do(1) }
   MAX-ACCESS  read-write
   STATUS      current
   DESCRIPTION
       "Do ping-config.
         Get this OID always return zero.
         1 - ping. Uses the ICMP protocol's mandatory ECHO_REQUEST datagram
         to elicit an ICMP ECHO_RESPONSE from a host or gateway. "
   ::= { gs2310pDiagnostics 3 }

gs2310pPingResult OBJECT-TYPE
   SYNTAX      DisplayString
   MAX-ACCESS  read-only
   STATUS      current
   DESCRIPTION
       " Show ping result. "
   ::= { gs2310pDiagnostics 4 }

gs2310pPing6IpAddress OBJECT-TYPE
   SYNTAX      DisplayString
   MAX-ACCESS  read-write
   STATUS      current
   DESCRIPTION
       " The destination IPv6 Address. "
   ::= { gs2310pDiagnostics 5 }

gs2310pPing6Size OBJECT-TYPE
   SYNTAX      Integer32(60..1400)
   MAX-ACCESS  read-write
   STATUS      current
   DESCRIPTION
       " Size of ICMP echo packet.
         range : 60-1400. "
   ::= { gs2310pDiagnostics 6 }

gs2310pDoPing6Config OBJECT-TYPE
   SYNTAX       INTEGER{ doNothing(0), do(1) }
   MAX-ACCESS  read-write
   STATUS      current
   DESCRIPTION
       "Do ping-config.
         Get this OID always return zero.
         1 - ping. Uses the ICMP protocol's mandatory ECHO_REQUEST datagram
         to elicit an ICMP ECHO_RESPONSE from a host or gateway. "
   ::= { gs2310pDiagnostics 7 }

gs2310pPing6Result OBJECT-TYPE
   SYNTAX      DisplayString
   MAX-ACCESS  read-only
   STATUS      current
   DESCRIPTION
       " Show ping result. "
   ::= { gs2310pDiagnostics 8 }




------------------------------------------------------------------------------------------------------------------
gs2310pTrap                                                  OBJECT IDENTIFIER ::= { lancomGS2310P 5 }

gs2310pTrapEvent                                             OBJECT IDENTIFIER ::= { gs2310pTrap 1 }

gs2310pEmergency NOTIFICATION-TYPE
  OBJECTS   { gs2310pInformation }
  STATUS        current
    DESCRIPTION
        "The severity level is Emergency. The system is unusable."
    ::= { gs2310pTrapEvent 1 }

gs2310pAlert NOTIFICATION-TYPE
  OBJECTS   { gs2310pInformation }
  STATUS        current
    DESCRIPTION
        "The severity level is Alert. The action must be taken immediately."
    ::= { gs2310pTrapEvent 2 }

gs2310pCritical NOTIFICATION-TYPE
  OBJECTS   { gs2310pInformation }
  STATUS        current
    DESCRIPTION
        "The severity level is Critical. Critical conditions."
    ::= { gs2310pTrapEvent 3 }

gs2310pError NOTIFICATION-TYPE
  OBJECTS   { gs2310pInformation }
  STATUS        current
    DESCRIPTION
        "The severity level is Error. Error conditions."
    ::= { gs2310pTrapEvent 4 }

gs2310pWarning NOTIFICATION-TYPE
  OBJECTS   { gs2310pInformation }
  STATUS        current
    DESCRIPTION
        "The severity level is Warning. Warning conditions."
    ::= { gs2310pTrapEvent 5 }

gs2310pNotice NOTIFICATION-TYPE
  OBJECTS   { gs2310pInformation }
  STATUS        current
    DESCRIPTION
        "The severity level is Notice. Normal but significant condition."
    ::= { gs2310pTrapEvent 6 }

gs2310pInformational NOTIFICATION-TYPE
  OBJECTS   { gs2310pInformation }
  STATUS        current
    DESCRIPTION
        "The severity level is Informational. Informational messages."
    ::= { gs2310pTrapEvent 7 }

gs2310pDebug NOTIFICATION-TYPE
  OBJECTS   { gs2310pInformation }
  STATUS        current
    DESCRIPTION
        "The severity level is Debug. debug-level messages."
    ::= { gs2310pTrapEvent 8 }

gs2310pTrapVariable                                          OBJECT IDENTIFIER ::= { gs2310pTrap 2 }

gs2310pInformation OBJECT-TYPE
    SYNTAX      DisplayString
    MAX-ACCESS  read-only
    STATUS      current
    DESCRIPTION
        "Trap information."
    ::= { gs2310pTrapVariable 1 }


END
