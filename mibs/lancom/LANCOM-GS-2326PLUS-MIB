LANCOM-GS-2326PLUS-MIB DEFINITIONS ::= BEGIN

IMPORTS
    DisplayString,MacAddress FROM SNMPv2-TC
    MODULE-COMPLIANCE,OBJECT-GROUP, NOTIFICATION-GROUP       FROM SNMPv2-CONF
    ifIndex    FROM RFC1213-MIB
    enterprises,MODULE-IDENTITY,OBJECT-TYPE,NOTIFICATION-TYPE,Counter32,Counter64,IpAddress        FROM SNMPv2-SMI
    InetAddress                   FROM INET-ADDRESS-MIB
    MacAddress FROM BRIDGE-MIB;

lancom-systems MODULE-IDENTITY
        LAST-UPDATED "202002190000Z"
        ORGANIZATION "LANCOM Systems GmbH."
        CONTACT-INFO
            "Adenauerstrasse 20 / B2, 52146 Wuerselen, Germany
            Email: info@lancom.de
            TEL: +49 (0)2405 49936 0
            FAX: +49 (0)2405 49936 99"
        DESCRIPTION
            "The MIB module is for LANCOM Systems"
        ::= { enterprises 2356 }

switchingSystems                                                          OBJECT IDENTIFIER ::= { lancom-systems 800 }

gigabitEthernetSwitches                                             OBJECT IDENTIFIER ::= { switchingSystems 3 }

lancomGS2326plus                                                OBJECT IDENTIFIER ::= { gigabitEthernetSwitches 2329 }

gs2326plusSystem                                                OBJECT IDENTIFIER ::= { lancomGS2326plus  1 }

gs2326plusSystemInformation                                     OBJECT IDENTIFIER ::= { gs2326plusSystem 1 }

gs2326plusModelName OBJECT-TYPE
   SYNTAX       DisplayString
   MAX-ACCESS   read-only
   STATUS       current
   DESCRIPTION
       ""
 ::= { gs2326plusSystemInformation 1 }

gs2326plusBIOSVersion OBJECT-TYPE
   SYNTAX       DisplayString
   MAX-ACCESS   read-only
   STATUS       current
   DESCRIPTION
       ""
   ::= { gs2326plusSystemInformation 2 }

gs2326plusFirmwareVersion OBJECT-TYPE
   SYNTAX       DisplayString
   MAX-ACCESS   read-only
   STATUS       current
   DESCRIPTION
       ""
   ::= { gs2326plusSystemInformation 3 }

gs2326plusHardwareMechanicalVersion OBJECT-TYPE
   SYNTAX       DisplayString
   MAX-ACCESS   read-only
   STATUS       current
   DESCRIPTION
       ""
   ::= { gs2326plusSystemInformation 4 }

gs2326plusSerialNumber OBJECT-TYPE
   SYNTAX       DisplayString
   MAX-ACCESS   read-only
   STATUS       current
   DESCRIPTION
       ""
   ::= { gs2326plusSystemInformation 5 }

gs2326plusHostMACAddress OBJECT-TYPE
   SYNTAX       MacAddress
   MAX-ACCESS   read-only
   STATUS       current
   DESCRIPTION
       ""
   ::= { gs2326plusSystemInformation 6 }

gs2326plusConsoleBaudrate OBJECT-TYPE
   SYNTAX       DisplayString
   MAX-ACCESS   read-only
   STATUS       current
   DESCRIPTION
       ""
   ::= { gs2326plusSystemInformation 7 }

gs2326plusRAMSize OBJECT-TYPE
   SYNTAX       DisplayString
   MAX-ACCESS   read-only
   STATUS       current
   DESCRIPTION
       ""
   ::= { gs2326plusSystemInformation 8 }

gs2326plusFlashSize OBJECT-TYPE
   SYNTAX       DisplayString
   MAX-ACCESS   read-only
   STATUS       current
   DESCRIPTION
       ""
   ::= { gs2326plusSystemInformation 9 }

gs2326plusBridgeFDBSize OBJECT-TYPE
   SYNTAX       DisplayString
   MAX-ACCESS   read-only
   STATUS       current
   DESCRIPTION
       ""
   ::= { gs2326plusSystemInformation 10 }

gs2326plusTransmitQueue OBJECT-TYPE
   SYNTAX       DisplayString
   MAX-ACCESS   read-only
   STATUS       current
   DESCRIPTION
       ""
   ::= { gs2326plusSystemInformation 11 }

gs2326plusMaximumFrameSize OBJECT-TYPE
   SYNTAX       DisplayString
   MAX-ACCESS   read-only
   STATUS       current
   DESCRIPTION
       ""
   ::= { gs2326plusSystemInformation 12 }

gs2326plusCPULoad OBJECT-TYPE
   SYNTAX       DisplayString
   MAX-ACCESS   read-only
   STATUS       current
   DESCRIPTION
       ""
   ::= { gs2326plusSystemInformation 13 }

gs2326plusSystemDescription OBJECT-TYPE
   SYNTAX       DisplayString
   MAX-ACCESS   read-only
   STATUS       current
   DESCRIPTION
       ""
   ::= { gs2326plusSystemInformation 21 }

gs2326plusLocation OBJECT-TYPE
   SYNTAX       DisplayString
   MAX-ACCESS   read-only
   STATUS       current
   DESCRIPTION
       ""
   ::= { gs2326plusSystemInformation 22 }

gs2326plusContact OBJECT-TYPE
   SYNTAX       DisplayString
   MAX-ACCESS   read-only
   STATUS       current
   DESCRIPTION
       ""
   ::= { gs2326plusSystemInformation 23 }

gs2326plusDeviceName OBJECT-TYPE
   SYNTAX       DisplayString
   MAX-ACCESS   read-only
   STATUS       current
   DESCRIPTION
       ""
   ::= { gs2326plusSystemInformation 24 }

gs2326plusSystemDate OBJECT-TYPE
   SYNTAX       DisplayString
   MAX-ACCESS   read-only
   STATUS       current
   DESCRIPTION
       ""
   ::= { gs2326plusSystemInformation 25 }

gs2326plusSystemUptime OBJECT-TYPE
   SYNTAX       DisplayString
   MAX-ACCESS   read-only
   STATUS       current
   DESCRIPTION
       ""
   ::= { gs2326plusSystemInformation 26 }

gs2326plusSystemIPv4Address OBJECT-TYPE
   SYNTAX       DisplayString
   MAX-ACCESS   read-only
   STATUS       current
   DESCRIPTION
       ""
   ::= { gs2326plusSystemInformation 27 }

gs2326plusSystemIPv4SubnetMask OBJECT-TYPE
   SYNTAX       DisplayString
   MAX-ACCESS   read-only
   STATUS       current
   DESCRIPTION
       ""
   ::= { gs2326plusSystemInformation 28 }

gs2326plusSystemIPv4Gateway OBJECT-TYPE
   SYNTAX       DisplayString
   MAX-ACCESS   read-only
   STATUS       current
   DESCRIPTION
       ""
   ::= { gs2326plusSystemInformation 29 }

gs2326plusIPv6LinkLocalAddress OBJECT-TYPE
   SYNTAX       DisplayString
   MAX-ACCESS   read-only
   STATUS       current
   DESCRIPTION
       ""
   ::= { gs2326plusSystemInformation 30 }

gs2326plusIPv6Address OBJECT-TYPE
   SYNTAX       DisplayString
   MAX-ACCESS   read-only
   STATUS       current
   DESCRIPTION
       ""
   ::= { gs2326plusSystemInformation 31 }

gs2326plusIPv6Prefix OBJECT-TYPE
   SYNTAX       DisplayString
   MAX-ACCESS   read-only
   STATUS       current
   DESCRIPTION
       ""
   ::= { gs2326plusSystemInformation 32 }

gs2326plusIPv6Gateway OBJECT-TYPE
   SYNTAX       DisplayString
   MAX-ACCESS   read-only
   STATUS       current
   DESCRIPTION
       ""
   ::= { gs2326plusSystemInformation 33 }

gs2326plusLargestFreeMemBlock OBJECT-TYPE
   SYNTAX       Integer32
   MAX-ACCESS   read-only
   STATUS       current
   DESCRIPTION
       "Largest free memory block in Kb"
   ::= { gs2326plusSystemInformation 1500 }

gs2326plusMemFree  OBJECT-TYPE
   SYNTAX       Integer32
   MAX-ACCESS   read-only
   STATUS       current
   DESCRIPTION
       "Free memory in Kb"
   ::= { gs2326plusSystemInformation 1501 }


gs2326plusSystemTime                                            OBJECT IDENTIFIER ::= { gs2326plusSystem 2 }

gs2326plusSystemTimeManual                                      OBJECT IDENTIFIER ::= { gs2326plusSystemTime 1 }

gs2326plusSystemTimeManualClockSource OBJECT-TYPE
   SYNTAX	INTEGER {useLocal(0),useNTP(1)}
   MAX-ACCESS   read-write
   STATUS       current
   DESCRIPTION
       "default: 0,
        0 : Use Local Settings,
        1 : Use NTP Server."
   ::= { gs2326plusSystemTimeManual 1 }

gs2326plusSystemTimeManualLocaltime OBJECT-TYPE
   SYNTAX       DisplayString
   MAX-ACCESS   read-write
   STATUS       current
   DESCRIPTION
       "Get/Set the system time of the device.
        The input format is 'Year-Month-Day Hour:Minute:Second'.
        ex: 2011-01-01 05:43:05  means 2011/1/1 - 05:43:05 .
        The value range:
        Year    : 2010 - 2090,
        Mouth   : 1 - 12,
        Day     : 1 - 31,
        Hour    : 0 - 23,
        Minute  : 0 - 59,
        Sec     : 0 - 59."
   ::= { gs2326plusSystemTimeManual 2 }

gs2326plusSystemTimeManualTimeZoneOffset OBJECT-TYPE
   SYNTAX       INTEGER(-720..780)
   MAX-ACCESS   read-write
   STATUS       current
   DESCRIPTION
       "Get/Set the NTP Time Zone.
        The value range is between -720 and 780 (minutes)."
   ::= { gs2326plusSystemTimeManual 3 }

gs2326plusSystemTimeManualDaylightSavings OBJECT-TYPE
   SYNTAX       INTEGER { disable(0), enable(1) }
   MAX-ACCESS   read-write
   STATUS       current
   DESCRIPTION
       "default: 0,
        0 : Disable,
        1 : Enable."
   ::= { gs2326plusSystemTimeManual 4 }

gs2326plusSystemTimeManualTimeSetOffset OBJECT-TYPE
   SYNTAX       Integer32(1..1440)
   MAX-ACCESS   read-write
   STATUS       current
   DESCRIPTION
       "Get/Set the Daylight Saving Time.
        The value range is between 1 and 1440 (minutes),
        Default : 60 (minutes)."
   ::= { gs2326plusSystemTimeManual 5 }

gs2326plusSystemTimeManualDaylightSavingsType OBJECT-TYPE
   SYNTAX       INTEGER { byDates(0), recurring(1) }
   MAX-ACCESS   read-write
   STATUS       current
   DESCRIPTION
       "default: 0,
        0 : By dates,
        1 : Recurring."
   ::= { gs2326plusSystemTimeManual 6 }

gs2326plusSystemTimeManualDaylightSavingsBydatesFrom OBJECT-TYPE
   SYNTAX       DisplayString
   MAX-ACCESS   read-write
   STATUS       current
   DESCRIPTION
       "Get/Set the Start time of By dates Daylight Savings.
        The input format is 'Year-Month-Day Hour:Minute'.
        ex: 2011-01-01 05:43  means 2011/1/1 - 05:43 .
        The value range:
        Year    : 2010 - 2090,
        Mouth   : 1 - 12,
        Day     : 1 - 31,
        Hour    : 0 - 23,
        Minute  : 0 - 59."
   ::= { gs2326plusSystemTimeManual 7 }

gs2326plusSystemTimeManualDaylightSavingsBydatesTo OBJECT-TYPE
   SYNTAX       DisplayString
   MAX-ACCESS   read-write
   STATUS       current
   DESCRIPTION
       "Get/Set the End time of By dates Daylight Savings.
        The input format is 'Year-Month-Day Hour:Minute'.
        ex: 2011-01-01 05:43  means 2011/1/1 - 05:43 .
        The value range:
        Year    : 2010 - 2090,
        Mouth   : 1 - 12,
        Day     : 1 - 31,
        Hour    : 0 - 23,
        Minute  : 0 - 59."
   ::= { gs2326plusSystemTimeManual 8 }

gs2326plusSystemTimeManualDaylightSavingsRecurringDayFrom OBJECT-TYPE
   SYNTAX      INTEGER {
                        sunday(0),
                        monday(1),
                        tuseday(2),
                        wednesday(3),
                        thursday(4),
                        friday(5),
                        saturday(6)
                        }
   MAX-ACCESS   read-write
   STATUS       current
   DESCRIPTION
       "Get/Set the Daylight Saving Time Day From.
        0 : Sun, 1 : Mon, 2 : Tue, 3 : Wed, 4 : Thu, 5 : Fri, 6 : Sat."
   ::= { gs2326plusSystemTimeManual 9 }

gs2326plusSystemTimeManualDaylightSavingsRecurringWeekFrom OBJECT-TYPE
   SYNTAX       INTEGER{
                        firstWeek(1),
                        secondWeek(2),
                        thirdWeek(3),
                        fourthWeek(4),
                        listWeek(5)
                        }
   MAX-ACCESS   read-write
   STATUS       current
   DESCRIPTION
       "Get/Set the Daylight Saving Time Week From.
        1 : first week, 2, 3, 4, 5 : last week"
   ::= { gs2326plusSystemTimeManual 10 }

gs2326plusSystemTimeManualDaylightSavingsRecurringMonthFrom OBJECT-TYPE
   SYNTAX      INTEGER {
                        jan(1),
                        feb(2),
                        mar(3),
                        apr(4),
                        may(5),
                        jun(6),
                        jul(7),
                        aug(8),
                        sep(9),
                        oct(10),
                        nov(11),
                        dec(12)
                        }
   MAX-ACCESS   read-write
   STATUS       current
   DESCRIPTION
       "Get/Set the Daylight Saving Time Month From.
        1 : Jan, 2 : Feb, 3 : Mar, 4 : Apr, 5 : May, 6 : Jun,
        7 : Jul, 8 : Aug, 9 : Sep, 10 : Oct, 11 : Nov, 12 : Dec."
   ::= { gs2326plusSystemTimeManual 11 }

gs2326plusSystemTimeManualDaylightSavingsRecurringTimeFrom OBJECT-TYPE
   SYNTAX       DisplayString
   MAX-ACCESS   read-write
   STATUS       current
   DESCRIPTION
       "Get/Set the Start time of By dates Daylight Savings.
        The input format is 'Hour:Minute'.
        ex: 05:43.
        The value range:
        Hour    : 0 - 23,
        Minute  : 0 - 59."
   ::= { gs2326plusSystemTimeManual 12 }

gs2326plusSystemTimeManualDaylightSavingsRecurringDayTo OBJECT-TYPE
   SYNTAX      INTEGER {
                        sunday(0),
                        monday(1),
                        tuseday(2),
                        wednesday(3),
                        thursday(4),
                        friday(5),
                        saturday(6)
                        }
   MAX-ACCESS   read-write
   STATUS       current
   DESCRIPTION
       "Get/Set the Daylight Saving Time Day To.
        0 : Sun, 1 : Mon, 2 : Tue, 3 : Wed, 4 : Thu, 5 : Fri, 6 : Sat."
   ::= { gs2326plusSystemTimeManual 13 }

gs2326plusSystemTimeManualDaylightSavingsRecurringWeekTo OBJECT-TYPE
   SYNTAX       INTEGER{
                        firstWeek(1),
                        secondWeek(2),
                        thirdWeek(3),
                        fourthWeek(4),
                        listWeek(5)
                        }
   MAX-ACCESS   read-write
   STATUS       current
   DESCRIPTION
       "Get/Set the Daylight Saving Time Week To.
        1 : first week, 2, 3, 4, 5 : last week"
   ::= { gs2326plusSystemTimeManual 14 }

gs2326plusSystemTimeManualDaylightSavingsRecurringMonthTo OBJECT-TYPE
   SYNTAX      INTEGER {
                        jan(1),
                        feb(2),
                        mar(3),
                        apr(4),
                        may(5),
                        jun(6),
                        jul(7),
                        aug(8),
                        sep(9),
                        oct(10),
                        nov(11),
                        dec(12)
                        }
   MAX-ACCESS   read-write
   STATUS       current
   DESCRIPTION
       "Get/Set the Daylight Saving Time Month To.
        1 : Jan, 2 : Feb, 3 : Mar, 4 : Apr, 5 : May, 6 : Jun,
        7 : Jul, 8 : Aug, 9 : Sep, 10 : Oct, 11 : Nov, 12 : Dec."
   ::= { gs2326plusSystemTimeManual 15 }

gs2326plusSystemTimeManualDaylightSavingsRecurringTimeTo OBJECT-TYPE
   SYNTAX       DisplayString
   MAX-ACCESS   read-write
   STATUS       current
   DESCRIPTION
       "Get/Set the Start time of By dates Daylight Savings.
        The input format is 'Hour:Minute'.
        ex: 05:43.
        The value range:
        Hour    : 0 - 23,
        Minute  : 0 - 59."
   ::= { gs2326plusSystemTimeManual 16 }

gs2326plusSystemTimeNTP                                     OBJECT IDENTIFIER ::= { gs2326plusSystemTime 2 }

gs2326plusSystemTimeNTPTable OBJECT-TYPE
   SYNTAX      SEQUENCE OF Gs2326plusSystemTimeNTPEntry
   MAX-ACCESS  not-accessible
   STATUS      current
   DESCRIPTION
       " "
   ::= { gs2326plusSystemTimeNTP 1 }

gs2326plusSystemTimeNTPEntry OBJECT-TYPE
   SYNTAX      Gs2326plusSystemTimeNTPEntry
   MAX-ACCESS  not-accessible
   STATUS      current
   DESCRIPTION
       ""
   INDEX    { gs2326plusSystemTimeNTPIndex  }
   ::= { gs2326plusSystemTimeNTPTable 1 }

Gs2326plusSystemTimeNTPEntry ::= SEQUENCE {
   gs2326plusSystemTimeNTPIndex             Integer32,
   gs2326plusSystemTimeNTPServerIPType      INTEGER,
   gs2326plusSystemTimeNTPServer            DisplayString,
   gs2326plusSystemTimeNTPCurrentMode       INTEGER
}

gs2326plusSystemTimeNTPIndex OBJECT-TYPE
   SYNTAX      Integer32(1..5)
   MAX-ACCESS  not-accessible
   STATUS      current
   DESCRIPTION
       " The index of the ntp entry. "
   ::= { gs2326plusSystemTimeNTPEntry 1 }

gs2326plusSystemTimeNTPServerIPType OBJECT-TYPE
   SYNTAX       INTEGER { ipv4(0), ipv6(1) }
   MAX-ACCESS   read-write
   STATUS       current
   DESCRIPTION
       "Default: 0,
        0 : IPv4,
        1 : IPv6."
   ::= { gs2326plusSystemTimeNTPEntry 2 }

gs2326plusSystemTimeNTPServer OBJECT-TYPE
   SYNTAX       DisplayString
   MAX-ACCESS   read-write
   STATUS       current
   DESCRIPTION
       "Get/Set the NTP Time Server1. You can use the IP address or domain name."
   ::= { gs2326plusSystemTimeNTPEntry 3 }

gs2326plusSystemTimeNTPCurrentMode OBJECT-TYPE
   SYNTAX      INTEGER { empty(0), active(1), edit(2), delete(3) }
   MAX-ACCESS  read-write
   STATUS      current
   DESCRIPTION
       " 0: Empty
        1: Active
        2: Edit
        3: Delete"
   ::= { gs2326plusSystemTimeNTPEntry 4 }

gs2326plusSystemTimeNTPRequestInterval OBJECT-TYPE
   SYNTAX       INTEGER(60..999999999)
   MAX-ACCESS   read-write
   STATUS       current
   DESCRIPTION
       "Get/Set the NTP Request Interval.
        Default : 86400.
        The value range is between 60 and 999999999 (seconds)."
   ::= { gs2326plusSystemTimeNTP 2 }

gs2326plusSystemTimeNTPTriesNumber OBJECT-TYPE
   SYNTAX       INTEGER(0..999999999)
   MAX-ACCESS   read-write
   STATUS       current
   DESCRIPTION
       "Get/Set the NTP Number of tries.
        Default : 4.
        The value range is between 0 and 999999999."
   ::= { gs2326plusSystemTimeNTP 3 }


gs2326plusSystemAccount                                         OBJECT IDENTIFIER ::= { gs2326plusSystem 3 }

gs2326plusSystemAccountUsers                                    OBJECT IDENTIFIER ::= { gs2326plusSystemAccount 1 }

gs2326plusSystemAccountUserCreate OBJECT-TYPE
   SYNTAX       INTEGER { none(0), create(1) }
   MAX-ACCESS   read-write
   STATUS       current
   DESCRIPTION
       "default: 0
        0 : None  (read only)
        1 : Create a user account"
   ::= { gs2326plusSystemAccountUsers 1 }

gs2326plusSystemAccountUsersTable OBJECT-TYPE
   SYNTAX      SEQUENCE OF Gs2326plusSystemAccountUsersEntry
   MAX-ACCESS  not-accessible
   STATUS      current
   DESCRIPTION
       " "
   ::= { gs2326plusSystemAccountUsers 2 }

gs2326plusSystemAccountUsersEntry OBJECT-TYPE
   SYNTAX      Gs2326plusSystemAccountUsersEntry
   MAX-ACCESS  not-accessible
   STATUS      current
   DESCRIPTION
       ""
   INDEX    { gs2326plusUserIndex  }
   ::= { gs2326plusSystemAccountUsersTable 1 }


Gs2326plusSystemAccountUsersEntry ::= SEQUENCE {
   gs2326plusUserIndex              Integer32 ,
   gs2326plusUserName               DisplayString,
   gs2326plusPassword               DisplayString,
   gs2326plusUserPrivilegeLevel     Integer32 ,
   gs2326plusAccountUserRowStatus   INTEGER
}


gs2326plusUserIndex OBJECT-TYPE
   SYNTAX      Integer32 (1..20)
   MAX-ACCESS  not-accessible
   STATUS      current
   DESCRIPTION
       " "
   ::= { gs2326plusSystemAccountUsersEntry 1 }

gs2326plusUserName OBJECT-TYPE
   SYNTAX      DisplayString (SIZE (1..32))
   MAX-ACCESS  read-write
   STATUS      current
   DESCRIPTION
       "Please use a combination of letters, numbers and underscores"
   ::= { gs2326plusSystemAccountUsersEntry 2 }

gs2326plusPassword OBJECT-TYPE
   SYNTAX      DisplayString (SIZE (1..32))
   MAX-ACCESS  read-write
   STATUS      current
   DESCRIPTION
       "Please use ASCII printable code except Quotation mark, Colon (punctuation), Less-than sign, Greater-than sign, At sign, Question mark and Space (punctuation)"
   ::= { gs2326plusSystemAccountUsersEntry 3 }

gs2326plusUserPrivilegeLevel OBJECT-TYPE
   SYNTAX      Integer32 (1..15)
   MAX-ACCESS  read-write
   STATUS      current
   DESCRIPTION
       "default:1
        User privilege level range : 1 - 15"
   ::= { gs2326plusSystemAccountUsersEntry 4 }

gs2326plusAccountUserRowStatus OBJECT-TYPE
   SYNTAX      INTEGER { active(1), notInservice(2), edit(3), destroy(4), undo(5) }
   MAX-ACCESS  read-write
   STATUS      current
   DESCRIPTION
       " 1: active
        2: notInservice
        3: edit
        4: destroy
        5: undo"
   ::= { gs2326plusSystemAccountUsersEntry 5 }

gs2326plusSystemAccountUsersSuperUserPassword OBJECT-TYPE
   SYNTAX      OCTET STRING (SIZE (0..32))
   MAX-ACCESS read-write
   STATUS      current
   DESCRIPTION
        "Super-User Password"
   ::= { gs2326plusSystemAccountUsers 1500 }

gs2326plusSystemAccountEnforcePasswordRules OBJECT-TYPE
   SYNTAX       INTEGER { yes(0), no(1) }
   MAX-ACCESS   read-write
   STATUS       current
   DESCRIPTION
       "default: 0
        0 : Do not enforce rules
        1 : enforce rules"
   ::= { gs2326plusSystemAccountUsers 1501 }

gs2326plusSystemAccountPrivilegeLevel                           OBJECT IDENTIFIER ::= { gs2326plusSystemAccount 2 }

gs2326plusAccountPrivilegeLevel OBJECT-TYPE
   SYNTAX      Integer32 (1..15)
   MAX-ACCESS  read-write
   STATUS      current
   DESCRIPTION
       "Default:15, Range : 1-15. "
   ::= { gs2326plusSystemAccountPrivilegeLevel 1 }

gs2326plusAggregationPrivilegeLevel OBJECT-TYPE
   SYNTAX      Integer32 (1..15)
   MAX-ACCESS  read-write
   STATUS      current
   DESCRIPTION
       "Default:15, Range : 1-15. "
   ::= { gs2326plusSystemAccountPrivilegeLevel 2 }

gs2326plusDiagnosticsPrivilegeLevel OBJECT-TYPE
   SYNTAX      Integer32 (1..15)
   MAX-ACCESS  read-write
   STATUS      current
   DESCRIPTION
       "Default:15, Range : 1-15. "
   ::= { gs2326plusSystemAccountPrivilegeLevel 3 }

gs2326plusEEEPrivilegeLevel OBJECT-TYPE
   SYNTAX      Integer32 (1..15)
   MAX-ACCESS  read-write
   STATUS      current
   DESCRIPTION
       "Default:15, Range : 1-15. "
   ::= { gs2326plusSystemAccountPrivilegeLevel 4 }

gs2326plusEasyportPrivilegeLevel OBJECT-TYPE
   SYNTAX      Integer32 (1..15)
   MAX-ACCESS  read-write
   STATUS      current
   DESCRIPTION
       "Default:15, Range : 1-15. "
   ::= { gs2326plusSystemAccountPrivilegeLevel 9 }

gs2326plusGARPPrivilegeLevel OBJECT-TYPE
   SYNTAX      Integer32 (1..15)
   MAX-ACCESS  read-write
   STATUS      current
   DESCRIPTION
       "Default:15, Range : 1-15. "
   ::= { gs2326plusSystemAccountPrivilegeLevel 10 }

gs2326plusGVRPPrivilegeLevel OBJECT-TYPE
   SYNTAX      Integer32 (1..15)
   MAX-ACCESS  read-write
   STATUS      current
   DESCRIPTION
       "Default:15, Range : 1-15. "
   ::= { gs2326plusSystemAccountPrivilegeLevel 11 }

gs2326plusIPPrivilegeLevel OBJECT-TYPE
   SYNTAX      Integer32 (1..15)
   MAX-ACCESS  read-write
   STATUS      current
   DESCRIPTION
       "Default:15, Range : 1-15. "
   ::= { gs2326plusSystemAccountPrivilegeLevel 12 }

gs2326plusIPMCSnoopingPrivilegeLevel OBJECT-TYPE
   SYNTAX      Integer32 (1..15)
   MAX-ACCESS  read-write
   STATUS      current
   DESCRIPTION
       "Default:15, Range : 1-15. "
   ::= { gs2326plusSystemAccountPrivilegeLevel 13 }

gs2326plusLACPPrivilegeLevel OBJECT-TYPE
   SYNTAX      Integer32 (1..15)
   MAX-ACCESS  read-write
   STATUS      current
   DESCRIPTION
       "Default:15, Range : 1-15. "
   ::= { gs2326plusSystemAccountPrivilegeLevel 14 }

gs2326plusLLDPPrivilegeLevel OBJECT-TYPE
   SYNTAX      Integer32 (1..15)
   MAX-ACCESS  read-write
   STATUS      current
   DESCRIPTION
       "Default:15, Range : 1-15. "
   ::= { gs2326plusSystemAccountPrivilegeLevel 15 }

gs2326plusLLDPMEDPrivilegeLevel OBJECT-TYPE
   SYNTAX      Integer32 (1..15)
   MAX-ACCESS  read-write
   STATUS      current
   DESCRIPTION
       "Default:15, Range : 1-15. "
   ::= { gs2326plusSystemAccountPrivilegeLevel 16 }

gs2326plusLoopProtectPrivilegeLevel OBJECT-TYPE
   SYNTAX      Integer32 (1..15)
   MAX-ACCESS  read-write
   STATUS      current
   DESCRIPTION
       "Default:15, Range : 1-15. "
   ::= { gs2326plusSystemAccountPrivilegeLevel 17 }

gs2326plusMACTablePrivilegeLevel OBJECT-TYPE
   SYNTAX      Integer32 (1..15)
   MAX-ACCESS  read-write
   STATUS      current
   DESCRIPTION
       "Default:15, Range : 1-15. "
   ::= { gs2326plusSystemAccountPrivilegeLevel 18 }

gs2326plusMVRPrivilegeLevel OBJECT-TYPE
   SYNTAX      Integer32 (1..15)
   MAX-ACCESS  read-write
   STATUS      current
   DESCRIPTION
       "Default:15, Range : 1-15. "
   ::= { gs2326plusSystemAccountPrivilegeLevel 22 }

gs2326plusMaintenancePrivilegeLevel OBJECT-TYPE
   SYNTAX      Integer32 (1..15)
   MAX-ACCESS  read-write
   STATUS      current
   DESCRIPTION
       "Default:15, Range : 1-15. "
   ::= { gs2326plusSystemAccountPrivilegeLevel 24 }

gs2326plusMirroringPrivilegeLevel OBJECT-TYPE
   SYNTAX      Integer32 (1..15)
   MAX-ACCESS  read-write
   STATUS      current
   DESCRIPTION
       "Default:15, Range : 1-15. "
   ::= { gs2326plusSystemAccountPrivilegeLevel 25 }

gs2326plusPortsPrivilegeLevel OBJECT-TYPE
   SYNTAX      Integer32 (1..15)
   MAX-ACCESS  read-write
   STATUS      current
   DESCRIPTION
       "Default:15, Range : 1-15. "
   ::= { gs2326plusSystemAccountPrivilegeLevel 27 }

gs2326plusPrivateVLANsPrivilegeLevel OBJECT-TYPE
   SYNTAX      Integer32 (1..15)
   MAX-ACCESS  read-write
   STATUS      current
   DESCRIPTION
       "Default:15, Range : 1-15. "
   ::= { gs2326plusSystemAccountPrivilegeLevel 28 }

gs2326plusQoSPrivilegeLevel OBJECT-TYPE
   SYNTAX      Integer32 (1..15)
   MAX-ACCESS  read-write
   STATUS      current
   DESCRIPTION
       "Default:15, Range : 1-15. "
   ::= { gs2326plusSystemAccountPrivilegeLevel 29 }

gs2326plusSFlowPrivilegeLevel OBJECT-TYPE
   SYNTAX      Integer32 (1..15)
   MAX-ACCESS  read-write
   STATUS      current
   DESCRIPTION
       "Default:15, Range : 1-15. "
   ::= { gs2326plusSystemAccountPrivilegeLevel 30 }

gs2326plusSMTPPrivilegeLevel OBJECT-TYPE
   SYNTAX      Integer32 (1..15)
   MAX-ACCESS  read-write
   STATUS      current
   DESCRIPTION
       "Default:15, Range : 1-15. "
   ::= { gs2326plusSystemAccountPrivilegeLevel 31 }

gs2326plusSNMPPrivilegeLevel OBJECT-TYPE
   SYNTAX      Integer32 (1..15)
   MAX-ACCESS  read-write
   STATUS      current
   DESCRIPTION
       "Default:15, Range : 1-15. "
   ::= { gs2326plusSystemAccountPrivilegeLevel 32 }

gs2326plusSecurityPrivilegeLevel OBJECT-TYPE
   SYNTAX      Integer32 (1..15)
   MAX-ACCESS  read-write
   STATUS      current
   DESCRIPTION
       "Default:15, Range : 1-15. "
   ::= { gs2326plusSystemAccountPrivilegeLevel 33 }

gs2326plusSingleIPPrivilegeLevel OBJECT-TYPE
   SYNTAX      Integer32 (1..15)
   MAX-ACCESS  read-write
   STATUS      current
   DESCRIPTION
       "Default:15, Range : 1-15. "
   ::= { gs2326plusSystemAccountPrivilegeLevel 34 }

gs2326plusSpanningTreePrivilegeLevel OBJECT-TYPE
   SYNTAX      Integer32 (1..15)
   MAX-ACCESS  read-write
   STATUS      current
   DESCRIPTION
       "Default:15, Range : 1-15. "
   ::= { gs2326plusSystemAccountPrivilegeLevel 35 }

gs2326plusSystemPrivilegeLevel OBJECT-TYPE
   SYNTAX      Integer32 (1..15)
   MAX-ACCESS  read-write
   STATUS      current
   DESCRIPTION
       "Default:15, Range : 1-15. "
   ::= { gs2326plusSystemAccountPrivilegeLevel 36 }

gs2326plusTrapEventPrivilegeLevel OBJECT-TYPE
   SYNTAX      Integer32 (1..15)
   MAX-ACCESS  read-write
   STATUS      current
   DESCRIPTION
       "Default:15, Range : 1-15. "
   ::= { gs2326plusSystemAccountPrivilegeLevel 37 }

gs2326plusUPnPPrivilegeLevel OBJECT-TYPE
   SYNTAX      Integer32 (1..15)
   MAX-ACCESS  read-write
   STATUS      current
   DESCRIPTION
       "Default:15, Range : 1-15. "
   ::= { gs2326plusSystemAccountPrivilegeLevel 38 }

gs2326plusVCLPrivilegeLevel OBJECT-TYPE
   SYNTAX      Integer32 (1..15)
   MAX-ACCESS  read-write
   STATUS      current
   DESCRIPTION
       "Default:15, Range : 1-15. "
   ::= { gs2326plusSystemAccountPrivilegeLevel 39 }

gs2326plusVLANsPrivilegeLevel OBJECT-TYPE
   SYNTAX      Integer32 (1..15)
   MAX-ACCESS  read-write
   STATUS      current
   DESCRIPTION
       "Default:15, Range : 1-15. "
   ::= { gs2326plusSystemAccountPrivilegeLevel 41 }

gs2326plusVoiceVLANPrivilegeLevel OBJECT-TYPE
   SYNTAX      Integer32 (1..15)
   MAX-ACCESS  read-write
   STATUS      current
   DESCRIPTION
       "Default:15, Range : 1-15. "
   ::= { gs2326plusSystemAccountPrivilegeLevel 42 }

gs2326plusIP                                                    OBJECT IDENTIFIER ::= { gs2326plusSystem 4 }

gs2326plusIPv4                                                  OBJECT IDENTIFIER ::= { gs2326plusIP 1 }

gs2326plusIPv4Configured                                                  OBJECT IDENTIFIER ::= { gs2326plusIPv4 1 }

gs2326plusIpv4DHCPClient OBJECT-TYPE
   SYNTAX      INTEGER { disable(0), enable(1) }
   MAX-ACCESS  read-write
   STATUS      current
   DESCRIPTION
       "default:0
       0: disable
       1: enable"
   ::= { gs2326plusIPv4Configured 1 }

gs2326plusIPv4Address OBJECT-TYPE
   SYNTAX      IpAddress
   MAX-ACCESS  read-write
   STATUS      current
   DESCRIPTION
       ""
   ::= { gs2326plusIPv4Configured 2 }

gs2326plusIPv4Mask OBJECT-TYPE
   SYNTAX      IpAddress
   MAX-ACCESS  read-write
   STATUS      current
   DESCRIPTION
       ""
   ::= { gs2326plusIPv4Configured 3 }

gs2326plusIPv4Gateway OBJECT-TYPE
   SYNTAX      IpAddress
   MAX-ACCESS  read-write
   STATUS      current
   DESCRIPTION
       ""
   ::= { gs2326plusIPv4Configured 4 }

gs2326plusIPv4VLANId OBJECT-TYPE
   SYNTAX      Integer32(1..4094)
   MAX-ACCESS  read-write
   STATUS      current
   DESCRIPTION
       "default:1"
   ::= { gs2326plusIPv4Configured 5 }

gs2326plusIPv4DNSServer OBJECT-TYPE
   SYNTAX      IpAddress
   MAX-ACCESS  read-write
   STATUS      current
   DESCRIPTION
       ""
   ::= { gs2326plusIPv4Configured 6 }

gs2326plusIPv4DNSProxy OBJECT-TYPE
   SYNTAX      INTEGER { disable(0), enable(1) }
   MAX-ACCESS  read-write
   STATUS      current
   DESCRIPTION
       "0:disable, 1:enable "
   ::= { gs2326plusIPv4Configured 7 }

gs2326plusIPv4Current                                                  OBJECT IDENTIFIER ::= { gs2326plusIPv4 2 }

gs2326plusIpv4CurrentDHCPClient OBJECT-TYPE
   SYNTAX      INTEGER { none(0), renew(1) }
   MAX-ACCESS  read-write
   STATUS      current
   DESCRIPTION
       "default:0
       0: none (for read)
       1: renew"
   ::= { gs2326plusIPv4Current 1 }

gs2326plusIPv4CurrentAddress OBJECT-TYPE
   SYNTAX      IpAddress
   MAX-ACCESS  read-only
   STATUS      current
   DESCRIPTION
       ""
   ::= { gs2326plusIPv4Current 2 }

gs2326plusIPv4CurrentMask OBJECT-TYPE
   SYNTAX      IpAddress
   MAX-ACCESS  read-only
   STATUS      current
   DESCRIPTION
       ""
   ::= { gs2326plusIPv4Current 3 }

gs2326plusIPv4CurrentGateway OBJECT-TYPE
   SYNTAX      IpAddress
   MAX-ACCESS  read-only
   STATUS      current
   DESCRIPTION
       ""
   ::= { gs2326plusIPv4Current 4 }

gs2326plusIPv4CurrentVLANId OBJECT-TYPE
   SYNTAX      Integer32(1..4094)
   MAX-ACCESS  read-only
   STATUS      current
   DESCRIPTION
       "default:1"
   ::= { gs2326plusIPv4Current 5 }

gs2326plusIPv4CurrentDNSServer OBJECT-TYPE
   SYNTAX      IpAddress
   MAX-ACCESS  read-only
   STATUS      current
   DESCRIPTION
       ""
   ::= { gs2326plusIPv4Current 6 }


gs2326plusIPv6                                                  OBJECT IDENTIFIER ::= { gs2326plusIP 2 }

gs2326plusIPv6Configured                                                  OBJECT IDENTIFIER ::= { gs2326plusIPv6 1 }

gs2326plusIpv6AutoConfiguration OBJECT-TYPE
   SYNTAX      INTEGER { disable(0), enable(1) }
   MAX-ACCESS  read-write
   STATUS      current
   DESCRIPTION
       "default:0
       0: disable
       1: enable"
   ::= { gs2326plusIPv6Configured 1 }

gs2326plusIpv6Address OBJECT-TYPE
   SYNTAX      DisplayString (SIZE (0..30))
   MAX-ACCESS  read-write
   STATUS      current
   DESCRIPTION
       ""
   ::= { gs2326plusIPv6Configured 2 }

gs2326plusIpv6Prefix OBJECT-TYPE
   SYNTAX      Integer32 (1..128)
   MAX-ACCESS  read-write
   STATUS      current
   DESCRIPTION
       "default: 96"
   ::= { gs2326plusIPv6Configured 3 }

gs2326plusIpv6Gateway OBJECT-TYPE
   SYNTAX      DisplayString (SIZE (0..30))
   MAX-ACCESS  read-write
   STATUS      current
   DESCRIPTION
       " "
   ::= { gs2326plusIPv6Configured 4 }

gs2326plusIPv6Current                                                  OBJECT IDENTIFIER ::= { gs2326plusIPv6 2 }

gs2326plusIpv6CurrentAutoConfiguration OBJECT-TYPE
   SYNTAX      INTEGER { disable(0), enable(1) }
   MAX-ACCESS  read-only
   STATUS      current
   DESCRIPTION
       "default:0
       0: disable
       1: enable"
   ::= { gs2326plusIPv6Current 1 }

gs2326plusIpv6CurrentAddress OBJECT-TYPE
   SYNTAX      DisplayString (SIZE (0..30))
   MAX-ACCESS  read-only
   STATUS      current
   DESCRIPTION
       ""
   ::= { gs2326plusIPv6Current 2 }


gs2326plusIpv6CurrentLinkLocalAddress OBJECT-TYPE
   SYNTAX      DisplayString(SIZE (0..30))
   MAX-ACCESS  read-only
   STATUS      current
   DESCRIPTION
       ""
   ::= { gs2326plusIPv6Current 3 }


gs2326plusIpv6CurrentPrefix OBJECT-TYPE
   SYNTAX      DisplayString(SIZE (0..64))
   MAX-ACCESS  read-only
   STATUS      current
   DESCRIPTION
       ""
   ::= { gs2326plusIPv6Current 4 }

gs2326plusIpv6CurrentGateway OBJECT-TYPE
   SYNTAX      DisplayString (SIZE (0..30))
   MAX-ACCESS  read-only
   STATUS      current
   DESCRIPTION
       " "
   ::= { gs2326plusIPv6Current 5 }

gs2326plusSyslog                                                OBJECT IDENTIFIER ::= { gs2326plusSystem 5 }

gs2326plusSyslogConf                                            OBJECT IDENTIFIER ::= { gs2326plusSyslog 1 }

gs2326plusServerMode OBJECT-TYPE
   SYNTAX      INTEGER { disable(0), enable(1) }
   MAX-ACCESS  read-write
   STATUS      current
   DESCRIPTION
       "default: 0
       0: disable
       1: enable "
   ::= { gs2326plusSyslogConf 1 }

gs2326plusServerAddress1 OBJECT-TYPE
   SYNTAX      IpAddress
   MAX-ACCESS  read-write
   STATUS      current
   DESCRIPTION
       " "
   ::= { gs2326plusSyslogConf 2 }

gs2326plusServerAddress2 OBJECT-TYPE
   SYNTAX      IpAddress
   MAX-ACCESS  read-write
   STATUS      current
   DESCRIPTION
       " "
   ::= { gs2326plusSyslogConf 3 }

gs2326plusSyslogLevel OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       "default: 6 (Info)
       0: Emergency
       1: Alert
       2: Critical
       3: Error
       4: Warning
       5: Notice
       6: Info
       7: Debug"
   ::= { gs2326plusSyslogConf 4 }

gs2326plusSyslogDetailedInfo                                    OBJECT IDENTIFIER ::= { gs2326plusSyslog 2 }

gs2326plusSyslogDetailedInfoClear OBJECT-TYPE
   SYNTAX      INTEGER { none(0), clear(1) }
   MAX-ACCESS  read-write
   STATUS      current
   DESCRIPTION
      "default: 0
       0 : None  (read only)
       1 : Clear Syslog"
   ::= { gs2326plusSyslogDetailedInfo 1 }

gs2326plusSyslogDetailedInfoTable OBJECT-TYPE
  SYNTAX      SEQUENCE OF Gs2326plusSyslogDetailedInfoEntry
  MAX-ACCESS  not-accessible
  STATUS      current
  DESCRIPTION
           " "
       ::= { gs2326plusSyslogDetailedInfo 2 }

gs2326plusSyslogDetailedInfoEntry OBJECT-TYPE
   SYNTAX      Gs2326plusSyslogDetailedInfoEntry
   MAX-ACCESS  not-accessible
   STATUS      current
   DESCRIPTION
           ""
   INDEX    { gs2326plusSyslogDetailedInfoIndex  }
   ::= { gs2326plusSyslogDetailedInfoTable 1 }

Gs2326plusSyslogDetailedInfoEntry ::= SEQUENCE {
   gs2326plusSyslogDetailedInfoIndex       Integer32,
   gs2326plusSyslogDetailedInfoLevel       DisplayString,
   gs2326plusSyslogDetailedInfoTime        DisplayString,
   gs2326plusSyslogDetailedInfoMessage     DisplayString
}

gs2326plusSyslogDetailedInfoIndex OBJECT-TYPE
   SYNTAX      Integer32(1..1024)
   MAX-ACCESS  not-accessible
   STATUS      current
   DESCRIPTION
       " "
   ::= { gs2326plusSyslogDetailedInfoEntry 1 }

gs2326plusSyslogDetailedInfoLevel OBJECT-TYPE
   SYNTAX      DisplayString
   MAX-ACCESS  read-only
   STATUS      current
   DESCRIPTION
       " "
   ::= { gs2326plusSyslogDetailedInfoEntry 2 }

gs2326plusSyslogDetailedInfoTime OBJECT-TYPE
   SYNTAX      DisplayString(SIZE (0..20))
   MAX-ACCESS  read-only
   STATUS      current
   DESCRIPTION
       " "
   ::= { gs2326plusSyslogDetailedInfoEntry 3 }

gs2326plusSyslogDetailedInfoMessage OBJECT-TYPE
   SYNTAX      DisplayString
   MAX-ACCESS  read-only
   STATUS      current
   DESCRIPTION
       " "
   ::= { gs2326plusSyslogDetailedInfoEntry 4 }


gs2326plusSnmp                                                OBJECT IDENTIFIER ::= { gs2326plusSystem 6 }

gs2326plusSnmpConf                                            OBJECT IDENTIFIER ::= { gs2326plusSnmp 1 }

gs2326plusGetCommunityMode OBJECT-TYPE
   SYNTAX       INTEGER { disable(0), enable(1) }
   MAX-ACCESS   read-write
   STATUS       current
   DESCRIPTION
       "Get/Set the get-community mode of the SNMP.
        default : 1, 0: disable, 1: enable. "
   ::= { gs2326plusSnmpConf 1 }

gs2326plusGetCommunity OBJECT-TYPE
   SYNTAX       DisplayString
   MAX-ACCESS   read-write
   STATUS       current
   DESCRIPTION
       "Get/Set the get-community of the SNMP."
   ::= { gs2326plusSnmpConf 2 }

gs2326plusSetCommunityMode OBJECT-TYPE
   SYNTAX       INTEGER { disable(0), enable(1) }
   MAX-ACCESS   read-write
   STATUS       current
   DESCRIPTION
       "Get/Set the set-community mode of the SNMP.
        default : 1, 0: disable, 1: enable. "
   ::= { gs2326plusSnmpConf 3 }

gs2326plusSetCommunity OBJECT-TYPE
   SYNTAX       DisplayString
   MAX-ACCESS   read-write
   STATUS       current
   DESCRIPTION
       "Get/Set the set-community of the SNMP."
   ::= { gs2326plusSnmpConf 4 }

gs2326plusGetCommunityConfTable OBJECT-TYPE
   SYNTAX      SEQUENCE OF GS2326PLUSGetCommunityConfEntry
   MAX-ACCESS  not-accessible
   STATUS      current
   DESCRIPTION
       " Show get-community of the SNMP. "
   ::= { gs2326plusSnmpConf 5 }

gs2326plusGetCommunityConfEntry OBJECT-TYPE
   SYNTAX      GS2326PLUSGetCommunityConfEntry
   MAX-ACCESS  not-accessible
   STATUS      current
   DESCRIPTION
       ""
   INDEX    { gs2326plusCommunityConfIndex  }
   ::= { gs2326plusGetCommunityConfTable 1 }

GS2326PLUSGetCommunityConfEntry ::= SEQUENCE {
   gs2326plusCommunityConfIndex				Integer32,
   gs2326plusCommunityConfGetCommunity			DisplayString
}

gs2326plusCommunityConfIndex OBJECT-TYPE
   SYNTAX      Integer32(1..4095)
   MAX-ACCESS  not-accessible
   STATUS      current
   DESCRIPTION
       " index, range : 1 - 5. "
   ::= { gs2326plusGetCommunityConfEntry 1 }

gs2326plusCommunityConfGetCommunity OBJECT-TYPE
   SYNTAX      DisplayString
   MAX-ACCESS  read-write
   STATUS      current
   DESCRIPTION
       " Get/Set the get-community of the SNMP."
   ::= { gs2326plusGetCommunityConfEntry 2 }

gs2326plusTrapHostConfTable OBJECT-TYPE
   SYNTAX      SEQUENCE OF GS2326PLUSTrapHostConfEntry
   MAX-ACCESS  not-accessible
   STATUS      current
   DESCRIPTION
       "A list of trap host entry. The numbers of entries are given by the value of gs2326plusTrapHostConfNumber."
   ::= { gs2326plusSnmpConf 6 }

gs2326plusTrapHostConfEntry OBJECT-TYPE
   SYNTAX      GS2326PLUSTrapHostConfEntry
   MAX-ACCESS  not-accessible
   STATUS      current
   DESCRIPTION
       "This is the entry information for trap host."
   INDEX    { gs2326plusTrapHostConfIndex  }
   ::= { gs2326plusTrapHostConfTable 1 }

GS2326PLUSTrapHostConfEntry ::= SEQUENCE {
    gs2326plusTrapHostConfIndex             Integer32,
    gs2326plusTrapHostConfVersion           INTEGER,
    gs2326plusTrapHostConfIPType            INTEGER,
    gs2326plusTrapHostConfIP                DisplayString,
    gs2326plusTrapHostConfPort              Integer32,
    gs2326plusTrapHostConfCommunity         DisplayString,
    gs2326plusTrapHostConfSeverityLevel     INTEGER,
    gs2326plusTrapHostConfSecurityLevel     INTEGER,
    gs2326plusTrapHostConfAuthPtc           INTEGER,
    gs2326plusTrapHostConfAuthPassword      DisplayString,
    gs2326plusTrapHostConfPrivPtc           INTEGER,
    gs2326plusTrapHostConfPrivPassword      DisplayString,
    gs2326plusTrapHostConfCurrentMode       INTEGER
}

gs2326plusTrapHostConfIndex OBJECT-TYPE
   SYNTAX      Integer32(1..6)
   MAX-ACCESS  not-accessible
   STATUS      current
   DESCRIPTION
       " The index of the trap host entry. "
   ::= { gs2326plusTrapHostConfEntry 1 }

gs2326plusTrapHostConfVersion OBJECT-TYPE
   SYNTAX       INTEGER { snmpv2c(2), snmpv3(3) }
   MAX-ACCESS   read-write
   STATUS       current
   DESCRIPTION
       "The version of the Trap PDU. Version : 2(SNMPv2c), 3(SNMPv3)"
   ::= { gs2326plusTrapHostConfEntry 2 }

gs2326plusTrapHostConfIPType OBJECT-TYPE
   SYNTAX       INTEGER { ipv4(4), ipv6(6) }
   MAX-ACCESS   read-write
   STATUS       current
   DESCRIPTION
       "Server IP Type. Default: 4,
        4 : IPv4,
        6 : IPv6."
   ::= { gs2326plusTrapHostConfEntry 3 }

gs2326plusTrapHostConfIP OBJECT-TYPE
   SYNTAX       DisplayString
   MAX-ACCESS   read-write
   STATUS       current
   DESCRIPTION
       "This is the IP of the trap host."
   ::= { gs2326plusTrapHostConfEntry 4 }

gs2326plusTrapHostConfPort OBJECT-TYPE
   SYNTAX       Integer32(1..65535)
   MAX-ACCESS   read-write
   STATUS       current
   DESCRIPTION
       "This is the receiving-port number of the trap host.
        range : 1 - 65535."
   ::= { gs2326plusTrapHostConfEntry 5 }

gs2326plusTrapHostConfCommunity OBJECT-TYPE
   SYNTAX       DisplayString (SIZE (1..32))
   MAX-ACCESS   read-write
   STATUS       current
   DESCRIPTION
       "The community/security name for the trap PDU."
   ::= { gs2326plusTrapHostConfEntry 6 }

gs2326plusTrapHostConfSeverityLevel	OBJECT-TYPE
   SYNTAX      INTEGER {
                    emergency(0),
                    alert(1),
                    critical(2),
                    error(3),
                    warning(4),
                    notice(5),
                    info(6),
                    debug(7)
                }
   MAX-ACCESS   read-write
   STATUS       current
   DESCRIPTION
       "The Severity Level.
        0 : Emerg, 1 : Alert, 2 : Critical, 3 : Error, 4 : Warning, 5 : Notice, 6 : Info, 7 : Debug."
	::= { gs2326plusTrapHostConfEntry 7 }

gs2326plusTrapHostConfSecurityLevel	OBJECT-TYPE
   SYNTAX       INTEGER { noAuthNoPriv(1), authNoPriv(2), authPriv(3) }
   MAX-ACCESS   read-write
   STATUS       current
   DESCRIPTION
       "The Security Level, NoAuthNoPriv, AuthNoPriv, and AuthPriv.
        1 : NoAuthNoPriv, 2 : AuthNoPriv, 3 : AuthPriv.
        Privacy protocol will be configured as 'DES' automatically if security level is 3(AuthPriv)."
	::= { gs2326plusTrapHostConfEntry 8 }

gs2326plusTrapHostConfAuthPtc	OBJECT-TYPE
   SYNTAX       INTEGER { md5(1), sha(2) }
   MAX-ACCESS   read-write
   STATUS       current
   DESCRIPTION
       "Authentication Protocol, there are SHA and MD5 supported presently.
        1 : MD5, 2 : SHA."
	::= { gs2326plusTrapHostConfEntry 9 }

gs2326plusTrapHostConfAuthPassword	OBJECT-TYPE
   SYNTAX      DisplayString
   MAX-ACCESS  read-write
   STATUS		current
   DESCRIPTION
       "Authentication Password, is used for authenticating. The return value is always '********'.
        If the authentication protocol is MD5, the length of password should be 8 ~ 32 characters.
        If the authentication protocol is SHA, the length of password should be 8 ~ 40 characters."
   ::= { gs2326plusTrapHostConfEntry 10 }

gs2326plusTrapHostConfPrivPtc	OBJECT-TYPE
   SYNTAX       INTEGER { des(1) }
   MAX-ACCESS   read-write
   STATUS       current
   DESCRIPTION
       "This is the Privacy Protocol, which is used in AuthPriv. Only supports DES.
        An empty string will be returned if the security level is not 3(AuthPriv).
        1 : DES."
	::= { gs2326plusTrapHostConfEntry 11 }

gs2326plusTrapHostConfPrivPassword	OBJECT-TYPE
   SYNTAX       DisplayString
   MAX-ACCESS   read-write
   STATUS       current
   DESCRIPTION
       "The password is Privacy Key.  The return value is always '********'.  This Key
        must be more than 8 characters, and less than 32 characters."
   ::= { gs2326plusTrapHostConfEntry 12 }

gs2326plusTrapHostConfCurrentMode OBJECT-TYPE
   SYNTAX       INTEGER { empty(0), active(1), edit(2), delete(3) }
   MAX-ACCESS   read-write
   STATUS       current
   DESCRIPTION
       "0:Empty, 1:Active mode, 2:Edit mode, 3:Delete."
   ::= { gs2326plusTrapHostConfEntry 13 }


gs2326plusSnmpSystem                                          OBJECT IDENTIFIER ::= { gs2326plusSnmp 2 }

gs2326plusSnmpState OBJECT-TYPE
   SYNTAX       INTEGER { disable(0), enable(1) }
   MAX-ACCESS   read-write
   STATUS       current
   DESCRIPTION
       "Get/Set the state of the SNMP.
        default : 1, 0: disable, 1: enable. "
   ::= { gs2326plusSnmpSystem 1 }

gs2326plusSnmpEngineID OBJECT-TYPE
   SYNTAX       OCTET STRING (SIZE(5..32))
   MAX-ACCESS   read-write
   STATUS       current
   DESCRIPTION
       "Get/Set the Engine ID of the SNMP.
        An SNMP engine's administratively-unique identifier."
   ::= { gs2326plusSnmpSystem 2 }

gs2326plusSnmpCommunities                                          OBJECT IDENTIFIER ::= { gs2326plusSnmp 3 }

gs2326plusSnmpCommunitiesCreate OBJECT-TYPE
   SYNTAX       INTEGER { none(0), create(1) }
   MAX-ACCESS   read-write
   STATUS       current
   DESCRIPTION
       "default: 0
        0 : None  (read only)
        1 : Create entry"
   ::= { gs2326plusSnmpCommunities 1 }

gs2326plusSnmpCommunitiesTable OBJECT-TYPE
   SYNTAX      SEQUENCE OF GS2326PLUSSnmpCommunitiesEntry
   MAX-ACCESS  not-accessible
   STATUS      current
   DESCRIPTION
       " Create SNMPv1/v2 Communities entry."
   ::= { gs2326plusSnmpCommunities 2 }

gs2326plusSnmpCommunitiesEntry OBJECT-TYPE
   SYNTAX      GS2326PLUSSnmpCommunitiesEntry
   MAX-ACCESS  not-accessible
   STATUS      current
   DESCRIPTION
       ""
   INDEX    { gs2326plusSnmpCommunitiesIndex  }
   ::= { gs2326plusSnmpCommunitiesTable 1 }

GS2326PLUSSnmpCommunitiesEntry ::= SEQUENCE {
   gs2326plusSnmpCommunitiesIndex          Integer32,
   gs2326plusSnmpCommunitiesCommunity      DisplayString,
   gs2326plusSnmpCommunitiesUserName       DisplayString,
   gs2326plusSnmpCommunitiesSourceIP       IpAddress,
   gs2326plusSnmpCommunitiesSourceMask     IpAddress,
   gs2326plusSnmpCommunitiesRowStatus      INTEGER
}

gs2326plusSnmpCommunitiesIndex OBJECT-TYPE
   SYNTAX      Integer32(1..4)
   MAX-ACCESS  not-accessible
   STATUS      current
   DESCRIPTION
       " "
   ::= { gs2326plusSnmpCommunitiesEntry 1 }

gs2326plusSnmpCommunitiesCommunity OBJECT-TYPE
   SYNTAX      DisplayString (SIZE (1..32))
   MAX-ACCESS  read-write
   STATUS      current
   DESCRIPTION
       "Up to 32 characters describing Community."
   ::= { gs2326plusSnmpCommunitiesEntry 2 }

gs2326plusSnmpCommunitiesUserName OBJECT-TYPE
   SYNTAX      DisplayString (SIZE (1..32))
   MAX-ACCESS  read-write
   STATUS      current
   DESCRIPTION
       " Up to 32 characters describing User Name. "
   ::= { gs2326plusSnmpCommunitiesEntry 3 }

gs2326plusSnmpCommunitiesSourceIP OBJECT-TYPE
   SYNTAX      IpAddress
   MAX-ACCESS  read-write
   STATUS      current
   DESCRIPTION
       " SNMP access source ip. "
   ::= { gs2326plusSnmpCommunitiesEntry 4 }

gs2326plusSnmpCommunitiesSourceMask OBJECT-TYPE
   SYNTAX      IpAddress
   MAX-ACCESS  read-write
   STATUS      current
   DESCRIPTION
       " SNMP access source address mask. "
   ::= { gs2326plusSnmpCommunitiesEntry 5 }

gs2326plusSnmpCommunitiesRowStatus OBJECT-TYPE
   SYNTAX      INTEGER { active(1), notInservice(2), destroy(4), undo(5) }
   MAX-ACCESS  read-write
   STATUS      current
   DESCRIPTION
       "1: active
        2: notInservice
        4: destroy
        5: undo"
   ::= { gs2326plusSnmpCommunitiesEntry 6 }


gs2326plusSnmpUsers                                          OBJECT IDENTIFIER ::= { gs2326plusSnmp 4 }

gs2326plusSnmpUsersCreate OBJECT-TYPE
   SYNTAX       INTEGER { none(0), create(1) }
   MAX-ACCESS   read-write
   STATUS       current
   DESCRIPTION
       "default: 0
        0 : None  (read only)
        1 : Create entry"
   ::= { gs2326plusSnmpUsers 1 }

gs2326plusSnmpUsersTable OBJECT-TYPE
   SYNTAX      SEQUENCE OF GS2326PLUSSnmpUsersEntry
   MAX-ACCESS  not-accessible
   STATUS      current
   DESCRIPTION
       " Create SNMPv3 users entry."
   ::= { gs2326plusSnmpUsers 2 }

gs2326plusSnmpUsersEntry OBJECT-TYPE
   SYNTAX      GS2326PLUSSnmpUsersEntry
   MAX-ACCESS  not-accessible
   STATUS      current
   DESCRIPTION
       ""
   INDEX    { gs2326plusSnmpUsersIndex  }
   ::= { gs2326plusSnmpUsersTable 1 }

GS2326PLUSSnmpUsersEntry ::= SEQUENCE {
   gs2326plusSnmpUsersIndex                    Integer32,
   gs2326plusSnmpUsersUserName                 DisplayString,
   gs2326plusSnmpUsersSecurityLevel            INTEGER,
   gs2326plusSnmpUsersAuthenticationProtocol   INTEGER,
   gs2326plusSnmpUsersAuthenticationPassword   DisplayString,
   gs2326plusSnmpUsersPrivacyProtocol          INTEGER,
   gs2326plusSnmpUsersPrivacyPassword          DisplayString,
   gs2326plusSnmpUsersRowStatus                INTEGER
}

gs2326plusSnmpUsersIndex OBJECT-TYPE
   SYNTAX      Integer32(1..10)
   MAX-ACCESS  not-accessible
   STATUS      current
   DESCRIPTION
       " "
   ::= { gs2326plusSnmpUsersEntry 1 }

gs2326plusSnmpUsersUserName OBJECT-TYPE
   SYNTAX      DisplayString (SIZE (1..32))
   MAX-ACCESS  read-write
   STATUS      current
   DESCRIPTION
       "Up to 32 characters describing User Name."
   ::= { gs2326plusSnmpUsersEntry 2 }

gs2326plusSnmpUsersSecurityLevel OBJECT-TYPE
   SYNTAX      INTEGER { noauthnopriv(1), authnopriv(2), authpriv(3) }
   MAX-ACCESS  read-write
   STATUS      current
   DESCRIPTION
       " 1: No authentication and no privacy.
         2: Authentication and no privacy.
         3: Authentication and privacy. "
   ::= { gs2326plusSnmpUsersEntry 3 }

gs2326plusSnmpUsersAuthenticationProtocol OBJECT-TYPE
   SYNTAX      INTEGER { none(0), md5(1), sha(2) }
   MAX-ACCESS  read-write
   STATUS      current
   DESCRIPTION
       " 0: None.
         1: MD5.
         2: SHA "
   ::= { gs2326plusSnmpUsersEntry 4 }

gs2326plusSnmpUsersAuthenticationPassword OBJECT-TYPE
   SYNTAX      DisplayString
   MAX-ACCESS  read-write
   STATUS      current
   DESCRIPTION
       " Authentication Password, is used for authenticating. The return value is always '********'.
         If the authentication protocol is MD5, the length of password should be 8 ~ 32 characters.
         If the authentication protocol is SHA, the length of password should be 8 ~ 40 characters. "
   ::= { gs2326plusSnmpUsersEntry 5 }

gs2326plusSnmpUsersPrivacyProtocol OBJECT-TYPE
   SYNTAX      INTEGER { none(0), des(1), aes(2) }
   MAX-ACCESS  read-write
   STATUS      current
   DESCRIPTION
       " 0: None.
         1: DES.
         2: AES
         This is the Privacy Protocol, which is used in AuthPriv.
         An empty string will be returned if the security level is not 3(AuthPriv) "
   ::= { gs2326plusSnmpUsersEntry 6 }

gs2326plusSnmpUsersPrivacyPassword OBJECT-TYPE
   SYNTAX      DisplayString
   MAX-ACCESS  read-write
   STATUS      current
   DESCRIPTION
       " The password is Privacy Key.  The return value is always '********'.  This Key
        must be more than 8 characters, and less than 32 characters. "
   ::= { gs2326plusSnmpUsersEntry 7 }

gs2326plusSnmpUsersRowStatus OBJECT-TYPE
   SYNTAX      INTEGER { active(1), notInservice(2), destroy(4), undo(5) }
   MAX-ACCESS  read-write
   STATUS      current
   DESCRIPTION
       "1: active
        2: notInservice
        4: destroy
        5: undo"
   ::= { gs2326plusSnmpUsersEntry 8 }


gs2326plusSnmpGroups                                          OBJECT IDENTIFIER ::= { gs2326plusSnmp 5 }

gs2326plusSnmpGroupsCreate OBJECT-TYPE
   SYNTAX       INTEGER { none(0), create(1) }
   MAX-ACCESS   read-write
   STATUS       current
   DESCRIPTION
       "default: 0
        0 : None  (read only)
        1 : Create entry"
   ::= { gs2326plusSnmpGroups 1 }

gs2326plusSnmpGroupsTable OBJECT-TYPE
   SYNTAX      SEQUENCE OF GS2326PLUSSnmpGroupsEntry
   MAX-ACCESS  not-accessible
   STATUS      current
   DESCRIPTION
       " Create SNMPv3 groups entry."
   ::= { gs2326plusSnmpGroups 2 }

gs2326plusSnmpGroupsEntry OBJECT-TYPE
   SYNTAX      GS2326PLUSSnmpGroupsEntry
   MAX-ACCESS  not-accessible
   STATUS      current
   DESCRIPTION
       ""
   INDEX    { gs2326plusSnmpGroupsIndex  }
   ::= { gs2326plusSnmpGroupsTable 1 }

GS2326PLUSSnmpGroupsEntry ::= SEQUENCE {
   gs2326plusSnmpGroupsIndex           Integer32,
   gs2326plusSnmpGroupsSecurityModel   INTEGER,
   gs2326plusSnmpGroupsSecurityName    DisplayString,
   gs2326plusSnmpGroupsGroupName       DisplayString,
   gs2326plusSnmpGroupsRowStatus       INTEGER
}

gs2326plusSnmpGroupsIndex OBJECT-TYPE
   SYNTAX      Integer32(1..14)
   MAX-ACCESS  not-accessible
   STATUS      current
   DESCRIPTION
       " "
   ::= { gs2326plusSnmpGroupsEntry 1 }

gs2326plusSnmpGroupsSecurityModel OBJECT-TYPE
   SYNTAX      INTEGER { v1(1), v2c(2), usm(3) }
   MAX-ACCESS  read-write
   STATUS      current
   DESCRIPTION
       " 1: v1.
         2: v2c.
         3: usm."
   ::= { gs2326plusSnmpGroupsEntry 2 }

gs2326plusSnmpGroupsSecurityName OBJECT-TYPE
   SYNTAX      DisplayString (SIZE (1..32))
   MAX-ACCESS  read-write
   STATUS      current
   DESCRIPTION
       "Up to 32 characters describing User Name."
   ::= { gs2326plusSnmpGroupsEntry 3 }

gs2326plusSnmpGroupsGroupName OBJECT-TYPE
   SYNTAX      DisplayString (SIZE (1..32))
   MAX-ACCESS  read-write
   STATUS      current
   DESCRIPTION
       "Up to 32 characters describing Group Name."
   ::= { gs2326plusSnmpGroupsEntry 4 }

gs2326plusSnmpGroupsRowStatus OBJECT-TYPE
   SYNTAX      INTEGER { active(1), notInservice(2), destroy(4), undo(5) }
   MAX-ACCESS  read-write
   STATUS      current
   DESCRIPTION
       "1: active
        2: notInservice
        4: destroy
        5: undo"
   ::= { gs2326plusSnmpGroupsEntry 5 }

gs2326plusSnmpViews                                              OBJECT IDENTIFIER ::= { gs2326plusSnmp 6 }

gs2326plusSnmpViewsCreate OBJECT-TYPE
   SYNTAX       INTEGER { none(0), create(1) }
   MAX-ACCESS   read-write
   STATUS       current
   DESCRIPTION
       "default: 0
        0 : None  (read only)
        1 : Create entry"
   ::= { gs2326plusSnmpViews 1 }

gs2326plusSnmpViewsTable OBJECT-TYPE
   SYNTAX      SEQUENCE OF GS2326PLUSSnmpViewsEntry
   MAX-ACCESS  not-accessible
   STATUS      current
   DESCRIPTION
       " Create SNMPv1/v2 Views entry."
   ::= { gs2326plusSnmpViews 2 }

gs2326plusSnmpViewsEntry OBJECT-TYPE
   SYNTAX      GS2326PLUSSnmpViewsEntry
   MAX-ACCESS  not-accessible
   STATUS      current
   DESCRIPTION
       ""
   INDEX    { gs2326plusSnmpViewsIndex  }
   ::= { gs2326plusSnmpViewsTable 1 }

GS2326PLUSSnmpViewsEntry ::= SEQUENCE {
   gs2326plusSnmpViewsIndex        Integer32,
   gs2326plusSnmpViewsName         DisplayString,
   gs2326plusSnmpViewsType         INTEGER,
   gs2326plusSnmpViewsOIDSubtree   DisplayString,
   gs2326plusSnmpViewsRowStatus    INTEGER
}

gs2326plusSnmpViewsIndex OBJECT-TYPE
   SYNTAX      Integer32(1..4)
   MAX-ACCESS  not-accessible
   STATUS      current
   DESCRIPTION
       " "
   ::= { gs2326plusSnmpViewsEntry 1 }

gs2326plusSnmpViewsName OBJECT-TYPE
   SYNTAX      DisplayString (SIZE (1..32))
   MAX-ACCESS  read-write
   STATUS      current
   DESCRIPTION
       "Up to 32 characters describing view Name."
   ::= { gs2326plusSnmpViewsEntry 2 }

gs2326plusSnmpViewsType OBJECT-TYPE
   SYNTAX      INTEGER { included(1), excluded(2) }
   MAX-ACCESS  read-write
   STATUS      current
   DESCRIPTION
       "1: included, An optional flag to indicate that this view subtree should be included.
	   2: excluded, An optional flag to indicate that this view subtree should be excluded."
   ::= { gs2326plusSnmpViewsEntry 3 }

gs2326plusSnmpViewsOIDSubtree OBJECT-TYPE
   SYNTAX      DisplayString (SIZE (1..128))
   MAX-ACCESS  read-write
   STATUS      current
   DESCRIPTION
       "The OID defining the root of the subtree to add to the named view."
   ::= { gs2326plusSnmpViewsEntry 4 }

gs2326plusSnmpViewsRowStatus OBJECT-TYPE
   SYNTAX      INTEGER { active(1), notInservice(2), destroy(4), undo(5) }
   MAX-ACCESS  read-write
   STATUS      current
   DESCRIPTION
       "1: active
        2: notInservice
        4: destroy
        5: undo"
   ::= { gs2326plusSnmpViewsEntry 5 }


gs2326plusSnmpAccess                                          OBJECT IDENTIFIER ::= { gs2326plusSnmp 7 }

gs2326plusSnmpAccessCreate OBJECT-TYPE
   SYNTAX       INTEGER { none(0), create(1) }
   MAX-ACCESS   read-write
   STATUS       current
   DESCRIPTION
       "default: 0
        0 : None  (read only)
        1 : Create entry"
   ::= { gs2326plusSnmpAccess 1 }

gs2326plusSnmpAccessTable OBJECT-TYPE
   SYNTAX      SEQUENCE OF GS2326PLUSSnmpAccessEntry
   MAX-ACCESS  not-accessible
   STATUS      current
   DESCRIPTION
       " Create SNMPv3 Access entry."
   ::= { gs2326plusSnmpAccess 2 }

gs2326plusSnmpAccessEntry OBJECT-TYPE
   SYNTAX      GS2326PLUSSnmpAccessEntry
   MAX-ACCESS  not-accessible
   STATUS      current
   DESCRIPTION
       ""
   INDEX    { gs2326plusSnmpAccessIndex  }
   ::= { gs2326plusSnmpAccessTable 1 }

GS2326PLUSSnmpAccessEntry ::= SEQUENCE {
   gs2326plusSnmpAccessIndex             Integer32,
   gs2326plusSnmpAccessGroupName         DisplayString,
   gs2326plusSnmpAccessSecurityModel     INTEGER,
   gs2326plusSnmpAccessSecurityLevel     INTEGER,
   gs2326plusSnmpAccessReadViewName      DisplayString,
   gs2326plusSnmpAccessWriteViewName     DisplayString,
   gs2326plusSnmpAccessRowStatus         INTEGER
}

gs2326plusSnmpAccessIndex OBJECT-TYPE
   SYNTAX      Integer32(1..14)
   MAX-ACCESS  not-accessible
   STATUS      current
   DESCRIPTION
       " "
   ::= { gs2326plusSnmpAccessEntry 1 }

gs2326plusSnmpAccessGroupName OBJECT-TYPE
   SYNTAX      DisplayString (SIZE (1..32))
   MAX-ACCESS  read-write
   STATUS      current
   DESCRIPTION
       "Up to 32 characters describing Group Name."
   ::= { gs2326plusSnmpAccessEntry 2 }

gs2326plusSnmpAccessSecurityModel OBJECT-TYPE
   SYNTAX      INTEGER { any(0), v1(1), v2c(2), usm(3) }
   MAX-ACCESS  read-write
   STATUS      current
   DESCRIPTION
       " 0: any.
         1: v1.
         2: v2c.
         3: usm."
   ::= { gs2326plusSnmpAccessEntry 3 }

gs2326plusSnmpAccessSecurityLevel OBJECT-TYPE
   SYNTAX      INTEGER { noauthnopriv(1), authnopriv(2), authpriv(3) }
   MAX-ACCESS  read-write
   STATUS      current
   DESCRIPTION
       " 1: No authentication and no privacy.
         2: Authentication and no privacy.
         3: Authentication and privacy. "
   ::= { gs2326plusSnmpAccessEntry 4 }

gs2326plusSnmpAccessReadViewName OBJECT-TYPE
   SYNTAX      DisplayString (SIZE (1..32))
   MAX-ACCESS  read-write
   STATUS      current
   DESCRIPTION
       "Up to 32 characters describing Read View Name.
        None is reserved for Empty."
   ::= { gs2326plusSnmpAccessEntry 5 }

gs2326plusSnmpAccessWriteViewName OBJECT-TYPE
   SYNTAX      DisplayString (SIZE (1..32))
   MAX-ACCESS  read-write
   STATUS      current
   DESCRIPTION
       "Up to 32 characters describing Write View Name.
        None is reserved for Empty."
   ::= { gs2326plusSnmpAccessEntry 6 }

gs2326plusSnmpAccessRowStatus OBJECT-TYPE
   SYNTAX      INTEGER { active(1), notInservice(2), destroy(4), undo(5) }
   MAX-ACCESS  read-write
   STATUS      current
   DESCRIPTION
       "1: active
        2: notInservice
        4: destroy
        5: undo"
   ::= { gs2326plusSnmpAccessEntry 7 }


----------------------------------------------------------------------------------------------------

gs2326plusConfiguration                                         OBJECT IDENTIFIER ::= { lancomGS2326plus  2 }

gs2326plusPort                                                  OBJECT IDENTIFIER ::= { gs2326plusConfiguration 1 }

gs2326plusPortConfigurationTable OBJECT-TYPE
   SYNTAX      SEQUENCE OF Gs2326plusPortConfigurationEntry
   MAX-ACCESS  not-accessible
   STATUS      current
   DESCRIPTION
       " Show port configurations. "
   ::= { gs2326plusPort 1 }

gs2326plusPortConfigurationEntry OBJECT-TYPE
   SYNTAX      Gs2326plusPortConfigurationEntry
   MAX-ACCESS  not-accessible
   STATUS      current
   DESCRIPTION
       ""
   INDEX    { gs2326plusPortConfPort  }
   ::= { gs2326plusPortConfigurationTable 1 }

Gs2326plusPortConfigurationEntry ::= SEQUENCE {
   gs2326plusPortConfPort                     Integer32,
   gs2326plusPortConfPortMedia                DisplayString,
   gs2326plusPortConfLink                     DisplayString,
   gs2326plusPortConfCurrentSpeed             DisplayString,
   gs2326plusPortConfSpeed                    INTEGER,
   gs2326plusPortConfCurrentFlowControlRx     INTEGER,
   gs2326plusPortConfCurrentFlowControlTx     INTEGER,
   gs2326plusPortConfFlowControl              INTEGER,
   gs2326plusPortConfMaxFrameSize             Integer32,
   gs2326plusPortConfExcessiveCollisionMode   INTEGER,
   gs2326plusPortConfPowerControl             INTEGER,
   gs2326plusPortConfDescription              DisplayString
}

gs2326plusPortConfPort OBJECT-TYPE
   SYNTAX      Integer32(1..4095)
   MAX-ACCESS  not-accessible
   STATUS      current
   DESCRIPTION
       " port, range : 1 - port number. "
   ::= { gs2326plusPortConfigurationEntry 1 }

gs2326plusPortConfPortMedia OBJECT-TYPE
   SYNTAX      DisplayString(SIZE (1..4))
   MAX-ACCESS  read-only
   STATUS      current
   DESCRIPTION
       " Show port media. "
   ::= { gs2326plusPortConfigurationEntry 2 }

gs2326plusPortConfLink OBJECT-TYPE
   SYNTAX      DisplayString(SIZE (2..4))
   MAX-ACCESS  read-only
   STATUS      current
   DESCRIPTION
       " The current link state. "
   ::= { gs2326plusPortConfigurationEntry 3 }

gs2326plusPortConfCurrentSpeed OBJECT-TYPE
   SYNTAX      DisplayString(SIZE (6..12))
   MAX-ACCESS  read-only
   STATUS      current
   DESCRIPTION
       " The current link speed of the port. "
   ::= { gs2326plusPortConfigurationEntry 4 }

gs2326plusPortConfSpeed OBJECT-TYPE
   SYNTAX      INTEGER {
                    disable(0),
                    auto(1),
                    speed10Half(2),
                    speed10Full(3),
                    speed100Half(4),
                    speed100Full(5),
                    speed1Gfull(6),
                    sfpAutoAMS(7),
                    speed100FXAMS(8),
                    speed1000XAMS(9),
                    speed100FX(10),
                    speed1000X(11)
                }
   MAX-ACCESS  read-write
   STATUS      current
   DESCRIPTION
       "default: 1,
        0: disable state,
        1: auto,
        2: 10 Half,
        3: 10 Full,
        4: 100 Half,
        5: 100 Full,
        6: 1G full,
        only 'Dual Media' port have 7-11 option.
        Dual Media port default: 7,
        7: SFP_Auto_AMS,
        8: 100FX_AMS,
        9: 1000X_AMS,
        10: 100FX,
        11: 1000X "
   ::= { gs2326plusPortConfigurationEntry 5 }

gs2326plusPortConfCurrentFlowControlRx OBJECT-TYPE
   SYNTAX      INTEGER { disable(0), enable(1), noSupport(2) }
   MAX-ACCESS  read-only
   STATUS      current
   DESCRIPTION
       "0: disable
        1: enable
        2: no support.  "
   ::= { gs2326plusPortConfigurationEntry 6 }

gs2326plusPortConfCurrentFlowControlTx OBJECT-TYPE
   SYNTAX      INTEGER { disable(0), enable(1), noSupport(2) }
   MAX-ACCESS  read-only
   STATUS      current
   DESCRIPTION
       "0: disable
        1: enable
        2: no support.  "
   ::= { gs2326plusPortConfigurationEntry 7 }

gs2326plusPortConfFlowControl OBJECT-TYPE
   SYNTAX      INTEGER { disable(0), enable(1), noSupport(2) }
   MAX-ACCESS  read-write
   STATUS      current
   DESCRIPTION
       "default: 0,
        0: disable
        1: enable
        2: no support. "
   ::= { gs2326plusPortConfigurationEntry 8 }

gs2326plusPortConfMaxFrameSize OBJECT-TYPE
   SYNTAX      Integer32 (1518..9600)
   MAX-ACCESS  read-write
   STATUS      current
   DESCRIPTION
       "default: 9600 , range : 1518 - 9600 "
   ::= { gs2326plusPortConfigurationEntry 9 }

gs2326plusPortConfExcessiveCollisionMode OBJECT-TYPE
   SYNTAX      INTEGER { discard(0), restart(1), noSupport(2) }
   MAX-ACCESS  read-write
   STATUS      current
   DESCRIPTION
       "default: 0,
        Excessive Collision Mode :
        0: Discard,
        1: Restart,
        2: no support.
       "
   ::= { gs2326plusPortConfigurationEntry 10 }

gs2326plusPortConfPowerControl OBJECT-TYPE
   SYNTAX      INTEGER { disable(0), actiphy(1), dynamic(2), enable(3), noSupport(4) }
   MAX-ACCESS  read-write
   STATUS      current
   DESCRIPTION
       "default: 0,
        PowerControl :
        0: disable,
        1: Actiphy,
        2: Dynamic (perfectReach),
        3: Enable,
        4: no support.
       "
   ::= { gs2326plusPortConfigurationEntry 11 }

gs2326plusPortConfDescription OBJECT-TYPE
   SYNTAX      DisplayString
   MAX-ACCESS  read-write
   STATUS      current
   DESCRIPTION
       " Interface specific description.
         Up to 47 characters describing this interface. "
   ::= { gs2326plusPortConfigurationEntry 12 }


gs2326plusPortTrafficStatisticsTable OBJECT-TYPE
   SYNTAX      SEQUENCE OF Gs2326plusPortTrafficStatisticsEntry
   MAX-ACCESS  not-accessible
   STATUS      current
   DESCRIPTION
       " "
   ::= { gs2326plusPort 2 }

gs2326plusPortTrafficStatisticsEntry OBJECT-TYPE
   SYNTAX      Gs2326plusPortTrafficStatisticsEntry
   MAX-ACCESS  not-accessible
   STATUS      current
   DESCRIPTION
       ""
   INDEX    { gs2326plusPortTrafficStatisticsPort  }
   ::= { gs2326plusPortTrafficStatisticsTable 1 }

Gs2326plusPortTrafficStatisticsEntry ::= SEQUENCE {
   gs2326plusPortTrafficStatisticsPort          Integer32,
   gs2326plusPortTrafficStatisticsClear         INTEGER,
   gs2326plusPortTrafficRxPackets               Counter64,
   gs2326plusPortTrafficRxOctets                Counter64,
   gs2326plusPortTrafficRxUnicast               Counter64,
   gs2326plusPortTrafficRxMulticast             Counter64,
   gs2326plusPortTrafficRxBroadcast             Counter64,
   gs2326plusPortTrafficRxPause                 Counter64,
   gs2326plusPortTrafficRx64Bytes               Counter64,
   gs2326plusPortTrafficRx65to127Bytes          Counter64,
   gs2326plusPortTrafficRx128to255Bytes         Counter64,
   gs2326plusPortTrafficRx256to511Bytes         Counter64,
   gs2326plusPortTrafficRx512to1023Bytes        Counter64,
   gs2326plusPortTrafficRx1024to1526Bytes       Counter64,
   gs2326plusPortTrafficRxExceecd1527Bytes      Counter64,
   gs2326plusPortTrafficRxQ0                    Counter64,
   gs2326plusPortTrafficRxQ1                    Counter64,
   gs2326plusPortTrafficRxQ2                    Counter64,
   gs2326plusPortTrafficRxQ3                    Counter64,
   gs2326plusPortTrafficRxQ4                    Counter64,
   gs2326plusPortTrafficRxQ5                    Counter64,
   gs2326plusPortTrafficRxQ6                    Counter64,
   gs2326plusPortTrafficRxQ7                    Counter64,
   gs2326plusPortTrafficRxDrops                 Counter64,
   gs2326plusPortTrafficRxCRCorAlignment        Counter64,
   gs2326plusPortTrafficRxUndersize             Counter64,
   gs2326plusPortTrafficRxOversize              Counter64,
   gs2326plusPortTrafficRxFragments             Counter64,
   gs2326plusPortTrafficRxJabber                Counter64,
   gs2326plusPortTrafficRxFiltered              Counter64,
   gs2326plusPortTrafficTxPackets               Counter64,
   gs2326plusPortTrafficTxOctets                Counter64,
   gs2326plusPortTrafficTxUnicast               Counter64,
   gs2326plusPortTrafficTxMulticast             Counter64,
   gs2326plusPortTrafficTxBroadcast             Counter64,
   gs2326plusPortTrafficTxPause                 Counter64,
   gs2326plusPortTrafficTx64Bytes               Counter64,
   gs2326plusPortTrafficTx65to127Bytes          Counter64,
   gs2326plusPortTrafficTx128to255Bytes         Counter64,
   gs2326plusPortTrafficTx256to511Bytes         Counter64,
   gs2326plusPortTrafficTx512to1023Bytes        Counter64,
   gs2326plusPortTrafficTx1024to1526Bytes       Counter64,
   gs2326plusPortTrafficTxExceecd1527Bytes      Counter64,
   gs2326plusPortTrafficTxQ0                    Counter64,
   gs2326plusPortTrafficTxQ1                    Counter64,
   gs2326plusPortTrafficTxQ2                    Counter64,
   gs2326plusPortTrafficTxQ3                    Counter64,
   gs2326plusPortTrafficTxQ4                    Counter64,
   gs2326plusPortTrafficTxQ5                    Counter64,
   gs2326plusPortTrafficTxQ6                    Counter64,
   gs2326plusPortTrafficTxQ7                    Counter64,
   gs2326plusPortTrafficTxDrops                 Counter64,
   gs2326plusPortTrafficTxLateOrExcColl         Counter64
}

gs2326plusPortTrafficStatisticsPort OBJECT-TYPE
   SYNTAX      Integer32 (1..4095)
   MAX-ACCESS  not-accessible
   STATUS      current
   DESCRIPTION
       " "
   ::= { gs2326plusPortTrafficStatisticsEntry 1 }

gs2326plusPortTrafficStatisticsClear OBJECT-TYPE
   SYNTAX      INTEGER { disable(0), enable(1) }
   MAX-ACCESS  read-write
   STATUS      current
   DESCRIPTION
       " "
   ::= { gs2326plusPortTrafficStatisticsEntry 2 }

gs2326plusPortTrafficRxPackets OBJECT-TYPE
   SYNTAX      Counter64
   MAX-ACCESS  read-only
   STATUS      current
   DESCRIPTION
       " "
   ::= { gs2326plusPortTrafficStatisticsEntry 3 }

gs2326plusPortTrafficRxOctets OBJECT-TYPE
   SYNTAX      Counter64
   MAX-ACCESS  read-only
   STATUS      current
   DESCRIPTION
       " "
   ::= { gs2326plusPortTrafficStatisticsEntry 4 }

gs2326plusPortTrafficRxUnicast OBJECT-TYPE
   SYNTAX      Counter64
   MAX-ACCESS  read-only
   STATUS      current
   DESCRIPTION
       " "
   ::= { gs2326plusPortTrafficStatisticsEntry 5 }

gs2326plusPortTrafficRxMulticast OBJECT-TYPE
   SYNTAX      Counter64
   MAX-ACCESS  read-only
   STATUS      current
   DESCRIPTION
       " "
   ::= { gs2326plusPortTrafficStatisticsEntry 6 }

gs2326plusPortTrafficRxBroadcast OBJECT-TYPE
   SYNTAX      Counter64
   MAX-ACCESS  read-only
   STATUS      current
   DESCRIPTION
       " "
   ::= { gs2326plusPortTrafficStatisticsEntry 7 }

gs2326plusPortTrafficRxPause OBJECT-TYPE
   SYNTAX      Counter64
   MAX-ACCESS  read-only
   STATUS      current
   DESCRIPTION
       " "
   ::= { gs2326plusPortTrafficStatisticsEntry 8 }

gs2326plusPortTrafficRx64Bytes OBJECT-TYPE
   SYNTAX      Counter64
   MAX-ACCESS  read-only
   STATUS      current
   DESCRIPTION
       " "
   ::= { gs2326plusPortTrafficStatisticsEntry 9 }

gs2326plusPortTrafficRx65to127Bytes OBJECT-TYPE
   SYNTAX      Counter64
   MAX-ACCESS  read-only
   STATUS      current
   DESCRIPTION
       " "
   ::= { gs2326plusPortTrafficStatisticsEntry 10 }

gs2326plusPortTrafficRx128to255Bytes OBJECT-TYPE
   SYNTAX      Counter64
   MAX-ACCESS  read-only
   STATUS      current
   DESCRIPTION
       " "
   ::= { gs2326plusPortTrafficStatisticsEntry 11 }

gs2326plusPortTrafficRx256to511Bytes OBJECT-TYPE
   SYNTAX      Counter64
   MAX-ACCESS  read-only
   STATUS      current
   DESCRIPTION
       " "
   ::= { gs2326plusPortTrafficStatisticsEntry 12 }

gs2326plusPortTrafficRx512to1023Bytes OBJECT-TYPE
   SYNTAX      Counter64
   MAX-ACCESS  read-only
   STATUS      current
   DESCRIPTION
       " "
   ::= { gs2326plusPortTrafficStatisticsEntry 13 }

gs2326plusPortTrafficRx1024to1526Bytes OBJECT-TYPE
   SYNTAX      Counter64
   MAX-ACCESS  read-only
   STATUS      current
   DESCRIPTION
       " "
   ::= { gs2326plusPortTrafficStatisticsEntry 14 }

gs2326plusPortTrafficRxExceecd1527Bytes OBJECT-TYPE
   SYNTAX      Counter64
   MAX-ACCESS  read-only
   STATUS      current
   DESCRIPTION
       " "
   ::= { gs2326plusPortTrafficStatisticsEntry 15 }

gs2326plusPortTrafficRxQ0 OBJECT-TYPE
   SYNTAX      Counter64
   MAX-ACCESS  read-only
   STATUS      current
   DESCRIPTION
       " "
   ::= { gs2326plusPortTrafficStatisticsEntry 16 }

gs2326plusPortTrafficRxQ1 OBJECT-TYPE
   SYNTAX      Counter64
   MAX-ACCESS  read-only
   STATUS      current
   DESCRIPTION
       " "
   ::= { gs2326plusPortTrafficStatisticsEntry 17 }

gs2326plusPortTrafficRxQ2 OBJECT-TYPE
   SYNTAX      Counter64
   MAX-ACCESS  read-only
   STATUS      current
   DESCRIPTION
       " "
   ::= { gs2326plusPortTrafficStatisticsEntry 18 }

gs2326plusPortTrafficRxQ3 OBJECT-TYPE
   SYNTAX      Counter64
   MAX-ACCESS  read-only
   STATUS      current
   DESCRIPTION
       " "
   ::= { gs2326plusPortTrafficStatisticsEntry 19 }

gs2326plusPortTrafficRxQ4 OBJECT-TYPE
   SYNTAX      Counter64
   MAX-ACCESS  read-only
   STATUS      current
   DESCRIPTION
       " "
   ::= { gs2326plusPortTrafficStatisticsEntry 20 }

gs2326plusPortTrafficRxQ5 OBJECT-TYPE
   SYNTAX      Counter64
   MAX-ACCESS  read-only
   STATUS      current
   DESCRIPTION
       " "
   ::= { gs2326plusPortTrafficStatisticsEntry 21 }

gs2326plusPortTrafficRxQ6 OBJECT-TYPE
   SYNTAX      Counter64
   MAX-ACCESS  read-only
   STATUS      current
   DESCRIPTION
       " "
   ::= { gs2326plusPortTrafficStatisticsEntry 22 }

gs2326plusPortTrafficRxQ7 OBJECT-TYPE
   SYNTAX      Counter64
   MAX-ACCESS  read-only
   STATUS      current
   DESCRIPTION
       " "
   ::= { gs2326plusPortTrafficStatisticsEntry 23 }

gs2326plusPortTrafficRxDrops OBJECT-TYPE
   SYNTAX      Counter64
   MAX-ACCESS  read-only
   STATUS      current
   DESCRIPTION
       " "
   ::= { gs2326plusPortTrafficStatisticsEntry 24 }

gs2326plusPortTrafficRxCRCorAlignment OBJECT-TYPE
   SYNTAX      Counter64
   MAX-ACCESS  read-only
   STATUS      current
   DESCRIPTION
       " "
   ::= { gs2326plusPortTrafficStatisticsEntry 25 }

gs2326plusPortTrafficRxUndersize OBJECT-TYPE
   SYNTAX      Counter64
   MAX-ACCESS  read-only
   STATUS      current
   DESCRIPTION
       " "
   ::= { gs2326plusPortTrafficStatisticsEntry 26 }

gs2326plusPortTrafficRxOversize OBJECT-TYPE
   SYNTAX      Counter64
   MAX-ACCESS  read-only
   STATUS      current
   DESCRIPTION
       " "
   ::= { gs2326plusPortTrafficStatisticsEntry 27 }

gs2326plusPortTrafficRxFragments OBJECT-TYPE
   SYNTAX      Counter64
   MAX-ACCESS  read-only
   STATUS      current
   DESCRIPTION
       " "
   ::= { gs2326plusPortTrafficStatisticsEntry 28 }

gs2326plusPortTrafficRxJabber OBJECT-TYPE
   SYNTAX      Counter64
   MAX-ACCESS  read-only
   STATUS      current
   DESCRIPTION
       " "
   ::= { gs2326plusPortTrafficStatisticsEntry 29 }

gs2326plusPortTrafficRxFiltered OBJECT-TYPE
   SYNTAX      Counter64
   MAX-ACCESS  read-only
   STATUS      current
   DESCRIPTION
       " "
   ::= { gs2326plusPortTrafficStatisticsEntry 30 }

gs2326plusPortTrafficTxPackets OBJECT-TYPE
   SYNTAX      Counter64
   MAX-ACCESS  read-only
   STATUS      current
   DESCRIPTION
       " "
   ::= { gs2326plusPortTrafficStatisticsEntry 31 }

gs2326plusPortTrafficTxOctets OBJECT-TYPE
   SYNTAX      Counter64
   MAX-ACCESS  read-only
   STATUS      current
   DESCRIPTION
       " "
   ::= { gs2326plusPortTrafficStatisticsEntry 32 }

gs2326plusPortTrafficTxUnicast OBJECT-TYPE
   SYNTAX      Counter64
   MAX-ACCESS  read-only
   STATUS      current
   DESCRIPTION
       " "
   ::= { gs2326plusPortTrafficStatisticsEntry 33 }

gs2326plusPortTrafficTxMulticast OBJECT-TYPE
   SYNTAX      Counter64
   MAX-ACCESS  read-only
   STATUS      current
   DESCRIPTION
       " "
   ::= { gs2326plusPortTrafficStatisticsEntry 34 }

gs2326plusPortTrafficTxBroadcast OBJECT-TYPE
   SYNTAX      Counter64
   MAX-ACCESS  read-only
   STATUS      current
   DESCRIPTION
       " "
   ::= { gs2326plusPortTrafficStatisticsEntry 35 }

gs2326plusPortTrafficTxPause OBJECT-TYPE
   SYNTAX      Counter64
   MAX-ACCESS  read-only
   STATUS      current
   DESCRIPTION
       " "
   ::= { gs2326plusPortTrafficStatisticsEntry 36 }

gs2326plusPortTrafficTx64Bytes OBJECT-TYPE
   SYNTAX      Counter64
   MAX-ACCESS  read-only
   STATUS      current
   DESCRIPTION
       " "
   ::= { gs2326plusPortTrafficStatisticsEntry 37 }

gs2326plusPortTrafficTx65to127Bytes OBJECT-TYPE
   SYNTAX      Counter64
   MAX-ACCESS  read-only
   STATUS      current
   DESCRIPTION
       " "
   ::= { gs2326plusPortTrafficStatisticsEntry 38 }

gs2326plusPortTrafficTx128to255Bytes OBJECT-TYPE
   SYNTAX      Counter64
   MAX-ACCESS  read-only
   STATUS      current
   DESCRIPTION
       " "
   ::= { gs2326plusPortTrafficStatisticsEntry 39 }

gs2326plusPortTrafficTx256to511Bytes OBJECT-TYPE
   SYNTAX      Counter64
   MAX-ACCESS  read-only
   STATUS      current
   DESCRIPTION
       " "
   ::= { gs2326plusPortTrafficStatisticsEntry 40 }

gs2326plusPortTrafficTx512to1023Bytes OBJECT-TYPE
   SYNTAX      Counter64
   MAX-ACCESS  read-only
   STATUS      current
   DESCRIPTION
       " "
   ::= { gs2326plusPortTrafficStatisticsEntry 41 }

gs2326plusPortTrafficTx1024to1526Bytes OBJECT-TYPE
   SYNTAX      Counter64
   MAX-ACCESS  read-only
   STATUS      current
   DESCRIPTION
       " "
   ::= { gs2326plusPortTrafficStatisticsEntry 42 }

gs2326plusPortTrafficTxExceecd1527Bytes OBJECT-TYPE
   SYNTAX      Counter64
   MAX-ACCESS  read-only
   STATUS      current
   DESCRIPTION
       " "
   ::= { gs2326plusPortTrafficStatisticsEntry 43 }

gs2326plusPortTrafficTxQ0 OBJECT-TYPE
   SYNTAX      Counter64
   MAX-ACCESS  read-only
   STATUS      current
   DESCRIPTION
       " "
   ::= { gs2326plusPortTrafficStatisticsEntry 44 }

gs2326plusPortTrafficTxQ1 OBJECT-TYPE
   SYNTAX      Counter64
   MAX-ACCESS  read-only
   STATUS      current
   DESCRIPTION
       " "
   ::= { gs2326plusPortTrafficStatisticsEntry 45 }

gs2326plusPortTrafficTxQ2 OBJECT-TYPE
   SYNTAX      Counter64
   MAX-ACCESS  read-only
   STATUS      current
   DESCRIPTION
       " "
   ::= { gs2326plusPortTrafficStatisticsEntry 46 }

gs2326plusPortTrafficTxQ3 OBJECT-TYPE
   SYNTAX      Counter64
   MAX-ACCESS  read-only
   STATUS      current
   DESCRIPTION
       " "
   ::= { gs2326plusPortTrafficStatisticsEntry 47 }

gs2326plusPortTrafficTxQ4 OBJECT-TYPE
   SYNTAX      Counter64
   MAX-ACCESS  read-only
   STATUS      current
   DESCRIPTION
       " "
   ::= { gs2326plusPortTrafficStatisticsEntry 48 }

gs2326plusPortTrafficTxQ5 OBJECT-TYPE
   SYNTAX      Counter64
   MAX-ACCESS  read-only
   STATUS      current
   DESCRIPTION
       " "
   ::= { gs2326plusPortTrafficStatisticsEntry 49 }

gs2326plusPortTrafficTxQ6 OBJECT-TYPE
   SYNTAX      Counter64
   MAX-ACCESS  read-only
   STATUS      current
   DESCRIPTION
       " "
   ::= { gs2326plusPortTrafficStatisticsEntry 50 }


gs2326plusPortTrafficTxQ7 OBJECT-TYPE
   SYNTAX      Counter64
   MAX-ACCESS  read-only
   STATUS      current
   DESCRIPTION
       " "
   ::= { gs2326plusPortTrafficStatisticsEntry 51 }

gs2326plusPortTrafficTxDrops OBJECT-TYPE
   SYNTAX      Counter64
   MAX-ACCESS  read-only
   STATUS      current
   DESCRIPTION
       " "
   ::= { gs2326plusPortTrafficStatisticsEntry 52 }

gs2326plusPortTrafficTxLateOrExcColl OBJECT-TYPE
   SYNTAX      Counter64
   MAX-ACCESS  read-only
   STATUS      current
   DESCRIPTION
       " "
   ::= { gs2326plusPortTrafficStatisticsEntry 53 }


gs2326plusPortQoSStatistics                                     OBJECT IDENTIFIER ::= { gs2326plusPort 3 }

gs2326plusPortQoSStatisticsClear OBJECT-TYPE
   SYNTAX      INTEGER { none(0), clear(1) }
   MAX-ACCESS  read-only
   STATUS      current
   DESCRIPTION
       "default: 0
       0: none
       1: clear "
   ::= { gs2326plusPortQoSStatistics 1 }

gs2326plusPortQoSStatisticsTable OBJECT-TYPE
   SYNTAX      SEQUENCE OF Gs2326plusPortQoSStatisticsEntry
   MAX-ACCESS  not-accessible
   STATUS      current
   DESCRIPTION
       " "
   ::= { gs2326plusPortQoSStatistics 2 }

gs2326plusPortQoSStatisticsEntry OBJECT-TYPE
   SYNTAX      Gs2326plusPortQoSStatisticsEntry
   MAX-ACCESS  not-accessible
   STATUS      current
   DESCRIPTION
       ""
   INDEX    { gs2326plusPortQoSStatisticsPort  }
   ::= { gs2326plusPortQoSStatisticsTable 1 }

Gs2326plusPortQoSStatisticsEntry ::= SEQUENCE {
   gs2326plusPortQoSStatisticsPort      Integer32,
   gs2326plusPortQoSQ0Rx                Counter64,
   gs2326plusPortQoSQ0Tx                Counter64,
   gs2326plusPortQoSQ1Rx                Counter64,
   gs2326plusPortQoSQ1Tx                Counter64,
   gs2326plusPortQoSQ2Rx                Counter64,
   gs2326plusPortQoSQ2Tx                Counter64,
   gs2326plusPortQoSQ3Rx                Counter64,
   gs2326plusPortQoSQ3Tx                Counter64,
   gs2326plusPortQoSQ4Rx                Counter64,
   gs2326plusPortQoSQ4Tx                Counter64,
   gs2326plusPortQoSQ5Rx                Counter64,
   gs2326plusPortQoSQ5Tx                Counter64,
   gs2326plusPortQoSQ6Rx                Counter64,
   gs2326plusPortQoSQ6Tx                Counter64,
   gs2326plusPortQoSQ7Rx                Counter64,
   gs2326plusPortQoSQ7Tx                Counter64
}

gs2326plusPortQoSStatisticsPort OBJECT-TYPE
   SYNTAX      Integer32(1..4095)
   MAX-ACCESS  not-accessible
   STATUS      current
   DESCRIPTION
       " "
   ::= { gs2326plusPortQoSStatisticsEntry 1 }

gs2326plusPortQoSQ0Rx OBJECT-TYPE
   SYNTAX      Counter64
   MAX-ACCESS  read-only
   STATUS      current
   DESCRIPTION
       " "
   ::= { gs2326plusPortQoSStatisticsEntry 2 }

gs2326plusPortQoSQ0Tx OBJECT-TYPE
   SYNTAX      Counter64
   MAX-ACCESS  read-only
   STATUS      current
   DESCRIPTION
       " "
   ::= { gs2326plusPortQoSStatisticsEntry 3 }

gs2326plusPortQoSQ1Rx OBJECT-TYPE
   SYNTAX      Counter64
   MAX-ACCESS  read-only
   STATUS      current
   DESCRIPTION
       " "
   ::= { gs2326plusPortQoSStatisticsEntry 4 }

gs2326plusPortQoSQ1Tx OBJECT-TYPE
   SYNTAX      Counter64
   MAX-ACCESS  read-only
   STATUS      current
   DESCRIPTION
       " "
   ::= { gs2326plusPortQoSStatisticsEntry 5 }

gs2326plusPortQoSQ2Rx OBJECT-TYPE
   SYNTAX      Counter64
   MAX-ACCESS  read-only
   STATUS      current
   DESCRIPTION
       " "
   ::= { gs2326plusPortQoSStatisticsEntry 6 }

gs2326plusPortQoSQ2Tx OBJECT-TYPE
   SYNTAX      Counter64
   MAX-ACCESS  read-only
   STATUS      current
   DESCRIPTION
       " "
   ::= { gs2326plusPortQoSStatisticsEntry 7 }

gs2326plusPortQoSQ3Rx OBJECT-TYPE
   SYNTAX      Counter64
   MAX-ACCESS  read-only
   STATUS      current
   DESCRIPTION
       " "
   ::= { gs2326plusPortQoSStatisticsEntry 8 }

gs2326plusPortQoSQ3Tx OBJECT-TYPE
   SYNTAX      Counter64
   MAX-ACCESS  read-only
   STATUS      current
   DESCRIPTION
       " "
   ::= { gs2326plusPortQoSStatisticsEntry 9 }

gs2326plusPortQoSQ4Rx OBJECT-TYPE
   SYNTAX      Counter64
   MAX-ACCESS  read-only
   STATUS      current
   DESCRIPTION
       " "
   ::= { gs2326plusPortQoSStatisticsEntry 10 }

gs2326plusPortQoSQ4Tx OBJECT-TYPE
   SYNTAX      Counter64
   MAX-ACCESS  read-only
   STATUS      current
   DESCRIPTION
       " "
   ::= { gs2326plusPortQoSStatisticsEntry 11 }

gs2326plusPortQoSQ5Rx OBJECT-TYPE
   SYNTAX      Counter64
   MAX-ACCESS  read-only
   STATUS      current
   DESCRIPTION
       " "
   ::= { gs2326plusPortQoSStatisticsEntry 12 }

gs2326plusPortQoSQ5Tx OBJECT-TYPE
   SYNTAX      Counter64
   MAX-ACCESS  read-only
   STATUS      current
   DESCRIPTION
       " "
   ::= { gs2326plusPortQoSStatisticsEntry 13 }

gs2326plusPortQoSQ6Rx OBJECT-TYPE
   SYNTAX      Counter64
   MAX-ACCESS  read-only
   STATUS      current
   DESCRIPTION
       " "
   ::= { gs2326plusPortQoSStatisticsEntry 14 }

gs2326plusPortQoSQ6Tx OBJECT-TYPE
   SYNTAX      Counter64
   MAX-ACCESS  read-only
   STATUS      current
   DESCRIPTION
       " "
   ::= { gs2326plusPortQoSStatisticsEntry 15 }

gs2326plusPortQoSQ7Rx OBJECT-TYPE
   SYNTAX      Counter64
   MAX-ACCESS  read-only
   STATUS      current
   DESCRIPTION
       " "
   ::= { gs2326plusPortQoSStatisticsEntry 16 }

gs2326plusPortQoSQ7Tx OBJECT-TYPE
   SYNTAX      Counter64
   MAX-ACCESS  read-only
   STATUS      current
   DESCRIPTION
       " "
   ::= { gs2326plusPortQoSStatisticsEntry 17 }

gs2326plusSFPInfoTable OBJECT-TYPE
   SYNTAX      SEQUENCE OF Gs2326plusSFPInfoEntry
   MAX-ACCESS  not-accessible
   STATUS      current
   DESCRIPTION
       " "
   ::= { gs2326plusPort 4 }

gs2326plusSFPInfoEntry OBJECT-TYPE
   SYNTAX      Gs2326plusSFPInfoEntry
   MAX-ACCESS  not-accessible
   STATUS      current
   DESCRIPTION
       ""
   INDEX    { gs2326plusSFPInfoIndex }
   ::= { gs2326plusSFPInfoTable 1 }

Gs2326plusSFPInfoEntry ::= SEQUENCE {
   gs2326plusSFPInfoIndex               Integer32,
   gs2326plusSFPInfoPort                DisplayString,
   gs2326plusSFPConnectorType           DisplayString,
   gs2326plusSFPFiberType               DisplayString,
   gs2326plusSFPTxCentralWavelength     DisplayString,
   gs2326plusSFPBaudRate                DisplayString,
   gs2326plusSFPVendorOUI               DisplayString,
   gs2326plusSFPVendorName              DisplayString,
   gs2326plusSFPVendorPN                DisplayString,
   gs2326plusSFPVendorRev               DisplayString,
   gs2326plusSFPVendorSN                DisplayString,
   gs2326plusSFPDateCode                DisplayString,
   gs2326plusSFPTemperature             DisplayString,
   gs2326plusSFPVcc                     DisplayString,
   gs2326plusSFPMon1Bias                DisplayString,
   gs2326plusSFPMon2TxPWR               DisplayString,
   gs2326plusSFPMon3RxPWR               DisplayString
}

gs2326plusSFPInfoIndex OBJECT-TYPE
   SYNTAX      Integer32(1..4095)
   MAX-ACCESS  not-accessible
   STATUS      current
   DESCRIPTION
       " "
   ::= { gs2326plusSFPInfoEntry 1 }

gs2326plusSFPInfoPort OBJECT-TYPE
   SYNTAX      DisplayString
   MAX-ACCESS  read-only
   STATUS      current
   DESCRIPTION
       " "
   ::= { gs2326plusSFPInfoEntry 2 }

gs2326plusSFPConnectorType OBJECT-TYPE
   SYNTAX      DisplayString
   MAX-ACCESS  read-only
   STATUS      current
   DESCRIPTION
       " "
   ::= { gs2326plusSFPInfoEntry 3 }

gs2326plusSFPFiberType OBJECT-TYPE
   SYNTAX      DisplayString
   MAX-ACCESS  read-only
   STATUS      current
   DESCRIPTION
       " "
   ::= { gs2326plusSFPInfoEntry 4 }

gs2326plusSFPTxCentralWavelength OBJECT-TYPE
   SYNTAX      DisplayString
   MAX-ACCESS  read-only
   STATUS      current
   DESCRIPTION
       " "
   ::= { gs2326plusSFPInfoEntry 5 }

gs2326plusSFPBaudRate OBJECT-TYPE
   SYNTAX      DisplayString
   MAX-ACCESS  read-only
   STATUS      current
   DESCRIPTION
       " "
   ::= { gs2326plusSFPInfoEntry 6 }

gs2326plusSFPVendorOUI OBJECT-TYPE
   SYNTAX      DisplayString
   MAX-ACCESS  read-only
   STATUS      current
   DESCRIPTION
       " "
   ::= { gs2326plusSFPInfoEntry 7 }

gs2326plusSFPVendorName OBJECT-TYPE
   SYNTAX      DisplayString
   MAX-ACCESS  read-only
   STATUS      current
   DESCRIPTION
       " "
   ::= { gs2326plusSFPInfoEntry 8 }

gs2326plusSFPVendorPN OBJECT-TYPE
   SYNTAX      DisplayString
   MAX-ACCESS  read-only
   STATUS      current
   DESCRIPTION
       " "
   ::= { gs2326plusSFPInfoEntry 9 }

gs2326plusSFPVendorRev OBJECT-TYPE
   SYNTAX      DisplayString
   MAX-ACCESS  read-only
   STATUS      current
   DESCRIPTION
       " "
   ::= { gs2326plusSFPInfoEntry 10 }

gs2326plusSFPVendorSN OBJECT-TYPE
   SYNTAX      DisplayString
   MAX-ACCESS  read-only
   STATUS      current
   DESCRIPTION
       " "
   ::= { gs2326plusSFPInfoEntry 11 }

gs2326plusSFPDateCode OBJECT-TYPE
   SYNTAX      DisplayString
   MAX-ACCESS  read-only
   STATUS      current
   DESCRIPTION
       " "
   ::= { gs2326plusSFPInfoEntry 12 }

gs2326plusSFPTemperature OBJECT-TYPE
   SYNTAX      DisplayString
   MAX-ACCESS  read-only
   STATUS      current
   DESCRIPTION
       " "
   ::= { gs2326plusSFPInfoEntry 13 }

gs2326plusSFPVcc OBJECT-TYPE
   SYNTAX      DisplayString
   MAX-ACCESS  read-only
   STATUS      current
   DESCRIPTION
       " "
   ::= { gs2326plusSFPInfoEntry 14 }

gs2326plusSFPMon1Bias OBJECT-TYPE
   SYNTAX      DisplayString
   MAX-ACCESS  read-only
   STATUS      current
   DESCRIPTION
       " "
   ::= { gs2326plusSFPInfoEntry 15 }

gs2326plusSFPMon2TxPWR OBJECT-TYPE
   SYNTAX      DisplayString
   MAX-ACCESS  read-only
   STATUS      current
   DESCRIPTION
       " "
   ::= { gs2326plusSFPInfoEntry 16 }

gs2326plusSFPMon3RxPWR OBJECT-TYPE
   SYNTAX      DisplayString
   MAX-ACCESS  read-only
   STATUS      current
   DESCRIPTION
       " "
   ::= { gs2326plusSFPInfoEntry 17 }


gs2326plusPortEEETable OBJECT-TYPE
   SYNTAX      SEQUENCE OF Gs2326plusPortEEEEntry
   MAX-ACCESS  not-accessible
   STATUS      current
   DESCRIPTION
      " "
   ::= { gs2326plusPort 5 }

gs2326plusPortEEEEntry OBJECT-TYPE
   SYNTAX      Gs2326plusPortEEEEntry
   MAX-ACCESS  not-accessible
   STATUS      current
   DESCRIPTION
       ""
   INDEX    { gs2326plusPortEEEPort }
   ::= { gs2326plusPortEEETable 1 }

Gs2326plusPortEEEEntry ::= SEQUENCE {
   gs2326plusPortEEEPort		        Integer32,
   gs2326plusPortEEEMode		        INTEGER,
   gs2326plusPortEEEUrgentQueue1		INTEGER,
   gs2326plusPortEEEUrgentQueue2		INTEGER,
   gs2326plusPortEEEUrgentQueue3		INTEGER,
   gs2326plusPortEEEUrgentQueue4		INTEGER,
   gs2326plusPortEEEUrgentQueue5		INTEGER,
   gs2326plusPortEEEUrgentQueue6		INTEGER,
   gs2326plusPortEEEUrgentQueue7		INTEGER,
   gs2326plusPortEEEUrgentQueue8		INTEGER
}

gs2326plusPortEEEPort OBJECT-TYPE
   SYNTAX      Integer32(1..4095)
   MAX-ACCESS  not-accessible
   STATUS      current
   DESCRIPTION
       " "
   ::= { gs2326plusPortEEEEntry 1 }

gs2326plusPortEEEMode OBJECT-TYPE
   SYNTAX      INTEGER { disable(0), enable(1) }
   MAX-ACCESS  read-write
   STATUS      current
   DESCRIPTION
       "default: 0
       0:disable
       1:enable "
   ::= { gs2326plusPortEEEEntry 2 }

gs2326plusPortEEEUrgentQueue1 OBJECT-TYPE
   SYNTAX      INTEGER { disable(0), enable(1) }
   MAX-ACCESS  read-write
   STATUS      current
   DESCRIPTION
       "default: 0
       0:disable
       1:enable "
   ::= { gs2326plusPortEEEEntry 3 }

gs2326plusPortEEEUrgentQueue2 OBJECT-TYPE
   SYNTAX      INTEGER { disable(0), enable(1) }
   MAX-ACCESS  read-write
   STATUS      current
   DESCRIPTION
       "default: 0
       0:disable
       1:enable "
   ::= { gs2326plusPortEEEEntry 4 }

gs2326plusPortEEEUrgentQueue3 OBJECT-TYPE
   SYNTAX      INTEGER { disable(0), enable(1) }
   MAX-ACCESS  read-write
   STATUS      current
   DESCRIPTION
       "default: 0
       0:disable
       1:enable "
   ::= { gs2326plusPortEEEEntry 5 }

gs2326plusPortEEEUrgentQueue4 OBJECT-TYPE
   SYNTAX      INTEGER { disable(0), enable(1) }
   MAX-ACCESS  read-write
   STATUS      current
   DESCRIPTION
       "default: 0
       0:disable
       1:enable "
   ::= { gs2326plusPortEEEEntry 6 }

gs2326plusPortEEEUrgentQueue5 OBJECT-TYPE
   SYNTAX      INTEGER { disable(0), enable(1) }
   MAX-ACCESS  read-write
   STATUS      current
   DESCRIPTION
       "default: 0
       0:disable
       1:enable "
   ::= { gs2326plusPortEEEEntry 7 }

gs2326plusPortEEEUrgentQueue6 OBJECT-TYPE
   SYNTAX      INTEGER { disable(0), enable(1) }
   MAX-ACCESS  read-write
   STATUS      current
   DESCRIPTION
       "default: 0
       0:disable
       1:enable "
   ::= { gs2326plusPortEEEEntry 8 }

gs2326plusPortEEEUrgentQueue7 OBJECT-TYPE
   SYNTAX      INTEGER { disable(0), enable(1) }
   MAX-ACCESS  read-write
   STATUS      current
   DESCRIPTION
       "default: 0
       0:disable
       1:enable "
   ::= { gs2326plusPortEEEEntry 9 }

gs2326plusPortEEEUrgentQueue8 OBJECT-TYPE
   SYNTAX      INTEGER { disable(0), enable(1) }
   MAX-ACCESS  read-write
   STATUS      current
   DESCRIPTION
       "default: 0
       0:disable
       1:enable "
   ::= { gs2326plusPortEEEEntry 10 }


gs2326plusVoiceVLAN                                             OBJECT IDENTIFIER ::= { gs2326plusConfiguration 2 }

gs2326plusVoiceVLANConf                                         OBJECT IDENTIFIER ::= { gs2326plusVoiceVLAN 1 }

gs2326plusVoiceVLANMode OBJECT-TYPE
   SYNTAX      INTEGER { disable(0), enable(1) }
   MAX-ACCESS  read-write
   STATUS      current
   DESCRIPTION
       " Voice VLAN mode operation.
       default: 0,
       0: disable
       1: enable"
   ::= { gs2326plusVoiceVLANConf 1 }

gs2326plusVoiceVLANVLANId OBJECT-TYPE
   SYNTAX      Integer32(1..4094)
   MAX-ACCESS  read-write
   STATUS      current
   DESCRIPTION
       "Voice VLAN ID.
        default: 1000,
        range : 1-4094. "
   ::= { gs2326plusVoiceVLANConf 2 }

gs2326plusVoiceVLANAgingTime OBJECT-TYPE
   SYNTAX      Integer32(10..1000000)
   MAX-ACCESS  read-write
   STATUS      current
   DESCRIPTION
       " Voice VLAN secure learning aging time.
         default: 86400,
         range : 10 - 10000000. "
   ::= { gs2326plusVoiceVLANConf 3 }

gs2326plusVoiceVLANTrafficClass OBJECT-TYPE
   SYNTAX      Integer32(0..7)
   MAX-ACCESS  read-write
   STATUS      current
   DESCRIPTION
       " Voice VLAN traffic class, all traffic on the Voice VLAN
         will apply this class, available value is from 0(Low)
         to 7(High).
         default: 7. "
   ::= { gs2326plusVoiceVLANConf 4 }


gs2326plusVoiceVLANPortTable OBJECT-TYPE
   SYNTAX      SEQUENCE OF Gs2326plusVoiceVLANPortEntry
   MAX-ACCESS  not-accessible
   STATUS      current
   DESCRIPTION
       " Show Voice Vlan configuration. "
   ::= { gs2326plusVoiceVLANConf 5 }

gs2326plusVoiceVLANPortEntry OBJECT-TYPE
   SYNTAX      Gs2326plusVoiceVLANPortEntry
   MAX-ACCESS  not-accessible
   STATUS      current
   DESCRIPTION
       ""
   INDEX    { gs2326plusVoiceVLANPort  }
   ::= { gs2326plusVoiceVLANPortTable 1 }

Gs2326plusVoiceVLANPortEntry ::= SEQUENCE {
   gs2326plusVoiceVLANPort                    Integer32,
   gs2326plusVoiceVLANPortMode                INTEGER,
   gs2326plusVoiceVLANPortSecurity            INTEGER,
   gs2326plusVoiceVLANPortDiscoveryProtocol   INTEGER
}

gs2326plusVoiceVLANPort OBJECT-TYPE
   SYNTAX      Integer32(1..4095)
   MAX-ACCESS  not-accessible
   STATUS      current
   DESCRIPTION
       " port, range : 1 - port number. "
   ::= { gs2326plusVoiceVLANPortEntry 1 }

gs2326plusVoiceVLANPortMode OBJECT-TYPE
   SYNTAX      INTEGER { disable(0), auto(1), forced(2) }
   MAX-ACCESS  read-write
   STATUS      current
   DESCRIPTION
       " Voice VLAN port mode.
         default: 0,
         0: Disable (Disjoin from Voice VLAN.)
         1: Auto (Enable auto detect mode. It detects whether there is VoIP phone attached to the specific port and configures the Voice VLAN members automatically.)
         2: Forced (Force join to Voice VLAN.)"
   ::= { gs2326plusVoiceVLANPortEntry 2 }

gs2326plusVoiceVLANPortSecurity OBJECT-TYPE
   SYNTAX      INTEGER { disable(0), enable(1) }
   MAX-ACCESS  read-write
   STATUS      current
   DESCRIPTION
       " Voice VLAN port security mode.
         default: 0,
         0: Disable (Disjoin from Voice VLAN.)
         1: enable ( Enable Voice VLAN security mode. When the function is
                     enabled, all non-telephone MAC address in Voice VLAN
                     will be blocked 10 seconds.)"
   ::= { gs2326plusVoiceVLANPortEntry 3 }

gs2326plusVoiceVLANPortDiscoveryProtocol OBJECT-TYPE
   SYNTAX      INTEGER { oui(0), lldp(1), both(2) }
   MAX-ACCESS  read-write
   STATUS      current
   DESCRIPTION
       " Voice VLAN port discovery protocol.
         default: 0
         0: OUI (Detect telephony device by OUI address.)
         1: LLDP (Detect telephony device by LLDP.)
         2: Both (Both OUI and LLDP.) "
   ::= { gs2326plusVoiceVLANPortEntry 4 }

gs2326plusVoiceVLANSkipNAS OBJECT-TYPE
   SYNTAX      INTEGER { disable(0), enable(1) }
   MAX-ACCESS  read-write
   STATUS      current
   DESCRIPTION
       " Voice VLAN skip NAS mode.
         default: 0,
         0: Disable (Do not skip NAS on Voice VLAN.)
         1: enable (Enable skipping of NAS on Voice VLAN. When the function is
                    enabled, authentication through the NAS module is not
                    applied to the Voice VLAN, but clients are allowed without
                    authentication.)"
   ::= { gs2326plusVoiceVLANPortEntry 5 }


gs2326plusVoiceVLANOUI                                          OBJECT IDENTIFIER ::= { gs2326plusVoiceVLAN 2 }

gs2326plusVoiceVLANOUICreate OBJECT-TYPE
   SYNTAX       INTEGER { none(0), create(1) }
   MAX-ACCESS   read-write
   STATUS       current
   DESCRIPTION
       "default: 0
        0 : None  (read only)
        1 : Create an OUI entry"
   ::= { gs2326plusVoiceVLANOUI 1 }

gs2326plusVoiceVLANOUITable OBJECT-TYPE
   SYNTAX      SEQUENCE OF Gs2326plusVoiceVLANOUIEntry
   MAX-ACCESS  not-accessible
   STATUS      current
   DESCRIPTION
       " Create Voice VLAN OUI entry. Modify OUI table will
         restart auto detect OUI process. "
   ::= { gs2326plusVoiceVLANOUI 2 }

gs2326plusVoiceVLANOUIEntry OBJECT-TYPE
   SYNTAX      Gs2326plusVoiceVLANOUIEntry
   MAX-ACCESS  not-accessible
   STATUS      current
   DESCRIPTION
       ""
   INDEX    { gs2326plusVoiceVLANOUIIndex  }
   ::= { gs2326plusVoiceVLANOUITable 1 }

Gs2326plusVoiceVLANOUIEntry ::= SEQUENCE {
   gs2326plusVoiceVLANOUIIndex         Integer32,
   gs2326plusVoiceVLANTelephonyOUI     OCTET STRING,
   gs2326plusVoiceVLANDescription      DisplayString,
   gs2326plusVoiceVLANOUIRowStatus     INTEGER
}

gs2326plusVoiceVLANOUIIndex OBJECT-TYPE
   SYNTAX      Integer32(1..16)
   MAX-ACCESS  not-accessible
   STATUS      current
   DESCRIPTION
       " "
   ::= { gs2326plusVoiceVLANOUIEntry 1 }

gs2326plusVoiceVLANTelephonyOUI OBJECT-TYPE
   SYNTAX      OCTET STRING (SIZE (1..32))
   MAX-ACCESS  read-write
   STATUS      current
   DESCRIPTION
       "OUI address, format : 0a 1b 2c "
   ::= { gs2326plusVoiceVLANOUIEntry 2 }

gs2326plusVoiceVLANDescription OBJECT-TYPE
   SYNTAX      DisplayString (SIZE (1..32))
   MAX-ACCESS  read-write
   STATUS      current
   DESCRIPTION
       " Up to 32 characters describing OUI address. "
   ::= { gs2326plusVoiceVLANOUIEntry 3 }

gs2326plusVoiceVLANOUIRowStatus OBJECT-TYPE
   SYNTAX      INTEGER { active(1), notInservice(2), destroy(4), undo(5) }
   MAX-ACCESS  read-write
   STATUS      current
   DESCRIPTION
       "1: active
        2: notInservice
        4: destroy
        5: undo"
   ::= { gs2326plusVoiceVLANOUIEntry 4 }

gs2326plusGARP                                                   OBJECT IDENTIFIER ::= { gs2326plusConfiguration 3 }

gs2326plusGARPConfTable OBJECT-TYPE
   SYNTAX      SEQUENCE OF Gs2326plusGARPConfEntry
   MAX-ACCESS  not-accessible
   STATUS      current
   DESCRIPTION
       " "
   ::= { gs2326plusGARP 1 }

gs2326plusGARPConfEntry OBJECT-TYPE
   SYNTAX      Gs2326plusGARPConfEntry
   MAX-ACCESS  not-accessible
   STATUS      current
   DESCRIPTION
       ""
   INDEX    { gs2326plusGARPConfPort  }
   ::= { gs2326plusGARPConfTable 1 }

Gs2326plusGARPConfEntry ::= SEQUENCE {
   gs2326plusGARPConfPort           Integer32,
   gs2326plusGARPJoinTimer          Integer32,
   gs2326plusGARPLeaveTimer         Integer32,
   gs2326plusGARPLeaveAllTimer      Integer32,
   gs2326plusGARPApplicantion       INTEGER,
   gs2326plusGARPAttributeType      INTEGER,
   gs2326plusGARPApplicant          INTEGER
}

gs2326plusGARPConfPort OBJECT-TYPE
   SYNTAX      Integer32(1..4095)
   MAX-ACCESS  not-accessible
   STATUS      current
   DESCRIPTION
       " "
   ::= { gs2326plusGARPConfEntry 1 }

gs2326plusGARPJoinTimer OBJECT-TYPE
   SYNTAX      Integer32(200..1000)
   MAX-ACCESS  read-write
   STATUS      current
   DESCRIPTION
       "default: 200, range : 200 - 1000 "
   ::= { gs2326plusGARPConfEntry 2 }

gs2326plusGARPLeaveTimer OBJECT-TYPE
   SYNTAX      Integer32(600..3000)
   MAX-ACCESS  read-write
   STATUS      current
   DESCRIPTION
       "default: 600 , range : 600 - 3000"
   ::= { gs2326plusGARPConfEntry 3 }

gs2326plusGARPLeaveAllTimer OBJECT-TYPE
   SYNTAX      Integer32(10000..50000)
   MAX-ACCESS  read-write
   STATUS      current
   DESCRIPTION
       "default: 10000, range : 10000 - 50000 "
   ::= { gs2326plusGARPConfEntry 4 }

gs2326plusGARPApplicantion OBJECT-TYPE
   SYNTAX      INTEGER { gvrp(1)}
   MAX-ACCESS  read-write
   STATUS      current
   DESCRIPTION
       "default: 1
       1: GVRP"
   ::= { gs2326plusGARPConfEntry 5 }

gs2326plusGARPAttributeType OBJECT-TYPE
   SYNTAX      INTEGER { vlan(1)}
   MAX-ACCESS  read-write
   STATUS      current
   DESCRIPTION
       "default: 1
       1: VLAN"
   ::= { gs2326plusGARPConfEntry 6 }

gs2326plusGARPApplicant OBJECT-TYPE
   SYNTAX      INTEGER { participant(0), nonParticipant(1) }
   MAX-ACCESS  read-write
   STATUS      current
   DESCRIPTION
       "default: 0
       0: normal-participant
       1: non-participant"
   ::= { gs2326plusGARPConfEntry 7 }

gs2326plusGARPStatisticsTable OBJECT-TYPE
   SYNTAX      SEQUENCE OF Gs2326plusGARPStatisticsEntry
   MAX-ACCESS  not-accessible
   STATUS      current
   DESCRIPTION
       " Show the basic GARP port statistics. "
   ::= { gs2326plusGARP 2 }

gs2326plusGARPStatisticsEntry OBJECT-TYPE
   SYNTAX      Gs2326plusGARPStatisticsEntry
   MAX-ACCESS  not-accessible
   STATUS      current
   DESCRIPTION
       ""
   INDEX    { gs2326plusGARPStatisticsPort  }
   ::= { gs2326plusGARPStatisticsTable 1 }

Gs2326plusGARPStatisticsEntry ::= SEQUENCE {
   gs2326plusGARPStatisticsPort             Integer32,
   gs2326plusGARPStatisticsPeerMAC          DisplayString,
   gs2326plusGARPStatisticsFailedCount      Counter32
}

gs2326plusGARPStatisticsPort OBJECT-TYPE
   SYNTAX      Integer32(1..4095)
   MAX-ACCESS  not-accessible
   STATUS      current
   DESCRIPTION
       " port, range : 1 - port number. "
   ::= { gs2326plusGARPStatisticsEntry 1 }

gs2326plusGARPStatisticsPeerMAC OBJECT-TYPE
   SYNTAX      DisplayString
   MAX-ACCESS  read-only
   STATUS      current
   DESCRIPTION
       " Peer MAC is MAC address of the neighbour Switch from with GARP frame is received.  "
   ::= { gs2326plusGARPStatisticsEntry 2 }

gs2326plusGARPStatisticsFailedCount OBJECT-TYPE
   SYNTAX      Counter32
   MAX-ACCESS  read-only
   STATUS      current
   DESCRIPTION
       " explain Failed count here. "
   ::= { gs2326plusGARPStatisticsEntry 3 }

gs2326plusGVRP                                                   OBJECT IDENTIFIER ::= { gs2326plusConfiguration 4 }

gs2326plusGVRPConf                                                   OBJECT IDENTIFIER ::= { gs2326plusGVRP 1 }

gs2326plusGVRPMode OBJECT-TYPE
   SYNTAX      INTEGER { disable(0), enable(1) }
   MAX-ACCESS  read-write
   STATUS      current
   DESCRIPTION
       "default: 0,
        0: disable,
        1: enable. "
   ::= { gs2326plusGVRPConf 1 }

gs2326plusGVRPConfTable OBJECT-TYPE
   SYNTAX      SEQUENCE OF Gs2326plusGVRPConfEntry
   MAX-ACCESS  not-accessible
   STATUS      current
   DESCRIPTION
       " "
   ::= { gs2326plusGVRPConf 2 }

gs2326plusGVRPConfEntry OBJECT-TYPE
   SYNTAX      Gs2326plusGVRPConfEntry
   MAX-ACCESS  not-accessible
   STATUS      current
   DESCRIPTION
       ""
   INDEX    { gs2326plusGVRPConfPort  }
   ::= { gs2326plusGVRPConfTable 1 }

Gs2326plusGVRPConfEntry ::= SEQUENCE {
   gs2326plusGVRPConfPort           Integer32,
   gs2326plusGVRPConfPortMode       INTEGER,
   gs2326plusGVRPConfPortRRole      INTEGER
}

gs2326plusGVRPConfPort OBJECT-TYPE
   SYNTAX      Integer32(1..4095)
   MAX-ACCESS  not-accessible
   STATUS      current
   DESCRIPTION
       " "
   ::= { gs2326plusGVRPConfEntry 1 }

gs2326plusGVRPConfPortMode OBJECT-TYPE
   SYNTAX      INTEGER { disable(0), enable(1) }
   MAX-ACCESS  read-write
   STATUS      current
   DESCRIPTION
       "default: 0
       1: enable
       0: disable"
   ::= { gs2326plusGVRPConfEntry 2 }

gs2326plusGVRPConfPortRRole OBJECT-TYPE
   SYNTAX      INTEGER { disable(0), enable(1) }
   MAX-ACCESS  read-write
   STATUS      current
   DESCRIPTION
       "default: 0
       1: enable
       0: disable"
   ::= { gs2326plusGVRPConfEntry 3 }

gs2326plusGVRPStatisticsTable OBJECT-TYPE
   SYNTAX      SEQUENCE OF Gs2326plusGVRPStatisticsEntry
   MAX-ACCESS  not-accessible
   STATUS      current
   DESCRIPTION
       " "
   ::= { gs2326plusGVRP 2 }

gs2326plusGVRPStatisticsEntry OBJECT-TYPE
   SYNTAX      Gs2326plusGVRPStatisticsEntry
   MAX-ACCESS  not-accessible
   STATUS      current
   DESCRIPTION
       ""
   INDEX    { gs2326plusGVRPStatisticsPort  }
   ::= { gs2326plusGVRPStatisticsTable 1 }

Gs2326plusGVRPStatisticsEntry ::= SEQUENCE {
   gs2326plusGVRPStatisticsPort         Integer32,
   gs2326plusGVRPStatisticsJoinTxCnt    Counter32,
   gs2326plusGVRPStatisticsLeaveTxCnt   Counter32
}

gs2326plusGVRPStatisticsPort OBJECT-TYPE
   SYNTAX      Integer32(1..4095)
   MAX-ACCESS  not-accessible
   STATUS      current
   DESCRIPTION
       " "
   ::= { gs2326plusGVRPStatisticsEntry 1 }

gs2326plusGVRPStatisticsJoinTxCnt OBJECT-TYPE
   SYNTAX      Counter32
   MAX-ACCESS  read-only
   STATUS      current
   DESCRIPTION
       ""
   ::= { gs2326plusGVRPStatisticsEntry 2 }

gs2326plusGVRPStatisticsLeaveTxCnt OBJECT-TYPE
   SYNTAX      Counter32
   MAX-ACCESS  read-only
   STATUS      current
   DESCRIPTION
       ""
   ::= { gs2326plusGVRPStatisticsEntry 3 }


gs2326plusMirroring                                             OBJECT IDENTIFIER ::= { gs2326plusConfiguration 6 }

gs2326plusPortToMirrorOn OBJECT-TYPE
   SYNTAX      Integer32(0..10)
   MAX-ACCESS  read-write
   STATUS      current
   DESCRIPTION
       "default: 0
        0: disable,
        range : 1 - port number. "
   ::= { gs2326plusMirroring 1 }

gs2326plusMirrorTable OBJECT-TYPE
   SYNTAX      SEQUENCE OF Gs2326plusMirrorEntry
   MAX-ACCESS  not-accessible
   STATUS      current
   DESCRIPTION
       " "
   ::= { gs2326plusMirroring 2 }

gs2326plusMirrorEntry OBJECT-TYPE
   SYNTAX      Gs2326plusMirrorEntry
   MAX-ACCESS  not-accessible
   STATUS      current
   DESCRIPTION
       ""
   INDEX    { gs2326plusMirrorPort  }
   ::= { gs2326plusMirrorTable 1 }

Gs2326plusMirrorEntry ::= SEQUENCE {
   gs2326plusMirrorPort		Integer32,
   gs2326plusMirrorMode		INTEGER
}

gs2326plusMirrorPort OBJECT-TYPE
   SYNTAX      Integer32(1..4095)
   MAX-ACCESS  not-accessible
   STATUS      current
   DESCRIPTION
       " "
   ::= { gs2326plusMirrorEntry 1 }

gs2326plusMirrorMode OBJECT-TYPE
   SYNTAX      INTEGER { disable(0), enable(1), rxOnly(2), txOnly(3) }
   MAX-ACCESS  read-write
   STATUS      current
   DESCRIPTION
       "default: 0
       0: disable
       1: enable
       2: rx only
       3: tx only
       Setting Tx mirroring for analyzer port has no effect. Tx mirroring ignored"
   ::= { gs2326plusMirrorEntry 2 }

gs2326plusTrapEventSeverity                                             OBJECT IDENTIFIER ::= { gs2326plusConfiguration 7 }

gs2326plusTrapEventSeverityACL OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  6(Info)
        0: Emergency
        1: Alert
        2: Critical
        3: Error
        4: Warning
        5: Notice
        6: Info
        7: Debug"
   ::= { gs2326plusTrapEventSeverity 1 }

gs2326plusTrapEventSeverityACLLog OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  7(Debug)
        0: Emergency
        1: Alert
        2: Critical
        3: Error
        4: Warning
        5: Notice
        6: Info
        7: Debug"
   ::= { gs2326plusTrapEventSeverity 2 }

gs2326plusTrapEventSeverityAccessMgmt OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  6(Info)
        0: Emergency
        1: Alert
        2: Critical
        3: Error
        4: Warning
        5: Notice
        6: Info
        7: Debug"
   ::= { gs2326plusTrapEventSeverity 3 }

gs2326plusTrapEventSeverityAuthFailed OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  4(Warning)
        0: Emergency
        1: Alert
        2: Critical
        3: Error
        4: Warning
        5: Notice
        6: Info
        7: Debug"
   ::= { gs2326plusTrapEventSeverity 4 }

gs2326plusTrapEventSeverityColdStart OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  4(Warning)
        0: Emergency
        1: Alert
        2: Critical
        3: Error
        4: Warning
        5: Notice
        6: Info
        7: Debug"
   ::= { gs2326plusTrapEventSeverity 5 }

gs2326plusTrapEventSeverityConfigInfo OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  6(Info)
        0: Emergency
        1: Alert
        2: Critical
        3: Error
        4: Warning
        5: Notice
        6: Info
        7: Debug"
   ::= { gs2326plusTrapEventSeverity 6 }

gs2326plusTrapEventSeverityFirmwareUpgrade OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  6(Info)
        0: Emergency
        1: Alert
        2: Critical
        3: Error
        4: Warning
        5: Notice
        6: Info
        7: Debug"
   ::= { gs2326plusTrapEventSeverity 7 }

gs2326plusTrapEventSeverityImportExport OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  6(Info)
        0: Emergency
        1: Alert
        2: Critical
        3: Error
        4: Warning
        5: Notice
        6: Info
        7: Debug"
   ::= { gs2326plusTrapEventSeverity 8 }

gs2326plusTrapEventSeverityLACP OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  6(Info)
        0: Emergency
        1: Alert
        2: Critical
        3: Error
        4: Warning
        5: Notice
        6: Info
        7: Debug"
   ::= { gs2326plusTrapEventSeverity 9 }

gs2326plusTrapEventSeverityLinkStatus OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  4(Warning)
        0: Emergency
        1: Alert
        2: Critical
        3: Error
        4: Warning
        5: Notice
        6: Info
        7: Debug"
   ::= { gs2326plusTrapEventSeverity 10 }

gs2326plusTrapEventSeverityLogin OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  6(Info)
        0: Emergency
        1: Alert
        2: Critical
        3: Error
        4: Warning
        5: Notice
        6: Info
        7: Debug"
   ::= { gs2326plusTrapEventSeverity 11 }

gs2326plusTrapEventSeverityLogout OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  6(Info)
        0: Emergency
        1: Alert
        2: Critical
        3: Error
        4: Warning
        5: Notice
        6: Info
        7: Debug"
   ::= { gs2326plusTrapEventSeverity 12 }

gs2326plusTrapEventSeverityLoopProtect OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  6(Info)
        0: Emergency
        1: Alert
        2: Critical
        3: Error
        4: Warning
        5: Notice
        6: Info
        7: Debug"
   ::= { gs2326plusTrapEventSeverity 13 }

gs2326plusTrapEventSeverityMgmtIPChange OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  6(Info)
        0: Emergency
        1: Alert
        2: Critical
        3: Error
        4: Warning
        5: Notice
        6: Info
        7: Debug"
   ::= { gs2326plusTrapEventSeverity 14 }

gs2326plusTrapEventSeverityModuleChange OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  5(Notice)
        0: Emergency
        1: Alert
        2: Critical
        3: Error
        4: Warning
        5: Notice
        6: Info
        7: Debug"
   ::= { gs2326plusTrapEventSeverity 15 }

gs2326plusTrapEventSeverityNAS OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  6(Info)
        0: Emergency
        1: Alert
        2: Critical
        3: Error
        4: Warning
        5: Notice
        6: Info
        7: Debug"
   ::= { gs2326plusTrapEventSeverity 16 }

gs2326plusTrapEventSeverityPasswordChange OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  6(Info)
        0: Emergency
        1: Alert
        2: Critical
        3: Error
        4: Warning
        5: Notice
        6: Info
        7: Debug"
   ::= { gs2326plusTrapEventSeverity 17 }

gs2326plusTrapEventSeverityPortSecurity OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  6(Info)
        0: Emergency
        1: Alert
        2: Critical
        3: Error
        4: Warning
        5: Notice
        6: Info
        7: Debug"
   ::= { gs2326plusTrapEventSeverity 18 }

gs2326plusTrapEventSeverityVLAN OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  6(Info)
        0: Emergency
        1: Alert
        2: Critical
        3: Error
        4: Warning
        5: Notice
        6: Info
        7: Debug"
   ::= { gs2326plusTrapEventSeverity 20 }

gs2326plusTrapEventSeverityWarmStart OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  4(Warning)
        0: Emergency
        1: Alert
        2: Critical
        3: Error
        4: Warning
        5: Notice
        6: Info
        7: Debug"
   ::= { gs2326plusTrapEventSeverity 21 }



gs2326plusTrapEventSeverityARPConflict OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  4(Warning)
        0: Emergency
        1: Alert
        2: Critical
        3: Error
        4: Warning
        5: Notice
        6: Info
        7: Debug"
   ::= { gs2326plusTrapEventSeverity 25 }

gs2326plusTrapEventSeveritySpoofingLimit OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  4(Warning)
        0: Emergency
        1: Alert
        2: Critical
        3: Error
        4: Warning
        5: Notice
        6: Info
        7: Debug"
   ::= { gs2326plusTrapEventSeverity 27 }

gs2326plusTrapEventSeverityStaticARPConflict	 OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  4(Warning)
        0: Emergency
        1: Alert
        2: Critical
        3: Error
        4: Warning
        5: Notice
        6: Info
        7: Debug"
   ::= { gs2326plusTrapEventSeverity 28 }

gs2326plusSMTP                                             OBJECT IDENTIFIER ::= { gs2326plusConfiguration 8 }

gs2326plusSMTPMailServer OBJECT-TYPE
   SYNTAX      DisplayString
   MAX-ACCESS  read-write
   STATUS      current
   DESCRIPTION
       " Up to 47 characters describing email server. "
   ::= { gs2326plusSMTP 1 }

gs2326plusSMTPUserName OBJECT-TYPE
   SYNTAX      DisplayString
   MAX-ACCESS  read-write
   STATUS      current
   DESCRIPTION
       " Up to 47 characters describing user name. "
   ::= { gs2326plusSMTP 2 }

gs2326plusSMTPPassword OBJECT-TYPE
   SYNTAX      DisplayString
   MAX-ACCESS  read-write
   STATUS      current
   DESCRIPTION
       " Up to 47 characters describing password. "
   ::= { gs2326plusSMTP 3 }

gs2326plusSMTPServeriryLevel OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       "default: 6
       0: Emergency
       1: Alert
       2: Critical
       3: Error
       4: Warning
       5: Notice
       6: Info
       7: Debug"
   ::= { gs2326plusSMTP 4 }

gs2326plusSMTPSender OBJECT-TYPE
   SYNTAX      DisplayString
   MAX-ACCESS  read-write
   STATUS      current
   DESCRIPTION
       " Up to 47 characters describing sender. "
   ::= { gs2326plusSMTP 5 }

gs2326plusSMTPReturnPath OBJECT-TYPE
   SYNTAX      DisplayString
   MAX-ACCESS  read-write
   STATUS      current
   DESCRIPTION
       " Up to 47 characters describing return path. "
   ::= { gs2326plusSMTP 6 }

gs2326plusSMTPEmailAddress1 OBJECT-TYPE
   SYNTAX      DisplayString
   MAX-ACCESS  read-write
   STATUS      current
   DESCRIPTION
       " Up to 47 characters describing mail address. "
   ::= { gs2326plusSMTP 7 }

gs2326plusSMTPEmailAddress2 OBJECT-TYPE
   SYNTAX      DisplayString
   MAX-ACCESS  read-write
   STATUS      current
   DESCRIPTION
       " Up to 47 characters describing mail address. "
   ::= { gs2326plusSMTP 8 }

gs2326plusSMTPEmailAddress3 OBJECT-TYPE
   SYNTAX      DisplayString
   MAX-ACCESS  read-write
   STATUS      current
   DESCRIPTION
       " Up to 47 characters describing mail address. "
   ::= { gs2326plusSMTP 9 }

gs2326plusSMTPEmailAddress4 OBJECT-TYPE
   SYNTAX      DisplayString
   MAX-ACCESS  read-write
   STATUS      current
   DESCRIPTION
       " Up to 47 characters describing mail address. "
   ::= { gs2326plusSMTP 10 }

gs2326plusSMTPEmailAddress5 OBJECT-TYPE
   SYNTAX      DisplayString
   MAX-ACCESS  read-write
   STATUS      current
   DESCRIPTION
       " Up to 47 characters describing mail address. "
   ::= { gs2326plusSMTP 11 }

gs2326plusSMTPEmailAddress6 OBJECT-TYPE
   SYNTAX      DisplayString
   MAX-ACCESS  read-write
   STATUS      current
   DESCRIPTION
       " Up to 47 characters describing mail address. "
   ::= { gs2326plusSMTP 12 }


gs2326plusACL                                                   OBJECT IDENTIFIER ::= { gs2326plusConfiguration 9 }

gs2326plusACLPortsConfTable OBJECT-TYPE
   SYNTAX      SEQUENCE OF Gs2326plusACLPortsConfEntry
   MAX-ACCESS  not-accessible
   STATUS      current
   DESCRIPTION
       " "
   ::= { gs2326plusACL 1 }

gs2326plusACLPortsConfEntry OBJECT-TYPE
   SYNTAX      Gs2326plusACLPortsConfEntry
   MAX-ACCESS  not-accessible
   STATUS      current
   DESCRIPTION
       ""
   INDEX    { gs2326plusACLPortsConfPort  }
   ::= { gs2326plusACLPortsConfTable 1 }

Gs2326plusACLPortsConfEntry ::= SEQUENCE {
   gs2326plusACLPortsConfPort               Integer32,
   gs2326plusACLPortsConfPolicyID           Integer32,
   gs2326plusACLPortsConfAction             INTEGER,
   gs2326plusACLPortsConfRateLimiterID      Integer32,
   gs2326plusACLPortsConfPortRedirect       Integer32,
   gs2326plusACLPortsConfMirror             INTEGER,
   gs2326plusACLPortsConfLogging            INTEGER,
   gs2326plusACLPortsConfShutdown           INTEGER,
   gs2326plusACLPortsConfState              INTEGER,
   gs2326plusACLPortsConfCounter            Counter32
}

gs2326plusACLPortsConfPort OBJECT-TYPE
   SYNTAX      Integer32 (1..4095)
   MAX-ACCESS  not-accessible
   STATUS      current
   DESCRIPTION
       " "
   ::= { gs2326plusACLPortsConfEntry 1 }

gs2326plusACLPortsConfPolicyID OBJECT-TYPE
   SYNTAX      Integer32 (0..255)
   MAX-ACCESS  read-write
   STATUS      current
   DESCRIPTION
       "default: 0, range : 0 - 255 "
   ::= { gs2326plusACLPortsConfEntry 2 }

gs2326plusACLPortsConfAction OBJECT-TYPE
   SYNTAX      INTEGER { deny(0), permit(1) }
   MAX-ACCESS  read-write
   STATUS      current
   DESCRIPTION
       "default: 1,
        0: Deny
        1: Permit"
   ::= { gs2326plusACLPortsConfEntry 3 }

gs2326plusACLPortsConfRateLimiterID OBJECT-TYPE
   SYNTAX      Integer32 (0..12)
   MAX-ACCESS  read-write
   STATUS      current
   DESCRIPTION
       "default: 0,
        0: Disable
        range : 0 - 12 "
   ::= { gs2326plusACLPortsConfEntry 4 }

gs2326plusACLPortsConfPortRedirect OBJECT-TYPE
   SYNTAX      Integer32 (0..4095)
   MAX-ACCESS  read-write
   STATUS      current
   DESCRIPTION
       "default: 0
        0: Disable
        range : 0 - end port number "
   ::= { gs2326plusACLPortsConfEntry 5 }

gs2326plusACLPortsConfMirror OBJECT-TYPE
   SYNTAX      INTEGER { disable(0), enable(1) }
   MAX-ACCESS  read-write
   STATUS      current
   DESCRIPTION
       "default: 0
        0: Disable
        1: Enable "
   ::= { gs2326plusACLPortsConfEntry 6 }

gs2326plusACLPortsConfLogging OBJECT-TYPE
   SYNTAX      INTEGER { disable(0), enable(1) }
   MAX-ACCESS  read-write
   STATUS      current
   DESCRIPTION
       "default: 0
        0: Disable
        1: Enable "
   ::= { gs2326plusACLPortsConfEntry 7 }

gs2326plusACLPortsConfShutdown OBJECT-TYPE
   SYNTAX      INTEGER { disable(0), enable(1) }
   MAX-ACCESS  read-write
   STATUS      current
   DESCRIPTION
       "default: 0
        0: Disable
        1: Enable "
   ::= { gs2326plusACLPortsConfEntry 8 }

gs2326plusACLPortsConfState OBJECT-TYPE
   SYNTAX      INTEGER { disable(0), enable(1) }
   MAX-ACCESS  read-write
   STATUS      current
   DESCRIPTION
       "default: 1
        0: Disable
        1: Enable "
   ::= { gs2326plusACLPortsConfEntry 9 }

gs2326plusACLPortsConfCounter OBJECT-TYPE
   SYNTAX      Counter32
   MAX-ACCESS  read-only
   STATUS      current
   DESCRIPTION
       "Counts the number of frames that match this ACE. "
   ::= { gs2326plusACLPortsConfEntry 10 }


gs2326plusACLRateLimiterTable OBJECT-TYPE
   SYNTAX      SEQUENCE OF Gs2326plusACLRateLimiterEntry
   MAX-ACCESS  not-accessible
   STATUS      current
   DESCRIPTION
       " "
   ::= { gs2326plusACL 2 }

gs2326plusACLRateLimiterEntry OBJECT-TYPE
   SYNTAX      Gs2326plusACLRateLimiterEntry
   MAX-ACCESS  not-accessible
   STATUS      current
   DESCRIPTION
       ""
   INDEX    { gs2326plusACLRateLimiterID  }
   ::= { gs2326plusACLRateLimiterTable 1 }

Gs2326plusACLRateLimiterEntry ::= SEQUENCE {
   gs2326plusACLRateLimiterID       Integer32,
   gs2326plusACLRateLimiterUnit     INTEGER,
   gs2326plusACLRateLimiterRate     Integer32
}

gs2326plusACLRateLimiterID OBJECT-TYPE
   SYNTAX      Integer32 (1..12)
   MAX-ACCESS  not-accessible
   STATUS      current
   DESCRIPTION
       " Rate Limiter ID.
         range : 1-12 "
   ::= { gs2326plusACLRateLimiterEntry 1 }

gs2326plusACLRateLimiterUnit OBJECT-TYPE
   SYNTAX      INTEGER { pps(0), kbps(1) }
   MAX-ACCESS  read-write
   STATUS      current
   DESCRIPTION
       "default: 0,
        0: pps
        1: kbps"
   ::= { gs2326plusACLRateLimiterEntry 2 }

gs2326plusACLRateLimiterRate OBJECT-TYPE
   SYNTAX      Integer32(0..3276700)
   MAX-ACCESS  read-write
   STATUS      current
   DESCRIPTION
       "default: 1,
        range : <0-3276700> pps
                <0-10000> kbps"
   ::= { gs2326plusACLRateLimiterEntry 3 }


gs2326plusACLACE                                          OBJECT IDENTIFIER ::= { gs2326plusACL 3 }

gs2326plusACLACECreate OBJECT-TYPE
   SYNTAX       INTEGER { none(0), create(1) }
   MAX-ACCESS   read-write
   STATUS       current
   DESCRIPTION
       "default: 0
        0 : None  (read only)
        1 : Create an ACE entry"
   ::= { gs2326plusACLACE 1 }

gs2326plusACLACETable OBJECT-TYPE
   SYNTAX      SEQUENCE OF Gs2326plusACLACEEntry
   MAX-ACCESS  not-accessible
   STATUS      current
   DESCRIPTION
       " Create ACL ACE entry. "
   ::= { gs2326plusACLACE 2 }

gs2326plusACLACEEntry OBJECT-TYPE
   SYNTAX      Gs2326plusACLACEEntry
   MAX-ACCESS  not-accessible
   STATUS      current
   DESCRIPTION
       ""
   INDEX    { gs2326plusACLACEIndex  }
   ::= { gs2326plusACLACETable 1 }

Gs2326plusACLACEEntry ::= SEQUENCE {
   gs2326plusACLACEIndex                Integer32,
   gs2326plusACLACEID                   Integer32,
   gs2326plusACLACENextID               Integer32,
   gs2326plusACLACEIngressPort          DisplayString,
   gs2326plusACLACEPortPolicyNumber     Integer32,

   gs2326plusACLACEPortPolicyBitmask    Integer32,
   gs2326plusACLACEFrameType            INTEGER,
   gs2326plusACLACEAction               INTEGER,
   gs2326plusACLACEDenyPortRedirect     DisplayString,
   gs2326plusACLACELogging              INTEGER,

   gs2326plusACLACEMirror               INTEGER,
   gs2326plusACLACERateLimiter          Integer32,
   gs2326plusACLACEShutdown             INTEGER,
   gs2326plusACLACEVLAN8021QTagged      INTEGER,
   gs2326plusACLACEVLANTagPriority      Integer32,

   gs2326plusACLACEVLANVID              Integer32,
   gs2326plusACLACEEtherType            Integer32,
   gs2326plusACLACESMAC                 DisplayString,
   gs2326plusACLACEDMACType             INTEGER,
   gs2326plusACLACEDMAC                 DisplayString,

   gs2326plusACLACEArpOpcode            INTEGER,
   gs2326plusACLACEArpFlagsRequestReply INTEGER,
   gs2326plusACLACEArpFlagsArpSmac      INTEGER,
   gs2326plusACLACEArpFlagsRarpDmac     INTEGER,
   gs2326plusACLACEArpFlagsLength       INTEGER,

   gs2326plusACLACEArpFlagsIp           INTEGER,
   gs2326plusACLACEArpFlagsEthernet     INTEGER,
   gs2326plusACLACESIPType              INTEGER,
   gs2326plusACLACESIPIPAddress         IpAddress,
   gs2326plusACLACESIPNetworkPrefix     Integer32,

   gs2326plusACLACEDIPType              INTEGER,
   gs2326plusACLACEDIPIPAddress         IpAddress,
   gs2326plusACLACEDIPNetworkPrefix     Integer32,

   gs2326plusACLACEIPProtocol           Integer32,
   gs2326plusACLACEIPFlagsTTL           INTEGER,
   gs2326plusACLACEIPFlagsOptions       INTEGER,
   gs2326plusACLACEIPFlagsFragment      INTEGER,
   gs2326plusACLACEICMPType             Integer32,

   gs2326plusACLACEICMPCode             Integer32,
   gs2326plusACLACESourcePortMin        Integer32,
   gs2326plusACLACESourcePortMax        Integer32,
   gs2326plusACLACEDestPortMin          Integer32,
   gs2326plusACLACEDestPortMax          Integer32,

   gs2326plusACLACETCPFlagsFin          INTEGER,
   gs2326plusACLACETCPFlagsSyn          INTEGER,
   gs2326plusACLACETCPFlagsRst          INTEGER,
   gs2326plusACLACETCPFlagsPsh          INTEGER,
   gs2326plusACLACETCPFlagsAck          INTEGER,

   gs2326plusACLACETCPFlagsUrg          INTEGER,

   gs2326plusACLACERowStatus            INTEGER
}

gs2326plusACLACEIndex OBJECT-TYPE
   SYNTAX      Integer32(1..256)
   MAX-ACCESS  not-accessible
   STATUS      current
   DESCRIPTION
       " "
   ::= { gs2326plusACLACEEntry 1 }

gs2326plusACLACEID OBJECT-TYPE
   SYNTAX      Integer32(1..256)
   MAX-ACCESS  read-write
   STATUS      current
   DESCRIPTION
       " If the ACE ID is specified and an entry with this ACE ID
         already exists, the ACE will be modified. Otherwise, a
         new ACE will be added.
         range : 1 - 256. "
   ::= { gs2326plusACLACEEntry 2 }

gs2326plusACLACENextID OBJECT-TYPE
   SYNTAX      Integer32 (0..256)
   MAX-ACCESS  read-write
   STATUS      current
   DESCRIPTION
       " If the next ACE ID is non zero, the ACE will be placed
         before this ACE in the list. If the next ACE ID is zero,
         the ACE will be placed last in the list.
         range : 0 - 256. "
   ::= { gs2326plusACLACEEntry 3 }

gs2326plusACLACEIngressPort OBJECT-TYPE
   SYNTAX      DisplayString
   MAX-ACCESS  read-write
   STATUS      current
   DESCRIPTION
       " Indicates the ingress port of the ACE. Possible values are:
         All: The ACE will match all ingress port.
         Port: The ACE will match a specific ingress port.Format: 1,3,6."
   ::= { gs2326plusACLACEEntry 4 }

gs2326plusACLACEPortPolicyNumber OBJECT-TYPE
   SYNTAX      Integer32(0..255)
   MAX-ACCESS  read-write
   STATUS      current
   DESCRIPTION
       " policy value.
         range : 0 - 255. "
   ::= { gs2326plusACLACEEntry 5 }

gs2326plusACLACEPortPolicyBitmask OBJECT-TYPE
   SYNTAX      Integer32(0..255)
   MAX-ACCESS  read-write
   STATUS      current
   DESCRIPTION
       " policy bitmask.
         range : 0 - 255(0xff). "
   ::= { gs2326plusACLACEEntry 6 }

gs2326plusACLACEFrameType OBJECT-TYPE
   SYNTAX      INTEGER {
                        any(0),
                        arp(1),
                        etype(2),
                        icmp(3),
                        ipv4(4),
                        tcp(5),
                        udp(6)
                        }
   MAX-ACCESS  read-write
   STATUS      current
   DESCRIPTION
       " 0: any,
         1: arp,
         2: etype,
         3: icmp,
         4: ipv4,
         5: tcp,
         6: udp."
   ::= { gs2326plusACLACEEntry 7 }

gs2326plusACLACEAction OBJECT-TYPE
   SYNTAX      INTEGER { deny(0), permit(1) }
   MAX-ACCESS  read-write
   STATUS      current
   DESCRIPTION
       "default: 1,
        0: Deny
        1: Permit"
   ::= { gs2326plusACLACEEntry 8 }

gs2326plusACLACEDenyPortRedirect OBJECT-TYPE
   SYNTAX      DisplayString
   MAX-ACCESS  read-write
   STATUS      current
   DESCRIPTION
       " Frames that hit the ACE are redirected to the port number specified here.
         Disabled: indicates that the port redirect operation is disabled.
         Port Format: 1,3,6."
   ::= { gs2326plusACLACEEntry 9 }

gs2326plusACLACELogging OBJECT-TYPE
   SYNTAX      INTEGER { disable(0), enable(1) }
   MAX-ACCESS  read-write
   STATUS      current
   DESCRIPTION
       "default: 0,
        0: disable - Frames matching the ACE are not logged.
        1: enable - Frames matching the ACE are stored in the system log."
   ::= { gs2326plusACLACEEntry 10 }

gs2326plusACLACEMirror OBJECT-TYPE
   SYNTAX      INTEGER { disable(0), enable(1) }
   MAX-ACCESS  read-write
   STATUS      current
   DESCRIPTION
       "default: 0,
        0: disable - Frames matching the ACE are not mirrored.
        1: enable - Frames matching the ACE are mirrored."
   ::= { gs2326plusACLACEEntry 11 }

gs2326plusACLACERateLimiter OBJECT-TYPE
   SYNTAX      Integer32(0..12)
   MAX-ACCESS  read-write
   STATUS      current
   DESCRIPTION
       "default: 0,
        0: Disable
        range : 0 - 12 "
   ::= { gs2326plusACLACEEntry 12 }

gs2326plusACLACEShutdown OBJECT-TYPE
   SYNTAX      INTEGER { disable(0), enable(1) }
   MAX-ACCESS  read-write
   STATUS      current
   DESCRIPTION
       "default: 0,
        0: disable - Port shut down is disabled for the AC.
        1: enable - If a frame matches the ACE, the ingress port will be disabled."
   ::= { gs2326plusACLACEEntry 13 }

gs2326plusACLACEVLAN8021QTagged OBJECT-TYPE
   SYNTAX      INTEGER { disable(0), enable(1), any(2) }
   MAX-ACCESS  read-write
   STATUS      current
   DESCRIPTION
       "Specify whether frames can hit the action according to the 802.1Q tagged.
        default: 2,
        0: disable - Untagged frame only.
        1: enable - Tagged frame only.
        2: Any - Any value is allowed. "
   ::= { gs2326plusACLACEEntry 14 }

gs2326plusACLACEVLANTagPriority OBJECT-TYPE
   SYNTAX      Integer32(0..8)
   MAX-ACCESS  read-write
   STATUS      current
   DESCRIPTION
       "Specify the tag priority for this ACE.
        The tag priority can't be set when 802.1Q Tagged is disabled
        default: 8,
        8: Any,
        range : 0 - 8 "
   ::= { gs2326plusACLACEEntry 15 }

gs2326plusACLACEVLANVID OBJECT-TYPE
   SYNTAX      Integer32(0..4094)
   MAX-ACCESS  read-write
   STATUS      current
   DESCRIPTION
       "Specify the VLAN ID filter for this ACE.
        The vid can't be set when 802.1Q Tagged is disabled.
        default: 0,
        0: Any - No VLAN ID filter is specified.
        range : 0 - 4094 "
   ::= { gs2326plusACLACEEntry 16 }

gs2326plusACLACEEtherType OBJECT-TYPE
   SYNTAX      Integer32(0..65535)
   MAX-ACCESS  read-write
   STATUS      current
   DESCRIPTION
       " 0: Any - Any but excluding 0x0800(IPv4) 0x0806(ARP) and 0x86DD(IPv6).
         range : 0 or 1536(0x0600)- 65535(0xffff). "
   ::= { gs2326plusACLACEEntry 17 }

gs2326plusACLACESMAC OBJECT-TYPE
   SYNTAX      DisplayString
   MAX-ACCESS  read-write
   STATUS      current
   DESCRIPTION
       " Configure source MAC address for this ACE.
         <mac-address>: A frame that hits this ACE matches this source MAC address value.
         Any: Don't care."
   ::= { gs2326plusACLACEEntry 18 }

gs2326plusACLACEDMACType OBJECT-TYPE
   SYNTAX      INTEGER { any(0), broadcast(1), unicast(2), multicast(3) , macAddress(4) }
   MAX-ACCESS  read-write
   STATUS      current
   DESCRIPTION
       "DMAC Type.
        default: 0,
        0: Any - Don't care.
        1: Broadcast - Frame must be broadcast.
        2: Unicast - Frame must be unicast.
        3: Multicast - Frame must be multicast.
        4: mac address.
        range : 0 - 4 "
   ::= { gs2326plusACLACEEntry 19 }

gs2326plusACLACEDMAC OBJECT-TYPE
   SYNTAX      DisplayString
   MAX-ACCESS  read-write
   STATUS      current
   DESCRIPTION
       " Configure destination MAC address for this ACE.
         <mac-address>: A frame that hits this ACE matches this destination MAC address value.
         Any: Don't care.
         Broadcast: Frame must be broadcast.
         Unicast: Frame must be unicast.
         Multicast: Frame must be multicast. "
   ::= { gs2326plusACLACEEntry 20 }

gs2326plusACLACEArpOpcode OBJECT-TYPE
   SYNTAX      INTEGER { any(0), arp(1), rarp(2), other(3), noData(4) }
   MAX-ACCESS  read-write
   STATUS      current
   DESCRIPTION
       "Configure ARP opcode for this ACE.
        default: 0,
        0: Any - Don't care.
        1: arp.
        2: rarp.
        3: other.
        4: No data.
        range : 0 - 4 "
   ::= { gs2326plusACLACEEntry 21 }

gs2326plusACLACEArpFlagsRequestReply OBJECT-TYPE
   SYNTAX      INTEGER { reply(0), request(1), any(2), noData(3)}
   MAX-ACCESS  read-write
   STATUS      current
   DESCRIPTION
       "Specify the available ARP/RARP opcode (OP) flag for this ACE.
        default: 2,
        0: Frame must have ARP Reply or RARP Reply OP flag.
        1: Frame must have ARP Request or RARP Request OP flag set.
        2: Any - Don't care.
        3: No data.
        range : 0 - 3 "
   ::= { gs2326plusACLACEEntry 22 }

gs2326plusACLACEArpFlagsArpSmac OBJECT-TYPE
   SYNTAX      INTEGER { notEqualSMAC(0), equalSMAC(1), any(2), noData(3)}
   MAX-ACCESS  read-write
   STATUS      current
   DESCRIPTION
       "Specify whether frames can hit the action according to their sender hardware address field (SHA) settings.
        default: 2,
        0: ARP frames where SHA is not equal to the SMAC address.
        1: ARP frames where SHA is equal to the SMAC address.
        2: Any - Don't care.
        3: No data.
        range : 0 - 3 "
   ::= { gs2326plusACLACEEntry 23 }

gs2326plusACLACEArpFlagsRarpDmac OBJECT-TYPE
   SYNTAX      INTEGER { notEqualDMAC(0), equalDMAC(1), any(2), noData(3)}
   MAX-ACCESS  read-write
   STATUS      current
   DESCRIPTION
       "Specify whether frames can hit the action according to their target hardware address field (THA) settings.
        default: 2,
        0: RARP frames where THA is not equal to the DMAC address.
        1: RARP frames where THA is equal to the DMAC address.
        2: Any - Don't care.
        3: No data.
        range : 0 - 3 "
   ::= { gs2326plusACLACEEntry 24 }

gs2326plusACLACEArpFlagsLength OBJECT-TYPE
   SYNTAX      INTEGER(0..3)
   MAX-ACCESS  read-write
   STATUS      current
   DESCRIPTION
       "Specify whether frames can hit the action according to their ARP/RARP hardware address length (HLN) and
        protocol address length (PLN) settings.
        default: 2,
        0: ARP/RARP frames where the HLN is not equal to Ethernet(0x06) or the (PLN) is not equal to IPv4(0x04).
        1: ARP/RARP frames where the HLN is equal to Ethernet (0x06) and the (PLN) is equal to IPv4(0x04).
        2: Any - Don't care.
        3: No data.
        range : 0 - 3 "
   ::= { gs2326plusACLACEEntry 25 }

gs2326plusACLACEArpFlagsIp OBJECT-TYPE
   SYNTAX      INTEGER(0..3)
   MAX-ACCESS  read-write
   STATUS      current
   DESCRIPTION
       "Specify whether frames can hit the action according to their ARP/RARP hardware address space (HRD) settings.
        default: 2,
        0: ARP/RARP frames where the HLD is not equal to Ethernet(1).
        1: ARP/RARP frames where the HLD is equal to Ethernet(1).
        2: Any - Don't care.
        3: No data.
        range : 0 - 3 "
   ::= { gs2326plusACLACEEntry 26 }

gs2326plusACLACEArpFlagsEthernet OBJECT-TYPE
   SYNTAX      INTEGER(0..3)
   MAX-ACCESS  read-write
   STATUS      current
   DESCRIPTION
       "Specify whether frames can hit the action according to their ARP/RARP protocol address space (PRO) settings.
        default: 2,
        0: ARP/RARP frames where the PRO is not equal to IP\n(0x800).
        1: ARP/RARP frames where the PRO is equal to IP(0x800).
        2: Any - Don't care.
        3: No data.
        range : 0 - 3 "
   ::= { gs2326plusACLACEEntry 27 }

gs2326plusACLACESIPType OBJECT-TYPE
   SYNTAX      INTEGER { any(0), ip(1), noData(2) }
   MAX-ACCESS  read-write
   STATUS      current
   DESCRIPTION
       "Configure source IP address for this ACE.
        default: 0,
        0: Any - Don't care.
        1: IP Address.
        2: No data.
        range : 0 - 1"
   ::= { gs2326plusACLACEEntry 28 }

gs2326plusACLACESIPIPAddress OBJECT-TYPE
   SYNTAX      IpAddress
   MAX-ACCESS  read-write
   STATUS      current
   DESCRIPTION
       "A frame that hits this ACE matches this source IP address value."
   ::= { gs2326plusACLACEEntry 29 }

gs2326plusACLACESIPNetworkPrefix OBJECT-TYPE
   SYNTAX      Integer32(0..32)
   MAX-ACCESS  read-write
   STATUS      current
   DESCRIPTION
       "Network prefix.
        default: 32,
        0: No data.
        range : 1 - 32"
   ::= { gs2326plusACLACEEntry 30 }


gs2326plusACLACEDIPType OBJECT-TYPE
   SYNTAX      INTEGER { any(0), ip(1),noData(2) }
   MAX-ACCESS  read-write
   STATUS      current
   DESCRIPTION
       "Configure destination IP address for this ACE.
        default: 0,
        0: Any - Don't care.
        1: IP Address.
        2: No data.
        range : 0 - 1"
   ::= { gs2326plusACLACEEntry 32 }

gs2326plusACLACEDIPIPAddress OBJECT-TYPE
   SYNTAX      IpAddress
   MAX-ACCESS  read-write
   STATUS      current
   DESCRIPTION
       "A frame that hits this ACE matches this destination IP address value."
   ::= { gs2326plusACLACEEntry 33 }

gs2326plusACLACEDIPNetworkPrefix OBJECT-TYPE
   SYNTAX      Integer32(0..32)
   MAX-ACCESS  read-write
   STATUS      current
   DESCRIPTION
       "Network prefix.
        default: 32,
        0: No data.
        range : 1 - 32"
   ::= { gs2326plusACLACEEntry 34 }


gs2326plusACLACEIPProtocol OBJECT-TYPE
   SYNTAX      Integer32(0..257)
   MAX-ACCESS  read-write
   STATUS      current
   DESCRIPTION
       "Configure IP protocol for this ACE.
        default: 256,
        256: Any - Don't care.
        257: No data.
        range : 0 - 256"
   ::= { gs2326plusACLACEEntry 36 }

gs2326plusACLACEIPFlagsTTL OBJECT-TYPE
   SYNTAX      INTEGER (0..3)
   MAX-ACCESS  read-write
   STATUS      current
   DESCRIPTION
       "Configure IP Time-to-Live flags for this ACE.
        default: 2,
        0: IPv4 frames with a Time-to-Live field is equal to zero.
        1: IPv4 frames with a Time-to-Live field greater than zero.
        2: Any - Don't care.
        3: No data.
        range : 0 - 3 "
   ::= { gs2326plusACLACEEntry 37 }

gs2326plusACLACEIPFlagsOptions OBJECT-TYPE
   SYNTAX      INTEGER { unset(0), set(1), any(2), noData(3) }
   MAX-ACCESS  read-write
   STATUS      current
   DESCRIPTION
       "Configure IP options flag for this ACE.
        default: 2,
        0: IPv4 frames where the options flag is unset.
        1: IPv4 frames where the options flag is set.
        2: Any - Don't care.
        3: No data.
        range : 0 - 3 "
   ::= { gs2326plusACLACEEntry 38 }

gs2326plusACLACEIPFlagsFragment OBJECT-TYPE
   SYNTAX      INTEGER(0..3)
   MAX-ACCESS  read-write
   STATUS      current
   DESCRIPTION
       "Configure IP fragment offset flags for this ACE.
        default: 2,
        0: IPv4 frames where the MF bit is unset and the FRAG OFFSET field is equal zero.
        1: IPv4 frames where the MF bit is set or the FRAG OFFSET field is greater than zero.
        2: Any - Don't care.
        3: No data.
        range : 0 - 3 "
   ::= { gs2326plusACLACEEntry 39 }

gs2326plusACLACEICMPType OBJECT-TYPE
   SYNTAX      Integer32(0..257)
   MAX-ACCESS  read-write
   STATUS      current
   DESCRIPTION
       "Configure ICMP type for this ACE.
        default: 256,
        256: Any - Don't care.
        257: No data.
        range : 0 - 256"
   ::= { gs2326plusACLACEEntry 40 }

gs2326plusACLACEICMPCode OBJECT-TYPE
   SYNTAX      Integer32(0..257)
   MAX-ACCESS  read-write
   STATUS      current
   DESCRIPTION
       "Configure ICMP code for this ACE.
        default: 256,
        256: Any - Don't care.
        257: No data.
        range : 0 - 257"
   ::= { gs2326plusACLACEEntry 41 }

gs2326plusACLACESourcePortMin OBJECT-TYPE
   SYNTAX      Integer32(0..65536)
   MAX-ACCESS  read-write
   STATUS      current
   DESCRIPTION
       "Configure Source UDP/TCP port range for this ACE.
        default: 0,
        65536: No data.
        range : 0 - 65536"
   ::= { gs2326plusACLACEEntry 42 }

gs2326plusACLACESourcePortMax OBJECT-TYPE
   SYNTAX      Integer32(0..65536)
   MAX-ACCESS  read-write
   STATUS      current
   DESCRIPTION
       "Configure Source UDP/TCP port range for this ACE.
        default: 0,
        65536: No data.
        range : 0 - 65536"
   ::= { gs2326plusACLACEEntry 43 }

gs2326plusACLACEDestPortMin OBJECT-TYPE
   SYNTAX      Integer32(0..65536)
   MAX-ACCESS  read-write
   STATUS      current
   DESCRIPTION
       "Configure Destination UDP/TCP port range for this ACE.
        default: 0,
        65536: No data.
        range : 0 - 65535"
   ::= { gs2326plusACLACEEntry 44 }

gs2326plusACLACEDestPortMax OBJECT-TYPE
   SYNTAX      Integer32(0..65536)
   MAX-ACCESS  read-write
   STATUS      current
   DESCRIPTION
       "Configure Destination UDP/TCP port range for this ACE.
        default: 0,
        65536: No data.
        range : 0 - 65535"
   ::= { gs2326plusACLACEEntry 45 }

gs2326plusACLACETCPFlagsFin OBJECT-TYPE
   SYNTAX      INTEGER { unset(0), set(1), any(2), noData(3) }
   MAX-ACCESS  read-write
   STATUS      current
   DESCRIPTION
       "Configure TCP (FIN) flags for this ACE.
        default: 2,
        0: TCP frames where the FIN field is unset.
        1: TCP frames where the FIN field is set.
        2: Any - Don't care.
        3: No data.
        range : 0 - 3 "
   ::= { gs2326plusACLACEEntry 46 }

gs2326plusACLACETCPFlagsSyn OBJECT-TYPE
   SYNTAX      INTEGER { unset(0), set(1), any(2), noData(3) }
   MAX-ACCESS  read-write
   STATUS      current
   DESCRIPTION
       "Configure TCP (SYN) flags for this ACE.
        default: 2,
        0: TCP frames where the SYN field is unset.
        1: TCP frames where the SYN field is set.
        2: Any - Don't care.
        3: No data.
        range : 0 - 3 "
   ::= { gs2326plusACLACEEntry 47 }

gs2326plusACLACETCPFlagsRst OBJECT-TYPE
   SYNTAX      INTEGER { unset(0), set(1), any(2), noData(3) }
   MAX-ACCESS  read-write
   STATUS      current
   DESCRIPTION
       "Configure TCP (RST) flags for this ACE.
        default: 2,
        0: TCP frames where the RST field is unset.
        1: TCP frames where the RST field is set.
        2: Any - Don't care.
        3: No data.
        range : 0 - 3 "
   ::= { gs2326plusACLACEEntry 48 }

gs2326plusACLACETCPFlagsPsh OBJECT-TYPE
   SYNTAX      INTEGER { unset(0), set(1), any(2), noData(3) }
   MAX-ACCESS  read-write
   STATUS      current
   DESCRIPTION
       "Configure TCP (PSH) flags for this ACE.
        default: 2,
        0: TCP frames where the PSH field is unset.
        1: TCP frames where the PSH field is set.
        2: Any - Don't care.
        3: No data.
        range : 0 - 3 "
   ::= { gs2326plusACLACEEntry 49 }

gs2326plusACLACETCPFlagsAck OBJECT-TYPE
   SYNTAX      INTEGER { unset(0), set(1), any(2), noData(3) }
   MAX-ACCESS  read-write
   STATUS      current
   DESCRIPTION
       "Configure TCP (ACK) flags for this ACE.
        default: 2,
        0: TCP frames where the ACK field is unset.
        1: TCP frames where the ACK field is set.
        2: Any - Don't care.
        3: No data.
        range : 0 - 3 "
   ::= { gs2326plusACLACEEntry 50 }

gs2326plusACLACETCPFlagsUrg OBJECT-TYPE
   SYNTAX      INTEGER { unset(0), set(1), any(2), noData(3) }
   MAX-ACCESS  read-write
   STATUS      current
   DESCRIPTION
       "Configure TCP (URG) flags for this ACE.
        default: 2,
        0: TCP frames where the URG field is unset.
        1: TCP frames where the URG field is set.
        2: Any - Don't care.
        3: No data.
        range : 0 - 3 "
   ::= { gs2326plusACLACEEntry 51 }

gs2326plusACLACERowStatus OBJECT-TYPE
   SYNTAX      INTEGER { active(1), notInservice(2), destroy(4), undo(5) }
   MAX-ACCESS  read-write
   STATUS      current
   DESCRIPTION
       " 1: active
         2: notInservice
         4: destroy
         5: undo"
   ::= { gs2326plusACLACEEntry 66 }


gs2326plusACLACEClear OBJECT-TYPE
   SYNTAX       INTEGER { noAction(0), clear(1) }
   MAX-ACCESS   read-write
   STATUS       current
   DESCRIPTION
       "default: 0
        0 : No action
        1 : Clear all ACL counters."
   ::= { gs2326plusACLACE 3 }

gs2326plusACLACEMoveACEID OBJECT-TYPE
   SYNTAX       Integer32(0..256)
   MAX-ACCESS   read-write
   STATUS       current
   DESCRIPTION
       "Move ACE,
        default: 0
        ACE ID must be exist.
        range : 1 - 256."
   ::= { gs2326plusACLACE 4 }

gs2326plusACLACEMoveNextACEID OBJECT-TYPE
   SYNTAX       Integer32(0..256)
   MAX-ACCESS   read-write
   STATUS       current
   DESCRIPTION
       "Move ACE,
        default: 0
        If the next ACE ID is non zero, the ACE will be placed before this ACE in the list. If the next ACE ID is zero,
        the ACE will be placed last in the list.
        range : 0 - 256."
   ::= { gs2326plusACLACE 5 }

gs2326plusACLACEStatusTable OBJECT-TYPE
   SYNTAX      SEQUENCE OF Gs2326plusACLACEStatusEntry
   MAX-ACCESS  not-accessible
   STATUS      current
   DESCRIPTION
       " ACL ACE Status entry. "
   ::= { gs2326plusACLACE 6 }

gs2326plusACLACEStatusEntry OBJECT-TYPE
   SYNTAX      Gs2326plusACLACEStatusEntry
   MAX-ACCESS  not-accessible
   STATUS      current
   DESCRIPTION
       ""
   INDEX    { gs2326plusACLACEStatusIndex  }
   ::= { gs2326plusACLACEStatusTable 1 }

Gs2326plusACLACEStatusEntry ::= SEQUENCE {
   gs2326plusACLACEStatusIndex          Integer32,
   gs2326plusACLACEStatusUser           DisplayString,
   gs2326plusACLACEStatusID             Integer32,
   gs2326plusACLACEStatusIngressPort    DisplayString,
   gs2326plusACLACEStatusFrameType      DisplayString,
   gs2326plusACLACEStatusAction         DisplayString,
   gs2326plusACLACEStatusRateLimiter    DisplayString,
   gs2326plusACLACEStatusPortCopy       DisplayString,
   gs2326plusACLACEStatusMirror         DisplayString,
   gs2326plusACLACEStatusCPU            DisplayString,
   gs2326plusACLACEStatusCounter        Counter32,
   gs2326plusACLACEStatusConflict       DisplayString
}

gs2326plusACLACEStatusIndex OBJECT-TYPE
   SYNTAX      Integer32(1..256)
   MAX-ACCESS  not-accessible
   STATUS      current
   DESCRIPTION
       " "
   ::= { gs2326plusACLACEStatusEntry 1 }

gs2326plusACLACEStatusUser OBJECT-TYPE
   SYNTAX      DisplayString
   MAX-ACCESS  read-only
   STATUS      current
   DESCRIPTION
       " Indicates the ACL user.
         S : Static.
         IPMG : IP Management.
         IPSG : IP Source Guard.
         IPMC : IPMC.
         ARPI : Arp Inspection.
         UPnP : UPnP.
         DHCP : DHCP. "
   ::= { gs2326plusACLACEStatusEntry 2 }

gs2326plusACLACEStatusID OBJECT-TYPE
   SYNTAX      Integer32(1..256)
   MAX-ACCESS  read-only
   STATUS      current
   DESCRIPTION
       " ACE ID.
         range : 1 - 256. "
   ::= { gs2326plusACLACEStatusEntry 3 }

gs2326plusACLACEStatusIngressPort OBJECT-TYPE
   SYNTAX      DisplayString
   MAX-ACCESS  read-only
   STATUS      current
   DESCRIPTION
       " Indicates the ingress port of the ACE. Possible values are:
         All: The ACE will match all ingress port.
         Port: The ACE will match a specific ingress port. "
   ::= { gs2326plusACLACEStatusEntry 4 }

gs2326plusACLACEStatusFrameType OBJECT-TYPE
   SYNTAX      DisplayString
   MAX-ACCESS  read-only
   STATUS      current
   DESCRIPTION
       " Indicates the frame type of the ACE. "
   ::= { gs2326plusACLACEStatusEntry 5 }

gs2326plusACLACEStatusAction OBJECT-TYPE
   SYNTAX      DisplayString
   MAX-ACCESS  read-only
   STATUS      current
   DESCRIPTION
       " Indicates the forwarding action of the ACE. "
   ::= { gs2326plusACLACEStatusEntry 6 }

gs2326plusACLACEStatusRateLimiter OBJECT-TYPE
   SYNTAX      DisplayString
   MAX-ACCESS  read-only
   STATUS      current
   DESCRIPTION
       " Indicates the rate limiter number of the ACE. "
   ::= { gs2326plusACLACEStatusEntry 7 }

gs2326plusACLACEStatusPortCopy OBJECT-TYPE
   SYNTAX      DisplayString
   MAX-ACCESS  read-only
   STATUS      current
   DESCRIPTION
       " Indicates the port redirect operation of the ACE. Frames matching the ACE are redirected to the port number. "
   ::= { gs2326plusACLACEStatusEntry 8 }

gs2326plusACLACEStatusMirror OBJECT-TYPE
   SYNTAX      DisplayString
   MAX-ACCESS  read-only
   STATUS      current
   DESCRIPTION
       " Specify the mirror operation of this port. "
   ::= { gs2326plusACLACEStatusEntry 9 }

gs2326plusACLACEStatusCPU OBJECT-TYPE
   SYNTAX      DisplayString
   MAX-ACCESS  read-only
   STATUS      current
   DESCRIPTION
       " Forward packet that matched the specific ACE to CPU. "
   ::= { gs2326plusACLACEStatusEntry 10 }

gs2326plusACLACEStatusCounter OBJECT-TYPE
   SYNTAX      Counter32
   MAX-ACCESS  read-only
   STATUS      current
   DESCRIPTION
       " The counter indicates the number of times the ACE was hit by a frame. "
   ::= { gs2326plusACLACEStatusEntry 11 }

gs2326plusACLACEStatusConflict OBJECT-TYPE
   SYNTAX      DisplayString
   MAX-ACCESS  read-only
   STATUS      current
   DESCRIPTION
       " Indicates the hardware status of the specific ACE. The specific ACE is not applied to the hardware due to hardware limitations. "
   ::= { gs2326plusACLACEStatusEntry 12 }

gs2326plusLoopProtection                                                  OBJECT IDENTIFIER ::= { gs2326plusConfiguration 12 }

gs2326plusLoopProtectionConfig                                            OBJECT IDENTIFIER ::= { gs2326plusLoopProtection 1 }

gs2326plusLoopProtectionGlobalEnable OBJECT-TYPE
   SYNTAX      INTEGER { disable(0), enable(1) }
   MAX-ACCESS  read-write
   STATUS      current
   DESCRIPTION
       "Configure loop protection mode.
        0: disable,
        1: enable,
        default: disable. "
   ::= { gs2326plusLoopProtectionConfig 1 }

gs2326plusLoopProtectionTranmisstionTime OBJECT-TYPE
   SYNTAX      Integer32(1..10)
   MAX-ACCESS  read-write
   STATUS      current
   DESCRIPTION
       "Configure loop protection transmit interval.
        default: 5,
        range: 1-10. "
   ::= { gs2326plusLoopProtectionConfig 2 }

gs2326plusLoopProtectionShutdownTime OBJECT-TYPE
   SYNTAX      Integer32(0..604800)
   MAX-ACCESS  read-write
   STATUS      current
   DESCRIPTION
       "Configure loop protection shutdown time.
        default: 180,
        range: 0-604800. "
   ::= { gs2326plusLoopProtectionConfig 3 }

gs2326plusLoopProtectionConfigurationTable OBJECT-TYPE
   SYNTAX      SEQUENCE OF Gs2326plusLoopProtectionConfigurationEntry
   MAX-ACCESS  not-accessible
   STATUS      current
   DESCRIPTION
       " Show Loop Protection configurations. "
   ::= { gs2326plusLoopProtectionConfig 4 }

gs2326plusLoopProtectionConfigurationEntry OBJECT-TYPE
   SYNTAX      Gs2326plusLoopProtectionConfigurationEntry
   MAX-ACCESS  not-accessible
   STATUS      current
   DESCRIPTION
       ""
   INDEX    { gs2326plusLoopProtectionConfPort  }
   ::= { gs2326plusLoopProtectionConfigurationTable 1 }

Gs2326plusLoopProtectionConfigurationEntry ::= SEQUENCE {
   gs2326plusLoopProtectionConfPort	    Integer32,
   gs2326plusLoopProtectionConfEnable	INTEGER,
   gs2326plusLoopProtectionConfAction	INTEGER,
   gs2326plusLoopProtectionConfTxmode	INTEGER
}

gs2326plusLoopProtectionConfPort OBJECT-TYPE
   SYNTAX      Integer32(1..4095)
   MAX-ACCESS  not-accessible
   STATUS      current
   DESCRIPTION
       " port, range : 1 - port number. "
   ::= { gs2326plusLoopProtectionConfigurationEntry 1 }

gs2326plusLoopProtectionConfEnable OBJECT-TYPE
   SYNTAX      INTEGER { disable(0), enable(1) }
   MAX-ACCESS  read-write
   STATUS      current
   DESCRIPTION
       "Configure loop protection port mode.
        0: disable,
        1: enable,
        default: enable. "
   ::= { gs2326plusLoopProtectionConfigurationEntry 2 }

gs2326plusLoopProtectionConfAction OBJECT-TYPE
   SYNTAX      INTEGER { shutdown(0), shutdownLog(1), log(2) }
   MAX-ACCESS  read-write
   STATUS      current
   DESCRIPTION
       " Configure loop protection port action.
         0: Shutdown port,
         1: Shutdown port and Log,
         2: Log Only,
         default: Shutdown port. "
   ::= { gs2326plusLoopProtectionConfigurationEntry 3 }

gs2326plusLoopProtectionConfTxmode OBJECT-TYPE
   SYNTAX      INTEGER { disable(0), enable(1) }
   MAX-ACCESS  read-write
   STATUS      current
   DESCRIPTION
       "Configure loop protection port transmit mode.
        0: disable,
        1: enable,
        default: enable. "
   ::= { gs2326plusLoopProtectionConfigurationEntry 4 }

gs2326plusLoopProtectionStatusTable OBJECT-TYPE
   SYNTAX      SEQUENCE OF Gs2326plusLoopProtectionStatusEntry
   MAX-ACCESS  not-accessible
   STATUS      current
   DESCRIPTION
       " Show Loop Protection Status. "
   ::= { gs2326plusLoopProtection 2 }

gs2326plusLoopProtectionStatusEntry OBJECT-TYPE
   SYNTAX      Gs2326plusLoopProtectionStatusEntry
   MAX-ACCESS  not-accessible
   STATUS      current
   DESCRIPTION
       ""
   INDEX    { gs2326plusLoopProtectionStatusPort  }
   ::= { gs2326plusLoopProtectionStatusTable 1 }

Gs2326plusLoopProtectionStatusEntry ::= SEQUENCE {
   gs2326plusLoopProtectionStatusPort	       Integer32,
   gs2326plusLoopProtectionStatusAction	       DisplayString,
   gs2326plusLoopProtectionStatusTransmit	   DisplayString,
   gs2326plusLoopProtectionStatusLoops	       Integer32,
   gs2326plusLoopProtectionStatusStatus	       DisplayString,
   gs2326plusLoopProtectionStatusLoop	       DisplayString,
   gs2326plusLoopProtectionStatusTimeLastLoop  DisplayString
}

gs2326plusLoopProtectionStatusPort OBJECT-TYPE
   SYNTAX      Integer32(1..4095)
   MAX-ACCESS  not-accessible
   STATUS      current
   DESCRIPTION
       " port, range : 1 - port number. "
   ::= { gs2326plusLoopProtectionStatusEntry 1 }

gs2326plusLoopProtectionStatusAction OBJECT-TYPE
   SYNTAX      DisplayString
   MAX-ACCESS  read-only
   STATUS      current
   DESCRIPTION
       " The currently configured port action. "
   ::= { gs2326plusLoopProtectionStatusEntry 2 }

gs2326plusLoopProtectionStatusTransmit OBJECT-TYPE
   SYNTAX      DisplayString
   MAX-ACCESS  read-only
   STATUS      current
   DESCRIPTION
       " The currently configured port transmit mode. "
   ::= { gs2326plusLoopProtectionStatusEntry 3 }

gs2326plusLoopProtectionStatusLoops OBJECT-TYPE
   SYNTAX      Integer32(0..1000000)
   MAX-ACCESS  read-only
   STATUS      current
   DESCRIPTION
       " The number of loops detected on this port. "
   ::= { gs2326plusLoopProtectionStatusEntry 4 }

gs2326plusLoopProtectionStatusStatus OBJECT-TYPE
   SYNTAX      DisplayString
   MAX-ACCESS  read-only
   STATUS      current
   DESCRIPTION
       " The current loop protection status of the port. "
   ::= { gs2326plusLoopProtectionStatusEntry 5 }

gs2326plusLoopProtectionStatusLoop OBJECT-TYPE
   SYNTAX      DisplayString
   MAX-ACCESS  read-only
   STATUS      current
   DESCRIPTION
       " Whether a loop is currently detected on the port. "
   ::= { gs2326plusLoopProtectionStatusEntry 6 }

gs2326plusLoopProtectionStatusTimeLastLoop OBJECT-TYPE
   SYNTAX      DisplayString
   MAX-ACCESS  read-only
   STATUS      current
   DESCRIPTION
       " The time of the last loop event detected. "
   ::= { gs2326plusLoopProtectionStatusEntry 7 }

gs2326plusQos                                                             OBJECT IDENTIFIER ::= { gs2326plusConfiguration 14 }

gs2326plusQosPortClassification                                           OBJECT IDENTIFIER ::= { gs2326plusQos 1 }

gs2326plusQosPortClassificationTable OBJECT-TYPE
   SYNTAX      SEQUENCE OF Gs2326plusQosPortClassificationEntry
   MAX-ACCESS  not-accessible
   STATUS      current
   DESCRIPTION
       " QoS Ingress Port Classification . "
   ::= { gs2326plusQosPortClassification  1 }

gs2326plusQosPortClassificationEntry OBJECT-TYPE
   SYNTAX      Gs2326plusQosPortClassificationEntry
   MAX-ACCESS  not-accessible
   STATUS      current
   DESCRIPTION
       ""
   INDEX    { gs2326plusQosPortClassificationPort  }
   ::= { gs2326plusQosPortClassificationTable 1 }

Gs2326plusQosPortClassificationEntry ::= SEQUENCE {
   gs2326plusQosPortClassificationPort         Integer32,
   gs2326plusQosPortClassificationQoSclass     Integer32,
   gs2326plusQosPortClassificationDPlevel      Integer32,
   gs2326plusQosPortClassificationPCP          Integer32,
   gs2326plusQosPortClassificationDEI          INTEGER,
   gs2326plusQosPortClassificationTagClass     INTEGER,
   gs2326plusQosPortClassificationDSCPBased    INTEGER,
   gs2326plusQosPortClassificationAddressMode  INTEGER
}

gs2326plusQosPortClassificationPort OBJECT-TYPE
   SYNTAX      Integer32(1..4095)
   MAX-ACCESS  not-accessible
   STATUS      current
   DESCRIPTION
       " port, range : 1 - port number. "
   ::= { gs2326plusQosPortClassificationEntry 1 }

gs2326plusQosPortClassificationQoSclass OBJECT-TYPE
   SYNTAX      Integer32(0..7)
   MAX-ACCESS  read-write
   STATUS      current
   DESCRIPTION
      "Controls the default QoS class, i.e., the QoS class
      for frames not classified in any other way. There is
      a one to one mapping between QoS class, queue and priority.
      A QoS class of 0 (zero) has the lowest priority.
      Note: If the QoS class has been dynamically changed, then
      the actual QoS class is shown in parentheses after the
      configured QoS class.

      Configure the default QoS class.
        range: 0-7,
        default: 0. "
   ::= { gs2326plusQosPortClassificationEntry 2 }

gs2326plusQosPortClassificationDPlevel OBJECT-TYPE
   SYNTAX      Integer32(0|1)
   MAX-ACCESS  read-write
   STATUS      current
   DESCRIPTION
       " DP level for frames not classified in any other way.
         range: 0-1,
         default: 0. "
   ::= { gs2326plusQosPortClassificationEntry 3 }

gs2326plusQosPortClassificationPCP OBJECT-TYPE
   SYNTAX      Integer32(0..7)
   MAX-ACCESS  read-write
   STATUS      current
   DESCRIPTION
      " Priority Code Point. It is a 3-bit field storing the priority level for the 802.1Q frame.
        range: 0-7,
        default: 0. "
   ::= { gs2326plusQosPortClassificationEntry 4 }

gs2326plusQosPortClassificationDEI OBJECT-TYPE
   SYNTAX      INTEGER { disable(0), enable(1) }
   MAX-ACCESS  read-write
   STATUS      current
   DESCRIPTION
      " Drop Eligible Indicator. It is a 1-bit field in the VLAN.
        range 0-1,
        default: 0. "
   ::= { gs2326plusQosPortClassificationEntry 5 }

gs2326plusQosPortClassificationTagClass OBJECT-TYPE
   SYNTAX      INTEGER { disable(0), enable(1) }
   MAX-ACCESS  read-write
   STATUS      current
   DESCRIPTION
      " Configure the classification mode for tagged frames.
        0: Disable,
        1: Enable,
        default: Disable. "
   ::= { gs2326plusQosPortClassificationEntry 6 }

gs2326plusQosPortClassificationDSCPBased OBJECT-TYPE
   SYNTAX      INTEGER { disable(0), enable(1) }
   MAX-ACCESS  read-write
   STATUS      current
   DESCRIPTION
      " Click to Enable DSCP Based QoS Ingress Port Classification.
        0: disable,
        1: enable,
        default: disable. "
   ::= { gs2326plusQosPortClassificationEntry 7 }

gs2326plusQosPortClassificationAddressMode OBJECT-TYPE
   SYNTAX      INTEGER { source(0), destination(1) }
   MAX-ACCESS  read-write
   STATUS      current
   DESCRIPTION
      "The IP/MAC address mode specifying whether the QCL classification
       must be based on source (SMAC/SIP) or destination (DMAC/DIP)
       addresses on this port.
        0: source,
        1: destination,
        default: source. "
   ::= { gs2326plusQosPortClassificationEntry 8 }

gs2326plusQoSIngressPortTagClassificationTable OBJECT-TYPE
   SYNTAX      SEQUENCE OF Gs2326plusQoSIngressPortTagClassificationEntry
   MAX-ACCESS  not-accessible
   STATUS      current
   DESCRIPTION
       " Show QoS Ingress Port Tag Classification. "
   ::= { gs2326plusQosPortClassification 2 }

gs2326plusQoSIngressPortTagClassificationEntry OBJECT-TYPE
   SYNTAX      Gs2326plusQoSIngressPortTagClassificationEntry
   MAX-ACCESS  not-accessible
   STATUS      current
   DESCRIPTION
       ""
   INDEX    { gs2326plusQoSIngressPortTagClassificationPort, gs2326plusQoSIngressPortTagPCP, gs2326plusQoSIngressPortTagDEI  }
   ::= { gs2326plusQoSIngressPortTagClassificationTable 1 }

Gs2326plusQoSIngressPortTagClassificationEntry ::= SEQUENCE {
   gs2326plusQoSIngressPortTagClassificationPort	Integer32,
   gs2326plusQoSIngressPortTagPCP					INTEGER,
   gs2326plusQoSIngressPortTagDEI					INTEGER,
   gs2326plusQoSIngressPortTagQosClass				Integer32,
   gs2326plusQoSIngressPortTagDPLevel				Integer32
}

gs2326plusQoSIngressPortTagClassificationPort OBJECT-TYPE
   SYNTAX      Integer32(1..4095)
   MAX-ACCESS  not-accessible
   STATUS      current
   DESCRIPTION
       " port, range : 1 - port number. "
   ::= { gs2326plusQoSIngressPortTagClassificationEntry 1 }

gs2326plusQoSIngressPortTagPCP OBJECT-TYPE
   SYNTAX      INTEGER { pcp0(1), pcp1(2), pcp2(3), pcp3(4), pcp4(5), pcp5(6), pcp6(7), pcp7(8) }
   MAX-ACCESS  not-accessible
   STATUS      current
   DESCRIPTION
       " range: 1-8,
         PCP0:1, PCP1:2...  "
   ::= { gs2326plusQoSIngressPortTagClassificationEntry 2 }

gs2326plusQoSIngressPortTagDEI OBJECT-TYPE
   SYNTAX      INTEGER { dei0(1), dei1(2) }
   MAX-ACCESS  not-accessible
   STATUS      current
   DESCRIPTION
       " range: 1-2,
         DEI0:1, DEI1:2. "
   ::= { gs2326plusQoSIngressPortTagClassificationEntry 3 }

gs2326plusQoSIngressPortTagQosClass OBJECT-TYPE
   SYNTAX      Integer32 (0..7)
   MAX-ACCESS  read-write
   STATUS      current
   DESCRIPTION
       " range: 0-7.  "
   ::= { gs2326plusQoSIngressPortTagClassificationEntry 4 }

gs2326plusQoSIngressPortTagDPLevel OBJECT-TYPE
   SYNTAX      Integer32 (0|1)
   MAX-ACCESS  read-write
   STATUS      current
   DESCRIPTION
       " range: 0-1.  "
   ::= { gs2326plusQoSIngressPortTagClassificationEntry 5 }


gs2326plusQosPortPolicingTable OBJECT-TYPE
   SYNTAX      SEQUENCE OF Gs2326plusQosPortPolicingEntry
   MAX-ACCESS  not-accessible
   STATUS      current
   DESCRIPTION
       "  configure the Policer settings for all switch ports. "
   ::= { gs2326plusQos  2 }

gs2326plusQosPortPolicingEntry OBJECT-TYPE
   SYNTAX      Gs2326plusQosPortPolicingEntry
   MAX-ACCESS  not-accessible
   STATUS      current
   DESCRIPTION
       ""
   INDEX    { gs2326plusQosPortPolicingPort  }
   ::= { gs2326plusQosPortPolicingTable 1 }

Gs2326plusQosPortPolicingEntry ::= SEQUENCE {
   gs2326plusQosPortPolicingPort	        Integer32,
   gs2326plusQosPortPolicingMode           INTEGER,
   gs2326plusQosPortPolicingRate	        Integer32,
   gs2326plusQosPortPolicingUnit	        INTEGER,
   gs2326plusQosPortPolicingFlowControl	INTEGER
}

gs2326plusQosPortPolicingPort OBJECT-TYPE
   SYNTAX      Integer32 (1..4095)
   MAX-ACCESS  not-accessible
   STATUS      current
   DESCRIPTION
       " port, range : 1 - port number. "
   ::= { gs2326plusQosPortPolicingEntry 1 }

gs2326plusQosPortPolicingMode OBJECT-TYPE
   SYNTAX      INTEGER { disable(0), enable(1) }
   MAX-ACCESS  read-write
   STATUS      current
   DESCRIPTION
      " Controls whether the policer is enabled on this switch port.
        0: disable,
        1: enable,
        default: disable. "
   ::= { gs2326plusQosPortPolicingEntry 2 }

gs2326plusQosPortPolicingRate OBJECT-TYPE
   SYNTAX      Integer32(100..10000000)
   MAX-ACCESS  read-write
   STATUS      current
   DESCRIPTION
       " Controls the rate for the policer.
         range: 100-10000000(kbps/fps),
         default: 500(kbps). "
   ::= { gs2326plusQosPortPolicingEntry 3 }

gs2326plusQosPortPolicingUnit OBJECT-TYPE
   SYNTAX      INTEGER { kbps(0), fps(1) }
   MAX-ACCESS  read-write
   STATUS      current
   DESCRIPTION
       " Controls the unit of measure for the policer rate.
         0: kbps,
         1: fps,
         default: kbps. "
   ::= { gs2326plusQosPortPolicingEntry 4 }

gs2326plusQosPortPolicingFlowControl OBJECT-TYPE
   SYNTAX      INTEGER { disable(0), enable(1) }
   MAX-ACCESS  read-write
   STATUS      current
   DESCRIPTION
       " If flow control is enabled and the port is in flow control mode,
        then pause frames are sent instead of discarding frames.
         0: disable,
         1: enable,
         default: disable. "
   ::= { gs2326plusQosPortPolicingEntry 5 }

gs2326plusQosPortScheduler                                           OBJECT IDENTIFIER ::= { gs2326plusQos 3 }

gs2326plusQosPortSchedulerModeTable OBJECT-TYPE
   SYNTAX      SEQUENCE OF Gs2326plusQosPortSchedulerModeEntry
   MAX-ACCESS  not-accessible
   STATUS      current
   DESCRIPTION
       " configure the basic QoS Port Scheduler Mode settings for all switch ports. "
   ::= { gs2326plusQosPortScheduler  1 }

gs2326plusQosPortSchedulerModeEntry OBJECT-TYPE
   SYNTAX      Gs2326plusQosPortSchedulerModeEntry
   MAX-ACCESS  not-accessible
   STATUS      current
   DESCRIPTION
       ""
   INDEX    { gs2326plusQosSchedulerModePort  }
   ::= { gs2326plusQosPortSchedulerModeTable 1 }

Gs2326plusQosPortSchedulerModeEntry ::= SEQUENCE {
   gs2326plusQosSchedulerModePort	                Integer32,
   gs2326plusQosSchedulerMode                        INTEGER,
   gs2326plusQosSchedulerShaper	                    INTEGER,
   gs2326plusQosSchedulerShaperRate	                Integer32
}

gs2326plusQosSchedulerModePort OBJECT-TYPE
   SYNTAX      Integer32 (1..4095)
   MAX-ACCESS  not-accessible
   STATUS      current
   DESCRIPTION
       " port, range : 1 - port number. "
   ::= { gs2326plusQosPortSchedulerModeEntry 1 }

gs2326plusQosSchedulerMode OBJECT-TYPE
   SYNTAX      INTEGER { strictPriority(0), weighted(1) }
   MAX-ACCESS  read-write
   STATUS      current
   DESCRIPTION
       " Controls whether the scheduler mode is Strict Priority or Weighted
       on this switch port.
       0:Strict Priority
       1:Weighted
         default: Strict Priority. "
   ::= { gs2326plusQosPortSchedulerModeEntry 2 }

gs2326plusQosSchedulerShaper OBJECT-TYPE
   SYNTAX      INTEGER { disable(0), enable(1) }
   MAX-ACCESS  read-write
   STATUS      current
   DESCRIPTION
       " Controls whether the port shaper is enabled
         0: Disable
         1: Enable.
         default: disable. "
   ::= { gs2326plusQosPortSchedulerModeEntry 3 }

gs2326plusQosSchedulerShaperRate OBJECT-TYPE
   SYNTAX      Integer32(100..1000000)
   MAX-ACCESS  read-write
   STATUS      current
   DESCRIPTION
       " Controls the rate for the port shaper.
         range: 100-1000000
         default: 500 kbps. "
   ::= { gs2326plusQosPortSchedulerModeEntry 4 }

gs2326plusQosPortSchedulerTable OBJECT-TYPE
   SYNTAX      SEQUENCE OF Gs2326plusQosPortSchedulerEntry
   MAX-ACCESS  not-accessible
   STATUS      current
   DESCRIPTION
       " Show Qos Port Scheduler. "
   ::= { gs2326plusQosPortScheduler 2 }

gs2326plusQosPortSchedulerEntry OBJECT-TYPE
   SYNTAX      Gs2326plusQosPortSchedulerEntry
   MAX-ACCESS  not-accessible
   STATUS      current
   DESCRIPTION
       ""
   INDEX    { gs2326plusQosSchedulerPort, gs2326plusQosSchedulerPortQueue}
   ::= { gs2326plusQosPortSchedulerTable 1 }

Gs2326plusQosPortSchedulerEntry ::= SEQUENCE {
   gs2326plusQosSchedulerPort						Integer32,
   gs2326plusQosSchedulerPortQueue					INTEGER,
   gs2326plusQosSchedulerPortQueueShaper				INTEGER,
   gs2326plusQosSchedulerPortQueueShaperRate			Integer32,
   gs2326plusQosSchedulerPortQueueShaperExcess		INTEGER,
   gs2326plusQosSchedulerPortQueueSchedulerWeight	Integer32,
   gs2326plusQosSchedulerPortQueueSchedulerPercent	DisplayString
}

gs2326plusQosSchedulerPort OBJECT-TYPE
   SYNTAX      Integer32 (1..4095)
   MAX-ACCESS  not-accessible
   STATUS      current
   DESCRIPTION
       " port, range : 1 - port number. "
   ::= { gs2326plusQosPortSchedulerEntry 1 }

gs2326plusQosSchedulerPortQueue OBJECT-TYPE
   SYNTAX      INTEGER { q0(1), q1(2), q2(3), q3(4), q4(5), q5(6), q6(7), q7(8) }
   MAX-ACCESS  not-accessible
   STATUS      current
   DESCRIPTION
       " range: 1-8.
         Q0: 1, Q1: 2, ... "
   ::= { gs2326plusQosPortSchedulerEntry 2 }

gs2326plusQosSchedulerPortQueueShaper OBJECT-TYPE
   SYNTAX      INTEGER { disable(0), enable(1) }
   MAX-ACCESS  read-write
   STATUS      current
   DESCRIPTION
       " 0: disable  1:enable,
         default: 0.  "
   ::= { gs2326plusQosPortSchedulerEntry 3 }

gs2326plusQosSchedulerPortQueueShaperRate OBJECT-TYPE
   SYNTAX      Integer32(100..1000000)
   MAX-ACCESS  read-write
   STATUS      current
   DESCRIPTION
       " range: 100..1000000 kbps.  "
   ::= { gs2326plusQosPortSchedulerEntry 4 }

gs2326plusQosSchedulerPortQueueShaperExcess OBJECT-TYPE
   SYNTAX      INTEGER { disable(0), enable(1) }
   MAX-ACCESS  read-write
   STATUS      current
   DESCRIPTION
       " 0: disable  1:enable,
         default: 0.  "
   ::= { gs2326plusQosPortSchedulerEntry 5 }

gs2326plusQosSchedulerPortQueueSchedulerWeight OBJECT-TYPE
   SYNTAX      Integer32(0..100)
   MAX-ACCESS  read-write
   STATUS      current
   DESCRIPTION
       " range: 1-100,
         default: 17.
         Only use in Q0 - Q5.  Q6 & Q7 show 0 "
   ::= { gs2326plusQosPortSchedulerEntry 6 }

gs2326plusQosSchedulerPortQueueSchedulerPercent OBJECT-TYPE
   SYNTAX      DisplayString
   MAX-ACCESS  read-only
   STATUS      current
   DESCRIPTION
       " Only use in Q0 - Q5. Q6 & Q7 show empty "
   ::= { gs2326plusQosPortSchedulerEntry 7 }

gs2326plusQosPortEgressTagRemarking                                           OBJECT IDENTIFIER ::= { gs2326plusQos 4 }

gs2326plusQosPortEgressTagRemarkingTable OBJECT-TYPE
   SYNTAX      SEQUENCE OF Gs2326plusQosPortEgressTagRemarkingEntry
   MAX-ACCESS  not-accessible
   STATUS      current
   DESCRIPTION
       " configure the basic QoS Port Egress Tag Remark Configuration settings for all switch ports. "
   ::= { gs2326plusQosPortEgressTagRemarking  1 }

gs2326plusQosPortEgressTagRemarkingEntry OBJECT-TYPE
   SYNTAX      Gs2326plusQosPortEgressTagRemarkingEntry
   MAX-ACCESS  not-accessible
   STATUS      current
   DESCRIPTION
       ""
   INDEX    { gs2326plusQosEgressTagRemarkingPort  }
   ::= { gs2326plusQosPortEgressTagRemarkingTable 1 }

Gs2326plusQosPortEgressTagRemarkingEntry ::= SEQUENCE {
   gs2326plusQosEgressTagRemarkingPort	                Integer32,
   gs2326plusQosEgressTagRemarkingMode	                INTEGER
}

gs2326plusQosEgressTagRemarkingPort OBJECT-TYPE
   SYNTAX      Integer32 (1..4095)
   MAX-ACCESS  not-accessible
   STATUS      current
   DESCRIPTION
       " port, range : 1 - port number. "
   ::= { gs2326plusQosPortEgressTagRemarkingEntry 1 }

gs2326plusQosEgressTagRemarkingMode OBJECT-TYPE
   SYNTAX      INTEGER { classified(0), default(1), mapped(2) }
   MAX-ACCESS  read-write
   STATUS      current
   DESCRIPTION
       " the tag remarking mode for this port.
       0:Classified, Use classified PCP/DEI values.
       1:Default, Use default PCP/DEI values.
       2:Mapped, Use mapped versions of QoS class and DP level."
   ::= { gs2326plusQosPortEgressTagRemarkingEntry 2 }


gs2326plusQosPortEgressTagRemarkingDefTable OBJECT-TYPE
   SYNTAX      SEQUENCE OF Gs2326plusQosPortEgressTagRemarkingDefEntry
   MAX-ACCESS  not-accessible
   STATUS      current
   DESCRIPTION
       " configure the basic QoS Port Egress Tag Remark Configuration settings for all switch ports. "
   ::= { gs2326plusQosPortEgressTagRemarking  2 }

gs2326plusQosPortEgressTagRemarkingDefEntry OBJECT-TYPE
   SYNTAX      Gs2326plusQosPortEgressTagRemarkingDefEntry
   MAX-ACCESS  not-accessible
   STATUS      current
   DESCRIPTION
       ""
   INDEX    { gs2326plusQosEgressTagRemarkingDefPort  }
   ::= { gs2326plusQosPortEgressTagRemarkingDefTable 1 }

Gs2326plusQosPortEgressTagRemarkingDefEntry ::= SEQUENCE {
   gs2326plusQosEgressTagRemarkingDefPort	            Integer32,
   gs2326plusQosEgressTagRemarkingDefPCP	                Integer32,
   gs2326plusQosEgressTagRemarkingDefDEI	                INTEGER
}

gs2326plusQosEgressTagRemarkingDefPort OBJECT-TYPE
   SYNTAX      Integer32(1..4095)
   MAX-ACCESS  not-accessible
   STATUS      current
   DESCRIPTION
       " port, range : 1 - port number. "
   ::= { gs2326plusQosPortEgressTagRemarkingDefEntry 1 }

gs2326plusQosEgressTagRemarkingDefPCP OBJECT-TYPE
   SYNTAX      Integer32(0..7)
   MAX-ACCESS  read-write
   STATUS      current
   DESCRIPTION
       " Controls the default PCP
       Range : 0-7"
   ::= { gs2326plusQosPortEgressTagRemarkingDefEntry 2 }

gs2326plusQosEgressTagRemarkingDefDEI OBJECT-TYPE
   SYNTAX      INTEGER { disable(0), enable(1) }
   MAX-ACCESS  read-write
   STATUS      current
   DESCRIPTION
       " controls the DEI
       Range 0-1"
   ::= { gs2326plusQosPortEgressTagRemarkingDefEntry 3 }

gs2326plusQosPortEgressTagRemarkingMapTable OBJECT-TYPE
   SYNTAX      SEQUENCE OF Gs2326plusQosPortEgressTagRemarkingMapEntry
   MAX-ACCESS  not-accessible
   STATUS      current
   DESCRIPTION
       " Show Qos Port Egress Tag Remarking Map. "
   ::= { gs2326plusQosPortEgressTagRemarking 4 }

gs2326plusQosPortEgressTagRemarkingMapEntry OBJECT-TYPE
   SYNTAX      Gs2326plusQosPortEgressTagRemarkingMapEntry
   MAX-ACCESS  not-accessible
   STATUS      current
   DESCRIPTION
       ""
   INDEX    { gs2326plusQosPortEgressTagRemarkingMapPort, gs2326plusQosTagRemarkingQoSClass, gs2326plusQosTagRemarkingDPLevel  }
   ::= { gs2326plusQosPortEgressTagRemarkingMapTable 1 }

Gs2326plusQosPortEgressTagRemarkingMapEntry ::= SEQUENCE {
   gs2326plusQosPortEgressTagRemarkingMapPort	Integer32,
   gs2326plusQosTagRemarkingQoSClass			INTEGER,
   gs2326plusQosTagRemarkingDPLevel				INTEGER,
   gs2326plusQosTagRemarkingPCP					Integer32,
   gs2326plusQosTagRemarkingDEI					INTEGER
}

gs2326plusQosPortEgressTagRemarkingMapPort OBJECT-TYPE
   SYNTAX      Integer32 (1..4095)
   MAX-ACCESS  not-accessible
   STATUS      current
   DESCRIPTION
       " port, range : 1 - port number. "
   ::= { gs2326plusQosPortEgressTagRemarkingMapEntry 1 }

gs2326plusQosTagRemarkingQoSClass OBJECT-TYPE
   SYNTAX      INTEGER {
                        class0(1),
                        class1(2),
                        class2(3),
                        class3(4),
                        class4(5),
                        class5(6),
                        class6(7),
                        class7(8)
                        }
   MAX-ACCESS  not-accessible
   STATUS      current
   DESCRIPTION
       " range: 1-8,
         QoS Class0: 1, QoS Class1: 2...  "
   ::= { gs2326plusQosPortEgressTagRemarkingMapEntry 2 }

gs2326plusQosTagRemarkingDPLevel OBJECT-TYPE
   SYNTAX      INTEGER { level0(1), level1(2) }
   MAX-ACCESS  not-accessible
   STATUS      current
   DESCRIPTION
       " range: 1-2,
         DP Level0: 1, DP Level1: 2. "
   ::= { gs2326plusQosPortEgressTagRemarkingMapEntry 3 }

gs2326plusQosTagRemarkingPCP OBJECT-TYPE
   SYNTAX      Integer32 (0..7)
   MAX-ACCESS  read-write
   STATUS      current
   DESCRIPTION
       " range: 0-7.  "
   ::= { gs2326plusQosPortEgressTagRemarkingMapEntry 4 }

gs2326plusQosTagRemarkingDEI OBJECT-TYPE
   SYNTAX      INTEGER (0|1)
   MAX-ACCESS  read-write
   STATUS      current
   DESCRIPTION
       " range: 0-1.  "
   ::= { gs2326plusQosPortEgressTagRemarkingMapEntry 5 }


gs2326plusQosPortDSCPTable OBJECT-TYPE
   SYNTAX      SEQUENCE OF Gs2326plusQosPortDSCPEntry
   MAX-ACCESS  not-accessible
   STATUS      current
   DESCRIPTION
       " configure the basic QoS Port DSCP Configuration settings for all switch ports. "
   ::= { gs2326plusQos  5 }

gs2326plusQosPortDSCPEntry OBJECT-TYPE
   SYNTAX      Gs2326plusQosPortDSCPEntry
   MAX-ACCESS  not-accessible
   STATUS      current
   DESCRIPTION
       ""
   INDEX    { gs2326plusQosPortDSCPPort  }
   ::= { gs2326plusQosPortDSCPTable 1 }

Gs2326plusQosPortDSCPEntry ::= SEQUENCE {
   gs2326plusQosPortDSCPPort	                Integer32,
   gs2326plusQosPortDSCPIngressTranslate       INTEGER,
   gs2326plusQosPortDSCPIngressClassify	    INTEGER,
   gs2326plusQosPortDSCPEgressRewrite	        INTEGER
}

gs2326plusQosPortDSCPPort OBJECT-TYPE
   SYNTAX      Integer32 (1..4095)
   MAX-ACCESS  not-accessible
   STATUS      current
   DESCRIPTION
       " port, range : 1 - port number. "
   ::= { gs2326plusQosPortDSCPEntry 1 }

gs2326plusQosPortDSCPIngressTranslate OBJECT-TYPE
   SYNTAX      INTEGER { disable(0), enable(1) }
   MAX-ACCESS  read-write
   STATUS      current
   DESCRIPTION
      " Configure DSCP ingress translation mode.
        0: disable,
        1: enable,
        default: disable. "
   ::= { gs2326plusQosPortDSCPEntry 2 }

gs2326plusQosPortDSCPIngressClassify OBJECT-TYPE
   SYNTAX      INTEGER(0..3)
   MAX-ACCESS  read-write
   STATUS      current
   DESCRIPTION
       " Classification for a port have 4 different values.
         range: 0-3,
         0: disable,No Ingress DSCP Classification.
         1: DSCP=0,Classify if incoming (or translated if enabled) DSCP is 0.
         2: Selected,Classify only selected DSCP for which classification is
         enabled as specified in DSCP Translation window for the specific DSCP.
         3: All,Classify all DSCP.
         default: disable. "
   ::= { gs2326plusQosPortDSCPEntry 3 }

gs2326plusQosPortDSCPEgressRewrite OBJECT-TYPE
   SYNTAX      INTEGER(0..3)
   MAX-ACCESS  read-write
   STATUS      current
   DESCRIPTION
       " Configure the port egress rewriting mode.
         range: 0-2
         0: Disable,No Egress rewrite.
         1: Enable, Rewrite enabled without remapping.
         2: Remap DP Unaware , DSCP from analyzer is remapped and frame is
         remarked with remapped DSCP value. The remapped DSCP value is always
         taken from the DSCP Translation->Egress Remap DP0 table.
         3: Remap DP Aware: DSCP from analyzer is remapped and frame is remarked
          with remapped DSCP value. Depending on the DP level of the frame, the
          remapped DSCP value is either taken from the DSCP Translation->Egress
          Remap DP0 table or from the DSCP Translation->Egress Remap DP1 table.
         default: disable. "
   ::= { gs2326plusQosPortDSCPEntry 4 }


gs2326plusQosDSCPTable OBJECT-TYPE
   SYNTAX      SEQUENCE OF Gs2326plusQosDSCPEntry
   MAX-ACCESS  not-accessible
   STATUS      current
   DESCRIPTION
       " configure the basic QoS DSCP based QoS Ingress Classification settings for all switches. "
   ::= { gs2326plusQos  6 }

gs2326plusQosDSCPEntry OBJECT-TYPE
   SYNTAX      Gs2326plusQosDSCPEntry
   MAX-ACCESS  not-accessible
   STATUS      current
   DESCRIPTION
       ""
   INDEX    { gs2326plusQosDSCPList  }
   ::= { gs2326plusQosDSCPTable 1 }

Gs2326plusQosDSCPEntry ::= SEQUENCE {
   gs2326plusQosDSCPList       Integer32,
   gs2326plusQosDSCP           DisplayString,
   gs2326plusQosDSCPTrust      INTEGER,
   gs2326plusQosDSCPQosClass	  Integer32,
   gs2326plusQosDSCPDPL	      INTEGER
}

gs2326plusQosDSCPList OBJECT-TYPE
   SYNTAX      Integer32(1..64)
   MAX-ACCESS  not-accessible
   STATUS      current
   DESCRIPTION
      " DSCP mapping table index(1-64). "
   ::= { gs2326plusQosDSCPEntry 1 }

gs2326plusQosDSCP OBJECT-TYPE
   SYNTAX      DisplayString
   MAX-ACCESS  read-only
   STATUS      current
   DESCRIPTION
      "Maximum number of supported DSCP values are 64."
   ::= { gs2326plusQosDSCPEntry 2 }

gs2326plusQosDSCPTrust OBJECT-TYPE
   SYNTAX      INTEGER { disable(0), enable(1) }
   MAX-ACCESS  read-write
   STATUS      current
   DESCRIPTION
      " Controls whether a specific DSCP value is trusted. Only frames with
      trusted DSCP values are mapped to a specific QoS class and Drop Precedence
       Level. Frames with untrusted DSCP values are treated as a non-IP frame.
        0: disable,
        1: enable,
        default: disable. "
   ::= { gs2326plusQosDSCPEntry 3 }

gs2326plusQosDSCPQosClass OBJECT-TYPE
   SYNTAX      Integer32(0..7)
   MAX-ACCESS  read-write
   STATUS      current
   DESCRIPTION
      " QoS class.
        range: 0-7,
        default: 0. "
   ::= { gs2326plusQosDSCPEntry 4 }

gs2326plusQosDSCPDPL OBJECT-TYPE
   SYNTAX      INTEGER(0|1)
   MAX-ACCESS  read-write
   STATUS      current
   DESCRIPTION
      " Drop Precedence Level.
        range: 0-1,
        default: disable. "
   ::= { gs2326plusQosDSCPEntry 5 }

gs2326plusQosDSCPTranslationTable OBJECT-TYPE
   SYNTAX      SEQUENCE OF Gs2326plusQosDSCPTranslationEntry
   MAX-ACCESS  not-accessible
   STATUS      current
   DESCRIPTION
       "  configure the basic QoS DSCP Translation settings for all switches. "
   ::= { gs2326plusQos  7 }

gs2326plusQosDSCPTranslationEntry OBJECT-TYPE
   SYNTAX      Gs2326plusQosDSCPTranslationEntry
   MAX-ACCESS  not-accessible
   STATUS      current
   DESCRIPTION
       ""
   INDEX    { gs2326plusQosDSCPTranslationList  }
   ::= { gs2326plusQosDSCPTranslationTable 1 }

Gs2326plusQosDSCPTranslationEntry ::= SEQUENCE {
   gs2326plusQosDSCPTranslationList                 Integer32,
   gs2326plusQosDSCPTranslationDSCPBasedId          DisplayString,
   gs2326plusQosDSCPTranslationIngressTranslate     Integer32,
   gs2326plusQosDSCPTranslationIngressClassify      INTEGER,
   gs2326plusQosDSCPTranslationEgressRemapDP0       Integer32,
   gs2326plusQosDSCPTranslationEgressRemapDP1       Integer32
}

gs2326plusQosDSCPTranslationList OBJECT-TYPE
   SYNTAX      Integer32(1..64)
   MAX-ACCESS  not-accessible
   STATUS      current
   DESCRIPTION
      " DSCP translation table index(1-64). "
   ::= { gs2326plusQosDSCPTranslationEntry 1 }

gs2326plusQosDSCPTranslationDSCPBasedId OBJECT-TYPE
   SYNTAX      DisplayString
   MAX-ACCESS  read-write
   STATUS      current
   DESCRIPTION
      " Configure global ingress DSCP translation table. "
   ::= { gs2326plusQosDSCPTranslationEntry 2 }

gs2326plusQosDSCPTranslationIngressTranslate OBJECT-TYPE
   SYNTAX      Integer32(0..63)
   MAX-ACCESS  read-write
   STATUS      current
   DESCRIPTION
      " DSCP at Ingress side can be translated to any of DSCP values.
        range: 0-63,
        default: 0. "
   ::= { gs2326plusQosDSCPTranslationEntry 3 }

gs2326plusQosDSCPTranslationIngressClassify OBJECT-TYPE
   SYNTAX      INTEGER { disable(0), enable(1) }
   MAX-ACCESS  read-write
   STATUS      current
   DESCRIPTION
      " Configure DSCP ingress classification.
        0: disable,
        1: enable,
        default: disable. "
   ::= { gs2326plusQosDSCPTranslationEntry 4 }

gs2326plusQosDSCPTranslationEgressRemapDP0 OBJECT-TYPE
   SYNTAX      Integer32(0..63)
   MAX-ACCESS  read-write
   STATUS      current
   DESCRIPTION
      "Controls the remapping for frames with DP level 0.
      Select the DSCP value from select menu to which you want to remap.
        range: 0-63,
        default: 0. "
   ::= { gs2326plusQosDSCPTranslationEntry 5 }

gs2326plusQosDSCPTranslationEgressRemapDP1 OBJECT-TYPE
   SYNTAX      Integer32(0..63)
   MAX-ACCESS  read-write
   STATUS      current
   DESCRIPTION
      "Controls the remapping for frames with DP level 1.
      Select the DSCP value from select menu to which you want to remap.
        range: 0-63,
        default: 0. "
   ::= { gs2326plusQosDSCPTranslationEntry 6 }


gs2326plusQosDSCPClassificationTable OBJECT-TYPE
   SYNTAX      SEQUENCE OF Gs2326plusQosDSCPClassificationEntry
   MAX-ACCESS  not-accessible
   STATUS      current
   DESCRIPTION
       "   configure the mapping of QoS class  to DSCP value. "
   ::= { gs2326plusQos  8 }

gs2326plusQosDSCPClassificationEntry OBJECT-TYPE
   SYNTAX      Gs2326plusQosDSCPClassificationEntry
   MAX-ACCESS  not-accessible
   STATUS      current
   DESCRIPTION
       ""
   INDEX    { gs2326plusQosDSCPClassificationQoSClass, gs2326plusQosDSCPClassificationDPL }
   ::= { gs2326plusQosDSCPClassificationTable 1 }

Gs2326plusQosDSCPClassificationEntry ::= SEQUENCE {
   gs2326plusQosDSCPClassificationQoSClass		INTEGER,
   gs2326plusQosDSCPClassificationDPL			INTEGER,
   gs2326plusQosDSCPClassificationDSCP			Integer32
}

gs2326plusQosDSCPClassificationQoSClass OBJECT-TYPE
   SYNTAX      INTEGER {
                        class0(1),
                        class1(2),
                        class2(3),
                        class3(4),
                        class4(5),
                        class5(6),
                        class6(7),
                        class7(8)
                        }
   MAX-ACCESS  not-accessible
   STATUS      current
   DESCRIPTION
      " Actual QoS class. Index 1~8 mean Qos Class 0~7."
   ::= { gs2326plusQosDSCPClassificationEntry 1 }

gs2326plusQosDSCPClassificationDPL OBJECT-TYPE
   SYNTAX      INTEGER(1|2)
   MAX-ACCESS  not-accessible
   STATUS      current
   DESCRIPTION
      " DPL. Index 1~2 mean DPL 0~1."
   ::= { gs2326plusQosDSCPClassificationEntry 2 }

gs2326plusQosDSCPClassificationDSCP OBJECT-TYPE
   SYNTAX      Integer32(0..63)
   MAX-ACCESS  read-write
   STATUS      current
   DESCRIPTION
      " Select the classified DSCP value.
        range: 0-63,
        default: 0. "
   ::= { gs2326plusQosDSCPClassificationEntry 3 }

gs2326plusQosControlList                                         OBJECT IDENTIFIER ::= { gs2326plusQos 9 }

gs2326plusQosQceCreate OBJECT-TYPE
   SYNTAX       INTEGER { none(0), create(1) }
   MAX-ACCESS   read-write
   STATUS       current
   DESCRIPTION
       "default: 0
        0 : None  (read only)
        1 : Create an Qos entry"
   ::= { gs2326plusQosControlList 1 }

gs2326plusQosQceTable OBJECT-TYPE
   SYNTAX      SEQUENCE OF Gs2326plusQosQceEntry
   MAX-ACCESS  not-accessible
   STATUS      current
   DESCRIPTION
       " Create Qos QCE entry. "
   ::= { gs2326plusQosControlList 2 }

gs2326plusQosQceEntry OBJECT-TYPE
   SYNTAX      Gs2326plusQosQceEntry
   MAX-ACCESS  not-accessible
   STATUS      current
   DESCRIPTION
       ""
   INDEX    { gs2326plusQosQceIndex  }
   ::= { gs2326plusQosQceTable 1 }

Gs2326plusQosQceEntry ::= SEQUENCE {
   gs2326plusQosQceIndex                Integer32,
   gs2326plusQosQceID                   Integer32,
   gs2326plusQosQceNextID               Integer32,
   gs2326plusQosQcePortMembers          DisplayString,

   gs2326plusQosQceTag                  DisplayString,
   gs2326plusQosQceVID                  DisplayString,
   gs2326plusQosPCP                     DisplayString,
   gs2326plusQosDEI                     DisplayString,
   gs2326plusQosSMAC                    DisplayString,
   gs2326plusQosDMACType                DisplayString,
   gs2326plusQosFrameType               INTEGER,

   gs2326plusQosMacEtherType            DisplayString,

   gs2326plusQosLLCSSAPAddr             DisplayString,
   gs2326plusQosLLCDSAPAddr             DisplayString,
   gs2326plusQosLLCControl              DisplayString,

   gs2326plusQosSNAPPID                 DisplayString,

   gs2326plusQosIpv4Protocol            DisplayString,
   gs2326plusQosIpv4ProtocolValue       Integer32,
   gs2326plusQosIpv4ProtocolUDPSport    DisplayString,
   gs2326plusQosIpv4ProtocolUDPDport    DisplayString,
   gs2326plusQosIpv4ProtocolTCPSport    DisplayString,
   gs2326plusQosIpv4ProtocolTCPDport    DisplayString,
   gs2326plusQosIpv4Ip                  DisplayString,
   gs2326plusQosIpv4Mask                DisplayString,
   gs2326plusQosIpv4IPFragment          INTEGER,
   gs2326plusQosIpv4DSCP                DisplayString,


   gs2326plusQosIpv6Protocol            DisplayString,
   gs2326plusQosIpv6ProtocolValue       Integer32,
   gs2326plusQosIpv6ProtocolUDPSport    DisplayString,
   gs2326plusQosIpv6ProtocolUDPDport    DisplayString,
   gs2326plusQosIpv6ProtocolTCPSport    DisplayString,
   gs2326plusQosIpv6ProtocolTCPDport    DisplayString,
   gs2326plusQosIpv6Ip                  DisplayString,
   gs2326plusQosIpv6Mask                DisplayString,
   gs2326plusQosIpv6DSCP                DisplayString,

   gs2326plusQosActionClass             Integer32,
   gs2326plusQosActionDPL               INTEGER,
   gs2326plusQosActionDSCP              Integer32,
   gs2326plusQosQceRowStatus            INTEGER
}

gs2326plusQosQceIndex OBJECT-TYPE
   SYNTAX      Integer32(1..256)
   MAX-ACCESS  not-accessible
   STATUS      current
   DESCRIPTION
       " "
   ::= { gs2326plusQosQceEntry 1 }

gs2326plusQosQceID OBJECT-TYPE
   SYNTAX      Integer32(1..256)
   MAX-ACCESS  read-write
   STATUS      current
   DESCRIPTION
       " If the QCE ID is specified and an entry with this QCE ID
         already exists, the QCE will be modified. Otherwise, a
         new QCE will be added.
         range : 1 - 256. "
   ::= { gs2326plusQosQceEntry 2 }

gs2326plusQosQceNextID OBJECT-TYPE
   SYNTAX      Integer32(1..256)
   MAX-ACCESS  read-write
   STATUS      current
   DESCRIPTION
       " If the next QCE ID is non zero, the QCE will be placed
         before this QCE in the list. If the next QCE ID is zero,
         the QCE will be placed last in the list.
         range : 1 - 256. "
   ::= { gs2326plusQosQceEntry 3 }

gs2326plusQosQcePortMembers OBJECT-TYPE
   SYNTAX      DisplayString
   MAX-ACCESS  read-write
   STATUS      current
   DESCRIPTION
       " Indicates the ingress port of the QCE. Possible values are:
         All: The QCE will match all ingress port.
         Port: The QCE will match a specific ingress port.Format: 1,3-6."
   ::= { gs2326plusQosQceEntry 4 }

gs2326plusQosQceTag OBJECT-TYPE
   SYNTAX      DisplayString
   MAX-ACCESS  read-write
   STATUS      current
   DESCRIPTION
       " Value of Tag field can be 'Any', 'Untag' or 'Tag'. "
   ::= { gs2326plusQosQceEntry 5 }

gs2326plusQosQceVID OBJECT-TYPE
   SYNTAX      DisplayString
   MAX-ACCESS  read-write
   STATUS      current
   DESCRIPTION
       " Valid value of VLAN ID can be any value in 'Specific 1~4094' or 'range 1-4094' or 'Any'. "
   ::= { gs2326plusQosQceEntry 6 }

gs2326plusQosPCP OBJECT-TYPE
   SYNTAX      DisplayString
   MAX-ACCESS  read-write
   STATUS      current
   DESCRIPTION
       " Priority Code Point: Valid value PCP are specific(0, 1, 2, 3, 4, 5, 6, 7)
         or range(0-1, 2-3, 4-5, 6-7, 0-3, 4-7) or 'Any'. "
   ::= { gs2326plusQosQceEntry 7 }

gs2326plusQosDEI OBJECT-TYPE
   SYNTAX      DisplayString
   MAX-ACCESS  read-write
   STATUS      current
   DESCRIPTION
       " Drop Eligible Indicator: Valid value of DEI can be any of values between 0, 1 or 'Any'. "
   ::= { gs2326plusQosQceEntry 8 }

gs2326plusQosSMAC  OBJECT-TYPE
   SYNTAX      DisplayString
   MAX-ACCESS  read-write
   STATUS      current
   DESCRIPTION
       "  Source MAC address: 24 MS bits OUI(00-00-00 ~ FF-FF-FF) or 'Any'. "
   ::= { gs2326plusQosQceEntry 9 }

gs2326plusQosDMACType OBJECT-TYPE
   SYNTAX      DisplayString
   MAX-ACCESS  read-write
   STATUS      current
   DESCRIPTION
       " Destination MAC type: possible values are 'UC'(unicast), 'MC'(multicast), 'BC'(broadcast) or 'Any'. "
   ::= { gs2326plusQosQceEntry 10 }

gs2326plusQosFrameType OBJECT-TYPE
   SYNTAX      INTEGER {
                        any(1),
                        ethernet(2),
                        llc(3),
                        snap(4),
                        ipv4(5),
                        ipv6(6)
                        }
   MAX-ACCESS  read-write
   STATUS      current
   DESCRIPTION
       " Frame Type can have any of the following values:
         1: Any,
         2: Ethernet,
         3: LLC,
         4: SNAP,
         5: IPv4,
         6: IPv6. "
   ::= { gs2326plusQosQceEntry 11 }

gs2326plusQosMacEtherType OBJECT-TYPE
   SYNTAX      DisplayString
   MAX-ACCESS  read-write
   STATUS      current
   DESCRIPTION
       " Valid ethernet type can have a value within 0x600-0xFFFF or 'Any' ,
         but excluding 0x800(IPv4) and 0x86DD(IPv6),
         range: 0000-FFFF,
         default: Any."
   ::= { gs2326plusQosQceEntry 12 }

gs2326plusQosLLCSSAPAddr OBJECT-TYPE
   SYNTAX      DisplayString
   MAX-ACCESS  read-write
   STATUS      current
   DESCRIPTION
       " Valid SSAP(Source Service Access Point) can vary from 0x00 to 0xFF or 'Any',
         range: 00-FF,
         default: Any. "
   ::= { gs2326plusQosQceEntry 13 }

gs2326plusQosLLCDSAPAddr OBJECT-TYPE
   SYNTAX      DisplayString
   MAX-ACCESS  read-write
   STATUS      current
   DESCRIPTION
       " Valid DSAP(Destination Service Access Point) can vary from 0x00 to 0xFF or 'Any',
         range: 00-FF,
         default: Any. "
   ::= { gs2326plusQosQceEntry 14 }

gs2326plusQosLLCControl OBJECT-TYPE
   SYNTAX      DisplayString
   MAX-ACCESS  read-write
   STATUS      current
   DESCRIPTION
       " Valid Control field can vary from 0x00 to 0xFF or 'Any',
         range: 00-FF,
         default: Any. "
   ::= { gs2326plusQosQceEntry 15 }

gs2326plusQosSNAPPID OBJECT-TYPE
   SYNTAX      DisplayString
   MAX-ACCESS  read-write
   STATUS      current
   DESCRIPTION
       " Valid PID(a.k.a ethernet type) can have value within 0x00-0xFFFF or 'Any',
         range: 0000-FFFF,
         default: Any. "
   ::= { gs2326plusQosQceEntry 16 }

gs2326plusQosIpv4Protocol OBJECT-TYPE
   SYNTAX      DisplayString
   MAX-ACCESS  read-write
   STATUS      current
   DESCRIPTION
       " IP protocol number: (Other, TCP or UDP) or 'Any'. "
   ::= { gs2326plusQosQceEntry 17 }

gs2326plusQosIpv4ProtocolValue  OBJECT-TYPE
   SYNTAX      Integer32(0..255)
   MAX-ACCESS  read-write
   STATUS      current
   DESCRIPTION
       " Ipv4 Protocol is Other.
         range: 0-255
         default: 0. "
   ::= { gs2326plusQosQceEntry 18 }

gs2326plusQosIpv4ProtocolUDPSport OBJECT-TYPE
   SYNTAX      DisplayString
   MAX-ACCESS  read-write
   STATUS      current
   DESCRIPTION
       " Source  TCP/UDP port:(0-65535) or 'Any',
         specific or port range applicable for IP protocol UDP/TCP. "
   ::= { gs2326plusQosQceEntry 19 }

gs2326plusQosIpv4ProtocolUDPDport OBJECT-TYPE
   SYNTAX      DisplayString
   MAX-ACCESS  read-write
   STATUS      current
   DESCRIPTION
       " Destination TCP/UDP port:(0-65535) or 'Any',
         specific or port range applicable for IP protocol UDP/TCP. "
   ::= { gs2326plusQosQceEntry 20 }

gs2326plusQosIpv4ProtocolTCPSport OBJECT-TYPE
   SYNTAX      DisplayString
   MAX-ACCESS  read-write
   STATUS      current
   DESCRIPTION
       " Source TCP/UDP port:(0-65535) or 'Any',
         specific or port range applicable for IP protocol UDP/TCP. "
   ::= { gs2326plusQosQceEntry 21 }

gs2326plusQosIpv4ProtocolTCPDport OBJECT-TYPE
   SYNTAX      DisplayString
   MAX-ACCESS  read-write
   STATUS      current
   DESCRIPTION
       " Destination TCP/UDP port:(0-65535) or 'Any',
         specific or port range applicable for IP protocol UDP/TCP. "
   ::= { gs2326plusQosQceEntry 22 }

gs2326plusQosIpv4Ip OBJECT-TYPE
   SYNTAX      DisplayString
   MAX-ACCESS  read-write
   STATUS      current
   DESCRIPTION
       "  Specific Source IP address in value format or value 0.0.0.0 is 'Any'.
          if Ipv4 Mask value 0.0.0.0 is 'Any' ,IP address value also is 'Any'.
          (x.y.z.w),x=0 unless y.z.w also 0,x not is 127 or greater than 223.
          If a port is configured to match on DMAC/DIP, this field is the
          Destination IP address."
   ::= { gs2326plusQosQceEntry 23 }

gs2326plusQosIpv4Mask OBJECT-TYPE
   SYNTAX      DisplayString
   MAX-ACCESS  read-write
   STATUS      current
   DESCRIPTION
       " Specific IP address in mask format or value 0.0.0.0 is 'Any'. "
   ::= { gs2326plusQosQceEntry 24 }

gs2326plusQosIpv4IPFragment OBJECT-TYPE
   SYNTAX      INTEGER { any(0), no(1), yes(2) }
   MAX-ACCESS  read-write
   STATUS      current
   DESCRIPTION
       " IPv4 frame fragmented option:
         2: yes,
         1: no,
         0: any. "
   ::= { gs2326plusQosQceEntry 25 }

gs2326plusQosIpv4DSCP OBJECT-TYPE
   SYNTAX      DisplayString
   MAX-ACCESS  read-write
   STATUS      current
   DESCRIPTION
       " Diffserv Code Point value (DSCP): It can be a specific value,
         range of values or 'Any'. DSCP values are in the range 0-63. "
   ::= { gs2326plusQosQceEntry 26 }

gs2326plusQosIpv6Protocol OBJECT-TYPE
   SYNTAX      DisplayString
   MAX-ACCESS  read-write
   STATUS      current
   DESCRIPTION
       " IP protocol number: (Other, TCP or UDP) or 'Any'. "
   ::= { gs2326plusQosQceEntry 27 }

gs2326plusQosIpv6ProtocolValue OBJECT-TYPE
   SYNTAX      Integer32(0..255)
   MAX-ACCESS  read-write
   STATUS      current
   DESCRIPTION
       " when IPv6 protocol is Other ,
         range: 0-255. "
   ::= { gs2326plusQosQceEntry 28 }

gs2326plusQosIpv6ProtocolUDPSport OBJECT-TYPE
   SYNTAX      DisplayString
   MAX-ACCESS  read-write
   STATUS      current
   DESCRIPTION
       " Source TCP/UDP port:(0-65535) or 'Any',
         specific or port range applicable for IP protocol UDP/TCP. "
   ::= { gs2326plusQosQceEntry 29 }

gs2326plusQosIpv6ProtocolUDPDport OBJECT-TYPE
   SYNTAX      DisplayString
   MAX-ACCESS  read-write
   STATUS      current
   DESCRIPTION
       " Destination TCP/UDP port:(0-65535) or 'Any',
         specific or port range applicable for IP protocol UDP/TCP. "
   ::= { gs2326plusQosQceEntry 30 }

gs2326plusQosIpv6ProtocolTCPSport OBJECT-TYPE
   SYNTAX      DisplayString
   MAX-ACCESS  read-write
   STATUS      current
   DESCRIPTION
       " Source TCP/UDP port:(0-65535) or 'Any',
         specific or port range applicable for IP protocol UDP/TCP. "
   ::= { gs2326plusQosQceEntry 31 }


gs2326plusQosIpv6ProtocolTCPDport OBJECT-TYPE
   SYNTAX      DisplayString
   MAX-ACCESS  read-write
   STATUS      current
   DESCRIPTION
       " Destination TCP/UDP port:(0-65535) or 'Any',
         specific or port range applicable for IP protocol UDP/TCP. "
   ::= { gs2326plusQosQceEntry 32 }

gs2326plusQosIpv6Ip OBJECT-TYPE
   SYNTAX      DisplayString
   MAX-ACCESS  read-write
   STATUS      current
   DESCRIPTION
       " IPv6 source address: (a.b.c.d) or value 0.0.0.0 is 'Any', 32 LS bits.
         If a port is configured to match on DMAC/DIP, this field is the
         Destination IP address."
   ::= { gs2326plusQosQceEntry 33 }

gs2326plusQosIpv6Mask OBJECT-TYPE
   SYNTAX      DisplayString
   MAX-ACCESS  read-write
   STATUS      current
   DESCRIPTION
       " IPv6 mask address: (a.b.c.d) or value 0.0.0.0 is 'Any', 32 LS bits. "
   ::= { gs2326plusQosQceEntry 34 }

gs2326plusQosIpv6DSCP OBJECT-TYPE
   SYNTAX      DisplayString
   MAX-ACCESS  read-write
   STATUS      current
   DESCRIPTION
       " Diffserv Code Point value (DSCP): It can be a specific value,
         range of values or 'Any'. DSCP values are in the range 0-63 including BE,
         CS1-CS7, EF or AF11-AF43. "
   ::= { gs2326plusQosQceEntry 35 }

gs2326plusQosActionClass  OBJECT-TYPE
   SYNTAX      Integer32(0..8)
   MAX-ACCESS  read-write
   STATUS      current
   DESCRIPTION
       " QoS class: (0-7) or 8: Default."
   ::= { gs2326plusQosQceEntry 36 }

gs2326plusQosActionDPL OBJECT-TYPE
   SYNTAX      INTEGER (0..4)
   MAX-ACCESS  read-write
   STATUS      current
   DESCRIPTION
       " DP Valid Drop Precedence Level can be (0-3) or 4: Default. "
   ::= { gs2326plusQosQceEntry 37 }

gs2326plusQosActionDSCP OBJECT-TYPE
   SYNTAX      Integer32(0..64)
   MAX-ACCESS  read-write
   STATUS      current
   DESCRIPTION
       " Valid DSCP value can be (0-63, BE, CS1-CS7, EF or AF11-AF43) or 64: Default. "
   ::= { gs2326plusQosQceEntry 38 }

gs2326plusQosQceRowStatus OBJECT-TYPE
   SYNTAX      INTEGER { active(1), notInservice(2), destroy(4) }
   MAX-ACCESS  read-write
   STATUS      current
   DESCRIPTION
       "  1: active2: notInservice 4: destroy"
   ::= { gs2326plusQosQceEntry 39 }

gs2326plusQosQceMoveID OBJECT-TYPE
   SYNTAX       Integer32(0..256)
   MAX-ACCESS   read-write
   STATUS       current
   DESCRIPTION
       " Move Qos,
         default: 0
         Qos ID must be exist.
         range : 0 - 256."
   ::= { gs2326plusQosControlList 3 }

gs2326plusQosQceMoveNextID OBJECT-TYPE
   SYNTAX       Integer32(0..256)
   MAX-ACCESS   read-write
   STATUS       current
   DESCRIPTION
       " Move Qos,
         default: 0
         If the next Qos ID is non zero, the Qos will be placed before this Qos in the list.
         If the next Qos ID is zero,the Qos will be placed last in the list.
         range : 0 - 256. "
   ::= { gs2326plusQosControlList 4 }


gs2326plusQosQCLStatusTable OBJECT-TYPE
   SYNTAX      SEQUENCE OF Gs2326plusQosQCLStatusEntry
   MAX-ACCESS  not-accessible
   STATUS      current
   DESCRIPTION
       "  configure the basic QoS DSCP Translation settings for all switches. "
   ::= { gs2326plusQos  10 }

gs2326plusQosQCLStatusEntry OBJECT-TYPE
   SYNTAX      Gs2326plusQosQCLStatusEntry
   MAX-ACCESS  not-accessible
   STATUS      current
   DESCRIPTION
       ""
   INDEX    { gs2326plusQosQCLStatusList  }
   ::= { gs2326plusQosQCLStatusTable 1 }

Gs2326plusQosQCLStatusEntry ::= SEQUENCE {
   gs2326plusQosQCLStatusList               Integer32,
   gs2326plusQosQCLStatusUser               DisplayString,
   gs2326plusQosQCLStatusQCEId              DisplayString,
   gs2326plusQosQCLStatusFrameType          DisplayString,
   gs2326plusQosQCLStatusPortlist           DisplayString,
   gs2326plusQosQCLStatusActionClass	       DisplayString,
   gs2326plusQosQCLStatusActionDPL	       DisplayString,
   gs2326plusQosQCLStatusActionDSCP	       DisplayString,
   gs2326plusQosQCLStatusActionConflict     DisplayString
}

gs2326plusQosQCLStatusList OBJECT-TYPE
   SYNTAX      Integer32(1..4095)
   MAX-ACCESS  not-accessible
   STATUS      current
   DESCRIPTION
       " QCL table index. "
   ::= { gs2326plusQosQCLStatusEntry 1}

gs2326plusQosQCLStatusUser OBJECT-TYPE
   SYNTAX      DisplayString
   MAX-ACCESS  read-only
   STATUS      current
   DESCRIPTION
       " Indicates the QCL user. "
   ::= { gs2326plusQosQCLStatusEntry 2 }

gs2326plusQosQCLStatusQCEId OBJECT-TYPE
   SYNTAX      DisplayString
   MAX-ACCESS  read-only
   STATUS      current
   DESCRIPTION
      " Indicates the index of QCE. "
   ::= { gs2326plusQosQCLStatusEntry 3}

gs2326plusQosQCLStatusFrameType OBJECT-TYPE
   SYNTAX      DisplayString
   MAX-ACCESS  read-only
   STATUS      current
   DESCRIPTION
       " Indicates the type of frame to look for incomming frames.
       Any: The QCE will match all frame type.
       Ethernet: Only Ethernet frames (with Ether Type 0x600-0xFFFF) are allowed.
       LLC: Only (LLC) frames are allowed.
       SNAP: Only (SNAP) frames are allowed.
       IPv4: The QCE will match only IPV4 frames.
       IPv6: The QCE will match only IPV6 frames."
   ::= { gs2326plusQosQCLStatusEntry 4}

gs2326plusQosQCLStatusPortlist OBJECT-TYPE
   SYNTAX      DisplayString
   MAX-ACCESS  read-only
   STATUS      current
   DESCRIPTION
       " Indicates the list of ports configured with the QCE. "
   ::= { gs2326plusQosQCLStatusEntry 5}

gs2326plusQosQCLStatusActionClass OBJECT-TYPE
   SYNTAX      DisplayString
   MAX-ACCESS  read-only
   STATUS      current
   DESCRIPTION
       " Classified QoS class; if a frame matches the QCE it will be put in the
       queue. "
   ::= { gs2326plusQosQCLStatusEntry 6}

gs2326plusQosQCLStatusActionDPL OBJECT-TYPE
   SYNTAX      DisplayString
   MAX-ACCESS  read-only
   STATUS      current
   DESCRIPTION
       " Drop Precedence Level; if a frame matches the QCE then DP level will
       set to value displayed under DPL column."
   ::= { gs2326plusQosQCLStatusEntry 7}

gs2326plusQosQCLStatusActionDSCP OBJECT-TYPE
   SYNTAX      DisplayString
   MAX-ACCESS  read-only
   STATUS      current
   DESCRIPTION
       " If a frame matches the QCE then DSCP will be classified with the value
       displayed under DSCP column."
   ::= { gs2326plusQosQCLStatusEntry 8}

gs2326plusQosQCLStatusActionConflict OBJECT-TYPE
   SYNTAX      DisplayString
   MAX-ACCESS  read-only
   STATUS      current
   DESCRIPTION
       " If a frame matches the QCE then DSCP will be classified with the value
        displayed under DSCP column. "
   ::= { gs2326plusQosQCLStatusEntry 9}


gs2326plusQosStormControl                                           OBJECT IDENTIFIER ::= { gs2326plusQos 11 }

gs2326plusQoSStormControlUC OBJECT-TYPE
   SYNTAX      INTEGER { disable(0), enable(1) }
   MAX-ACCESS  read-write
   STATUS      current
   DESCRIPTION
       "Enable or disable the storm control status for the Unicast frame type.
       default:  0
        0: disable
        1: enable"
   ::= { gs2326plusQosStormControl 2 }

gs2326plusQoSStormControlUCRate OBJECT-TYPE
   SYNTAX      DisplayString
   MAX-ACCESS  read-write
   STATUS      current
   DESCRIPTION
       "The rate unit is packets per second (pps). Valid values are: 1, 2, 4, 8,
        16, 32, 64, 128, 256, 512, 1K, 2K, 4K, 8K, 16K, 32K, 64K, 128K, 256K,
        512K or 1024K."
   ::= { gs2326plusQosStormControl 3 }

gs2326plusQoSStormControlMC OBJECT-TYPE
   SYNTAX      INTEGER { disable(0), enable(1) }
   MAX-ACCESS  read-write
   STATUS      current
   DESCRIPTION
       "Enable or disable the storm control status for the Multicast frame type.
       default:  0
        0: disable
        1: enable"
   ::= { gs2326plusQosStormControl 4 }

gs2326plusQoSStormControlMCRate OBJECT-TYPE
   SYNTAX      DisplayString
   MAX-ACCESS  read-write
   STATUS      current
   DESCRIPTION
       "The rate unit is packets per second (pps). Valid values are: 1, 2, 4, 8,
        16, 32, 64, 128, 256, 512, 1K, 2K, 4K, 8K, 16K, 32K, 64K, 128K, 256K,
        512K or 1024K."
   ::= { gs2326plusQosStormControl 5 }

gs2326plusQoSStormControlBC OBJECT-TYPE
   SYNTAX      INTEGER { disable(0), enable(1) }
   MAX-ACCESS  read-write
   STATUS      current
   DESCRIPTION
       "Enable or disable the storm control status for the Broadcast frame type.
       default:  0
        0: disable
        1: enable"
   ::= { gs2326plusQosStormControl 6 }

gs2326plusQoSStormControlBCRate OBJECT-TYPE
   SYNTAX      DisplayString
   MAX-ACCESS  read-write
   STATUS      current
   DESCRIPTION
       "The rate unit is packets per second (pps). Valid values are: 1, 2, 4, 8,
        16, 32, 64, 128, 256, 512, 1K, 2K, 4K, 8K, 16K, 32K, 64K, 128K, 256K,
        512K or 1024K."
   ::= { gs2326plusQosStormControl 7 }


gs2326plusVlan                                                           OBJECT IDENTIFIER ::= { gs2326plusConfiguration 15 }

gs2326plusVlanPorts                                                      OBJECT IDENTIFIER ::= { gs2326plusVlan 1 }

gs2326plusVlanPortsTPIDforCustomSport  OBJECT-TYPE
   SYNTAX      OCTET STRING(SIZE(2))
   MAX-ACCESS  read-write
   STATUS      current
   DESCRIPTION
       "Configure the TPID used for Custom S-ports. This is a global setting for
       all the Custom S-ports.
       range: 0x0600-0xffff,
       default: 0x88a8. "
   ::= { gs2326plusVlanPorts 1 }

gs2326plusVlanPortsTable OBJECT-TYPE
   SYNTAX      SEQUENCE OF Gs2326plusVlanPortsEntry
   MAX-ACCESS  not-accessible
   STATUS      current
   DESCRIPTION
       " Configure Vlan ports Configuration mode. "
   ::= { gs2326plusVlanPorts 2 }

gs2326plusVlanPortsEntry OBJECT-TYPE
   SYNTAX      Gs2326plusVlanPortsEntry
   MAX-ACCESS  not-accessible
   STATUS      current
   DESCRIPTION
       ""
   INDEX    { gs2326plusVlanPortsPort  }
   ::= { gs2326plusVlanPortsTable 1 }

Gs2326plusVlanPortsEntry ::= SEQUENCE {
   gs2326plusVlanPortsPort	         Integer32,
   gs2326plusVlanPortsPVID     Integer32,
   gs2326plusVlanPortsFrameType      INTEGER,
   gs2326plusVlanPortsIngressFilter  INTEGER,
   gs2326plusVlanPortsEgressRule     INTEGER,
   gs2326plusVlanPortsPortType       INTEGER
}

gs2326plusVlanPortsPort OBJECT-TYPE
   SYNTAX      Integer32(1..4094)
   MAX-ACCESS  not-accessible
   STATUS      current
   DESCRIPTION
       " port, range : 1 - port number. "
   ::= { gs2326plusVlanPortsEntry 1 }

gs2326plusVlanPortsPVID OBJECT-TYPE
   SYNTAX      Integer32(1..4094)
   MAX-ACCESS  read-write
   STATUS      current
   DESCRIPTION
       "Configure PVID.
        range: 1-4094,
        default: 1. "
   ::= { gs2326plusVlanPortsEntry 2 }

gs2326plusVlanPortsFrameType OBJECT-TYPE
   SYNTAX      INTEGER { all(0), tagged(1), untagged(2) }
   MAX-ACCESS  read-write
   STATUS      current
   DESCRIPTION
       "Configure frame type of switch ports.
        0: all,
        1: tagged,
        2: untagged,
        default: all.  "
   ::= { gs2326plusVlanPortsEntry 3 }

gs2326plusVlanPortsIngressFilter OBJECT-TYPE
   SYNTAX      INTEGER { disable(0), enable(1) }
   MAX-ACCESS  read-write
   STATUS      current
   DESCRIPTION
       "Configure ingress filtering of switch ports.
        0: disable,
        1: enable,
        default:disable . "
   ::= { gs2326plusVlanPortsEntry 4 }

gs2326plusVlanPortsEgressRule OBJECT-TYPE
   SYNTAX      INTEGER { access(0), hybrid(1), trunk(2) }
   MAX-ACCESS  read-write
   STATUS      current
   DESCRIPTION
       "Configure egress-rule of switch ports.
        0: access,
        1: hybrid,
        2: trunk"
   ::= { gs2326plusVlanPortsEntry 5 }

gs2326plusVlanPortsPortType OBJECT-TYPE
   SYNTAX      INTEGER { cPort(0), sCustomPort(1), sPort(2), unaware(3) }
   MAX-ACCESS  read-write
   STATUS      current
   DESCRIPTION
       "Configure port type of switch ports.
        0: c-port,
        1: s-custom-port,
        2: s-port,
        3: unaware.
        default: c-port. "
   ::= { gs2326plusVlanPortsEntry 6 }

gs2326plusVlanPrivateVLAN                                                              OBJECT IDENTIFIER ::= { gs2326plusVlan 2 }

gs2326plusVlanPrivateVLANMembership                                                    OBJECT IDENTIFIER ::= { gs2326plusVlanPrivateVLAN 1 }

gs2326plusVlanPrivateVLANMembershipCreate OBJECT-TYPE
   SYNTAX       Integer32(1..4094)
   MAX-ACCESS   read-write
   STATUS       current
   DESCRIPTION
       "default: 0
        0 : None  (read only)
        1 : Create a pvlan"
   ::= { gs2326plusVlanPrivateVLANMembership 1 }

gs2326plusVlanPrivateVLANMembershipTable OBJECT-TYPE
   SYNTAX      SEQUENCE OF Gs2326plusVlanPrivateVLANMembershipEntry
   MAX-ACCESS  not-accessible
   STATUS      current
   DESCRIPTION
       " Configure Private Vlan Configuration. "
   ::= { gs2326plusVlanPrivateVLANMembership 2 }

gs2326plusVlanPrivateVLANMembershipEntry OBJECT-TYPE
   SYNTAX      Gs2326plusVlanPrivateVLANMembershipEntry
   MAX-ACCESS  not-accessible
   STATUS      current
   DESCRIPTION
       ""
   INDEX    { gs2326plusVlanPrivateVLANIndex  }
   ::= { gs2326plusVlanPrivateVLANMembershipTable 1 }

Gs2326plusVlanPrivateVLANMembershipEntry ::= SEQUENCE {
   gs2326plusVlanPrivateVLANIndex          Integer32,
   gs2326plusVlanPrivateVLANID             Integer32,
   gs2326plusVlanPrivateVLANMemberships    DisplayString,
   gs2326plusVlanPrivateVLANRowStatus      INTEGER
}

gs2326plusVlanPrivateVLANIndex OBJECT-TYPE
   SYNTAX      Integer32(1..52)
   MAX-ACCESS  not-accessible
   STATUS      current
   DESCRIPTION
       "private VLAN Index. "
   ::= { gs2326plusVlanPrivateVLANMembershipEntry 1 }

gs2326plusVlanPrivateVLANID OBJECT-TYPE
   SYNTAX      Integer32(1..52)
   MAX-ACCESS  read-write
   STATUS      current
   DESCRIPTION
       "Indicates the ID of this particular private VLAN.
       The CreateEntry can be modify, the other entry can't be modify."
   ::= { gs2326plusVlanPrivateVLANMembershipEntry 2 }

gs2326plusVlanPrivateVLANMemberships OBJECT-TYPE
   SYNTAX      DisplayString
   MAX-ACCESS  read-write
   STATUS      current
   DESCRIPTION
       "To include the ports in a Private VLAN"
   ::= { gs2326plusVlanPrivateVLANMembershipEntry 3 }

gs2326plusVlanPrivateVLANRowStatus OBJECT-TYPE
   SYNTAX      INTEGER { active(1), notInservice(2), destroy(4) }
   MAX-ACCESS  read-write
   STATUS      current
   DESCRIPTION
       "1: active
        2: notInservice
        4: destroy"
   ::= { gs2326plusVlanPrivateVLANMembershipEntry 4 }

gs2326plusVlanPortIsolationTable OBJECT-TYPE
   SYNTAX      SEQUENCE OF Gs2326plusVlanPortIsolationEntry
   MAX-ACCESS  not-accessible
   STATUS      current
   DESCRIPTION
       " Configure Vlan Port Isolation Configuration. "
   ::= { gs2326plusVlanPrivateVLAN 2 }

gs2326plusVlanPortIsolationEntry OBJECT-TYPE
   SYNTAX      Gs2326plusVlanPortIsolationEntry
   MAX-ACCESS  not-accessible
   STATUS      current
   DESCRIPTION
       ""
   INDEX    { gs2326plusVlanPortIsolationPort  }
   ::= { gs2326plusVlanPortIsolationTable 1 }

Gs2326plusVlanPortIsolationEntry ::= SEQUENCE {
   gs2326plusVlanPortIsolationPort Integer32,
   gs2326plusVlanPortIsolation     INTEGER
}

gs2326plusVlanPortIsolationPort OBJECT-TYPE
   SYNTAX      Integer32(1..4094)
   MAX-ACCESS  not-accessible
   STATUS      current
   DESCRIPTION
       " port, range : 1 - port number. "
   ::= { gs2326plusVlanPortIsolationEntry 1 }

gs2326plusVlanPortIsolation OBJECT-TYPE
   SYNTAX      INTEGER{ disable(0), enable(1) }
   MAX-ACCESS  read-write
   STATUS      current
   DESCRIPTION
       "default: 0
        0:disable
        1:enable"
   ::= { gs2326plusVlanPortIsolationEntry 2 }


gs2326plusMACbasedVLAN                                                      OBJECT IDENTIFIER ::= { gs2326plusVlan 3 }

gs2326plusMACbasedVLANConf                                                      OBJECT IDENTIFIER ::= { gs2326plusMACbasedVLAN 1 }

gs2326plusMACbasedVLANConfCreate OBJECT-TYPE
   SYNTAX       Integer32
   MAX-ACCESS   read-write
   STATUS       current
   DESCRIPTION
       "default: 0
       0 : None  (read only) 1 : Create MAC base vlan"
   ::= { gs2326plusMACbasedVLANConf 1 }

gs2326plusMACbasedVLANConfTable OBJECT-TYPE
   SYNTAX      SEQUENCE OF Gs2326plusMACbasedVLANConfEntry
   MAX-ACCESS  not-accessible
   STATUS      current
   DESCRIPTION
       " Configure Vlan Port Isolation Configuration. "
   ::= { gs2326plusMACbasedVLANConf 2 }

gs2326plusMACbasedVLANConfEntry OBJECT-TYPE
   SYNTAX      Gs2326plusMACbasedVLANConfEntry
   MAX-ACCESS  not-accessible
   STATUS      current
   DESCRIPTION
       ""
   INDEX    { gs2326plusMACbasedVLANIndex  }
   ::= { gs2326plusMACbasedVLANConfTable 1 }

Gs2326plusMACbasedVLANConfEntry ::= SEQUENCE {
   gs2326plusMACbasedVLANIndex         Integer32,
   gs2326plusMACbasedVLANMACAddress    MacAddress,
   gs2326plusMACbasedVLANID            Integer32,
   gs2326plusMACbasedMemberships       DisplayString,
   gs2326plusMACbaseRowStatus          INTEGER
}

gs2326plusMACbasedVLANIndex OBJECT-TYPE
   SYNTAX      Integer32(1..256)
   MAX-ACCESS  read-write
   STATUS      current
   DESCRIPTION
       "Indicates the VLAN ID. "
   ::= { gs2326plusMACbasedVLANConfEntry 1 }

gs2326plusMACbasedVLANMACAddress OBJECT-TYPE
   SYNTAX      MacAddress
   MAX-ACCESS  read-write
   STATUS      current
   DESCRIPTION
       "Indicates the MAC address.
       The CreateEntry can be modify, the other entry can't be modify."
   ::= { gs2326plusMACbasedVLANConfEntry 2 }

gs2326plusMACbasedVLANID OBJECT-TYPE
   SYNTAX      Integer32(1..4094)
   MAX-ACCESS  read-write
   STATUS      current
   DESCRIPTION
       "Indicates the VLAN ID. "
   ::= { gs2326plusMACbasedVLANConfEntry 3 }

gs2326plusMACbasedMemberships OBJECT-TYPE
   SYNTAX      DisplayString
   MAX-ACCESS  read-write
   STATUS      current
   DESCRIPTION
       "The ports are displayed for each MAC-based VLAN entry.
        To include the port in a MAC-based VLAN"
   ::= { gs2326plusMACbasedVLANConfEntry 4 }


gs2326plusMACbaseRowStatus OBJECT-TYPE
   SYNTAX      INTEGER { active(1), notInservice(2), destroy(4)}
   MAX-ACCESS  read-write
   STATUS      current
   DESCRIPTION
       "1: active
        2: notInservice
        4: destroy"
   ::= { gs2326plusMACbasedVLANConfEntry 5 }

gs2326plusIGMPSnooping                                                           OBJECT IDENTIFIER ::= { gs2326plusConfiguration 16 }

gs2326plusIGMPSnoopingBasic                                                      OBJECT IDENTIFIER ::= { gs2326plusIGMPSnooping 1 }

gs2326plusIGMPSnoopingEnable  OBJECT-TYPE
   SYNTAX      INTEGER { disable(0), enable(1) }
   MAX-ACCESS  read-write
   STATUS      current
   DESCRIPTION
       "Enable/Disable the Global IGMP Snooping"
   ::= { gs2326plusIGMPSnoopingBasic 1 }

gs2326plusIGMPSnoopingUnregisteredIPMCv4Flooding  OBJECT-TYPE
   SYNTAX      INTEGER { disable(0), enable(1) }
   MAX-ACCESS  read-write
   STATUS      current
   DESCRIPTION
       "Enable/Disable unregistered IPMCv4 traffic flooding. "
   ::= { gs2326plusIGMPSnoopingBasic 2 }

gs2326plusIGMPSnoopingSSMIPRangeAddr  OBJECT-TYPE
   SYNTAX      DisplayString
   MAX-ACCESS  read-write
   STATUS      current
   DESCRIPTION
       "SSM (Source-Specific Multicast) Range allows the SSM-aware hosts and
       routers run the SSM service model for the groups in the address range. "
   ::= { gs2326plusIGMPSnoopingBasic 3 }

gs2326plusIGMPSnoopingSSMIPRangeValue  OBJECT-TYPE
   SYNTAX      Integer32(4..32)
   MAX-ACCESS  read-write
   STATUS      current
   DESCRIPTION
       "SSM (Source-Specific Multicast) Range allows the SSM-aware hosts and
       routers run the SSM service model for the groups in the address range value. "
   ::= { gs2326plusIGMPSnoopingBasic 4 }

gs2326plusIGMPSnoopingProxyEnabled  OBJECT-TYPE
   SYNTAX      INTEGER { disable(0), enable(1) }
   MAX-ACCESS  read-write
   STATUS      current
   DESCRIPTION
       "Enable/Disable IGMP Proxy. This feature can be used to avoid forwarding
       unnecessary join and leave messages to the router side. "
   ::= { gs2326plusIGMPSnoopingBasic 5 }

gs2326plusIGMPSnoopingPortRelatedTable OBJECT-TYPE
   SYNTAX      SEQUENCE OF Gs2326plusIGMPSnoopingPortRelatedEntry
   MAX-ACCESS  not-accessible
   STATUS      current
   DESCRIPTION
       " Configure IGMP Snooping Port Related Configuration. "
   ::= { gs2326plusIGMPSnoopingBasic 6 }

gs2326plusIGMPSnoopingPortRelatedEntry OBJECT-TYPE
   SYNTAX      Gs2326plusIGMPSnoopingPortRelatedEntry
   MAX-ACCESS  not-accessible
   STATUS      current
   DESCRIPTION
       ""
   INDEX    { ifIndex  }
   ::= { gs2326plusIGMPSnoopingPortRelatedTable 1 }

Gs2326plusIGMPSnoopingPortRelatedEntry ::= SEQUENCE {
   gs2326plusIGMPSnoopingRouterPort	INTEGER,
   gs2326plusIGMPSnoopingFastLeave  	INTEGER,
   gs2326plusIGMPSnoopingThrottling    Integer32
}

gs2326plusIGMPSnoopingRouterPort OBJECT-TYPE
   SYNTAX      INTEGER { disable(0), enable(1) }
   MAX-ACCESS  read-write
   STATUS      current
   DESCRIPTION
       "Specify which ports act as router ports. A router port is a port on the
       Ethernet switch that leads towards the Layer 3 multicast device or IGMP
       querier. If an aggregation member port is selected as a router port, the
       whole aggregation will act as a router port. "
   ::= { gs2326plusIGMPSnoopingPortRelatedEntry 1 }

gs2326plusIGMPSnoopingFastLeave OBJECT-TYPE
   SYNTAX      INTEGER { disable(0), enable(1) }
   MAX-ACCESS  read-write
   STATUS      current
   DESCRIPTION
       "Enable/Disable the fast leave on the port. "
   ::= { gs2326plusIGMPSnoopingPortRelatedEntry 2 }

gs2326plusIGMPSnoopingThrottling OBJECT-TYPE
   SYNTAX      Integer32(0..10)
   MAX-ACCESS  read-write
   STATUS      current
   DESCRIPTION
       "Enable to limit the number of multicast groups to which a switch port can belong.
       0: unlimited"
   ::= { gs2326plusIGMPSnoopingPortRelatedEntry 3 }

gs2326plusIGMPSnoopingVLANTable OBJECT-TYPE
   SYNTAX      SEQUENCE OF Gs2326plusIGMPSnoopingVLANEntry
   MAX-ACCESS  not-accessible
   STATUS      current
   DESCRIPTION
       " Configure IGMP Snooping Vlan Configuration. "
   ::= { gs2326plusIGMPSnooping 2 }

gs2326plusIGMPSnoopingVLANEntry OBJECT-TYPE
   SYNTAX      Gs2326plusIGMPSnoopingVLANEntry
   MAX-ACCESS  not-accessible
   STATUS      current
   DESCRIPTION
       ""
   INDEX    { gs2326plusIGMPSnoopingVLANID  }
   ::= { gs2326plusIGMPSnoopingVLANTable 1 }

Gs2326plusIGMPSnoopingVLANEntry ::= SEQUENCE {
   gs2326plusIGMPSnoopingVLANID        	Integer32,
   gs2326plusIGMPSnoopingVLANEnable    	INTEGER,
   gs2326plusIGMPSnoopingVLANIGMPQuerier   INTEGER,
   gs2326plusIGMPSnoopingVLANCompatibility INTEGER,
   gs2326plusIGMPSnoopingVLANRV        	Integer32,
   gs2326plusIGMPSnoopingVLANQI      	    Integer32,
   gs2326plusIGMPSnoopingVLANQRI   	    Integer32,
   gs2326plusIGMPSnoopingVLANLLQI   	    Integer32,
   gs2326plusIGMPSnoopingVLANURI    	    Integer32
}

gs2326plusIGMPSnoopingVLANID OBJECT-TYPE
   SYNTAX      Integer32(1..4095)
   MAX-ACCESS  read-write
   STATUS      current
   DESCRIPTION
       "The VLAN ID of the entry"
   ::= { gs2326plusIGMPSnoopingVLANEntry 1 }

gs2326plusIGMPSnoopingVLANEnable OBJECT-TYPE
   SYNTAX      INTEGER { disable(0), enable(1) }
   MAX-ACCESS  read-write
   STATUS      current
   DESCRIPTION
       "Enable/Disable the per-VLAN IGMP Snooping. Up to 32 VLANs can be
       selected for IGMP Snooping. "
   ::= { gs2326plusIGMPSnoopingVLANEntry 2 }

gs2326plusIGMPSnoopingVLANIGMPQuerier OBJECT-TYPE
   SYNTAX      INTEGER { disable(0), enable(1) }
   MAX-ACCESS  read-write
   STATUS      current
   DESCRIPTION
       "Enable/Disable the IGMP Querier in the VLAN. "
   ::= { gs2326plusIGMPSnoopingVLANEntry 3 }

gs2326plusIGMPSnoopingVLANCompatibility OBJECT-TYPE
   SYNTAX      INTEGER { igmpAuto(0), forcedIGMPv1(1), forcedIGMPv2(2), forcedIGMPv3(3), none(4) }
   MAX-ACCESS  read-write
   STATUS      current
   DESCRIPTION
       "Compatibility is maintained by hosts and routers taking appropriate
       actions depending on the versions of IGMP operating on hosts and routers
       within a network. The allowed selection is IGMP-Auto, Forced IGMPv1,
       Forced IGMPv2, Forced IGMPv3, default compatibility value is IGMP-Auto. "
   ::= { gs2326plusIGMPSnoopingVLANEntry 4 }

gs2326plusIGMPSnoopingVLANRV OBJECT-TYPE
   SYNTAX      Integer32(-1|1..255)
   MAX-ACCESS  read-write
   STATUS      current
   DESCRIPTION
       "Robustness Variable. The Robustness Variable allows tuning for the
       expected packet loss on a network. The allowed range is 1 to 255, default
        robustness variable value is 2. (-1: none)"
   ::= { gs2326plusIGMPSnoopingVLANEntry 5 }

gs2326plusIGMPSnoopingVLANQI OBJECT-TYPE
   SYNTAX      Integer32(-1|1..31744)
   MAX-ACCESS  read-write
   STATUS      current
   DESCRIPTION
       "Query Interval. The Query Interval is the interval between General
       Queries sent by the Querier. The allowed range is 1 to 31744 seconds,
       default query interval is 125 seconds.  (-1: none)"
   ::= { gs2326plusIGMPSnoopingVLANEntry 6 }

gs2326plusIGMPSnoopingVLANQRI OBJECT-TYPE
   SYNTAX      Integer32(-1|0..31744)
   MAX-ACCESS  read-write
   STATUS      current
   DESCRIPTION
       "Query Response Interval. The Maximum Response Delay used to calculate
       the Maximum Response Code inserted into the periodic General Queries. The
        allowed range is 0 to 31744 in tenths of seconds, default query response
         interval is 100 in tenths of seconds (10 seconds).   (-1: none)"
   ::= { gs2326plusIGMPSnoopingVLANEntry 7 }

gs2326plusIGMPSnoopingVLANLLQI OBJECT-TYPE
   SYNTAX      Integer32(-1|0..31744)
   MAX-ACCESS  read-write
   STATUS      current
   DESCRIPTION
       "LLQI (LMQI for IGMP).  Last Member Query Interval. The Last Member Query
       Time is the time value represented by the Last Member Query Interval,
       multiplied by the Last Member Query Count. The allowed range is 0 to
       31744 in tenths of seconds, default last member query interval is 10 in
       tenths of seconds (1 second).    (-1: none)"
   ::= { gs2326plusIGMPSnoopingVLANEntry 8 }

gs2326plusIGMPSnoopingVLANURI OBJECT-TYPE
   SYNTAX      Integer32(-1|0..31744)
   MAX-ACCESS  read-write
   STATUS      current
   DESCRIPTION
       "Unsolicited Report Interval. The Unsolicited Report Interval is the time
        between repetitions of a host's initial report of membership in a group.
         The allowed range is 0 to 31744 seconds, default unsolicited report
         interval is 1 second.    (-1: none)"
   ::= { gs2326plusIGMPSnoopingVLANEntry 9 }

gs2326plusIGMPSnoopingPortGroupFiltering                                                      OBJECT IDENTIFIER ::= { gs2326plusIGMPSnooping 3 }

gs2326plusIGMPSnoopingPortGroupFilteringCreate OBJECT-TYPE
   SYNTAX       Integer32
   MAX-ACCESS   read-write
   STATUS       current
   DESCRIPTION
       "default: 0
       0 : None  (read only) 1 : Create IGMP Snooping Port Group Filtering "
   ::= { gs2326plusIGMPSnoopingPortGroupFiltering 1 }

gs2326plusIGMPSnoopingPortGroupFilteringTable OBJECT-TYPE
   SYNTAX      SEQUENCE OF Gs2326plusIGMPSnoopingPortGroupFilteringEntry
   MAX-ACCESS  not-accessible
   STATUS      current
   DESCRIPTION
       " Configure IGMP Snooping port group filtering. "
   ::= { gs2326plusIGMPSnoopingPortGroupFiltering 2 }

gs2326plusIGMPSnoopingPortGroupFilteringEntry OBJECT-TYPE
   SYNTAX      Gs2326plusIGMPSnoopingPortGroupFilteringEntry
   MAX-ACCESS  not-accessible
   STATUS      current
   DESCRIPTION
       ""
   INDEX    { gs2326plusIGMPSnoopingPortGroupFilteringIndex  }
   ::= { gs2326plusIGMPSnoopingPortGroupFilteringTable 1 }

Gs2326plusIGMPSnoopingPortGroupFilteringEntry ::= SEQUENCE {
   gs2326plusIGMPSnoopingPortGroupFilteringIndex         Integer32,
   gs2326plusIGMPSnoopingPortGroupFilteringPort          Integer32,
   gs2326plusIGMPSnoopingPortGroupFilteringGroups        DisplayString,
   gs2326plusIGMPSnoopingPortGroupFilteringRowStatus     INTEGER
}

gs2326plusIGMPSnoopingPortGroupFilteringIndex OBJECT-TYPE
   SYNTAX      Integer32(1..65535)
   MAX-ACCESS  not-accessible
   STATUS      current
   DESCRIPTION
       "IGMP Snooping Port Group Filtering Configuration Index. "
   ::= { gs2326plusIGMPSnoopingPortGroupFilteringEntry 1 }

gs2326plusIGMPSnoopingPortGroupFilteringPort OBJECT-TYPE
   SYNTAX      Integer32(1..65535)
   MAX-ACCESS  read-write
   STATUS      current
   DESCRIPTION
       "The logical port for the settings. "
   ::= { gs2326plusIGMPSnoopingPortGroupFilteringEntry 2 }

gs2326plusIGMPSnoopingPortGroupFilteringGroups OBJECT-TYPE
   SYNTAX      DisplayString
   MAX-ACCESS  read-write
   STATUS      current
   DESCRIPTION
       "The IP Multicast Group that will be filtered. "
   ::= { gs2326plusIGMPSnoopingPortGroupFilteringEntry 3 }

gs2326plusIGMPSnoopingPortGroupFilteringRowStatus OBJECT-TYPE
   SYNTAX      INTEGER { active(1), notInservice(2), destroy(4)}
   MAX-ACCESS  read-write
   STATUS      current
   DESCRIPTION
       "1: active
        2: notInservice
        4: destroy"
   ::= { gs2326plusIGMPSnoopingPortGroupFilteringEntry 4 }

gs2326plusIGMPSnoopingStatus                                                      OBJECT IDENTIFIER ::= { gs2326plusIGMPSnooping 4 }

gs2326plusIGMPSnoopingstatisticClear OBJECT-TYPE
   SYNTAX      INTEGER { none(0), clear(1)}
   MAX-ACCESS  read-write
   STATUS      current
   DESCRIPTION
       "Clears all Statistics counters."
   ::= { gs2326plusIGMPSnoopingStatus 1 }


gs2326plusIGMPSnoopingstatisticTable OBJECT-TYPE
   SYNTAX      SEQUENCE OF Gs2326plusIGMPSnoopingstatisticEntry
   MAX-ACCESS  not-accessible
   STATUS      current
   DESCRIPTION
       " Configure Vlan Port Isolation Configuration. "
   ::= { gs2326plusIGMPSnoopingStatus 2 }

gs2326plusIGMPSnoopingstatisticEntry OBJECT-TYPE
   SYNTAX      Gs2326plusIGMPSnoopingstatisticEntry
   MAX-ACCESS  not-accessible
   STATUS      current
   DESCRIPTION
       ""
   INDEX    { gs2326plusIGMPSnoopingstatisticVLANID  }
   ::= { gs2326plusIGMPSnoopingstatisticTable 1 }

Gs2326plusIGMPSnoopingstatisticEntry ::= SEQUENCE {
   gs2326plusIGMPSnoopingstatisticVLANID              Integer32,
   gs2326plusIGMPSnoopingstatisticQuerierVersion      DisplayString,
   gs2326plusIGMPSnoopingstatisticHostVersion         DisplayString,
   gs2326plusIGMPSnoopingstatisticQuerierStatus       DisplayString,
   gs2326plusIGMPSnoopingstatisticQueriesTransmitted  Counter32,
   gs2326plusIGMPSnoopingstatisticQueriesReceived     Counter32,
   gs2326plusIGMPSnoopingstatisticV1ReportsReceived   Counter32,
   gs2326plusIGMPSnoopingstatisticV2ReportsReceived   Counter32,
   gs2326plusIGMPSnoopingstatisticV3ReportsReceived   Counter32,
   gs2326plusIGMPSnoopingstatisticV2LeavesReceived    Counter32
}


gs2326plusIGMPSnoopingstatisticVLANID OBJECT-TYPE
   SYNTAX      Integer32(1..4095)
   MAX-ACCESS  read-only
   STATUS      current
   DESCRIPTION
       "The VLAN ID of the entry. "
   ::= { gs2326plusIGMPSnoopingstatisticEntry 1 }

gs2326plusIGMPSnoopingstatisticQuerierVersion OBJECT-TYPE
   SYNTAX      DisplayString
   MAX-ACCESS  read-only
   STATUS      current
   DESCRIPTION
       "Working Querier Version currently. "
   ::= { gs2326plusIGMPSnoopingstatisticEntry 2 }

gs2326plusIGMPSnoopingstatisticHostVersion OBJECT-TYPE
   SYNTAX      DisplayString
   MAX-ACCESS  read-only
   STATUS      current
   DESCRIPTION
       "Working Host Version currently. "
   ::= { gs2326plusIGMPSnoopingstatisticEntry 3 }

gs2326plusIGMPSnoopingstatisticQuerierStatus OBJECT-TYPE
   SYNTAX      DisplayString
   MAX-ACCESS  read-only
   STATUS      current
   DESCRIPTION
       "Shows the Querier status is ACTIVE or IDLE. DISABLE denotes the specific
        interface is administratively disabled. "
   ::= { gs2326plusIGMPSnoopingstatisticEntry 4 }

gs2326plusIGMPSnoopingstatisticQueriesTransmitted OBJECT-TYPE
   SYNTAX      Counter32
   MAX-ACCESS  read-only
   STATUS      current
   DESCRIPTION
       "The number of Transmitted Queries. "
   ::= { gs2326plusIGMPSnoopingstatisticEntry 5 }

gs2326plusIGMPSnoopingstatisticQueriesReceived OBJECT-TYPE
   SYNTAX      Counter32
   MAX-ACCESS  read-only
   STATUS      current
   DESCRIPTION
       "The number of Received Queries. "
   ::= { gs2326plusIGMPSnoopingstatisticEntry 6 }

gs2326plusIGMPSnoopingstatisticV1ReportsReceived OBJECT-TYPE
   SYNTAX      Counter32
   MAX-ACCESS  read-only
   STATUS      current
   DESCRIPTION
       "The number of Received V1 Reports. "
   ::= { gs2326plusIGMPSnoopingstatisticEntry 7 }

gs2326plusIGMPSnoopingstatisticV2ReportsReceived OBJECT-TYPE
   SYNTAX      Counter32
   MAX-ACCESS  read-only
   STATUS      current
   DESCRIPTION
       "The number of Received V2 Reports. "
   ::= { gs2326plusIGMPSnoopingstatisticEntry 8 }

gs2326plusIGMPSnoopingstatisticV3ReportsReceived OBJECT-TYPE
   SYNTAX      Counter32
   MAX-ACCESS  read-only
   STATUS      current
   DESCRIPTION
       "The number of Received V3 Reports. "
   ::= { gs2326plusIGMPSnoopingstatisticEntry 9 }

gs2326plusIGMPSnoopingstatisticV2LeavesReceived OBJECT-TYPE
   SYNTAX      Counter32
   MAX-ACCESS  read-only
   STATUS      current
   DESCRIPTION
       "The number of Received V2 Leaves. "
   ::= { gs2326plusIGMPSnoopingstatisticEntry 10 }

gs2326plusIGMPSnoopingRouterPortTable OBJECT-TYPE
   SYNTAX      SEQUENCE OF Gs2326plusIGMPSnoopingRouterPortEntry
   MAX-ACCESS  not-accessible
   STATUS      current
   DESCRIPTION
       " Configure Vlan Port Isolation Configuration. "
   ::= { gs2326plusIGMPSnoopingStatus 3 }

gs2326plusIGMPSnoopingRouterPortEntry OBJECT-TYPE
   SYNTAX      Gs2326plusIGMPSnoopingRouterPortEntry
   MAX-ACCESS  not-accessible
   STATUS      current
   DESCRIPTION
       ""
   INDEX    { ifIndex  }
   ::= { gs2326plusIGMPSnoopingRouterPortTable 1 }

Gs2326plusIGMPSnoopingRouterPortEntry ::= SEQUENCE {
   gs2326plusIGMPSnoopingRouterPortStatus            DisplayString
}

gs2326plusIGMPSnoopingRouterPortStatus OBJECT-TYPE
   SYNTAX      DisplayString
   MAX-ACCESS  read-only
   STATUS      current
   DESCRIPTION
       "Display which ports act as router ports. A router port is a port on the
       Ethernet switch that leads towards the Layer 3 multicast device or IGMP
       querier.
       Static denotes the specific port is configured to be a router port.
       Dynamic denotes the specific port is learnt to be a router port.
       Both denote the specific port is configured or learnt to be a router port. "
   ::= { gs2326plusIGMPSnoopingRouterPortEntry 1 }

gs2326plusIGMPSnoopingGroupsTable OBJECT-TYPE
   SYNTAX      SEQUENCE OF Gs2326plusIGMPSnoopingGroupsEntry
   MAX-ACCESS  not-accessible
   STATUS      current
   DESCRIPTION
       "IGMP Snooping Groups Information . "
   ::= { gs2326plusIGMPSnooping 5 }

gs2326plusIGMPSnoopingGroupsEntry OBJECT-TYPE
   SYNTAX      Gs2326plusIGMPSnoopingGroupsEntry
   MAX-ACCESS  not-accessible
   STATUS      current
   DESCRIPTION
       ""
   INDEX    { gs2326plusIGMPSnoopingGroupsIndex  }
   ::= { gs2326plusIGMPSnoopingGroupsTable 1 }

Gs2326plusIGMPSnoopingGroupsEntry ::= SEQUENCE {
   gs2326plusIGMPSnoopingGroupsIndex          Integer32,
   gs2326plusIGMPSnoopingGroupsVLANID         Integer32,
   gs2326plusIGMPSnoopingGroups               InetAddress,
   gs2326plusIGMPSnoopingGroupsMemberships    DisplayString
}

gs2326plusIGMPSnoopingGroupsIndex OBJECT-TYPE
   SYNTAX      Integer32(1..65535)
   MAX-ACCESS  not-accessible
   STATUS      current
   DESCRIPTION
       "IGMP Snooping Groups Index"
   ::= { gs2326plusIGMPSnoopingGroupsEntry 1 }

gs2326plusIGMPSnoopingGroupsVLANID OBJECT-TYPE
   SYNTAX      Integer32(1..4095)
   MAX-ACCESS  read-only
   STATUS      current
   DESCRIPTION
       "VLAN ID of the group. "
   ::= { gs2326plusIGMPSnoopingGroupsEntry 2 }

gs2326plusIGMPSnoopingGroups OBJECT-TYPE
   SYNTAX      DisplayString
   MAX-ACCESS  read-only
   STATUS      current
   DESCRIPTION
       "Group address of the group displayed."
   ::= { gs2326plusIGMPSnoopingGroupsEntry 3 }

gs2326plusIGMPSnoopingGroupsMemberships OBJECT-TYPE
   SYNTAX      DisplayString
   MAX-ACCESS  read-only
   STATUS      current
   DESCRIPTION
       "Ports under this group."
   ::= { gs2326plusIGMPSnoopingGroupsEntry 4 }

gs2326plusIGMPSnoopingSSMTable OBJECT-TYPE
   SYNTAX      SEQUENCE OF Gs2326plusIGMPSnoopingSSMEntry
   MAX-ACCESS  not-accessible
   STATUS      current
   DESCRIPTION
       "The IGMP SFM (Source-Filtered Multicast) Information Table also contains
        the SSM (Source-Specific Multicast) information. This table is sorted
         first by VLAN ID, then by group, and then by Port. Different source
         addresses belong to the same group are treated as single entry."
   ::= { gs2326plusIGMPSnooping 6 }

gs2326plusIGMPSnoopingSSMEntry OBJECT-TYPE
   SYNTAX      Gs2326plusIGMPSnoopingSSMEntry
   MAX-ACCESS  not-accessible
   STATUS      current
   DESCRIPTION
       ""
   INDEX    { gs2326plusIGMPSnoopingSSMIndex  }
   ::= { gs2326plusIGMPSnoopingSSMTable 1 }

Gs2326plusIGMPSnoopingSSMEntry ::= SEQUENCE {
   gs2326plusIGMPSnoopingSSMIndex          Integer32,
   gs2326plusIGMPSnoopingSSMVLANID         Integer32,
   gs2326plusIGMPSnoopingSSMGroup          DisplayString,
   gs2326plusIGMPSnoopingSSMPort           Integer32,
   gs2326plusIGMPSnoopingSSMMode           DisplayString,
   gs2326plusIGMPSnoopingSSMSourceAddress  DisplayString,
   gs2326plusIGMPSnoopingSSMType           DisplayString
}

gs2326plusIGMPSnoopingSSMIndex OBJECT-TYPE
   SYNTAX      Integer32(1..65535)
   MAX-ACCESS  not-accessible
   STATUS      current
   DESCRIPTION
       "IGMP Snooping SSM Index"
   ::= { gs2326plusIGMPSnoopingSSMEntry 1 }

gs2326plusIGMPSnoopingSSMVLANID OBJECT-TYPE
   SYNTAX      Integer32(1..4095)
   MAX-ACCESS  read-only
   STATUS      current
   DESCRIPTION
       "VLAN ID of the group. "
   ::= { gs2326plusIGMPSnoopingSSMEntry 2 }

gs2326plusIGMPSnoopingSSMGroup OBJECT-TYPE
   SYNTAX      DisplayString
   MAX-ACCESS  read-only
   STATUS      current
   DESCRIPTION
       "Group address of the group displayed."
   ::= { gs2326plusIGMPSnoopingSSMEntry 3 }

gs2326plusIGMPSnoopingSSMPort OBJECT-TYPE
   SYNTAX      Integer32(1..65535)
   MAX-ACCESS  read-only
   STATUS      current
   DESCRIPTION
       "Ports under this group."
   ::= { gs2326plusIGMPSnoopingSSMEntry 4 }

gs2326plusIGMPSnoopingSSMMode OBJECT-TYPE
   SYNTAX      DisplayString
   MAX-ACCESS  read-only
   STATUS      current
   DESCRIPTION
       "Indicates the filtering mode maintained per (VLAN ID, port number,
       Group Address) basis. It can be either Include or Exclude."
   ::= { gs2326plusIGMPSnoopingSSMEntry 5 }

gs2326plusIGMPSnoopingSSMSourceAddress OBJECT-TYPE
   SYNTAX      DisplayString
   MAX-ACCESS  read-only
   STATUS      current
   DESCRIPTION
       "IP Address of the source. Currently, system limits the total number of
       IP source addresses for filtering to be 128."
   ::= { gs2326plusIGMPSnoopingSSMEntry 6 }

gs2326plusIGMPSnoopingSSMType OBJECT-TYPE
   SYNTAX      DisplayString
   MAX-ACCESS  read-only
   STATUS      current
   DESCRIPTION
       "Indicates the Type. It can be either Allow or Deny."
   ::= { gs2326plusIGMPSnoopingSSMEntry 7 }

gs2326plusMLDSnooping                                                           OBJECT IDENTIFIER ::= { gs2326plusConfiguration 17 }

gs2326plusMLDSnoopingBasic                                                      OBJECT IDENTIFIER ::= { gs2326plusMLDSnooping 1 }

gs2326plusMLDSnoopingEnable  OBJECT-TYPE
   SYNTAX      INTEGER { disable(0), enable(1) }
   MAX-ACCESS  read-write
   STATUS      current
   DESCRIPTION
       "Enable/Disable the Global MLD Snooping"
   ::= { gs2326plusMLDSnoopingBasic 1 }

gs2326plusMLDSnoopingUnregisteredIPMCv6Flooding  OBJECT-TYPE
   SYNTAX      INTEGER { disable(0), enable(1) }
   MAX-ACCESS  read-write
   STATUS      current
   DESCRIPTION
       "Enable/Disable unregistered IPMCv6 traffic flooding. "
   ::= { gs2326plusMLDSnoopingBasic 2 }

gs2326plusMLDSnoopingSSMIPRangeAddr  OBJECT-TYPE
   SYNTAX      DisplayString
   MAX-ACCESS  read-write
   STATUS      current
   DESCRIPTION
       "SSM (Source-Specific Multicast) Range allows the SSM-aware hosts and
       routers run the SSM service model for the groups in the address range. "
   ::= { gs2326plusMLDSnoopingBasic 3 }

gs2326plusMLDSnoopingSSMIPRangeValue  OBJECT-TYPE
   SYNTAX      Integer32(8..128)
   MAX-ACCESS  read-write
   STATUS      current
   DESCRIPTION
       "SSM (Source-Specific Multicast) Range allows the SSM-aware hosts and
       routers run the SSM service model for the groups in the address range value. "
   ::= { gs2326plusMLDSnoopingBasic 4 }

gs2326plusMLDSnoopingProxyEnabled  OBJECT-TYPE
   SYNTAX      INTEGER { disable(0), enable(1) }
   MAX-ACCESS  read-write
   STATUS      current
   DESCRIPTION
       "Enable/Disable MLD Proxy. This feature can be used to avoid forwarding
       unnecessary join and leave messages to the router side. "
   ::= { gs2326plusMLDSnoopingBasic 5 }

gs2326plusMLDSnoopingPortRelatedTable OBJECT-TYPE
   SYNTAX      SEQUENCE OF Gs2326plusMLDSnoopingPortRelatedEntry
   MAX-ACCESS  not-accessible
   STATUS      current
   DESCRIPTION
       " Configure MLD Snooping Port Related Configuration. "
   ::= { gs2326plusMLDSnoopingBasic 6 }

gs2326plusMLDSnoopingPortRelatedEntry OBJECT-TYPE
   SYNTAX      Gs2326plusMLDSnoopingPortRelatedEntry
   MAX-ACCESS  not-accessible
   STATUS      current
   DESCRIPTION
       ""
   INDEX    { ifIndex  }
   ::= { gs2326plusMLDSnoopingPortRelatedTable 1 }

Gs2326plusMLDSnoopingPortRelatedEntry ::= SEQUENCE {
   gs2326plusMLDSnoopingRouterPort	INTEGER,
   gs2326plusMLDSnoopingFastLeave  	INTEGER,
   gs2326plusMLDSnoopingThrottling    Integer32
}

gs2326plusMLDSnoopingRouterPort OBJECT-TYPE
   SYNTAX      INTEGER { disable(0), enable(1) }
   MAX-ACCESS  read-write
   STATUS      current
   DESCRIPTION
       "Specify which ports act as router ports. A router port is a port on the
       Ethernet switch that leads towards the Layer 3 multicast device or IGMP
       querier. If an aggregation member port is selected as a router port, the
       whole aggregation will act as a router port. "
   ::= { gs2326plusMLDSnoopingPortRelatedEntry 1 }

gs2326plusMLDSnoopingFastLeave OBJECT-TYPE
   SYNTAX      INTEGER { disable(0), enable(1) }
   MAX-ACCESS  read-write
   STATUS      current
   DESCRIPTION
       "Enable/Disable the fast leave on the port. "
   ::= { gs2326plusMLDSnoopingPortRelatedEntry 2 }

gs2326plusMLDSnoopingThrottling OBJECT-TYPE
   SYNTAX      Integer32(0..10)
   MAX-ACCESS  read-write
   STATUS      current
   DESCRIPTION
       "Enable to limit the number of multicast groups to which a switch port can belong.
       0: unlimited"
   ::= { gs2326plusMLDSnoopingPortRelatedEntry 3 }

gs2326plusMLDSnoopingVLANTable OBJECT-TYPE
   SYNTAX      SEQUENCE OF Gs2326plusMLDSnoopingVLANEntry
   MAX-ACCESS  not-accessible
   STATUS      current
   DESCRIPTION
       " Configure MLD Snooping Vlan Configuration. "
   ::= { gs2326plusMLDSnooping 2 }

gs2326plusMLDSnoopingVLANEntry OBJECT-TYPE
   SYNTAX      Gs2326plusMLDSnoopingVLANEntry
   MAX-ACCESS  not-accessible
   STATUS      current
   DESCRIPTION
       ""
   INDEX    { gs2326plusMLDSnoopingVLANID  }
   ::= { gs2326plusMLDSnoopingVLANTable 1 }

Gs2326plusMLDSnoopingVLANEntry ::= SEQUENCE {
   gs2326plusMLDSnoopingVLANID        	Integer32,
   gs2326plusMLDSnoopingVLANEnable    	INTEGER,
   gs2326plusMLDSnoopingVLANIGMPQuerier   INTEGER,
   gs2326plusMLDSnoopingVLANCompatibility INTEGER,
   gs2326plusMLDSnoopingVLANRV        	Integer32,
   gs2326plusMLDSnoopingVLANQI      	    Integer32,
   gs2326plusMLDSnoopingVLANQRI   	    Integer32,
   gs2326plusMLDSnoopingVLANLLQI   	    Integer32,
   gs2326plusMLDSnoopingVLANURI    	    Integer32
}

gs2326plusMLDSnoopingVLANID OBJECT-TYPE
   SYNTAX      Integer32(1..4095)
   MAX-ACCESS  read-write
   STATUS      current
   DESCRIPTION
       "The VLAN ID of the entry"
   ::= { gs2326plusMLDSnoopingVLANEntry 1 }

gs2326plusMLDSnoopingVLANEnable OBJECT-TYPE
   SYNTAX      INTEGER { disable(0), enable(1) }
   MAX-ACCESS  read-write
   STATUS      current
   DESCRIPTION
       "Enable/Disable the per-VLAN MLD Snooping. Up to 32 VLANs can be
       selected for MLD Snooping. "
   ::= { gs2326plusMLDSnoopingVLANEntry 2 }

gs2326plusMLDSnoopingVLANIGMPQuerier OBJECT-TYPE
   SYNTAX      INTEGER { disable(0), enable(1) }
   MAX-ACCESS  read-write
   STATUS      current
   DESCRIPTION
       "Enable/Disable the MLD Querier in the VLAN. "
   ::= { gs2326plusMLDSnoopingVLANEntry 3 }

gs2326plusMLDSnoopingVLANCompatibility OBJECT-TYPE
   SYNTAX      INTEGER { mldAuto(0), forcedMLDv1(1), forcedMLDv2(2), none(3) }
   MAX-ACCESS  read-write
   STATUS      current
   DESCRIPTION
       "Compatibility is maintained by hosts and routers taking appropriate
       actions depending on the versions of IGMP operating on hosts and routers
       within a network. The allowed selection is MLD-Auto, Forced MLDv1,
       Forced MLDv2, default compatibility value is IGMP-Auto. "
   ::= { gs2326plusMLDSnoopingVLANEntry 4 }

gs2326plusMLDSnoopingVLANRV OBJECT-TYPE
   SYNTAX      Integer32(-1|1..255)
   MAX-ACCESS  read-write
   STATUS      current
   DESCRIPTION
       "Robustness Variable. The Robustness Variable allows tuning for the
       expected packet loss on a network. The allowed range is 1 to 255, default
        robustness variable value is 2. (-1: none)"
   ::= { gs2326plusMLDSnoopingVLANEntry 5 }

gs2326plusMLDSnoopingVLANQI OBJECT-TYPE
   SYNTAX      Integer32(-1|1..31744)
   MAX-ACCESS  read-write
   STATUS      current
   DESCRIPTION
       "Query Interval. The Query Interval is the interval between General
       Queries sent by the Querier. The allowed range is 1 to 31744 seconds,
       default query interval is 125 seconds.  (-1: none)"
   ::= { gs2326plusMLDSnoopingVLANEntry 6 }

gs2326plusMLDSnoopingVLANQRI OBJECT-TYPE
   SYNTAX      Integer32(-1|0..31744)
   MAX-ACCESS  read-write
   STATUS      current
   DESCRIPTION
       "Query Response Interval. The Maximum Response Delay used to calculate
       the Maximum Response Code inserted into the periodic General Queries. The
        allowed range is 0 to 31744 in tenths of seconds, default query response
         interval is 100 in tenths of seconds (10 seconds).   (-1: none)"
   ::= { gs2326plusMLDSnoopingVLANEntry 7 }

gs2326plusMLDSnoopingVLANLLQI OBJECT-TYPE
   SYNTAX      Integer32(-1|0..31744)
   MAX-ACCESS  read-write
   STATUS      current
   DESCRIPTION
       "LLQI (LMQI for MLD).  Last Member Query Interval. The Last Member Query
       Time is the time value represented by the Last Member Query Interval,
       multiplied by the Last Member Query Count. The allowed range is 0 to
       31744 in tenths of seconds, default last member query interval is 10 in
       tenths of seconds (1 second).    (-1: none)"
   ::= { gs2326plusMLDSnoopingVLANEntry 8 }

gs2326plusMLDSnoopingVLANURI OBJECT-TYPE
   SYNTAX      Integer32(-1|0..31744)
   MAX-ACCESS  read-write
   STATUS      current
   DESCRIPTION
       "Unsolicited Report Interval. The Unsolicited Report Interval is the time
        between repetitions of a host's initial report of membership in a group.
         The allowed range is 0 to 31744 seconds, default unsolicited report
         interval is 1 second.    (-1: none)"
   ::= { gs2326plusMLDSnoopingVLANEntry 9 }

gs2326plusMLDSnoopingPortGroupFiltering                                                      OBJECT IDENTIFIER ::= { gs2326plusMLDSnooping 3 }

gs2326plusMLDSnoopingPortGroupFilteringCreate OBJECT-TYPE
   SYNTAX       Integer32
   MAX-ACCESS   read-write
   STATUS       current
   DESCRIPTION
       "default: 0
       0 : None  (read only) 1 : Create MLD Snooping Port Group Filtering "
   ::= { gs2326plusMLDSnoopingPortGroupFiltering 1 }

gs2326plusMLDSnoopingPortGroupFilteringTable OBJECT-TYPE
   SYNTAX      SEQUENCE OF Gs2326plusMLDSnoopingPortGroupFilteringEntry
   MAX-ACCESS  not-accessible
   STATUS      current
   DESCRIPTION
       " Configure MLD Snooping port group filtering. "
   ::= { gs2326plusMLDSnoopingPortGroupFiltering 2 }

gs2326plusMLDSnoopingPortGroupFilteringEntry OBJECT-TYPE
   SYNTAX      Gs2326plusMLDSnoopingPortGroupFilteringEntry
   MAX-ACCESS  not-accessible
   STATUS      current
   DESCRIPTION
       ""
   INDEX    { gs2326plusMLDSnoopingPortGroupFilteringIndex  }
   ::= { gs2326plusMLDSnoopingPortGroupFilteringTable 1 }

Gs2326plusMLDSnoopingPortGroupFilteringEntry ::= SEQUENCE {
   gs2326plusMLDSnoopingPortGroupFilteringIndex         Integer32,
   gs2326plusMLDSnoopingPortGroupFilteringPort          Integer32,
   gs2326plusMLDSnoopingPortGroupFilteringGroups        DisplayString,
   gs2326plusMLDSnoopingPortGroupFilteringRowStatus     INTEGER
}

gs2326plusMLDSnoopingPortGroupFilteringIndex OBJECT-TYPE
   SYNTAX      Integer32(1..65535)
   MAX-ACCESS  not-accessible
   STATUS      current
   DESCRIPTION
       "MLD Snooping Port Group Filtering Configuration Index. "
   ::= { gs2326plusMLDSnoopingPortGroupFilteringEntry 1 }

gs2326plusMLDSnoopingPortGroupFilteringPort OBJECT-TYPE
   SYNTAX      Integer32(1..65535)
   MAX-ACCESS  read-write
   STATUS      current
   DESCRIPTION
       "The logical port for the settings. "
   ::= { gs2326plusMLDSnoopingPortGroupFilteringEntry 2 }

gs2326plusMLDSnoopingPortGroupFilteringGroups OBJECT-TYPE
   SYNTAX      DisplayString
   MAX-ACCESS  read-write
   STATUS      current
   DESCRIPTION
       "The IP Multicast Group that will be filtered. "
   ::= { gs2326plusMLDSnoopingPortGroupFilteringEntry 3 }

gs2326plusMLDSnoopingPortGroupFilteringRowStatus OBJECT-TYPE
   SYNTAX      INTEGER { active(1), notInservice(2), destroy(4)}
   MAX-ACCESS  read-write
   STATUS      current
   DESCRIPTION
       "1: active
        2: notInservice
        4: destroy"
   ::= { gs2326plusMLDSnoopingPortGroupFilteringEntry 4 }

gs2326plusMLDSnoopingStatus                                                      OBJECT IDENTIFIER ::= { gs2326plusMLDSnooping 4 }

gs2326plusMLDSnoopingstatisticClear OBJECT-TYPE
   SYNTAX      INTEGER { none(0), clear(1)}
   MAX-ACCESS  read-write
   STATUS      current
   DESCRIPTION
       "Clears all Statistics counters."
   ::= { gs2326plusMLDSnoopingStatus 1 }


gs2326plusMLDSnoopingstatisticTable OBJECT-TYPE
   SYNTAX      SEQUENCE OF Gs2326plusMLDSnoopingstatisticEntry
   MAX-ACCESS  not-accessible
   STATUS      current
   DESCRIPTION
       " Configure Vlan Port Isolation Configuration. "
   ::= { gs2326plusMLDSnoopingStatus 2 }

gs2326plusMLDSnoopingstatisticEntry OBJECT-TYPE
   SYNTAX      Gs2326plusMLDSnoopingstatisticEntry
   MAX-ACCESS  not-accessible
   STATUS      current
   DESCRIPTION
       ""
   INDEX    { gs2326plusMLDSnoopingstatisticVLANID  }
   ::= { gs2326plusMLDSnoopingstatisticTable 1 }

Gs2326plusMLDSnoopingstatisticEntry ::= SEQUENCE {
   gs2326plusMLDSnoopingstatisticVLANID              Integer32,
   gs2326plusMLDSnoopingstatisticQuerierVersion      DisplayString,
   gs2326plusMLDSnoopingstatisticHostVersion         DisplayString,
   gs2326plusMLDSnoopingstatisticQuerierStatus       DisplayString,
   gs2326plusMLDSnoopingstatisticQueriesTransmitted  Counter32,
   gs2326plusMLDSnoopingstatisticQueriesReceived     Counter32,
   gs2326plusMLDSnoopingstatisticV1ReportsReceived   Counter32,
   gs2326plusMLDSnoopingstatisticV2ReportsReceived   Counter32,
   gs2326plusMLDSnoopingstatisticV1LeavesReceived    Counter32
}


gs2326plusMLDSnoopingstatisticVLANID OBJECT-TYPE
   SYNTAX      Integer32(1..4095)
   MAX-ACCESS  read-only
   STATUS      current
   DESCRIPTION
       "The VLAN ID of the entry. "
   ::= { gs2326plusMLDSnoopingstatisticEntry 1 }

gs2326plusMLDSnoopingstatisticQuerierVersion OBJECT-TYPE
   SYNTAX      DisplayString
   MAX-ACCESS  read-only
   STATUS      current
   DESCRIPTION
       "Working Querier Version currently. "
   ::= { gs2326plusMLDSnoopingstatisticEntry 2 }

gs2326plusMLDSnoopingstatisticHostVersion OBJECT-TYPE
   SYNTAX      DisplayString
   MAX-ACCESS  read-only
   STATUS      current
   DESCRIPTION
       "Working Host Version currently. "
   ::= { gs2326plusMLDSnoopingstatisticEntry 3 }

gs2326plusMLDSnoopingstatisticQuerierStatus OBJECT-TYPE
   SYNTAX      DisplayString
   MAX-ACCESS  read-only
   STATUS      current
   DESCRIPTION
       "Shows the Querier status is ACTIVE or IDLE. DISABLE denotes the specific
        interface is administratively disabled. "
   ::= { gs2326plusMLDSnoopingstatisticEntry 4 }

gs2326plusMLDSnoopingstatisticQueriesTransmitted OBJECT-TYPE
   SYNTAX      Counter32
   MAX-ACCESS  read-only
   STATUS      current
   DESCRIPTION
       "The number of Transmitted Queries. "
   ::= { gs2326plusMLDSnoopingstatisticEntry 5 }

gs2326plusMLDSnoopingstatisticQueriesReceived OBJECT-TYPE
   SYNTAX      Counter32
   MAX-ACCESS  read-only
   STATUS      current
   DESCRIPTION
       "The number of Received Queries. "
   ::= { gs2326plusMLDSnoopingstatisticEntry 6 }

gs2326plusMLDSnoopingstatisticV1ReportsReceived OBJECT-TYPE
   SYNTAX      Counter32
   MAX-ACCESS  read-only
   STATUS      current
   DESCRIPTION
       "The number of Received V1 Reports. "
   ::= { gs2326plusMLDSnoopingstatisticEntry 7 }

gs2326plusMLDSnoopingstatisticV2ReportsReceived OBJECT-TYPE
   SYNTAX      Counter32
   MAX-ACCESS  read-only
   STATUS      current
   DESCRIPTION
       "The number of Received V2 Reports. "
   ::= { gs2326plusMLDSnoopingstatisticEntry 8 }

gs2326plusMLDSnoopingstatisticV1LeavesReceived OBJECT-TYPE
   SYNTAX      Counter32
   MAX-ACCESS  read-only
   STATUS      current
   DESCRIPTION
       "The number of Received V1 Leaves. "
   ::= { gs2326plusMLDSnoopingstatisticEntry 9 }

gs2326plusMLDSnoopingRouterPortTable OBJECT-TYPE
   SYNTAX      SEQUENCE OF Gs2326plusMLDSnoopingRouterPortEntry
   MAX-ACCESS  not-accessible
   STATUS      current
   DESCRIPTION
       " Configure Vlan Port Isolation Configuration. "
   ::= { gs2326plusMLDSnoopingStatus 3 }

gs2326plusMLDSnoopingRouterPortEntry OBJECT-TYPE
   SYNTAX      Gs2326plusMLDSnoopingRouterPortEntry
   MAX-ACCESS  not-accessible
   STATUS      current
   DESCRIPTION
       ""
   INDEX    { ifIndex  }
   ::= { gs2326plusMLDSnoopingRouterPortTable 1 }

Gs2326plusMLDSnoopingRouterPortEntry ::= SEQUENCE {
   gs2326plusMLDSnoopingRouterPortStatus            DisplayString
}

gs2326plusMLDSnoopingRouterPortStatus OBJECT-TYPE
   SYNTAX      DisplayString
   MAX-ACCESS  read-only
   STATUS      current
   DESCRIPTION
       "Display which ports act as router ports. A router port is a port on the
       Ethernet switch that leads towards the Layer 3 multicast device or IGMP
       querier.
       Static denotes the specific port is configured to be a router port.
       Dynamic denotes the specific port is learnt to be a router port.
       Both denote the specific port is configured or learnt to be a router port. "
   ::= { gs2326plusMLDSnoopingRouterPortEntry 1 }

gs2326plusMLDSnoopingGroupsTable OBJECT-TYPE
   SYNTAX      SEQUENCE OF Gs2326plusMLDSnoopingGroupsEntry
   MAX-ACCESS  not-accessible
   STATUS      current
   DESCRIPTION
       "MLD Snooping Groups Information . "
   ::= { gs2326plusMLDSnooping 5 }

gs2326plusMLDSnoopingGroupsEntry OBJECT-TYPE
   SYNTAX      Gs2326plusMLDSnoopingGroupsEntry
   MAX-ACCESS  not-accessible
   STATUS      current
   DESCRIPTION
       ""
   INDEX    { gs2326plusMLDSnoopingGroupsIndex  }
   ::= { gs2326plusMLDSnoopingGroupsTable 1 }

Gs2326plusMLDSnoopingGroupsEntry ::= SEQUENCE {
   gs2326plusMLDSnoopingGroupsIndex          Integer32,
   gs2326plusMLDSnoopingGroupsVLANID         Integer32,
   gs2326plusMLDSnoopingGroups               InetAddress,
   gs2326plusMLDSnoopingGroupsMemberships    DisplayString
}

gs2326plusMLDSnoopingGroupsIndex OBJECT-TYPE
   SYNTAX      Integer32(1..65535)
   MAX-ACCESS  not-accessible
   STATUS      current
   DESCRIPTION
       "MLD Snooping Groups Index"
   ::= { gs2326plusMLDSnoopingGroupsEntry 1 }

gs2326plusMLDSnoopingGroupsVLANID OBJECT-TYPE
   SYNTAX      Integer32(1..4095)
   MAX-ACCESS  read-only
   STATUS      current
   DESCRIPTION
       "VLAN ID of the group. "
   ::= { gs2326plusMLDSnoopingGroupsEntry 2 }

gs2326plusMLDSnoopingGroups OBJECT-TYPE
   SYNTAX      DisplayString
   MAX-ACCESS  read-only
   STATUS      current
   DESCRIPTION
       "Group address of the group displayed."
   ::= { gs2326plusMLDSnoopingGroupsEntry 3 }

gs2326plusMLDSnoopingGroupsMemberships OBJECT-TYPE
   SYNTAX      DisplayString
   MAX-ACCESS  read-only
   STATUS      current
   DESCRIPTION
       "Ports under this group."
   ::= { gs2326plusMLDSnoopingGroupsEntry 4 }

gs2326plusMLDSnoopingSSMTable OBJECT-TYPE
   SYNTAX      SEQUENCE OF Gs2326plusMLDSnoopingSSMEntry
   MAX-ACCESS  not-accessible
   STATUS      current
   DESCRIPTION
       "The MLD SFM (Source-Filtered Multicast) Information Table also contains
        the SSM (Source-Specific Multicast) information. This table is sorted
         first by VLAN ID, then by group, and then by Port. Different source
         addresses belong to the same group are treated as single entry."
   ::= { gs2326plusMLDSnooping 6 }

gs2326plusMLDSnoopingSSMEntry OBJECT-TYPE
   SYNTAX      Gs2326plusMLDSnoopingSSMEntry
   MAX-ACCESS  not-accessible
   STATUS      current
   DESCRIPTION
       ""
   INDEX    { gs2326plusMLDSnoopingSSMIndex  }
   ::= { gs2326plusMLDSnoopingSSMTable 1 }

Gs2326plusMLDSnoopingSSMEntry ::= SEQUENCE {
   gs2326plusMLDSnoopingSSMIndex          Integer32,
   gs2326plusMLDSnoopingSSMVLANID         Integer32,
   gs2326plusMLDSnoopingSSMGroup          DisplayString,
   gs2326plusMLDSnoopingSSMPort           Integer32,
   gs2326plusMLDSnoopingSSMMode           DisplayString,
   gs2326plusMLDSnoopingSSMSourceAddress  DisplayString,
   gs2326plusMLDSnoopingSSMType           DisplayString
}

gs2326plusMLDSnoopingSSMIndex OBJECT-TYPE
   SYNTAX      Integer32(1..65535)
   MAX-ACCESS  not-accessible
   STATUS      current
   DESCRIPTION
       "MLD Snooping SSM Index"
   ::= { gs2326plusMLDSnoopingSSMEntry 1 }

gs2326plusMLDSnoopingSSMVLANID OBJECT-TYPE
   SYNTAX      Integer32(1..4095)
   MAX-ACCESS  read-only
   STATUS      current
   DESCRIPTION
       "VLAN ID of the group. "
   ::= { gs2326plusMLDSnoopingSSMEntry 2 }

gs2326plusMLDSnoopingSSMGroup OBJECT-TYPE
   SYNTAX      DisplayString
   MAX-ACCESS  read-only
   STATUS      current
   DESCRIPTION
       "Group address of the group displayed."
   ::= { gs2326plusMLDSnoopingSSMEntry 3 }

gs2326plusMLDSnoopingSSMPort OBJECT-TYPE
   SYNTAX      Integer32(1..65535)
   MAX-ACCESS  read-only
   STATUS      current
   DESCRIPTION
       "Ports under this group."
   ::= { gs2326plusMLDSnoopingSSMEntry 4 }

gs2326plusMLDSnoopingSSMMode OBJECT-TYPE
   SYNTAX      DisplayString
   MAX-ACCESS  read-only
   STATUS      current
   DESCRIPTION
       "Indicates the filtering mode maintained per (VLAN ID, port number,
       Group Address) basis. It can be either Include or Exclude."
   ::= { gs2326plusMLDSnoopingSSMEntry 5 }

gs2326plusMLDSnoopingSSMSourceAddress OBJECT-TYPE
   SYNTAX      DisplayString
   MAX-ACCESS  read-only
   STATUS      current
   DESCRIPTION
       "IP Address of the source. Currently, system limits the total number of
       IP source addresses for filtering to be 128."
   ::= { gs2326plusMLDSnoopingSSMEntry 6 }

gs2326plusMLDSnoopingSSMType OBJECT-TYPE
   SYNTAX      DisplayString
   MAX-ACCESS  read-only
   STATUS      current
   DESCRIPTION
       "Indicates the Type. It can be either Allow or Deny."
   ::= { gs2326plusMLDSnoopingSSMEntry 7 }


gs2326plusMVR                                                                   OBJECT IDENTIFIER ::= { gs2326plusConfiguration 18 }

gs2326plusMVRConfiguration                                                      OBJECT IDENTIFIER ::= { gs2326plusMVR 1 }

gs2326plusMVRMode  OBJECT-TYPE
   SYNTAX      INTEGER { disable(0), enable(1) }
   MAX-ACCESS  read-write
   STATUS      current
   DESCRIPTION
       "Enable/Disable the Global MVR. "
   ::= { gs2326plusMVRConfiguration 1 }

gs2326plusMVRVLANId  OBJECT-TYPE
   SYNTAX      Integer32(1..4094)
   MAX-ACCESS  read-write
   STATUS      current
   DESCRIPTION
       "Specify the Multicast VLAN ID. "
   ::= { gs2326plusMVRConfiguration 2 }

gs2326plusMVRPortConfigurationTable OBJECT-TYPE
   SYNTAX      SEQUENCE OF Gs2326plusMVRPortConfigurationEntry
   MAX-ACCESS  not-accessible
   STATUS      current
   DESCRIPTION
       " Configure MVR Port Configuration. "
   ::= { gs2326plusMVRConfiguration 3 }

gs2326plusMVRPortConfigurationEntry OBJECT-TYPE
   SYNTAX      Gs2326plusMVRPortConfigurationEntry
   MAX-ACCESS  not-accessible
   STATUS      current
   DESCRIPTION
       ""
   INDEX    { ifIndex  }
   ::= { gs2326plusMVRPortConfigurationTable 1 }

Gs2326plusMVRPortConfigurationEntry ::= SEQUENCE {
   gs2326plusMVRPortConfigurationMode	INTEGER,
   gs2326plusMVRPortConfigurationType  	INTEGER,
   gs2326plusMVRPortConfigurationImmediateLeave    INTEGER
}

gs2326plusMVRPortConfigurationMode OBJECT-TYPE
   SYNTAX      INTEGER { disable(0), enable(1) }
   MAX-ACCESS  read-write
   STATUS      current
   DESCRIPTION
       "Enable MVR on the port. "
   ::= { gs2326plusMVRPortConfigurationEntry 1 }

gs2326plusMVRPortConfigurationType OBJECT-TYPE
   SYNTAX      INTEGER { receiver(0), source(1) }
   MAX-ACCESS  read-write
   STATUS      current
   DESCRIPTION
       "Specify the MVR port type on the port. "
   ::= { gs2326plusMVRPortConfigurationEntry 2 }

gs2326plusMVRPortConfigurationImmediateLeave OBJECT-TYPE
   SYNTAX      INTEGER { disable(0), enable(1) }
   MAX-ACCESS  read-write
   STATUS      current
   DESCRIPTION
       "Enable the fast leave on the port. "
   ::= { gs2326plusMVRPortConfigurationEntry 3 }


gs2326plusMVRPortGroupFiltering                                                      OBJECT IDENTIFIER ::= { gs2326plusMVR 2 }

gs2326plusMVRPortGroupFilteringCreate OBJECT-TYPE
   SYNTAX       Integer32
   MAX-ACCESS   read-write
   STATUS       current
   DESCRIPTION
       "default: 0
       0 : None  (read only) 1 : Create MLD Snooping Port Group Filtering "
   ::= { gs2326plusMVRPortGroupFiltering 1 }

gs2326plusMVRPortGroupFilteringTable OBJECT-TYPE
   SYNTAX      SEQUENCE OF Gs2326plusMVRPortGroupFilteringEntry
   MAX-ACCESS  not-accessible
   STATUS      current
   DESCRIPTION
       " Configure MVR port group filtering. "
   ::= { gs2326plusMVRPortGroupFiltering 2 }

gs2326plusMVRPortGroupFilteringEntry OBJECT-TYPE
   SYNTAX      Gs2326plusMVRPortGroupFilteringEntry
   MAX-ACCESS  not-accessible
   STATUS      current
   DESCRIPTION
       ""
   INDEX    { gs2326plusMVRPortGroupFilteringIndex  }
   ::= { gs2326plusMVRPortGroupFilteringTable 1 }

Gs2326plusMVRPortGroupFilteringEntry ::= SEQUENCE {
   gs2326plusMVRPortGroupFilteringIndex         Integer32,
   gs2326plusMVRPortGroupFilteringPort          Integer32,
   gs2326plusMVRPortGroupFilteringStartGroups   DisplayString,
   gs2326plusMVRPortGroupFilteringEndGroups     DisplayString,
   gs2326plusMVRPortGroupFilteringRowStatus     INTEGER
}

gs2326plusMVRPortGroupFilteringIndex OBJECT-TYPE
   SYNTAX      Integer32(1..65535)
   MAX-ACCESS  not-accessible
   STATUS      current
   DESCRIPTION
       "MVR Port Group Filtering Configuration Index. "
   ::= { gs2326plusMVRPortGroupFilteringEntry 1 }

gs2326plusMVRPortGroupFilteringPort OBJECT-TYPE
   SYNTAX      Integer32(1..65535)
   MAX-ACCESS  read-write
   STATUS      current
   DESCRIPTION
       "The logical port for the settings. "
   ::= { gs2326plusMVRPortGroupFilteringEntry 2 }

gs2326plusMVRPortGroupFilteringStartGroups OBJECT-TYPE
   SYNTAX      DisplayString
   MAX-ACCESS  read-write
   STATUS      current
   DESCRIPTION
       "The IP Multicast Group that will be allowed. "
   ::= { gs2326plusMVRPortGroupFilteringEntry 3 }

gs2326plusMVRPortGroupFilteringEndGroups OBJECT-TYPE
   SYNTAX      DisplayString
   MAX-ACCESS  read-write
   STATUS      current
   DESCRIPTION
       "The IP Multicast Group that will be allowed. "
   ::= { gs2326plusMVRPortGroupFilteringEntry 4 }

gs2326plusMVRPortGroupFilteringRowStatus OBJECT-TYPE
   SYNTAX      INTEGER { active(1), notInservice(2), destroy(4)}
   MAX-ACCESS  read-write
   STATUS      current
   DESCRIPTION
       "1: active
        2: notInservice
        4: destroy"
   ::= { gs2326plusMVRPortGroupFilteringEntry 5 }

gs2326plusMVRGroupsTable OBJECT-TYPE
   SYNTAX      SEQUENCE OF Gs2326plusMVRGroupsEntry
   MAX-ACCESS  not-accessible
   STATUS      current
   DESCRIPTION
       "MVR Groups Information . "
   ::= { gs2326plusMVR 3 }

gs2326plusMVRGroupsEntry OBJECT-TYPE
   SYNTAX      Gs2326plusMVRGroupsEntry
   MAX-ACCESS  not-accessible
   STATUS      current
   DESCRIPTION
       ""
   INDEX    { gs2326plusMVRGroupsIndex  }
   ::= { gs2326plusMVRGroupsTable 1 }

Gs2326plusMVRGroupsEntry ::= SEQUENCE {
   gs2326plusMVRGroupsIndex          Integer32,
   gs2326plusMVRGroupsVLANID         Integer32,
   gs2326plusMVRGroups               InetAddress,
   gs2326plusMVRGroupsMemberships    DisplayString
}

gs2326plusMVRGroupsIndex OBJECT-TYPE
   SYNTAX      Integer32(1..65535)
   MAX-ACCESS  not-accessible
   STATUS      current
   DESCRIPTION
       "MVR Groups Index"
   ::= { gs2326plusMVRGroupsEntry 1 }

gs2326plusMVRGroupsVLANID OBJECT-TYPE
   SYNTAX      Integer32(1..4095)
   MAX-ACCESS  read-only
   STATUS      current
   DESCRIPTION
       "VLAN ID of the group. "
   ::= { gs2326plusMVRGroupsEntry 2 }

gs2326plusMVRGroups OBJECT-TYPE
   SYNTAX      DisplayString
   MAX-ACCESS  read-only
   STATUS      current
   DESCRIPTION
       "Group address of the group displayed."
   ::= { gs2326plusMVRGroupsEntry 3 }

gs2326plusMVRGroupsMemberships OBJECT-TYPE
   SYNTAX      DisplayString
   MAX-ACCESS  read-only
   STATUS      current
   DESCRIPTION
       "Ports under this group."
   ::= { gs2326plusMVRGroupsEntry 4 }


gs2326plusMVRStatus                                                      OBJECT IDENTIFIER ::= { gs2326plusMVR 4 }

gs2326plusMVRstatisticClear OBJECT-TYPE
   SYNTAX      INTEGER { none(0), clear(1)}
   MAX-ACCESS  read-write
   STATUS      current
   DESCRIPTION
       "Clears all Statistics counters."
   ::= { gs2326plusMVRStatus 1 }

gs2326plusMVRstatisticVLANID OBJECT-TYPE
   SYNTAX      Integer32(1..4095)
   MAX-ACCESS  read-only
   STATUS      current
   DESCRIPTION
       "The VLAN ID of the entry. "
   ::= { gs2326plusMVRStatus 2 }

gs2326plusMVRstatisticV1ReportsReceived OBJECT-TYPE
   SYNTAX      Counter32
   MAX-ACCESS  read-only
   STATUS      current
   DESCRIPTION
       "The number of Received V1 Reports. "
   ::= { gs2326plusMVRStatus 3 }

gs2326plusMVRstatisticV2ReportsReceived OBJECT-TYPE
   SYNTAX      Counter32
   MAX-ACCESS  read-only
   STATUS      current
   DESCRIPTION
       "The number of Received V2 Reports. "
   ::= { gs2326plusMVRStatus 4 }

gs2326plusMVRstatisticV3ReportsReceived OBJECT-TYPE
   SYNTAX      Counter32
   MAX-ACCESS  read-only
   STATUS      current
   DESCRIPTION
       "The number of Received V3 Reports. "
   ::= { gs2326plusMVRStatus 5 }

gs2326plusMVRstatisticV2LeavesReceived OBJECT-TYPE
   SYNTAX      Counter32
   MAX-ACCESS  read-only
   STATUS      current
   DESCRIPTION
       "The number of Received V2 Leaves. "
   ::= { gs2326plusMVRStatus 6 }

gs2326plusLACP                                                     OBJECT IDENTIFIER ::= { gs2326plusConfiguration 19 }

gs2326plusLACPConf                                                 OBJECT IDENTIFIER ::= { gs2326plusLACP 1 }

gs2326plusLACPPortConfigurationTable OBJECT-TYPE
   SYNTAX      SEQUENCE OF Gs2326plusLACPPortConfigurationEntry
   MAX-ACCESS  not-accessible
   STATUS      current
   DESCRIPTION
       " "
   ::= { gs2326plusLACPConf 1 }

gs2326plusLACPPortConfigurationEntry OBJECT-TYPE
   SYNTAX      Gs2326plusLACPPortConfigurationEntry
   MAX-ACCESS  not-accessible
   STATUS      current
   DESCRIPTION
       ""
   INDEX    { gs2326plusLACPPortConfigurationPort  }
   ::= { gs2326plusLACPPortConfigurationTable 1 }

Gs2326plusLACPPortConfigurationEntry ::= SEQUENCE {
    gs2326plusLACPPortConfigurationPort         Integer32,
    gs2326plusLACPPortConfigurationMode         INTEGER,
    gs2326plusLACPPortConfigurationKey          Integer32,
    gs2326plusLACPPortConfigurationRole         INTEGER
}

gs2326plusLACPPortConfigurationPort OBJECT-TYPE
   SYNTAX      Integer32(1..4095)
   MAX-ACCESS  not-accessible
   STATUS      current
   DESCRIPTION
       " "
   ::= { gs2326plusLACPPortConfigurationEntry 1 }

gs2326plusLACPPortConfigurationMode OBJECT-TYPE
   SYNTAX      INTEGER { disable(0), enable(1) }
   MAX-ACCESS  read-write
   STATUS      current
   DESCRIPTION
       "Enable/Disable LACP Mode."
   ::= { gs2326plusLACPPortConfigurationEntry 2 }

gs2326plusLACPPortConfigurationKey OBJECT-TYPE
   SYNTAX      Integer32(0..65535)
   MAX-ACCESS  read-write
   STATUS      current
   DESCRIPTION
       "LACP key : 1-65535. 0 : Auto"
   ::= { gs2326plusLACPPortConfigurationEntry 3 }

gs2326plusLACPPortConfigurationRole OBJECT-TYPE
   SYNTAX      INTEGER { passive(0), active(1) }
   MAX-ACCESS  read-write
   STATUS      current
   DESCRIPTION
       "0 : passive, Listen for LACP packets.
        1 : active, Initiate LACP negotiation, and transmit LACP packets each second"
   ::= { gs2326plusLACPPortConfigurationEntry 4 }

gs2326plusLACPSystemStatusTable OBJECT-TYPE
   SYNTAX      SEQUENCE OF Gs2326plusLACPSystemStatusEntry
   MAX-ACCESS  not-accessible
   STATUS      current
   DESCRIPTION
       " "
   ::= { gs2326plusLACP 2 }

gs2326plusLACPSystemStatusEntry OBJECT-TYPE
   SYNTAX      Gs2326plusLACPSystemStatusEntry
   MAX-ACCESS  not-accessible
   STATUS      current
   DESCRIPTION
       ""
   INDEX    { gs2326plusLACPSystemStatusIndex  }
   ::= { gs2326plusLACPSystemStatusTable 1 }

Gs2326plusLACPSystemStatusEntry ::= SEQUENCE {
   gs2326plusLACPSystemStatusIndex             Integer32,
   gs2326plusLACPSystemStatusAggrID            DisplayString,
   gs2326plusLACPSystemStatusPartnerSystemID   MacAddress,
   gs2326plusLACPSystemStatusPartnerKey        DisplayString,
   gs2326plusLACPSystemStatusLastchanged       DisplayString,
   gs2326plusLACPSystemStatusLocalPorts        DisplayString
}

gs2326plusLACPSystemStatusIndex OBJECT-TYPE
   SYNTAX      Integer32(1..12)
   MAX-ACCESS  not-accessible
   STATUS      current
   DESCRIPTION
       " "
   ::= { gs2326plusLACPSystemStatusEntry 1 }

gs2326plusLACPSystemStatusAggrID OBJECT-TYPE
   SYNTAX      DisplayString
   MAX-ACCESS  read-only
   STATUS      current
   DESCRIPTION
       "The Aggregation ID associated with this aggregation instance."
   ::= { gs2326plusLACPSystemStatusEntry 2 }

gs2326plusLACPSystemStatusPartnerSystemID OBJECT-TYPE
   SYNTAX      MacAddress
   MAX-ACCESS  read-only
   STATUS      current
   DESCRIPTION
       "The system ID (MAC address) of the aggregation partner."
   ::= { gs2326plusLACPSystemStatusEntry 3 }

gs2326plusLACPSystemStatusPartnerKey OBJECT-TYPE
   SYNTAX      DisplayString
   MAX-ACCESS  read-only
   STATUS      current
   DESCRIPTION
       " The Key that the partner has assigned to this aggregation ID. "
   ::= { gs2326plusLACPSystemStatusEntry 4 }

gs2326plusLACPSystemStatusLastchanged OBJECT-TYPE
   SYNTAX      DisplayString
   MAX-ACCESS  read-only
   STATUS      current
   DESCRIPTION
       " The time since this aggregation changed. "
   ::= { gs2326plusLACPSystemStatusEntry 5 }

gs2326plusLACPSystemStatusLocalPorts OBJECT-TYPE
   SYNTAX      DisplayString
   MAX-ACCESS  read-only
   STATUS      current
   DESCRIPTION
       " Shows which ports are a part of this aggregation for this switch. "
   ::= { gs2326plusLACPSystemStatusEntry 6 }

gs2326plusLACPStatusTable OBJECT-TYPE
   SYNTAX      SEQUENCE OF Gs2326plusLACPStatusEntry
   MAX-ACCESS  not-accessible
   STATUS      current
   DESCRIPTION
       " "
   ::= { gs2326plusLACP 3 }

gs2326plusLACPStatusEntry OBJECT-TYPE
   SYNTAX      Gs2326plusLACPStatusEntry
   MAX-ACCESS  not-accessible
   STATUS      current
   DESCRIPTION
       ""
   INDEX    { gs2326plusLACPStatusPort  }
   ::= { gs2326plusLACPStatusTable 1 }

Gs2326plusLACPStatusEntry ::= SEQUENCE {
   gs2326plusLACPStatusPort                Integer32,
   gs2326plusLACPStatusLACP                DisplayString,
   gs2326plusLACPStatusKey                 DisplayString,
   gs2326plusLACPStatusAggrID              DisplayString,
   gs2326plusLACPStatusPartnerSystemID     DisplayString,
   gs2326plusLACPStatusPartnerPort         DisplayString
}

gs2326plusLACPStatusPort OBJECT-TYPE
   SYNTAX      Integer32(1..4095)
   MAX-ACCESS  not-accessible
   STATUS      current
   DESCRIPTION
       " "
   ::= { gs2326plusLACPStatusEntry 1 }

gs2326plusLACPStatusLACP OBJECT-TYPE
   SYNTAX      DisplayString
   MAX-ACCESS  read-only
   STATUS      current
   DESCRIPTION
       "Enabled means that LACP is enabled and the port link is up.
        Disabled means that LACP is not enabled or that the port link is down.
        Backup means that the port could not join the aggregation group but will join if other port leaves.
        Meanwhile it's LACP status is disabled."
   ::= { gs2326plusLACPStatusEntry 2 }

gs2326plusLACPStatusKey OBJECT-TYPE
   SYNTAX      DisplayString
   MAX-ACCESS  read-only
   STATUS      current
   DESCRIPTION
       "The key assigned to this port. Only ports with the same key can aggregate together."
   ::= { gs2326plusLACPStatusEntry 3 }

gs2326plusLACPStatusAggrID	 OBJECT-TYPE
   SYNTAX      DisplayString
   MAX-ACCESS  read-only
   STATUS      current
   DESCRIPTION
       " The Aggregation ID assigned to this aggregation group. "
   ::= { gs2326plusLACPStatusEntry 4 }

gs2326plusLACPStatusPartnerSystemID OBJECT-TYPE
   SYNTAX      DisplayString
   MAX-ACCESS  read-only
   STATUS      current
   DESCRIPTION
       " The partner's System ID. "
   ::= { gs2326plusLACPStatusEntry 5 }

gs2326plusLACPStatusPartnerPort OBJECT-TYPE
   SYNTAX      DisplayString
   MAX-ACCESS  read-only
   STATUS      current
   DESCRIPTION
       " The partner's port number connected to this port. "
   ::= { gs2326plusLACPStatusEntry 6 }


gs2326plusLACPStatisticsTable OBJECT-TYPE
   SYNTAX      SEQUENCE OF Gs2326plusLACPStatisticsEntry
   MAX-ACCESS  not-accessible
   STATUS      current
   DESCRIPTION
       " "
   ::= { gs2326plusLACP 4 }

gs2326plusLACPStatisticsEntry OBJECT-TYPE
   SYNTAX      Gs2326plusLACPStatisticsEntry
   MAX-ACCESS  not-accessible
   STATUS      current
   DESCRIPTION
       ""
   INDEX    { gs2326plusLACPStatisticsPort  }
   ::= { gs2326plusLACPStatisticsTable 1 }

Gs2326plusLACPStatisticsEntry ::= SEQUENCE {
   gs2326plusLACPStatisticsPort        Integer32,
   gs2326plusLACPReceived              Counter32,
   gs2326plusLACPTransmitted           Counter32,
   gs2326plusLACPDiscardedUnknown      Counter32,
   gs2326plusLACPDiscardedIllegal      Counter32
}

gs2326plusLACPStatisticsPort OBJECT-TYPE
   SYNTAX      Integer32(1..4095)
   MAX-ACCESS  not-accessible
   STATUS      current
   DESCRIPTION
       " "
   ::= { gs2326plusLACPStatisticsEntry 1 }

gs2326plusLACPReceived OBJECT-TYPE
   SYNTAX      Counter32
   MAX-ACCESS  read-only
   STATUS      current
   DESCRIPTION
       "Shows how many LACP frames have been received at each port. "
   ::= { gs2326plusLACPStatisticsEntry 2 }

gs2326plusLACPTransmitted OBJECT-TYPE
   SYNTAX      Counter32
   MAX-ACCESS  read-only
   STATUS      current
   DESCRIPTION
       " Shows how many LACP frames have been sent from each port. "
   ::= { gs2326plusLACPStatisticsEntry 3 }

gs2326plusLACPDiscardedUnknown OBJECT-TYPE
   SYNTAX      Counter32
   MAX-ACCESS  read-only
   STATUS      current
   DESCRIPTION
       " Shows how many unknown LACP frames have been discarded at each port. "
   ::= { gs2326plusLACPStatisticsEntry 4 }

gs2326plusLACPDiscardedIllegal OBJECT-TYPE
   SYNTAX      Counter32
   MAX-ACCESS  read-only
   STATUS      current
   DESCRIPTION
       " Shows how many illegal LACP frames have been discarded at each port. "
   ::= { gs2326plusLACPStatisticsEntry 5 }

gs2326plusLACPStatisticsClear OBJECT-TYPE
   SYNTAX      INTEGER { none(0), clear(1) }
   MAX-ACCESS  read-write
   STATUS      current
   DESCRIPTION
       "default: 0
       0: none
       1: clear"
   ::= { gs2326plusLACP 5 }

gs2326plusSTP                                                     OBJECT IDENTIFIER ::= { gs2326plusConfiguration 20 }

gs2326plusSTPBridgeBasicConf                                                 OBJECT IDENTIFIER ::= { gs2326plusSTP 1 }

gs2326plusSTPBridgeProtocolVersion OBJECT-TYPE
   SYNTAX      INTEGER { stp(0), rstp(2), mstp(3) }
   MAX-ACCESS  read-write
   STATUS      current
   DESCRIPTION
       "default: 3,
       0: stp
       2: rstp
       3: mstp"
   ::= { gs2326plusSTPBridgeBasicConf 1 }

gs2326plusSTPBridgePriority OBJECT-TYPE
   SYNTAX      Integer32(0..61440)
   MAX-ACCESS  read-write
   STATUS      current
   DESCRIPTION
       " default: 32768,
       STP bridge priority (0/4096/8192/12288/16384/20480/24576/28672/32768/36864/40960/45056/49152/53248/57344/61440)"
   ::= { gs2326plusSTPBridgeBasicConf 2 }

gs2326plusSTPBridgeForwardDelay OBJECT-TYPE
   SYNTAX      Integer32(4..30)
   MAX-ACCESS  read-write
   STATUS      current
   DESCRIPTION
       " Forward Delay default: 15, range: 4 - 30.
         MaxAge must be <= (FwdDelay-1)*2."
   ::= { gs2326plusSTPBridgeBasicConf 3 }

gs2326plusSTPBridgeMaxAge OBJECT-TYPE
   SYNTAX      Integer32(6..40)
   MAX-ACCESS  read-write
   STATUS      current
   DESCRIPTION
       " Max Age default: 20, range: 6 - 40.
         MaxAge must be <= (FwdDelay-1)*2"
   ::= { gs2326plusSTPBridgeBasicConf 4 }

gs2326plusSTPBridgeMaximumHopCount OBJECT-TYPE
   SYNTAX      Integer32(6..40)
   MAX-ACCESS  read-write
   STATUS      current
   DESCRIPTION
       " Maximum Hop Count default: 20, range: 6 - 40."
   ::= { gs2326plusSTPBridgeBasicConf 5 }

gs2326plusSTPBridgeTransmitHoldCount OBJECT-TYPE
   SYNTAX      Integer32(1..10)
   MAX-ACCESS  read-write
   STATUS      current
   DESCRIPTION
       " Transmit Hold Count default: 6, range: 1 - 10."
   ::= { gs2326plusSTPBridgeBasicConf 6 }

gs2326plusSTPBridgeAdvancedConf                                                 OBJECT IDENTIFIER ::= { gs2326plusSTP 2 }

gs2326plusSTPBridgeEdgePortBPDUFiltering OBJECT-TYPE
   SYNTAX      INTEGER { disable(0), enable(1) }
   MAX-ACCESS  read-write
   STATUS      current
   DESCRIPTION
       " default: 0,
        0: disable
        1: enable"
   ::= { gs2326plusSTPBridgeAdvancedConf 1 }

gs2326plusSTPBridgeEdgePortBPDUGuard OBJECT-TYPE
   SYNTAX      INTEGER { disable(0), enable(1) }
   MAX-ACCESS  read-write
   STATUS      current
   DESCRIPTION
       " default: 0,
        0: disable
        1: enable"
   ::= { gs2326plusSTPBridgeAdvancedConf 2 }

gs2326plusSTPBridgePortErrorRecoveryTimeout OBJECT-TYPE
   SYNTAX      Integer32(0..86400)
   MAX-ACCESS  read-write
   STATUS      current
   DESCRIPTION
       " Port Error Recovery Timeout disable: 0, range: 30 - 86400."
   ::= { gs2326plusSTPBridgeAdvancedConf 3 }

gs2326plusSTPMSTIConf                                                 OBJECT IDENTIFIER ::= { gs2326plusSTP 3 }

gs2326plusSTPMSTIConfigurationName OBJECT-TYPE
   SYNTAX      DisplayString (SIZE (1..32))
   MAX-ACCESS  read-write
   STATUS      current
   DESCRIPTION
       "A text string up to 32 characters long."
   ::= { gs2326plusSTPMSTIConf 1 }

gs2326plusSTPMSTIConfigurationRevision   OBJECT-TYPE
   SYNTAX      Integer32(0..65535)
   MAX-ACCESS  read-write
   STATUS      current
   DESCRIPTION
       " Configuration Revision default: 0, range: 0 - 65535."
   ::= { gs2326plusSTPMSTIConf 2 }

gs2326plusSTPMSTIMappingConf                                                 OBJECT IDENTIFIER ::= { gs2326plusSTP 4 }

gs2326plusSTPMSTI1VLANsMapped OBJECT-TYPE
   SYNTAX      DisplayString (SIZE (1..4096))
   MAX-ACCESS  read-write
   STATUS      current
   DESCRIPTION
       "The list of VLANs mapped to the MSTI1.
       The VLANs must be separated with comma or space.
       An unused MSTI should just be left empty. "
   ::= { gs2326plusSTPMSTIMappingConf 1 }

gs2326plusSTPMSTI2VLANsMapped OBJECT-TYPE
   SYNTAX      DisplayString (SIZE (1..4096))
   MAX-ACCESS  read-write
   STATUS      current
   DESCRIPTION
       "The list of VLANs mapped to the MSTI2.
       The VLANs must be separated with comma or space.
       An unused MSTI should just be left empty. "
   ::= { gs2326plusSTPMSTIMappingConf 2 }

gs2326plusSTPMSTI3VLANsMapped OBJECT-TYPE
   SYNTAX      DisplayString (SIZE (1..4096))
   MAX-ACCESS  read-write
   STATUS      current
   DESCRIPTION
       "The list of VLANs mapped to the MSTI3.
       The VLANs must be separated with comma or space.
       An unused MSTI should just be left empty. "
   ::= { gs2326plusSTPMSTIMappingConf 3 }

gs2326plusSTPMSTI4VLANsMapped OBJECT-TYPE
   SYNTAX      DisplayString (SIZE (1..4096))
   MAX-ACCESS  read-write
   STATUS      current
   DESCRIPTION
       "The list of VLANs mapped to the MSTI4.
       The VLANs must be separated with comma or space.
       An unused MSTI should just be left empty. "
   ::= { gs2326plusSTPMSTIMappingConf 4 }

gs2326plusSTPMSTI5VLANsMapped OBJECT-TYPE
   SYNTAX      DisplayString (SIZE (1..4096))
   MAX-ACCESS  read-write
   STATUS      current
   DESCRIPTION
       "The list of VLANs mapped to the MSTI5.
       The VLANs must be separated with comma or space.
       An unused MSTI should just be left empty. "
   ::= { gs2326plusSTPMSTIMappingConf 5 }

gs2326plusSTPMSTI6VLANsMapped OBJECT-TYPE
   SYNTAX      DisplayString (SIZE (1..4096))
   MAX-ACCESS  read-write
   STATUS      current
   DESCRIPTION
       "The list of VLANs mapped to the MSTI6.
       The VLANs must be separated with comma or space.
       An unused MSTI should just be left empty. "
   ::= { gs2326plusSTPMSTIMappingConf 6 }

gs2326plusSTPMSTI7VLANsMapped OBJECT-TYPE
   SYNTAX      DisplayString (SIZE (1..4096))
   MAX-ACCESS  read-write
   STATUS      current
   DESCRIPTION
       "The list of VLANs mapped to the MSTI7.
       The VLANs must be separated with comma or space.
       An unused MSTI should just be left empty. "
   ::= { gs2326plusSTPMSTIMappingConf 7 }

gs2326plusSTPMSTIPriority                                                 OBJECT IDENTIFIER ::= { gs2326plusSTP 5 }

gs2326plusSTPCISTPriority OBJECT-TYPE
   SYNTAX      Integer32(0..61440)
   MAX-ACCESS  read-write
   STATUS      current
   DESCRIPTION
       " default: 32768,
       STP CIST priority (0/4096/8192/12288/16384/20480/24576/28672/32768/36864/40960/45056/49152/53248/57344/61440)"
   ::= { gs2326plusSTPMSTIPriority 1 }

gs2326plusSTPMSTI1Priority OBJECT-TYPE
   SYNTAX      Integer32(0..61440)
   MAX-ACCESS  read-write
   STATUS      current
   DESCRIPTION
       " default: 32768,
       STP CIST priority (0/4096/8192/12288/16384/20480/24576/28672/32768/36864/40960/45056/49152/53248/57344/61440)"
   ::= { gs2326plusSTPMSTIPriority 2 }

gs2326plusSTPMSTI2Priority OBJECT-TYPE
   SYNTAX      Integer32(0..61440)
   MAX-ACCESS  read-write
   STATUS      current
   DESCRIPTION
       " default: 32768,
       STP CIST priority (0/4096/8192/12288/16384/20480/24576/28672/32768/36864/40960/45056/49152/53248/57344/61440)"
   ::= { gs2326plusSTPMSTIPriority 3 }

gs2326plusSTPMSTI3Priority OBJECT-TYPE
   SYNTAX      Integer32(0..61440)
   MAX-ACCESS  read-write
   STATUS      current
   DESCRIPTION
       " default: 32768,
       STP CIST priority (0/4096/8192/12288/16384/20480/24576/28672/32768/36864/40960/45056/49152/53248/57344/61440)"
   ::= { gs2326plusSTPMSTIPriority 4 }

gs2326plusSTPMSTI4Priority OBJECT-TYPE
   SYNTAX      Integer32(0..61440)
   MAX-ACCESS  read-write
   STATUS      current
   DESCRIPTION
       " default: 32768,
       STP CIST priority (0/4096/8192/12288/16384/20480/24576/28672/32768/36864/40960/45056/49152/53248/57344/61440)"
   ::= { gs2326plusSTPMSTIPriority 5 }

gs2326plusSTPMSTI5Priority OBJECT-TYPE
   SYNTAX      Integer32(0..61440)
   MAX-ACCESS  read-write
   STATUS      current
   DESCRIPTION
       " default: 32768,
       STP CIST priority (0/4096/8192/12288/16384/20480/24576/28672/32768/36864/40960/45056/49152/53248/57344/61440)"
   ::= { gs2326plusSTPMSTIPriority 6 }

gs2326plusSTPMSTI6Priority OBJECT-TYPE
   SYNTAX      Integer32(0..61440)
   MAX-ACCESS  read-write
   STATUS      current
   DESCRIPTION
       " default: 32768,
       STP CIST priority (0/4096/8192/12288/16384/20480/24576/28672/32768/36864/40960/45056/49152/53248/57344/61440)"
   ::= { gs2326plusSTPMSTIPriority 7 }

gs2326plusSTPMSTI7Priority OBJECT-TYPE
   SYNTAX      Integer32(0..61440)
   MAX-ACCESS  read-write
   STATUS      current
   DESCRIPTION
       " default: 32768,
       STP CIST priority (0/4096/8192/12288/16384/20480/24576/28672/32768/36864/40960/45056/49152/53248/57344/61440)"
   ::= { gs2326plusSTPMSTIPriority 8 }

gs2326plusSTPCISTPort                                                          OBJECT IDENTIFIER ::= { gs2326plusSTP 6 }

gs2326plusSTPCISTAggregatedPort                                                OBJECT IDENTIFIER ::= { gs2326plusSTPCISTPort 1 }

gs2326plusSTPCISTAggregatedPortSTPEnabled OBJECT-TYPE
   SYNTAX      INTEGER { disable(0), enable(1) }
   MAX-ACCESS  read-write
   STATUS      current
   DESCRIPTION
       " default: 0,
        0: disable
        1: enable"
   ::= { gs2326plusSTPCISTAggregatedPort 1 }

gs2326plusSTPCISTAggregatedPortPathCost OBJECT-TYPE
   SYNTAX      Integer32(0..200000000)
   MAX-ACCESS  read-write
   STATUS      current
   DESCRIPTION
       " Auto: 0,
        Specific Path Cost range: 1 - 200000000."
   ::= { gs2326plusSTPCISTAggregatedPort 2 }

gs2326plusSTPCISTAggregatedPortPriority OBJECT-TYPE
   SYNTAX      Integer32(0..240)
   MAX-ACCESS  read-write
   STATUS      current
   DESCRIPTION
       " default: 128,
       CIST Aggregated Port Priority (0/16/32/48/64/80/96/112/128/144/160/176/192/208/224/240)"
   ::= { gs2326plusSTPCISTAggregatedPort 3 }

gs2326plusSTPCISTAggregatedPortAdminEdge OBJECT-TYPE
   SYNTAX      INTEGER { non-edge(0), edge(1) }
   MAX-ACCESS  read-write
   STATUS      current
   DESCRIPTION
       " default: 0,
        0: non-edge
        1: edge"
   ::= { gs2326plusSTPCISTAggregatedPort 4 }

gs2326plusSTPCISTAggregatedPortAutoEdge OBJECT-TYPE
   SYNTAX      INTEGER { disable(0), enable(1) }
   MAX-ACCESS  read-write
   STATUS      current
   DESCRIPTION
       " default: 1,
        0: disable
        1: enable"
   ::= { gs2326plusSTPCISTAggregatedPort 5 }

gs2326plusSTPCISTAggregatedPortRestrictedRole OBJECT-TYPE
   SYNTAX      INTEGER { disable(0), enable(1) }
   MAX-ACCESS  read-write
   STATUS      current
   DESCRIPTION
       " default: 0,
        0: disable
        1: enable"
   ::= { gs2326plusSTPCISTAggregatedPort 6 }

gs2326plusSTPCISTAggregatedPortRestrictedTCN OBJECT-TYPE
   SYNTAX      INTEGER { disable(0), enable(1) }
   MAX-ACCESS  read-write
   STATUS      current
   DESCRIPTION
       " default: 0,
        0: disable
        1: enable"
   ::= { gs2326plusSTPCISTAggregatedPort 7 }

gs2326plusSTPCISTAggregatedPortBPDUGuard OBJECT-TYPE
   SYNTAX      INTEGER { disable(0), enable(1) }
   MAX-ACCESS  read-write
   STATUS      current
   DESCRIPTION
       " default: 0,
        0: disable
        1: enable"
   ::= { gs2326plusSTPCISTAggregatedPort 8 }

gs2326plusSTPCISTAggregatedPortPointtoPoint OBJECT-TYPE
   SYNTAX      INTEGER { forcetrue(0), forcefalse(1), auto(2) }
   MAX-ACCESS  read-write
   STATUS      current
   DESCRIPTION
       " default: 0,
        0: Forced True
        1: Forced False
        2: Auto"
   ::= { gs2326plusSTPCISTAggregatedPort 9 }

gs2326plusSTPCISTNormalPortTable OBJECT-TYPE
   SYNTAX      SEQUENCE OF Gs2326plusSTPCISTNormalPortEntry
   MAX-ACCESS  not-accessible
   STATUS      current
   DESCRIPTION
       " Show CIST Normal Port Configurations. "
   ::= { gs2326plusSTPCISTPort 2 }

gs2326plusSTPCISTNormalPortEntry OBJECT-TYPE
   SYNTAX      Gs2326plusSTPCISTNormalPortEntry
   MAX-ACCESS  not-accessible
   STATUS      current
   DESCRIPTION
       ""
   INDEX    { gs2326plusSTPCISTNormalPortConfPort  }
   ::= { gs2326plusSTPCISTNormalPortTable 1 }

Gs2326plusSTPCISTNormalPortEntry ::= SEQUENCE {
   gs2326plusSTPCISTNormalPortConfPort         Integer32,
   gs2326plusSTPCISTNormalPortSTPEnabled       INTEGER,
   gs2326plusSTPCISTNormalPortPathCost         Integer32,
   gs2326plusSTPCISTNormalPortPriority         Integer32,
   gs2326plusSTPCISTNormalPortAdminEdge        INTEGER,
   gs2326plusSTPCISTNormalPortAutoEdge         INTEGER,
   gs2326plusSTPCISTNormalPortRestrictedRole   INTEGER,
   gs2326plusSTPCISTNormalPortRestrictedTCN    INTEGER,
   gs2326plusSTPCISTNormalPortBPDUGuard        INTEGER,
   gs2326plusSTPCISTNormalPortPointtoPoint     INTEGER
}

gs2326plusSTPCISTNormalPortConfPort OBJECT-TYPE
   SYNTAX      Integer32(1..4095)
   MAX-ACCESS  not-accessible
   STATUS      current
   DESCRIPTION
       " port, range : 1 - port number. "
   ::= { gs2326plusSTPCISTNormalPortEntry 1 }

gs2326plusSTPCISTNormalPortSTPEnabled OBJECT-TYPE
   SYNTAX      INTEGER { disable(0), enable(1) }
   MAX-ACCESS  read-write
   STATUS      current
   DESCRIPTION
       " default: 0,
        0: disable
        1: enable"
   ::= { gs2326plusSTPCISTNormalPortEntry 2 }

gs2326plusSTPCISTNormalPortPathCost OBJECT-TYPE
   SYNTAX      Integer32(0..200000000)
   MAX-ACCESS  read-write
   STATUS      current
   DESCRIPTION
       " Auto: 0,
        Specific Path Cost range: 1 - 200000000."
   ::= { gs2326plusSTPCISTNormalPortEntry 3 }

gs2326plusSTPCISTNormalPortPriority OBJECT-TYPE
   SYNTAX      Integer32(0..240)
   MAX-ACCESS  read-write
   STATUS      current
   DESCRIPTION
       " default: 128,
       CIST Aggregated Port Priority (0/16/32/48/64/80/96/112/128/144/160/176/192/208/224/240)"
   ::= { gs2326plusSTPCISTNormalPortEntry 4 }

gs2326plusSTPCISTNormalPortAdminEdge OBJECT-TYPE
   SYNTAX      INTEGER { non-edge(0), edge(1) }
   MAX-ACCESS  read-write
   STATUS      current
   DESCRIPTION
       " default: 0,
        0: non-edge
        1: edge"
   ::= { gs2326plusSTPCISTNormalPortEntry 5 }

gs2326plusSTPCISTNormalPortAutoEdge OBJECT-TYPE
   SYNTAX      INTEGER { disable(0), enable(1) }
   MAX-ACCESS  read-write
   STATUS      current
   DESCRIPTION
       " default: 1,
        0: disable
        1: enable"
   ::= { gs2326plusSTPCISTNormalPortEntry 6 }

gs2326plusSTPCISTNormalPortRestrictedRole OBJECT-TYPE
   SYNTAX      INTEGER { disable(0), enable(1) }
   MAX-ACCESS  read-write
   STATUS      current
   DESCRIPTION
       " default: 0,
        0: disable
        1: enable"
   ::= { gs2326plusSTPCISTNormalPortEntry 7 }

gs2326plusSTPCISTNormalPortRestrictedTCN OBJECT-TYPE
   SYNTAX      INTEGER { disable(0), enable(1) }
   MAX-ACCESS  read-write
   STATUS      current
   DESCRIPTION
       " default: 0,
        0: disable
        1: enable"
   ::= { gs2326plusSTPCISTNormalPortEntry 8 }

gs2326plusSTPCISTNormalPortBPDUGuard OBJECT-TYPE
   SYNTAX      INTEGER { disable(0), enable(1) }
   MAX-ACCESS  read-write
   STATUS      current
   DESCRIPTION
       " default: 0,
        0: disable
        1: enable"
   ::= { gs2326plusSTPCISTNormalPortEntry 9 }

gs2326plusSTPCISTNormalPortPointtoPoint OBJECT-TYPE
   SYNTAX      INTEGER { forcetrue(0), forcefalse(1), auto(2) }
   MAX-ACCESS  read-write
   STATUS      current
   DESCRIPTION
       " default: 2,
        0: Forced True
        1: Forced False
        2: Auto"
   ::= { gs2326plusSTPCISTNormalPortEntry 10 }


gs2326plusSTPMSTIPort                                                          OBJECT IDENTIFIER ::= { gs2326plusSTP 7 }

gs2326plusSTPMSTI1Port                                                         OBJECT IDENTIFIER ::= { gs2326plusSTPMSTIPort 1 }

gs2326plusSTPMSTI1AggregatedPort                                                OBJECT IDENTIFIER ::= { gs2326plusSTPMSTI1Port 1 }

gs2326plusSTPMSTI1AggregatedPortPathCost OBJECT-TYPE
   SYNTAX      Integer32(0..200000000)
   MAX-ACCESS  read-write
   STATUS      current
   DESCRIPTION
       " Auto: 0,
        Specific Path Cost range: 1 - 200000000."
   ::= { gs2326plusSTPMSTI1AggregatedPort 1 }

gs2326plusSTPMSTI1AggregatedPortPriority OBJECT-TYPE
   SYNTAX      Integer32(0..240)
   MAX-ACCESS  read-write
   STATUS      current
   DESCRIPTION
       " default: 128,
       Aggregated Port Priority (0/16/32/48/64/80/96/112/128/144/160/176/192/208/224/240)"
   ::= { gs2326plusSTPMSTI1AggregatedPort 2 }

gs2326plusSTPMSTI1NormalPortTable OBJECT-TYPE
   SYNTAX      SEQUENCE OF Gs2326plusSTPMSTI1NormalPortEntry
   MAX-ACCESS  not-accessible
   STATUS      current
   DESCRIPTION
       " Show MSTI1 Normal Port Configurations. "
   ::= { gs2326plusSTPMSTI1Port 2 }

gs2326plusSTPMSTI1NormalPortEntry OBJECT-TYPE
   SYNTAX      Gs2326plusSTPMSTI1NormalPortEntry
   MAX-ACCESS  not-accessible
   STATUS      current
   DESCRIPTION
       ""
   INDEX    { gs2326plusSTPMSTI1NormalPortConfPort  }
   ::= { gs2326plusSTPMSTI1NormalPortTable 1 }

Gs2326plusSTPMSTI1NormalPortEntry ::= SEQUENCE {
   gs2326plusSTPMSTI1NormalPortConfPort         Integer32,
   gs2326plusSTPMSTI1NormalPortPathCost         Integer32,
   gs2326plusSTPMSTI1NormalPortPriority         Integer32
}

gs2326plusSTPMSTI1NormalPortConfPort OBJECT-TYPE
   SYNTAX      Integer32(1..4095)
   MAX-ACCESS  not-accessible
   STATUS      current
   DESCRIPTION
       " port, range : 1 - port number. "
   ::= { gs2326plusSTPMSTI1NormalPortEntry 1 }

gs2326plusSTPMSTI1NormalPortPathCost OBJECT-TYPE
   SYNTAX      Integer32(0..200000000)
   MAX-ACCESS  read-write
   STATUS      current
   DESCRIPTION
       " Auto: 0,
        Specific Path Cost range: 1 - 200000000."
   ::= { gs2326plusSTPMSTI1NormalPortEntry 2 }

gs2326plusSTPMSTI1NormalPortPriority OBJECT-TYPE
   SYNTAX      Integer32(0..240)
   MAX-ACCESS  read-write
   STATUS      current
   DESCRIPTION
       " default: 128,
       Aggregated Port Priority (0/16/32/48/64/80/96/112/128/144/160/176/192/208/224/240)"
   ::= { gs2326plusSTPMSTI1NormalPortEntry 3 }

gs2326plusSTPMSTI2Port                                                          OBJECT IDENTIFIER ::= { gs2326plusSTPMSTIPort 2 }

gs2326plusSTPMSTI2AggregatedPort                                                OBJECT IDENTIFIER ::= { gs2326plusSTPMSTI2Port 1 }

gs2326plusSTPMSTI2AggregatedPortPathCost OBJECT-TYPE
   SYNTAX      Integer32(0..200000000)
   MAX-ACCESS  read-write
   STATUS      current
   DESCRIPTION
       " Auto: 0,
        Specific Path Cost range: 1 - 200000000."
   ::= { gs2326plusSTPMSTI2AggregatedPort 1 }

gs2326plusSTPMSTI2AggregatedPortPriority OBJECT-TYPE
   SYNTAX      Integer32(0..240)
   MAX-ACCESS  read-write
   STATUS      current
   DESCRIPTION
       " default: 128,
       Aggregated Port Priority (0/16/32/48/64/80/96/112/128/144/160/176/192/208/224/240)"
   ::= { gs2326plusSTPMSTI2AggregatedPort 2 }

gs2326plusSTPMSTI2NormalPortTable OBJECT-TYPE
   SYNTAX      SEQUENCE OF Gs2326plusSTPMSTI2NormalPortEntry
   MAX-ACCESS  not-accessible
   STATUS      current
   DESCRIPTION
       " Show MSTI2 Normal Port Configurations. "
   ::= { gs2326plusSTPMSTI2Port 2 }

gs2326plusSTPMSTI2NormalPortEntry OBJECT-TYPE
   SYNTAX      Gs2326plusSTPMSTI2NormalPortEntry
   MAX-ACCESS  not-accessible
   STATUS      current
   DESCRIPTION
       ""
   INDEX    { gs2326plusSTPMSTI2NormalPortConfPort  }
   ::= { gs2326plusSTPMSTI2NormalPortTable 1 }

Gs2326plusSTPMSTI2NormalPortEntry ::= SEQUENCE {
   gs2326plusSTPMSTI2NormalPortConfPort         Integer32,
   gs2326plusSTPMSTI2NormalPortPathCost         Integer32,
   gs2326plusSTPMSTI2NormalPortPriority         Integer32
}

gs2326plusSTPMSTI2NormalPortConfPort OBJECT-TYPE
   SYNTAX      Integer32(1..4095)
   MAX-ACCESS  not-accessible
   STATUS      current
   DESCRIPTION
       " port, range : 1 - port number. "
   ::= { gs2326plusSTPMSTI2NormalPortEntry 1 }

gs2326plusSTPMSTI2NormalPortPathCost OBJECT-TYPE
   SYNTAX      Integer32(0..200000000)
   MAX-ACCESS  read-write
   STATUS      current
   DESCRIPTION
       " Auto: 0,
        Specific Path Cost range: 1 - 200000000."
   ::= { gs2326plusSTPMSTI2NormalPortEntry 2 }

gs2326plusSTPMSTI2NormalPortPriority OBJECT-TYPE
   SYNTAX      Integer32(0..240)
   MAX-ACCESS  read-write
   STATUS      current
   DESCRIPTION
       " default: 128,
       Aggregated Port Priority (0/16/32/48/64/80/96/112/128/144/160/176/192/208/224/240)"
   ::= { gs2326plusSTPMSTI2NormalPortEntry 3 }

gs2326plusSTPMSTI3Port                                                          OBJECT IDENTIFIER ::= { gs2326plusSTPMSTIPort 3 }

gs2326plusSTPMSTI3AggregatedPort                                                OBJECT IDENTIFIER ::= { gs2326plusSTPMSTI3Port 1 }

gs2326plusSTPMSTI3AggregatedPortPathCost OBJECT-TYPE
   SYNTAX      Integer32(0..200000000)
   MAX-ACCESS  read-write
   STATUS      current
   DESCRIPTION
       " Auto: 0,
        Specific Path Cost range: 1 - 200000000."
   ::= { gs2326plusSTPMSTI3AggregatedPort 1 }

gs2326plusSTPMSTI3AggregatedPortPriority OBJECT-TYPE
   SYNTAX      Integer32(0..240)
   MAX-ACCESS  read-write
   STATUS      current
   DESCRIPTION
       " default: 128,
       Aggregated Port Priority (0/16/32/48/64/80/96/112/128/144/160/176/192/208/224/240)"
   ::= { gs2326plusSTPMSTI3AggregatedPort 2 }

gs2326plusSTPMSTI3NormalPortTable OBJECT-TYPE
   SYNTAX      SEQUENCE OF Gs2326plusSTPMSTI3NormalPortEntry
   MAX-ACCESS  not-accessible
   STATUS      current
   DESCRIPTION
       " Show MSTI3 Normal Port Configurations. "
   ::= { gs2326plusSTPMSTI3Port 2 }

gs2326plusSTPMSTI3NormalPortEntry OBJECT-TYPE
   SYNTAX      Gs2326plusSTPMSTI3NormalPortEntry
   MAX-ACCESS  not-accessible
   STATUS      current
   DESCRIPTION
       ""
   INDEX    { gs2326plusSTPMSTI3NormalPortConfPort  }
   ::= { gs2326plusSTPMSTI3NormalPortTable 1 }

Gs2326plusSTPMSTI3NormalPortEntry ::= SEQUENCE {
   gs2326plusSTPMSTI3NormalPortConfPort         Integer32,
   gs2326plusSTPMSTI3NormalPortPathCost         Integer32,
   gs2326plusSTPMSTI3NormalPortPriority         Integer32
}

gs2326plusSTPMSTI3NormalPortConfPort OBJECT-TYPE
   SYNTAX      Integer32(1..4095)
   MAX-ACCESS  not-accessible
   STATUS      current
   DESCRIPTION
       " port, range : 1 - port number. "
   ::= { gs2326plusSTPMSTI3NormalPortEntry 1 }

gs2326plusSTPMSTI3NormalPortPathCost OBJECT-TYPE
   SYNTAX      Integer32(0..200000000)
   MAX-ACCESS  read-write
   STATUS      current
   DESCRIPTION
       " Auto: 0,
        Specific Path Cost range: 1 - 200000000."
   ::= { gs2326plusSTPMSTI3NormalPortEntry 2 }

gs2326plusSTPMSTI3NormalPortPriority OBJECT-TYPE
   SYNTAX      Integer32(0..240)
   MAX-ACCESS  read-write
   STATUS      current
   DESCRIPTION
       " default: 128,
       Aggregated Port Priority (0/16/32/48/64/80/96/112/128/144/160/176/192/208/224/240)"
   ::= { gs2326plusSTPMSTI3NormalPortEntry 3 }

gs2326plusSTPMSTI4Port                                                          OBJECT IDENTIFIER ::= { gs2326plusSTPMSTIPort 4 }

gs2326plusSTPMSTI4AggregatedPort                                                OBJECT IDENTIFIER ::= { gs2326plusSTPMSTI4Port 1 }

gs2326plusSTPMSTI4AggregatedPortPathCost OBJECT-TYPE
   SYNTAX      Integer32(0..200000000)
   MAX-ACCESS  read-write
   STATUS      current
   DESCRIPTION
       " Auto: 0,
        Specific Path Cost range: 1 - 200000000."
   ::= { gs2326plusSTPMSTI4AggregatedPort 1 }

gs2326plusSTPMSTI4AggregatedPortPriority OBJECT-TYPE
   SYNTAX      Integer32(0..240)
   MAX-ACCESS  read-write
   STATUS      current
   DESCRIPTION
       " default: 128,
       Aggregated Port Priority (0/16/32/48/64/80/96/112/128/144/160/176/192/208/224/240)"
   ::= { gs2326plusSTPMSTI4AggregatedPort 2 }

gs2326plusSTPMSTI4NormalPortTable OBJECT-TYPE
   SYNTAX      SEQUENCE OF Gs2326plusSTPMSTI4NormalPortEntry
   MAX-ACCESS  not-accessible
   STATUS      current
   DESCRIPTION
       " Show MSTI4 Normal Port Configurations. "
   ::= { gs2326plusSTPMSTI4Port 2 }

gs2326plusSTPMSTI4NormalPortEntry OBJECT-TYPE
   SYNTAX      Gs2326plusSTPMSTI4NormalPortEntry
   MAX-ACCESS  not-accessible
   STATUS      current
   DESCRIPTION
       ""
   INDEX    { gs2326plusSTPMSTI4NormalPortConfPort  }
   ::= { gs2326plusSTPMSTI4NormalPortTable 1 }

Gs2326plusSTPMSTI4NormalPortEntry ::= SEQUENCE {
   gs2326plusSTPMSTI4NormalPortConfPort         Integer32,
   gs2326plusSTPMSTI4NormalPortPathCost         Integer32,
   gs2326plusSTPMSTI4NormalPortPriority         Integer32
}

gs2326plusSTPMSTI4NormalPortConfPort OBJECT-TYPE
   SYNTAX      Integer32(1..4095)
   MAX-ACCESS  not-accessible
   STATUS      current
   DESCRIPTION
       " port, range : 1 - port number. "
   ::= { gs2326plusSTPMSTI4NormalPortEntry 1 }

gs2326plusSTPMSTI4NormalPortPathCost OBJECT-TYPE
   SYNTAX      Integer32(0..200000000)
   MAX-ACCESS  read-write
   STATUS      current
   DESCRIPTION
       " Auto: 0,
        Specific Path Cost range: 1 - 200000000."
   ::= { gs2326plusSTPMSTI4NormalPortEntry 2 }

gs2326plusSTPMSTI4NormalPortPriority OBJECT-TYPE
   SYNTAX      Integer32(0..240)
   MAX-ACCESS  read-write
   STATUS      current
   DESCRIPTION
       " default: 128,
       Aggregated Port Priority (0/16/32/48/64/80/96/112/128/144/160/176/192/208/224/240)"
   ::= { gs2326plusSTPMSTI4NormalPortEntry 3 }

gs2326plusSTPMSTI5Port                                                          OBJECT IDENTIFIER ::= { gs2326plusSTPMSTIPort 5 }

gs2326plusSTPMSTI5AggregatedPort                                                OBJECT IDENTIFIER ::= { gs2326plusSTPMSTI5Port 1 }

gs2326plusSTPMSTI5AggregatedPortPathCost OBJECT-TYPE
   SYNTAX      Integer32(0..200000000)
   MAX-ACCESS  read-write
   STATUS      current
   DESCRIPTION
       " Auto: 0,
        Specific Path Cost range: 1 - 200000000."
   ::= { gs2326plusSTPMSTI5AggregatedPort 1 }

gs2326plusSTPMSTI5AggregatedPortPriority OBJECT-TYPE
   SYNTAX      Integer32(0..240)
   MAX-ACCESS  read-write
   STATUS      current
   DESCRIPTION
       " default: 128,
       Aggregated Port Priority (0/16/32/48/64/80/96/112/128/144/160/176/192/208/224/240)"
   ::= { gs2326plusSTPMSTI5AggregatedPort 2 }

gs2326plusSTPMSTI5NormalPortTable OBJECT-TYPE
   SYNTAX      SEQUENCE OF Gs2326plusSTPMSTI5NormalPortEntry
   MAX-ACCESS  not-accessible
   STATUS      current
   DESCRIPTION
       " Show MSTI5 Normal Port Configurations. "
   ::= { gs2326plusSTPMSTI5Port 2 }

gs2326plusSTPMSTI5NormalPortEntry OBJECT-TYPE
   SYNTAX      Gs2326plusSTPMSTI5NormalPortEntry
   MAX-ACCESS  not-accessible
   STATUS      current
   DESCRIPTION
       ""
   INDEX    { gs2326plusSTPMSTI5NormalPortConfPort  }
   ::= { gs2326plusSTPMSTI5NormalPortTable 1 }

Gs2326plusSTPMSTI5NormalPortEntry ::= SEQUENCE {
   gs2326plusSTPMSTI5NormalPortConfPort         Integer32,
   gs2326plusSTPMSTI5NormalPortPathCost         Integer32,
   gs2326plusSTPMSTI5NormalPortPriority         Integer32
}

gs2326plusSTPMSTI5NormalPortConfPort OBJECT-TYPE
   SYNTAX      Integer32(1..4095)
   MAX-ACCESS  not-accessible
   STATUS      current
   DESCRIPTION
       " port, range : 1 - port number. "
   ::= { gs2326plusSTPMSTI5NormalPortEntry 1 }

gs2326plusSTPMSTI5NormalPortPathCost OBJECT-TYPE
   SYNTAX      Integer32(0..200000000)
   MAX-ACCESS  read-write
   STATUS      current
   DESCRIPTION
       " Auto: 0,
        Specific Path Cost range: 1 - 200000000."
   ::= { gs2326plusSTPMSTI5NormalPortEntry 2 }

gs2326plusSTPMSTI5NormalPortPriority OBJECT-TYPE
   SYNTAX      Integer32(0..240)
   MAX-ACCESS  read-write
   STATUS      current
   DESCRIPTION
       " default: 128,
       Aggregated Port Priority (0/16/32/48/64/80/96/112/128/144/160/176/192/208/224/240)"
   ::= { gs2326plusSTPMSTI5NormalPortEntry 3 }

gs2326plusSTPMSTI6Port                                                          OBJECT IDENTIFIER ::= { gs2326plusSTPMSTIPort 6 }

gs2326plusSTPMSTI6AggregatedPort                                                OBJECT IDENTIFIER ::= { gs2326plusSTPMSTI6Port 1 }

gs2326plusSTPMSTI6AggregatedPortPathCost OBJECT-TYPE
   SYNTAX      Integer32(0..200000000)
   MAX-ACCESS  read-write
   STATUS      current
   DESCRIPTION
       " Auto: 0,
        Specific Path Cost range: 1 - 200000000."
   ::= { gs2326plusSTPMSTI6AggregatedPort 1 }

gs2326plusSTPMSTI6AggregatedPortPriority OBJECT-TYPE
   SYNTAX      Integer32(0..240)
   MAX-ACCESS  read-write
   STATUS      current
   DESCRIPTION
       " default: 128,
       Aggregated Port Priority (0/16/32/48/64/80/96/112/128/144/160/176/192/208/224/240)"
   ::= { gs2326plusSTPMSTI6AggregatedPort 2 }

gs2326plusSTPMSTI6NormalPortTable OBJECT-TYPE
   SYNTAX      SEQUENCE OF Gs2326plusSTPMSTI6NormalPortEntry
   MAX-ACCESS  not-accessible
   STATUS      current
   DESCRIPTION
       " Show MSTI6 Normal Port Configurations. "
   ::= { gs2326plusSTPMSTI6Port 2 }

gs2326plusSTPMSTI6NormalPortEntry OBJECT-TYPE
   SYNTAX      Gs2326plusSTPMSTI6NormalPortEntry
   MAX-ACCESS  not-accessible
   STATUS      current
   DESCRIPTION
       ""
   INDEX    { gs2326plusSTPMSTI6NormalPortConfPort  }
   ::= { gs2326plusSTPMSTI6NormalPortTable 1 }

Gs2326plusSTPMSTI6NormalPortEntry ::= SEQUENCE {
   gs2326plusSTPMSTI6NormalPortConfPort         Integer32,
   gs2326plusSTPMSTI6NormalPortPathCost         Integer32,
   gs2326plusSTPMSTI6NormalPortPriority         Integer32
}

gs2326plusSTPMSTI6NormalPortConfPort OBJECT-TYPE
   SYNTAX      Integer32(1..4095)
   MAX-ACCESS  not-accessible
   STATUS      current
   DESCRIPTION
       " port, range : 1 - port number. "
   ::= { gs2326plusSTPMSTI6NormalPortEntry 1 }

gs2326plusSTPMSTI6NormalPortPathCost OBJECT-TYPE
   SYNTAX      Integer32(0..200000000)
   MAX-ACCESS  read-write
   STATUS      current
   DESCRIPTION
       " Auto: 0,
        Specific Path Cost range: 1 - 200000000."
   ::= { gs2326plusSTPMSTI6NormalPortEntry 2 }

gs2326plusSTPMSTI6NormalPortPriority OBJECT-TYPE
   SYNTAX      Integer32(0..240)
   MAX-ACCESS  read-write
   STATUS      current
   DESCRIPTION
       " default: 128,
       Aggregated Port Priority (0/16/32/48/64/80/96/112/128/144/160/176/192/208/224/240)"
   ::= { gs2326plusSTPMSTI6NormalPortEntry 3 }

gs2326plusSTPMSTI7Port                                                          OBJECT IDENTIFIER ::= { gs2326plusSTPMSTIPort 7 }

gs2326plusSTPMSTI7AggregatedPort                                                OBJECT IDENTIFIER ::= { gs2326plusSTPMSTI7Port 1 }

gs2326plusSTPMSTI7AggregatedPortPathCost OBJECT-TYPE
   SYNTAX      Integer32(0..200000000)
   MAX-ACCESS  read-write
   STATUS      current
   DESCRIPTION
       " Auto: 0,
        Specific Path Cost range: 1 - 200000000."
   ::= { gs2326plusSTPMSTI7AggregatedPort 1 }

gs2326plusSTPMSTI7AggregatedPortPriority OBJECT-TYPE
   SYNTAX      Integer32(0..240)
   MAX-ACCESS  read-write
   STATUS      current
   DESCRIPTION
       " default: 128,
       Aggregated Port Priority (0/16/32/48/64/80/96/112/128/144/160/176/192/208/224/240)"
   ::= { gs2326plusSTPMSTI7AggregatedPort 2 }

gs2326plusSTPMSTI7NormalPortTable OBJECT-TYPE
   SYNTAX      SEQUENCE OF Gs2326plusSTPMSTI7NormalPortEntry
   MAX-ACCESS  not-accessible
   STATUS      current
   DESCRIPTION
       " Show MSTI7 Normal Port Configurations. "
   ::= { gs2326plusSTPMSTI7Port 2 }

gs2326plusSTPMSTI7NormalPortEntry OBJECT-TYPE
   SYNTAX      Gs2326plusSTPMSTI7NormalPortEntry
   MAX-ACCESS  not-accessible
   STATUS      current
   DESCRIPTION
       ""
   INDEX    { gs2326plusSTPMSTI7NormalPortConfPort  }
   ::= { gs2326plusSTPMSTI7NormalPortTable 1 }

Gs2326plusSTPMSTI7NormalPortEntry ::= SEQUENCE {
   gs2326plusSTPMSTI7NormalPortConfPort         Integer32,
   gs2326plusSTPMSTI7NormalPortPathCost         Integer32,
   gs2326plusSTPMSTI7NormalPortPriority         Integer32
}

gs2326plusSTPMSTI7NormalPortConfPort OBJECT-TYPE
   SYNTAX      Integer32(1..4095)
   MAX-ACCESS  not-accessible
   STATUS      current
   DESCRIPTION
       " port, range : 1 - port number. "
   ::= { gs2326plusSTPMSTI7NormalPortEntry 1 }

gs2326plusSTPMSTI7NormalPortPathCost OBJECT-TYPE
   SYNTAX      Integer32(0..200000000)
   MAX-ACCESS  read-write
   STATUS      current
   DESCRIPTION
       " Auto: 0,
        Specific Path Cost range: 1 - 200000000."
   ::= { gs2326plusSTPMSTI7NormalPortEntry 2 }

gs2326plusSTPMSTI7NormalPortPriority OBJECT-TYPE
   SYNTAX      Integer32(0..240)
   MAX-ACCESS  read-write
   STATUS      current
   DESCRIPTION
       " default: 128,
       Aggregated Port Priority (0/16/32/48/64/80/96/112/128/144/160/176/192/208/224/240)"
   ::= { gs2326plusSTPMSTI7NormalPortEntry 3 }


gs2326plusSTPBridgeStatus                                                      OBJECT IDENTIFIER ::= { gs2326plusSTP 8 }

gs2326plusCISTBridgeSTP                                                        OBJECT IDENTIFIER ::= { gs2326plusSTPBridgeStatus 1 }

gs2326plusCISTBridgeSTPStatus                                                  OBJECT IDENTIFIER ::= { gs2326plusCISTBridgeSTP 1 }

gs2326plusCISTBridgeInstance OBJECT-TYPE
   SYNTAX       DisplayString
   MAX-ACCESS   read-only
   STATUS       current
   DESCRIPTION
       "The Bridge instance - CIST, MST1, ..."
   ::= { gs2326plusCISTBridgeSTPStatus 1 }

gs2326plusCISTBridgeID OBJECT-TYPE
   SYNTAX       DisplayString
   MAX-ACCESS   read-only
   STATUS       current
   DESCRIPTION
       "The Bridge ID of this Bridge instance."
   ::= { gs2326plusCISTBridgeSTPStatus 2 }

gs2326plusCISTRootID OBJECT-TYPE
   SYNTAX       DisplayString
   MAX-ACCESS   read-only
   STATUS       current
   DESCRIPTION
       "The Bridge ID of the currently elected root bridge."
   ::= { gs2326plusCISTBridgeSTPStatus 3 }

gs2326plusCISTRootPort OBJECT-TYPE
   SYNTAX       DisplayString
   MAX-ACCESS   read-only
   STATUS       current
   DESCRIPTION
       "The switch port currently assigned the root port role."
   ::= { gs2326plusCISTBridgeSTPStatus 4 }

gs2326plusCISTRootCost OBJECT-TYPE
   SYNTAX       Integer32(0..200000000)
   MAX-ACCESS   read-only
   STATUS       current
   DESCRIPTION
       "Root Path Cost."
   ::= { gs2326plusCISTBridgeSTPStatus 5 }

gs2326plusCISTRegionalRoot OBJECT-TYPE
   SYNTAX       DisplayString
   MAX-ACCESS   read-only
   STATUS       current
   DESCRIPTION
       "The Bridge ID of the currently elected regional root bridge, inside the MSTP region of this bridge."
   ::= { gs2326plusCISTBridgeSTPStatus 6 }

gs2326plusCISTInternalRootCost OBJECT-TYPE
   SYNTAX       Integer32(0..200000000)
   MAX-ACCESS   read-only
   STATUS       current
   DESCRIPTION
       "The Regional Root Path Cost."
   ::= { gs2326plusCISTBridgeSTPStatus 7 }

gs2326plusCISTTopologyFlag OBJECT-TYPE
   SYNTAX       DisplayString
   MAX-ACCESS   read-only
   STATUS       current
   DESCRIPTION
       "The current state of the Topology Change Flag of this Bridge instance."
   ::= { gs2326plusCISTBridgeSTPStatus 8 }

gs2326plusCISTTopologyChangeCount OBJECT-TYPE
   SYNTAX       Counter32
   MAX-ACCESS   read-only
   STATUS       current
   DESCRIPTION
       "The number of times where the topology change flag has been set."
   ::= { gs2326plusCISTBridgeSTPStatus 9 }

gs2326plusCISTTopologyChangeLast OBJECT-TYPE
   SYNTAX       DisplayString
   MAX-ACCESS   read-only
   STATUS       current
   DESCRIPTION
       "The time passed since the Topology Flag was last set."
   ::= { gs2326plusCISTBridgeSTPStatus 10 }

gs2326plusCISTPortStateTable OBJECT-TYPE
   SYNTAX      SEQUENCE OF Gs2326plusCISTPortStateEntry
   MAX-ACCESS  not-accessible
   STATUS      current
   DESCRIPTION
       " Show CIST Ports and Aggregations State Configurations. "
   ::= { gs2326plusCISTBridgeSTP 2 }

gs2326plusCISTPortStateEntry OBJECT-TYPE
   SYNTAX      Gs2326plusCISTPortStateEntry
   MAX-ACCESS  not-accessible
   STATUS      current
   DESCRIPTION
       ""
   INDEX    { gs2326plusCISTPortStateIndex  }
   ::= { gs2326plusCISTPortStateTable 1 }

Gs2326plusCISTPortStateEntry ::= SEQUENCE {
   gs2326plusCISTPortStateIndex        Integer32,
   gs2326plusCISTPortStatePort         DisplayString,
   gs2326plusCISTPortStatePortID       DisplayString,
   gs2326plusCISTPortStateRole         DisplayString,
   gs2326plusCISTPortStateState        DisplayString,
   gs2326plusCISTPortStatePathCost     Integer32,
   gs2326plusCISTPortStateEdge         DisplayString,
   gs2326plusCISTPortStatePoint2Point  DisplayString,
   gs2326plusCISTPortStateUptime       DisplayString
}

gs2326plusCISTPortStateIndex OBJECT-TYPE
   SYNTAX      Integer32(1..4095)
   MAX-ACCESS  not-accessible
   STATUS      current
   DESCRIPTION
       "table index."
   ::= { gs2326plusCISTPortStateEntry 1 }

gs2326plusCISTPortStatePort OBJECT-TYPE
   SYNTAX      DisplayString
   MAX-ACCESS  read-only
   STATUS      current
   DESCRIPTION
       "The switch port number of the logical STP port."
   ::= { gs2326plusCISTPortStateEntry 2 }

gs2326plusCISTPortStatePortID OBJECT-TYPE
   SYNTAX      DisplayString
   MAX-ACCESS  read-only
   STATUS      current
   DESCRIPTION
       "The port id as used by the STP protocol.
        This is the priority part and the logical port index of the bridge port."
   ::= { gs2326plusCISTPortStateEntry 3 }

gs2326plusCISTPortStateRole OBJECT-TYPE
   SYNTAX      DisplayString
   MAX-ACCESS  read-only
   STATUS      current
   DESCRIPTION
       "The current STP port role."
   ::= { gs2326plusCISTPortStateEntry 4 }

gs2326plusCISTPortStateState OBJECT-TYPE
   SYNTAX      DisplayString
   MAX-ACCESS  read-only
   STATUS      current
   DESCRIPTION
       "The current STP port state."
   ::= { gs2326plusCISTPortStateEntry 5 }

gs2326plusCISTPortStatePathCost OBJECT-TYPE
   SYNTAX      Integer32(0..200000000)
   MAX-ACCESS  read-only
   STATUS      current
   DESCRIPTION
       "The current STP port path cost."
   ::= { gs2326plusCISTPortStateEntry 6 }

gs2326plusCISTPortStateEdge OBJECT-TYPE
   SYNTAX      DisplayString
   MAX-ACCESS  read-only
   STATUS      current
   DESCRIPTION
       "The current STP port Edge Flag."
   ::= { gs2326plusCISTPortStateEntry 7 }

gs2326plusCISTPortStatePoint2Point OBJECT-TYPE
   SYNTAX      DisplayString
   MAX-ACCESS  read-only
   STATUS      current
   DESCRIPTION
       "The current STP port point-to-point flag."
   ::= { gs2326plusCISTPortStateEntry 8 }

gs2326plusCISTPortStateUptime OBJECT-TYPE
   SYNTAX      DisplayString
   MAX-ACCESS  read-only
   STATUS      current
   DESCRIPTION
       "The time since the bridge port was last initialized."
   ::= { gs2326plusCISTPortStateEntry 9 }

gs2326plusMSTI1BridgeSTP                                                        OBJECT IDENTIFIER ::= { gs2326plusSTPBridgeStatus 2 }

gs2326plusMSTI1BridgeSTPStatus                                                  OBJECT IDENTIFIER ::= { gs2326plusMSTI1BridgeSTP 1 }

gs2326plusMSTI1BridgeInstance OBJECT-TYPE
   SYNTAX       DisplayString
   MAX-ACCESS   read-only
   STATUS       current
   DESCRIPTION
       "The Bridge instance - CIST, MST1, ..."
   ::= { gs2326plusMSTI1BridgeSTPStatus 1 }

gs2326plusMSTI1BridgeID OBJECT-TYPE
   SYNTAX       DisplayString
   MAX-ACCESS   read-only
   STATUS       current
   DESCRIPTION
       "The Bridge ID of this Bridge instance."
   ::= { gs2326plusMSTI1BridgeSTPStatus 2 }

gs2326plusMSTI1RootID OBJECT-TYPE
   SYNTAX       DisplayString
   MAX-ACCESS   read-only
   STATUS       current
   DESCRIPTION
       "The Bridge ID of the currently elected root bridge."
   ::= { gs2326plusMSTI1BridgeSTPStatus 3 }

gs2326plusMSTI1RootPort OBJECT-TYPE
   SYNTAX       DisplayString
   MAX-ACCESS   read-only
   STATUS       current
   DESCRIPTION
       "The switch port currently assigned the root port role."
   ::= { gs2326plusMSTI1BridgeSTPStatus 4 }

gs2326plusMSTI1RootCost OBJECT-TYPE
   SYNTAX       Integer32(0..200000000)
   MAX-ACCESS   read-only
   STATUS       current
   DESCRIPTION
       "Root Path Cost."
   ::= { gs2326plusMSTI1BridgeSTPStatus 5 }

gs2326plusMSTI1TopologyFlag OBJECT-TYPE
   SYNTAX       DisplayString
   MAX-ACCESS   read-only
   STATUS       current
   DESCRIPTION
       "The current state of the Topology Change Flag of this Bridge instance."
   ::= { gs2326plusMSTI1BridgeSTPStatus 8 }

gs2326plusMSTI1TopologyChangeCount OBJECT-TYPE
   SYNTAX       Counter32
   MAX-ACCESS   read-only
   STATUS       current
   DESCRIPTION
       "The number of times where the topology change flag has been set."
   ::= { gs2326plusMSTI1BridgeSTPStatus 9 }

gs2326plusMSTI1TopologyChangeLast OBJECT-TYPE
   SYNTAX       DisplayString
   MAX-ACCESS   read-only
   STATUS       current
   DESCRIPTION
       "The time passed since the Topology Flag was last set."
   ::= { gs2326plusMSTI1BridgeSTPStatus 10 }

gs2326plusMSTI1PortStateTable OBJECT-TYPE
   SYNTAX      SEQUENCE OF Gs2326plusMSTI1PortStateEntry
   MAX-ACCESS  not-accessible
   STATUS      current
   DESCRIPTION
       " Show MSTI1 Ports and Aggregations State Configurations. "
   ::= { gs2326plusMSTI1BridgeSTP 2 }

gs2326plusMSTI1PortStateEntry OBJECT-TYPE
   SYNTAX      Gs2326plusMSTI1PortStateEntry
   MAX-ACCESS  not-accessible
   STATUS      current
   DESCRIPTION
       ""
   INDEX    { gs2326plusMSTI1PortStateIndex  }
   ::= { gs2326plusMSTI1PortStateTable 1 }

Gs2326plusMSTI1PortStateEntry ::= SEQUENCE {
   gs2326plusMSTI1PortStateIndex        Integer32,
   gs2326plusMSTI1PortStatePort         DisplayString,
   gs2326plusMSTI1PortStatePortID       DisplayString,
   gs2326plusMSTI1PortStateRole         DisplayString,
   gs2326plusMSTI1PortStateState        DisplayString,
   gs2326plusMSTI1PortStatePathCost     Integer32,
   gs2326plusMSTI1PortStateEdge         DisplayString,
   gs2326plusMSTI1PortStatePoint2Point  DisplayString,
   gs2326plusMSTI1PortStateUptime       DisplayString
}

gs2326plusMSTI1PortStateIndex OBJECT-TYPE
   SYNTAX      Integer32(1..4095)
   MAX-ACCESS  not-accessible
   STATUS      current
   DESCRIPTION
       "table index."
   ::= { gs2326plusMSTI1PortStateEntry 1 }

gs2326plusMSTI1PortStatePort OBJECT-TYPE
   SYNTAX      DisplayString
   MAX-ACCESS  read-only
   STATUS      current
   DESCRIPTION
       "The switch port number of the logical STP port."
   ::= { gs2326plusMSTI1PortStateEntry 2 }

gs2326plusMSTI1PortStatePortID OBJECT-TYPE
   SYNTAX      DisplayString
   MAX-ACCESS  read-only
   STATUS      current
   DESCRIPTION
       "The port id as used by the STP protocol.
        This is the priority part and the logical port index of the bridge port."
   ::= { gs2326plusMSTI1PortStateEntry 3 }

gs2326plusMSTI1PortStateRole OBJECT-TYPE
   SYNTAX      DisplayString
   MAX-ACCESS  read-only
   STATUS      current
   DESCRIPTION
       "The current STP port role."
   ::= { gs2326plusMSTI1PortStateEntry 4 }

gs2326plusMSTI1PortStateState OBJECT-TYPE
   SYNTAX      DisplayString
   MAX-ACCESS  read-only
   STATUS      current
   DESCRIPTION
       "The current STP port state."
   ::= { gs2326plusMSTI1PortStateEntry 5 }

gs2326plusMSTI1PortStatePathCost OBJECT-TYPE
   SYNTAX      Integer32(0..200000000)
   MAX-ACCESS  read-only
   STATUS      current
   DESCRIPTION
       "The current STP port path cost."
   ::= { gs2326plusMSTI1PortStateEntry 6 }

gs2326plusMSTI1PortStateEdge OBJECT-TYPE
   SYNTAX      DisplayString
   MAX-ACCESS  read-only
   STATUS      current
   DESCRIPTION
       "The current STP port Edge Flag."
   ::= { gs2326plusMSTI1PortStateEntry 7 }

gs2326plusMSTI1PortStatePoint2Point OBJECT-TYPE
   SYNTAX      DisplayString
   MAX-ACCESS  read-only
   STATUS      current
   DESCRIPTION
       "The current STP port point-to-point flag."
   ::= { gs2326plusMSTI1PortStateEntry 8 }

gs2326plusMSTI1PortStateUptime OBJECT-TYPE
   SYNTAX      DisplayString
   MAX-ACCESS  read-only
   STATUS      current
   DESCRIPTION
       "The time since the bridge port was last initialized."
   ::= { gs2326plusMSTI1PortStateEntry 9 }

gs2326plusMSTI2BridgeSTP                                                        OBJECT IDENTIFIER ::= { gs2326plusSTPBridgeStatus 3 }

gs2326plusMSTI2BridgeSTPStatus                                                  OBJECT IDENTIFIER ::= { gs2326plusMSTI2BridgeSTP 1 }

gs2326plusMSTI2BridgeInstance OBJECT-TYPE
   SYNTAX       DisplayString
   MAX-ACCESS   read-only
   STATUS       current
   DESCRIPTION
       "The Bridge instance - CIST, MST1, ..."
   ::= { gs2326plusMSTI2BridgeSTPStatus 1 }

gs2326plusMSTI2BridgeID OBJECT-TYPE
   SYNTAX       DisplayString
   MAX-ACCESS   read-only
   STATUS       current
   DESCRIPTION
       "The Bridge ID of this Bridge instance."
   ::= { gs2326plusMSTI2BridgeSTPStatus 2 }

gs2326plusMSTI2RootID OBJECT-TYPE
   SYNTAX       DisplayString
   MAX-ACCESS   read-only
   STATUS       current
   DESCRIPTION
       "The Bridge ID of the currently elected root bridge."
   ::= { gs2326plusMSTI2BridgeSTPStatus 3 }

gs2326plusMSTI2RootPort OBJECT-TYPE
   SYNTAX       DisplayString
   MAX-ACCESS   read-only
   STATUS       current
   DESCRIPTION
       "The switch port currently assigned the root port role."
   ::= { gs2326plusMSTI2BridgeSTPStatus 4 }

gs2326plusMSTI2RootCost OBJECT-TYPE
   SYNTAX       Integer32(0..200000000)
   MAX-ACCESS   read-only
   STATUS       current
   DESCRIPTION
       "Root Path Cost."
   ::= { gs2326plusMSTI2BridgeSTPStatus 5 }

gs2326plusMSTI2TopologyFlag OBJECT-TYPE
   SYNTAX       DisplayString
   MAX-ACCESS   read-only
   STATUS       current
   DESCRIPTION
       "The current state of the Topology Change Flag of this Bridge instance."
   ::= { gs2326plusMSTI2BridgeSTPStatus 8 }

gs2326plusMSTI2TopologyChangeCount OBJECT-TYPE
   SYNTAX       Counter32
   MAX-ACCESS   read-only
   STATUS       current
   DESCRIPTION
       "The number of times where the topology change flag has been set."
   ::= { gs2326plusMSTI2BridgeSTPStatus 9 }

gs2326plusMSTI2TopologyChangeLast OBJECT-TYPE
   SYNTAX       DisplayString
   MAX-ACCESS   read-only
   STATUS       current
   DESCRIPTION
       "The time passed since the Topology Flag was last set."
   ::= { gs2326plusMSTI2BridgeSTPStatus 10 }

gs2326plusMSTI2PortStateTable OBJECT-TYPE
   SYNTAX      SEQUENCE OF Gs2326plusMSTI2PortStateEntry
   MAX-ACCESS  not-accessible
   STATUS      current
   DESCRIPTION
       " Show MSTI2 Ports and Aggregations State Configurations. "
   ::= { gs2326plusMSTI2BridgeSTP 2 }

gs2326plusMSTI2PortStateEntry OBJECT-TYPE
   SYNTAX      Gs2326plusMSTI2PortStateEntry
   MAX-ACCESS  not-accessible
   STATUS      current
   DESCRIPTION
       ""
   INDEX    { gs2326plusMSTI2PortStateIndex  }
   ::= { gs2326plusMSTI2PortStateTable 1 }

Gs2326plusMSTI2PortStateEntry ::= SEQUENCE {
   gs2326plusMSTI2PortStateIndex        Integer32,
   gs2326plusMSTI2PortStatePort         DisplayString,
   gs2326plusMSTI2PortStatePortID       DisplayString,
   gs2326plusMSTI2PortStateRole         DisplayString,
   gs2326plusMSTI2PortStateState        DisplayString,
   gs2326plusMSTI2PortStatePathCost     Integer32,
   gs2326plusMSTI2PortStateEdge         DisplayString,
   gs2326plusMSTI2PortStatePoint2Point  DisplayString,
   gs2326plusMSTI2PortStateUptime       DisplayString
}

gs2326plusMSTI2PortStateIndex OBJECT-TYPE
   SYNTAX      Integer32(1..4095)
   MAX-ACCESS  not-accessible
   STATUS      current
   DESCRIPTION
       "table index."
   ::= { gs2326plusMSTI2PortStateEntry 1 }

gs2326plusMSTI2PortStatePort OBJECT-TYPE
   SYNTAX      DisplayString
   MAX-ACCESS  read-only
   STATUS      current
   DESCRIPTION
       "The switch port number of the logical STP port."
   ::= { gs2326plusMSTI2PortStateEntry 2 }

gs2326plusMSTI2PortStatePortID OBJECT-TYPE
   SYNTAX      DisplayString
   MAX-ACCESS  read-only
   STATUS      current
   DESCRIPTION
       "The port id as used by the STP protocol.
        This is the priority part and the logical port index of the bridge port."
   ::= { gs2326plusMSTI2PortStateEntry 3 }

gs2326plusMSTI2PortStateRole OBJECT-TYPE
   SYNTAX      DisplayString
   MAX-ACCESS  read-only
   STATUS      current
   DESCRIPTION
       "The current STP port role."
   ::= { gs2326plusMSTI2PortStateEntry 4 }

gs2326plusMSTI2PortStateState OBJECT-TYPE
   SYNTAX      DisplayString
   MAX-ACCESS  read-only
   STATUS      current
   DESCRIPTION
       "The current STP port state."
   ::= { gs2326plusMSTI2PortStateEntry 5 }

gs2326plusMSTI2PortStatePathCost OBJECT-TYPE
   SYNTAX      Integer32(0..200000000)
   MAX-ACCESS  read-only
   STATUS      current
   DESCRIPTION
       "The current STP port path cost."
   ::= { gs2326plusMSTI2PortStateEntry 6 }

gs2326plusMSTI2PortStateEdge OBJECT-TYPE
   SYNTAX      DisplayString
   MAX-ACCESS  read-only
   STATUS      current
   DESCRIPTION
       "The current STP port Edge Flag."
   ::= { gs2326plusMSTI2PortStateEntry 7 }

gs2326plusMSTI2PortStatePoint2Point OBJECT-TYPE
   SYNTAX      DisplayString
   MAX-ACCESS  read-only
   STATUS      current
   DESCRIPTION
       "The current STP port point-to-point flag."
   ::= { gs2326plusMSTI2PortStateEntry 8 }

gs2326plusMSTI2PortStateUptime OBJECT-TYPE
   SYNTAX      DisplayString
   MAX-ACCESS  read-only
   STATUS      current
   DESCRIPTION
       "The time since the bridge port was last initialized."
   ::= { gs2326plusMSTI2PortStateEntry 9 }

gs2326plusMSTI3BridgeSTP                                                        OBJECT IDENTIFIER ::= { gs2326plusSTPBridgeStatus 4 }

gs2326plusMSTI3BridgeSTPStatus                                                  OBJECT IDENTIFIER ::= { gs2326plusMSTI3BridgeSTP 1 }

gs2326plusMSTI3BridgeInstance OBJECT-TYPE
   SYNTAX       DisplayString
   MAX-ACCESS   read-only
   STATUS       current
   DESCRIPTION
       "The Bridge instance - CIST, MST1, ..."
   ::= { gs2326plusMSTI3BridgeSTPStatus 1 }

gs2326plusMSTI3BridgeID OBJECT-TYPE
   SYNTAX       DisplayString
   MAX-ACCESS   read-only
   STATUS       current
   DESCRIPTION
       "The Bridge ID of this Bridge instance."
   ::= { gs2326plusMSTI3BridgeSTPStatus 2 }

gs2326plusMSTI3RootID OBJECT-TYPE
   SYNTAX       DisplayString
   MAX-ACCESS   read-only
   STATUS       current
   DESCRIPTION
       "The Bridge ID of the currently elected root bridge."
   ::= { gs2326plusMSTI3BridgeSTPStatus 3 }

gs2326plusMSTI3RootPort OBJECT-TYPE
   SYNTAX       DisplayString
   MAX-ACCESS   read-only
   STATUS       current
   DESCRIPTION
       "The switch port currently assigned the root port role."
   ::= { gs2326plusMSTI3BridgeSTPStatus 4 }

gs2326plusMSTI3RootCost OBJECT-TYPE
   SYNTAX       Integer32(0..200000000)
   MAX-ACCESS   read-only
   STATUS       current
   DESCRIPTION
       "Root Path Cost."
   ::= { gs2326plusMSTI3BridgeSTPStatus 5 }

gs2326plusMSTI3TopologyFlag OBJECT-TYPE
   SYNTAX       DisplayString
   MAX-ACCESS   read-only
   STATUS       current
   DESCRIPTION
       "The current state of the Topology Change Flag of this Bridge instance."
   ::= { gs2326plusMSTI3BridgeSTPStatus 8 }

gs2326plusMSTI3TopologyChangeCount OBJECT-TYPE
   SYNTAX       Counter32
   MAX-ACCESS   read-only
   STATUS       current
   DESCRIPTION
       "The number of times where the topology change flag has been set."
   ::= { gs2326plusMSTI3BridgeSTPStatus 9 }

gs2326plusMSTI3TopologyChangeLast OBJECT-TYPE
   SYNTAX       DisplayString
   MAX-ACCESS   read-only
   STATUS       current
   DESCRIPTION
       "The time passed since the Topology Flag was last set."
   ::= { gs2326plusMSTI3BridgeSTPStatus 10 }

gs2326plusMSTI3PortStateTable OBJECT-TYPE
   SYNTAX      SEQUENCE OF Gs2326plusMSTI3PortStateEntry
   MAX-ACCESS  not-accessible
   STATUS      current
   DESCRIPTION
       " Show MSTI3 Ports and Aggregations State Configurations. "
   ::= { gs2326plusMSTI3BridgeSTP 2 }

gs2326plusMSTI3PortStateEntry OBJECT-TYPE
   SYNTAX      Gs2326plusMSTI3PortStateEntry
   MAX-ACCESS  not-accessible
   STATUS      current
   DESCRIPTION
       ""
   INDEX    { gs2326plusMSTI3PortStateIndex  }
   ::= { gs2326plusMSTI3PortStateTable 1 }

Gs2326plusMSTI3PortStateEntry ::= SEQUENCE {
   gs2326plusMSTI3PortStateIndex        Integer32,
   gs2326plusMSTI3PortStatePort         DisplayString,
   gs2326plusMSTI3PortStatePortID       DisplayString,
   gs2326plusMSTI3PortStateRole         DisplayString,
   gs2326plusMSTI3PortStateState        DisplayString,
   gs2326plusMSTI3PortStatePathCost     Integer32,
   gs2326plusMSTI3PortStateEdge         DisplayString,
   gs2326plusMSTI3PortStatePoint2Point  DisplayString,
   gs2326plusMSTI3PortStateUptime       DisplayString
}

gs2326plusMSTI3PortStateIndex OBJECT-TYPE
   SYNTAX      Integer32(1..4095)
   MAX-ACCESS  not-accessible
   STATUS      current
   DESCRIPTION
       "table index."
   ::= { gs2326plusMSTI3PortStateEntry 1 }

gs2326plusMSTI3PortStatePort OBJECT-TYPE
   SYNTAX      DisplayString
   MAX-ACCESS  read-only
   STATUS      current
   DESCRIPTION
       "The switch port number of the logical STP port."
   ::= { gs2326plusMSTI3PortStateEntry 2 }

gs2326plusMSTI3PortStatePortID OBJECT-TYPE
   SYNTAX      DisplayString
   MAX-ACCESS  read-only
   STATUS      current
   DESCRIPTION
       "The port id as used by the STP protocol.
        This is the priority part and the logical port index of the bridge port."
   ::= { gs2326plusMSTI3PortStateEntry 3 }

gs2326plusMSTI3PortStateRole OBJECT-TYPE
   SYNTAX      DisplayString
   MAX-ACCESS  read-only
   STATUS      current
   DESCRIPTION
       "The current STP port role."
   ::= { gs2326plusMSTI3PortStateEntry 4 }

gs2326plusMSTI3PortStateState OBJECT-TYPE
   SYNTAX      DisplayString
   MAX-ACCESS  read-only
   STATUS      current
   DESCRIPTION
       "The current STP port state."
   ::= { gs2326plusMSTI3PortStateEntry 5 }

gs2326plusMSTI3PortStatePathCost OBJECT-TYPE
   SYNTAX      Integer32(0..200000000)
   MAX-ACCESS  read-only
   STATUS      current
   DESCRIPTION
       "The current STP port path cost."
   ::= { gs2326plusMSTI3PortStateEntry 6 }

gs2326plusMSTI3PortStateEdge OBJECT-TYPE
   SYNTAX      DisplayString
   MAX-ACCESS  read-only
   STATUS      current
   DESCRIPTION
       "The current STP port Edge Flag."
   ::= { gs2326plusMSTI3PortStateEntry 7 }

gs2326plusMSTI3PortStatePoint2Point OBJECT-TYPE
   SYNTAX      DisplayString
   MAX-ACCESS  read-only
   STATUS      current
   DESCRIPTION
       "The current STP port point-to-point flag."
   ::= { gs2326plusMSTI3PortStateEntry 8 }

gs2326plusMSTI3PortStateUptime OBJECT-TYPE
   SYNTAX      DisplayString
   MAX-ACCESS  read-only
   STATUS      current
   DESCRIPTION
       "The time since the bridge port was last initialized."
   ::= { gs2326plusMSTI3PortStateEntry 9 }

gs2326plusMSTI4BridgeSTP                                                        OBJECT IDENTIFIER ::= { gs2326plusSTPBridgeStatus 5 }

gs2326plusMSTI4BridgeSTPStatus                                                  OBJECT IDENTIFIER ::= { gs2326plusMSTI4BridgeSTP 1 }

gs2326plusMSTI4BridgeInstance OBJECT-TYPE
   SYNTAX       DisplayString
   MAX-ACCESS   read-only
   STATUS       current
   DESCRIPTION
       "The Bridge instance - CIST, MST1, ..."
   ::= { gs2326plusMSTI4BridgeSTPStatus 1 }

gs2326plusMSTI4BridgeID OBJECT-TYPE
   SYNTAX       DisplayString
   MAX-ACCESS   read-only
   STATUS       current
   DESCRIPTION
       "The Bridge ID of this Bridge instance."
   ::= { gs2326plusMSTI4BridgeSTPStatus 2 }

gs2326plusMSTI4RootID OBJECT-TYPE
   SYNTAX       DisplayString
   MAX-ACCESS   read-only
   STATUS       current
   DESCRIPTION
       "The Bridge ID of the currently elected root bridge."
   ::= { gs2326plusMSTI4BridgeSTPStatus 3 }

gs2326plusMSTI4RootPort OBJECT-TYPE
   SYNTAX       DisplayString
   MAX-ACCESS   read-only
   STATUS       current
   DESCRIPTION
       "The switch port currently assigned the root port role."
   ::= { gs2326plusMSTI4BridgeSTPStatus 4 }

gs2326plusMSTI4RootCost OBJECT-TYPE
   SYNTAX       Integer32(0..200000000)
   MAX-ACCESS   read-only
   STATUS       current
   DESCRIPTION
       "Root Path Cost."
   ::= { gs2326plusMSTI4BridgeSTPStatus 5 }

gs2326plusMSTI4TopologyFlag OBJECT-TYPE
   SYNTAX       DisplayString
   MAX-ACCESS   read-only
   STATUS       current
   DESCRIPTION
       "The current state of the Topology Change Flag of this Bridge instance."
   ::= { gs2326plusMSTI4BridgeSTPStatus 8 }

gs2326plusMSTI4TopologyChangeCount OBJECT-TYPE
   SYNTAX       Counter32
   MAX-ACCESS   read-only
   STATUS       current
   DESCRIPTION
       "The number of times where the topology change flag has been set."
   ::= { gs2326plusMSTI4BridgeSTPStatus 9 }

gs2326plusMSTI4TopologyChangeLast OBJECT-TYPE
   SYNTAX       DisplayString
   MAX-ACCESS   read-only
   STATUS       current
   DESCRIPTION
       "The time passed since the Topology Flag was last set."
   ::= { gs2326plusMSTI4BridgeSTPStatus 10 }

gs2326plusMSTI4PortStateTable OBJECT-TYPE
   SYNTAX      SEQUENCE OF Gs2326plusMSTI4PortStateEntry
   MAX-ACCESS  not-accessible
   STATUS      current
   DESCRIPTION
       " Show MSTI4 Ports and Aggregations State Configurations. "
   ::= { gs2326plusMSTI4BridgeSTP 2 }

gs2326plusMSTI4PortStateEntry OBJECT-TYPE
   SYNTAX      Gs2326plusMSTI4PortStateEntry
   MAX-ACCESS  not-accessible
   STATUS      current
   DESCRIPTION
       ""
   INDEX    { gs2326plusMSTI4PortStateIndex  }
   ::= { gs2326plusMSTI4PortStateTable 1 }

Gs2326plusMSTI4PortStateEntry ::= SEQUENCE {
   gs2326plusMSTI4PortStateIndex        Integer32,
   gs2326plusMSTI4PortStatePort         DisplayString,
   gs2326plusMSTI4PortStatePortID       DisplayString,
   gs2326plusMSTI4PortStateRole         DisplayString,
   gs2326plusMSTI4PortStateState        DisplayString,
   gs2326plusMSTI4PortStatePathCost     Integer32,
   gs2326plusMSTI4PortStateEdge         DisplayString,
   gs2326plusMSTI4PortStatePoint2Point  DisplayString,
   gs2326plusMSTI4PortStateUptime       DisplayString
}

gs2326plusMSTI4PortStateIndex OBJECT-TYPE
   SYNTAX      Integer32(1..4095)
   MAX-ACCESS  not-accessible
   STATUS      current
   DESCRIPTION
       "table index."
   ::= { gs2326plusMSTI4PortStateEntry 1 }

gs2326plusMSTI4PortStatePort OBJECT-TYPE
   SYNTAX      DisplayString
   MAX-ACCESS  read-only
   STATUS      current
   DESCRIPTION
       "The switch port number of the logical STP port."
   ::= { gs2326plusMSTI4PortStateEntry 2 }

gs2326plusMSTI4PortStatePortID OBJECT-TYPE
   SYNTAX      DisplayString
   MAX-ACCESS  read-only
   STATUS      current
   DESCRIPTION
       "The port id as used by the STP protocol.
        This is the priority part and the logical port index of the bridge port."
   ::= { gs2326plusMSTI4PortStateEntry 3 }

gs2326plusMSTI4PortStateRole OBJECT-TYPE
   SYNTAX      DisplayString
   MAX-ACCESS  read-only
   STATUS      current
   DESCRIPTION
       "The current STP port role."
   ::= { gs2326plusMSTI4PortStateEntry 4 }

gs2326plusMSTI4PortStateState OBJECT-TYPE
   SYNTAX      DisplayString
   MAX-ACCESS  read-only
   STATUS      current
   DESCRIPTION
       "The current STP port state."
   ::= { gs2326plusMSTI4PortStateEntry 5 }

gs2326plusMSTI4PortStatePathCost OBJECT-TYPE
   SYNTAX      Integer32(0..200000000)
   MAX-ACCESS  read-only
   STATUS      current
   DESCRIPTION
       "The current STP port path cost."
   ::= { gs2326plusMSTI4PortStateEntry 6 }

gs2326plusMSTI4PortStateEdge OBJECT-TYPE
   SYNTAX      DisplayString
   MAX-ACCESS  read-only
   STATUS      current
   DESCRIPTION
       "The current STP port Edge Flag."
   ::= { gs2326plusMSTI4PortStateEntry 7 }

gs2326plusMSTI4PortStatePoint2Point OBJECT-TYPE
   SYNTAX      DisplayString
   MAX-ACCESS  read-only
   STATUS      current
   DESCRIPTION
       "The current STP port point-to-point flag."
   ::= { gs2326plusMSTI4PortStateEntry 8 }

gs2326plusMSTI4PortStateUptime OBJECT-TYPE
   SYNTAX      DisplayString
   MAX-ACCESS  read-only
   STATUS      current
   DESCRIPTION
       "The time since the bridge port was last initialized."
   ::= { gs2326plusMSTI4PortStateEntry 9 }

gs2326plusMSTI5BridgeSTP                                                        OBJECT IDENTIFIER ::= { gs2326plusSTPBridgeStatus 6 }

gs2326plusMSTI5BridgeSTPStatus                                                  OBJECT IDENTIFIER ::= { gs2326plusMSTI5BridgeSTP 1 }

gs2326plusMSTI5BridgeInstance OBJECT-TYPE
   SYNTAX       DisplayString
   MAX-ACCESS   read-only
   STATUS       current
   DESCRIPTION
       "The Bridge instance - CIST, MST1, ..."
   ::= { gs2326plusMSTI5BridgeSTPStatus 1 }

gs2326plusMSTI5BridgeID OBJECT-TYPE
   SYNTAX       DisplayString
   MAX-ACCESS   read-only
   STATUS       current
   DESCRIPTION
       "The Bridge ID of this Bridge instance."
   ::= { gs2326plusMSTI5BridgeSTPStatus 2 }

gs2326plusMSTI5RootID OBJECT-TYPE
   SYNTAX       DisplayString
   MAX-ACCESS   read-only
   STATUS       current
   DESCRIPTION
       "The Bridge ID of the currently elected root bridge."
   ::= { gs2326plusMSTI5BridgeSTPStatus 3 }

gs2326plusMSTI5RootPort OBJECT-TYPE
   SYNTAX       DisplayString
   MAX-ACCESS   read-only
   STATUS       current
   DESCRIPTION
       "The switch port currently assigned the root port role."
   ::= { gs2326plusMSTI5BridgeSTPStatus 4 }

gs2326plusMSTI5RootCost OBJECT-TYPE
   SYNTAX       Integer32(0..200000000)
   MAX-ACCESS   read-only
   STATUS       current
   DESCRIPTION
       "Root Path Cost."
   ::= { gs2326plusMSTI5BridgeSTPStatus 5 }

gs2326plusMSTI5TopologyFlag OBJECT-TYPE
   SYNTAX       DisplayString
   MAX-ACCESS   read-only
   STATUS       current
   DESCRIPTION
       "The current state of the Topology Change Flag of this Bridge instance."
   ::= { gs2326plusMSTI5BridgeSTPStatus 8 }

gs2326plusMSTI5TopologyChangeCount OBJECT-TYPE
   SYNTAX       Counter32
   MAX-ACCESS   read-only
   STATUS       current
   DESCRIPTION
       "The number of times where the topology change flag has been set."
   ::= { gs2326plusMSTI5BridgeSTPStatus 9 }

gs2326plusMSTI5TopologyChangeLast OBJECT-TYPE
   SYNTAX       DisplayString
   MAX-ACCESS   read-only
   STATUS       current
   DESCRIPTION
       "The time passed since the Topology Flag was last set."
   ::= { gs2326plusMSTI5BridgeSTPStatus 10 }

gs2326plusMSTI5PortStateTable OBJECT-TYPE
   SYNTAX      SEQUENCE OF Gs2326plusMSTI5PortStateEntry
   MAX-ACCESS  not-accessible
   STATUS      current
   DESCRIPTION
       " Show MSTI5 Ports and Aggregations State Configurations. "
   ::= { gs2326plusMSTI5BridgeSTP 2 }

gs2326plusMSTI5PortStateEntry OBJECT-TYPE
   SYNTAX      Gs2326plusMSTI5PortStateEntry
   MAX-ACCESS  not-accessible
   STATUS      current
   DESCRIPTION
       ""
   INDEX    { gs2326plusMSTI5PortStateIndex  }
   ::= { gs2326plusMSTI5PortStateTable 1 }

Gs2326plusMSTI5PortStateEntry ::= SEQUENCE {
   gs2326plusMSTI5PortStateIndex        Integer32,
   gs2326plusMSTI5PortStatePort         DisplayString,
   gs2326plusMSTI5PortStatePortID       DisplayString,
   gs2326plusMSTI5PortStateRole         DisplayString,
   gs2326plusMSTI5PortStateState        DisplayString,
   gs2326plusMSTI5PortStatePathCost     Integer32,
   gs2326plusMSTI5PortStateEdge         DisplayString,
   gs2326plusMSTI5PortStatePoint2Point  DisplayString,
   gs2326plusMSTI5PortStateUptime       DisplayString
}

gs2326plusMSTI5PortStateIndex OBJECT-TYPE
   SYNTAX      Integer32(1..4095)
   MAX-ACCESS  not-accessible
   STATUS      current
   DESCRIPTION
       "table index."
   ::= { gs2326plusMSTI5PortStateEntry 1 }

gs2326plusMSTI5PortStatePort OBJECT-TYPE
   SYNTAX      DisplayString
   MAX-ACCESS  read-only
   STATUS      current
   DESCRIPTION
       "The switch port number of the logical STP port."
   ::= { gs2326plusMSTI5PortStateEntry 2 }

gs2326plusMSTI5PortStatePortID OBJECT-TYPE
   SYNTAX      DisplayString
   MAX-ACCESS  read-only
   STATUS      current
   DESCRIPTION
       "The port id as used by the STP protocol.
        This is the priority part and the logical port index of the bridge port."
   ::= { gs2326plusMSTI5PortStateEntry 3 }

gs2326plusMSTI5PortStateRole OBJECT-TYPE
   SYNTAX      DisplayString
   MAX-ACCESS  read-only
   STATUS      current
   DESCRIPTION
       "The current STP port role."
   ::= { gs2326plusMSTI5PortStateEntry 4 }

gs2326plusMSTI5PortStateState OBJECT-TYPE
   SYNTAX      DisplayString
   MAX-ACCESS  read-only
   STATUS      current
   DESCRIPTION
       "The current STP port state."
   ::= { gs2326plusMSTI5PortStateEntry 5 }

gs2326plusMSTI5PortStatePathCost OBJECT-TYPE
   SYNTAX      Integer32(0..200000000)
   MAX-ACCESS  read-only
   STATUS      current
   DESCRIPTION
       "The current STP port path cost."
   ::= { gs2326plusMSTI5PortStateEntry 6 }

gs2326plusMSTI5PortStateEdge OBJECT-TYPE
   SYNTAX      DisplayString
   MAX-ACCESS  read-only
   STATUS      current
   DESCRIPTION
       "The current STP port Edge Flag."
   ::= { gs2326plusMSTI5PortStateEntry 7 }

gs2326plusMSTI5PortStatePoint2Point OBJECT-TYPE
   SYNTAX      DisplayString
   MAX-ACCESS  read-only
   STATUS      current
   DESCRIPTION
       "The current STP port point-to-point flag."
   ::= { gs2326plusMSTI5PortStateEntry 8 }

gs2326plusMSTI5PortStateUptime OBJECT-TYPE
   SYNTAX      DisplayString
   MAX-ACCESS  read-only
   STATUS      current
   DESCRIPTION
       "The time since the bridge port was last initialized."
   ::= { gs2326plusMSTI5PortStateEntry 9 }

gs2326plusMSTI6BridgeSTP                                                        OBJECT IDENTIFIER ::= { gs2326plusSTPBridgeStatus 7 }

gs2326plusMSTI6BridgeSTPStatus                                                  OBJECT IDENTIFIER ::= { gs2326plusMSTI6BridgeSTP 1 }

gs2326plusMSTI6BridgeInstance OBJECT-TYPE
   SYNTAX       DisplayString
   MAX-ACCESS   read-only
   STATUS       current
   DESCRIPTION
       "The Bridge instance - CIST, MST1, ..."
   ::= { gs2326plusMSTI6BridgeSTPStatus 1 }

gs2326plusMSTI6BridgeID OBJECT-TYPE
   SYNTAX       DisplayString
   MAX-ACCESS   read-only
   STATUS       current
   DESCRIPTION
       "The Bridge ID of this Bridge instance."
   ::= { gs2326plusMSTI6BridgeSTPStatus 2 }

gs2326plusMSTI6RootID OBJECT-TYPE
   SYNTAX       DisplayString
   MAX-ACCESS   read-only
   STATUS       current
   DESCRIPTION
       "The Bridge ID of the currently elected root bridge."
   ::= { gs2326plusMSTI6BridgeSTPStatus 3 }

gs2326plusMSTI6RootPort OBJECT-TYPE
   SYNTAX       DisplayString
   MAX-ACCESS   read-only
   STATUS       current
   DESCRIPTION
       "The switch port currently assigned the root port role."
   ::= { gs2326plusMSTI6BridgeSTPStatus 4 }

gs2326plusMSTI6RootCost OBJECT-TYPE
   SYNTAX       Integer32(0..200000000)
   MAX-ACCESS   read-only
   STATUS       current
   DESCRIPTION
       "Root Path Cost."
   ::= { gs2326plusMSTI6BridgeSTPStatus 5 }

gs2326plusMSTI6TopologyFlag OBJECT-TYPE
   SYNTAX       DisplayString
   MAX-ACCESS   read-only
   STATUS       current
   DESCRIPTION
       "The current state of the Topology Change Flag of this Bridge instance."
   ::= { gs2326plusMSTI6BridgeSTPStatus 8 }

gs2326plusMSTI6TopologyChangeCount OBJECT-TYPE
   SYNTAX       Counter32
   MAX-ACCESS   read-only
   STATUS       current
   DESCRIPTION
       "The number of times where the topology change flag has been set."
   ::= { gs2326plusMSTI6BridgeSTPStatus 9 }

gs2326plusMSTI6TopologyChangeLast OBJECT-TYPE
   SYNTAX       DisplayString
   MAX-ACCESS   read-only
   STATUS       current
   DESCRIPTION
       "The time passed since the Topology Flag was last set."
   ::= { gs2326plusMSTI6BridgeSTPStatus 10 }

gs2326plusMSTI6PortStateTable OBJECT-TYPE
   SYNTAX      SEQUENCE OF Gs2326plusMSTI6PortStateEntry
   MAX-ACCESS  not-accessible
   STATUS      current
   DESCRIPTION
       " Show MSTI6 Ports and Aggregations State Configurations. "
   ::= { gs2326plusMSTI6BridgeSTP 2 }

gs2326plusMSTI6PortStateEntry OBJECT-TYPE
   SYNTAX      Gs2326plusMSTI6PortStateEntry
   MAX-ACCESS  not-accessible
   STATUS      current
   DESCRIPTION
       ""
   INDEX    { gs2326plusMSTI6PortStateIndex  }
   ::= { gs2326plusMSTI6PortStateTable 1 }

Gs2326plusMSTI6PortStateEntry ::= SEQUENCE {
   gs2326plusMSTI6PortStateIndex        Integer32,
   gs2326plusMSTI6PortStatePort         DisplayString,
   gs2326plusMSTI6PortStatePortID       DisplayString,
   gs2326plusMSTI6PortStateRole         DisplayString,
   gs2326plusMSTI6PortStateState        DisplayString,
   gs2326plusMSTI6PortStatePathCost     Integer32,
   gs2326plusMSTI6PortStateEdge         DisplayString,
   gs2326plusMSTI6PortStatePoint2Point  DisplayString,
   gs2326plusMSTI6PortStateUptime       DisplayString
}

gs2326plusMSTI6PortStateIndex OBJECT-TYPE
   SYNTAX      Integer32(1..4095)
   MAX-ACCESS  not-accessible
   STATUS      current
   DESCRIPTION
       "table index."
   ::= { gs2326plusMSTI6PortStateEntry 1 }

gs2326plusMSTI6PortStatePort OBJECT-TYPE
   SYNTAX      DisplayString
   MAX-ACCESS  read-only
   STATUS      current
   DESCRIPTION
       "The switch port number of the logical STP port."
   ::= { gs2326plusMSTI6PortStateEntry 2 }

gs2326plusMSTI6PortStatePortID OBJECT-TYPE
   SYNTAX      DisplayString
   MAX-ACCESS  read-only
   STATUS      current
   DESCRIPTION
       "The port id as used by the STP protocol.
        This is the priority part and the logical port index of the bridge port."
   ::= { gs2326plusMSTI6PortStateEntry 3 }

gs2326plusMSTI6PortStateRole OBJECT-TYPE
   SYNTAX      DisplayString
   MAX-ACCESS  read-only
   STATUS      current
   DESCRIPTION
       "The current STP port role."
   ::= { gs2326plusMSTI6PortStateEntry 4 }

gs2326plusMSTI6PortStateState OBJECT-TYPE
   SYNTAX      DisplayString
   MAX-ACCESS  read-only
   STATUS      current
   DESCRIPTION
       "The current STP port state."
   ::= { gs2326plusMSTI6PortStateEntry 5 }

gs2326plusMSTI6PortStatePathCost OBJECT-TYPE
   SYNTAX      Integer32(0..200000000)
   MAX-ACCESS  read-only
   STATUS      current
   DESCRIPTION
       "The current STP port path cost."
   ::= { gs2326plusMSTI6PortStateEntry 6 }

gs2326plusMSTI6PortStateEdge OBJECT-TYPE
   SYNTAX      DisplayString
   MAX-ACCESS  read-only
   STATUS      current
   DESCRIPTION
       "The current STP port Edge Flag."
   ::= { gs2326plusMSTI6PortStateEntry 7 }

gs2326plusMSTI6PortStatePoint2Point OBJECT-TYPE
   SYNTAX      DisplayString
   MAX-ACCESS  read-only
   STATUS      current
   DESCRIPTION
       "The current STP port point-to-point flag."
   ::= { gs2326plusMSTI6PortStateEntry 8 }

gs2326plusMSTI6PortStateUptime OBJECT-TYPE
   SYNTAX      DisplayString
   MAX-ACCESS  read-only
   STATUS      current
   DESCRIPTION
       "The time since the bridge port was last initialized."
   ::= { gs2326plusMSTI6PortStateEntry 9 }

gs2326plusMSTI7BridgeSTP                                                        OBJECT IDENTIFIER ::= { gs2326plusSTPBridgeStatus 8 }

gs2326plusMSTI7BridgeSTPStatus                                                  OBJECT IDENTIFIER ::= { gs2326plusMSTI7BridgeSTP 1 }

gs2326plusMSTI7BridgeInstance OBJECT-TYPE
   SYNTAX       DisplayString
   MAX-ACCESS   read-only
   STATUS       current
   DESCRIPTION
       "The Bridge instance - CIST, MST1, ..."
   ::= { gs2326plusMSTI7BridgeSTPStatus 1 }

gs2326plusMSTI7BridgeID OBJECT-TYPE
   SYNTAX       DisplayString
   MAX-ACCESS   read-only
   STATUS       current
   DESCRIPTION
       "The Bridge ID of this Bridge instance."
   ::= { gs2326plusMSTI7BridgeSTPStatus 2 }

gs2326plusMSTI7RootID OBJECT-TYPE
   SYNTAX       DisplayString
   MAX-ACCESS   read-only
   STATUS       current
   DESCRIPTION
       "The Bridge ID of the currently elected root bridge."
   ::= { gs2326plusMSTI7BridgeSTPStatus 3 }

gs2326plusMSTI7RootPort OBJECT-TYPE
   SYNTAX       DisplayString
   MAX-ACCESS   read-only
   STATUS       current
   DESCRIPTION
       "The switch port currently assigned the root port role."
   ::= { gs2326plusMSTI7BridgeSTPStatus 4 }

gs2326plusMSTI7RootCost OBJECT-TYPE
   SYNTAX       Integer32(0..200000000)
   MAX-ACCESS   read-only
   STATUS       current
   DESCRIPTION
       "Root Path Cost."
   ::= { gs2326plusMSTI7BridgeSTPStatus 5 }

gs2326plusMSTI7TopologyFlag OBJECT-TYPE
   SYNTAX       DisplayString
   MAX-ACCESS   read-only
   STATUS       current
   DESCRIPTION
       "The current state of the Topology Change Flag of this Bridge instance."
   ::= { gs2326plusMSTI7BridgeSTPStatus 8 }

gs2326plusMSTI7TopologyChangeCount OBJECT-TYPE
   SYNTAX       Counter32
   MAX-ACCESS   read-only
   STATUS       current
   DESCRIPTION
       "The number of times where the topology change flag has been set."
   ::= { gs2326plusMSTI7BridgeSTPStatus 9 }

gs2326plusMSTI7TopologyChangeLast OBJECT-TYPE
   SYNTAX       DisplayString
   MAX-ACCESS   read-only
   STATUS       current
   DESCRIPTION
       "The time passed since the Topology Flag was last set."
   ::= { gs2326plusMSTI7BridgeSTPStatus 10 }

gs2326plusMSTI7PortStateTable OBJECT-TYPE
   SYNTAX      SEQUENCE OF Gs2326plusMSTI7PortStateEntry
   MAX-ACCESS  not-accessible
   STATUS      current
   DESCRIPTION
       " Show MSTI7 Ports and Aggregations State Configurations. "
   ::= { gs2326plusMSTI7BridgeSTP 2 }

gs2326plusMSTI7PortStateEntry OBJECT-TYPE
   SYNTAX      Gs2326plusMSTI7PortStateEntry
   MAX-ACCESS  not-accessible
   STATUS      current
   DESCRIPTION
       ""
   INDEX    { gs2326plusMSTI7PortStateIndex  }
   ::= { gs2326plusMSTI7PortStateTable 1 }

Gs2326plusMSTI7PortStateEntry ::= SEQUENCE {
   gs2326plusMSTI7PortStateIndex        Integer32,
   gs2326plusMSTI7PortStatePort         DisplayString,
   gs2326plusMSTI7PortStatePortID       DisplayString,
   gs2326plusMSTI7PortStateRole         DisplayString,
   gs2326plusMSTI7PortStateState        DisplayString,
   gs2326plusMSTI7PortStatePathCost     Integer32,
   gs2326plusMSTI7PortStateEdge         DisplayString,
   gs2326plusMSTI7PortStatePoint2Point  DisplayString,
   gs2326plusMSTI7PortStateUptime       DisplayString
}

gs2326plusMSTI7PortStateIndex OBJECT-TYPE
   SYNTAX      Integer32(1..4095)
   MAX-ACCESS  not-accessible
   STATUS      current
   DESCRIPTION
       "table index."
   ::= { gs2326plusMSTI7PortStateEntry 1 }

gs2326plusMSTI7PortStatePort OBJECT-TYPE
   SYNTAX      DisplayString
   MAX-ACCESS  read-only
   STATUS      current
   DESCRIPTION
       "The switch port number of the logical STP port."
   ::= { gs2326plusMSTI7PortStateEntry 2 }

gs2326plusMSTI7PortStatePortID OBJECT-TYPE
   SYNTAX      DisplayString
   MAX-ACCESS  read-only
   STATUS      current
   DESCRIPTION
       "The port id as used by the STP protocol.
        This is the priority part and the logical port index of the bridge port."
   ::= { gs2326plusMSTI7PortStateEntry 3 }

gs2326plusMSTI7PortStateRole OBJECT-TYPE
   SYNTAX      DisplayString
   MAX-ACCESS  read-only
   STATUS      current
   DESCRIPTION
       "The current STP port role."
   ::= { gs2326plusMSTI7PortStateEntry 4 }

gs2326plusMSTI7PortStateState OBJECT-TYPE
   SYNTAX      DisplayString
   MAX-ACCESS  read-only
   STATUS      current
   DESCRIPTION
       "The current STP port state."
   ::= { gs2326plusMSTI7PortStateEntry 5 }

gs2326plusMSTI7PortStatePathCost OBJECT-TYPE
   SYNTAX      Integer32(0..200000000)
   MAX-ACCESS  read-only
   STATUS      current
   DESCRIPTION
       "The current STP port path cost."
   ::= { gs2326plusMSTI7PortStateEntry 6 }

gs2326plusMSTI7PortStateEdge OBJECT-TYPE
   SYNTAX      DisplayString
   MAX-ACCESS  read-only
   STATUS      current
   DESCRIPTION
       "The current STP port Edge Flag."
   ::= { gs2326plusMSTI7PortStateEntry 7 }

gs2326plusMSTI7PortStatePoint2Point OBJECT-TYPE
   SYNTAX      DisplayString
   MAX-ACCESS  read-only
   STATUS      current
   DESCRIPTION
       "The current STP port point-to-point flag."
   ::= { gs2326plusMSTI7PortStateEntry 8 }

gs2326plusMSTI7PortStateUptime OBJECT-TYPE
   SYNTAX      DisplayString
   MAX-ACCESS  read-only
   STATUS      current
   DESCRIPTION
       "The time since the bridge port was last initialized."
   ::= { gs2326plusMSTI7PortStateEntry 9 }

gs2326plusSTPPortStatusTable OBJECT-TYPE
   SYNTAX      SEQUENCE OF Gs2326plusSTPPortStatusEntry
   MAX-ACCESS  not-accessible
   STATUS      current
   DESCRIPTION
       " Show STP Port Status."
   ::= { gs2326plusSTP 9 }

gs2326plusSTPPortStatusEntry OBJECT-TYPE
   SYNTAX      Gs2326plusSTPPortStatusEntry
   MAX-ACCESS  not-accessible
   STATUS      current
   DESCRIPTION
       ""
   INDEX    { gs2326plusSTPPortStatusPort  }
   ::= { gs2326plusSTPPortStatusTable 1 }

Gs2326plusSTPPortStatusEntry ::= SEQUENCE {
   gs2326plusSTPPortStatusPort         Integer32,
   gs2326plusSTPPortStatusCISTRole     DisplayString,
   gs2326plusSTPPortStatusCISTState    DisplayString,
   gs2326plusSTPPortStatusUptime       DisplayString
}

gs2326plusSTPPortStatusPort OBJECT-TYPE
   SYNTAX      Integer32(1..4095)
   MAX-ACCESS  not-accessible
   STATUS      current
   DESCRIPTION
       " port, range : 1 - port number. "
   ::= { gs2326plusSTPPortStatusEntry 1 }

gs2326plusSTPPortStatusCISTRole OBJECT-TYPE
   SYNTAX      DisplayString
   MAX-ACCESS  read-only
   STATUS      current
   DESCRIPTION
       " The current STP port role of the CIST port. "
   ::= { gs2326plusSTPPortStatusEntry 2 }

gs2326plusSTPPortStatusCISTState OBJECT-TYPE
   SYNTAX      DisplayString
   MAX-ACCESS  read-only
   STATUS      current
   DESCRIPTION
       " The current STP port state of the CIST port. "
   ::= { gs2326plusSTPPortStatusEntry 3 }

gs2326plusSTPPortStatusUptime OBJECT-TYPE
   SYNTAX      DisplayString
   MAX-ACCESS  read-only
   STATUS      current
   DESCRIPTION
       " The time since the bridge port was last initialized. "
   ::= { gs2326plusSTPPortStatusEntry 4 }

gs2326plusSTPPortStatisticsTable OBJECT-TYPE
   SYNTAX      SEQUENCE OF Gs2326plusSTPPortStatisticsEntry
   MAX-ACCESS  not-accessible
   STATUS      current
   DESCRIPTION
       " Show STP Port Statistics."
   ::= { gs2326plusSTP 10 }

gs2326plusSTPPortStatisticsEntry OBJECT-TYPE
   SYNTAX      Gs2326plusSTPPortStatisticsEntry
   MAX-ACCESS  not-accessible
   STATUS      current
   DESCRIPTION
       ""
   INDEX    { gs2326plusSTPStatisticsIndex  }
   ::= { gs2326plusSTPPortStatisticsTable 1 }

Gs2326plusSTPPortStatisticsEntry ::= SEQUENCE {
   gs2326plusSTPStatisticsIndex            Integer32,
   gs2326plusSTPStatisticsPort             DisplayString,
   gs2326plusSTPStatisticsTxMSTP           Counter32,
   gs2326plusSTPStatisticsTxRSTP           Counter32,
   gs2326plusSTPStatisticsTxSTP            Counter32,
   gs2326plusSTPStatisticsTxTCN            Counter32,
   gs2326plusSTPStatisticsRxMSTP           Counter32,
   gs2326plusSTPStatisticsRxRSTP           Counter32,
   gs2326plusSTPStatisticsRxSTP            Counter32,
   gs2326plusSTPStatisticsRxTCN            Counter32,
   gs2326plusSTPStatisticsDiscardedUnknown Counter32,
   gs2326plusSTPStatisticsDiscardedIllegal Counter32
}

gs2326plusSTPStatisticsIndex OBJECT-TYPE
   SYNTAX      Integer32(1..4095)
   MAX-ACCESS  not-accessible
   STATUS      current
   DESCRIPTION
       "table index."
   ::= { gs2326plusSTPPortStatisticsEntry 1 }

gs2326plusSTPStatisticsPort OBJECT-TYPE
   SYNTAX      DisplayString
   MAX-ACCESS  not-accessible
   STATUS      current
   DESCRIPTION
       " port, range : 1 - port number. "
   ::= { gs2326plusSTPPortStatisticsEntry 2 }

gs2326plusSTPStatisticsTxMSTP OBJECT-TYPE
   SYNTAX      Counter32
   MAX-ACCESS  read-only
   STATUS      current
   DESCRIPTION
       " The number of MSTP Configuration BPDU's received/transmitted on the port."
   ::= { gs2326plusSTPPortStatisticsEntry 3 }

gs2326plusSTPStatisticsTxRSTP OBJECT-TYPE
   SYNTAX      Counter32
   MAX-ACCESS  read-only
   STATUS      current
   DESCRIPTION
       " The number of RSTP Configuration BPDU's received/transmitted on the port. "
   ::= { gs2326plusSTPPortStatisticsEntry 4 }

gs2326plusSTPStatisticsTxSTP OBJECT-TYPE
   SYNTAX      Counter32
   MAX-ACCESS  read-only
   STATUS      current
   DESCRIPTION
       " The number of legacy STP Configuration BPDU's received/transmitted on the port. "
   ::= { gs2326plusSTPPortStatisticsEntry 5 }

gs2326plusSTPStatisticsTxTCN OBJECT-TYPE
   SYNTAX      Counter32
   MAX-ACCESS  read-only
   STATUS      current
   DESCRIPTION
       " The number of Topology Change Notification BPDU's received/transmitted on the port. "
   ::= { gs2326plusSTPPortStatisticsEntry 6 }

gs2326plusSTPStatisticsRxMSTP OBJECT-TYPE
   SYNTAX      Counter32
   MAX-ACCESS  read-only
   STATUS      current
   DESCRIPTION
       " The number of MSTP Configuration BPDU's received/transmitted on the port."
   ::= { gs2326plusSTPPortStatisticsEntry 7 }

gs2326plusSTPStatisticsRxRSTP OBJECT-TYPE
   SYNTAX      Counter32
   MAX-ACCESS  read-only
   STATUS      current
   DESCRIPTION
       " The number of RSTP Configuration BPDU's received/transmitted on the port. "
   ::= { gs2326plusSTPPortStatisticsEntry 8 }

gs2326plusSTPStatisticsRxSTP OBJECT-TYPE
   SYNTAX      Counter32
   MAX-ACCESS  read-only
   STATUS      current
   DESCRIPTION
       " The number of legacy STP Configuration BPDU's received/transmitted on the port. "
   ::= { gs2326plusSTPPortStatisticsEntry 9 }

gs2326plusSTPStatisticsRxTCN OBJECT-TYPE
   SYNTAX      Counter32
   MAX-ACCESS  read-only
   STATUS      current
   DESCRIPTION
       " The number of Topology Change Notification BPDU's received/transmitted on the port. "
   ::= { gs2326plusSTPPortStatisticsEntry 10 }

gs2326plusSTPStatisticsDiscardedUnknown OBJECT-TYPE
   SYNTAX      Counter32
   MAX-ACCESS  read-only
   STATUS      current
   DESCRIPTION
       " The number of unknown Spanning Tree BPDU's received and discarded on the port. "
   ::= { gs2326plusSTPPortStatisticsEntry 11 }

gs2326plusSTPStatisticsDiscardedIllegal OBJECT-TYPE
   SYNTAX      Counter32
   MAX-ACCESS  read-only
   STATUS      current
   DESCRIPTION
       " The number of illegal Spanning Tree BPDU's received and discarded on the port. "
   ::= { gs2326plusSTPPortStatisticsEntry 12 }


gs2326plusFilteringDataBase                                                  OBJECT IDENTIFIER ::= { gs2326plusConfiguration 21 }

gs2326plusFilteringDataBaseConfig                                            OBJECT IDENTIFIER ::= { gs2326plusFilteringDataBase 1 }

gs2326plusFilteringDataBaseAgingTime OBJECT-TYPE
   SYNTAX      Integer32(0..1000000)
   MAX-ACCESS  read-write
   STATUS      current
   DESCRIPTION
       "Configure aging time by entering a value here in seconds.
        default: 300,
        range: 10-1000000.
        Disable automatic aging : 0."
   ::= { gs2326plusFilteringDataBaseConfig 1 }

gs2326plusFilteringDataBaseConfigTable OBJECT-TYPE
   SYNTAX      SEQUENCE OF GS2326PLUSFilteringDataBaseConfigEntry
   MAX-ACCESS  not-accessible
   STATUS      current
   DESCRIPTION
       " "
   ::= { gs2326plusFilteringDataBaseConfig 2 }

gs2326plusFilteringDataBaseConfigEntry OBJECT-TYPE
   SYNTAX      GS2326PLUSFilteringDataBaseConfigEntry
   MAX-ACCESS  not-accessible
   STATUS      current
   DESCRIPTION
       ""
   INDEX    { gs2326plusFilteringDataBaseConfigPort  }
   ::= { gs2326plusFilteringDataBaseConfigTable 1 }

GS2326PLUSFilteringDataBaseConfigEntry ::= SEQUENCE {
   gs2326plusFilteringDataBaseConfigPort        Integer32,
   gs2326plusFilteringDataBaseConfigLearning    INTEGER
}

gs2326plusFilteringDataBaseConfigPort OBJECT-TYPE
   SYNTAX      Integer32(1..4095)
   MAX-ACCESS  not-accessible
   STATUS      current
   DESCRIPTION
       " "
   ::= { gs2326plusFilteringDataBaseConfigEntry 1 }

gs2326plusFilteringDataBaseConfigLearning OBJECT-TYPE
   SYNTAX      INTEGER { auto(0), disable(1), secure(2) }
   MAX-ACCESS  read-write
   STATUS      current
   DESCRIPTION
       "Configure learning mode of switch ports.
        default: 0,
        0: auto,
        1: disable,
        2: secure. "
   ::= { gs2326plusFilteringDataBaseConfigEntry 2 }


gs2326plusFilteringDataBaseStaticMAC                                OBJECT IDENTIFIER ::= { gs2326plusFilteringDataBaseConfig 3 }

gs2326plusFilteringDataBaseStaticMACCreate OBJECT-TYPE
   SYNTAX       INTEGER { none(0), create(1) }
   MAX-ACCESS   read-write
   STATUS       current
   DESCRIPTION
       "default: 0
        0 : None  (read only)
        1 : Create Static MAC Table"
   ::= { gs2326plusFilteringDataBaseStaticMAC 1 }

gs2326plusFilteringDataBaseStaticMACTable OBJECT-TYPE
   SYNTAX      SEQUENCE OF GS2326PLUSFilteringDataBaseStaticMACEntry
   MAX-ACCESS  not-accessible
   STATUS      current
   DESCRIPTION
       " "
   ::= { gs2326plusFilteringDataBaseStaticMAC 2 }

gs2326plusFilteringDataBaseStaticMACEntry OBJECT-TYPE
   SYNTAX      GS2326PLUSFilteringDataBaseStaticMACEntry
   MAX-ACCESS  not-accessible
   STATUS      current
   DESCRIPTION
       ""
   INDEX    { gs2326plusFilteringDataBaseStaticMACIndex  }
   ::= { gs2326plusFilteringDataBaseStaticMACTable 1 }

GS2326PLUSFilteringDataBaseStaticMACEntry ::= SEQUENCE {
   gs2326plusFilteringDataBaseStaticMACIndex	    Integer32,
   gs2326plusFilteringDataBaseStaticMACVLANId	    Integer32,
   gs2326plusFilteringDataBaseStaticMACAddress      MacAddress,
   gs2326plusFilteringDataBaseStaticMACPortMembers  DisplayString,
   gs2326plusFilteringDataBaseStaticMACRowStatus	INTEGER
}

gs2326plusFilteringDataBaseStaticMACIndex OBJECT-TYPE
   SYNTAX      Integer32(1..4095)
   MAX-ACCESS  not-accessible
   STATUS      current
   DESCRIPTION
       " "
   ::= { gs2326plusFilteringDataBaseStaticMACEntry 1 }

gs2326plusFilteringDataBaseStaticMACVLANId OBJECT-TYPE
   SYNTAX      Integer32(1..4094)
   MAX-ACCESS  read-write
   STATUS      current
   DESCRIPTION
       " VLAN ID, range: 1 - 4094. "
   ::= { gs2326plusFilteringDataBaseStaticMACEntry 2 }

gs2326plusFilteringDataBaseStaticMACAddress OBJECT-TYPE
   SYNTAX      MacAddress
   MAX-ACCESS  read-write
   STATUS      current
   DESCRIPTION
       " MAC address, format 0a 1b 2c 3d 4e 5f "
   ::= { gs2326plusFilteringDataBaseStaticMACEntry 3 }

gs2326plusFilteringDataBaseStaticMACPortMembers OBJECT-TYPE
   SYNTAX      DisplayString
   MAX-ACCESS  read-write
   STATUS      current
   DESCRIPTION
       "To include the ports in a Static MAC Table"
   ::= { gs2326plusFilteringDataBaseStaticMACEntry 4 }

gs2326plusFilteringDataBaseStaticMACRowStatus OBJECT-TYPE
   SYNTAX      INTEGER { active(1), notInservice(2), destroy(4), undo(5) }
   MAX-ACCESS  read-write
   STATUS      current
   DESCRIPTION
       "1: active
        2: notInservice
        4: destroy
        5: undo"
   ::= { gs2326plusFilteringDataBaseStaticMACEntry 5 }


gs2326plusFilteringDataBaseDynamicMACTable OBJECT-TYPE
   SYNTAX      SEQUENCE OF GS2326PLUSFilteringDataBaseDynamicMACEntry
   MAX-ACCESS  not-accessible
   STATUS      current
   DESCRIPTION
       " "
   ::= { gs2326plusFilteringDataBaseConfig 4 }

gs2326plusFilteringDataBaseDynamicMACEntry OBJECT-TYPE
   SYNTAX      GS2326PLUSFilteringDataBaseDynamicMACEntry
   MAX-ACCESS  not-accessible
   STATUS      current
   DESCRIPTION
       ""
   INDEX    { gs2326plusFilteringDataBaseDynamicMACIndex  }
   ::= { gs2326plusFilteringDataBaseDynamicMACTable 1 }

GS2326PLUSFilteringDataBaseDynamicMACEntry ::= SEQUENCE {
   gs2326plusFilteringDataBaseDynamicMACIndex	    Integer32,
   gs2326plusFilteringDataBaseDynamicMACType	    INTEGER,
   gs2326plusFilteringDataBaseDynamicMACVLAN	    Integer32,
   gs2326plusFilteringDataBaseDynamicMACAddress     MacAddress,
   gs2326plusFilteringDataBaseDynamicPortMembers    DisplayString
}

gs2326plusFilteringDataBaseDynamicMACIndex OBJECT-TYPE
   SYNTAX      Integer32(1..4095)
   MAX-ACCESS  not-accessible
   STATUS      current
   DESCRIPTION
       " "
   ::= { gs2326plusFilteringDataBaseDynamicMACEntry 1 }

gs2326plusFilteringDataBaseDynamicMACType OBJECT-TYPE
   SYNTAX      INTEGER { dynamic(0), static(1) }
   MAX-ACCESS  read-only
   STATUS      current
   DESCRIPTION
       "Indicates whether the entry is a static or a dynamic entry."
   ::= { gs2326plusFilteringDataBaseDynamicMACEntry 2 }

gs2326plusFilteringDataBaseDynamicMACVLAN OBJECT-TYPE
   SYNTAX      Integer32(1..4094)
   MAX-ACCESS  read-only
   STATUS      current
   DESCRIPTION
       "The VLAN ID of the entry."
   ::= { gs2326plusFilteringDataBaseDynamicMACEntry 3 }

gs2326plusFilteringDataBaseDynamicMACAddress OBJECT-TYPE
   SYNTAX      MacAddress
   MAX-ACCESS  read-only
   STATUS      current
   DESCRIPTION
       "The MAC address of the entry."
   ::= { gs2326plusFilteringDataBaseDynamicMACEntry 4 }

gs2326plusFilteringDataBaseDynamicPortMembers OBJECT-TYPE
   SYNTAX      DisplayString
   MAX-ACCESS  read-only
   STATUS      current
   DESCRIPTION
       "The ports that are members of the entry."
   ::= { gs2326plusFilteringDataBaseDynamicMACEntry 5 }


gs2326plusSFlowAgent                                                  OBJECT IDENTIFIER ::= { gs2326plusConfiguration 22 }

gs2326plusSFlowAgentCollector                                            OBJECT IDENTIFIER ::= { gs2326plusSFlowAgent 1 }

gs2326plusSFlowAgentReceiverMode OBJECT-TYPE
   SYNTAX      INTEGER { disable(0), enable(1) }
   MAX-ACCESS  read-write
   STATUS      current
   DESCRIPTION
       "default: 0
       0: disable
       1: enable "
   ::= { gs2326plusSFlowAgentCollector 1 }


gs2326plusLMC                                                   OBJECT IDENTIFIER ::= { gs2326plusConfiguration 1500 }

gs2326plusLMCOperating OBJECT-TYPE
   SYNTAX      INTEGER { disabled(0), enabled(1), try(2) }
   MAX-ACCESS  read-write
   STATUS      current
   DESCRIPTION
       "0: disabled
        1: enabled
        2: try"
   ::= { gs2326plusLMC 1 }

gs2326plusLMCConfigViaDhcp OBJECT-TYPE
   SYNTAX      INTEGER { disabled(0), enabled(1) }
   MAX-ACCESS  read-write
   STATUS      current
   DESCRIPTION
       "0: disabled
        1: enabled"
   ::= { gs2326plusLMC 2 }

gs2326plusLMCDomain OBJECT-TYPE
   SYNTAX      DisplayString(SIZE(0..255))
   MAX-ACCESS  read-write
   STATUS      current
   DESCRIPTION
       "0: disabled
        1: enabled"
   ::= { gs2326plusLMC 3 }

gs2326plusLMCDhcpClientAutoRenew OBJECT-TYPE
   SYNTAX      INTEGER { disabled(0), enabled(1) }
   MAX-ACCESS  read-write
   STATUS      current
   DESCRIPTION
       "0: disabled
        1: enabled"
   ::= { gs2326plusLMC 4 }

gs2326plusLMCZeroTouchSupport OBJECT-TYPE
   SYNTAX      INTEGER { No(0), Yes(1) }
   MAX-ACCESS  read-only
   STATUS      current
   DESCRIPTION
       "0: No
        1: Yes"
   ::= { gs2326plusLMC 50 }

gs2326plusLMCPairingTokenPresent OBJECT-TYPE
   SYNTAX      INTEGER { No(0), Yes(1) }
   MAX-ACCESS  read-only
   STATUS      current
   DESCRIPTION
       "0: No
        1: Yes"
   ::= { gs2326plusLMC 51 }

gs2326plusLMCClientStatus OBJECT-TYPE
   SYNTAX      DisplayString
   MAX-ACCESS  read-only
   STATUS      current
   DESCRIPTION
           ""
   ::= { gs2326plusLMC  52 }


gs2326plusLMCManagementStatus OBJECT-TYPE
   SYNTAX      INTEGER {Unpaired(0), Paired(1), PairedAndClaimed(14)}
   MAX-ACCESS  read-only
   STATUS      current
   DESCRIPTION
           "0: Unpaired
            1: Paired
            14: PairedAndClaimed"
   ::= { gs2326plusLMC  53 }

gs2326plusLMCControlStatus OBJECT-TYPE
   SYNTAX      INTEGER {Disabled(2), Operating(4)}
   MAX-ACCESS  read-only
   STATUS      current
   DESCRIPTION
           "2: Disabled
            4: Operating"
   ::= { gs2326plusLMC  54 }

gs2326plusLMCMonitoringStatus OBJECT-TYPE
   SYNTAX      INTEGER {Disabled(2), Operating(4)}
   MAX-ACCESS  read-only
   STATUS      current
   DESCRIPTION
           "2: Disabled
            4: Operating"
   ::= { gs2326plusLMC  55 }

gs2326plusLMCConfigurationSource OBJECT-TYPE
   SYNTAX      DisplayString
   MAX-ACCESS  read-only
   STATUS      current
   DESCRIPTION
           ""
   ::= { gs2326plusLMC  56 }

gs2326plusLMCConfigModified OBJECT-TYPE
   SYNTAX      INTEGER { No(0), Yes(1) }
   MAX-ACCESS  read-only
   STATUS      current
   DESCRIPTION
       "0: No
        1: Yes"
   ::= { gs2326plusLMC 57 }

gs2326plusLMCDeviceID OBJECT-TYPE
   SYNTAX      DisplayString
   MAX-ACCESS  read-only
   STATUS      current
   DESCRIPTION
           ""
   ::= { gs2326plusLMC  58 }

gs2326plusLMCRoundTripTime OBJECT-TYPE
   SYNTAX      INTEGER
   MAX-ACCESS  read-only
   STATUS      current
   DESCRIPTION
           ""
   ::= { gs2326plusLMC  100 }
----------------------------------------------------------------------------------------------------------------------------
gs2326plusSecurity                                              OBJECT IDENTIFIER ::= { lancomGS2326plus  3 }

gs2326plusIPSourceGuard                                         OBJECT IDENTIFIER ::= { gs2326plusSecurity 1 }

gs2326plusIPSourceGuardConf                                     OBJECT IDENTIFIER ::= { gs2326plusIPSourceGuard 1 }

gs2326plusIPSourceGuardMode OBJECT-TYPE
   SYNTAX      INTEGER { disable(0), enable(1) }
   MAX-ACCESS  read-write
   STATUS      current
   DESCRIPTION
       " default:  0
        0: disable
        1: enable"
   ::= { gs2326plusIPSourceGuardConf 1 }

gs2326plusIPSourceGuardPortConfigTable OBJECT-TYPE
   SYNTAX      SEQUENCE OF Gs2326plusIPSourceGuardPortConfigEntry
   MAX-ACCESS  not-accessible
   STATUS      current
   DESCRIPTION
       " "
   ::= { gs2326plusIPSourceGuardConf 2 }

gs2326plusIPSourceGuardPortConfigEntry OBJECT-TYPE
   SYNTAX      Gs2326plusIPSourceGuardPortConfigEntry
   MAX-ACCESS  not-accessible
   STATUS      current
   DESCRIPTION
       ""
   INDEX    { gs2326plusIPSourceGuardPortConfigPort  }
   ::= { gs2326plusIPSourceGuardPortConfigTable 1 }

Gs2326plusIPSourceGuardPortConfigEntry ::= SEQUENCE {
   gs2326plusIPSourceGuardPortConfigPort               Integer32,
   gs2326plusIPSourceGuardPortConfigMode               INTEGER,
   gs2326plusIPSourceGuardPortMaxDynamicClients        Integer32
}

gs2326plusIPSourceGuardPortConfigPort OBJECT-TYPE
   SYNTAX      Integer32(1..4095)
   MAX-ACCESS  not-accessible
   STATUS      current
   DESCRIPTION
       " "
   ::= { gs2326plusIPSourceGuardPortConfigEntry 1 }

gs2326plusIPSourceGuardPortConfigMode OBJECT-TYPE
   SYNTAX      INTEGER { disable(0), enable(1) }
   MAX-ACCESS  read-write
   STATUS      current
   DESCRIPTION
       "default: 0
       0:disable
       1:enable "
   ::= { gs2326plusIPSourceGuardPortConfigEntry 2 }

gs2326plusIPSourceGuardPortMaxDynamicClients OBJECT-TYPE
   SYNTAX      Integer32(0..2|99)
   MAX-ACCESS  read-write
   STATUS      current
   DESCRIPTION
       "default: 99
       0~2: Max Dynamic clients
       99:Unlimited "
   ::= { gs2326plusIPSourceGuardPortConfigEntry 3 }


gs2326plusIPSourceGuardStatic                                OBJECT IDENTIFIER ::= { gs2326plusIPSourceGuard 2 }

gs2326plusIPSourceGuardStaticCreate OBJECT-TYPE
   SYNTAX       INTEGER { none(0), create(1) }
   MAX-ACCESS   read-write
   STATUS       current
   DESCRIPTION
       "default: 0
        0 : None  (read only)
        1 : Create a IP Source Guard"
   ::= { gs2326plusIPSourceGuardStatic 1 }

gs2326plusIPSourceGuardStaticTable OBJECT-TYPE
   SYNTAX      SEQUENCE OF Gs2326plusIPSourceGuardStaticEntry
   MAX-ACCESS  not-accessible
   STATUS      current
   DESCRIPTION
       " "
   ::= { gs2326plusIPSourceGuardStatic 2 }

gs2326plusIPSourceGuardStaticEntry OBJECT-TYPE
   SYNTAX      Gs2326plusIPSourceGuardStaticEntry
   MAX-ACCESS  not-accessible
   STATUS      current
   DESCRIPTION
       ""
   INDEX    { gs2326plusIPSourceGuardStaticIndex  }
   ::= { gs2326plusIPSourceGuardStaticTable 1 }

Gs2326plusIPSourceGuardStaticEntry ::= SEQUENCE {
   gs2326plusIPSourceGuardStaticIndex         Integer32,
   gs2326plusIPSourceGuardStaticPort          Integer32,
   gs2326plusIPSourceGuardStaticVLANId        Integer32,
   gs2326plusIPSourceGuardStaticIPAddress     IpAddress,
   gs2326plusIPSourceGuardStaticMACAddress    MacAddress,
   gs2326plusIPSourceGuardStaticRowStatus     INTEGER
}

gs2326plusIPSourceGuardStaticIndex OBJECT-TYPE
   SYNTAX      Integer32(1..28)
   MAX-ACCESS  not-accessible
   STATUS      current
   DESCRIPTION
       " "
   ::= { gs2326plusIPSourceGuardStaticEntry 1 }

gs2326plusIPSourceGuardStaticPort OBJECT-TYPE
   SYNTAX      Integer32(1..4095)
   MAX-ACCESS  read-write
   STATUS      current
   DESCRIPTION
       " Port, range: 1 - port number. "
   ::= { gs2326plusIPSourceGuardStaticEntry 2 }

gs2326plusIPSourceGuardStaticVLANId OBJECT-TYPE
   SYNTAX      Integer32(1..4094)
   MAX-ACCESS  read-write
   STATUS      current
   DESCRIPTION
       " VLAN ID, range: 1 - 4094. "
   ::= { gs2326plusIPSourceGuardStaticEntry 3 }

gs2326plusIPSourceGuardStaticIPAddress OBJECT-TYPE
   SYNTAX      IpAddress
   MAX-ACCESS  read-write
   STATUS      current
   DESCRIPTION
       " IP address allowed for doing IP source guard. "
   ::= { gs2326plusIPSourceGuardStaticEntry 4 }

gs2326plusIPSourceGuardStaticMACAddress OBJECT-TYPE
   SYNTAX      MacAddress
   MAX-ACCESS  read-write
   STATUS      current
   DESCRIPTION
       " Allowed Source MAC address, format 0a 1b 2c 3d 4e 5f "
   ::= { gs2326plusIPSourceGuardStaticEntry 5 }

gs2326plusIPSourceGuardStaticRowStatus OBJECT-TYPE
   SYNTAX      INTEGER { active(1), notInservice(2), edit(3), destroy(4), undo(5) }
   MAX-ACCESS  read-write
   STATUS      current
   DESCRIPTION
       "1: active
        2: notInservice
        3: edit
        4: destroy
        5: undo"
   ::= { gs2326plusIPSourceGuardStaticEntry 6 }

gs2326plusIPSourceGuardDynamicTable OBJECT-TYPE
   SYNTAX      SEQUENCE OF Gs2326plusIPSourceGuardDynamicEntry
   MAX-ACCESS  not-accessible
   STATUS      current
   DESCRIPTION
       " "
   ::= { gs2326plusIPSourceGuard 3 }

gs2326plusIPSourceGuardDynamicEntry OBJECT-TYPE
   SYNTAX      Gs2326plusIPSourceGuardDynamicEntry
   MAX-ACCESS  not-accessible
   STATUS      current
   DESCRIPTION
       ""
   INDEX    { gs2326plusIPSourceGuardDynamicIndex  }
   ::= { gs2326plusIPSourceGuardDynamicTable 1 }

Gs2326plusIPSourceGuardDynamicEntry ::= SEQUENCE {
   gs2326plusIPSourceGuardDynamicIndex          Integer32,
   gs2326plusIPSourceGuardDynamicPort           Integer32,
   gs2326plusIPSourceGuardDynamicVLANId         Integer32,
   gs2326plusIPSourceGuardDynamicIPAddress      IpAddress,
   gs2326plusIPSourceGuardDynamicMACAddress     MacAddress
}

gs2326plusIPSourceGuardDynamicIndex OBJECT-TYPE
   SYNTAX      Integer32(1..4095)
   MAX-ACCESS  not-accessible
   STATUS      current
   DESCRIPTION
       " "
   ::= { gs2326plusIPSourceGuardDynamicEntry 1 }

gs2326plusIPSourceGuardDynamicPort OBJECT-TYPE
   SYNTAX      Integer32(1..10)
   MAX-ACCESS  read-only
   STATUS      current
   DESCRIPTION
       " "
   ::= { gs2326plusIPSourceGuardDynamicEntry 2 }

gs2326plusIPSourceGuardDynamicVLANId OBJECT-TYPE
   SYNTAX      Integer32(1..4094)
   MAX-ACCESS  read-only
   STATUS      current
   DESCRIPTION
       " "
   ::= { gs2326plusIPSourceGuardDynamicEntry 3 }

gs2326plusIPSourceGuardDynamicIPAddress OBJECT-TYPE
   SYNTAX      IpAddress
   MAX-ACCESS  read-only
   STATUS      current
   DESCRIPTION
       " "
   ::= { gs2326plusIPSourceGuardDynamicEntry 4 }

gs2326plusIPSourceGuardDynamicMACAddress OBJECT-TYPE
   SYNTAX      MacAddress
   MAX-ACCESS  read-only
   STATUS      current
   DESCRIPTION
       " "
   ::= { gs2326plusIPSourceGuardDynamicEntry 5 }

gs2326plusARPInspection                                         OBJECT IDENTIFIER ::= { gs2326plusSecurity 2 }

gs2326plusARPInspectionConf                                     OBJECT IDENTIFIER ::= { gs2326plusARPInspection 1 }

gs2326plusARPInspectionConfMode OBJECT-TYPE
   SYNTAX      INTEGER { disable(0), enable(1) }
   MAX-ACCESS  read-write
   STATUS      current
   DESCRIPTION
       "default: 0
        0: disable
        1: enable"
   ::= { gs2326plusARPInspectionConf 1 }

gs2326plusARPInspectionConfTable OBJECT-TYPE
   SYNTAX      SEQUENCE OF Gs2326plusARPInspectionConfEntry
   MAX-ACCESS  not-accessible
   STATUS      current
   DESCRIPTION
       " "
   ::= { gs2326plusARPInspectionConf 2 }

gs2326plusARPInspectionConfEntry OBJECT-TYPE
   SYNTAX      Gs2326plusARPInspectionConfEntry
   MAX-ACCESS  not-accessible
   STATUS      current
   DESCRIPTION
       ""
   INDEX    { gs2326plusARPInspectionConfPortIndex  }
   ::= { gs2326plusARPInspectionConfTable 1 }

Gs2326plusARPInspectionConfEntry ::= SEQUENCE {
   gs2326plusARPInspectionConfPortIndex	Integer32,
   gs2326plusARPInspectionConfPortMode	INTEGER
}

gs2326plusARPInspectionConfPortIndex OBJECT-TYPE
   SYNTAX      Integer32(1..4095)
   MAX-ACCESS  not-accessible
   STATUS      current
   DESCRIPTION
       " "
   ::= { gs2326plusARPInspectionConfEntry 1 }

gs2326plusARPInspectionConfPortMode OBJECT-TYPE
   SYNTAX      INTEGER { disable(0), enable(1) }
   MAX-ACCESS  read-write
   STATUS      current
   DESCRIPTION
       "default: 0
        0: disable
        1: enable"
   ::= { gs2326plusARPInspectionConfEntry 2 }


gs2326plusARPInspectionStatic                                OBJECT IDENTIFIER ::= { gs2326plusARPInspection 2 }

gs2326plusARPInspectionStaticCreate OBJECT-TYPE
   SYNTAX      INTEGER { none(0), create(1) }
   MAX-ACCESS  read-write
   STATUS      current
   DESCRIPTION
       "default: 0
        0: none
        1: create"
   ::= { gs2326plusARPInspectionStatic 1 }

gs2326plusARPInspectionStaticTable OBJECT-TYPE
   SYNTAX      SEQUENCE OF Gs2326plusARPInspectionStaticEntry
   MAX-ACCESS  not-accessible
   STATUS      current
   DESCRIPTION
       " "
   ::= { gs2326plusARPInspectionStatic 2 }

gs2326plusARPInspectionStaticEntry OBJECT-TYPE
   SYNTAX      Gs2326plusARPInspectionStaticEntry
   MAX-ACCESS  not-accessible
   STATUS      current
   DESCRIPTION
       ""
   INDEX    { gs2326plusARPInspectionStaticIndex  }
   ::= { gs2326plusARPInspectionStaticTable 1 }

Gs2326plusARPInspectionStaticEntry ::= SEQUENCE {
   gs2326plusARPInspectionStaticIndex       Integer32,
   gs2326plusARPInspectionStaticPort        Integer32,
   gs2326plusARPInspectionStaticVLANId      Integer32,
   gs2326plusARPInspectionStaticIPAddress   IpAddress,
   gs2326plusARPInspectionStaticMACAddress  MacAddress,
   gs2326plusARPInspectionStaticRowStatus   INTEGER
}

gs2326plusARPInspectionStaticIndex OBJECT-TYPE
   SYNTAX      Integer32(1..4095)
   MAX-ACCESS  not-accessible
   STATUS      current
   DESCRIPTION
       ""
   ::= { gs2326plusARPInspectionStaticEntry 1 }

gs2326plusARPInspectionStaticPort OBJECT-TYPE
   SYNTAX      Integer32(1..4095)
   MAX-ACCESS  read-write
   STATUS      current
   DESCRIPTION
       " Port, range: 1 - port number. "
   ::= { gs2326plusARPInspectionStaticEntry 2 }

gs2326plusARPInspectionStaticVLANId OBJECT-TYPE
   SYNTAX      Integer32(1..4094)
   MAX-ACCESS  read-write
   STATUS      current
   DESCRIPTION
       " VLAN ID, range: 1 - 4094. "
   ::= { gs2326plusARPInspectionStaticEntry 3 }

gs2326plusARPInspectionStaticIPAddress OBJECT-TYPE
   SYNTAX      IpAddress
   MAX-ACCESS  read-write
   STATUS      current
   DESCRIPTION
       " IP address allowed for doing ARP request. "
   ::= { gs2326plusARPInspectionStaticEntry 4 }

gs2326plusARPInspectionStaticMACAddress OBJECT-TYPE
   SYNTAX      MacAddress
   MAX-ACCESS  read-write
   STATUS      current
   DESCRIPTION
       " Allowed Source MAC address in ARP request packets, format 0a 1b 2c 3d 4e 5f "
   ::= { gs2326plusARPInspectionStaticEntry 5 }

gs2326plusARPInspectionStaticRowStatus OBJECT-TYPE
   SYNTAX     INTEGER { active(1), notInservice(2), edit(3), destroy(4), undo(5) }
   MAX-ACCESS  read-write
   STATUS      current
   DESCRIPTION
       "1: active
        2: notInservice
        3: edit
        4: destroy
        5: undo"
   ::= { gs2326plusARPInspectionStaticEntry 6 }

gs2326plusARPInspectionDynamicTable OBJECT-TYPE
   SYNTAX      SEQUENCE OF Gs2326plusARPInspectionDynamicEntry
   MAX-ACCESS  not-accessible
   STATUS      current
   DESCRIPTION
       " "
   ::= { gs2326plusARPInspection 3 }

gs2326plusARPInspectionDynamicEntry OBJECT-TYPE
   SYNTAX      Gs2326plusARPInspectionDynamicEntry
   MAX-ACCESS  not-accessible
   STATUS      current
   DESCRIPTION
       ""
   INDEX    { gs2326plusARPInspectionDynamicIndex  }
   ::= { gs2326plusARPInspectionDynamicTable 1 }

Gs2326plusARPInspectionDynamicEntry ::= SEQUENCE {
   gs2326plusARPInspectionDynamicIndex          Integer32,
   gs2326plusARPInspectionDynamicPort           Integer32,
   gs2326plusARPInspectionDynamicVLANId         Integer32,
   gs2326plusARPInspectionDynamicIPAddress      IpAddress,
   gs2326plusARPInspectionDynamicMACAddress     MacAddress
}

gs2326plusARPInspectionDynamicIndex OBJECT-TYPE
   SYNTAX      Integer32(1..4095)
   MAX-ACCESS  not-accessible
   STATUS      current
   DESCRIPTION
       " "
   ::= { gs2326plusARPInspectionDynamicEntry 1 }

gs2326plusARPInspectionDynamicPort OBJECT-TYPE
   SYNTAX      Integer32(1..4095)
   MAX-ACCESS  read-only
   STATUS      current
   DESCRIPTION
       ""
   ::= { gs2326plusARPInspectionDynamicEntry 2 }

gs2326plusARPInspectionDynamicVLANId OBJECT-TYPE
   SYNTAX      Integer32(1..4094)
   MAX-ACCESS  read-only
   STATUS      current
   DESCRIPTION
       ""
   ::= { gs2326plusARPInspectionDynamicEntry 3 }

gs2326plusARPInspectionDynamicIPAddress OBJECT-TYPE
   SYNTAX      IpAddress
   MAX-ACCESS  read-only
   STATUS      current
   DESCRIPTION
       ""
   ::= { gs2326plusARPInspectionDynamicEntry 4 }

gs2326plusARPInspectionDynamicMACAddress OBJECT-TYPE
   SYNTAX      MacAddress
   MAX-ACCESS  read-only
   STATUS      current
   DESCRIPTION
       ""
   ::= { gs2326plusARPInspectionDynamicEntry 5 }

gs2326plusARPStaticGatewayCtrl	                                OBJECT IDENTIFIER ::= { gs2326plusARPInspection 6 }

gs2326plusARPStaticGatewayCtrlSystemConf                                      OBJECT IDENTIFIER ::= { gs2326plusARPStaticGatewayCtrl 1 }

gs2326plusARPStaticGatewayCtrlMode OBJECT-TYPE
   SYNTAX      INTEGER { disable(0), enable(1) }
   MAX-ACCESS  read-write
   STATUS      current
   DESCRIPTION
       "default: 0
       0: disable
       1: enable "
   ::= { gs2326plusARPStaticGatewayCtrlSystemConf 1 }

gs2326plusARPStaticGatewayCtrlCreate OBJECT-TYPE
   SYNTAX      INTEGER { none(0), create(1) }
   MAX-ACCESS  read-write
   STATUS      current
   DESCRIPTION
       "default: 0
        0: none
        1: create"
   ::= { gs2326plusARPStaticGatewayCtrl 2 }

gs2326plusARPStaticGatewayCtrlTable OBJECT-TYPE
   SYNTAX      SEQUENCE OF Gs2326plusARPStaticGatewayCtrlEntry
   MAX-ACCESS  not-accessible
   STATUS      current
   DESCRIPTION
       " "
   ::= { gs2326plusARPStaticGatewayCtrl 3 }

gs2326plusARPStaticGatewayCtrlEntry OBJECT-TYPE
   SYNTAX      Gs2326plusARPStaticGatewayCtrlEntry
   MAX-ACCESS  not-accessible
   STATUS      current
   DESCRIPTION
       ""
   INDEX    { gs2326plusARPStaticGatewayCtrlIndex  }
   ::= { gs2326plusARPStaticGatewayCtrlTable 1 }

Gs2326plusARPStaticGatewayCtrlEntry ::= SEQUENCE {
   gs2326plusARPStaticGatewayCtrlIndex       Integer32,
   gs2326plusARPStaticGatewayCtrlIPAddress   IpAddress,
   gs2326plusARPStaticGatewayCtrlMACAddress  MacAddress,
   gs2326plusARPStaticGatewayCtrlPort        Integer32,
   gs2326plusARPStaticGatewayCtrlAction      INTEGER,
   gs2326plusARPStaticGatewayCtrlState       DisplayString,
   gs2326plusARPStaticGatewayCtrlReOpen      INTEGER,
   gs2326plusARPStaticGatewayCtrlRowStatus   INTEGER
}

gs2326plusARPStaticGatewayCtrlIndex OBJECT-TYPE
   SYNTAX      Integer32(1..4)
   MAX-ACCESS  not-accessible
   STATUS      current
   DESCRIPTION
       ""
   ::= { gs2326plusARPStaticGatewayCtrlEntry 1 }

gs2326plusARPStaticGatewayCtrlIPAddress OBJECT-TYPE
   SYNTAX      IpAddress
   MAX-ACCESS  read-write
   STATUS      current
   DESCRIPTION
       " Source IP address. "
   ::= { gs2326plusARPStaticGatewayCtrlEntry 2 }

gs2326plusARPStaticGatewayCtrlMACAddress OBJECT-TYPE
   SYNTAX      MacAddress
   MAX-ACCESS  read-write
   STATUS      current
   DESCRIPTION
       " Source MAC address , format 0a 1b 2c 3d 4e 5f "
   ::= { gs2326plusARPStaticGatewayCtrlEntry 3 }

gs2326plusARPStaticGatewayCtrlPort OBJECT-TYPE
   SYNTAX      Integer32(1..4095)
   MAX-ACCESS  read-write
   STATUS      current
   DESCRIPTION
       " Port, range: 1 - port number. "
   ::= { gs2326plusARPStaticGatewayCtrlEntry 4 }

gs2326plusARPStaticGatewayCtrlAction OBJECT-TYPE
   SYNTAX      INTEGER {none(0),trap(1),dropAndTrap(2), shutdown(3), trapAndShutdown(4) }
   MAX-ACCESS  read-write
   STATUS      current
   DESCRIPTION
       "default: 0
       0: none
       1: trap
       2: drop&trap
       3: shutdown
       4: trap&shutdown"
   ::= { gs2326plusARPStaticGatewayCtrlEntry 5 }

gs2326plusARPStaticGatewayCtrlState OBJECT-TYPE
   SYNTAX      DisplayString
   MAX-ACCESS  read-only
   STATUS      current
   DESCRIPTION
       ""
   ::= { gs2326plusARPStaticGatewayCtrlEntry 6 }

gs2326plusARPStaticGatewayCtrlReOpen OBJECT-TYPE
   SYNTAX      INTEGER { none(0), reopen(1) }
   MAX-ACCESS  read-write
   STATUS      current
   DESCRIPTION
       "default: 0
       0: none
       1: reopen"
   ::= { gs2326plusARPStaticGatewayCtrlEntry 7 }

gs2326plusARPStaticGatewayCtrlRowStatus OBJECT-TYPE
   SYNTAX      INTEGER { active(1), notInservice(2), edit(3), destroy(4), undo(5) }
   MAX-ACCESS  read-write
   STATUS      current
   DESCRIPTION
       "1: active
        2: notInservice
        3: edit
        4: destroy
        5: undo"
   ::= { gs2326plusARPStaticGatewayCtrlEntry 8 }

gs2326plusARPSpoofingPrevention	                                OBJECT IDENTIFIER ::= { gs2326plusARPInspection 7 }

gs2326plusARPSpoofingPreventionSystemConf                                      OBJECT IDENTIFIER ::= { gs2326plusARPSpoofingPrevention 1 }

gs2326plusARPSpoofingPreventionMode OBJECT-TYPE
   SYNTAX      INTEGER { disable(0), enable(1) }
   MAX-ACCESS  read-write
   STATUS      current
   DESCRIPTION
       "default: 0
       0: disable
       1: enable "
   ::= { gs2326plusARPSpoofingPreventionSystemConf 1 }

gs2326plusARPSpoofingPreventionTable OBJECT-TYPE
   SYNTAX      SEQUENCE OF Gs2326plusARPSpoofingPreventionEntry
   MAX-ACCESS  not-accessible
   STATUS      current
   DESCRIPTION
       " "
   ::= { gs2326plusARPSpoofingPrevention 2 }

gs2326plusARPSpoofingPreventionEntry OBJECT-TYPE
   SYNTAX      Gs2326plusARPSpoofingPreventionEntry
   MAX-ACCESS  not-accessible
   STATUS      current
   DESCRIPTION
       ""
   INDEX    { gs2326plusARPSpoofingPreventionPort  }
   ::= { gs2326plusARPSpoofingPreventionTable 1 }

Gs2326plusARPSpoofingPreventionEntry ::= SEQUENCE {
   gs2326plusARPSpoofingPreventionPort           Integer32,
   gs2326plusARPSpoofingPreventionPortMode       INTEGER,
   gs2326plusARPSpoofingPreventionPortLimit      Integer32,
   gs2326plusARPSpoofingPreventionPortAction     INTEGER,
   gs2326plusARPSpoofingPreventionPortState      DisplayString,
   gs2326plusARPSpoofingPreventionPortReOpen     INTEGER
}

gs2326plusARPSpoofingPreventionPort OBJECT-TYPE
   SYNTAX      Integer32(1..4095)
   MAX-ACCESS  not-accessible
   STATUS      current
   DESCRIPTION
       " "
   ::= { gs2326plusARPSpoofingPreventionEntry 1 }

gs2326plusARPSpoofingPreventionPortMode OBJECT-TYPE
   SYNTAX      INTEGER { disable(0), enable(1) }
   MAX-ACCESS  read-write
   STATUS      current
   DESCRIPTION
       "default: 0
       0: disable
       1: enable"
   ::= { gs2326plusARPSpoofingPreventionEntry 2 }

gs2326plusARPSpoofingPreventionPortLimit OBJECT-TYPE
   SYNTAX      Integer32(1..100)
   MAX-ACCESS  read-write
   STATUS      current
   DESCRIPTION
       "default: 1, range: 1-100"
   ::= { gs2326plusARPSpoofingPreventionEntry 3 }

gs2326plusARPSpoofingPreventionPortAction OBJECT-TYPE
   SYNTAX      INTEGER { none(0), trap(1), dropAndTrap(2), shutdown(3), trapAndShutdown(4) }
   MAX-ACCESS  read-write
   STATUS      current
   DESCRIPTION
       "default: 0
       0: none
       1: trap
       2: drop&trap
       3: shutdown
       4: trap&shutdown"
   ::= { gs2326plusARPSpoofingPreventionEntry 4 }

gs2326plusARPSpoofingPreventionPortState OBJECT-TYPE
   SYNTAX      DisplayString
   MAX-ACCESS  read-only
   STATUS      current
   DESCRIPTION
       ""
   ::= { gs2326plusARPSpoofingPreventionEntry 5 }

gs2326plusARPSpoofingPreventionPortReOpen OBJECT-TYPE
   SYNTAX      INTEGER { none(0), reopen(1) }
   MAX-ACCESS  read-write
   STATUS      current
   DESCRIPTION
       "default: 0
       0: none
       1: reopen"
   ::= { gs2326plusARPSpoofingPreventionEntry 6 }

gs2326plusARPIPDoSPrevention	                                OBJECT IDENTIFIER ::= { gs2326plusARPInspection 8 }

gs2326plusARPIPDoSPreventionTCPMode OBJECT-TYPE
   SYNTAX      INTEGER { disable(0), enable(1) }
   MAX-ACCESS  read-write
   STATUS      current
   DESCRIPTION
       "default: 0
       0: disable
       1: enable "
   ::= { gs2326plusARPIPDoSPrevention 1 }

gs2326plusARPIPDoSPreventionUDPMode OBJECT-TYPE
   SYNTAX      INTEGER { disable(0), enable(1) }
   MAX-ACCESS  read-write
   STATUS      current
   DESCRIPTION
       "default: 0
       0: disable
       1: enable "
   ::= { gs2326plusARPIPDoSPrevention 2 }

gs2326plusARPIPDoSPreventionICMPMode OBJECT-TYPE
   SYNTAX      INTEGER { disable(0), enable(1) }
   MAX-ACCESS  read-write
   STATUS      current
   DESCRIPTION
       "default: 0
       0: disable
       1: enable "
   ::= { gs2326plusARPIPDoSPrevention 3 }

gs2326plusARPIPDoSPreventionServerPort1 OBJECT-TYPE
   SYNTAX      Integer32(0..4094)
   MAX-ACCESS  read-write
   STATUS      current
   DESCRIPTION
       " Port, range: 0 - port number. 0: none. "
   ::= { gs2326plusARPIPDoSPrevention 4 }

gs2326plusARPIPDoSPreventionServerPort2 OBJECT-TYPE
   SYNTAX      Integer32(0..4094)
   MAX-ACCESS  read-write
   STATUS      current
   DESCRIPTION
       " Port, range: 0 - port number. 0: none. "
   ::= { gs2326plusARPIPDoSPrevention 5 }

gs2326plusARPIPDoSPreventionServerPort3 OBJECT-TYPE
   SYNTAX      Integer32(0..4094)
   MAX-ACCESS  read-write
   STATUS      current
   DESCRIPTION
       " Port, range: 0 - port number. 0: none. "
   ::= { gs2326plusARPIPDoSPrevention 6 }

gs2326plusARPIPDoSPreventionServerPort4 OBJECT-TYPE
   SYNTAX      Integer32(0..4094)
   MAX-ACCESS  read-write
   STATUS      current
   DESCRIPTION
       " Port, range: 0 - port number. 0: none. "
   ::= { gs2326plusARPIPDoSPrevention 7 }

gs2326plusDHCPSnooping                                          OBJECT IDENTIFIER ::= { gs2326plusSecurity 3 }

gs2326plusDHCPSnoopingConf                                          OBJECT IDENTIFIER ::= { gs2326plusDHCPSnooping 1 }

gs2326plusDHCPSnoopingMode OBJECT-TYPE
   SYNTAX      INTEGER { disable(0), enable(1) }
   MAX-ACCESS  read-write
   STATUS      current
   DESCRIPTION
       "default: 0
       0: disable
       1: enable"
   ::= { gs2326plusDHCPSnoopingConf 1 }

gs2326plusDHCPSnoopingPortModeConfigurationTable OBJECT-TYPE
   SYNTAX      SEQUENCE OF Gs2326plusDHCPSnoopingPortModeConfigurationEntry
   MAX-ACCESS  not-accessible
   STATUS      current
   DESCRIPTION
       " "
   ::= { gs2326plusDHCPSnoopingConf 2 }

gs2326plusDHCPSnoopingPortModeConfigurationEntry OBJECT-TYPE
   SYNTAX      Gs2326plusDHCPSnoopingPortModeConfigurationEntry
   MAX-ACCESS  not-accessible
   STATUS      current
   DESCRIPTION
       ""
   INDEX    { gs2326plusDHCPSnoopingPortModeConfigurationPort  }
   ::= { gs2326plusDHCPSnoopingPortModeConfigurationTable 1 }

Gs2326plusDHCPSnoopingPortModeConfigurationEntry ::= SEQUENCE {
   gs2326plusDHCPSnoopingPortModeConfigurationPort	Integer32,
   gs2326plusDHCPSnoopingPortModeConfigurationMode	INTEGER
}

gs2326plusDHCPSnoopingPortModeConfigurationPort OBJECT-TYPE
   SYNTAX      Integer32(1..4095)
   MAX-ACCESS  not-accessible
   STATUS      current
   DESCRIPTION
       " "
   ::= { gs2326plusDHCPSnoopingPortModeConfigurationEntry 1 }

gs2326plusDHCPSnoopingPortModeConfigurationMode OBJECT-TYPE
   SYNTAX      INTEGER { trust(0), untrust(1) }
   MAX-ACCESS  read-write
   STATUS      current
   DESCRIPTION
       "default: 1
       0: trust port mode
       1: untrust port mode"
   ::= { gs2326plusDHCPSnoopingPortModeConfigurationEntry 2 }

gs2326plusDHCPSnoopingStatisticsTable OBJECT-TYPE
   SYNTAX      SEQUENCE OF Gs2326plusDHCPSnoopingStatisticsEntry
   MAX-ACCESS  not-accessible
   STATUS      current
   DESCRIPTION
       " "
   ::= { gs2326plusDHCPSnooping 2 }

gs2326plusDHCPSnoopingStatisticsEntry OBJECT-TYPE
   SYNTAX      Gs2326plusDHCPSnoopingStatisticsEntry
   MAX-ACCESS  not-accessible
   STATUS      current
   DESCRIPTION
       ""
   INDEX    { gs2326plusDHCPSnoopingStatisticsPort  }
   ::= { gs2326plusDHCPSnoopingStatisticsTable 1 }

Gs2326plusDHCPSnoopingStatisticsEntry ::= SEQUENCE {
   gs2326plusDHCPSnoopingStatisticsPort         Integer32,
   gs2326plusDHCPSnoopingStatisticsClear        INTEGER,
   gs2326plusDHCPSnoopingRxDiscover             Counter32,
   gs2326plusDHCPSnoopingRxOffer                Counter32,
   gs2326plusDHCPSnoopingRxRequest              Counter32,
   gs2326plusDHCPSnoopingRxDecline              Counter32,
   gs2326plusDHCPSnoopingRxACK                  Counter32,
   gs2326plusDHCPSnoopingRxNAK                  Counter32,
   gs2326plusDHCPSnoopingRxRelease              Counter32,
   gs2326plusDHCPSnoopingRxInform               Counter32,
   gs2326plusDHCPSnoopingRxLeaseQuery           Counter32,
   gs2326plusDHCPSnoopingRxLeaseUnassigned      Counter32,
   gs2326plusDHCPSnoopingRxLeaseUnknown         Counter32,
   gs2326plusDHCPSnoopingRxLeaseActive          Counter32,
   gs2326plusDHCPSnoopingTxDiscover             Counter32,
   gs2326plusDHCPSnoopingTxOffer                Counter32,
   gs2326plusDHCPSnoopingTxRequest              Counter32,
   gs2326plusDHCPSnoopingTxDecline              Counter32,
   gs2326plusDHCPSnoopingTxACK                  Counter32,
   gs2326plusDHCPSnoopingTxNAK                  Counter32,
   gs2326plusDHCPSnoopingTxRelease              Counter32,
   gs2326plusDHCPSnoopingTxInform               Counter32,
   gs2326plusDHCPSnoopingTxLeaseQuery           Counter32,
   gs2326plusDHCPSnoopingTxLeaseUnassigned      Counter32,
   gs2326plusDHCPSnoopingTxLeaseUnknown         Counter32,
   gs2326plusDHCPSnoopingTxLeaseActive          Counter32
}

gs2326plusDHCPSnoopingStatisticsPort OBJECT-TYPE
   SYNTAX      Integer32(1..4095)
   MAX-ACCESS  not-accessible
   STATUS      current
   DESCRIPTION
       " "
   ::= { gs2326plusDHCPSnoopingStatisticsEntry 1 }

gs2326plusDHCPSnoopingStatisticsClear OBJECT-TYPE
   SYNTAX      INTEGER { none(0), clear(1) }
   MAX-ACCESS  read-write
   STATUS      current
   DESCRIPTION
       "default: 0
       0: none
       1: clear"
   ::= { gs2326plusDHCPSnoopingStatisticsEntry 2 }

gs2326plusDHCPSnoopingRxDiscover OBJECT-TYPE
   SYNTAX      Counter32
   MAX-ACCESS  read-only
   STATUS      current
   DESCRIPTION
       " "
   ::= { gs2326plusDHCPSnoopingStatisticsEntry 3 }

gs2326plusDHCPSnoopingRxOffer OBJECT-TYPE
   SYNTAX      Counter32
   MAX-ACCESS  read-only
   STATUS      current
   DESCRIPTION
       " "
   ::= { gs2326plusDHCPSnoopingStatisticsEntry 4 }

gs2326plusDHCPSnoopingRxRequest OBJECT-TYPE
   SYNTAX      Counter32
   MAX-ACCESS  read-only
   STATUS      current
   DESCRIPTION
       " "
   ::= { gs2326plusDHCPSnoopingStatisticsEntry 5 }

gs2326plusDHCPSnoopingRxDecline OBJECT-TYPE
   SYNTAX      Counter32
   MAX-ACCESS  read-only
   STATUS      current
   DESCRIPTION
       " "
   ::= { gs2326plusDHCPSnoopingStatisticsEntry 6 }

gs2326plusDHCPSnoopingRxACK OBJECT-TYPE
   SYNTAX      Counter32
   MAX-ACCESS  read-only
   STATUS      current
   DESCRIPTION
       " "
   ::= { gs2326plusDHCPSnoopingStatisticsEntry 7 }

gs2326plusDHCPSnoopingRxNAK OBJECT-TYPE
   SYNTAX      Counter32
   MAX-ACCESS  read-only
   STATUS      current
   DESCRIPTION
       " "
   ::= { gs2326plusDHCPSnoopingStatisticsEntry 8 }

gs2326plusDHCPSnoopingRxRelease OBJECT-TYPE
   SYNTAX      Counter32
   MAX-ACCESS  read-only
   STATUS      current
   DESCRIPTION
       " "
   ::= { gs2326plusDHCPSnoopingStatisticsEntry 9 }

gs2326plusDHCPSnoopingRxInform OBJECT-TYPE
   SYNTAX      Counter32
   MAX-ACCESS  read-only
   STATUS      current
   DESCRIPTION
       " "
   ::= { gs2326plusDHCPSnoopingStatisticsEntry 10 }

gs2326plusDHCPSnoopingRxLeaseQuery OBJECT-TYPE
   SYNTAX      Counter32
   MAX-ACCESS  read-only
   STATUS      current
   DESCRIPTION
       " "
   ::= { gs2326plusDHCPSnoopingStatisticsEntry 11 }

gs2326plusDHCPSnoopingRxLeaseUnassigned OBJECT-TYPE
   SYNTAX      Counter32
   MAX-ACCESS  read-only
   STATUS      current
   DESCRIPTION
       " "
   ::= { gs2326plusDHCPSnoopingStatisticsEntry 12 }

gs2326plusDHCPSnoopingRxLeaseUnknown OBJECT-TYPE
   SYNTAX      Counter32
   MAX-ACCESS  read-only
   STATUS      current
   DESCRIPTION
       " "
   ::= { gs2326plusDHCPSnoopingStatisticsEntry 13 }

gs2326plusDHCPSnoopingRxLeaseActive OBJECT-TYPE
   SYNTAX      Counter32
   MAX-ACCESS  read-only
   STATUS      current
   DESCRIPTION
       " "
   ::= { gs2326plusDHCPSnoopingStatisticsEntry 14 }

gs2326plusDHCPSnoopingTxDiscover OBJECT-TYPE
   SYNTAX      Counter32
   MAX-ACCESS  read-only
   STATUS      current
   DESCRIPTION
       " "
   ::= { gs2326plusDHCPSnoopingStatisticsEntry 15 }

gs2326plusDHCPSnoopingTxOffer OBJECT-TYPE
   SYNTAX      Counter32
   MAX-ACCESS  read-only
   STATUS      current
   DESCRIPTION
       " "
   ::= { gs2326plusDHCPSnoopingStatisticsEntry 16 }

gs2326plusDHCPSnoopingTxRequest OBJECT-TYPE
   SYNTAX      Counter32
   MAX-ACCESS  read-only
   STATUS      current
   DESCRIPTION
       " "
   ::= { gs2326plusDHCPSnoopingStatisticsEntry 17 }

gs2326plusDHCPSnoopingTxDecline OBJECT-TYPE
   SYNTAX      Counter32
   MAX-ACCESS  read-only
   STATUS      current
   DESCRIPTION
       " "
   ::= { gs2326plusDHCPSnoopingStatisticsEntry 18 }

gs2326plusDHCPSnoopingTxACK OBJECT-TYPE
   SYNTAX      Counter32
   MAX-ACCESS  read-only
   STATUS      current
   DESCRIPTION
       " "
   ::= { gs2326plusDHCPSnoopingStatisticsEntry 19 }

gs2326plusDHCPSnoopingTxNAK OBJECT-TYPE
   SYNTAX      Counter32
   MAX-ACCESS  read-only
   STATUS      current
   DESCRIPTION
       " "
   ::= { gs2326plusDHCPSnoopingStatisticsEntry 20 }

gs2326plusDHCPSnoopingTxRelease OBJECT-TYPE
   SYNTAX      Counter32
   MAX-ACCESS  read-only
   STATUS      current
   DESCRIPTION
       " "
   ::= { gs2326plusDHCPSnoopingStatisticsEntry 21 }

gs2326plusDHCPSnoopingTxInform OBJECT-TYPE
   SYNTAX      Counter32
   MAX-ACCESS  read-only
   STATUS      current
   DESCRIPTION
       " "
   ::= { gs2326plusDHCPSnoopingStatisticsEntry 22 }

gs2326plusDHCPSnoopingTxLeaseQuery OBJECT-TYPE
   SYNTAX      Counter32
   MAX-ACCESS  read-only
   STATUS      current
   DESCRIPTION
       " "
   ::= { gs2326plusDHCPSnoopingStatisticsEntry 23 }

gs2326plusDHCPSnoopingTxLeaseUnassigned OBJECT-TYPE
   SYNTAX      Counter32
   MAX-ACCESS  read-only
   STATUS      current
   DESCRIPTION
       " "
   ::= { gs2326plusDHCPSnoopingStatisticsEntry 24 }

gs2326plusDHCPSnoopingTxLeaseUnknown OBJECT-TYPE
   SYNTAX      Counter32
   MAX-ACCESS  read-only
   STATUS      current
   DESCRIPTION
       " "
   ::= { gs2326plusDHCPSnoopingStatisticsEntry 25 }

gs2326plusDHCPSnoopingTxLeaseActive OBJECT-TYPE
   SYNTAX      Counter32
   MAX-ACCESS  read-only
   STATUS      current
   DESCRIPTION
       " "
   ::= { gs2326plusDHCPSnoopingStatisticsEntry 26 }


gs2326plusDHCPRelay                                             OBJECT IDENTIFIER ::= { gs2326plusSecurity 4 }

gs2326plusDHCPRelayConfiguration                                         OBJECT IDENTIFIER ::= { gs2326plusDHCPRelay 1 }

gs2326plusDHCPRelayMode OBJECT-TYPE
   SYNTAX      INTEGER { disable(0), enable(1) }
   MAX-ACCESS  read-write
   STATUS      current
   DESCRIPTION
       "default: 0
       0: disable
       1: enable
       We need at least one server"
   ::= { gs2326plusDHCPRelayConfiguration 1 }

gs2326plusDHCPRelayServer OBJECT-TYPE
   SYNTAX      IpAddress
   MAX-ACCESS  read-write
   STATUS      current
   DESCRIPTION
       " "
   ::= { gs2326plusDHCPRelayConfiguration 2 }

gs2326plusDHCPRelayInformationMode OBJECT-TYPE
   SYNTAX      INTEGER { disable(0), enable(1) }
   MAX-ACCESS  read-write
   STATUS      current
   DESCRIPTION
       "default: 0
       0: disable
       1: enable "
   ::= { gs2326plusDHCPRelayConfiguration 3 }

gs2326plusDHCPRelayInformationPolicy OBJECT-TYPE
   SYNTAX      INTEGER { replace(0), keep(1), drop(2) }
   MAX-ACCESS  read-write
   STATUS      current
   DESCRIPTION
       "default: 0
       0: replace
       1: keep
       2: drop "
   ::= { gs2326plusDHCPRelayConfiguration 4 }

gs2326plusDHCPRelayInformationCustom OBJECT-TYPE
   SYNTAX      DisplayString(SIZE(0..32))
   MAX-ACCESS  read-write
   STATUS      current
   DESCRIPTION
       "DHCP Option 82 Circuit ID custom information"
   ::= { gs2326plusDHCPRelayConfiguration 1500 }

gs2326plusDHCPRelayConfigurationGateways                                          OBJECT IDENTIFIER ::= { gs2326plusDHCPRelayConfiguration 5 }

gs2326plusDHCPRelayConfigurationGatewaysCreate OBJECT-TYPE
   SYNTAX       INTEGER { none(0), create(1) }
   MAX-ACCESS   read-write
   STATUS       current
   DESCRIPTION
       "default: 0
        0 : None  (read only)
        1 : Create entry"
   ::= { gs2326plusDHCPRelayConfigurationGateways 1 }

gs2326plusDHCPRelayConfigurationGatewaysTable OBJECT-TYPE
   SYNTAX      SEQUENCE OF Gs2326plusDHCPRelayConfigurationGatewaysEntry
   MAX-ACCESS  not-accessible
   STATUS      current
   DESCRIPTION
       " Create DHCP Relay Gateway IP address entry."
   ::= { gs2326plusDHCPRelayConfigurationGateways 2 }

gs2326plusDHCPRelayConfigurationGatewaysEntry OBJECT-TYPE
   SYNTAX      Gs2326plusDHCPRelayConfigurationGatewaysEntry
   MAX-ACCESS  not-accessible
   STATUS      current
   DESCRIPTION
       ""
   INDEX    { gs2326plusDHCPRelayConfigurationGatewaysIndex  }
   ::= { gs2326plusDHCPRelayConfigurationGatewaysTable 1 }

Gs2326plusDHCPRelayConfigurationGatewaysEntry ::= SEQUENCE {
   gs2326plusDHCPRelayConfigurationGatewaysIndex           Integer32,
   gs2326plusDHCPRelayConfigurationGatewaysVLANId          Integer32,
   gs2326plusDHCPRelayConfigurationGatewaysIP              IpAddress,
   gs2326plusDHCPRelayConfigurationGatewaysRowStatus       INTEGER
}

gs2326plusDHCPRelayConfigurationGatewaysIndex OBJECT-TYPE
   SYNTAX      Integer32(1..6)
   MAX-ACCESS  not-accessible
   STATUS      current
   DESCRIPTION
       " "
   ::= { gs2326plusDHCPRelayConfigurationGatewaysEntry 1 }

gs2326plusDHCPRelayConfigurationGatewaysVLANId OBJECT-TYPE
   SYNTAX      Integer32(1..4094)
   MAX-ACCESS  read-write
   STATUS      current
   DESCRIPTION
       " VLAN ID "
   ::= { gs2326plusDHCPRelayConfigurationGatewaysEntry 2 }

gs2326plusDHCPRelayConfigurationGatewaysIP OBJECT-TYPE
   SYNTAX      IpAddress
   MAX-ACCESS  read-write
   STATUS      current
   DESCRIPTION
       "DHCP GIADDR address."
   ::= { gs2326plusDHCPRelayConfigurationGatewaysEntry 3 }

gs2326plusDHCPRelayConfigurationGatewaysRowStatus OBJECT-TYPE
   SYNTAX      INTEGER { active(1), notInservice(2), destroy(4), undo(5) }
   MAX-ACCESS  read-write
   STATUS      current
   DESCRIPTION
       "1: active
        2: notInservice
        4: destroy
        5: undo"
   ::= { gs2326plusDHCPRelayConfigurationGatewaysEntry 4 }

gs2326plusDHCPRelayStatistics                                   OBJECT IDENTIFIER ::= { gs2326plusDHCPRelay 2 }

gs2326plusDHCPRelayServerStatistics                                   OBJECT IDENTIFIER ::= { gs2326plusDHCPRelayStatistics 1 }

gs2326plusServerStatTransmitToServer OBJECT-TYPE
   SYNTAX      Counter32
   MAX-ACCESS  read-only
   STATUS      current
   DESCRIPTION
       " "
   ::= { gs2326plusDHCPRelayServerStatistics 1 }

gs2326plusServerStatTransmitError OBJECT-TYPE
   SYNTAX      Counter32
   MAX-ACCESS  read-only
   STATUS      current
   DESCRIPTION
       " "
   ::= { gs2326plusDHCPRelayServerStatistics 2 }

gs2326plusServerStatReceiveFromServer OBJECT-TYPE
   SYNTAX      Counter32
   MAX-ACCESS  read-only
   STATUS      current
   DESCRIPTION
       " "
   ::= { gs2326plusDHCPRelayServerStatistics 3 }

gs2326plusServerStatReceiveMissingAgentOption OBJECT-TYPE
   SYNTAX      Counter32
   MAX-ACCESS  read-only
   STATUS      current
   DESCRIPTION
       " "
   ::= { gs2326plusDHCPRelayServerStatistics 4 }

gs2326plusServerStatReceiveMissingCircuitID OBJECT-TYPE
   SYNTAX      Counter32
   MAX-ACCESS  read-only
   STATUS      current
   DESCRIPTION
       " "
   ::= { gs2326plusDHCPRelayServerStatistics 5 }

gs2326plusServerStatReceiveMissingRemoteID OBJECT-TYPE
   SYNTAX      Counter32
   MAX-ACCESS  read-only
   STATUS      current
   DESCRIPTION
       " "
   ::= { gs2326plusDHCPRelayServerStatistics 6 }

gs2326plusServerStatReceiveBadCircuitID OBJECT-TYPE
   SYNTAX      Counter32
   MAX-ACCESS  read-only
   STATUS      current
   DESCRIPTION
       " "
   ::= { gs2326plusDHCPRelayServerStatistics 7 }

gs2326plusServerStatReceiveBadRemoteID OBJECT-TYPE
   SYNTAX      Counter32
   MAX-ACCESS  read-only
   STATUS      current
   DESCRIPTION
       " "
   ::= { gs2326plusDHCPRelayServerStatistics 8 }

gs2326plusDHCPRelayClientStatistics                                   OBJECT IDENTIFIER ::= { gs2326plusDHCPRelayStatistics 2 }

gs2326plusClientStatTransmitToClient OBJECT-TYPE
   SYNTAX      Counter32
   MAX-ACCESS  read-only
   STATUS      current
   DESCRIPTION
       " "
   ::= { gs2326plusDHCPRelayClientStatistics 1 }

gs2326plusClientStatTransmitError OBJECT-TYPE
   SYNTAX      Counter32
   MAX-ACCESS  read-only
   STATUS      current
   DESCRIPTION
       " "
   ::= { gs2326plusDHCPRelayClientStatistics 2 }

gs2326plusClientStatReceivefromClient OBJECT-TYPE
   SYNTAX      Counter32
   MAX-ACCESS  read-only
   STATUS      current
   DESCRIPTION
       " "
   ::= { gs2326plusDHCPRelayClientStatistics 3 }

gs2326plusClientStatReceiveAgentOption OBJECT-TYPE
   SYNTAX      Counter32
   MAX-ACCESS  read-only
   STATUS      current
   DESCRIPTION
       " "
   ::= { gs2326plusDHCPRelayClientStatistics 4 }

gs2326plusClientStatReplaceAgentOption OBJECT-TYPE
   SYNTAX      Counter32
   MAX-ACCESS  read-only
   STATUS      current
   DESCRIPTION
       " "
   ::= { gs2326plusDHCPRelayClientStatistics 5 }

gs2326plusClientStatKeepAgentOption OBJECT-TYPE
   SYNTAX      Counter32
   MAX-ACCESS  read-only
   STATUS      current
   DESCRIPTION
       " "
   ::= { gs2326plusDHCPRelayClientStatistics 6 }

gs2326plusClientStatDropAgentOption OBJECT-TYPE
   SYNTAX      Counter32
   MAX-ACCESS  read-only
   STATUS      current
   DESCRIPTION
       " "
   ::= { gs2326plusDHCPRelayClientStatistics 7 }

gs2326plusPortSecurity                                          OBJECT IDENTIFIER ::= { gs2326plusSecurity 5 }

gs2326plusPortSecLimitCtrl                                      OBJECT IDENTIFIER ::= { gs2326plusPortSecurity 1 }

gs2326plusPortSecLimitCtrlSystemConf                                      OBJECT IDENTIFIER ::= { gs2326plusPortSecLimitCtrl 1 }

gs2326plusPortSecurityMode OBJECT-TYPE
   SYNTAX      INTEGER { disable(0), enable(1) }
   MAX-ACCESS  read-write
   STATUS      current
   DESCRIPTION
       "default: 0
       0: disable
       1: enable "
   ::= { gs2326plusPortSecLimitCtrlSystemConf 1 }

gs2326plusPortSecurityAging OBJECT-TYPE
   SYNTAX      INTEGER { disable(0), enable(1) }
   MAX-ACCESS  read-write
   STATUS      current
   DESCRIPTION
       "default: 0
       0: disable
       1: enable "
   ::= { gs2326plusPortSecLimitCtrlSystemConf 2 }

gs2326plusPortSecurityAgingPeriod OBJECT-TYPE
   SYNTAX      INTEGER(10..10000000)
   MAX-ACCESS  read-write
   STATUS      current
   DESCRIPTION
       "default: 3600, range: 10-10000000 "
   ::= { gs2326plusPortSecLimitCtrlSystemConf 3 }

gs2326plusPortSecLimitCtrlTable OBJECT-TYPE
   SYNTAX      SEQUENCE OF Gs2326plusPortSecLimitCtrlEntry
   MAX-ACCESS  not-accessible
   STATUS      current
   DESCRIPTION
       " "
   ::= { gs2326plusPortSecLimitCtrl 2 }

gs2326plusPortSecLimitCtrlEntry OBJECT-TYPE
   SYNTAX      Gs2326plusPortSecLimitCtrlEntry
   MAX-ACCESS  not-accessible
   STATUS      current
   DESCRIPTION
       ""
   INDEX    { gs2326plusPortSecLimitCtrlPort  }
   ::= { gs2326plusPortSecLimitCtrlTable 1 }

Gs2326plusPortSecLimitCtrlEntry ::= SEQUENCE {
   gs2326plusPortSecLimitCtrlPort           Integer32,
   gs2326plusPortSecLimitCtrlPortMode       INTEGER,
   gs2326plusPortSecLimitCtrlPortLimit      Integer32,
   gs2326plusPortSecLimitCtrlPortAction     INTEGER,
   gs2326plusPortSecLimitCtrlPortState      DisplayString,
   gs2326plusPortSecLimitCtrlPortReOpen     INTEGER
}

gs2326plusPortSecLimitCtrlPort OBJECT-TYPE
   SYNTAX      Integer32(1..4095)
   MAX-ACCESS  not-accessible
   STATUS      current
   DESCRIPTION
       " "
   ::= { gs2326plusPortSecLimitCtrlEntry 1 }

gs2326plusPortSecLimitCtrlPortMode OBJECT-TYPE
   SYNTAX      INTEGER { disable(0), enable(1) }
   MAX-ACCESS  read-write
   STATUS      current
   DESCRIPTION
       "default: 0
       0: disable
       1: enable"
   ::= { gs2326plusPortSecLimitCtrlEntry 2 }

gs2326plusPortSecLimitCtrlPortLimit OBJECT-TYPE
   SYNTAX      Integer32(1..1024)
   MAX-ACCESS  read-write
   STATUS      current
   DESCRIPTION
       "default: 4, range: 1-1024"
   ::= { gs2326plusPortSecLimitCtrlEntry 3 }

gs2326plusPortSecLimitCtrlPortAction OBJECT-TYPE
   SYNTAX      INTEGER { none(0), trap(1), shutdown(2), trapShutdown(3) }
   MAX-ACCESS  read-write
   STATUS      current
   DESCRIPTION
       "default: 0
       0: none
       1: trap
       2: shutdown
       3: trap&shutdown"
   ::= { gs2326plusPortSecLimitCtrlEntry 4 }

gs2326plusPortSecLimitCtrlPortState OBJECT-TYPE
   SYNTAX      DisplayString
   MAX-ACCESS  read-only
   STATUS      current
   DESCRIPTION
       ""
   ::= { gs2326plusPortSecLimitCtrlEntry 5 }

gs2326plusPortSecLimitCtrlPortReOpen OBJECT-TYPE
   SYNTAX      INTEGER { none(0), reopen(1) }
   MAX-ACCESS  read-write
   STATUS      current
   DESCRIPTION
       "default: 0
       0: none
       1: reopen"
   ::= { gs2326plusPortSecLimitCtrlEntry 6 }

gs2326plusPortSecSwitchStatusTable OBJECT-TYPE
   SYNTAX      SEQUENCE OF Gs2326plusPortSecSwitchStatusEntry
   MAX-ACCESS  not-accessible
   STATUS      current
   DESCRIPTION
       " "
   ::= { gs2326plusPortSecurity 2 }

gs2326plusPortSecSwitchStatusEntry OBJECT-TYPE
   SYNTAX      Gs2326plusPortSecSwitchStatusEntry
   MAX-ACCESS  not-accessible
   STATUS      current
   DESCRIPTION
       ""
   INDEX    { gs2326plusPortSecSwitchStatusPort  }
   ::= { gs2326plusPortSecSwitchStatusTable 1 }

Gs2326plusPortSecSwitchStatusEntry ::= SEQUENCE {
   gs2326plusPortSecSwitchStatusPort                Integer32,
   gs2326plusPortSecSwitchStatusUsers               DisplayString,
   gs2326plusPortSecSwitchStatusState               DisplayString,
   gs2326plusPortSecSwitchStatusMACCountCurrent     Integer32,
   gs2326plusPortSecSwitchStatusMACCountLimit       Integer32
}

gs2326plusPortSecSwitchStatusPort OBJECT-TYPE
   SYNTAX      Integer32(1..4095)
   MAX-ACCESS  not-accessible
   STATUS      current
   DESCRIPTION
       " "
   ::= { gs2326plusPortSecSwitchStatusEntry 1 }

gs2326plusPortSecSwitchStatusUsers OBJECT-TYPE
   SYNTAX      DisplayString
   MAX-ACCESS  read-only
   STATUS      current
   DESCRIPTION
       " Users Abbr: L = Limit Control, 8 = 802.1X, D = DHCP Snooping, V = Voice VLAN,
         '-' means that the corresponding user module is not enabled. "
   ::= { gs2326plusPortSecSwitchStatusEntry 2 }

gs2326plusPortSecSwitchStatusState OBJECT-TYPE
   SYNTAX      DisplayString
   MAX-ACCESS  read-only
   STATUS      current
   DESCRIPTION
       " Shows the current state of the port : Disabled, Ready, Limit Reached, Shutdown. "
   ::= { gs2326plusPortSecSwitchStatusEntry 3 }

gs2326plusPortSecSwitchStatusMACCountCurrent OBJECT-TYPE
   SYNTAX      Integer32(1..4095)
   MAX-ACCESS  read-only
   STATUS      current
   DESCRIPTION
       ""
   ::= { gs2326plusPortSecSwitchStatusEntry 4 }

gs2326plusPortSecSwitchStatusMACCountLimit OBJECT-TYPE
   SYNTAX      Integer32(1..4095)
   MAX-ACCESS  read-only
   STATUS      current
   DESCRIPTION
       ""
   ::= { gs2326plusPortSecSwitchStatusEntry 5 }

gs2326plusPortSecPortStatus                                      OBJECT IDENTIFIER ::= { gs2326plusPortSecurity 3 }

gs2326plusPortSecPortStatusPort OBJECT-TYPE
   SYNTAX       Integer32(1..4095)
   MAX-ACCESS   read-write
   STATUS       current
   DESCRIPTION
       "port number
        default: 1
        range: 1 - port number."
   ::= { gs2326plusPortSecPortStatus 1 }

gs2326plusPortSecPortStatusTable OBJECT-TYPE
   SYNTAX      SEQUENCE OF Gs2326plusPortSecPortStatusEntry
   MAX-ACCESS  not-accessible
   STATUS      current
   DESCRIPTION
      " "
   ::= { gs2326plusPortSecPortStatus 2 }

gs2326plusPortSecPortStatusEntry OBJECT-TYPE
   SYNTAX      Gs2326plusPortSecPortStatusEntry
   MAX-ACCESS  not-accessible
   STATUS      current
   DESCRIPTION
       ""
   INDEX    { gs2326plusPortSecPortStatusIndex  }
   ::= { gs2326plusPortSecPortStatusTable 1 }

Gs2326plusPortSecPortStatusEntry ::= SEQUENCE {
   gs2326plusPortSecPortStatusIndex              Integer32,
   gs2326plusPortSecPortStatusMACAddress         MacAddress,
   gs2326plusPortSecPortStatusVLANId             Integer32,
   gs2326plusPortSecPortStatusState              DisplayString,
   gs2326plusPortSecPortStatusTimeOfAddition     DisplayString,
   gs2326plusPortSecPortStatusAgeAndHold         DisplayString
}

gs2326plusPortSecPortStatusIndex OBJECT-TYPE
   SYNTAX      Integer32(1..4095)
   MAX-ACCESS  not-accessible
   STATUS      current
   DESCRIPTION
       " "
   ::= { gs2326plusPortSecPortStatusEntry 1 }

gs2326plusPortSecPortStatusMACAddress OBJECT-TYPE
   SYNTAX      MacAddress
   MAX-ACCESS  read-only
   STATUS      current
   DESCRIPTION
       " "
   ::= { gs2326plusPortSecPortStatusEntry 2 }

gs2326plusPortSecPortStatusVLANId OBJECT-TYPE
   SYNTAX      Integer32(1..4094)
   MAX-ACCESS  read-only
   STATUS      current
   DESCRIPTION
       " "
   ::= { gs2326plusPortSecPortStatusEntry 3 }

gs2326plusPortSecPortStatusState OBJECT-TYPE
   SYNTAX      DisplayString
   MAX-ACCESS  read-only
   STATUS      current
   DESCRIPTION
       "Blocked / Forwarding "
   ::= { gs2326plusPortSecPortStatusEntry 4 }

gs2326plusPortSecPortStatusTimeOfAddition OBJECT-TYPE
   SYNTAX      DisplayString
   MAX-ACCESS  read-only
   STATUS      current
   DESCRIPTION
       " "
   ::= { gs2326plusPortSecPortStatusEntry 5 }

gs2326plusPortSecPortStatusAgeAndHold OBJECT-TYPE
   SYNTAX      DisplayString
   MAX-ACCESS  read-only
   STATUS      current
   DESCRIPTION
       " "
   ::= { gs2326plusPortSecPortStatusEntry 6 }


gs2326plusAccessManagement                                      OBJECT IDENTIFIER ::= { gs2326plusSecurity 6 }

gs2326plusAccessMgtConf                                         OBJECT IDENTIFIER ::= { gs2326plusAccessManagement 1 }

gs2326plusAccessMgtConfMode OBJECT-TYPE
   SYNTAX      INTEGER { disable(0), enable(1) }
   MAX-ACCESS  read-write
   STATUS      current
   DESCRIPTION
       "default: 0
       0: disable
       1: enable "
   ::= { gs2326plusAccessMgtConf 1 }

gs2326plusAccessMgtConfCreate OBJECT-TYPE
   SYNTAX      INTEGER { none(0), create(1) }
   MAX-ACCESS  read-write
   STATUS      current
   DESCRIPTION
       "default: 0
       0: none
       1: create "
   ::= { gs2326plusAccessMgtConf 2 }

gs2326plusAccessMgtConfTable OBJECT-TYPE
   SYNTAX      SEQUENCE OF Gs2326plusAccessMgtConfEntry
   MAX-ACCESS  not-accessible
   STATUS      current
   DESCRIPTION
       " "
   ::= { gs2326plusAccessMgtConf 3 }

gs2326plusAccessMgtConfEntry OBJECT-TYPE
   SYNTAX      Gs2326plusAccessMgtConfEntry
   MAX-ACCESS  not-accessible
   STATUS      current
   DESCRIPTION
       ""
   INDEX    { gs2326plusAccessMgtIndex  }
   ::= { gs2326plusAccessMgtConfTable 1 }

Gs2326plusAccessMgtConfEntry ::= SEQUENCE {
   gs2326plusAccessMgtIndex             Integer32,
   gs2326plusAccessMgtAddresstype       INTEGER,
   gs2326plusAccessMgtStartIpAddress    DisplayString,
   gs2326plusAccessMgtEndIpAddress      DisplayString,
   gs2326plusAccessMgtHttpHttps         INTEGER,
   gs2326plusAccessMgtSNMP              INTEGER,
   gs2326plusAccessMgtTelnetSSH         INTEGER,
   gs2326plusAccessMgtRowStatus         INTEGER
}

gs2326plusAccessMgtIndex OBJECT-TYPE
   SYNTAX      Integer32(1..16)
   MAX-ACCESS  read-write
   STATUS      current
   DESCRIPTION
       "Set Access Management config index
        range : 1-16."
   ::= { gs2326plusAccessMgtConfEntry 1 }

gs2326plusAccessMgtAddresstype OBJECT-TYPE
   SYNTAX      INTEGER { ipv4(0), ipv6(1) }
   MAX-ACCESS  read-write
   STATUS      current
   DESCRIPTION
       "0: ipv4
        1: ipv6 "
   ::= { gs2326plusAccessMgtConfEntry 2 }

gs2326plusAccessMgtStartIpAddress OBJECT-TYPE
   SYNTAX      DisplayString
   MAX-ACCESS  read-write
   STATUS      current
   DESCRIPTION
       " Start IP address.
         IP address doesn't allowed all zero or all 'ff'H."
   ::= { gs2326plusAccessMgtConfEntry 3 }

gs2326plusAccessMgtEndIpAddress OBJECT-TYPE
   SYNTAX      DisplayString
   MAX-ACCESS  read-write
   STATUS      current
   DESCRIPTION
       " End IP address.
         IP address doesn't allowed all zero or all 'ff'H.
         End ip address is not less than start ip address."
   ::= { gs2326plusAccessMgtConfEntry 4 }

gs2326plusAccessMgtHttpHttps OBJECT-TYPE
   SYNTAX      INTEGER { disable(0), enable(1) }
   MAX-ACCESS  read-write
   STATUS      current
   DESCRIPTION
       "default: 0
       0: disable
       1: enable "
   ::= { gs2326plusAccessMgtConfEntry 5 }

gs2326plusAccessMgtSNMP OBJECT-TYPE
   SYNTAX      INTEGER { disable(0), enable(1) }
   MAX-ACCESS  read-write
   STATUS      current
   DESCRIPTION
       "default: 0
       0: disable
       1: enable "
   ::= { gs2326plusAccessMgtConfEntry 6 }

gs2326plusAccessMgtTelnetSSH OBJECT-TYPE
   SYNTAX      INTEGER { disable(0), enable(1) }
   MAX-ACCESS  read-write
   STATUS      current
   DESCRIPTION
       "default: 0
       0: disable
       1: enable "
   ::= { gs2326plusAccessMgtConfEntry 7 }

gs2326plusAccessMgtRowStatus OBJECT-TYPE
   SYNTAX      INTEGER { active(1), notInservice(2), edit(3),destroy(4), undo(5) }
   MAX-ACCESS  read-write
   STATUS      current
   DESCRIPTION
       "1: active
        2: notInservice
        3: edit
        4: destroy
        5: undo"
   ::= { gs2326plusAccessMgtConfEntry 8 }

gs2326plusAccessMgtStatistics                                   OBJECT IDENTIFIER ::= { gs2326plusAccessManagement 2 }

gs2326plusHttpReceivedPkts OBJECT-TYPE
   SYNTAX      Counter32
   MAX-ACCESS  read-only
   STATUS      current
   DESCRIPTION
       " "
   ::= { gs2326plusAccessMgtStatistics 1 }

gs2326plusHttpAllowedPkts OBJECT-TYPE
   SYNTAX      Counter32
   MAX-ACCESS  read-only
   STATUS      current
   DESCRIPTION
       " "
   ::= { gs2326plusAccessMgtStatistics 2 }

gs2326plusHttpDiscardedPkts OBJECT-TYPE
   SYNTAX      Counter32
   MAX-ACCESS  read-only
   STATUS      current
   DESCRIPTION
       " "
   ::= { gs2326plusAccessMgtStatistics 3 }

gs2326plusHttpsReceivedPkts OBJECT-TYPE
   SYNTAX      Counter32
   MAX-ACCESS  read-only
   STATUS      current
   DESCRIPTION
       " "
   ::= { gs2326plusAccessMgtStatistics 4 }

gs2326plusHttpsAllowedPkts OBJECT-TYPE
   SYNTAX      Counter32
   MAX-ACCESS  read-only
   STATUS      current
   DESCRIPTION
       " "
   ::= { gs2326plusAccessMgtStatistics 5 }

gs2326plusHttpsDiscardedPkts OBJECT-TYPE
   SYNTAX      Counter32
   MAX-ACCESS  read-only
   STATUS      current
   DESCRIPTION
       " "
   ::= { gs2326plusAccessMgtStatistics 6 }

gs2326plusSnmpReceivedPkts OBJECT-TYPE
   SYNTAX      Counter32
   MAX-ACCESS  read-only
   STATUS      current
   DESCRIPTION
       " "
   ::= { gs2326plusAccessMgtStatistics 7 }

gs2326plusSnmpAllowedPkts OBJECT-TYPE
   SYNTAX      Counter32
   MAX-ACCESS  read-only
   STATUS      current
   DESCRIPTION
       " "
   ::= { gs2326plusAccessMgtStatistics 8 }

gs2326plusSnmpDiscardedPkts OBJECT-TYPE
   SYNTAX      Counter32
   MAX-ACCESS  read-only
   STATUS      current
   DESCRIPTION
       " "
   ::= { gs2326plusAccessMgtStatistics 9 }

gs2326plusTelnetReceivedPkts OBJECT-TYPE
   SYNTAX      Counter32
   MAX-ACCESS  read-only
   STATUS      current
   DESCRIPTION
       " "
   ::= { gs2326plusAccessMgtStatistics 10 }

gs2326plusTelnetAllowedPkts OBJECT-TYPE
   SYNTAX      Counter32
   MAX-ACCESS  read-only
   STATUS      current
   DESCRIPTION
       " "
   ::= { gs2326plusAccessMgtStatistics 11 }

gs2326plusTelnetDiscardedPkts OBJECT-TYPE
   SYNTAX      Counter32
   MAX-ACCESS  read-only
   STATUS      current
   DESCRIPTION
       " "
   ::= { gs2326plusAccessMgtStatistics 12 }

gs2326plusSSHReceivedPkts OBJECT-TYPE
   SYNTAX      Counter32
   MAX-ACCESS  read-only
   STATUS      current
   DESCRIPTION
       " "
   ::= { gs2326plusAccessMgtStatistics 13 }

gs2326plusSSHAllowedPkts OBJECT-TYPE
   SYNTAX      Counter32
   MAX-ACCESS  read-only
   STATUS      current
   DESCRIPTION
       " "
   ::= { gs2326plusAccessMgtStatistics 14 }

gs2326plusSSHDiscardedPkts OBJECT-TYPE
   SYNTAX      Counter32
   MAX-ACCESS  read-only
   STATUS      current
   DESCRIPTION
       " "
   ::= { gs2326plusAccessMgtStatistics 15 }

gs2326plusAccessMgtStatisticsClearAll OBJECT-TYPE
   SYNTAX      INTEGER { none(0), clear(1) }
   MAX-ACCESS  read-write
   STATUS      current
   DESCRIPTION
       "0: none
        1: clear"
   ::= { gs2326plusAccessMgtStatistics 16 }

gs2326plusSSH                                                   OBJECT IDENTIFIER ::= { gs2326plusSecurity 7 }

gs2326plusSSHMode OBJECT-TYPE
   SYNTAX      INTEGER { disable(0), enable(1) }
   MAX-ACCESS  read-write
   STATUS      current
   DESCRIPTION
       "default: 1
        0: disable
        1: enable"
   ::= { gs2326plusSSH 1 }

gs2326plusHTTPS                                                 OBJECT IDENTIFIER ::= { gs2326plusSecurity 8 }

gs2326plusHTTPSMode OBJECT-TYPE
   SYNTAX      INTEGER { disable(0), enable(1) }
   MAX-ACCESS  read-write
   STATUS      current
   DESCRIPTION
       "default: 1
        0: disable
        1: enable"
   ::= { gs2326plusHTTPS 1 }

gs2326plusHTTPSAutoRedirect OBJECT-TYPE
   SYNTAX      INTEGER { disable(0), enable(1) }
   MAX-ACCESS  read-write
   STATUS      current
   DESCRIPTION
       "default: 0
        0: disable
        1: enable"
   ::= { gs2326plusHTTPS 2 }

gs2326plusHTTPSCertRenew OBJECT-TYPE
   SYNTAX      INTEGER { doNothing(0), renew(1) }
   MAX-ACCESS  read-write
   STATUS      current
   DESCRIPTION
       "default: 0 ,
        0: doNothing
        1: renew"
   ::= { gs2326plusHTTPS 3 }

gs2326plusHTTPSMinProtoVersion OBJECT-TYPE
   SYNTAX      INTEGER { SSLv3(0), TLSv1(1), TLSv11(2), TLSv12(3)}
   MAX-ACCESS  read-write
   STATUS      current
   DESCRIPTION
       "default: 1
        0: SSLv3
        1: TLSv1
        2: TLSv1.1
        3: TLSv1.2"
   ::= { gs2326plusHTTPS 4 }

gs2326plusHTTPMode OBJECT-TYPE
   SYNTAX      INTEGER { disable(0), enable(1) }
   MAX-ACCESS  read-write
   STATUS      current
   DESCRIPTION
       "default: 1
        0: disable
        1: enable"
   ::= { gs2326plusHTTPS 5 }

gs2326plusAuthMethod                                            OBJECT IDENTIFIER ::= { gs2326plusSecurity 9 }

gs2326plusConsoleAuthMethod OBJECT-TYPE
   SYNTAX      INTEGER { none(0), local(1), radius(2), tacacsplus(3) }
   MAX-ACCESS  read-write
   STATUS      current
   DESCRIPTION
       "default: 1
        0: none
        1: local
        2: RADIUS
        3: TACACS+"
   ::= { gs2326plusAuthMethod 1 }

gs2326plusConsoleFallback OBJECT-TYPE
   SYNTAX      INTEGER { disable(0), enable(1) }
   MAX-ACCESS  read-write
   STATUS      current
   DESCRIPTION
       "default: 0
        0:disable
        1:enable"
   ::= { gs2326plusAuthMethod 2 }

gs2326plusTelnetAuthMethod OBJECT-TYPE
   SYNTAX      INTEGER { none(0), local(1), radius(2), tacacsplus(3) }
   MAX-ACCESS  read-write
   STATUS      current
   DESCRIPTION
       "default: 1
        0: none
        1: local
        2: RADIUS
        3: TACACS+"
   ::= { gs2326plusAuthMethod 3 }

gs2326plusTelnetFallback OBJECT-TYPE
   SYNTAX      INTEGER { disable(0), enable(1) }
   MAX-ACCESS  read-write
   STATUS      current
   DESCRIPTION
       "default: 0
        0:disable
        1:enable"
   ::= { gs2326plusAuthMethod 4 }

gs2326plusSshAuthMethod OBJECT-TYPE
   SYNTAX      INTEGER { none(0), local(1), radius(2), tacacsplus(3) }
   MAX-ACCESS  read-write
   STATUS      current
   DESCRIPTION
       "default: 1
        0: none
        1: local
        2: RADIUS
        3: TACACS+"
   ::= { gs2326plusAuthMethod 5 }

gs2326plusSshFallback OBJECT-TYPE
   SYNTAX      INTEGER { disable(0), enable(1) }
   MAX-ACCESS  read-write
   STATUS      current
   DESCRIPTION
       "default: 0
        0:disable
        1:enable"
   ::= { gs2326plusAuthMethod 6 }

gs2326plusTftpAuthMethod OBJECT-TYPE
   SYNTAX      INTEGER { none(0), local(1), radius(2), tacacsplus(3) }
   MAX-ACCESS  read-write
   STATUS      current
   DESCRIPTION
       "default: 1
        0: none
        1: local
        2: RADIUS
        3: TACACS+"
   ::= { gs2326plusAuthMethod 9 }

gs2326plusTftpFallback OBJECT-TYPE
   SYNTAX      INTEGER { disable(0), enable(1) }
   MAX-ACCESS  read-write
   STATUS      current
   DESCRIPTION
       "default: 0
        0:disable
        1:enable"
   ::= { gs2326plusAuthMethod 10 }

gs2326plusLoginFailures OBJECT-TYPE
   SYNTAX      Integer32(0..99)
   MAX-ACCESS  read-write
   STATUS      current
   DESCRIPTION
       "When login failures mechanism is triggered,the lock minutes will prevent to login in this periods.
        The value '0' should deactivate this feature.
        range: 0-99.
        default: 5."
   ::= { gs2326plusAuthMethod 11 }

gs2326plusLockMinutes OBJECT-TYPE
   SYNTAX      Integer32(1..99)
   MAX-ACCESS  read-write
   STATUS      current
   DESCRIPTION
       "Lock time to login failures trigger.
        range: 1-99.
        default: 5."
   ::= { gs2326plusAuthMethod 12 }

gs2326plusHttpAuthMethod OBJECT-TYPE
   SYNTAX      INTEGER { none(0), local(1), radius(2), tacacsplus(3) }
   MAX-ACCESS  read-write
   STATUS      current
   DESCRIPTION
       "default: 1
        0: none
        1: local
        2: RADIUS
        3: TACACS+"
   ::= { gs2326plusAuthMethod 13 }

gs2326plusHttpFallback OBJECT-TYPE
   SYNTAX      INTEGER { disable(0), enable(1) }
   MAX-ACCESS  read-write
   STATUS      current
   DESCRIPTION
       "default: 0
        0:disable
        1:enable"
   ::= { gs2326plusAuthMethod 14 }

gs2326plusHttpsAuthMethod OBJECT-TYPE
   SYNTAX      INTEGER { none(0), local(1), radius(2), tacacsplus(3) }
   MAX-ACCESS  read-write
   STATUS      current
   DESCRIPTION
       "default: 1
        0: none
        1: local
        2: RADIUS
        3: TACACS+"
   ::= { gs2326plusAuthMethod 15 }

gs2326plusHttpsFallback OBJECT-TYPE
   SYNTAX      INTEGER { disable(0), enable(1) }
   MAX-ACCESS  read-write
   STATUS      current
   DESCRIPTION
       "default: 0
        0:disable
        1:enable"
   ::= { gs2326plusAuthMethod 16 }


gs2326plusAAA                                              OBJECT IDENTIFIER ::= { gs2326plusSecurity 10 }

gs2326plusAAACommonServer                                  OBJECT IDENTIFIER ::= { gs2326plusAAA 1 }

gs2326plusAAACommonServerTimeout OBJECT-TYPE
   SYNTAX      Integer32(3..3600)
   MAX-ACCESS  read-write
   STATUS      current
   DESCRIPTION
       "The Timeout, which can be set to a number between 3 and 3600 seconds, is
       the maximum time to wait for a reply from a server. If the server does not
       reply within this timeframe, we will consider it to be dead and continue
       with the next enabled server (if any). RADIUS servers are using the UDP
       protocol, which is unreliable by design. In order to cope with lost frames,
       the timeout interval is divided into 3 subintervals of equal length. If a
       reply is not received within the subinterval, the request is transmitted
       again. This algorithm causes the RADIUS server to be queried up to 3 times
       before it is considered to be dead.
        default: 15."
   ::= { gs2326plusAAACommonServer 1 }

gs2326plusAAACommonServerDeadTime OBJECT-TYPE
   SYNTAX      Integer32(0..3600)
   MAX-ACCESS  read-write
   STATUS      current
   DESCRIPTION
       "The Dead Time, which can be set to a number between 0 and 3600 seconds,
       is the period during which the switch will not send new requests to a
       server that has failed to respond to a previous request. This will stop
       the switch from continually trying to contact a server that it has already
       determined as dead.
       Setting the Dead Time to a value greater than 0 (zero) will enable this feature,
       but only if more than one server has been configured.
       default: 300."
   ::= { gs2326plusAAACommonServer 2 }

gs2326plusAAATACACSPlusAuthAndAccounting                  OBJECT IDENTIFIER ::= { gs2326plusAAA 2 }

gs2326plusAAAAuthorization OBJECT-TYPE
   SYNTAX      INTEGER { disable(0), enable(1) }
   MAX-ACCESS  read-write
   STATUS      current
   DESCRIPTION
       "Authorization is the action of determining what a user is allowed to do.
       An authorization request may indicate that the user is not authenticated.
       In this case it is up to the authorization agent to determine if an
       unauthenticated user is allowed the services in question. "
   ::= { gs2326plusAAATACACSPlusAuthAndAccounting 1 }

gs2326plusAAAFallbackToLocalAuthorization OBJECT-TYPE
   SYNTAX      INTEGER { disable(0), enable(1) }
   MAX-ACCESS  read-write
   STATUS      current
   DESCRIPTION
       "This function is an auxiliary function of Authorization. When the DUT
       cannot communicate with TACACS+ Server normally, it will check the right/
        permission level of the Local Account to execute the Authorization. "
   ::= { gs2326plusAAATACACSPlusAuthAndAccounting 2 }

gs2326plusAAAAccounting OBJECT-TYPE
   SYNTAX      INTEGER { disable(0), enable(1) }
   MAX-ACCESS  read-write
   STATUS      current
   DESCRIPTION
       "Accounting is typically the third action after authentication and
       authorization. Accounting is the action of recording what a user is doing,
       and/or has done. TACACS+ accounting records contain all the information
       used in the authorization records and resource usage information. "
   ::= { gs2326plusAAATACACSPlusAuthAndAccounting 3 }

gs2326plusRADIUSAuthenticationServerTable OBJECT-TYPE
   SYNTAX      SEQUENCE OF Gs2326plusRADIUSAuthenticationServerEntry
   MAX-ACCESS  not-accessible
   STATUS      current
   DESCRIPTION
       " "
   ::= { gs2326plusAAA 3 }

gs2326plusRADIUSAuthenticationServerEntry OBJECT-TYPE
   SYNTAX      Gs2326plusRADIUSAuthenticationServerEntry
   MAX-ACCESS  not-accessible
   STATUS      current
   DESCRIPTION
       ""
   INDEX    { gs2326plusRADIUSAuthenticationServerIndex  }
   ::= { gs2326plusRADIUSAuthenticationServerTable 1 }

Gs2326plusRADIUSAuthenticationServerEntry ::= SEQUENCE {
   gs2326plusRADIUSAuthenticationServerIndex     Integer32,
   gs2326plusRADIUSAuthenticationServerEnable    INTEGER,
   gs2326plusRADIUSAuthenticationServerIP        DisplayString,
   gs2326plusRADIUSAuthenticationServerPort      Integer32,
   gs2326plusRADIUSAuthenticationServerSecret    DisplayString
}

gs2326plusRADIUSAuthenticationServerIndex OBJECT-TYPE
   SYNTAX      Integer32(1..5)
   MAX-ACCESS  not-accessible
   STATUS      current
   DESCRIPTION
       "RADIUS Authentication Server index
        range : 1-5."
   ::= { gs2326plusRADIUSAuthenticationServerEntry 1 }

gs2326plusRADIUSAuthenticationServerEnable OBJECT-TYPE
   SYNTAX      INTEGER { disable(0), enable(1) }
   MAX-ACCESS  read-write
   STATUS      current
   DESCRIPTION
       "Enable/Disable the RADIUS Authentication Server. the RADIUSAuthenticationServerEnable
       can be set, when IP and Secret have value "
   ::= { gs2326plusRADIUSAuthenticationServerEntry 2 }

gs2326plusRADIUSAuthenticationServerIP OBJECT-TYPE
   SYNTAX      DisplayString
   MAX-ACCESS  read-write
   STATUS      current
   DESCRIPTION
       "The IP address or hostname of the RADIUS Authentication Server.
       IP address is expressed in  dotted decimal notation. "
   ::= { gs2326plusRADIUSAuthenticationServerEntry 3 }

gs2326plusRADIUSAuthenticationServerPort OBJECT-TYPE
   SYNTAX      Integer32(0..65535)
   MAX-ACCESS  read-write
   STATUS      current
   DESCRIPTION
       "The UDP port to use on the RADIUS Authentication Server. If the port is
       set to 0 (zero), the default port (1812) is used on the RADIUS Authentication Server. "
   ::= { gs2326plusRADIUSAuthenticationServerEntry 4 }

gs2326plusRADIUSAuthenticationServerSecret OBJECT-TYPE
   SYNTAX      DisplayString
   MAX-ACCESS  read-write
   STATUS      current
   DESCRIPTION
       "The secret - up to 64 characters long - shared between the RADIUS Authentication Server and the switch. "
   ::= { gs2326plusRADIUSAuthenticationServerEntry 5 }


gs2326plusRADIUSAccountingServerTable OBJECT-TYPE
   SYNTAX      SEQUENCE OF Gs2326plusRADIUSAccountingServerEntry
   MAX-ACCESS  not-accessible
   STATUS      current
   DESCRIPTION
       " "
   ::= { gs2326plusAAA 4 }

gs2326plusRADIUSAccountingServerEntry OBJECT-TYPE
   SYNTAX      Gs2326plusRADIUSAccountingServerEntry
   MAX-ACCESS  not-accessible
   STATUS      current
   DESCRIPTION
       ""
   INDEX    { gs2326plusRADIUSAccountingServerIndex  }
   ::= { gs2326plusRADIUSAccountingServerTable 1 }

Gs2326plusRADIUSAccountingServerEntry ::= SEQUENCE {
   gs2326plusRADIUSAccountingServerIndex     Integer32,
   gs2326plusRADIUSAccountingServerEnable    INTEGER,
   gs2326plusRADIUSAccountingServerIP        DisplayString,
   gs2326plusRADIUSAccountingServerPort      Integer32,
   gs2326plusRADIUSAccountingServerSecret    DisplayString
}

gs2326plusRADIUSAccountingServerIndex OBJECT-TYPE
   SYNTAX      Integer32(1..5)
   MAX-ACCESS  not-accessible
   STATUS      current
   DESCRIPTION
       "RADIUS Accounting Server index
        range : 1-5."
   ::= { gs2326plusRADIUSAccountingServerEntry 1 }

gs2326plusRADIUSAccountingServerEnable OBJECT-TYPE
   SYNTAX      INTEGER { disable(0), enable(1) }
   MAX-ACCESS  read-write
   STATUS      current
   DESCRIPTION
       "Enable/Disable the RADIUS Accounting Server. The RADIUSAccountingServerEnable
       can be set, when IP and Secret have value. "
   ::= { gs2326plusRADIUSAccountingServerEntry 2 }

gs2326plusRADIUSAccountingServerIP OBJECT-TYPE
   SYNTAX      DisplayString
   MAX-ACCESS  read-write
   STATUS      current
   DESCRIPTION
       "The IP address or hostname of the RADIUS Accounting Server.
       IP address is expressed in  dotted decimal notation. "
   ::= { gs2326plusRADIUSAccountingServerEntry 3 }

gs2326plusRADIUSAccountingServerPort OBJECT-TYPE
   SYNTAX      Integer32(0..65535)
   MAX-ACCESS  read-write
   STATUS      current
   DESCRIPTION
       "The UDP port to use on the RADIUS Accounting Server. If the port is
       set to 0 (zero), the default port (1812) is used on the RADIUS Accounting Server. "
   ::= { gs2326plusRADIUSAccountingServerEntry 4 }

gs2326plusRADIUSAccountingServerSecret OBJECT-TYPE
   SYNTAX      DisplayString
   MAX-ACCESS  read-write
   STATUS      current
   DESCRIPTION
       "The secret - up to 64 characters long - shared between the RADIUS Accounting Server and the switch. "
   ::= { gs2326plusRADIUSAccountingServerEntry 5 }

gs2326plusTACACSPlusAuthenticationServerTable OBJECT-TYPE
   SYNTAX      SEQUENCE OF Gs2326plusTACACSPlusAuthenticationServerEntry
   MAX-ACCESS  not-accessible
   STATUS      current
   DESCRIPTION
       " "
   ::= { gs2326plusAAA 5 }

gs2326plusTACACSPlusAuthenticationServerEntry OBJECT-TYPE
   SYNTAX      Gs2326plusTACACSPlusAuthenticationServerEntry
   MAX-ACCESS  not-accessible
   STATUS      current
   DESCRIPTION
       ""
   INDEX    { gs2326plusTACACSPlusAuthenticationServerIndex  }
   ::= { gs2326plusTACACSPlusAuthenticationServerTable 1 }

Gs2326plusTACACSPlusAuthenticationServerEntry ::= SEQUENCE {
   gs2326plusTACACSPlusAuthenticationServerIndex     Integer32,
   gs2326plusTACACSPlusAuthenticationServerEnable    INTEGER,
   gs2326plusTACACSPlusAuthenticationServerIP        DisplayString,
   gs2326plusTACACSPlusAuthenticationServerPort      Integer32,
   gs2326plusTACACSPlusAuthenticationServerSecret    DisplayString
}

gs2326plusTACACSPlusAuthenticationServerIndex OBJECT-TYPE
   SYNTAX      Integer32(1..5)
   MAX-ACCESS  not-accessible
   STATUS      current
   DESCRIPTION
       "TACACSPlus Authentication Server index
        range : 1-5."
   ::= { gs2326plusTACACSPlusAuthenticationServerEntry 1 }

gs2326plusTACACSPlusAuthenticationServerEnable OBJECT-TYPE
   SYNTAX      INTEGER { disable(0), enable(1) }
   MAX-ACCESS  read-write
   STATUS      current
   DESCRIPTION
       "Enable/Disable the TACACSPlus Authentication Server. The
       TACACSPlusAuthenticationServerEnable can be set, when IP and Secret have
       value."
   ::= { gs2326plusTACACSPlusAuthenticationServerEntry 2 }

gs2326plusTACACSPlusAuthenticationServerIP OBJECT-TYPE
   SYNTAX      DisplayString
   MAX-ACCESS  read-write
   STATUS      current
   DESCRIPTION
       "The IP address or hostname of the TACACSPlus Authentication Server.
       IP address is expressed in  dotted decimal notation. "
   ::= { gs2326plusTACACSPlusAuthenticationServerEntry 3 }

gs2326plusTACACSPlusAuthenticationServerPort OBJECT-TYPE
   SYNTAX      Integer32(0..65535)
   MAX-ACCESS  read-write
   STATUS      current
   DESCRIPTION
       "The UDP port to use on the TACACSPlus Authentication Server. If the
       port is set to 0 (zero), the default port (1812) is used on the
       TACACSPlus Authentication Server. "
   ::= { gs2326plusTACACSPlusAuthenticationServerEntry 4 }

gs2326plusTACACSPlusAuthenticationServerSecret OBJECT-TYPE
   SYNTAX      DisplayString
   MAX-ACCESS  read-write
   STATUS      current
   DESCRIPTION
       "The secret - up to 64 characters long - shared between the TACACSPlus Authentication Server and the switch. "
   ::= { gs2326plusTACACSPlusAuthenticationServerEntry 5 }


gs2326plusRADIUSStatisticsTable OBJECT-TYPE
   SYNTAX      SEQUENCE OF Gs2326plusRADIUSStatisticsEntry
   MAX-ACCESS  not-accessible
   STATUS      current
   DESCRIPTION
       " "
   ::= { gs2326plusAAA 6 }

gs2326plusRADIUSStatisticsEntry OBJECT-TYPE
   SYNTAX      Gs2326plusRADIUSStatisticsEntry
   MAX-ACCESS  not-accessible
   STATUS      current
   DESCRIPTION
       ""
   INDEX    { gs2326plusRADIUSAuthStatisticsServerIndex  }
   ::= { gs2326plusRADIUSStatisticsTable 1 }

Gs2326plusRADIUSStatisticsEntry ::= SEQUENCE {
   gs2326plusRADIUSAuthStatisticsServerIndex                           Integer32,
   gs2326plusRADIUSAuthStatisticsRecPktAccessAccepts                   Counter32,
   gs2326plusRADIUSAuthStatisticsRecPktAccessRejects                   Counter32,
   gs2326plusRADIUSAuthStatisticsRecPktAccessChallenges                Counter32,
   gs2326plusRADIUSAuthStatisticsRecPktMalformedAccResponses           Counter32,
   gs2326plusRADIUSAuthStatisticsRecPktBadAuthenticators               Counter32,
   gs2326plusRADIUSAuthStatisticsRecPktUnknownTypes                    Counter32,
   gs2326plusRADIUSAuthStatisticsRecPktDropped                         Counter32,
   gs2326plusRADIUSAuthStatisticsTransmitPktAccessRequests             Counter32,
   gs2326plusRADIUSAuthStatisticsTransmitPktAccessRetransmissions      Counter32,
   gs2326plusRADIUSAuthStatisticsTransmitPktPendingRequests            Counter32,
   gs2326plusRADIUSAuthStatisticsTransmitPktTimeouts                   Counter32,
   gs2326plusRADIUSAuthIP                                              DisplayString,
   gs2326plusRADIUSAuthState                                           DisplayString,
   gs2326plusRADIUSAuthRoundTripTime                                   DisplayString,

   gs2326plusRADIUSAccountingStatisticsRecPktResponses                 Counter32,
   gs2326plusRADIUSAccountingStatisticsRecPktMalformedResponses        Counter32,
   gs2326plusRADIUSAccountingStatisticsRecPktBadAuthenticators         Counter32,
   gs2326plusRADIUSAccountingStatisticsRecPktUnknownTypes              Counter32,
   gs2326plusRADIUSAccountingStatisticsRecPktDropped                   Counter32,
   gs2326plusRADIUSAccountingStatisticsTransmitPktRequests             Counter32,
   gs2326plusRADIUSAccountingStatisticsTransmitPktRetransmissions      Counter32,
   gs2326plusRADIUSAccountingStatisticsTransmitPktPendingRequests      Counter32,
   gs2326plusRADIUSAccountingStatisticsTransmitPktTimeouts             Counter32,
   gs2326plusRADIUSAccountingIP                                        DisplayString,
   gs2326plusRADIUSAccountingState                                     DisplayString,
   gs2326plusRADIUSAccountingRoundTripTime                             DisplayString,
   gs2326plusRADIUSStatisticsClear                                     INTEGER
}

gs2326plusRADIUSAuthStatisticsServerIndex OBJECT-TYPE
   SYNTAX      Integer32(1..5)
   MAX-ACCESS  not-accessible
   STATUS      current
   DESCRIPTION
       "RADIUS Authentication Server index
        range : 1-5."
   ::= { gs2326plusRADIUSStatisticsEntry 1 }

gs2326plusRADIUSAuthStatisticsRecPktAccessAccepts OBJECT-TYPE
   SYNTAX      Counter32
   MAX-ACCESS  read-only
   STATUS      current
   DESCRIPTION
       "The number of RADIUS Access-Accept packets (valid or invalid) received from the server."
   ::= { gs2326plusRADIUSStatisticsEntry 2 }

gs2326plusRADIUSAuthStatisticsRecPktAccessRejects OBJECT-TYPE
   SYNTAX      Counter32
   MAX-ACCESS  read-only
   STATUS      current
   DESCRIPTION
       "The number of RADIUS Access-Reject packets (valid or invalid) received from the server."
   ::= { gs2326plusRADIUSStatisticsEntry 3 }

gs2326plusRADIUSAuthStatisticsRecPktAccessChallenges OBJECT-TYPE
   SYNTAX      Counter32
   MAX-ACCESS  read-only
   STATUS      current
   DESCRIPTION
       "The number of RADIUS Access-Challenge packets (valid or invalid) received from the server. "
   ::= { gs2326plusRADIUSStatisticsEntry 4 }

gs2326plusRADIUSAuthStatisticsRecPktMalformedAccResponses OBJECT-TYPE
   SYNTAX      Counter32
   MAX-ACCESS  read-only
   STATUS      current
   DESCRIPTION
       "The number of malformed RADIUS Access-Response packets received from the
        server. Malformed packets include packets with an invalid length. Bad
        authenticators or Message Authenticator attributes or unknown types are
        not included as malformed access responses. "
   ::= { gs2326plusRADIUSStatisticsEntry 5 }

gs2326plusRADIUSAuthStatisticsRecPktBadAuthenticators OBJECT-TYPE
   SYNTAX      Counter32
   MAX-ACCESS  read-only
   STATUS      current
   DESCRIPTION
       "The number of RADIUS Access-Response packets containing invalid
       authenticators or Message Authenticator attributes received from the server."
   ::= { gs2326plusRADIUSStatisticsEntry 6 }

gs2326plusRADIUSAuthStatisticsRecPktUnknownTypes OBJECT-TYPE
   SYNTAX      Counter32
   MAX-ACCESS  read-only
   STATUS      current
   DESCRIPTION
       "The number of RADIUS packets that were received with unknown types from
       the server on the authentication port and dropped."
   ::= { gs2326plusRADIUSStatisticsEntry 7 }

gs2326plusRADIUSAuthStatisticsRecPktDropped OBJECT-TYPE
   SYNTAX      Counter32
   MAX-ACCESS  read-only
   STATUS      current
   DESCRIPTION
       "The number of RADIUS packets that were received from the server on the
       authentication port and dropped for some other reason."
   ::= { gs2326plusRADIUSStatisticsEntry 8 }

gs2326plusRADIUSAuthStatisticsTransmitPktAccessRequests OBJECT-TYPE
   SYNTAX      Counter32
   MAX-ACCESS  read-only
   STATUS      current
   DESCRIPTION
       "The number of RADIUS Access-Request packets sent to the server. This
       does not include retransmissions."
   ::= { gs2326plusRADIUSStatisticsEntry 9 }

gs2326plusRADIUSAuthStatisticsTransmitPktAccessRetransmissions OBJECT-TYPE
   SYNTAX      Counter32
   MAX-ACCESS  read-only
   STATUS      current
   DESCRIPTION
       "The number of RADIUS Access-Request packets retransmitted to the RADIUS
       authentication server."
   ::= { gs2326plusRADIUSStatisticsEntry 10 }

gs2326plusRADIUSAuthStatisticsTransmitPktPendingRequests OBJECT-TYPE
   SYNTAX      Counter32
   MAX-ACCESS  read-only
   STATUS      current
   DESCRIPTION
       "The number of RADIUS Access-Request packets destined for the server that
        have not yet timed out or received a response. This variable is
        incremented when an Access-Request is sent and decremented due to
        receipt of an Access-Accept, Access-Reject, Access-Challenge, timeout,
        or retransmission. "
   ::= { gs2326plusRADIUSStatisticsEntry 11 }

gs2326plusRADIUSAuthStatisticsTransmitPktTimeouts OBJECT-TYPE
   SYNTAX      Counter32
   MAX-ACCESS  read-only
   STATUS      current
   DESCRIPTION
       "The number of authentication timeouts to the server. After a timeout,
       the client may retry to the same server, send to a different server, or
       give up. A retry to the same server is counted as a retransmit as well as
        a timeout. A send to a different server is counted as a Request as well
        as a timeout. "
   ::= { gs2326plusRADIUSStatisticsEntry 12 }

gs2326plusRADIUSAuthIP OBJECT-TYPE
   SYNTAX      DisplayString
   MAX-ACCESS  read-only
   STATUS      current
   DESCRIPTION
       "IP address and UDP port for the authentication server in question."
   ::= { gs2326plusRADIUSStatisticsEntry 13 }

gs2326plusRADIUSAuthState OBJECT-TYPE
   SYNTAX      DisplayString
   MAX-ACCESS  read-only
   STATUS      current
   DESCRIPTION
       "Shows the state of the server. It takes one of the following values:
        Disabled: The selected server is disabled.
        Not Ready: The server is enabled, but IP communication is not yet up and running.
        Ready: The server is enabled, IP communication is up and running, and the RADIUS
         module is ready to accept access attempts.
        Dead (X seconds left): Access attempts were made to this server, but it did not
        reply within the configured timeout. The server has temporarily been disabled,
        but will get re-enabled when the dead-time expires. The number of seconds left
        before this occurs is displayed in parentheses. This state is only reachable
        when more than one server is enabled. "
   ::= { gs2326plusRADIUSStatisticsEntry 14 }

gs2326plusRADIUSAuthRoundTripTime OBJECT-TYPE
   SYNTAX      DisplayString
   MAX-ACCESS  read-only
   STATUS      current
   DESCRIPTION
       "The time interval (measured in milliseconds) between the most recent
       Access-Reply/Access-Challenge and the Access-Request that matched it from
        the RADIUS authentication server. The granularity of this measurement is
         100 ms. A value of 0 ms indicates that there hasn't been round-trip
         communication with the server yet. "
   ::= { gs2326plusRADIUSStatisticsEntry 15 }

gs2326plusRADIUSAccountingStatisticsRecPktResponses OBJECT-TYPE
   SYNTAX      Counter32
   MAX-ACCESS  read-only
   STATUS      current
   DESCRIPTION
       "The number of RADIUS packets (valid or invalid) received from the server."
   ::= { gs2326plusRADIUSStatisticsEntry 16 }

gs2326plusRADIUSAccountingStatisticsRecPktMalformedResponses OBJECT-TYPE
   SYNTAX      Counter32
   MAX-ACCESS  read-only
   STATUS      current
   DESCRIPTION
       "The number of malformed RADIUS packets received from the server.
       Malformed packets include packets with an invalid length. Bad
       authenticators or unknown types are not included as malformed access
       responses. "
   ::= { gs2326plusRADIUSStatisticsEntry 17 }

gs2326plusRADIUSAccountingStatisticsRecPktBadAuthenticators OBJECT-TYPE
   SYNTAX      Counter32
   MAX-ACCESS  read-only
   STATUS      current
   DESCRIPTION
       "The number of RADIUS packets containing invalid authenticators received
       from the server."
   ::= { gs2326plusRADIUSStatisticsEntry 18 }

gs2326plusRADIUSAccountingStatisticsRecPktUnknownTypes OBJECT-TYPE
   SYNTAX      Counter32
   MAX-ACCESS  read-only
   STATUS      current
   DESCRIPTION
       "The number of RADIUS packets of unknown types that were received from
       the server on the accounting port."
   ::= { gs2326plusRADIUSStatisticsEntry 19 }

gs2326plusRADIUSAccountingStatisticsRecPktDropped OBJECT-TYPE
   SYNTAX      Counter32
   MAX-ACCESS  read-only
   STATUS      current
   DESCRIPTION
       "The number of RADIUS packets that were received from the server on the
       accounting port and dropped for some other reason."
   ::= { gs2326plusRADIUSStatisticsEntry 20 }

gs2326plusRADIUSAccountingStatisticsTransmitPktRequests OBJECT-TYPE
   SYNTAX      Counter32
   MAX-ACCESS  read-only
   STATUS      current
   DESCRIPTION
       "The number of RADIUS packets sent to the server. This does not include
       retransmissions."
   ::= { gs2326plusRADIUSStatisticsEntry 21 }

gs2326plusRADIUSAccountingStatisticsTransmitPktRetransmissions OBJECT-TYPE
   SYNTAX      Counter32
   MAX-ACCESS  read-only
   STATUS      current
   DESCRIPTION
       "The number of RADIUS packets retransmitted to the RADIUS accounting server."
   ::= { gs2326plusRADIUSStatisticsEntry 22 }

gs2326plusRADIUSAccountingStatisticsTransmitPktPendingRequests OBJECT-TYPE
   SYNTAX      Counter32
   MAX-ACCESS  read-only
   STATUS      current
   DESCRIPTION
       "The number of RADIUS packets destined for the server that have not yet
       timed out or received a response. This variable is incremented when a
       Request is sent and decremented due to receipt of a Response, timeout,
       or retransmission. "
   ::= { gs2326plusRADIUSStatisticsEntry 23 }

gs2326plusRADIUSAccountingStatisticsTransmitPktTimeouts OBJECT-TYPE
   SYNTAX      Counter32
   MAX-ACCESS  read-only
   STATUS      current
   DESCRIPTION
       "The number of accounting timeouts to the server. After a timeout, the
       client may retry to the same server, send to a different server, or give
       up. A retry to the same server is counted as a retransmit as well as a
       timeout. A send to a different server is counted as a Request as well as
       a timeout. "
   ::= { gs2326plusRADIUSStatisticsEntry 24 }

gs2326plusRADIUSAccountingIP OBJECT-TYPE
   SYNTAX      DisplayString
   MAX-ACCESS  read-only
   STATUS      current
   DESCRIPTION
       "IP address and UDP port for the accounting server in question."
   ::= { gs2326plusRADIUSStatisticsEntry 25 }

gs2326plusRADIUSAccountingState OBJECT-TYPE
   SYNTAX      DisplayString
   MAX-ACCESS  read-only
   STATUS      current
   DESCRIPTION
       " Shows the state of the server. It takes one of the following values:
        Disabled: The selected server is disabled.
        Not Ready: The server is enabled, but IP communication is not yet up and running.
        Ready: The server is enabled, IP communication is up and running, and the RADIUS
        module is ready to accept accounting attempts.
        Dead (X seconds left): Accounting attempts were made to this server, but it did
        not reply within the configured timeout. The server has temporarily been
        disabled, but will get re-enabled when the dead-time expires. The number of
        seconds left before this occurs is displayed in parentheses. This state is only
        reachable when more than one server is enabled.  "
   ::= { gs2326plusRADIUSStatisticsEntry 26 }

gs2326plusRADIUSAccountingRoundTripTime OBJECT-TYPE
   SYNTAX      DisplayString
   MAX-ACCESS  read-only
   STATUS      current
   DESCRIPTION
       "The time interval (measured in milliseconds) between the most recent
       Response and the Request that matched it from the RADIUS accounting
       server. The granularity of this measurement is 100 ms. A value of 0 ms
       indicates that there hasn't been round-trip communication with the server
       yet. "
   ::= { gs2326plusRADIUSStatisticsEntry 27 }

gs2326plusRADIUSStatisticsClear OBJECT-TYPE
   SYNTAX      INTEGER(0|1)
   MAX-ACCESS  read-write
   STATUS      current
   DESCRIPTION
       "Clears the counters for the server.
       read: always 0
       clear: set 1"
   ::= { gs2326plusRADIUSStatisticsEntry 28 }


gs2326plusNAS                                              OBJECT IDENTIFIER ::= { gs2326plusSecurity 11 }

gs2326plusNASConfiguration                                 OBJECT IDENTIFIER ::= { gs2326plusNAS 1 }

gs2326plusNASConfigMode OBJECT-TYPE
   SYNTAX      INTEGER { disable(0), enable(1) }
   MAX-ACCESS  read-write
   STATUS      current
   DESCRIPTION
       "Indicates if NAS is globally enabled or disabled on the switch.
	    If globally disabled, all ports are allowed forwarding of frames."
   ::= { gs2326plusNASConfiguration 1 }

gs2326plusNASConfigReauthEnabled OBJECT-TYPE
   SYNTAX      INTEGER { disable(0), enable(1) }
   MAX-ACCESS  read-write
   STATUS      current
   DESCRIPTION
       "If checked, successfully authenticated supplicants/clients are
	    reauthenticated after the interval specified by the Reauthentication
		Period. Reauthentication for 802.1X-enabled ports can be used to
		detect if a new device is plugged into a switch port or if a
		supplicant is no longer attached.
		For MAC-based ports, reauthentication is only useful if the RADIUS
		server configuration has changed. It does not involve communication
		between the switch and the client, and therefore doesn't imply that
		a client is still present on a port."
   ::= { gs2326plusNASConfiguration 2 }

gs2326plusNASConfigReauthPeriod OBJECT-TYPE
   SYNTAX      Integer32(1..3600)
   MAX-ACCESS  read-write
   STATUS      current
   DESCRIPTION
       "Determines the period, in seconds, after which a connected client must
	    be reauthenticated. This is only active if the Reauthentication Enabled
		checkbox is checked.
		range: 1 - 3600 seconds."
   ::= { gs2326plusNASConfiguration 3 }

gs2326plusNASConfigEAPOLTimeout OBJECT-TYPE
   SYNTAX      Integer32(1..65535)
   MAX-ACCESS  read-write
   STATUS      current
   DESCRIPTION
       "Determines the time for retransmission of Request Identity EAPOL frames.
	    This has no effect for MAC-based ports.
		range: 1 - 65535 seconds."
   ::= { gs2326plusNASConfiguration 4 }

gs2326plusNASConfigAgingPeriod OBJECT-TYPE
   SYNTAX      Integer32(10..1000000)
   MAX-ACCESS  read-write
   STATUS      current
   DESCRIPTION
       "When the NAS module uses the Port Security module to secure MAC addresses,
	    the Port Security module needs to check for activity on the MAC address
		in question at regular intervals and free resources if no activity
		is seen within a given period of time.
		Admin State supported : Single, Multi and MAC-Based Auth. 802.1X.
		range: 10 - 1000000 seconds."
   ::= { gs2326plusNASConfiguration 5 }

gs2326plusNASConfigHoldTime OBJECT-TYPE
   SYNTAX      Integer32(10..1000000)
   MAX-ACCESS  read-write
   STATUS      current
   DESCRIPTION
       "If a client is denied access - either because the RADIUS server denies
	    the client access or because the RADIUS server request times out
		- the client is put on hold in the Unauthorized state. The hold timer
		does not count during an on-going authentication. In MAC-based Auth.
		mode, the switch will ignore new frames coming from the client during
		the hold time.
		Admin State supported : Single, Multi and MAC-Based Auth. 802.1X.
		range: 10 - 1000000 seconds."
   ::= { gs2326plusNASConfiguration 6 }

gs2326plusNASConfigRADIUSAssignedQoSEnabled OBJECT-TYPE
   SYNTAX      INTEGER { disable(0), enable(1) }
   MAX-ACCESS  read-write
   STATUS      current
   DESCRIPTION
       "RADIUS-assigned QoS provides a means to centrally control the
	    traffic class to which traffic coming from a successfully authenticated
		supplicant is assigned on the switch. The RADIUS server must be configured
		to transmit special RADIUS attributes to take advantage of this feature."
   ::= { gs2326plusNASConfiguration 7 }

gs2326plusNASConfigRADIUSAssignedVLANEnabled OBJECT-TYPE
   SYNTAX      INTEGER { disable(0), enable(1) }
   MAX-ACCESS  read-write
   STATUS      current
   DESCRIPTION
       "RADIUS-assigned VLAN provides a means to centrally control the VLAN on
	    which a successfully authenticated supplicant is placed on the switch.
	    Incoming traffic will be classified to and switched on the RADIUS-assigned
		VLAN. The RADIUS server must be configured to transmit special RADIUS
		attributes to take advantage of this feature.When enable, the individual
		ports' ditto setting determine whether RADIUS-assigned VLAN is enabled
		on that port. When disable, RADIUS-server assigned VLAN is disabled on
		all ports. "
   ::= { gs2326plusNASConfiguration 8 }

gs2326plusNASConfigGuestVLANEnabled OBJECT-TYPE
   SYNTAX      INTEGER { disable(0), enable(1) }
   MAX-ACCESS  read-write
   STATUS      current
   DESCRIPTION
       "A Guest VLAN is a special VLAN - typically with limited network access -
	   on which 802.1X-unaware clients are placed after a network administrator-defined
	   timeout. The switch follows a set of rules for entering and leaving the Guest
	   VLAN as listed below.When enable, the individual ports' ditto setting determines
	   whether the port can be moved into Guest VLAN. When disable, the ability to
	   move to the Guest VLAN is disabled on all ports. "
   ::= { gs2326plusNASConfiguration 9 }

gs2326plusNASConfigGuestVLANID OBJECT-TYPE
   SYNTAX      Integer32(1..4094)
   MAX-ACCESS  read-write
   STATUS      current
   DESCRIPTION
       "This is the value that a port's Port VLAN ID is set to if a port is moved into
	   the Guest VLAN. It is only changeable if the Guest VLAN option is globally enabled.
	   range: 1 - 4094."
   ::= { gs2326plusNASConfiguration 10 }

gs2326plusNASConfigMaxReauthCount OBJECT-TYPE
   SYNTAX      Integer32(1..255)
   MAX-ACCESS  read-write
   STATUS      current
   DESCRIPTION
       "The number of times the switch transmits an EAPOL Request Identity frame without
	   response before considering entering the Guest VLAN is adjusted with this setting.
	   The value can only be changed if the Guest VLAN option is globally enabled.
	   range: 1 - 255."
   ::= { gs2326plusNASConfiguration 11 }

gs2326plusNASConfigAllowGuestVLANEAPOLSeen OBJECT-TYPE
   SYNTAX      INTEGER { disable(0), enable(1) }
   MAX-ACCESS  read-write
   STATUS      current
   DESCRIPTION
       "The switch remembers if an EAPOL frame has been received on the port for the
	   life-time of the port. Once the switch considers whether to enter the Guest VLAN,
	   it will first check if this option is enabled or disabled. If disabled, the switch
	   will only enter the Guest VLAN if an EAPOL frame has not been received on the port
	   for the life-time of the port. If enabled (checked), the switch will consider
	   entering the Guest VLAN even if an EAPOL frame has been received on the port for
	   the life-time of the port.The value can only be changed if the Guest VLAN option
	   is globally enabled."
   ::= { gs2326plusNASConfiguration 12 }

gs2326plusNASConfigMacBasedUseEAP OBJECT-TYPE
   SYNTAX      INTEGER { disable(0), enable(1) }
   MAX-ACCESS  read-write
   STATUS      current
   DESCRIPTION
       "The switch can do the RADIUS authentication on behalf of the client in the
       MAC-based Auth. port authentication mode. It can either present itself as a
       normal 802.1X client to the RADIUS Server and use EAP, supporting only the
       MD5-Challenge, or alternativly can use plain RADIUS with username / passwort
       authentification without EAP if this setting is disabled."
   ::= { gs2326plusNASConfiguration 101 }

gs2326plusNASPortConfigTable OBJECT-TYPE
   SYNTAX      SEQUENCE OF Gs2326plusNASPortConfigEntry
   MAX-ACCESS  not-accessible
   STATUS      current
   DESCRIPTION
       ""
   ::= { gs2326plusNASConfiguration 13 }

gs2326plusNASPortConfigEntry OBJECT-TYPE
   SYNTAX      Gs2326plusNASPortConfigEntry
   MAX-ACCESS  not-accessible
   STATUS      current
   DESCRIPTION
       ""
   INDEX    { gs2326plusNASPortConfigPort }
   ::= { gs2326plusNASPortConfigTable 1 }

Gs2326plusNASPortConfigEntry ::= SEQUENCE {
   gs2326plusNASPortConfigPort                       Integer32,
   gs2326plusNASPortConfigAdminState                 INTEGER,
   gs2326plusNASPortConfigRADIUSAssignedQoSEnabled	  INTEGER,
   gs2326plusNASPortConfigRADIUSAssignedVLANEnabled  INTEGER,
   gs2326plusNASPortConfigGuestVLANEnabled           INTEGER,
   gs2326plusNASPortConfigFallbackEnabled            INTEGER,
   gs2326plusNASPortConfigPortState                  DisplayString,
   gs2326plusNASPortConfigReauthenticate             INTEGER,
   gs2326plusNASPortConfigReinitialize               INTEGER
}

gs2326plusNASPortConfigPort OBJECT-TYPE
   SYNTAX      Integer32(1..255)
   MAX-ACCESS  not-accessible
   STATUS      current
   DESCRIPTION
       " port, range : 1 - port number. "
   ::= { gs2326plusNASPortConfigEntry 1 }

gs2326plusNASPortConfigAdminState OBJECT-TYPE
   SYNTAX      INTEGER{ forceAuthorized(1),
						forceUnauthorized(2),
						portBased(3),
						single(4),
						multi(5),
						macBased(6),
						macBasedSingle(7)
					  }
   MAX-ACCESS  read-write
   STATUS      current
   DESCRIPTION
       "This selection controls the port's authentication mode.
		1: Force Authorized,
		2: Force Unauthorized,
		3: Port-based 802.1X,
		4: Single 802.1X,
		5: Multi 802.1X,
		6: MAC-based Auth,
		7: MAC-based Single Auth."
   ::= { gs2326plusNASPortConfigEntry 2 }

gs2326plusNASPortConfigRADIUSAssignedQoSEnabled OBJECT-TYPE
   SYNTAX      INTEGER { disable(0), enable(1) }
   MAX-ACCESS  read-write
   STATUS      current
   DESCRIPTION
       "When RADIUS-Assigned QoS is both globally enabled and enabled (checked)
	    on a given port, the switch reacts to QoS Class information carried in
		the RADIUS Access-Accept packet transmitted by the RADIUS server when a
		supplicant is successfully authenticated. If present and valid, traffic
		received on the supplicant's port will be classified to the given QoS Class.
		Admin State supported : Port-based and Single 802.1X and MAC-based Single Auth."
   ::= { gs2326plusNASPortConfigEntry 3 }

gs2326plusNASPortConfigRADIUSAssignedVLANEnabled OBJECT-TYPE
   SYNTAX      INTEGER { disable(0), enable(1) }
   MAX-ACCESS  read-write
   STATUS      current
   DESCRIPTION
       "When RADIUS-Assigned VLAN is both globally enabled and enabled (checked)
	   for a given port, the switch reacts to VLAN ID information carried in the
	   RADIUS Access-Accept packet transmitted by the RADIUS server when a supplicant
	   is successfully authenticated. If present and valid, the port's Port VLAN ID
	   will be changed to this VLAN ID, the port will be set to be a member of that
	   VLAN ID, and the port will be forced into VLAN unaware mode. Once assigned,
	   all traffic arriving on the port will be classified and switched on the
	   RADIUS-assigned VLAN ID.
	   Admin State supported : Port-based and Single 802.1X and MAC-based Single Auth."
   ::= { gs2326plusNASPortConfigEntry 4 }

gs2326plusNASPortConfigGuestVLANEnabled OBJECT-TYPE
   SYNTAX      INTEGER { disable(0), enable(1) }
   MAX-ACCESS  read-write
   STATUS      current
   DESCRIPTION
       "When Guest VLAN is both globally enabled and enabled (checked) for a given port,
	   the switch considers moving the port into the Guest VLAN according to the rules
	   outlined below.
	   Admin State supported : Port-based , Single and Multi 802.1X."
   ::= { gs2326plusNASPortConfigEntry 5 }

gs2326plusNASPortConfigPortState OBJECT-TYPE
   SYNTAX      DisplayString
   MAX-ACCESS  read-only
   STATUS      current
   DESCRIPTION
       "Globally Disabled: NAS is globally disabled.
		Link Down: NAS is globally enabled, but there is no link on the port.
		Authorized: The port is in Force Authorized or a single-supplicant mode
		and the supplicant is authorized.
		Unauthorized: The port is in Force Unauthorized or a single-supplicant
		mode and the supplicant is not successfully authorized by the RADIUS server.
		X Auth/Y Unauth: The port is in a multi-supplicant mode. Currently X clients
		are authorized and Y are unauthorized."
   ::= { gs2326plusNASPortConfigEntry 6 }

gs2326plusNASPortConfigReauthenticate OBJECT-TYPE
   SYNTAX      INTEGER { doNothing(0), do(1) }
   MAX-ACCESS  read-write
   STATUS      current
   DESCRIPTION
       "Schedules a reauthentication whenever the quiet-period of the port runs out
	   (EAPOL-based authentication). For MAC-based authentication, reauthentication
	   will be attempted immediately.The button only has effect for successfully
	   authenticated clients on the port and will not cause the clients to get
	   temporarily unauthorized."
   ::= { gs2326plusNASPortConfigEntry 7 }

gs2326plusNASPortConfigReinitialize OBJECT-TYPE
   SYNTAX      INTEGER { doNothing(0), do(1) }
   MAX-ACCESS  read-write
   STATUS      current
   DESCRIPTION
       "Forces a reinitialization of the clients on the port and thereby a reauthentication
	   immediately. The clients will transfer to the unauthorized state while the
	   reauthentication is in progress."
   ::= { gs2326plusNASPortConfigEntry 8 }

gs2326plusNASPortConfigFallbackEnabled OBJECT-TYPE
   SYNTAX      INTEGER { disable(0), enable(1) }
   MAX-ACCESS  read-write
   STATUS      current
   DESCRIPTION
       "When Fallback is enabled, the switch will take over the supplicants role
       after max reauthentication count is reached and tries to authenticate the
       client on its behalf as described for MAC-based Auth.
       Admin State supported : Single and Multi 802.1X."
   ::= { gs2326plusNASPortConfigEntry 101 }

gs2326plusNASSwitchStatusTable OBJECT-TYPE
   SYNTAX      SEQUENCE OF Gs2326plusNASSwitchStatusEntry
   MAX-ACCESS  not-accessible
   STATUS      current
   DESCRIPTION
       ""
   ::= { gs2326plusNAS 2 }

gs2326plusNASSwitchStatusEntry OBJECT-TYPE
   SYNTAX      Gs2326plusNASSwitchStatusEntry
   MAX-ACCESS  not-accessible
   STATUS      current
   DESCRIPTION
       ""
   INDEX    { gs2326plusNASPortConfigPort }
   ::= { gs2326plusNASSwitchStatusTable 1 }

Gs2326plusNASSwitchStatusEntry ::= SEQUENCE {
   gs2326plusNASSwitchStatusAdminState 	DisplayString,
   gs2326plusNASSwitchStatusPortState		DisplayString,
   gs2326plusNASSwitchStatusLastSource		DisplayString,
   gs2326plusNASSwitchStatusLastID			DisplayString,
   gs2326plusNASSwitchStatusQoSClass		DisplayString,
   gs2326plusNASSwitchStatusPortVlanID		DisplayString
}

gs2326plusNASSwitchStatusAdminState OBJECT-TYPE
   SYNTAX      DisplayString
   MAX-ACCESS  read-only
   STATUS      current
   DESCRIPTION
       "The port's current administrative state. Refer to NAS Admin State for a description of possible values."
   ::= { gs2326plusNASSwitchStatusEntry 2 }

gs2326plusNASSwitchStatusPortState OBJECT-TYPE
   SYNTAX      DisplayString
   MAX-ACCESS  read-only
   STATUS      current
   DESCRIPTION
       "The current state of the port. Refer to NAS Port State for a description of the individual states."
   ::= { gs2326plusNASSwitchStatusEntry 3 }

gs2326plusNASSwitchStatusLastSource OBJECT-TYPE
   SYNTAX      DisplayString
   MAX-ACCESS  read-only
   STATUS      current
   DESCRIPTION
       "The source MAC address carried in the most recently received EAPOL frame for EAPOL-based authentication,
	   and the most recently received frame from a new client for MAC-based authentication."
   ::= { gs2326plusNASSwitchStatusEntry 4 }

gs2326plusNASSwitchStatusLastID OBJECT-TYPE
   SYNTAX      DisplayString
   MAX-ACCESS  read-only
   STATUS      current
   DESCRIPTION
       "The user name (supplicant identity) carried in the most recently received Response Identity EAPOL frame
	   for EAPOL-based authentication, and the source MAC address from the most recently received frame from a
	   new client for MAC-based authentication."
   ::= { gs2326plusNASSwitchStatusEntry 5 }

gs2326plusNASSwitchStatusQoSClass OBJECT-TYPE
   SYNTAX      DisplayString
   MAX-ACCESS  read-only
   STATUS      current
   DESCRIPTION
       "QoS Class assigned to the port by the RADIUS server if enabled."
   ::= { gs2326plusNASSwitchStatusEntry 6 }

gs2326plusNASSwitchStatusPortVlanID OBJECT-TYPE
   SYNTAX      DisplayString
   MAX-ACCESS  read-only
   STATUS      current
   DESCRIPTION
       "The VLAN ID that NAS has put the port in. The field is blank, if the Port VLAN ID is not overridden by NAS."
   ::= { gs2326plusNASSwitchStatusEntry 7 }

gs2326plusNASPortStatus                                 OBJECT IDENTIFIER ::= { gs2326plusNAS 3 }

gs2326plusNASPortStatusCountersTable OBJECT-TYPE
   SYNTAX      SEQUENCE OF Gs2326plusNASPortStatusCountersEntry
   MAX-ACCESS  not-accessible
   STATUS      current
   DESCRIPTION
       ""
   ::= { gs2326plusNASPortStatus 1 }

gs2326plusNASPortStatusCountersEntry OBJECT-TYPE
   SYNTAX      Gs2326plusNASPortStatusCountersEntry
   MAX-ACCESS  not-accessible
   STATUS      current
   DESCRIPTION
       ""
   INDEX    { gs2326plusNASPortConfigPort }
   ::= { gs2326plusNASPortStatusCountersTable 1 }

Gs2326plusNASPortStatusCountersEntry ::= SEQUENCE {
   gs2326plusNASRxCountersEAPOLTotal  	                  Counter32,
   gs2326plusNASRxCountersEAPOLResponseID	              Counter32,
   gs2326plusNASRxCountersEAPOLResponses	              Counter32,
   gs2326plusNASRxCountersEAPOLStart	                  Counter32,
   gs2326plusNASRxCountersEAPOLLogoff                    Counter32,
   gs2326plusNASRxCountersEAPOLInvalidType               Counter32,
   gs2326plusNASRxCountersEAPOLInvalidLength             Counter32,
   gs2326plusNASTxCountersEAPOLTotal                     Counter32,
   gs2326plusNASTxCountersEAPOLRequestID                 Counter32,
   gs2326plusNASTxCountersEAPOLRequests                  Counter32,
   gs2326plusNASRxBackendServerCountersAccessChallenges  Counter32,
   gs2326plusNASRxBackendServerCountersOtherRequests     Counter32,
   gs2326plusNASRxBackendServerCountersAuthSuccesses     Counter32,
   gs2326plusNASRxBackendServerCountersAuthFailures      Counter32,
   gs2326plusNASTxBackendServerCountersResponses         Counter32,
   gs2326plusNASLastSupplicantInfoMACAddress             DisplayString,
   gs2326plusNASLastSupplicantInfoVlanID                 Integer32,
   gs2326plusNASLastSupplicantInfoVersion                Integer32,
   gs2326plusNASLastSupplicantInfoIdentity               DisplayString,
   gs2326plusNASCountersDoClear                          INTEGER
}

gs2326plusNASRxCountersEAPOLTotal OBJECT-TYPE
   SYNTAX      Counter32
   MAX-ACCESS  read-only
   STATUS      current
   DESCRIPTION
       "The number of valid EAPOL frames of any type that have been received by the switch."
   ::= { gs2326plusNASPortStatusCountersEntry 2 }

gs2326plusNASRxCountersEAPOLResponseID OBJECT-TYPE
   SYNTAX      Counter32
   MAX-ACCESS  read-only
   STATUS      current
   DESCRIPTION
       "The number of valid EAPOL Response Identity frames that have been received by the switch."
   ::= { gs2326plusNASPortStatusCountersEntry 3 }

gs2326plusNASRxCountersEAPOLResponses OBJECT-TYPE
   SYNTAX      Counter32
   MAX-ACCESS  read-only
   STATUS      current
   DESCRIPTION
       "The number of valid EAPOL response frames (other than Response Identity frames)
	   that have been received by the switch."
   ::= { gs2326plusNASPortStatusCountersEntry 4 }

gs2326plusNASRxCountersEAPOLStart OBJECT-TYPE
   SYNTAX      Counter32
   MAX-ACCESS  read-only
   STATUS      current
   DESCRIPTION
       "The number of EAPOL Start frames that have been received by the switch."
   ::= { gs2326plusNASPortStatusCountersEntry 5 }

gs2326plusNASRxCountersEAPOLLogoff OBJECT-TYPE
   SYNTAX      Counter32
   MAX-ACCESS  read-only
   STATUS      current
   DESCRIPTION
       "The number of valid EAPOL Logoff frames that have been received by the switch."
   ::= { gs2326plusNASPortStatusCountersEntry 6 }

gs2326plusNASRxCountersEAPOLInvalidType OBJECT-TYPE
   SYNTAX      Counter32
   MAX-ACCESS  read-only
   STATUS      current
   DESCRIPTION
       "The number of EAPOL frames that have been received by the switch in which
	   the frame type is not recognized."
   ::= { gs2326plusNASPortStatusCountersEntry 7 }

gs2326plusNASRxCountersEAPOLInvalidLength OBJECT-TYPE
   SYNTAX      Counter32
   MAX-ACCESS  read-only
   STATUS      current
   DESCRIPTION
       "The number of EAPOL frames that have been received by the switch in which the
	   Packet Body Length field is invalid."
   ::= { gs2326plusNASPortStatusCountersEntry 8 }

gs2326plusNASTxCountersEAPOLTotal OBJECT-TYPE
   SYNTAX      Counter32
   MAX-ACCESS  read-only
   STATUS      current
   DESCRIPTION
       "The number of EAPOL frames of any type that have been transmitted by the switch."
   ::= { gs2326plusNASPortStatusCountersEntry 9 }

gs2326plusNASTxCountersEAPOLRequestID OBJECT-TYPE
   SYNTAX      Counter32
   MAX-ACCESS  read-only
   STATUS      current
   DESCRIPTION
       "The number of EAPOL Request Identity frames that have been transmitted by the switch."
   ::= { gs2326plusNASPortStatusCountersEntry 10 }

gs2326plusNASTxCountersEAPOLRequests OBJECT-TYPE
   SYNTAX      Counter32
   MAX-ACCESS  read-only
   STATUS      current
   DESCRIPTION
       "The number of valid EAPOL Request frames (other than Request Identity frames)
	   that have been transmitted by the switch."
   ::= { gs2326plusNASPortStatusCountersEntry 11 }

gs2326plusNASRxBackendServerCountersAccessChallenges OBJECT-TYPE
   SYNTAX      Counter32
   MAX-ACCESS  read-only
   STATUS      current
   DESCRIPTION
       "802.1X-based: Counts the number of times that the switch receives the first request
	   from the backend server following the first response from the supplicant.
	   MAC-based: Counts all Access Challenges received from the backend server for this
	   port or client."
   ::= { gs2326plusNASPortStatusCountersEntry 12 }

gs2326plusNASRxBackendServerCountersOtherRequests OBJECT-TYPE
   SYNTAX      Counter32
   MAX-ACCESS  read-only
   STATUS      current
   DESCRIPTION
       "802.1X-based: Counts the number of times that the switch sends an EAP Request
	   packet following the first to the supplicant.
	   MAC-based: Not applicable."
   ::= { gs2326plusNASPortStatusCountersEntry 13 }

gs2326plusNASRxBackendServerCountersAuthSuccesses OBJECT-TYPE
   SYNTAX      Counter32
   MAX-ACCESS  read-only
   STATUS      current
   DESCRIPTION
       "Counts the number of times that the switch receives a success indication.
	   Indicates that the supplicant/client has successfully authenticated to the
	   backend server."
   ::= { gs2326plusNASPortStatusCountersEntry 14 }

gs2326plusNASRxBackendServerCountersAuthFailures OBJECT-TYPE
   SYNTAX      Counter32
   MAX-ACCESS  read-only
   STATUS      current
   DESCRIPTION
       "Counts the number of times that the switch receives a failure message.
	   This indicates that the supplicant/client has not authenticated to the
	   backend server. "
   ::= { gs2326plusNASPortStatusCountersEntry 15 }

gs2326plusNASTxBackendServerCountersResponses OBJECT-TYPE
   SYNTAX      Counter32
   MAX-ACCESS  read-only
   STATUS      current
   DESCRIPTION
       "802.1X-based: Counts the number of times that the switch attempts to
	   send a supplicant's first response packet to the backend server. Indicates
	   the switch attempted communication with the backend server. Possible
	   retransmissions are not counted.
	   MAC-based: Counts all the backend server packets sent from the switch
	   towards the backend server for a given port or client. Possible
	   retransmissions are not counted."
   ::= { gs2326plusNASPortStatusCountersEntry 16 }

gs2326plusNASLastSupplicantInfoMACAddress OBJECT-TYPE
   SYNTAX      DisplayString
   MAX-ACCESS  read-only
   STATUS      current
   DESCRIPTION
       "The MAC address of the last supplicant/client."
   ::= { gs2326plusNASPortStatusCountersEntry 17 }

gs2326plusNASLastSupplicantInfoVlanID OBJECT-TYPE
   SYNTAX      Integer32
   MAX-ACCESS  read-only
   STATUS      current
   DESCRIPTION
       "The VLAN ID on which the last frame from the last supplicant/client was received."
   ::= { gs2326plusNASPortStatusCountersEntry 18 }

gs2326plusNASLastSupplicantInfoVersion OBJECT-TYPE
   SYNTAX      Integer32
   MAX-ACCESS  read-only
   STATUS      current
   DESCRIPTION
       "802.1X-based: The protocol version number carried in the most recently
	   received EAPOL frame.
	   MAC-based: Not applicable."
   ::= { gs2326plusNASPortStatusCountersEntry 19 }

gs2326plusNASLastSupplicantInfoIdentity OBJECT-TYPE
   SYNTAX      DisplayString
   MAX-ACCESS  read-only
   STATUS      current
   DESCRIPTION
       "802.1X-based: The user name (supplicant identity) carried in the most recently received
	   Response Identity EAPOL frame.
	   MAC-based: Not applicable."
   ::= { gs2326plusNASPortStatusCountersEntry 20 }

gs2326plusNASCountersDoClear OBJECT-TYPE
   SYNTAX      INTEGER { doNothing(0), do(1) }
   MAX-ACCESS  read-write
   STATUS      current
   DESCRIPTION
       "Clear the counters for the selected port."
   ::= { gs2326plusNASPortStatusCountersEntry 21 }

gs2326plusNASPortStatusClientsTable OBJECT-TYPE
   SYNTAX      SEQUENCE OF Gs2326plusNASPortStatusClientsEntry
   MAX-ACCESS  not-accessible
   STATUS      current
   DESCRIPTION
       ""
   ::= { gs2326plusNASPortStatus 2 }

gs2326plusNASPortStatusClientsEntry OBJECT-TYPE
   SYNTAX      Gs2326plusNASPortStatusClientsEntry
   MAX-ACCESS  not-accessible
   STATUS      current
   DESCRIPTION
       ""
   INDEX    { gs2326plusNASPortConfigPort,
		gs2326plusNASClientsIndex}
   ::= { gs2326plusNASPortStatusClientsTable 1 }

Gs2326plusNASPortStatusClientsEntry ::= SEQUENCE {
   gs2326plusNASClientsIndex  	                  		    Integer32,
   gs2326plusNASClientsIdentity							DisplayString,
   gs2326plusNASClientsMACAddress  	                  	DisplayString,
   gs2326plusNASClientsVlanID		              			Integer32,
   gs2326plusNASClientsState	              				DisplayString,
   gs2326plusNASClientsLastAuth	                  		DisplayString,
   gs2326plusNASRxClientsEAPOLTotal  	                  	Counter32,
   gs2326plusNASRxClientsEAPOLResponseID	              	Counter32,
   gs2326plusNASRxClientsEAPOLResponses	              	Counter32,
   gs2326plusNASRxClientsEAPOLStart	                  	Counter32,
   gs2326plusNASRxClientsEAPOLLogoff                    	Counter32,
   gs2326plusNASRxClientsEAPOLInvalidType               	Counter32,
   gs2326plusNASRxClientsEAPOLInvalidLength             	Counter32,
   gs2326plusNASTxClientsEAPOLTotal                     	Counter32,
   gs2326plusNASTxClientsEAPOLRequestID                 	Counter32,
   gs2326plusNASTxClientsEAPOLRequests                  	Counter32,
   gs2326plusNASRxBackendServerClientsAccessChallenges  	Counter32,
   gs2326plusNASRxBackendServerClientsOtherRequests     	Counter32,
   gs2326plusNASRxBackendServerClientsAuthSuccesses     	Counter32,
   gs2326plusNASRxBackendServerClientsAuthFailures      	Counter32,
   gs2326plusNASTxBackendServerClientsResponses         	Counter32
}

gs2326plusNASClientsIndex OBJECT-TYPE
   SYNTAX      Integer32(1..255)
   MAX-ACCESS  not-accessible
   STATUS      current
   DESCRIPTION
       "Entry of client table in the port."
   ::= { gs2326plusNASPortStatusClientsEntry 1 }

gs2326plusNASClientsIdentity OBJECT-TYPE
   SYNTAX      DisplayString
   MAX-ACCESS  read-only
   STATUS      current
   DESCRIPTION
       "Shows the identity of the supplicant, as received in the Response Identity
	   EAPOL frame.This isn't available for MAC-based Auth."
   ::= { gs2326plusNASPortStatusClientsEntry 2 }

gs2326plusNASClientsMACAddress OBJECT-TYPE
   SYNTAX      DisplayString
   MAX-ACCESS  read-only
   STATUS      current
   DESCRIPTION
       "Multi 802.1X, this column holds the MAC address of the attached supplicant.
	   MAC-based Auth., this column holds the MAC address of the attached client."
   ::= { gs2326plusNASPortStatusClientsEntry 3 }

gs2326plusNASClientsVlanID OBJECT-TYPE
   SYNTAX      Integer32(1..4095)
   MAX-ACCESS  read-only
   STATUS      current
   DESCRIPTION
       "This column holds the VLAN ID that the corresponding client is currently
	   secured through the Port Security module."
   ::= { gs2326plusNASPortStatusClientsEntry 4 }

gs2326plusNASClientsState OBJECT-TYPE
   SYNTAX      DisplayString
   MAX-ACCESS  read-only
   STATUS      current
   DESCRIPTION
       "The client can either be authenticated or unauthenticated. In the authenticated
	   state, it is allowed to forward frames on the port, and in the unauthenticated
	   state, it is blocked."
   ::= { gs2326plusNASPortStatusClientsEntry 5 }

gs2326plusNASClientsLastAuth OBJECT-TYPE
   SYNTAX      DisplayString
   MAX-ACCESS  read-only
   STATUS      current
   DESCRIPTION
       "Shows the date and time of the last authentication of the client."
   ::= { gs2326plusNASPortStatusClientsEntry 6 }

gs2326plusNASRxClientsEAPOLTotal OBJECT-TYPE
   SYNTAX      Counter32
   MAX-ACCESS  read-only
   STATUS      current
   DESCRIPTION
       "The number of valid EAPOL frames of any type that have been received by the switch."
   ::= { gs2326plusNASPortStatusClientsEntry 7 }

gs2326plusNASRxClientsEAPOLResponseID OBJECT-TYPE
   SYNTAX      Counter32
   MAX-ACCESS  read-only
   STATUS      current
   DESCRIPTION
       "The number of valid EAPOL Response Identity frames that have been received by the switch."
   ::= { gs2326plusNASPortStatusClientsEntry 8 }

gs2326plusNASRxClientsEAPOLResponses OBJECT-TYPE
   SYNTAX      Counter32
   MAX-ACCESS  read-only
   STATUS      current
   DESCRIPTION
       "The number of valid EAPOL response frames (other than Response Identity frames)
	   that have been received by the switch."
   ::= { gs2326plusNASPortStatusClientsEntry 9 }

gs2326plusNASRxClientsEAPOLStart OBJECT-TYPE
   SYNTAX      Counter32
   MAX-ACCESS  read-only
   STATUS      current
   DESCRIPTION
       "The number of EAPOL Start frames that have been received by the switch."
   ::= { gs2326plusNASPortStatusClientsEntry 10 }

gs2326plusNASRxClientsEAPOLLogoff OBJECT-TYPE
   SYNTAX      Counter32
   MAX-ACCESS  read-only
   STATUS      current
   DESCRIPTION
       "The number of valid EAPOL Logoff frames that have been received by the switch."
   ::= { gs2326plusNASPortStatusClientsEntry 11 }

gs2326plusNASRxClientsEAPOLInvalidType OBJECT-TYPE
   SYNTAX      Counter32
   MAX-ACCESS  read-only
   STATUS      current
   DESCRIPTION
       "The number of EAPOL frames that have been received by the switch in which
	   the frame type is not recognized."
   ::= { gs2326plusNASPortStatusClientsEntry 12 }

gs2326plusNASRxClientsEAPOLInvalidLength OBJECT-TYPE
   SYNTAX      Counter32
   MAX-ACCESS  read-only
   STATUS      current
   DESCRIPTION
       "The number of EAPOL frames that have been received by the switch in which the
	   Packet Body Length field is invalid."
   ::= { gs2326plusNASPortStatusClientsEntry 13 }

gs2326plusNASTxClientsEAPOLTotal OBJECT-TYPE
   SYNTAX      Counter32
   MAX-ACCESS  read-only
   STATUS      current
   DESCRIPTION
       "The number of EAPOL frames of any type that have been transmitted by the switch."
   ::= { gs2326plusNASPortStatusClientsEntry 14 }

gs2326plusNASTxClientsEAPOLRequestID OBJECT-TYPE
   SYNTAX      Counter32
   MAX-ACCESS  read-only
   STATUS      current
   DESCRIPTION
       "The number of EAPOL Request Identity frames that have been transmitted by the switch."
   ::= { gs2326plusNASPortStatusClientsEntry 15 }

gs2326plusNASTxClientsEAPOLRequests OBJECT-TYPE
   SYNTAX      Counter32
   MAX-ACCESS  read-only
   STATUS      current
   DESCRIPTION
       "The number of valid EAPOL Request frames (other than Request Identity frames)
	   that have been transmitted by the switch."
   ::= { gs2326plusNASPortStatusClientsEntry 16 }

gs2326plusNASRxBackendServerClientsAccessChallenges OBJECT-TYPE
   SYNTAX      Counter32
   MAX-ACCESS  read-only
   STATUS      current
   DESCRIPTION
       "802.1X-based: Counts the number of times that the switch receives the first request
	   from the backend server following the first response from the supplicant.
	   MAC-based: Counts all Access Challenges received from the backend server for this
	   port or client."
   ::= { gs2326plusNASPortStatusClientsEntry 17 }

gs2326plusNASRxBackendServerClientsOtherRequests OBJECT-TYPE
   SYNTAX      Counter32
   MAX-ACCESS  read-only
   STATUS      current
   DESCRIPTION
       "802.1X-based: Counts the number of times that the switch sends an EAP Request
	   packet following the first to the supplicant.
	   MAC-based: Not applicable."
   ::= { gs2326plusNASPortStatusClientsEntry 18 }

gs2326plusNASRxBackendServerClientsAuthSuccesses OBJECT-TYPE
   SYNTAX      Counter32
   MAX-ACCESS  read-only
   STATUS      current
   DESCRIPTION
       "Counts the number of times that the switch receives a success indication.
	   Indicates that the supplicant/client has successfully authenticated to the
	   backend server."
   ::= { gs2326plusNASPortStatusClientsEntry 19 }

gs2326plusNASRxBackendServerClientsAuthFailures OBJECT-TYPE
   SYNTAX      Counter32
   MAX-ACCESS  read-only
   STATUS      current
   DESCRIPTION
       "Counts the number of times that the switch receives a failure message.
	   This indicates that the supplicant/client has not authenticated to the
	   backend server. "
   ::= { gs2326plusNASPortStatusClientsEntry 20 }

gs2326plusNASTxBackendServerClientsResponses OBJECT-TYPE
   SYNTAX      Counter32
   MAX-ACCESS  read-only
   STATUS      current
   DESCRIPTION
       "802.1X-based: Counts the number of times that the switch attempts to
	   send a supplicant's first response packet to the backend server. Indicates
	   the switch attempted communication with the backend server. Possible
	   retransmissions are not counted.
	   MAC-based: Counts all the backend server packets sent from the switch
	   towards the backend server for a given port or client. Possible
	   retransmissions are not counted."
   ::= { gs2326plusNASPortStatusClientsEntry 21 }


gs2326plusMaintenance                                           OBJECT IDENTIFIER ::= { lancomGS2326plus  4 }

gs2326plusRestartDevice OBJECT-TYPE
   SYNTAX      INTEGER { disable(0), enable(1) }
   MAX-ACCESS  read-write
   STATUS      current
   DESCRIPTION
       "default: 0
        0:none
        1:yes"
   ::= { gs2326plusMaintenance 1 }

gs2326plusColdRestartDevice OBJECT-TYPE
   SYNTAX      INTEGER { disable(0), enable(1) }
   MAX-ACCESS  read-write
   STATUS      current
   DESCRIPTION
       "default: 0
        0:none
        1:yes"
   ::= { gs2326plusMaintenance 1500 }

gs2326plusFirmware                                         OBJECT IDENTIFIER ::= { gs2326plusMaintenance 2 }

gs2326plusFirmwareIpAddress OBJECT-TYPE
   SYNTAX       IpAddress
   MAX-ACCESS   read-write
   STATUS       current
   DESCRIPTION
        "Get/Set the firmware tftp server."
   ::= { gs2326plusFirmware 1 }

gs2326plusFirmwareFileName OBJECT-TYPE
   SYNTAX       DisplayString
   MAX-ACCESS   read-write
   STATUS       current
   DESCRIPTION
        "Get/Set the path and filename for firmware upgrading."
   ::= { gs2326plusFirmware 2 }

gs2326plusDoFirmwareUpgrade OBJECT-TYPE
   SYNTAX       INTEGER { doNothing(0), do(1) }
   MAX-ACCESS   read-write
   STATUS       current
   DESCRIPTION
        "Do firmware upgrade. Get this OID always return zero.
              1 - do firmware upgrade.
              0 - do nothing."
   ::= { gs2326plusFirmware 3 }

gs2326plusSaveOrRestore                                         OBJECT IDENTIFIER ::= { gs2326plusMaintenance 3 }

gs2326plusFactoryDefaults OBJECT-TYPE
   SYNTAX      INTEGER { none(0), yes(1) }
   MAX-ACCESS  read-write
   STATUS      current
   DESCRIPTION
       "default: 0
        0:none
        1:yes"
   ::= { gs2326plusSaveOrRestore 1 }

gs2326plusSaveStart OBJECT-TYPE
   SYNTAX      INTEGER { none(0), yes(1) }
   MAX-ACCESS  read-write
   STATUS      current
   DESCRIPTION
       "default: 0
        0:none
        1:yes"
   ::= { gs2326plusSaveOrRestore 2 }

gs2326plusSaveUser OBJECT-TYPE
   SYNTAX      INTEGER { none(0), yes(1) }
   MAX-ACCESS  read-write
   STATUS      current
   DESCRIPTION
       "default: 0
        0:none
        1:yes"
   ::= { gs2326plusSaveOrRestore 3 }

gs2326plusRestoreUser OBJECT-TYPE
   SYNTAX      INTEGER { none(0), yes(1) }
   MAX-ACCESS  read-write
   STATUS      current
   DESCRIPTION
       "default: 0
        0:none
        1:yes"
   ::= { gs2326plusSaveOrRestore 4 }


gs2326plusExportOrImport                                        OBJECT IDENTIFIER ::= { gs2326plusMaintenance 4 }

gs2326plusExportIpAddress OBJECT-TYPE
   SYNTAX       IpAddress
   MAX-ACCESS   read-write
   STATUS       current
   DESCRIPTION
        "Get/Set the export tftp server."
   ::= { gs2326plusExportOrImport 1 }

gs2326plusExportConfigName OBJECT-TYPE
   SYNTAX       DisplayString
   MAX-ACCESS   read-write
   STATUS       current
   DESCRIPTION
       "Get/Set the export file path and name."
   ::= { gs2326plusExportOrImport 2 }

gs2326plusDoExportConfig OBJECT-TYPE
   SYNTAX       INTEGER{ doNothing(0), do(1) }
   MAX-ACCESS   read-write
   STATUS       current
   DESCRIPTION
        "Do export-config.
         Get this OID always return zero.
         1 - export."
   ::= { gs2326plusExportOrImport 3 }

gs2326plusImportIpAddress OBJECT-TYPE
   SYNTAX       IpAddress
   MAX-ACCESS   read-write
   STATUS       current
   DESCRIPTION
        "Get/Set the import tftp server."
   ::= { gs2326plusExportOrImport 4 }

gs2326plusImportConfigName OBJECT-TYPE
   SYNTAX      DisplayString
   MAX-ACCESS  read-write
   STATUS      current
   DESCRIPTION
       "Get/Set the import file path and name."
   ::= { gs2326plusExportOrImport 5 }

gs2326plusDoImportConfig OBJECT-TYPE
   SYNTAX       INTEGER{ doNothing(0), do(1) }
   MAX-ACCESS   read-write
   STATUS       current
   DESCRIPTION
        "Do export-config.
         Get this OID always return zero.
         1 - import."
   ::= { gs2326plusExportOrImport 6 }

gs2326plusDiagnostics                                           OBJECT IDENTIFIER ::= { gs2326plusMaintenance 5 }

gs2326plusPingIpAddress OBJECT-TYPE
   SYNTAX      IpAddress
   MAX-ACCESS  read-write
   STATUS      current
   DESCRIPTION
       " The destination IP Address. "
   ::= { gs2326plusDiagnostics 1 }

gs2326plusPingSize OBJECT-TYPE
   SYNTAX      Integer32(60..1400)
   MAX-ACCESS  read-write
   STATUS      current
   DESCRIPTION
       " Size of ICMP echo packet.
         range : 60-1400, default : 64. "
   ::= { gs2326plusDiagnostics 2 }

gs2326plusDoPingConfig OBJECT-TYPE
   SYNTAX       INTEGER{ doNothing(0), do(1) }
   MAX-ACCESS  read-write
   STATUS      current
   DESCRIPTION
       "Do ping-config.
         Get this OID always return zero.
         1 - ping. Uses the ICMP protocol's mandatory ECHO_REQUEST datagram
         to elicit an ICMP ECHO_RESPONSE from a host or gateway. "
   ::= { gs2326plusDiagnostics 3 }

gs2326plusPingResult OBJECT-TYPE
   SYNTAX      DisplayString
   MAX-ACCESS  read-only
   STATUS      current
   DESCRIPTION
       " Show ping result. "
   ::= { gs2326plusDiagnostics 4 }

gs2326plusPing6IpAddress OBJECT-TYPE
   SYNTAX      DisplayString
   MAX-ACCESS  read-write
   STATUS      current
   DESCRIPTION
       " The destination IPv6 Address. "
   ::= { gs2326plusDiagnostics 5 }

gs2326plusPing6Size OBJECT-TYPE
   SYNTAX      Integer32(60..1400)
   MAX-ACCESS  read-write
   STATUS      current
   DESCRIPTION
       " Size of ICMP echo packet.
         range : 60-1400. "
   ::= { gs2326plusDiagnostics 6 }

gs2326plusDoPing6Config OBJECT-TYPE
   SYNTAX       INTEGER{ doNothing(0), do(1) }
   MAX-ACCESS  read-write
   STATUS      current
   DESCRIPTION
       "Do ping-config.
         Get this OID always return zero.
         1 - ping. Uses the ICMP protocol's mandatory ECHO_REQUEST datagram
         to elicit an ICMP ECHO_RESPONSE from a host or gateway. "
   ::= { gs2326plusDiagnostics 7 }

gs2326plusPing6Result OBJECT-TYPE
   SYNTAX      DisplayString
   MAX-ACCESS  read-only
   STATUS      current
   DESCRIPTION
       " Show ping result. "
   ::= { gs2326plusDiagnostics 8 }


gs2326plusVeriPHY                                           OBJECT IDENTIFIER ::= { gs2326plusDiagnostics 9 }

gs2326plusVeriPHYTest OBJECT-TYPE
   SYNTAX      Integer32(1..4095)
   MAX-ACCESS  read-write
   STATUS      current
   DESCRIPTION
       "Run VeriPHY Cable Diagnostics.
        port, range : 0 - port number.
        0 : ALL "
   ::= { gs2326plusVeriPHY 1 }

gs2326plusVeriPHYTable OBJECT-TYPE
   SYNTAX      SEQUENCE OF Gs2326plusVeriPHYEntry
   MAX-ACCESS  not-accessible
   STATUS      current
   DESCRIPTION
       " "
   ::= { gs2326plusVeriPHY 2 }

gs2326plusVeriPHYEntry OBJECT-TYPE
   SYNTAX      Gs2326plusVeriPHYEntry
   MAX-ACCESS  not-accessible
   STATUS      current
   DESCRIPTION
       ""
   INDEX    { gs2326plusVeriPHYPort  }
   ::= { gs2326plusVeriPHYTable 1 }

Gs2326plusVeriPHYEntry ::= SEQUENCE {
   gs2326plusVeriPHYPort        Integer32,
   gs2326plusVeriPHYPairA       DisplayString,
   gs2326plusVeriPHYLengthA     DisplayString,
   gs2326plusVeriPHYPairB       DisplayString,
   gs2326plusVeriPHYLengthB     DisplayString,
   gs2326plusVeriPHYPairC       DisplayString,
   gs2326plusVeriPHYLengthC     DisplayString,
   gs2326plusVeriPHYPairD       DisplayString,
   gs2326plusVeriPHYLengthD     DisplayString
}

gs2326plusVeriPHYPort OBJECT-TYPE
   SYNTAX      Integer32(1..4095)
   MAX-ACCESS  not-accessible
   STATUS      current
   DESCRIPTION
       " The length (in meters) of the cable pair. "
   ::= { gs2326plusVeriPHYEntry 1 }

gs2326plusVeriPHYPairA OBJECT-TYPE
   SYNTAX      DisplayString
   MAX-ACCESS  read-only
   STATUS      current
   DESCRIPTION
       " The status of the cable pair. "
   ::= { gs2326plusVeriPHYEntry 2 }

gs2326plusVeriPHYLengthA OBJECT-TYPE
   SYNTAX      DisplayString
   MAX-ACCESS  read-only
   STATUS      current
   DESCRIPTION
       " The length (in meters) of the cable pair. "
   ::= { gs2326plusVeriPHYEntry 3 }

gs2326plusVeriPHYPairB OBJECT-TYPE
   SYNTAX      DisplayString
   MAX-ACCESS  read-only
   STATUS      current
   DESCRIPTION
       " The status of the cable pair. "
   ::= { gs2326plusVeriPHYEntry 4 }

gs2326plusVeriPHYLengthB OBJECT-TYPE
   SYNTAX      DisplayString
   MAX-ACCESS  read-only
   STATUS      current
   DESCRIPTION
       " The length (in meters) of the cable pair. "
   ::= { gs2326plusVeriPHYEntry 5 }

gs2326plusVeriPHYPairC OBJECT-TYPE
   SYNTAX      DisplayString
   MAX-ACCESS  read-only
   STATUS      current
   DESCRIPTION
       " The status of the cable pair. "
   ::= { gs2326plusVeriPHYEntry 6 }

gs2326plusVeriPHYLengthC OBJECT-TYPE
   SYNTAX      DisplayString
   MAX-ACCESS  read-only
   STATUS      current
   DESCRIPTION
       " The length (in meters) of the cable pair. "
   ::= { gs2326plusVeriPHYEntry 7 }

gs2326plusVeriPHYPairD OBJECT-TYPE
   SYNTAX      DisplayString
   MAX-ACCESS  read-only
   STATUS      current
   DESCRIPTION
       " The status of the cable pair. "
   ::= { gs2326plusVeriPHYEntry 8 }

gs2326plusVeriPHYLengthD OBJECT-TYPE
   SYNTAX      DisplayString
   MAX-ACCESS  read-only
   STATUS      current
   DESCRIPTION
       " The length (in meters) of the cable pair. "
   ::= { gs2326plusVeriPHYEntry 9 }


------------------------------------------------------------------------------------------------------------------
gs2326plusTrap                                                  OBJECT IDENTIFIER ::= { lancomGS2326plus  5 }

gs2326plusTrapEvent                                             OBJECT IDENTIFIER ::= { gs2326plusTrap 1 }

gs2326plusEmergency NOTIFICATION-TYPE
  OBJECTS   { gs2326plusInformation }
  STATUS        current
    DESCRIPTION
        "The severity level is Emergency. The system is unusable."
    ::= { gs2326plusTrapEvent 1 }

gs2326plusAlert NOTIFICATION-TYPE
  OBJECTS   { gs2326plusInformation }
  STATUS        current
    DESCRIPTION
        "The severity level is Alert. The action must be taken immediately."
    ::= { gs2326plusTrapEvent 2 }

gs2326plusCritical NOTIFICATION-TYPE
  OBJECTS   { gs2326plusInformation }
  STATUS        current
    DESCRIPTION
        "The severity level is Critical. Critical conditions."
    ::= { gs2326plusTrapEvent 3 }

gs2326plusError NOTIFICATION-TYPE
  OBJECTS   { gs2326plusInformation }
  STATUS        current
    DESCRIPTION
        "The severity level is Error. Error conditions."
    ::= { gs2326plusTrapEvent 4 }

gs2326plusWarning NOTIFICATION-TYPE
  OBJECTS   { gs2326plusInformation }
  STATUS        current
    DESCRIPTION
        "The severity level is Warning. Warning conditions."
    ::= { gs2326plusTrapEvent 5 }

gs2326plusNotice NOTIFICATION-TYPE
  OBJECTS   { gs2326plusInformation }
  STATUS        current
    DESCRIPTION
        "The severity level is Notice. Normal but significant condition."
    ::= { gs2326plusTrapEvent 6 }

gs2326plusInformational NOTIFICATION-TYPE
  OBJECTS   { gs2326plusInformation }
  STATUS        current
    DESCRIPTION
        "The severity level is Informational. Informational messages."
    ::= { gs2326plusTrapEvent 7 }

gs2326plusDebug NOTIFICATION-TYPE
  OBJECTS   { gs2326plusInformation }
  STATUS        current
    DESCRIPTION
        "The severity level is Debug. debug-level messages."
    ::= { gs2326plusTrapEvent 8 }

gs2326plusTrapVariable                                          OBJECT IDENTIFIER ::= { gs2326plusTrap 2 }

gs2326plusInformation OBJECT-TYPE
    SYNTAX      DisplayString
    MAX-ACCESS  read-only
    STATUS      current
    DESCRIPTION
        "Trap information."
    ::= { gs2326plusTrapVariable 1 }


END
