LANCOM-GS-2328F-MIB DEFINITIONS ::= BEGIN

IMPORTS
    DisplayString,MacAddress FROM SNMPv2-TC
    MODULE-COMPLIANCE,OBJECT-GROUP, NOTIFICATION-GROUP       FROM SNMPv2-CONF
    ifIndex    FROM RFC1213-MIB
    enterprises,MODULE-IDENTITY,OBJECT-TYPE,NOTIFICATION-TYPE,Counter32,Counter64,IpAddress        FROM SNMPv2-SMI
    InetAddress                   FROM INET-ADDRESS-MIB
    MacAddress FROM BRIDGE-MIB;

lancom-systems MODULE-IDENTITY
        LAST-UPDATED "202002190000Z"
        ORGANIZATION "LANCOM Systems GmbH."
        CONTACT-INFO
            "Adenauerstrasse 20 / B2, 52146 Wuerselen, Germany
            Email: info@lancom.de
            TEL: +49 (0)2405 49936 0
            FAX: +49 (0)2405 49936 99"
        DESCRIPTION
            "The MIB module is for LANCOM Systems"
        ::= { enterprises 2356 }

switchingSystems                                                          OBJECT IDENTIFIER ::= { lancom-systems 800 }

gigabitEthernetSwitches                                             OBJECT IDENTIFIER ::= { switchingSystems 3 }

lancomGS2328F                                                OBJECT IDENTIFIER ::= { gigabitEthernetSwitches 2332 }

gs2328fSystem                                                OBJECT IDENTIFIER ::= { lancomGS2328F  1 }

gs2328fSystemInformation                                     OBJECT IDENTIFIER ::= { gs2328fSystem 1 }

gs2328fModelName OBJECT-TYPE
   SYNTAX       DisplayString
   MAX-ACCESS   read-only
   STATUS       current
   DESCRIPTION
       ""
 ::= { gs2328fSystemInformation 1 }

gs2328fBIOSVersion OBJECT-TYPE
   SYNTAX       DisplayString
   MAX-ACCESS   read-only
   STATUS       current
   DESCRIPTION
       ""
   ::= { gs2328fSystemInformation 2 }

gs2328fFirmwareVersion OBJECT-TYPE
   SYNTAX       DisplayString
   MAX-ACCESS   read-only
   STATUS       current
   DESCRIPTION
       ""
   ::= { gs2328fSystemInformation 3 }

gs2328fHardwareMechanicalVersion OBJECT-TYPE
   SYNTAX       DisplayString
   MAX-ACCESS   read-only
   STATUS       current
   DESCRIPTION
       ""
   ::= { gs2328fSystemInformation 4 }

gs2328fSerialNumber OBJECT-TYPE
   SYNTAX       DisplayString
   MAX-ACCESS   read-only
   STATUS       current
   DESCRIPTION
       ""
   ::= { gs2328fSystemInformation 5 }

gs2328fHostMACAddress OBJECT-TYPE
   SYNTAX       MacAddress
   MAX-ACCESS   read-only
   STATUS       current
   DESCRIPTION
       ""
   ::= { gs2328fSystemInformation 6 }

gs2328fConsoleBaudrate OBJECT-TYPE
   SYNTAX       DisplayString
   MAX-ACCESS   read-only
   STATUS       current
   DESCRIPTION
       ""
   ::= { gs2328fSystemInformation 7 }

gs2328fRAMSize OBJECT-TYPE
   SYNTAX       DisplayString
   MAX-ACCESS   read-only
   STATUS       current
   DESCRIPTION
       ""
   ::= { gs2328fSystemInformation 8 }

gs2328fFlashSize OBJECT-TYPE
   SYNTAX       DisplayString
   MAX-ACCESS   read-only
   STATUS       current
   DESCRIPTION
       ""
   ::= { gs2328fSystemInformation 9 }

gs2328fBridgeFDBSize OBJECT-TYPE
   SYNTAX       DisplayString
   MAX-ACCESS   read-only
   STATUS       current
   DESCRIPTION
       ""
   ::= { gs2328fSystemInformation 10 }

gs2328fTransmitQueue OBJECT-TYPE
   SYNTAX       DisplayString
   MAX-ACCESS   read-only
   STATUS       current
   DESCRIPTION
       ""
   ::= { gs2328fSystemInformation 11 }

gs2328fMaximumFrameSize OBJECT-TYPE
   SYNTAX       DisplayString
   MAX-ACCESS   read-only
   STATUS       current
   DESCRIPTION
       ""
   ::= { gs2328fSystemInformation 12 }

gs2328fCPULoad OBJECT-TYPE
   SYNTAX       DisplayString
   MAX-ACCESS   read-only
   STATUS       current
   DESCRIPTION
       ""
   ::= { gs2328fSystemInformation 13 }

gs2328fFanSpeed OBJECT-TYPE
   SYNTAX       DisplayString
   MAX-ACCESS   read-only
   STATUS       current
   DESCRIPTION
       ""
   ::= { gs2328fSystemInformation 17 }

gs2328fACPower OBJECT-TYPE
   SYNTAX       DisplayString
   MAX-ACCESS   read-only
   STATUS       current
   DESCRIPTION
       ""
   ::= { gs2328fSystemInformation 18 }

gs2328fTemperature OBJECT-TYPE
   SYNTAX       DisplayString
   MAX-ACCESS   read-only
   STATUS       current
   DESCRIPTION
       ""
   ::= { gs2328fSystemInformation 19 }

gs2328fDCPower OBJECT-TYPE
   SYNTAX       DisplayString
   MAX-ACCESS   read-only
   STATUS       current
   DESCRIPTION
       ""
   ::= { gs2328fSystemInformation 20 }

gs2328fSystemDescription OBJECT-TYPE
   SYNTAX       DisplayString
   MAX-ACCESS   read-only
   STATUS       current
   DESCRIPTION
       ""
   ::= { gs2328fSystemInformation 21 }

gs2328fLocation OBJECT-TYPE
   SYNTAX       DisplayString
   MAX-ACCESS   read-only
   STATUS       current
   DESCRIPTION
       ""
   ::= { gs2328fSystemInformation 22 }

gs2328fContact OBJECT-TYPE
   SYNTAX       DisplayString
   MAX-ACCESS   read-only
   STATUS       current
   DESCRIPTION
       ""
   ::= { gs2328fSystemInformation 23 }

gs2328fDeviceName OBJECT-TYPE
   SYNTAX       DisplayString
   MAX-ACCESS   read-only
   STATUS       current
   DESCRIPTION
       ""
   ::= { gs2328fSystemInformation 24 }

gs2328fSystemDate OBJECT-TYPE
   SYNTAX       DisplayString
   MAX-ACCESS   read-only
   STATUS       current
   DESCRIPTION
       ""
   ::= { gs2328fSystemInformation 25 }

gs2328fSystemUptime OBJECT-TYPE
   SYNTAX       DisplayString
   MAX-ACCESS   read-only
   STATUS       current
   DESCRIPTION
       ""
   ::= { gs2328fSystemInformation 26 }

gs2328fSystemIPv4Address OBJECT-TYPE
   SYNTAX       DisplayString
   MAX-ACCESS   read-only
   STATUS       current
   DESCRIPTION
       ""
   ::= { gs2328fSystemInformation 27 }

gs2328fSystemIPv4SubnetMask OBJECT-TYPE
   SYNTAX       DisplayString
   MAX-ACCESS   read-only
   STATUS       current
   DESCRIPTION
       ""
   ::= { gs2328fSystemInformation 28 }

gs2328fSystemIPv4Gateway OBJECT-TYPE
   SYNTAX       DisplayString
   MAX-ACCESS   read-only
   STATUS       current
   DESCRIPTION
       ""
   ::= { gs2328fSystemInformation 29 }

gs2328fIPv6LinkLocalAddress OBJECT-TYPE
   SYNTAX       DisplayString
   MAX-ACCESS   read-only
   STATUS       current
   DESCRIPTION
       ""
   ::= { gs2328fSystemInformation 30 }

gs2328fIPv6Address OBJECT-TYPE
   SYNTAX       DisplayString
   MAX-ACCESS   read-only
   STATUS       current
   DESCRIPTION
       ""
   ::= { gs2328fSystemInformation 31 }

gs2328fIPv6Prefix OBJECT-TYPE
   SYNTAX       DisplayString
   MAX-ACCESS   read-only
   STATUS       current
   DESCRIPTION
       ""
   ::= { gs2328fSystemInformation 32 }

gs2328fIPv6Gateway OBJECT-TYPE
   SYNTAX       DisplayString
   MAX-ACCESS   read-only
   STATUS       current
   DESCRIPTION
       ""
   ::= { gs2328fSystemInformation 33 }

gs2328fLargestFreeMemBlock OBJECT-TYPE
   SYNTAX       Integer32
   MAX-ACCESS   read-only
   STATUS       current
   DESCRIPTION
       "Largest free memory block in Kb"
   ::= { gs2328fSystemInformation 1500 }

gs2328fMemFree  OBJECT-TYPE
   SYNTAX       Integer32
   MAX-ACCESS   read-only
   STATUS       current
   DESCRIPTION
       "Free memory in Kb"
   ::= { gs2328fSystemInformation 1501 }



gs2328fSystemTime                                            OBJECT IDENTIFIER ::= { gs2328fSystem 2 }

gs2328fSystemTimeManual                                      OBJECT IDENTIFIER ::= { gs2328fSystemTime 1 }

gs2328fSystemTimeManualClockSource OBJECT-TYPE
   SYNTAX	INTEGER {useLocal(0),useNTP(1)}
   MAX-ACCESS   read-write
   STATUS       current
   DESCRIPTION
       "default: 0,
        0 : Use Local Settings,
        1 : Use NTP Server."
   ::= { gs2328fSystemTimeManual 1 }

gs2328fSystemTimeManualLocaltime OBJECT-TYPE
   SYNTAX       DisplayString
   MAX-ACCESS   read-write
   STATUS       current
   DESCRIPTION
       "Get/Set the system time of the device.
        The input format is 'Year-Month-Day Hour:Minute:Second'.
        ex: 2011-01-01 05:43:05  means 2011/1/1 - 05:43:05 .
        The value range:
        Year    : 2010 - 2090,
        Mouth   : 1 - 12,
        Day     : 1 - 31,
        Hour    : 0 - 23,
        Minute  : 0 - 59,
        Sec     : 0 - 59."
   ::= { gs2328fSystemTimeManual 2 }

gs2328fSystemTimeManualTimeZoneOffset OBJECT-TYPE
   SYNTAX       INTEGER(-720..780)
   MAX-ACCESS   read-write
   STATUS       current
   DESCRIPTION
       "Get/Set the NTP Time Zone.
        The value range is between -720 and 780 (minutes)."
   ::= { gs2328fSystemTimeManual 3 }

gs2328fSystemTimeManualDaylightSavings OBJECT-TYPE
   SYNTAX       INTEGER { disable(0), enable(1) }
   MAX-ACCESS   read-write
   STATUS       current
   DESCRIPTION
       "default: 0,
        0 : Disable,
        1 : Enable."
   ::= { gs2328fSystemTimeManual 4 }

gs2328fSystemTimeManualTimeSetOffset OBJECT-TYPE
   SYNTAX       Integer32(1..1440)
   MAX-ACCESS   read-write
   STATUS       current
   DESCRIPTION
       "Get/Set the Daylight Saving Time.
        The value range is between 1 and 1440 (minutes),
        Default : 60 (minutes)."
   ::= { gs2328fSystemTimeManual 5 }

gs2328fSystemTimeManualDaylightSavingsType OBJECT-TYPE
   SYNTAX       INTEGER { byDates(0), recurring(1) }
   MAX-ACCESS   read-write
   STATUS       current
   DESCRIPTION
       "default: 0,
        0 : By dates,
        1 : Recurring."
   ::= { gs2328fSystemTimeManual 6 }

gs2328fSystemTimeManualDaylightSavingsBydatesFrom OBJECT-TYPE
   SYNTAX       DisplayString
   MAX-ACCESS   read-write
   STATUS       current
   DESCRIPTION
       "Get/Set the Start time of By dates Daylight Savings.
        The input format is 'Year-Month-Day Hour:Minute'.
        ex: 2011-01-01 05:43  means 2011/1/1 - 05:43 .
        The value range:
        Year    : 2010 - 2090,
        Mouth   : 1 - 12,
        Day     : 1 - 31,
        Hour    : 0 - 23,
        Minute  : 0 - 59."
   ::= { gs2328fSystemTimeManual 7 }

gs2328fSystemTimeManualDaylightSavingsBydatesTo OBJECT-TYPE
   SYNTAX       DisplayString
   MAX-ACCESS   read-write
   STATUS       current
   DESCRIPTION
       "Get/Set the End time of By dates Daylight Savings.
        The input format is 'Year-Month-Day Hour:Minute'.
        ex: 2011-01-01 05:43  means 2011/1/1 - 05:43 .
        The value range:
        Year    : 2010 - 2090,
        Mouth   : 1 - 12,
        Day     : 1 - 31,
        Hour    : 0 - 23,
        Minute  : 0 - 59."
   ::= { gs2328fSystemTimeManual 8 }

gs2328fSystemTimeManualDaylightSavingsRecurringDayFrom OBJECT-TYPE
   SYNTAX      INTEGER {
                        sunday(0),
                        monday(1),
                        tuseday(2),
                        wednesday(3),
                        thursday(4),
                        friday(5),
                        saturday(6)
                        }
   MAX-ACCESS   read-write
   STATUS       current
   DESCRIPTION
       "Get/Set the Daylight Saving Time Day From.
        0 : Sun, 1 : Mon, 2 : Tue, 3 : Wed, 4 : Thu, 5 : Fri, 6 : Sat."
   ::= { gs2328fSystemTimeManual 9 }

gs2328fSystemTimeManualDaylightSavingsRecurringWeekFrom OBJECT-TYPE
   SYNTAX       INTEGER{
                        firstWeek(1),
                        secondWeek(2),
                        thirdWeek(3),
                        fourthWeek(4),
                        listWeek(5)
                        }
   MAX-ACCESS   read-write
   STATUS       current
   DESCRIPTION
       "Get/Set the Daylight Saving Time Week From.
        1 : first week, 2, 3, 4, 5 : last week"
   ::= { gs2328fSystemTimeManual 10 }

gs2328fSystemTimeManualDaylightSavingsRecurringMonthFrom OBJECT-TYPE
   SYNTAX      INTEGER {
                        jan(1),
                        feb(2),
                        mar(3),
                        apr(4),
                        may(5),
                        jun(6),
                        jul(7),
                        aug(8),
                        sep(9),
                        oct(10),
                        nov(11),
                        dec(12)
                        }
   MAX-ACCESS   read-write
   STATUS       current
   DESCRIPTION
       "Get/Set the Daylight Saving Time Month From.
        1 : Jan, 2 : Feb, 3 : Mar, 4 : Apr, 5 : May, 6 : Jun,
        7 : Jul, 8 : Aug, 9 : Sep, 10 : Oct, 11 : Nov, 12 : Dec."
   ::= { gs2328fSystemTimeManual 11 }

gs2328fSystemTimeManualDaylightSavingsRecurringTimeFrom OBJECT-TYPE
   SYNTAX       DisplayString
   MAX-ACCESS   read-write
   STATUS       current
   DESCRIPTION
       "Get/Set the Start time of By dates Daylight Savings.
        The input format is 'Hour:Minute'.
        ex: 05:43.
        The value range:
        Hour    : 0 - 23,
        Minute  : 0 - 59."
   ::= { gs2328fSystemTimeManual 12 }

gs2328fSystemTimeManualDaylightSavingsRecurringDayTo OBJECT-TYPE
   SYNTAX      INTEGER {
                        sunday(0),
                        monday(1),
                        tuseday(2),
                        wednesday(3),
                        thursday(4),
                        friday(5),
                        saturday(6)
                        }
   MAX-ACCESS   read-write
   STATUS       current
   DESCRIPTION
       "Get/Set the Daylight Saving Time Day To.
        0 : Sun, 1 : Mon, 2 : Tue, 3 : Wed, 4 : Thu, 5 : Fri, 6 : Sat."
   ::= { gs2328fSystemTimeManual 13 }

gs2328fSystemTimeManualDaylightSavingsRecurringWeekTo OBJECT-TYPE
   SYNTAX       INTEGER{
                        firstWeek(1),
                        secondWeek(2),
                        thirdWeek(3),
                        fourthWeek(4),
                        listWeek(5)
                        }
   MAX-ACCESS   read-write
   STATUS       current
   DESCRIPTION
       "Get/Set the Daylight Saving Time Week To.
        1 : first week, 2, 3, 4, 5 : last week"
   ::= { gs2328fSystemTimeManual 14 }

gs2328fSystemTimeManualDaylightSavingsRecurringMonthTo OBJECT-TYPE
   SYNTAX      INTEGER {
                        jan(1),
                        feb(2),
                        mar(3),
                        apr(4),
                        may(5),
                        jun(6),
                        jul(7),
                        aug(8),
                        sep(9),
                        oct(10),
                        nov(11),
                        dec(12)
                        }
   MAX-ACCESS   read-write
   STATUS       current
   DESCRIPTION
       "Get/Set the Daylight Saving Time Month To.
        1 : Jan, 2 : Feb, 3 : Mar, 4 : Apr, 5 : May, 6 : Jun,
        7 : Jul, 8 : Aug, 9 : Sep, 10 : Oct, 11 : Nov, 12 : Dec."
   ::= { gs2328fSystemTimeManual 15 }

gs2328fSystemTimeManualDaylightSavingsRecurringTimeTo OBJECT-TYPE
   SYNTAX       DisplayString
   MAX-ACCESS   read-write
   STATUS       current
   DESCRIPTION
       "Get/Set the Start time of By dates Daylight Savings.
        The input format is 'Hour:Minute'.
        ex: 05:43.
        The value range:
        Hour    : 0 - 23,
        Minute  : 0 - 59."
   ::= { gs2328fSystemTimeManual 16 }

gs2328fSystemTimeNTP                                     OBJECT IDENTIFIER ::= { gs2328fSystemTime 2 }

gs2328fSystemTimeNTPTable OBJECT-TYPE
   SYNTAX      SEQUENCE OF GS2328FSystemTimeNTPEntry
   MAX-ACCESS  not-accessible
   STATUS      current
   DESCRIPTION
       " "
   ::= { gs2328fSystemTimeNTP 1 }

gs2328fSystemTimeNTPEntry OBJECT-TYPE
   SYNTAX      GS2328FSystemTimeNTPEntry
   MAX-ACCESS  not-accessible
   STATUS      current
   DESCRIPTION
       ""
   INDEX    { gs2328fSystemTimeNTPIndex  }
   ::= { gs2328fSystemTimeNTPTable 1 }

GS2328FSystemTimeNTPEntry ::= SEQUENCE {
   gs2328fSystemTimeNTPIndex             Integer32,
   gs2328fSystemTimeNTPServerIPType      INTEGER,
   gs2328fSystemTimeNTPServer            DisplayString,
   gs2328fSystemTimeNTPCurrentMode       INTEGER
}

gs2328fSystemTimeNTPIndex OBJECT-TYPE
   SYNTAX      Integer32(1..5)
   MAX-ACCESS  not-accessible
   STATUS      current
   DESCRIPTION
       " The index of the ntp entry. "
   ::= { gs2328fSystemTimeNTPEntry 1 }

gs2328fSystemTimeNTPServerIPType OBJECT-TYPE
   SYNTAX       INTEGER { ipv4(0), ipv6(1) }
   MAX-ACCESS   read-write
   STATUS       current
   DESCRIPTION
       "Default: 0,
        0 : IPv4,
        1 : IPv6."
   ::= { gs2328fSystemTimeNTPEntry 2 }

gs2328fSystemTimeNTPServer OBJECT-TYPE
   SYNTAX       DisplayString
   MAX-ACCESS   read-write
   STATUS       current
   DESCRIPTION
       "Get/Set the NTP Time Server1. You can use the IP address or domain name."
   ::= { gs2328fSystemTimeNTPEntry 3 }

gs2328fSystemTimeNTPCurrentMode OBJECT-TYPE
   SYNTAX      INTEGER { empty(0), active(1), edit(2), delete(3) }
   MAX-ACCESS  read-write
   STATUS      current
   DESCRIPTION
       " 0: Empty
        1: Active
        2: Edit
        3: Delete"
   ::= { gs2328fSystemTimeNTPEntry 4 }

gs2328fSystemTimeNTPRequestInterval OBJECT-TYPE
   SYNTAX       INTEGER(60..999999999)
   MAX-ACCESS   read-write
   STATUS       current
   DESCRIPTION
       "Get/Set the NTP Request Interval.
        Default : 86400.
        The value range is between 60 and 999999999 (seconds)."
   ::= { gs2328fSystemTimeNTP 2 }

gs2328fSystemTimeNTPTriesNumber OBJECT-TYPE
   SYNTAX       INTEGER(0..999999999)
   MAX-ACCESS   read-write
   STATUS       current
   DESCRIPTION
       "Get/Set the NTP Number of tries.
        Default : 4.
        The value range is between 0 and 999999999."
   ::= { gs2328fSystemTimeNTP 3 }


gs2328fSystemAccount                                         OBJECT IDENTIFIER ::= { gs2328fSystem 3 }

gs2328fSystemAccountUsers                                    OBJECT IDENTIFIER ::= { gs2328fSystemAccount 1 }

gs2328fSystemAccountUserCreate OBJECT-TYPE
   SYNTAX       INTEGER { none(0), create(1) }
   MAX-ACCESS   read-write
   STATUS       current
   DESCRIPTION
       "default: 0
        0 : None  (read only)
        1 : Create a user account"
   ::= { gs2328fSystemAccountUsers 1 }

gs2328fSystemAccountUsersTable OBJECT-TYPE
   SYNTAX      SEQUENCE OF GS2328FSystemAccountUsersEntry
   MAX-ACCESS  not-accessible
   STATUS      current
   DESCRIPTION
       " "
   ::= { gs2328fSystemAccountUsers 2 }

gs2328fSystemAccountUsersEntry OBJECT-TYPE
   SYNTAX      GS2328FSystemAccountUsersEntry
   MAX-ACCESS  not-accessible
   STATUS      current
   DESCRIPTION
       ""
   INDEX    { gs2328fUserIndex  }
   ::= { gs2328fSystemAccountUsersTable 1 }


GS2328FSystemAccountUsersEntry ::= SEQUENCE {
   gs2328fUserIndex              Integer32 ,
   gs2328fUserName               DisplayString,
   gs2328fPassword               DisplayString,
   gs2328fUserPrivilegeLevel     Integer32 ,
   gs2328fAccountUserRowStatus   INTEGER
}


gs2328fUserIndex OBJECT-TYPE
   SYNTAX      Integer32 (1..20)
   MAX-ACCESS  not-accessible
   STATUS      current
   DESCRIPTION
       " "
   ::= { gs2328fSystemAccountUsersEntry 1 }

gs2328fUserName OBJECT-TYPE
   SYNTAX      DisplayString (SIZE (1..32))
   MAX-ACCESS  read-write
   STATUS      current
   DESCRIPTION
       "Please use a combination of letters, numbers and underscores"
   ::= { gs2328fSystemAccountUsersEntry 2 }

gs2328fPassword OBJECT-TYPE
   SYNTAX      DisplayString (SIZE (1..32))
   MAX-ACCESS  read-write
   STATUS      current
   DESCRIPTION
       "Please use ASCII printable code except Quotation mark, Colon (punctuation), Less-than sign, Greater-than sign, At sign, Question mark and Space (punctuation)"
   ::= { gs2328fSystemAccountUsersEntry 3 }

gs2328fUserPrivilegeLevel OBJECT-TYPE
   SYNTAX      Integer32 (1..15)
   MAX-ACCESS  read-write
   STATUS      current
   DESCRIPTION
       "default:1
        User privilege level range : 1 - 15"
   ::= { gs2328fSystemAccountUsersEntry 4 }

gs2328fAccountUserRowStatus OBJECT-TYPE
   SYNTAX      INTEGER { active(1), notInservice(2), edit(3), destroy(4), undo(5) }
   MAX-ACCESS  read-write
   STATUS      current
   DESCRIPTION
       " 1: active
        2: notInservice
        3: edit
        4: destroy
        5: undo"
   ::= { gs2328fSystemAccountUsersEntry 5 }

gs2328fSystemAccountUsersSuperUserPassword OBJECT-TYPE
   SYNTAX      OCTET STRING (SIZE (0..32))
   MAX-ACCESS read-write
   STATUS      current
   DESCRIPTION
        "Super-User Password"
   ::= { gs2328fSystemAccountUsers 1500 }

gs2328fSystemAccountEnforcePasswordRules OBJECT-TYPE
   SYNTAX       INTEGER { yes(0), no(1) }
   MAX-ACCESS   read-write
   STATUS       current
   DESCRIPTION
       "default: 0
        0 : Do not enforce rules
        1 : enforce rules"
   ::= { gs2328fSystemAccountUsers 1501 }

gs2328fSystemAccountPrivilegeLevel                           OBJECT IDENTIFIER ::= { gs2328fSystemAccount 2 }

gs2328fAccountPrivilegeLevel OBJECT-TYPE
   SYNTAX      Integer32 (1..15)
   MAX-ACCESS  read-write
   STATUS      current
   DESCRIPTION
       "Default:15, Range : 1-15. "
   ::= { gs2328fSystemAccountPrivilegeLevel 1 }

gs2328fAggregationPrivilegeLevel OBJECT-TYPE
   SYNTAX      Integer32 (1..15)
   MAX-ACCESS  read-write
   STATUS      current
   DESCRIPTION
       "Default:15, Range : 1-15. "
   ::= { gs2328fSystemAccountPrivilegeLevel 2 }

gs2328fDiagnosticsPrivilegeLevel OBJECT-TYPE
   SYNTAX      Integer32 (1..15)
   MAX-ACCESS  read-write
   STATUS      current
   DESCRIPTION
       "Default:15, Range : 1-15. "
   ::= { gs2328fSystemAccountPrivilegeLevel 3 }

gs2328fEEEPrivilegeLevel OBJECT-TYPE
   SYNTAX      Integer32 (1..15)
   MAX-ACCESS  read-write
   STATUS      current
   DESCRIPTION
       "Default:15, Range : 1-15. "
   ::= { gs2328fSystemAccountPrivilegeLevel 4 }

gs2328fEasyportPrivilegeLevel OBJECT-TYPE
   SYNTAX      Integer32 (1..15)
   MAX-ACCESS  read-write
   STATUS      current
   DESCRIPTION
       "Default:15, Range : 1-15. "
   ::= { gs2328fSystemAccountPrivilegeLevel 9 }

gs2328fGARPPrivilegeLevel OBJECT-TYPE
   SYNTAX      Integer32 (1..15)
   MAX-ACCESS  read-write
   STATUS      current
   DESCRIPTION
       "Default:15, Range : 1-15. "
   ::= { gs2328fSystemAccountPrivilegeLevel 10 }

gs2328fGVRPPrivilegeLevel OBJECT-TYPE
   SYNTAX      Integer32 (1..15)
   MAX-ACCESS  read-write
   STATUS      current
   DESCRIPTION
       "Default:15, Range : 1-15. "
   ::= { gs2328fSystemAccountPrivilegeLevel 11 }

gs2328fIPPrivilegeLevel OBJECT-TYPE
   SYNTAX      Integer32 (1..15)
   MAX-ACCESS  read-write
   STATUS      current
   DESCRIPTION
       "Default:15, Range : 1-15. "
   ::= { gs2328fSystemAccountPrivilegeLevel 12 }

gs2328fIPMCSnoopingPrivilegeLevel OBJECT-TYPE
   SYNTAX      Integer32 (1..15)
   MAX-ACCESS  read-write
   STATUS      current
   DESCRIPTION
       "Default:15, Range : 1-15. "
   ::= { gs2328fSystemAccountPrivilegeLevel 13 }

gs2328fLACPPrivilegeLevel OBJECT-TYPE
   SYNTAX      Integer32 (1..15)
   MAX-ACCESS  read-write
   STATUS      current
   DESCRIPTION
       "Default:15, Range : 1-15. "
   ::= { gs2328fSystemAccountPrivilegeLevel 14 }

gs2328fLLDPPrivilegeLevel OBJECT-TYPE
   SYNTAX      Integer32 (1..15)
   MAX-ACCESS  read-write
   STATUS      current
   DESCRIPTION
       "Default:15, Range : 1-15. "
   ::= { gs2328fSystemAccountPrivilegeLevel 15 }

gs2328fLLDPMEDPrivilegeLevel OBJECT-TYPE
   SYNTAX      Integer32 (1..15)
   MAX-ACCESS  read-write
   STATUS      current
   DESCRIPTION
       "Default:15, Range : 1-15. "
   ::= { gs2328fSystemAccountPrivilegeLevel 16 }

gs2328fLoopProtectPrivilegeLevel OBJECT-TYPE
   SYNTAX      Integer32 (1..15)
   MAX-ACCESS  read-write
   STATUS      current
   DESCRIPTION
       "Default:15, Range : 1-15. "
   ::= { gs2328fSystemAccountPrivilegeLevel 17 }

gs2328fMACTablePrivilegeLevel OBJECT-TYPE
   SYNTAX      Integer32 (1..15)
   MAX-ACCESS  read-write
   STATUS      current
   DESCRIPTION
       "Default:15, Range : 1-15. "
   ::= { gs2328fSystemAccountPrivilegeLevel 18 }

gs2328fMVRPrivilegeLevel OBJECT-TYPE
   SYNTAX      Integer32 (1..15)
   MAX-ACCESS  read-write
   STATUS      current
   DESCRIPTION
       "Default:15, Range : 1-15. "
   ::= { gs2328fSystemAccountPrivilegeLevel 22 }

gs2328fMaintenancePrivilegeLevel OBJECT-TYPE
   SYNTAX      Integer32 (1..15)
   MAX-ACCESS  read-write
   STATUS      current
   DESCRIPTION
       "Default:15, Range : 1-15. "
   ::= { gs2328fSystemAccountPrivilegeLevel 24 }

gs2328fMirroringPrivilegeLevel OBJECT-TYPE
   SYNTAX      Integer32 (1..15)
   MAX-ACCESS  read-write
   STATUS      current
   DESCRIPTION
       "Default:15, Range : 1-15. "
   ::= { gs2328fSystemAccountPrivilegeLevel 25 }

gs2328fPortsPrivilegeLevel OBJECT-TYPE
   SYNTAX      Integer32 (1..15)
   MAX-ACCESS  read-write
   STATUS      current
   DESCRIPTION
       "Default:15, Range : 1-15. "
   ::= { gs2328fSystemAccountPrivilegeLevel 27 }

gs2328fPrivateVLANsPrivilegeLevel OBJECT-TYPE
   SYNTAX      Integer32 (1..15)
   MAX-ACCESS  read-write
   STATUS      current
   DESCRIPTION
       "Default:15, Range : 1-15. "
   ::= { gs2328fSystemAccountPrivilegeLevel 28 }

gs2328fQoSPrivilegeLevel OBJECT-TYPE
   SYNTAX      Integer32 (1..15)
   MAX-ACCESS  read-write
   STATUS      current
   DESCRIPTION
       "Default:15, Range : 1-15. "
   ::= { gs2328fSystemAccountPrivilegeLevel 29 }

gs2328fSFlowPrivilegeLevel OBJECT-TYPE
   SYNTAX      Integer32 (1..15)
   MAX-ACCESS  read-write
   STATUS      current
   DESCRIPTION
       "Default:15, Range : 1-15. "
   ::= { gs2328fSystemAccountPrivilegeLevel 30 }

gs2328fSMTPPrivilegeLevel OBJECT-TYPE
   SYNTAX      Integer32 (1..15)
   MAX-ACCESS  read-write
   STATUS      current
   DESCRIPTION
       "Default:15, Range : 1-15. "
   ::= { gs2328fSystemAccountPrivilegeLevel 31 }

gs2328fSNMPPrivilegeLevel OBJECT-TYPE
   SYNTAX      Integer32 (1..15)
   MAX-ACCESS  read-write
   STATUS      current
   DESCRIPTION
       "Default:15, Range : 1-15. "
   ::= { gs2328fSystemAccountPrivilegeLevel 32 }

gs2328fSecurityPrivilegeLevel OBJECT-TYPE
   SYNTAX      Integer32 (1..15)
   MAX-ACCESS  read-write
   STATUS      current
   DESCRIPTION
       "Default:15, Range : 1-15. "
   ::= { gs2328fSystemAccountPrivilegeLevel 33 }

gs2328fSingleIPPrivilegeLevel OBJECT-TYPE
   SYNTAX      Integer32 (1..15)
   MAX-ACCESS  read-write
   STATUS      current
   DESCRIPTION
       "Default:15, Range : 1-15. "
   ::= { gs2328fSystemAccountPrivilegeLevel 34 }

gs2328fSpanningTreePrivilegeLevel OBJECT-TYPE
   SYNTAX      Integer32 (1..15)
   MAX-ACCESS  read-write
   STATUS      current
   DESCRIPTION
       "Default:15, Range : 1-15. "
   ::= { gs2328fSystemAccountPrivilegeLevel 35 }

gs2328fSystemPrivilegeLevel OBJECT-TYPE
   SYNTAX      Integer32 (1..15)
   MAX-ACCESS  read-write
   STATUS      current
   DESCRIPTION
       "Default:15, Range : 1-15. "
   ::= { gs2328fSystemAccountPrivilegeLevel 36 }

gs2328fTrapEventPrivilegeLevel OBJECT-TYPE
   SYNTAX      Integer32 (1..15)
   MAX-ACCESS  read-write
   STATUS      current
   DESCRIPTION
       "Default:15, Range : 1-15. "
   ::= { gs2328fSystemAccountPrivilegeLevel 37 }

gs2328fUPnPPrivilegeLevel OBJECT-TYPE
   SYNTAX      Integer32 (1..15)
   MAX-ACCESS  read-write
   STATUS      current
   DESCRIPTION
       "Default:15, Range : 1-15. "
   ::= { gs2328fSystemAccountPrivilegeLevel 38 }

gs2328fVCLPrivilegeLevel OBJECT-TYPE
   SYNTAX      Integer32 (1..15)
   MAX-ACCESS  read-write
   STATUS      current
   DESCRIPTION
       "Default:15, Range : 1-15. "
   ::= { gs2328fSystemAccountPrivilegeLevel 39 }

gs2328fVLANsPrivilegeLevel OBJECT-TYPE
   SYNTAX      Integer32 (1..15)
   MAX-ACCESS  read-write
   STATUS      current
   DESCRIPTION
       "Default:15, Range : 1-15. "
   ::= { gs2328fSystemAccountPrivilegeLevel 41 }

gs2328fVoiceVLANPrivilegeLevel OBJECT-TYPE
   SYNTAX      Integer32 (1..15)
   MAX-ACCESS  read-write
   STATUS      current
   DESCRIPTION
       "Default:15, Range : 1-15. "
   ::= { gs2328fSystemAccountPrivilegeLevel 42 }

gs2328fIP                                                    OBJECT IDENTIFIER ::= { gs2328fSystem 4 }

gs2328fIPv4                                                  OBJECT IDENTIFIER ::= { gs2328fIP 1 }

gs2328fIPv4Configured                                                  OBJECT IDENTIFIER ::= { gs2328fIPv4 1 }

gs2328fIpv4DHCPClient OBJECT-TYPE
   SYNTAX      INTEGER { disable(0), enable(1) }
   MAX-ACCESS  read-write
   STATUS      current
   DESCRIPTION
       "default:0
       0: disable
       1: enable"
   ::= { gs2328fIPv4Configured 1 }

gs2328fIPv4Address OBJECT-TYPE
   SYNTAX      IpAddress
   MAX-ACCESS  read-write
   STATUS      current
   DESCRIPTION
       ""
   ::= { gs2328fIPv4Configured 2 }

gs2328fIPv4Mask OBJECT-TYPE
   SYNTAX      IpAddress
   MAX-ACCESS  read-write
   STATUS      current
   DESCRIPTION
       ""
   ::= { gs2328fIPv4Configured 3 }

gs2328fIPv4Gateway OBJECT-TYPE
   SYNTAX      IpAddress
   MAX-ACCESS  read-write
   STATUS      current
   DESCRIPTION
       ""
   ::= { gs2328fIPv4Configured 4 }

gs2328fIPv4VLANId OBJECT-TYPE
   SYNTAX      Integer32(1..4094)
   MAX-ACCESS  read-write
   STATUS      current
   DESCRIPTION
       "default:1"
   ::= { gs2328fIPv4Configured 5 }

gs2328fIPv4DNSServer OBJECT-TYPE
   SYNTAX      IpAddress
   MAX-ACCESS  read-write
   STATUS      current
   DESCRIPTION
       ""
   ::= { gs2328fIPv4Configured 6 }

gs2328fIPv4DNSProxy OBJECT-TYPE
   SYNTAX      INTEGER { disable(0), enable(1) }
   MAX-ACCESS  read-write
   STATUS      current
   DESCRIPTION
       "0:disable, 1:enable "
   ::= { gs2328fIPv4Configured 7 }

gs2328fIPv4Current                                                  OBJECT IDENTIFIER ::= { gs2328fIPv4 2 }

gs2328fIpv4CurrentDHCPClient OBJECT-TYPE
   SYNTAX      INTEGER { none(0), renew(1) }
   MAX-ACCESS  read-write
   STATUS      current
   DESCRIPTION
       "default:0
       0: none (for read)
       1: renew"
   ::= { gs2328fIPv4Current 1 }

gs2328fIPv4CurrentAddress OBJECT-TYPE
   SYNTAX      IpAddress
   MAX-ACCESS  read-only
   STATUS      current
   DESCRIPTION
       ""
   ::= { gs2328fIPv4Current 2 }

gs2328fIPv4CurrentMask OBJECT-TYPE
   SYNTAX      IpAddress
   MAX-ACCESS  read-only
   STATUS      current
   DESCRIPTION
       ""
   ::= { gs2328fIPv4Current 3 }

gs2328fIPv4CurrentGateway OBJECT-TYPE
   SYNTAX      IpAddress
   MAX-ACCESS  read-only
   STATUS      current
   DESCRIPTION
       ""
   ::= { gs2328fIPv4Current 4 }

gs2328fIPv4CurrentVLANId OBJECT-TYPE
   SYNTAX      Integer32(1..4094)
   MAX-ACCESS  read-only
   STATUS      current
   DESCRIPTION
       "default:1"
   ::= { gs2328fIPv4Current 5 }

gs2328fIPv4CurrentDNSServer OBJECT-TYPE
   SYNTAX      IpAddress
   MAX-ACCESS  read-only
   STATUS      current
   DESCRIPTION
       ""
   ::= { gs2328fIPv4Current 6 }


gs2328fIPv6                                                  OBJECT IDENTIFIER ::= { gs2328fIP 2 }

gs2328fIPv6Configured                                                  OBJECT IDENTIFIER ::= { gs2328fIPv6 1 }

gs2328fIpv6AutoConfiguration OBJECT-TYPE
   SYNTAX      INTEGER { disable(0), enable(1) }
   MAX-ACCESS  read-write
   STATUS      current
   DESCRIPTION
       "default:0
       0: disable
       1: enable"
   ::= { gs2328fIPv6Configured 1 }

gs2328fIpv6Address OBJECT-TYPE
   SYNTAX      DisplayString (SIZE (0..30))
   MAX-ACCESS  read-write
   STATUS      current
   DESCRIPTION
       ""
   ::= { gs2328fIPv6Configured 2 }

gs2328fIpv6Prefix OBJECT-TYPE
   SYNTAX      Integer32 (1..128)
   MAX-ACCESS  read-write
   STATUS      current
   DESCRIPTION
       "default: 96"
   ::= { gs2328fIPv6Configured 3 }

gs2328fIpv6Gateway OBJECT-TYPE
   SYNTAX      DisplayString (SIZE (0..30))
   MAX-ACCESS  read-write
   STATUS      current
   DESCRIPTION
       " "
   ::= { gs2328fIPv6Configured 4 }

gs2328fIPv6Current                                                  OBJECT IDENTIFIER ::= { gs2328fIPv6 2 }

gs2328fIpv6CurrentAutoConfiguration OBJECT-TYPE
   SYNTAX      INTEGER { disable(0), enable(1) }
   MAX-ACCESS  read-only
   STATUS      current
   DESCRIPTION
       "default:0
       0: disable
       1: enable"
   ::= { gs2328fIPv6Current 1 }

gs2328fIpv6CurrentAddress OBJECT-TYPE
   SYNTAX      DisplayString (SIZE (0..30))
   MAX-ACCESS  read-only
   STATUS      current
   DESCRIPTION
       ""
   ::= { gs2328fIPv6Current 2 }


gs2328fIpv6CurrentLinkLocalAddress OBJECT-TYPE
   SYNTAX      DisplayString(SIZE (0..30))
   MAX-ACCESS  read-only
   STATUS      current
   DESCRIPTION
       ""
   ::= { gs2328fIPv6Current 3 }


gs2328fIpv6CurrentPrefix OBJECT-TYPE
   SYNTAX      DisplayString(SIZE (0..64))
   MAX-ACCESS  read-only
   STATUS      current
   DESCRIPTION
       ""
   ::= { gs2328fIPv6Current 4 }

gs2328fIpv6CurrentGateway OBJECT-TYPE
   SYNTAX      DisplayString (SIZE (0..30))
   MAX-ACCESS  read-only
   STATUS      current
   DESCRIPTION
       " "
   ::= { gs2328fIPv6Current 5 }

gs2328fSyslog                                                OBJECT IDENTIFIER ::= { gs2328fSystem 5 }

gs2328fSyslogConf                                            OBJECT IDENTIFIER ::= { gs2328fSyslog 1 }

gs2328fServerMode OBJECT-TYPE
   SYNTAX      INTEGER { disable(0), enable(1) }
   MAX-ACCESS  read-write
   STATUS      current
   DESCRIPTION
       "default: 0
       0: disable
       1: enable "
   ::= { gs2328fSyslogConf 1 }

gs2328fServerAddress1 OBJECT-TYPE
   SYNTAX      IpAddress
   MAX-ACCESS  read-write
   STATUS      current
   DESCRIPTION
       " "
   ::= { gs2328fSyslogConf 2 }

gs2328fServerAddress2 OBJECT-TYPE
   SYNTAX      IpAddress
   MAX-ACCESS  read-write
   STATUS      current
   DESCRIPTION
       " "
   ::= { gs2328fSyslogConf 3 }

gs2328fSyslogLevel OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       "default: 6 (Info)
       0: Emergency
       1: Alert
       2: Critical
       3: Error
       4: Warning
       5: Notice
       6: Info
       7: Debug"
   ::= { gs2328fSyslogConf 4 }

gs2328fSyslogDetailedInfo                                    OBJECT IDENTIFIER ::= { gs2328fSyslog 2 }

gs2328fSyslogDetailedInfoClear OBJECT-TYPE
   SYNTAX      INTEGER { none(0), clear(1) }
   MAX-ACCESS  read-write
   STATUS      current
   DESCRIPTION
      "default: 0
       0 : None  (read only)
       1 : Clear Syslog"
   ::= { gs2328fSyslogDetailedInfo 1 }

gs2328fSyslogDetailedInfoTable OBJECT-TYPE
  SYNTAX      SEQUENCE OF GS2328FSyslogDetailedInfoEntry
  MAX-ACCESS  not-accessible
  STATUS      current
  DESCRIPTION
           " "
       ::= { gs2328fSyslogDetailedInfo 2 }

gs2328fSyslogDetailedInfoEntry OBJECT-TYPE
   SYNTAX      GS2328FSyslogDetailedInfoEntry
   MAX-ACCESS  not-accessible
   STATUS      current
   DESCRIPTION
           ""
   INDEX    { gs2328fSyslogDetailedInfoIndex  }
   ::= { gs2328fSyslogDetailedInfoTable 1 }

GS2328FSyslogDetailedInfoEntry ::= SEQUENCE {
   gs2328fSyslogDetailedInfoIndex       Integer32,
   gs2328fSyslogDetailedInfoLevel       DisplayString,
   gs2328fSyslogDetailedInfoTime        DisplayString,
   gs2328fSyslogDetailedInfoMessage     DisplayString
}

gs2328fSyslogDetailedInfoIndex OBJECT-TYPE
   SYNTAX      Integer32(1..1024)
   MAX-ACCESS  not-accessible
   STATUS      current
   DESCRIPTION
       " "
   ::= { gs2328fSyslogDetailedInfoEntry 1 }

gs2328fSyslogDetailedInfoLevel OBJECT-TYPE
   SYNTAX      DisplayString
   MAX-ACCESS  read-only
   STATUS      current
   DESCRIPTION
       " "
   ::= { gs2328fSyslogDetailedInfoEntry 2 }

gs2328fSyslogDetailedInfoTime OBJECT-TYPE
   SYNTAX      DisplayString(SIZE (0..20))
   MAX-ACCESS  read-only
   STATUS      current
   DESCRIPTION
       " "
   ::= { gs2328fSyslogDetailedInfoEntry 3 }

gs2328fSyslogDetailedInfoMessage OBJECT-TYPE
   SYNTAX      DisplayString
   MAX-ACCESS  read-only
   STATUS      current
   DESCRIPTION
       " "
   ::= { gs2328fSyslogDetailedInfoEntry 4 }


gs2328fSnmp                                                OBJECT IDENTIFIER ::= { gs2328fSystem 6 }

gs2328fSnmpConf                                            OBJECT IDENTIFIER ::= { gs2328fSnmp 1 }

gs2328fGetCommunityMode OBJECT-TYPE
   SYNTAX       INTEGER { disable(0), enable(1) }
   MAX-ACCESS   read-write
   STATUS       current
   DESCRIPTION
       "Get/Set the get-community mode of the SNMP.
        default : 1, 0: disable, 1: enable. "
   ::= { gs2328fSnmpConf 1 }

gs2328fGetCommunity OBJECT-TYPE
   SYNTAX       DisplayString
   MAX-ACCESS   read-write
   STATUS       current
   DESCRIPTION
       "Get/Set the get-community of the SNMP."
   ::= { gs2328fSnmpConf 2 }

gs2328fSetCommunityMode OBJECT-TYPE
   SYNTAX       INTEGER { disable(0), enable(1) }
   MAX-ACCESS   read-write
   STATUS       current
   DESCRIPTION
       "Get/Set the set-community mode of the SNMP.
        default : 1, 0: disable, 1: enable. "
   ::= { gs2328fSnmpConf 3 }

gs2328fSetCommunity OBJECT-TYPE
   SYNTAX       DisplayString
   MAX-ACCESS   read-write
   STATUS       current
   DESCRIPTION
       "Get/Set the set-community of the SNMP."
   ::= { gs2328fSnmpConf 4 }

gs2328fGetCommunityConfTable OBJECT-TYPE
   SYNTAX      SEQUENCE OF GS2328FGetCommunityConfEntry
   MAX-ACCESS  not-accessible
   STATUS      current
   DESCRIPTION
       " Show get-community of the SNMP. "
   ::= { gs2328fSnmpConf 5 }

gs2328fGetCommunityConfEntry OBJECT-TYPE
   SYNTAX      GS2328FGetCommunityConfEntry
   MAX-ACCESS  not-accessible
   STATUS      current
   DESCRIPTION
       ""
   INDEX    { gs2328fCommunityConfIndex  }
   ::= { gs2328fGetCommunityConfTable 1 }

GS2328FGetCommunityConfEntry ::= SEQUENCE {
   gs2328fCommunityConfIndex				Integer32,
   gs2328fCommunityConfGetCommunity			DisplayString
}

gs2328fCommunityConfIndex OBJECT-TYPE
   SYNTAX      Integer32(1..4095)
   MAX-ACCESS  not-accessible
   STATUS      current
   DESCRIPTION
       " index, range : 1 - 5. "
   ::= { gs2328fGetCommunityConfEntry 1 }

gs2328fCommunityConfGetCommunity OBJECT-TYPE
   SYNTAX      DisplayString
   MAX-ACCESS  read-write
   STATUS      current
   DESCRIPTION
       " Get/Set the get-community of the SNMP."
   ::= { gs2328fGetCommunityConfEntry 2 }

gs2328fTrapHostConfTable OBJECT-TYPE
   SYNTAX      SEQUENCE OF GS2328FTrapHostConfEntry
   MAX-ACCESS  not-accessible
   STATUS      current
   DESCRIPTION
       "A list of trap host entry. The numbers of entries are given by the value of gs2328fTrapHostConfNumber."
   ::= { gs2328fSnmpConf 6 }

gs2328fTrapHostConfEntry OBJECT-TYPE
   SYNTAX      GS2328FTrapHostConfEntry
   MAX-ACCESS  not-accessible
   STATUS      current
   DESCRIPTION
       "This is the entry information for trap host."
   INDEX    { gs2328fTrapHostConfIndex  }
   ::= { gs2328fTrapHostConfTable 1 }

GS2328FTrapHostConfEntry ::= SEQUENCE {
    gs2328fTrapHostConfIndex             Integer32,
    gs2328fTrapHostConfVersion           INTEGER,
    gs2328fTrapHostConfIPType            INTEGER,
    gs2328fTrapHostConfIP                DisplayString,
    gs2328fTrapHostConfPort              Integer32,
    gs2328fTrapHostConfCommunity         DisplayString,
    gs2328fTrapHostConfSeverityLevel     INTEGER,
    gs2328fTrapHostConfSecurityLevel     INTEGER,
    gs2328fTrapHostConfAuthPtc           INTEGER,
    gs2328fTrapHostConfAuthPassword      DisplayString,
    gs2328fTrapHostConfPrivPtc           INTEGER,
    gs2328fTrapHostConfPrivPassword      DisplayString,
    gs2328fTrapHostConfCurrentMode       INTEGER
}

gs2328fTrapHostConfIndex OBJECT-TYPE
   SYNTAX      Integer32(1..6)
   MAX-ACCESS  not-accessible
   STATUS      current
   DESCRIPTION
       " The index of the trap host entry. "
   ::= { gs2328fTrapHostConfEntry 1 }

gs2328fTrapHostConfVersion OBJECT-TYPE
   SYNTAX       INTEGER { snmpv2c(2), snmpv3(3) }
   MAX-ACCESS   read-write
   STATUS       current
   DESCRIPTION
       "The version of the Trap PDU. Version : 2(SNMPv2c), 3(SNMPv3)"
   ::= { gs2328fTrapHostConfEntry 2 }

gs2328fTrapHostConfIPType OBJECT-TYPE
   SYNTAX       INTEGER { ipv4(4), ipv6(6) }
   MAX-ACCESS   read-write
   STATUS       current
   DESCRIPTION
       "Server IP Type. Default: 4,
        4 : IPv4,
        6 : IPv6."
   ::= { gs2328fTrapHostConfEntry 3 }

gs2328fTrapHostConfIP OBJECT-TYPE
   SYNTAX       DisplayString
   MAX-ACCESS   read-write
   STATUS       current
   DESCRIPTION
       "This is the IP of the trap host."
   ::= { gs2328fTrapHostConfEntry 4 }

gs2328fTrapHostConfPort OBJECT-TYPE
   SYNTAX       Integer32(1..65535)
   MAX-ACCESS   read-write
   STATUS       current
   DESCRIPTION
       "This is the receiving-port number of the trap host.
        range : 1 - 65535."
   ::= { gs2328fTrapHostConfEntry 5 }

gs2328fTrapHostConfCommunity OBJECT-TYPE
   SYNTAX       DisplayString (SIZE (1..32))
   MAX-ACCESS   read-write
   STATUS       current
   DESCRIPTION
       "The community/security name for the trap PDU."
   ::= { gs2328fTrapHostConfEntry 6 }

gs2328fTrapHostConfSeverityLevel	OBJECT-TYPE
   SYNTAX      INTEGER {
                    emergency(0),
                    alert(1),
                    critical(2),
                    error(3),
                    warning(4),
                    notice(5),
                    info(6),
                    debug(7)
                }
   MAX-ACCESS   read-write
   STATUS       current
   DESCRIPTION
       "The Severity Level.
        0 : Emerg, 1 : Alert, 2 : Critical, 3 : Error, 4 : Warning, 5 : Notice, 6 : Info, 7 : Debug."
	::= { gs2328fTrapHostConfEntry 7 }

gs2328fTrapHostConfSecurityLevel	OBJECT-TYPE
   SYNTAX       INTEGER { noAuthNoPriv(1), authNoPriv(2), authPriv(3) }
   MAX-ACCESS   read-write
   STATUS       current
   DESCRIPTION
       "The Security Level, NoAuthNoPriv, AuthNoPriv, and AuthPriv.
        1 : NoAuthNoPriv, 2 : AuthNoPriv, 3 : AuthPriv.
        Privacy protocol will be configured as 'DES' automatically if security level is 3(AuthPriv)."
	::= { gs2328fTrapHostConfEntry 8 }

gs2328fTrapHostConfAuthPtc	OBJECT-TYPE
   SYNTAX       INTEGER { md5(1), sha(2) }
   MAX-ACCESS   read-write
   STATUS       current
   DESCRIPTION
       "Authentication Protocol, there are SHA and MD5 supported presently.
        1 : MD5, 2 : SHA."
	::= { gs2328fTrapHostConfEntry 9 }

gs2328fTrapHostConfAuthPassword	OBJECT-TYPE
   SYNTAX      DisplayString
   MAX-ACCESS  read-write
   STATUS		current
   DESCRIPTION
       "Authentication Password, is used for authenticating. The return value is always '********'.
        If the authentication protocol is MD5, the length of password should be 8 ~ 32 characters.
        If the authentication protocol is SHA, the length of password should be 8 ~ 40 characters."
   ::= { gs2328fTrapHostConfEntry 10 }

gs2328fTrapHostConfPrivPtc	OBJECT-TYPE
   SYNTAX       INTEGER { des(1) }
   MAX-ACCESS   read-write
   STATUS       current
   DESCRIPTION
       "This is the Privacy Protocol, which is used in AuthPriv. Only supports DES.
        An empty string will be returned if the security level is not 3(AuthPriv).
        1 : DES."
	::= { gs2328fTrapHostConfEntry 11 }

gs2328fTrapHostConfPrivPassword	OBJECT-TYPE
   SYNTAX       DisplayString
   MAX-ACCESS   read-write
   STATUS       current
   DESCRIPTION
       "The password is Privacy Key.  The return value is always '********'.  This Key
        must be more than 8 characters, and less than 32 characters."
   ::= { gs2328fTrapHostConfEntry 12 }

gs2328fTrapHostConfCurrentMode OBJECT-TYPE
   SYNTAX       INTEGER { empty(0), active(1), edit(2), delete(3) }
   MAX-ACCESS   read-write
   STATUS       current
   DESCRIPTION
       "0:Empty, 1:Active mode, 2:Edit mode, 3:Delete."
   ::= { gs2328fTrapHostConfEntry 13 }


gs2328fSnmpSystem                                          OBJECT IDENTIFIER ::= { gs2328fSnmp 2 }

gs2328fSnmpState OBJECT-TYPE
   SYNTAX       INTEGER { disable(0), enable(1) }
   MAX-ACCESS   read-write
   STATUS       current
   DESCRIPTION
       "Get/Set the state of the SNMP.
        default : 1, 0: disable, 1: enable. "
   ::= { gs2328fSnmpSystem 1 }

gs2328fSnmpEngineID OBJECT-TYPE
   SYNTAX       OCTET STRING (SIZE(5..32))
   MAX-ACCESS   read-write
   STATUS       current
   DESCRIPTION
       "Get/Set the Engine ID of the SNMP.
        An SNMP engine's administratively-unique identifier."
   ::= { gs2328fSnmpSystem 2 }

gs2328fSnmpCommunities                                          OBJECT IDENTIFIER ::= { gs2328fSnmp 3 }

gs2328fSnmpCommunitiesCreate OBJECT-TYPE
   SYNTAX       INTEGER { none(0), create(1) }
   MAX-ACCESS   read-write
   STATUS       current
   DESCRIPTION
       "default: 0
        0 : None  (read only)
        1 : Create entry"
   ::= { gs2328fSnmpCommunities 1 }

gs2328fSnmpCommunitiesTable OBJECT-TYPE
   SYNTAX      SEQUENCE OF GS2328FSnmpCommunitiesEntry
   MAX-ACCESS  not-accessible
   STATUS      current
   DESCRIPTION
       " Create SNMPv1/v2 Communities entry."
   ::= { gs2328fSnmpCommunities 2 }

gs2328fSnmpCommunitiesEntry OBJECT-TYPE
   SYNTAX      GS2328FSnmpCommunitiesEntry
   MAX-ACCESS  not-accessible
   STATUS      current
   DESCRIPTION
       ""
   INDEX    { gs2328fSnmpCommunitiesIndex  }
   ::= { gs2328fSnmpCommunitiesTable 1 }

GS2328FSnmpCommunitiesEntry ::= SEQUENCE {
   gs2328fSnmpCommunitiesIndex          Integer32,
   gs2328fSnmpCommunitiesCommunity      DisplayString,
   gs2328fSnmpCommunitiesUserName       DisplayString,
   gs2328fSnmpCommunitiesSourceIP       IpAddress,
   gs2328fSnmpCommunitiesSourceMask     IpAddress,
   gs2328fSnmpCommunitiesRowStatus      INTEGER
}

gs2328fSnmpCommunitiesIndex OBJECT-TYPE
   SYNTAX      Integer32(1..4)
   MAX-ACCESS  not-accessible
   STATUS      current
   DESCRIPTION
       " "
   ::= { gs2328fSnmpCommunitiesEntry 1 }

gs2328fSnmpCommunitiesCommunity OBJECT-TYPE
   SYNTAX      DisplayString (SIZE (1..32))
   MAX-ACCESS  read-write
   STATUS      current
   DESCRIPTION
       "Up to 32 characters describing Community."
   ::= { gs2328fSnmpCommunitiesEntry 2 }

gs2328fSnmpCommunitiesUserName OBJECT-TYPE
   SYNTAX      DisplayString (SIZE (1..32))
   MAX-ACCESS  read-write
   STATUS      current
   DESCRIPTION
       " Up to 32 characters describing User Name. "
   ::= { gs2328fSnmpCommunitiesEntry 3 }

gs2328fSnmpCommunitiesSourceIP OBJECT-TYPE
   SYNTAX      IpAddress
   MAX-ACCESS  read-write
   STATUS      current
   DESCRIPTION
       " SNMP access source ip. "
   ::= { gs2328fSnmpCommunitiesEntry 4 }

gs2328fSnmpCommunitiesSourceMask OBJECT-TYPE
   SYNTAX      IpAddress
   MAX-ACCESS  read-write
   STATUS      current
   DESCRIPTION
       " SNMP access source address mask. "
   ::= { gs2328fSnmpCommunitiesEntry 5 }

gs2328fSnmpCommunitiesRowStatus OBJECT-TYPE
   SYNTAX      INTEGER { active(1), notInservice(2), destroy(4), undo(5) }
   MAX-ACCESS  read-write
   STATUS      current
   DESCRIPTION
       "1: active
        2: notInservice
        4: destroy
        5: undo"
   ::= { gs2328fSnmpCommunitiesEntry 6 }


gs2328fSnmpUsers                                          OBJECT IDENTIFIER ::= { gs2328fSnmp 4 }

gs2328fSnmpUsersCreate OBJECT-TYPE
   SYNTAX       INTEGER { none(0), create(1) }
   MAX-ACCESS   read-write
   STATUS       current
   DESCRIPTION
       "default: 0
        0 : None  (read only)
        1 : Create entry"
   ::= { gs2328fSnmpUsers 1 }

gs2328fSnmpUsersTable OBJECT-TYPE
   SYNTAX      SEQUENCE OF GS2328FSnmpUsersEntry
   MAX-ACCESS  not-accessible
   STATUS      current
   DESCRIPTION
       " Create SNMPv3 users entry."
   ::= { gs2328fSnmpUsers 2 }

gs2328fSnmpUsersEntry OBJECT-TYPE
   SYNTAX      GS2328FSnmpUsersEntry
   MAX-ACCESS  not-accessible
   STATUS      current
   DESCRIPTION
       ""
   INDEX    { gs2328fSnmpUsersIndex  }
   ::= { gs2328fSnmpUsersTable 1 }

GS2328FSnmpUsersEntry ::= SEQUENCE {
   gs2328fSnmpUsersIndex                    Integer32,
   gs2328fSnmpUsersUserName                 DisplayString,
   gs2328fSnmpUsersSecurityLevel            INTEGER,
   gs2328fSnmpUsersAuthenticationProtocol   INTEGER,
   gs2328fSnmpUsersAuthenticationPassword   DisplayString,
   gs2328fSnmpUsersPrivacyProtocol          INTEGER,
   gs2328fSnmpUsersPrivacyPassword          DisplayString,
   gs2328fSnmpUsersRowStatus                INTEGER
}

gs2328fSnmpUsersIndex OBJECT-TYPE
   SYNTAX      Integer32(1..10)
   MAX-ACCESS  not-accessible
   STATUS      current
   DESCRIPTION
       " "
   ::= { gs2328fSnmpUsersEntry 1 }

gs2328fSnmpUsersUserName OBJECT-TYPE
   SYNTAX      DisplayString (SIZE (1..32))
   MAX-ACCESS  read-write
   STATUS      current
   DESCRIPTION
       "Up to 32 characters describing User Name."
   ::= { gs2328fSnmpUsersEntry 2 }

gs2328fSnmpUsersSecurityLevel OBJECT-TYPE
   SYNTAX      INTEGER { noauthnopriv(1), authnopriv(2), authpriv(3) }
   MAX-ACCESS  read-write
   STATUS      current
   DESCRIPTION
       " 1: No authentication and no privacy.
         2: Authentication and no privacy.
         3: Authentication and privacy. "
   ::= { gs2328fSnmpUsersEntry 3 }

gs2328fSnmpUsersAuthenticationProtocol OBJECT-TYPE
   SYNTAX      INTEGER { none(0), md5(1), sha(2) }
   MAX-ACCESS  read-write
   STATUS      current
   DESCRIPTION
       " 0: None.
         1: MD5.
         2: SHA "
   ::= { gs2328fSnmpUsersEntry 4 }

gs2328fSnmpUsersAuthenticationPassword OBJECT-TYPE
   SYNTAX      DisplayString
   MAX-ACCESS  read-write
   STATUS      current
   DESCRIPTION
       " Authentication Password, is used for authenticating. The return value is always '********'.
         If the authentication protocol is MD5, the length of password should be 8 ~ 32 characters.
         If the authentication protocol is SHA, the length of password should be 8 ~ 40 characters. "
   ::= { gs2328fSnmpUsersEntry 5 }

gs2328fSnmpUsersPrivacyProtocol OBJECT-TYPE
   SYNTAX      INTEGER { none(0), des(1), aes(2) }
   MAX-ACCESS  read-write
   STATUS      current
   DESCRIPTION
       " 0: None.
         1: DES.
         2: AES
         This is the Privacy Protocol, which is used in AuthPriv.
         An empty string will be returned if the security level is not 3(AuthPriv) "
   ::= { gs2328fSnmpUsersEntry 6 }

gs2328fSnmpUsersPrivacyPassword OBJECT-TYPE
   SYNTAX      DisplayString
   MAX-ACCESS  read-write
   STATUS      current
   DESCRIPTION
       " The password is Privacy Key.  The return value is always '********'.  This Key
        must be more than 8 characters, and less than 32 characters. "
   ::= { gs2328fSnmpUsersEntry 7 }

gs2328fSnmpUsersRowStatus OBJECT-TYPE
   SYNTAX      INTEGER { active(1), notInservice(2), destroy(4), undo(5) }
   MAX-ACCESS  read-write
   STATUS      current
   DESCRIPTION
       "1: active
        2: notInservice
        4: destroy
        5: undo"
   ::= { gs2328fSnmpUsersEntry 8 }


gs2328fSnmpGroups                                          OBJECT IDENTIFIER ::= { gs2328fSnmp 5 }

gs2328fSnmpGroupsCreate OBJECT-TYPE
   SYNTAX       INTEGER { none(0), create(1) }
   MAX-ACCESS   read-write
   STATUS       current
   DESCRIPTION
       "default: 0
        0 : None  (read only)
        1 : Create entry"
   ::= { gs2328fSnmpGroups 1 }

gs2328fSnmpGroupsTable OBJECT-TYPE
   SYNTAX      SEQUENCE OF GS2328FSnmpGroupsEntry
   MAX-ACCESS  not-accessible
   STATUS      current
   DESCRIPTION
       " Create SNMPv3 groups entry."
   ::= { gs2328fSnmpGroups 2 }

gs2328fSnmpGroupsEntry OBJECT-TYPE
   SYNTAX      GS2328FSnmpGroupsEntry
   MAX-ACCESS  not-accessible
   STATUS      current
   DESCRIPTION
       ""
   INDEX    { gs2328fSnmpGroupsIndex  }
   ::= { gs2328fSnmpGroupsTable 1 }

GS2328FSnmpGroupsEntry ::= SEQUENCE {
   gs2328fSnmpGroupsIndex           Integer32,
   gs2328fSnmpGroupsSecurityModel   INTEGER,
   gs2328fSnmpGroupsSecurityName    DisplayString,
   gs2328fSnmpGroupsGroupName       DisplayString,
   gs2328fSnmpGroupsRowStatus       INTEGER
}

gs2328fSnmpGroupsIndex OBJECT-TYPE
   SYNTAX      Integer32(1..14)
   MAX-ACCESS  not-accessible
   STATUS      current
   DESCRIPTION
       " "
   ::= { gs2328fSnmpGroupsEntry 1 }

gs2328fSnmpGroupsSecurityModel OBJECT-TYPE
   SYNTAX      INTEGER { v1(1), v2c(2), usm(3) }
   MAX-ACCESS  read-write
   STATUS      current
   DESCRIPTION
       " 1: v1.
         2: v2c.
         3: usm."
   ::= { gs2328fSnmpGroupsEntry 2 }

gs2328fSnmpGroupsSecurityName OBJECT-TYPE
   SYNTAX      DisplayString (SIZE (1..32))
   MAX-ACCESS  read-write
   STATUS      current
   DESCRIPTION
       "Up to 32 characters describing User Name."
   ::= { gs2328fSnmpGroupsEntry 3 }

gs2328fSnmpGroupsGroupName OBJECT-TYPE
   SYNTAX      DisplayString (SIZE (1..32))
   MAX-ACCESS  read-write
   STATUS      current
   DESCRIPTION
       "Up to 32 characters describing Group Name."
   ::= { gs2328fSnmpGroupsEntry 4 }

gs2328fSnmpGroupsRowStatus OBJECT-TYPE
   SYNTAX      INTEGER { active(1), notInservice(2), destroy(4), undo(5) }
   MAX-ACCESS  read-write
   STATUS      current
   DESCRIPTION
       "1: active
        2: notInservice
        4: destroy
        5: undo"
   ::= { gs2328fSnmpGroupsEntry 5 }

gs2328fSnmpViews                                              OBJECT IDENTIFIER ::= { gs2328fSnmp 6 }

gs2328fSnmpViewsCreate OBJECT-TYPE
   SYNTAX       INTEGER { none(0), create(1) }
   MAX-ACCESS   read-write
   STATUS       current
   DESCRIPTION
       "default: 0
        0 : None  (read only)
        1 : Create entry"
   ::= { gs2328fSnmpViews 1 }

gs2328fSnmpViewsTable OBJECT-TYPE
   SYNTAX      SEQUENCE OF GS2328FSnmpViewsEntry
   MAX-ACCESS  not-accessible
   STATUS      current
   DESCRIPTION
       " Create SNMPv1/v2 Views entry."
   ::= { gs2328fSnmpViews 2 }

gs2328fSnmpViewsEntry OBJECT-TYPE
   SYNTAX      GS2328FSnmpViewsEntry
   MAX-ACCESS  not-accessible
   STATUS      current
   DESCRIPTION
       ""
   INDEX    { gs2328fSnmpViewsIndex  }
   ::= { gs2328fSnmpViewsTable 1 }

GS2328FSnmpViewsEntry ::= SEQUENCE {
   gs2328fSnmpViewsIndex        Integer32,
   gs2328fSnmpViewsName         DisplayString,
   gs2328fSnmpViewsType         INTEGER,
   gs2328fSnmpViewsOIDSubtree   DisplayString,
   gs2328fSnmpViewsRowStatus    INTEGER
}

gs2328fSnmpViewsIndex OBJECT-TYPE
   SYNTAX      Integer32(1..4)
   MAX-ACCESS  not-accessible
   STATUS      current
   DESCRIPTION
       " "
   ::= { gs2328fSnmpViewsEntry 1 }

gs2328fSnmpViewsName OBJECT-TYPE
   SYNTAX      DisplayString (SIZE (1..32))
   MAX-ACCESS  read-write
   STATUS      current
   DESCRIPTION
       "Up to 32 characters describing view Name."
   ::= { gs2328fSnmpViewsEntry 2 }

gs2328fSnmpViewsType OBJECT-TYPE
   SYNTAX      INTEGER { included(1), excluded(2) }
   MAX-ACCESS  read-write
   STATUS      current
   DESCRIPTION
       "1: included, An optional flag to indicate that this view subtree should be included.
	   2: excluded, An optional flag to indicate that this view subtree should be excluded."
   ::= { gs2328fSnmpViewsEntry 3 }

gs2328fSnmpViewsOIDSubtree OBJECT-TYPE
   SYNTAX      DisplayString (SIZE (1..128))
   MAX-ACCESS  read-write
   STATUS      current
   DESCRIPTION
       "The OID defining the root of the subtree to add to the named view."
   ::= { gs2328fSnmpViewsEntry 4 }

gs2328fSnmpViewsRowStatus OBJECT-TYPE
   SYNTAX      INTEGER { active(1), notInservice(2), destroy(4), undo(5) }
   MAX-ACCESS  read-write
   STATUS      current
   DESCRIPTION
       "1: active
        2: notInservice
        4: destroy
        5: undo"
   ::= { gs2328fSnmpViewsEntry 5 }


gs2328fSnmpAccess                                          OBJECT IDENTIFIER ::= { gs2328fSnmp 7 }

gs2328fSnmpAccessCreate OBJECT-TYPE
   SYNTAX       INTEGER { none(0), create(1) }
   MAX-ACCESS   read-write
   STATUS       current
   DESCRIPTION
       "default: 0
        0 : None  (read only)
        1 : Create entry"
   ::= { gs2328fSnmpAccess 1 }

gs2328fSnmpAccessTable OBJECT-TYPE
   SYNTAX      SEQUENCE OF GS2328FSnmpAccessEntry
   MAX-ACCESS  not-accessible
   STATUS      current
   DESCRIPTION
       " Create SNMPv3 Access entry."
   ::= { gs2328fSnmpAccess 2 }

gs2328fSnmpAccessEntry OBJECT-TYPE
   SYNTAX      GS2328FSnmpAccessEntry
   MAX-ACCESS  not-accessible
   STATUS      current
   DESCRIPTION
       ""
   INDEX    { gs2328fSnmpAccessIndex  }
   ::= { gs2328fSnmpAccessTable 1 }

GS2328FSnmpAccessEntry ::= SEQUENCE {
   gs2328fSnmpAccessIndex             Integer32,
   gs2328fSnmpAccessGroupName         DisplayString,
   gs2328fSnmpAccessSecurityModel     INTEGER,
   gs2328fSnmpAccessSecurityLevel     INTEGER,
   gs2328fSnmpAccessReadViewName      DisplayString,
   gs2328fSnmpAccessWriteViewName     DisplayString,
   gs2328fSnmpAccessRowStatus         INTEGER
}

gs2328fSnmpAccessIndex OBJECT-TYPE
   SYNTAX      Integer32(1..14)
   MAX-ACCESS  not-accessible
   STATUS      current
   DESCRIPTION
       " "
   ::= { gs2328fSnmpAccessEntry 1 }

gs2328fSnmpAccessGroupName OBJECT-TYPE
   SYNTAX      DisplayString (SIZE (1..32))
   MAX-ACCESS  read-write
   STATUS      current
   DESCRIPTION
       "Up to 32 characters describing Group Name."
   ::= { gs2328fSnmpAccessEntry 2 }

gs2328fSnmpAccessSecurityModel OBJECT-TYPE
   SYNTAX      INTEGER { any(0), v1(1), v2c(2), usm(3) }
   MAX-ACCESS  read-write
   STATUS      current
   DESCRIPTION
       " 0: any.
         1: v1.
         2: v2c.
         3: usm."
   ::= { gs2328fSnmpAccessEntry 3 }

gs2328fSnmpAccessSecurityLevel OBJECT-TYPE
   SYNTAX      INTEGER { noauthnopriv(1), authnopriv(2), authpriv(3) }
   MAX-ACCESS  read-write
   STATUS      current
   DESCRIPTION
       " 1: No authentication and no privacy.
         2: Authentication and no privacy.
         3: Authentication and privacy. "
   ::= { gs2328fSnmpAccessEntry 4 }

gs2328fSnmpAccessReadViewName OBJECT-TYPE
   SYNTAX      DisplayString (SIZE (1..32))
   MAX-ACCESS  read-write
   STATUS      current
   DESCRIPTION
       "Up to 32 characters describing Read View Name.
        None is reserved for Empty."
   ::= { gs2328fSnmpAccessEntry 5 }

gs2328fSnmpAccessWriteViewName OBJECT-TYPE
   SYNTAX      DisplayString (SIZE (1..32))
   MAX-ACCESS  read-write
   STATUS      current
   DESCRIPTION
       "Up to 32 characters describing Write View Name.
        None is reserved for Empty."
   ::= { gs2328fSnmpAccessEntry 6 }

gs2328fSnmpAccessRowStatus OBJECT-TYPE
   SYNTAX      INTEGER { active(1), notInservice(2), destroy(4), undo(5) }
   MAX-ACCESS  read-write
   STATUS      current
   DESCRIPTION
       "1: active
        2: notInservice
        4: destroy
        5: undo"
   ::= { gs2328fSnmpAccessEntry 7 }


----------------------------------------------------------------------------------------------------

gs2328fConfiguration                                         OBJECT IDENTIFIER ::= { lancomGS2328F  2 }

gs2328fPort                                                  OBJECT IDENTIFIER ::= { gs2328fConfiguration 1 }

gs2328fPortConfigurationTable OBJECT-TYPE
   SYNTAX      SEQUENCE OF GS2328FPortConfigurationEntry
   MAX-ACCESS  not-accessible
   STATUS      current
   DESCRIPTION
       " Show port configurations. "
   ::= { gs2328fPort 1 }

gs2328fPortConfigurationEntry OBJECT-TYPE
   SYNTAX      GS2328FPortConfigurationEntry
   MAX-ACCESS  not-accessible
   STATUS      current
   DESCRIPTION
       ""
   INDEX    { gs2328fPortConfPort  }
   ::= { gs2328fPortConfigurationTable 1 }

GS2328FPortConfigurationEntry ::= SEQUENCE {
   gs2328fPortConfPort                     Integer32,
   gs2328fPortConfPortMedia                DisplayString,
   gs2328fPortConfLink                     DisplayString,
   gs2328fPortConfCurrentSpeed             DisplayString,
   gs2328fPortConfSpeed                    INTEGER,
   gs2328fPortConfCurrentFlowControlRx     INTEGER,
   gs2328fPortConfCurrentFlowControlTx     INTEGER,
   gs2328fPortConfFlowControl              INTEGER,
   gs2328fPortConfMaxFrameSize             Integer32,
   gs2328fPortConfExcessiveCollisionMode   INTEGER,
   gs2328fPortConfPowerControl             INTEGER,
   gs2328fPortConfDescription              DisplayString
}

gs2328fPortConfPort OBJECT-TYPE
   SYNTAX      Integer32(1..4095)
   MAX-ACCESS  not-accessible
   STATUS      current
   DESCRIPTION
       " port, range : 1 - port number. "
   ::= { gs2328fPortConfigurationEntry 1 }

gs2328fPortConfPortMedia OBJECT-TYPE
   SYNTAX      DisplayString(SIZE (1..4))
   MAX-ACCESS  read-only
   STATUS      current
   DESCRIPTION
       " Show port media. "
   ::= { gs2328fPortConfigurationEntry 2 }

gs2328fPortConfLink OBJECT-TYPE
   SYNTAX      DisplayString(SIZE (2..4))
   MAX-ACCESS  read-only
   STATUS      current
   DESCRIPTION
       " The current link state. "
   ::= { gs2328fPortConfigurationEntry 3 }

gs2328fPortConfCurrentSpeed OBJECT-TYPE
   SYNTAX      DisplayString(SIZE (6..12))
   MAX-ACCESS  read-only
   STATUS      current
   DESCRIPTION
       " The current link speed of the port. "
   ::= { gs2328fPortConfigurationEntry 4 }

gs2328fPortConfSpeed OBJECT-TYPE
   SYNTAX      INTEGER {
                    disable(0),
                    auto(1),
                    speed10Half(2),
                    speed10Full(3),
                    speed100Half(4),
                    speed100Full(5),
                    speed1Gfull(6),
                    sfpAutoAMS(7),
                    speed100FXAMS(8),
                    speed1000XAMS(9),
                    speed100FX(10),
                    speed1000X(11),
                    speed10GFull(12)
                }
   MAX-ACCESS  read-write
   STATUS      current
   DESCRIPTION
       "default: 1,
        0: disable state,
        1: auto,
        2: 10 Half,
        3: 10 Full,
        4: 100 Half,
        5: 100 Full,
        6: 1G full,
        only 'Dual Media' port have 7-11 option.
        Dual Media port default: 7,
        7: SFP_Auto_AMS,
        8: 100FX_AMS,
        9: 1000X_AMS,
        10: 100FX,
        11: 1000X,
        12: 10G Full. "
   ::= { gs2328fPortConfigurationEntry 5 }

gs2328fPortConfCurrentFlowControlRx OBJECT-TYPE
   SYNTAX      INTEGER { disable(0), enable(1), noSupport(2) }
   MAX-ACCESS  read-only
   STATUS      current
   DESCRIPTION
       "0: disable
        1: enable
        2: no support.  "
   ::= { gs2328fPortConfigurationEntry 6 }

gs2328fPortConfCurrentFlowControlTx OBJECT-TYPE
   SYNTAX      INTEGER { disable(0), enable(1), noSupport(2) }
   MAX-ACCESS  read-only
   STATUS      current
   DESCRIPTION
       "0: disable
        1: enable
        2: no support.  "
   ::= { gs2328fPortConfigurationEntry 7 }

gs2328fPortConfFlowControl OBJECT-TYPE
   SYNTAX      INTEGER { disable(0), enable(1), noSupport(2) }
   MAX-ACCESS  read-write
   STATUS      current
   DESCRIPTION
       "default: 0,
        0: disable
        1: enable
        2: no support. "
   ::= { gs2328fPortConfigurationEntry 8 }

gs2328fPortConfMaxFrameSize OBJECT-TYPE
   SYNTAX      Integer32 (1518..9600)
   MAX-ACCESS  read-write
   STATUS      current
   DESCRIPTION
       "default: 9600 , range : 1518 - 9600 "
   ::= { gs2328fPortConfigurationEntry 9 }

gs2328fPortConfExcessiveCollisionMode OBJECT-TYPE
   SYNTAX      INTEGER { discard(0), restart(1), noSupport(2) }
   MAX-ACCESS  read-write
   STATUS      current
   DESCRIPTION
       "default: 0,
        Excessive Collision Mode :
        0: Discard,
        1: Restart,
        2: no support.
       "
   ::= { gs2328fPortConfigurationEntry 10 }

gs2328fPortConfPowerControl OBJECT-TYPE
   SYNTAX      INTEGER { disable(0), actiphy(1), dynamic(2), enable(3), noSupport(4) }
   MAX-ACCESS  read-write
   STATUS      current
   DESCRIPTION
       "default: 0,
        PowerControl :
        0: disable,
        1: Actiphy,
        2: Dynamic (perfectReach),
        3: Enable,
        4: no support.
       "
   ::= { gs2328fPortConfigurationEntry 11 }

gs2328fPortConfDescription OBJECT-TYPE
   SYNTAX      DisplayString
   MAX-ACCESS  read-write
   STATUS      current
   DESCRIPTION
       " Interface specific description.
         Up to 47 characters describing this interface. "
   ::= { gs2328fPortConfigurationEntry 12 }


gs2328fPortTrafficStatisticsTable OBJECT-TYPE
   SYNTAX      SEQUENCE OF GS2328FPortTrafficStatisticsEntry
   MAX-ACCESS  not-accessible
   STATUS      current
   DESCRIPTION
       " "
   ::= { gs2328fPort 2 }

gs2328fPortTrafficStatisticsEntry OBJECT-TYPE
   SYNTAX      GS2328FPortTrafficStatisticsEntry
   MAX-ACCESS  not-accessible
   STATUS      current
   DESCRIPTION
       ""
   INDEX    { gs2328fPortTrafficStatisticsPort  }
   ::= { gs2328fPortTrafficStatisticsTable 1 }

GS2328FPortTrafficStatisticsEntry ::= SEQUENCE {
   gs2328fPortTrafficStatisticsPort          Integer32,
   gs2328fPortTrafficStatisticsClear         INTEGER,
   gs2328fPortTrafficRxPackets               Counter64,
   gs2328fPortTrafficRxOctets                Counter64,
   gs2328fPortTrafficRxUnicast               Counter64,
   gs2328fPortTrafficRxMulticast             Counter64,
   gs2328fPortTrafficRxBroadcast             Counter64,
   gs2328fPortTrafficRxPause                 Counter64,
   gs2328fPortTrafficRx64Bytes               Counter64,
   gs2328fPortTrafficRx65to127Bytes          Counter64,
   gs2328fPortTrafficRx128to255Bytes         Counter64,
   gs2328fPortTrafficRx256to511Bytes         Counter64,
   gs2328fPortTrafficRx512to1023Bytes        Counter64,
   gs2328fPortTrafficRx1024to1526Bytes       Counter64,
   gs2328fPortTrafficRxExceecd1527Bytes      Counter64,
   gs2328fPortTrafficRxQ0                    Counter64,
   gs2328fPortTrafficRxQ1                    Counter64,
   gs2328fPortTrafficRxQ2                    Counter64,
   gs2328fPortTrafficRxQ3                    Counter64,
   gs2328fPortTrafficRxQ4                    Counter64,
   gs2328fPortTrafficRxQ5                    Counter64,
   gs2328fPortTrafficRxQ6                    Counter64,
   gs2328fPortTrafficRxQ7                    Counter64,
   gs2328fPortTrafficRxDrops                 Counter64,
   gs2328fPortTrafficRxCRCorAlignment        Counter64,
   gs2328fPortTrafficRxUndersize             Counter64,
   gs2328fPortTrafficRxOversize              Counter64,
   gs2328fPortTrafficRxFragments             Counter64,
   gs2328fPortTrafficRxJabber                Counter64,
   gs2328fPortTrafficRxFiltered              Counter64,
   gs2328fPortTrafficTxPackets               Counter64,
   gs2328fPortTrafficTxOctets                Counter64,
   gs2328fPortTrafficTxUnicast               Counter64,
   gs2328fPortTrafficTxMulticast             Counter64,
   gs2328fPortTrafficTxBroadcast             Counter64,
   gs2328fPortTrafficTxPause                 Counter64,
   gs2328fPortTrafficTx64Bytes               Counter64,
   gs2328fPortTrafficTx65to127Bytes          Counter64,
   gs2328fPortTrafficTx128to255Bytes         Counter64,
   gs2328fPortTrafficTx256to511Bytes         Counter64,
   gs2328fPortTrafficTx512to1023Bytes        Counter64,
   gs2328fPortTrafficTx1024to1526Bytes       Counter64,
   gs2328fPortTrafficTxExceecd1527Bytes      Counter64,
   gs2328fPortTrafficTxQ0                    Counter64,
   gs2328fPortTrafficTxQ1                    Counter64,
   gs2328fPortTrafficTxQ2                    Counter64,
   gs2328fPortTrafficTxQ3                    Counter64,
   gs2328fPortTrafficTxQ4                    Counter64,
   gs2328fPortTrafficTxQ5                    Counter64,
   gs2328fPortTrafficTxQ6                    Counter64,
   gs2328fPortTrafficTxQ7                    Counter64,
   gs2328fPortTrafficTxDrops                 Counter64,
   gs2328fPortTrafficTxLateOrExcColl         Counter64
}

gs2328fPortTrafficStatisticsPort OBJECT-TYPE
   SYNTAX      Integer32 (1..4095)
   MAX-ACCESS  not-accessible
   STATUS      current
   DESCRIPTION
       " "
   ::= { gs2328fPortTrafficStatisticsEntry 1 }

gs2328fPortTrafficStatisticsClear OBJECT-TYPE
   SYNTAX      INTEGER { disable(0), enable(1) }
   MAX-ACCESS  read-write
   STATUS      current
   DESCRIPTION
       " "
   ::= { gs2328fPortTrafficStatisticsEntry 2 }

gs2328fPortTrafficRxPackets OBJECT-TYPE
   SYNTAX      Counter64
   MAX-ACCESS  read-only
   STATUS      current
   DESCRIPTION
       " "
   ::= { gs2328fPortTrafficStatisticsEntry 3 }

gs2328fPortTrafficRxOctets OBJECT-TYPE
   SYNTAX      Counter64
   MAX-ACCESS  read-only
   STATUS      current
   DESCRIPTION
       " "
   ::= { gs2328fPortTrafficStatisticsEntry 4 }

gs2328fPortTrafficRxUnicast OBJECT-TYPE
   SYNTAX      Counter64
   MAX-ACCESS  read-only
   STATUS      current
   DESCRIPTION
       " "
   ::= { gs2328fPortTrafficStatisticsEntry 5 }

gs2328fPortTrafficRxMulticast OBJECT-TYPE
   SYNTAX      Counter64
   MAX-ACCESS  read-only
   STATUS      current
   DESCRIPTION
       " "
   ::= { gs2328fPortTrafficStatisticsEntry 6 }

gs2328fPortTrafficRxBroadcast OBJECT-TYPE
   SYNTAX      Counter64
   MAX-ACCESS  read-only
   STATUS      current
   DESCRIPTION
       " "
   ::= { gs2328fPortTrafficStatisticsEntry 7 }

gs2328fPortTrafficRxPause OBJECT-TYPE
   SYNTAX      Counter64
   MAX-ACCESS  read-only
   STATUS      current
   DESCRIPTION
       " "
   ::= { gs2328fPortTrafficStatisticsEntry 8 }

gs2328fPortTrafficRx64Bytes OBJECT-TYPE
   SYNTAX      Counter64
   MAX-ACCESS  read-only
   STATUS      current
   DESCRIPTION
       " "
   ::= { gs2328fPortTrafficStatisticsEntry 9 }

gs2328fPortTrafficRx65to127Bytes OBJECT-TYPE
   SYNTAX      Counter64
   MAX-ACCESS  read-only
   STATUS      current
   DESCRIPTION
       " "
   ::= { gs2328fPortTrafficStatisticsEntry 10 }

gs2328fPortTrafficRx128to255Bytes OBJECT-TYPE
   SYNTAX      Counter64
   MAX-ACCESS  read-only
   STATUS      current
   DESCRIPTION
       " "
   ::= { gs2328fPortTrafficStatisticsEntry 11 }

gs2328fPortTrafficRx256to511Bytes OBJECT-TYPE
   SYNTAX      Counter64
   MAX-ACCESS  read-only
   STATUS      current
   DESCRIPTION
       " "
   ::= { gs2328fPortTrafficStatisticsEntry 12 }

gs2328fPortTrafficRx512to1023Bytes OBJECT-TYPE
   SYNTAX      Counter64
   MAX-ACCESS  read-only
   STATUS      current
   DESCRIPTION
       " "
   ::= { gs2328fPortTrafficStatisticsEntry 13 }

gs2328fPortTrafficRx1024to1526Bytes OBJECT-TYPE
   SYNTAX      Counter64
   MAX-ACCESS  read-only
   STATUS      current
   DESCRIPTION
       " "
   ::= { gs2328fPortTrafficStatisticsEntry 14 }

gs2328fPortTrafficRxExceecd1527Bytes OBJECT-TYPE
   SYNTAX      Counter64
   MAX-ACCESS  read-only
   STATUS      current
   DESCRIPTION
       " "
   ::= { gs2328fPortTrafficStatisticsEntry 15 }

gs2328fPortTrafficRxQ0 OBJECT-TYPE
   SYNTAX      Counter64
   MAX-ACCESS  read-only
   STATUS      current
   DESCRIPTION
       " "
   ::= { gs2328fPortTrafficStatisticsEntry 16 }

gs2328fPortTrafficRxQ1 OBJECT-TYPE
   SYNTAX      Counter64
   MAX-ACCESS  read-only
   STATUS      current
   DESCRIPTION
       " "
   ::= { gs2328fPortTrafficStatisticsEntry 17 }

gs2328fPortTrafficRxQ2 OBJECT-TYPE
   SYNTAX      Counter64
   MAX-ACCESS  read-only
   STATUS      current
   DESCRIPTION
       " "
   ::= { gs2328fPortTrafficStatisticsEntry 18 }

gs2328fPortTrafficRxQ3 OBJECT-TYPE
   SYNTAX      Counter64
   MAX-ACCESS  read-only
   STATUS      current
   DESCRIPTION
       " "
   ::= { gs2328fPortTrafficStatisticsEntry 19 }

gs2328fPortTrafficRxQ4 OBJECT-TYPE
   SYNTAX      Counter64
   MAX-ACCESS  read-only
   STATUS      current
   DESCRIPTION
       " "
   ::= { gs2328fPortTrafficStatisticsEntry 20 }

gs2328fPortTrafficRxQ5 OBJECT-TYPE
   SYNTAX      Counter64
   MAX-ACCESS  read-only
   STATUS      current
   DESCRIPTION
       " "
   ::= { gs2328fPortTrafficStatisticsEntry 21 }

gs2328fPortTrafficRxQ6 OBJECT-TYPE
   SYNTAX      Counter64
   MAX-ACCESS  read-only
   STATUS      current
   DESCRIPTION
       " "
   ::= { gs2328fPortTrafficStatisticsEntry 22 }

gs2328fPortTrafficRxQ7 OBJECT-TYPE
   SYNTAX      Counter64
   MAX-ACCESS  read-only
   STATUS      current
   DESCRIPTION
       " "
   ::= { gs2328fPortTrafficStatisticsEntry 23 }

gs2328fPortTrafficRxDrops OBJECT-TYPE
   SYNTAX      Counter64
   MAX-ACCESS  read-only
   STATUS      current
   DESCRIPTION
       " "
   ::= { gs2328fPortTrafficStatisticsEntry 24 }

gs2328fPortTrafficRxCRCorAlignment OBJECT-TYPE
   SYNTAX      Counter64
   MAX-ACCESS  read-only
   STATUS      current
   DESCRIPTION
       " "
   ::= { gs2328fPortTrafficStatisticsEntry 25 }

gs2328fPortTrafficRxUndersize OBJECT-TYPE
   SYNTAX      Counter64
   MAX-ACCESS  read-only
   STATUS      current
   DESCRIPTION
       " "
   ::= { gs2328fPortTrafficStatisticsEntry 26 }

gs2328fPortTrafficRxOversize OBJECT-TYPE
   SYNTAX      Counter64
   MAX-ACCESS  read-only
   STATUS      current
   DESCRIPTION
       " "
   ::= { gs2328fPortTrafficStatisticsEntry 27 }

gs2328fPortTrafficRxFragments OBJECT-TYPE
   SYNTAX      Counter64
   MAX-ACCESS  read-only
   STATUS      current
   DESCRIPTION
       " "
   ::= { gs2328fPortTrafficStatisticsEntry 28 }

gs2328fPortTrafficRxJabber OBJECT-TYPE
   SYNTAX      Counter64
   MAX-ACCESS  read-only
   STATUS      current
   DESCRIPTION
       " "
   ::= { gs2328fPortTrafficStatisticsEntry 29 }

gs2328fPortTrafficRxFiltered OBJECT-TYPE
   SYNTAX      Counter64
   MAX-ACCESS  read-only
   STATUS      current
   DESCRIPTION
       " "
   ::= { gs2328fPortTrafficStatisticsEntry 30 }

gs2328fPortTrafficTxPackets OBJECT-TYPE
   SYNTAX      Counter64
   MAX-ACCESS  read-only
   STATUS      current
   DESCRIPTION
       " "
   ::= { gs2328fPortTrafficStatisticsEntry 31 }

gs2328fPortTrafficTxOctets OBJECT-TYPE
   SYNTAX      Counter64
   MAX-ACCESS  read-only
   STATUS      current
   DESCRIPTION
       " "
   ::= { gs2328fPortTrafficStatisticsEntry 32 }

gs2328fPortTrafficTxUnicast OBJECT-TYPE
   SYNTAX      Counter64
   MAX-ACCESS  read-only
   STATUS      current
   DESCRIPTION
       " "
   ::= { gs2328fPortTrafficStatisticsEntry 33 }

gs2328fPortTrafficTxMulticast OBJECT-TYPE
   SYNTAX      Counter64
   MAX-ACCESS  read-only
   STATUS      current
   DESCRIPTION
       " "
   ::= { gs2328fPortTrafficStatisticsEntry 34 }

gs2328fPortTrafficTxBroadcast OBJECT-TYPE
   SYNTAX      Counter64
   MAX-ACCESS  read-only
   STATUS      current
   DESCRIPTION
       " "
   ::= { gs2328fPortTrafficStatisticsEntry 35 }

gs2328fPortTrafficTxPause OBJECT-TYPE
   SYNTAX      Counter64
   MAX-ACCESS  read-only
   STATUS      current
   DESCRIPTION
       " "
   ::= { gs2328fPortTrafficStatisticsEntry 36 }

gs2328fPortTrafficTx64Bytes OBJECT-TYPE
   SYNTAX      Counter64
   MAX-ACCESS  read-only
   STATUS      current
   DESCRIPTION
       " "
   ::= { gs2328fPortTrafficStatisticsEntry 37 }

gs2328fPortTrafficTx65to127Bytes OBJECT-TYPE
   SYNTAX      Counter64
   MAX-ACCESS  read-only
   STATUS      current
   DESCRIPTION
       " "
   ::= { gs2328fPortTrafficStatisticsEntry 38 }

gs2328fPortTrafficTx128to255Bytes OBJECT-TYPE
   SYNTAX      Counter64
   MAX-ACCESS  read-only
   STATUS      current
   DESCRIPTION
       " "
   ::= { gs2328fPortTrafficStatisticsEntry 39 }

gs2328fPortTrafficTx256to511Bytes OBJECT-TYPE
   SYNTAX      Counter64
   MAX-ACCESS  read-only
   STATUS      current
   DESCRIPTION
       " "
   ::= { gs2328fPortTrafficStatisticsEntry 40 }

gs2328fPortTrafficTx512to1023Bytes OBJECT-TYPE
   SYNTAX      Counter64
   MAX-ACCESS  read-only
   STATUS      current
   DESCRIPTION
       " "
   ::= { gs2328fPortTrafficStatisticsEntry 41 }

gs2328fPortTrafficTx1024to1526Bytes OBJECT-TYPE
   SYNTAX      Counter64
   MAX-ACCESS  read-only
   STATUS      current
   DESCRIPTION
       " "
   ::= { gs2328fPortTrafficStatisticsEntry 42 }

gs2328fPortTrafficTxExceecd1527Bytes OBJECT-TYPE
   SYNTAX      Counter64
   MAX-ACCESS  read-only
   STATUS      current
   DESCRIPTION
       " "
   ::= { gs2328fPortTrafficStatisticsEntry 43 }

gs2328fPortTrafficTxQ0 OBJECT-TYPE
   SYNTAX      Counter64
   MAX-ACCESS  read-only
   STATUS      current
   DESCRIPTION
       " "
   ::= { gs2328fPortTrafficStatisticsEntry 44 }

gs2328fPortTrafficTxQ1 OBJECT-TYPE
   SYNTAX      Counter64
   MAX-ACCESS  read-only
   STATUS      current
   DESCRIPTION
       " "
   ::= { gs2328fPortTrafficStatisticsEntry 45 }

gs2328fPortTrafficTxQ2 OBJECT-TYPE
   SYNTAX      Counter64
   MAX-ACCESS  read-only
   STATUS      current
   DESCRIPTION
       " "
   ::= { gs2328fPortTrafficStatisticsEntry 46 }

gs2328fPortTrafficTxQ3 OBJECT-TYPE
   SYNTAX      Counter64
   MAX-ACCESS  read-only
   STATUS      current
   DESCRIPTION
       " "
   ::= { gs2328fPortTrafficStatisticsEntry 47 }

gs2328fPortTrafficTxQ4 OBJECT-TYPE
   SYNTAX      Counter64
   MAX-ACCESS  read-only
   STATUS      current
   DESCRIPTION
       " "
   ::= { gs2328fPortTrafficStatisticsEntry 48 }

gs2328fPortTrafficTxQ5 OBJECT-TYPE
   SYNTAX      Counter64
   MAX-ACCESS  read-only
   STATUS      current
   DESCRIPTION
       " "
   ::= { gs2328fPortTrafficStatisticsEntry 49 }

gs2328fPortTrafficTxQ6 OBJECT-TYPE
   SYNTAX      Counter64
   MAX-ACCESS  read-only
   STATUS      current
   DESCRIPTION
       " "
   ::= { gs2328fPortTrafficStatisticsEntry 50 }


gs2328fPortTrafficTxQ7 OBJECT-TYPE
   SYNTAX      Counter64
   MAX-ACCESS  read-only
   STATUS      current
   DESCRIPTION
       " "
   ::= { gs2328fPortTrafficStatisticsEntry 51 }

gs2328fPortTrafficTxDrops OBJECT-TYPE
   SYNTAX      Counter64
   MAX-ACCESS  read-only
   STATUS      current
   DESCRIPTION
       " "
   ::= { gs2328fPortTrafficStatisticsEntry 52 }

gs2328fPortTrafficTxLateOrExcColl OBJECT-TYPE
   SYNTAX      Counter64
   MAX-ACCESS  read-only
   STATUS      current
   DESCRIPTION
       " "
   ::= { gs2328fPortTrafficStatisticsEntry 53 }


gs2328fPortQoSStatistics                                     OBJECT IDENTIFIER ::= { gs2328fPort 3 }

gs2328fPortQoSStatisticsClear OBJECT-TYPE
   SYNTAX      INTEGER { none(0), clear(1) }
   MAX-ACCESS  read-only
   STATUS      current
   DESCRIPTION
       "default: 0
       0: none
       1: clear "
   ::= { gs2328fPortQoSStatistics 1 }

gs2328fPortQoSStatisticsTable OBJECT-TYPE
   SYNTAX      SEQUENCE OF GS2328FPortQoSStatisticsEntry
   MAX-ACCESS  not-accessible
   STATUS      current
   DESCRIPTION
       " "
   ::= { gs2328fPortQoSStatistics 2 }

gs2328fPortQoSStatisticsEntry OBJECT-TYPE
   SYNTAX      GS2328FPortQoSStatisticsEntry
   MAX-ACCESS  not-accessible
   STATUS      current
   DESCRIPTION
       ""
   INDEX    { gs2328fPortQoSStatisticsPort  }
   ::= { gs2328fPortQoSStatisticsTable 1 }

GS2328FPortQoSStatisticsEntry ::= SEQUENCE {
   gs2328fPortQoSStatisticsPort      Integer32,
   gs2328fPortQoSQ0Rx                Counter64,
   gs2328fPortQoSQ0Tx                Counter64,
   gs2328fPortQoSQ1Rx                Counter64,
   gs2328fPortQoSQ1Tx                Counter64,
   gs2328fPortQoSQ2Rx                Counter64,
   gs2328fPortQoSQ2Tx                Counter64,
   gs2328fPortQoSQ3Rx                Counter64,
   gs2328fPortQoSQ3Tx                Counter64,
   gs2328fPortQoSQ4Rx                Counter64,
   gs2328fPortQoSQ4Tx                Counter64,
   gs2328fPortQoSQ5Rx                Counter64,
   gs2328fPortQoSQ5Tx                Counter64,
   gs2328fPortQoSQ6Rx                Counter64,
   gs2328fPortQoSQ6Tx                Counter64,
   gs2328fPortQoSQ7Rx                Counter64,
   gs2328fPortQoSQ7Tx                Counter64
}

gs2328fPortQoSStatisticsPort OBJECT-TYPE
   SYNTAX      Integer32(1..4095)
   MAX-ACCESS  not-accessible
   STATUS      current
   DESCRIPTION
       " "
   ::= { gs2328fPortQoSStatisticsEntry 1 }

gs2328fPortQoSQ0Rx OBJECT-TYPE
   SYNTAX      Counter64
   MAX-ACCESS  read-only
   STATUS      current
   DESCRIPTION
       " "
   ::= { gs2328fPortQoSStatisticsEntry 2 }

gs2328fPortQoSQ0Tx OBJECT-TYPE
   SYNTAX      Counter64
   MAX-ACCESS  read-only
   STATUS      current
   DESCRIPTION
       " "
   ::= { gs2328fPortQoSStatisticsEntry 3 }

gs2328fPortQoSQ1Rx OBJECT-TYPE
   SYNTAX      Counter64
   MAX-ACCESS  read-only
   STATUS      current
   DESCRIPTION
       " "
   ::= { gs2328fPortQoSStatisticsEntry 4 }

gs2328fPortQoSQ1Tx OBJECT-TYPE
   SYNTAX      Counter64
   MAX-ACCESS  read-only
   STATUS      current
   DESCRIPTION
       " "
   ::= { gs2328fPortQoSStatisticsEntry 5 }

gs2328fPortQoSQ2Rx OBJECT-TYPE
   SYNTAX      Counter64
   MAX-ACCESS  read-only
   STATUS      current
   DESCRIPTION
       " "
   ::= { gs2328fPortQoSStatisticsEntry 6 }

gs2328fPortQoSQ2Tx OBJECT-TYPE
   SYNTAX      Counter64
   MAX-ACCESS  read-only
   STATUS      current
   DESCRIPTION
       " "
   ::= { gs2328fPortQoSStatisticsEntry 7 }

gs2328fPortQoSQ3Rx OBJECT-TYPE
   SYNTAX      Counter64
   MAX-ACCESS  read-only
   STATUS      current
   DESCRIPTION
       " "
   ::= { gs2328fPortQoSStatisticsEntry 8 }

gs2328fPortQoSQ3Tx OBJECT-TYPE
   SYNTAX      Counter64
   MAX-ACCESS  read-only
   STATUS      current
   DESCRIPTION
       " "
   ::= { gs2328fPortQoSStatisticsEntry 9 }

gs2328fPortQoSQ4Rx OBJECT-TYPE
   SYNTAX      Counter64
   MAX-ACCESS  read-only
   STATUS      current
   DESCRIPTION
       " "
   ::= { gs2328fPortQoSStatisticsEntry 10 }

gs2328fPortQoSQ4Tx OBJECT-TYPE
   SYNTAX      Counter64
   MAX-ACCESS  read-only
   STATUS      current
   DESCRIPTION
       " "
   ::= { gs2328fPortQoSStatisticsEntry 11 }

gs2328fPortQoSQ5Rx OBJECT-TYPE
   SYNTAX      Counter64
   MAX-ACCESS  read-only
   STATUS      current
   DESCRIPTION
       " "
   ::= { gs2328fPortQoSStatisticsEntry 12 }

gs2328fPortQoSQ5Tx OBJECT-TYPE
   SYNTAX      Counter64
   MAX-ACCESS  read-only
   STATUS      current
   DESCRIPTION
       " "
   ::= { gs2328fPortQoSStatisticsEntry 13 }

gs2328fPortQoSQ6Rx OBJECT-TYPE
   SYNTAX      Counter64
   MAX-ACCESS  read-only
   STATUS      current
   DESCRIPTION
       " "
   ::= { gs2328fPortQoSStatisticsEntry 14 }

gs2328fPortQoSQ6Tx OBJECT-TYPE
   SYNTAX      Counter64
   MAX-ACCESS  read-only
   STATUS      current
   DESCRIPTION
       " "
   ::= { gs2328fPortQoSStatisticsEntry 15 }

gs2328fPortQoSQ7Rx OBJECT-TYPE
   SYNTAX      Counter64
   MAX-ACCESS  read-only
   STATUS      current
   DESCRIPTION
       " "
   ::= { gs2328fPortQoSStatisticsEntry 16 }

gs2328fPortQoSQ7Tx OBJECT-TYPE
   SYNTAX      Counter64
   MAX-ACCESS  read-only
   STATUS      current
   DESCRIPTION
       " "
   ::= { gs2328fPortQoSStatisticsEntry 17 }

gs2328fSFPInfoTable OBJECT-TYPE
   SYNTAX      SEQUENCE OF GS2328FSFPInfoEntry
   MAX-ACCESS  not-accessible
   STATUS      current
   DESCRIPTION
       " "
   ::= { gs2328fPort 4 }

gs2328fSFPInfoEntry OBJECT-TYPE
   SYNTAX      GS2328FSFPInfoEntry
   MAX-ACCESS  not-accessible
   STATUS      current
   DESCRIPTION
       ""
   INDEX    { gs2328fSFPInfoIndex }
   ::= { gs2328fSFPInfoTable 1 }

GS2328FSFPInfoEntry ::= SEQUENCE {
   gs2328fSFPInfoIndex               Integer32,
   gs2328fSFPInfoPort                DisplayString,
   gs2328fSFPConnectorType           DisplayString,
   gs2328fSFPFiberType               DisplayString,
   gs2328fSFPTxCentralWavelength     DisplayString,
   gs2328fSFPBaudRate                DisplayString,
   gs2328fSFPVendorOUI               DisplayString,
   gs2328fSFPVendorName              DisplayString,
   gs2328fSFPVendorPN                DisplayString,
   gs2328fSFPVendorRev               DisplayString,
   gs2328fSFPVendorSN                DisplayString,
   gs2328fSFPDateCode                DisplayString,
   gs2328fSFPTemperature             DisplayString,
   gs2328fSFPVcc                     DisplayString,
   gs2328fSFPMon1Bias                DisplayString,
   gs2328fSFPMon2TxPWR               DisplayString,
   gs2328fSFPMon3RxPWR               DisplayString
}

gs2328fSFPInfoIndex OBJECT-TYPE
   SYNTAX      Integer32(1..4095)
   MAX-ACCESS  not-accessible
   STATUS      current
   DESCRIPTION
       " "
   ::= { gs2328fSFPInfoEntry 1 }

gs2328fSFPInfoPort OBJECT-TYPE
   SYNTAX      DisplayString
   MAX-ACCESS  read-only
   STATUS      current
   DESCRIPTION
       " "
   ::= { gs2328fSFPInfoEntry 2 }

gs2328fSFPConnectorType OBJECT-TYPE
   SYNTAX      DisplayString
   MAX-ACCESS  read-only
   STATUS      current
   DESCRIPTION
       " "
   ::= { gs2328fSFPInfoEntry 3 }

gs2328fSFPFiberType OBJECT-TYPE
   SYNTAX      DisplayString
   MAX-ACCESS  read-only
   STATUS      current
   DESCRIPTION
       " "
   ::= { gs2328fSFPInfoEntry 4 }

gs2328fSFPTxCentralWavelength OBJECT-TYPE
   SYNTAX      DisplayString
   MAX-ACCESS  read-only
   STATUS      current
   DESCRIPTION
       " "
   ::= { gs2328fSFPInfoEntry 5 }

gs2328fSFPBaudRate OBJECT-TYPE
   SYNTAX      DisplayString
   MAX-ACCESS  read-only
   STATUS      current
   DESCRIPTION
       " "
   ::= { gs2328fSFPInfoEntry 6 }

gs2328fSFPVendorOUI OBJECT-TYPE
   SYNTAX      DisplayString
   MAX-ACCESS  read-only
   STATUS      current
   DESCRIPTION
       " "
   ::= { gs2328fSFPInfoEntry 7 }

gs2328fSFPVendorName OBJECT-TYPE
   SYNTAX      DisplayString
   MAX-ACCESS  read-only
   STATUS      current
   DESCRIPTION
       " "
   ::= { gs2328fSFPInfoEntry 8 }

gs2328fSFPVendorPN OBJECT-TYPE
   SYNTAX      DisplayString
   MAX-ACCESS  read-only
   STATUS      current
   DESCRIPTION
       " "
   ::= { gs2328fSFPInfoEntry 9 }

gs2328fSFPVendorRev OBJECT-TYPE
   SYNTAX      DisplayString
   MAX-ACCESS  read-only
   STATUS      current
   DESCRIPTION
       " "
   ::= { gs2328fSFPInfoEntry 10 }

gs2328fSFPVendorSN OBJECT-TYPE
   SYNTAX      DisplayString
   MAX-ACCESS  read-only
   STATUS      current
   DESCRIPTION
       " "
   ::= { gs2328fSFPInfoEntry 11 }

gs2328fSFPDateCode OBJECT-TYPE
   SYNTAX      DisplayString
   MAX-ACCESS  read-only
   STATUS      current
   DESCRIPTION
       " "
   ::= { gs2328fSFPInfoEntry 12 }

gs2328fSFPTemperature OBJECT-TYPE
   SYNTAX      DisplayString
   MAX-ACCESS  read-only
   STATUS      current
   DESCRIPTION
       " "
   ::= { gs2328fSFPInfoEntry 13 }

gs2328fSFPVcc OBJECT-TYPE
   SYNTAX      DisplayString
   MAX-ACCESS  read-only
   STATUS      current
   DESCRIPTION
       " "
   ::= { gs2328fSFPInfoEntry 14 }

gs2328fSFPMon1Bias OBJECT-TYPE
   SYNTAX      DisplayString
   MAX-ACCESS  read-only
   STATUS      current
   DESCRIPTION
       " "
   ::= { gs2328fSFPInfoEntry 15 }

gs2328fSFPMon2TxPWR OBJECT-TYPE
   SYNTAX      DisplayString
   MAX-ACCESS  read-only
   STATUS      current
   DESCRIPTION
       " "
   ::= { gs2328fSFPInfoEntry 16 }

gs2328fSFPMon3RxPWR OBJECT-TYPE
   SYNTAX      DisplayString
   MAX-ACCESS  read-only
   STATUS      current
   DESCRIPTION
       " "
   ::= { gs2328fSFPInfoEntry 17 }


gs2328fVoiceVLAN                                             OBJECT IDENTIFIER ::= { gs2328fConfiguration 2 }

gs2328fVoiceVLANConf                                         OBJECT IDENTIFIER ::= { gs2328fVoiceVLAN 1 }

gs2328fVoiceVLANMode OBJECT-TYPE
   SYNTAX      INTEGER { disable(0), enable(1) }
   MAX-ACCESS  read-write
   STATUS      current
   DESCRIPTION
       " Voice VLAN mode operation.
       default: 0,
       0: disable
       1: enable"
   ::= { gs2328fVoiceVLANConf 1 }

gs2328fVoiceVLANVLANId OBJECT-TYPE
   SYNTAX      Integer32(1..4094)
   MAX-ACCESS  read-write
   STATUS      current
   DESCRIPTION
       "Voice VLAN ID.
        default: 1000,
        range : 1-4094. "
   ::= { gs2328fVoiceVLANConf 2 }

gs2328fVoiceVLANAgingTime OBJECT-TYPE
   SYNTAX      Integer32(10..1000000)
   MAX-ACCESS  read-write
   STATUS      current
   DESCRIPTION
       " Voice VLAN secure learning aging time.
         default: 86400,
         range : 10 - 10000000. "
   ::= { gs2328fVoiceVLANConf 3 }

gs2328fVoiceVLANTrafficClass OBJECT-TYPE
   SYNTAX      Integer32(0..7)
   MAX-ACCESS  read-write
   STATUS      current
   DESCRIPTION
       " Voice VLAN traffic class, all traffic on the Voice VLAN
         will apply this class, available value is from 0(Low)
         to 7(High).
         default: 7. "
   ::= { gs2328fVoiceVLANConf 4 }


gs2328fVoiceVLANPortTable OBJECT-TYPE
   SYNTAX      SEQUENCE OF GS2328FVoiceVLANPortEntry
   MAX-ACCESS  not-accessible
   STATUS      current
   DESCRIPTION
       " Show Voice Vlan configuration. "
   ::= { gs2328fVoiceVLANConf 5 }

gs2328fVoiceVLANPortEntry OBJECT-TYPE
   SYNTAX      GS2328FVoiceVLANPortEntry
   MAX-ACCESS  not-accessible
   STATUS      current
   DESCRIPTION
       ""
   INDEX    { gs2328fVoiceVLANPort  }
   ::= { gs2328fVoiceVLANPortTable 1 }

GS2328FVoiceVLANPortEntry ::= SEQUENCE {
   gs2328fVoiceVLANPort                    Integer32,
   gs2328fVoiceVLANPortMode                INTEGER,
   gs2328fVoiceVLANPortSecurity            INTEGER,
   gs2328fVoiceVLANPortDiscoveryProtocol   INTEGER
}

gs2328fVoiceVLANPort OBJECT-TYPE
   SYNTAX      Integer32(1..4095)
   MAX-ACCESS  not-accessible
   STATUS      current
   DESCRIPTION
       " port, range : 1 - port number. "
   ::= { gs2328fVoiceVLANPortEntry 1 }

gs2328fVoiceVLANPortMode OBJECT-TYPE
   SYNTAX      INTEGER { disable(0), auto(1), forced(2) }
   MAX-ACCESS  read-write
   STATUS      current
   DESCRIPTION
       " Voice VLAN port mode.
         default: 0,
         0: Disable (Disjoin from Voice VLAN.)
         1: Auto (Enable auto detect mode. It detects whether there is VoIP phone attached to the specific port and configures the Voice VLAN members automatically.)
         2: Forced (Force join to Voice VLAN.)"
   ::= { gs2328fVoiceVLANPortEntry 2 }

gs2328fVoiceVLANPortSecurity OBJECT-TYPE
   SYNTAX      INTEGER { disable(0), enable(1) }
   MAX-ACCESS  read-write
   STATUS      current
   DESCRIPTION
       " Voice VLAN port security mode.
         default: 0,
         0: Disable (Disjoin from Voice VLAN.)
         1: enable ( Enable Voice VLAN security mode. When the function is
                     enabled, all non-telephone MAC address in Voice VLAN
                     will be blocked 10 seconds.)"
   ::= { gs2328fVoiceVLANPortEntry 3 }

gs2328fVoiceVLANPortDiscoveryProtocol OBJECT-TYPE
   SYNTAX      INTEGER { oui(0), lldp(1), both(2) }
   MAX-ACCESS  read-write
   STATUS      current
   DESCRIPTION
       " Voice VLAN port discovery protocol.
         default: 0
         0: OUI (Detect telephony device by OUI address.)
         1: LLDP (Detect telephony device by LLDP.)
         2: Both (Both OUI and LLDP.) "
   ::= { gs2328fVoiceVLANPortEntry 4 }

gs2328fVoiceVLANSkipNAS OBJECT-TYPE
   SYNTAX      INTEGER { disable(0), enable(1) }
   MAX-ACCESS  read-write
   STATUS      current
   DESCRIPTION
       " Voice VLAN skip NAS mode.
         default: 0,
         0: Disable (Do not skip NAS on Voice VLAN.)
         1: enable (Enable skipping of NAS on Voice VLAN. When the function is
                    enabled, authentication through the NAS module is not
                    applied to the Voice VLAN, but clients are allowed without
                    authentication.)"
   ::= { gs2328fVoiceVLANPortEntry 5 }


gs2328fVoiceVLANOUI                                          OBJECT IDENTIFIER ::= { gs2328fVoiceVLAN 2 }

gs2328fVoiceVLANOUICreate OBJECT-TYPE
   SYNTAX       INTEGER { none(0), create(1) }
   MAX-ACCESS   read-write
   STATUS       current
   DESCRIPTION
       "default: 0
        0 : None  (read only)
        1 : Create an OUI entry"
   ::= { gs2328fVoiceVLANOUI 1 }

gs2328fVoiceVLANOUITable OBJECT-TYPE
   SYNTAX      SEQUENCE OF GS2328FVoiceVLANOUIEntry
   MAX-ACCESS  not-accessible
   STATUS      current
   DESCRIPTION
       " Create Voice VLAN OUI entry. Modify OUI table will
         restart auto detect OUI process. "
   ::= { gs2328fVoiceVLANOUI 2 }

gs2328fVoiceVLANOUIEntry OBJECT-TYPE
   SYNTAX      GS2328FVoiceVLANOUIEntry
   MAX-ACCESS  not-accessible
   STATUS      current
   DESCRIPTION
       ""
   INDEX    { gs2328fVoiceVLANOUIIndex  }
   ::= { gs2328fVoiceVLANOUITable 1 }

GS2328FVoiceVLANOUIEntry ::= SEQUENCE {
   gs2328fVoiceVLANOUIIndex         Integer32,
   gs2328fVoiceVLANTelephonyOUI     OCTET STRING,
   gs2328fVoiceVLANDescription      DisplayString,
   gs2328fVoiceVLANOUIRowStatus     INTEGER
}

gs2328fVoiceVLANOUIIndex OBJECT-TYPE
   SYNTAX      Integer32(1..16)
   MAX-ACCESS  not-accessible
   STATUS      current
   DESCRIPTION
       " "
   ::= { gs2328fVoiceVLANOUIEntry 1 }

gs2328fVoiceVLANTelephonyOUI OBJECT-TYPE
   SYNTAX      OCTET STRING (SIZE (1..32))
   MAX-ACCESS  read-write
   STATUS      current
   DESCRIPTION
       "OUI address, format : 0a 1b 2c "
   ::= { gs2328fVoiceVLANOUIEntry 2 }

gs2328fVoiceVLANDescription OBJECT-TYPE
   SYNTAX      DisplayString (SIZE (1..32))
   MAX-ACCESS  read-write
   STATUS      current
   DESCRIPTION
       " Up to 32 characters describing OUI address. "
   ::= { gs2328fVoiceVLANOUIEntry 3 }

gs2328fVoiceVLANOUIRowStatus OBJECT-TYPE
   SYNTAX      INTEGER { active(1), notInservice(2), destroy(4), undo(5) }
   MAX-ACCESS  read-write
   STATUS      current
   DESCRIPTION
       "1: active
        2: notInservice
        4: destroy
        5: undo"
   ::= { gs2328fVoiceVLANOUIEntry 4 }

gs2328fGARP                                                   OBJECT IDENTIFIER ::= { gs2328fConfiguration 3 }

gs2328fGARPConfTable OBJECT-TYPE
   SYNTAX      SEQUENCE OF GS2328FGARPConfEntry
   MAX-ACCESS  not-accessible
   STATUS      current
   DESCRIPTION
       " "
   ::= { gs2328fGARP 1 }

gs2328fGARPConfEntry OBJECT-TYPE
   SYNTAX      GS2328FGARPConfEntry
   MAX-ACCESS  not-accessible
   STATUS      current
   DESCRIPTION
       ""
   INDEX    { gs2328fGARPConfPort  }
   ::= { gs2328fGARPConfTable 1 }

GS2328FGARPConfEntry ::= SEQUENCE {
   gs2328fGARPConfPort           Integer32,
   gs2328fGARPJoinTimer          Integer32,
   gs2328fGARPLeaveTimer         Integer32,
   gs2328fGARPLeaveAllTimer      Integer32,
   gs2328fGARPApplicantion       INTEGER,
   gs2328fGARPAttributeType      INTEGER,
   gs2328fGARPApplicant          INTEGER
}

gs2328fGARPConfPort OBJECT-TYPE
   SYNTAX      Integer32(1..4095)
   MAX-ACCESS  not-accessible
   STATUS      current
   DESCRIPTION
       " "
   ::= { gs2328fGARPConfEntry 1 }

gs2328fGARPJoinTimer OBJECT-TYPE
   SYNTAX      Integer32(200..1000)
   MAX-ACCESS  read-write
   STATUS      current
   DESCRIPTION
       "default: 200, range : 200 - 1000 "
   ::= { gs2328fGARPConfEntry 2 }

gs2328fGARPLeaveTimer OBJECT-TYPE
   SYNTAX      Integer32(600..3000)
   MAX-ACCESS  read-write
   STATUS      current
   DESCRIPTION
       "default: 600 , range : 600 - 3000"
   ::= { gs2328fGARPConfEntry 3 }

gs2328fGARPLeaveAllTimer OBJECT-TYPE
   SYNTAX      Integer32(10000..50000)
   MAX-ACCESS  read-write
   STATUS      current
   DESCRIPTION
       "default: 10000, range : 10000 - 50000 "
   ::= { gs2328fGARPConfEntry 4 }

gs2328fGARPApplicantion OBJECT-TYPE
   SYNTAX      INTEGER { gvrp(1)}
   MAX-ACCESS  read-write
   STATUS      current
   DESCRIPTION
       "default: 1
       1: GVRP"
   ::= { gs2328fGARPConfEntry 5 }

gs2328fGARPAttributeType OBJECT-TYPE
   SYNTAX      INTEGER { vlan(1)}
   MAX-ACCESS  read-write
   STATUS      current
   DESCRIPTION
       "default: 1
       1: VLAN"
   ::= { gs2328fGARPConfEntry 6 }

gs2328fGARPApplicant OBJECT-TYPE
   SYNTAX      INTEGER { participant(0), nonParticipant(1) }
   MAX-ACCESS  read-write
   STATUS      current
   DESCRIPTION
       "default: 0
       0: normal-participant
       1: non-participant"
   ::= { gs2328fGARPConfEntry 7 }

gs2328fGARPStatisticsTable OBJECT-TYPE
   SYNTAX      SEQUENCE OF GS2328FGARPStatisticsEntry
   MAX-ACCESS  not-accessible
   STATUS      current
   DESCRIPTION
       " Show the basic GARP port statistics. "
   ::= { gs2328fGARP 2 }

gs2328fGARPStatisticsEntry OBJECT-TYPE
   SYNTAX      GS2328FGARPStatisticsEntry
   MAX-ACCESS  not-accessible
   STATUS      current
   DESCRIPTION
       ""
   INDEX    { gs2328fGARPStatisticsPort  }
   ::= { gs2328fGARPStatisticsTable 1 }

GS2328FGARPStatisticsEntry ::= SEQUENCE {
   gs2328fGARPStatisticsPort             Integer32,
   gs2328fGARPStatisticsPeerMAC          DisplayString,
   gs2328fGARPStatisticsFailedCount      Counter32
}

gs2328fGARPStatisticsPort OBJECT-TYPE
   SYNTAX      Integer32(1..4095)
   MAX-ACCESS  not-accessible
   STATUS      current
   DESCRIPTION
       " port, range : 1 - port number. "
   ::= { gs2328fGARPStatisticsEntry 1 }

gs2328fGARPStatisticsPeerMAC OBJECT-TYPE
   SYNTAX      DisplayString
   MAX-ACCESS  read-only
   STATUS      current
   DESCRIPTION
       " Peer MAC is MAC address of the neighbour Switch from with GARP frame is received.  "
   ::= { gs2328fGARPStatisticsEntry 2 }

gs2328fGARPStatisticsFailedCount OBJECT-TYPE
   SYNTAX      Counter32
   MAX-ACCESS  read-only
   STATUS      current
   DESCRIPTION
       " explain Failed count here. "
   ::= { gs2328fGARPStatisticsEntry 3 }

gs2328fGVRP                                                   OBJECT IDENTIFIER ::= { gs2328fConfiguration 4 }

gs2328fGVRPConf                                                   OBJECT IDENTIFIER ::= { gs2328fGVRP 1 }

gs2328fGVRPMode OBJECT-TYPE
   SYNTAX      INTEGER { disable(0), enable(1) }
   MAX-ACCESS  read-write
   STATUS      current
   DESCRIPTION
       "default: 0,
        0: disable,
        1: enable. "
   ::= { gs2328fGVRPConf 1 }

gs2328fGVRPConfTable OBJECT-TYPE
   SYNTAX      SEQUENCE OF GS2328FGVRPConfEntry
   MAX-ACCESS  not-accessible
   STATUS      current
   DESCRIPTION
       " "
   ::= { gs2328fGVRPConf 2 }

gs2328fGVRPConfEntry OBJECT-TYPE
   SYNTAX      GS2328FGVRPConfEntry
   MAX-ACCESS  not-accessible
   STATUS      current
   DESCRIPTION
       ""
   INDEX    { gs2328fGVRPConfPort  }
   ::= { gs2328fGVRPConfTable 1 }

GS2328FGVRPConfEntry ::= SEQUENCE {
   gs2328fGVRPConfPort           Integer32,
   gs2328fGVRPConfPortMode       INTEGER,
   gs2328fGVRPConfPortRRole      INTEGER
}

gs2328fGVRPConfPort OBJECT-TYPE
   SYNTAX      Integer32(1..4095)
   MAX-ACCESS  not-accessible
   STATUS      current
   DESCRIPTION
       " "
   ::= { gs2328fGVRPConfEntry 1 }

gs2328fGVRPConfPortMode OBJECT-TYPE
   SYNTAX      INTEGER { disable(0), enable(1) }
   MAX-ACCESS  read-write
   STATUS      current
   DESCRIPTION
       "default: 0
       1: enable
       0: disable"
   ::= { gs2328fGVRPConfEntry 2 }

gs2328fGVRPConfPortRRole OBJECT-TYPE
   SYNTAX      INTEGER { disable(0), enable(1) }
   MAX-ACCESS  read-write
   STATUS      current
   DESCRIPTION
       "default: 0
       1: enable
       0: disable"
   ::= { gs2328fGVRPConfEntry 3 }

gs2328fGVRPStatisticsTable OBJECT-TYPE
   SYNTAX      SEQUENCE OF GS2328FGVRPStatisticsEntry
   MAX-ACCESS  not-accessible
   STATUS      current
   DESCRIPTION
       " "
   ::= { gs2328fGVRP 2 }

gs2328fGVRPStatisticsEntry OBJECT-TYPE
   SYNTAX      GS2328FGVRPStatisticsEntry
   MAX-ACCESS  not-accessible
   STATUS      current
   DESCRIPTION
       ""
   INDEX    { gs2328fGVRPStatisticsPort  }
   ::= { gs2328fGVRPStatisticsTable 1 }

GS2328FGVRPStatisticsEntry ::= SEQUENCE {
   gs2328fGVRPStatisticsPort         Integer32,
   gs2328fGVRPStatisticsJoinTxCnt    Counter32,
   gs2328fGVRPStatisticsLeaveTxCnt   Counter32
}

gs2328fGVRPStatisticsPort OBJECT-TYPE
   SYNTAX      Integer32(1..4095)
   MAX-ACCESS  not-accessible
   STATUS      current
   DESCRIPTION
       " "
   ::= { gs2328fGVRPStatisticsEntry 1 }

gs2328fGVRPStatisticsJoinTxCnt OBJECT-TYPE
   SYNTAX      Counter32
   MAX-ACCESS  read-only
   STATUS      current
   DESCRIPTION
       ""
   ::= { gs2328fGVRPStatisticsEntry 2 }

gs2328fGVRPStatisticsLeaveTxCnt OBJECT-TYPE
   SYNTAX      Counter32
   MAX-ACCESS  read-only
   STATUS      current
   DESCRIPTION
       ""
   ::= { gs2328fGVRPStatisticsEntry 3 }


gs2328fMirroring                                             OBJECT IDENTIFIER ::= { gs2328fConfiguration 6 }

gs2328fPortToMirrorOn OBJECT-TYPE
   SYNTAX      Integer32(0..10)
   MAX-ACCESS  read-write
   STATUS      current
   DESCRIPTION
       "default: 0
        0: disable,
        range : 1 - port number. "
   ::= { gs2328fMirroring 1 }

gs2328fMirrorTable OBJECT-TYPE
   SYNTAX      SEQUENCE OF GS2328FMirrorEntry
   MAX-ACCESS  not-accessible
   STATUS      current
   DESCRIPTION
       " "
   ::= { gs2328fMirroring 2 }

gs2328fMirrorEntry OBJECT-TYPE
   SYNTAX      GS2328FMirrorEntry
   MAX-ACCESS  not-accessible
   STATUS      current
   DESCRIPTION
       ""
   INDEX    { gs2328fMirrorPort  }
   ::= { gs2328fMirrorTable 1 }

GS2328FMirrorEntry ::= SEQUENCE {
   gs2328fMirrorPort		Integer32,
   gs2328fMirrorMode		INTEGER
}

gs2328fMirrorPort OBJECT-TYPE
   SYNTAX      Integer32(1..4095)
   MAX-ACCESS  not-accessible
   STATUS      current
   DESCRIPTION
       " "
   ::= { gs2328fMirrorEntry 1 }

gs2328fMirrorMode OBJECT-TYPE
   SYNTAX      INTEGER { disable(0), enable(1), rxOnly(2), txOnly(3) }
   MAX-ACCESS  read-write
   STATUS      current
   DESCRIPTION
       "default: 0
       0: disable
       1: enable
       2: rx only
       3: tx only
       Setting Tx mirroring for analyzer port has no effect. Tx mirroring ignored"
   ::= { gs2328fMirrorEntry 2 }

gs2328fTrapEventSeverity                                             OBJECT IDENTIFIER ::= { gs2328fConfiguration 7 }

gs2328fTrapEventSeverityACL OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  6(Info)
        0: Emergency
        1: Alert
        2: Critical
        3: Error
        4: Warning
        5: Notice
        6: Info
        7: Debug"
   ::= { gs2328fTrapEventSeverity 1 }

gs2328fTrapEventSeverityACLLog OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  7(Debug)
        0: Emergency
        1: Alert
        2: Critical
        3: Error
        4: Warning
        5: Notice
        6: Info
        7: Debug"
   ::= { gs2328fTrapEventSeverity 2 }

gs2328fTrapEventSeverityAccessMgmt OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  6(Info)
        0: Emergency
        1: Alert
        2: Critical
        3: Error
        4: Warning
        5: Notice
        6: Info
        7: Debug"
   ::= { gs2328fTrapEventSeverity 3 }

gs2328fTrapEventSeverityAuthFailed OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  4(Warning)
        0: Emergency
        1: Alert
        2: Critical
        3: Error
        4: Warning
        5: Notice
        6: Info
        7: Debug"
   ::= { gs2328fTrapEventSeverity 4 }

gs2328fTrapEventSeverityColdStart OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  4(Warning)
        0: Emergency
        1: Alert
        2: Critical
        3: Error
        4: Warning
        5: Notice
        6: Info
        7: Debug"
   ::= { gs2328fTrapEventSeverity 5 }

gs2328fTrapEventSeverityConfigInfo OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  6(Info)
        0: Emergency
        1: Alert
        2: Critical
        3: Error
        4: Warning
        5: Notice
        6: Info
        7: Debug"
   ::= { gs2328fTrapEventSeverity 6 }

gs2328fTrapEventSeverityFirmwareUpgrade OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  6(Info)
        0: Emergency
        1: Alert
        2: Critical
        3: Error
        4: Warning
        5: Notice
        6: Info
        7: Debug"
   ::= { gs2328fTrapEventSeverity 7 }

gs2328fTrapEventSeverityImportExport OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  6(Info)
        0: Emergency
        1: Alert
        2: Critical
        3: Error
        4: Warning
        5: Notice
        6: Info
        7: Debug"
   ::= { gs2328fTrapEventSeverity 8 }

gs2328fTrapEventSeverityLACP OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  6(Info)
        0: Emergency
        1: Alert
        2: Critical
        3: Error
        4: Warning
        5: Notice
        6: Info
        7: Debug"
   ::= { gs2328fTrapEventSeverity 9 }

gs2328fTrapEventSeverityLinkStatus OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  4(Warning)
        0: Emergency
        1: Alert
        2: Critical
        3: Error
        4: Warning
        5: Notice
        6: Info
        7: Debug"
   ::= { gs2328fTrapEventSeverity 10 }

gs2328fTrapEventSeverityLogin OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  6(Info)
        0: Emergency
        1: Alert
        2: Critical
        3: Error
        4: Warning
        5: Notice
        6: Info
        7: Debug"
   ::= { gs2328fTrapEventSeverity 11 }

gs2328fTrapEventSeverityLogout OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  6(Info)
        0: Emergency
        1: Alert
        2: Critical
        3: Error
        4: Warning
        5: Notice
        6: Info
        7: Debug"
   ::= { gs2328fTrapEventSeverity 12 }

gs2328fTrapEventSeverityLoopProtect OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  6(Info)
        0: Emergency
        1: Alert
        2: Critical
        3: Error
        4: Warning
        5: Notice
        6: Info
        7: Debug"
   ::= { gs2328fTrapEventSeverity 13 }

gs2328fTrapEventSeverityMgmtIPChange OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  6(Info)
        0: Emergency
        1: Alert
        2: Critical
        3: Error
        4: Warning
        5: Notice
        6: Info
        7: Debug"
   ::= { gs2328fTrapEventSeverity 14 }

gs2328fTrapEventSeverityModuleChange OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  5(Notice)
        0: Emergency
        1: Alert
        2: Critical
        3: Error
        4: Warning
        5: Notice
        6: Info
        7: Debug"
   ::= { gs2328fTrapEventSeverity 15 }

gs2328fTrapEventSeverityNAS OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  6(Info)
        0: Emergency
        1: Alert
        2: Critical
        3: Error
        4: Warning
        5: Notice
        6: Info
        7: Debug"
   ::= { gs2328fTrapEventSeverity 16 }

gs2328fTrapEventSeverityPasswordChange OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  6(Info)
        0: Emergency
        1: Alert
        2: Critical
        3: Error
        4: Warning
        5: Notice
        6: Info
        7: Debug"
   ::= { gs2328fTrapEventSeverity 17 }

gs2328fTrapEventSeverityPortSecurity OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  6(Info)
        0: Emergency
        1: Alert
        2: Critical
        3: Error
        4: Warning
        5: Notice
        6: Info
        7: Debug"
   ::= { gs2328fTrapEventSeverity 18 }

gs2328fTrapEventSeverityVLAN OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  6(Info)
        0: Emergency
        1: Alert
        2: Critical
        3: Error
        4: Warning
        5: Notice
        6: Info
        7: Debug"
   ::= { gs2328fTrapEventSeverity 20 }

gs2328fTrapEventSeverityWarmStart OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  4(Warning)
        0: Emergency
        1: Alert
        2: Critical
        3: Error
        4: Warning
        5: Notice
        6: Info
        7: Debug"
   ::= { gs2328fTrapEventSeverity 21 }



gs2328fTrapEventSeverityARPConflict OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  4(Warning)
        0: Emergency
        1: Alert
        2: Critical
        3: Error
        4: Warning
        5: Notice
        6: Info
        7: Debug"
   ::= { gs2328fTrapEventSeverity 25 }

gs2328fTrapEventSeveritySpoofingLimit OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  4(Warning)
        0: Emergency
        1: Alert
        2: Critical
        3: Error
        4: Warning
        5: Notice
        6: Info
        7: Debug"
   ::= { gs2328fTrapEventSeverity 27 }

gs2328fTrapEventSeverityStaticARPConflict	 OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  4(Warning)
        0: Emergency
        1: Alert
        2: Critical
        3: Error
        4: Warning
        5: Notice
        6: Info
        7: Debug"
   ::= { gs2328fTrapEventSeverity 28 }

gs2328fSMTP                                             OBJECT IDENTIFIER ::= { gs2328fConfiguration 8 }

gs2328fSMTPMailServer OBJECT-TYPE
   SYNTAX      DisplayString
   MAX-ACCESS  read-write
   STATUS      current
   DESCRIPTION
       " Up to 47 characters describing email server. "
   ::= { gs2328fSMTP 1 }

gs2328fSMTPUserName OBJECT-TYPE
   SYNTAX      DisplayString
   MAX-ACCESS  read-write
   STATUS      current
   DESCRIPTION
       " Up to 47 characters describing user name. "
   ::= { gs2328fSMTP 2 }

gs2328fSMTPPassword OBJECT-TYPE
   SYNTAX      DisplayString
   MAX-ACCESS  read-write
   STATUS      current
   DESCRIPTION
       " Up to 47 characters describing password. "
   ::= { gs2328fSMTP 3 }

gs2328fSMTPServeriryLevel OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       "default: 6
       0: Emergency
       1: Alert
       2: Critical
       3: Error
       4: Warning
       5: Notice
       6: Info
       7: Debug"
   ::= { gs2328fSMTP 4 }

gs2328fSMTPSender OBJECT-TYPE
   SYNTAX      DisplayString
   MAX-ACCESS  read-write
   STATUS      current
   DESCRIPTION
       " Up to 47 characters describing sender. "
   ::= { gs2328fSMTP 5 }

gs2328fSMTPReturnPath OBJECT-TYPE
   SYNTAX      DisplayString
   MAX-ACCESS  read-write
   STATUS      current
   DESCRIPTION
       " Up to 47 characters describing return path. "
   ::= { gs2328fSMTP 6 }

gs2328fSMTPEmailAddress1 OBJECT-TYPE
   SYNTAX      DisplayString
   MAX-ACCESS  read-write
   STATUS      current
   DESCRIPTION
       " Up to 47 characters describing mail address. "
   ::= { gs2328fSMTP 7 }

gs2328fSMTPEmailAddress2 OBJECT-TYPE
   SYNTAX      DisplayString
   MAX-ACCESS  read-write
   STATUS      current
   DESCRIPTION
       " Up to 47 characters describing mail address. "
   ::= { gs2328fSMTP 8 }

gs2328fSMTPEmailAddress3 OBJECT-TYPE
   SYNTAX      DisplayString
   MAX-ACCESS  read-write
   STATUS      current
   DESCRIPTION
       " Up to 47 characters describing mail address. "
   ::= { gs2328fSMTP 9 }

gs2328fSMTPEmailAddress4 OBJECT-TYPE
   SYNTAX      DisplayString
   MAX-ACCESS  read-write
   STATUS      current
   DESCRIPTION
       " Up to 47 characters describing mail address. "
   ::= { gs2328fSMTP 10 }

gs2328fSMTPEmailAddress5 OBJECT-TYPE
   SYNTAX      DisplayString
   MAX-ACCESS  read-write
   STATUS      current
   DESCRIPTION
       " Up to 47 characters describing mail address. "
   ::= { gs2328fSMTP 11 }

gs2328fSMTPEmailAddress6 OBJECT-TYPE
   SYNTAX      DisplayString
   MAX-ACCESS  read-write
   STATUS      current
   DESCRIPTION
       " Up to 47 characters describing mail address. "
   ::= { gs2328fSMTP 12 }


gs2328fACL                                                   OBJECT IDENTIFIER ::= { gs2328fConfiguration 9 }

gs2328fACLPortsConfTable OBJECT-TYPE
   SYNTAX      SEQUENCE OF GS2328FACLPortsConfEntry
   MAX-ACCESS  not-accessible
   STATUS      current
   DESCRIPTION
       " "
   ::= { gs2328fACL 1 }

gs2328fACLPortsConfEntry OBJECT-TYPE
   SYNTAX      GS2328FACLPortsConfEntry
   MAX-ACCESS  not-accessible
   STATUS      current
   DESCRIPTION
       ""
   INDEX    { gs2328fACLPortsConfPort  }
   ::= { gs2328fACLPortsConfTable 1 }

GS2328FACLPortsConfEntry ::= SEQUENCE {
   gs2328fACLPortsConfPort               Integer32,
   gs2328fACLPortsConfPolicyID           Integer32,
   gs2328fACLPortsConfAction             INTEGER,
   gs2328fACLPortsConfRateLimiterID      Integer32,
   gs2328fACLPortsConfPortRedirect       Integer32,
   gs2328fACLPortsConfMirror             INTEGER,
   gs2328fACLPortsConfLogging            INTEGER,
   gs2328fACLPortsConfShutdown           INTEGER,
   gs2328fACLPortsConfState              INTEGER,
   gs2328fACLPortsConfCounter            Counter32
}

gs2328fACLPortsConfPort OBJECT-TYPE
   SYNTAX      Integer32 (1..4095)
   MAX-ACCESS  not-accessible
   STATUS      current
   DESCRIPTION
       " "
   ::= { gs2328fACLPortsConfEntry 1 }

gs2328fACLPortsConfPolicyID OBJECT-TYPE
   SYNTAX      Integer32 (0..255)
   MAX-ACCESS  read-write
   STATUS      current
   DESCRIPTION
       "default: 0, range : 0 - 255 "
   ::= { gs2328fACLPortsConfEntry 2 }

gs2328fACLPortsConfAction OBJECT-TYPE
   SYNTAX      INTEGER { deny(0), permit(1) }
   MAX-ACCESS  read-write
   STATUS      current
   DESCRIPTION
       "default: 1,
        0: Deny
        1: Permit"
   ::= { gs2328fACLPortsConfEntry 3 }

gs2328fACLPortsConfRateLimiterID OBJECT-TYPE
   SYNTAX      Integer32 (0..12)
   MAX-ACCESS  read-write
   STATUS      current
   DESCRIPTION
       "default: 0,
        0: Disable
        range : 0 - 12 "
   ::= { gs2328fACLPortsConfEntry 4 }

gs2328fACLPortsConfPortRedirect OBJECT-TYPE
   SYNTAX      Integer32 (0..4095)
   MAX-ACCESS  read-write
   STATUS      current
   DESCRIPTION
       "default: 0
        0: Disable
        range : 0 - end port number "
   ::= { gs2328fACLPortsConfEntry 5 }

gs2328fACLPortsConfMirror OBJECT-TYPE
   SYNTAX      INTEGER { disable(0), enable(1) }
   MAX-ACCESS  read-write
   STATUS      current
   DESCRIPTION
       "default: 0
        0: Disable
        1: Enable "
   ::= { gs2328fACLPortsConfEntry 6 }

gs2328fACLPortsConfLogging OBJECT-TYPE
   SYNTAX      INTEGER { disable(0), enable(1) }
   MAX-ACCESS  read-write
   STATUS      current
   DESCRIPTION
       "default: 0
        0: Disable
        1: Enable "
   ::= { gs2328fACLPortsConfEntry 7 }

gs2328fACLPortsConfShutdown OBJECT-TYPE
   SYNTAX      INTEGER { disable(0), enable(1) }
   MAX-ACCESS  read-write
   STATUS      current
   DESCRIPTION
       "default: 0
        0: Disable
        1: Enable "
   ::= { gs2328fACLPortsConfEntry 8 }

gs2328fACLPortsConfState OBJECT-TYPE
   SYNTAX      INTEGER { disable(0), enable(1) }
   MAX-ACCESS  read-write
   STATUS      current
   DESCRIPTION
       "default: 1
        0: Disable
        1: Enable "
   ::= { gs2328fACLPortsConfEntry 9 }

gs2328fACLPortsConfCounter OBJECT-TYPE
   SYNTAX      Counter32
   MAX-ACCESS  read-only
   STATUS      current
   DESCRIPTION
       "Counts the number of frames that match this ACE. "
   ::= { gs2328fACLPortsConfEntry 10 }


gs2328fACLRateLimiterTable OBJECT-TYPE
   SYNTAX      SEQUENCE OF GS2328FACLRateLimiterEntry
   MAX-ACCESS  not-accessible
   STATUS      current
   DESCRIPTION
       " "
   ::= { gs2328fACL 2 }

gs2328fACLRateLimiterEntry OBJECT-TYPE
   SYNTAX      GS2328FACLRateLimiterEntry
   MAX-ACCESS  not-accessible
   STATUS      current
   DESCRIPTION
       ""
   INDEX    { gs2328fACLRateLimiterID  }
   ::= { gs2328fACLRateLimiterTable 1 }

GS2328FACLRateLimiterEntry ::= SEQUENCE {
   gs2328fACLRateLimiterID       Integer32,
   gs2328fACLRateLimiterUnit     INTEGER,
   gs2328fACLRateLimiterRate     Integer32
}

gs2328fACLRateLimiterID OBJECT-TYPE
   SYNTAX      Integer32 (1..12)
   MAX-ACCESS  not-accessible
   STATUS      current
   DESCRIPTION
       " Rate Limiter ID.
         range : 1-12 "
   ::= { gs2328fACLRateLimiterEntry 1 }

gs2328fACLRateLimiterUnit OBJECT-TYPE
   SYNTAX      INTEGER { pps(0), kbps(1) }
   MAX-ACCESS  read-write
   STATUS      current
   DESCRIPTION
       "default: 0,
        0: pps
        1: kbps"
   ::= { gs2328fACLRateLimiterEntry 2 }

gs2328fACLRateLimiterRate OBJECT-TYPE
   SYNTAX      Integer32(0..3276700)
   MAX-ACCESS  read-write
   STATUS      current
   DESCRIPTION
       "default: 1,
        range : <0-3276700> pps
                <0-10000> kbps"
   ::= { gs2328fACLRateLimiterEntry 3 }


gs2328fACLACE                                          OBJECT IDENTIFIER ::= { gs2328fACL 3 }

gs2328fACLACECreate OBJECT-TYPE
   SYNTAX       INTEGER { none(0), create(1) }
   MAX-ACCESS   read-write
   STATUS       current
   DESCRIPTION
       "default: 0
        0 : None  (read only)
        1 : Create an ACE entry"
   ::= { gs2328fACLACE 1 }

gs2328fACLACETable OBJECT-TYPE
   SYNTAX      SEQUENCE OF GS2328FACLACEEntry
   MAX-ACCESS  not-accessible
   STATUS      current
   DESCRIPTION
       " Create ACL ACE entry. "
   ::= { gs2328fACLACE 2 }

gs2328fACLACEEntry OBJECT-TYPE
   SYNTAX      GS2328FACLACEEntry
   MAX-ACCESS  not-accessible
   STATUS      current
   DESCRIPTION
       ""
   INDEX    { gs2328fACLACEIndex  }
   ::= { gs2328fACLACETable 1 }

GS2328FACLACEEntry ::= SEQUENCE {
   gs2328fACLACEIndex                Integer32,
   gs2328fACLACEID                   Integer32,
   gs2328fACLACENextID               Integer32,
   gs2328fACLACEIngressPort          DisplayString,
   gs2328fACLACEPortPolicyNumber     Integer32,

   gs2328fACLACEPortPolicyBitmask    Integer32,
   gs2328fACLACEFrameType            INTEGER,
   gs2328fACLACEAction               INTEGER,
   gs2328fACLACEDenyPortRedirect     DisplayString,
   gs2328fACLACELogging              INTEGER,

   gs2328fACLACEMirror               INTEGER,
   gs2328fACLACERateLimiter          Integer32,
   gs2328fACLACEShutdown             INTEGER,
   gs2328fACLACEVLAN8021QTagged      INTEGER,
   gs2328fACLACEVLANTagPriority      Integer32,

   gs2328fACLACEVLANVID              Integer32,
   gs2328fACLACEEtherType            Integer32,
   gs2328fACLACESMAC                 DisplayString,
   gs2328fACLACEDMACType             INTEGER,
   gs2328fACLACEDMAC                 DisplayString,

   gs2328fACLACEArpOpcode            INTEGER,
   gs2328fACLACEArpFlagsRequestReply INTEGER,
   gs2328fACLACEArpFlagsArpSmac      INTEGER,
   gs2328fACLACEArpFlagsRarpDmac     INTEGER,
   gs2328fACLACEArpFlagsLength       INTEGER,

   gs2328fACLACEArpFlagsIp           INTEGER,
   gs2328fACLACEArpFlagsEthernet     INTEGER,
   gs2328fACLACESIPType              INTEGER,
   gs2328fACLACESIPIPAddress         IpAddress,
   gs2328fACLACESIPNetworkPrefix     Integer32,

   gs2328fACLACEDIPType              INTEGER,
   gs2328fACLACEDIPIPAddress         IpAddress,
   gs2328fACLACEDIPNetworkPrefix     Integer32,

   gs2328fACLACEIPProtocol           Integer32,
   gs2328fACLACEIPFlagsTTL           INTEGER,
   gs2328fACLACEIPFlagsOptions       INTEGER,
   gs2328fACLACEIPFlagsFragment      INTEGER,
   gs2328fACLACEICMPType             Integer32,

   gs2328fACLACEICMPCode             Integer32,
   gs2328fACLACESourcePortMin        Integer32,
   gs2328fACLACESourcePortMax        Integer32,
   gs2328fACLACEDestPortMin          Integer32,
   gs2328fACLACEDestPortMax          Integer32,

   gs2328fACLACETCPFlagsFin          INTEGER,
   gs2328fACLACETCPFlagsSyn          INTEGER,
   gs2328fACLACETCPFlagsRst          INTEGER,
   gs2328fACLACETCPFlagsPsh          INTEGER,
   gs2328fACLACETCPFlagsAck          INTEGER,

   gs2328fACLACETCPFlagsUrg          INTEGER,

   gs2328fACLACERowStatus            INTEGER
}

gs2328fACLACEIndex OBJECT-TYPE
   SYNTAX      Integer32(1..256)
   MAX-ACCESS  not-accessible
   STATUS      current
   DESCRIPTION
       " "
   ::= { gs2328fACLACEEntry 1 }

gs2328fACLACEID OBJECT-TYPE
   SYNTAX      Integer32(1..256)
   MAX-ACCESS  read-write
   STATUS      current
   DESCRIPTION
       " If the ACE ID is specified and an entry with this ACE ID
         already exists, the ACE will be modified. Otherwise, a
         new ACE will be added.
         range : 1 - 256. "
   ::= { gs2328fACLACEEntry 2 }

gs2328fACLACENextID OBJECT-TYPE
   SYNTAX      Integer32 (0..256)
   MAX-ACCESS  read-write
   STATUS      current
   DESCRIPTION
       " If the next ACE ID is non zero, the ACE will be placed
         before this ACE in the list. If the next ACE ID is zero,
         the ACE will be placed last in the list.
         range : 0 - 256. "
   ::= { gs2328fACLACEEntry 3 }

gs2328fACLACEIngressPort OBJECT-TYPE
   SYNTAX      DisplayString
   MAX-ACCESS  read-write
   STATUS      current
   DESCRIPTION
       " Indicates the ingress port of the ACE. Possible values are:
         All: The ACE will match all ingress port.
         Port: The ACE will match a specific ingress port.Format: 1,3,6."
   ::= { gs2328fACLACEEntry 4 }

gs2328fACLACEPortPolicyNumber OBJECT-TYPE
   SYNTAX      Integer32(0..255)
   MAX-ACCESS  read-write
   STATUS      current
   DESCRIPTION
       " policy value.
         range : 0 - 255. "
   ::= { gs2328fACLACEEntry 5 }

gs2328fACLACEPortPolicyBitmask OBJECT-TYPE
   SYNTAX      Integer32(0..255)
   MAX-ACCESS  read-write
   STATUS      current
   DESCRIPTION
       " policy bitmask.
         range : 0 - 255(0xff). "
   ::= { gs2328fACLACEEntry 6 }

gs2328fACLACEFrameType OBJECT-TYPE
   SYNTAX      INTEGER {
                        any(0),
                        arp(1),
                        etype(2),
                        icmp(3),
                        ipv4(4),
                        tcp(5),
                        udp(6)
                        }
   MAX-ACCESS  read-write
   STATUS      current
   DESCRIPTION
       " 0: any,
         1: arp,
         2: etype,
         3: icmp,
         4: ipv4,
         5: tcp,
         6: udp."
   ::= { gs2328fACLACEEntry 7 }

gs2328fACLACEAction OBJECT-TYPE
   SYNTAX      INTEGER { deny(0), permit(1) }
   MAX-ACCESS  read-write
   STATUS      current
   DESCRIPTION
       "default: 1,
        0: Deny
        1: Permit"
   ::= { gs2328fACLACEEntry 8 }

gs2328fACLACEDenyPortRedirect OBJECT-TYPE
   SYNTAX      DisplayString
   MAX-ACCESS  read-write
   STATUS      current
   DESCRIPTION
       " Frames that hit the ACE are redirected to the port number specified here.
         Disabled: indicates that the port redirect operation is disabled.
         Port Format: 1,3,6."
   ::= { gs2328fACLACEEntry 9 }

gs2328fACLACELogging OBJECT-TYPE
   SYNTAX      INTEGER { disable(0), enable(1) }
   MAX-ACCESS  read-write
   STATUS      current
   DESCRIPTION
       "default: 0,
        0: disable - Frames matching the ACE are not logged.
        1: enable - Frames matching the ACE are stored in the system log."
   ::= { gs2328fACLACEEntry 10 }

gs2328fACLACEMirror OBJECT-TYPE
   SYNTAX      INTEGER { disable(0), enable(1) }
   MAX-ACCESS  read-write
   STATUS      current
   DESCRIPTION
       "default: 0,
        0: disable - Frames matching the ACE are not mirrored.
        1: enable - Frames matching the ACE are mirrored."
   ::= { gs2328fACLACEEntry 11 }

gs2328fACLACERateLimiter OBJECT-TYPE
   SYNTAX      Integer32(0..12)
   MAX-ACCESS  read-write
   STATUS      current
   DESCRIPTION
       "default: 0,
        0: Disable
        range : 0 - 12 "
   ::= { gs2328fACLACEEntry 12 }

gs2328fACLACEShutdown OBJECT-TYPE
   SYNTAX      INTEGER { disable(0), enable(1) }
   MAX-ACCESS  read-write
   STATUS      current
   DESCRIPTION
       "default: 0,
        0: disable - Port shut down is disabled for the AC.
        1: enable - If a frame matches the ACE, the ingress port will be disabled."
   ::= { gs2328fACLACEEntry 13 }

gs2328fACLACEVLAN8021QTagged OBJECT-TYPE
   SYNTAX      INTEGER { disable(0), enable(1), any(2) }
   MAX-ACCESS  read-write
   STATUS      current
   DESCRIPTION
       "Specify whether frames can hit the action according to the 802.1Q tagged.
        default: 2,
        0: disable - Untagged frame only.
        1: enable - Tagged frame only.
        2: Any - Any value is allowed. "
   ::= { gs2328fACLACEEntry 14 }

gs2328fACLACEVLANTagPriority OBJECT-TYPE
   SYNTAX      Integer32(0..8)
   MAX-ACCESS  read-write
   STATUS      current
   DESCRIPTION
       "Specify the tag priority for this ACE.
        The tag priority can't be set when 802.1Q Tagged is disabled
        default: 8,
        8: Any,
        range : 0 - 8 "
   ::= { gs2328fACLACEEntry 15 }

gs2328fACLACEVLANVID OBJECT-TYPE
   SYNTAX      Integer32(0..4094)
   MAX-ACCESS  read-write
   STATUS      current
   DESCRIPTION
       "Specify the VLAN ID filter for this ACE.
        The vid can't be set when 802.1Q Tagged is disabled.
        default: 0,
        0: Any - No VLAN ID filter is specified.
        range : 0 - 4094 "
   ::= { gs2328fACLACEEntry 16 }

gs2328fACLACEEtherType OBJECT-TYPE
   SYNTAX      Integer32(0..65535)
   MAX-ACCESS  read-write
   STATUS      current
   DESCRIPTION
       " 0: Any - Any but excluding 0x0800(IPv4) 0x0806(ARP) and 0x86DD(IPv6).
         range : 0 or 1536(0x0600)- 65535(0xffff). "
   ::= { gs2328fACLACEEntry 17 }

gs2328fACLACESMAC OBJECT-TYPE
   SYNTAX      DisplayString
   MAX-ACCESS  read-write
   STATUS      current
   DESCRIPTION
       " Configure source MAC address for this ACE.
         <mac-address>: A frame that hits this ACE matches this source MAC address value.
         Any: Don't care."
   ::= { gs2328fACLACEEntry 18 }

gs2328fACLACEDMACType OBJECT-TYPE
   SYNTAX      INTEGER { any(0), broadcast(1), unicast(2), multicast(3) , macAddress(4) }
   MAX-ACCESS  read-write
   STATUS      current
   DESCRIPTION
       "DMAC Type.
        default: 0,
        0: Any - Don't care.
        1: Broadcast - Frame must be broadcast.
        2: Unicast - Frame must be unicast.
        3: Multicast - Frame must be multicast.
        4: mac address.
        range : 0 - 4 "
   ::= { gs2328fACLACEEntry 19 }

gs2328fACLACEDMAC OBJECT-TYPE
   SYNTAX      DisplayString
   MAX-ACCESS  read-write
   STATUS      current
   DESCRIPTION
       " Configure destination MAC address for this ACE.
         <mac-address>: A frame that hits this ACE matches this destination MAC address value.
         Any: Don't care.
         Broadcast: Frame must be broadcast.
         Unicast: Frame must be unicast.
         Multicast: Frame must be multicast. "
   ::= { gs2328fACLACEEntry 20 }

gs2328fACLACEArpOpcode OBJECT-TYPE
   SYNTAX      INTEGER { any(0), arp(1), rarp(2), other(3), noData(4) }
   MAX-ACCESS  read-write
   STATUS      current
   DESCRIPTION
       "Configure ARP opcode for this ACE.
        default: 0,
        0: Any - Don't care.
        1: arp.
        2: rarp.
        3: other.
        4: No data.
        range : 0 - 4 "
   ::= { gs2328fACLACEEntry 21 }

gs2328fACLACEArpFlagsRequestReply OBJECT-TYPE
   SYNTAX      INTEGER { reply(0), request(1), any(2), noData(3)}
   MAX-ACCESS  read-write
   STATUS      current
   DESCRIPTION
       "Specify the available ARP/RARP opcode (OP) flag for this ACE.
        default: 2,
        0: Frame must have ARP Reply or RARP Reply OP flag.
        1: Frame must have ARP Request or RARP Request OP flag set.
        2: Any - Don't care.
        3: No data.
        range : 0 - 3 "
   ::= { gs2328fACLACEEntry 22 }

gs2328fACLACEArpFlagsArpSmac OBJECT-TYPE
   SYNTAX      INTEGER { notEqualSMAC(0), equalSMAC(1), any(2), noData(3)}
   MAX-ACCESS  read-write
   STATUS      current
   DESCRIPTION
       "Specify whether frames can hit the action according to their sender hardware address field (SHA) settings.
        default: 2,
        0: ARP frames where SHA is not equal to the SMAC address.
        1: ARP frames where SHA is equal to the SMAC address.
        2: Any - Don't care.
        3: No data.
        range : 0 - 3 "
   ::= { gs2328fACLACEEntry 23 }

gs2328fACLACEArpFlagsRarpDmac OBJECT-TYPE
   SYNTAX      INTEGER { notEqualDMAC(0), equalDMAC(1), any(2), noData(3)}
   MAX-ACCESS  read-write
   STATUS      current
   DESCRIPTION
       "Specify whether frames can hit the action according to their target hardware address field (THA) settings.
        default: 2,
        0: RARP frames where THA is not equal to the DMAC address.
        1: RARP frames where THA is equal to the DMAC address.
        2: Any - Don't care.
        3: No data.
        range : 0 - 3 "
   ::= { gs2328fACLACEEntry 24 }

gs2328fACLACEArpFlagsLength OBJECT-TYPE
   SYNTAX      INTEGER(0..3)
   MAX-ACCESS  read-write
   STATUS      current
   DESCRIPTION
       "Specify whether frames can hit the action according to their ARP/RARP hardware address length (HLN) and
        protocol address length (PLN) settings.
        default: 2,
        0: ARP/RARP frames where the HLN is not equal to Ethernet(0x06) or the (PLN) is not equal to IPv4(0x04).
        1: ARP/RARP frames where the HLN is equal to Ethernet (0x06) and the (PLN) is equal to IPv4(0x04).
        2: Any - Don't care.
        3: No data.
        range : 0 - 3 "
   ::= { gs2328fACLACEEntry 25 }

gs2328fACLACEArpFlagsIp OBJECT-TYPE
   SYNTAX      INTEGER(0..3)
   MAX-ACCESS  read-write
   STATUS      current
   DESCRIPTION
       "Specify whether frames can hit the action according to their ARP/RARP hardware address space (HRD) settings.
        default: 2,
        0: ARP/RARP frames where the HLD is not equal to Ethernet(1).
        1: ARP/RARP frames where the HLD is equal to Ethernet(1).
        2: Any - Don't care.
        3: No data.
        range : 0 - 3 "
   ::= { gs2328fACLACEEntry 26 }

gs2328fACLACEArpFlagsEthernet OBJECT-TYPE
   SYNTAX      INTEGER(0..3)
   MAX-ACCESS  read-write
   STATUS      current
   DESCRIPTION
       "Specify whether frames can hit the action according to their ARP/RARP protocol address space (PRO) settings.
        default: 2,
        0: ARP/RARP frames where the PRO is not equal to IP\n(0x800).
        1: ARP/RARP frames where the PRO is equal to IP(0x800).
        2: Any - Don't care.
        3: No data.
        range : 0 - 3 "
   ::= { gs2328fACLACEEntry 27 }

gs2328fACLACESIPType OBJECT-TYPE
   SYNTAX      INTEGER { any(0), ip(1), noData(2) }
   MAX-ACCESS  read-write
   STATUS      current
   DESCRIPTION
       "Configure source IP address for this ACE.
        default: 0,
        0: Any - Don't care.
        1: IP Address.
        2: No data.
        range : 0 - 1"
   ::= { gs2328fACLACEEntry 28 }

gs2328fACLACESIPIPAddress OBJECT-TYPE
   SYNTAX      IpAddress
   MAX-ACCESS  read-write
   STATUS      current
   DESCRIPTION
       "A frame that hits this ACE matches this source IP address value."
   ::= { gs2328fACLACEEntry 29 }

gs2328fACLACESIPNetworkPrefix OBJECT-TYPE
   SYNTAX      Integer32(0..32)
   MAX-ACCESS  read-write
   STATUS      current
   DESCRIPTION
       "Network prefix.
        default: 32,
        0: No data.
        range : 1 - 32"
   ::= { gs2328fACLACEEntry 30 }


gs2328fACLACEDIPType OBJECT-TYPE
   SYNTAX      INTEGER { any(0), ip(1),noData(2) }
   MAX-ACCESS  read-write
   STATUS      current
   DESCRIPTION
       "Configure destination IP address for this ACE.
        default: 0,
        0: Any - Don't care.
        1: IP Address.
        2: No data.
        range : 0 - 1"
   ::= { gs2328fACLACEEntry 32 }

gs2328fACLACEDIPIPAddress OBJECT-TYPE
   SYNTAX      IpAddress
   MAX-ACCESS  read-write
   STATUS      current
   DESCRIPTION
       "A frame that hits this ACE matches this destination IP address value."
   ::= { gs2328fACLACEEntry 33 }

gs2328fACLACEDIPNetworkPrefix OBJECT-TYPE
   SYNTAX      Integer32(0..32)
   MAX-ACCESS  read-write
   STATUS      current
   DESCRIPTION
       "Network prefix.
        default: 32,
        0: No data.
        range : 1 - 32"
   ::= { gs2328fACLACEEntry 34 }


gs2328fACLACEIPProtocol OBJECT-TYPE
   SYNTAX      Integer32(0..257)
   MAX-ACCESS  read-write
   STATUS      current
   DESCRIPTION
       "Configure IP protocol for this ACE.
        default: 256,
        256: Any - Don't care.
        257: No data.
        range : 0 - 256"
   ::= { gs2328fACLACEEntry 36 }

gs2328fACLACEIPFlagsTTL OBJECT-TYPE
   SYNTAX      INTEGER (0..3)
   MAX-ACCESS  read-write
   STATUS      current
   DESCRIPTION
       "Configure IP Time-to-Live flags for this ACE.
        default: 2,
        0: IPv4 frames with a Time-to-Live field is equal to zero.
        1: IPv4 frames with a Time-to-Live field greater than zero.
        2: Any - Don't care.
        3: No data.
        range : 0 - 3 "
   ::= { gs2328fACLACEEntry 37 }

gs2328fACLACEIPFlagsOptions OBJECT-TYPE
   SYNTAX      INTEGER { unset(0), set(1), any(2), noData(3) }
   MAX-ACCESS  read-write
   STATUS      current
   DESCRIPTION
       "Configure IP options flag for this ACE.
        default: 2,
        0: IPv4 frames where the options flag is unset.
        1: IPv4 frames where the options flag is set.
        2: Any - Don't care.
        3: No data.
        range : 0 - 3 "
   ::= { gs2328fACLACEEntry 38 }

gs2328fACLACEIPFlagsFragment OBJECT-TYPE
   SYNTAX      INTEGER(0..3)
   MAX-ACCESS  read-write
   STATUS      current
   DESCRIPTION
       "Configure IP fragment offset flags for this ACE.
        default: 2,
        0: IPv4 frames where the MF bit is unset and the FRAG OFFSET field is equal zero.
        1: IPv4 frames where the MF bit is set or the FRAG OFFSET field is greater than zero.
        2: Any - Don't care.
        3: No data.
        range : 0 - 3 "
   ::= { gs2328fACLACEEntry 39 }

gs2328fACLACEICMPType OBJECT-TYPE
   SYNTAX      Integer32(0..257)
   MAX-ACCESS  read-write
   STATUS      current
   DESCRIPTION
       "Configure ICMP type for this ACE.
        default: 256,
        256: Any - Don't care.
        257: No data.
        range : 0 - 256"
   ::= { gs2328fACLACEEntry 40 }

gs2328fACLACEICMPCode OBJECT-TYPE
   SYNTAX      Integer32(0..257)
   MAX-ACCESS  read-write
   STATUS      current
   DESCRIPTION
       "Configure ICMP code for this ACE.
        default: 256,
        256: Any - Don't care.
        257: No data.
        range : 0 - 257"
   ::= { gs2328fACLACEEntry 41 }

gs2328fACLACESourcePortMin OBJECT-TYPE
   SYNTAX      Integer32(0..65536)
   MAX-ACCESS  read-write
   STATUS      current
   DESCRIPTION
       "Configure Source UDP/TCP port range for this ACE.
        default: 0,
        65536: No data.
        range : 0 - 65536"
   ::= { gs2328fACLACEEntry 42 }

gs2328fACLACESourcePortMax OBJECT-TYPE
   SYNTAX      Integer32(0..65536)
   MAX-ACCESS  read-write
   STATUS      current
   DESCRIPTION
       "Configure Source UDP/TCP port range for this ACE.
        default: 0,
        65536: No data.
        range : 0 - 65536"
   ::= { gs2328fACLACEEntry 43 }

gs2328fACLACEDestPortMin OBJECT-TYPE
   SYNTAX      Integer32(0..65536)
   MAX-ACCESS  read-write
   STATUS      current
   DESCRIPTION
       "Configure Destination UDP/TCP port range for this ACE.
        default: 0,
        65536: No data.
        range : 0 - 65535"
   ::= { gs2328fACLACEEntry 44 }

gs2328fACLACEDestPortMax OBJECT-TYPE
   SYNTAX      Integer32(0..65536)
   MAX-ACCESS  read-write
   STATUS      current
   DESCRIPTION
       "Configure Destination UDP/TCP port range for this ACE.
        default: 0,
        65536: No data.
        range : 0 - 65535"
   ::= { gs2328fACLACEEntry 45 }

gs2328fACLACETCPFlagsFin OBJECT-TYPE
   SYNTAX      INTEGER { unset(0), set(1), any(2), noData(3) }
   MAX-ACCESS  read-write
   STATUS      current
   DESCRIPTION
       "Configure TCP (FIN) flags for this ACE.
        default: 2,
        0: TCP frames where the FIN field is unset.
        1: TCP frames where the FIN field is set.
        2: Any - Don't care.
        3: No data.
        range : 0 - 3 "
   ::= { gs2328fACLACEEntry 46 }

gs2328fACLACETCPFlagsSyn OBJECT-TYPE
   SYNTAX      INTEGER { unset(0), set(1), any(2), noData(3) }
   MAX-ACCESS  read-write
   STATUS      current
   DESCRIPTION
       "Configure TCP (SYN) flags for this ACE.
        default: 2,
        0: TCP frames where the SYN field is unset.
        1: TCP frames where the SYN field is set.
        2: Any - Don't care.
        3: No data.
        range : 0 - 3 "
   ::= { gs2328fACLACEEntry 47 }

gs2328fACLACETCPFlagsRst OBJECT-TYPE
   SYNTAX      INTEGER { unset(0), set(1), any(2), noData(3) }
   MAX-ACCESS  read-write
   STATUS      current
   DESCRIPTION
       "Configure TCP (RST) flags for this ACE.
        default: 2,
        0: TCP frames where the RST field is unset.
        1: TCP frames where the RST field is set.
        2: Any - Don't care.
        3: No data.
        range : 0 - 3 "
   ::= { gs2328fACLACEEntry 48 }

gs2328fACLACETCPFlagsPsh OBJECT-TYPE
   SYNTAX      INTEGER { unset(0), set(1), any(2), noData(3) }
   MAX-ACCESS  read-write
   STATUS      current
   DESCRIPTION
       "Configure TCP (PSH) flags for this ACE.
        default: 2,
        0: TCP frames where the PSH field is unset.
        1: TCP frames where the PSH field is set.
        2: Any - Don't care.
        3: No data.
        range : 0 - 3 "
   ::= { gs2328fACLACEEntry 49 }

gs2328fACLACETCPFlagsAck OBJECT-TYPE
   SYNTAX      INTEGER { unset(0), set(1), any(2), noData(3) }
   MAX-ACCESS  read-write
   STATUS      current
   DESCRIPTION
       "Configure TCP (ACK) flags for this ACE.
        default: 2,
        0: TCP frames where the ACK field is unset.
        1: TCP frames where the ACK field is set.
        2: Any - Don't care.
        3: No data.
        range : 0 - 3 "
   ::= { gs2328fACLACEEntry 50 }

gs2328fACLACETCPFlagsUrg OBJECT-TYPE
   SYNTAX      INTEGER { unset(0), set(1), any(2), noData(3) }
   MAX-ACCESS  read-write
   STATUS      current
   DESCRIPTION
       "Configure TCP (URG) flags for this ACE.
        default: 2,
        0: TCP frames where the URG field is unset.
        1: TCP frames where the URG field is set.
        2: Any - Don't care.
        3: No data.
        range : 0 - 3 "
   ::= { gs2328fACLACEEntry 51 }

gs2328fACLACERowStatus OBJECT-TYPE
   SYNTAX      INTEGER { active(1), notInservice(2), destroy(4), undo(5) }
   MAX-ACCESS  read-write
   STATUS      current
   DESCRIPTION
       " 1: active
         2: notInservice
         4: destroy
         5: undo"
   ::= { gs2328fACLACEEntry 66 }


gs2328fACLACEClear OBJECT-TYPE
   SYNTAX       INTEGER { noAction(0), clear(1) }
   MAX-ACCESS   read-write
   STATUS       current
   DESCRIPTION
       "default: 0
        0 : No action
        1 : Clear all ACL counters."
   ::= { gs2328fACLACE 3 }

gs2328fACLACEMoveACEID OBJECT-TYPE
   SYNTAX       Integer32(0..256)
   MAX-ACCESS   read-write
   STATUS       current
   DESCRIPTION
       "Move ACE,
        default: 0
        ACE ID must be exist.
        range : 1 - 256."
   ::= { gs2328fACLACE 4 }

gs2328fACLACEMoveNextACEID OBJECT-TYPE
   SYNTAX       Integer32(0..256)
   MAX-ACCESS   read-write
   STATUS       current
   DESCRIPTION
       "Move ACE,
        default: 0
        If the next ACE ID is non zero, the ACE will be placed before this ACE in the list. If the next ACE ID is zero,
        the ACE will be placed last in the list.
        range : 0 - 256."
   ::= { gs2328fACLACE 5 }

gs2328fACLACEStatusTable OBJECT-TYPE
   SYNTAX      SEQUENCE OF GS2328FACLACEStatusEntry
   MAX-ACCESS  not-accessible
   STATUS      current
   DESCRIPTION
       " ACL ACE Status entry. "
   ::= { gs2328fACLACE 6 }

gs2328fACLACEStatusEntry OBJECT-TYPE
   SYNTAX      GS2328FACLACEStatusEntry
   MAX-ACCESS  not-accessible
   STATUS      current
   DESCRIPTION
       ""
   INDEX    { gs2328fACLACEStatusIndex  }
   ::= { gs2328fACLACEStatusTable 1 }

GS2328FACLACEStatusEntry ::= SEQUENCE {
   gs2328fACLACEStatusIndex          Integer32,
   gs2328fACLACEStatusUser           DisplayString,
   gs2328fACLACEStatusID             Integer32,
   gs2328fACLACEStatusIngressPort    DisplayString,
   gs2328fACLACEStatusFrameType      DisplayString,
   gs2328fACLACEStatusAction         DisplayString,
   gs2328fACLACEStatusRateLimiter    DisplayString,
   gs2328fACLACEStatusPortCopy       DisplayString,
   gs2328fACLACEStatusMirror         DisplayString,
   gs2328fACLACEStatusCPU            DisplayString,
   gs2328fACLACEStatusCounter        Counter32,
   gs2328fACLACEStatusConflict       DisplayString
}

gs2328fACLACEStatusIndex OBJECT-TYPE
   SYNTAX      Integer32(1..256)
   MAX-ACCESS  not-accessible
   STATUS      current
   DESCRIPTION
       " "
   ::= { gs2328fACLACEStatusEntry 1 }

gs2328fACLACEStatusUser OBJECT-TYPE
   SYNTAX      DisplayString
   MAX-ACCESS  read-only
   STATUS      current
   DESCRIPTION
       " Indicates the ACL user.
         S : Static.
         IPMG : IP Management.
         IPSG : IP Source Guard.
         IPMC : IPMC.
         ARPI : Arp Inspection.
         UPnP : UPnP.
         DHCP : DHCP. "
   ::= { gs2328fACLACEStatusEntry 2 }

gs2328fACLACEStatusID OBJECT-TYPE
   SYNTAX      Integer32(1..256)
   MAX-ACCESS  read-only
   STATUS      current
   DESCRIPTION
       " ACE ID.
         range : 1 - 256. "
   ::= { gs2328fACLACEStatusEntry 3 }

gs2328fACLACEStatusIngressPort OBJECT-TYPE
   SYNTAX      DisplayString
   MAX-ACCESS  read-only
   STATUS      current
   DESCRIPTION
       " Indicates the ingress port of the ACE. Possible values are:
         All: The ACE will match all ingress port.
         Port: The ACE will match a specific ingress port. "
   ::= { gs2328fACLACEStatusEntry 4 }

gs2328fACLACEStatusFrameType OBJECT-TYPE
   SYNTAX      DisplayString
   MAX-ACCESS  read-only
   STATUS      current
   DESCRIPTION
       " Indicates the frame type of the ACE. "
   ::= { gs2328fACLACEStatusEntry 5 }

gs2328fACLACEStatusAction OBJECT-TYPE
   SYNTAX      DisplayString
   MAX-ACCESS  read-only
   STATUS      current
   DESCRIPTION
       " Indicates the forwarding action of the ACE. "
   ::= { gs2328fACLACEStatusEntry 6 }

gs2328fACLACEStatusRateLimiter OBJECT-TYPE
   SYNTAX      DisplayString
   MAX-ACCESS  read-only
   STATUS      current
   DESCRIPTION
       " Indicates the rate limiter number of the ACE. "
   ::= { gs2328fACLACEStatusEntry 7 }

gs2328fACLACEStatusPortCopy OBJECT-TYPE
   SYNTAX      DisplayString
   MAX-ACCESS  read-only
   STATUS      current
   DESCRIPTION
       " Indicates the port redirect operation of the ACE. Frames matching the ACE are redirected to the port number. "
   ::= { gs2328fACLACEStatusEntry 8 }

gs2328fACLACEStatusMirror OBJECT-TYPE
   SYNTAX      DisplayString
   MAX-ACCESS  read-only
   STATUS      current
   DESCRIPTION
       " Specify the mirror operation of this port. "
   ::= { gs2328fACLACEStatusEntry 9 }

gs2328fACLACEStatusCPU OBJECT-TYPE
   SYNTAX      DisplayString
   MAX-ACCESS  read-only
   STATUS      current
   DESCRIPTION
       " Forward packet that matched the specific ACE to CPU. "
   ::= { gs2328fACLACEStatusEntry 10 }

gs2328fACLACEStatusCounter OBJECT-TYPE
   SYNTAX      Counter32
   MAX-ACCESS  read-only
   STATUS      current
   DESCRIPTION
       " The counter indicates the number of times the ACE was hit by a frame. "
   ::= { gs2328fACLACEStatusEntry 11 }

gs2328fACLACEStatusConflict OBJECT-TYPE
   SYNTAX      DisplayString
   MAX-ACCESS  read-only
   STATUS      current
   DESCRIPTION
       " Indicates the hardware status of the specific ACE. The specific ACE is not applied to the hardware due to hardware limitations. "
   ::= { gs2328fACLACEStatusEntry 12 }

gs2328fLoopProtection                                                  OBJECT IDENTIFIER ::= { gs2328fConfiguration 12 }

gs2328fLoopProtectionConfig                                            OBJECT IDENTIFIER ::= { gs2328fLoopProtection 1 }

gs2328fLoopProtectionGlobalEnable OBJECT-TYPE
   SYNTAX      INTEGER { disable(0), enable(1) }
   MAX-ACCESS  read-write
   STATUS      current
   DESCRIPTION
       "Configure loop protection mode.
        0: disable,
        1: enable,
        default: disable. "
   ::= { gs2328fLoopProtectionConfig 1 }

gs2328fLoopProtectionTranmisstionTime OBJECT-TYPE
   SYNTAX      Integer32(1..10)
   MAX-ACCESS  read-write
   STATUS      current
   DESCRIPTION
       "Configure loop protection transmit interval.
        default: 5,
        range: 1-10. "
   ::= { gs2328fLoopProtectionConfig 2 }

gs2328fLoopProtectionShutdownTime OBJECT-TYPE
   SYNTAX      Integer32(0..604800)
   MAX-ACCESS  read-write
   STATUS      current
   DESCRIPTION
       "Configure loop protection shutdown time.
        default: 180,
        range: 0-604800. "
   ::= { gs2328fLoopProtectionConfig 3 }

gs2328fLoopProtectionConfigurationTable OBJECT-TYPE
   SYNTAX      SEQUENCE OF GS2328FLoopProtectionConfigurationEntry
   MAX-ACCESS  not-accessible
   STATUS      current
   DESCRIPTION
       " Show Loop Protection configurations. "
   ::= { gs2328fLoopProtectionConfig 4 }

gs2328fLoopProtectionConfigurationEntry OBJECT-TYPE
   SYNTAX      GS2328FLoopProtectionConfigurationEntry
   MAX-ACCESS  not-accessible
   STATUS      current
   DESCRIPTION
       ""
   INDEX    { gs2328fLoopProtectionConfPort  }
   ::= { gs2328fLoopProtectionConfigurationTable 1 }

GS2328FLoopProtectionConfigurationEntry ::= SEQUENCE {
   gs2328fLoopProtectionConfPort	    Integer32,
   gs2328fLoopProtectionConfEnable	INTEGER,
   gs2328fLoopProtectionConfAction	INTEGER,
   gs2328fLoopProtectionConfTxmode	INTEGER
}

gs2328fLoopProtectionConfPort OBJECT-TYPE
   SYNTAX      Integer32(1..4095)
   MAX-ACCESS  not-accessible
   STATUS      current
   DESCRIPTION
       " port, range : 1 - port number. "
   ::= { gs2328fLoopProtectionConfigurationEntry 1 }

gs2328fLoopProtectionConfEnable OBJECT-TYPE
   SYNTAX      INTEGER { disable(0), enable(1) }
   MAX-ACCESS  read-write
   STATUS      current
   DESCRIPTION
       "Configure loop protection port mode.
        0: disable,
        1: enable,
        default: enable. "
   ::= { gs2328fLoopProtectionConfigurationEntry 2 }

gs2328fLoopProtectionConfAction OBJECT-TYPE
   SYNTAX      INTEGER { shutdown(0), shutdownLog(1), log(2) }
   MAX-ACCESS  read-write
   STATUS      current
   DESCRIPTION
       " Configure loop protection port action.
         0: Shutdown port,
         1: Shutdown port and Log,
         2: Log Only,
         default: Shutdown port. "
   ::= { gs2328fLoopProtectionConfigurationEntry 3 }

gs2328fLoopProtectionConfTxmode OBJECT-TYPE
   SYNTAX      INTEGER { disable(0), enable(1) }
   MAX-ACCESS  read-write
   STATUS      current
   DESCRIPTION
       "Configure loop protection port transmit mode.
        0: disable,
        1: enable,
        default: enable. "
   ::= { gs2328fLoopProtectionConfigurationEntry 4 }

gs2328fLoopProtectionStatusTable OBJECT-TYPE
   SYNTAX      SEQUENCE OF GS2328FLoopProtectionStatusEntry
   MAX-ACCESS  not-accessible
   STATUS      current
   DESCRIPTION
       " Show Loop Protection Status. "
   ::= { gs2328fLoopProtection 2 }

gs2328fLoopProtectionStatusEntry OBJECT-TYPE
   SYNTAX      GS2328FLoopProtectionStatusEntry
   MAX-ACCESS  not-accessible
   STATUS      current
   DESCRIPTION
       ""
   INDEX    { gs2328fLoopProtectionStatusPort  }
   ::= { gs2328fLoopProtectionStatusTable 1 }

GS2328FLoopProtectionStatusEntry ::= SEQUENCE {
   gs2328fLoopProtectionStatusPort	       Integer32,
   gs2328fLoopProtectionStatusAction	       DisplayString,
   gs2328fLoopProtectionStatusTransmit	   DisplayString,
   gs2328fLoopProtectionStatusLoops	       Integer32,
   gs2328fLoopProtectionStatusStatus	       DisplayString,
   gs2328fLoopProtectionStatusLoop	       DisplayString,
   gs2328fLoopProtectionStatusTimeLastLoop  DisplayString
}

gs2328fLoopProtectionStatusPort OBJECT-TYPE
   SYNTAX      Integer32(1..4095)
   MAX-ACCESS  not-accessible
   STATUS      current
   DESCRIPTION
       " port, range : 1 - port number. "
   ::= { gs2328fLoopProtectionStatusEntry 1 }

gs2328fLoopProtectionStatusAction OBJECT-TYPE
   SYNTAX      DisplayString
   MAX-ACCESS  read-only
   STATUS      current
   DESCRIPTION
       " The currently configured port action. "
   ::= { gs2328fLoopProtectionStatusEntry 2 }

gs2328fLoopProtectionStatusTransmit OBJECT-TYPE
   SYNTAX      DisplayString
   MAX-ACCESS  read-only
   STATUS      current
   DESCRIPTION
       " The currently configured port transmit mode. "
   ::= { gs2328fLoopProtectionStatusEntry 3 }

gs2328fLoopProtectionStatusLoops OBJECT-TYPE
   SYNTAX      Integer32(0..1000000)
   MAX-ACCESS  read-only
   STATUS      current
   DESCRIPTION
       " The number of loops detected on this port. "
   ::= { gs2328fLoopProtectionStatusEntry 4 }

gs2328fLoopProtectionStatusStatus OBJECT-TYPE
   SYNTAX      DisplayString
   MAX-ACCESS  read-only
   STATUS      current
   DESCRIPTION
       " The current loop protection status of the port. "
   ::= { gs2328fLoopProtectionStatusEntry 5 }

gs2328fLoopProtectionStatusLoop OBJECT-TYPE
   SYNTAX      DisplayString
   MAX-ACCESS  read-only
   STATUS      current
   DESCRIPTION
       " Whether a loop is currently detected on the port. "
   ::= { gs2328fLoopProtectionStatusEntry 6 }

gs2328fLoopProtectionStatusTimeLastLoop OBJECT-TYPE
   SYNTAX      DisplayString
   MAX-ACCESS  read-only
   STATUS      current
   DESCRIPTION
       " The time of the last loop event detected. "
   ::= { gs2328fLoopProtectionStatusEntry 7 }

gs2328fQos                                                             OBJECT IDENTIFIER ::= { gs2328fConfiguration 14 }

gs2328fQosPortClassification                                           OBJECT IDENTIFIER ::= { gs2328fQos 1 }

gs2328fQosPortClassificationTable OBJECT-TYPE
   SYNTAX      SEQUENCE OF GS2328FQosPortClassificationEntry
   MAX-ACCESS  not-accessible
   STATUS      current
   DESCRIPTION
       " QoS Ingress Port Classification . "
   ::= { gs2328fQosPortClassification  1 }

gs2328fQosPortClassificationEntry OBJECT-TYPE
   SYNTAX      GS2328FQosPortClassificationEntry
   MAX-ACCESS  not-accessible
   STATUS      current
   DESCRIPTION
       ""
   INDEX    { gs2328fQosPortClassificationPort  }
   ::= { gs2328fQosPortClassificationTable 1 }

GS2328FQosPortClassificationEntry ::= SEQUENCE {
   gs2328fQosPortClassificationPort	        Integer32,
   gs2328fQosPortClassificationQoSclass       Integer32,
   gs2328fQosPortClassificationDPlevel	    Integer32,
   gs2328fQosPortClassificationPCP	        Integer32,
   gs2328fQosPortClassificationDEI	        INTEGER,
   gs2328fQosPortClassificationTagClass	    INTEGER,
   gs2328fQosPortClassificationDSCPBased    INTEGER,
   gs2328fQosPortClassificationAddressMode  INTEGER
}

gs2328fQosPortClassificationPort OBJECT-TYPE
   SYNTAX      Integer32(1..4095)
   MAX-ACCESS  not-accessible
   STATUS      current
   DESCRIPTION
       " port, range : 1 - port number. "
   ::= { gs2328fQosPortClassificationEntry 1 }

gs2328fQosPortClassificationQoSclass OBJECT-TYPE
   SYNTAX      Integer32(0..7)
   MAX-ACCESS  read-write
   STATUS      current
   DESCRIPTION
      "Controls the default QoS class, i.e., the QoS class
      for frames not classified in any other way. There is
      a one to one mapping between QoS class, queue and priority.
      A QoS class of 0 (zero) has the lowest priority.
      Note: If the QoS class has been dynamically changed, then
      the actual QoS class is shown in parentheses after the
      configured QoS class.

      Configure the default QoS class.
        range: 0-7,
        default: 0. "
   ::= { gs2328fQosPortClassificationEntry 2 }

gs2328fQosPortClassificationDPlevel OBJECT-TYPE
   SYNTAX      Integer32(0|1)
   MAX-ACCESS  read-write
   STATUS      current
   DESCRIPTION
       " DP level for frames not classified in any other way.
         range: 0-1,
         default: 0. "
   ::= { gs2328fQosPortClassificationEntry 3 }

gs2328fQosPortClassificationPCP OBJECT-TYPE
   SYNTAX      Integer32(0..7)
   MAX-ACCESS  read-write
   STATUS      current
   DESCRIPTION
      " Priority Code Point. It is a 3-bit field storing the priority level for the 802.1Q frame.
        range: 0-7,
        default: 0. "
   ::= { gs2328fQosPortClassificationEntry 4 }

gs2328fQosPortClassificationDEI OBJECT-TYPE
   SYNTAX      INTEGER { disable(0), enable(1) }
   MAX-ACCESS  read-write
   STATUS      current
   DESCRIPTION
      " Drop Eligible Indicator. It is a 1-bit field in the VLAN.
        range 0-1,
        default: 0. "
   ::= { gs2328fQosPortClassificationEntry 5 }

gs2328fQosPortClassificationTagClass OBJECT-TYPE
   SYNTAX      INTEGER { disable(0), enable(1) }
   MAX-ACCESS  read-write
   STATUS      current
   DESCRIPTION
      " Configure the classification mode for tagged frames.
        0: Disable,
        1: Enable,
        default: Disable. "
   ::= { gs2328fQosPortClassificationEntry 6 }

gs2328fQosPortClassificationDSCPBased OBJECT-TYPE
   SYNTAX      INTEGER { disable(0), enable(1) }
   MAX-ACCESS  read-write
   STATUS      current
   DESCRIPTION
      " Click to Enable DSCP Based QoS Ingress Port Classification.
        0: disable,
        1: enable,
        default: disable. "
   ::= { gs2328fQosPortClassificationEntry 7 }

gs2328fQosPortClassificationAddressMode OBJECT-TYPE
   SYNTAX      INTEGER { source(0), destination(1) }
   MAX-ACCESS  read-write
   STATUS      current
   DESCRIPTION
      "The IP/MAC address mode specifying whether the QCL classification
       must be based on source (SMAC/SIP) or destination (DMAC/DIP)
       addresses on this port.
        0: source,
        1: destination,
        default: source. "
   ::= { gs2328fQosPortClassificationEntry 8 }

gs2328fQoSIngressPortTagClassificationTable OBJECT-TYPE
   SYNTAX      SEQUENCE OF GS2328FQoSIngressPortTagClassificationEntry
   MAX-ACCESS  not-accessible
   STATUS      current
   DESCRIPTION
       " Show QoS Ingress Port Tag Classification. "
   ::= { gs2328fQosPortClassification 2 }

gs2328fQoSIngressPortTagClassificationEntry OBJECT-TYPE
   SYNTAX      GS2328FQoSIngressPortTagClassificationEntry
   MAX-ACCESS  not-accessible
   STATUS      current
   DESCRIPTION
       ""
   INDEX    { gs2328fQoSIngressPortTagClassificationPort, gs2328fQoSIngressPortTagPCP, gs2328fQoSIngressPortTagDEI  }
   ::= { gs2328fQoSIngressPortTagClassificationTable 1 }

GS2328FQoSIngressPortTagClassificationEntry ::= SEQUENCE {
   gs2328fQoSIngressPortTagClassificationPort	Integer32,
   gs2328fQoSIngressPortTagPCP					INTEGER,
   gs2328fQoSIngressPortTagDEI					INTEGER,
   gs2328fQoSIngressPortTagQosClass				Integer32,
   gs2328fQoSIngressPortTagDPLevel				Integer32
}

gs2328fQoSIngressPortTagClassificationPort OBJECT-TYPE
   SYNTAX      Integer32(1..4095)
   MAX-ACCESS  not-accessible
   STATUS      current
   DESCRIPTION
       " port, range : 1 - port number. "
   ::= { gs2328fQoSIngressPortTagClassificationEntry 1 }

gs2328fQoSIngressPortTagPCP OBJECT-TYPE
   SYNTAX      INTEGER { pcp0(1), pcp1(2), pcp2(3), pcp3(4), pcp4(5), pcp5(6), pcp6(7), pcp7(8) }
   MAX-ACCESS  not-accessible
   STATUS      current
   DESCRIPTION
       " range: 1-8,
         PCP0:1, PCP1:2...  "
   ::= { gs2328fQoSIngressPortTagClassificationEntry 2 }

gs2328fQoSIngressPortTagDEI OBJECT-TYPE
   SYNTAX      INTEGER { dei0(1), dei1(2) }
   MAX-ACCESS  not-accessible
   STATUS      current
   DESCRIPTION
       " range: 1-2,
         DEI0:1, DEI1:2. "
   ::= { gs2328fQoSIngressPortTagClassificationEntry 3 }

gs2328fQoSIngressPortTagQosClass OBJECT-TYPE
   SYNTAX      Integer32 (0..7)
   MAX-ACCESS  read-write
   STATUS      current
   DESCRIPTION
       " range: 0-7.  "
   ::= { gs2328fQoSIngressPortTagClassificationEntry 4 }

gs2328fQoSIngressPortTagDPLevel OBJECT-TYPE
   SYNTAX      Integer32 (0|1)
   MAX-ACCESS  read-write
   STATUS      current
   DESCRIPTION
       " range: 0-1.  "
   ::= { gs2328fQoSIngressPortTagClassificationEntry 5 }


gs2328fQosPortPolicingTable OBJECT-TYPE
   SYNTAX      SEQUENCE OF GS2328FQosPortPolicingEntry
   MAX-ACCESS  not-accessible
   STATUS      current
   DESCRIPTION
       "  configure the Policer settings for all switch ports. "
   ::= { gs2328fQos  2 }

gs2328fQosPortPolicingEntry OBJECT-TYPE
   SYNTAX      GS2328FQosPortPolicingEntry
   MAX-ACCESS  not-accessible
   STATUS      current
   DESCRIPTION
       ""
   INDEX    { gs2328fQosPortPolicingPort  }
   ::= { gs2328fQosPortPolicingTable 1 }

GS2328FQosPortPolicingEntry ::= SEQUENCE {
   gs2328fQosPortPolicingPort	        Integer32,
   gs2328fQosPortPolicingMode           INTEGER,
   gs2328fQosPortPolicingRate	        Integer32,
   gs2328fQosPortPolicingUnit	        INTEGER,
   gs2328fQosPortPolicingFlowControl	INTEGER
}

gs2328fQosPortPolicingPort OBJECT-TYPE
   SYNTAX      Integer32 (1..4095)
   MAX-ACCESS  not-accessible
   STATUS      current
   DESCRIPTION
       " port, range : 1 - port number. "
   ::= { gs2328fQosPortPolicingEntry 1 }

gs2328fQosPortPolicingMode OBJECT-TYPE
   SYNTAX      INTEGER { disable(0), enable(1) }
   MAX-ACCESS  read-write
   STATUS      current
   DESCRIPTION
      " Controls whether the policer is enabled on this switch port.
        0: disable,
        1: enable,
        default: disable. "
   ::= { gs2328fQosPortPolicingEntry 2 }

gs2328fQosPortPolicingRate OBJECT-TYPE
   SYNTAX      Integer32(100..10000000)
   MAX-ACCESS  read-write
   STATUS      current
   DESCRIPTION
       " Controls the rate for the policer.
         range: 100-10000000(kbps/fps),
         default: 500(kbps). "
   ::= { gs2328fQosPortPolicingEntry 3 }

gs2328fQosPortPolicingUnit OBJECT-TYPE
   SYNTAX      INTEGER { kbps(0), fps(1) }
   MAX-ACCESS  read-write
   STATUS      current
   DESCRIPTION
       " Controls the unit of measure for the policer rate.
         0: kbps,
         1: fps,
         default: kbps. "
   ::= { gs2328fQosPortPolicingEntry 4 }

gs2328fQosPortPolicingFlowControl OBJECT-TYPE
   SYNTAX      INTEGER { disable(0), enable(1) }
   MAX-ACCESS  read-write
   STATUS      current
   DESCRIPTION
       " If flow control is enabled and the port is in flow control mode,
        then pause frames are sent instead of discarding frames.
         0: disable,
         1: enable,
         default: disable. "
   ::= { gs2328fQosPortPolicingEntry 5 }

gs2328fQosPortScheduler                                           OBJECT IDENTIFIER ::= { gs2328fQos 3 }

gs2328fQosPortSchedulerModeTable OBJECT-TYPE
   SYNTAX      SEQUENCE OF GS2328FQosPortSchedulerModeEntry
   MAX-ACCESS  not-accessible
   STATUS      current
   DESCRIPTION
       " configure the basic QoS Port Scheduler Mode settings for all switch ports. "
   ::= { gs2328fQosPortScheduler  1 }

gs2328fQosPortSchedulerModeEntry OBJECT-TYPE
   SYNTAX      GS2328FQosPortSchedulerModeEntry
   MAX-ACCESS  not-accessible
   STATUS      current
   DESCRIPTION
       ""
   INDEX    { gs2328fQosSchedulerModePort  }
   ::= { gs2328fQosPortSchedulerModeTable 1 }

GS2328FQosPortSchedulerModeEntry ::= SEQUENCE {
   gs2328fQosSchedulerModePort	                Integer32,
   gs2328fQosSchedulerMode                        INTEGER,
   gs2328fQosSchedulerShaper	                    INTEGER,
   gs2328fQosSchedulerShaperRate	                Integer32
}

gs2328fQosSchedulerModePort OBJECT-TYPE
   SYNTAX      Integer32 (1..4095)
   MAX-ACCESS  not-accessible
   STATUS      current
   DESCRIPTION
       " port, range : 1 - port number. "
   ::= { gs2328fQosPortSchedulerModeEntry 1 }

gs2328fQosSchedulerMode OBJECT-TYPE
   SYNTAX      INTEGER { strictPriority(0), weighted(1) }
   MAX-ACCESS  read-write
   STATUS      current
   DESCRIPTION
       " Controls whether the scheduler mode is Strict Priority or Weighted
       on this switch port.
       0:Strict Priority
       1:Weighted
         default: Strict Priority. "
   ::= { gs2328fQosPortSchedulerModeEntry 2 }

gs2328fQosSchedulerShaper OBJECT-TYPE
   SYNTAX      INTEGER { disable(0), enable(1) }
   MAX-ACCESS  read-write
   STATUS      current
   DESCRIPTION
       " Controls whether the port shaper is enabled
         0: Disable
         1: Enable.
         default: disable. "
   ::= { gs2328fQosPortSchedulerModeEntry 3 }

gs2328fQosSchedulerShaperRate OBJECT-TYPE
   SYNTAX      Integer32(100..1000000)
   MAX-ACCESS  read-write
   STATUS      current
   DESCRIPTION
       " Controls the rate for the port shaper.
         range: 100-1000000
         default: 500 kbps. "
   ::= { gs2328fQosPortSchedulerModeEntry 4 }

gs2328fQosPortSchedulerTable OBJECT-TYPE
   SYNTAX      SEQUENCE OF GS2328FQosPortSchedulerEntry
   MAX-ACCESS  not-accessible
   STATUS      current
   DESCRIPTION
       " Show Qos Port Scheduler. "
   ::= { gs2328fQosPortScheduler 2 }

gs2328fQosPortSchedulerEntry OBJECT-TYPE
   SYNTAX      GS2328FQosPortSchedulerEntry
   MAX-ACCESS  not-accessible
   STATUS      current
   DESCRIPTION
       ""
   INDEX    { gs2328fQosSchedulerPort, gs2328fQosSchedulerPortQueue}
   ::= { gs2328fQosPortSchedulerTable 1 }

GS2328FQosPortSchedulerEntry ::= SEQUENCE {
   gs2328fQosSchedulerPort						Integer32,
   gs2328fQosSchedulerPortQueue					INTEGER,
   gs2328fQosSchedulerPortQueueShaper				INTEGER,
   gs2328fQosSchedulerPortQueueShaperRate			Integer32,
   gs2328fQosSchedulerPortQueueShaperExcess		INTEGER,
   gs2328fQosSchedulerPortQueueSchedulerWeight	Integer32,
   gs2328fQosSchedulerPortQueueSchedulerPercent	DisplayString
}

gs2328fQosSchedulerPort OBJECT-TYPE
   SYNTAX      Integer32 (1..4095)
   MAX-ACCESS  not-accessible
   STATUS      current
   DESCRIPTION
       " port, range : 1 - port number. "
   ::= { gs2328fQosPortSchedulerEntry 1 }

gs2328fQosSchedulerPortQueue OBJECT-TYPE
   SYNTAX      INTEGER { q0(1), q1(2), q2(3), q3(4), q4(5), q5(6), q6(7), q7(8) }
   MAX-ACCESS  not-accessible
   STATUS      current
   DESCRIPTION
       " range: 1-8.
         Q0: 1, Q1: 2, ... "
   ::= { gs2328fQosPortSchedulerEntry 2 }

gs2328fQosSchedulerPortQueueShaper OBJECT-TYPE
   SYNTAX      INTEGER { disable(0), enable(1) }
   MAX-ACCESS  read-write
   STATUS      current
   DESCRIPTION
       " 0: disable  1:enable,
         default: 0.  "
   ::= { gs2328fQosPortSchedulerEntry 3 }

gs2328fQosSchedulerPortQueueShaperRate OBJECT-TYPE
   SYNTAX      Integer32(100..1000000)
   MAX-ACCESS  read-write
   STATUS      current
   DESCRIPTION
       " range: 100..1000000 kbps.  "
   ::= { gs2328fQosPortSchedulerEntry 4 }

gs2328fQosSchedulerPortQueueShaperExcess OBJECT-TYPE
   SYNTAX      INTEGER { disable(0), enable(1) }
   MAX-ACCESS  read-write
   STATUS      current
   DESCRIPTION
       " 0: disable  1:enable,
         default: 0.  "
   ::= { gs2328fQosPortSchedulerEntry 5 }

gs2328fQosSchedulerPortQueueSchedulerWeight OBJECT-TYPE
   SYNTAX      Integer32(0..100)
   MAX-ACCESS  read-write
   STATUS      current
   DESCRIPTION
       " range: 1-100,
         default: 17.
         Only use in Q0 - Q5.  Q6 & Q7 show 0 "
   ::= { gs2328fQosPortSchedulerEntry 6 }

gs2328fQosSchedulerPortQueueSchedulerPercent OBJECT-TYPE
   SYNTAX      DisplayString
   MAX-ACCESS  read-only
   STATUS      current
   DESCRIPTION
       " Only use in Q0 - Q5. Q6 & Q7 show empty "
   ::= { gs2328fQosPortSchedulerEntry 7 }

gs2328fQosPortEgressTagRemarking                                           OBJECT IDENTIFIER ::= { gs2328fQos 4 }

gs2328fQosPortEgressTagRemarkingTable OBJECT-TYPE
   SYNTAX      SEQUENCE OF GS2328FQosPortEgressTagRemarkingEntry
   MAX-ACCESS  not-accessible
   STATUS      current
   DESCRIPTION
       " configure the basic QoS Port Egress Tag Remark Configuration settings for all switch ports. "
   ::= { gs2328fQosPortEgressTagRemarking  1 }

gs2328fQosPortEgressTagRemarkingEntry OBJECT-TYPE
   SYNTAX      GS2328FQosPortEgressTagRemarkingEntry
   MAX-ACCESS  not-accessible
   STATUS      current
   DESCRIPTION
       ""
   INDEX    { gs2328fQosEgressTagRemarkingPort  }
   ::= { gs2328fQosPortEgressTagRemarkingTable 1 }

GS2328FQosPortEgressTagRemarkingEntry ::= SEQUENCE {
   gs2328fQosEgressTagRemarkingPort	                Integer32,
   gs2328fQosEgressTagRemarkingMode	                INTEGER
}

gs2328fQosEgressTagRemarkingPort OBJECT-TYPE
   SYNTAX      Integer32 (1..4095)
   MAX-ACCESS  not-accessible
   STATUS      current
   DESCRIPTION
       " port, range : 1 - port number. "
   ::= { gs2328fQosPortEgressTagRemarkingEntry 1 }

gs2328fQosEgressTagRemarkingMode OBJECT-TYPE
   SYNTAX      INTEGER { classified(0), default(1), mapped(2) }
   MAX-ACCESS  read-write
   STATUS      current
   DESCRIPTION
       " the tag remarking mode for this port.
       0:Classified, Use classified PCP/DEI values.
       1:Default, Use default PCP/DEI values.
       2:Mapped, Use mapped versions of QoS class and DP level."
   ::= { gs2328fQosPortEgressTagRemarkingEntry 2 }


gs2328fQosPortEgressTagRemarkingDefTable OBJECT-TYPE
   SYNTAX      SEQUENCE OF GS2328FQosPortEgressTagRemarkingDefEntry
   MAX-ACCESS  not-accessible
   STATUS      current
   DESCRIPTION
       " configure the basic QoS Port Egress Tag Remark Configuration settings for all switch ports. "
   ::= { gs2328fQosPortEgressTagRemarking  2 }

gs2328fQosPortEgressTagRemarkingDefEntry OBJECT-TYPE
   SYNTAX      GS2328FQosPortEgressTagRemarkingDefEntry
   MAX-ACCESS  not-accessible
   STATUS      current
   DESCRIPTION
       ""
   INDEX    { gs2328fQosEgressTagRemarkingDefPort  }
   ::= { gs2328fQosPortEgressTagRemarkingDefTable 1 }

GS2328FQosPortEgressTagRemarkingDefEntry ::= SEQUENCE {
   gs2328fQosEgressTagRemarkingDefPort	            Integer32,
   gs2328fQosEgressTagRemarkingDefPCP	                Integer32,
   gs2328fQosEgressTagRemarkingDefDEI	                INTEGER
}

gs2328fQosEgressTagRemarkingDefPort OBJECT-TYPE
   SYNTAX      Integer32(1..4095)
   MAX-ACCESS  not-accessible
   STATUS      current
   DESCRIPTION
       " port, range : 1 - port number. "
   ::= { gs2328fQosPortEgressTagRemarkingDefEntry 1 }

gs2328fQosEgressTagRemarkingDefPCP OBJECT-TYPE
   SYNTAX      Integer32(0..7)
   MAX-ACCESS  read-write
   STATUS      current
   DESCRIPTION
       " Controls the default PCP
       Range : 0-7"
   ::= { gs2328fQosPortEgressTagRemarkingDefEntry 2 }

gs2328fQosEgressTagRemarkingDefDEI OBJECT-TYPE
   SYNTAX      INTEGER { disable(0), enable(1) }
   MAX-ACCESS  read-write
   STATUS      current
   DESCRIPTION
       " controls the DEI
       Range 0-1"
   ::= { gs2328fQosPortEgressTagRemarkingDefEntry 3 }

gs2328fQosPortEgressTagRemarkingMapTable OBJECT-TYPE
   SYNTAX      SEQUENCE OF GS2328FQosPortEgressTagRemarkingMapEntry
   MAX-ACCESS  not-accessible
   STATUS      current
   DESCRIPTION
       " Show Qos Port Egress Tag Remarking Map. "
   ::= { gs2328fQosPortEgressTagRemarking 4 }

gs2328fQosPortEgressTagRemarkingMapEntry OBJECT-TYPE
   SYNTAX      GS2328FQosPortEgressTagRemarkingMapEntry
   MAX-ACCESS  not-accessible
   STATUS      current
   DESCRIPTION
       ""
   INDEX    { gs2328fQosPortEgressTagRemarkingMapPort, gs2328fQosTagRemarkingQoSClass, gs2328fQosTagRemarkingDPLevel  }
   ::= { gs2328fQosPortEgressTagRemarkingMapTable 1 }

GS2328FQosPortEgressTagRemarkingMapEntry ::= SEQUENCE {
   gs2328fQosPortEgressTagRemarkingMapPort	Integer32,
   gs2328fQosTagRemarkingQoSClass			INTEGER,
   gs2328fQosTagRemarkingDPLevel				INTEGER,
   gs2328fQosTagRemarkingPCP					Integer32,
   gs2328fQosTagRemarkingDEI					INTEGER
}

gs2328fQosPortEgressTagRemarkingMapPort OBJECT-TYPE
   SYNTAX      Integer32 (1..4095)
   MAX-ACCESS  not-accessible
   STATUS      current
   DESCRIPTION
       " port, range : 1 - port number. "
   ::= { gs2328fQosPortEgressTagRemarkingMapEntry 1 }

gs2328fQosTagRemarkingQoSClass OBJECT-TYPE
   SYNTAX      INTEGER {
                        class0(1),
                        class1(2),
                        class2(3),
                        class3(4),
                        class4(5),
                        class5(6),
                        class6(7),
                        class7(8)
                        }
   MAX-ACCESS  not-accessible
   STATUS      current
   DESCRIPTION
       " range: 1-8,
         QoS Class0: 1, QoS Class1: 2...  "
   ::= { gs2328fQosPortEgressTagRemarkingMapEntry 2 }

gs2328fQosTagRemarkingDPLevel OBJECT-TYPE
   SYNTAX      INTEGER { level0(1), level1(2) }
   MAX-ACCESS  not-accessible
   STATUS      current
   DESCRIPTION
       " range: 1-2,
         DP Level0: 1, DP Level1: 2. "
   ::= { gs2328fQosPortEgressTagRemarkingMapEntry 3 }

gs2328fQosTagRemarkingPCP OBJECT-TYPE
   SYNTAX      Integer32 (0..7)
   MAX-ACCESS  read-write
   STATUS      current
   DESCRIPTION
       " range: 0-7.  "
   ::= { gs2328fQosPortEgressTagRemarkingMapEntry 4 }

gs2328fQosTagRemarkingDEI OBJECT-TYPE
   SYNTAX      INTEGER (0|1)
   MAX-ACCESS  read-write
   STATUS      current
   DESCRIPTION
       " range: 0-1.  "
   ::= { gs2328fQosPortEgressTagRemarkingMapEntry 5 }


gs2328fQosPortDSCPTable OBJECT-TYPE
   SYNTAX      SEQUENCE OF GS2328FQosPortDSCPEntry
   MAX-ACCESS  not-accessible
   STATUS      current
   DESCRIPTION
       " configure the basic QoS Port DSCP Configuration settings for all switch ports. "
   ::= { gs2328fQos  5 }

gs2328fQosPortDSCPEntry OBJECT-TYPE
   SYNTAX      GS2328FQosPortDSCPEntry
   MAX-ACCESS  not-accessible
   STATUS      current
   DESCRIPTION
       ""
   INDEX    { gs2328fQosPortDSCPPort  }
   ::= { gs2328fQosPortDSCPTable 1 }

GS2328FQosPortDSCPEntry ::= SEQUENCE {
   gs2328fQosPortDSCPPort	                Integer32,
   gs2328fQosPortDSCPIngressTranslate       INTEGER,
   gs2328fQosPortDSCPIngressClassify	    INTEGER,
   gs2328fQosPortDSCPEgressRewrite	        INTEGER
}

gs2328fQosPortDSCPPort OBJECT-TYPE
   SYNTAX      Integer32 (1..4095)
   MAX-ACCESS  not-accessible
   STATUS      current
   DESCRIPTION
       " port, range : 1 - port number. "
   ::= { gs2328fQosPortDSCPEntry 1 }

gs2328fQosPortDSCPIngressTranslate OBJECT-TYPE
   SYNTAX      INTEGER { disable(0), enable(1) }
   MAX-ACCESS  read-write
   STATUS      current
   DESCRIPTION
      " Configure DSCP ingress translation mode.
        0: disable,
        1: enable,
        default: disable. "
   ::= { gs2328fQosPortDSCPEntry 2 }

gs2328fQosPortDSCPIngressClassify OBJECT-TYPE
   SYNTAX      INTEGER(0..3)
   MAX-ACCESS  read-write
   STATUS      current
   DESCRIPTION
       " Classification for a port have 4 different values.
         range: 0-3,
         0: disable,No Ingress DSCP Classification.
         1: DSCP=0,Classify if incoming (or translated if enabled) DSCP is 0.
         2: Selected,Classify only selected DSCP for which classification is
         enabled as specified in DSCP Translation window for the specific DSCP.
         3: All,Classify all DSCP.
         default: disable. "
   ::= { gs2328fQosPortDSCPEntry 3 }

gs2328fQosPortDSCPEgressRewrite OBJECT-TYPE
   SYNTAX      INTEGER(0..3)
   MAX-ACCESS  read-write
   STATUS      current
   DESCRIPTION
       " Configure the port egress rewriting mode.
         range: 0-2
         0: Disable,No Egress rewrite.
         1: Enable, Rewrite enabled without remapping.
         2: Remap DP Unaware , DSCP from analyzer is remapped and frame is
         remarked with remapped DSCP value. The remapped DSCP value is always
         taken from the DSCP Translation->Egress Remap DP0 table.
         3: Remap DP Aware: DSCP from analyzer is remapped and frame is remarked
          with remapped DSCP value. Depending on the DP level of the frame, the
          remapped DSCP value is either taken from the DSCP Translation->Egress
          Remap DP0 table or from the DSCP Translation->Egress Remap DP1 table.
         default: disable. "
   ::= { gs2328fQosPortDSCPEntry 4 }


gs2328fQosDSCPTable OBJECT-TYPE
   SYNTAX      SEQUENCE OF GS2328FQosDSCPEntry
   MAX-ACCESS  not-accessible
   STATUS      current
   DESCRIPTION
       " configure the basic QoS DSCP based QoS Ingress Classification settings for all switches. "
   ::= { gs2328fQos  6 }

gs2328fQosDSCPEntry OBJECT-TYPE
   SYNTAX      GS2328FQosDSCPEntry
   MAX-ACCESS  not-accessible
   STATUS      current
   DESCRIPTION
       ""
   INDEX    { gs2328fQosDSCPList  }
   ::= { gs2328fQosDSCPTable 1 }

GS2328FQosDSCPEntry ::= SEQUENCE {
   gs2328fQosDSCPList       Integer32,
   gs2328fQosDSCP           DisplayString,
   gs2328fQosDSCPTrust      INTEGER,
   gs2328fQosDSCPQosClass	  Integer32,
   gs2328fQosDSCPDPL	      INTEGER
}

gs2328fQosDSCPList OBJECT-TYPE
   SYNTAX      Integer32(1..64)
   MAX-ACCESS  not-accessible
   STATUS      current
   DESCRIPTION
      " DSCP mapping table index(1-64). "
   ::= { gs2328fQosDSCPEntry 1 }

gs2328fQosDSCP OBJECT-TYPE
   SYNTAX      DisplayString
   MAX-ACCESS  read-only
   STATUS      current
   DESCRIPTION
      "Maximum number of supported DSCP values are 64."
   ::= { gs2328fQosDSCPEntry 2 }

gs2328fQosDSCPTrust OBJECT-TYPE
   SYNTAX      INTEGER { disable(0), enable(1) }
   MAX-ACCESS  read-write
   STATUS      current
   DESCRIPTION
      " Controls whether a specific DSCP value is trusted. Only frames with
      trusted DSCP values are mapped to a specific QoS class and Drop Precedence
       Level. Frames with untrusted DSCP values are treated as a non-IP frame.
        0: disable,
        1: enable,
        default: disable. "
   ::= { gs2328fQosDSCPEntry 3 }

gs2328fQosDSCPQosClass OBJECT-TYPE
   SYNTAX      Integer32(0..7)
   MAX-ACCESS  read-write
   STATUS      current
   DESCRIPTION
      " QoS class.
        range: 0-7,
        default: 0. "
   ::= { gs2328fQosDSCPEntry 4 }

gs2328fQosDSCPDPL OBJECT-TYPE
   SYNTAX      INTEGER(0|1)
   MAX-ACCESS  read-write
   STATUS      current
   DESCRIPTION
      " Drop Precedence Level.
        range: 0-1,
        default: disable. "
   ::= { gs2328fQosDSCPEntry 5 }

gs2328fQosDSCPTranslationTable OBJECT-TYPE
   SYNTAX      SEQUENCE OF GS2328FQosDSCPTranslationEntry
   MAX-ACCESS  not-accessible
   STATUS      current
   DESCRIPTION
       "  configure the basic QoS DSCP Translation settings for all switches. "
   ::= { gs2328fQos  7 }

gs2328fQosDSCPTranslationEntry OBJECT-TYPE
   SYNTAX      GS2328FQosDSCPTranslationEntry
   MAX-ACCESS  not-accessible
   STATUS      current
   DESCRIPTION
       ""
   INDEX    { gs2328fQosDSCPTranslationList  }
   ::= { gs2328fQosDSCPTranslationTable 1 }

GS2328FQosDSCPTranslationEntry ::= SEQUENCE {
   gs2328fQosDSCPTranslationList                 Integer32,
   gs2328fQosDSCPTranslationDSCPBasedId          DisplayString,
   gs2328fQosDSCPTranslationIngressTranslate     Integer32,
   gs2328fQosDSCPTranslationIngressClassify      INTEGER,
   gs2328fQosDSCPTranslationEgressRemapDP0       Integer32,
   gs2328fQosDSCPTranslationEgressRemapDP1       Integer32
}

gs2328fQosDSCPTranslationList OBJECT-TYPE
   SYNTAX      Integer32(1..64)
   MAX-ACCESS  not-accessible
   STATUS      current
   DESCRIPTION
      " DSCP translation table index(1-64). "
   ::= { gs2328fQosDSCPTranslationEntry 1 }

gs2328fQosDSCPTranslationDSCPBasedId OBJECT-TYPE
   SYNTAX      DisplayString
   MAX-ACCESS  read-write
   STATUS      current
   DESCRIPTION
      " Configure global ingress DSCP translation table. "
   ::= { gs2328fQosDSCPTranslationEntry 2 }

gs2328fQosDSCPTranslationIngressTranslate OBJECT-TYPE
   SYNTAX      Integer32(0..63)
   MAX-ACCESS  read-write
   STATUS      current
   DESCRIPTION
      " DSCP at Ingress side can be translated to any of DSCP values.
        range: 0-63,
        default: 0. "
   ::= { gs2328fQosDSCPTranslationEntry 3 }

gs2328fQosDSCPTranslationIngressClassify OBJECT-TYPE
   SYNTAX      INTEGER { disable(0), enable(1) }
   MAX-ACCESS  read-write
   STATUS      current
   DESCRIPTION
      " Configure DSCP ingress classification.
        0: disable,
        1: enable,
        default: disable. "
   ::= { gs2328fQosDSCPTranslationEntry 4 }

gs2328fQosDSCPTranslationEgressRemapDP0 OBJECT-TYPE
   SYNTAX      Integer32(0..63)
   MAX-ACCESS  read-write
   STATUS      current
   DESCRIPTION
      "Controls the remapping for frames with DP level 0.
      Select the DSCP value from select menu to which you want to remap.
        range: 0-63,
        default: 0. "
   ::= { gs2328fQosDSCPTranslationEntry 5 }

gs2328fQosDSCPTranslationEgressRemapDP1 OBJECT-TYPE
   SYNTAX      Integer32(0..63)
   MAX-ACCESS  read-write
   STATUS      current
   DESCRIPTION
      "Controls the remapping for frames with DP level 1.
      Select the DSCP value from select menu to which you want to remap.
        range: 0-63,
        default: 0. "
   ::= { gs2328fQosDSCPTranslationEntry 6 }


gs2328fQosDSCPClassificationTable OBJECT-TYPE
   SYNTAX      SEQUENCE OF GS2328FQosDSCPClassificationEntry
   MAX-ACCESS  not-accessible
   STATUS      current
   DESCRIPTION
       "   configure the mapping of QoS class  to DSCP value. "
   ::= { gs2328fQos  8 }

gs2328fQosDSCPClassificationEntry OBJECT-TYPE
   SYNTAX      GS2328FQosDSCPClassificationEntry
   MAX-ACCESS  not-accessible
   STATUS      current
   DESCRIPTION
       ""
   INDEX    { gs2328fQosDSCPClassificationQoSClass, gs2328fQosDSCPClassificationDPL }
   ::= { gs2328fQosDSCPClassificationTable 1 }

GS2328FQosDSCPClassificationEntry ::= SEQUENCE {
   gs2328fQosDSCPClassificationQoSClass		INTEGER,
   gs2328fQosDSCPClassificationDPL			INTEGER,
   gs2328fQosDSCPClassificationDSCP			Integer32
}

gs2328fQosDSCPClassificationQoSClass OBJECT-TYPE
   SYNTAX      INTEGER {
                        class0(1),
                        class1(2),
                        class2(3),
                        class3(4),
                        class4(5),
                        class5(6),
                        class6(7),
                        class7(8)
                        }
   MAX-ACCESS  not-accessible
   STATUS      current
   DESCRIPTION
      " Actual QoS class. Index 1~8 mean Qos Class 0~7."
   ::= { gs2328fQosDSCPClassificationEntry 1 }

gs2328fQosDSCPClassificationDPL OBJECT-TYPE
   SYNTAX      INTEGER(1|2)
   MAX-ACCESS  not-accessible
   STATUS      current
   DESCRIPTION
      " DPL. Index 1~2 mean DPL 0~1."
   ::= { gs2328fQosDSCPClassificationEntry 2 }

gs2328fQosDSCPClassificationDSCP OBJECT-TYPE
   SYNTAX      Integer32(0..63)
   MAX-ACCESS  read-write
   STATUS      current
   DESCRIPTION
      " Select the classified DSCP value.
        range: 0-63,
        default: 0. "
   ::= { gs2328fQosDSCPClassificationEntry 3 }

gs2328fQosControlList                                         OBJECT IDENTIFIER ::= { gs2328fQos 9 }

gs2328fQosQceCreate OBJECT-TYPE
   SYNTAX       INTEGER { none(0), create(1) }
   MAX-ACCESS   read-write
   STATUS       current
   DESCRIPTION
       "default: 0
        0 : None  (read only)
        1 : Create an Qos entry"
   ::= { gs2328fQosControlList 1 }

gs2328fQosQceTable OBJECT-TYPE
   SYNTAX      SEQUENCE OF GS2328FQosQceEntry
   MAX-ACCESS  not-accessible
   STATUS      current
   DESCRIPTION
       " Create Qos QCE entry. "
   ::= { gs2328fQosControlList 2 }

gs2328fQosQceEntry OBJECT-TYPE
   SYNTAX      GS2328FQosQceEntry
   MAX-ACCESS  not-accessible
   STATUS      current
   DESCRIPTION
       ""
   INDEX    { gs2328fQosQceIndex  }
   ::= { gs2328fQosQceTable 1 }

GS2328FQosQceEntry ::= SEQUENCE {
   gs2328fQosQceIndex                Integer32,
   gs2328fQosQceID                   Integer32,
   gs2328fQosQceNextID               Integer32,
   gs2328fQosQcePortMembers          DisplayString,

   gs2328fQosQceTag                  DisplayString,
   gs2328fQosQceVID                  DisplayString,
   gs2328fQosPCP                     DisplayString,
   gs2328fQosDEI                     DisplayString,
   gs2328fQosSMAC                    DisplayString,
   gs2328fQosDMACType                DisplayString,
   gs2328fQosFrameType               INTEGER,

   gs2328fQosMacEtherType            DisplayString,

   gs2328fQosLLCSSAPAddr             DisplayString,
   gs2328fQosLLCDSAPAddr             DisplayString,
   gs2328fQosLLCControl              DisplayString,

   gs2328fQosSNAPPID                 DisplayString,

   gs2328fQosIpv4Protocol            DisplayString,
   gs2328fQosIpv4ProtocolValue       Integer32,
   gs2328fQosIpv4ProtocolUDPSport    DisplayString,
   gs2328fQosIpv4ProtocolUDPDport    DisplayString,
   gs2328fQosIpv4ProtocolTCPSport    DisplayString,
   gs2328fQosIpv4ProtocolTCPDport    DisplayString,
   gs2328fQosIpv4Ip                  DisplayString,
   gs2328fQosIpv4Mask                DisplayString,
   gs2328fQosIpv4IPFragment          INTEGER,
   gs2328fQosIpv4DSCP                DisplayString,


   gs2328fQosIpv6Protocol            DisplayString,
   gs2328fQosIpv6ProtocolValue       Integer32,
   gs2328fQosIpv6ProtocolUDPSport    DisplayString,
   gs2328fQosIpv6ProtocolUDPDport    DisplayString,
   gs2328fQosIpv6ProtocolTCPSport    DisplayString,
   gs2328fQosIpv6ProtocolTCPDport    DisplayString,
   gs2328fQosIpv6Ip                  DisplayString,
   gs2328fQosIpv6Mask                DisplayString,
   gs2328fQosIpv6DSCP                DisplayString,

   gs2328fQosActionClass             Integer32,
   gs2328fQosActionDPL               INTEGER,
   gs2328fQosActionDSCP              Integer32,
   gs2328fQosQceRowStatus            INTEGER
}

gs2328fQosQceIndex OBJECT-TYPE
   SYNTAX      Integer32(1..256)
   MAX-ACCESS  not-accessible
   STATUS      current
   DESCRIPTION
       " "
   ::= { gs2328fQosQceEntry 1 }

gs2328fQosQceID OBJECT-TYPE
   SYNTAX      Integer32(1..256)
   MAX-ACCESS  read-write
   STATUS      current
   DESCRIPTION
       " If the QCE ID is specified and an entry with this QCE ID
         already exists, the QCE will be modified. Otherwise, a
         new QCE will be added.
         range : 1 - 256. "
   ::= { gs2328fQosQceEntry 2 }

gs2328fQosQceNextID OBJECT-TYPE
   SYNTAX      Integer32(1..256)
   MAX-ACCESS  read-write
   STATUS      current
   DESCRIPTION
       " If the next QCE ID is non zero, the QCE will be placed
         before this QCE in the list. If the next QCE ID is zero,
         the QCE will be placed last in the list.
         range : 1 - 256. "
   ::= { gs2328fQosQceEntry 3 }

gs2328fQosQcePortMembers OBJECT-TYPE
   SYNTAX      DisplayString
   MAX-ACCESS  read-write
   STATUS      current
   DESCRIPTION
       " Indicates the ingress port of the QCE. Possible values are:
         All: The QCE will match all ingress port.
         Port: The QCE will match a specific ingress port.Format: 1,3-6."
   ::= { gs2328fQosQceEntry 4 }

gs2328fQosQceTag OBJECT-TYPE
   SYNTAX      DisplayString
   MAX-ACCESS  read-write
   STATUS      current
   DESCRIPTION
       " Value of Tag field can be 'Any', 'Untag' or 'Tag'. "
   ::= { gs2328fQosQceEntry 5 }

gs2328fQosQceVID OBJECT-TYPE
   SYNTAX      DisplayString
   MAX-ACCESS  read-write
   STATUS      current
   DESCRIPTION
       " Valid value of VLAN ID can be any value in 'Specific 1~4094' or 'range 1-4094' or 'Any'. "
   ::= { gs2328fQosQceEntry 6 }

gs2328fQosPCP OBJECT-TYPE
   SYNTAX      DisplayString
   MAX-ACCESS  read-write
   STATUS      current
   DESCRIPTION
       " Priority Code Point: Valid value PCP are specific(0, 1, 2, 3, 4, 5, 6, 7)
         or range(0-1, 2-3, 4-5, 6-7, 0-3, 4-7) or 'Any'. "
   ::= { gs2328fQosQceEntry 7 }

gs2328fQosDEI OBJECT-TYPE
   SYNTAX      DisplayString
   MAX-ACCESS  read-write
   STATUS      current
   DESCRIPTION
       " Drop Eligible Indicator: Valid value of DEI can be any of values between 0, 1 or 'Any'. "
   ::= { gs2328fQosQceEntry 8 }

gs2328fQosSMAC  OBJECT-TYPE
   SYNTAX      DisplayString
   MAX-ACCESS  read-write
   STATUS      current
   DESCRIPTION
       "  Source MAC address: 24 MS bits OUI(00-00-00 ~ FF-FF-FF) or 'Any'. "
   ::= { gs2328fQosQceEntry 9 }

gs2328fQosDMACType OBJECT-TYPE
   SYNTAX      DisplayString
   MAX-ACCESS  read-write
   STATUS      current
   DESCRIPTION
       " Destination MAC type: possible values are 'UC'(unicast), 'MC'(multicast), 'BC'(broadcast) or 'Any'. "
   ::= { gs2328fQosQceEntry 10 }

gs2328fQosFrameType OBJECT-TYPE
   SYNTAX      INTEGER {
                        any(1),
                        ethernet(2),
                        llc(3),
                        snap(4),
                        ipv4(5),
                        ipv6(6)
                        }
   MAX-ACCESS  read-write
   STATUS      current
   DESCRIPTION
       " Frame Type can have any of the following values:
         1: Any,
         2: Ethernet,
         3: LLC,
         4: SNAP,
         5: IPv4,
         6: IPv6. "
   ::= { gs2328fQosQceEntry 11 }

gs2328fQosMacEtherType OBJECT-TYPE
   SYNTAX      DisplayString
   MAX-ACCESS  read-write
   STATUS      current
   DESCRIPTION
       " Valid ethernet type can have a value within 0x600-0xFFFF or 'Any' ,
         but excluding 0x800(IPv4) and 0x86DD(IPv6),
         range: 0000-FFFF,
         default: Any."
   ::= { gs2328fQosQceEntry 12 }

gs2328fQosLLCSSAPAddr OBJECT-TYPE
   SYNTAX      DisplayString
   MAX-ACCESS  read-write
   STATUS      current
   DESCRIPTION
       " Valid SSAP(Source Service Access Point) can vary from 0x00 to 0xFF or 'Any',
         range: 00-FF,
         default: Any. "
   ::= { gs2328fQosQceEntry 13 }

gs2328fQosLLCDSAPAddr OBJECT-TYPE
   SYNTAX      DisplayString
   MAX-ACCESS  read-write
   STATUS      current
   DESCRIPTION
       " Valid DSAP(Destination Service Access Point) can vary from 0x00 to 0xFF or 'Any',
         range: 00-FF,
         default: Any. "
   ::= { gs2328fQosQceEntry 14 }

gs2328fQosLLCControl OBJECT-TYPE
   SYNTAX      DisplayString
   MAX-ACCESS  read-write
   STATUS      current
   DESCRIPTION
       " Valid Control field can vary from 0x00 to 0xFF or 'Any',
         range: 00-FF,
         default: Any. "
   ::= { gs2328fQosQceEntry 15 }

gs2328fQosSNAPPID OBJECT-TYPE
   SYNTAX      DisplayString
   MAX-ACCESS  read-write
   STATUS      current
   DESCRIPTION
       " Valid PID(a.k.a ethernet type) can have value within 0x00-0xFFFF or 'Any',
         range: 0000-FFFF,
         default: Any. "
   ::= { gs2328fQosQceEntry 16 }

gs2328fQosIpv4Protocol OBJECT-TYPE
   SYNTAX      DisplayString
   MAX-ACCESS  read-write
   STATUS      current
   DESCRIPTION
       " IP protocol number: (Other, TCP or UDP) or 'Any'. "
   ::= { gs2328fQosQceEntry 17 }

gs2328fQosIpv4ProtocolValue  OBJECT-TYPE
   SYNTAX      Integer32(0..255)
   MAX-ACCESS  read-write
   STATUS      current
   DESCRIPTION
       " Ipv4 Protocol is Other.
         range: 0-255
         default: 0. "
   ::= { gs2328fQosQceEntry 18 }

gs2328fQosIpv4ProtocolUDPSport OBJECT-TYPE
   SYNTAX      DisplayString
   MAX-ACCESS  read-write
   STATUS      current
   DESCRIPTION
       " Source  TCP/UDP port:(0-65535) or 'Any',
         specific or port range applicable for IP protocol UDP/TCP. "
   ::= { gs2328fQosQceEntry 19 }

gs2328fQosIpv4ProtocolUDPDport OBJECT-TYPE
   SYNTAX      DisplayString
   MAX-ACCESS  read-write
   STATUS      current
   DESCRIPTION
       " Destination TCP/UDP port:(0-65535) or 'Any',
         specific or port range applicable for IP protocol UDP/TCP. "
   ::= { gs2328fQosQceEntry 20 }

gs2328fQosIpv4ProtocolTCPSport OBJECT-TYPE
   SYNTAX      DisplayString
   MAX-ACCESS  read-write
   STATUS      current
   DESCRIPTION
       " Source TCP/UDP port:(0-65535) or 'Any',
         specific or port range applicable for IP protocol UDP/TCP. "
   ::= { gs2328fQosQceEntry 21 }

gs2328fQosIpv4ProtocolTCPDport OBJECT-TYPE
   SYNTAX      DisplayString
   MAX-ACCESS  read-write
   STATUS      current
   DESCRIPTION
       " Destination TCP/UDP port:(0-65535) or 'Any',
         specific or port range applicable for IP protocol UDP/TCP. "
   ::= { gs2328fQosQceEntry 22 }

gs2328fQosIpv4Ip OBJECT-TYPE
   SYNTAX      DisplayString
   MAX-ACCESS  read-write
   STATUS      current
   DESCRIPTION
       "  Specific Source IP address in value format or value 0.0.0.0 is 'Any'.
          if Ipv4 Mask value 0.0.0.0 is 'Any' ,IP address value also is 'Any'.
          (x.y.z.w),x=0 unless y.z.w also 0,x not is 127 or greater than 223.
          If a port is configured to match on DMAC/DIP, this field is the
          Destination IP address."
   ::= { gs2328fQosQceEntry 23 }

gs2328fQosIpv4Mask OBJECT-TYPE
   SYNTAX      DisplayString
   MAX-ACCESS  read-write
   STATUS      current
   DESCRIPTION
       " Specific IP address in mask format or value 0.0.0.0 is 'Any'. "
   ::= { gs2328fQosQceEntry 24 }

gs2328fQosIpv4IPFragment OBJECT-TYPE
   SYNTAX      INTEGER { any(0), no(1), yes(2) }
   MAX-ACCESS  read-write
   STATUS      current
   DESCRIPTION
       " IPv4 frame fragmented option:
         2: yes,
         1: no,
         0: any. "
   ::= { gs2328fQosQceEntry 25 }

gs2328fQosIpv4DSCP OBJECT-TYPE
   SYNTAX      DisplayString
   MAX-ACCESS  read-write
   STATUS      current
   DESCRIPTION
       " Diffserv Code Point value (DSCP): It can be a specific value,
         range of values or 'Any'. DSCP values are in the range 0-63. "
   ::= { gs2328fQosQceEntry 26 }

gs2328fQosIpv6Protocol OBJECT-TYPE
   SYNTAX      DisplayString
   MAX-ACCESS  read-write
   STATUS      current
   DESCRIPTION
       " IP protocol number: (Other, TCP or UDP) or 'Any'. "
   ::= { gs2328fQosQceEntry 27 }

gs2328fQosIpv6ProtocolValue OBJECT-TYPE
   SYNTAX      Integer32(0..255)
   MAX-ACCESS  read-write
   STATUS      current
   DESCRIPTION
       " when IPv6 protocol is Other ,
         range: 0-255. "
   ::= { gs2328fQosQceEntry 28 }

gs2328fQosIpv6ProtocolUDPSport OBJECT-TYPE
   SYNTAX      DisplayString
   MAX-ACCESS  read-write
   STATUS      current
   DESCRIPTION
       " Source TCP/UDP port:(0-65535) or 'Any',
         specific or port range applicable for IP protocol UDP/TCP. "
   ::= { gs2328fQosQceEntry 29 }

gs2328fQosIpv6ProtocolUDPDport OBJECT-TYPE
   SYNTAX      DisplayString
   MAX-ACCESS  read-write
   STATUS      current
   DESCRIPTION
       " Destination TCP/UDP port:(0-65535) or 'Any',
         specific or port range applicable for IP protocol UDP/TCP. "
   ::= { gs2328fQosQceEntry 30 }

gs2328fQosIpv6ProtocolTCPSport OBJECT-TYPE
   SYNTAX      DisplayString
   MAX-ACCESS  read-write
   STATUS      current
   DESCRIPTION
       " Source TCP/UDP port:(0-65535) or 'Any',
         specific or port range applicable for IP protocol UDP/TCP. "
   ::= { gs2328fQosQceEntry 31 }


gs2328fQosIpv6ProtocolTCPDport OBJECT-TYPE
   SYNTAX      DisplayString
   MAX-ACCESS  read-write
   STATUS      current
   DESCRIPTION
       " Destination TCP/UDP port:(0-65535) or 'Any',
         specific or port range applicable for IP protocol UDP/TCP. "
   ::= { gs2328fQosQceEntry 32 }

gs2328fQosIpv6Ip OBJECT-TYPE
   SYNTAX      DisplayString
   MAX-ACCESS  read-write
   STATUS      current
   DESCRIPTION
       " IPv6 source address: (a.b.c.d) or value 0.0.0.0 is 'Any', 32 LS bits.
         If a port is configured to match on DMAC/DIP, this field is the
         Destination IP address."
   ::= { gs2328fQosQceEntry 33 }

gs2328fQosIpv6Mask OBJECT-TYPE
   SYNTAX      DisplayString
   MAX-ACCESS  read-write
   STATUS      current
   DESCRIPTION
       " IPv6 mask address: (a.b.c.d) or value 0.0.0.0 is 'Any', 32 LS bits. "
   ::= { gs2328fQosQceEntry 34 }

gs2328fQosIpv6DSCP OBJECT-TYPE
   SYNTAX      DisplayString
   MAX-ACCESS  read-write
   STATUS      current
   DESCRIPTION
       " Diffserv Code Point value (DSCP): It can be a specific value,
         range of values or 'Any'. DSCP values are in the range 0-63 including BE,
         CS1-CS7, EF or AF11-AF43. "
   ::= { gs2328fQosQceEntry 35 }

gs2328fQosActionClass  OBJECT-TYPE
   SYNTAX      Integer32(0..8)
   MAX-ACCESS  read-write
   STATUS      current
   DESCRIPTION
       " QoS class: (0-7) or 8: Default."
   ::= { gs2328fQosQceEntry 36 }

gs2328fQosActionDPL OBJECT-TYPE
   SYNTAX      INTEGER (0..4)
   MAX-ACCESS  read-write
   STATUS      current
   DESCRIPTION
       " DP Valid Drop Precedence Level can be (0-3) or 4: Default. "
   ::= { gs2328fQosQceEntry 37 }

gs2328fQosActionDSCP OBJECT-TYPE
   SYNTAX      Integer32(0..64)
   MAX-ACCESS  read-write
   STATUS      current
   DESCRIPTION
       " Valid DSCP value can be (0-63, BE, CS1-CS7, EF or AF11-AF43) or 64: Default. "
   ::= { gs2328fQosQceEntry 38 }

gs2328fQosQceRowStatus OBJECT-TYPE
   SYNTAX      INTEGER { active(1), notInservice(2), destroy(4) }
   MAX-ACCESS  read-write
   STATUS      current
   DESCRIPTION
       "  1: active2: notInservice 4: destroy"
   ::= { gs2328fQosQceEntry 39 }

gs2328fQosQceMoveID OBJECT-TYPE
   SYNTAX       Integer32(0..256)
   MAX-ACCESS   read-write
   STATUS       current
   DESCRIPTION
       " Move Qos,
         default: 0
         Qos ID must be exist.
         range : 0 - 256."
   ::= { gs2328fQosControlList 3 }

gs2328fQosQceMoveNextID OBJECT-TYPE
   SYNTAX       Integer32(0..256)
   MAX-ACCESS   read-write
   STATUS       current
   DESCRIPTION
       " Move Qos,
         default: 0
         If the next Qos ID is non zero, the Qos will be placed before this Qos in the list.
         If the next Qos ID is zero,the Qos will be placed last in the list.
         range : 0 - 256. "
   ::= { gs2328fQosControlList 4 }


gs2328fQosQCLStatusTable OBJECT-TYPE
   SYNTAX      SEQUENCE OF GS2328FQosQCLStatusEntry
   MAX-ACCESS  not-accessible
   STATUS      current
   DESCRIPTION
       "  configure the basic QoS DSCP Translation settings for all switches. "
   ::= { gs2328fQos  10 }

gs2328fQosQCLStatusEntry OBJECT-TYPE
   SYNTAX      GS2328FQosQCLStatusEntry
   MAX-ACCESS  not-accessible
   STATUS      current
   DESCRIPTION
       ""
   INDEX    { gs2328fQosQCLStatusList  }
   ::= { gs2328fQosQCLStatusTable 1 }

GS2328FQosQCLStatusEntry ::= SEQUENCE {
   gs2328fQosQCLStatusList               Integer32,
   gs2328fQosQCLStatusUser               DisplayString,
   gs2328fQosQCLStatusQCEId              DisplayString,
   gs2328fQosQCLStatusFrameType          DisplayString,
   gs2328fQosQCLStatusPortlist           DisplayString,
   gs2328fQosQCLStatusActionClass	       DisplayString,
   gs2328fQosQCLStatusActionDPL	       DisplayString,
   gs2328fQosQCLStatusActionDSCP	       DisplayString,
   gs2328fQosQCLStatusActionConflict     DisplayString
}

gs2328fQosQCLStatusList OBJECT-TYPE
   SYNTAX      Integer32(1..4095)
   MAX-ACCESS  not-accessible
   STATUS      current
   DESCRIPTION
       " QCL table index. "
   ::= { gs2328fQosQCLStatusEntry 1}

gs2328fQosQCLStatusUser OBJECT-TYPE
   SYNTAX      DisplayString
   MAX-ACCESS  read-only
   STATUS      current
   DESCRIPTION
       " Indicates the QCL user. "
   ::= { gs2328fQosQCLStatusEntry 2 }

gs2328fQosQCLStatusQCEId OBJECT-TYPE
   SYNTAX      DisplayString
   MAX-ACCESS  read-only
   STATUS      current
   DESCRIPTION
      " Indicates the index of QCE. "
   ::= { gs2328fQosQCLStatusEntry 3}

gs2328fQosQCLStatusFrameType OBJECT-TYPE
   SYNTAX      DisplayString
   MAX-ACCESS  read-only
   STATUS      current
   DESCRIPTION
       " Indicates the type of frame to look for incomming frames.
       Any: The QCE will match all frame type.
       Ethernet: Only Ethernet frames (with Ether Type 0x600-0xFFFF) are allowed.
       LLC: Only (LLC) frames are allowed.
       SNAP: Only (SNAP) frames are allowed.
       IPv4: The QCE will match only IPV4 frames.
       IPv6: The QCE will match only IPV6 frames."
   ::= { gs2328fQosQCLStatusEntry 4}

gs2328fQosQCLStatusPortlist OBJECT-TYPE
   SYNTAX      DisplayString
   MAX-ACCESS  read-only
   STATUS      current
   DESCRIPTION
       " Indicates the list of ports configured with the QCE. "
   ::= { gs2328fQosQCLStatusEntry 5}

gs2328fQosQCLStatusActionClass OBJECT-TYPE
   SYNTAX      DisplayString
   MAX-ACCESS  read-only
   STATUS      current
   DESCRIPTION
       " Classified QoS class; if a frame matches the QCE it will be put in the
       queue. "
   ::= { gs2328fQosQCLStatusEntry 6}

gs2328fQosQCLStatusActionDPL OBJECT-TYPE
   SYNTAX      DisplayString
   MAX-ACCESS  read-only
   STATUS      current
   DESCRIPTION
       " Drop Precedence Level; if a frame matches the QCE then DP level will
       set to value displayed under DPL column."
   ::= { gs2328fQosQCLStatusEntry 7}

gs2328fQosQCLStatusActionDSCP OBJECT-TYPE
   SYNTAX      DisplayString
   MAX-ACCESS  read-only
   STATUS      current
   DESCRIPTION
       " If a frame matches the QCE then DSCP will be classified with the value
       displayed under DSCP column."
   ::= { gs2328fQosQCLStatusEntry 8}

gs2328fQosQCLStatusActionConflict OBJECT-TYPE
   SYNTAX      DisplayString
   MAX-ACCESS  read-only
   STATUS      current
   DESCRIPTION
       " If a frame matches the QCE then DSCP will be classified with the value
        displayed under DSCP column. "
   ::= { gs2328fQosQCLStatusEntry 9}


gs2328fQosStormControl                                           OBJECT IDENTIFIER ::= { gs2328fQos 11 }

gs2328fQoSStormControlUC OBJECT-TYPE
   SYNTAX      INTEGER { disable(0), enable(1) }
   MAX-ACCESS  read-write
   STATUS      current
   DESCRIPTION
       "Enable or disable the storm control status for the Unicast frame type.
       default:  0
        0: disable
        1: enable"
   ::= { gs2328fQosStormControl 2 }

gs2328fQoSStormControlUCRate OBJECT-TYPE
   SYNTAX      DisplayString
   MAX-ACCESS  read-write
   STATUS      current
   DESCRIPTION
       "The rate unit is packets per second (pps). Valid values are: 1, 2, 4, 8,
        16, 32, 64, 128, 256, 512, 1K, 2K, 4K, 8K, 16K, 32K, 64K, 128K, 256K,
        512K or 1024K."
   ::= { gs2328fQosStormControl 3 }

gs2328fQoSStormControlMC OBJECT-TYPE
   SYNTAX      INTEGER { disable(0), enable(1) }
   MAX-ACCESS  read-write
   STATUS      current
   DESCRIPTION
       "Enable or disable the storm control status for the Multicast frame type.
       default:  0
        0: disable
        1: enable"
   ::= { gs2328fQosStormControl 4 }

gs2328fQoSStormControlMCRate OBJECT-TYPE
   SYNTAX      DisplayString
   MAX-ACCESS  read-write
   STATUS      current
   DESCRIPTION
       "The rate unit is packets per second (pps). Valid values are: 1, 2, 4, 8,
        16, 32, 64, 128, 256, 512, 1K, 2K, 4K, 8K, 16K, 32K, 64K, 128K, 256K,
        512K or 1024K."
   ::= { gs2328fQosStormControl 5 }

gs2328fQoSStormControlBC OBJECT-TYPE
   SYNTAX      INTEGER { disable(0), enable(1) }
   MAX-ACCESS  read-write
   STATUS      current
   DESCRIPTION
       "Enable or disable the storm control status for the Broadcast frame type.
       default:  0
        0: disable
        1: enable"
   ::= { gs2328fQosStormControl 6 }

gs2328fQoSStormControlBCRate OBJECT-TYPE
   SYNTAX      DisplayString
   MAX-ACCESS  read-write
   STATUS      current
   DESCRIPTION
       "The rate unit is packets per second (pps). Valid values are: 1, 2, 4, 8,
        16, 32, 64, 128, 256, 512, 1K, 2K, 4K, 8K, 16K, 32K, 64K, 128K, 256K,
        512K or 1024K."
   ::= { gs2328fQosStormControl 7 }


gs2328fVlan                                                           OBJECT IDENTIFIER ::= { gs2328fConfiguration 15 }

gs2328fVlanPorts                                                      OBJECT IDENTIFIER ::= { gs2328fVlan 1 }

gs2328fVlanPortsTPIDforCustomSport  OBJECT-TYPE
   SYNTAX      OCTET STRING(SIZE(2))
   MAX-ACCESS  read-write
   STATUS      current
   DESCRIPTION
       "Configure the TPID used for Custom S-ports. This is a global setting for
       all the Custom S-ports.
       range: 0x0600-0xffff,
       default: 0x88a8. "
   ::= { gs2328fVlanPorts 1 }

gs2328fVlanPortsTable OBJECT-TYPE
   SYNTAX      SEQUENCE OF GS2328FVlanPortsEntry
   MAX-ACCESS  not-accessible
   STATUS      current
   DESCRIPTION
       " Configure Vlan ports Configuration mode. "
   ::= { gs2328fVlanPorts 2 }

gs2328fVlanPortsEntry OBJECT-TYPE
   SYNTAX      GS2328FVlanPortsEntry
   MAX-ACCESS  not-accessible
   STATUS      current
   DESCRIPTION
       ""
   INDEX    { gs2328fVlanPortsPort  }
   ::= { gs2328fVlanPortsTable 1 }

GS2328FVlanPortsEntry ::= SEQUENCE {
   gs2328fVlanPortsPort	         Integer32,
   gs2328fVlanPortsPVID     Integer32,
   gs2328fVlanPortsFrameType      INTEGER,
   gs2328fVlanPortsIngressFilter  INTEGER,
   gs2328fVlanPortsEgressRule     INTEGER,
   gs2328fVlanPortsPortType       INTEGER
}

gs2328fVlanPortsPort OBJECT-TYPE
   SYNTAX      Integer32(1..4094)
   MAX-ACCESS  not-accessible
   STATUS      current
   DESCRIPTION
       " port, range : 1 - port number. "
   ::= { gs2328fVlanPortsEntry 1 }

gs2328fVlanPortsPVID OBJECT-TYPE
   SYNTAX      Integer32(1..4094)
   MAX-ACCESS  read-write
   STATUS      current
   DESCRIPTION
       "Configure PVID.
        range: 1-4094,
        default: 1. "
   ::= { gs2328fVlanPortsEntry 2 }

gs2328fVlanPortsFrameType OBJECT-TYPE
   SYNTAX      INTEGER { all(0), tagged(1), untagged(2) }
   MAX-ACCESS  read-write
   STATUS      current
   DESCRIPTION
       "Configure frame type of switch ports.
        0: all,
        1: tagged,
        2: untagged,
        default: all.  "
   ::= { gs2328fVlanPortsEntry 3 }

gs2328fVlanPortsIngressFilter OBJECT-TYPE
   SYNTAX      INTEGER { disable(0), enable(1) }
   MAX-ACCESS  read-write
   STATUS      current
   DESCRIPTION
       "Configure ingress filtering of switch ports.
        0: disable,
        1: enable,
        default:disable . "
   ::= { gs2328fVlanPortsEntry 4 }

gs2328fVlanPortsEgressRule OBJECT-TYPE
   SYNTAX      INTEGER { access(0), hybrid(1), trunk(2) }
   MAX-ACCESS  read-write
   STATUS      current
   DESCRIPTION
       "Configure egress-rule of switch ports.
        0: access,
        1: hybrid,
        2: trunk"
   ::= { gs2328fVlanPortsEntry 5 }

gs2328fVlanPortsPortType OBJECT-TYPE
   SYNTAX      INTEGER { cPort(0), sCustomPort(1), sPort(2), unaware(3) }
   MAX-ACCESS  read-write
   STATUS      current
   DESCRIPTION
       "Configure port type of switch ports.
        0: c-port,
        1: s-custom-port,
        2: s-port,
        3: unaware.
        default: c-port. "
   ::= { gs2328fVlanPortsEntry 6 }

gs2328fVlanPrivateVLAN                                                              OBJECT IDENTIFIER ::= { gs2328fVlan 2 }

gs2328fVlanPrivateVLANMembership                                                    OBJECT IDENTIFIER ::= { gs2328fVlanPrivateVLAN 1 }

gs2328fVlanPrivateVLANMembershipCreate OBJECT-TYPE
   SYNTAX       Integer32(1..4094)
   MAX-ACCESS   read-write
   STATUS       current
   DESCRIPTION
       "default: 0
        0 : None  (read only)
        1 : Create a pvlan"
   ::= { gs2328fVlanPrivateVLANMembership 1 }

gs2328fVlanPrivateVLANMembershipTable OBJECT-TYPE
   SYNTAX      SEQUENCE OF Gs2328fVlanPrivateVLANMembershipEntry
   MAX-ACCESS  not-accessible
   STATUS      current
   DESCRIPTION
       " Configure Private Vlan Configuration. "
   ::= { gs2328fVlanPrivateVLANMembership 2 }

gs2328fVlanPrivateVLANMembershipEntry OBJECT-TYPE
   SYNTAX      Gs2328fVlanPrivateVLANMembershipEntry
   MAX-ACCESS  not-accessible
   STATUS      current
   DESCRIPTION
       ""
   INDEX    { gs2328fVlanPrivateVLANIndex  }
   ::= { gs2328fVlanPrivateVLANMembershipTable 1 }

Gs2328fVlanPrivateVLANMembershipEntry ::= SEQUENCE {
   gs2328fVlanPrivateVLANIndex          Integer32,
   gs2328fVlanPrivateVLANID             Integer32,
   gs2328fVlanPrivateVLANMemberships    DisplayString,
   gs2328fVlanPrivateVLANRowStatus      INTEGER
}

gs2328fVlanPrivateVLANIndex OBJECT-TYPE
   SYNTAX      Integer32(1..52)
   MAX-ACCESS  not-accessible
   STATUS      current
   DESCRIPTION
       "private VLAN Index. "
   ::= { gs2328fVlanPrivateVLANMembershipEntry 1 }

gs2328fVlanPrivateVLANID OBJECT-TYPE
   SYNTAX      Integer32(1..52)
   MAX-ACCESS  read-write
   STATUS      current
   DESCRIPTION
       "Indicates the ID of this particular private VLAN.
       The CreateEntry can be modify, the other entry can't be modify."
   ::= { gs2328fVlanPrivateVLANMembershipEntry 2 }

gs2328fVlanPrivateVLANMemberships OBJECT-TYPE
   SYNTAX      DisplayString
   MAX-ACCESS  read-write
   STATUS      current
   DESCRIPTION
       "To include the ports in a Private VLAN"
   ::= { gs2328fVlanPrivateVLANMembershipEntry 3 }

gs2328fVlanPrivateVLANRowStatus OBJECT-TYPE
   SYNTAX      INTEGER { active(1), notInservice(2), destroy(4) }
   MAX-ACCESS  read-write
   STATUS      current
   DESCRIPTION
       "1: active
        2: notInservice
        4: destroy"
   ::= { gs2328fVlanPrivateVLANMembershipEntry 4 }

gs2328fVlanPortIsolationTable OBJECT-TYPE
   SYNTAX      SEQUENCE OF Gs2328fVlanPortIsolationEntry
   MAX-ACCESS  not-accessible
   STATUS      current
   DESCRIPTION
       " Configure Vlan Port Isolation Configuration. "
   ::= { gs2328fVlanPrivateVLAN 2 }

gs2328fVlanPortIsolationEntry OBJECT-TYPE
   SYNTAX      Gs2328fVlanPortIsolationEntry
   MAX-ACCESS  not-accessible
   STATUS      current
   DESCRIPTION
       ""
   INDEX    { gs2328fVlanPortIsolationPort  }
   ::= { gs2328fVlanPortIsolationTable 1 }

Gs2328fVlanPortIsolationEntry ::= SEQUENCE {
   gs2328fVlanPortIsolationPort Integer32,
   gs2328fVlanPortIsolation     INTEGER
}

gs2328fVlanPortIsolationPort OBJECT-TYPE
   SYNTAX      Integer32(1..4094)
   MAX-ACCESS  not-accessible
   STATUS      current
   DESCRIPTION
       " port, range : 1 - port number. "
   ::= { gs2328fVlanPortIsolationEntry 1 }

gs2328fVlanPortIsolation OBJECT-TYPE
   SYNTAX      INTEGER{ disable(0), enable(1) }
   MAX-ACCESS  read-write
   STATUS      current
   DESCRIPTION
       "default: 0
        0:disable
        1:enable"
   ::= { gs2328fVlanPortIsolationEntry 2 }


gs2328fMACbasedVLAN                                                      OBJECT IDENTIFIER ::= { gs2328fVlan 3 }

gs2328fMACbasedVLANConf                                                      OBJECT IDENTIFIER ::= { gs2328fMACbasedVLAN 1 }

gs2328fMACbasedVLANConfCreate OBJECT-TYPE
   SYNTAX       Integer32
   MAX-ACCESS   read-write
   STATUS       current
   DESCRIPTION
       "default: 0
       0 : None  (read only) 1 : Create MAC base vlan"
   ::= { gs2328fMACbasedVLANConf 1 }

gs2328fMACbasedVLANConfTable OBJECT-TYPE
   SYNTAX      SEQUENCE OF Gs2328fMACbasedVLANConfEntry
   MAX-ACCESS  not-accessible
   STATUS      current
   DESCRIPTION
       " Configure Vlan Port Isolation Configuration. "
   ::= { gs2328fMACbasedVLANConf 2 }

gs2328fMACbasedVLANConfEntry OBJECT-TYPE
   SYNTAX      Gs2328fMACbasedVLANConfEntry
   MAX-ACCESS  not-accessible
   STATUS      current
   DESCRIPTION
       ""
   INDEX    { gs2328fMACbasedVLANIndex  }
   ::= { gs2328fMACbasedVLANConfTable 1 }

Gs2328fMACbasedVLANConfEntry ::= SEQUENCE {
   gs2328fMACbasedVLANIndex         Integer32,
   gs2328fMACbasedVLANMACAddress    MacAddress,
   gs2328fMACbasedVLANID            Integer32,
   gs2328fMACbasedMemberships       DisplayString,
   gs2328fMACbaseRowStatus          INTEGER
}

gs2328fMACbasedVLANIndex OBJECT-TYPE
   SYNTAX      Integer32(1..256)
   MAX-ACCESS  read-write
   STATUS      current
   DESCRIPTION
       "Indicates the VLAN ID. "
   ::= { gs2328fMACbasedVLANConfEntry 1 }

gs2328fMACbasedVLANMACAddress OBJECT-TYPE
   SYNTAX      MacAddress
   MAX-ACCESS  read-write
   STATUS      current
   DESCRIPTION
       "Indicates the MAC address.
       The CreateEntry can be modify, the other entry can't be modify."
   ::= { gs2328fMACbasedVLANConfEntry 2 }

gs2328fMACbasedVLANID OBJECT-TYPE
   SYNTAX      Integer32(1..4094)
   MAX-ACCESS  read-write
   STATUS      current
   DESCRIPTION
       "Indicates the VLAN ID. "
   ::= { gs2328fMACbasedVLANConfEntry 3 }

gs2328fMACbasedMemberships OBJECT-TYPE
   SYNTAX      DisplayString
   MAX-ACCESS  read-write
   STATUS      current
   DESCRIPTION
       "The ports are displayed for each MAC-based VLAN entry.
        To include the port in a MAC-based VLAN"
   ::= { gs2328fMACbasedVLANConfEntry 4 }


gs2328fMACbaseRowStatus OBJECT-TYPE
   SYNTAX      INTEGER { active(1), notInservice(2), destroy(4)}
   MAX-ACCESS  read-write
   STATUS      current
   DESCRIPTION
       "1: active
        2: notInservice
        4: destroy"
   ::= { gs2328fMACbasedVLANConfEntry 5 }

gs2328fIGMPSnooping                                                           OBJECT IDENTIFIER ::= { gs2328fConfiguration 16 }

gs2328fIGMPSnoopingBasic                                                      OBJECT IDENTIFIER ::= { gs2328fIGMPSnooping 1 }

gs2328fIGMPSnoopingEnable  OBJECT-TYPE
   SYNTAX      INTEGER { disable(0), enable(1) }
   MAX-ACCESS  read-write
   STATUS      current
   DESCRIPTION
       "Enable/Disable the Global IGMP Snooping"
   ::= { gs2328fIGMPSnoopingBasic 1 }

gs2328fIGMPSnoopingUnregisteredIPMCv4Flooding  OBJECT-TYPE
   SYNTAX      INTEGER { disable(0), enable(1) }
   MAX-ACCESS  read-write
   STATUS      current
   DESCRIPTION
       "Enable/Disable unregistered IPMCv4 traffic flooding. "
   ::= { gs2328fIGMPSnoopingBasic 2 }

gs2328fIGMPSnoopingSSMIPRangeAddr  OBJECT-TYPE
   SYNTAX      DisplayString
   MAX-ACCESS  read-write
   STATUS      current
   DESCRIPTION
       "SSM (Source-Specific Multicast) Range allows the SSM-aware hosts and
       routers run the SSM service model for the groups in the address range. "
   ::= { gs2328fIGMPSnoopingBasic 3 }

gs2328fIGMPSnoopingSSMIPRangeValue  OBJECT-TYPE
   SYNTAX      Integer32(4..32)
   MAX-ACCESS  read-write
   STATUS      current
   DESCRIPTION
       "SSM (Source-Specific Multicast) Range allows the SSM-aware hosts and
       routers run the SSM service model for the groups in the address range value. "
   ::= { gs2328fIGMPSnoopingBasic 4 }

gs2328fIGMPSnoopingProxyEnabled  OBJECT-TYPE
   SYNTAX      INTEGER { disable(0), enable(1) }
   MAX-ACCESS  read-write
   STATUS      current
   DESCRIPTION
       "Enable/Disable IGMP Proxy. This feature can be used to avoid forwarding
       unnecessary join and leave messages to the router side. "
   ::= { gs2328fIGMPSnoopingBasic 5 }

gs2328fIGMPSnoopingPortRelatedTable OBJECT-TYPE
   SYNTAX      SEQUENCE OF Gs2328fIGMPSnoopingPortRelatedEntry
   MAX-ACCESS  not-accessible
   STATUS      current
   DESCRIPTION
       " Configure IGMP Snooping Port Related Configuration. "
   ::= { gs2328fIGMPSnoopingBasic 6 }

gs2328fIGMPSnoopingPortRelatedEntry OBJECT-TYPE
   SYNTAX      Gs2328fIGMPSnoopingPortRelatedEntry
   MAX-ACCESS  not-accessible
   STATUS      current
   DESCRIPTION
       ""
   INDEX    { ifIndex  }
   ::= { gs2328fIGMPSnoopingPortRelatedTable 1 }

Gs2328fIGMPSnoopingPortRelatedEntry ::= SEQUENCE {
   gs2328fIGMPSnoopingRouterPort	INTEGER,
   gs2328fIGMPSnoopingFastLeave  	INTEGER,
   gs2328fIGMPSnoopingThrottling    Integer32
}

gs2328fIGMPSnoopingRouterPort OBJECT-TYPE
   SYNTAX      INTEGER { disable(0), enable(1) }
   MAX-ACCESS  read-write
   STATUS      current
   DESCRIPTION
       "Specify which ports act as router ports. A router port is a port on the
       Ethernet switch that leads towards the Layer 3 multicast device or IGMP
       querier. If an aggregation member port is selected as a router port, the
       whole aggregation will act as a router port. "
   ::= { gs2328fIGMPSnoopingPortRelatedEntry 1 }

gs2328fIGMPSnoopingFastLeave OBJECT-TYPE
   SYNTAX      INTEGER { disable(0), enable(1) }
   MAX-ACCESS  read-write
   STATUS      current
   DESCRIPTION
       "Enable/Disable the fast leave on the port. "
   ::= { gs2328fIGMPSnoopingPortRelatedEntry 2 }

gs2328fIGMPSnoopingThrottling OBJECT-TYPE
   SYNTAX      Integer32(0..10)
   MAX-ACCESS  read-write
   STATUS      current
   DESCRIPTION
       "Enable to limit the number of multicast groups to which a switch port can belong.
       0: unlimited"
   ::= { gs2328fIGMPSnoopingPortRelatedEntry 3 }

gs2328fIGMPSnoopingVLANTable OBJECT-TYPE
   SYNTAX      SEQUENCE OF Gs2328fIGMPSnoopingVLANEntry
   MAX-ACCESS  not-accessible
   STATUS      current
   DESCRIPTION
       " Configure IGMP Snooping Vlan Configuration. "
   ::= { gs2328fIGMPSnooping 2 }

gs2328fIGMPSnoopingVLANEntry OBJECT-TYPE
   SYNTAX      Gs2328fIGMPSnoopingVLANEntry
   MAX-ACCESS  not-accessible
   STATUS      current
   DESCRIPTION
       ""
   INDEX    { gs2328fIGMPSnoopingVLANID  }
   ::= { gs2328fIGMPSnoopingVLANTable 1 }

Gs2328fIGMPSnoopingVLANEntry ::= SEQUENCE {
   gs2328fIGMPSnoopingVLANID        	Integer32,
   gs2328fIGMPSnoopingVLANEnable    	INTEGER,
   gs2328fIGMPSnoopingVLANIGMPQuerier   INTEGER,
   gs2328fIGMPSnoopingVLANCompatibility INTEGER,
   gs2328fIGMPSnoopingVLANRV        	Integer32,
   gs2328fIGMPSnoopingVLANQI      	    Integer32,
   gs2328fIGMPSnoopingVLANQRI   	    Integer32,
   gs2328fIGMPSnoopingVLANLLQI   	    Integer32,
   gs2328fIGMPSnoopingVLANURI    	    Integer32
}

gs2328fIGMPSnoopingVLANID OBJECT-TYPE
   SYNTAX      Integer32(1..4095)
   MAX-ACCESS  read-write
   STATUS      current
   DESCRIPTION
       "The VLAN ID of the entry"
   ::= { gs2328fIGMPSnoopingVLANEntry 1 }

gs2328fIGMPSnoopingVLANEnable OBJECT-TYPE
   SYNTAX      INTEGER { disable(0), enable(1) }
   MAX-ACCESS  read-write
   STATUS      current
   DESCRIPTION
       "Enable/Disable the per-VLAN IGMP Snooping. Up to 32 VLANs can be
       selected for IGMP Snooping. "
   ::= { gs2328fIGMPSnoopingVLANEntry 2 }

gs2328fIGMPSnoopingVLANIGMPQuerier OBJECT-TYPE
   SYNTAX      INTEGER { disable(0), enable(1) }
   MAX-ACCESS  read-write
   STATUS      current
   DESCRIPTION
       "Enable/Disable the IGMP Querier in the VLAN. "
   ::= { gs2328fIGMPSnoopingVLANEntry 3 }

gs2328fIGMPSnoopingVLANCompatibility OBJECT-TYPE
   SYNTAX      INTEGER { igmpAuto(0), forcedIGMPv1(1), forcedIGMPv2(2), forcedIGMPv3(3), none(4) }
   MAX-ACCESS  read-write
   STATUS      current
   DESCRIPTION
       "Compatibility is maintained by hosts and routers taking appropriate
       actions depending on the versions of IGMP operating on hosts and routers
       within a network. The allowed selection is IGMP-Auto, Forced IGMPv1,
       Forced IGMPv2, Forced IGMPv3, default compatibility value is IGMP-Auto. "
   ::= { gs2328fIGMPSnoopingVLANEntry 4 }

gs2328fIGMPSnoopingVLANRV OBJECT-TYPE
   SYNTAX      Integer32(-1|1..255)
   MAX-ACCESS  read-write
   STATUS      current
   DESCRIPTION
       "Robustness Variable. The Robustness Variable allows tuning for the
       expected packet loss on a network. The allowed range is 1 to 255, default
        robustness variable value is 2. (-1: none)"
   ::= { gs2328fIGMPSnoopingVLANEntry 5 }

gs2328fIGMPSnoopingVLANQI OBJECT-TYPE
   SYNTAX      Integer32(-1|1..31744)
   MAX-ACCESS  read-write
   STATUS      current
   DESCRIPTION
       "Query Interval. The Query Interval is the interval between General
       Queries sent by the Querier. The allowed range is 1 to 31744 seconds,
       default query interval is 125 seconds.  (-1: none)"
   ::= { gs2328fIGMPSnoopingVLANEntry 6 }

gs2328fIGMPSnoopingVLANQRI OBJECT-TYPE
   SYNTAX      Integer32(-1|0..31744)
   MAX-ACCESS  read-write
   STATUS      current
   DESCRIPTION
       "Query Response Interval. The Maximum Response Delay used to calculate
       the Maximum Response Code inserted into the periodic General Queries. The
        allowed range is 0 to 31744 in tenths of seconds, default query response
         interval is 100 in tenths of seconds (10 seconds).   (-1: none)"
   ::= { gs2328fIGMPSnoopingVLANEntry 7 }

gs2328fIGMPSnoopingVLANLLQI OBJECT-TYPE
   SYNTAX      Integer32(-1|0..31744)
   MAX-ACCESS  read-write
   STATUS      current
   DESCRIPTION
       "LLQI (LMQI for IGMP).  Last Member Query Interval. The Last Member Query
       Time is the time value represented by the Last Member Query Interval,
       multiplied by the Last Member Query Count. The allowed range is 0 to
       31744 in tenths of seconds, default last member query interval is 10 in
       tenths of seconds (1 second).    (-1: none)"
   ::= { gs2328fIGMPSnoopingVLANEntry 8 }

gs2328fIGMPSnoopingVLANURI OBJECT-TYPE
   SYNTAX      Integer32(-1|0..31744)
   MAX-ACCESS  read-write
   STATUS      current
   DESCRIPTION
       "Unsolicited Report Interval. The Unsolicited Report Interval is the time
        between repetitions of a host's initial report of membership in a group.
         The allowed range is 0 to 31744 seconds, default unsolicited report
         interval is 1 second.    (-1: none)"
   ::= { gs2328fIGMPSnoopingVLANEntry 9 }

gs2328fIGMPSnoopingPortGroupFiltering                                                      OBJECT IDENTIFIER ::= { gs2328fIGMPSnooping 3 }

gs2328fIGMPSnoopingPortGroupFilteringCreate OBJECT-TYPE
   SYNTAX       Integer32
   MAX-ACCESS   read-write
   STATUS       current
   DESCRIPTION
       "default: 0
       0 : None  (read only) 1 : Create IGMP Snooping Port Group Filtering "
   ::= { gs2328fIGMPSnoopingPortGroupFiltering 1 }

gs2328fIGMPSnoopingPortGroupFilteringTable OBJECT-TYPE
   SYNTAX      SEQUENCE OF Gs2328fIGMPSnoopingPortGroupFilteringEntry
   MAX-ACCESS  not-accessible
   STATUS      current
   DESCRIPTION
       " Configure IGMP Snooping port group filtering. "
   ::= { gs2328fIGMPSnoopingPortGroupFiltering 2 }

gs2328fIGMPSnoopingPortGroupFilteringEntry OBJECT-TYPE
   SYNTAX      Gs2328fIGMPSnoopingPortGroupFilteringEntry
   MAX-ACCESS  not-accessible
   STATUS      current
   DESCRIPTION
       ""
   INDEX    { gs2328fIGMPSnoopingPortGroupFilteringIndex  }
   ::= { gs2328fIGMPSnoopingPortGroupFilteringTable 1 }

Gs2328fIGMPSnoopingPortGroupFilteringEntry ::= SEQUENCE {
   gs2328fIGMPSnoopingPortGroupFilteringIndex         Integer32,
   gs2328fIGMPSnoopingPortGroupFilteringPort          Integer32,
   gs2328fIGMPSnoopingPortGroupFilteringGroups        DisplayString,
   gs2328fIGMPSnoopingPortGroupFilteringRowStatus     INTEGER
}

gs2328fIGMPSnoopingPortGroupFilteringIndex OBJECT-TYPE
   SYNTAX      Integer32(1..65535)
   MAX-ACCESS  not-accessible
   STATUS      current
   DESCRIPTION
       "IGMP Snooping Port Group Filtering Configuration Index. "
   ::= { gs2328fIGMPSnoopingPortGroupFilteringEntry 1 }

gs2328fIGMPSnoopingPortGroupFilteringPort OBJECT-TYPE
   SYNTAX      Integer32(1..65535)
   MAX-ACCESS  read-write
   STATUS      current
   DESCRIPTION
       "The logical port for the settings. "
   ::= { gs2328fIGMPSnoopingPortGroupFilteringEntry 2 }

gs2328fIGMPSnoopingPortGroupFilteringGroups OBJECT-TYPE
   SYNTAX      DisplayString
   MAX-ACCESS  read-write
   STATUS      current
   DESCRIPTION
       "The IP Multicast Group that will be filtered. "
   ::= { gs2328fIGMPSnoopingPortGroupFilteringEntry 3 }

gs2328fIGMPSnoopingPortGroupFilteringRowStatus OBJECT-TYPE
   SYNTAX      INTEGER { active(1), notInservice(2), destroy(4)}
   MAX-ACCESS  read-write
   STATUS      current
   DESCRIPTION
       "1: active
        2: notInservice
        4: destroy"
   ::= { gs2328fIGMPSnoopingPortGroupFilteringEntry 4 }

gs2328fIGMPSnoopingStatus                                                      OBJECT IDENTIFIER ::= { gs2328fIGMPSnooping 4 }

gs2328fIGMPSnoopingstatisticClear OBJECT-TYPE
   SYNTAX      INTEGER { none(0), clear(1)}
   MAX-ACCESS  read-write
   STATUS      current
   DESCRIPTION
       "Clears all Statistics counters."
   ::= { gs2328fIGMPSnoopingStatus 1 }


gs2328fIGMPSnoopingstatisticTable OBJECT-TYPE
   SYNTAX      SEQUENCE OF Gs2328fIGMPSnoopingstatisticEntry
   MAX-ACCESS  not-accessible
   STATUS      current
   DESCRIPTION
       " Configure Vlan Port Isolation Configuration. "
   ::= { gs2328fIGMPSnoopingStatus 2 }

gs2328fIGMPSnoopingstatisticEntry OBJECT-TYPE
   SYNTAX      Gs2328fIGMPSnoopingstatisticEntry
   MAX-ACCESS  not-accessible
   STATUS      current
   DESCRIPTION
       ""
   INDEX    { gs2328fIGMPSnoopingstatisticVLANID  }
   ::= { gs2328fIGMPSnoopingstatisticTable 1 }

Gs2328fIGMPSnoopingstatisticEntry ::= SEQUENCE {
   gs2328fIGMPSnoopingstatisticVLANID              Integer32,
   gs2328fIGMPSnoopingstatisticQuerierVersion      DisplayString,
   gs2328fIGMPSnoopingstatisticHostVersion         DisplayString,
   gs2328fIGMPSnoopingstatisticQuerierStatus       DisplayString,
   gs2328fIGMPSnoopingstatisticQueriesTransmitted  Counter32,
   gs2328fIGMPSnoopingstatisticQueriesReceived     Counter32,
   gs2328fIGMPSnoopingstatisticV1ReportsReceived   Counter32,
   gs2328fIGMPSnoopingstatisticV2ReportsReceived   Counter32,
   gs2328fIGMPSnoopingstatisticV3ReportsReceived   Counter32,
   gs2328fIGMPSnoopingstatisticV2LeavesReceived    Counter32
}


gs2328fIGMPSnoopingstatisticVLANID OBJECT-TYPE
   SYNTAX      Integer32(1..4095)
   MAX-ACCESS  read-only
   STATUS      current
   DESCRIPTION
       "The VLAN ID of the entry. "
   ::= { gs2328fIGMPSnoopingstatisticEntry 1 }

gs2328fIGMPSnoopingstatisticQuerierVersion OBJECT-TYPE
   SYNTAX      DisplayString
   MAX-ACCESS  read-only
   STATUS      current
   DESCRIPTION
       "Working Querier Version currently. "
   ::= { gs2328fIGMPSnoopingstatisticEntry 2 }

gs2328fIGMPSnoopingstatisticHostVersion OBJECT-TYPE
   SYNTAX      DisplayString
   MAX-ACCESS  read-only
   STATUS      current
   DESCRIPTION
       "Working Host Version currently. "
   ::= { gs2328fIGMPSnoopingstatisticEntry 3 }

gs2328fIGMPSnoopingstatisticQuerierStatus OBJECT-TYPE
   SYNTAX      DisplayString
   MAX-ACCESS  read-only
   STATUS      current
   DESCRIPTION
       "Shows the Querier status is ACTIVE or IDLE. DISABLE denotes the specific
        interface is administratively disabled. "
   ::= { gs2328fIGMPSnoopingstatisticEntry 4 }

gs2328fIGMPSnoopingstatisticQueriesTransmitted OBJECT-TYPE
   SYNTAX      Counter32
   MAX-ACCESS  read-only
   STATUS      current
   DESCRIPTION
       "The number of Transmitted Queries. "
   ::= { gs2328fIGMPSnoopingstatisticEntry 5 }

gs2328fIGMPSnoopingstatisticQueriesReceived OBJECT-TYPE
   SYNTAX      Counter32
   MAX-ACCESS  read-only
   STATUS      current
   DESCRIPTION
       "The number of Received Queries. "
   ::= { gs2328fIGMPSnoopingstatisticEntry 6 }

gs2328fIGMPSnoopingstatisticV1ReportsReceived OBJECT-TYPE
   SYNTAX      Counter32
   MAX-ACCESS  read-only
   STATUS      current
   DESCRIPTION
       "The number of Received V1 Reports. "
   ::= { gs2328fIGMPSnoopingstatisticEntry 7 }

gs2328fIGMPSnoopingstatisticV2ReportsReceived OBJECT-TYPE
   SYNTAX      Counter32
   MAX-ACCESS  read-only
   STATUS      current
   DESCRIPTION
       "The number of Received V2 Reports. "
   ::= { gs2328fIGMPSnoopingstatisticEntry 8 }

gs2328fIGMPSnoopingstatisticV3ReportsReceived OBJECT-TYPE
   SYNTAX      Counter32
   MAX-ACCESS  read-only
   STATUS      current
   DESCRIPTION
       "The number of Received V3 Reports. "
   ::= { gs2328fIGMPSnoopingstatisticEntry 9 }

gs2328fIGMPSnoopingstatisticV2LeavesReceived OBJECT-TYPE
   SYNTAX      Counter32
   MAX-ACCESS  read-only
   STATUS      current
   DESCRIPTION
       "The number of Received V2 Leaves. "
   ::= { gs2328fIGMPSnoopingstatisticEntry 10 }

gs2328fIGMPSnoopingRouterPortTable OBJECT-TYPE
   SYNTAX      SEQUENCE OF Gs2328fIGMPSnoopingRouterPortEntry
   MAX-ACCESS  not-accessible
   STATUS      current
   DESCRIPTION
       " Configure Vlan Port Isolation Configuration. "
   ::= { gs2328fIGMPSnoopingStatus 3 }

gs2328fIGMPSnoopingRouterPortEntry OBJECT-TYPE
   SYNTAX      Gs2328fIGMPSnoopingRouterPortEntry
   MAX-ACCESS  not-accessible
   STATUS      current
   DESCRIPTION
       ""
   INDEX    { ifIndex  }
   ::= { gs2328fIGMPSnoopingRouterPortTable 1 }

Gs2328fIGMPSnoopingRouterPortEntry ::= SEQUENCE {
   gs2328fIGMPSnoopingRouterPortStatus            DisplayString
}

gs2328fIGMPSnoopingRouterPortStatus OBJECT-TYPE
   SYNTAX      DisplayString
   MAX-ACCESS  read-only
   STATUS      current
   DESCRIPTION
       "Display which ports act as router ports. A router port is a port on the
       Ethernet switch that leads towards the Layer 3 multicast device or IGMP
       querier.
       Static denotes the specific port is configured to be a router port.
       Dynamic denotes the specific port is learnt to be a router port.
       Both denote the specific port is configured or learnt to be a router port. "
   ::= { gs2328fIGMPSnoopingRouterPortEntry 1 }

gs2328fIGMPSnoopingGroupsTable OBJECT-TYPE
   SYNTAX      SEQUENCE OF Gs2328fIGMPSnoopingGroupsEntry
   MAX-ACCESS  not-accessible
   STATUS      current
   DESCRIPTION
       "IGMP Snooping Groups Information . "
   ::= { gs2328fIGMPSnooping 5 }

gs2328fIGMPSnoopingGroupsEntry OBJECT-TYPE
   SYNTAX      Gs2328fIGMPSnoopingGroupsEntry
   MAX-ACCESS  not-accessible
   STATUS      current
   DESCRIPTION
       ""
   INDEX    { gs2328fIGMPSnoopingGroupsIndex  }
   ::= { gs2328fIGMPSnoopingGroupsTable 1 }

Gs2328fIGMPSnoopingGroupsEntry ::= SEQUENCE {
   gs2328fIGMPSnoopingGroupsIndex          Integer32,
   gs2328fIGMPSnoopingGroupsVLANID         Integer32,
   gs2328fIGMPSnoopingGroups               InetAddress,
   gs2328fIGMPSnoopingGroupsMemberships    DisplayString
}

gs2328fIGMPSnoopingGroupsIndex OBJECT-TYPE
   SYNTAX      Integer32(1..65535)
   MAX-ACCESS  not-accessible
   STATUS      current
   DESCRIPTION
       "IGMP Snooping Groups Index"
   ::= { gs2328fIGMPSnoopingGroupsEntry 1 }

gs2328fIGMPSnoopingGroupsVLANID OBJECT-TYPE
   SYNTAX      Integer32(1..4095)
   MAX-ACCESS  read-only
   STATUS      current
   DESCRIPTION
       "VLAN ID of the group. "
   ::= { gs2328fIGMPSnoopingGroupsEntry 2 }

gs2328fIGMPSnoopingGroups OBJECT-TYPE
   SYNTAX      DisplayString
   MAX-ACCESS  read-only
   STATUS      current
   DESCRIPTION
       "Group address of the group displayed."
   ::= { gs2328fIGMPSnoopingGroupsEntry 3 }

gs2328fIGMPSnoopingGroupsMemberships OBJECT-TYPE
   SYNTAX      DisplayString
   MAX-ACCESS  read-only
   STATUS      current
   DESCRIPTION
       "Ports under this group."
   ::= { gs2328fIGMPSnoopingGroupsEntry 4 }

gs2328fIGMPSnoopingSSMTable OBJECT-TYPE
   SYNTAX      SEQUENCE OF Gs2328fIGMPSnoopingSSMEntry
   MAX-ACCESS  not-accessible
   STATUS      current
   DESCRIPTION
       "The IGMP SFM (Source-Filtered Multicast) Information Table also contains
        the SSM (Source-Specific Multicast) information. This table is sorted
         first by VLAN ID, then by group, and then by Port. Different source
         addresses belong to the same group are treated as single entry."
   ::= { gs2328fIGMPSnooping 6 }

gs2328fIGMPSnoopingSSMEntry OBJECT-TYPE
   SYNTAX      Gs2328fIGMPSnoopingSSMEntry
   MAX-ACCESS  not-accessible
   STATUS      current
   DESCRIPTION
       ""
   INDEX    { gs2328fIGMPSnoopingSSMIndex  }
   ::= { gs2328fIGMPSnoopingSSMTable 1 }

Gs2328fIGMPSnoopingSSMEntry ::= SEQUENCE {
   gs2328fIGMPSnoopingSSMIndex          Integer32,
   gs2328fIGMPSnoopingSSMVLANID         Integer32,
   gs2328fIGMPSnoopingSSMGroup          DisplayString,
   gs2328fIGMPSnoopingSSMPort           Integer32,
   gs2328fIGMPSnoopingSSMMode           DisplayString,
   gs2328fIGMPSnoopingSSMSourceAddress  DisplayString,
   gs2328fIGMPSnoopingSSMType           DisplayString
}

gs2328fIGMPSnoopingSSMIndex OBJECT-TYPE
   SYNTAX      Integer32(1..65535)
   MAX-ACCESS  not-accessible
   STATUS      current
   DESCRIPTION
       "IGMP Snooping SSM Index"
   ::= { gs2328fIGMPSnoopingSSMEntry 1 }

gs2328fIGMPSnoopingSSMVLANID OBJECT-TYPE
   SYNTAX      Integer32(1..4095)
   MAX-ACCESS  read-only
   STATUS      current
   DESCRIPTION
       "VLAN ID of the group. "
   ::= { gs2328fIGMPSnoopingSSMEntry 2 }

gs2328fIGMPSnoopingSSMGroup OBJECT-TYPE
   SYNTAX      DisplayString
   MAX-ACCESS  read-only
   STATUS      current
   DESCRIPTION
       "Group address of the group displayed."
   ::= { gs2328fIGMPSnoopingSSMEntry 3 }

gs2328fIGMPSnoopingSSMPort OBJECT-TYPE
   SYNTAX      Integer32(1..65535)
   MAX-ACCESS  read-only
   STATUS      current
   DESCRIPTION
       "Ports under this group."
   ::= { gs2328fIGMPSnoopingSSMEntry 4 }

gs2328fIGMPSnoopingSSMMode OBJECT-TYPE
   SYNTAX      DisplayString
   MAX-ACCESS  read-only
   STATUS      current
   DESCRIPTION
       "Indicates the filtering mode maintained per (VLAN ID, port number,
       Group Address) basis. It can be either Include or Exclude."
   ::= { gs2328fIGMPSnoopingSSMEntry 5 }

gs2328fIGMPSnoopingSSMSourceAddress OBJECT-TYPE
   SYNTAX      DisplayString
   MAX-ACCESS  read-only
   STATUS      current
   DESCRIPTION
       "IP Address of the source. Currently, system limits the total number of
       IP source addresses for filtering to be 128."
   ::= { gs2328fIGMPSnoopingSSMEntry 6 }

gs2328fIGMPSnoopingSSMType OBJECT-TYPE
   SYNTAX      DisplayString
   MAX-ACCESS  read-only
   STATUS      current
   DESCRIPTION
       "Indicates the Type. It can be either Allow or Deny."
   ::= { gs2328fIGMPSnoopingSSMEntry 7 }

gs2328fMLDSnooping                                                           OBJECT IDENTIFIER ::= { gs2328fConfiguration 17 }

gs2328fMLDSnoopingBasic                                                      OBJECT IDENTIFIER ::= { gs2328fMLDSnooping 1 }

gs2328fMLDSnoopingEnable  OBJECT-TYPE
   SYNTAX      INTEGER { disable(0), enable(1) }
   MAX-ACCESS  read-write
   STATUS      current
   DESCRIPTION
       "Enable/Disable the Global MLD Snooping"
   ::= { gs2328fMLDSnoopingBasic 1 }

gs2328fMLDSnoopingUnregisteredIPMCv6Flooding  OBJECT-TYPE
   SYNTAX      INTEGER { disable(0), enable(1) }
   MAX-ACCESS  read-write
   STATUS      current
   DESCRIPTION
       "Enable/Disable unregistered IPMCv6 traffic flooding. "
   ::= { gs2328fMLDSnoopingBasic 2 }

gs2328fMLDSnoopingSSMIPRangeAddr  OBJECT-TYPE
   SYNTAX      DisplayString
   MAX-ACCESS  read-write
   STATUS      current
   DESCRIPTION
       "SSM (Source-Specific Multicast) Range allows the SSM-aware hosts and
       routers run the SSM service model for the groups in the address range. "
   ::= { gs2328fMLDSnoopingBasic 3 }

gs2328fMLDSnoopingSSMIPRangeValue  OBJECT-TYPE
   SYNTAX      Integer32(8..128)
   MAX-ACCESS  read-write
   STATUS      current
   DESCRIPTION
       "SSM (Source-Specific Multicast) Range allows the SSM-aware hosts and
       routers run the SSM service model for the groups in the address range value. "
   ::= { gs2328fMLDSnoopingBasic 4 }

gs2328fMLDSnoopingProxyEnabled  OBJECT-TYPE
   SYNTAX      INTEGER { disable(0), enable(1) }
   MAX-ACCESS  read-write
   STATUS      current
   DESCRIPTION
       "Enable/Disable MLD Proxy. This feature can be used to avoid forwarding
       unnecessary join and leave messages to the router side. "
   ::= { gs2328fMLDSnoopingBasic 5 }

gs2328fMLDSnoopingPortRelatedTable OBJECT-TYPE
   SYNTAX      SEQUENCE OF Gs2328fMLDSnoopingPortRelatedEntry
   MAX-ACCESS  not-accessible
   STATUS      current
   DESCRIPTION
       " Configure MLD Snooping Port Related Configuration. "
   ::= { gs2328fMLDSnoopingBasic 6 }

gs2328fMLDSnoopingPortRelatedEntry OBJECT-TYPE
   SYNTAX      Gs2328fMLDSnoopingPortRelatedEntry
   MAX-ACCESS  not-accessible
   STATUS      current
   DESCRIPTION
       ""
   INDEX    { ifIndex  }
   ::= { gs2328fMLDSnoopingPortRelatedTable 1 }

Gs2328fMLDSnoopingPortRelatedEntry ::= SEQUENCE {
   gs2328fMLDSnoopingRouterPort	INTEGER,
   gs2328fMLDSnoopingFastLeave  	INTEGER,
   gs2328fMLDSnoopingThrottling    Integer32
}

gs2328fMLDSnoopingRouterPort OBJECT-TYPE
   SYNTAX      INTEGER { disable(0), enable(1) }
   MAX-ACCESS  read-write
   STATUS      current
   DESCRIPTION
       "Specify which ports act as router ports. A router port is a port on the
       Ethernet switch that leads towards the Layer 3 multicast device or IGMP
       querier. If an aggregation member port is selected as a router port, the
       whole aggregation will act as a router port. "
   ::= { gs2328fMLDSnoopingPortRelatedEntry 1 }

gs2328fMLDSnoopingFastLeave OBJECT-TYPE
   SYNTAX      INTEGER { disable(0), enable(1) }
   MAX-ACCESS  read-write
   STATUS      current
   DESCRIPTION
       "Enable/Disable the fast leave on the port. "
   ::= { gs2328fMLDSnoopingPortRelatedEntry 2 }

gs2328fMLDSnoopingThrottling OBJECT-TYPE
   SYNTAX      Integer32(0..10)
   MAX-ACCESS  read-write
   STATUS      current
   DESCRIPTION
       "Enable to limit the number of multicast groups to which a switch port can belong.
       0: unlimited"
   ::= { gs2328fMLDSnoopingPortRelatedEntry 3 }

gs2328fMLDSnoopingVLANTable OBJECT-TYPE
   SYNTAX      SEQUENCE OF Gs2328fMLDSnoopingVLANEntry
   MAX-ACCESS  not-accessible
   STATUS      current
   DESCRIPTION
       " Configure MLD Snooping Vlan Configuration. "
   ::= { gs2328fMLDSnooping 2 }

gs2328fMLDSnoopingVLANEntry OBJECT-TYPE
   SYNTAX      Gs2328fMLDSnoopingVLANEntry
   MAX-ACCESS  not-accessible
   STATUS      current
   DESCRIPTION
       ""
   INDEX    { gs2328fMLDSnoopingVLANID  }
   ::= { gs2328fMLDSnoopingVLANTable 1 }

Gs2328fMLDSnoopingVLANEntry ::= SEQUENCE {
   gs2328fMLDSnoopingVLANID        	Integer32,
   gs2328fMLDSnoopingVLANEnable    	INTEGER,
   gs2328fMLDSnoopingVLANIGMPQuerier   INTEGER,
   gs2328fMLDSnoopingVLANCompatibility INTEGER,
   gs2328fMLDSnoopingVLANRV        	Integer32,
   gs2328fMLDSnoopingVLANQI      	    Integer32,
   gs2328fMLDSnoopingVLANQRI   	    Integer32,
   gs2328fMLDSnoopingVLANLLQI   	    Integer32,
   gs2328fMLDSnoopingVLANURI    	    Integer32
}

gs2328fMLDSnoopingVLANID OBJECT-TYPE
   SYNTAX      Integer32(1..4095)
   MAX-ACCESS  read-write
   STATUS      current
   DESCRIPTION
       "The VLAN ID of the entry"
   ::= { gs2328fMLDSnoopingVLANEntry 1 }

gs2328fMLDSnoopingVLANEnable OBJECT-TYPE
   SYNTAX      INTEGER { disable(0), enable(1) }
   MAX-ACCESS  read-write
   STATUS      current
   DESCRIPTION
       "Enable/Disable the per-VLAN MLD Snooping. Up to 32 VLANs can be
       selected for MLD Snooping. "
   ::= { gs2328fMLDSnoopingVLANEntry 2 }

gs2328fMLDSnoopingVLANIGMPQuerier OBJECT-TYPE
   SYNTAX      INTEGER { disable(0), enable(1) }
   MAX-ACCESS  read-write
   STATUS      current
   DESCRIPTION
       "Enable/Disable the MLD Querier in the VLAN. "
   ::= { gs2328fMLDSnoopingVLANEntry 3 }

gs2328fMLDSnoopingVLANCompatibility OBJECT-TYPE
   SYNTAX      INTEGER { mldAuto(0), forcedMLDv1(1), forcedMLDv2(2), none(3) }
   MAX-ACCESS  read-write
   STATUS      current
   DESCRIPTION
       "Compatibility is maintained by hosts and routers taking appropriate
       actions depending on the versions of IGMP operating on hosts and routers
       within a network. The allowed selection is MLD-Auto, Forced MLDv1,
       Forced MLDv2, default compatibility value is IGMP-Auto. "
   ::= { gs2328fMLDSnoopingVLANEntry 4 }

gs2328fMLDSnoopingVLANRV OBJECT-TYPE
   SYNTAX      Integer32(-1|1..255)
   MAX-ACCESS  read-write
   STATUS      current
   DESCRIPTION
       "Robustness Variable. The Robustness Variable allows tuning for the
       expected packet loss on a network. The allowed range is 1 to 255, default
        robustness variable value is 2. (-1: none)"
   ::= { gs2328fMLDSnoopingVLANEntry 5 }

gs2328fMLDSnoopingVLANQI OBJECT-TYPE
   SYNTAX      Integer32(-1|1..31744)
   MAX-ACCESS  read-write
   STATUS      current
   DESCRIPTION
       "Query Interval. The Query Interval is the interval between General
       Queries sent by the Querier. The allowed range is 1 to 31744 seconds,
       default query interval is 125 seconds.  (-1: none)"
   ::= { gs2328fMLDSnoopingVLANEntry 6 }

gs2328fMLDSnoopingVLANQRI OBJECT-TYPE
   SYNTAX      Integer32(-1|0..31744)
   MAX-ACCESS  read-write
   STATUS      current
   DESCRIPTION
       "Query Response Interval. The Maximum Response Delay used to calculate
       the Maximum Response Code inserted into the periodic General Queries. The
        allowed range is 0 to 31744 in tenths of seconds, default query response
         interval is 100 in tenths of seconds (10 seconds).   (-1: none)"
   ::= { gs2328fMLDSnoopingVLANEntry 7 }

gs2328fMLDSnoopingVLANLLQI OBJECT-TYPE
   SYNTAX      Integer32(-1|0..31744)
   MAX-ACCESS  read-write
   STATUS      current
   DESCRIPTION
       "LLQI (LMQI for MLD).  Last Member Query Interval. The Last Member Query
       Time is the time value represented by the Last Member Query Interval,
       multiplied by the Last Member Query Count. The allowed range is 0 to
       31744 in tenths of seconds, default last member query interval is 10 in
       tenths of seconds (1 second).    (-1: none)"
   ::= { gs2328fMLDSnoopingVLANEntry 8 }

gs2328fMLDSnoopingVLANURI OBJECT-TYPE
   SYNTAX      Integer32(-1|0..31744)
   MAX-ACCESS  read-write
   STATUS      current
   DESCRIPTION
       "Unsolicited Report Interval. The Unsolicited Report Interval is the time
        between repetitions of a host's initial report of membership in a group.
         The allowed range is 0 to 31744 seconds, default unsolicited report
         interval is 1 second.    (-1: none)"
   ::= { gs2328fMLDSnoopingVLANEntry 9 }

gs2328fMLDSnoopingPortGroupFiltering                                                      OBJECT IDENTIFIER ::= { gs2328fMLDSnooping 3 }

gs2328fMLDSnoopingPortGroupFilteringCreate OBJECT-TYPE
   SYNTAX       Integer32
   MAX-ACCESS   read-write
   STATUS       current
   DESCRIPTION
       "default: 0
       0 : None  (read only) 1 : Create MLD Snooping Port Group Filtering "
   ::= { gs2328fMLDSnoopingPortGroupFiltering 1 }

gs2328fMLDSnoopingPortGroupFilteringTable OBJECT-TYPE
   SYNTAX      SEQUENCE OF Gs2328fMLDSnoopingPortGroupFilteringEntry
   MAX-ACCESS  not-accessible
   STATUS      current
   DESCRIPTION
       " Configure MLD Snooping port group filtering. "
   ::= { gs2328fMLDSnoopingPortGroupFiltering 2 }

gs2328fMLDSnoopingPortGroupFilteringEntry OBJECT-TYPE
   SYNTAX      Gs2328fMLDSnoopingPortGroupFilteringEntry
   MAX-ACCESS  not-accessible
   STATUS      current
   DESCRIPTION
       ""
   INDEX    { gs2328fMLDSnoopingPortGroupFilteringIndex  }
   ::= { gs2328fMLDSnoopingPortGroupFilteringTable 1 }

Gs2328fMLDSnoopingPortGroupFilteringEntry ::= SEQUENCE {
   gs2328fMLDSnoopingPortGroupFilteringIndex         Integer32,
   gs2328fMLDSnoopingPortGroupFilteringPort          Integer32,
   gs2328fMLDSnoopingPortGroupFilteringGroups        DisplayString,
   gs2328fMLDSnoopingPortGroupFilteringRowStatus     INTEGER
}

gs2328fMLDSnoopingPortGroupFilteringIndex OBJECT-TYPE
   SYNTAX      Integer32(1..65535)
   MAX-ACCESS  not-accessible
   STATUS      current
   DESCRIPTION
       "MLD Snooping Port Group Filtering Configuration Index. "
   ::= { gs2328fMLDSnoopingPortGroupFilteringEntry 1 }

gs2328fMLDSnoopingPortGroupFilteringPort OBJECT-TYPE
   SYNTAX      Integer32(1..65535)
   MAX-ACCESS  read-write
   STATUS      current
   DESCRIPTION
       "The logical port for the settings. "
   ::= { gs2328fMLDSnoopingPortGroupFilteringEntry 2 }

gs2328fMLDSnoopingPortGroupFilteringGroups OBJECT-TYPE
   SYNTAX      DisplayString
   MAX-ACCESS  read-write
   STATUS      current
   DESCRIPTION
       "The IP Multicast Group that will be filtered. "
   ::= { gs2328fMLDSnoopingPortGroupFilteringEntry 3 }

gs2328fMLDSnoopingPortGroupFilteringRowStatus OBJECT-TYPE
   SYNTAX      INTEGER { active(1), notInservice(2), destroy(4)}
   MAX-ACCESS  read-write
   STATUS      current
   DESCRIPTION
       "1: active
        2: notInservice
        4: destroy"
   ::= { gs2328fMLDSnoopingPortGroupFilteringEntry 4 }

gs2328fMLDSnoopingStatus                                                      OBJECT IDENTIFIER ::= { gs2328fMLDSnooping 4 }

gs2328fMLDSnoopingstatisticClear OBJECT-TYPE
   SYNTAX      INTEGER { none(0), clear(1)}
   MAX-ACCESS  read-write
   STATUS      current
   DESCRIPTION
       "Clears all Statistics counters."
   ::= { gs2328fMLDSnoopingStatus 1 }


gs2328fMLDSnoopingstatisticTable OBJECT-TYPE
   SYNTAX      SEQUENCE OF Gs2328fMLDSnoopingstatisticEntry
   MAX-ACCESS  not-accessible
   STATUS      current
   DESCRIPTION
       " Configure Vlan Port Isolation Configuration. "
   ::= { gs2328fMLDSnoopingStatus 2 }

gs2328fMLDSnoopingstatisticEntry OBJECT-TYPE
   SYNTAX      Gs2328fMLDSnoopingstatisticEntry
   MAX-ACCESS  not-accessible
   STATUS      current
   DESCRIPTION
       ""
   INDEX    { gs2328fMLDSnoopingstatisticVLANID  }
   ::= { gs2328fMLDSnoopingstatisticTable 1 }

Gs2328fMLDSnoopingstatisticEntry ::= SEQUENCE {
   gs2328fMLDSnoopingstatisticVLANID              Integer32,
   gs2328fMLDSnoopingstatisticQuerierVersion      DisplayString,
   gs2328fMLDSnoopingstatisticHostVersion         DisplayString,
   gs2328fMLDSnoopingstatisticQuerierStatus       DisplayString,
   gs2328fMLDSnoopingstatisticQueriesTransmitted  Counter32,
   gs2328fMLDSnoopingstatisticQueriesReceived     Counter32,
   gs2328fMLDSnoopingstatisticV1ReportsReceived   Counter32,
   gs2328fMLDSnoopingstatisticV2ReportsReceived   Counter32,
   gs2328fMLDSnoopingstatisticV1LeavesReceived    Counter32
}


gs2328fMLDSnoopingstatisticVLANID OBJECT-TYPE
   SYNTAX      Integer32(1..4095)
   MAX-ACCESS  read-only
   STATUS      current
   DESCRIPTION
       "The VLAN ID of the entry. "
   ::= { gs2328fMLDSnoopingstatisticEntry 1 }

gs2328fMLDSnoopingstatisticQuerierVersion OBJECT-TYPE
   SYNTAX      DisplayString
   MAX-ACCESS  read-only
   STATUS      current
   DESCRIPTION
       "Working Querier Version currently. "
   ::= { gs2328fMLDSnoopingstatisticEntry 2 }

gs2328fMLDSnoopingstatisticHostVersion OBJECT-TYPE
   SYNTAX      DisplayString
   MAX-ACCESS  read-only
   STATUS      current
   DESCRIPTION
       "Working Host Version currently. "
   ::= { gs2328fMLDSnoopingstatisticEntry 3 }

gs2328fMLDSnoopingstatisticQuerierStatus OBJECT-TYPE
   SYNTAX      DisplayString
   MAX-ACCESS  read-only
   STATUS      current
   DESCRIPTION
       "Shows the Querier status is ACTIVE or IDLE. DISABLE denotes the specific
        interface is administratively disabled. "
   ::= { gs2328fMLDSnoopingstatisticEntry 4 }

gs2328fMLDSnoopingstatisticQueriesTransmitted OBJECT-TYPE
   SYNTAX      Counter32
   MAX-ACCESS  read-only
   STATUS      current
   DESCRIPTION
       "The number of Transmitted Queries. "
   ::= { gs2328fMLDSnoopingstatisticEntry 5 }

gs2328fMLDSnoopingstatisticQueriesReceived OBJECT-TYPE
   SYNTAX      Counter32
   MAX-ACCESS  read-only
   STATUS      current
   DESCRIPTION
       "The number of Received Queries. "
   ::= { gs2328fMLDSnoopingstatisticEntry 6 }

gs2328fMLDSnoopingstatisticV1ReportsReceived OBJECT-TYPE
   SYNTAX      Counter32
   MAX-ACCESS  read-only
   STATUS      current
   DESCRIPTION
       "The number of Received V1 Reports. "
   ::= { gs2328fMLDSnoopingstatisticEntry 7 }

gs2328fMLDSnoopingstatisticV2ReportsReceived OBJECT-TYPE
   SYNTAX      Counter32
   MAX-ACCESS  read-only
   STATUS      current
   DESCRIPTION
       "The number of Received V2 Reports. "
   ::= { gs2328fMLDSnoopingstatisticEntry 8 }

gs2328fMLDSnoopingstatisticV1LeavesReceived OBJECT-TYPE
   SYNTAX      Counter32
   MAX-ACCESS  read-only
   STATUS      current
   DESCRIPTION
       "The number of Received V1 Leaves. "
   ::= { gs2328fMLDSnoopingstatisticEntry 9 }

gs2328fMLDSnoopingRouterPortTable OBJECT-TYPE
   SYNTAX      SEQUENCE OF Gs2328fMLDSnoopingRouterPortEntry
   MAX-ACCESS  not-accessible
   STATUS      current
   DESCRIPTION
       " Configure Vlan Port Isolation Configuration. "
   ::= { gs2328fMLDSnoopingStatus 3 }

gs2328fMLDSnoopingRouterPortEntry OBJECT-TYPE
   SYNTAX      Gs2328fMLDSnoopingRouterPortEntry
   MAX-ACCESS  not-accessible
   STATUS      current
   DESCRIPTION
       ""
   INDEX    { ifIndex  }
   ::= { gs2328fMLDSnoopingRouterPortTable 1 }

Gs2328fMLDSnoopingRouterPortEntry ::= SEQUENCE {
   gs2328fMLDSnoopingRouterPortStatus            DisplayString
}

gs2328fMLDSnoopingRouterPortStatus OBJECT-TYPE
   SYNTAX      DisplayString
   MAX-ACCESS  read-only
   STATUS      current
   DESCRIPTION
       "Display which ports act as router ports. A router port is a port on the
       Ethernet switch that leads towards the Layer 3 multicast device or IGMP
       querier.
       Static denotes the specific port is configured to be a router port.
       Dynamic denotes the specific port is learnt to be a router port.
       Both denote the specific port is configured or learnt to be a router port. "
   ::= { gs2328fMLDSnoopingRouterPortEntry 1 }

gs2328fMLDSnoopingGroupsTable OBJECT-TYPE
   SYNTAX      SEQUENCE OF Gs2328fMLDSnoopingGroupsEntry
   MAX-ACCESS  not-accessible
   STATUS      current
   DESCRIPTION
       "MLD Snooping Groups Information . "
   ::= { gs2328fMLDSnooping 5 }

gs2328fMLDSnoopingGroupsEntry OBJECT-TYPE
   SYNTAX      Gs2328fMLDSnoopingGroupsEntry
   MAX-ACCESS  not-accessible
   STATUS      current
   DESCRIPTION
       ""
   INDEX    { gs2328fMLDSnoopingGroupsIndex  }
   ::= { gs2328fMLDSnoopingGroupsTable 1 }

Gs2328fMLDSnoopingGroupsEntry ::= SEQUENCE {
   gs2328fMLDSnoopingGroupsIndex          Integer32,
   gs2328fMLDSnoopingGroupsVLANID         Integer32,
   gs2328fMLDSnoopingGroups               InetAddress,
   gs2328fMLDSnoopingGroupsMemberships    DisplayString
}

gs2328fMLDSnoopingGroupsIndex OBJECT-TYPE
   SYNTAX      Integer32(1..65535)
   MAX-ACCESS  not-accessible
   STATUS      current
   DESCRIPTION
       "MLD Snooping Groups Index"
   ::= { gs2328fMLDSnoopingGroupsEntry 1 }

gs2328fMLDSnoopingGroupsVLANID OBJECT-TYPE
   SYNTAX      Integer32(1..4095)
   MAX-ACCESS  read-only
   STATUS      current
   DESCRIPTION
       "VLAN ID of the group. "
   ::= { gs2328fMLDSnoopingGroupsEntry 2 }

gs2328fMLDSnoopingGroups OBJECT-TYPE
   SYNTAX      DisplayString
   MAX-ACCESS  read-only
   STATUS      current
   DESCRIPTION
       "Group address of the group displayed."
   ::= { gs2328fMLDSnoopingGroupsEntry 3 }

gs2328fMLDSnoopingGroupsMemberships OBJECT-TYPE
   SYNTAX      DisplayString
   MAX-ACCESS  read-only
   STATUS      current
   DESCRIPTION
       "Ports under this group."
   ::= { gs2328fMLDSnoopingGroupsEntry 4 }

gs2328fMLDSnoopingSSMTable OBJECT-TYPE
   SYNTAX      SEQUENCE OF Gs2328fMLDSnoopingSSMEntry
   MAX-ACCESS  not-accessible
   STATUS      current
   DESCRIPTION
       "The MLD SFM (Source-Filtered Multicast) Information Table also contains
        the SSM (Source-Specific Multicast) information. This table is sorted
         first by VLAN ID, then by group, and then by Port. Different source
         addresses belong to the same group are treated as single entry."
   ::= { gs2328fMLDSnooping 6 }

gs2328fMLDSnoopingSSMEntry OBJECT-TYPE
   SYNTAX      Gs2328fMLDSnoopingSSMEntry
   MAX-ACCESS  not-accessible
   STATUS      current
   DESCRIPTION
       ""
   INDEX    { gs2328fMLDSnoopingSSMIndex  }
   ::= { gs2328fMLDSnoopingSSMTable 1 }

Gs2328fMLDSnoopingSSMEntry ::= SEQUENCE {
   gs2328fMLDSnoopingSSMIndex          Integer32,
   gs2328fMLDSnoopingSSMVLANID         Integer32,
   gs2328fMLDSnoopingSSMGroup          DisplayString,
   gs2328fMLDSnoopingSSMPort           Integer32,
   gs2328fMLDSnoopingSSMMode           DisplayString,
   gs2328fMLDSnoopingSSMSourceAddress  DisplayString,
   gs2328fMLDSnoopingSSMType           DisplayString
}

gs2328fMLDSnoopingSSMIndex OBJECT-TYPE
   SYNTAX      Integer32(1..65535)
   MAX-ACCESS  not-accessible
   STATUS      current
   DESCRIPTION
       "MLD Snooping SSM Index"
   ::= { gs2328fMLDSnoopingSSMEntry 1 }

gs2328fMLDSnoopingSSMVLANID OBJECT-TYPE
   SYNTAX      Integer32(1..4095)
   MAX-ACCESS  read-only
   STATUS      current
   DESCRIPTION
       "VLAN ID of the group. "
   ::= { gs2328fMLDSnoopingSSMEntry 2 }

gs2328fMLDSnoopingSSMGroup OBJECT-TYPE
   SYNTAX      DisplayString
   MAX-ACCESS  read-only
   STATUS      current
   DESCRIPTION
       "Group address of the group displayed."
   ::= { gs2328fMLDSnoopingSSMEntry 3 }

gs2328fMLDSnoopingSSMPort OBJECT-TYPE
   SYNTAX      Integer32(1..65535)
   MAX-ACCESS  read-only
   STATUS      current
   DESCRIPTION
       "Ports under this group."
   ::= { gs2328fMLDSnoopingSSMEntry 4 }

gs2328fMLDSnoopingSSMMode OBJECT-TYPE
   SYNTAX      DisplayString
   MAX-ACCESS  read-only
   STATUS      current
   DESCRIPTION
       "Indicates the filtering mode maintained per (VLAN ID, port number,
       Group Address) basis. It can be either Include or Exclude."
   ::= { gs2328fMLDSnoopingSSMEntry 5 }

gs2328fMLDSnoopingSSMSourceAddress OBJECT-TYPE
   SYNTAX      DisplayString
   MAX-ACCESS  read-only
   STATUS      current
   DESCRIPTION
       "IP Address of the source. Currently, system limits the total number of
       IP source addresses for filtering to be 128."
   ::= { gs2328fMLDSnoopingSSMEntry 6 }

gs2328fMLDSnoopingSSMType OBJECT-TYPE
   SYNTAX      DisplayString
   MAX-ACCESS  read-only
   STATUS      current
   DESCRIPTION
       "Indicates the Type. It can be either Allow or Deny."
   ::= { gs2328fMLDSnoopingSSMEntry 7 }


gs2328fMVR                                                                   OBJECT IDENTIFIER ::= { gs2328fConfiguration 18 }

gs2328fMVRConfiguration                                                      OBJECT IDENTIFIER ::= { gs2328fMVR 1 }

gs2328fMVRMode  OBJECT-TYPE
   SYNTAX      INTEGER { disable(0), enable(1) }
   MAX-ACCESS  read-write
   STATUS      current
   DESCRIPTION
       "Enable/Disable the Global MVR. "
   ::= { gs2328fMVRConfiguration 1 }

gs2328fMVRVLANId  OBJECT-TYPE
   SYNTAX      Integer32(1..4094)
   MAX-ACCESS  read-write
   STATUS      current
   DESCRIPTION
       "Specify the Multicast VLAN ID. "
   ::= { gs2328fMVRConfiguration 2 }

gs2328fMVRPortConfigurationTable OBJECT-TYPE
   SYNTAX      SEQUENCE OF Gs2328fMVRPortConfigurationEntry
   MAX-ACCESS  not-accessible
   STATUS      current
   DESCRIPTION
       " Configure MVR Port Configuration. "
   ::= { gs2328fMVRConfiguration 3 }

gs2328fMVRPortConfigurationEntry OBJECT-TYPE
   SYNTAX      Gs2328fMVRPortConfigurationEntry
   MAX-ACCESS  not-accessible
   STATUS      current
   DESCRIPTION
       ""
   INDEX    { ifIndex  }
   ::= { gs2328fMVRPortConfigurationTable 1 }

Gs2328fMVRPortConfigurationEntry ::= SEQUENCE {
   gs2328fMVRPortConfigurationMode	INTEGER,
   gs2328fMVRPortConfigurationType  	INTEGER,
   gs2328fMVRPortConfigurationImmediateLeave    INTEGER
}

gs2328fMVRPortConfigurationMode OBJECT-TYPE
   SYNTAX      INTEGER { disable(0), enable(1) }
   MAX-ACCESS  read-write
   STATUS      current
   DESCRIPTION
       "Enable MVR on the port. "
   ::= { gs2328fMVRPortConfigurationEntry 1 }

gs2328fMVRPortConfigurationType OBJECT-TYPE
   SYNTAX      INTEGER { receiver(0), source(1) }
   MAX-ACCESS  read-write
   STATUS      current
   DESCRIPTION
       "Specify the MVR port type on the port. "
   ::= { gs2328fMVRPortConfigurationEntry 2 }

gs2328fMVRPortConfigurationImmediateLeave OBJECT-TYPE
   SYNTAX      INTEGER { disable(0), enable(1) }
   MAX-ACCESS  read-write
   STATUS      current
   DESCRIPTION
       "Enable the fast leave on the port. "
   ::= { gs2328fMVRPortConfigurationEntry 3 }


gs2328fMVRPortGroupFiltering                                                      OBJECT IDENTIFIER ::= { gs2328fMVR 2 }

gs2328fMVRPortGroupFilteringCreate OBJECT-TYPE
   SYNTAX       Integer32
   MAX-ACCESS   read-write
   STATUS       current
   DESCRIPTION
       "default: 0
       0 : None  (read only) 1 : Create MLD Snooping Port Group Filtering "
   ::= { gs2328fMVRPortGroupFiltering 1 }

gs2328fMVRPortGroupFilteringTable OBJECT-TYPE
   SYNTAX      SEQUENCE OF Gs2328fMVRPortGroupFilteringEntry
   MAX-ACCESS  not-accessible
   STATUS      current
   DESCRIPTION
       " Configure MVR port group filtering. "
   ::= { gs2328fMVRPortGroupFiltering 2 }

gs2328fMVRPortGroupFilteringEntry OBJECT-TYPE
   SYNTAX      Gs2328fMVRPortGroupFilteringEntry
   MAX-ACCESS  not-accessible
   STATUS      current
   DESCRIPTION
       ""
   INDEX    { gs2328fMVRPortGroupFilteringIndex  }
   ::= { gs2328fMVRPortGroupFilteringTable 1 }

Gs2328fMVRPortGroupFilteringEntry ::= SEQUENCE {
   gs2328fMVRPortGroupFilteringIndex         Integer32,
   gs2328fMVRPortGroupFilteringPort          Integer32,
   gs2328fMVRPortGroupFilteringStartGroups   DisplayString,
   gs2328fMVRPortGroupFilteringEndGroups     DisplayString,
   gs2328fMVRPortGroupFilteringRowStatus     INTEGER
}

gs2328fMVRPortGroupFilteringIndex OBJECT-TYPE
   SYNTAX      Integer32(1..65535)
   MAX-ACCESS  not-accessible
   STATUS      current
   DESCRIPTION
       "MVR Port Group Filtering Configuration Index. "
   ::= { gs2328fMVRPortGroupFilteringEntry 1 }

gs2328fMVRPortGroupFilteringPort OBJECT-TYPE
   SYNTAX      Integer32(1..65535)
   MAX-ACCESS  read-write
   STATUS      current
   DESCRIPTION
       "The logical port for the settings. "
   ::= { gs2328fMVRPortGroupFilteringEntry 2 }

gs2328fMVRPortGroupFilteringStartGroups OBJECT-TYPE
   SYNTAX      DisplayString
   MAX-ACCESS  read-write
   STATUS      current
   DESCRIPTION
       "The IP Multicast Group that will be allowed. "
   ::= { gs2328fMVRPortGroupFilteringEntry 3 }

gs2328fMVRPortGroupFilteringEndGroups OBJECT-TYPE
   SYNTAX      DisplayString
   MAX-ACCESS  read-write
   STATUS      current
   DESCRIPTION
       "The IP Multicast Group that will be allowed. "
   ::= { gs2328fMVRPortGroupFilteringEntry 4 }

gs2328fMVRPortGroupFilteringRowStatus OBJECT-TYPE
   SYNTAX      INTEGER { active(1), notInservice(2), destroy(4)}
   MAX-ACCESS  read-write
   STATUS      current
   DESCRIPTION
       "1: active
        2: notInservice
        4: destroy"
   ::= { gs2328fMVRPortGroupFilteringEntry 5 }

gs2328fMVRGroupsTable OBJECT-TYPE
   SYNTAX      SEQUENCE OF Gs2328fMVRGroupsEntry
   MAX-ACCESS  not-accessible
   STATUS      current
   DESCRIPTION
       "MVR Groups Information . "
   ::= { gs2328fMVR 3 }

gs2328fMVRGroupsEntry OBJECT-TYPE
   SYNTAX      Gs2328fMVRGroupsEntry
   MAX-ACCESS  not-accessible
   STATUS      current
   DESCRIPTION
       ""
   INDEX    { gs2328fMVRGroupsIndex  }
   ::= { gs2328fMVRGroupsTable 1 }

Gs2328fMVRGroupsEntry ::= SEQUENCE {
   gs2328fMVRGroupsIndex          Integer32,
   gs2328fMVRGroupsVLANID         Integer32,
   gs2328fMVRGroups               InetAddress,
   gs2328fMVRGroupsMemberships    DisplayString
}

gs2328fMVRGroupsIndex OBJECT-TYPE
   SYNTAX      Integer32(1..65535)
   MAX-ACCESS  not-accessible
   STATUS      current
   DESCRIPTION
       "MVR Groups Index"
   ::= { gs2328fMVRGroupsEntry 1 }

gs2328fMVRGroupsVLANID OBJECT-TYPE
   SYNTAX      Integer32(1..4095)
   MAX-ACCESS  read-only
   STATUS      current
   DESCRIPTION
       "VLAN ID of the group. "
   ::= { gs2328fMVRGroupsEntry 2 }

gs2328fMVRGroups OBJECT-TYPE
   SYNTAX      DisplayString
   MAX-ACCESS  read-only
   STATUS      current
   DESCRIPTION
       "Group address of the group displayed."
   ::= { gs2328fMVRGroupsEntry 3 }

gs2328fMVRGroupsMemberships OBJECT-TYPE
   SYNTAX      DisplayString
   MAX-ACCESS  read-only
   STATUS      current
   DESCRIPTION
       "Ports under this group."
   ::= { gs2328fMVRGroupsEntry 4 }


gs2328fMVRStatus                                                      OBJECT IDENTIFIER ::= { gs2328fMVR 4 }

gs2328fMVRstatisticClear OBJECT-TYPE
   SYNTAX      INTEGER { none(0), clear(1)}
   MAX-ACCESS  read-write
   STATUS      current
   DESCRIPTION
       "Clears all Statistics counters."
   ::= { gs2328fMVRStatus 1 }

gs2328fMVRstatisticVLANID OBJECT-TYPE
   SYNTAX      Integer32(1..4095)
   MAX-ACCESS  read-only
   STATUS      current
   DESCRIPTION
       "The VLAN ID of the entry. "
   ::= { gs2328fMVRStatus 2 }

gs2328fMVRstatisticV1ReportsReceived OBJECT-TYPE
   SYNTAX      Counter32
   MAX-ACCESS  read-only
   STATUS      current
   DESCRIPTION
       "The number of Received V1 Reports. "
   ::= { gs2328fMVRStatus 3 }

gs2328fMVRstatisticV2ReportsReceived OBJECT-TYPE
   SYNTAX      Counter32
   MAX-ACCESS  read-only
   STATUS      current
   DESCRIPTION
       "The number of Received V2 Reports. "
   ::= { gs2328fMVRStatus 4 }

gs2328fMVRstatisticV3ReportsReceived OBJECT-TYPE
   SYNTAX      Counter32
   MAX-ACCESS  read-only
   STATUS      current
   DESCRIPTION
       "The number of Received V3 Reports. "
   ::= { gs2328fMVRStatus 5 }

gs2328fMVRstatisticV2LeavesReceived OBJECT-TYPE
   SYNTAX      Counter32
   MAX-ACCESS  read-only
   STATUS      current
   DESCRIPTION
       "The number of Received V2 Leaves. "
   ::= { gs2328fMVRStatus 6 }

gs2328fLACP                                                     OBJECT IDENTIFIER ::= { gs2328fConfiguration 19 }

gs2328fLACPConf                                                 OBJECT IDENTIFIER ::= { gs2328fLACP 1 }

gs2328fLACPPortConfigurationTable OBJECT-TYPE
   SYNTAX      SEQUENCE OF Gs2328fLACPPortConfigurationEntry
   MAX-ACCESS  not-accessible
   STATUS      current
   DESCRIPTION
       " "
   ::= { gs2328fLACPConf 1 }

gs2328fLACPPortConfigurationEntry OBJECT-TYPE
   SYNTAX      Gs2328fLACPPortConfigurationEntry
   MAX-ACCESS  not-accessible
   STATUS      current
   DESCRIPTION
       ""
   INDEX    { gs2328fLACPPortConfigurationPort  }
   ::= { gs2328fLACPPortConfigurationTable 1 }

Gs2328fLACPPortConfigurationEntry ::= SEQUENCE {
    gs2328fLACPPortConfigurationPort         Integer32,
    gs2328fLACPPortConfigurationMode         INTEGER,
    gs2328fLACPPortConfigurationKey          Integer32,
    gs2328fLACPPortConfigurationRole         INTEGER
}

gs2328fLACPPortConfigurationPort OBJECT-TYPE
   SYNTAX      Integer32(1..4095)
   MAX-ACCESS  not-accessible
   STATUS      current
   DESCRIPTION
       " "
   ::= { gs2328fLACPPortConfigurationEntry 1 }

gs2328fLACPPortConfigurationMode OBJECT-TYPE
   SYNTAX      INTEGER { disable(0), enable(1) }
   MAX-ACCESS  read-write
   STATUS      current
   DESCRIPTION
       "Enable/Disable LACP Mode."
   ::= { gs2328fLACPPortConfigurationEntry 2 }

gs2328fLACPPortConfigurationKey OBJECT-TYPE
   SYNTAX      Integer32(0..65535)
   MAX-ACCESS  read-write
   STATUS      current
   DESCRIPTION
       "LACP key : 1-65535. 0 : Auto"
   ::= { gs2328fLACPPortConfigurationEntry 3 }

gs2328fLACPPortConfigurationRole OBJECT-TYPE
   SYNTAX      INTEGER { passive(0), active(1) }
   MAX-ACCESS  read-write
   STATUS      current
   DESCRIPTION
       "0 : passive, Listen for LACP packets.
        1 : active, Initiate LACP negotiation, and transmit LACP packets each second"
   ::= { gs2328fLACPPortConfigurationEntry 4 }

gs2328fLACPSystemStatusTable OBJECT-TYPE
   SYNTAX      SEQUENCE OF Gs2328fLACPSystemStatusEntry
   MAX-ACCESS  not-accessible
   STATUS      current
   DESCRIPTION
       " "
   ::= { gs2328fLACP 2 }

gs2328fLACPSystemStatusEntry OBJECT-TYPE
   SYNTAX      Gs2328fLACPSystemStatusEntry
   MAX-ACCESS  not-accessible
   STATUS      current
   DESCRIPTION
       ""
   INDEX    { gs2328fLACPSystemStatusIndex  }
   ::= { gs2328fLACPSystemStatusTable 1 }

Gs2328fLACPSystemStatusEntry ::= SEQUENCE {
   gs2328fLACPSystemStatusIndex             Integer32,
   gs2328fLACPSystemStatusAggrID            DisplayString,
   gs2328fLACPSystemStatusPartnerSystemID   MacAddress,
   gs2328fLACPSystemStatusPartnerKey        DisplayString,
   gs2328fLACPSystemStatusLastchanged       DisplayString,
   gs2328fLACPSystemStatusLocalPorts        DisplayString
}

gs2328fLACPSystemStatusIndex OBJECT-TYPE
   SYNTAX      Integer32(1..12)
   MAX-ACCESS  not-accessible
   STATUS      current
   DESCRIPTION
       " "
   ::= { gs2328fLACPSystemStatusEntry 1 }

gs2328fLACPSystemStatusAggrID OBJECT-TYPE
   SYNTAX      DisplayString
   MAX-ACCESS  read-only
   STATUS      current
   DESCRIPTION
       "The Aggregation ID associated with this aggregation instance."
   ::= { gs2328fLACPSystemStatusEntry 2 }

gs2328fLACPSystemStatusPartnerSystemID OBJECT-TYPE
   SYNTAX      MacAddress
   MAX-ACCESS  read-only
   STATUS      current
   DESCRIPTION
       "The system ID (MAC address) of the aggregation partner."
   ::= { gs2328fLACPSystemStatusEntry 3 }

gs2328fLACPSystemStatusPartnerKey OBJECT-TYPE
   SYNTAX      DisplayString
   MAX-ACCESS  read-only
   STATUS      current
   DESCRIPTION
       " The Key that the partner has assigned to this aggregation ID. "
   ::= { gs2328fLACPSystemStatusEntry 4 }

gs2328fLACPSystemStatusLastchanged OBJECT-TYPE
   SYNTAX      DisplayString
   MAX-ACCESS  read-only
   STATUS      current
   DESCRIPTION
       " The time since this aggregation changed. "
   ::= { gs2328fLACPSystemStatusEntry 5 }

gs2328fLACPSystemStatusLocalPorts OBJECT-TYPE
   SYNTAX      DisplayString
   MAX-ACCESS  read-only
   STATUS      current
   DESCRIPTION
       " Shows which ports are a part of this aggregation for this switch. "
   ::= { gs2328fLACPSystemStatusEntry 6 }

gs2328fLACPStatusTable OBJECT-TYPE
   SYNTAX      SEQUENCE OF Gs2328fLACPStatusEntry
   MAX-ACCESS  not-accessible
   STATUS      current
   DESCRIPTION
       " "
   ::= { gs2328fLACP 3 }

gs2328fLACPStatusEntry OBJECT-TYPE
   SYNTAX      Gs2328fLACPStatusEntry
   MAX-ACCESS  not-accessible
   STATUS      current
   DESCRIPTION
       ""
   INDEX    { gs2328fLACPStatusPort  }
   ::= { gs2328fLACPStatusTable 1 }

Gs2328fLACPStatusEntry ::= SEQUENCE {
   gs2328fLACPStatusPort                Integer32,
   gs2328fLACPStatusLACP                DisplayString,
   gs2328fLACPStatusKey                 DisplayString,
   gs2328fLACPStatusAggrID              DisplayString,
   gs2328fLACPStatusPartnerSystemID     DisplayString,
   gs2328fLACPStatusPartnerPort         DisplayString
}

gs2328fLACPStatusPort OBJECT-TYPE
   SYNTAX      Integer32(1..4095)
   MAX-ACCESS  not-accessible
   STATUS      current
   DESCRIPTION
       " "
   ::= { gs2328fLACPStatusEntry 1 }

gs2328fLACPStatusLACP OBJECT-TYPE
   SYNTAX      DisplayString
   MAX-ACCESS  read-only
   STATUS      current
   DESCRIPTION
       "Enabled means that LACP is enabled and the port link is up.
        Disabled means that LACP is not enabled or that the port link is down.
        Backup means that the port could not join the aggregation group but will join if other port leaves.
        Meanwhile it's LACP status is disabled."
   ::= { gs2328fLACPStatusEntry 2 }

gs2328fLACPStatusKey OBJECT-TYPE
   SYNTAX      DisplayString
   MAX-ACCESS  read-only
   STATUS      current
   DESCRIPTION
       "The key assigned to this port. Only ports with the same key can aggregate together."
   ::= { gs2328fLACPStatusEntry 3 }

gs2328fLACPStatusAggrID	 OBJECT-TYPE
   SYNTAX      DisplayString
   MAX-ACCESS  read-only
   STATUS      current
   DESCRIPTION
       " The Aggregation ID assigned to this aggregation group. "
   ::= { gs2328fLACPStatusEntry 4 }

gs2328fLACPStatusPartnerSystemID OBJECT-TYPE
   SYNTAX      DisplayString
   MAX-ACCESS  read-only
   STATUS      current
   DESCRIPTION
       " The partner's System ID. "
   ::= { gs2328fLACPStatusEntry 5 }

gs2328fLACPStatusPartnerPort OBJECT-TYPE
   SYNTAX      DisplayString
   MAX-ACCESS  read-only
   STATUS      current
   DESCRIPTION
       " The partner's port number connected to this port. "
   ::= { gs2328fLACPStatusEntry 6 }


gs2328fLACPStatisticsTable OBJECT-TYPE
   SYNTAX      SEQUENCE OF Gs2328fLACPStatisticsEntry
   MAX-ACCESS  not-accessible
   STATUS      current
   DESCRIPTION
       " "
   ::= { gs2328fLACP 4 }

gs2328fLACPStatisticsEntry OBJECT-TYPE
   SYNTAX      Gs2328fLACPStatisticsEntry
   MAX-ACCESS  not-accessible
   STATUS      current
   DESCRIPTION
       ""
   INDEX    { gs2328fLACPStatisticsPort  }
   ::= { gs2328fLACPStatisticsTable 1 }

Gs2328fLACPStatisticsEntry ::= SEQUENCE {
   gs2328fLACPStatisticsPort        Integer32,
   gs2328fLACPReceived              Counter32,
   gs2328fLACPTransmitted           Counter32,
   gs2328fLACPDiscardedUnknown      Counter32,
   gs2328fLACPDiscardedIllegal      Counter32
}

gs2328fLACPStatisticsPort OBJECT-TYPE
   SYNTAX      Integer32(1..4095)
   MAX-ACCESS  not-accessible
   STATUS      current
   DESCRIPTION
       " "
   ::= { gs2328fLACPStatisticsEntry 1 }

gs2328fLACPReceived OBJECT-TYPE
   SYNTAX      Counter32
   MAX-ACCESS  read-only
   STATUS      current
   DESCRIPTION
       "Shows how many LACP frames have been received at each port. "
   ::= { gs2328fLACPStatisticsEntry 2 }

gs2328fLACPTransmitted OBJECT-TYPE
   SYNTAX      Counter32
   MAX-ACCESS  read-only
   STATUS      current
   DESCRIPTION
       " Shows how many LACP frames have been sent from each port. "
   ::= { gs2328fLACPStatisticsEntry 3 }

gs2328fLACPDiscardedUnknown OBJECT-TYPE
   SYNTAX      Counter32
   MAX-ACCESS  read-only
   STATUS      current
   DESCRIPTION
       " Shows how many unknown LACP frames have been discarded at each port. "
   ::= { gs2328fLACPStatisticsEntry 4 }

gs2328fLACPDiscardedIllegal OBJECT-TYPE
   SYNTAX      Counter32
   MAX-ACCESS  read-only
   STATUS      current
   DESCRIPTION
       " Shows how many illegal LACP frames have been discarded at each port. "
   ::= { gs2328fLACPStatisticsEntry 5 }

gs2328fLACPStatisticsClear OBJECT-TYPE
   SYNTAX      INTEGER { none(0), clear(1) }
   MAX-ACCESS  read-write
   STATUS      current
   DESCRIPTION
       "default: 0
       0: none
       1: clear"
   ::= { gs2328fLACP 5 }

gs2328fSTP                                                     OBJECT IDENTIFIER ::= { gs2328fConfiguration 20 }

gs2328fSTPBridgeBasicConf                                                 OBJECT IDENTIFIER ::= { gs2328fSTP 1 }

gs2328fSTPBridgeProtocolVersion OBJECT-TYPE
   SYNTAX      INTEGER { stp(0), rstp(2), mstp(3) }
   MAX-ACCESS  read-write
   STATUS      current
   DESCRIPTION
       "default: 3,
       0: stp
       2: rstp
       3: mstp"
   ::= { gs2328fSTPBridgeBasicConf 1 }

gs2328fSTPBridgePriority OBJECT-TYPE
   SYNTAX      Integer32(0..61440)
   MAX-ACCESS  read-write
   STATUS      current
   DESCRIPTION
       " default: 32768,
       STP bridge priority (0/4096/8192/12288/16384/20480/24576/28672/32768/36864/40960/45056/49152/53248/57344/61440)"
   ::= { gs2328fSTPBridgeBasicConf 2 }

gs2328fSTPBridgeForwardDelay OBJECT-TYPE
   SYNTAX      Integer32(4..30)
   MAX-ACCESS  read-write
   STATUS      current
   DESCRIPTION
       " Forward Delay default: 15, range: 4 - 30.
         MaxAge must be <= (FwdDelay-1)*2."
   ::= { gs2328fSTPBridgeBasicConf 3 }

gs2328fSTPBridgeMaxAge OBJECT-TYPE
   SYNTAX      Integer32(6..40)
   MAX-ACCESS  read-write
   STATUS      current
   DESCRIPTION
       " Max Age default: 20, range: 6 - 40.
         MaxAge must be <= (FwdDelay-1)*2"
   ::= { gs2328fSTPBridgeBasicConf 4 }

gs2328fSTPBridgeMaximumHopCount OBJECT-TYPE
   SYNTAX      Integer32(6..40)
   MAX-ACCESS  read-write
   STATUS      current
   DESCRIPTION
       " Maximum Hop Count default: 20, range: 6 - 40."
   ::= { gs2328fSTPBridgeBasicConf 5 }

gs2328fSTPBridgeTransmitHoldCount OBJECT-TYPE
   SYNTAX      Integer32(1..10)
   MAX-ACCESS  read-write
   STATUS      current
   DESCRIPTION
       " Transmit Hold Count default: 6, range: 1 - 10."
   ::= { gs2328fSTPBridgeBasicConf 6 }

gs2328fSTPBridgeAdvancedConf                                                 OBJECT IDENTIFIER ::= { gs2328fSTP 2 }

gs2328fSTPBridgeEdgePortBPDUFiltering OBJECT-TYPE
   SYNTAX      INTEGER { disable(0), enable(1) }
   MAX-ACCESS  read-write
   STATUS      current
   DESCRIPTION
       " default: 0,
        0: disable
        1: enable"
   ::= { gs2328fSTPBridgeAdvancedConf 1 }

gs2328fSTPBridgeEdgePortBPDUGuard OBJECT-TYPE
   SYNTAX      INTEGER { disable(0), enable(1) }
   MAX-ACCESS  read-write
   STATUS      current
   DESCRIPTION
       " default: 0,
        0: disable
        1: enable"
   ::= { gs2328fSTPBridgeAdvancedConf 2 }

gs2328fSTPBridgePortErrorRecoveryTimeout OBJECT-TYPE
   SYNTAX      Integer32(0..86400)
   MAX-ACCESS  read-write
   STATUS      current
   DESCRIPTION
       " Port Error Recovery Timeout disable: 0, range: 30 - 86400."
   ::= { gs2328fSTPBridgeAdvancedConf 3 }

gs2328fSTPMSTIConf                                                 OBJECT IDENTIFIER ::= { gs2328fSTP 3 }

gs2328fSTPMSTIConfigurationName OBJECT-TYPE
   SYNTAX      DisplayString (SIZE (1..32))
   MAX-ACCESS  read-write
   STATUS      current
   DESCRIPTION
       "A text string up to 32 characters long."
   ::= { gs2328fSTPMSTIConf 1 }

gs2328fSTPMSTIConfigurationRevision   OBJECT-TYPE
   SYNTAX      Integer32(0..65535)
   MAX-ACCESS  read-write
   STATUS      current
   DESCRIPTION
       " Configuration Revision default: 0, range: 0 - 65535."
   ::= { gs2328fSTPMSTIConf 2 }

gs2328fSTPMSTIMappingConf                                                 OBJECT IDENTIFIER ::= { gs2328fSTP 4 }

gs2328fSTPMSTI1VLANsMapped OBJECT-TYPE
   SYNTAX      DisplayString (SIZE (1..4096))
   MAX-ACCESS  read-write
   STATUS      current
   DESCRIPTION
       "The list of VLANs mapped to the MSTI1.
       The VLANs must be separated with comma or space.
       An unused MSTI should just be left empty. "
   ::= { gs2328fSTPMSTIMappingConf 1 }

gs2328fSTPMSTI2VLANsMapped OBJECT-TYPE
   SYNTAX      DisplayString (SIZE (1..4096))
   MAX-ACCESS  read-write
   STATUS      current
   DESCRIPTION
       "The list of VLANs mapped to the MSTI2.
       The VLANs must be separated with comma or space.
       An unused MSTI should just be left empty. "
   ::= { gs2328fSTPMSTIMappingConf 2 }

gs2328fSTPMSTI3VLANsMapped OBJECT-TYPE
   SYNTAX      DisplayString (SIZE (1..4096))
   MAX-ACCESS  read-write
   STATUS      current
   DESCRIPTION
       "The list of VLANs mapped to the MSTI3.
       The VLANs must be separated with comma or space.
       An unused MSTI should just be left empty. "
   ::= { gs2328fSTPMSTIMappingConf 3 }

gs2328fSTPMSTI4VLANsMapped OBJECT-TYPE
   SYNTAX      DisplayString (SIZE (1..4096))
   MAX-ACCESS  read-write
   STATUS      current
   DESCRIPTION
       "The list of VLANs mapped to the MSTI4.
       The VLANs must be separated with comma or space.
       An unused MSTI should just be left empty. "
   ::= { gs2328fSTPMSTIMappingConf 4 }

gs2328fSTPMSTI5VLANsMapped OBJECT-TYPE
   SYNTAX      DisplayString (SIZE (1..4096))
   MAX-ACCESS  read-write
   STATUS      current
   DESCRIPTION
       "The list of VLANs mapped to the MSTI5.
       The VLANs must be separated with comma or space.
       An unused MSTI should just be left empty. "
   ::= { gs2328fSTPMSTIMappingConf 5 }

gs2328fSTPMSTI6VLANsMapped OBJECT-TYPE
   SYNTAX      DisplayString (SIZE (1..4096))
   MAX-ACCESS  read-write
   STATUS      current
   DESCRIPTION
       "The list of VLANs mapped to the MSTI6.
       The VLANs must be separated with comma or space.
       An unused MSTI should just be left empty. "
   ::= { gs2328fSTPMSTIMappingConf 6 }

gs2328fSTPMSTI7VLANsMapped OBJECT-TYPE
   SYNTAX      DisplayString (SIZE (1..4096))
   MAX-ACCESS  read-write
   STATUS      current
   DESCRIPTION
       "The list of VLANs mapped to the MSTI7.
       The VLANs must be separated with comma or space.
       An unused MSTI should just be left empty. "
   ::= { gs2328fSTPMSTIMappingConf 7 }

gs2328fSTPMSTIPriority                                                 OBJECT IDENTIFIER ::= { gs2328fSTP 5 }

gs2328fSTPCISTPriority OBJECT-TYPE
   SYNTAX      Integer32(0..61440)
   MAX-ACCESS  read-write
   STATUS      current
   DESCRIPTION
       " default: 32768,
       STP CIST priority (0/4096/8192/12288/16384/20480/24576/28672/32768/36864/40960/45056/49152/53248/57344/61440)"
   ::= { gs2328fSTPMSTIPriority 1 }

gs2328fSTPMSTI1Priority OBJECT-TYPE
   SYNTAX      Integer32(0..61440)
   MAX-ACCESS  read-write
   STATUS      current
   DESCRIPTION
       " default: 32768,
       STP CIST priority (0/4096/8192/12288/16384/20480/24576/28672/32768/36864/40960/45056/49152/53248/57344/61440)"
   ::= { gs2328fSTPMSTIPriority 2 }

gs2328fSTPMSTI2Priority OBJECT-TYPE
   SYNTAX      Integer32(0..61440)
   MAX-ACCESS  read-write
   STATUS      current
   DESCRIPTION
       " default: 32768,
       STP CIST priority (0/4096/8192/12288/16384/20480/24576/28672/32768/36864/40960/45056/49152/53248/57344/61440)"
   ::= { gs2328fSTPMSTIPriority 3 }

gs2328fSTPMSTI3Priority OBJECT-TYPE
   SYNTAX      Integer32(0..61440)
   MAX-ACCESS  read-write
   STATUS      current
   DESCRIPTION
       " default: 32768,
       STP CIST priority (0/4096/8192/12288/16384/20480/24576/28672/32768/36864/40960/45056/49152/53248/57344/61440)"
   ::= { gs2328fSTPMSTIPriority 4 }

gs2328fSTPMSTI4Priority OBJECT-TYPE
   SYNTAX      Integer32(0..61440)
   MAX-ACCESS  read-write
   STATUS      current
   DESCRIPTION
       " default: 32768,
       STP CIST priority (0/4096/8192/12288/16384/20480/24576/28672/32768/36864/40960/45056/49152/53248/57344/61440)"
   ::= { gs2328fSTPMSTIPriority 5 }

gs2328fSTPMSTI5Priority OBJECT-TYPE
   SYNTAX      Integer32(0..61440)
   MAX-ACCESS  read-write
   STATUS      current
   DESCRIPTION
       " default: 32768,
       STP CIST priority (0/4096/8192/12288/16384/20480/24576/28672/32768/36864/40960/45056/49152/53248/57344/61440)"
   ::= { gs2328fSTPMSTIPriority 6 }

gs2328fSTPMSTI6Priority OBJECT-TYPE
   SYNTAX      Integer32(0..61440)
   MAX-ACCESS  read-write
   STATUS      current
   DESCRIPTION
       " default: 32768,
       STP CIST priority (0/4096/8192/12288/16384/20480/24576/28672/32768/36864/40960/45056/49152/53248/57344/61440)"
   ::= { gs2328fSTPMSTIPriority 7 }

gs2328fSTPMSTI7Priority OBJECT-TYPE
   SYNTAX      Integer32(0..61440)
   MAX-ACCESS  read-write
   STATUS      current
   DESCRIPTION
       " default: 32768,
       STP CIST priority (0/4096/8192/12288/16384/20480/24576/28672/32768/36864/40960/45056/49152/53248/57344/61440)"
   ::= { gs2328fSTPMSTIPriority 8 }

gs2328fSTPCISTPort                                                          OBJECT IDENTIFIER ::= { gs2328fSTP 6 }

gs2328fSTPCISTAggregatedPort                                                OBJECT IDENTIFIER ::= { gs2328fSTPCISTPort 1 }

gs2328fSTPCISTAggregatedPortSTPEnabled OBJECT-TYPE
   SYNTAX      INTEGER { disable(0), enable(1) }
   MAX-ACCESS  read-write
   STATUS      current
   DESCRIPTION
       " default: 0,
        0: disable
        1: enable"
   ::= { gs2328fSTPCISTAggregatedPort 1 }

gs2328fSTPCISTAggregatedPortPathCost OBJECT-TYPE
   SYNTAX      Integer32(0..200000000)
   MAX-ACCESS  read-write
   STATUS      current
   DESCRIPTION
       " Auto: 0,
        Specific Path Cost range: 1 - 200000000."
   ::= { gs2328fSTPCISTAggregatedPort 2 }

gs2328fSTPCISTAggregatedPortPriority OBJECT-TYPE
   SYNTAX      Integer32(0..240)
   MAX-ACCESS  read-write
   STATUS      current
   DESCRIPTION
       " default: 128,
       CIST Aggregated Port Priority (0/16/32/48/64/80/96/112/128/144/160/176/192/208/224/240)"
   ::= { gs2328fSTPCISTAggregatedPort 3 }

gs2328fSTPCISTAggregatedPortAdminEdge OBJECT-TYPE
   SYNTAX      INTEGER { non-edge(0), edge(1) }
   MAX-ACCESS  read-write
   STATUS      current
   DESCRIPTION
       " default: 0,
        0: non-edge
        1: edge"
   ::= { gs2328fSTPCISTAggregatedPort 4 }

gs2328fSTPCISTAggregatedPortAutoEdge OBJECT-TYPE
   SYNTAX      INTEGER { disable(0), enable(1) }
   MAX-ACCESS  read-write
   STATUS      current
   DESCRIPTION
       " default: 1,
        0: disable
        1: enable"
   ::= { gs2328fSTPCISTAggregatedPort 5 }

gs2328fSTPCISTAggregatedPortRestrictedRole OBJECT-TYPE
   SYNTAX      INTEGER { disable(0), enable(1) }
   MAX-ACCESS  read-write
   STATUS      current
   DESCRIPTION
       " default: 0,
        0: disable
        1: enable"
   ::= { gs2328fSTPCISTAggregatedPort 6 }

gs2328fSTPCISTAggregatedPortRestrictedTCN OBJECT-TYPE
   SYNTAX      INTEGER { disable(0), enable(1) }
   MAX-ACCESS  read-write
   STATUS      current
   DESCRIPTION
       " default: 0,
        0: disable
        1: enable"
   ::= { gs2328fSTPCISTAggregatedPort 7 }

gs2328fSTPCISTAggregatedPortBPDUGuard OBJECT-TYPE
   SYNTAX      INTEGER { disable(0), enable(1) }
   MAX-ACCESS  read-write
   STATUS      current
   DESCRIPTION
       " default: 0,
        0: disable
        1: enable"
   ::= { gs2328fSTPCISTAggregatedPort 8 }

gs2328fSTPCISTAggregatedPortPointtoPoint OBJECT-TYPE
   SYNTAX      INTEGER { forcetrue(0), forcefalse(1), auto(2) }
   MAX-ACCESS  read-write
   STATUS      current
   DESCRIPTION
       " default: 0,
        0: Forced True
        1: Forced False
        2: Auto"
   ::= { gs2328fSTPCISTAggregatedPort 9 }

gs2328fSTPCISTNormalPortTable OBJECT-TYPE
   SYNTAX      SEQUENCE OF Gs2328fSTPCISTNormalPortEntry
   MAX-ACCESS  not-accessible
   STATUS      current
   DESCRIPTION
       " Show CIST Normal Port Configurations. "
   ::= { gs2328fSTPCISTPort 2 }

gs2328fSTPCISTNormalPortEntry OBJECT-TYPE
   SYNTAX      Gs2328fSTPCISTNormalPortEntry
   MAX-ACCESS  not-accessible
   STATUS      current
   DESCRIPTION
       ""
   INDEX    { gs2328fSTPCISTNormalPortConfPort  }
   ::= { gs2328fSTPCISTNormalPortTable 1 }

Gs2328fSTPCISTNormalPortEntry ::= SEQUENCE {
   gs2328fSTPCISTNormalPortConfPort         Integer32,
   gs2328fSTPCISTNormalPortSTPEnabled       INTEGER,
   gs2328fSTPCISTNormalPortPathCost         Integer32,
   gs2328fSTPCISTNormalPortPriority         Integer32,
   gs2328fSTPCISTNormalPortAdminEdge        INTEGER,
   gs2328fSTPCISTNormalPortAutoEdge         INTEGER,
   gs2328fSTPCISTNormalPortRestrictedRole   INTEGER,
   gs2328fSTPCISTNormalPortRestrictedTCN    INTEGER,
   gs2328fSTPCISTNormalPortBPDUGuard        INTEGER,
   gs2328fSTPCISTNormalPortPointtoPoint     INTEGER
}

gs2328fSTPCISTNormalPortConfPort OBJECT-TYPE
   SYNTAX      Integer32(1..4095)
   MAX-ACCESS  not-accessible
   STATUS      current
   DESCRIPTION
       " port, range : 1 - port number. "
   ::= { gs2328fSTPCISTNormalPortEntry 1 }

gs2328fSTPCISTNormalPortSTPEnabled OBJECT-TYPE
   SYNTAX      INTEGER { disable(0), enable(1) }
   MAX-ACCESS  read-write
   STATUS      current
   DESCRIPTION
       " default: 0,
        0: disable
        1: enable"
   ::= { gs2328fSTPCISTNormalPortEntry 2 }

gs2328fSTPCISTNormalPortPathCost OBJECT-TYPE
   SYNTAX      Integer32(0..200000000)
   MAX-ACCESS  read-write
   STATUS      current
   DESCRIPTION
       " Auto: 0,
        Specific Path Cost range: 1 - 200000000."
   ::= { gs2328fSTPCISTNormalPortEntry 3 }

gs2328fSTPCISTNormalPortPriority OBJECT-TYPE
   SYNTAX      Integer32(0..240)
   MAX-ACCESS  read-write
   STATUS      current
   DESCRIPTION
       " default: 128,
       CIST Aggregated Port Priority (0/16/32/48/64/80/96/112/128/144/160/176/192/208/224/240)"
   ::= { gs2328fSTPCISTNormalPortEntry 4 }

gs2328fSTPCISTNormalPortAdminEdge OBJECT-TYPE
   SYNTAX      INTEGER { non-edge(0), edge(1) }
   MAX-ACCESS  read-write
   STATUS      current
   DESCRIPTION
       " default: 0,
        0: non-edge
        1: edge"
   ::= { gs2328fSTPCISTNormalPortEntry 5 }

gs2328fSTPCISTNormalPortAutoEdge OBJECT-TYPE
   SYNTAX      INTEGER { disable(0), enable(1) }
   MAX-ACCESS  read-write
   STATUS      current
   DESCRIPTION
       " default: 1,
        0: disable
        1: enable"
   ::= { gs2328fSTPCISTNormalPortEntry 6 }

gs2328fSTPCISTNormalPortRestrictedRole OBJECT-TYPE
   SYNTAX      INTEGER { disable(0), enable(1) }
   MAX-ACCESS  read-write
   STATUS      current
   DESCRIPTION
       " default: 0,
        0: disable
        1: enable"
   ::= { gs2328fSTPCISTNormalPortEntry 7 }

gs2328fSTPCISTNormalPortRestrictedTCN OBJECT-TYPE
   SYNTAX      INTEGER { disable(0), enable(1) }
   MAX-ACCESS  read-write
   STATUS      current
   DESCRIPTION
       " default: 0,
        0: disable
        1: enable"
   ::= { gs2328fSTPCISTNormalPortEntry 8 }

gs2328fSTPCISTNormalPortBPDUGuard OBJECT-TYPE
   SYNTAX      INTEGER { disable(0), enable(1) }
   MAX-ACCESS  read-write
   STATUS      current
   DESCRIPTION
       " default: 0,
        0: disable
        1: enable"
   ::= { gs2328fSTPCISTNormalPortEntry 9 }

gs2328fSTPCISTNormalPortPointtoPoint OBJECT-TYPE
   SYNTAX      INTEGER { forcetrue(0), forcefalse(1), auto(2) }
   MAX-ACCESS  read-write
   STATUS      current
   DESCRIPTION
       " default: 2,
        0: Forced True
        1: Forced False
        2: Auto"
   ::= { gs2328fSTPCISTNormalPortEntry 10 }


gs2328fSTPMSTIPort                                                          OBJECT IDENTIFIER ::= { gs2328fSTP 7 }

gs2328fSTPMSTI1Port                                                         OBJECT IDENTIFIER ::= { gs2328fSTPMSTIPort 1 }

gs2328fSTPMSTI1AggregatedPort                                                OBJECT IDENTIFIER ::= { gs2328fSTPMSTI1Port 1 }

gs2328fSTPMSTI1AggregatedPortPathCost OBJECT-TYPE
   SYNTAX      Integer32(0..200000000)
   MAX-ACCESS  read-write
   STATUS      current
   DESCRIPTION
       " Auto: 0,
        Specific Path Cost range: 1 - 200000000."
   ::= { gs2328fSTPMSTI1AggregatedPort 1 }

gs2328fSTPMSTI1AggregatedPortPriority OBJECT-TYPE
   SYNTAX      Integer32(0..240)
   MAX-ACCESS  read-write
   STATUS      current
   DESCRIPTION
       " default: 128,
       Aggregated Port Priority (0/16/32/48/64/80/96/112/128/144/160/176/192/208/224/240)"
   ::= { gs2328fSTPMSTI1AggregatedPort 2 }

gs2328fSTPMSTI1NormalPortTable OBJECT-TYPE
   SYNTAX      SEQUENCE OF Gs2328fSTPMSTI1NormalPortEntry
   MAX-ACCESS  not-accessible
   STATUS      current
   DESCRIPTION
       " Show MSTI1 Normal Port Configurations. "
   ::= { gs2328fSTPMSTI1Port 2 }

gs2328fSTPMSTI1NormalPortEntry OBJECT-TYPE
   SYNTAX      Gs2328fSTPMSTI1NormalPortEntry
   MAX-ACCESS  not-accessible
   STATUS      current
   DESCRIPTION
       ""
   INDEX    { gs2328fSTPMSTI1NormalPortConfPort  }
   ::= { gs2328fSTPMSTI1NormalPortTable 1 }

Gs2328fSTPMSTI1NormalPortEntry ::= SEQUENCE {
   gs2328fSTPMSTI1NormalPortConfPort         Integer32,
   gs2328fSTPMSTI1NormalPortPathCost         Integer32,
   gs2328fSTPMSTI1NormalPortPriority         Integer32
}

gs2328fSTPMSTI1NormalPortConfPort OBJECT-TYPE
   SYNTAX      Integer32(1..4095)
   MAX-ACCESS  not-accessible
   STATUS      current
   DESCRIPTION
       " port, range : 1 - port number. "
   ::= { gs2328fSTPMSTI1NormalPortEntry 1 }

gs2328fSTPMSTI1NormalPortPathCost OBJECT-TYPE
   SYNTAX      Integer32(0..200000000)
   MAX-ACCESS  read-write
   STATUS      current
   DESCRIPTION
       " Auto: 0,
        Specific Path Cost range: 1 - 200000000."
   ::= { gs2328fSTPMSTI1NormalPortEntry 2 }

gs2328fSTPMSTI1NormalPortPriority OBJECT-TYPE
   SYNTAX      Integer32(0..240)
   MAX-ACCESS  read-write
   STATUS      current
   DESCRIPTION
       " default: 128,
       Aggregated Port Priority (0/16/32/48/64/80/96/112/128/144/160/176/192/208/224/240)"
   ::= { gs2328fSTPMSTI1NormalPortEntry 3 }

gs2328fSTPMSTI2Port                                                          OBJECT IDENTIFIER ::= { gs2328fSTPMSTIPort 2 }

gs2328fSTPMSTI2AggregatedPort                                                OBJECT IDENTIFIER ::= { gs2328fSTPMSTI2Port 1 }

gs2328fSTPMSTI2AggregatedPortPathCost OBJECT-TYPE
   SYNTAX      Integer32(0..200000000)
   MAX-ACCESS  read-write
   STATUS      current
   DESCRIPTION
       " Auto: 0,
        Specific Path Cost range: 1 - 200000000."
   ::= { gs2328fSTPMSTI2AggregatedPort 1 }

gs2328fSTPMSTI2AggregatedPortPriority OBJECT-TYPE
   SYNTAX      Integer32(0..240)
   MAX-ACCESS  read-write
   STATUS      current
   DESCRIPTION
       " default: 128,
       Aggregated Port Priority (0/16/32/48/64/80/96/112/128/144/160/176/192/208/224/240)"
   ::= { gs2328fSTPMSTI2AggregatedPort 2 }

gs2328fSTPMSTI2NormalPortTable OBJECT-TYPE
   SYNTAX      SEQUENCE OF Gs2328fSTPMSTI2NormalPortEntry
   MAX-ACCESS  not-accessible
   STATUS      current
   DESCRIPTION
       " Show MSTI2 Normal Port Configurations. "
   ::= { gs2328fSTPMSTI2Port 2 }

gs2328fSTPMSTI2NormalPortEntry OBJECT-TYPE
   SYNTAX      Gs2328fSTPMSTI2NormalPortEntry
   MAX-ACCESS  not-accessible
   STATUS      current
   DESCRIPTION
       ""
   INDEX    { gs2328fSTPMSTI2NormalPortConfPort  }
   ::= { gs2328fSTPMSTI2NormalPortTable 1 }

Gs2328fSTPMSTI2NormalPortEntry ::= SEQUENCE {
   gs2328fSTPMSTI2NormalPortConfPort         Integer32,
   gs2328fSTPMSTI2NormalPortPathCost         Integer32,
   gs2328fSTPMSTI2NormalPortPriority         Integer32
}

gs2328fSTPMSTI2NormalPortConfPort OBJECT-TYPE
   SYNTAX      Integer32(1..4095)
   MAX-ACCESS  not-accessible
   STATUS      current
   DESCRIPTION
       " port, range : 1 - port number. "
   ::= { gs2328fSTPMSTI2NormalPortEntry 1 }

gs2328fSTPMSTI2NormalPortPathCost OBJECT-TYPE
   SYNTAX      Integer32(0..200000000)
   MAX-ACCESS  read-write
   STATUS      current
   DESCRIPTION
       " Auto: 0,
        Specific Path Cost range: 1 - 200000000."
   ::= { gs2328fSTPMSTI2NormalPortEntry 2 }

gs2328fSTPMSTI2NormalPortPriority OBJECT-TYPE
   SYNTAX      Integer32(0..240)
   MAX-ACCESS  read-write
   STATUS      current
   DESCRIPTION
       " default: 128,
       Aggregated Port Priority (0/16/32/48/64/80/96/112/128/144/160/176/192/208/224/240)"
   ::= { gs2328fSTPMSTI2NormalPortEntry 3 }

gs2328fSTPMSTI3Port                                                          OBJECT IDENTIFIER ::= { gs2328fSTPMSTIPort 3 }

gs2328fSTPMSTI3AggregatedPort                                                OBJECT IDENTIFIER ::= { gs2328fSTPMSTI3Port 1 }

gs2328fSTPMSTI3AggregatedPortPathCost OBJECT-TYPE
   SYNTAX      Integer32(0..200000000)
   MAX-ACCESS  read-write
   STATUS      current
   DESCRIPTION
       " Auto: 0,
        Specific Path Cost range: 1 - 200000000."
   ::= { gs2328fSTPMSTI3AggregatedPort 1 }

gs2328fSTPMSTI3AggregatedPortPriority OBJECT-TYPE
   SYNTAX      Integer32(0..240)
   MAX-ACCESS  read-write
   STATUS      current
   DESCRIPTION
       " default: 128,
       Aggregated Port Priority (0/16/32/48/64/80/96/112/128/144/160/176/192/208/224/240)"
   ::= { gs2328fSTPMSTI3AggregatedPort 2 }

gs2328fSTPMSTI3NormalPortTable OBJECT-TYPE
   SYNTAX      SEQUENCE OF Gs2328fSTPMSTI3NormalPortEntry
   MAX-ACCESS  not-accessible
   STATUS      current
   DESCRIPTION
       " Show MSTI3 Normal Port Configurations. "
   ::= { gs2328fSTPMSTI3Port 2 }

gs2328fSTPMSTI3NormalPortEntry OBJECT-TYPE
   SYNTAX      Gs2328fSTPMSTI3NormalPortEntry
   MAX-ACCESS  not-accessible
   STATUS      current
   DESCRIPTION
       ""
   INDEX    { gs2328fSTPMSTI3NormalPortConfPort  }
   ::= { gs2328fSTPMSTI3NormalPortTable 1 }

Gs2328fSTPMSTI3NormalPortEntry ::= SEQUENCE {
   gs2328fSTPMSTI3NormalPortConfPort         Integer32,
   gs2328fSTPMSTI3NormalPortPathCost         Integer32,
   gs2328fSTPMSTI3NormalPortPriority         Integer32
}

gs2328fSTPMSTI3NormalPortConfPort OBJECT-TYPE
   SYNTAX      Integer32(1..4095)
   MAX-ACCESS  not-accessible
   STATUS      current
   DESCRIPTION
       " port, range : 1 - port number. "
   ::= { gs2328fSTPMSTI3NormalPortEntry 1 }

gs2328fSTPMSTI3NormalPortPathCost OBJECT-TYPE
   SYNTAX      Integer32(0..200000000)
   MAX-ACCESS  read-write
   STATUS      current
   DESCRIPTION
       " Auto: 0,
        Specific Path Cost range: 1 - 200000000."
   ::= { gs2328fSTPMSTI3NormalPortEntry 2 }

gs2328fSTPMSTI3NormalPortPriority OBJECT-TYPE
   SYNTAX      Integer32(0..240)
   MAX-ACCESS  read-write
   STATUS      current
   DESCRIPTION
       " default: 128,
       Aggregated Port Priority (0/16/32/48/64/80/96/112/128/144/160/176/192/208/224/240)"
   ::= { gs2328fSTPMSTI3NormalPortEntry 3 }

gs2328fSTPMSTI4Port                                                          OBJECT IDENTIFIER ::= { gs2328fSTPMSTIPort 4 }

gs2328fSTPMSTI4AggregatedPort                                                OBJECT IDENTIFIER ::= { gs2328fSTPMSTI4Port 1 }

gs2328fSTPMSTI4AggregatedPortPathCost OBJECT-TYPE
   SYNTAX      Integer32(0..200000000)
   MAX-ACCESS  read-write
   STATUS      current
   DESCRIPTION
       " Auto: 0,
        Specific Path Cost range: 1 - 200000000."
   ::= { gs2328fSTPMSTI4AggregatedPort 1 }

gs2328fSTPMSTI4AggregatedPortPriority OBJECT-TYPE
   SYNTAX      Integer32(0..240)
   MAX-ACCESS  read-write
   STATUS      current
   DESCRIPTION
       " default: 128,
       Aggregated Port Priority (0/16/32/48/64/80/96/112/128/144/160/176/192/208/224/240)"
   ::= { gs2328fSTPMSTI4AggregatedPort 2 }

gs2328fSTPMSTI4NormalPortTable OBJECT-TYPE
   SYNTAX      SEQUENCE OF Gs2328fSTPMSTI4NormalPortEntry
   MAX-ACCESS  not-accessible
   STATUS      current
   DESCRIPTION
       " Show MSTI4 Normal Port Configurations. "
   ::= { gs2328fSTPMSTI4Port 2 }

gs2328fSTPMSTI4NormalPortEntry OBJECT-TYPE
   SYNTAX      Gs2328fSTPMSTI4NormalPortEntry
   MAX-ACCESS  not-accessible
   STATUS      current
   DESCRIPTION
       ""
   INDEX    { gs2328fSTPMSTI4NormalPortConfPort  }
   ::= { gs2328fSTPMSTI4NormalPortTable 1 }

Gs2328fSTPMSTI4NormalPortEntry ::= SEQUENCE {
   gs2328fSTPMSTI4NormalPortConfPort         Integer32,
   gs2328fSTPMSTI4NormalPortPathCost         Integer32,
   gs2328fSTPMSTI4NormalPortPriority         Integer32
}

gs2328fSTPMSTI4NormalPortConfPort OBJECT-TYPE
   SYNTAX      Integer32(1..4095)
   MAX-ACCESS  not-accessible
   STATUS      current
   DESCRIPTION
       " port, range : 1 - port number. "
   ::= { gs2328fSTPMSTI4NormalPortEntry 1 }

gs2328fSTPMSTI4NormalPortPathCost OBJECT-TYPE
   SYNTAX      Integer32(0..200000000)
   MAX-ACCESS  read-write
   STATUS      current
   DESCRIPTION
       " Auto: 0,
        Specific Path Cost range: 1 - 200000000."
   ::= { gs2328fSTPMSTI4NormalPortEntry 2 }

gs2328fSTPMSTI4NormalPortPriority OBJECT-TYPE
   SYNTAX      Integer32(0..240)
   MAX-ACCESS  read-write
   STATUS      current
   DESCRIPTION
       " default: 128,
       Aggregated Port Priority (0/16/32/48/64/80/96/112/128/144/160/176/192/208/224/240)"
   ::= { gs2328fSTPMSTI4NormalPortEntry 3 }

gs2328fSTPMSTI5Port                                                          OBJECT IDENTIFIER ::= { gs2328fSTPMSTIPort 5 }

gs2328fSTPMSTI5AggregatedPort                                                OBJECT IDENTIFIER ::= { gs2328fSTPMSTI5Port 1 }

gs2328fSTPMSTI5AggregatedPortPathCost OBJECT-TYPE
   SYNTAX      Integer32(0..200000000)
   MAX-ACCESS  read-write
   STATUS      current
   DESCRIPTION
       " Auto: 0,
        Specific Path Cost range: 1 - 200000000."
   ::= { gs2328fSTPMSTI5AggregatedPort 1 }

gs2328fSTPMSTI5AggregatedPortPriority OBJECT-TYPE
   SYNTAX      Integer32(0..240)
   MAX-ACCESS  read-write
   STATUS      current
   DESCRIPTION
       " default: 128,
       Aggregated Port Priority (0/16/32/48/64/80/96/112/128/144/160/176/192/208/224/240)"
   ::= { gs2328fSTPMSTI5AggregatedPort 2 }

gs2328fSTPMSTI5NormalPortTable OBJECT-TYPE
   SYNTAX      SEQUENCE OF Gs2328fSTPMSTI5NormalPortEntry
   MAX-ACCESS  not-accessible
   STATUS      current
   DESCRIPTION
       " Show MSTI5 Normal Port Configurations. "
   ::= { gs2328fSTPMSTI5Port 2 }

gs2328fSTPMSTI5NormalPortEntry OBJECT-TYPE
   SYNTAX      Gs2328fSTPMSTI5NormalPortEntry
   MAX-ACCESS  not-accessible
   STATUS      current
   DESCRIPTION
       ""
   INDEX    { gs2328fSTPMSTI5NormalPortConfPort  }
   ::= { gs2328fSTPMSTI5NormalPortTable 1 }

Gs2328fSTPMSTI5NormalPortEntry ::= SEQUENCE {
   gs2328fSTPMSTI5NormalPortConfPort         Integer32,
   gs2328fSTPMSTI5NormalPortPathCost         Integer32,
   gs2328fSTPMSTI5NormalPortPriority         Integer32
}

gs2328fSTPMSTI5NormalPortConfPort OBJECT-TYPE
   SYNTAX      Integer32(1..4095)
   MAX-ACCESS  not-accessible
   STATUS      current
   DESCRIPTION
       " port, range : 1 - port number. "
   ::= { gs2328fSTPMSTI5NormalPortEntry 1 }

gs2328fSTPMSTI5NormalPortPathCost OBJECT-TYPE
   SYNTAX      Integer32(0..200000000)
   MAX-ACCESS  read-write
   STATUS      current
   DESCRIPTION
       " Auto: 0,
        Specific Path Cost range: 1 - 200000000."
   ::= { gs2328fSTPMSTI5NormalPortEntry 2 }

gs2328fSTPMSTI5NormalPortPriority OBJECT-TYPE
   SYNTAX      Integer32(0..240)
   MAX-ACCESS  read-write
   STATUS      current
   DESCRIPTION
       " default: 128,
       Aggregated Port Priority (0/16/32/48/64/80/96/112/128/144/160/176/192/208/224/240)"
   ::= { gs2328fSTPMSTI5NormalPortEntry 3 }

gs2328fSTPMSTI6Port                                                          OBJECT IDENTIFIER ::= { gs2328fSTPMSTIPort 6 }

gs2328fSTPMSTI6AggregatedPort                                                OBJECT IDENTIFIER ::= { gs2328fSTPMSTI6Port 1 }

gs2328fSTPMSTI6AggregatedPortPathCost OBJECT-TYPE
   SYNTAX      Integer32(0..200000000)
   MAX-ACCESS  read-write
   STATUS      current
   DESCRIPTION
       " Auto: 0,
        Specific Path Cost range: 1 - 200000000."
   ::= { gs2328fSTPMSTI6AggregatedPort 1 }

gs2328fSTPMSTI6AggregatedPortPriority OBJECT-TYPE
   SYNTAX      Integer32(0..240)
   MAX-ACCESS  read-write
   STATUS      current
   DESCRIPTION
       " default: 128,
       Aggregated Port Priority (0/16/32/48/64/80/96/112/128/144/160/176/192/208/224/240)"
   ::= { gs2328fSTPMSTI6AggregatedPort 2 }

gs2328fSTPMSTI6NormalPortTable OBJECT-TYPE
   SYNTAX      SEQUENCE OF Gs2328fSTPMSTI6NormalPortEntry
   MAX-ACCESS  not-accessible
   STATUS      current
   DESCRIPTION
       " Show MSTI6 Normal Port Configurations. "
   ::= { gs2328fSTPMSTI6Port 2 }

gs2328fSTPMSTI6NormalPortEntry OBJECT-TYPE
   SYNTAX      Gs2328fSTPMSTI6NormalPortEntry
   MAX-ACCESS  not-accessible
   STATUS      current
   DESCRIPTION
       ""
   INDEX    { gs2328fSTPMSTI6NormalPortConfPort  }
   ::= { gs2328fSTPMSTI6NormalPortTable 1 }

Gs2328fSTPMSTI6NormalPortEntry ::= SEQUENCE {
   gs2328fSTPMSTI6NormalPortConfPort         Integer32,
   gs2328fSTPMSTI6NormalPortPathCost         Integer32,
   gs2328fSTPMSTI6NormalPortPriority         Integer32
}

gs2328fSTPMSTI6NormalPortConfPort OBJECT-TYPE
   SYNTAX      Integer32(1..4095)
   MAX-ACCESS  not-accessible
   STATUS      current
   DESCRIPTION
       " port, range : 1 - port number. "
   ::= { gs2328fSTPMSTI6NormalPortEntry 1 }

gs2328fSTPMSTI6NormalPortPathCost OBJECT-TYPE
   SYNTAX      Integer32(0..200000000)
   MAX-ACCESS  read-write
   STATUS      current
   DESCRIPTION
       " Auto: 0,
        Specific Path Cost range: 1 - 200000000."
   ::= { gs2328fSTPMSTI6NormalPortEntry 2 }

gs2328fSTPMSTI6NormalPortPriority OBJECT-TYPE
   SYNTAX      Integer32(0..240)
   MAX-ACCESS  read-write
   STATUS      current
   DESCRIPTION
       " default: 128,
       Aggregated Port Priority (0/16/32/48/64/80/96/112/128/144/160/176/192/208/224/240)"
   ::= { gs2328fSTPMSTI6NormalPortEntry 3 }

gs2328fSTPMSTI7Port                                                          OBJECT IDENTIFIER ::= { gs2328fSTPMSTIPort 7 }

gs2328fSTPMSTI7AggregatedPort                                                OBJECT IDENTIFIER ::= { gs2328fSTPMSTI7Port 1 }

gs2328fSTPMSTI7AggregatedPortPathCost OBJECT-TYPE
   SYNTAX      Integer32(0..200000000)
   MAX-ACCESS  read-write
   STATUS      current
   DESCRIPTION
       " Auto: 0,
        Specific Path Cost range: 1 - 200000000."
   ::= { gs2328fSTPMSTI7AggregatedPort 1 }

gs2328fSTPMSTI7AggregatedPortPriority OBJECT-TYPE
   SYNTAX      Integer32(0..240)
   MAX-ACCESS  read-write
   STATUS      current
   DESCRIPTION
       " default: 128,
       Aggregated Port Priority (0/16/32/48/64/80/96/112/128/144/160/176/192/208/224/240)"
   ::= { gs2328fSTPMSTI7AggregatedPort 2 }

gs2328fSTPMSTI7NormalPortTable OBJECT-TYPE
   SYNTAX      SEQUENCE OF Gs2328fSTPMSTI7NormalPortEntry
   MAX-ACCESS  not-accessible
   STATUS      current
   DESCRIPTION
       " Show MSTI7 Normal Port Configurations. "
   ::= { gs2328fSTPMSTI7Port 2 }

gs2328fSTPMSTI7NormalPortEntry OBJECT-TYPE
   SYNTAX      Gs2328fSTPMSTI7NormalPortEntry
   MAX-ACCESS  not-accessible
   STATUS      current
   DESCRIPTION
       ""
   INDEX    { gs2328fSTPMSTI7NormalPortConfPort  }
   ::= { gs2328fSTPMSTI7NormalPortTable 1 }

Gs2328fSTPMSTI7NormalPortEntry ::= SEQUENCE {
   gs2328fSTPMSTI7NormalPortConfPort         Integer32,
   gs2328fSTPMSTI7NormalPortPathCost         Integer32,
   gs2328fSTPMSTI7NormalPortPriority         Integer32
}

gs2328fSTPMSTI7NormalPortConfPort OBJECT-TYPE
   SYNTAX      Integer32(1..4095)
   MAX-ACCESS  not-accessible
   STATUS      current
   DESCRIPTION
       " port, range : 1 - port number. "
   ::= { gs2328fSTPMSTI7NormalPortEntry 1 }

gs2328fSTPMSTI7NormalPortPathCost OBJECT-TYPE
   SYNTAX      Integer32(0..200000000)
   MAX-ACCESS  read-write
   STATUS      current
   DESCRIPTION
       " Auto: 0,
        Specific Path Cost range: 1 - 200000000."
   ::= { gs2328fSTPMSTI7NormalPortEntry 2 }

gs2328fSTPMSTI7NormalPortPriority OBJECT-TYPE
   SYNTAX      Integer32(0..240)
   MAX-ACCESS  read-write
   STATUS      current
   DESCRIPTION
       " default: 128,
       Aggregated Port Priority (0/16/32/48/64/80/96/112/128/144/160/176/192/208/224/240)"
   ::= { gs2328fSTPMSTI7NormalPortEntry 3 }


gs2328fSTPBridgeStatus                                                      OBJECT IDENTIFIER ::= { gs2328fSTP 8 }

gs2328fCISTBridgeSTP                                                        OBJECT IDENTIFIER ::= { gs2328fSTPBridgeStatus 1 }

gs2328fCISTBridgeSTPStatus                                                  OBJECT IDENTIFIER ::= { gs2328fCISTBridgeSTP 1 }

gs2328fCISTBridgeInstance OBJECT-TYPE
   SYNTAX       DisplayString
   MAX-ACCESS   read-only
   STATUS       current
   DESCRIPTION
       "The Bridge instance - CIST, MST1, ..."
   ::= { gs2328fCISTBridgeSTPStatus 1 }

gs2328fCISTBridgeID OBJECT-TYPE
   SYNTAX       DisplayString
   MAX-ACCESS   read-only
   STATUS       current
   DESCRIPTION
       "The Bridge ID of this Bridge instance."
   ::= { gs2328fCISTBridgeSTPStatus 2 }

gs2328fCISTRootID OBJECT-TYPE
   SYNTAX       DisplayString
   MAX-ACCESS   read-only
   STATUS       current
   DESCRIPTION
       "The Bridge ID of the currently elected root bridge."
   ::= { gs2328fCISTBridgeSTPStatus 3 }

gs2328fCISTRootPort OBJECT-TYPE
   SYNTAX       DisplayString
   MAX-ACCESS   read-only
   STATUS       current
   DESCRIPTION
       "The switch port currently assigned the root port role."
   ::= { gs2328fCISTBridgeSTPStatus 4 }

gs2328fCISTRootCost OBJECT-TYPE
   SYNTAX       Integer32(0..200000000)
   MAX-ACCESS   read-only
   STATUS       current
   DESCRIPTION
       "Root Path Cost."
   ::= { gs2328fCISTBridgeSTPStatus 5 }

gs2328fCISTRegionalRoot OBJECT-TYPE
   SYNTAX       DisplayString
   MAX-ACCESS   read-only
   STATUS       current
   DESCRIPTION
       "The Bridge ID of the currently elected regional root bridge, inside the MSTP region of this bridge."
   ::= { gs2328fCISTBridgeSTPStatus 6 }

gs2328fCISTInternalRootCost OBJECT-TYPE
   SYNTAX       Integer32(0..200000000)
   MAX-ACCESS   read-only
   STATUS       current
   DESCRIPTION
       "The Regional Root Path Cost."
   ::= { gs2328fCISTBridgeSTPStatus 7 }

gs2328fCISTTopologyFlag OBJECT-TYPE
   SYNTAX       DisplayString
   MAX-ACCESS   read-only
   STATUS       current
   DESCRIPTION
       "The current state of the Topology Change Flag of this Bridge instance."
   ::= { gs2328fCISTBridgeSTPStatus 8 }

gs2328fCISTTopologyChangeCount OBJECT-TYPE
   SYNTAX       Counter32
   MAX-ACCESS   read-only
   STATUS       current
   DESCRIPTION
       "The number of times where the topology change flag has been set."
   ::= { gs2328fCISTBridgeSTPStatus 9 }

gs2328fCISTTopologyChangeLast OBJECT-TYPE
   SYNTAX       DisplayString
   MAX-ACCESS   read-only
   STATUS       current
   DESCRIPTION
       "The time passed since the Topology Flag was last set."
   ::= { gs2328fCISTBridgeSTPStatus 10 }

gs2328fCISTPortStateTable OBJECT-TYPE
   SYNTAX      SEQUENCE OF Gs2328fCISTPortStateEntry
   MAX-ACCESS  not-accessible
   STATUS      current
   DESCRIPTION
       " Show CIST Ports and Aggregations State Configurations. "
   ::= { gs2328fCISTBridgeSTP 2 }

gs2328fCISTPortStateEntry OBJECT-TYPE
   SYNTAX      Gs2328fCISTPortStateEntry
   MAX-ACCESS  not-accessible
   STATUS      current
   DESCRIPTION
       ""
   INDEX    { gs2328fCISTPortStateIndex  }
   ::= { gs2328fCISTPortStateTable 1 }

Gs2328fCISTPortStateEntry ::= SEQUENCE {
   gs2328fCISTPortStateIndex        Integer32,
   gs2328fCISTPortStatePort         DisplayString,
   gs2328fCISTPortStatePortID       DisplayString,
   gs2328fCISTPortStateRole         DisplayString,
   gs2328fCISTPortStateState        DisplayString,
   gs2328fCISTPortStatePathCost     Integer32,
   gs2328fCISTPortStateEdge         DisplayString,
   gs2328fCISTPortStatePoint2Point  DisplayString,
   gs2328fCISTPortStateUptime       DisplayString
}

gs2328fCISTPortStateIndex OBJECT-TYPE
   SYNTAX      Integer32(1..4095)
   MAX-ACCESS  not-accessible
   STATUS      current
   DESCRIPTION
       "table index."
   ::= { gs2328fCISTPortStateEntry 1 }

gs2328fCISTPortStatePort OBJECT-TYPE
   SYNTAX      DisplayString
   MAX-ACCESS  read-only
   STATUS      current
   DESCRIPTION
       "The switch port number of the logical STP port."
   ::= { gs2328fCISTPortStateEntry 2 }

gs2328fCISTPortStatePortID OBJECT-TYPE
   SYNTAX      DisplayString
   MAX-ACCESS  read-only
   STATUS      current
   DESCRIPTION
       "The port id as used by the STP protocol.
        This is the priority part and the logical port index of the bridge port."
   ::= { gs2328fCISTPortStateEntry 3 }

gs2328fCISTPortStateRole OBJECT-TYPE
   SYNTAX      DisplayString
   MAX-ACCESS  read-only
   STATUS      current
   DESCRIPTION
       "The current STP port role."
   ::= { gs2328fCISTPortStateEntry 4 }

gs2328fCISTPortStateState OBJECT-TYPE
   SYNTAX      DisplayString
   MAX-ACCESS  read-only
   STATUS      current
   DESCRIPTION
       "The current STP port state."
   ::= { gs2328fCISTPortStateEntry 5 }

gs2328fCISTPortStatePathCost OBJECT-TYPE
   SYNTAX      Integer32(0..200000000)
   MAX-ACCESS  read-only
   STATUS      current
   DESCRIPTION
       "The current STP port path cost."
   ::= { gs2328fCISTPortStateEntry 6 }

gs2328fCISTPortStateEdge OBJECT-TYPE
   SYNTAX      DisplayString
   MAX-ACCESS  read-only
   STATUS      current
   DESCRIPTION
       "The current STP port Edge Flag."
   ::= { gs2328fCISTPortStateEntry 7 }

gs2328fCISTPortStatePoint2Point OBJECT-TYPE
   SYNTAX      DisplayString
   MAX-ACCESS  read-only
   STATUS      current
   DESCRIPTION
       "The current STP port point-to-point flag."
   ::= { gs2328fCISTPortStateEntry 8 }

gs2328fCISTPortStateUptime OBJECT-TYPE
   SYNTAX      DisplayString
   MAX-ACCESS  read-only
   STATUS      current
   DESCRIPTION
       "The time since the bridge port was last initialized."
   ::= { gs2328fCISTPortStateEntry 9 }

gs2328fMSTI1BridgeSTP                                                        OBJECT IDENTIFIER ::= { gs2328fSTPBridgeStatus 2 }

gs2328fMSTI1BridgeSTPStatus                                                  OBJECT IDENTIFIER ::= { gs2328fMSTI1BridgeSTP 1 }

gs2328fMSTI1BridgeInstance OBJECT-TYPE
   SYNTAX       DisplayString
   MAX-ACCESS   read-only
   STATUS       current
   DESCRIPTION
       "The Bridge instance - CIST, MST1, ..."
   ::= { gs2328fMSTI1BridgeSTPStatus 1 }

gs2328fMSTI1BridgeID OBJECT-TYPE
   SYNTAX       DisplayString
   MAX-ACCESS   read-only
   STATUS       current
   DESCRIPTION
       "The Bridge ID of this Bridge instance."
   ::= { gs2328fMSTI1BridgeSTPStatus 2 }

gs2328fMSTI1RootID OBJECT-TYPE
   SYNTAX       DisplayString
   MAX-ACCESS   read-only
   STATUS       current
   DESCRIPTION
       "The Bridge ID of the currently elected root bridge."
   ::= { gs2328fMSTI1BridgeSTPStatus 3 }

gs2328fMSTI1RootPort OBJECT-TYPE
   SYNTAX       DisplayString
   MAX-ACCESS   read-only
   STATUS       current
   DESCRIPTION
       "The switch port currently assigned the root port role."
   ::= { gs2328fMSTI1BridgeSTPStatus 4 }

gs2328fMSTI1RootCost OBJECT-TYPE
   SYNTAX       Integer32(0..200000000)
   MAX-ACCESS   read-only
   STATUS       current
   DESCRIPTION
       "Root Path Cost."
   ::= { gs2328fMSTI1BridgeSTPStatus 5 }

gs2328fMSTI1TopologyFlag OBJECT-TYPE
   SYNTAX       DisplayString
   MAX-ACCESS   read-only
   STATUS       current
   DESCRIPTION
       "The current state of the Topology Change Flag of this Bridge instance."
   ::= { gs2328fMSTI1BridgeSTPStatus 8 }

gs2328fMSTI1TopologyChangeCount OBJECT-TYPE
   SYNTAX       Counter32
   MAX-ACCESS   read-only
   STATUS       current
   DESCRIPTION
       "The number of times where the topology change flag has been set."
   ::= { gs2328fMSTI1BridgeSTPStatus 9 }

gs2328fMSTI1TopologyChangeLast OBJECT-TYPE
   SYNTAX       DisplayString
   MAX-ACCESS   read-only
   STATUS       current
   DESCRIPTION
       "The time passed since the Topology Flag was last set."
   ::= { gs2328fMSTI1BridgeSTPStatus 10 }

gs2328fMSTI1PortStateTable OBJECT-TYPE
   SYNTAX      SEQUENCE OF Gs2328fMSTI1PortStateEntry
   MAX-ACCESS  not-accessible
   STATUS      current
   DESCRIPTION
       " Show MSTI1 Ports and Aggregations State Configurations. "
   ::= { gs2328fMSTI1BridgeSTP 2 }

gs2328fMSTI1PortStateEntry OBJECT-TYPE
   SYNTAX      Gs2328fMSTI1PortStateEntry
   MAX-ACCESS  not-accessible
   STATUS      current
   DESCRIPTION
       ""
   INDEX    { gs2328fMSTI1PortStateIndex  }
   ::= { gs2328fMSTI1PortStateTable 1 }

Gs2328fMSTI1PortStateEntry ::= SEQUENCE {
   gs2328fMSTI1PortStateIndex        Integer32,
   gs2328fMSTI1PortStatePort         DisplayString,
   gs2328fMSTI1PortStatePortID       DisplayString,
   gs2328fMSTI1PortStateRole         DisplayString,
   gs2328fMSTI1PortStateState        DisplayString,
   gs2328fMSTI1PortStatePathCost     Integer32,
   gs2328fMSTI1PortStateEdge         DisplayString,
   gs2328fMSTI1PortStatePoint2Point  DisplayString,
   gs2328fMSTI1PortStateUptime       DisplayString
}

gs2328fMSTI1PortStateIndex OBJECT-TYPE
   SYNTAX      Integer32(1..4095)
   MAX-ACCESS  not-accessible
   STATUS      current
   DESCRIPTION
       "table index."
   ::= { gs2328fMSTI1PortStateEntry 1 }

gs2328fMSTI1PortStatePort OBJECT-TYPE
   SYNTAX      DisplayString
   MAX-ACCESS  read-only
   STATUS      current
   DESCRIPTION
       "The switch port number of the logical STP port."
   ::= { gs2328fMSTI1PortStateEntry 2 }

gs2328fMSTI1PortStatePortID OBJECT-TYPE
   SYNTAX      DisplayString
   MAX-ACCESS  read-only
   STATUS      current
   DESCRIPTION
       "The port id as used by the STP protocol.
        This is the priority part and the logical port index of the bridge port."
   ::= { gs2328fMSTI1PortStateEntry 3 }

gs2328fMSTI1PortStateRole OBJECT-TYPE
   SYNTAX      DisplayString
   MAX-ACCESS  read-only
   STATUS      current
   DESCRIPTION
       "The current STP port role."
   ::= { gs2328fMSTI1PortStateEntry 4 }

gs2328fMSTI1PortStateState OBJECT-TYPE
   SYNTAX      DisplayString
   MAX-ACCESS  read-only
   STATUS      current
   DESCRIPTION
       "The current STP port state."
   ::= { gs2328fMSTI1PortStateEntry 5 }

gs2328fMSTI1PortStatePathCost OBJECT-TYPE
   SYNTAX      Integer32(0..200000000)
   MAX-ACCESS  read-only
   STATUS      current
   DESCRIPTION
       "The current STP port path cost."
   ::= { gs2328fMSTI1PortStateEntry 6 }

gs2328fMSTI1PortStateEdge OBJECT-TYPE
   SYNTAX      DisplayString
   MAX-ACCESS  read-only
   STATUS      current
   DESCRIPTION
       "The current STP port Edge Flag."
   ::= { gs2328fMSTI1PortStateEntry 7 }

gs2328fMSTI1PortStatePoint2Point OBJECT-TYPE
   SYNTAX      DisplayString
   MAX-ACCESS  read-only
   STATUS      current
   DESCRIPTION
       "The current STP port point-to-point flag."
   ::= { gs2328fMSTI1PortStateEntry 8 }

gs2328fMSTI1PortStateUptime OBJECT-TYPE
   SYNTAX      DisplayString
   MAX-ACCESS  read-only
   STATUS      current
   DESCRIPTION
       "The time since the bridge port was last initialized."
   ::= { gs2328fMSTI1PortStateEntry 9 }

gs2328fMSTI2BridgeSTP                                                        OBJECT IDENTIFIER ::= { gs2328fSTPBridgeStatus 3 }

gs2328fMSTI2BridgeSTPStatus                                                  OBJECT IDENTIFIER ::= { gs2328fMSTI2BridgeSTP 1 }

gs2328fMSTI2BridgeInstance OBJECT-TYPE
   SYNTAX       DisplayString
   MAX-ACCESS   read-only
   STATUS       current
   DESCRIPTION
       "The Bridge instance - CIST, MST1, ..."
   ::= { gs2328fMSTI2BridgeSTPStatus 1 }

gs2328fMSTI2BridgeID OBJECT-TYPE
   SYNTAX       DisplayString
   MAX-ACCESS   read-only
   STATUS       current
   DESCRIPTION
       "The Bridge ID of this Bridge instance."
   ::= { gs2328fMSTI2BridgeSTPStatus 2 }

gs2328fMSTI2RootID OBJECT-TYPE
   SYNTAX       DisplayString
   MAX-ACCESS   read-only
   STATUS       current
   DESCRIPTION
       "The Bridge ID of the currently elected root bridge."
   ::= { gs2328fMSTI2BridgeSTPStatus 3 }

gs2328fMSTI2RootPort OBJECT-TYPE
   SYNTAX       DisplayString
   MAX-ACCESS   read-only
   STATUS       current
   DESCRIPTION
       "The switch port currently assigned the root port role."
   ::= { gs2328fMSTI2BridgeSTPStatus 4 }

gs2328fMSTI2RootCost OBJECT-TYPE
   SYNTAX       Integer32(0..200000000)
   MAX-ACCESS   read-only
   STATUS       current
   DESCRIPTION
       "Root Path Cost."
   ::= { gs2328fMSTI2BridgeSTPStatus 5 }

gs2328fMSTI2TopologyFlag OBJECT-TYPE
   SYNTAX       DisplayString
   MAX-ACCESS   read-only
   STATUS       current
   DESCRIPTION
       "The current state of the Topology Change Flag of this Bridge instance."
   ::= { gs2328fMSTI2BridgeSTPStatus 8 }

gs2328fMSTI2TopologyChangeCount OBJECT-TYPE
   SYNTAX       Counter32
   MAX-ACCESS   read-only
   STATUS       current
   DESCRIPTION
       "The number of times where the topology change flag has been set."
   ::= { gs2328fMSTI2BridgeSTPStatus 9 }

gs2328fMSTI2TopologyChangeLast OBJECT-TYPE
   SYNTAX       DisplayString
   MAX-ACCESS   read-only
   STATUS       current
   DESCRIPTION
       "The time passed since the Topology Flag was last set."
   ::= { gs2328fMSTI2BridgeSTPStatus 10 }

gs2328fMSTI2PortStateTable OBJECT-TYPE
   SYNTAX      SEQUENCE OF Gs2328fMSTI2PortStateEntry
   MAX-ACCESS  not-accessible
   STATUS      current
   DESCRIPTION
       " Show MSTI2 Ports and Aggregations State Configurations. "
   ::= { gs2328fMSTI2BridgeSTP 2 }

gs2328fMSTI2PortStateEntry OBJECT-TYPE
   SYNTAX      Gs2328fMSTI2PortStateEntry
   MAX-ACCESS  not-accessible
   STATUS      current
   DESCRIPTION
       ""
   INDEX    { gs2328fMSTI2PortStateIndex  }
   ::= { gs2328fMSTI2PortStateTable 1 }

Gs2328fMSTI2PortStateEntry ::= SEQUENCE {
   gs2328fMSTI2PortStateIndex        Integer32,
   gs2328fMSTI2PortStatePort         DisplayString,
   gs2328fMSTI2PortStatePortID       DisplayString,
   gs2328fMSTI2PortStateRole         DisplayString,
   gs2328fMSTI2PortStateState        DisplayString,
   gs2328fMSTI2PortStatePathCost     Integer32,
   gs2328fMSTI2PortStateEdge         DisplayString,
   gs2328fMSTI2PortStatePoint2Point  DisplayString,
   gs2328fMSTI2PortStateUptime       DisplayString
}

gs2328fMSTI2PortStateIndex OBJECT-TYPE
   SYNTAX      Integer32(1..4095)
   MAX-ACCESS  not-accessible
   STATUS      current
   DESCRIPTION
       "table index."
   ::= { gs2328fMSTI2PortStateEntry 1 }

gs2328fMSTI2PortStatePort OBJECT-TYPE
   SYNTAX      DisplayString
   MAX-ACCESS  read-only
   STATUS      current
   DESCRIPTION
       "The switch port number of the logical STP port."
   ::= { gs2328fMSTI2PortStateEntry 2 }

gs2328fMSTI2PortStatePortID OBJECT-TYPE
   SYNTAX      DisplayString
   MAX-ACCESS  read-only
   STATUS      current
   DESCRIPTION
       "The port id as used by the STP protocol.
        This is the priority part and the logical port index of the bridge port."
   ::= { gs2328fMSTI2PortStateEntry 3 }

gs2328fMSTI2PortStateRole OBJECT-TYPE
   SYNTAX      DisplayString
   MAX-ACCESS  read-only
   STATUS      current
   DESCRIPTION
       "The current STP port role."
   ::= { gs2328fMSTI2PortStateEntry 4 }

gs2328fMSTI2PortStateState OBJECT-TYPE
   SYNTAX      DisplayString
   MAX-ACCESS  read-only
   STATUS      current
   DESCRIPTION
       "The current STP port state."
   ::= { gs2328fMSTI2PortStateEntry 5 }

gs2328fMSTI2PortStatePathCost OBJECT-TYPE
   SYNTAX      Integer32(0..200000000)
   MAX-ACCESS  read-only
   STATUS      current
   DESCRIPTION
       "The current STP port path cost."
   ::= { gs2328fMSTI2PortStateEntry 6 }

gs2328fMSTI2PortStateEdge OBJECT-TYPE
   SYNTAX      DisplayString
   MAX-ACCESS  read-only
   STATUS      current
   DESCRIPTION
       "The current STP port Edge Flag."
   ::= { gs2328fMSTI2PortStateEntry 7 }

gs2328fMSTI2PortStatePoint2Point OBJECT-TYPE
   SYNTAX      DisplayString
   MAX-ACCESS  read-only
   STATUS      current
   DESCRIPTION
       "The current STP port point-to-point flag."
   ::= { gs2328fMSTI2PortStateEntry 8 }

gs2328fMSTI2PortStateUptime OBJECT-TYPE
   SYNTAX      DisplayString
   MAX-ACCESS  read-only
   STATUS      current
   DESCRIPTION
       "The time since the bridge port was last initialized."
   ::= { gs2328fMSTI2PortStateEntry 9 }

gs2328fMSTI3BridgeSTP                                                        OBJECT IDENTIFIER ::= { gs2328fSTPBridgeStatus 4 }

gs2328fMSTI3BridgeSTPStatus                                                  OBJECT IDENTIFIER ::= { gs2328fMSTI3BridgeSTP 1 }

gs2328fMSTI3BridgeInstance OBJECT-TYPE
   SYNTAX       DisplayString
   MAX-ACCESS   read-only
   STATUS       current
   DESCRIPTION
       "The Bridge instance - CIST, MST1, ..."
   ::= { gs2328fMSTI3BridgeSTPStatus 1 }

gs2328fMSTI3BridgeID OBJECT-TYPE
   SYNTAX       DisplayString
   MAX-ACCESS   read-only
   STATUS       current
   DESCRIPTION
       "The Bridge ID of this Bridge instance."
   ::= { gs2328fMSTI3BridgeSTPStatus 2 }

gs2328fMSTI3RootID OBJECT-TYPE
   SYNTAX       DisplayString
   MAX-ACCESS   read-only
   STATUS       current
   DESCRIPTION
       "The Bridge ID of the currently elected root bridge."
   ::= { gs2328fMSTI3BridgeSTPStatus 3 }

gs2328fMSTI3RootPort OBJECT-TYPE
   SYNTAX       DisplayString
   MAX-ACCESS   read-only
   STATUS       current
   DESCRIPTION
       "The switch port currently assigned the root port role."
   ::= { gs2328fMSTI3BridgeSTPStatus 4 }

gs2328fMSTI3RootCost OBJECT-TYPE
   SYNTAX       Integer32(0..200000000)
   MAX-ACCESS   read-only
   STATUS       current
   DESCRIPTION
       "Root Path Cost."
   ::= { gs2328fMSTI3BridgeSTPStatus 5 }

gs2328fMSTI3TopologyFlag OBJECT-TYPE
   SYNTAX       DisplayString
   MAX-ACCESS   read-only
   STATUS       current
   DESCRIPTION
       "The current state of the Topology Change Flag of this Bridge instance."
   ::= { gs2328fMSTI3BridgeSTPStatus 8 }

gs2328fMSTI3TopologyChangeCount OBJECT-TYPE
   SYNTAX       Counter32
   MAX-ACCESS   read-only
   STATUS       current
   DESCRIPTION
       "The number of times where the topology change flag has been set."
   ::= { gs2328fMSTI3BridgeSTPStatus 9 }

gs2328fMSTI3TopologyChangeLast OBJECT-TYPE
   SYNTAX       DisplayString
   MAX-ACCESS   read-only
   STATUS       current
   DESCRIPTION
       "The time passed since the Topology Flag was last set."
   ::= { gs2328fMSTI3BridgeSTPStatus 10 }

gs2328fMSTI3PortStateTable OBJECT-TYPE
   SYNTAX      SEQUENCE OF Gs2328fMSTI3PortStateEntry
   MAX-ACCESS  not-accessible
   STATUS      current
   DESCRIPTION
       " Show MSTI3 Ports and Aggregations State Configurations. "
   ::= { gs2328fMSTI3BridgeSTP 2 }

gs2328fMSTI3PortStateEntry OBJECT-TYPE
   SYNTAX      Gs2328fMSTI3PortStateEntry
   MAX-ACCESS  not-accessible
   STATUS      current
   DESCRIPTION
       ""
   INDEX    { gs2328fMSTI3PortStateIndex  }
   ::= { gs2328fMSTI3PortStateTable 1 }

Gs2328fMSTI3PortStateEntry ::= SEQUENCE {
   gs2328fMSTI3PortStateIndex        Integer32,
   gs2328fMSTI3PortStatePort         DisplayString,
   gs2328fMSTI3PortStatePortID       DisplayString,
   gs2328fMSTI3PortStateRole         DisplayString,
   gs2328fMSTI3PortStateState        DisplayString,
   gs2328fMSTI3PortStatePathCost     Integer32,
   gs2328fMSTI3PortStateEdge         DisplayString,
   gs2328fMSTI3PortStatePoint2Point  DisplayString,
   gs2328fMSTI3PortStateUptime       DisplayString
}

gs2328fMSTI3PortStateIndex OBJECT-TYPE
   SYNTAX      Integer32(1..4095)
   MAX-ACCESS  not-accessible
   STATUS      current
   DESCRIPTION
       "table index."
   ::= { gs2328fMSTI3PortStateEntry 1 }

gs2328fMSTI3PortStatePort OBJECT-TYPE
   SYNTAX      DisplayString
   MAX-ACCESS  read-only
   STATUS      current
   DESCRIPTION
       "The switch port number of the logical STP port."
   ::= { gs2328fMSTI3PortStateEntry 2 }

gs2328fMSTI3PortStatePortID OBJECT-TYPE
   SYNTAX      DisplayString
   MAX-ACCESS  read-only
   STATUS      current
   DESCRIPTION
       "The port id as used by the STP protocol.
        This is the priority part and the logical port index of the bridge port."
   ::= { gs2328fMSTI3PortStateEntry 3 }

gs2328fMSTI3PortStateRole OBJECT-TYPE
   SYNTAX      DisplayString
   MAX-ACCESS  read-only
   STATUS      current
   DESCRIPTION
       "The current STP port role."
   ::= { gs2328fMSTI3PortStateEntry 4 }

gs2328fMSTI3PortStateState OBJECT-TYPE
   SYNTAX      DisplayString
   MAX-ACCESS  read-only
   STATUS      current
   DESCRIPTION
       "The current STP port state."
   ::= { gs2328fMSTI3PortStateEntry 5 }

gs2328fMSTI3PortStatePathCost OBJECT-TYPE
   SYNTAX      Integer32(0..200000000)
   MAX-ACCESS  read-only
   STATUS      current
   DESCRIPTION
       "The current STP port path cost."
   ::= { gs2328fMSTI3PortStateEntry 6 }

gs2328fMSTI3PortStateEdge OBJECT-TYPE
   SYNTAX      DisplayString
   MAX-ACCESS  read-only
   STATUS      current
   DESCRIPTION
       "The current STP port Edge Flag."
   ::= { gs2328fMSTI3PortStateEntry 7 }

gs2328fMSTI3PortStatePoint2Point OBJECT-TYPE
   SYNTAX      DisplayString
   MAX-ACCESS  read-only
   STATUS      current
   DESCRIPTION
       "The current STP port point-to-point flag."
   ::= { gs2328fMSTI3PortStateEntry 8 }

gs2328fMSTI3PortStateUptime OBJECT-TYPE
   SYNTAX      DisplayString
   MAX-ACCESS  read-only
   STATUS      current
   DESCRIPTION
       "The time since the bridge port was last initialized."
   ::= { gs2328fMSTI3PortStateEntry 9 }

gs2328fMSTI4BridgeSTP                                                        OBJECT IDENTIFIER ::= { gs2328fSTPBridgeStatus 5 }

gs2328fMSTI4BridgeSTPStatus                                                  OBJECT IDENTIFIER ::= { gs2328fMSTI4BridgeSTP 1 }

gs2328fMSTI4BridgeInstance OBJECT-TYPE
   SYNTAX       DisplayString
   MAX-ACCESS   read-only
   STATUS       current
   DESCRIPTION
       "The Bridge instance - CIST, MST1, ..."
   ::= { gs2328fMSTI4BridgeSTPStatus 1 }

gs2328fMSTI4BridgeID OBJECT-TYPE
   SYNTAX       DisplayString
   MAX-ACCESS   read-only
   STATUS       current
   DESCRIPTION
       "The Bridge ID of this Bridge instance."
   ::= { gs2328fMSTI4BridgeSTPStatus 2 }

gs2328fMSTI4RootID OBJECT-TYPE
   SYNTAX       DisplayString
   MAX-ACCESS   read-only
   STATUS       current
   DESCRIPTION
       "The Bridge ID of the currently elected root bridge."
   ::= { gs2328fMSTI4BridgeSTPStatus 3 }

gs2328fMSTI4RootPort OBJECT-TYPE
   SYNTAX       DisplayString
   MAX-ACCESS   read-only
   STATUS       current
   DESCRIPTION
       "The switch port currently assigned the root port role."
   ::= { gs2328fMSTI4BridgeSTPStatus 4 }

gs2328fMSTI4RootCost OBJECT-TYPE
   SYNTAX       Integer32(0..200000000)
   MAX-ACCESS   read-only
   STATUS       current
   DESCRIPTION
       "Root Path Cost."
   ::= { gs2328fMSTI4BridgeSTPStatus 5 }

gs2328fMSTI4TopologyFlag OBJECT-TYPE
   SYNTAX       DisplayString
   MAX-ACCESS   read-only
   STATUS       current
   DESCRIPTION
       "The current state of the Topology Change Flag of this Bridge instance."
   ::= { gs2328fMSTI4BridgeSTPStatus 8 }

gs2328fMSTI4TopologyChangeCount OBJECT-TYPE
   SYNTAX       Counter32
   MAX-ACCESS   read-only
   STATUS       current
   DESCRIPTION
       "The number of times where the topology change flag has been set."
   ::= { gs2328fMSTI4BridgeSTPStatus 9 }

gs2328fMSTI4TopologyChangeLast OBJECT-TYPE
   SYNTAX       DisplayString
   MAX-ACCESS   read-only
   STATUS       current
   DESCRIPTION
       "The time passed since the Topology Flag was last set."
   ::= { gs2328fMSTI4BridgeSTPStatus 10 }

gs2328fMSTI4PortStateTable OBJECT-TYPE
   SYNTAX      SEQUENCE OF Gs2328fMSTI4PortStateEntry
   MAX-ACCESS  not-accessible
   STATUS      current
   DESCRIPTION
       " Show MSTI4 Ports and Aggregations State Configurations. "
   ::= { gs2328fMSTI4BridgeSTP 2 }

gs2328fMSTI4PortStateEntry OBJECT-TYPE
   SYNTAX      Gs2328fMSTI4PortStateEntry
   MAX-ACCESS  not-accessible
   STATUS      current
   DESCRIPTION
       ""
   INDEX    { gs2328fMSTI4PortStateIndex  }
   ::= { gs2328fMSTI4PortStateTable 1 }

Gs2328fMSTI4PortStateEntry ::= SEQUENCE {
   gs2328fMSTI4PortStateIndex        Integer32,
   gs2328fMSTI4PortStatePort         DisplayString,
   gs2328fMSTI4PortStatePortID       DisplayString,
   gs2328fMSTI4PortStateRole         DisplayString,
   gs2328fMSTI4PortStateState        DisplayString,
   gs2328fMSTI4PortStatePathCost     Integer32,
   gs2328fMSTI4PortStateEdge         DisplayString,
   gs2328fMSTI4PortStatePoint2Point  DisplayString,
   gs2328fMSTI4PortStateUptime       DisplayString
}

gs2328fMSTI4PortStateIndex OBJECT-TYPE
   SYNTAX      Integer32(1..4095)
   MAX-ACCESS  not-accessible
   STATUS      current
   DESCRIPTION
       "table index."
   ::= { gs2328fMSTI4PortStateEntry 1 }

gs2328fMSTI4PortStatePort OBJECT-TYPE
   SYNTAX      DisplayString
   MAX-ACCESS  read-only
   STATUS      current
   DESCRIPTION
       "The switch port number of the logical STP port."
   ::= { gs2328fMSTI4PortStateEntry 2 }

gs2328fMSTI4PortStatePortID OBJECT-TYPE
   SYNTAX      DisplayString
   MAX-ACCESS  read-only
   STATUS      current
   DESCRIPTION
       "The port id as used by the STP protocol.
        This is the priority part and the logical port index of the bridge port."
   ::= { gs2328fMSTI4PortStateEntry 3 }

gs2328fMSTI4PortStateRole OBJECT-TYPE
   SYNTAX      DisplayString
   MAX-ACCESS  read-only
   STATUS      current
   DESCRIPTION
       "The current STP port role."
   ::= { gs2328fMSTI4PortStateEntry 4 }

gs2328fMSTI4PortStateState OBJECT-TYPE
   SYNTAX      DisplayString
   MAX-ACCESS  read-only
   STATUS      current
   DESCRIPTION
       "The current STP port state."
   ::= { gs2328fMSTI4PortStateEntry 5 }

gs2328fMSTI4PortStatePathCost OBJECT-TYPE
   SYNTAX      Integer32(0..200000000)
   MAX-ACCESS  read-only
   STATUS      current
   DESCRIPTION
       "The current STP port path cost."
   ::= { gs2328fMSTI4PortStateEntry 6 }

gs2328fMSTI4PortStateEdge OBJECT-TYPE
   SYNTAX      DisplayString
   MAX-ACCESS  read-only
   STATUS      current
   DESCRIPTION
       "The current STP port Edge Flag."
   ::= { gs2328fMSTI4PortStateEntry 7 }

gs2328fMSTI4PortStatePoint2Point OBJECT-TYPE
   SYNTAX      DisplayString
   MAX-ACCESS  read-only
   STATUS      current
   DESCRIPTION
       "The current STP port point-to-point flag."
   ::= { gs2328fMSTI4PortStateEntry 8 }

gs2328fMSTI4PortStateUptime OBJECT-TYPE
   SYNTAX      DisplayString
   MAX-ACCESS  read-only
   STATUS      current
   DESCRIPTION
       "The time since the bridge port was last initialized."
   ::= { gs2328fMSTI4PortStateEntry 9 }

gs2328fMSTI5BridgeSTP                                                        OBJECT IDENTIFIER ::= { gs2328fSTPBridgeStatus 6 }

gs2328fMSTI5BridgeSTPStatus                                                  OBJECT IDENTIFIER ::= { gs2328fMSTI5BridgeSTP 1 }

gs2328fMSTI5BridgeInstance OBJECT-TYPE
   SYNTAX       DisplayString
   MAX-ACCESS   read-only
   STATUS       current
   DESCRIPTION
       "The Bridge instance - CIST, MST1, ..."
   ::= { gs2328fMSTI5BridgeSTPStatus 1 }

gs2328fMSTI5BridgeID OBJECT-TYPE
   SYNTAX       DisplayString
   MAX-ACCESS   read-only
   STATUS       current
   DESCRIPTION
       "The Bridge ID of this Bridge instance."
   ::= { gs2328fMSTI5BridgeSTPStatus 2 }

gs2328fMSTI5RootID OBJECT-TYPE
   SYNTAX       DisplayString
   MAX-ACCESS   read-only
   STATUS       current
   DESCRIPTION
       "The Bridge ID of the currently elected root bridge."
   ::= { gs2328fMSTI5BridgeSTPStatus 3 }

gs2328fMSTI5RootPort OBJECT-TYPE
   SYNTAX       DisplayString
   MAX-ACCESS   read-only
   STATUS       current
   DESCRIPTION
       "The switch port currently assigned the root port role."
   ::= { gs2328fMSTI5BridgeSTPStatus 4 }

gs2328fMSTI5RootCost OBJECT-TYPE
   SYNTAX       Integer32(0..200000000)
   MAX-ACCESS   read-only
   STATUS       current
   DESCRIPTION
       "Root Path Cost."
   ::= { gs2328fMSTI5BridgeSTPStatus 5 }

gs2328fMSTI5TopologyFlag OBJECT-TYPE
   SYNTAX       DisplayString
   MAX-ACCESS   read-only
   STATUS       current
   DESCRIPTION
       "The current state of the Topology Change Flag of this Bridge instance."
   ::= { gs2328fMSTI5BridgeSTPStatus 8 }

gs2328fMSTI5TopologyChangeCount OBJECT-TYPE
   SYNTAX       Counter32
   MAX-ACCESS   read-only
   STATUS       current
   DESCRIPTION
       "The number of times where the topology change flag has been set."
   ::= { gs2328fMSTI5BridgeSTPStatus 9 }

gs2328fMSTI5TopologyChangeLast OBJECT-TYPE
   SYNTAX       DisplayString
   MAX-ACCESS   read-only
   STATUS       current
   DESCRIPTION
       "The time passed since the Topology Flag was last set."
   ::= { gs2328fMSTI5BridgeSTPStatus 10 }

gs2328fMSTI5PortStateTable OBJECT-TYPE
   SYNTAX      SEQUENCE OF Gs2328fMSTI5PortStateEntry
   MAX-ACCESS  not-accessible
   STATUS      current
   DESCRIPTION
       " Show MSTI5 Ports and Aggregations State Configurations. "
   ::= { gs2328fMSTI5BridgeSTP 2 }

gs2328fMSTI5PortStateEntry OBJECT-TYPE
   SYNTAX      Gs2328fMSTI5PortStateEntry
   MAX-ACCESS  not-accessible
   STATUS      current
   DESCRIPTION
       ""
   INDEX    { gs2328fMSTI5PortStateIndex  }
   ::= { gs2328fMSTI5PortStateTable 1 }

Gs2328fMSTI5PortStateEntry ::= SEQUENCE {
   gs2328fMSTI5PortStateIndex        Integer32,
   gs2328fMSTI5PortStatePort         DisplayString,
   gs2328fMSTI5PortStatePortID       DisplayString,
   gs2328fMSTI5PortStateRole         DisplayString,
   gs2328fMSTI5PortStateState        DisplayString,
   gs2328fMSTI5PortStatePathCost     Integer32,
   gs2328fMSTI5PortStateEdge         DisplayString,
   gs2328fMSTI5PortStatePoint2Point  DisplayString,
   gs2328fMSTI5PortStateUptime       DisplayString
}

gs2328fMSTI5PortStateIndex OBJECT-TYPE
   SYNTAX      Integer32(1..4095)
   MAX-ACCESS  not-accessible
   STATUS      current
   DESCRIPTION
       "table index."
   ::= { gs2328fMSTI5PortStateEntry 1 }

gs2328fMSTI5PortStatePort OBJECT-TYPE
   SYNTAX      DisplayString
   MAX-ACCESS  read-only
   STATUS      current
   DESCRIPTION
       "The switch port number of the logical STP port."
   ::= { gs2328fMSTI5PortStateEntry 2 }

gs2328fMSTI5PortStatePortID OBJECT-TYPE
   SYNTAX      DisplayString
   MAX-ACCESS  read-only
   STATUS      current
   DESCRIPTION
       "The port id as used by the STP protocol.
        This is the priority part and the logical port index of the bridge port."
   ::= { gs2328fMSTI5PortStateEntry 3 }

gs2328fMSTI5PortStateRole OBJECT-TYPE
   SYNTAX      DisplayString
   MAX-ACCESS  read-only
   STATUS      current
   DESCRIPTION
       "The current STP port role."
   ::= { gs2328fMSTI5PortStateEntry 4 }

gs2328fMSTI5PortStateState OBJECT-TYPE
   SYNTAX      DisplayString
   MAX-ACCESS  read-only
   STATUS      current
   DESCRIPTION
       "The current STP port state."
   ::= { gs2328fMSTI5PortStateEntry 5 }

gs2328fMSTI5PortStatePathCost OBJECT-TYPE
   SYNTAX      Integer32(0..200000000)
   MAX-ACCESS  read-only
   STATUS      current
   DESCRIPTION
       "The current STP port path cost."
   ::= { gs2328fMSTI5PortStateEntry 6 }

gs2328fMSTI5PortStateEdge OBJECT-TYPE
   SYNTAX      DisplayString
   MAX-ACCESS  read-only
   STATUS      current
   DESCRIPTION
       "The current STP port Edge Flag."
   ::= { gs2328fMSTI5PortStateEntry 7 }

gs2328fMSTI5PortStatePoint2Point OBJECT-TYPE
   SYNTAX      DisplayString
   MAX-ACCESS  read-only
   STATUS      current
   DESCRIPTION
       "The current STP port point-to-point flag."
   ::= { gs2328fMSTI5PortStateEntry 8 }

gs2328fMSTI5PortStateUptime OBJECT-TYPE
   SYNTAX      DisplayString
   MAX-ACCESS  read-only
   STATUS      current
   DESCRIPTION
       "The time since the bridge port was last initialized."
   ::= { gs2328fMSTI5PortStateEntry 9 }

gs2328fMSTI6BridgeSTP                                                        OBJECT IDENTIFIER ::= { gs2328fSTPBridgeStatus 7 }

gs2328fMSTI6BridgeSTPStatus                                                  OBJECT IDENTIFIER ::= { gs2328fMSTI6BridgeSTP 1 }

gs2328fMSTI6BridgeInstance OBJECT-TYPE
   SYNTAX       DisplayString
   MAX-ACCESS   read-only
   STATUS       current
   DESCRIPTION
       "The Bridge instance - CIST, MST1, ..."
   ::= { gs2328fMSTI6BridgeSTPStatus 1 }

gs2328fMSTI6BridgeID OBJECT-TYPE
   SYNTAX       DisplayString
   MAX-ACCESS   read-only
   STATUS       current
   DESCRIPTION
       "The Bridge ID of this Bridge instance."
   ::= { gs2328fMSTI6BridgeSTPStatus 2 }

gs2328fMSTI6RootID OBJECT-TYPE
   SYNTAX       DisplayString
   MAX-ACCESS   read-only
   STATUS       current
   DESCRIPTION
       "The Bridge ID of the currently elected root bridge."
   ::= { gs2328fMSTI6BridgeSTPStatus 3 }

gs2328fMSTI6RootPort OBJECT-TYPE
   SYNTAX       DisplayString
   MAX-ACCESS   read-only
   STATUS       current
   DESCRIPTION
       "The switch port currently assigned the root port role."
   ::= { gs2328fMSTI6BridgeSTPStatus 4 }

gs2328fMSTI6RootCost OBJECT-TYPE
   SYNTAX       Integer32(0..200000000)
   MAX-ACCESS   read-only
   STATUS       current
   DESCRIPTION
       "Root Path Cost."
   ::= { gs2328fMSTI6BridgeSTPStatus 5 }

gs2328fMSTI6TopologyFlag OBJECT-TYPE
   SYNTAX       DisplayString
   MAX-ACCESS   read-only
   STATUS       current
   DESCRIPTION
       "The current state of the Topology Change Flag of this Bridge instance."
   ::= { gs2328fMSTI6BridgeSTPStatus 8 }

gs2328fMSTI6TopologyChangeCount OBJECT-TYPE
   SYNTAX       Counter32
   MAX-ACCESS   read-only
   STATUS       current
   DESCRIPTION
       "The number of times where the topology change flag has been set."
   ::= { gs2328fMSTI6BridgeSTPStatus 9 }

gs2328fMSTI6TopologyChangeLast OBJECT-TYPE
   SYNTAX       DisplayString
   MAX-ACCESS   read-only
   STATUS       current
   DESCRIPTION
       "The time passed since the Topology Flag was last set."
   ::= { gs2328fMSTI6BridgeSTPStatus 10 }

gs2328fMSTI6PortStateTable OBJECT-TYPE
   SYNTAX      SEQUENCE OF Gs2328fMSTI6PortStateEntry
   MAX-ACCESS  not-accessible
   STATUS      current
   DESCRIPTION
       " Show MSTI6 Ports and Aggregations State Configurations. "
   ::= { gs2328fMSTI6BridgeSTP 2 }

gs2328fMSTI6PortStateEntry OBJECT-TYPE
   SYNTAX      Gs2328fMSTI6PortStateEntry
   MAX-ACCESS  not-accessible
   STATUS      current
   DESCRIPTION
       ""
   INDEX    { gs2328fMSTI6PortStateIndex  }
   ::= { gs2328fMSTI6PortStateTable 1 }

Gs2328fMSTI6PortStateEntry ::= SEQUENCE {
   gs2328fMSTI6PortStateIndex        Integer32,
   gs2328fMSTI6PortStatePort         DisplayString,
   gs2328fMSTI6PortStatePortID       DisplayString,
   gs2328fMSTI6PortStateRole         DisplayString,
   gs2328fMSTI6PortStateState        DisplayString,
   gs2328fMSTI6PortStatePathCost     Integer32,
   gs2328fMSTI6PortStateEdge         DisplayString,
   gs2328fMSTI6PortStatePoint2Point  DisplayString,
   gs2328fMSTI6PortStateUptime       DisplayString
}

gs2328fMSTI6PortStateIndex OBJECT-TYPE
   SYNTAX      Integer32(1..4095)
   MAX-ACCESS  not-accessible
   STATUS      current
   DESCRIPTION
       "table index."
   ::= { gs2328fMSTI6PortStateEntry 1 }

gs2328fMSTI6PortStatePort OBJECT-TYPE
   SYNTAX      DisplayString
   MAX-ACCESS  read-only
   STATUS      current
   DESCRIPTION
       "The switch port number of the logical STP port."
   ::= { gs2328fMSTI6PortStateEntry 2 }

gs2328fMSTI6PortStatePortID OBJECT-TYPE
   SYNTAX      DisplayString
   MAX-ACCESS  read-only
   STATUS      current
   DESCRIPTION
       "The port id as used by the STP protocol.
        This is the priority part and the logical port index of the bridge port."
   ::= { gs2328fMSTI6PortStateEntry 3 }

gs2328fMSTI6PortStateRole OBJECT-TYPE
   SYNTAX      DisplayString
   MAX-ACCESS  read-only
   STATUS      current
   DESCRIPTION
       "The current STP port role."
   ::= { gs2328fMSTI6PortStateEntry 4 }

gs2328fMSTI6PortStateState OBJECT-TYPE
   SYNTAX      DisplayString
   MAX-ACCESS  read-only
   STATUS      current
   DESCRIPTION
       "The current STP port state."
   ::= { gs2328fMSTI6PortStateEntry 5 }

gs2328fMSTI6PortStatePathCost OBJECT-TYPE
   SYNTAX      Integer32(0..200000000)
   MAX-ACCESS  read-only
   STATUS      current
   DESCRIPTION
       "The current STP port path cost."
   ::= { gs2328fMSTI6PortStateEntry 6 }

gs2328fMSTI6PortStateEdge OBJECT-TYPE
   SYNTAX      DisplayString
   MAX-ACCESS  read-only
   STATUS      current
   DESCRIPTION
       "The current STP port Edge Flag."
   ::= { gs2328fMSTI6PortStateEntry 7 }

gs2328fMSTI6PortStatePoint2Point OBJECT-TYPE
   SYNTAX      DisplayString
   MAX-ACCESS  read-only
   STATUS      current
   DESCRIPTION
       "The current STP port point-to-point flag."
   ::= { gs2328fMSTI6PortStateEntry 8 }

gs2328fMSTI6PortStateUptime OBJECT-TYPE
   SYNTAX      DisplayString
   MAX-ACCESS  read-only
   STATUS      current
   DESCRIPTION
       "The time since the bridge port was last initialized."
   ::= { gs2328fMSTI6PortStateEntry 9 }

gs2328fMSTI7BridgeSTP                                                        OBJECT IDENTIFIER ::= { gs2328fSTPBridgeStatus 8 }

gs2328fMSTI7BridgeSTPStatus                                                  OBJECT IDENTIFIER ::= { gs2328fMSTI7BridgeSTP 1 }

gs2328fMSTI7BridgeInstance OBJECT-TYPE
   SYNTAX       DisplayString
   MAX-ACCESS   read-only
   STATUS       current
   DESCRIPTION
       "The Bridge instance - CIST, MST1, ..."
   ::= { gs2328fMSTI7BridgeSTPStatus 1 }

gs2328fMSTI7BridgeID OBJECT-TYPE
   SYNTAX       DisplayString
   MAX-ACCESS   read-only
   STATUS       current
   DESCRIPTION
       "The Bridge ID of this Bridge instance."
   ::= { gs2328fMSTI7BridgeSTPStatus 2 }

gs2328fMSTI7RootID OBJECT-TYPE
   SYNTAX       DisplayString
   MAX-ACCESS   read-only
   STATUS       current
   DESCRIPTION
       "The Bridge ID of the currently elected root bridge."
   ::= { gs2328fMSTI7BridgeSTPStatus 3 }

gs2328fMSTI7RootPort OBJECT-TYPE
   SYNTAX       DisplayString
   MAX-ACCESS   read-only
   STATUS       current
   DESCRIPTION
       "The switch port currently assigned the root port role."
   ::= { gs2328fMSTI7BridgeSTPStatus 4 }

gs2328fMSTI7RootCost OBJECT-TYPE
   SYNTAX       Integer32(0..200000000)
   MAX-ACCESS   read-only
   STATUS       current
   DESCRIPTION
       "Root Path Cost."
   ::= { gs2328fMSTI7BridgeSTPStatus 5 }

gs2328fMSTI7TopologyFlag OBJECT-TYPE
   SYNTAX       DisplayString
   MAX-ACCESS   read-only
   STATUS       current
   DESCRIPTION
       "The current state of the Topology Change Flag of this Bridge instance."
   ::= { gs2328fMSTI7BridgeSTPStatus 8 }

gs2328fMSTI7TopologyChangeCount OBJECT-TYPE
   SYNTAX       Counter32
   MAX-ACCESS   read-only
   STATUS       current
   DESCRIPTION
       "The number of times where the topology change flag has been set."
   ::= { gs2328fMSTI7BridgeSTPStatus 9 }

gs2328fMSTI7TopologyChangeLast OBJECT-TYPE
   SYNTAX       DisplayString
   MAX-ACCESS   read-only
   STATUS       current
   DESCRIPTION
       "The time passed since the Topology Flag was last set."
   ::= { gs2328fMSTI7BridgeSTPStatus 10 }

gs2328fMSTI7PortStateTable OBJECT-TYPE
   SYNTAX      SEQUENCE OF Gs2328fMSTI7PortStateEntry
   MAX-ACCESS  not-accessible
   STATUS      current
   DESCRIPTION
       " Show MSTI7 Ports and Aggregations State Configurations. "
   ::= { gs2328fMSTI7BridgeSTP 2 }

gs2328fMSTI7PortStateEntry OBJECT-TYPE
   SYNTAX      Gs2328fMSTI7PortStateEntry
   MAX-ACCESS  not-accessible
   STATUS      current
   DESCRIPTION
       ""
   INDEX    { gs2328fMSTI7PortStateIndex  }
   ::= { gs2328fMSTI7PortStateTable 1 }

Gs2328fMSTI7PortStateEntry ::= SEQUENCE {
   gs2328fMSTI7PortStateIndex        Integer32,
   gs2328fMSTI7PortStatePort         DisplayString,
   gs2328fMSTI7PortStatePortID       DisplayString,
   gs2328fMSTI7PortStateRole         DisplayString,
   gs2328fMSTI7PortStateState        DisplayString,
   gs2328fMSTI7PortStatePathCost     Integer32,
   gs2328fMSTI7PortStateEdge         DisplayString,
   gs2328fMSTI7PortStatePoint2Point  DisplayString,
   gs2328fMSTI7PortStateUptime       DisplayString
}

gs2328fMSTI7PortStateIndex OBJECT-TYPE
   SYNTAX      Integer32(1..4095)
   MAX-ACCESS  not-accessible
   STATUS      current
   DESCRIPTION
       "table index."
   ::= { gs2328fMSTI7PortStateEntry 1 }

gs2328fMSTI7PortStatePort OBJECT-TYPE
   SYNTAX      DisplayString
   MAX-ACCESS  read-only
   STATUS      current
   DESCRIPTION
       "The switch port number of the logical STP port."
   ::= { gs2328fMSTI7PortStateEntry 2 }

gs2328fMSTI7PortStatePortID OBJECT-TYPE
   SYNTAX      DisplayString
   MAX-ACCESS  read-only
   STATUS      current
   DESCRIPTION
       "The port id as used by the STP protocol.
        This is the priority part and the logical port index of the bridge port."
   ::= { gs2328fMSTI7PortStateEntry 3 }

gs2328fMSTI7PortStateRole OBJECT-TYPE
   SYNTAX      DisplayString
   MAX-ACCESS  read-only
   STATUS      current
   DESCRIPTION
       "The current STP port role."
   ::= { gs2328fMSTI7PortStateEntry 4 }

gs2328fMSTI7PortStateState OBJECT-TYPE
   SYNTAX      DisplayString
   MAX-ACCESS  read-only
   STATUS      current
   DESCRIPTION
       "The current STP port state."
   ::= { gs2328fMSTI7PortStateEntry 5 }

gs2328fMSTI7PortStatePathCost OBJECT-TYPE
   SYNTAX      Integer32(0..200000000)
   MAX-ACCESS  read-only
   STATUS      current
   DESCRIPTION
       "The current STP port path cost."
   ::= { gs2328fMSTI7PortStateEntry 6 }

gs2328fMSTI7PortStateEdge OBJECT-TYPE
   SYNTAX      DisplayString
   MAX-ACCESS  read-only
   STATUS      current
   DESCRIPTION
       "The current STP port Edge Flag."
   ::= { gs2328fMSTI7PortStateEntry 7 }

gs2328fMSTI7PortStatePoint2Point OBJECT-TYPE
   SYNTAX      DisplayString
   MAX-ACCESS  read-only
   STATUS      current
   DESCRIPTION
       "The current STP port point-to-point flag."
   ::= { gs2328fMSTI7PortStateEntry 8 }

gs2328fMSTI7PortStateUptime OBJECT-TYPE
   SYNTAX      DisplayString
   MAX-ACCESS  read-only
   STATUS      current
   DESCRIPTION
       "The time since the bridge port was last initialized."
   ::= { gs2328fMSTI7PortStateEntry 9 }

gs2328fSTPPortStatusTable OBJECT-TYPE
   SYNTAX      SEQUENCE OF Gs2328fSTPPortStatusEntry
   MAX-ACCESS  not-accessible
   STATUS      current
   DESCRIPTION
       " Show STP Port Status."
   ::= { gs2328fSTP 9 }

gs2328fSTPPortStatusEntry OBJECT-TYPE
   SYNTAX      Gs2328fSTPPortStatusEntry
   MAX-ACCESS  not-accessible
   STATUS      current
   DESCRIPTION
       ""
   INDEX    { gs2328fSTPPortStatusPort  }
   ::= { gs2328fSTPPortStatusTable 1 }

Gs2328fSTPPortStatusEntry ::= SEQUENCE {
   gs2328fSTPPortStatusPort         Integer32,
   gs2328fSTPPortStatusCISTRole     DisplayString,
   gs2328fSTPPortStatusCISTState    DisplayString,
   gs2328fSTPPortStatusUptime       DisplayString
}

gs2328fSTPPortStatusPort OBJECT-TYPE
   SYNTAX      Integer32(1..4095)
   MAX-ACCESS  not-accessible
   STATUS      current
   DESCRIPTION
       " port, range : 1 - port number. "
   ::= { gs2328fSTPPortStatusEntry 1 }

gs2328fSTPPortStatusCISTRole OBJECT-TYPE
   SYNTAX      DisplayString
   MAX-ACCESS  read-only
   STATUS      current
   DESCRIPTION
       " The current STP port role of the CIST port. "
   ::= { gs2328fSTPPortStatusEntry 2 }

gs2328fSTPPortStatusCISTState OBJECT-TYPE
   SYNTAX      DisplayString
   MAX-ACCESS  read-only
   STATUS      current
   DESCRIPTION
       " The current STP port state of the CIST port. "
   ::= { gs2328fSTPPortStatusEntry 3 }

gs2328fSTPPortStatusUptime OBJECT-TYPE
   SYNTAX      DisplayString
   MAX-ACCESS  read-only
   STATUS      current
   DESCRIPTION
       " The time since the bridge port was last initialized. "
   ::= { gs2328fSTPPortStatusEntry 4 }

gs2328fSTPPortStatisticsTable OBJECT-TYPE
   SYNTAX      SEQUENCE OF Gs2328fSTPPortStatisticsEntry
   MAX-ACCESS  not-accessible
   STATUS      current
   DESCRIPTION
       " Show STP Port Statistics."
   ::= { gs2328fSTP 10 }

gs2328fSTPPortStatisticsEntry OBJECT-TYPE
   SYNTAX      Gs2328fSTPPortStatisticsEntry
   MAX-ACCESS  not-accessible
   STATUS      current
   DESCRIPTION
       ""
   INDEX    { gs2328fSTPStatisticsIndex  }
   ::= { gs2328fSTPPortStatisticsTable 1 }

Gs2328fSTPPortStatisticsEntry ::= SEQUENCE {
   gs2328fSTPStatisticsIndex            Integer32,
   gs2328fSTPStatisticsPort             DisplayString,
   gs2328fSTPStatisticsTxMSTP           Counter32,
   gs2328fSTPStatisticsTxRSTP           Counter32,
   gs2328fSTPStatisticsTxSTP            Counter32,
   gs2328fSTPStatisticsTxTCN            Counter32,
   gs2328fSTPStatisticsRxMSTP           Counter32,
   gs2328fSTPStatisticsRxRSTP           Counter32,
   gs2328fSTPStatisticsRxSTP            Counter32,
   gs2328fSTPStatisticsRxTCN            Counter32,
   gs2328fSTPStatisticsDiscardedUnknown Counter32,
   gs2328fSTPStatisticsDiscardedIllegal Counter32
}

gs2328fSTPStatisticsIndex OBJECT-TYPE
   SYNTAX      Integer32(1..4095)
   MAX-ACCESS  not-accessible
   STATUS      current
   DESCRIPTION
       "table index."
   ::= { gs2328fSTPPortStatisticsEntry 1 }

gs2328fSTPStatisticsPort OBJECT-TYPE
   SYNTAX      DisplayString
   MAX-ACCESS  not-accessible
   STATUS      current
   DESCRIPTION
       " port, range : 1 - port number. "
   ::= { gs2328fSTPPortStatisticsEntry 2 }

gs2328fSTPStatisticsTxMSTP OBJECT-TYPE
   SYNTAX      Counter32
   MAX-ACCESS  read-only
   STATUS      current
   DESCRIPTION
       " The number of MSTP Configuration BPDU's received/transmitted on the port."
   ::= { gs2328fSTPPortStatisticsEntry 3 }

gs2328fSTPStatisticsTxRSTP OBJECT-TYPE
   SYNTAX      Counter32
   MAX-ACCESS  read-only
   STATUS      current
   DESCRIPTION
       " The number of RSTP Configuration BPDU's received/transmitted on the port. "
   ::= { gs2328fSTPPortStatisticsEntry 4 }

gs2328fSTPStatisticsTxSTP OBJECT-TYPE
   SYNTAX      Counter32
   MAX-ACCESS  read-only
   STATUS      current
   DESCRIPTION
       " The number of legacy STP Configuration BPDU's received/transmitted on the port. "
   ::= { gs2328fSTPPortStatisticsEntry 5 }

gs2328fSTPStatisticsTxTCN OBJECT-TYPE
   SYNTAX      Counter32
   MAX-ACCESS  read-only
   STATUS      current
   DESCRIPTION
       " The number of Topology Change Notification BPDU's received/transmitted on the port. "
   ::= { gs2328fSTPPortStatisticsEntry 6 }

gs2328fSTPStatisticsRxMSTP OBJECT-TYPE
   SYNTAX      Counter32
   MAX-ACCESS  read-only
   STATUS      current
   DESCRIPTION
       " The number of MSTP Configuration BPDU's received/transmitted on the port."
   ::= { gs2328fSTPPortStatisticsEntry 7 }

gs2328fSTPStatisticsRxRSTP OBJECT-TYPE
   SYNTAX      Counter32
   MAX-ACCESS  read-only
   STATUS      current
   DESCRIPTION
       " The number of RSTP Configuration BPDU's received/transmitted on the port. "
   ::= { gs2328fSTPPortStatisticsEntry 8 }

gs2328fSTPStatisticsRxSTP OBJECT-TYPE
   SYNTAX      Counter32
   MAX-ACCESS  read-only
   STATUS      current
   DESCRIPTION
       " The number of legacy STP Configuration BPDU's received/transmitted on the port. "
   ::= { gs2328fSTPPortStatisticsEntry 9 }

gs2328fSTPStatisticsRxTCN OBJECT-TYPE
   SYNTAX      Counter32
   MAX-ACCESS  read-only
   STATUS      current
   DESCRIPTION
       " The number of Topology Change Notification BPDU's received/transmitted on the port. "
   ::= { gs2328fSTPPortStatisticsEntry 10 }

gs2328fSTPStatisticsDiscardedUnknown OBJECT-TYPE
   SYNTAX      Counter32
   MAX-ACCESS  read-only
   STATUS      current
   DESCRIPTION
       " The number of unknown Spanning Tree BPDU's received and discarded on the port. "
   ::= { gs2328fSTPPortStatisticsEntry 11 }

gs2328fSTPStatisticsDiscardedIllegal OBJECT-TYPE
   SYNTAX      Counter32
   MAX-ACCESS  read-only
   STATUS      current
   DESCRIPTION
       " The number of illegal Spanning Tree BPDU's received and discarded on the port. "
   ::= { gs2328fSTPPortStatisticsEntry 12 }


gs2328fFilteringDataBase                                                  OBJECT IDENTIFIER ::= { gs2328fConfiguration 21 }

gs2328fFilteringDataBaseConfig                                            OBJECT IDENTIFIER ::= { gs2328fFilteringDataBase 1 }

gs2328fFilteringDataBaseAgingTime OBJECT-TYPE
   SYNTAX      Integer32(0..1000000)
   MAX-ACCESS  read-write
   STATUS      current
   DESCRIPTION
       "Configure aging time by entering a value here in seconds.
        default: 300,
        range: 10-1000000.
        Disable automatic aging : 0."
   ::= { gs2328fFilteringDataBaseConfig 1 }

gs2328fFilteringDataBaseConfigTable OBJECT-TYPE
   SYNTAX      SEQUENCE OF GS2328FFilteringDataBaseConfigEntry
   MAX-ACCESS  not-accessible
   STATUS      current
   DESCRIPTION
       " "
   ::= { gs2328fFilteringDataBaseConfig 2 }

gs2328fFilteringDataBaseConfigEntry OBJECT-TYPE
   SYNTAX      GS2328FFilteringDataBaseConfigEntry
   MAX-ACCESS  not-accessible
   STATUS      current
   DESCRIPTION
       ""
   INDEX    { gs2328fFilteringDataBaseConfigPort  }
   ::= { gs2328fFilteringDataBaseConfigTable 1 }

GS2328FFilteringDataBaseConfigEntry ::= SEQUENCE {
   gs2328fFilteringDataBaseConfigPort        Integer32,
   gs2328fFilteringDataBaseConfigLearning    INTEGER
}

gs2328fFilteringDataBaseConfigPort OBJECT-TYPE
   SYNTAX      Integer32(1..4095)
   MAX-ACCESS  not-accessible
   STATUS      current
   DESCRIPTION
       " "
   ::= { gs2328fFilteringDataBaseConfigEntry 1 }

gs2328fFilteringDataBaseConfigLearning OBJECT-TYPE
   SYNTAX      INTEGER { auto(0), disable(1), secure(2) }
   MAX-ACCESS  read-write
   STATUS      current
   DESCRIPTION
       "Configure learning mode of switch ports.
        default: 0,
        0: auto,
        1: disable,
        2: secure. "
   ::= { gs2328fFilteringDataBaseConfigEntry 2 }


gs2328fFilteringDataBaseStaticMAC                                OBJECT IDENTIFIER ::= { gs2328fFilteringDataBaseConfig 3 }

gs2328fFilteringDataBaseStaticMACCreate OBJECT-TYPE
   SYNTAX       INTEGER { none(0), create(1) }
   MAX-ACCESS   read-write
   STATUS       current
   DESCRIPTION
       "default: 0
        0 : None  (read only)
        1 : Create Static MAC Table"
   ::= { gs2328fFilteringDataBaseStaticMAC 1 }

gs2328fFilteringDataBaseStaticMACTable OBJECT-TYPE
   SYNTAX      SEQUENCE OF GS2328FFilteringDataBaseStaticMACEntry
   MAX-ACCESS  not-accessible
   STATUS      current
   DESCRIPTION
       " "
   ::= { gs2328fFilteringDataBaseStaticMAC 2 }

gs2328fFilteringDataBaseStaticMACEntry OBJECT-TYPE
   SYNTAX      GS2328FFilteringDataBaseStaticMACEntry
   MAX-ACCESS  not-accessible
   STATUS      current
   DESCRIPTION
       ""
   INDEX    { gs2328fFilteringDataBaseStaticMACIndex  }
   ::= { gs2328fFilteringDataBaseStaticMACTable 1 }

GS2328FFilteringDataBaseStaticMACEntry ::= SEQUENCE {
   gs2328fFilteringDataBaseStaticMACIndex	    Integer32,
   gs2328fFilteringDataBaseStaticMACVLANId	    Integer32,
   gs2328fFilteringDataBaseStaticMACAddress      MacAddress,
   gs2328fFilteringDataBaseStaticMACPortMembers  DisplayString,
   gs2328fFilteringDataBaseStaticMACRowStatus	INTEGER
}

gs2328fFilteringDataBaseStaticMACIndex OBJECT-TYPE
   SYNTAX      Integer32(1..4095)
   MAX-ACCESS  not-accessible
   STATUS      current
   DESCRIPTION
       " "
   ::= { gs2328fFilteringDataBaseStaticMACEntry 1 }

gs2328fFilteringDataBaseStaticMACVLANId OBJECT-TYPE
   SYNTAX      Integer32(1..4094)
   MAX-ACCESS  read-write
   STATUS      current
   DESCRIPTION
       " VLAN ID, range: 1 - 4094. "
   ::= { gs2328fFilteringDataBaseStaticMACEntry 2 }

gs2328fFilteringDataBaseStaticMACAddress OBJECT-TYPE
   SYNTAX      MacAddress
   MAX-ACCESS  read-write
   STATUS      current
   DESCRIPTION
       " MAC address, format 0a 1b 2c 3d 4e 5f "
   ::= { gs2328fFilteringDataBaseStaticMACEntry 3 }

gs2328fFilteringDataBaseStaticMACPortMembers OBJECT-TYPE
   SYNTAX      DisplayString
   MAX-ACCESS  read-write
   STATUS      current
   DESCRIPTION
       "To include the ports in a Static MAC Table"
   ::= { gs2328fFilteringDataBaseStaticMACEntry 4 }

gs2328fFilteringDataBaseStaticMACRowStatus OBJECT-TYPE
   SYNTAX      INTEGER { active(1), notInservice(2), destroy(4), undo(5) }
   MAX-ACCESS  read-write
   STATUS      current
   DESCRIPTION
       "1: active
        2: notInservice
        4: destroy
        5: undo"
   ::= { gs2328fFilteringDataBaseStaticMACEntry 5 }


gs2328fFilteringDataBaseDynamicMACTable OBJECT-TYPE
   SYNTAX      SEQUENCE OF GS2328FFilteringDataBaseDynamicMACEntry
   MAX-ACCESS  not-accessible
   STATUS      current
   DESCRIPTION
       " "
   ::= { gs2328fFilteringDataBaseConfig 4 }

gs2328fFilteringDataBaseDynamicMACEntry OBJECT-TYPE
   SYNTAX      GS2328FFilteringDataBaseDynamicMACEntry
   MAX-ACCESS  not-accessible
   STATUS      current
   DESCRIPTION
       ""
   INDEX    { gs2328fFilteringDataBaseDynamicMACIndex  }
   ::= { gs2328fFilteringDataBaseDynamicMACTable 1 }

GS2328FFilteringDataBaseDynamicMACEntry ::= SEQUENCE {
   gs2328fFilteringDataBaseDynamicMACIndex	    Integer32,
   gs2328fFilteringDataBaseDynamicMACType	    INTEGER,
   gs2328fFilteringDataBaseDynamicMACVLAN	    Integer32,
   gs2328fFilteringDataBaseDynamicMACAddress     MacAddress,
   gs2328fFilteringDataBaseDynamicPortMembers    DisplayString
}

gs2328fFilteringDataBaseDynamicMACIndex OBJECT-TYPE
   SYNTAX      Integer32(1..4095)
   MAX-ACCESS  not-accessible
   STATUS      current
   DESCRIPTION
       " "
   ::= { gs2328fFilteringDataBaseDynamicMACEntry 1 }

gs2328fFilteringDataBaseDynamicMACType OBJECT-TYPE
   SYNTAX      INTEGER { dynamic(0), static(1) }
   MAX-ACCESS  read-only
   STATUS      current
   DESCRIPTION
       "Indicates whether the entry is a static or a dynamic entry."
   ::= { gs2328fFilteringDataBaseDynamicMACEntry 2 }

gs2328fFilteringDataBaseDynamicMACVLAN OBJECT-TYPE
   SYNTAX      Integer32(1..4094)
   MAX-ACCESS  read-only
   STATUS      current
   DESCRIPTION
       "The VLAN ID of the entry."
   ::= { gs2328fFilteringDataBaseDynamicMACEntry 3 }

gs2328fFilteringDataBaseDynamicMACAddress OBJECT-TYPE
   SYNTAX      MacAddress
   MAX-ACCESS  read-only
   STATUS      current
   DESCRIPTION
       "The MAC address of the entry."
   ::= { gs2328fFilteringDataBaseDynamicMACEntry 4 }

gs2328fFilteringDataBaseDynamicPortMembers OBJECT-TYPE
   SYNTAX      DisplayString
   MAX-ACCESS  read-only
   STATUS      current
   DESCRIPTION
       "The ports that are members of the entry."
   ::= { gs2328fFilteringDataBaseDynamicMACEntry 5 }


gs2328fSFlowAgent                                                  OBJECT IDENTIFIER ::= { gs2328fConfiguration 22 }

gs2328fSFlowAgentCollector                                            OBJECT IDENTIFIER ::= { gs2328fSFlowAgent 1 }

gs2328fSFlowAgentReceiverMode OBJECT-TYPE
   SYNTAX      INTEGER { disable(0), enable(1) }
   MAX-ACCESS  read-write
   STATUS      current
   DESCRIPTION
       "default: 0
       0: disable
       1: enable "
   ::= { gs2328fSFlowAgentCollector 1 }


gs2328fLMC                                                   OBJECT IDENTIFIER ::= { gs2328fConfiguration 1500 }

gs2328fLMCOperating OBJECT-TYPE
   SYNTAX      INTEGER { disabled(0), enabled(1), try(2) }
   MAX-ACCESS  read-write
   STATUS      current
   DESCRIPTION
       "0: disabled
        1: enabled
        2: try"
   ::= { gs2328fLMC 1 }

gs2328fLMCConfigViaDhcp OBJECT-TYPE
   SYNTAX      INTEGER { disabled(0), enabled(1) }
   MAX-ACCESS  read-write
   STATUS      current
   DESCRIPTION
       "0: disabled
        1: enabled"
   ::= { gs2328fLMC 2 }

gs2328fLMCDomain OBJECT-TYPE
   SYNTAX      DisplayString(SIZE(0..255))
   MAX-ACCESS  read-write
   STATUS      current
   DESCRIPTION
       "0: disabled
        1: enabled"
   ::= { gs2328fLMC 3 }

gs2328fLMChcpClientAutoRenew OBJECT-TYPE
   SYNTAX      INTEGER { disabled(0), enabled(1) }
   MAX-ACCESS  read-write
   STATUS      current
   DESCRIPTION
       "0: disabled
        1: enabled"
   ::= { gs2328fLMC 4 }


gs2328fLMCZeroTouchSupport OBJECT-TYPE
   SYNTAX      INTEGER { No(0), Yes(1) }
   MAX-ACCESS  read-only
   STATUS      current
   DESCRIPTION
       "0: No
        1: Yes"
   ::= { gs2328fLMC 50 }

gs2328fLMCPairingTokenPresent OBJECT-TYPE
   SYNTAX      INTEGER { No(0), Yes(1) }
   MAX-ACCESS  read-only
   STATUS      current
   DESCRIPTION
       "0: No
        1: Yes"
   ::= { gs2328fLMC 51 }

gs2328fLMCClientStatus OBJECT-TYPE
   SYNTAX      DisplayString
   MAX-ACCESS  read-only
   STATUS      current
   DESCRIPTION
           ""
   ::= { gs2328fLMC  52 }


gs2328fLMCManagementStatus OBJECT-TYPE
   SYNTAX      INTEGER {Unpaired(0), Paired(1), PairedAndClaimed(14)}
   MAX-ACCESS  read-only
   STATUS      current
   DESCRIPTION
           "0: Unpaired
            1: Paired
            14: PairedAndClaimed"
   ::= { gs2328fLMC  53 }

gs2328fLMCControlStatus OBJECT-TYPE
   SYNTAX      INTEGER {Disabled(2), Operating(4)}
   MAX-ACCESS  read-only
   STATUS      current
   DESCRIPTION
           "2: Disabled
            4: Operating"
   ::= { gs2328fLMC  54 }

gs2328fLMCMonitoringStatus OBJECT-TYPE
   SYNTAX      INTEGER {Disabled(2), Operating(4)}
   MAX-ACCESS  read-only
   STATUS      current
   DESCRIPTION
           "2: Disabled
            4: Operating"
   ::= { gs2328fLMC  55 }

gs2328fLMCConfigurationSource OBJECT-TYPE
   SYNTAX      DisplayString
   MAX-ACCESS  read-only
   STATUS      current
   DESCRIPTION
           ""
   ::= { gs2328fLMC  56 }

gs2328fLMCConfigModified OBJECT-TYPE
   SYNTAX      INTEGER { No(0), Yes(1) }
   MAX-ACCESS  read-only
   STATUS      current
   DESCRIPTION
       "0: No
        1: Yes"
   ::= { gs2328fLMC 57 }

gs2328fLMCDeviceID OBJECT-TYPE
   SYNTAX      DisplayString
   MAX-ACCESS  read-only
   STATUS      current
   DESCRIPTION
           ""
   ::= { gs2328fLMC  58 }

gs2328fLMCRoundTripTime OBJECT-TYPE
   SYNTAX      INTEGER
   MAX-ACCESS  read-only
   STATUS      current
   DESCRIPTION
           ""
   ::= { gs2328fLMC  100 }
----------------------------------------------------------------------------------------------------------------------------
gs2328fSecurity                                              OBJECT IDENTIFIER ::= { lancomGS2328F  3 }

gs2328fIPSourceGuard                                         OBJECT IDENTIFIER ::= { gs2328fSecurity 1 }

gs2328fIPSourceGuardConf                                     OBJECT IDENTIFIER ::= { gs2328fIPSourceGuard 1 }

gs2328fIPSourceGuardMode OBJECT-TYPE
   SYNTAX      INTEGER { disable(0), enable(1) }
   MAX-ACCESS  read-write
   STATUS      current
   DESCRIPTION
       " default:  0
        0: disable
        1: enable"
   ::= { gs2328fIPSourceGuardConf 1 }

gs2328fIPSourceGuardPortConfigTable OBJECT-TYPE
   SYNTAX      SEQUENCE OF GS2328FIPSourceGuardPortConfigEntry
   MAX-ACCESS  not-accessible
   STATUS      current
   DESCRIPTION
       " "
   ::= { gs2328fIPSourceGuardConf 2 }

gs2328fIPSourceGuardPortConfigEntry OBJECT-TYPE
   SYNTAX      GS2328FIPSourceGuardPortConfigEntry
   MAX-ACCESS  not-accessible
   STATUS      current
   DESCRIPTION
       ""
   INDEX    { gs2328fIPSourceGuardPortConfigPort  }
   ::= { gs2328fIPSourceGuardPortConfigTable 1 }

GS2328FIPSourceGuardPortConfigEntry ::= SEQUENCE {
   gs2328fIPSourceGuardPortConfigPort               Integer32,
   gs2328fIPSourceGuardPortConfigMode               INTEGER,
   gs2328fIPSourceGuardPortMaxDynamicClients        Integer32
}

gs2328fIPSourceGuardPortConfigPort OBJECT-TYPE
   SYNTAX      Integer32(1..4095)
   MAX-ACCESS  not-accessible
   STATUS      current
   DESCRIPTION
       " "
   ::= { gs2328fIPSourceGuardPortConfigEntry 1 }

gs2328fIPSourceGuardPortConfigMode OBJECT-TYPE
   SYNTAX      INTEGER { disable(0), enable(1) }
   MAX-ACCESS  read-write
   STATUS      current
   DESCRIPTION
       "default: 0
       0:disable
       1:enable "
   ::= { gs2328fIPSourceGuardPortConfigEntry 2 }

gs2328fIPSourceGuardPortMaxDynamicClients OBJECT-TYPE
   SYNTAX      Integer32(0..2|99)
   MAX-ACCESS  read-write
   STATUS      current
   DESCRIPTION
       "default: 99
       0~2: Max Dynamic clients
       99:Unlimited "
   ::= { gs2328fIPSourceGuardPortConfigEntry 3 }


gs2328fIPSourceGuardStatic                                OBJECT IDENTIFIER ::= { gs2328fIPSourceGuard 2 }

gs2328fIPSourceGuardStaticCreate OBJECT-TYPE
   SYNTAX       INTEGER { none(0), create(1) }
   MAX-ACCESS   read-write
   STATUS       current
   DESCRIPTION
       "default: 0
        0 : None  (read only)
        1 : Create a IP Source Guard"
   ::= { gs2328fIPSourceGuardStatic 1 }

gs2328fIPSourceGuardStaticTable OBJECT-TYPE
   SYNTAX      SEQUENCE OF GS2328FIPSourceGuardStaticEntry
   MAX-ACCESS  not-accessible
   STATUS      current
   DESCRIPTION
       " "
   ::= { gs2328fIPSourceGuardStatic 2 }

gs2328fIPSourceGuardStaticEntry OBJECT-TYPE
   SYNTAX      GS2328FIPSourceGuardStaticEntry
   MAX-ACCESS  not-accessible
   STATUS      current
   DESCRIPTION
       ""
   INDEX    { gs2328fIPSourceGuardStaticIndex  }
   ::= { gs2328fIPSourceGuardStaticTable 1 }

GS2328FIPSourceGuardStaticEntry ::= SEQUENCE {
   gs2328fIPSourceGuardStaticIndex         Integer32,
   gs2328fIPSourceGuardStaticPort          Integer32,
   gs2328fIPSourceGuardStaticVLANId        Integer32,
   gs2328fIPSourceGuardStaticIPAddress     IpAddress,
   gs2328fIPSourceGuardStaticMACAddress    MacAddress,
   gs2328fIPSourceGuardStaticRowStatus     INTEGER
}

gs2328fIPSourceGuardStaticIndex OBJECT-TYPE
   SYNTAX      Integer32(1..28)
   MAX-ACCESS  not-accessible
   STATUS      current
   DESCRIPTION
       " "
   ::= { gs2328fIPSourceGuardStaticEntry 1 }

gs2328fIPSourceGuardStaticPort OBJECT-TYPE
   SYNTAX      Integer32(1..4095)
   MAX-ACCESS  read-write
   STATUS      current
   DESCRIPTION
       " Port, range: 1 - port number. "
   ::= { gs2328fIPSourceGuardStaticEntry 2 }

gs2328fIPSourceGuardStaticVLANId OBJECT-TYPE
   SYNTAX      Integer32(1..4094)
   MAX-ACCESS  read-write
   STATUS      current
   DESCRIPTION
       " VLAN ID, range: 1 - 4094. "
   ::= { gs2328fIPSourceGuardStaticEntry 3 }

gs2328fIPSourceGuardStaticIPAddress OBJECT-TYPE
   SYNTAX      IpAddress
   MAX-ACCESS  read-write
   STATUS      current
   DESCRIPTION
       " IP address allowed for doing IP source guard. "
   ::= { gs2328fIPSourceGuardStaticEntry 4 }

gs2328fIPSourceGuardStaticMACAddress OBJECT-TYPE
   SYNTAX      MacAddress
   MAX-ACCESS  read-write
   STATUS      current
   DESCRIPTION
       " Allowed Source MAC address, format 0a 1b 2c 3d 4e 5f "
   ::= { gs2328fIPSourceGuardStaticEntry 5 }

gs2328fIPSourceGuardStaticRowStatus OBJECT-TYPE
   SYNTAX      INTEGER { active(1), notInservice(2), edit(3), destroy(4), undo(5) }
   MAX-ACCESS  read-write
   STATUS      current
   DESCRIPTION
       "1: active
        2: notInservice
        3: edit
        4: destroy
        5: undo"
   ::= { gs2328fIPSourceGuardStaticEntry 6 }

gs2328fIPSourceGuardDynamicTable OBJECT-TYPE
   SYNTAX      SEQUENCE OF GS2328FIPSourceGuardDynamicEntry
   MAX-ACCESS  not-accessible
   STATUS      current
   DESCRIPTION
       " "
   ::= { gs2328fIPSourceGuard 3 }

gs2328fIPSourceGuardDynamicEntry OBJECT-TYPE
   SYNTAX      GS2328FIPSourceGuardDynamicEntry
   MAX-ACCESS  not-accessible
   STATUS      current
   DESCRIPTION
       ""
   INDEX    { gs2328fIPSourceGuardDynamicIndex  }
   ::= { gs2328fIPSourceGuardDynamicTable 1 }

GS2328FIPSourceGuardDynamicEntry ::= SEQUENCE {
   gs2328fIPSourceGuardDynamicIndex          Integer32,
   gs2328fIPSourceGuardDynamicPort           Integer32,
   gs2328fIPSourceGuardDynamicVLANId         Integer32,
   gs2328fIPSourceGuardDynamicIPAddress      IpAddress,
   gs2328fIPSourceGuardDynamicMACAddress     MacAddress
}

gs2328fIPSourceGuardDynamicIndex OBJECT-TYPE
   SYNTAX      Integer32(1..4095)
   MAX-ACCESS  not-accessible
   STATUS      current
   DESCRIPTION
       " "
   ::= { gs2328fIPSourceGuardDynamicEntry 1 }

gs2328fIPSourceGuardDynamicPort OBJECT-TYPE
   SYNTAX      Integer32(1..10)
   MAX-ACCESS  read-only
   STATUS      current
   DESCRIPTION
       " "
   ::= { gs2328fIPSourceGuardDynamicEntry 2 }

gs2328fIPSourceGuardDynamicVLANId OBJECT-TYPE
   SYNTAX      Integer32(1..4094)
   MAX-ACCESS  read-only
   STATUS      current
   DESCRIPTION
       " "
   ::= { gs2328fIPSourceGuardDynamicEntry 3 }

gs2328fIPSourceGuardDynamicIPAddress OBJECT-TYPE
   SYNTAX      IpAddress
   MAX-ACCESS  read-only
   STATUS      current
   DESCRIPTION
       " "
   ::= { gs2328fIPSourceGuardDynamicEntry 4 }

gs2328fIPSourceGuardDynamicMACAddress OBJECT-TYPE
   SYNTAX      MacAddress
   MAX-ACCESS  read-only
   STATUS      current
   DESCRIPTION
       " "
   ::= { gs2328fIPSourceGuardDynamicEntry 5 }

gs2328fARPInspection                                         OBJECT IDENTIFIER ::= { gs2328fSecurity 2 }

gs2328fARPInspectionConf                                     OBJECT IDENTIFIER ::= { gs2328fARPInspection 1 }

gs2328fARPInspectionConfMode OBJECT-TYPE
   SYNTAX      INTEGER { disable(0), enable(1) }
   MAX-ACCESS  read-write
   STATUS      current
   DESCRIPTION
       "default: 0
        0: disable
        1: enable"
   ::= { gs2328fARPInspectionConf 1 }

gs2328fARPInspectionConfTable OBJECT-TYPE
   SYNTAX      SEQUENCE OF GS2328FARPInspectionConfEntry
   MAX-ACCESS  not-accessible
   STATUS      current
   DESCRIPTION
       " "
   ::= { gs2328fARPInspectionConf 2 }

gs2328fARPInspectionConfEntry OBJECT-TYPE
   SYNTAX      GS2328FARPInspectionConfEntry
   MAX-ACCESS  not-accessible
   STATUS      current
   DESCRIPTION
       ""
   INDEX    { gs2328fARPInspectionConfPortIndex  }
   ::= { gs2328fARPInspectionConfTable 1 }

GS2328FARPInspectionConfEntry ::= SEQUENCE {
   gs2328fARPInspectionConfPortIndex	Integer32,
   gs2328fARPInspectionConfPortMode	INTEGER
}

gs2328fARPInspectionConfPortIndex OBJECT-TYPE
   SYNTAX      Integer32(1..4095)
   MAX-ACCESS  not-accessible
   STATUS      current
   DESCRIPTION
       " "
   ::= { gs2328fARPInspectionConfEntry 1 }

gs2328fARPInspectionConfPortMode OBJECT-TYPE
   SYNTAX      INTEGER { disable(0), enable(1) }
   MAX-ACCESS  read-write
   STATUS      current
   DESCRIPTION
       "default: 0
        0: disable
        1: enable"
   ::= { gs2328fARPInspectionConfEntry 2 }


gs2328fARPInspectionStatic                                OBJECT IDENTIFIER ::= { gs2328fARPInspection 2 }

gs2328fARPInspectionStaticCreate OBJECT-TYPE
   SYNTAX      INTEGER { none(0), create(1) }
   MAX-ACCESS  read-write
   STATUS      current
   DESCRIPTION
       "default: 0
        0: none
        1: create"
   ::= { gs2328fARPInspectionStatic 1 }

gs2328fARPInspectionStaticTable OBJECT-TYPE
   SYNTAX      SEQUENCE OF GS2328FARPInspectionStaticEntry
   MAX-ACCESS  not-accessible
   STATUS      current
   DESCRIPTION
       " "
   ::= { gs2328fARPInspectionStatic 2 }

gs2328fARPInspectionStaticEntry OBJECT-TYPE
   SYNTAX      GS2328FARPInspectionStaticEntry
   MAX-ACCESS  not-accessible
   STATUS      current
   DESCRIPTION
       ""
   INDEX    { gs2328fARPInspectionStaticIndex  }
   ::= { gs2328fARPInspectionStaticTable 1 }

GS2328FARPInspectionStaticEntry ::= SEQUENCE {
   gs2328fARPInspectionStaticIndex       Integer32,
   gs2328fARPInspectionStaticPort        Integer32,
   gs2328fARPInspectionStaticVLANId      Integer32,
   gs2328fARPInspectionStaticIPAddress   IpAddress,
   gs2328fARPInspectionStaticMACAddress  MacAddress,
   gs2328fARPInspectionStaticRowStatus   INTEGER
}

gs2328fARPInspectionStaticIndex OBJECT-TYPE
   SYNTAX      Integer32(1..4095)
   MAX-ACCESS  not-accessible
   STATUS      current
   DESCRIPTION
       ""
   ::= { gs2328fARPInspectionStaticEntry 1 }

gs2328fARPInspectionStaticPort OBJECT-TYPE
   SYNTAX      Integer32(1..4095)
   MAX-ACCESS  read-write
   STATUS      current
   DESCRIPTION
       " Port, range: 1 - port number. "
   ::= { gs2328fARPInspectionStaticEntry 2 }

gs2328fARPInspectionStaticVLANId OBJECT-TYPE
   SYNTAX      Integer32(1..4094)
   MAX-ACCESS  read-write
   STATUS      current
   DESCRIPTION
       " VLAN ID, range: 1 - 4094. "
   ::= { gs2328fARPInspectionStaticEntry 3 }

gs2328fARPInspectionStaticIPAddress OBJECT-TYPE
   SYNTAX      IpAddress
   MAX-ACCESS  read-write
   STATUS      current
   DESCRIPTION
       " IP address allowed for doing ARP request. "
   ::= { gs2328fARPInspectionStaticEntry 4 }

gs2328fARPInspectionStaticMACAddress OBJECT-TYPE
   SYNTAX      MacAddress
   MAX-ACCESS  read-write
   STATUS      current
   DESCRIPTION
       " Allowed Source MAC address in ARP request packets, format 0a 1b 2c 3d 4e 5f "
   ::= { gs2328fARPInspectionStaticEntry 5 }

gs2328fARPInspectionStaticRowStatus OBJECT-TYPE
   SYNTAX     INTEGER { active(1), notInservice(2), edit(3), destroy(4), undo(5) }
   MAX-ACCESS  read-write
   STATUS      current
   DESCRIPTION
       "1: active
        2: notInservice
        3: edit
        4: destroy
        5: undo"
   ::= { gs2328fARPInspectionStaticEntry 6 }

gs2328fARPInspectionDynamicTable OBJECT-TYPE
   SYNTAX      SEQUENCE OF GS2328FARPInspectionDynamicEntry
   MAX-ACCESS  not-accessible
   STATUS      current
   DESCRIPTION
       " "
   ::= { gs2328fARPInspection 3 }

gs2328fARPInspectionDynamicEntry OBJECT-TYPE
   SYNTAX      GS2328FARPInspectionDynamicEntry
   MAX-ACCESS  not-accessible
   STATUS      current
   DESCRIPTION
       ""
   INDEX    { gs2328fARPInspectionDynamicIndex  }
   ::= { gs2328fARPInspectionDynamicTable 1 }

GS2328FARPInspectionDynamicEntry ::= SEQUENCE {
   gs2328fARPInspectionDynamicIndex          Integer32,
   gs2328fARPInspectionDynamicPort           Integer32,
   gs2328fARPInspectionDynamicVLANId         Integer32,
   gs2328fARPInspectionDynamicIPAddress      IpAddress,
   gs2328fARPInspectionDynamicMACAddress     MacAddress
}

gs2328fARPInspectionDynamicIndex OBJECT-TYPE
   SYNTAX      Integer32(1..4095)
   MAX-ACCESS  not-accessible
   STATUS      current
   DESCRIPTION
       " "
   ::= { gs2328fARPInspectionDynamicEntry 1 }

gs2328fARPInspectionDynamicPort OBJECT-TYPE
   SYNTAX      Integer32(1..4095)
   MAX-ACCESS  read-only
   STATUS      current
   DESCRIPTION
       ""
   ::= { gs2328fARPInspectionDynamicEntry 2 }

gs2328fARPInspectionDynamicVLANId OBJECT-TYPE
   SYNTAX      Integer32(1..4094)
   MAX-ACCESS  read-only
   STATUS      current
   DESCRIPTION
       ""
   ::= { gs2328fARPInspectionDynamicEntry 3 }

gs2328fARPInspectionDynamicIPAddress OBJECT-TYPE
   SYNTAX      IpAddress
   MAX-ACCESS  read-only
   STATUS      current
   DESCRIPTION
       ""
   ::= { gs2328fARPInspectionDynamicEntry 4 }

gs2328fARPInspectionDynamicMACAddress OBJECT-TYPE
   SYNTAX      MacAddress
   MAX-ACCESS  read-only
   STATUS      current
   DESCRIPTION
       ""
   ::= { gs2328fARPInspectionDynamicEntry 5 }

gs2328fARPStaticGatewayCtrl	                                OBJECT IDENTIFIER ::= { gs2328fARPInspection 6 }

gs2328fARPStaticGatewayCtrlSystemConf                                      OBJECT IDENTIFIER ::= { gs2328fARPStaticGatewayCtrl 1 }

gs2328fARPStaticGatewayCtrlMode OBJECT-TYPE
   SYNTAX      INTEGER { disable(0), enable(1) }
   MAX-ACCESS  read-write
   STATUS      current
   DESCRIPTION
       "default: 0
       0: disable
       1: enable "
   ::= { gs2328fARPStaticGatewayCtrlSystemConf 1 }

gs2328fARPStaticGatewayCtrlCreate OBJECT-TYPE
   SYNTAX      INTEGER { none(0), create(1) }
   MAX-ACCESS  read-write
   STATUS      current
   DESCRIPTION
       "default: 0
        0: none
        1: create"
   ::= { gs2328fARPStaticGatewayCtrl 2 }

gs2328fARPStaticGatewayCtrlTable OBJECT-TYPE
   SYNTAX      SEQUENCE OF GS2328FARPStaticGatewayCtrlEntry
   MAX-ACCESS  not-accessible
   STATUS      current
   DESCRIPTION
       " "
   ::= { gs2328fARPStaticGatewayCtrl 3 }

gs2328fARPStaticGatewayCtrlEntry OBJECT-TYPE
   SYNTAX      GS2328FARPStaticGatewayCtrlEntry
   MAX-ACCESS  not-accessible
   STATUS      current
   DESCRIPTION
       ""
   INDEX    { gs2328fARPStaticGatewayCtrlIndex  }
   ::= { gs2328fARPStaticGatewayCtrlTable 1 }

GS2328FARPStaticGatewayCtrlEntry ::= SEQUENCE {
   gs2328fARPStaticGatewayCtrlIndex       Integer32,
   gs2328fARPStaticGatewayCtrlIPAddress   IpAddress,
   gs2328fARPStaticGatewayCtrlMACAddress  MacAddress,
   gs2328fARPStaticGatewayCtrlPort        Integer32,
   gs2328fARPStaticGatewayCtrlAction      INTEGER,
   gs2328fARPStaticGatewayCtrlState       DisplayString,
   gs2328fARPStaticGatewayCtrlReOpen      INTEGER,
   gs2328fARPStaticGatewayCtrlRowStatus   INTEGER
}

gs2328fARPStaticGatewayCtrlIndex OBJECT-TYPE
   SYNTAX      Integer32(1..4)
   MAX-ACCESS  not-accessible
   STATUS      current
   DESCRIPTION
       ""
   ::= { gs2328fARPStaticGatewayCtrlEntry 1 }

gs2328fARPStaticGatewayCtrlIPAddress OBJECT-TYPE
   SYNTAX      IpAddress
   MAX-ACCESS  read-write
   STATUS      current
   DESCRIPTION
       " Source IP address. "
   ::= { gs2328fARPStaticGatewayCtrlEntry 2 }

gs2328fARPStaticGatewayCtrlMACAddress OBJECT-TYPE
   SYNTAX      MacAddress
   MAX-ACCESS  read-write
   STATUS      current
   DESCRIPTION
       " Source MAC address , format 0a 1b 2c 3d 4e 5f "
   ::= { gs2328fARPStaticGatewayCtrlEntry 3 }

gs2328fARPStaticGatewayCtrlPort OBJECT-TYPE
   SYNTAX      Integer32(1..4095)
   MAX-ACCESS  read-write
   STATUS      current
   DESCRIPTION
       " Port, range: 1 - port number. "
   ::= { gs2328fARPStaticGatewayCtrlEntry 4 }

gs2328fARPStaticGatewayCtrlAction OBJECT-TYPE
   SYNTAX      INTEGER {none(0),trap(1),dropAndTrap(2), shutdown(3), trapAndShutdown(4) }
   MAX-ACCESS  read-write
   STATUS      current
   DESCRIPTION
       "default: 0
       0: none
       1: trap
       2: drop&trap
       3: shutdown
       4: trap&shutdown"
   ::= { gs2328fARPStaticGatewayCtrlEntry 5 }

gs2328fARPStaticGatewayCtrlState OBJECT-TYPE
   SYNTAX      DisplayString
   MAX-ACCESS  read-only
   STATUS      current
   DESCRIPTION
       ""
   ::= { gs2328fARPStaticGatewayCtrlEntry 6 }

gs2328fARPStaticGatewayCtrlReOpen OBJECT-TYPE
   SYNTAX      INTEGER { none(0), reopen(1) }
   MAX-ACCESS  read-write
   STATUS      current
   DESCRIPTION
       "default: 0
       0: none
       1: reopen"
   ::= { gs2328fARPStaticGatewayCtrlEntry 7 }

gs2328fARPStaticGatewayCtrlRowStatus OBJECT-TYPE
   SYNTAX      INTEGER { active(1), notInservice(2), edit(3), destroy(4), undo(5) }
   MAX-ACCESS  read-write
   STATUS      current
   DESCRIPTION
       "1: active
        2: notInservice
        3: edit
        4: destroy
        5: undo"
   ::= { gs2328fARPStaticGatewayCtrlEntry 8 }

gs2328fARPSpoofingPrevention	                                OBJECT IDENTIFIER ::= { gs2328fARPInspection 7 }

gs2328fARPSpoofingPreventionSystemConf                                      OBJECT IDENTIFIER ::= { gs2328fARPSpoofingPrevention 1 }

gs2328fARPSpoofingPreventionMode OBJECT-TYPE
   SYNTAX      INTEGER { disable(0), enable(1) }
   MAX-ACCESS  read-write
   STATUS      current
   DESCRIPTION
       "default: 0
       0: disable
       1: enable "
   ::= { gs2328fARPSpoofingPreventionSystemConf 1 }

gs2328fARPSpoofingPreventionTable OBJECT-TYPE
   SYNTAX      SEQUENCE OF GS2328FARPSpoofingPreventionEntry
   MAX-ACCESS  not-accessible
   STATUS      current
   DESCRIPTION
       " "
   ::= { gs2328fARPSpoofingPrevention 2 }

gs2328fARPSpoofingPreventionEntry OBJECT-TYPE
   SYNTAX      GS2328FARPSpoofingPreventionEntry
   MAX-ACCESS  not-accessible
   STATUS      current
   DESCRIPTION
       ""
   INDEX    { gs2328fARPSpoofingPreventionPort  }
   ::= { gs2328fARPSpoofingPreventionTable 1 }

GS2328FARPSpoofingPreventionEntry ::= SEQUENCE {
   gs2328fARPSpoofingPreventionPort           Integer32,
   gs2328fARPSpoofingPreventionPortMode       INTEGER,
   gs2328fARPSpoofingPreventionPortLimit      Integer32,
   gs2328fARPSpoofingPreventionPortAction     INTEGER,
   gs2328fARPSpoofingPreventionPortState      DisplayString,
   gs2328fARPSpoofingPreventionPortReOpen     INTEGER
}

gs2328fARPSpoofingPreventionPort OBJECT-TYPE
   SYNTAX      Integer32(1..4095)
   MAX-ACCESS  not-accessible
   STATUS      current
   DESCRIPTION
       " "
   ::= { gs2328fARPSpoofingPreventionEntry 1 }

gs2328fARPSpoofingPreventionPortMode OBJECT-TYPE
   SYNTAX      INTEGER { disable(0), enable(1) }
   MAX-ACCESS  read-write
   STATUS      current
   DESCRIPTION
       "default: 0
       0: disable
       1: enable"
   ::= { gs2328fARPSpoofingPreventionEntry 2 }

gs2328fARPSpoofingPreventionPortLimit OBJECT-TYPE
   SYNTAX      Integer32(1..100)
   MAX-ACCESS  read-write
   STATUS      current
   DESCRIPTION
       "default: 1, range: 1-100"
   ::= { gs2328fARPSpoofingPreventionEntry 3 }

gs2328fARPSpoofingPreventionPortAction OBJECT-TYPE
   SYNTAX      INTEGER { none(0), trap(1), dropAndTrap(2), shutdown(3), trapAndShutdown(4) }
   MAX-ACCESS  read-write
   STATUS      current
   DESCRIPTION
       "default: 0
       0: none
       1: trap
       2: drop&trap
       3: shutdown
       4: trap&shutdown"
   ::= { gs2328fARPSpoofingPreventionEntry 4 }

gs2328fARPSpoofingPreventionPortState OBJECT-TYPE
   SYNTAX      DisplayString
   MAX-ACCESS  read-only
   STATUS      current
   DESCRIPTION
       ""
   ::= { gs2328fARPSpoofingPreventionEntry 5 }

gs2328fARPSpoofingPreventionPortReOpen OBJECT-TYPE
   SYNTAX      INTEGER { none(0), reopen(1) }
   MAX-ACCESS  read-write
   STATUS      current
   DESCRIPTION
       "default: 0
       0: none
       1: reopen"
   ::= { gs2328fARPSpoofingPreventionEntry 6 }

gs2328fARPIPDoSPrevention	                                OBJECT IDENTIFIER ::= { gs2328fARPInspection 8 }

gs2328fARPIPDoSPreventionTCPMode OBJECT-TYPE
   SYNTAX      INTEGER { disable(0), enable(1) }
   MAX-ACCESS  read-write
   STATUS      current
   DESCRIPTION
       "default: 0
       0: disable
       1: enable "
   ::= { gs2328fARPIPDoSPrevention 1 }

gs2328fARPIPDoSPreventionUDPMode OBJECT-TYPE
   SYNTAX      INTEGER { disable(0), enable(1) }
   MAX-ACCESS  read-write
   STATUS      current
   DESCRIPTION
       "default: 0
       0: disable
       1: enable "
   ::= { gs2328fARPIPDoSPrevention 2 }

gs2328fARPIPDoSPreventionICMPMode OBJECT-TYPE
   SYNTAX      INTEGER { disable(0), enable(1) }
   MAX-ACCESS  read-write
   STATUS      current
   DESCRIPTION
       "default: 0
       0: disable
       1: enable "
   ::= { gs2328fARPIPDoSPrevention 3 }

gs2328fARPIPDoSPreventionServerPort1 OBJECT-TYPE
   SYNTAX      Integer32(0..4094)
   MAX-ACCESS  read-write
   STATUS      current
   DESCRIPTION
       " Port, range: 0 - port number. 0: none. "
   ::= { gs2328fARPIPDoSPrevention 4 }

gs2328fARPIPDoSPreventionServerPort2 OBJECT-TYPE
   SYNTAX      Integer32(0..4094)
   MAX-ACCESS  read-write
   STATUS      current
   DESCRIPTION
       " Port, range: 0 - port number. 0: none. "
   ::= { gs2328fARPIPDoSPrevention 5 }

gs2328fARPIPDoSPreventionServerPort3 OBJECT-TYPE
   SYNTAX      Integer32(0..4094)
   MAX-ACCESS  read-write
   STATUS      current
   DESCRIPTION
       " Port, range: 0 - port number. 0: none. "
   ::= { gs2328fARPIPDoSPrevention 6 }

gs2328fARPIPDoSPreventionServerPort4 OBJECT-TYPE
   SYNTAX      Integer32(0..4094)
   MAX-ACCESS  read-write
   STATUS      current
   DESCRIPTION
       " Port, range: 0 - port number. 0: none. "
   ::= { gs2328fARPIPDoSPrevention 7 }

gs2328fDHCPSnooping                                          OBJECT IDENTIFIER ::= { gs2328fSecurity 3 }

gs2328fDHCPSnoopingConf                                          OBJECT IDENTIFIER ::= { gs2328fDHCPSnooping 1 }

gs2328fDHCPSnoopingMode OBJECT-TYPE
   SYNTAX      INTEGER { disable(0), enable(1) }
   MAX-ACCESS  read-write
   STATUS      current
   DESCRIPTION
       "default: 0
       0: disable
       1: enable"
   ::= { gs2328fDHCPSnoopingConf 1 }

gs2328fDHCPSnoopingPortModeConfigurationTable OBJECT-TYPE
   SYNTAX      SEQUENCE OF GS2328FDHCPSnoopingPortModeConfigurationEntry
   MAX-ACCESS  not-accessible
   STATUS      current
   DESCRIPTION
       " "
   ::= { gs2328fDHCPSnoopingConf 2 }

gs2328fDHCPSnoopingPortModeConfigurationEntry OBJECT-TYPE
   SYNTAX      GS2328FDHCPSnoopingPortModeConfigurationEntry
   MAX-ACCESS  not-accessible
   STATUS      current
   DESCRIPTION
       ""
   INDEX    { gs2328fDHCPSnoopingPortModeConfigurationPort  }
   ::= { gs2328fDHCPSnoopingPortModeConfigurationTable 1 }

GS2328FDHCPSnoopingPortModeConfigurationEntry ::= SEQUENCE {
   gs2328fDHCPSnoopingPortModeConfigurationPort	Integer32,
   gs2328fDHCPSnoopingPortModeConfigurationMode	INTEGER
}

gs2328fDHCPSnoopingPortModeConfigurationPort OBJECT-TYPE
   SYNTAX      Integer32(1..4095)
   MAX-ACCESS  not-accessible
   STATUS      current
   DESCRIPTION
       " "
   ::= { gs2328fDHCPSnoopingPortModeConfigurationEntry 1 }

gs2328fDHCPSnoopingPortModeConfigurationMode OBJECT-TYPE
   SYNTAX      INTEGER { trust(0), untrust(1) }
   MAX-ACCESS  read-write
   STATUS      current
   DESCRIPTION
       "default: 1
       0: trust port mode
       1: untrust port mode"
   ::= { gs2328fDHCPSnoopingPortModeConfigurationEntry 2 }

gs2328fDHCPSnoopingStatisticsTable OBJECT-TYPE
   SYNTAX      SEQUENCE OF GS2328FDHCPSnoopingStatisticsEntry
   MAX-ACCESS  not-accessible
   STATUS      current
   DESCRIPTION
       " "
   ::= { gs2328fDHCPSnooping 2 }

gs2328fDHCPSnoopingStatisticsEntry OBJECT-TYPE
   SYNTAX      GS2328FDHCPSnoopingStatisticsEntry
   MAX-ACCESS  not-accessible
   STATUS      current
   DESCRIPTION
       ""
   INDEX    { gs2328fDHCPSnoopingStatisticsPort  }
   ::= { gs2328fDHCPSnoopingStatisticsTable 1 }

GS2328FDHCPSnoopingStatisticsEntry ::= SEQUENCE {
   gs2328fDHCPSnoopingStatisticsPort         Integer32,
   gs2328fDHCPSnoopingStatisticsClear        INTEGER,
   gs2328fDHCPSnoopingRxDiscover             Counter32,
   gs2328fDHCPSnoopingRxOffer                Counter32,
   gs2328fDHCPSnoopingRxRequest              Counter32,
   gs2328fDHCPSnoopingRxDecline              Counter32,
   gs2328fDHCPSnoopingRxACK                  Counter32,
   gs2328fDHCPSnoopingRxNAK                  Counter32,
   gs2328fDHCPSnoopingRxRelease              Counter32,
   gs2328fDHCPSnoopingRxInform               Counter32,
   gs2328fDHCPSnoopingRxLeaseQuery           Counter32,
   gs2328fDHCPSnoopingRxLeaseUnassigned      Counter32,
   gs2328fDHCPSnoopingRxLeaseUnknown         Counter32,
   gs2328fDHCPSnoopingRxLeaseActive          Counter32,
   gs2328fDHCPSnoopingTxDiscover             Counter32,
   gs2328fDHCPSnoopingTxOffer                Counter32,
   gs2328fDHCPSnoopingTxRequest              Counter32,
   gs2328fDHCPSnoopingTxDecline              Counter32,
   gs2328fDHCPSnoopingTxACK                  Counter32,
   gs2328fDHCPSnoopingTxNAK                  Counter32,
   gs2328fDHCPSnoopingTxRelease              Counter32,
   gs2328fDHCPSnoopingTxInform               Counter32,
   gs2328fDHCPSnoopingTxLeaseQuery           Counter32,
   gs2328fDHCPSnoopingTxLeaseUnassigned      Counter32,
   gs2328fDHCPSnoopingTxLeaseUnknown         Counter32,
   gs2328fDHCPSnoopingTxLeaseActive          Counter32
}

gs2328fDHCPSnoopingStatisticsPort OBJECT-TYPE
   SYNTAX      Integer32(1..4095)
   MAX-ACCESS  not-accessible
   STATUS      current
   DESCRIPTION
       " "
   ::= { gs2328fDHCPSnoopingStatisticsEntry 1 }

gs2328fDHCPSnoopingStatisticsClear OBJECT-TYPE
   SYNTAX      INTEGER { none(0), clear(1) }
   MAX-ACCESS  read-write
   STATUS      current
   DESCRIPTION
       "default: 0
       0: none
       1: clear"
   ::= { gs2328fDHCPSnoopingStatisticsEntry 2 }

gs2328fDHCPSnoopingRxDiscover OBJECT-TYPE
   SYNTAX      Counter32
   MAX-ACCESS  read-only
   STATUS      current
   DESCRIPTION
       " "
   ::= { gs2328fDHCPSnoopingStatisticsEntry 3 }

gs2328fDHCPSnoopingRxOffer OBJECT-TYPE
   SYNTAX      Counter32
   MAX-ACCESS  read-only
   STATUS      current
   DESCRIPTION
       " "
   ::= { gs2328fDHCPSnoopingStatisticsEntry 4 }

gs2328fDHCPSnoopingRxRequest OBJECT-TYPE
   SYNTAX      Counter32
   MAX-ACCESS  read-only
   STATUS      current
   DESCRIPTION
       " "
   ::= { gs2328fDHCPSnoopingStatisticsEntry 5 }

gs2328fDHCPSnoopingRxDecline OBJECT-TYPE
   SYNTAX      Counter32
   MAX-ACCESS  read-only
   STATUS      current
   DESCRIPTION
       " "
   ::= { gs2328fDHCPSnoopingStatisticsEntry 6 }

gs2328fDHCPSnoopingRxACK OBJECT-TYPE
   SYNTAX      Counter32
   MAX-ACCESS  read-only
   STATUS      current
   DESCRIPTION
       " "
   ::= { gs2328fDHCPSnoopingStatisticsEntry 7 }

gs2328fDHCPSnoopingRxNAK OBJECT-TYPE
   SYNTAX      Counter32
   MAX-ACCESS  read-only
   STATUS      current
   DESCRIPTION
       " "
   ::= { gs2328fDHCPSnoopingStatisticsEntry 8 }

gs2328fDHCPSnoopingRxRelease OBJECT-TYPE
   SYNTAX      Counter32
   MAX-ACCESS  read-only
   STATUS      current
   DESCRIPTION
       " "
   ::= { gs2328fDHCPSnoopingStatisticsEntry 9 }

gs2328fDHCPSnoopingRxInform OBJECT-TYPE
   SYNTAX      Counter32
   MAX-ACCESS  read-only
   STATUS      current
   DESCRIPTION
       " "
   ::= { gs2328fDHCPSnoopingStatisticsEntry 10 }

gs2328fDHCPSnoopingRxLeaseQuery OBJECT-TYPE
   SYNTAX      Counter32
   MAX-ACCESS  read-only
   STATUS      current
   DESCRIPTION
       " "
   ::= { gs2328fDHCPSnoopingStatisticsEntry 11 }

gs2328fDHCPSnoopingRxLeaseUnassigned OBJECT-TYPE
   SYNTAX      Counter32
   MAX-ACCESS  read-only
   STATUS      current
   DESCRIPTION
       " "
   ::= { gs2328fDHCPSnoopingStatisticsEntry 12 }

gs2328fDHCPSnoopingRxLeaseUnknown OBJECT-TYPE
   SYNTAX      Counter32
   MAX-ACCESS  read-only
   STATUS      current
   DESCRIPTION
       " "
   ::= { gs2328fDHCPSnoopingStatisticsEntry 13 }

gs2328fDHCPSnoopingRxLeaseActive OBJECT-TYPE
   SYNTAX      Counter32
   MAX-ACCESS  read-only
   STATUS      current
   DESCRIPTION
       " "
   ::= { gs2328fDHCPSnoopingStatisticsEntry 14 }

gs2328fDHCPSnoopingTxDiscover OBJECT-TYPE
   SYNTAX      Counter32
   MAX-ACCESS  read-only
   STATUS      current
   DESCRIPTION
       " "
   ::= { gs2328fDHCPSnoopingStatisticsEntry 15 }

gs2328fDHCPSnoopingTxOffer OBJECT-TYPE
   SYNTAX      Counter32
   MAX-ACCESS  read-only
   STATUS      current
   DESCRIPTION
       " "
   ::= { gs2328fDHCPSnoopingStatisticsEntry 16 }

gs2328fDHCPSnoopingTxRequest OBJECT-TYPE
   SYNTAX      Counter32
   MAX-ACCESS  read-only
   STATUS      current
   DESCRIPTION
       " "
   ::= { gs2328fDHCPSnoopingStatisticsEntry 17 }

gs2328fDHCPSnoopingTxDecline OBJECT-TYPE
   SYNTAX      Counter32
   MAX-ACCESS  read-only
   STATUS      current
   DESCRIPTION
       " "
   ::= { gs2328fDHCPSnoopingStatisticsEntry 18 }

gs2328fDHCPSnoopingTxACK OBJECT-TYPE
   SYNTAX      Counter32
   MAX-ACCESS  read-only
   STATUS      current
   DESCRIPTION
       " "
   ::= { gs2328fDHCPSnoopingStatisticsEntry 19 }

gs2328fDHCPSnoopingTxNAK OBJECT-TYPE
   SYNTAX      Counter32
   MAX-ACCESS  read-only
   STATUS      current
   DESCRIPTION
       " "
   ::= { gs2328fDHCPSnoopingStatisticsEntry 20 }

gs2328fDHCPSnoopingTxRelease OBJECT-TYPE
   SYNTAX      Counter32
   MAX-ACCESS  read-only
   STATUS      current
   DESCRIPTION
       " "
   ::= { gs2328fDHCPSnoopingStatisticsEntry 21 }

gs2328fDHCPSnoopingTxInform OBJECT-TYPE
   SYNTAX      Counter32
   MAX-ACCESS  read-only
   STATUS      current
   DESCRIPTION
       " "
   ::= { gs2328fDHCPSnoopingStatisticsEntry 22 }

gs2328fDHCPSnoopingTxLeaseQuery OBJECT-TYPE
   SYNTAX      Counter32
   MAX-ACCESS  read-only
   STATUS      current
   DESCRIPTION
       " "
   ::= { gs2328fDHCPSnoopingStatisticsEntry 23 }

gs2328fDHCPSnoopingTxLeaseUnassigned OBJECT-TYPE
   SYNTAX      Counter32
   MAX-ACCESS  read-only
   STATUS      current
   DESCRIPTION
       " "
   ::= { gs2328fDHCPSnoopingStatisticsEntry 24 }

gs2328fDHCPSnoopingTxLeaseUnknown OBJECT-TYPE
   SYNTAX      Counter32
   MAX-ACCESS  read-only
   STATUS      current
   DESCRIPTION
       " "
   ::= { gs2328fDHCPSnoopingStatisticsEntry 25 }

gs2328fDHCPSnoopingTxLeaseActive OBJECT-TYPE
   SYNTAX      Counter32
   MAX-ACCESS  read-only
   STATUS      current
   DESCRIPTION
       " "
   ::= { gs2328fDHCPSnoopingStatisticsEntry 26 }


gs2328fDHCPRelay                                             OBJECT IDENTIFIER ::= { gs2328fSecurity 4 }

gs2328fDHCPRelayConfiguration                                         OBJECT IDENTIFIER ::= { gs2328fDHCPRelay 1 }

gs2328fDHCPRelayMode OBJECT-TYPE
   SYNTAX      INTEGER { disable(0), enable(1) }
   MAX-ACCESS  read-write
   STATUS      current
   DESCRIPTION
       "default: 0
       0: disable
       1: enable
       We need at least one server"
   ::= { gs2328fDHCPRelayConfiguration 1 }

gs2328fDHCPRelayServer OBJECT-TYPE
   SYNTAX      IpAddress
   MAX-ACCESS  read-write
   STATUS      current
   DESCRIPTION
       " "
   ::= { gs2328fDHCPRelayConfiguration 2 }

gs2328fDHCPRelayInformationMode OBJECT-TYPE
   SYNTAX      INTEGER { disable(0), enable(1) }
   MAX-ACCESS  read-write
   STATUS      current
   DESCRIPTION
       "default: 0
       0: disable
       1: enable "
   ::= { gs2328fDHCPRelayConfiguration 3 }

gs2328fDHCPRelayInformationPolicy OBJECT-TYPE
   SYNTAX      INTEGER { replace(0), keep(1), drop(2) }
   MAX-ACCESS  read-write
   STATUS      current
   DESCRIPTION
       "default: 0
       0: replace
       1: keep
       2: drop "
   ::= { gs2328fDHCPRelayConfiguration 4 }

gs2328fDHCPRelayInformationCustom OBJECT-TYPE
   SYNTAX      DisplayString(SIZE(0..32))
   MAX-ACCESS  read-write
   STATUS      current
   DESCRIPTION
       "DHCP Option 82 Circuit ID custom information"
   ::= { gs2328fDHCPRelayConfiguration 1500 }

gs2328fDHCPRelayConfigurationGateways                                          OBJECT IDENTIFIER ::= { gs2328fDHCPRelayConfiguration 5 }

gs2328fDHCPRelayConfigurationGatewaysCreate OBJECT-TYPE
   SYNTAX       INTEGER { none(0), create(1) }
   MAX-ACCESS   read-write
   STATUS       current
   DESCRIPTION
       "default: 0
        0 : None  (read only)
        1 : Create entry"
   ::= { gs2328fDHCPRelayConfigurationGateways 1 }

gs2328fDHCPRelayConfigurationGatewaysTable OBJECT-TYPE
   SYNTAX      SEQUENCE OF Gs2328fDHCPRelayConfigurationGatewaysEntry
   MAX-ACCESS  not-accessible
   STATUS      current
   DESCRIPTION
       " Create DHCP Relay Gateway IP address entry."
   ::= { gs2328fDHCPRelayConfigurationGateways 2 }

gs2328fDHCPRelayConfigurationGatewaysEntry OBJECT-TYPE
   SYNTAX      Gs2328fDHCPRelayConfigurationGatewaysEntry
   MAX-ACCESS  not-accessible
   STATUS      current
   DESCRIPTION
       ""
   INDEX    { gs2328fDHCPRelayConfigurationGatewaysIndex  }
   ::= { gs2328fDHCPRelayConfigurationGatewaysTable 1 }

Gs2328fDHCPRelayConfigurationGatewaysEntry ::= SEQUENCE {
   gs2328fDHCPRelayConfigurationGatewaysIndex           Integer32,
   gs2328fDHCPRelayConfigurationGatewaysVLANId          Integer32,
   gs2328fDHCPRelayConfigurationGatewaysIP              IpAddress,
   gs2328fDHCPRelayConfigurationGatewaysRowStatus       INTEGER
}

gs2328fDHCPRelayConfigurationGatewaysIndex OBJECT-TYPE
   SYNTAX      Integer32(1..6)
   MAX-ACCESS  not-accessible
   STATUS      current
   DESCRIPTION
       " "
   ::= { gs2328fDHCPRelayConfigurationGatewaysEntry 1 }

gs2328fDHCPRelayConfigurationGatewaysVLANId OBJECT-TYPE
   SYNTAX      Integer32(1..4094)
   MAX-ACCESS  read-write
   STATUS      current
   DESCRIPTION
       " VLAN ID "
   ::= { gs2328fDHCPRelayConfigurationGatewaysEntry 2 }

gs2328fDHCPRelayConfigurationGatewaysIP OBJECT-TYPE
   SYNTAX      IpAddress
   MAX-ACCESS  read-write
   STATUS      current
   DESCRIPTION
       "DHCP GIADDR address."
   ::= { gs2328fDHCPRelayConfigurationGatewaysEntry 3 }

gs2328fDHCPRelayConfigurationGatewaysRowStatus OBJECT-TYPE
   SYNTAX      INTEGER { active(1), notInservice(2), destroy(4), undo(5) }
   MAX-ACCESS  read-write
   STATUS      current
   DESCRIPTION
       "1: active
        2: notInservice
        4: destroy
        5: undo"
   ::= { gs2328fDHCPRelayConfigurationGatewaysEntry 4 }

gs2328fDHCPRelayStatistics                                   OBJECT IDENTIFIER ::= { gs2328fDHCPRelay 2 }

gs2328fDHCPRelayServerStatistics                                   OBJECT IDENTIFIER ::= { gs2328fDHCPRelayStatistics 1 }

gs2328fServerStatTransmitToServer OBJECT-TYPE
   SYNTAX      Counter32
   MAX-ACCESS  read-only
   STATUS      current
   DESCRIPTION
       " "
   ::= { gs2328fDHCPRelayServerStatistics 1 }

gs2328fServerStatTransmitError OBJECT-TYPE
   SYNTAX      Counter32
   MAX-ACCESS  read-only
   STATUS      current
   DESCRIPTION
       " "
   ::= { gs2328fDHCPRelayServerStatistics 2 }

gs2328fServerStatReceiveFromServer OBJECT-TYPE
   SYNTAX      Counter32
   MAX-ACCESS  read-only
   STATUS      current
   DESCRIPTION
       " "
   ::= { gs2328fDHCPRelayServerStatistics 3 }

gs2328fServerStatReceiveMissingAgentOption OBJECT-TYPE
   SYNTAX      Counter32
   MAX-ACCESS  read-only
   STATUS      current
   DESCRIPTION
       " "
   ::= { gs2328fDHCPRelayServerStatistics 4 }

gs2328fServerStatReceiveMissingCircuitID OBJECT-TYPE
   SYNTAX      Counter32
   MAX-ACCESS  read-only
   STATUS      current
   DESCRIPTION
       " "
   ::= { gs2328fDHCPRelayServerStatistics 5 }

gs2328fServerStatReceiveMissingRemoteID OBJECT-TYPE
   SYNTAX      Counter32
   MAX-ACCESS  read-only
   STATUS      current
   DESCRIPTION
       " "
   ::= { gs2328fDHCPRelayServerStatistics 6 }

gs2328fServerStatReceiveBadCircuitID OBJECT-TYPE
   SYNTAX      Counter32
   MAX-ACCESS  read-only
   STATUS      current
   DESCRIPTION
       " "
   ::= { gs2328fDHCPRelayServerStatistics 7 }

gs2328fServerStatReceiveBadRemoteID OBJECT-TYPE
   SYNTAX      Counter32
   MAX-ACCESS  read-only
   STATUS      current
   DESCRIPTION
       " "
   ::= { gs2328fDHCPRelayServerStatistics 8 }

gs2328fDHCPRelayClientStatistics                                   OBJECT IDENTIFIER ::= { gs2328fDHCPRelayStatistics 2 }

gs2328fClientStatTransmitToClient OBJECT-TYPE
   SYNTAX      Counter32
   MAX-ACCESS  read-only
   STATUS      current
   DESCRIPTION
       " "
   ::= { gs2328fDHCPRelayClientStatistics 1 }

gs2328fClientStatTransmitError OBJECT-TYPE
   SYNTAX      Counter32
   MAX-ACCESS  read-only
   STATUS      current
   DESCRIPTION
       " "
   ::= { gs2328fDHCPRelayClientStatistics 2 }

gs2328fClientStatReceivefromClient OBJECT-TYPE
   SYNTAX      Counter32
   MAX-ACCESS  read-only
   STATUS      current
   DESCRIPTION
       " "
   ::= { gs2328fDHCPRelayClientStatistics 3 }

gs2328fClientStatReceiveAgentOption OBJECT-TYPE
   SYNTAX      Counter32
   MAX-ACCESS  read-only
   STATUS      current
   DESCRIPTION
       " "
   ::= { gs2328fDHCPRelayClientStatistics 4 }

gs2328fClientStatReplaceAgentOption OBJECT-TYPE
   SYNTAX      Counter32
   MAX-ACCESS  read-only
   STATUS      current
   DESCRIPTION
       " "
   ::= { gs2328fDHCPRelayClientStatistics 5 }

gs2328fClientStatKeepAgentOption OBJECT-TYPE
   SYNTAX      Counter32
   MAX-ACCESS  read-only
   STATUS      current
   DESCRIPTION
       " "
   ::= { gs2328fDHCPRelayClientStatistics 6 }

gs2328fClientStatDropAgentOption OBJECT-TYPE
   SYNTAX      Counter32
   MAX-ACCESS  read-only
   STATUS      current
   DESCRIPTION
       " "
   ::= { gs2328fDHCPRelayClientStatistics 7 }

gs2328fPortSecurity                                          OBJECT IDENTIFIER ::= { gs2328fSecurity 5 }

gs2328fPortSecLimitCtrl                                      OBJECT IDENTIFIER ::= { gs2328fPortSecurity 1 }

gs2328fPortSecLimitCtrlSystemConf                                      OBJECT IDENTIFIER ::= { gs2328fPortSecLimitCtrl 1 }

gs2328fPortSecurityMode OBJECT-TYPE
   SYNTAX      INTEGER { disable(0), enable(1) }
   MAX-ACCESS  read-write
   STATUS      current
   DESCRIPTION
       "default: 0
       0: disable
       1: enable "
   ::= { gs2328fPortSecLimitCtrlSystemConf 1 }

gs2328fPortSecurityAging OBJECT-TYPE
   SYNTAX      INTEGER { disable(0), enable(1) }
   MAX-ACCESS  read-write
   STATUS      current
   DESCRIPTION
       "default: 0
       0: disable
       1: enable "
   ::= { gs2328fPortSecLimitCtrlSystemConf 2 }

gs2328fPortSecurityAgingPeriod OBJECT-TYPE
   SYNTAX      INTEGER(10..10000000)
   MAX-ACCESS  read-write
   STATUS      current
   DESCRIPTION
       "default: 3600, range: 10-10000000 "
   ::= { gs2328fPortSecLimitCtrlSystemConf 3 }

gs2328fPortSecLimitCtrlTable OBJECT-TYPE
   SYNTAX      SEQUENCE OF GS2328FPortSecLimitCtrlEntry
   MAX-ACCESS  not-accessible
   STATUS      current
   DESCRIPTION
       " "
   ::= { gs2328fPortSecLimitCtrl 2 }

gs2328fPortSecLimitCtrlEntry OBJECT-TYPE
   SYNTAX      GS2328FPortSecLimitCtrlEntry
   MAX-ACCESS  not-accessible
   STATUS      current
   DESCRIPTION
       ""
   INDEX    { gs2328fPortSecLimitCtrlPort  }
   ::= { gs2328fPortSecLimitCtrlTable 1 }

GS2328FPortSecLimitCtrlEntry ::= SEQUENCE {
   gs2328fPortSecLimitCtrlPort           Integer32,
   gs2328fPortSecLimitCtrlPortMode       INTEGER,
   gs2328fPortSecLimitCtrlPortLimit      Integer32,
   gs2328fPortSecLimitCtrlPortAction     INTEGER,
   gs2328fPortSecLimitCtrlPortState      DisplayString,
   gs2328fPortSecLimitCtrlPortReOpen     INTEGER
}

gs2328fPortSecLimitCtrlPort OBJECT-TYPE
   SYNTAX      Integer32(1..4095)
   MAX-ACCESS  not-accessible
   STATUS      current
   DESCRIPTION
       " "
   ::= { gs2328fPortSecLimitCtrlEntry 1 }

gs2328fPortSecLimitCtrlPortMode OBJECT-TYPE
   SYNTAX      INTEGER { disable(0), enable(1) }
   MAX-ACCESS  read-write
   STATUS      current
   DESCRIPTION
       "default: 0
       0: disable
       1: enable"
   ::= { gs2328fPortSecLimitCtrlEntry 2 }

gs2328fPortSecLimitCtrlPortLimit OBJECT-TYPE
   SYNTAX      Integer32(1..1024)
   MAX-ACCESS  read-write
   STATUS      current
   DESCRIPTION
       "default: 4, range: 1-1024"
   ::= { gs2328fPortSecLimitCtrlEntry 3 }

gs2328fPortSecLimitCtrlPortAction OBJECT-TYPE
   SYNTAX      INTEGER { none(0), trap(1), shutdown(2), trapShutdown(3) }
   MAX-ACCESS  read-write
   STATUS      current
   DESCRIPTION
       "default: 0
       0: none
       1: trap
       2: shutdown
       3: trap&shutdown"
   ::= { gs2328fPortSecLimitCtrlEntry 4 }

gs2328fPortSecLimitCtrlPortState OBJECT-TYPE
   SYNTAX      DisplayString
   MAX-ACCESS  read-only
   STATUS      current
   DESCRIPTION
       ""
   ::= { gs2328fPortSecLimitCtrlEntry 5 }

gs2328fPortSecLimitCtrlPortReOpen OBJECT-TYPE
   SYNTAX      INTEGER { none(0), reopen(1) }
   MAX-ACCESS  read-write
   STATUS      current
   DESCRIPTION
       "default: 0
       0: none
       1: reopen"
   ::= { gs2328fPortSecLimitCtrlEntry 6 }

gs2328fPortSecSwitchStatusTable OBJECT-TYPE
   SYNTAX      SEQUENCE OF GS2328FPortSecSwitchStatusEntry
   MAX-ACCESS  not-accessible
   STATUS      current
   DESCRIPTION
       " "
   ::= { gs2328fPortSecurity 2 }

gs2328fPortSecSwitchStatusEntry OBJECT-TYPE
   SYNTAX      GS2328FPortSecSwitchStatusEntry
   MAX-ACCESS  not-accessible
   STATUS      current
   DESCRIPTION
       ""
   INDEX    { gs2328fPortSecSwitchStatusPort  }
   ::= { gs2328fPortSecSwitchStatusTable 1 }

GS2328FPortSecSwitchStatusEntry ::= SEQUENCE {
   gs2328fPortSecSwitchStatusPort                Integer32,
   gs2328fPortSecSwitchStatusUsers               DisplayString,
   gs2328fPortSecSwitchStatusState               DisplayString,
   gs2328fPortSecSwitchStatusMACCountCurrent     Integer32,
   gs2328fPortSecSwitchStatusMACCountLimit       Integer32
}

gs2328fPortSecSwitchStatusPort OBJECT-TYPE
   SYNTAX      Integer32(1..4095)
   MAX-ACCESS  not-accessible
   STATUS      current
   DESCRIPTION
       " "
   ::= { gs2328fPortSecSwitchStatusEntry 1 }

gs2328fPortSecSwitchStatusUsers OBJECT-TYPE
   SYNTAX      DisplayString
   MAX-ACCESS  read-only
   STATUS      current
   DESCRIPTION
       " Users Abbr: L = Limit Control, 8 = 802.1X, D = DHCP Snooping, V = Voice VLAN,
         '-' means that the corresponding user module is not enabled. "
   ::= { gs2328fPortSecSwitchStatusEntry 2 }

gs2328fPortSecSwitchStatusState OBJECT-TYPE
   SYNTAX      DisplayString
   MAX-ACCESS  read-only
   STATUS      current
   DESCRIPTION
       " Shows the current state of the port : Disabled, Ready, Limit Reached, Shutdown. "
   ::= { gs2328fPortSecSwitchStatusEntry 3 }

gs2328fPortSecSwitchStatusMACCountCurrent OBJECT-TYPE
   SYNTAX      Integer32(1..4095)
   MAX-ACCESS  read-only
   STATUS      current
   DESCRIPTION
       ""
   ::= { gs2328fPortSecSwitchStatusEntry 4 }

gs2328fPortSecSwitchStatusMACCountLimit OBJECT-TYPE
   SYNTAX      Integer32(1..4095)
   MAX-ACCESS  read-only
   STATUS      current
   DESCRIPTION
       ""
   ::= { gs2328fPortSecSwitchStatusEntry 5 }

gs2328fPortSecPortStatus                                      OBJECT IDENTIFIER ::= { gs2328fPortSecurity 3 }

gs2328fPortSecPortStatusPort OBJECT-TYPE
   SYNTAX       Integer32(1..4095)
   MAX-ACCESS   read-write
   STATUS       current
   DESCRIPTION
       "port number
        default: 1
        range: 1 - port number."
   ::= { gs2328fPortSecPortStatus 1 }

gs2328fPortSecPortStatusTable OBJECT-TYPE
   SYNTAX      SEQUENCE OF GS2328FPortSecPortStatusEntry
   MAX-ACCESS  not-accessible
   STATUS      current
   DESCRIPTION
      " "
   ::= { gs2328fPortSecPortStatus 2 }

gs2328fPortSecPortStatusEntry OBJECT-TYPE
   SYNTAX      GS2328FPortSecPortStatusEntry
   MAX-ACCESS  not-accessible
   STATUS      current
   DESCRIPTION
       ""
   INDEX    { gs2328fPortSecPortStatusIndex  }
   ::= { gs2328fPortSecPortStatusTable 1 }

GS2328FPortSecPortStatusEntry ::= SEQUENCE {
   gs2328fPortSecPortStatusIndex              Integer32,
   gs2328fPortSecPortStatusMACAddress         MacAddress,
   gs2328fPortSecPortStatusVLANId             Integer32,
   gs2328fPortSecPortStatusState              DisplayString,
   gs2328fPortSecPortStatusTimeOfAddition     DisplayString,
   gs2328fPortSecPortStatusAgeAndHold         DisplayString
}

gs2328fPortSecPortStatusIndex OBJECT-TYPE
   SYNTAX      Integer32(1..4095)
   MAX-ACCESS  not-accessible
   STATUS      current
   DESCRIPTION
       " "
   ::= { gs2328fPortSecPortStatusEntry 1 }

gs2328fPortSecPortStatusMACAddress OBJECT-TYPE
   SYNTAX      MacAddress
   MAX-ACCESS  read-only
   STATUS      current
   DESCRIPTION
       " "
   ::= { gs2328fPortSecPortStatusEntry 2 }

gs2328fPortSecPortStatusVLANId OBJECT-TYPE
   SYNTAX      Integer32(1..4094)
   MAX-ACCESS  read-only
   STATUS      current
   DESCRIPTION
       " "
   ::= { gs2328fPortSecPortStatusEntry 3 }

gs2328fPortSecPortStatusState OBJECT-TYPE
   SYNTAX      DisplayString
   MAX-ACCESS  read-only
   STATUS      current
   DESCRIPTION
       "Blocked / Forwarding "
   ::= { gs2328fPortSecPortStatusEntry 4 }

gs2328fPortSecPortStatusTimeOfAddition OBJECT-TYPE
   SYNTAX      DisplayString
   MAX-ACCESS  read-only
   STATUS      current
   DESCRIPTION
       " "
   ::= { gs2328fPortSecPortStatusEntry 5 }

gs2328fPortSecPortStatusAgeAndHold OBJECT-TYPE
   SYNTAX      DisplayString
   MAX-ACCESS  read-only
   STATUS      current
   DESCRIPTION
       " "
   ::= { gs2328fPortSecPortStatusEntry 6 }


gs2328fAccessManagement                                      OBJECT IDENTIFIER ::= { gs2328fSecurity 6 }

gs2328fAccessMgtConf                                         OBJECT IDENTIFIER ::= { gs2328fAccessManagement 1 }

gs2328fAccessMgtConfMode OBJECT-TYPE
   SYNTAX      INTEGER { disable(0), enable(1) }
   MAX-ACCESS  read-write
   STATUS      current
   DESCRIPTION
       "default: 0
       0: disable
       1: enable "
   ::= { gs2328fAccessMgtConf 1 }

gs2328fAccessMgtConfCreate OBJECT-TYPE
   SYNTAX      INTEGER { none(0), create(1) }
   MAX-ACCESS  read-write
   STATUS      current
   DESCRIPTION
       "default: 0
       0: none
       1: create "
   ::= { gs2328fAccessMgtConf 2 }

gs2328fAccessMgtConfTable OBJECT-TYPE
   SYNTAX      SEQUENCE OF GS2328FAccessMgtConfEntry
   MAX-ACCESS  not-accessible
   STATUS      current
   DESCRIPTION
       " "
   ::= { gs2328fAccessMgtConf 3 }

gs2328fAccessMgtConfEntry OBJECT-TYPE
   SYNTAX      GS2328FAccessMgtConfEntry
   MAX-ACCESS  not-accessible
   STATUS      current
   DESCRIPTION
       ""
   INDEX    { gs2328fAccessMgtIndex  }
   ::= { gs2328fAccessMgtConfTable 1 }

GS2328FAccessMgtConfEntry ::= SEQUENCE {
   gs2328fAccessMgtIndex             Integer32,
   gs2328fAccessMgtAddresstype       INTEGER,
   gs2328fAccessMgtStartIpAddress    DisplayString,
   gs2328fAccessMgtEndIpAddress      DisplayString,
   gs2328fAccessMgtHttpHttps         INTEGER,
   gs2328fAccessMgtSNMP              INTEGER,
   gs2328fAccessMgtTelnetSSH         INTEGER,
   gs2328fAccessMgtRowStatus         INTEGER
}

gs2328fAccessMgtIndex OBJECT-TYPE
   SYNTAX      Integer32(1..16)
   MAX-ACCESS  read-write
   STATUS      current
   DESCRIPTION
       "Set Access Management config index
        range : 1-16."
   ::= { gs2328fAccessMgtConfEntry 1 }

gs2328fAccessMgtAddresstype OBJECT-TYPE
   SYNTAX      INTEGER { ipv4(0), ipv6(1) }
   MAX-ACCESS  read-write
   STATUS      current
   DESCRIPTION
       "0: ipv4
        1: ipv6 "
   ::= { gs2328fAccessMgtConfEntry 2 }

gs2328fAccessMgtStartIpAddress OBJECT-TYPE
   SYNTAX      DisplayString
   MAX-ACCESS  read-write
   STATUS      current
   DESCRIPTION
       " Start IP address.
         IP address doesn't allowed all zero or all 'ff'H."
   ::= { gs2328fAccessMgtConfEntry 3 }

gs2328fAccessMgtEndIpAddress OBJECT-TYPE
   SYNTAX      DisplayString
   MAX-ACCESS  read-write
   STATUS      current
   DESCRIPTION
       " End IP address.
         IP address doesn't allowed all zero or all 'ff'H.
         End ip address is not less than start ip address."
   ::= { gs2328fAccessMgtConfEntry 4 }

gs2328fAccessMgtHttpHttps OBJECT-TYPE
   SYNTAX      INTEGER { disable(0), enable(1) }
   MAX-ACCESS  read-write
   STATUS      current
   DESCRIPTION
       "default: 0
       0: disable
       1: enable "
   ::= { gs2328fAccessMgtConfEntry 5 }

gs2328fAccessMgtSNMP OBJECT-TYPE
   SYNTAX      INTEGER { disable(0), enable(1) }
   MAX-ACCESS  read-write
   STATUS      current
   DESCRIPTION
       "default: 0
       0: disable
       1: enable "
   ::= { gs2328fAccessMgtConfEntry 6 }

gs2328fAccessMgtTelnetSSH OBJECT-TYPE
   SYNTAX      INTEGER { disable(0), enable(1) }
   MAX-ACCESS  read-write
   STATUS      current
   DESCRIPTION
       "default: 0
       0: disable
       1: enable "
   ::= { gs2328fAccessMgtConfEntry 7 }

gs2328fAccessMgtRowStatus OBJECT-TYPE
   SYNTAX      INTEGER { active(1), notInservice(2), edit(3),destroy(4), undo(5) }
   MAX-ACCESS  read-write
   STATUS      current
   DESCRIPTION
       "1: active
        2: notInservice
        3: edit
        4: destroy
        5: undo"
   ::= { gs2328fAccessMgtConfEntry 8 }

gs2328fAccessMgtStatistics                                   OBJECT IDENTIFIER ::= { gs2328fAccessManagement 2 }

gs2328fHttpReceivedPkts OBJECT-TYPE
   SYNTAX      Counter32
   MAX-ACCESS  read-only
   STATUS      current
   DESCRIPTION
       " "
   ::= { gs2328fAccessMgtStatistics 1 }

gs2328fHttpAllowedPkts OBJECT-TYPE
   SYNTAX      Counter32
   MAX-ACCESS  read-only
   STATUS      current
   DESCRIPTION
       " "
   ::= { gs2328fAccessMgtStatistics 2 }

gs2328fHttpDiscardedPkts OBJECT-TYPE
   SYNTAX      Counter32
   MAX-ACCESS  read-only
   STATUS      current
   DESCRIPTION
       " "
   ::= { gs2328fAccessMgtStatistics 3 }

gs2328fHttpsReceivedPkts OBJECT-TYPE
   SYNTAX      Counter32
   MAX-ACCESS  read-only
   STATUS      current
   DESCRIPTION
       " "
   ::= { gs2328fAccessMgtStatistics 4 }

gs2328fHttpsAllowedPkts OBJECT-TYPE
   SYNTAX      Counter32
   MAX-ACCESS  read-only
   STATUS      current
   DESCRIPTION
       " "
   ::= { gs2328fAccessMgtStatistics 5 }

gs2328fHttpsDiscardedPkts OBJECT-TYPE
   SYNTAX      Counter32
   MAX-ACCESS  read-only
   STATUS      current
   DESCRIPTION
       " "
   ::= { gs2328fAccessMgtStatistics 6 }

gs2328fSnmpReceivedPkts OBJECT-TYPE
   SYNTAX      Counter32
   MAX-ACCESS  read-only
   STATUS      current
   DESCRIPTION
       " "
   ::= { gs2328fAccessMgtStatistics 7 }

gs2328fSnmpAllowedPkts OBJECT-TYPE
   SYNTAX      Counter32
   MAX-ACCESS  read-only
   STATUS      current
   DESCRIPTION
       " "
   ::= { gs2328fAccessMgtStatistics 8 }

gs2328fSnmpDiscardedPkts OBJECT-TYPE
   SYNTAX      Counter32
   MAX-ACCESS  read-only
   STATUS      current
   DESCRIPTION
       " "
   ::= { gs2328fAccessMgtStatistics 9 }

gs2328fTelnetReceivedPkts OBJECT-TYPE
   SYNTAX      Counter32
   MAX-ACCESS  read-only
   STATUS      current
   DESCRIPTION
       " "
   ::= { gs2328fAccessMgtStatistics 10 }

gs2328fTelnetAllowedPkts OBJECT-TYPE
   SYNTAX      Counter32
   MAX-ACCESS  read-only
   STATUS      current
   DESCRIPTION
       " "
   ::= { gs2328fAccessMgtStatistics 11 }

gs2328fTelnetDiscardedPkts OBJECT-TYPE
   SYNTAX      Counter32
   MAX-ACCESS  read-only
   STATUS      current
   DESCRIPTION
       " "
   ::= { gs2328fAccessMgtStatistics 12 }

gs2328fSSHReceivedPkts OBJECT-TYPE
   SYNTAX      Counter32
   MAX-ACCESS  read-only
   STATUS      current
   DESCRIPTION
       " "
   ::= { gs2328fAccessMgtStatistics 13 }

gs2328fSSHAllowedPkts OBJECT-TYPE
   SYNTAX      Counter32
   MAX-ACCESS  read-only
   STATUS      current
   DESCRIPTION
       " "
   ::= { gs2328fAccessMgtStatistics 14 }

gs2328fSSHDiscardedPkts OBJECT-TYPE
   SYNTAX      Counter32
   MAX-ACCESS  read-only
   STATUS      current
   DESCRIPTION
       " "
   ::= { gs2328fAccessMgtStatistics 15 }

gs2328fAccessMgtStatisticsClearAll OBJECT-TYPE
   SYNTAX      INTEGER { none(0), clear(1) }
   MAX-ACCESS  read-write
   STATUS      current
   DESCRIPTION
       "0: none
        1: clear"
   ::= { gs2328fAccessMgtStatistics 16 }

gs2328fSSH                                                   OBJECT IDENTIFIER ::= { gs2328fSecurity 7 }

gs2328fSSHMode OBJECT-TYPE
   SYNTAX      INTEGER { disable(0), enable(1) }
   MAX-ACCESS  read-write
   STATUS      current
   DESCRIPTION
       "default: 1
        0: disable
        1: enable"
   ::= { gs2328fSSH 1 }

gs2328fHTTPS                                                 OBJECT IDENTIFIER ::= { gs2328fSecurity 8 }

gs2328fHTTPSMode OBJECT-TYPE
   SYNTAX      INTEGER { disable(0), enable(1) }
   MAX-ACCESS  read-write
   STATUS      current
   DESCRIPTION
       "default: 1
        0: disable
        1: enable"
   ::= { gs2328fHTTPS 1 }

gs2328fHTTPSAutoRedirect OBJECT-TYPE
   SYNTAX      INTEGER { disable(0), enable(1) }
   MAX-ACCESS  read-write
   STATUS      current
   DESCRIPTION
       "default: 0
        0: disable
        1: enable"
   ::= { gs2328fHTTPS 2 }

gs2328fHTTPSCertRenew OBJECT-TYPE
   SYNTAX      INTEGER { doNothing(0), renew(1) }
   MAX-ACCESS  read-write
   STATUS      current
   DESCRIPTION
       "default: 0 ,
        0: doNothing
        1: renew"
   ::= { gs2328fHTTPS 3 }

gs2328fHTTPSMinProtoVersion OBJECT-TYPE
   SYNTAX      INTEGER { SSLv3(0), TLSv1(1), TLSv11(2), TLSv12(3)}
   MAX-ACCESS  read-write
   STATUS      current
   DESCRIPTION
       "default: 1
        0: SSLv3
        1: TLSv1
        2: TLSv1.1
        3: TLSv1.2"
   ::= { gs2328fHTTPS 4 }

gs2328fHTTPMode OBJECT-TYPE
   SYNTAX      INTEGER { disable(0), enable(1) }
   MAX-ACCESS  read-write
   STATUS      current
   DESCRIPTION
       "default: 1
        0: disable
        1: enable"
   ::= { gs2328fHTTPS 5 }

gs2328fAuthMethod                                            OBJECT IDENTIFIER ::= { gs2328fSecurity 9 }

gs2328fConsoleAuthMethod OBJECT-TYPE
   SYNTAX      INTEGER { none(0), local(1), radius(2), tacacsplus(3) }
   MAX-ACCESS  read-write
   STATUS      current
   DESCRIPTION
       "default: 1
        0: none
        1: local
        2: RADIUS
        3: TACACS+"
   ::= { gs2328fAuthMethod 1 }

gs2328fConsoleFallback OBJECT-TYPE
   SYNTAX      INTEGER { disable(0), enable(1) }
   MAX-ACCESS  read-write
   STATUS      current
   DESCRIPTION
       "default: 0
        0:disable
        1:enable"
   ::= { gs2328fAuthMethod 2 }

gs2328fTelnetAuthMethod OBJECT-TYPE
   SYNTAX      INTEGER { none(0), local(1), radius(2), tacacsplus(3) }
   MAX-ACCESS  read-write
   STATUS      current
   DESCRIPTION
       "default: 1
        0: none
        1: local
        2: RADIUS
        3: TACACS+"
   ::= { gs2328fAuthMethod 3 }

gs2328fTelnetFallback OBJECT-TYPE
   SYNTAX      INTEGER { disable(0), enable(1) }
   MAX-ACCESS  read-write
   STATUS      current
   DESCRIPTION
       "default: 0
        0:disable
        1:enable"
   ::= { gs2328fAuthMethod 4 }

gs2328fSshAuthMethod OBJECT-TYPE
   SYNTAX      INTEGER { none(0), local(1), radius(2), tacacsplus(3) }
   MAX-ACCESS  read-write
   STATUS      current
   DESCRIPTION
       "default: 1
        0: none
        1: local
        2: RADIUS
        3: TACACS+"
   ::= { gs2328fAuthMethod 5 }

gs2328fSshFallback OBJECT-TYPE
   SYNTAX      INTEGER { disable(0), enable(1) }
   MAX-ACCESS  read-write
   STATUS      current
   DESCRIPTION
       "default: 0
        0:disable
        1:enable"
   ::= { gs2328fAuthMethod 6 }

gs2328fTftpAuthMethod OBJECT-TYPE
   SYNTAX      INTEGER { none(0), local(1), radius(2), tacacsplus(3) }
   MAX-ACCESS  read-write
   STATUS      current
   DESCRIPTION
       "default: 1
        0: none
        1: local
        2: RADIUS
        3: TACACS+"
   ::= { gs2328fAuthMethod 9 }

gs2328fTftpFallback OBJECT-TYPE
   SYNTAX      INTEGER { disable(0), enable(1) }
   MAX-ACCESS  read-write
   STATUS      current
   DESCRIPTION
       "default: 0
        0:disable
        1:enable"
   ::= { gs2328fAuthMethod 10 }

gs2328fLoginFailures OBJECT-TYPE
   SYNTAX      Integer32(0..99)
   MAX-ACCESS  read-write
   STATUS      current
   DESCRIPTION
       "When login failures mechanism is triggered,the lock minutes will prevent to login in this periods.
        The value '0' should deactivate this feature.
        range: 0-99.
        default: 5."
   ::= { gs2328fAuthMethod 11 }

gs2328fLockMinutes OBJECT-TYPE
   SYNTAX      Integer32(1..99)
   MAX-ACCESS  read-write
   STATUS      current
   DESCRIPTION
       "Lock time to login failures trigger.
        range: 1-99.
        default: 5."
   ::= { gs2328fAuthMethod 12 }

gs2328fHttpAuthMethod OBJECT-TYPE
   SYNTAX      INTEGER { none(0), local(1), radius(2), tacacsplus(3) }
   MAX-ACCESS  read-write
   STATUS      current
   DESCRIPTION
       "default: 1
        0: none
        1: local
        2: RADIUS
        3: TACACS+"
   ::= { gs2328fAuthMethod 13 }

gs2328fHttpFallback OBJECT-TYPE
   SYNTAX      INTEGER { disable(0), enable(1) }
   MAX-ACCESS  read-write
   STATUS      current
   DESCRIPTION
       "default: 0
        0:disable
        1:enable"
   ::= { gs2328fAuthMethod 14 }

gs2328fHttpsAuthMethod OBJECT-TYPE
   SYNTAX      INTEGER { none(0), local(1), radius(2), tacacsplus(3) }
   MAX-ACCESS  read-write
   STATUS      current
   DESCRIPTION
       "default: 1
        0: none
        1: local
        2: RADIUS
        3: TACACS+"
   ::= { gs2328fAuthMethod 15 }

gs2328fHttpsFallback OBJECT-TYPE
   SYNTAX      INTEGER { disable(0), enable(1) }
   MAX-ACCESS  read-write
   STATUS      current
   DESCRIPTION
       "default: 0
        0:disable
        1:enable"
   ::= { gs2328fAuthMethod 16 }


gs2328fAAA                                              OBJECT IDENTIFIER ::= { gs2328fSecurity 10 }

gs2328fAAACommonServer                                  OBJECT IDENTIFIER ::= { gs2328fAAA 1 }

gs2328fAAACommonServerTimeout OBJECT-TYPE
   SYNTAX      Integer32(3..3600)
   MAX-ACCESS  read-write
   STATUS      current
   DESCRIPTION
       "The Timeout, which can be set to a number between 3 and 3600 seconds, is
       the maximum time to wait for a reply from a server. If the server does not
       reply within this timeframe, we will consider it to be dead and continue
       with the next enabled server (if any). RADIUS servers are using the UDP
       protocol, which is unreliable by design. In order to cope with lost frames,
       the timeout interval is divided into 3 subintervals of equal length. If a
       reply is not received within the subinterval, the request is transmitted
       again. This algorithm causes the RADIUS server to be queried up to 3 times
       before it is considered to be dead.
        default: 15."
   ::= { gs2328fAAACommonServer 1 }

gs2328fAAACommonServerDeadTime OBJECT-TYPE
   SYNTAX      Integer32(0..3600)
   MAX-ACCESS  read-write
   STATUS      current
   DESCRIPTION
       "The Dead Time, which can be set to a number between 0 and 3600 seconds,
       is the period during which the switch will not send new requests to a
       server that has failed to respond to a previous request. This will stop
       the switch from continually trying to contact a server that it has already
       determined as dead.
       Setting the Dead Time to a value greater than 0 (zero) will enable this feature,
       but only if more than one server has been configured.
       default: 300."
   ::= { gs2328fAAACommonServer 2 }

gs2328fAAATACACSPlusAuthAndAccounting                  OBJECT IDENTIFIER ::= { gs2328fAAA 2 }

gs2328fAAAAuthorization OBJECT-TYPE
   SYNTAX      INTEGER { disable(0), enable(1) }
   MAX-ACCESS  read-write
   STATUS      current
   DESCRIPTION
       "Authorization is the action of determining what a user is allowed to do.
       An authorization request may indicate that the user is not authenticated.
       In this case it is up to the authorization agent to determine if an
       unauthenticated user is allowed the services in question. "
   ::= { gs2328fAAATACACSPlusAuthAndAccounting 1 }

gs2328fAAAFallbackToLocalAuthorization OBJECT-TYPE
   SYNTAX      INTEGER { disable(0), enable(1) }
   MAX-ACCESS  read-write
   STATUS      current
   DESCRIPTION
       "This function is an auxiliary function of Authorization. When the DUT
       cannot communicate with TACACS+ Server normally, it will check the right/
        permission level of the Local Account to execute the Authorization. "
   ::= { gs2328fAAATACACSPlusAuthAndAccounting 2 }

gs2328fAAAAccounting OBJECT-TYPE
   SYNTAX      INTEGER { disable(0), enable(1) }
   MAX-ACCESS  read-write
   STATUS      current
   DESCRIPTION
       "Accounting is typically the third action after authentication and
       authorization. Accounting is the action of recording what a user is doing,
       and/or has done. TACACS+ accounting records contain all the information
       used in the authorization records and resource usage information. "
   ::= { gs2328fAAATACACSPlusAuthAndAccounting 3 }

gs2328fRADIUSAuthenticationServerTable OBJECT-TYPE
   SYNTAX      SEQUENCE OF Gs2328fRADIUSAuthenticationServerEntry
   MAX-ACCESS  not-accessible
   STATUS      current
   DESCRIPTION
       " "
   ::= { gs2328fAAA 3 }

gs2328fRADIUSAuthenticationServerEntry OBJECT-TYPE
   SYNTAX      Gs2328fRADIUSAuthenticationServerEntry
   MAX-ACCESS  not-accessible
   STATUS      current
   DESCRIPTION
       ""
   INDEX    { gs2328fRADIUSAuthenticationServerIndex  }
   ::= { gs2328fRADIUSAuthenticationServerTable 1 }

Gs2328fRADIUSAuthenticationServerEntry ::= SEQUENCE {
   gs2328fRADIUSAuthenticationServerIndex     Integer32,
   gs2328fRADIUSAuthenticationServerEnable    INTEGER,
   gs2328fRADIUSAuthenticationServerIP        DisplayString,
   gs2328fRADIUSAuthenticationServerPort      Integer32,
   gs2328fRADIUSAuthenticationServerSecret    DisplayString
}

gs2328fRADIUSAuthenticationServerIndex OBJECT-TYPE
   SYNTAX      Integer32(1..5)
   MAX-ACCESS  not-accessible
   STATUS      current
   DESCRIPTION
       "RADIUS Authentication Server index
        range : 1-5."
   ::= { gs2328fRADIUSAuthenticationServerEntry 1 }

gs2328fRADIUSAuthenticationServerEnable OBJECT-TYPE
   SYNTAX      INTEGER { disable(0), enable(1) }
   MAX-ACCESS  read-write
   STATUS      current
   DESCRIPTION
       "Enable/Disable the RADIUS Authentication Server. the RADIUSAuthenticationServerEnable
       can be set, when IP and Secret have value "
   ::= { gs2328fRADIUSAuthenticationServerEntry 2 }

gs2328fRADIUSAuthenticationServerIP OBJECT-TYPE
   SYNTAX      DisplayString
   MAX-ACCESS  read-write
   STATUS      current
   DESCRIPTION
       "The IP address or hostname of the RADIUS Authentication Server.
       IP address is expressed in  dotted decimal notation. "
   ::= { gs2328fRADIUSAuthenticationServerEntry 3 }

gs2328fRADIUSAuthenticationServerPort OBJECT-TYPE
   SYNTAX      Integer32(0..65535)
   MAX-ACCESS  read-write
   STATUS      current
   DESCRIPTION
       "The UDP port to use on the RADIUS Authentication Server. If the port is
       set to 0 (zero), the default port (1812) is used on the RADIUS Authentication Server. "
   ::= { gs2328fRADIUSAuthenticationServerEntry 4 }

gs2328fRADIUSAuthenticationServerSecret OBJECT-TYPE
   SYNTAX      DisplayString
   MAX-ACCESS  read-write
   STATUS      current
   DESCRIPTION
       "The secret - up to 64 characters long - shared between the RADIUS Authentication Server and the switch. "
   ::= { gs2328fRADIUSAuthenticationServerEntry 5 }


gs2328fRADIUSAccountingServerTable OBJECT-TYPE
   SYNTAX      SEQUENCE OF Gs2328fRADIUSAccountingServerEntry
   MAX-ACCESS  not-accessible
   STATUS      current
   DESCRIPTION
       " "
   ::= { gs2328fAAA 4 }

gs2328fRADIUSAccountingServerEntry OBJECT-TYPE
   SYNTAX      Gs2328fRADIUSAccountingServerEntry
   MAX-ACCESS  not-accessible
   STATUS      current
   DESCRIPTION
       ""
   INDEX    { gs2328fRADIUSAccountingServerIndex  }
   ::= { gs2328fRADIUSAccountingServerTable 1 }

Gs2328fRADIUSAccountingServerEntry ::= SEQUENCE {
   gs2328fRADIUSAccountingServerIndex     Integer32,
   gs2328fRADIUSAccountingServerEnable    INTEGER,
   gs2328fRADIUSAccountingServerIP        DisplayString,
   gs2328fRADIUSAccountingServerPort      Integer32,
   gs2328fRADIUSAccountingServerSecret    DisplayString
}

gs2328fRADIUSAccountingServerIndex OBJECT-TYPE
   SYNTAX      Integer32(1..5)
   MAX-ACCESS  not-accessible
   STATUS      current
   DESCRIPTION
       "RADIUS Accounting Server index
        range : 1-5."
   ::= { gs2328fRADIUSAccountingServerEntry 1 }

gs2328fRADIUSAccountingServerEnable OBJECT-TYPE
   SYNTAX      INTEGER { disable(0), enable(1) }
   MAX-ACCESS  read-write
   STATUS      current
   DESCRIPTION
       "Enable/Disable the RADIUS Accounting Server. The RADIUSAccountingServerEnable
       can be set, when IP and Secret have value. "
   ::= { gs2328fRADIUSAccountingServerEntry 2 }

gs2328fRADIUSAccountingServerIP OBJECT-TYPE
   SYNTAX      DisplayString
   MAX-ACCESS  read-write
   STATUS      current
   DESCRIPTION
       "The IP address or hostname of the RADIUS Accounting Server.
       IP address is expressed in  dotted decimal notation. "
   ::= { gs2328fRADIUSAccountingServerEntry 3 }

gs2328fRADIUSAccountingServerPort OBJECT-TYPE
   SYNTAX      Integer32(0..65535)
   MAX-ACCESS  read-write
   STATUS      current
   DESCRIPTION
       "The UDP port to use on the RADIUS Accounting Server. If the port is
       set to 0 (zero), the default port (1812) is used on the RADIUS Accounting Server. "
   ::= { gs2328fRADIUSAccountingServerEntry 4 }

gs2328fRADIUSAccountingServerSecret OBJECT-TYPE
   SYNTAX      DisplayString
   MAX-ACCESS  read-write
   STATUS      current
   DESCRIPTION
       "The secret - up to 64 characters long - shared between the RADIUS Accounting Server and the switch. "
   ::= { gs2328fRADIUSAccountingServerEntry 5 }

gs2328fTACACSPlusAuthenticationServerTable OBJECT-TYPE
   SYNTAX      SEQUENCE OF Gs2328fTACACSPlusAuthenticationServerEntry
   MAX-ACCESS  not-accessible
   STATUS      current
   DESCRIPTION
       " "
   ::= { gs2328fAAA 5 }

gs2328fTACACSPlusAuthenticationServerEntry OBJECT-TYPE
   SYNTAX      Gs2328fTACACSPlusAuthenticationServerEntry
   MAX-ACCESS  not-accessible
   STATUS      current
   DESCRIPTION
       ""
   INDEX    { gs2328fTACACSPlusAuthenticationServerIndex  }
   ::= { gs2328fTACACSPlusAuthenticationServerTable 1 }

Gs2328fTACACSPlusAuthenticationServerEntry ::= SEQUENCE {
   gs2328fTACACSPlusAuthenticationServerIndex     Integer32,
   gs2328fTACACSPlusAuthenticationServerEnable    INTEGER,
   gs2328fTACACSPlusAuthenticationServerIP        DisplayString,
   gs2328fTACACSPlusAuthenticationServerPort      Integer32,
   gs2328fTACACSPlusAuthenticationServerSecret    DisplayString
}

gs2328fTACACSPlusAuthenticationServerIndex OBJECT-TYPE
   SYNTAX      Integer32(1..5)
   MAX-ACCESS  not-accessible
   STATUS      current
   DESCRIPTION
       "TACACSPlus Authentication Server index
        range : 1-5."
   ::= { gs2328fTACACSPlusAuthenticationServerEntry 1 }

gs2328fTACACSPlusAuthenticationServerEnable OBJECT-TYPE
   SYNTAX      INTEGER { disable(0), enable(1) }
   MAX-ACCESS  read-write
   STATUS      current
   DESCRIPTION
       "Enable/Disable the TACACSPlus Authentication Server. The
       TACACSPlusAuthenticationServerEnable can be set, when IP and Secret have
       value."
   ::= { gs2328fTACACSPlusAuthenticationServerEntry 2 }

gs2328fTACACSPlusAuthenticationServerIP OBJECT-TYPE
   SYNTAX      DisplayString
   MAX-ACCESS  read-write
   STATUS      current
   DESCRIPTION
       "The IP address or hostname of the TACACSPlus Authentication Server.
       IP address is expressed in  dotted decimal notation. "
   ::= { gs2328fTACACSPlusAuthenticationServerEntry 3 }

gs2328fTACACSPlusAuthenticationServerPort OBJECT-TYPE
   SYNTAX      Integer32(0..65535)
   MAX-ACCESS  read-write
   STATUS      current
   DESCRIPTION
       "The UDP port to use on the TACACSPlus Authentication Server. If the
       port is set to 0 (zero), the default port (1812) is used on the
       TACACSPlus Authentication Server. "
   ::= { gs2328fTACACSPlusAuthenticationServerEntry 4 }

gs2328fTACACSPlusAuthenticationServerSecret OBJECT-TYPE
   SYNTAX      DisplayString
   MAX-ACCESS  read-write
   STATUS      current
   DESCRIPTION
       "The secret - up to 64 characters long - shared between the TACACSPlus Authentication Server and the switch. "
   ::= { gs2328fTACACSPlusAuthenticationServerEntry 5 }


gs2328fRADIUSStatisticsTable OBJECT-TYPE
   SYNTAX      SEQUENCE OF Gs2328fRADIUSStatisticsEntry
   MAX-ACCESS  not-accessible
   STATUS      current
   DESCRIPTION
       " "
   ::= { gs2328fAAA 6 }

gs2328fRADIUSStatisticsEntry OBJECT-TYPE
   SYNTAX      Gs2328fRADIUSStatisticsEntry
   MAX-ACCESS  not-accessible
   STATUS      current
   DESCRIPTION
       ""
   INDEX    { gs2328fRADIUSAuthStatisticsServerIndex  }
   ::= { gs2328fRADIUSStatisticsTable 1 }

Gs2328fRADIUSStatisticsEntry ::= SEQUENCE {
   gs2328fRADIUSAuthStatisticsServerIndex                           Integer32,
   gs2328fRADIUSAuthStatisticsRecPktAccessAccepts                   Counter32,
   gs2328fRADIUSAuthStatisticsRecPktAccessRejects                   Counter32,
   gs2328fRADIUSAuthStatisticsRecPktAccessChallenges                Counter32,
   gs2328fRADIUSAuthStatisticsRecPktMalformedAccResponses           Counter32,
   gs2328fRADIUSAuthStatisticsRecPktBadAuthenticators               Counter32,
   gs2328fRADIUSAuthStatisticsRecPktUnknownTypes                    Counter32,
   gs2328fRADIUSAuthStatisticsRecPktDropped                         Counter32,
   gs2328fRADIUSAuthStatisticsTransmitPktAccessRequests             Counter32,
   gs2328fRADIUSAuthStatisticsTransmitPktAccessRetransmissions      Counter32,
   gs2328fRADIUSAuthStatisticsTransmitPktPendingRequests            Counter32,
   gs2328fRADIUSAuthStatisticsTransmitPktTimeouts                   Counter32,
   gs2328fRADIUSAuthIP                                              DisplayString,
   gs2328fRADIUSAuthState                                           DisplayString,
   gs2328fRADIUSAuthRoundTripTime                                   DisplayString,

   gs2328fRADIUSAccountingStatisticsRecPktResponses                 Counter32,
   gs2328fRADIUSAccountingStatisticsRecPktMalformedResponses        Counter32,
   gs2328fRADIUSAccountingStatisticsRecPktBadAuthenticators         Counter32,
   gs2328fRADIUSAccountingStatisticsRecPktUnknownTypes              Counter32,
   gs2328fRADIUSAccountingStatisticsRecPktDropped                   Counter32,
   gs2328fRADIUSAccountingStatisticsTransmitPktRequests             Counter32,
   gs2328fRADIUSAccountingStatisticsTransmitPktRetransmissions      Counter32,
   gs2328fRADIUSAccountingStatisticsTransmitPktPendingRequests      Counter32,
   gs2328fRADIUSAccountingStatisticsTransmitPktTimeouts             Counter32,
   gs2328fRADIUSAccountingIP                                        DisplayString,
   gs2328fRADIUSAccountingState                                     DisplayString,
   gs2328fRADIUSAccountingRoundTripTime                             DisplayString,
   gs2328fRADIUSStatisticsClear                                     INTEGER
}

gs2328fRADIUSAuthStatisticsServerIndex OBJECT-TYPE
   SYNTAX      Integer32(1..5)
   MAX-ACCESS  not-accessible
   STATUS      current
   DESCRIPTION
       "RADIUS Authentication Server index
        range : 1-5."
   ::= { gs2328fRADIUSStatisticsEntry 1 }

gs2328fRADIUSAuthStatisticsRecPktAccessAccepts OBJECT-TYPE
   SYNTAX      Counter32
   MAX-ACCESS  read-only
   STATUS      current
   DESCRIPTION
       "The number of RADIUS Access-Accept packets (valid or invalid) received from the server."
   ::= { gs2328fRADIUSStatisticsEntry 2 }

gs2328fRADIUSAuthStatisticsRecPktAccessRejects OBJECT-TYPE
   SYNTAX      Counter32
   MAX-ACCESS  read-only
   STATUS      current
   DESCRIPTION
       "The number of RADIUS Access-Reject packets (valid or invalid) received from the server."
   ::= { gs2328fRADIUSStatisticsEntry 3 }

gs2328fRADIUSAuthStatisticsRecPktAccessChallenges OBJECT-TYPE
   SYNTAX      Counter32
   MAX-ACCESS  read-only
   STATUS      current
   DESCRIPTION
       "The number of RADIUS Access-Challenge packets (valid or invalid) received from the server. "
   ::= { gs2328fRADIUSStatisticsEntry 4 }

gs2328fRADIUSAuthStatisticsRecPktMalformedAccResponses OBJECT-TYPE
   SYNTAX      Counter32
   MAX-ACCESS  read-only
   STATUS      current
   DESCRIPTION
       "The number of malformed RADIUS Access-Response packets received from the
        server. Malformed packets include packets with an invalid length. Bad
        authenticators or Message Authenticator attributes or unknown types are
        not included as malformed access responses. "
   ::= { gs2328fRADIUSStatisticsEntry 5 }

gs2328fRADIUSAuthStatisticsRecPktBadAuthenticators OBJECT-TYPE
   SYNTAX      Counter32
   MAX-ACCESS  read-only
   STATUS      current
   DESCRIPTION
       "The number of RADIUS Access-Response packets containing invalid
       authenticators or Message Authenticator attributes received from the server."
   ::= { gs2328fRADIUSStatisticsEntry 6 }

gs2328fRADIUSAuthStatisticsRecPktUnknownTypes OBJECT-TYPE
   SYNTAX      Counter32
   MAX-ACCESS  read-only
   STATUS      current
   DESCRIPTION
       "The number of RADIUS packets that were received with unknown types from
       the server on the authentication port and dropped."
   ::= { gs2328fRADIUSStatisticsEntry 7 }

gs2328fRADIUSAuthStatisticsRecPktDropped OBJECT-TYPE
   SYNTAX      Counter32
   MAX-ACCESS  read-only
   STATUS      current
   DESCRIPTION
       "The number of RADIUS packets that were received from the server on the
       authentication port and dropped for some other reason."
   ::= { gs2328fRADIUSStatisticsEntry 8 }

gs2328fRADIUSAuthStatisticsTransmitPktAccessRequests OBJECT-TYPE
   SYNTAX      Counter32
   MAX-ACCESS  read-only
   STATUS      current
   DESCRIPTION
       "The number of RADIUS Access-Request packets sent to the server. This
       does not include retransmissions."
   ::= { gs2328fRADIUSStatisticsEntry 9 }

gs2328fRADIUSAuthStatisticsTransmitPktAccessRetransmissions OBJECT-TYPE
   SYNTAX      Counter32
   MAX-ACCESS  read-only
   STATUS      current
   DESCRIPTION
       "The number of RADIUS Access-Request packets retransmitted to the RADIUS
       authentication server."
   ::= { gs2328fRADIUSStatisticsEntry 10 }

gs2328fRADIUSAuthStatisticsTransmitPktPendingRequests OBJECT-TYPE
   SYNTAX      Counter32
   MAX-ACCESS  read-only
   STATUS      current
   DESCRIPTION
       "The number of RADIUS Access-Request packets destined for the server that
        have not yet timed out or received a response. This variable is
        incremented when an Access-Request is sent and decremented due to
        receipt of an Access-Accept, Access-Reject, Access-Challenge, timeout,
        or retransmission. "
   ::= { gs2328fRADIUSStatisticsEntry 11 }

gs2328fRADIUSAuthStatisticsTransmitPktTimeouts OBJECT-TYPE
   SYNTAX      Counter32
   MAX-ACCESS  read-only
   STATUS      current
   DESCRIPTION
       "The number of authentication timeouts to the server. After a timeout,
       the client may retry to the same server, send to a different server, or
       give up. A retry to the same server is counted as a retransmit as well as
        a timeout. A send to a different server is counted as a Request as well
        as a timeout. "
   ::= { gs2328fRADIUSStatisticsEntry 12 }

gs2328fRADIUSAuthIP OBJECT-TYPE
   SYNTAX      DisplayString
   MAX-ACCESS  read-only
   STATUS      current
   DESCRIPTION
       "IP address and UDP port for the authentication server in question."
   ::= { gs2328fRADIUSStatisticsEntry 13 }

gs2328fRADIUSAuthState OBJECT-TYPE
   SYNTAX      DisplayString
   MAX-ACCESS  read-only
   STATUS      current
   DESCRIPTION
       "Shows the state of the server. It takes one of the following values:
        Disabled: The selected server is disabled.
        Not Ready: The server is enabled, but IP communication is not yet up and running.
        Ready: The server is enabled, IP communication is up and running, and the RADIUS
         module is ready to accept access attempts.
        Dead (X seconds left): Access attempts were made to this server, but it did not
        reply within the configured timeout. The server has temporarily been disabled,
        but will get re-enabled when the dead-time expires. The number of seconds left
        before this occurs is displayed in parentheses. This state is only reachable
        when more than one server is enabled. "
   ::= { gs2328fRADIUSStatisticsEntry 14 }

gs2328fRADIUSAuthRoundTripTime OBJECT-TYPE
   SYNTAX      DisplayString
   MAX-ACCESS  read-only
   STATUS      current
   DESCRIPTION
       "The time interval (measured in milliseconds) between the most recent
       Access-Reply/Access-Challenge and the Access-Request that matched it from
        the RADIUS authentication server. The granularity of this measurement is
         100 ms. A value of 0 ms indicates that there hasn't been round-trip
         communication with the server yet. "
   ::= { gs2328fRADIUSStatisticsEntry 15 }

gs2328fRADIUSAccountingStatisticsRecPktResponses OBJECT-TYPE
   SYNTAX      Counter32
   MAX-ACCESS  read-only
   STATUS      current
   DESCRIPTION
       "The number of RADIUS packets (valid or invalid) received from the server."
   ::= { gs2328fRADIUSStatisticsEntry 16 }

gs2328fRADIUSAccountingStatisticsRecPktMalformedResponses OBJECT-TYPE
   SYNTAX      Counter32
   MAX-ACCESS  read-only
   STATUS      current
   DESCRIPTION
       "The number of malformed RADIUS packets received from the server.
       Malformed packets include packets with an invalid length. Bad
       authenticators or unknown types are not included as malformed access
       responses. "
   ::= { gs2328fRADIUSStatisticsEntry 17 }

gs2328fRADIUSAccountingStatisticsRecPktBadAuthenticators OBJECT-TYPE
   SYNTAX      Counter32
   MAX-ACCESS  read-only
   STATUS      current
   DESCRIPTION
       "The number of RADIUS packets containing invalid authenticators received
       from the server."
   ::= { gs2328fRADIUSStatisticsEntry 18 }

gs2328fRADIUSAccountingStatisticsRecPktUnknownTypes OBJECT-TYPE
   SYNTAX      Counter32
   MAX-ACCESS  read-only
   STATUS      current
   DESCRIPTION
       "The number of RADIUS packets of unknown types that were received from
       the server on the accounting port."
   ::= { gs2328fRADIUSStatisticsEntry 19 }

gs2328fRADIUSAccountingStatisticsRecPktDropped OBJECT-TYPE
   SYNTAX      Counter32
   MAX-ACCESS  read-only
   STATUS      current
   DESCRIPTION
       "The number of RADIUS packets that were received from the server on the
       accounting port and dropped for some other reason."
   ::= { gs2328fRADIUSStatisticsEntry 20 }

gs2328fRADIUSAccountingStatisticsTransmitPktRequests OBJECT-TYPE
   SYNTAX      Counter32
   MAX-ACCESS  read-only
   STATUS      current
   DESCRIPTION
       "The number of RADIUS packets sent to the server. This does not include
       retransmissions."
   ::= { gs2328fRADIUSStatisticsEntry 21 }

gs2328fRADIUSAccountingStatisticsTransmitPktRetransmissions OBJECT-TYPE
   SYNTAX      Counter32
   MAX-ACCESS  read-only
   STATUS      current
   DESCRIPTION
       "The number of RADIUS packets retransmitted to the RADIUS accounting server."
   ::= { gs2328fRADIUSStatisticsEntry 22 }

gs2328fRADIUSAccountingStatisticsTransmitPktPendingRequests OBJECT-TYPE
   SYNTAX      Counter32
   MAX-ACCESS  read-only
   STATUS      current
   DESCRIPTION
       "The number of RADIUS packets destined for the server that have not yet
       timed out or received a response. This variable is incremented when a
       Request is sent and decremented due to receipt of a Response, timeout,
       or retransmission. "
   ::= { gs2328fRADIUSStatisticsEntry 23 }

gs2328fRADIUSAccountingStatisticsTransmitPktTimeouts OBJECT-TYPE
   SYNTAX      Counter32
   MAX-ACCESS  read-only
   STATUS      current
   DESCRIPTION
       "The number of accounting timeouts to the server. After a timeout, the
       client may retry to the same server, send to a different server, or give
       up. A retry to the same server is counted as a retransmit as well as a
       timeout. A send to a different server is counted as a Request as well as
       a timeout. "
   ::= { gs2328fRADIUSStatisticsEntry 24 }

gs2328fRADIUSAccountingIP OBJECT-TYPE
   SYNTAX      DisplayString
   MAX-ACCESS  read-only
   STATUS      current
   DESCRIPTION
       "IP address and UDP port for the accounting server in question."
   ::= { gs2328fRADIUSStatisticsEntry 25 }

gs2328fRADIUSAccountingState OBJECT-TYPE
   SYNTAX      DisplayString
   MAX-ACCESS  read-only
   STATUS      current
   DESCRIPTION
       " Shows the state of the server. It takes one of the following values:
        Disabled: The selected server is disabled.
        Not Ready: The server is enabled, but IP communication is not yet up and running.
        Ready: The server is enabled, IP communication is up and running, and the RADIUS
        module is ready to accept accounting attempts.
        Dead (X seconds left): Accounting attempts were made to this server, but it did
        not reply within the configured timeout. The server has temporarily been
        disabled, but will get re-enabled when the dead-time expires. The number of
        seconds left before this occurs is displayed in parentheses. This state is only
        reachable when more than one server is enabled.  "
   ::= { gs2328fRADIUSStatisticsEntry 26 }

gs2328fRADIUSAccountingRoundTripTime OBJECT-TYPE
   SYNTAX      DisplayString
   MAX-ACCESS  read-only
   STATUS      current
   DESCRIPTION
       "The time interval (measured in milliseconds) between the most recent
       Response and the Request that matched it from the RADIUS accounting
       server. The granularity of this measurement is 100 ms. A value of 0 ms
       indicates that there hasn't been round-trip communication with the server
       yet. "
   ::= { gs2328fRADIUSStatisticsEntry 27 }

gs2328fRADIUSStatisticsClear OBJECT-TYPE
   SYNTAX      INTEGER(0|1)
   MAX-ACCESS  read-write
   STATUS      current
   DESCRIPTION
       "Clears the counters for the server.
       read: always 0
       clear: set 1"
   ::= { gs2328fRADIUSStatisticsEntry 28 }

gs2328fNAS                                              OBJECT IDENTIFIER ::= { gs2328fSecurity 11 }

gs2328fNASConfiguration                                 OBJECT IDENTIFIER ::= { gs2328fNAS 1 }

gs2328fNASConfigMode OBJECT-TYPE
   SYNTAX      INTEGER { disable(0), enable(1) }
   MAX-ACCESS  read-write
   STATUS      current
   DESCRIPTION
       "Indicates if NAS is globally enabled or disabled on the switch.
	    If globally disabled, all ports are allowed forwarding of frames."
   ::= { gs2328fNASConfiguration 1 }

gs2328fNASConfigReauthEnabled OBJECT-TYPE
   SYNTAX      INTEGER { disable(0), enable(1) }
   MAX-ACCESS  read-write
   STATUS      current
   DESCRIPTION
       "If checked, successfully authenticated supplicants/clients are
	    reauthenticated after the interval specified by the Reauthentication
		Period. Reauthentication for 802.1X-enabled ports can be used to
		detect if a new device is plugged into a switch port or if a
		supplicant is no longer attached.
		For MAC-based ports, reauthentication is only useful if the RADIUS
		server configuration has changed. It does not involve communication
		between the switch and the client, and therefore doesn't imply that
		a client is still present on a port."
   ::= { gs2328fNASConfiguration 2 }

gs2328fNASConfigReauthPeriod OBJECT-TYPE
   SYNTAX      Integer32(1..3600)
   MAX-ACCESS  read-write
   STATUS      current
   DESCRIPTION
       "Determines the period, in seconds, after which a connected client must
	    be reauthenticated. This is only active if the Reauthentication Enabled
		checkbox is checked.
		range: 1 - 3600 seconds."
   ::= { gs2328fNASConfiguration 3 }

gs2328fNASConfigEAPOLTimeout OBJECT-TYPE
   SYNTAX      Integer32(1..65535)
   MAX-ACCESS  read-write
   STATUS      current
   DESCRIPTION
       "Determines the time for retransmission of Request Identity EAPOL frames.
	    This has no effect for MAC-based ports.
		range: 1 - 65535 seconds."
   ::= { gs2328fNASConfiguration 4 }

gs2328fNASConfigAgingPeriod OBJECT-TYPE
   SYNTAX      Integer32(10..1000000)
   MAX-ACCESS  read-write
   STATUS      current
   DESCRIPTION
       "When the NAS module uses the Port Security module to secure MAC addresses,
	    the Port Security module needs to check for activity on the MAC address
		in question at regular intervals and free resources if no activity
		is seen within a given period of time.
		Admin State supported : Single, Multi and MAC-Based Auth. 802.1X.
		range: 10 - 1000000 seconds."
   ::= { gs2328fNASConfiguration 5 }

gs2328fNASConfigHoldTime OBJECT-TYPE
   SYNTAX      Integer32(10..1000000)
   MAX-ACCESS  read-write
   STATUS      current
   DESCRIPTION
       "If a client is denied access - either because the RADIUS server denies
	    the client access or because the RADIUS server request times out
		- the client is put on hold in the Unauthorized state. The hold timer
		does not count during an on-going authentication. In MAC-based Auth.
		mode, the switch will ignore new frames coming from the client during
		the hold time.
		Admin State supported : Single, Multi and MAC-Based Auth. 802.1X.
		range: 10 - 1000000 seconds."
   ::= { gs2328fNASConfiguration 6 }

gs2328fNASConfigRADIUSAssignedQoSEnabled OBJECT-TYPE
   SYNTAX      INTEGER { disable(0), enable(1) }
   MAX-ACCESS  read-write
   STATUS      current
   DESCRIPTION
       "RADIUS-assigned QoS provides a means to centrally control the
	    traffic class to which traffic coming from a successfully authenticated
		supplicant is assigned on the switch. The RADIUS server must be configured
		to transmit special RADIUS attributes to take advantage of this feature."
   ::= { gs2328fNASConfiguration 7 }

gs2328fNASConfigRADIUSAssignedVLANEnabled OBJECT-TYPE
   SYNTAX      INTEGER { disable(0), enable(1) }
   MAX-ACCESS  read-write
   STATUS      current
   DESCRIPTION
       "RADIUS-assigned VLAN provides a means to centrally control the VLAN on
	    which a successfully authenticated supplicant is placed on the switch.
	    Incoming traffic will be classified to and switched on the RADIUS-assigned
		VLAN. The RADIUS server must be configured to transmit special RADIUS
		attributes to take advantage of this feature.When enable, the individual
		ports' ditto setting determine whether RADIUS-assigned VLAN is enabled
		on that port. When disable, RADIUS-server assigned VLAN is disabled on
		all ports. "
   ::= { gs2328fNASConfiguration 8 }

gs2328fNASConfigGuestVLANEnabled OBJECT-TYPE
   SYNTAX      INTEGER { disable(0), enable(1) }
   MAX-ACCESS  read-write
   STATUS      current
   DESCRIPTION
       "A Guest VLAN is a special VLAN - typically with limited network access -
	   on which 802.1X-unaware clients are placed after a network administrator-defined
	   timeout. The switch follows a set of rules for entering and leaving the Guest
	   VLAN as listed below.When enable, the individual ports' ditto setting determines
	   whether the port can be moved into Guest VLAN. When disable, the ability to
	   move to the Guest VLAN is disabled on all ports. "
   ::= { gs2328fNASConfiguration 9 }

gs2328fNASConfigGuestVLANID OBJECT-TYPE
   SYNTAX      Integer32(1..4094)
   MAX-ACCESS  read-write
   STATUS      current
   DESCRIPTION
       "This is the value that a port's Port VLAN ID is set to if a port is moved into
	   the Guest VLAN. It is only changeable if the Guest VLAN option is globally enabled.
	   range: 1 - 4094."
   ::= { gs2328fNASConfiguration 10 }

gs2328fNASConfigMaxReauthCount OBJECT-TYPE
   SYNTAX      Integer32(1..255)
   MAX-ACCESS  read-write
   STATUS      current
   DESCRIPTION
       "The number of times the switch transmits an EAPOL Request Identity frame without
	   response before considering entering the Guest VLAN is adjusted with this setting.
	   The value can only be changed if the Guest VLAN option is globally enabled.
	   range: 1 - 255."
   ::= { gs2328fNASConfiguration 11 }

gs2328fNASConfigAllowGuestVLANEAPOLSeen OBJECT-TYPE
   SYNTAX      INTEGER { disable(0), enable(1) }
   MAX-ACCESS  read-write
   STATUS      current
   DESCRIPTION
       "The switch remembers if an EAPOL frame has been received on the port for the
	   life-time of the port. Once the switch considers whether to enter the Guest VLAN,
	   it will first check if this option is enabled or disabled. If disabled, the switch
	   will only enter the Guest VLAN if an EAPOL frame has not been received on the port
	   for the life-time of the port. If enabled (checked), the switch will consider
	   entering the Guest VLAN even if an EAPOL frame has been received on the port for
	   the life-time of the port.The value can only be changed if the Guest VLAN option
	   is globally enabled."
   ::= { gs2328fNASConfiguration 12 }

gs2328fNASConfigMacBasedUseEAP OBJECT-TYPE
   SYNTAX      INTEGER { disable(0), enable(1) }
   MAX-ACCESS  read-write
   STATUS      current
   DESCRIPTION
       "The switch can do the RADIUS authentication on behalf of the client in the
       MAC-based Auth. port authentication mode. It can either present itself as a
       normal 802.1X client to the RADIUS Server and use EAP, supporting only the
       MD5-Challenge, or alternativly can use plain RADIUS with username / passwort
       authentification without EAP if this setting is disabled."
   ::= { gs2328fNASConfiguration 101 }

gs2328fNASPortConfigTable OBJECT-TYPE
   SYNTAX      SEQUENCE OF Gs2328fNASPortConfigEntry
   MAX-ACCESS  not-accessible
   STATUS      current
   DESCRIPTION
       ""
   ::= { gs2328fNASConfiguration 13 }

gs2328fNASPortConfigEntry OBJECT-TYPE
   SYNTAX      Gs2328fNASPortConfigEntry
   MAX-ACCESS  not-accessible
   STATUS      current
   DESCRIPTION
       ""
   INDEX    { gs2328fNASPortConfigPort }
   ::= { gs2328fNASPortConfigTable 1 }

Gs2328fNASPortConfigEntry ::= SEQUENCE {
   gs2328fNASPortConfigPort                       Integer32,
   gs2328fNASPortConfigAdminState                 INTEGER,
   gs2328fNASPortConfigRADIUSAssignedQoSEnabled	  INTEGER,
   gs2328fNASPortConfigRADIUSAssignedVLANEnabled  INTEGER,
   gs2328fNASPortConfigGuestVLANEnabled           INTEGER,
   gs2328fNASPortConfigFallbackEnabled            INTEGER,
   gs2328fNASPortConfigPortState                  DisplayString,
   gs2328fNASPortConfigReauthenticate             INTEGER,
   gs2328fNASPortConfigReinitialize               INTEGER
}

gs2328fNASPortConfigPort OBJECT-TYPE
   SYNTAX      Integer32(1..255)
   MAX-ACCESS  not-accessible
   STATUS      current
   DESCRIPTION
       " port, range : 1 - port number. "
   ::= { gs2328fNASPortConfigEntry 1 }

gs2328fNASPortConfigAdminState OBJECT-TYPE
   SYNTAX      INTEGER{ forceAuthorized(1),
						forceUnauthorized(2),
						portBased(3),
						single(4),
						multi(5),
						macBased(6),
						macBasedSingle(7)
					  }
   MAX-ACCESS  read-write
   STATUS      current
   DESCRIPTION
       "This selection controls the port's authentication mode.
		1: Force Authorized,
		2: Force Unauthorized,
		3: Port-based 802.1X,
		4: Single 802.1X,
		5: Multi 802.1X,
		6: MAC-based Auth,
		7: MAC-based Single Auth."
   ::= { gs2328fNASPortConfigEntry 2 }

gs2328fNASPortConfigRADIUSAssignedQoSEnabled OBJECT-TYPE
   SYNTAX      INTEGER { disable(0), enable(1) }
   MAX-ACCESS  read-write
   STATUS      current
   DESCRIPTION
       "When RADIUS-Assigned QoS is both globally enabled and enabled (checked)
	    on a given port, the switch reacts to QoS Class information carried in
		the RADIUS Access-Accept packet transmitted by the RADIUS server when a
		supplicant is successfully authenticated. If present and valid, traffic
		received on the supplicant's port will be classified to the given QoS Class.
		Admin State supported : Port-based and Single 802.1X and MAC-based Single Auth."
   ::= { gs2328fNASPortConfigEntry 3 }

gs2328fNASPortConfigRADIUSAssignedVLANEnabled OBJECT-TYPE
   SYNTAX      INTEGER { disable(0), enable(1) }
   MAX-ACCESS  read-write
   STATUS      current
   DESCRIPTION
       "When RADIUS-Assigned VLAN is both globally enabled and enabled (checked)
	   for a given port, the switch reacts to VLAN ID information carried in the
	   RADIUS Access-Accept packet transmitted by the RADIUS server when a supplicant
	   is successfully authenticated. If present and valid, the port's Port VLAN ID
	   will be changed to this VLAN ID, the port will be set to be a member of that
	   VLAN ID, and the port will be forced into VLAN unaware mode. Once assigned,
	   all traffic arriving on the port will be classified and switched on the
	   RADIUS-assigned VLAN ID.
	   Admin State supported : Port-based and Single 802.1X and MAC-based Single Auth."
   ::= { gs2328fNASPortConfigEntry 4 }

gs2328fNASPortConfigGuestVLANEnabled OBJECT-TYPE
   SYNTAX      INTEGER { disable(0), enable(1) }
   MAX-ACCESS  read-write
   STATUS      current
   DESCRIPTION
       "When Guest VLAN is both globally enabled and enabled (checked) for a given port,
	   the switch considers moving the port into the Guest VLAN according to the rules
	   outlined below.
	   Admin State supported : Port-based , Single and Multi 802.1X."
   ::= { gs2328fNASPortConfigEntry 5 }

gs2328fNASPortConfigPortState OBJECT-TYPE
   SYNTAX      DisplayString
   MAX-ACCESS  read-only
   STATUS      current
   DESCRIPTION
       "Globally Disabled: NAS is globally disabled.
		Link Down: NAS is globally enabled, but there is no link on the port.
		Authorized: The port is in Force Authorized or a single-supplicant mode
		and the supplicant is authorized.
		Unauthorized: The port is in Force Unauthorized or a single-supplicant
		mode and the supplicant is not successfully authorized by the RADIUS server.
		X Auth/Y Unauth: The port is in a multi-supplicant mode. Currently X clients
		are authorized and Y are unauthorized."
   ::= { gs2328fNASPortConfigEntry 6 }

gs2328fNASPortConfigReauthenticate OBJECT-TYPE
   SYNTAX      INTEGER { doNothing(0), do(1) }
   MAX-ACCESS  read-write
   STATUS      current
   DESCRIPTION
       "Schedules a reauthentication whenever the quiet-period of the port runs out
	   (EAPOL-based authentication). For MAC-based authentication, reauthentication
	   will be attempted immediately.The button only has effect for successfully
	   authenticated clients on the port and will not cause the clients to get
	   temporarily unauthorized."
   ::= { gs2328fNASPortConfigEntry 7 }

gs2328fNASPortConfigReinitialize OBJECT-TYPE
   SYNTAX      INTEGER { doNothing(0), do(1) }
   MAX-ACCESS  read-write
   STATUS      current
   DESCRIPTION
       "Forces a reinitialization of the clients on the port and thereby a reauthentication
	   immediately. The clients will transfer to the unauthorized state while the
	   reauthentication is in progress."
   ::= { gs2328fNASPortConfigEntry 8 }

gs2328fNASPortConfigFallbackEnabled OBJECT-TYPE
   SYNTAX      INTEGER { disable(0), enable(1) }
   MAX-ACCESS  read-write
   STATUS      current
   DESCRIPTION
       "When Fallback is enabled, the switch will take over the supplicants role
       after max reauthentication count is reached and tries to authenticate the
       client on its behalf as described for MAC-based Auth.
       Admin State supported : Single and Multi 802.1X."
   ::= { gs2328fNASPortConfigEntry 101 }

gs2328fNASSwitchStatusTable OBJECT-TYPE
   SYNTAX      SEQUENCE OF Gs2328fNASSwitchStatusEntry
   MAX-ACCESS  not-accessible
   STATUS      current
   DESCRIPTION
       ""
   ::= { gs2328fNAS 2 }

gs2328fNASSwitchStatusEntry OBJECT-TYPE
   SYNTAX      Gs2328fNASSwitchStatusEntry
   MAX-ACCESS  not-accessible
   STATUS      current
   DESCRIPTION
       ""
   INDEX    { gs2328fNASPortConfigPort }
   ::= { gs2328fNASSwitchStatusTable 1 }

Gs2328fNASSwitchStatusEntry ::= SEQUENCE {
   gs2328fNASSwitchStatusAdminState 	DisplayString,
   gs2328fNASSwitchStatusPortState		DisplayString,
   gs2328fNASSwitchStatusLastSource		DisplayString,
   gs2328fNASSwitchStatusLastID			DisplayString,
   gs2328fNASSwitchStatusQoSClass		DisplayString,
   gs2328fNASSwitchStatusPortVlanID		DisplayString
}

gs2328fNASSwitchStatusAdminState OBJECT-TYPE
   SYNTAX      DisplayString
   MAX-ACCESS  read-only
   STATUS      current
   DESCRIPTION
       "The port's current administrative state. Refer to NAS Admin State for a description of possible values."
   ::= { gs2328fNASSwitchStatusEntry 2 }

gs2328fNASSwitchStatusPortState OBJECT-TYPE
   SYNTAX      DisplayString
   MAX-ACCESS  read-only
   STATUS      current
   DESCRIPTION
       "The current state of the port. Refer to NAS Port State for a description of the individual states."
   ::= { gs2328fNASSwitchStatusEntry 3 }

gs2328fNASSwitchStatusLastSource OBJECT-TYPE
   SYNTAX      DisplayString
   MAX-ACCESS  read-only
   STATUS      current
   DESCRIPTION
       "The source MAC address carried in the most recently received EAPOL frame for EAPOL-based authentication,
	   and the most recently received frame from a new client for MAC-based authentication."
   ::= { gs2328fNASSwitchStatusEntry 4 }

gs2328fNASSwitchStatusLastID OBJECT-TYPE
   SYNTAX      DisplayString
   MAX-ACCESS  read-only
   STATUS      current
   DESCRIPTION
       "The user name (supplicant identity) carried in the most recently received Response Identity EAPOL frame
	   for EAPOL-based authentication, and the source MAC address from the most recently received frame from a
	   new client for MAC-based authentication."
   ::= { gs2328fNASSwitchStatusEntry 5 }

gs2328fNASSwitchStatusQoSClass OBJECT-TYPE
   SYNTAX      DisplayString
   MAX-ACCESS  read-only
   STATUS      current
   DESCRIPTION
       "QoS Class assigned to the port by the RADIUS server if enabled."
   ::= { gs2328fNASSwitchStatusEntry 6 }

gs2328fNASSwitchStatusPortVlanID OBJECT-TYPE
   SYNTAX      DisplayString
   MAX-ACCESS  read-only
   STATUS      current
   DESCRIPTION
       "The VLAN ID that NAS has put the port in. The field is blank, if the Port VLAN ID is not overridden by NAS."
   ::= { gs2328fNASSwitchStatusEntry 7 }

gs2328fNASPortStatus                                 OBJECT IDENTIFIER ::= { gs2328fNAS 3 }

gs2328fNASPortStatusCountersTable OBJECT-TYPE
   SYNTAX      SEQUENCE OF Gs2328fNASPortStatusCountersEntry
   MAX-ACCESS  not-accessible
   STATUS      current
   DESCRIPTION
       ""
   ::= { gs2328fNASPortStatus 1 }

gs2328fNASPortStatusCountersEntry OBJECT-TYPE
   SYNTAX      Gs2328fNASPortStatusCountersEntry
   MAX-ACCESS  not-accessible
   STATUS      current
   DESCRIPTION
       ""
   INDEX    { gs2328fNASPortConfigPort }
   ::= { gs2328fNASPortStatusCountersTable 1 }

Gs2328fNASPortStatusCountersEntry ::= SEQUENCE {
   gs2328fNASRxCountersEAPOLTotal  	                  Counter32,
   gs2328fNASRxCountersEAPOLResponseID	              Counter32,
   gs2328fNASRxCountersEAPOLResponses	              Counter32,
   gs2328fNASRxCountersEAPOLStart	                  Counter32,
   gs2328fNASRxCountersEAPOLLogoff                    Counter32,
   gs2328fNASRxCountersEAPOLInvalidType               Counter32,
   gs2328fNASRxCountersEAPOLInvalidLength             Counter32,
   gs2328fNASTxCountersEAPOLTotal                     Counter32,
   gs2328fNASTxCountersEAPOLRequestID                 Counter32,
   gs2328fNASTxCountersEAPOLRequests                  Counter32,
   gs2328fNASRxBackendServerCountersAccessChallenges  Counter32,
   gs2328fNASRxBackendServerCountersOtherRequests     Counter32,
   gs2328fNASRxBackendServerCountersAuthSuccesses     Counter32,
   gs2328fNASRxBackendServerCountersAuthFailures      Counter32,
   gs2328fNASTxBackendServerCountersResponses         Counter32,
   gs2328fNASLastSupplicantInfoMACAddress             DisplayString,
   gs2328fNASLastSupplicantInfoVlanID                 Integer32,
   gs2328fNASLastSupplicantInfoVersion                Integer32,
   gs2328fNASLastSupplicantInfoIdentity               DisplayString,
   gs2328fNASCountersDoClear                          INTEGER
}

gs2328fNASRxCountersEAPOLTotal OBJECT-TYPE
   SYNTAX      Counter32
   MAX-ACCESS  read-only
   STATUS      current
   DESCRIPTION
       "The number of valid EAPOL frames of any type that have been received by the switch."
   ::= { gs2328fNASPortStatusCountersEntry 2 }

gs2328fNASRxCountersEAPOLResponseID OBJECT-TYPE
   SYNTAX      Counter32
   MAX-ACCESS  read-only
   STATUS      current
   DESCRIPTION
       "The number of valid EAPOL Response Identity frames that have been received by the switch."
   ::= { gs2328fNASPortStatusCountersEntry 3 }

gs2328fNASRxCountersEAPOLResponses OBJECT-TYPE
   SYNTAX      Counter32
   MAX-ACCESS  read-only
   STATUS      current
   DESCRIPTION
       "The number of valid EAPOL response frames (other than Response Identity frames)
	   that have been received by the switch."
   ::= { gs2328fNASPortStatusCountersEntry 4 }

gs2328fNASRxCountersEAPOLStart OBJECT-TYPE
   SYNTAX      Counter32
   MAX-ACCESS  read-only
   STATUS      current
   DESCRIPTION
       "The number of EAPOL Start frames that have been received by the switch."
   ::= { gs2328fNASPortStatusCountersEntry 5 }

gs2328fNASRxCountersEAPOLLogoff OBJECT-TYPE
   SYNTAX      Counter32
   MAX-ACCESS  read-only
   STATUS      current
   DESCRIPTION
       "The number of valid EAPOL Logoff frames that have been received by the switch."
   ::= { gs2328fNASPortStatusCountersEntry 6 }

gs2328fNASRxCountersEAPOLInvalidType OBJECT-TYPE
   SYNTAX      Counter32
   MAX-ACCESS  read-only
   STATUS      current
   DESCRIPTION
       "The number of EAPOL frames that have been received by the switch in which
	   the frame type is not recognized."
   ::= { gs2328fNASPortStatusCountersEntry 7 }

gs2328fNASRxCountersEAPOLInvalidLength OBJECT-TYPE
   SYNTAX      Counter32
   MAX-ACCESS  read-only
   STATUS      current
   DESCRIPTION
       "The number of EAPOL frames that have been received by the switch in which the
	   Packet Body Length field is invalid."
   ::= { gs2328fNASPortStatusCountersEntry 8 }

gs2328fNASTxCountersEAPOLTotal OBJECT-TYPE
   SYNTAX      Counter32
   MAX-ACCESS  read-only
   STATUS      current
   DESCRIPTION
       "The number of EAPOL frames of any type that have been transmitted by the switch."
   ::= { gs2328fNASPortStatusCountersEntry 9 }

gs2328fNASTxCountersEAPOLRequestID OBJECT-TYPE
   SYNTAX      Counter32
   MAX-ACCESS  read-only
   STATUS      current
   DESCRIPTION
       "The number of EAPOL Request Identity frames that have been transmitted by the switch."
   ::= { gs2328fNASPortStatusCountersEntry 10 }

gs2328fNASTxCountersEAPOLRequests OBJECT-TYPE
   SYNTAX      Counter32
   MAX-ACCESS  read-only
   STATUS      current
   DESCRIPTION
       "The number of valid EAPOL Request frames (other than Request Identity frames)
	   that have been transmitted by the switch."
   ::= { gs2328fNASPortStatusCountersEntry 11 }

gs2328fNASRxBackendServerCountersAccessChallenges OBJECT-TYPE
   SYNTAX      Counter32
   MAX-ACCESS  read-only
   STATUS      current
   DESCRIPTION
       "802.1X-based: Counts the number of times that the switch receives the first request
	   from the backend server following the first response from the supplicant.
	   MAC-based: Counts all Access Challenges received from the backend server for this
	   port or client."
   ::= { gs2328fNASPortStatusCountersEntry 12 }

gs2328fNASRxBackendServerCountersOtherRequests OBJECT-TYPE
   SYNTAX      Counter32
   MAX-ACCESS  read-only
   STATUS      current
   DESCRIPTION
       "802.1X-based: Counts the number of times that the switch sends an EAP Request
	   packet following the first to the supplicant.
	   MAC-based: Not applicable."
   ::= { gs2328fNASPortStatusCountersEntry 13 }

gs2328fNASRxBackendServerCountersAuthSuccesses OBJECT-TYPE
   SYNTAX      Counter32
   MAX-ACCESS  read-only
   STATUS      current
   DESCRIPTION
       "Counts the number of times that the switch receives a success indication.
	   Indicates that the supplicant/client has successfully authenticated to the
	   backend server."
   ::= { gs2328fNASPortStatusCountersEntry 14 }

gs2328fNASRxBackendServerCountersAuthFailures OBJECT-TYPE
   SYNTAX      Counter32
   MAX-ACCESS  read-only
   STATUS      current
   DESCRIPTION
       "Counts the number of times that the switch receives a failure message.
	   This indicates that the supplicant/client has not authenticated to the
	   backend server. "
   ::= { gs2328fNASPortStatusCountersEntry 15 }

gs2328fNASTxBackendServerCountersResponses OBJECT-TYPE
   SYNTAX      Counter32
   MAX-ACCESS  read-only
   STATUS      current
   DESCRIPTION
       "802.1X-based: Counts the number of times that the switch attempts to
	   send a supplicant's first response packet to the backend server. Indicates
	   the switch attempted communication with the backend server. Possible
	   retransmissions are not counted.
	   MAC-based: Counts all the backend server packets sent from the switch
	   towards the backend server for a given port or client. Possible
	   retransmissions are not counted."
   ::= { gs2328fNASPortStatusCountersEntry 16 }

gs2328fNASLastSupplicantInfoMACAddress OBJECT-TYPE
   SYNTAX      DisplayString
   MAX-ACCESS  read-only
   STATUS      current
   DESCRIPTION
       "The MAC address of the last supplicant/client."
   ::= { gs2328fNASPortStatusCountersEntry 17 }

gs2328fNASLastSupplicantInfoVlanID OBJECT-TYPE
   SYNTAX      Integer32
   MAX-ACCESS  read-only
   STATUS      current
   DESCRIPTION
       "The VLAN ID on which the last frame from the last supplicant/client was received."
   ::= { gs2328fNASPortStatusCountersEntry 18 }

gs2328fNASLastSupplicantInfoVersion OBJECT-TYPE
   SYNTAX      Integer32
   MAX-ACCESS  read-only
   STATUS      current
   DESCRIPTION
       "802.1X-based: The protocol version number carried in the most recently
	   received EAPOL frame.
	   MAC-based: Not applicable."
   ::= { gs2328fNASPortStatusCountersEntry 19 }

gs2328fNASLastSupplicantInfoIdentity OBJECT-TYPE
   SYNTAX      DisplayString
   MAX-ACCESS  read-only
   STATUS      current
   DESCRIPTION
       "802.1X-based: The user name (supplicant identity) carried in the most recently received
	   Response Identity EAPOL frame.
	   MAC-based: Not applicable."
   ::= { gs2328fNASPortStatusCountersEntry 20 }

gs2328fNASCountersDoClear OBJECT-TYPE
   SYNTAX      INTEGER { doNothing(0), do(1) }
   MAX-ACCESS  read-write
   STATUS      current
   DESCRIPTION
       "Clear the counters for the selected port."
   ::= { gs2328fNASPortStatusCountersEntry 21 }

gs2328fNASPortStatusClientsTable OBJECT-TYPE
   SYNTAX      SEQUENCE OF Gs2328fNASPortStatusClientsEntry
   MAX-ACCESS  not-accessible
   STATUS      current
   DESCRIPTION
       ""
   ::= { gs2328fNASPortStatus 2 }

gs2328fNASPortStatusClientsEntry OBJECT-TYPE
   SYNTAX      Gs2328fNASPortStatusClientsEntry
   MAX-ACCESS  not-accessible
   STATUS      current
   DESCRIPTION
       ""
   INDEX    { gs2328fNASPortConfigPort,
		gs2328fNASClientsIndex}
   ::= { gs2328fNASPortStatusClientsTable 1 }

Gs2328fNASPortStatusClientsEntry ::= SEQUENCE {
   gs2328fNASClientsIndex  	                  		    Integer32,
   gs2328fNASClientsIdentity							DisplayString,
   gs2328fNASClientsMACAddress  	                  	DisplayString,
   gs2328fNASClientsVlanID		              			Integer32,
   gs2328fNASClientsState	              				DisplayString,
   gs2328fNASClientsLastAuth	                  		DisplayString,
   gs2328fNASRxClientsEAPOLTotal  	                  	Counter32,
   gs2328fNASRxClientsEAPOLResponseID	              	Counter32,
   gs2328fNASRxClientsEAPOLResponses	              	Counter32,
   gs2328fNASRxClientsEAPOLStart	                  	Counter32,
   gs2328fNASRxClientsEAPOLLogoff                    	Counter32,
   gs2328fNASRxClientsEAPOLInvalidType               	Counter32,
   gs2328fNASRxClientsEAPOLInvalidLength             	Counter32,
   gs2328fNASTxClientsEAPOLTotal                     	Counter32,
   gs2328fNASTxClientsEAPOLRequestID                 	Counter32,
   gs2328fNASTxClientsEAPOLRequests                  	Counter32,
   gs2328fNASRxBackendServerClientsAccessChallenges  	Counter32,
   gs2328fNASRxBackendServerClientsOtherRequests     	Counter32,
   gs2328fNASRxBackendServerClientsAuthSuccesses     	Counter32,
   gs2328fNASRxBackendServerClientsAuthFailures      	Counter32,
   gs2328fNASTxBackendServerClientsResponses         	Counter32
}

gs2328fNASClientsIndex OBJECT-TYPE
   SYNTAX      Integer32(1..255)
   MAX-ACCESS  not-accessible
   STATUS      current
   DESCRIPTION
       "Entry of client table in the port."
   ::= { gs2328fNASPortStatusClientsEntry 1 }

gs2328fNASClientsIdentity OBJECT-TYPE
   SYNTAX      DisplayString
   MAX-ACCESS  read-only
   STATUS      current
   DESCRIPTION
       "Shows the identity of the supplicant, as received in the Response Identity
	   EAPOL frame.This isn't available for MAC-based Auth."
   ::= { gs2328fNASPortStatusClientsEntry 2 }

gs2328fNASClientsMACAddress OBJECT-TYPE
   SYNTAX      DisplayString
   MAX-ACCESS  read-only
   STATUS      current
   DESCRIPTION
       "Multi 802.1X, this column holds the MAC address of the attached supplicant.
	   MAC-based Auth., this column holds the MAC address of the attached client."
   ::= { gs2328fNASPortStatusClientsEntry 3 }

gs2328fNASClientsVlanID OBJECT-TYPE
   SYNTAX      Integer32(1..4095)
   MAX-ACCESS  read-only
   STATUS      current
   DESCRIPTION
       "This column holds the VLAN ID that the corresponding client is currently
	   secured through the Port Security module."
   ::= { gs2328fNASPortStatusClientsEntry 4 }

gs2328fNASClientsState OBJECT-TYPE
   SYNTAX      DisplayString
   MAX-ACCESS  read-only
   STATUS      current
   DESCRIPTION
       "The client can either be authenticated or unauthenticated. In the authenticated
	   state, it is allowed to forward frames on the port, and in the unauthenticated
	   state, it is blocked."
   ::= { gs2328fNASPortStatusClientsEntry 5 }

gs2328fNASClientsLastAuth OBJECT-TYPE
   SYNTAX      DisplayString
   MAX-ACCESS  read-only
   STATUS      current
   DESCRIPTION
       "Shows the date and time of the last authentication of the client."
   ::= { gs2328fNASPortStatusClientsEntry 6 }

gs2328fNASRxClientsEAPOLTotal OBJECT-TYPE
   SYNTAX      Counter32
   MAX-ACCESS  read-only
   STATUS      current
   DESCRIPTION
       "The number of valid EAPOL frames of any type that have been received by the switch."
   ::= { gs2328fNASPortStatusClientsEntry 7 }

gs2328fNASRxClientsEAPOLResponseID OBJECT-TYPE
   SYNTAX      Counter32
   MAX-ACCESS  read-only
   STATUS      current
   DESCRIPTION
       "The number of valid EAPOL Response Identity frames that have been received by the switch."
   ::= { gs2328fNASPortStatusClientsEntry 8 }

gs2328fNASRxClientsEAPOLResponses OBJECT-TYPE
   SYNTAX      Counter32
   MAX-ACCESS  read-only
   STATUS      current
   DESCRIPTION
       "The number of valid EAPOL response frames (other than Response Identity frames)
	   that have been received by the switch."
   ::= { gs2328fNASPortStatusClientsEntry 9 }

gs2328fNASRxClientsEAPOLStart OBJECT-TYPE
   SYNTAX      Counter32
   MAX-ACCESS  read-only
   STATUS      current
   DESCRIPTION
       "The number of EAPOL Start frames that have been received by the switch."
   ::= { gs2328fNASPortStatusClientsEntry 10 }

gs2328fNASRxClientsEAPOLLogoff OBJECT-TYPE
   SYNTAX      Counter32
   MAX-ACCESS  read-only
   STATUS      current
   DESCRIPTION
       "The number of valid EAPOL Logoff frames that have been received by the switch."
   ::= { gs2328fNASPortStatusClientsEntry 11 }

gs2328fNASRxClientsEAPOLInvalidType OBJECT-TYPE
   SYNTAX      Counter32
   MAX-ACCESS  read-only
   STATUS      current
   DESCRIPTION
       "The number of EAPOL frames that have been received by the switch in which
	   the frame type is not recognized."
   ::= { gs2328fNASPortStatusClientsEntry 12 }

gs2328fNASRxClientsEAPOLInvalidLength OBJECT-TYPE
   SYNTAX      Counter32
   MAX-ACCESS  read-only
   STATUS      current
   DESCRIPTION
       "The number of EAPOL frames that have been received by the switch in which the
	   Packet Body Length field is invalid."
   ::= { gs2328fNASPortStatusClientsEntry 13 }

gs2328fNASTxClientsEAPOLTotal OBJECT-TYPE
   SYNTAX      Counter32
   MAX-ACCESS  read-only
   STATUS      current
   DESCRIPTION
       "The number of EAPOL frames of any type that have been transmitted by the switch."
   ::= { gs2328fNASPortStatusClientsEntry 14 }

gs2328fNASTxClientsEAPOLRequestID OBJECT-TYPE
   SYNTAX      Counter32
   MAX-ACCESS  read-only
   STATUS      current
   DESCRIPTION
       "The number of EAPOL Request Identity frames that have been transmitted by the switch."
   ::= { gs2328fNASPortStatusClientsEntry 15 }

gs2328fNASTxClientsEAPOLRequests OBJECT-TYPE
   SYNTAX      Counter32
   MAX-ACCESS  read-only
   STATUS      current
   DESCRIPTION
       "The number of valid EAPOL Request frames (other than Request Identity frames)
	   that have been transmitted by the switch."
   ::= { gs2328fNASPortStatusClientsEntry 16 }

gs2328fNASRxBackendServerClientsAccessChallenges OBJECT-TYPE
   SYNTAX      Counter32
   MAX-ACCESS  read-only
   STATUS      current
   DESCRIPTION
       "802.1X-based: Counts the number of times that the switch receives the first request
	   from the backend server following the first response from the supplicant.
	   MAC-based: Counts all Access Challenges received from the backend server for this
	   port or client."
   ::= { gs2328fNASPortStatusClientsEntry 17 }

gs2328fNASRxBackendServerClientsOtherRequests OBJECT-TYPE
   SYNTAX      Counter32
   MAX-ACCESS  read-only
   STATUS      current
   DESCRIPTION
       "802.1X-based: Counts the number of times that the switch sends an EAP Request
	   packet following the first to the supplicant.
	   MAC-based: Not applicable."
   ::= { gs2328fNASPortStatusClientsEntry 18 }

gs2328fNASRxBackendServerClientsAuthSuccesses OBJECT-TYPE
   SYNTAX      Counter32
   MAX-ACCESS  read-only
   STATUS      current
   DESCRIPTION
       "Counts the number of times that the switch receives a success indication.
	   Indicates that the supplicant/client has successfully authenticated to the
	   backend server."
   ::= { gs2328fNASPortStatusClientsEntry 19 }

gs2328fNASRxBackendServerClientsAuthFailures OBJECT-TYPE
   SYNTAX      Counter32
   MAX-ACCESS  read-only
   STATUS      current
   DESCRIPTION
       "Counts the number of times that the switch receives a failure message.
	   This indicates that the supplicant/client has not authenticated to the
	   backend server. "
   ::= { gs2328fNASPortStatusClientsEntry 20 }

gs2328fNASTxBackendServerClientsResponses OBJECT-TYPE
   SYNTAX      Counter32
   MAX-ACCESS  read-only
   STATUS      current
   DESCRIPTION
       "802.1X-based: Counts the number of times that the switch attempts to
	   send a supplicant's first response packet to the backend server. Indicates
	   the switch attempted communication with the backend server. Possible
	   retransmissions are not counted.
	   MAC-based: Counts all the backend server packets sent from the switch
	   towards the backend server for a given port or client. Possible
	   retransmissions are not counted."
   ::= { gs2328fNASPortStatusClientsEntry 21 }


gs2328fMaintenance                                           OBJECT IDENTIFIER ::= { lancomGS2328F  4 }

gs2328fRestartDevice OBJECT-TYPE
   SYNTAX      INTEGER { disable(0), enable(1) }
   MAX-ACCESS  read-write
   STATUS      current
   DESCRIPTION
       "default: 0
        0:none
        1:yes"
   ::= { gs2328fMaintenance 1 }

gs2328fColdRestartDevice OBJECT-TYPE
   SYNTAX      INTEGER { disable(0), enable(1) }
   MAX-ACCESS  read-write
   STATUS      current
   DESCRIPTION
       "default: 0
        0:none
        1:yes"
   ::= { gs2328fMaintenance 1500 }

gs2328fFirmware                                         OBJECT IDENTIFIER ::= { gs2328fMaintenance 2 }

gs2328fFirmwareIpAddress OBJECT-TYPE
   SYNTAX       IpAddress
   MAX-ACCESS   read-write
   STATUS       current
   DESCRIPTION
        "Get/Set the firmware tftp server."
   ::= { gs2328fFirmware 1 }

gs2328fFirmwareFileName OBJECT-TYPE
   SYNTAX       DisplayString
   MAX-ACCESS   read-write
   STATUS       current
   DESCRIPTION
        "Get/Set the path and filename for firmware upgrading."
   ::= { gs2328fFirmware 2 }

gs2328fDoFirmwareUpgrade OBJECT-TYPE
   SYNTAX       INTEGER { doNothing(0), do(1) }
   MAX-ACCESS   read-write
   STATUS       current
   DESCRIPTION
        "Do firmware upgrade. Get this OID always return zero.
              1 - do firmware upgrade.
              0 - do nothing."
   ::= { gs2328fFirmware 3 }

gs2328fSaveOrRestore                                         OBJECT IDENTIFIER ::= { gs2328fMaintenance 3 }

gs2328fFactoryDefaults OBJECT-TYPE
   SYNTAX      INTEGER { none(0), yes(1) }
   MAX-ACCESS  read-write
   STATUS      current
   DESCRIPTION
       "default: 0
        0:none
        1:yes"
   ::= { gs2328fSaveOrRestore 1 }

gs2328fSaveStart OBJECT-TYPE
   SYNTAX      INTEGER { none(0), yes(1) }
   MAX-ACCESS  read-write
   STATUS      current
   DESCRIPTION
       "default: 0
        0:none
        1:yes"
   ::= { gs2328fSaveOrRestore 2 }

gs2328fSaveUser OBJECT-TYPE
   SYNTAX      INTEGER { none(0), yes(1) }
   MAX-ACCESS  read-write
   STATUS      current
   DESCRIPTION
       "default: 0
        0:none
        1:yes"
   ::= { gs2328fSaveOrRestore 3 }

gs2328fRestoreUser OBJECT-TYPE
   SYNTAX      INTEGER { none(0), yes(1) }
   MAX-ACCESS  read-write
   STATUS      current
   DESCRIPTION
       "default: 0
        0:none
        1:yes"
   ::= { gs2328fSaveOrRestore 4 }


gs2328fExportOrImport                                        OBJECT IDENTIFIER ::= { gs2328fMaintenance 4 }

gs2328fExportIpAddress OBJECT-TYPE
   SYNTAX       IpAddress
   MAX-ACCESS   read-write
   STATUS       current
   DESCRIPTION
        "Get/Set the export tftp server."
   ::= { gs2328fExportOrImport 1 }

gs2328fExportConfigName OBJECT-TYPE
   SYNTAX       DisplayString
   MAX-ACCESS   read-write
   STATUS       current
   DESCRIPTION
       "Get/Set the export file path and name."
   ::= { gs2328fExportOrImport 2 }

gs2328fDoExportConfig OBJECT-TYPE
   SYNTAX       INTEGER{ doNothing(0), do(1) }
   MAX-ACCESS   read-write
   STATUS       current
   DESCRIPTION
        "Do export-config.
         Get this OID always return zero.
         1 - export."
   ::= { gs2328fExportOrImport 3 }

gs2328fImportIpAddress OBJECT-TYPE
   SYNTAX       IpAddress
   MAX-ACCESS   read-write
   STATUS       current
   DESCRIPTION
        "Get/Set the import tftp server."
   ::= { gs2328fExportOrImport 4 }

gs2328fImportConfigName OBJECT-TYPE
   SYNTAX      DisplayString
   MAX-ACCESS  read-write
   STATUS      current
   DESCRIPTION
       "Get/Set the import file path and name."
   ::= { gs2328fExportOrImport 5 }

gs2328fDoImportConfig OBJECT-TYPE
   SYNTAX       INTEGER{ doNothing(0), do(1) }
   MAX-ACCESS   read-write
   STATUS       current
   DESCRIPTION
        "Do export-config.
         Get this OID always return zero.
         1 - import."
   ::= { gs2328fExportOrImport 6 }

gs2328fDiagnostics                                           OBJECT IDENTIFIER ::= { gs2328fMaintenance 5 }

gs2328fPingIpAddress OBJECT-TYPE
   SYNTAX      IpAddress
   MAX-ACCESS  read-write
   STATUS      current
   DESCRIPTION
       " The destination IP Address. "
   ::= { gs2328fDiagnostics 1 }

gs2328fPingSize OBJECT-TYPE
   SYNTAX      Integer32(60..1400)
   MAX-ACCESS  read-write
   STATUS      current
   DESCRIPTION
       " Size of ICMP echo packet.
         range : 60-1400, default : 64. "
   ::= { gs2328fDiagnostics 2 }

gs2328fDoPingConfig OBJECT-TYPE
   SYNTAX       INTEGER{ doNothing(0), do(1) }
   MAX-ACCESS  read-write
   STATUS      current
   DESCRIPTION
       "Do ping-config.
         Get this OID always return zero.
         1 - ping. Uses the ICMP protocol's mandatory ECHO_REQUEST datagram
         to elicit an ICMP ECHO_RESPONSE from a host or gateway. "
   ::= { gs2328fDiagnostics 3 }

gs2328fPingResult OBJECT-TYPE
   SYNTAX      DisplayString
   MAX-ACCESS  read-only
   STATUS      current
   DESCRIPTION
       " Show ping result. "
   ::= { gs2328fDiagnostics 4 }

gs2328fPing6IpAddress OBJECT-TYPE
   SYNTAX      DisplayString
   MAX-ACCESS  read-write
   STATUS      current
   DESCRIPTION
       " The destination IPv6 Address. "
   ::= { gs2328fDiagnostics 5 }

gs2328fPing6Size OBJECT-TYPE
   SYNTAX      Integer32(60..1400)
   MAX-ACCESS  read-write
   STATUS      current
   DESCRIPTION
       " Size of ICMP echo packet.
         range : 60-1400. "
   ::= { gs2328fDiagnostics 6 }

gs2328fDoPing6Config OBJECT-TYPE
   SYNTAX       INTEGER{ doNothing(0), do(1) }
   MAX-ACCESS  read-write
   STATUS      current
   DESCRIPTION
       "Do ping-config.
         Get this OID always return zero.
         1 - ping. Uses the ICMP protocol's mandatory ECHO_REQUEST datagram
         to elicit an ICMP ECHO_RESPONSE from a host or gateway. "
   ::= { gs2328fDiagnostics 7 }

gs2328fPing6Result OBJECT-TYPE
   SYNTAX      DisplayString
   MAX-ACCESS  read-only
   STATUS      current
   DESCRIPTION
       " Show ping result. "
   ::= { gs2328fDiagnostics 8 }


------------------------------------------------------------------------------------------------------------------
gs2328fTrap                                                  OBJECT IDENTIFIER ::= { lancomGS2328F  5 }

gs2328fTrapEvent                                             OBJECT IDENTIFIER ::= { gs2328fTrap 1 }

gs2328fEmergency NOTIFICATION-TYPE
  OBJECTS   { gs2328fInformation }
  STATUS        current
    DESCRIPTION
        "The severity level is Emergency. The system is unusable."
    ::= { gs2328fTrapEvent 1 }

gs2328fAlert NOTIFICATION-TYPE
  OBJECTS   { gs2328fInformation }
  STATUS        current
    DESCRIPTION
        "The severity level is Alert. The action must be taken immediately."
    ::= { gs2328fTrapEvent 2 }

gs2328fCritical NOTIFICATION-TYPE
  OBJECTS   { gs2328fInformation }
  STATUS        current
    DESCRIPTION
        "The severity level is Critical. Critical conditions."
    ::= { gs2328fTrapEvent 3 }

gs2328fError NOTIFICATION-TYPE
  OBJECTS   { gs2328fInformation }
  STATUS        current
    DESCRIPTION
        "The severity level is Error. Error conditions."
    ::= { gs2328fTrapEvent 4 }

gs2328fWarning NOTIFICATION-TYPE
  OBJECTS   { gs2328fInformation }
  STATUS        current
    DESCRIPTION
        "The severity level is Warning. Warning conditions."
    ::= { gs2328fTrapEvent 5 }

gs2328fNotice NOTIFICATION-TYPE
  OBJECTS   { gs2328fInformation }
  STATUS        current
    DESCRIPTION
        "The severity level is Notice. Normal but significant condition."
    ::= { gs2328fTrapEvent 6 }

gs2328fInformational NOTIFICATION-TYPE
  OBJECTS   { gs2328fInformation }
  STATUS        current
    DESCRIPTION
        "The severity level is Informational. Informational messages."
    ::= { gs2328fTrapEvent 7 }

gs2328fDebug NOTIFICATION-TYPE
  OBJECTS   { gs2328fInformation }
  STATUS        current
    DESCRIPTION
        "The severity level is Debug. debug-level messages."
    ::= { gs2328fTrapEvent 8 }

gs2328fTrapVariable                                          OBJECT IDENTIFIER ::= { gs2328fTrap 2 }

gs2328fInformation OBJECT-TYPE
    SYNTAX      DisplayString
    MAX-ACCESS  read-only
    STATUS      current
    DESCRIPTION
        "Trap information."
    ::= { gs2328fTrapVariable 1 }


END
